OneAccess-R1645v2-4679-Lan2FGU DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Lan2FGU OBJECT IDENTIFIER ::= {r1645Rootv2 4679}

r1645v2Lan2FGUMOProp OBJECT IDENTIFIER ::= {r1645v2Lan2FGU 1}

r1645v2Lan2FGUMOPropEntry OBJECT IDENTIFIER ::= {r1645v2Lan2FGUMOProp 1}

r1645v2Lan2FGUMOPropPath OBJECT-TYPE
   SYNTAX      ContainmentPath
   MAX-ACCESS  read-only
   STATUS      current
   DESCRIPTION
      "Textual description of the containment tree from the instance of
       the root object down to the instance of the current object."
   ::= {r1645v2Lan2FGUMOPropEntry 3}

r1645v2Lan2FGUMOPropRev OBJECT-TYPE
   SYNTAX      ObjectRevision
   MAX-ACCESS  read-only
   STATUS      current
   DESCRIPTION
      "This value corresponds with the revision of the MANAGED OBJECT."
   ::= {r1645v2Lan2FGUMOPropEntry 4}



er1645v2Lan2FGU OBJECT IDENTIFIER ::= {r1645v2Lan2FGU 11}


er1645v2Lan2FGURemark OBJECT-TYPE
   SYNTAX      DisplayString
   MAX-ACCESS  read-write
   STATUS      current
   DESCRIPTION
      "Path: ethernet2.editConf.remark
       Info: intfRemark"
   ::= {er1645v2Lan2FGU 321}


er1645v2Lan2FGUAdminStatus OBJECT-TYPE
   SYNTAX      INTEGER
               {
               up (1),
               down (2)
               }
   MAX-ACCESS  read-write
   STATUS      current
   DESCRIPTION
      "Path: ethernet2.editConf.adminStatus
       Info: ifAdminStatus

       Possibilities:
               up   (1)
               down   (2)"
   ::= {er1645v2Lan2FGU 106}


er1645v2Lan2FGUBw OBJECT IDENTIFIER ::= {er1645v2Lan2FGU 5}

er1645v2Lan2FGUBwSSC OBJECT IDENTIFIER ::= {er1645v2Lan2FGUBw 1}

er1645v2Lan2FGUBwEntry OBJECT IDENTIFIER ::= {er1645v2Lan2FGUBwSSC 1}

er1645v2Lan2FGUBwMode OBJECT-TYPE
   SYNTAX      INTEGER
               {
               reshaping (1),
               policing (2),
               policingReshape (3)
               }
   MAX-ACCESS  read-write
   STATUS      current
   DESCRIPTION
      "Path: ethernet2.editConf.bandwidth.mode

       Possibilities:
               reshaping   (1)
               policing   (2)
               policingReshape   (3)"
   ::= {er1645v2Lan2FGUBwEntry 3758096384}

er1645v2Lan2FGUBwCir OBJECT-TYPE
   SYNTAX      Integer32
   MAX-ACCESS  read-write
   STATUS      current
   DESCRIPTION
      "Path: ethernet2.editConf.bandwidth.cir"
   ::= {er1645v2Lan2FGUBwEntry 268435456}

er1645v2Lan2FGUBwEir OBJECT-TYPE
   SYNTAX      Integer32
   MAX-ACCESS  read-write
   STATUS      current
   DESCRIPTION
      "Path: ethernet2.editConf.bandwidth.eir"
   ::= {er1645v2Lan2FGUBwEntry 1879048192}

er1645v2Lan2FGUBwUnit OBJECT-TYPE
   SYNTAX      INTEGER
               {
               bitssec (1),
               percent (2)
               }
   MAX-ACCESS  read-write
   STATUS      current
   DESCRIPTION
      "Path: ethernet2.editConf.bandwidth.unit

       Possibilities:
               bits/sec   (1)
               percent   (2)"
   ::= {er1645v2Lan2FGUBwEntry 1342177280}

er1645v2Lan2FGUBwTc OBJECT-TYPE
   SYNTAX      INTEGER
               {
               auto (0)
               }
   MAX-ACCESS  read-write
   STATUS      current
   DESCRIPTION
      "Path: ethernet2.editConf.bandwidth.tc

       Possibilities:
               auto   (0)"
   ::= {er1645v2Lan2FGUBwEntry 1610612736}

er1645v2Lan2FGUBwTcFactor OBJECT-TYPE
   SYNTAX      INTEGER
               {
               ms (10),
               s100us (1)
               }
   MAX-ACCESS  read-write
   STATUS      current
   DESCRIPTION
      "Path: ethernet2.editConf.bandwidth.tcFactor

       Possibilities:
               ms   (10)
               *100us   (1)"
   ::= {er1645v2Lan2FGUBwEntry 2147483648}

er1645v2Lan2FGUBwCorrType OBJECT-TYPE
   SYNTAX      INTEGER
               {
               noCorrection (0),
               predefined (1),
               manual (2)
               }
   MAX-ACCESS  read-write
   STATUS      current
   DESCRIPTION
      "Path: ethernet2.editConf.bandwidth.correction.type

       Possibilities:
               noCorrection   (0)
               predefined   (1)
               manual   (2)"
   ::= {er1645v2Lan2FGUBwEntry 570425344}

er1645v2Lan2FGUBwCorrPredefEncapsFrameRelay OBJECT-TYPE
   SYNTAX      DisplayString
   MAX-ACCESS  read-write
   STATUS      current
   DESCRIPTION
      "Path: ethernet2.editConf.bandwidth.correction.predefined.encapsulation.frameRelay"
   ::= {er1645v2Lan2FGUBwEntry 608436224}

er1645v2Lan2FGUBwCorrPredefEncapsPpp OBJECT-TYPE
   SYNTAX      DisplayString
   MAX-ACCESS  read-write
   STATUS      current
   DESCRIPTION
      "Path: ethernet2.editConf.bandwidth.correction.predefined.encapsulation.ppp"
   ::= {er1645v2Lan2FGUBwEntry 608698368}

er1645v2Lan2FGUBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.bandwidth.correction.predefined.encapsulation.atm.higherLayer

       Possibilities:
               rfc2684   (0)
               ppp   (1)
               pppOverEthernet   (2)"
   ::= {er1645v2Lan2FGUBwEntry 608993280}

er1645v2Lan2FGUBwCorrPredefEncapsAtmMp OBJECT-TYPE
   SYNTAX      INTEGER
               {
               llcEncapsulation (0),
               vcMultiplexing (1)
               }
   MAX-ACCESS  read-write
   STATUS      current
   DESCRIPTION
      "Path: ethernet2.editConf.bandwidth.correction.predefined.encapsulation.atm.multiProtocol

       Possibilities:
               llcEncapsulation   (0)
               vcMultiplexing   (1)"
   ::= {er1645v2Lan2FGUBwEntry 609026048}

er1645v2Lan2FGUBwCorrPredefEncapsHdlc OBJECT-TYPE
   SYNTAX      DisplayString
   MAX-ACCESS  read-write
   STATUS      current
   DESCRIPTION
      "Path: ethernet2.editConf.bandwidth.correction.predefined.encapsulation.hdlc"
   ::= {er1645v2Lan2FGUBwEntry 609222656}

er1645v2Lan2FGUBwCorrPredefEncapsEfmFs OBJECT-TYPE
   SYNTAX      Integer32
   MAX-ACCESS  read-write
   STATUS      current
   DESCRIPTION
      "Path: ethernet2.editConf.bandwidth.correction.predefined.encapsulation.efm.fragmentSize"
   ::= {er1645v2Lan2FGUBwEntry 609517568}

er1645v2Lan2FGUBwCorrPredefEncapsEfmIb OBJECT-TYPE
   SYNTAX      Integer32
   MAX-ACCESS  read-write
   STATUS      current
   DESCRIPTION
      "Path: ethernet2.editConf.bandwidth.correction.predefined.encapsulation.efm.idleBytes"
   ::= {er1645v2Lan2FGUBwEntry 609550336}

er1645v2Lan2FGUBwCorrPredefMode OBJECT-TYPE
   SYNTAX      INTEGER
               {
               routing (0),
               bridging (1)
               }
   MAX-ACCESS  read-write
   STATUS      current
   DESCRIPTION
      "Path: ethernet2.editConf.bandwidth.correction.predefined.mode

       Possibilities:
               routing   (0)
               bridging   (1)"
   ::= {er1645v2Lan2FGUBwEntry 612368384}

er1645v2Lan2FGUBwCorrManualOverhead OBJECT-TYPE
   SYNTAX      Integer32
   MAX-ACCESS  read-write
   STATUS      current
   DESCRIPTION
      "Path: ethernet2.editConf.bandwidth.correction.manual.overhead"
   ::= {er1645v2Lan2FGUBwEntry 637665280}

er1645v2Lan2FGUBwCorrManualFrameData OBJECT-TYPE
   SYNTAX      Counter32
   MAX-ACCESS  read-write
   STATUS      current
   DESCRIPTION
      "Path: ethernet2.editConf.bandwidth.correction.manual.frameData

       32 bit unsigned wrappable counter."
   ::= {er1645v2Lan2FGUBwEntry 637796352}

er1645v2Lan2FGUBwCorrManualFrameHeader OBJECT-TYPE
   SYNTAX      Counter32
   MAX-ACCESS  read-write
   STATUS      current
   DESCRIPTION
      "Path: ethernet2.editConf.bandwidth.correction.manual.frameHeader

       32 bit unsigned wrappable counter."
   ::= {er1645v2Lan2FGUBwEntry 637927424}

er1645v2Lan2FGUBwMaxFifoQLen OBJECT-TYPE
   SYNTAX      Integer32
   MAX-ACCESS  read-write
   STATUS      current
   DESCRIPTION
      "Path: ethernet2.editConf.bandwidth.maxFifoQLen"
   ::= {er1645v2Lan2FGUBwEntry 805306368}

er1645v2Lan2FGUBwDeFlagCir OBJECT-TYPE
   SYNTAX      INTEGER
               {
               allowed (1),
               notAllowed (2)
               }
   MAX-ACCESS  read-write
   STATUS      current
   DESCRIPTION
      "Path: ethernet2.editConf.bandwidth.deFlag.cir

       Possibilities:
               allowed   (1)
               notAllowed   (2)"
   ::= {er1645v2Lan2FGUBwEntry 3490709504}

er1645v2Lan2FGUBwDeFlagEir OBJECT-TYPE
   SYNTAX      INTEGER
               {
               allowed (1),
               notAllowed (2)
               }
   MAX-ACCESS  read-write
   STATUS      current
   DESCRIPTION
      "Path: ethernet2.editConf.bandwidth.deFlag.eir

       Possibilities:
               allowed   (1)
               notAllowed   (2)"
   ::= {er1645v2Lan2FGUBwEntry 3491758080}

er1645v2Lan2FGUBwDeFlagViolate OBJECT-TYPE
   SYNTAX      INTEGER
               {
               allowed (1),
               notAllowed (2)
               }
   MAX-ACCESS  read-write
   STATUS      current
   DESCRIPTION
      "Path: ethernet2.editConf.bandwidth.deFlag.violate

       Possibilities:
               allowed   (1)
               notAllowed   (2)"
   ::= {er1645v2Lan2FGUBwEntry 3492806656}

er1645v2Lan2FGUBwActCirActNone OBJECT-TYPE
   SYNTAX      OCTET STRING
   MAX-ACCESS  read-write
   STATUS      current
   DESCRIPTION
      "Path: ethernet2.editConf.bandwidth.action.cirAction.none"
   ::= {er1645v2Lan2FGUBwEntry 4062183424}

er1645v2Lan2FGUBwActCirActEthCos1 OBJECT-TYPE
   SYNTAX      INTEGER
               {
               unchanged (256)
               }
   MAX-ACCESS  read-write
   STATUS      current
   DESCRIPTION
      "Path: ethernet2.editConf.bandwidth.action.cirAction.ethernet.cosDepth1

       Possibilities:
               unchanged   (256)"
   ::= {er1645v2Lan2FGUBwEntry 4064346112}

er1645v2Lan2FGUBwActCirActEthDei1 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth1

       Possibilities:
               unchanged   (255)
               clear   (0)
               set   (1)"
   ::= {er1645v2Lan2FGUBwEntry 4065656832}

er1645v2Lan2FGUBwActCirActEthCos2 OBJECT-TYPE
   SYNTAX      INTEGER
               {
               unchanged (256)
               }
   MAX-ACCESS  read-write
   STATUS      current
   DESCRIPTION
      "Path: ethernet2.editConf.bandwidth.action.cirAction.ethernet.cosDepth2

       Possibilities:
               unchanged   (256)"
   ::= {er1645v2Lan2FGUBwEntry 4064411648}

er1645v2Lan2FGUBwActCirActEthDei2 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth2

       Possibilities:
               unchanged   (255)
               clear   (0)
               set   (1)"
   ::= {er1645v2Lan2FGUBwEntry 4065722368}

er1645v2Lan2FGUBwActCirActEthCos3 OBJECT-TYPE
   SYNTAX      INTEGER
               {
               unchanged (256)
               }
   MAX-ACCESS  read-write
   STATUS      current
   DESCRIPTION
      "Path: ethernet2.editConf.bandwidth.action.cirAction.ethernet.cosDepth3

       Possibilities:
               unchanged   (256)"
   ::= {er1645v2Lan2FGUBwEntry 4064477184}

er1645v2Lan2FGUBwActCirActEthDei3 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth3

       Possibilities:
               unchanged   (255)
               clear   (0)
               set   (1)"
   ::= {er1645v2Lan2FGUBwEntry 4065787904}

er1645v2Lan2FGUBwActCirActEthCos4 OBJECT-TYPE
   SYNTAX      INTEGER
               {
               unchanged (256)
               }
   MAX-ACCESS  read-write
   STATUS      current
   DESCRIPTION
      "Path: ethernet2.editConf.bandwidth.action.cirAction.ethernet.cosDepth4

       Possibilities:
               unchanged   (256)"
   ::= {er1645v2Lan2FGUBwEntry 4064542720}

er1645v2Lan2FGUBwActCirActEthDei4 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth4

       Possibilities:
               unchanged   (255)
               clear   (0)
               set   (1)"
   ::= {er1645v2Lan2FGUBwEntry 4065853440}

er1645v2Lan2FGUBwActCirActEthCos5 OBJECT-TYPE
   SYNTAX      INTEGER
               {
               unchanged (256)
               }
   MAX-ACCESS  read-write
   STATUS      current
   DESCRIPTION
      "Path: ethernet2.editConf.bandwidth.action.cirAction.ethernet.cosDepth5

       Possibilities:
               unchanged   (256)"
   ::= {er1645v2Lan2FGUBwEntry 4064608256}

er1645v2Lan2FGUBwActCirActEthDei5 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth5

       Possibilities:
               unchanged   (255)
               clear   (0)
               set   (1)"
   ::= {er1645v2Lan2FGUBwEntry 4065918976}

er1645v2Lan2FGUBwActCirActEthCos6 OBJECT-TYPE
   SYNTAX      INTEGER
               {
               unchanged (256)
               }
   MAX-ACCESS  read-write
   STATUS      current
   DESCRIPTION
      "Path: ethernet2.editConf.bandwidth.action.cirAction.ethernet.cosDepth6

       Possibilities:
               unchanged   (256)"
   ::= {er1645v2Lan2FGUBwEntry 4064673792}

er1645v2Lan2FGUBwActCirActEthDei6 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth6

       Possibilities:
               unchanged   (255)
               clear   (0)
               set   (1)"
   ::= {er1645v2Lan2FGUBwEntry 4065984512}

er1645v2Lan2FGUBwActCirActEthCos7 OBJECT-TYPE
   SYNTAX      INTEGER
               {
               unchanged (256)
               }
   MAX-ACCESS  read-write
   STATUS      current
   DESCRIPTION
      "Path: ethernet2.editConf.bandwidth.action.cirAction.ethernet.cosDepth7

       Possibilities:
               unchanged   (256)"
   ::= {er1645v2Lan2FGUBwEntry 4064739328}

er1645v2Lan2FGUBwActCirActEthDei7 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth7

       Possibilities:
               unchanged   (255)
               clear   (0)
               set   (1)"
   ::= {er1645v2Lan2FGUBwEntry 4066050048}

er1645v2Lan2FGUBwActCirActEthCos8 OBJECT-TYPE
   SYNTAX      INTEGER
               {
               unchanged (256)
               }
   MAX-ACCESS  read-write
   STATUS      current
   DESCRIPTION
      "Path: ethernet2.editConf.bandwidth.action.cirAction.ethernet.cosDepth8

       Possibilities:
               unchanged   (256)"
   ::= {er1645v2Lan2FGUBwEntry 4064804864}

er1645v2Lan2FGUBwActCirActEthDei8 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth8

       Possibilities:
               unchanged   (255)
               clear   (0)
               set   (1)"
   ::= {er1645v2Lan2FGUBwEntry 4066115584}

er1645v2Lan2FGUBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4064870400}

er1645v2Lan2FGUBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4064935936}

er1645v2Lan2FGUBwActCirActEthDrpLev OBJECT-TYPE
   SYNTAX      INTEGER
               {
               unchanged (0)
               }
   MAX-ACCESS  read-write
   STATUS      current
   DESCRIPTION
      "Path: ethernet2.editConf.bandwidth.action.cirAction.ethernet.dropLevel

       Possibilities:
               unchanged   (0)"
   ::= {er1645v2Lan2FGUBwEntry 4065001472}

er1645v2Lan2FGUBwActCirActEthDeFlag OBJECT-TYPE
   SYNTAX      INTEGER
               {
               unchanged (255),
               clear (0),
               set (1)
               }
   MAX-ACCESS  read-write
   STATUS      current
   DESCRIPTION
      "Path: ethernet2.editConf.bandwidth.action.cirAction.ethernet.deFlag

       Possibilities:
               unchanged   (255)
               clear   (0)
               set   (1)"
   ::= {er1645v2Lan2FGUBwEntry 4065198080}

er1645v2Lan2FGUBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4071161856}

er1645v2Lan2FGUBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4071227392}

er1645v2Lan2FGUBwActCirActIpDrpLev OBJECT-TYPE
   SYNTAX      INTEGER
               {
               unchanged (0)
               }
   MAX-ACCESS  read-write
   STATUS      current
   DESCRIPTION
      "Path: ethernet2.editConf.bandwidth.action.cirAction.ip.dropLevel

       Possibilities:
               unchanged   (0)"
   ::= {er1645v2Lan2FGUBwEntry 4071292928}

er1645v2Lan2FGUBwActCirActIpDeFlag OBJECT-TYPE
   SYNTAX      INTEGER
               {
               unchanged (255),
               clear (0),
               set (1)
               }
   MAX-ACCESS  read-write
   STATUS      current
   DESCRIPTION
      "Path: ethernet2.editConf.bandwidth.action.cirAction.ip.deFlag

       Possibilities:
               unchanged   (255)
               clear   (0)
               set   (1)"
   ::= {er1645v2Lan2FGUBwEntry 4071489536}

er1645v2Lan2FGUBwActEirActNone OBJECT-TYPE
   SYNTAX      OCTET STRING
   MAX-ACCESS  read-write
   STATUS      current
   DESCRIPTION
      "Path: ethernet2.editConf.bandwidth.action.eirAction.none"
   ::= {er1645v2Lan2FGUBwEntry 4095737856}

er1645v2Lan2FGUBwActEirActEthCos1 OBJECT-TYPE
   SYNTAX      INTEGER
               {
               unchanged (256)
               }
   MAX-ACCESS  read-write
   STATUS      current
   DESCRIPTION
      "Path: ethernet2.editConf.bandwidth.action.eirAction.ethernet.cosDepth1

       Possibilities:
               unchanged   (256)"
   ::= {er1645v2Lan2FGUBwEntry 4097900544}

er1645v2Lan2FGUBwActEirActEthDei1 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth1

       Possibilities:
               unchanged   (255)
               clear   (0)
               set   (1)"
   ::= {er1645v2Lan2FGUBwEntry 4099211264}

er1645v2Lan2FGUBwActEirActEthCos2 OBJECT-TYPE
   SYNTAX      INTEGER
               {
               unchanged (256)
               }
   MAX-ACCESS  read-write
   STATUS      current
   DESCRIPTION
      "Path: ethernet2.editConf.bandwidth.action.eirAction.ethernet.cosDepth2

       Possibilities:
               unchanged   (256)"
   ::= {er1645v2Lan2FGUBwEntry 4097966080}

er1645v2Lan2FGUBwActEirActEthDei2 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth2

       Possibilities:
               unchanged   (255)
               clear   (0)
               set   (1)"
   ::= {er1645v2Lan2FGUBwEntry 4099276800}

er1645v2Lan2FGUBwActEirActEthCos3 OBJECT-TYPE
   SYNTAX      INTEGER
               {
               unchanged (256)
               }
   MAX-ACCESS  read-write
   STATUS      current
   DESCRIPTION
      "Path: ethernet2.editConf.bandwidth.action.eirAction.ethernet.cosDepth3

       Possibilities:
               unchanged   (256)"
   ::= {er1645v2Lan2FGUBwEntry 4098031616}

er1645v2Lan2FGUBwActEirActEthDei3 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth3

       Possibilities:
               unchanged   (255)
               clear   (0)
               set   (1)"
   ::= {er1645v2Lan2FGUBwEntry 4099342336}

er1645v2Lan2FGUBwActEirActEthCos4 OBJECT-TYPE
   SYNTAX      INTEGER
               {
               unchanged (256)
               }
   MAX-ACCESS  read-write
   STATUS      current
   DESCRIPTION
      "Path: ethernet2.editConf.bandwidth.action.eirAction.ethernet.cosDepth4

       Possibilities:
               unchanged   (256)"
   ::= {er1645v2Lan2FGUBwEntry 4098097152}

er1645v2Lan2FGUBwActEirActEthDei4 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth4

       Possibilities:
               unchanged   (255)
               clear   (0)
               set   (1)"
   ::= {er1645v2Lan2FGUBwEntry 4099407872}

er1645v2Lan2FGUBwActEirActEthCos5 OBJECT-TYPE
   SYNTAX      INTEGER
               {
               unchanged (256)
               }
   MAX-ACCESS  read-write
   STATUS      current
   DESCRIPTION
      "Path: ethernet2.editConf.bandwidth.action.eirAction.ethernet.cosDepth5

       Possibilities:
               unchanged   (256)"
   ::= {er1645v2Lan2FGUBwEntry 4098162688}

er1645v2Lan2FGUBwActEirActEthDei5 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth5

       Possibilities:
               unchanged   (255)
               clear   (0)
               set   (1)"
   ::= {er1645v2Lan2FGUBwEntry 4099473408}

er1645v2Lan2FGUBwActEirActEthCos6 OBJECT-TYPE
   SYNTAX      INTEGER
               {
               unchanged (256)
               }
   MAX-ACCESS  read-write
   STATUS      current
   DESCRIPTION
      "Path: ethernet2.editConf.bandwidth.action.eirAction.ethernet.cosDepth6

       Possibilities:
               unchanged   (256)"
   ::= {er1645v2Lan2FGUBwEntry 4098228224}

er1645v2Lan2FGUBwActEirActEthDei6 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth6

       Possibilities:
               unchanged   (255)
               clear   (0)
               set   (1)"
   ::= {er1645v2Lan2FGUBwEntry 4099538944}

er1645v2Lan2FGUBwActEirActEthCos7 OBJECT-TYPE
   SYNTAX      INTEGER
               {
               unchanged (256)
               }
   MAX-ACCESS  read-write
   STATUS      current
   DESCRIPTION
      "Path: ethernet2.editConf.bandwidth.action.eirAction.ethernet.cosDepth7

       Possibilities:
               unchanged   (256)"
   ::= {er1645v2Lan2FGUBwEntry 4098293760}

er1645v2Lan2FGUBwActEirActEthDei7 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth7

       Possibilities:
               unchanged   (255)
               clear   (0)
               set   (1)"
   ::= {er1645v2Lan2FGUBwEntry 4099604480}

er1645v2Lan2FGUBwActEirActEthCos8 OBJECT-TYPE
   SYNTAX      INTEGER
               {
               unchanged (256)
               }
   MAX-ACCESS  read-write
   STATUS      current
   DESCRIPTION
      "Path: ethernet2.editConf.bandwidth.action.eirAction.ethernet.cosDepth8

       Possibilities:
               unchanged   (256)"
   ::= {er1645v2Lan2FGUBwEntry 4098359296}

er1645v2Lan2FGUBwActEirActEthDei8 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth8

       Possibilities:
               unchanged   (255)
               clear   (0)
               set   (1)"
   ::= {er1645v2Lan2FGUBwEntry 4099670016}

er1645v2Lan2FGUBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4098424832}

er1645v2Lan2FGUBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4098490368}

er1645v2Lan2FGUBwActEirActEthDrpLev OBJECT-TYPE
   SYNTAX      INTEGER
               {
               unchanged (0)
               }
   MAX-ACCESS  read-write
   STATUS      current
   DESCRIPTION
      "Path: ethernet2.editConf.bandwidth.action.eirAction.ethernet.dropLevel

       Possibilities:
               unchanged   (0)"
   ::= {er1645v2Lan2FGUBwEntry 4098555904}

er1645v2Lan2FGUBwActEirActEthDeFlag OBJECT-TYPE
   SYNTAX      INTEGER
               {
               unchanged (255),
               clear (0),
               set (1)
               }
   MAX-ACCESS  read-write
   STATUS      current
   DESCRIPTION
      "Path: ethernet2.editConf.bandwidth.action.eirAction.ethernet.deFlag

       Possibilities:
               unchanged   (255)
               clear   (0)
               set   (1)"
   ::= {er1645v2Lan2FGUBwEntry 4098752512}

er1645v2Lan2FGUBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4104716288}

er1645v2Lan2FGUBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4104781824}

er1645v2Lan2FGUBwActEirActIpDrpLev OBJECT-TYPE
   SYNTAX      INTEGER
               {
               unchanged (0)
               }
   MAX-ACCESS  read-write
   STATUS      current
   DESCRIPTION
      "Path: ethernet2.editConf.bandwidth.action.eirAction.ip.dropLevel

       Possibilities:
               unchanged   (0)"
   ::= {er1645v2Lan2FGUBwEntry 4104847360}

er1645v2Lan2FGUBwActEirActIpDeFlag OBJECT-TYPE
   SYNTAX      INTEGER
               {
               unchanged (255),
               clear (0),
               set (1)
               }
   MAX-ACCESS  read-write
   STATUS      current
   DESCRIPTION
      "Path: ethernet2.editConf.bandwidth.action.eirAction.ip.deFlag

       Possibilities:
               unchanged   (255)
               clear   (0)
               set   (1)"
   ::= {er1645v2Lan2FGUBwEntry 4105043968}

er1645v2Lan2FGUBwActViolActNone OBJECT-TYPE
   SYNTAX      OCTET STRING
   MAX-ACCESS  read-write
   STATUS      current
   DESCRIPTION
      "Path: ethernet2.editConf.bandwidth.action.violateAction.none"
   ::= {er1645v2Lan2FGUBwEntry 4129292288}

er1645v2Lan2FGUBwActViolActDrop OBJECT-TYPE
   SYNTAX      OCTET STRING
   MAX-ACCESS  read-write
   STATUS      current
   DESCRIPTION
      "Path: ethernet2.editConf.bandwidth.action.violateAction.drop"
   ::= {er1645v2Lan2FGUBwEntry 4133486592}

er1645v2Lan2FGUBwActViolActEthCos1 OBJECT-TYPE
   SYNTAX      INTEGER
               {
               unchanged (256)
               }
   MAX-ACCESS  read-write
   STATUS      current
   DESCRIPTION
      "Path: ethernet2.editConf.bandwidth.action.violateAction.ethernet.cosDepth1

       Possibilities:
               unchanged   (256)"
   ::= {er1645v2Lan2FGUBwEntry 4131454976}

er1645v2Lan2FGUBwActViolActEthDei1 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth1

       Possibilities:
               unchanged   (255)
               clear   (0)
               set   (1)"
   ::= {er1645v2Lan2FGUBwEntry 4132765696}

er1645v2Lan2FGUBwActViolActEthCos2 OBJECT-TYPE
   SYNTAX      INTEGER
               {
               unchanged (256)
               }
   MAX-ACCESS  read-write
   STATUS      current
   DESCRIPTION
      "Path: ethernet2.editConf.bandwidth.action.violateAction.ethernet.cosDepth2

       Possibilities:
               unchanged   (256)"
   ::= {er1645v2Lan2FGUBwEntry 4131520512}

er1645v2Lan2FGUBwActViolActEthDei2 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth2

       Possibilities:
               unchanged   (255)
               clear   (0)
               set   (1)"
   ::= {er1645v2Lan2FGUBwEntry 4132831232}

er1645v2Lan2FGUBwActViolActEthCos3 OBJECT-TYPE
   SYNTAX      INTEGER
               {
               unchanged (256)
               }
   MAX-ACCESS  read-write
   STATUS      current
   DESCRIPTION
      "Path: ethernet2.editConf.bandwidth.action.violateAction.ethernet.cosDepth3

       Possibilities:
               unchanged   (256)"
   ::= {er1645v2Lan2FGUBwEntry 4131586048}

er1645v2Lan2FGUBwActViolActEthDei3 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth3

       Possibilities:
               unchanged   (255)
               clear   (0)
               set   (1)"
   ::= {er1645v2Lan2FGUBwEntry 4132896768}

er1645v2Lan2FGUBwActViolActEthCos4 OBJECT-TYPE
   SYNTAX      INTEGER
               {
               unchanged (256)
               }
   MAX-ACCESS  read-write
   STATUS      current
   DESCRIPTION
      "Path: ethernet2.editConf.bandwidth.action.violateAction.ethernet.cosDepth4

       Possibilities:
               unchanged   (256)"
   ::= {er1645v2Lan2FGUBwEntry 4131651584}

er1645v2Lan2FGUBwActViolActEthDei4 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth4

       Possibilities:
               unchanged   (255)
               clear   (0)
               set   (1)"
   ::= {er1645v2Lan2FGUBwEntry 4132962304}

er1645v2Lan2FGUBwActViolActEthCos5 OBJECT-TYPE
   SYNTAX      INTEGER
               {
               unchanged (256)
               }
   MAX-ACCESS  read-write
   STATUS      current
   DESCRIPTION
      "Path: ethernet2.editConf.bandwidth.action.violateAction.ethernet.cosDepth5

       Possibilities:
               unchanged   (256)"
   ::= {er1645v2Lan2FGUBwEntry 4131717120}

er1645v2Lan2FGUBwActViolActEthDei5 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth5

       Possibilities:
               unchanged   (255)
               clear   (0)
               set   (1)"
   ::= {er1645v2Lan2FGUBwEntry 4133027840}

er1645v2Lan2FGUBwActViolActEthCos6 OBJECT-TYPE
   SYNTAX      INTEGER
               {
               unchanged (256)
               }
   MAX-ACCESS  read-write
   STATUS      current
   DESCRIPTION
      "Path: ethernet2.editConf.bandwidth.action.violateAction.ethernet.cosDepth6

       Possibilities:
               unchanged   (256)"
   ::= {er1645v2Lan2FGUBwEntry 4131782656}

er1645v2Lan2FGUBwActViolActEthDei6 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth6

       Possibilities:
               unchanged   (255)
               clear   (0)
               set   (1)"
   ::= {er1645v2Lan2FGUBwEntry 4133093376}

er1645v2Lan2FGUBwActViolActEthCos7 OBJECT-TYPE
   SYNTAX      INTEGER
               {
               unchanged (256)
               }
   MAX-ACCESS  read-write
   STATUS      current
   DESCRIPTION
      "Path: ethernet2.editConf.bandwidth.action.violateAction.ethernet.cosDepth7

       Possibilities:
               unchanged   (256)"
   ::= {er1645v2Lan2FGUBwEntry 4131848192}

er1645v2Lan2FGUBwActViolActEthDei7 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth7

       Possibilities:
               unchanged   (255)
               clear   (0)
               set   (1)"
   ::= {er1645v2Lan2FGUBwEntry 4133158912}

er1645v2Lan2FGUBwActViolActEthCos8 OBJECT-TYPE
   SYNTAX      INTEGER
               {
               unchanged (256)
               }
   MAX-ACCESS  read-write
   STATUS      current
   DESCRIPTION
      "Path: ethernet2.editConf.bandwidth.action.violateAction.ethernet.cosDepth8

       Possibilities:
               unchanged   (256)"
   ::= {er1645v2Lan2FGUBwEntry 4131913728}

er1645v2Lan2FGUBwActViolActEthDei8 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth8

       Possibilities:
               unchanged   (255)
               clear   (0)
               set   (1)"
   ::= {er1645v2Lan2FGUBwEntry 4133224448}

er1645v2Lan2FGUBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4131979264}

er1645v2Lan2FGUBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4132044800}

er1645v2Lan2FGUBwActViolActEthDrpLev OBJECT-TYPE
   SYNTAX      INTEGER
               {
               unchanged (0)
               }
   MAX-ACCESS  read-write
   STATUS      current
   DESCRIPTION
      "Path: ethernet2.editConf.bandwidth.action.violateAction.ethernet.dropLevel

       Possibilities:
               unchanged   (0)"
   ::= {er1645v2Lan2FGUBwEntry 4132110336}

er1645v2Lan2FGUBwActViolActEthDeFlag OBJECT-TYPE
   SYNTAX      INTEGER
               {
               unchanged (255),
               clear (0),
               set (1)
               }
   MAX-ACCESS  read-write
   STATUS      current
   DESCRIPTION
      "Path: ethernet2.editConf.bandwidth.action.violateAction.ethernet.deFlag

       Possibilities:
               unchanged   (255)
               clear   (0)
               set   (1)"
   ::= {er1645v2Lan2FGUBwEntry 4132306944}

er1645v2Lan2FGUBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUBwEntry 4138270720}

er1645v2Lan2FGUBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUBwEntry 4138336256}

er1645v2Lan2FGUBwActViolActIpDrpLev OBJECT-TYPE
   SYNTAX      INTEGER
               {
               unchanged (0)
               }
   MAX-ACCESS  read-write
   STATUS      current
   DESCRIPTION
      "Path: ethernet2.editConf.bandwidth.action.violateAction.ip.dropLevel

       Possibilities:
               unchanged   (0)"
   ::= {er1645v2Lan2FGUBwEntry 4138401792}

er1645v2Lan2FGUBwActViolActIpDeFlag OBJECT-TYPE
   SYNTAX      INTEGER
               {
               unchanged (255),
               clear (0),
               set (1)
               }
   MAX-ACCESS  read-write
   STATUS      current
   DESCRIPTION
      "Path: ethernet2.editConf.bandwidth.action.violateAction.ip.deFlag

       Possibilities:
               unchanged   (255)
               clear   (0)
               set   (1)"
   ::= {er1645v2Lan2FGUBwEntry 4138598400}


er1645v2Lan2FGUIbw OBJECT IDENTIFIER ::= {er1645v2Lan2FGU 13}

er1645v2Lan2FGUIbwSSC OBJECT IDENTIFIER ::= {er1645v2Lan2FGUIbw 1}

er1645v2Lan2FGUIbwEntry OBJECT IDENTIFIER ::= {er1645v2Lan2FGUIbwSSC 1}

er1645v2Lan2FGUIbwMode OBJECT-TYPE
   SYNTAX      INTEGER
               {
               reshaping (1),
               policing (2)
               }
   MAX-ACCESS  read-write
   STATUS      current
   DESCRIPTION
      "Path: ethernet2.editConf.inboundBandwidth.mode

       Possibilities:
               reshaping   (1)
               policing   (2)"
   ::= {er1645v2Lan2FGUIbwEntry 3758096384}

er1645v2Lan2FGUIbwCir OBJECT-TYPE
   SYNTAX      Integer32
   MAX-ACCESS  read-write
   STATUS      current
   DESCRIPTION
      "Path: ethernet2.editConf.inboundBandwidth.cir"
   ::= {er1645v2Lan2FGUIbwEntry 268435456}

er1645v2Lan2FGUIbwEir OBJECT-TYPE
   SYNTAX      Integer32
   MAX-ACCESS  read-write
   STATUS      current
   DESCRIPTION
      "Path: ethernet2.editConf.inboundBandwidth.eir"
   ::= {er1645v2Lan2FGUIbwEntry 1879048192}

er1645v2Lan2FGUIbwUnit OBJECT-TYPE
   SYNTAX      INTEGER
               {
               bitssec (1),
               percent (2)
               }
   MAX-ACCESS  read-write
   STATUS      current
   DESCRIPTION
      "Path: ethernet2.editConf.inboundBandwidth.unit

       Possibilities:
               bits/sec   (1)
               percent   (2)"
   ::= {er1645v2Lan2FGUIbwEntry 1342177280}

er1645v2Lan2FGUIbwTc OBJECT-TYPE
   SYNTAX      INTEGER
               {
               auto (0)
               }
   MAX-ACCESS  read-write
   STATUS      current
   DESCRIPTION
      "Path: ethernet2.editConf.inboundBandwidth.tc

       Possibilities:
               auto   (0)"
   ::= {er1645v2Lan2FGUIbwEntry 1610612736}

er1645v2Lan2FGUIbwTcFactor OBJECT-TYPE
   SYNTAX      INTEGER
               {
               ms (10),
               s100us (1)
               }
   MAX-ACCESS  read-write
   STATUS      current
   DESCRIPTION
      "Path: ethernet2.editConf.inboundBandwidth.tcFactor

       Possibilities:
               ms   (10)
               *100us   (1)"
   ::= {er1645v2Lan2FGUIbwEntry 2147483648}

er1645v2Lan2FGUIbwCorrType OBJECT-TYPE
   SYNTAX      INTEGER
               {
               noCorrection (0),
               predefined (1),
               manual (2)
               }
   MAX-ACCESS  read-write
   STATUS      current
   DESCRIPTION
      "Path: ethernet2.editConf.inboundBandwidth.correction.type

       Possibilities:
               noCorrection   (0)
               predefined   (1)
               manual   (2)"
   ::= {er1645v2Lan2FGUIbwEntry 570425344}

er1645v2Lan2FGUIbwCorrPredefEncapsFrameRelay OBJECT-TYPE
   SYNTAX      DisplayString
   MAX-ACCESS  read-write
   STATUS      current
   DESCRIPTION
      "Path: ethernet2.editConf.inboundBandwidth.correction.predefined.encapsulation.frameRelay"
   ::= {er1645v2Lan2FGUIbwEntry 608436224}

er1645v2Lan2FGUIbwCorrPredefEncapsPpp OBJECT-TYPE
   SYNTAX      DisplayString
   MAX-ACCESS  read-write
   STATUS      current
   DESCRIPTION
      "Path: ethernet2.editConf.inboundBandwidth.correction.predefined.encapsulation.ppp"
   ::= {er1645v2Lan2FGUIbwEntry 608698368}

er1645v2Lan2FGUIbwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.inboundBandwidth.correction.predefined.encapsulation.atm.higherLayer

       Possibilities:
               rfc2684   (0)
               ppp   (1)
               pppOverEthernet   (2)"
   ::= {er1645v2Lan2FGUIbwEntry 608993280}

er1645v2Lan2FGUIbwCorrPredefEncapsAtmMp OBJECT-TYPE
   SYNTAX      INTEGER
               {
               llcEncapsulation (0),
               vcMultiplexing (1)
               }
   MAX-ACCESS  read-write
   STATUS      current
   DESCRIPTION
      "Path: ethernet2.editConf.inboundBandwidth.correction.predefined.encapsulation.atm.multiProtocol

       Possibilities:
               llcEncapsulation   (0)
               vcMultiplexing   (1)"
   ::= {er1645v2Lan2FGUIbwEntry 609026048}

er1645v2Lan2FGUIbwCorrPredefEncapsHdlc OBJECT-TYPE
   SYNTAX      DisplayString
   MAX-ACCESS  read-write
   STATUS      current
   DESCRIPTION
      "Path: ethernet2.editConf.inboundBandwidth.correction.predefined.encapsulation.hdlc"
   ::= {er1645v2Lan2FGUIbwEntry 609222656}

er1645v2Lan2FGUIbwCorrPredefEncapsEfmFs OBJECT-TYPE
   SYNTAX      Integer32
   MAX-ACCESS  read-write
   STATUS      current
   DESCRIPTION
      "Path: ethernet2.editConf.inboundBandwidth.correction.predefined.encapsulation.efm.fragmentSize"
   ::= {er1645v2Lan2FGUIbwEntry 609517568}

er1645v2Lan2FGUIbwCorrPredefEncapsEfmIb OBJECT-TYPE
   SYNTAX      Integer32
   MAX-ACCESS  read-write
   STATUS      current
   DESCRIPTION
      "Path: ethernet2.editConf.inboundBandwidth.correction.predefined.encapsulation.efm.idleBytes"
   ::= {er1645v2Lan2FGUIbwEntry 609550336}

er1645v2Lan2FGUIbwCorrPredefMode OBJECT-TYPE
   SYNTAX      INTEGER
               {
               routing (0),
               bridging (1)
               }
   MAX-ACCESS  read-write
   STATUS      current
   DESCRIPTION
      "Path: ethernet2.editConf.inboundBandwidth.correction.predefined.mode

       Possibilities:
               routing   (0)
               bridging   (1)"
   ::= {er1645v2Lan2FGUIbwEntry 612368384}

er1645v2Lan2FGUIbwCorrManualOverhead OBJECT-TYPE
   SYNTAX      Integer32
   MAX-ACCESS  read-write
   STATUS      current
   DESCRIPTION
      "Path: ethernet2.editConf.inboundBandwidth.correction.manual.overhead"
   ::= {er1645v2Lan2FGUIbwEntry 637665280}

er1645v2Lan2FGUIbwCorrManualFrameData OBJECT-TYPE
   SYNTAX      Counter32
   MAX-ACCESS  read-write
   STATUS      current
   DESCRIPTION
      "Path: ethernet2.editConf.inboundBandwidth.correction.manual.frameData

       32 bit unsigned wrappable counter."
   ::= {er1645v2Lan2FGUIbwEntry 637796352}

er1645v2Lan2FGUIbwCorrManualFrameHeader OBJECT-TYPE
   SYNTAX      Counter32
   MAX-ACCESS  read-write
   STATUS      current
   DESCRIPTION
      "Path: ethernet2.editConf.inboundBandwidth.correction.manual.frameHeader

       32 bit unsigned wrappable counter."
   ::= {er1645v2Lan2FGUIbwEntry 637927424}

er1645v2Lan2FGUIbwMaxFifoQLen OBJECT-TYPE
   SYNTAX      Integer32
   MAX-ACCESS  read-write
   STATUS      current
   DESCRIPTION
      "Path: ethernet2.editConf.inboundBandwidth.maxFifoQLen"
   ::= {er1645v2Lan2FGUIbwEntry 805306368}

er1645v2Lan2FGUIbwPriorityPolicy OBJECT-TYPE
   SYNTAX      DisplayString
   MAX-ACCESS  read-write
   STATUS      current
   DESCRIPTION
      "Path: ethernet2.editConf.inboundBandwidth.priorityPolicy"
   ::= {er1645v2Lan2FGUIbwEntry 1073741824}

er1645v2Lan2FGUIbwDeFlagCir OBJECT-TYPE
   SYNTAX      INTEGER
               {
               allowed (1),
               notAllowed (2)
               }
   MAX-ACCESS  read-write
   STATUS      current
   DESCRIPTION
      "Path: ethernet2.editConf.inboundBandwidth.deFlag.cir

       Possibilities:
               allowed   (1)
               notAllowed   (2)"
   ::= {er1645v2Lan2FGUIbwEntry 3490709504}

er1645v2Lan2FGUIbwDeFlagEir OBJECT-TYPE
   SYNTAX      INTEGER
               {
               allowed (1),
               notAllowed (2)
               }
   MAX-ACCESS  read-write
   STATUS      current
   DESCRIPTION
      "Path: ethernet2.editConf.inboundBandwidth.deFlag.eir

       Possibilities:
               allowed   (1)
               notAllowed   (2)"
   ::= {er1645v2Lan2FGUIbwEntry 3491758080}

er1645v2Lan2FGUIbwDeFlagViolate OBJECT-TYPE
   SYNTAX      INTEGER
               {
               allowed (1),
               notAllowed (2)
               }
   MAX-ACCESS  read-write
   STATUS      current
   DESCRIPTION
      "Path: ethernet2.editConf.inboundBandwidth.deFlag.violate

       Possibilities:
               allowed   (1)
               notAllowed   (2)"
   ::= {er1645v2Lan2FGUIbwEntry 3492806656}

er1645v2Lan2FGUIbwActCirActNone OBJECT-TYPE
   SYNTAX      OCTET STRING
   MAX-ACCESS  read-write
   STATUS      current
   DESCRIPTION
      "Path: ethernet2.editConf.inboundBandwidth.action.cirAction.none"
   ::= {er1645v2Lan2FGUIbwEntry 4062183424}

er1645v2Lan2FGUIbwActCirActEthCos1 OBJECT-TYPE
   SYNTAX      INTEGER
               {
               unchanged (256)
               }
   MAX-ACCESS  read-write
   STATUS      current
   DESCRIPTION
      "Path: ethernet2.editConf.inboundBandwidth.action.cirAction.ethernet.cosDepth1

       Possibilities:
               unchanged   (256)"
   ::= {er1645v2Lan2FGUIbwEntry 4064346112}

er1645v2Lan2FGUIbwActCirActEthDei1 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth1

       Possibilities:
               unchanged   (255)
               clear   (0)
               set   (1)"
   ::= {er1645v2Lan2FGUIbwEntry 4065656832}

er1645v2Lan2FGUIbwActCirActEthCos2 OBJECT-TYPE
   SYNTAX      INTEGER
               {
               unchanged (256)
               }
   MAX-ACCESS  read-write
   STATUS      current
   DESCRIPTION
      "Path: ethernet2.editConf.inboundBandwidth.action.cirAction.ethernet.cosDepth2

       Possibilities:
               unchanged   (256)"
   ::= {er1645v2Lan2FGUIbwEntry 4064411648}

er1645v2Lan2FGUIbwActCirActEthDei2 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth2

       Possibilities:
               unchanged   (255)
               clear   (0)
               set   (1)"
   ::= {er1645v2Lan2FGUIbwEntry 4065722368}

er1645v2Lan2FGUIbwActCirActEthCos3 OBJECT-TYPE
   SYNTAX      INTEGER
               {
               unchanged (256)
               }
   MAX-ACCESS  read-write
   STATUS      current
   DESCRIPTION
      "Path: ethernet2.editConf.inboundBandwidth.action.cirAction.ethernet.cosDepth3

       Possibilities:
               unchanged   (256)"
   ::= {er1645v2Lan2FGUIbwEntry 4064477184}

er1645v2Lan2FGUIbwActCirActEthDei3 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth3

       Possibilities:
               unchanged   (255)
               clear   (0)
               set   (1)"
   ::= {er1645v2Lan2FGUIbwEntry 4065787904}

er1645v2Lan2FGUIbwActCirActEthCos4 OBJECT-TYPE
   SYNTAX      INTEGER
               {
               unchanged (256)
               }
   MAX-ACCESS  read-write
   STATUS      current
   DESCRIPTION
      "Path: ethernet2.editConf.inboundBandwidth.action.cirAction.ethernet.cosDepth4

       Possibilities:
               unchanged   (256)"
   ::= {er1645v2Lan2FGUIbwEntry 4064542720}

er1645v2Lan2FGUIbwActCirActEthDei4 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth4

       Possibilities:
               unchanged   (255)
               clear   (0)
               set   (1)"
   ::= {er1645v2Lan2FGUIbwEntry 4065853440}

er1645v2Lan2FGUIbwActCirActEthCos5 OBJECT-TYPE
   SYNTAX      INTEGER
               {
               unchanged (256)
               }
   MAX-ACCESS  read-write
   STATUS      current
   DESCRIPTION
      "Path: ethernet2.editConf.inboundBandwidth.action.cirAction.ethernet.cosDepth5

       Possibilities:
               unchanged   (256)"
   ::= {er1645v2Lan2FGUIbwEntry 4064608256}

er1645v2Lan2FGUIbwActCirActEthDei5 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth5

       Possibilities:
               unchanged   (255)
               clear   (0)
               set   (1)"
   ::= {er1645v2Lan2FGUIbwEntry 4065918976}

er1645v2Lan2FGUIbwActCirActEthCos6 OBJECT-TYPE
   SYNTAX      INTEGER
               {
               unchanged (256)
               }
   MAX-ACCESS  read-write
   STATUS      current
   DESCRIPTION
      "Path: ethernet2.editConf.inboundBandwidth.action.cirAction.ethernet.cosDepth6

       Possibilities:
               unchanged   (256)"
   ::= {er1645v2Lan2FGUIbwEntry 4064673792}

er1645v2Lan2FGUIbwActCirActEthDei6 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth6

       Possibilities:
               unchanged   (255)
               clear   (0)
               set   (1)"
   ::= {er1645v2Lan2FGUIbwEntry 4065984512}

er1645v2Lan2FGUIbwActCirActEthCos7 OBJECT-TYPE
   SYNTAX      INTEGER
               {
               unchanged (256)
               }
   MAX-ACCESS  read-write
   STATUS      current
   DESCRIPTION
      "Path: ethernet2.editConf.inboundBandwidth.action.cirAction.ethernet.cosDepth7

       Possibilities:
               unchanged   (256)"
   ::= {er1645v2Lan2FGUIbwEntry 4064739328}

er1645v2Lan2FGUIbwActCirActEthDei7 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth7

       Possibilities:
               unchanged   (255)
               clear   (0)
               set   (1)"
   ::= {er1645v2Lan2FGUIbwEntry 4066050048}

er1645v2Lan2FGUIbwActCirActEthCos8 OBJECT-TYPE
   SYNTAX      INTEGER
               {
               unchanged (256)
               }
   MAX-ACCESS  read-write
   STATUS      current
   DESCRIPTION
      "Path: ethernet2.editConf.inboundBandwidth.action.cirAction.ethernet.cosDepth8

       Possibilities:
               unchanged   (256)"
   ::= {er1645v2Lan2FGUIbwEntry 4064804864}

er1645v2Lan2FGUIbwActCirActEthDei8 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth8

       Possibilities:
               unchanged   (255)
               clear   (0)
               set   (1)"
   ::= {er1645v2Lan2FGUIbwEntry 4066115584}

er1645v2Lan2FGUIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4064870400}

er1645v2Lan2FGUIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4064935936}

er1645v2Lan2FGUIbwActCirActEthDrpLev OBJECT-TYPE
   SYNTAX      INTEGER
               {
               unchanged (0)
               }
   MAX-ACCESS  read-write
   STATUS      current
   DESCRIPTION
      "Path: ethernet2.editConf.inboundBandwidth.action.cirAction.ethernet.dropLevel

       Possibilities:
               unchanged   (0)"
   ::= {er1645v2Lan2FGUIbwEntry 4065001472}

er1645v2Lan2FGUIbwActCirActEthDeFlag OBJECT-TYPE
   SYNTAX      INTEGER
               {
               unchanged (255),
               clear (0),
               set (1)
               }
   MAX-ACCESS  read-write
   STATUS      current
   DESCRIPTION
      "Path: ethernet2.editConf.inboundBandwidth.action.cirAction.ethernet.deFlag

       Possibilities:
               unchanged   (255)
               clear   (0)
               set   (1)"
   ::= {er1645v2Lan2FGUIbwEntry 4065198080}

er1645v2Lan2FGUIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4071161856}

er1645v2Lan2FGUIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4071227392}

er1645v2Lan2FGUIbwActCirActIpDrpLev OBJECT-TYPE
   SYNTAX      INTEGER
               {
               unchanged (0)
               }
   MAX-ACCESS  read-write
   STATUS      current
   DESCRIPTION
      "Path: ethernet2.editConf.inboundBandwidth.action.cirAction.ip.dropLevel

       Possibilities:
               unchanged   (0)"
   ::= {er1645v2Lan2FGUIbwEntry 4071292928}

er1645v2Lan2FGUIbwActCirActIpDeFlag OBJECT-TYPE
   SYNTAX      INTEGER
               {
               unchanged (255),
               clear (0),
               set (1)
               }
   MAX-ACCESS  read-write
   STATUS      current
   DESCRIPTION
      "Path: ethernet2.editConf.inboundBandwidth.action.cirAction.ip.deFlag

       Possibilities:
               unchanged   (255)
               clear   (0)
               set   (1)"
   ::= {er1645v2Lan2FGUIbwEntry 4071489536}

er1645v2Lan2FGUIbwActEirActNone OBJECT-TYPE
   SYNTAX      OCTET STRING
   MAX-ACCESS  read-write
   STATUS      current
   DESCRIPTION
      "Path: ethernet2.editConf.inboundBandwidth.action.eirAction.none"
   ::= {er1645v2Lan2FGUIbwEntry 4095737856}

er1645v2Lan2FGUIbwActEirActEthCos1 OBJECT-TYPE
   SYNTAX      INTEGER
               {
               unchanged (256)
               }
   MAX-ACCESS  read-write
   STATUS      current
   DESCRIPTION
      "Path: ethernet2.editConf.inboundBandwidth.action.eirAction.ethernet.cosDepth1

       Possibilities:
               unchanged   (256)"
   ::= {er1645v2Lan2FGUIbwEntry 4097900544}

er1645v2Lan2FGUIbwActEirActEthDei1 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth1

       Possibilities:
               unchanged   (255)
               clear   (0)
               set   (1)"
   ::= {er1645v2Lan2FGUIbwEntry 4099211264}

er1645v2Lan2FGUIbwActEirActEthCos2 OBJECT-TYPE
   SYNTAX      INTEGER
               {
               unchanged (256)
               }
   MAX-ACCESS  read-write
   STATUS      current
   DESCRIPTION
      "Path: ethernet2.editConf.inboundBandwidth.action.eirAction.ethernet.cosDepth2

       Possibilities:
               unchanged   (256)"
   ::= {er1645v2Lan2FGUIbwEntry 4097966080}

er1645v2Lan2FGUIbwActEirActEthDei2 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth2

       Possibilities:
               unchanged   (255)
               clear   (0)
               set   (1)"
   ::= {er1645v2Lan2FGUIbwEntry 4099276800}

er1645v2Lan2FGUIbwActEirActEthCos3 OBJECT-TYPE
   SYNTAX      INTEGER
               {
               unchanged (256)
               }
   MAX-ACCESS  read-write
   STATUS      current
   DESCRIPTION
      "Path: ethernet2.editConf.inboundBandwidth.action.eirAction.ethernet.cosDepth3

       Possibilities:
               unchanged   (256)"
   ::= {er1645v2Lan2FGUIbwEntry 4098031616}

er1645v2Lan2FGUIbwActEirActEthDei3 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth3

       Possibilities:
               unchanged   (255)
               clear   (0)
               set   (1)"
   ::= {er1645v2Lan2FGUIbwEntry 4099342336}

er1645v2Lan2FGUIbwActEirActEthCos4 OBJECT-TYPE
   SYNTAX      INTEGER
               {
               unchanged (256)
               }
   MAX-ACCESS  read-write
   STATUS      current
   DESCRIPTION
      "Path: ethernet2.editConf.inboundBandwidth.action.eirAction.ethernet.cosDepth4

       Possibilities:
               unchanged   (256)"
   ::= {er1645v2Lan2FGUIbwEntry 4098097152}

er1645v2Lan2FGUIbwActEirActEthDei4 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth4

       Possibilities:
               unchanged   (255)
               clear   (0)
               set   (1)"
   ::= {er1645v2Lan2FGUIbwEntry 4099407872}

er1645v2Lan2FGUIbwActEirActEthCos5 OBJECT-TYPE
   SYNTAX      INTEGER
               {
               unchanged (256)
               }
   MAX-ACCESS  read-write
   STATUS      current
   DESCRIPTION
      "Path: ethernet2.editConf.inboundBandwidth.action.eirAction.ethernet.cosDepth5

       Possibilities:
               unchanged   (256)"
   ::= {er1645v2Lan2FGUIbwEntry 4098162688}

er1645v2Lan2FGUIbwActEirActEthDei5 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth5

       Possibilities:
               unchanged   (255)
               clear   (0)
               set   (1)"
   ::= {er1645v2Lan2FGUIbwEntry 4099473408}

er1645v2Lan2FGUIbwActEirActEthCos6 OBJECT-TYPE
   SYNTAX      INTEGER
               {
               unchanged (256)
               }
   MAX-ACCESS  read-write
   STATUS      current
   DESCRIPTION
      "Path: ethernet2.editConf.inboundBandwidth.action.eirAction.ethernet.cosDepth6

       Possibilities:
               unchanged   (256)"
   ::= {er1645v2Lan2FGUIbwEntry 4098228224}

er1645v2Lan2FGUIbwActEirActEthDei6 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth6

       Possibilities:
               unchanged   (255)
               clear   (0)
               set   (1)"
   ::= {er1645v2Lan2FGUIbwEntry 4099538944}

er1645v2Lan2FGUIbwActEirActEthCos7 OBJECT-TYPE
   SYNTAX      INTEGER
               {
               unchanged (256)
               }
   MAX-ACCESS  read-write
   STATUS      current
   DESCRIPTION
      "Path: ethernet2.editConf.inboundBandwidth.action.eirAction.ethernet.cosDepth7

       Possibilities:
               unchanged   (256)"
   ::= {er1645v2Lan2FGUIbwEntry 4098293760}

er1645v2Lan2FGUIbwActEirActEthDei7 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth7

       Possibilities:
               unchanged   (255)
               clear   (0)
               set   (1)"
   ::= {er1645v2Lan2FGUIbwEntry 4099604480}

er1645v2Lan2FGUIbwActEirActEthCos8 OBJECT-TYPE
   SYNTAX      INTEGER
               {
               unchanged (256)
               }
   MAX-ACCESS  read-write
   STATUS      current
   DESCRIPTION
      "Path: ethernet2.editConf.inboundBandwidth.action.eirAction.ethernet.cosDepth8

       Possibilities:
               unchanged   (256)"
   ::= {er1645v2Lan2FGUIbwEntry 4098359296}

er1645v2Lan2FGUIbwActEirActEthDei8 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth8

       Possibilities:
               unchanged   (255)
               clear   (0)
               set   (1)"
   ::= {er1645v2Lan2FGUIbwEntry 4099670016}

er1645v2Lan2FGUIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4098424832}

er1645v2Lan2FGUIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4098490368}

er1645v2Lan2FGUIbwActEirActEthDrpLev OBJECT-TYPE
   SYNTAX      INTEGER
               {
               unchanged (0)
               }
   MAX-ACCESS  read-write
   STATUS      current
   DESCRIPTION
      "Path: ethernet2.editConf.inboundBandwidth.action.eirAction.ethernet.dropLevel

       Possibilities:
               unchanged   (0)"
   ::= {er1645v2Lan2FGUIbwEntry 4098555904}

er1645v2Lan2FGUIbwActEirActEthDeFlag OBJECT-TYPE
   SYNTAX      INTEGER
               {
               unchanged (255),
               clear (0),
               set (1)
               }
   MAX-ACCESS  read-write
   STATUS      current
   DESCRIPTION
      "Path: ethernet2.editConf.inboundBandwidth.action.eirAction.ethernet.deFlag

       Possibilities:
               unchanged   (255)
               clear   (0)
               set   (1)"
   ::= {er1645v2Lan2FGUIbwEntry 4098752512}

er1645v2Lan2FGUIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4104716288}

er1645v2Lan2FGUIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4104781824}

er1645v2Lan2FGUIbwActEirActIpDrpLev OBJECT-TYPE
   SYNTAX      INTEGER
               {
               unchanged (0)
               }
   MAX-ACCESS  read-write
   STATUS      current
   DESCRIPTION
      "Path: ethernet2.editConf.inboundBandwidth.action.eirAction.ip.dropLevel

       Possibilities:
               unchanged   (0)"
   ::= {er1645v2Lan2FGUIbwEntry 4104847360}

er1645v2Lan2FGUIbwActEirActIpDeFlag OBJECT-TYPE
   SYNTAX      INTEGER
               {
               unchanged (255),
               clear (0),
               set (1)
               }
   MAX-ACCESS  read-write
   STATUS      current
   DESCRIPTION
      "Path: ethernet2.editConf.inboundBandwidth.action.eirAction.ip.deFlag

       Possibilities:
               unchanged   (255)
               clear   (0)
               set   (1)"
   ::= {er1645v2Lan2FGUIbwEntry 4105043968}

er1645v2Lan2FGUIbwActViolActNone OBJECT-TYPE
   SYNTAX      OCTET STRING
   MAX-ACCESS  read-write
   STATUS      current
   DESCRIPTION
      "Path: ethernet2.editConf.inboundBandwidth.action.violateAction.none"
   ::= {er1645v2Lan2FGUIbwEntry 4129292288}

er1645v2Lan2FGUIbwActViolActDrop OBJECT-TYPE
   SYNTAX      OCTET STRING
   MAX-ACCESS  read-write
   STATUS      current
   DESCRIPTION
      "Path: ethernet2.editConf.inboundBandwidth.action.violateAction.drop"
   ::= {er1645v2Lan2FGUIbwEntry 4133486592}

er1645v2Lan2FGUIbwActViolActEthCos1 OBJECT-TYPE
   SYNTAX      INTEGER
               {
               unchanged (256)
               }
   MAX-ACCESS  read-write
   STATUS      current
   DESCRIPTION
      "Path: ethernet2.editConf.inboundBandwidth.action.violateAction.ethernet.cosDepth1

       Possibilities:
               unchanged   (256)"
   ::= {er1645v2Lan2FGUIbwEntry 4131454976}

er1645v2Lan2FGUIbwActViolActEthDei1 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth1

       Possibilities:
               unchanged   (255)
               clear   (0)
               set   (1)"
   ::= {er1645v2Lan2FGUIbwEntry 4132765696}

er1645v2Lan2FGUIbwActViolActEthCos2 OBJECT-TYPE
   SYNTAX      INTEGER
               {
               unchanged (256)
               }
   MAX-ACCESS  read-write
   STATUS      current
   DESCRIPTION
      "Path: ethernet2.editConf.inboundBandwidth.action.violateAction.ethernet.cosDepth2

       Possibilities:
               unchanged   (256)"
   ::= {er1645v2Lan2FGUIbwEntry 4131520512}

er1645v2Lan2FGUIbwActViolActEthDei2 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth2

       Possibilities:
               unchanged   (255)
               clear   (0)
               set   (1)"
   ::= {er1645v2Lan2FGUIbwEntry 4132831232}

er1645v2Lan2FGUIbwActViolActEthCos3 OBJECT-TYPE
   SYNTAX      INTEGER
               {
               unchanged (256)
               }
   MAX-ACCESS  read-write
   STATUS      current
   DESCRIPTION
      "Path: ethernet2.editConf.inboundBandwidth.action.violateAction.ethernet.cosDepth3

       Possibilities:
               unchanged   (256)"
   ::= {er1645v2Lan2FGUIbwEntry 4131586048}

er1645v2Lan2FGUIbwActViolActEthDei3 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth3

       Possibilities:
               unchanged   (255)
               clear   (0)
               set   (1)"
   ::= {er1645v2Lan2FGUIbwEntry 4132896768}

er1645v2Lan2FGUIbwActViolActEthCos4 OBJECT-TYPE
   SYNTAX      INTEGER
               {
               unchanged (256)
               }
   MAX-ACCESS  read-write
   STATUS      current
   DESCRIPTION
      "Path: ethernet2.editConf.inboundBandwidth.action.violateAction.ethernet.cosDepth4

       Possibilities:
               unchanged   (256)"
   ::= {er1645v2Lan2FGUIbwEntry 4131651584}

er1645v2Lan2FGUIbwActViolActEthDei4 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth4

       Possibilities:
               unchanged   (255)
               clear   (0)
               set   (1)"
   ::= {er1645v2Lan2FGUIbwEntry 4132962304}

er1645v2Lan2FGUIbwActViolActEthCos5 OBJECT-TYPE
   SYNTAX      INTEGER
               {
               unchanged (256)
               }
   MAX-ACCESS  read-write
   STATUS      current
   DESCRIPTION
      "Path: ethernet2.editConf.inboundBandwidth.action.violateAction.ethernet.cosDepth5

       Possibilities:
               unchanged   (256)"
   ::= {er1645v2Lan2FGUIbwEntry 4131717120}

er1645v2Lan2FGUIbwActViolActEthDei5 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth5

       Possibilities:
               unchanged   (255)
               clear   (0)
               set   (1)"
   ::= {er1645v2Lan2FGUIbwEntry 4133027840}

er1645v2Lan2FGUIbwActViolActEthCos6 OBJECT-TYPE
   SYNTAX      INTEGER
               {
               unchanged (256)
               }
   MAX-ACCESS  read-write
   STATUS      current
   DESCRIPTION
      "Path: ethernet2.editConf.inboundBandwidth.action.violateAction.ethernet.cosDepth6

       Possibilities:
               unchanged   (256)"
   ::= {er1645v2Lan2FGUIbwEntry 4131782656}

er1645v2Lan2FGUIbwActViolActEthDei6 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth6

       Possibilities:
               unchanged   (255)
               clear   (0)
               set   (1)"
   ::= {er1645v2Lan2FGUIbwEntry 4133093376}

er1645v2Lan2FGUIbwActViolActEthCos7 OBJECT-TYPE
   SYNTAX      INTEGER
               {
               unchanged (256)
               }
   MAX-ACCESS  read-write
   STATUS      current
   DESCRIPTION
      "Path: ethernet2.editConf.inboundBandwidth.action.violateAction.ethernet.cosDepth7

       Possibilities:
               unchanged   (256)"
   ::= {er1645v2Lan2FGUIbwEntry 4131848192}

er1645v2Lan2FGUIbwActViolActEthDei7 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth7

       Possibilities:
               unchanged   (255)
               clear   (0)
               set   (1)"
   ::= {er1645v2Lan2FGUIbwEntry 4133158912}

er1645v2Lan2FGUIbwActViolActEthCos8 OBJECT-TYPE
   SYNTAX      INTEGER
               {
               unchanged (256)
               }
   MAX-ACCESS  read-write
   STATUS      current
   DESCRIPTION
      "Path: ethernet2.editConf.inboundBandwidth.action.violateAction.ethernet.cosDepth8

       Possibilities:
               unchanged   (256)"
   ::= {er1645v2Lan2FGUIbwEntry 4131913728}

er1645v2Lan2FGUIbwActViolActEthDei8 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth8

       Possibilities:
               unchanged   (255)
               clear   (0)
               set   (1)"
   ::= {er1645v2Lan2FGUIbwEntry 4133224448}

er1645v2Lan2FGUIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4131979264}

er1645v2Lan2FGUIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4132044800}

er1645v2Lan2FGUIbwActViolActEthDrpLev OBJECT-TYPE
   SYNTAX      INTEGER
               {
               unchanged (0)
               }
   MAX-ACCESS  read-write
   STATUS      current
   DESCRIPTION
      "Path: ethernet2.editConf.inboundBandwidth.action.violateAction.ethernet.dropLevel

       Possibilities:
               unchanged   (0)"
   ::= {er1645v2Lan2FGUIbwEntry 4132110336}

er1645v2Lan2FGUIbwActViolActEthDeFlag OBJECT-TYPE
   SYNTAX      INTEGER
               {
               unchanged (255),
               clear (0),
               set (1)
               }
   MAX-ACCESS  read-write
   STATUS      current
   DESCRIPTION
      "Path: ethernet2.editConf.inboundBandwidth.action.violateAction.ethernet.deFlag

       Possibilities:
               unchanged   (255)
               clear   (0)
               set   (1)"
   ::= {er1645v2Lan2FGUIbwEntry 4132306944}

er1645v2Lan2FGUIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUIbwEntry 4138270720}

er1645v2Lan2FGUIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUIbwEntry 4138336256}

er1645v2Lan2FGUIbwActViolActIpDrpLev OBJECT-TYPE
   SYNTAX      INTEGER
               {
               unchanged (0)
               }
   MAX-ACCESS  read-write
   STATUS      current
   DESCRIPTION
      "Path: ethernet2.editConf.inboundBandwidth.action.violateAction.ip.dropLevel

       Possibilities:
               unchanged   (0)"
   ::= {er1645v2Lan2FGUIbwEntry 4138401792}

er1645v2Lan2FGUIbwActViolActIpDeFlag OBJECT-TYPE
   SYNTAX      INTEGER
               {
               unchanged (255),
               clear (0),
               set (1)
               }
   MAX-ACCESS  read-write
   STATUS      current
   DESCRIPTION
      "Path: ethernet2.editConf.inboundBandwidth.action.violateAction.ip.deFlag

       Possibilities:
               unchanged   (255)
               clear   (0)
               set   (1)"
   ::= {er1645v2Lan2FGUIbwEntry 4138598400}

er1645v2Lan2FGUIbwSubInterfacesExcluded OBJECT-TYPE
   SYNTAX      INTEGER
               {
               s (1)
               }
   MAX-ACCESS  read-write
   STATUS      current
   DESCRIPTION
      "Path: ethernet2.editConf.inboundBandwidth.subInterfaces.excluded

       Possibilities:
                  (1)"
   ::= {er1645v2Lan2FGUIbwEntry 2416967680}

er1645v2Lan2FGUIbwSubInterfacesIncludedInAccessList OBJECT-TYPE
   SYNTAX      DisplayString
   MAX-ACCESS  read-write
   STATUS      current
   DESCRIPTION
      "Path: ethernet2.editConf.inboundBandwidth.subInterfaces.included.inAccessList"
   ::= {er1645v2Lan2FGUIbwEntry 2418020352}


er1645v2Lan2FGUPriorityPolicy OBJECT-TYPE
   SYNTAX      DisplayString
   MAX-ACCESS  read-write
   STATUS      current
   DESCRIPTION
      "Path: ethernet2.editConf.priorityPolicy
       Info: Preferred Policy"
   ::= {er1645v2Lan2FGU 39}


er1645v2Lan2FGUMru OBJECT-TYPE
   SYNTAX      Integer32
   MAX-ACCESS  read-write
   STATUS      current
   DESCRIPTION
      "Path: ethernet2.editConf.mru"
   ::= {er1645v2Lan2FGU 43}


er1645v2Lan2FGUDelayOptimisation OBJECT-TYPE
   SYNTAX      INTEGER
               {
               disabled (0),
               enabled (1)
               }
   MAX-ACCESS  read-write
   STATUS      current
   DESCRIPTION
      "Path: ethernet2.editConf.delayOptimisation
       Info: optimise delay

       Possibilities:
               disabled   (0)
               enabled   (1)"
   ::= {er1645v2Lan2FGU 80}


er1645v2Lan2FGUAlarmMask OBJECT-TYPE
   SYNTAX      Integer32
   MAX-ACCESS  read-write
   STATUS      current
   DESCRIPTION
      "Path: ethernet2.editConf.alarmMask
       Info: ifAlarmMask

       Bit meanings:
               bit 0 = linkDown,
               bit 9 = pppoEDown"
   ::= {er1645v2Lan2FGU 135}


er1645v2Lan2FGUAlarmLev OBJECT IDENTIFIER ::= {er1645v2Lan2FGU 170}

er1645v2Lan2FGUAlarmLevSSC OBJECT IDENTIFIER ::= {er1645v2Lan2FGUAlarmLev 1}

er1645v2Lan2FGUAlarmLevEntry OBJECT IDENTIFIER ::= {er1645v2Lan2FGUAlarmLevSSC 1}

er1645v2Lan2FGUAlarmLevLinkDown OBJECT-TYPE
   SYNTAX      Integer32
   MAX-ACCESS  read-write
   STATUS      current
   DESCRIPTION
      "Path: ethernet2.editConf.alarmLevel.linkDown"
   ::= {er1645v2Lan2FGUAlarmLevEntry 16777216}

er1645v2Lan2FGUAlarmLevPppoEDown OBJECT-TYPE
   SYNTAX      Integer32
   MAX-ACCESS  read-write
   STATUS      current
   DESCRIPTION
      "Path: ethernet2.editConf.alarmLevel.pppoEDown"
   ::= {er1645v2Lan2FGUAlarmLevEntry 167772160}


er1645v2Lan2FGUArp OBJECT IDENTIFIER ::= {er1645v2Lan2FGU 19}

er1645v2Lan2FGUArpSSC OBJECT IDENTIFIER ::= {er1645v2Lan2FGUArp 1}

er1645v2Lan2FGUArpEntry OBJECT IDENTIFIER ::= {er1645v2Lan2FGUArpSSC 1}

er1645v2Lan2FGUArpTimeOut OBJECT-TYPE
   SYNTAX      TimeTicks
   MAX-ACCESS  read-write
   STATUS      current
   DESCRIPTION
      "Path: ethernet2.editConf.arp.timeOut

       Time in centi-second."
   ::= {er1645v2Lan2FGUArpEntry 201326592}

er1645v2Lan2FGUArpProxyArp OBJECT-TYPE
   SYNTAX      INTEGER
               {
               disabled (0),
               enabled (1)
               }
   MAX-ACCESS  read-write
   STATUS      current
   DESCRIPTION
      "Path: ethernet2.editConf.arp.proxyArp

       Possibilities:
               disabled   (0)
               enabled   (1)"
   ::= {er1645v2Lan2FGUArpEntry 838860800}

er1645v2Lan2FGUArpStaticArp OBJECT-TYPE
   SYNTAX      SEQUENCE OF Er1645v2Lan2FGUArpStaticArpEntry
   MAX-ACCESS  not-accessible
   STATUS      current
   DESCRIPTION
      ""
   ::= {er1645v2Lan2FGUArp 50331648}

er1645v2Lan2FGUArpStaticArpEntry OBJECT-TYPE
   SYNTAX      Er1645v2Lan2FGUArpStaticArpEntry
   MAX-ACCESS  not-accessible
   STATUS      current
   DESCRIPTION
      ""
   INDEX      { er1645v2Lan2FGUArpStaticArpTableIx }
   ::= {er1645v2Lan2FGUArpStaticArp 1}

Er1645v2Lan2FGUArpStaticArpEntry ::=
   SEQUENCE
      {
      er1645v2Lan2FGUArpStaticArpActions
         VariableLengthTableActions,
      er1645v2Lan2FGUArpStaticArpTableIx
         TableIndex,
      er1645v2Lan2FGUArpStaticArpMacAddress
         OCTET STRING,
      er1645v2Lan2FGUArpStaticArpIpAddress
         IpAddress
      }

er1645v2Lan2FGUArpStaticArpActions OBJECT-TYPE
   SYNTAX      VariableLengthTableActions
   MAX-ACCESS  read-write
   STATUS      current
   DESCRIPTION
      "By way of this field, some manipulations
       on this table may be performed."
   ::= {er1645v2Lan2FGUArpStaticArpEntry 2}

er1645v2Lan2FGUArpStaticArpTableIx OBJECT-TYPE
   SYNTAX      TableIndex
   MAX-ACCESS  not-accessible
   STATUS      current
   DESCRIPTION
      ""
   ::= {er1645v2Lan2FGUArpStaticArpEntry 11}

er1645v2Lan2FGUArpStaticArpMacAddress OBJECT-TYPE
   SYNTAX      OCTET STRING
   MAX-ACCESS  read-write
   STATUS      current
   DESCRIPTION
      "Path: ethernet2.editConf.arp.staticArp.macAddress

       MAC address."
   ::= {er1645v2Lan2FGUArpStaticArpEntry 16777216}

er1645v2Lan2FGUArpStaticArpIpAddress OBJECT-TYPE
   SYNTAX      IpAddress
   MAX-ACCESS  read-write
   STATUS      current
   DESCRIPTION
      "Path: ethernet2.editConf.arp.staticArp.ipAddress"
   ::= {er1645v2Lan2FGUArpStaticArpEntry 33554432}


er1645v2Lan2FGUBrC OBJECT IDENTIFIER ::= {er1645v2Lan2FGU 27}

er1645v2Lan2FGUBrCSSC OBJECT IDENTIFIER ::= {er1645v2Lan2FGUBrC 1}

er1645v2Lan2FGUBrCEntry OBJECT IDENTIFIER ::= {er1645v2Lan2FGUBrCSSC 1}

er1645v2Lan2FGUBrCAccessList OBJECT-TYPE
   SYNTAX      DisplayString
   MAX-ACCESS  read-write
   STATUS      current
   DESCRIPTION
      "Path: ethernet2.editConf.bridging.accessList"
   ::= {er1645v2Lan2FGUBrCEntry 83886080}

er1645v2Lan2FGUBrCInAccessList OBJECT-TYPE
   SYNTAX      DisplayString
   MAX-ACCESS  read-write
   STATUS      current
   DESCRIPTION
      "Path: ethernet2.editConf.bridging.inAccessList"
   ::= {er1645v2Lan2FGUBrCEntry 251658240}

er1645v2Lan2FGUBrCTp OBJECT-TYPE
   SYNTAX      DisplayString
   MAX-ACCESS  read-write
   STATUS      current
   DESCRIPTION
      "Path: ethernet2.editConf.bridging.trafficPolicy"
   ::= {er1645v2Lan2FGUBrCEntry 100663296}

er1645v2Lan2FGUBrCBridgeGroup OBJECT-TYPE
   SYNTAX      DisplayString
   MAX-ACCESS  read-write
   STATUS      current
   DESCRIPTION
      "Path: ethernet2.editConf.bridging.bridgeGroup"
   ::= {er1645v2Lan2FGUBrCEntry 117440512}

er1645v2Lan2FGUBrCLimBC OBJECT-TYPE
   SYNTAX      INTEGER
               {
               disabled (0),
               enabled (1)
               }
   MAX-ACCESS  read-write
   STATUS      current
   DESCRIPTION
      "Path: ethernet2.editConf.bridging.limitBroadcasts

       Possibilities:
               disabled   (0)
               enabled   (1)"
   ::= {er1645v2Lan2FGUBrCEntry 134217728}

er1645v2Lan2FGUBrCPrivateMode OBJECT-TYPE
   SYNTAX      INTEGER
               {
               disabled (0),
               enabled (1)
               }
   MAX-ACCESS  read-write
   STATUS      current
   DESCRIPTION
      "Path: ethernet2.editConf.bridging.privateMode

       Possibilities:
               disabled   (0)
               enabled   (1)"
   ::= {er1645v2Lan2FGUBrCEntry 419430400}

er1645v2Lan2FGUBrCLearning OBJECT-TYPE
   SYNTAX      INTEGER
               {
               disabled (0),
               enabled (1)
               }
   MAX-ACCESS  read-write
   STATUS      current
   DESCRIPTION
      "Path: ethernet2.editConf.bridging.learning

       Possibilities:
               disabled   (0)
               enabled   (1)"
   ::= {er1645v2Lan2FGUBrCEntry 201326592}

er1645v2Lan2FGUBrCMaxCacheSize OBJECT-TYPE
   SYNTAX      INTEGER
               {
               unlimited (0)
               }
   MAX-ACCESS  read-write
   STATUS      current
   DESCRIPTION
      "Path: ethernet2.editConf.bridging.maxCacheSize

       Possibilities:
               unlimited   (0)"
   ::= {er1645v2Lan2FGUBrCEntry 218103808}

er1645v2Lan2FGUBrCRelearnDropOnRelearn OBJECT-TYPE
   SYNTAX      INTEGER
               {
               disabled (0),
               enabled (1)
               }
   MAX-ACCESS  read-write
   STATUS      current
   DESCRIPTION
      "Path: ethernet2.editConf.bridging.relearn.dropOnRelearn

       Possibilities:
               disabled   (0)
               enabled   (1)"
   ::= {er1645v2Lan2FGUBrCEntry 234946560}

er1645v2Lan2FGUBrCRelearnShutdownThreshold OBJECT-TYPE
   SYNTAX      Integer32
   MAX-ACCESS  read-write
   STATUS      current
   DESCRIPTION
      "Path: ethernet2.editConf.bridging.relearn.shutdownThreshold"
   ::= {er1645v2Lan2FGUBrCEntry 235012096}

er1645v2Lan2FGUBrCRelearnShutdownTime OBJECT-TYPE
   SYNTAX      TimeTicks
   MAX-ACCESS  read-write
   STATUS      current
   DESCRIPTION
      "Path: ethernet2.editConf.bridging.relearn.shutdownTime

       Time in centi-second."
   ::= {er1645v2Lan2FGUBrCEntry 235077632}

er1645v2Lan2FGUBrCRelearnLoopDetection OBJECT-TYPE
   SYNTAX      INTEGER
               {
               disabled (0),
               passive (1),
               active (2)
               }
   MAX-ACCESS  read-write
   STATUS      current
   DESCRIPTION
      "Path: ethernet2.editConf.bridging.relearn.loopDetection

       Possibilities:
               disabled   (0)
               passive   (1)
               active   (2)"
   ::= {er1645v2Lan2FGUBrCEntry 235143168}

er1645v2Lan2FGUBrCRelearnLoopDetectionInterval OBJECT-TYPE
   SYNTAX      TimeTicks
   MAX-ACCESS  read-write
   STATUS      current
   DESCRIPTION
      "Path: ethernet2.editConf.bridging.relearn.loopDetectionInterval

       Time in centi-second."
   ::= {er1645v2Lan2FGUBrCEntry 235208704}

er1645v2Lan2FGUBrCVlanMemberShip OBJECT-TYPE
   SYNTAX      INTEGER
               {
               all (0),
               none (1),
               grouped (2)
               }
   MAX-ACCESS  read-write
   STATUS      current
   DESCRIPTION
      "Path: ethernet2.editConf.bridging.vlanMemberShip

       Possibilities:
               all   (0)
               none   (1)
               grouped   (2)"
   ::= {er1645v2Lan2FGUBrCEntry 318767104}

er1645v2Lan2FGUBrCDot1adType OBJECT-TYPE
   SYNTAX      INTEGER
               {
               slOPTg (0),
               cPort (4),
               sPort (1),
               nni (2)
               }
   MAX-ACCESS  read-write
   STATUS      current
   DESCRIPTION
      "Path: ethernet2.editConf.bridging.dot1ad.type

       Possibilities:
               <OPT>   (0)
               cPort   (4)
               sPort   (1)
               nni   (2)"
   ::= {er1645v2Lan2FGUBrCEntry 503382016}

er1645v2Lan2FGUBrCPriority OBJECT-TYPE
   SYNTAX      Integer32
   MAX-ACCESS  read-write
   STATUS      current
   DESCRIPTION
      "Path: ethernet2.editConf.bridging.priority"
   ::= {er1645v2Lan2FGUBrCEntry 33554432}

er1645v2Lan2FGUBrCPathCost OBJECT-TYPE
   SYNTAX      Integer32
   MAX-ACCESS  read-write
   STATUS      current
   DESCRIPTION
      "Path: ethernet2.editConf.bridging.pathCost"
   ::= {er1645v2Lan2FGUBrCEntry 50331648}

er1645v2Lan2FGUBrCInternalPathCost OBJECT-TYPE
   SYNTAX      Integer32
   MAX-ACCESS  read-write
   STATUS      current
   DESCRIPTION
      "Path: ethernet2.editConf.bridging.internalPathCost"
   ::= {er1645v2Lan2FGUBrCEntry 301989888}

er1645v2Lan2FGUBrCTCD OBJECT-TYPE
   SYNTAX      INTEGER
               {
               disabled (0),
               enabled (1)
               }
   MAX-ACCESS  read-write
   STATUS      current
   DESCRIPTION
      "Path: ethernet2.editConf.bridging.topologyChangeDetection

       Possibilities:
               disabled   (0)
               enabled   (1)"
   ::= {er1645v2Lan2FGUBrCEntry 67108864}

er1645v2Lan2FGUBrCRestrictedRole OBJECT-TYPE
   SYNTAX      INTEGER
               {
               disabled (0),
               enabled (1)
               }
   MAX-ACCESS  read-write
   STATUS      current
   DESCRIPTION
      "Path: ethernet2.editConf.bridging.restrictedRole

       Possibilities:
               disabled   (0)
               enabled   (1)"
   ::= {er1645v2Lan2FGUBrCEntry 335544320}

er1645v2Lan2FGUBrCAdminEdge OBJECT-TYPE
   SYNTAX      INTEGER
               {
               disabled (0),
               enabled (1)
               }
   MAX-ACCESS  read-write
   STATUS      current
   DESCRIPTION
      "Path: ethernet2.editConf.bridging.adminEdge

       Possibilities:
               disabled   (0)
               enabled   (1)"
   ::= {er1645v2Lan2FGUBrCEntry 268435456}

er1645v2Lan2FGUBrCMgmtInline OBJECT-TYPE
   SYNTAX      INTEGER
               {
               disabled (0),
               enabled (1)
               }
   MAX-ACCESS  read-write
   STATUS      current
   DESCRIPTION
      "Path: ethernet2.editConf.bridging.mgmtInline

       Possibilities:
               disabled   (0)
               enabled   (1)"
   ::= {er1645v2Lan2FGUBrCEntry 369098752}

er1645v2Lan2FGUBrCL2ptMode OBJECT-TYPE
   SYNTAX      INTEGER
               {
               disabled (0),
               enabled (1)
               }
   MAX-ACCESS  read-write
   STATUS      current
   DESCRIPTION
      "Path: ethernet2.editConf.bridging.l2ProtTunnel.mode

       Possibilities:
               disabled   (0)
               enabled   (1)"
   ::= {er1645v2Lan2FGUBrCEntry 403701760}

er1645v2Lan2FGUBrCL2ptProtocols OBJECT-TYPE
   SYNTAX      Integer32
   MAX-ACCESS  read-write
   STATUS      current
   DESCRIPTION
      "Path: ethernet2.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2FGUBrCEntry 404750336}

er1645v2Lan2FGUBrCL2ptDestMac OBJECT-TYPE
   SYNTAX      OCTET STRING
   MAX-ACCESS  read-write
   STATUS      current
   DESCRIPTION
      "Path: ethernet2.editConf.bridging.l2ProtTunnel.destinationMac

       MAC address."
   ::= {er1645v2Lan2FGUBrCEntry 405798912}

er1645v2Lan2FGUBrCL2ptCos OBJECT-TYPE
   SYNTAX      INTEGER
               {
               unchanged (255)
               }
   MAX-ACCESS  read-write
   STATUS      current
   DESCRIPTION
      "Path: ethernet2.editConf.bridging.l2ProtTunnel.cos

       Possibilities:
               unchanged   (255)"
   ::= {er1645v2Lan2FGUBrCEntry 406847488}

er1645v2Lan2FGUBrCL2ptDropThrStp OBJECT-TYPE
   SYNTAX      INTEGER
               {
               unlimited (0)
               }
   UNITS       "packets/sec"
   MAX-ACCESS  read-write
   STATUS      current
   DESCRIPTION
      "Path: ethernet2.editConf.bridging.l2ProtTunnel.dropThresholds.stp

       unit name = packets/sec

       Possibilities:
               unlimited   (0)"
   ::= {er1645v2Lan2FGUBrCEntry 407900160}

er1645v2Lan2FGUBrCL2ptDropThrLldp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lldp

       unit name = packets/sec

       Possibilities:
               unlimited   (0)"
   ::= {er1645v2Lan2FGUBrCEntry 407904256}

er1645v2Lan2FGUBrCL2ptDropThrOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.oam

       unit name = packets/sec

       Possibilities:
               unlimited   (0)"
   ::= {er1645v2Lan2FGUBrCEntry 407908352}

er1645v2Lan2FGUBrCL2ptDropThrCdp OBJECT-TYPE
   SYNTAX      INTEGER
               {
               unlimited (0)
               }
   UNITS       "packets/sec"
   MAX-ACCESS  read-write
   STATUS      current
   DESCRIPTION
      "Path: ethernet2.editConf.bridging.l2ProtTunnel.dropThresholds.cdp

       unit name = packets/sec

       Possibilities:
               unlimited   (0)"
   ::= {er1645v2Lan2FGUBrCEntry 407912448}

er1645v2Lan2FGUBrCL2ptDropThrVtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.vtp

       unit name = packets/sec

       Possibilities:
               unlimited   (0)"
   ::= {er1645v2Lan2FGUBrCEntry 407916544}

er1645v2Lan2FGUBrCL2ptDropThrLacp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lacp

       unit name = packets/sec

       Possibilities:
               unlimited   (0)"
   ::= {er1645v2Lan2FGUBrCEntry 407920640}

er1645v2Lan2FGUBrCL2ptDropThrEfmOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.efmOam

       unit name = packets/sec

       Possibilities:
               unlimited   (0)"
   ::= {er1645v2Lan2FGUBrCEntry 407924736}

er1645v2Lan2FGUBrCL2ptDropThrPvst OBJECT-TYPE
   SYNTAX      INTEGER
               {
               unlimited (0)
               }
   UNITS       "packets/sec"
   MAX-ACCESS  read-write
   STATUS      current
   DESCRIPTION
      "Path: ethernet2.editConf.bridging.l2ProtTunnel.dropThresholds.pvst

       unit name = packets/sec

       Possibilities:
               unlimited   (0)"
   ::= {er1645v2Lan2FGUBrCEntry 407928832}

er1645v2Lan2FGUBrCL2ptDropThrMmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mmrp

       unit name = packets/sec

       Possibilities:
               unlimited   (0)"
   ::= {er1645v2Lan2FGUBrCEntry 407932928}

er1645v2Lan2FGUBrCL2ptDropThrMvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mvrp

       unit name = packets/sec

       Possibilities:
               unlimited   (0)"
   ::= {er1645v2Lan2FGUBrCEntry 407937024}

er1645v2Lan2FGUBrCL2ptDropThrGvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gvrp

       unit name = packets/sec

       Possibilities:
               unlimited   (0)"
   ::= {er1645v2Lan2FGUBrCEntry 407941120}

er1645v2Lan2FGUBrCL2ptDropThrGmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gmrp

       unit name = packets/sec

       Possibilities:
               unlimited   (0)"
   ::= {er1645v2Lan2FGUBrCEntry 407945216}

er1645v2Lan2FGUBrCL2ptDropThrDtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.dtp

       unit name = packets/sec

       Possibilities:
               unlimited   (0)"
   ::= {er1645v2Lan2FGUBrCEntry 407949312}

er1645v2Lan2FGUBrCL2ptDropThrPagp OBJECT-TYPE
   SYNTAX      INTEGER
               {
               unlimited (0)
               }
   UNITS       "packets/sec"
   MAX-ACCESS  read-write
   STATUS      current
   DESCRIPTION
      "Path: ethernet2.editConf.bridging.l2ProtTunnel.dropThresholds.pagp

       unit name = packets/sec

       Possibilities:
               unlimited   (0)"
   ::= {er1645v2Lan2FGUBrCEntry 407953408}

er1645v2Lan2FGUBrCL2ptDropThrUdld OBJECT-TYPE
   SYNTAX      INTEGER
               {
               unlimited (0)
               }
   UNITS       "packets/sec"
   MAX-ACCESS  read-write
   STATUS      current
   DESCRIPTION
      "Path: ethernet2.editConf.bridging.l2ProtTunnel.dropThresholds.udld

       unit name = packets/sec

       Possibilities:
               unlimited   (0)"
   ::= {er1645v2Lan2FGUBrCEntry 407957504}


er1645v2Lan2FGUVlanTagging OBJECT IDENTIFIER ::= {er1645v2Lan2FGU 14}

er1645v2Lan2FGUVlanTaggingSSC OBJECT IDENTIFIER ::= {er1645v2Lan2FGUVlanTagging 1}

er1645v2Lan2FGUVlanTaggingEntry OBJECT IDENTIFIER ::= {er1645v2Lan2FGUVlanTaggingSSC 1}

er1645v2Lan2FGUVlanTaggingUntaggedAction OBJECT-TYPE
   SYNTAX      INTEGER
               {
               discard (0),
               accept (1),
               tag (2)
               }
   MAX-ACCESS  read-write
   STATUS      current
   DESCRIPTION
      "Path: ethernet2.editConf.vlanTagging.untagged.action

       Possibilities:
               discard   (0)
               accept   (1)
               tag   (2)"
   ::= {er1645v2Lan2FGUVlanTaggingEntry 671088640}

er1645v2Lan2FGUVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.untagged.tagInfo.tpid

       Possibilities:
               dot1Q   (33024)
               dot1ad   (34984)
               0x9100   (37120)
               0x9200   (37376)
               0x9300   (37632)"
   ::= {er1645v2Lan2FGUVlanTaggingEntry 746586112}

er1645v2Lan2FGUVlanTaggingUntaggedTagInfoVid OBJECT-TYPE
   SYNTAX      Integer32
   MAX-ACCESS  read-write
   STATUS      current
   DESCRIPTION
      "Path: ethernet2.editConf.vlanTagging.untagged.tagInfo.vid"
   ::= {er1645v2Lan2FGUVlanTaggingEntry 754974720}

er1645v2Lan2FGUVlanTaggingUnknownVlansAction OBJECT-TYPE
   SYNTAX      INTEGER
               {
               discard (0),
               accept (1),
               tag (2)
               }
   MAX-ACCESS  read-write
   STATUS      current
   DESCRIPTION
      "Path: ethernet2.editConf.vlanTagging.unknownVlans.action

       Possibilities:
               discard   (0)
               accept   (1)
               tag   (2)"
   ::= {er1645v2Lan2FGUVlanTaggingEntry 1744830464}

er1645v2Lan2FGUVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.unknownVlans.tagInfo.tpid

       Possibilities:
               dot1Q   (33024)
               dot1ad   (34984)
               0x9100   (37120)
               0x9200   (37376)
               0x9300   (37632)"
   ::= {er1645v2Lan2FGUVlanTaggingEntry 1820327936}

er1645v2Lan2FGUVlanTaggingUnknownVlansTagInfoVid OBJECT-TYPE
   SYNTAX      Integer32
   MAX-ACCESS  read-write
   STATUS      current
   DESCRIPTION
      "Path: ethernet2.editConf.vlanTagging.unknownVlans.tagInfo.vid"
   ::= {er1645v2Lan2FGUVlanTaggingEntry 1828716544}

er1645v2Lan2FGUVlanTaggingVlans OBJECT-TYPE
   SYNTAX      SEQUENCE OF Er1645v2Lan2FGUVlanTaggingVlansEntry
   MAX-ACCESS  not-accessible
   STATUS      current
   DESCRIPTION
      ""
   ::= {er1645v2Lan2FGUVlanTagging 1073741824}

er1645v2Lan2FGUVlanTaggingVlansEntry OBJECT-TYPE
   SYNTAX      Er1645v2Lan2FGUVlanTaggingVlansEntry
   MAX-ACCESS  not-accessible
   STATUS      current
   DESCRIPTION
      ""
   INDEX      { er1645v2Lan2FGUVlanTaggingVlansTableIx }
   ::= {er1645v2Lan2FGUVlanTaggingVlans 1}

Er1645v2Lan2FGUVlanTaggingVlansEntry ::=
   SEQUENCE
      {
      er1645v2Lan2FGUVlanTaggingVlansActions
         VariableLengthTableActions,
      er1645v2Lan2FGUVlanTaggingVlansTableIx
         TableIndex,
      er1645v2Lan2FGUVlanTaggingVlansVid
         Integer32,
      er1645v2Lan2FGUVlanTaggingVlansEndVid
         Integer32,
      er1645v2Lan2FGUVlanTaggingVlansAction
         INTEGER,
      er1645v2Lan2FGUVlanTaggingVlansTagInfoTpid
         INTEGER,
      er1645v2Lan2FGUVlanTaggingVlansTagInfoVid
         Integer32
      }

er1645v2Lan2FGUVlanTaggingVlansActions OBJECT-TYPE
   SYNTAX      VariableLengthTableActions
   MAX-ACCESS  read-write
   STATUS      current
   DESCRIPTION
      "By way of this field, some manipulations
       on this table may be performed."
   ::= {er1645v2Lan2FGUVlanTaggingVlansEntry 2}

er1645v2Lan2FGUVlanTaggingVlansTableIx OBJECT-TYPE
   SYNTAX      TableIndex
   MAX-ACCESS  not-accessible
   STATUS      current
   DESCRIPTION
      ""
   ::= {er1645v2Lan2FGUVlanTaggingVlansEntry 11}

er1645v2Lan2FGUVlanTaggingVlansVid OBJECT-TYPE
   SYNTAX      Integer32
   MAX-ACCESS  read-write
   STATUS      current
   DESCRIPTION
      "Path: ethernet2.editConf.vlanTagging.vlans.vid"
   ::= {er1645v2Lan2FGUVlanTaggingVlansEntry 536870912}

er1645v2Lan2FGUVlanTaggingVlansEndVid OBJECT-TYPE
   SYNTAX      Integer32
   MAX-ACCESS  read-write
   STATUS      current
   DESCRIPTION
      "Path: ethernet2.editConf.vlanTagging.vlans.endVid"
   ::= {er1645v2Lan2FGUVlanTaggingVlansEntry 2147483648}

er1645v2Lan2FGUVlanTaggingVlansAction OBJECT-TYPE
   SYNTAX      INTEGER
               {
               discard (0),
               accept (1),
               tag (2)
               }
   MAX-ACCESS  read-write
   STATUS      current
   DESCRIPTION
      "Path: ethernet2.editConf.vlanTagging.vlans.action

       Possibilities:
               discard   (0)
               accept   (1)
               tag   (2)"
   ::= {er1645v2Lan2FGUVlanTaggingVlansEntry 1073741824}

er1645v2Lan2FGUVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.vlans.tagInfo.tpid

       Possibilities:
               dot1Q   (33024)
               dot1ad   (34984)
               0x9100   (37120)
               0x9200   (37376)
               0x9300   (37632)"
   ::= {er1645v2Lan2FGUVlanTaggingVlansEntry 1677721600}

er1645v2Lan2FGUVlanTaggingVlansTagInfoVid OBJECT-TYPE
   SYNTAX      Integer32
   MAX-ACCESS  read-write
   STATUS      current
   DESCRIPTION
      "Path: ethernet2.editConf.vlanTagging.vlans.tagInfo.vid"
   ::= {er1645v2Lan2FGUVlanTaggingVlansEntry 1744830464}


er1645v2Lan2FGUOam OBJECT IDENTIFIER ::= {er1645v2Lan2FGU 900}

er1645v2Lan2FGUOamSSC OBJECT IDENTIFIER ::= {er1645v2Lan2FGUOam 1}

er1645v2Lan2FGUOamEntry OBJECT IDENTIFIER ::= {er1645v2Lan2FGUOamSSC 1}

er1645v2Lan2FGUOamMode OBJECT-TYPE
   SYNTAX      INTEGER
               {
               disabled (0),
               passive (3),
               active (2)
               }
   MAX-ACCESS  read-write
   STATUS      current
   DESCRIPTION
      "Path: ethernet2.editConf.oam.mode

       Possibilities:
               disabled   (0)
               passive   (3)
               active   (2)"
   ::= {er1645v2Lan2FGUOamEntry 16777216}

er1645v2Lan2FGUOamLpbkLocalParAction OBJECT-TYPE
   SYNTAX      INTEGER
               {
               discard (0),
               forward (1)
               }
   MAX-ACCESS  read-write
   STATUS      current
   DESCRIPTION
      "Path: ethernet2.editConf.oam.loopbackLocalParserAction

       Possibilities:
               discard   (0)
               forward   (1)"
   ::= {er1645v2Lan2FGUOamEntry 33554432}

er1645v2Lan2FGUOamLpbkSwapMacAddr OBJECT-TYPE
   SYNTAX      INTEGER
               {
               disabled (0),
               enabled (1)
               }
   MAX-ACCESS  read-write
   STATUS      current
   DESCRIPTION
      "Path: ethernet2.editConf.oam.loopbackSwapMacAddresses

       Possibilities:
               disabled   (0)
               enabled   (1)"
   ::= {er1645v2Lan2FGUOamEntry 50331648}

er1645v2Lan2FGUOamLoopbackIgnoreRx OBJECT-TYPE
   SYNTAX      INTEGER
               {
               no (0),
               yes (1)
               }
   MAX-ACCESS  read-write
   STATUS      current
   DESCRIPTION
      "Path: ethernet2.editConf.oam.loopbackIgnoreRx

       Possibilities:
               no   (0)
               yes   (1)"
   ::= {er1645v2Lan2FGUOamEntry 67108864}

er1645v2Lan2FGUOamEventsErroredSymbolEnabled OBJECT-TYPE
   SYNTAX      INTEGER
               {
               no (0),
               yes (1)
               }
   MAX-ACCESS  read-write
   STATUS      current
   DESCRIPTION
      "Path: ethernet2.editConf.oam.events.erroredSymbol.enabled

       Possibilities:
               no   (0)
               yes   (1)"
   ::= {er1645v2Lan2FGUOamEntry 83951872}

er1645v2Lan2FGUOamEventsErroredSymbolWindowHi OBJECT-TYPE
   SYNTAX      INTEGER
               {
               default (0)
               }
   UNITS       "symbols"
   MAX-ACCESS  read-write
   STATUS      current
   DESCRIPTION
      "Path: ethernet2.editConf.oam.events.erroredSymbol.windowHi

       unit name = symbols

       Possibilities:
               default   (0)"
   ::= {er1645v2Lan2FGUOamEntry 83952128}

er1645v2Lan2FGUOamEventsErroredSymbolWindowLo OBJECT-TYPE
   SYNTAX      INTEGER
               {
               default (0)
               }
   UNITS       "symbols"
   MAX-ACCESS  read-write
   STATUS      current
   DESCRIPTION
      "Path: ethernet2.editConf.oam.events.erroredSymbol.windowLo

       unit name = symbols

       Possibilities:
               default   (0)"
   ::= {er1645v2Lan2FGUOamEntry 83952384}

er1645v2Lan2FGUOamEventsErroredSymbolThresholdHi OBJECT-TYPE
   SYNTAX      Integer32
   UNITS       "symbols"
   MAX-ACCESS  read-write
   STATUS      current
   DESCRIPTION
      "Path: ethernet2.editConf.oam.events.erroredSymbol.thresholdHi

       unit name = symbols"
   ::= {er1645v2Lan2FGUOamEntry 83952640}

er1645v2Lan2FGUOamEventsErroredSymbolThresholdLo OBJECT-TYPE
   SYNTAX      Integer32
   UNITS       "symbols"
   MAX-ACCESS  read-write
   STATUS      current
   DESCRIPTION
      "Path: ethernet2.editConf.oam.events.erroredSymbol.thresholdLo

       unit name = symbols"
   ::= {er1645v2Lan2FGUOamEntry 83952896}

er1645v2Lan2FGUOamEventsErroredFramePeriodEnabled OBJECT-TYPE
   SYNTAX      INTEGER
               {
               no (0),
               yes (1)
               }
   MAX-ACCESS  read-write
   STATUS      current
   DESCRIPTION
      "Path: ethernet2.editConf.oam.events.erroredFramePeriod.enabled

       Possibilities:
               no   (0)
               yes   (1)"
   ::= {er1645v2Lan2FGUOamEntry 84017408}

er1645v2Lan2FGUOamEventsErroredFramePeriodWindow OBJECT-TYPE
   SYNTAX      INTEGER
               {
               default (0)
               }
   UNITS       "frames"
   MAX-ACCESS  read-write
   STATUS      current
   DESCRIPTION
      "Path: ethernet2.editConf.oam.events.erroredFramePeriod.window

       unit name = frames

       Possibilities:
               default   (0)"
   ::= {er1645v2Lan2FGUOamEntry 84017664}

er1645v2Lan2FGUOamEventsErroredFramePeriodThreshold OBJECT-TYPE
   SYNTAX      Integer32
   UNITS       "frames"
   MAX-ACCESS  read-write
   STATUS      current
   DESCRIPTION
      "Path: ethernet2.editConf.oam.events.erroredFramePeriod.threshold

       unit name = frames"
   ::= {er1645v2Lan2FGUOamEntry 84017920}

er1645v2Lan2FGUOamEventsErroredFrameEnabled OBJECT-TYPE
   SYNTAX      INTEGER
               {
               no (0),
               yes (1)
               }
   MAX-ACCESS  read-write
   STATUS      current
   DESCRIPTION
      "Path: ethernet2.editConf.oam.events.erroredFrame.enabled

       Possibilities:
               no   (0)
               yes   (1)"
   ::= {er1645v2Lan2FGUOamEntry 84082944}

er1645v2Lan2FGUOamEventsErroredFrameWindow OBJECT-TYPE
   SYNTAX      Integer32
   UNITS       "100msec"
   MAX-ACCESS  read-write
   STATUS      current
   DESCRIPTION
      "Path: ethernet2.editConf.oam.events.erroredFrame.window

       unit name = 100msec"
   ::= {er1645v2Lan2FGUOamEntry 84083200}

er1645v2Lan2FGUOamEventsErroredFrameThreshold OBJECT-TYPE
   SYNTAX      Integer32
   UNITS       "frames"
   MAX-ACCESS  read-write
   STATUS      current
   DESCRIPTION
      "Path: ethernet2.editConf.oam.events.erroredFrame.threshold

       unit name = frames"
   ::= {er1645v2Lan2FGUOamEntry 84083456}

er1645v2Lan2FGUOamEventsErroredFrameSecondsEnabled OBJECT-TYPE
   SYNTAX      INTEGER
               {
               no (0),
               yes (1)
               }
   MAX-ACCESS  read-write
   STATUS      current
   DESCRIPTION
      "Path: ethernet2.editConf.oam.events.erroredFrameSeconds.enabled

       Possibilities:
               no   (0)
               yes   (1)"
   ::= {er1645v2Lan2FGUOamEntry 84148480}

er1645v2Lan2FGUOamEventsErroredFrameSecondsWindow OBJECT-TYPE
   SYNTAX      Integer32
   UNITS       "100msec"
   MAX-ACCESS  read-write
   STATUS      current
   DESCRIPTION
      "Path: ethernet2.editConf.oam.events.erroredFrameSeconds.window

       unit name = 100msec"
   ::= {er1645v2Lan2FGUOamEntry 84148736}

er1645v2Lan2FGUOamEventsErroredFrameSecondsThreshold OBJECT-TYPE
   SYNTAX      Integer32
   UNITS       "frames"
   MAX-ACCESS  read-write
   STATUS      current
   DESCRIPTION
      "Path: ethernet2.editConf.oam.events.erroredFrameSeconds.threshold

       unit name = frames"
   ::= {er1645v2Lan2FGUOamEntry 84148992}

er1645v2Lan2FGUOamEventsDyingGasp OBJECT-TYPE
   SYNTAX      INTEGER
               {
               disabled (0),
               enabled (1)
               }
   MAX-ACCESS  read-write
   STATUS      current
   DESCRIPTION
      "Path: ethernet2.editConf.oam.events.dyingGasp

       Possibilities:
               disabled   (0)
               enabled   (1)"
   ::= {er1645v2Lan2FGUOamEntry 84213760}

er1645v2Lan2FGUOamEventsCriticalEvent OBJECT-TYPE
   SYNTAX      INTEGER
               {
               disabled (0),
               enabled (1)
               }
   MAX-ACCESS  read-write
   STATUS      current
   DESCRIPTION
      "Path: ethernet2.editConf.oam.events.criticalEvent

       Possibilities:
               disabled   (0)
               enabled   (1)"
   ::= {er1645v2Lan2FGUOamEntry 84279296}


er1645v2Lan2FGULst OBJECT IDENTIFIER ::= {er1645v2Lan2FGU 12}

er1645v2Lan2FGULstSSC OBJECT IDENTIFIER ::= {er1645v2Lan2FGULst 1}

er1645v2Lan2FGULstEntry OBJECT IDENTIFIER ::= {er1645v2Lan2FGULstSSC 1}

er1645v2Lan2FGULstTrackedInterface OBJECT-TYPE
   SYNTAX      DisplayString
   MAX-ACCESS  read-write
   STATUS      current
   DESCRIPTION
      "Path: ethernet2.editConf.linkStateTracking.trackedInterface"
   ::= {er1645v2Lan2FGULstEntry 16777216}


er1645v2Lan2FGUDot1x OBJECT IDENTIFIER ::= {er1645v2Lan2FGU 191}

er1645v2Lan2FGUDot1xSSC OBJECT IDENTIFIER ::= {er1645v2Lan2FGUDot1x 1}

er1645v2Lan2FGUDot1xEntry OBJECT IDENTIFIER ::= {er1645v2Lan2FGUDot1xSSC 1}

er1645v2Lan2FGUDot1xMode OBJECT-TYPE
   SYNTAX      INTEGER
               {
               inactive (0),
               auto (1)
               }
   MAX-ACCESS  read-write
   STATUS      current
   DESCRIPTION
      "Path: ethernet2.editConf.dot1x.mode

       Possibilities:
               inactive   (0)
               auto   (1)"
   ::= {er1645v2Lan2FGUDot1xEntry 16777216}

er1645v2Lan2FGUDot1xMaxHosts OBJECT-TYPE
   SYNTAX      Integer32
   MAX-ACCESS  read-write
   STATUS      current
   DESCRIPTION
      "Path: ethernet2.editConf.dot1x.maxHosts"
   ::= {er1645v2Lan2FGUDot1xEntry 33554432}

er1645v2Lan2FGUDot1xReAuthentication OBJECT-TYPE
   SYNTAX      INTEGER
               {
               disabled (0),
               enabled (1)
               }
   MAX-ACCESS  read-write
   STATUS      current
   DESCRIPTION
      "Path: ethernet2.editConf.dot1x.reAuthentication

       Possibilities:
               disabled   (0)
               enabled   (1)"
   ::= {er1645v2Lan2FGUDot1xEntry 50331648}

er1645v2Lan2FGUDot1xReAuthPeriod OBJECT-TYPE
   SYNTAX      TimeTicks
   MAX-ACCESS  read-write
   STATUS      current
   DESCRIPTION
      "Path: ethernet2.editConf.dot1x.reAuthPeriod

       Time in centi-second."
   ::= {er1645v2Lan2FGUDot1xEntry 67108864}

er1645v2Lan2FGUDot1xQuietPeriod OBJECT-TYPE
   SYNTAX      TimeTicks
   MAX-ACCESS  read-write
   STATUS      current
   DESCRIPTION
      "Path: ethernet2.editConf.dot1x.quietPeriod

       Time in centi-second."
   ::= {er1645v2Lan2FGUDot1xEntry 83886080}

er1645v2Lan2FGUDot1xSupplTimeout OBJECT-TYPE
   SYNTAX      TimeTicks
   MAX-ACCESS  read-write
   STATUS      current
   DESCRIPTION
      "Path: ethernet2.editConf.dot1x.supplTimeout

       Time in centi-second."
   ::= {er1645v2Lan2FGUDot1xEntry 100663296}

er1645v2Lan2FGUDot1xServerTimeout OBJECT-TYPE
   SYNTAX      TimeTicks
   MAX-ACCESS  read-write
   STATUS      current
   DESCRIPTION
      "Path: ethernet2.editConf.dot1x.serverTimeout

       Time in centi-second."
   ::= {er1645v2Lan2FGUDot1xEntry 117440512}

er1645v2Lan2FGUDot1xMaxReqCount OBJECT-TYPE
   SYNTAX      Integer32
   MAX-ACCESS  read-write
   STATUS      current
   DESCRIPTION
      "Path: ethernet2.editConf.dot1x.maxReqCount"
   ::= {er1645v2Lan2FGUDot1xEntry 134217728}


er1645v2Lan2FGUMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet2.editConf.mode
       Info: routing and/or bridging or ipV6 or multilink selection

       Possibilities:
               bridging   (0)
               routing   (1)
               routingAndBridging   (2)
               ipV6   (3)
               ipV6/ipV4   (4)
               multilink   (5)"
   ::= {er1645v2Lan2FGU 29}


er1645v2Lan2FGUIpV6 OBJECT IDENTIFIER ::= {er1645v2Lan2FGU 15}

er1645v2Lan2FGUIpV6SSC OBJECT IDENTIFIER ::= {er1645v2Lan2FGUIpV6 1}

er1645v2Lan2FGUIpV6Entry OBJECT IDENTIFIER ::= {er1645v2Lan2FGUIpV6SSC 1}

er1645v2Lan2FGUIpV6VrfRouter OBJECT-TYPE
   SYNTAX      DisplayString
   MAX-ACCESS  read-write
   STATUS      current
   DESCRIPTION
      "Path: ethernet2.editConf.ipV6.vrfRouter"
   ::= {er1645v2Lan2FGUIpV6Entry 16777216}

er1645v2Lan2FGUIpV6AddrAutoConfigNrDupAddrDetects OBJECT-TYPE
   SYNTAX      Integer32
   MAX-ACCESS  read-write
   STATUS      current
   DESCRIPTION
      "Path: ethernet2.editConf.ipV6.addrAutoConfig.nrDupAddrDetects"
   ::= {er1645v2Lan2FGUIpV6Entry 67174400}

er1645v2Lan2FGUIpV6AddrAutoConfigAcceptRa OBJECT-TYPE
   SYNTAX      INTEGER
               {
               disabled (0),
               enabled (1)
               }
   MAX-ACCESS  read-write
   STATUS      current
   DESCRIPTION
      "Path: ethernet2.editConf.ipV6.addrAutoConfig.acceptRa

       Possibilities:
               disabled   (0)
               enabled   (1)"
   ::= {er1645v2Lan2FGUIpV6Entry 67239936}

er1645v2Lan2FGUIpV6AddrAutoConfigAcceptRaRdnss OBJECT-TYPE
   SYNTAX      INTEGER
               {
               disabled (0),
               enabled (1)
               }
   MAX-ACCESS  read-write
   STATUS      current
   DESCRIPTION
      "Path: ethernet2.editConf.ipV6.addrAutoConfig.acceptRaRdnss

       Possibilities:
               disabled   (0)
               enabled   (1)"
   ::= {er1645v2Lan2FGUIpV6Entry 67305472}

er1645v2Lan2FGUIpV6AddrAutoConfigAcceptRaDnssl OBJECT-TYPE
   SYNTAX      INTEGER
               {
               disabled (0),
               enabled (1)
               }
   MAX-ACCESS  read-write
   STATUS      current
   DESCRIPTION
      "Path: ethernet2.editConf.ipV6.addrAutoConfig.acceptRaDnssl

       Possibilities:
               disabled   (0)
               enabled   (1)"
   ::= {er1645v2Lan2FGUIpV6Entry 67371008}

er1645v2Lan2FGUIpV6DefaultRoute OBJECT-TYPE
   SYNTAX      INTEGER
               {
               disabled (0),
               enabled (1)
               }
   MAX-ACCESS  read-write
   STATUS      current
   DESCRIPTION
      "Path: ethernet2.editConf.ipV6.defaultRoute

       Possibilities:
               disabled   (0)
               enabled   (1)"
   ::= {er1645v2Lan2FGUIpV6Entry 83886080}

er1645v2Lan2FGUIpV6RaSend OBJECT-TYPE
   SYNTAX      INTEGER
               {
               disabled (0),
               enabled (1)
               }
   MAX-ACCESS  read-write
   STATUS      current
   DESCRIPTION
      "Path: ethernet2.editConf.ipV6.ra.send

       Possibilities:
               disabled   (0)
               enabled   (1)"
   ::= {er1645v2Lan2FGUIpV6Entry 100728832}

er1645v2Lan2FGUIpV6RaMinInterval OBJECT-TYPE
   SYNTAX      TimeTicks
   MAX-ACCESS  read-write
   STATUS      current
   DESCRIPTION
      "Path: ethernet2.editConf.ipV6.ra.minInterval

       Time in centi-second."
   ::= {er1645v2Lan2FGUIpV6Entry 100794368}

er1645v2Lan2FGUIpV6RaMaxInterval OBJECT-TYPE
   SYNTAX      TimeTicks
   MAX-ACCESS  read-write
   STATUS      current
   DESCRIPTION
      "Path: ethernet2.editConf.ipV6.ra.maxInterval

       Time in centi-second."
   ::= {er1645v2Lan2FGUIpV6Entry 100859904}

er1645v2Lan2FGUIpV6RaManagedFlag OBJECT-TYPE
   SYNTAX      INTEGER
               {
               disabled (0),
               enabled (1)
               }
   MAX-ACCESS  read-write
   STATUS      current
   DESCRIPTION
      "Path: ethernet2.editConf.ipV6.ra.managedFlag

       Possibilities:
               disabled   (0)
               enabled   (1)"
   ::= {er1645v2Lan2FGUIpV6Entry 100925440}

er1645v2Lan2FGUIpV6RaOtherConfFlag OBJECT-TYPE
   SYNTAX      INTEGER
               {
               disabled (0),
               enabled (1)
               }
   MAX-ACCESS  read-write
   STATUS      current
   DESCRIPTION
      "Path: ethernet2.editConf.ipV6.ra.otherConfFlag

       Possibilities:
               disabled   (0)
               enabled   (1)"
   ::= {er1645v2Lan2FGUIpV6Entry 100990976}

er1645v2Lan2FGUIpV6RaLinkMtu OBJECT-TYPE
   SYNTAX      Integer32
   MAX-ACCESS  read-write
   STATUS      current
   DESCRIPTION
      "Path: ethernet2.editConf.ipV6.ra.linkMtu"
   ::= {er1645v2Lan2FGUIpV6Entry 101056512}

er1645v2Lan2FGUIpV6RaReachableTime OBJECT-TYPE
   SYNTAX      TimeTicks
   MAX-ACCESS  read-write
   STATUS      current
   DESCRIPTION
      "Path: ethernet2.editConf.ipV6.ra.reachableTime

       Time in centi-second."
   ::= {er1645v2Lan2FGUIpV6Entry 101122048}

er1645v2Lan2FGUIpV6RaRetransmitTime OBJECT-TYPE
   SYNTAX      TimeTicks
   MAX-ACCESS  read-write
   STATUS      current
   DESCRIPTION
      "Path: ethernet2.editConf.ipV6.ra.retransmitTime

       Time in centi-second."
   ::= {er1645v2Lan2FGUIpV6Entry 101187584}

er1645v2Lan2FGUIpV6RaHopLimit OBJECT-TYPE
   SYNTAX      Integer32
   MAX-ACCESS  read-write
   STATUS      current
   DESCRIPTION
      "Path: ethernet2.editConf.ipV6.ra.hopLimit"
   ::= {er1645v2Lan2FGUIpV6Entry 101253120}

er1645v2Lan2FGUIpV6RaDefaultLifeTime OBJECT-TYPE
   SYNTAX      TimeTicks
   MAX-ACCESS  read-write
   STATUS      current
   DESCRIPTION
      "Path: ethernet2.editConf.ipV6.ra.defaultLifeTime

       Time in centi-second."
   ::= {er1645v2Lan2FGUIpV6Entry 101318656}

er1645v2Lan2FGUIpV6RaDnsOptionsRdnssLifeTime OBJECT-TYPE
   SYNTAX      TimeTicks
   MAX-ACCESS  read-write
   STATUS      current
   DESCRIPTION
      "Path: ethernet2.editConf.ipV6.ra.dnsOptions.rdnss.lifeTime

       Time in centi-second."
   ::= {er1645v2Lan2FGUIpV6Entry 101393408}

er1645v2Lan2FGUIpV6RaDnsOptionsRdnssImportServers OBJECT-TYPE
   SYNTAX      INTEGER
               {
               disabled (0),
               enabled (1)
               }
   MAX-ACCESS  read-write
   STATUS      current
   DESCRIPTION
      "Path: ethernet2.editConf.ipV6.ra.dnsOptions.rdnss.importServers

       Possibilities:
               disabled   (0)
               enabled   (1)"
   ::= {er1645v2Lan2FGUIpV6Entry 101395456}

er1645v2Lan2FGUIpV6RaDnsOptionsDnsslLifeTime OBJECT-TYPE
   SYNTAX      TimeTicks
   MAX-ACCESS  read-write
   STATUS      current
   DESCRIPTION
      "Path: ethernet2.editConf.ipV6.ra.dnsOptions.dnssl.lifeTime

       Time in centi-second."
   ::= {er1645v2Lan2FGUIpV6Entry 101401600}

er1645v2Lan2FGUIpV6RaDnsOptionsDnsslImportDomains OBJECT-TYPE
   SYNTAX      INTEGER
               {
               disabled (0),
               enabled (1)
               }
   MAX-ACCESS  read-write
   STATUS      current
   DESCRIPTION
      "Path: ethernet2.editConf.ipV6.ra.dnsOptions.dnssl.importDomains

       Possibilities:
               disabled   (0)
               enabled   (1)"
   ::= {er1645v2Lan2FGUIpV6Entry 101403648}

er1645v2Lan2FGUIpV6RsSend OBJECT-TYPE
   SYNTAX      INTEGER
               {
               disabled (0),
               enabled (1)
               }
   MAX-ACCESS  read-write
   STATUS      current
   DESCRIPTION
      "Path: ethernet2.editConf.ipV6.rs.send

       Possibilities:
               disabled   (0)
               enabled   (1)"
   ::= {er1645v2Lan2FGUIpV6Entry 335609856}

er1645v2Lan2FGUIpV6RsMaxRandomDelay OBJECT-TYPE
   SYNTAX      TimeTicks
   MAX-ACCESS  read-write
   STATUS      current
   DESCRIPTION
      "Path: ethernet2.editConf.ipV6.rs.maxRandomDelay

       Time in centi-second."
   ::= {er1645v2Lan2FGUIpV6Entry 335675392}

er1645v2Lan2FGUIpV6RsInterval OBJECT-TYPE
   SYNTAX      TimeTicks
   MAX-ACCESS  read-write
   STATUS      current
   DESCRIPTION
      "Path: ethernet2.editConf.ipV6.rs.interval

       Time in centi-second."
   ::= {er1645v2Lan2FGUIpV6Entry 335740928}

er1645v2Lan2FGUIpV6RsMaxSolicitations OBJECT-TYPE
   SYNTAX      Integer32
   MAX-ACCESS  read-write
   STATUS      current
   DESCRIPTION
      "Path: ethernet2.editConf.ipV6.rs.maxSolicitations"
   ::= {er1645v2Lan2FGUIpV6Entry 335806464}

er1645v2Lan2FGUIpV6TrafficPolicyInbound OBJECT-TYPE
   SYNTAX      DisplayString
   MAX-ACCESS  read-write
   STATUS      current
   DESCRIPTION
      "Path: ethernet2.editConf.ipV6.trafficPolicy.inbound"
   ::= {er1645v2Lan2FGUIpV6Entry 184614912}

er1645v2Lan2FGUIpV6TrafficPolicyOutbound OBJECT-TYPE
   SYNTAX      DisplayString
   MAX-ACCESS  read-write
   STATUS      current
   DESCRIPTION
      "Path: ethernet2.editConf.ipV6.trafficPolicy.outbound"
   ::= {er1645v2Lan2FGUIpV6Entry 184680448}

er1645v2Lan2FGUIpV6FirewallZone OBJECT-TYPE
   SYNTAX      DisplayString
   MAX-ACCESS  read-write
   STATUS      current
   DESCRIPTION
      "Path: ethernet2.editConf.ipV6.firewall.zone"
   ::= {er1645v2Lan2FGUIpV6Entry 201392128}

er1645v2Lan2FGUIpV6DhcpClientAddrAC OBJECT-TYPE
   SYNTAX      INTEGER
               {
               disabled (0),
               enabled (1)
               }
   MAX-ACCESS  read-write
   STATUS      current
   DESCRIPTION
      "Path: ethernet2.editConf.ipV6.dhcp.client.addrAutoConfig

       Possibilities:
               disabled   (0)
               enabled   (1)"
   ::= {er1645v2Lan2FGUIpV6Entry 170131456}

er1645v2Lan2FGUIpV6DhcpClientPrDelMode OBJECT-TYPE
   SYNTAX      INTEGER
               {
               disabled (0),
               enabled (1)
               }
   MAX-ACCESS  read-write
   STATUS      current
   DESCRIPTION
      "Path: ethernet2.editConf.ipV6.dhcp.client.pd.mode

       Possibilities:
               disabled   (0)
               enabled   (1)"
   ::= {er1645v2Lan2FGUIpV6Entry 170394624}

er1645v2Lan2FGUIpV6DhcpClientPrDelPool OBJECT-TYPE
   SYNTAX      DisplayString
   MAX-ACCESS  read-write
   STATUS      current
   DESCRIPTION
      "Path: ethernet2.editConf.ipV6.dhcp.client.pd.pool"
   ::= {er1645v2Lan2FGUIpV6Entry 170395648}

er1645v2Lan2FGUIpV6DhcpClientPrDelPdExclOpt OBJECT-TYPE
   SYNTAX      INTEGER
               {
               disabled (0),
               enabled (1)
               }
   MAX-ACCESS  read-write
   STATUS      current
   DESCRIPTION
      "Path: ethernet2.editConf.ipV6.dhcp.client.pd.pdExclOpt

       Possibilities:
               disabled   (0)
               enabled   (1)"
   ::= {er1645v2Lan2FGUIpV6Entry 170396672}

er1645v2Lan2FGUIpV6DhcpClientDnsServerPref OBJECT-TYPE
   SYNTAX      Integer32
   MAX-ACCESS  read-write
   STATUS      current
   DESCRIPTION
      "Path: ethernet2.editConf.ipV6.dhcp.client.dns.serverPref"
   ::= {er1645v2Lan2FGUIpV6Entry 170918912}

er1645v2Lan2FGUIpV6DhcpClientRapidCommit OBJECT-TYPE
   SYNTAX      INTEGER
               {
               disabled (0),
               enabled (1)
               }
   MAX-ACCESS  read-write
   STATUS      current
   DESCRIPTION
      "Path: ethernet2.editConf.ipV6.dhcp.client.rapidCommit

       Possibilities:
               disabled   (0)
               enabled   (1)"
   ::= {er1645v2Lan2FGUIpV6Entry 170655744}

er1645v2Lan2FGUIpV6DhcpClientTimersSolTimeOut OBJECT-TYPE
   SYNTAX      TimeTicks
   MAX-ACCESS  read-write
   STATUS      current
   DESCRIPTION
      "Path: ethernet2.editConf.ipV6.dhcp.client.timers.solTimeOut

       Time in centi-second."
   ::= {er1645v2Lan2FGUIpV6Entry 171181056}

er1645v2Lan2FGUIpV6DhcpClientTimersSolMaxRt OBJECT-TYPE
   SYNTAX      TimeTicks
   MAX-ACCESS  read-write
   STATUS      current
   DESCRIPTION
      "Path: ethernet2.editConf.ipV6.dhcp.client.timers.solMaxRt

       Time in centi-second."
   ::= {er1645v2Lan2FGUIpV6Entry 171182080}

er1645v2Lan2FGUIpV6DhcpClientTimersInfoRefresh OBJECT-TYPE
   SYNTAX      TimeTicks
   MAX-ACCESS  read-write
   STATUS      current
   DESCRIPTION
      "Path: ethernet2.editConf.ipV6.dhcp.client.timers.infoRefresh

       Time in centi-second."
   ::= {er1645v2Lan2FGUIpV6Entry 171183104}

er1645v2Lan2FGUIpV6DhcpServerMode OBJECT-TYPE
   SYNTAX      INTEGER
               {
               disabled (0),
               enabled (1)
               }
   MAX-ACCESS  read-write
   STATUS      current
   DESCRIPTION
      "Path: ethernet2.editConf.ipV6.dhcp.server.mode

       Possibilities:
               disabled   (0)
               enabled   (1)"
   ::= {er1645v2Lan2FGUIpV6Entry 172228608}

er1645v2Lan2FGUIpV6DhcpServerPreference OBJECT-TYPE
   SYNTAX      Integer32
   MAX-ACCESS  read-write
   STATUS      current
   DESCRIPTION
      "Path: ethernet2.editConf.ipV6.dhcp.server.preference"
   ::= {er1645v2Lan2FGUIpV6Entry 172490752}

er1645v2Lan2FGUIpV6DhcpServerPool OBJECT-TYPE
   SYNTAX      DisplayString
   MAX-ACCESS  read-write
   STATUS      current
   DESCRIPTION
      "Path: ethernet2.editConf.ipV6.dhcp.server.pool"
   ::= {er1645v2Lan2FGUIpV6Entry 172752896}

er1645v2Lan2FGUIpV6DhcpServerRapidCommit OBJECT-TYPE
   SYNTAX      INTEGER
               {
               disabled (0),
               enabled (1)
               }
   MAX-ACCESS  read-write
   STATUS      current
   DESCRIPTION
      "Path: ethernet2.editConf.ipV6.dhcp.server.rapidCommit

       Possibilities:
               disabled   (0)
               enabled   (1)"
   ::= {er1645v2Lan2FGUIpV6Entry 173015040}

er1645v2Lan2FGUIpV6DhcpServerTimersInfoRefresh OBJECT-TYPE
   SYNTAX      TimeTicks
   MAX-ACCESS  read-write
   STATUS      current
   DESCRIPTION
      "Path: ethernet2.editConf.ipV6.dhcp.server.timers.infoRefresh

       Time in centi-second."
   ::= {er1645v2Lan2FGUIpV6Entry 173278208}

er1645v2Lan2FGUIpV6DhcpRelayMode OBJECT-TYPE
   SYNTAX      INTEGER
               {
               disabled (0),
               enabled (1)
               }
   MAX-ACCESS  read-write
   STATUS      current
   DESCRIPTION
      "Path: ethernet2.editConf.ipV6.dhcp.relay.mode

       Possibilities:
               disabled   (0)
               enabled   (1)"
   ::= {er1645v2Lan2FGUIpV6Entry 174071808}

er1645v2Lan2FGUIpV6SendRedirect OBJECT-TYPE
   SYNTAX      INTEGER
               {
               disabled (0),
               enabled (1)
               }
   MAX-ACCESS  read-write
   STATUS      current
   DESCRIPTION
      "Path: ethernet2.editConf.ipV6.sendRedirect

       Possibilities:
               disabled   (0)
               enabled   (1)"
   ::= {er1645v2Lan2FGUIpV6Entry 117440512}

er1645v2Lan2FGUIpV6LinkMtu OBJECT-TYPE
   SYNTAX      Integer32
   MAX-ACCESS  read-write
   STATUS      current
   DESCRIPTION
      "Path: ethernet2.editConf.ipV6.linkMtu"
   ::= {er1645v2Lan2FGUIpV6Entry 134217728}

er1645v2Lan2FGUIpV6InterfaceId OBJECT-TYPE
   SYNTAX      OCTET STRING
   MAX-ACCESS  read-write
   STATUS      current
   DESCRIPTION
      "Path: ethernet2.editConf.ipV6.interfaceId"
   ::= {er1645v2Lan2FGUIpV6Entry 150994944}

er1645v2Lan2FGUIpV6MF OBJECT-TYPE
   SYNTAX      Integer32
   MAX-ACCESS  read-write
   STATUS      current
   DESCRIPTION
      "Path: ethernet2.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGUIpV6Entry 285212672}

er1645v2Lan2FGUIpV6IcmpMessagesNoRoute OBJECT-TYPE
   SYNTAX      INTEGER
               {
               disabled (0),
               enabled (1)
               }
   MAX-ACCESS  read-write
   STATUS      current
   DESCRIPTION
      "Path: ethernet2.editConf.ipV6.icmpMessages.noRoute

       Possibilities:
               disabled   (0)
               enabled   (1)"
   ::= {er1645v2Lan2FGUIpV6Entry 302055424}

er1645v2Lan2FGUIpV6IcmpMessagesBeyondScope OBJECT-TYPE
   SYNTAX      INTEGER
               {
               disabled (0),
               enabled (1)
               }
   MAX-ACCESS  read-write
   STATUS      current
   DESCRIPTION
      "Path: ethernet2.editConf.ipV6.icmpMessages.beyondScope

       Possibilities:
               disabled   (0)
               enabled   (1)"
   ::= {er1645v2Lan2FGUIpV6Entry 302186496}

er1645v2Lan2FGUIpV6IcmpMessagesAddressUnreachable OBJECT-TYPE
   SYNTAX      INTEGER
               {
               disabled (0),
               enabled (1)
               }
   MAX-ACCESS  read-write
   STATUS      current
   DESCRIPTION
      "Path: ethernet2.editConf.ipV6.icmpMessages.addressUnreachable

       Possibilities:
               disabled   (0)
               enabled   (1)"
   ::= {er1645v2Lan2FGUIpV6Entry 302252032}

er1645v2Lan2FGUIpV6IcmpMessagesPortUnreachable OBJECT-TYPE
   SYNTAX      INTEGER
               {
               disabled (0),
               enabled (1)
               }
   MAX-ACCESS  read-write
   STATUS      current
   DESCRIPTION
      "Path: ethernet2.editConf.ipV6.icmpMessages.portUnreachable

       Possibilities:
               disabled   (0)
               enabled   (1)"
   ::= {er1645v2Lan2FGUIpV6Entry 302317568}

er1645v2Lan2FGUIpV6IcmpMessagesPacketTooBig OBJECT-TYPE
   SYNTAX      INTEGER
               {
               disabled (0),
               enabled (1)
               }
   MAX-ACCESS  read-write
   STATUS      current
   DESCRIPTION
      "Path: ethernet2.editConf.ipV6.icmpMessages.packetTooBig

       Possibilities:
               disabled   (0)
               enabled   (1)"
   ::= {er1645v2Lan2FGUIpV6Entry 302645248}

er1645v2Lan2FGUIpV6IcmpMessagesHopLimitExceeded OBJECT-TYPE
   SYNTAX      INTEGER
               {
               disabled (0),
               enabled (1)
               }
   MAX-ACCESS  read-write
   STATUS      current
   DESCRIPTION
      "Path: ethernet2.editConf.ipV6.icmpMessages.hopLimitExceeded

       Possibilities:
               disabled   (0)
               enabled   (1)"
   ::= {er1645v2Lan2FGUIpV6Entry 303300608}

er1645v2Lan2FGUIpV6IcmpMessagesFragTimeExceeded OBJECT-TYPE
   SYNTAX      INTEGER
               {
               disabled (0),
               enabled (1)
               }
   MAX-ACCESS  read-write
   STATUS      current
   DESCRIPTION
      "Path: ethernet2.editConf.ipV6.icmpMessages.fragTimeExceeded

       Possibilities:
               disabled   (0)
               enabled   (1)"
   ::= {er1645v2Lan2FGUIpV6Entry 303366144}

er1645v2Lan2FGUIpV6IcmpMessagesHeaderFieldErr OBJECT-TYPE
   SYNTAX      INTEGER
               {
               disabled (0),
               enabled (1)
               }
   MAX-ACCESS  read-write
   STATUS      current
   DESCRIPTION
      "Path: ethernet2.editConf.ipV6.icmpMessages.headerFieldErr

       Possibilities:
               disabled   (0)
               enabled   (1)"
   ::= {er1645v2Lan2FGUIpV6Entry 303955968}

er1645v2Lan2FGUIpV6IcmpMessagesOptionUnrecognized OBJECT-TYPE
   SYNTAX      INTEGER
               {
               disabled (0),
               enabled (1)
               }
   MAX-ACCESS  read-write
   STATUS      current
   DESCRIPTION
      "Path: ethernet2.editConf.ipV6.icmpMessages.optionUnrecognized

       Possibilities:
               disabled   (0)
               enabled   (1)"
   ::= {er1645v2Lan2FGUIpV6Entry 304087040}

er1645v2Lan2FGUIpV6IcmpMessagesRedirect OBJECT-TYPE
   SYNTAX      INTEGER
               {
               disabled (0),
               enabled (1)
               }
   MAX-ACCESS  read-write
   STATUS      current
   DESCRIPTION
      "Path: ethernet2.editConf.ipV6.icmpMessages.redirect

       Possibilities:
               disabled   (0)
               enabled   (1)"
   ::= {er1645v2Lan2FGUIpV6Entry 304611328}

er1645v2Lan2FGUIpV6Addresses OBJECT-TYPE
   SYNTAX      SEQUENCE OF Er1645v2Lan2FGUIpV6AddressesEntry
   MAX-ACCESS  not-accessible
   STATUS      current
   DESCRIPTION
      ""
   ::= {er1645v2Lan2FGUIpV6 50331648}

er1645v2Lan2FGUIpV6AddressesEntry OBJECT-TYPE
   SYNTAX      Er1645v2Lan2FGUIpV6AddressesEntry
   MAX-ACCESS  not-accessible
   STATUS      current
   DESCRIPTION
      ""
   INDEX      { er1645v2Lan2FGUIpV6AddressesTableIx }
   ::= {er1645v2Lan2FGUIpV6Addresses 1}

Er1645v2Lan2FGUIpV6AddressesEntry ::=
   SEQUENCE
      {
      er1645v2Lan2FGUIpV6AddressesActions
         VariableLengthTableActions,
      er1645v2Lan2FGUIpV6AddressesTableIx
         TableIndex,
      er1645v2Lan2FGUIpV6AddressesType
         INTEGER,
      er1645v2Lan2FGUIpV6AddressesAddress
         Ipv6Address,
      er1645v2Lan2FGUIpV6AddressesPrefixLength
         Integer32,
      er1645v2Lan2FGUIpV6AddressesGeneralPrefix
         DisplayString,
      er1645v2Lan2FGUIpV6AddressesRaSend
         INTEGER,
      er1645v2Lan2FGUIpV6AddressesRaOnLinkFlag
         INTEGER,
      er1645v2Lan2FGUIpV6AddressesRaAutoFlag
         INTEGER,
      er1645v2Lan2FGUIpV6AddressesRaValidLifeTime
         TimeTicks,
      er1645v2Lan2FGUIpV6AddressesRaValidLTMode
         INTEGER,
      er1645v2Lan2FGUIpV6AddressesRaPrefLifeTime
         TimeTicks,
      er1645v2Lan2FGUIpV6AddressesRaPrefLTMode
         INTEGER
      }

er1645v2Lan2FGUIpV6AddressesActions OBJECT-TYPE
   SYNTAX      VariableLengthTableActions
   MAX-ACCESS  read-write
   STATUS      current
   DESCRIPTION
      "By way of this field, some manipulations
       on this table may be performed."
   ::= {er1645v2Lan2FGUIpV6AddressesEntry 2}

er1645v2Lan2FGUIpV6AddressesTableIx OBJECT-TYPE
   SYNTAX      TableIndex
   MAX-ACCESS  not-accessible
   STATUS      current
   DESCRIPTION
      ""
   ::= {er1645v2Lan2FGUIpV6AddressesEntry 11}

er1645v2Lan2FGUIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.ipV6.addresses.type

       Possibilities:
               unicast   (0)
               eui64   (1)
               anycast   (2)
               linkLocal   (3)
               generalPrefix   (4)"
   ::= {er1645v2Lan2FGUIpV6AddressesEntry 50331648}

er1645v2Lan2FGUIpV6AddressesAddress OBJECT-TYPE
   SYNTAX      Ipv6Address
   MAX-ACCESS  read-write
   STATUS      current
   DESCRIPTION
      "Path: ethernet2.editConf.ipV6.addresses.address

       ipv6 address"
   ::= {er1645v2Lan2FGUIpV6AddressesEntry 16777216}

er1645v2Lan2FGUIpV6AddressesPrefixLength OBJECT-TYPE
   SYNTAX      Integer32
   MAX-ACCESS  read-write
   STATUS      current
   DESCRIPTION
      "Path: ethernet2.editConf.ipV6.addresses.prefixLength"
   ::= {er1645v2Lan2FGUIpV6AddressesEntry 33554432}

er1645v2Lan2FGUIpV6AddressesGeneralPrefix OBJECT-TYPE
   SYNTAX      DisplayString
   MAX-ACCESS  read-write
   STATUS      current
   DESCRIPTION
      "Path: ethernet2.editConf.ipV6.addresses.generalPrefix"
   ::= {er1645v2Lan2FGUIpV6AddressesEntry 83886080}

er1645v2Lan2FGUIpV6AddressesRaSend OBJECT-TYPE
   SYNTAX      INTEGER
               {
               disabled (0),
               enabled (1)
               }
   MAX-ACCESS  read-write
   STATUS      current
   DESCRIPTION
      "Path: ethernet2.editConf.ipV6.addresses.ra.send

       Possibilities:
               disabled   (0)
               enabled   (1)"
   ::= {er1645v2Lan2FGUIpV6AddressesEntry 67174400}

er1645v2Lan2FGUIpV6AddressesRaOnLinkFlag OBJECT-TYPE
   SYNTAX      INTEGER
               {
               disabled (0),
               enabled (1)
               }
   MAX-ACCESS  read-write
   STATUS      current
   DESCRIPTION
      "Path: ethernet2.editConf.ipV6.addresses.ra.onLinkFlag

       Possibilities:
               disabled   (0)
               enabled   (1)"
   ::= {er1645v2Lan2FGUIpV6AddressesEntry 67371008}

er1645v2Lan2FGUIpV6AddressesRaAutoFlag OBJECT-TYPE
   SYNTAX      INTEGER
               {
               disabled (0),
               enabled (1)
               }
   MAX-ACCESS  read-write
   STATUS      current
   DESCRIPTION
      "Path: ethernet2.editConf.ipV6.addresses.ra.autonomousFlag

       Possibilities:
               disabled   (0)
               enabled   (1)"
   ::= {er1645v2Lan2FGUIpV6AddressesEntry 67567616}

er1645v2Lan2FGUIpV6AddressesRaValidLifeTime OBJECT-TYPE
   SYNTAX      TimeTicks
   MAX-ACCESS  read-write
   STATUS      current
   DESCRIPTION
      "Path: ethernet2.editConf.ipV6.addresses.ra.validLifeTime

       Time in centi-second."
   ::= {er1645v2Lan2FGUIpV6AddressesEntry 67239936}

er1645v2Lan2FGUIpV6AddressesRaValidLTMode OBJECT-TYPE
   SYNTAX      INTEGER
               {
               fixed (0),
               infinite (2)
               }
   MAX-ACCESS  read-write
   STATUS      current
   DESCRIPTION
      "Path: ethernet2.editConf.ipV6.addresses.ra.validLifeTimeMode

       Possibilities:
               fixed   (0)
               infinite   (2)"
   ::= {er1645v2Lan2FGUIpV6AddressesEntry 67305472}

er1645v2Lan2FGUIpV6AddressesRaPrefLifeTime OBJECT-TYPE
   SYNTAX      TimeTicks
   MAX-ACCESS  read-write
   STATUS      current
   DESCRIPTION
      "Path: ethernet2.editConf.ipV6.addresses.ra.prefLifeTime

       Time in centi-second."
   ::= {er1645v2Lan2FGUIpV6AddressesEntry 67436544}

er1645v2Lan2FGUIpV6AddressesRaPrefLTMode OBJECT-TYPE
   SYNTAX      INTEGER
               {
               fixed (0),
               infinite (2)
               }
   MAX-ACCESS  read-write
   STATUS      current
   DESCRIPTION
      "Path: ethernet2.editConf.ipV6.addresses.ra.prefLifeTimeMode

       Possibilities:
               fixed   (0)
               infinite   (2)"
   ::= {er1645v2Lan2FGUIpV6AddressesEntry 67502080}

er1645v2Lan2FGUIpV6RaDnsOptionsRdnssServers OBJECT-TYPE
   SYNTAX      SEQUENCE OF Er1645v2Lan2FGUIpV6RaDnsOptionsRdnssServersEntry
   MAX-ACCESS  not-accessible
   STATUS      current
   DESCRIPTION
      ""
   ::= {er1645v2Lan2FGUIpV6 101394432}

er1645v2Lan2FGUIpV6RaDnsOptionsRdnssServersEntry OBJECT-TYPE
   SYNTAX      Er1645v2Lan2FGUIpV6RaDnsOptionsRdnssServersEntry
   MAX-ACCESS  not-accessible
   STATUS      current
   DESCRIPTION
      ""
   INDEX      { er1645v2Lan2FGUIpV6RaDnsOptionsRdnssServersTableIx }
   ::= {er1645v2Lan2FGUIpV6RaDnsOptionsRdnssServers 1}

Er1645v2Lan2FGUIpV6RaDnsOptionsRdnssServersEntry ::=
   SEQUENCE
      {
      er1645v2Lan2FGUIpV6RaDnsOptionsRdnssServersActions
         VariableLengthTableActions,
      er1645v2Lan2FGUIpV6RaDnsOptionsRdnssServersTableIx
         TableIndex,
      er1645v2Lan2FGUIpV6RaDnsOptionsRdnssServersAddress
         Ipv6Address
      }

er1645v2Lan2FGUIpV6RaDnsOptionsRdnssServersActions OBJECT-TYPE
   SYNTAX      VariableLengthTableActions
   MAX-ACCESS  read-write
   STATUS      current
   DESCRIPTION
      "By way of this field, some manipulations
       on this table may be performed."
   ::= {er1645v2Lan2FGUIpV6RaDnsOptionsRdnssServersEntry 2}

er1645v2Lan2FGUIpV6RaDnsOptionsRdnssServersTableIx OBJECT-TYPE
   SYNTAX      TableIndex
   MAX-ACCESS  not-accessible
   STATUS      current
   DESCRIPTION
      ""
   ::= {er1645v2Lan2FGUIpV6RaDnsOptionsRdnssServersEntry 11}

er1645v2Lan2FGUIpV6RaDnsOptionsRdnssServersAddress OBJECT-TYPE
   SYNTAX      Ipv6Address
   MAX-ACCESS  read-write
   STATUS      current
   DESCRIPTION
      "Path: ethernet2.editConf.ipV6.ra.dnsOptions.rdnss.servers.address

       ipv6 address"
   ::= {er1645v2Lan2FGUIpV6RaDnsOptionsRdnssServersEntry 16777216}

er1645v2Lan2FGUIpV6RaDnsOptionsDnsslDomains OBJECT-TYPE
   SYNTAX      SEQUENCE OF Er1645v2Lan2FGUIpV6RaDnsOptionsDnsslDomainsEntry
   MAX-ACCESS  not-accessible
   STATUS      current
   DESCRIPTION
      ""
   ::= {er1645v2Lan2FGUIpV6 101402624}

er1645v2Lan2FGUIpV6RaDnsOptionsDnsslDomainsEntry OBJECT-TYPE
   SYNTAX      Er1645v2Lan2FGUIpV6RaDnsOptionsDnsslDomainsEntry
   MAX-ACCESS  not-accessible
   STATUS      current
   DESCRIPTION
      ""
   INDEX      { er1645v2Lan2FGUIpV6RaDnsOptionsDnsslDomainsTableIx }
   ::= {er1645v2Lan2FGUIpV6RaDnsOptionsDnsslDomains 1}

Er1645v2Lan2FGUIpV6RaDnsOptionsDnsslDomainsEntry ::=
   SEQUENCE
      {
      er1645v2Lan2FGUIpV6RaDnsOptionsDnsslDomainsActions
         VariableLengthTableActions,
      er1645v2Lan2FGUIpV6RaDnsOptionsDnsslDomainsTableIx
         TableIndex,
      er1645v2Lan2FGUIpV6RaDnsOptionsDnsslDomainsName
         DisplayString
      }

er1645v2Lan2FGUIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGUIpV6RaDnsOptionsDnsslDomainsEntry 2}

er1645v2Lan2FGUIpV6RaDnsOptionsDnsslDomainsTableIx OBJECT-TYPE
   SYNTAX      TableIndex
   MAX-ACCESS  not-accessible
   STATUS      current
   DESCRIPTION
      ""
   ::= {er1645v2Lan2FGUIpV6RaDnsOptionsDnsslDomainsEntry 11}

er1645v2Lan2FGUIpV6RaDnsOptionsDnsslDomainsName OBJECT-TYPE
   SYNTAX      DisplayString
   MAX-ACCESS  read-write
   STATUS      current
   DESCRIPTION
      "Path: ethernet2.editConf.ipV6.ra.dnsOptions.dnssl.domains.name"
   ::= {er1645v2Lan2FGUIpV6RaDnsOptionsDnsslDomainsEntry 16777216}

er1645v2Lan2FGUIpV6DhcpClientUserClassOpt OBJECT-TYPE
   SYNTAX      SEQUENCE OF Er1645v2Lan2FGUIpV6DhcpClientUserClassOptEntry
   MAX-ACCESS  not-accessible
   STATUS      current
   DESCRIPTION
      ""
   ::= {er1645v2Lan2FGUIpV6 171442176}

er1645v2Lan2FGUIpV6DhcpClientUserClassOptEntry OBJECT-TYPE
   SYNTAX      Er1645v2Lan2FGUIpV6DhcpClientUserClassOptEntry
   MAX-ACCESS  not-accessible
   STATUS      current
   DESCRIPTION
      ""
   INDEX      { er1645v2Lan2FGUIpV6DhcpClientUserClassOptTableIx }
   ::= {er1645v2Lan2FGUIpV6DhcpClientUserClassOpt 1}

Er1645v2Lan2FGUIpV6DhcpClientUserClassOptEntry ::=
   SEQUENCE
      {
      er1645v2Lan2FGUIpV6DhcpClientUserClassOptActions
         VariableLengthTableActions,
      er1645v2Lan2FGUIpV6DhcpClientUserClassOptTableIx
         TableIndex,
      er1645v2Lan2FGUIpV6DhcpClientUserClassOptValueAscii
         DisplayString,
      er1645v2Lan2FGUIpV6DhcpClientUserClassOptValueDecimal
         Integer32,
      er1645v2Lan2FGUIpV6DhcpClientUserClassOptValueHexData
         OCTET STRING
      }

er1645v2Lan2FGUIpV6DhcpClientUserClassOptActions OBJECT-TYPE
   SYNTAX      VariableLengthTableActions
   MAX-ACCESS  read-write
   STATUS      current
   DESCRIPTION
      "By way of this field, some manipulations
       on this table may be performed."
   ::= {er1645v2Lan2FGUIpV6DhcpClientUserClassOptEntry 2}

er1645v2Lan2FGUIpV6DhcpClientUserClassOptTableIx OBJECT-TYPE
   SYNTAX      TableIndex
   MAX-ACCESS  not-accessible
   STATUS      current
   DESCRIPTION
      ""
   ::= {er1645v2Lan2FGUIpV6DhcpClientUserClassOptEntry 11}

er1645v2Lan2FGUIpV6DhcpClientUserClassOptValueAscii OBJECT-TYPE
   SYNTAX      DisplayString
   MAX-ACCESS  read-write
   STATUS      current
   DESCRIPTION
      "Path: ethernet2.editConf.ipV6.dhcp.client.userClassOpt.value.ascii"
   ::= {er1645v2Lan2FGUIpV6DhcpClientUserClassOptEntry 16842752}

er1645v2Lan2FGUIpV6DhcpClientUserClassOptValueDecimal OBJECT-TYPE
   SYNTAX      Integer32
   MAX-ACCESS  read-write
   STATUS      current
   DESCRIPTION
      "Path: ethernet2.editConf.ipV6.dhcp.client.userClassOpt.value.decimal"
   ::= {er1645v2Lan2FGUIpV6DhcpClientUserClassOptEntry 16908288}

er1645v2Lan2FGUIpV6DhcpClientUserClassOptValueHexData OBJECT-TYPE
   SYNTAX      OCTET STRING
   MAX-ACCESS  read-write
   STATUS      current
   DESCRIPTION
      "Path: ethernet2.editConf.ipV6.dhcp.client.userClassOpt.value.hexData"
   ::= {er1645v2Lan2FGUIpV6DhcpClientUserClassOptEntry 16973824}

er1645v2Lan2FGUIpV6DhcpClientVendorCl OBJECT-TYPE
   SYNTAX      SEQUENCE OF Er1645v2Lan2FGUIpV6DhcpClientVendorClEntry
   MAX-ACCESS  not-accessible
   STATUS      current
   DESCRIPTION
      ""
   ::= {er1645v2Lan2FGUIpV6 171704320}

er1645v2Lan2FGUIpV6DhcpClientVendorClEntry OBJECT-TYPE
   SYNTAX      Er1645v2Lan2FGUIpV6DhcpClientVendorClEntry
   MAX-ACCESS  not-accessible
   STATUS      current
   DESCRIPTION
      ""
   INDEX      { er1645v2Lan2FGUIpV6DhcpClientVendorClTableIx }
   ::= {er1645v2Lan2FGUIpV6DhcpClientVendorCl 1}

Er1645v2Lan2FGUIpV6DhcpClientVendorClEntry ::=
   SEQUENCE
      {
      er1645v2Lan2FGUIpV6DhcpClientVendorClActions
         VariableLengthTableActions,
      er1645v2Lan2FGUIpV6DhcpClientVendorClTableIx
         TableIndex,
      er1645v2Lan2FGUIpV6DhcpClientVendorClValueAscii
         DisplayString,
      er1645v2Lan2FGUIpV6DhcpClientVendorClValueDecimal
         Integer32,
      er1645v2Lan2FGUIpV6DhcpClientVendorClValueHexData
         OCTET STRING
      }

er1645v2Lan2FGUIpV6DhcpClientVendorClActions OBJECT-TYPE
   SYNTAX      VariableLengthTableActions
   MAX-ACCESS  read-write
   STATUS      current
   DESCRIPTION
      "By way of this field, some manipulations
       on this table may be performed."
   ::= {er1645v2Lan2FGUIpV6DhcpClientVendorClEntry 2}

er1645v2Lan2FGUIpV6DhcpClientVendorClTableIx OBJECT-TYPE
   SYNTAX      TableIndex
   MAX-ACCESS  not-accessible
   STATUS      current
   DESCRIPTION
      ""
   ::= {er1645v2Lan2FGUIpV6DhcpClientVendorClEntry 11}

er1645v2Lan2FGUIpV6DhcpClientVendorClValueAscii OBJECT-TYPE
   SYNTAX      DisplayString
   MAX-ACCESS  read-write
   STATUS      current
   DESCRIPTION
      "Path: ethernet2.editConf.ipV6.dhcp.client.vendorClassOpt.value.ascii"
   ::= {er1645v2Lan2FGUIpV6DhcpClientVendorClEntry 16842752}

er1645v2Lan2FGUIpV6DhcpClientVendorClValueDecimal OBJECT-TYPE
   SYNTAX      Integer32
   MAX-ACCESS  read-write
   STATUS      current
   DESCRIPTION
      "Path: ethernet2.editConf.ipV6.dhcp.client.vendorClassOpt.value.decimal"
   ::= {er1645v2Lan2FGUIpV6DhcpClientVendorClEntry 16908288}

er1645v2Lan2FGUIpV6DhcpClientVendorClValueHexData OBJECT-TYPE
   SYNTAX      OCTET STRING
   MAX-ACCESS  read-write
   STATUS      current
   DESCRIPTION
      "Path: ethernet2.editConf.ipV6.dhcp.client.vendorClassOpt.value.hexData"
   ::= {er1645v2Lan2FGUIpV6DhcpClientVendorClEntry 16973824}

er1645v2Lan2FGUIpV6DhcpRelayDestinations OBJECT-TYPE
   SYNTAX      SEQUENCE OF Er1645v2Lan2FGUIpV6DhcpRelayDestinationsEntry
   MAX-ACCESS  not-accessible
   STATUS      current
   DESCRIPTION
      ""
   ::= {er1645v2Lan2FGUIpV6 174080000}

er1645v2Lan2FGUIpV6DhcpRelayDestinationsEntry OBJECT-TYPE
   SYNTAX      Er1645v2Lan2FGUIpV6DhcpRelayDestinationsEntry
   MAX-ACCESS  not-accessible
   STATUS      current
   DESCRIPTION
      ""
   INDEX      { er1645v2Lan2FGUIpV6DhcpRelayDestinationsTableIx }
   ::= {er1645v2Lan2FGUIpV6DhcpRelayDestinations 1}

Er1645v2Lan2FGUIpV6DhcpRelayDestinationsEntry ::=
   SEQUENCE
      {
      er1645v2Lan2FGUIpV6DhcpRelayDestinationsActions
         VariableLengthTableActions,
      er1645v2Lan2FGUIpV6DhcpRelayDestinationsTableIx
         TableIndex,
      er1645v2Lan2FGUIpV6DhcpRelayDestinationsAddress
         Ipv6Address,
      er1645v2Lan2FGUIpV6DhcpRelayDestinationsInterface
         DisplayString
      }

er1645v2Lan2FGUIpV6DhcpRelayDestinationsActions OBJECT-TYPE
   SYNTAX      VariableLengthTableActions
   MAX-ACCESS  read-write
   STATUS      current
   DESCRIPTION
      "By way of this field, some manipulations
       on this table may be performed."
   ::= {er1645v2Lan2FGUIpV6DhcpRelayDestinationsEntry 2}

er1645v2Lan2FGUIpV6DhcpRelayDestinationsTableIx OBJECT-TYPE
   SYNTAX      TableIndex
   MAX-ACCESS  not-accessible
   STATUS      current
   DESCRIPTION
      ""
   ::= {er1645v2Lan2FGUIpV6DhcpRelayDestinationsEntry 11}

er1645v2Lan2FGUIpV6DhcpRelayDestinationsAddress OBJECT-TYPE
   SYNTAX      Ipv6Address
   MAX-ACCESS  read-write
   STATUS      current
   DESCRIPTION
      "Path: ethernet2.editConf.ipV6.dhcp.relay.destinations.address

       ipv6 address"
   ::= {er1645v2Lan2FGUIpV6DhcpRelayDestinationsEntry 16777216}

er1645v2Lan2FGUIpV6DhcpRelayDestinationsInterface OBJECT-TYPE
   SYNTAX      DisplayString
   MAX-ACCESS  read-write
   STATUS      current
   DESCRIPTION
      "Path: ethernet2.editConf.ipV6.dhcp.relay.destinations.interface"
   ::= {er1645v2Lan2FGUIpV6DhcpRelayDestinationsEntry 33554432}


er1645v2Lan2FGUFlowControl OBJECT-TYPE
   SYNTAX      INTEGER
               {
               disabled (1),
               rx (2),
               tx (3),
               rxAndTx (4)
               }
   MAX-ACCESS  read-write
   STATUS      current
   DESCRIPTION
      "Path: ethernet2.editConf.flowControl
       Info: LAN flow control

       Possibilities:
               disabled   (1)
               rx   (2)
               tx   (3)
               rxAndTx   (4)"
   ::= {er1645v2Lan2FGU 7}


er1645v2Lan2FGUInboundNUcastPriority OBJECT IDENTIFIER ::= {er1645v2Lan2FGU 230}

er1645v2Lan2FGUInboundNUcastPrioritySSC OBJECT IDENTIFIER ::= {er1645v2Lan2FGUInboundNUcastPriority 1}

er1645v2Lan2FGUInboundNUcastPriorityEntry OBJECT IDENTIFIER ::= {er1645v2Lan2FGUInboundNUcastPrioritySSC 1}

er1645v2Lan2FGUInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2Lan2FGUInboundNUcastPriorityEntry 16777216}

er1645v2Lan2FGUInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.multicast

       Possibilities:
               queue1   (0)
               queue2   (1)
               queue3   (2)
               queue4   (3)
               queue5   (4)
               lowDelayQueue   (5)
               lowDelay2Queue   (6)
               systemQueue   (7)"
   ::= {er1645v2Lan2FGUInboundNUcastPriorityEntry 33554432}


er1645v2Lan2FGUIp OBJECT IDENTIFIER ::= {er1645v2Lan2FGU 1}

er1645v2Lan2FGUIpSSC OBJECT IDENTIFIER ::= {er1645v2Lan2FGUIp 1}

er1645v2Lan2FGUIpEntry OBJECT IDENTIFIER ::= {er1645v2Lan2FGUIpSSC 1}

er1645v2Lan2FGUIpVrfRouter OBJECT-TYPE
   SYNTAX      DisplayString
   MAX-ACCESS  read-write
   STATUS      current
   DESCRIPTION
      "Path: ethernet2.editConf.ip.vrfRouter"
   ::= {er1645v2Lan2FGUIpEntry 738197504}

er1645v2Lan2FGUIpAdr OBJECT-TYPE
   SYNTAX      IpAddress
   MAX-ACCESS  read-write
   STATUS      current
   DESCRIPTION
      "Path: ethernet2.editConf.ip.address"
   ::= {er1645v2Lan2FGUIpEntry 2030043136}

er1645v2Lan2FGUIpNetm OBJECT-TYPE
   SYNTAX      IpAddress
   MAX-ACCESS  read-write
   STATUS      current
   DESCRIPTION
      "Path: ethernet2.editConf.ip.netMask"
   ::= {er1645v2Lan2FGUIpEntry 2063597568}

er1645v2Lan2FGUIpSNetName OBJECT-TYPE
   SYNTAX      INTEGER
               {
               slOPTg (0),
               corp (2),
               dmz (3),
               internet (1)
               }
   MAX-ACCESS  read-write
   STATUS      current
   DESCRIPTION
      "Path: ethernet2.editConf.ip.sNet.name

       Possibilities:
               <OPT>   (0)
               corp   (2)
               dmz   (3)
               internet   (1)"
   ::= {er1645v2Lan2FGUIpEntry 855703552}

er1645v2Lan2FGUIpSNetCust OBJECT-TYPE
   SYNTAX      DisplayString
   MAX-ACCESS  read-write
   STATUS      current
   DESCRIPTION
      "Path: ethernet2.editConf.ip.sNet.custom"
   ::= {er1645v2Lan2FGUIpEntry 855769088}

er1645v2Lan2FGUIpDhcpC OBJECT-TYPE
   SYNTAX      INTEGER
               {
               disabled (0),
               enabled (1)
               }
   MAX-ACCESS  read-write
   STATUS      current
   DESCRIPTION
      "Path: ethernet2.editConf.ip.dhcpClient

       Possibilities:
               disabled   (0)
               enabled   (1)"
   ::= {er1645v2Lan2FGUIpEntry 838860800}

er1645v2Lan2FGUIpDhcpGatewayPreference OBJECT-TYPE
   SYNTAX      Integer32
   MAX-ACCESS  read-write
   STATUS      current
   DESCRIPTION
      "Path: ethernet2.editConf.ip.dhcp.gatewayPreference"
   ::= {er1645v2Lan2FGUIpEntry 872480768}

er1645v2Lan2FGUIpDhcpRoutePreference OBJECT-TYPE
   SYNTAX      Integer32
   MAX-ACCESS  read-write
   STATUS      current
   DESCRIPTION
      "Path: ethernet2.editConf.ip.dhcp.routePreference"
   ::= {er1645v2Lan2FGUIpEntry 872546304}

er1645v2Lan2FGUIpDhcpDnsPreference OBJECT-TYPE
   SYNTAX      Integer32
   MAX-ACCESS  read-write
   STATUS      current
   DESCRIPTION
      "Path: ethernet2.editConf.ip.dhcp.dnsPreference"
   ::= {er1645v2Lan2FGUIpEntry 872611840}

er1645v2Lan2FGUIpMtu OBJECT-TYPE
   SYNTAX      Integer32
   MAX-ACCESS  read-write
   STATUS      current
   DESCRIPTION
      "Path: ethernet2.editConf.ip.mtu"
   ::= {er1645v2Lan2FGUIpEntry 671088640}

er1645v2Lan2FGUIpMssAdjust OBJECT-TYPE
   SYNTAX      INTEGER
               {
               disabled (0),
               auto (65536)
               }
   MAX-ACCESS  read-write
   STATUS      current
   DESCRIPTION
      "Path: ethernet2.editConf.ip.mssAdjust

       Possibilities:
               disabled   (0)
               auto   (65536)"
   ::= {er1645v2Lan2FGUIpEntry 754974720}

er1645v2Lan2FGUIpRipMetric OBJECT-TYPE
   SYNTAX      Integer32
   MAX-ACCESS  read-write
   STATUS      current
   DESCRIPTION
      "Path: ethernet2.editConf.ip.rip.metric"
   ::= {er1645v2Lan2FGUIpEntry 353566720}

er1645v2Lan2FGUIpRipMetricOut OBJECT-TYPE
   SYNTAX      Integer32
   MAX-ACCESS  read-write
   STATUS      current
   DESCRIPTION
      "Path: ethernet2.editConf.ip.rip.metricOut"
   ::= {er1645v2Lan2FGUIpEntry 353632256}

er1645v2Lan2FGUIpRipMode OBJECT-TYPE
   SYNTAX      INTEGER
               {
               disabled (0),
               passive (1),
               active (2)
               }
   MAX-ACCESS  read-write
   STATUS      current
   DESCRIPTION
      "Path: ethernet2.editConf.ip.rip.mode

       Possibilities:
               disabled   (0)
               passive   (1)
               active   (2)"
   ::= {er1645v2Lan2FGUIpEntry 353697792}

er1645v2Lan2FGUIpRipTxVer OBJECT-TYPE
   SYNTAX      INTEGER
               {
               rip1 (0),
               rip2 (1),
               rip1mcompatible (2)
               }
   MAX-ACCESS  read-write
   STATUS      current
   DESCRIPTION
      "Path: ethernet2.editConf.ip.rip.txVersion

       Possibilities:
               rip1   (0)
               rip2   (1)
               rip1-compatible   (2)"
   ::= {er1645v2Lan2FGUIpEntry 354615296}

er1645v2Lan2FGUIpRipRxVer OBJECT-TYPE
   SYNTAX      INTEGER
               {
               rip1only (0),
               rip2only (1),
               rip12 (2)
               }
   MAX-ACCESS  read-write
   STATUS      current
   DESCRIPTION
      "Path: ethernet2.editConf.ip.rip.rxVersion

       Possibilities:
               rip1only   (0)
               rip2only   (1)
               rip1&2   (2)"
   ::= {er1645v2Lan2FGUIpEntry 354680832}

er1645v2Lan2FGUIpRipSplitH OBJECT-TYPE
   SYNTAX      INTEGER
               {
               disabled (0),
               enabled (1),
               poisonedReverse (2)
               }
   MAX-ACCESS  read-write
   STATUS      current
   DESCRIPTION
      "Path: ethernet2.editConf.ip.rip.splitHorizon

       Possibilities:
               disabled   (0)
               enabled   (1)
               poisonedReverse   (2)"
   ::= {er1645v2Lan2FGUIpEntry 353828864}

er1645v2Lan2FGUIpRipAuth OBJECT-TYPE
   SYNTAX      INTEGER
               {
               disabled (0),
               texts (1),
               md5 (2)
               }
   MAX-ACCESS  read-write
   STATUS      current
   DESCRIPTION
      "Path: ethernet2.editConf.ip.rip.authentication

       Possibilities:
               disabled   (0)
               text    (1)
               md5   (2)"
   ::= {er1645v2Lan2FGUIpEntry 353501184}

er1645v2Lan2FGUIpRipFilter OBJECT-TYPE
   SYNTAX      DisplayString
   MAX-ACCESS  read-write
   STATUS      current
   DESCRIPTION
      "Path: ethernet2.editConf.ip.rip.filter"
   ::= {er1645v2Lan2FGUIpEntry 354418688}

er1645v2Lan2FGUIpRipFilterIn OBJECT-TYPE
   SYNTAX      DisplayString
   MAX-ACCESS  read-write
   STATUS      current
   DESCRIPTION
      "Path: ethernet2.editConf.ip.rip.filterIn"
   ::= {er1645v2Lan2FGUIpEntry 354484224}

er1645v2Lan2FGUIpRipClearNextHop OBJECT-TYPE
   SYNTAX      INTEGER
               {
               disabled (0),
               enabled (1)
               }
   MAX-ACCESS  read-write
   STATUS      current
   DESCRIPTION
      "Path: ethernet2.editConf.ip.rip.clearNextHop

       Possibilities:
               disabled   (0)
               enabled   (1)"
   ::= {er1645v2Lan2FGUIpEntry 352452608}

er1645v2Lan2FGUIpAccPol OBJECT-TYPE
   SYNTAX      DisplayString
   MAX-ACCESS  read-write
   STATUS      current
   DESCRIPTION
      "Path: ethernet2.editConf.ip.accessPolicy"
   ::= {er1645v2Lan2FGUIpEntry 704643072}

er1645v2Lan2FGUIpAB OBJECT-TYPE
   SYNTAX      DisplayString
   MAX-ACCESS  read-write
   STATUS      current
   DESCRIPTION
      "Path: ethernet2.editConf.ip.trafficPolicy"
   ::= {er1645v2Lan2FGUIpEntry 234881024}

er1645v2Lan2FGUIpMA OBJECT-TYPE
   SYNTAX      INTEGER
               {
               disabled (0),
               enabled (1)
               }
   MAX-ACCESS  read-write
   STATUS      current
   DESCRIPTION
      "Path: ethernet2.editConf.ip.mgmtAccess

       Possibilities:
               disabled   (0)
               enabled   (1)"
   ::= {er1645v2Lan2FGUIpEntry 268435456}

er1645v2Lan2FGUIpMF OBJECT-TYPE
   SYNTAX      Integer32
   MAX-ACCESS  read-write
   STATUS      current
   DESCRIPTION
      "Path: ethernet2.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGUIpEntry 285212672}

er1645v2Lan2FGUIpDB OBJECT-TYPE
   SYNTAX      INTEGER
               {
               disabled (0),
               enabled (1)
               }
   MAX-ACCESS  read-write
   STATUS      current
   DESCRIPTION
      "Path: ethernet2.editConf.ip.directedBroadcasts

       Possibilities:
               disabled   (0)
               enabled   (1)"
   ::= {er1645v2Lan2FGUIpEntry 369098752}

er1645v2Lan2FGUIpIR OBJECT-TYPE
   SYNTAX      INTEGER
               {
               disabled (0),
               enabled (1)
               }
   MAX-ACCESS  read-write
   STATUS      current
   DESCRIPTION
      "Path: ethernet2.editConf.ip.icmpRedirects

       Possibilities:
               disabled   (0)
               enabled   (1)"
   ::= {er1645v2Lan2FGUIpEntry 436207616}

er1645v2Lan2FGUIpIgmp OBJECT-TYPE
   SYNTAX      INTEGER
               {
               disabled (0),
               proxy (1),
               router (2),
               v3Router (5)
               }
   MAX-ACCESS  read-write
   STATUS      current
   DESCRIPTION
      "Path: ethernet2.editConf.ip.igmp

       Possibilities:
               disabled   (0)
               proxy   (1)
               router   (2)
               v3Router   (5)"
   ::= {er1645v2Lan2FGUIpEntry 536870912}

er1645v2Lan2FGUIpNN OBJECT-TYPE
   SYNTAX      DisplayString
   MAX-ACCESS  read-write
   STATUS      current
   DESCRIPTION
      "Path: ethernet2.editConf.ip.nat"
   ::= {er1645v2Lan2FGUIpEntry 452984832}

er1645v2Lan2FGUIpVrrp OBJECT-TYPE
   SYNTAX      INTEGER
               {
               disabled (0),
               enabled (1)
               }
   MAX-ACCESS  read-write
   STATUS      current
   DESCRIPTION
      "Path: ethernet2.editConf.ip.vrrp

       Possibilities:
               disabled   (0)
               enabled   (1)"
   ::= {er1645v2Lan2FGUIpEntry 721420288}

er1645v2Lan2FGUIpPimMode OBJECT-TYPE
   SYNTAX      INTEGER
               {
               disabled (0),
               sparse (1),
               passive (2)
               }
   MAX-ACCESS  read-write
   STATUS      current
   DESCRIPTION
      "Path: ethernet2.editConf.ip.pim.mode

       Possibilities:
               disabled   (0)
               sparse   (1)
               passive   (2)"
   ::= {er1645v2Lan2FGUIpEntry 771817472}

er1645v2Lan2FGUIpPimDrPriority OBJECT-TYPE
   SYNTAX      Counter32
   MAX-ACCESS  read-write
   STATUS      current
   DESCRIPTION
      "Path: ethernet2.editConf.ip.pim.drPriority

       32 bit unsigned wrappable counter."
   ::= {er1645v2Lan2FGUIpEntry 771883008}

er1645v2Lan2FGUIpPimHelloTime OBJECT-TYPE
   SYNTAX      TimeTicks
   MAX-ACCESS  read-write
   STATUS      current
   DESCRIPTION
      "Path: ethernet2.editConf.ip.pim.helloTime

       Time in centi-second."
   ::= {er1645v2Lan2FGUIpEntry 771948544}

er1645v2Lan2FGUIpPimPropagationDelay OBJECT-TYPE
   SYNTAX      TimeTicks
   MAX-ACCESS  read-write
   STATUS      current
   DESCRIPTION
      "Path: ethernet2.editConf.ip.pim.propagationDelay

       Time in centi-second."
   ::= {er1645v2Lan2FGUIpEntry 772014080}

er1645v2Lan2FGUIpPimOverrideInterval OBJECT-TYPE
   SYNTAX      TimeTicks
   MAX-ACCESS  read-write
   STATUS      current
   DESCRIPTION
      "Path: ethernet2.editConf.ip.pim.overrideInterval

       Time in centi-second."
   ::= {er1645v2Lan2FGUIpEntry 772079616}

er1645v2Lan2FGUIpPimBsrBorder OBJECT-TYPE
   SYNTAX      INTEGER
               {
               disabled (0),
               enabled (1)
               }
   MAX-ACCESS  read-write
   STATUS      current
   DESCRIPTION
      "Path: ethernet2.editConf.ip.pim.bsrBorder

       Possibilities:
               disabled   (0)
               enabled   (1)"
   ::= {er1645v2Lan2FGUIpEntry 772145152}

er1645v2Lan2FGUIpPimTtlThreshold OBJECT-TYPE
   SYNTAX      Integer32
   MAX-ACCESS  read-write
   STATUS      current
   DESCRIPTION
      "Path: ethernet2.editConf.ip.pim.ttlThreshold"
   ::= {er1645v2Lan2FGUIpEntry 772210688}

er1645v2Lan2FGUIpIMNetworkUnreachable OBJECT-TYPE
   SYNTAX      INTEGER
               {
               disabled (0),
               enabled (1)
               }
   MAX-ACCESS  read-write
   STATUS      current
   DESCRIPTION
      "Path: ethernet2.editConf.ip.icmpMessages.networkUnreachable

       Possibilities:
               disabled   (0)
               enabled   (1)"
   ::= {er1645v2Lan2FGUIpEntry 788594688}

er1645v2Lan2FGUIpIMHostUnreachable OBJECT-TYPE
   SYNTAX      INTEGER
               {
               disabled (0),
               enabled (1)
               }
   MAX-ACCESS  read-write
   STATUS      current
   DESCRIPTION
      "Path: ethernet2.editConf.ip.icmpMessages.hostUnreachable

       Possibilities:
               disabled   (0)
               enabled   (1)"
   ::= {er1645v2Lan2FGUIpEntry 788660224}

er1645v2Lan2FGUIpIMProtocolUnreachable OBJECT-TYPE
   SYNTAX      INTEGER
               {
               disabled (0),
               enabled (1)
               }
   MAX-ACCESS  read-write
   STATUS      current
   DESCRIPTION
      "Path: ethernet2.editConf.ip.icmpMessages.protocolUnreachable

       Possibilities:
               disabled   (0)
               enabled   (1)"
   ::= {er1645v2Lan2FGUIpEntry 788725760}

er1645v2Lan2FGUIpIMPortUnreachable OBJECT-TYPE
   SYNTAX      INTEGER
               {
               disabled (0),
               enabled (1)
               }
   MAX-ACCESS  read-write
   STATUS      current
   DESCRIPTION
      "Path: ethernet2.editConf.ip.icmpMessages.portUnreachable

       Possibilities:
               disabled   (0)
               enabled   (1)"
   ::= {er1645v2Lan2FGUIpEntry 788791296}

er1645v2Lan2FGUIpIMMtuExceeded OBJECT-TYPE
   SYNTAX      INTEGER
               {
               disabled (0),
               enabled (1)
               }
   MAX-ACCESS  read-write
   STATUS      current
   DESCRIPTION
      "Path: ethernet2.editConf.ip.icmpMessages.mtuExceeded

       Possibilities:
               disabled   (0)
               enabled   (1)"
   ::= {er1645v2Lan2FGUIpEntry 788856832}

er1645v2Lan2FGUIpIMAdminProhibited OBJECT-TYPE
   SYNTAX      INTEGER
               {
               disabled (0),
               enabled (1)
               }
   MAX-ACCESS  read-write
   STATUS      current
   DESCRIPTION
      "Path: ethernet2.editConf.ip.icmpMessages.adminProhibited

       Possibilities:
               disabled   (0)
               enabled   (1)"
   ::= {er1645v2Lan2FGUIpEntry 788922368}

er1645v2Lan2FGUIpIMTtlExceeded OBJECT-TYPE
   SYNTAX      INTEGER
               {
               disabled (0),
               enabled (1)
               }
   MAX-ACCESS  read-write
   STATUS      current
   DESCRIPTION
      "Path: ethernet2.editConf.ip.icmpMessages.ttlExceeded

       Possibilities:
               disabled   (0)
               enabled   (1)"
   ::= {er1645v2Lan2FGUIpEntry 788987904}

er1645v2Lan2FGUIpIMRedirect OBJECT-TYPE
   SYNTAX      INTEGER
               {
               disabled (0),
               enabled (1)
               }
   MAX-ACCESS  read-write
   STATUS      current
   DESCRIPTION
      "Path: ethernet2.editConf.ip.icmpMessages.redirect

       Possibilities:
               disabled   (0)
               enabled   (1)"
   ::= {er1645v2Lan2FGUIpEntry 789053440}

er1645v2Lan2FGUIpSaddr OBJECT-TYPE
   SYNTAX      SEQUENCE OF Er1645v2Lan2FGUIpSaddrEntry
   MAX-ACCESS  not-accessible
   STATUS      current
   DESCRIPTION
      ""
   ::= {er1645v2Lan2FGUIp 385875968}

er1645v2Lan2FGUIpSaddrEntry OBJECT-TYPE
   SYNTAX      Er1645v2Lan2FGUIpSaddrEntry
   MAX-ACCESS  not-accessible
   STATUS      current
   DESCRIPTION
      ""
   INDEX      { er1645v2Lan2FGUIpSaddrTableIx }
   ::= {er1645v2Lan2FGUIpSaddr 1}

Er1645v2Lan2FGUIpSaddrEntry ::=
   SEQUENCE
      {
      er1645v2Lan2FGUIpSaddrActions
         VariableLengthTableActions,
      er1645v2Lan2FGUIpSaddrTableIx
         TableIndex,
      er1645v2Lan2FGUIpSaddrAddress
         IpAddress,
      er1645v2Lan2FGUIpSaddrNetMask
         IpAddress
      }

er1645v2Lan2FGUIpSaddrActions OBJECT-TYPE
   SYNTAX      VariableLengthTableActions
   MAX-ACCESS  read-write
   STATUS      current
   DESCRIPTION
      "By way of this field, some manipulations
       on this table may be performed."
   ::= {er1645v2Lan2FGUIpSaddrEntry 2}

er1645v2Lan2FGUIpSaddrTableIx OBJECT-TYPE
   SYNTAX      TableIndex
   MAX-ACCESS  not-accessible
   STATUS      current
   DESCRIPTION
      ""
   ::= {er1645v2Lan2FGUIpSaddrEntry 11}

er1645v2Lan2FGUIpSaddrAddress OBJECT-TYPE
   SYNTAX      IpAddress
   MAX-ACCESS  read-write
   STATUS      current
   DESCRIPTION
      "Path: ethernet2.editConf.ip.secondaryIp.address"
   ::= {er1645v2Lan2FGUIpSaddrEntry 2030043136}

er1645v2Lan2FGUIpSaddrNetMask OBJECT-TYPE
   SYNTAX      IpAddress
   MAX-ACCESS  read-write
   STATUS      current
   DESCRIPTION
      "Path: ethernet2.editConf.ip.secondaryIp.netMask"
   ::= {er1645v2Lan2FGUIpSaddrEntry 2063597568}

er1645v2Lan2FGUIpH OBJECT-TYPE
   SYNTAX      SEQUENCE OF Er1645v2Lan2FGUIpHEntry
   MAX-ACCESS  not-accessible
   STATUS      current
   DESCRIPTION
      ""
   ::= {er1645v2Lan2FGUIp 251658240}

er1645v2Lan2FGUIpHEntry OBJECT-TYPE
   SYNTAX      Er1645v2Lan2FGUIpHEntry
   MAX-ACCESS  not-accessible
   STATUS      current
   DESCRIPTION
      ""
   INDEX      { er1645v2Lan2FGUIpHTableIx }
   ::= {er1645v2Lan2FGUIpH 1}

Er1645v2Lan2FGUIpHEntry ::=
   SEQUENCE
      {
      er1645v2Lan2FGUIpHActions
         VariableLengthTableActions,
      er1645v2Lan2FGUIpHTableIx
         TableIndex,
      er1645v2Lan2FGUIpHAddress
         IpAddress,
      er1645v2Lan2FGUIpHDhcpRelayOptionSubscriberId
         DisplayString
      }

er1645v2Lan2FGUIpHActions OBJECT-TYPE
   SYNTAX      VariableLengthTableActions
   MAX-ACCESS  read-write
   STATUS      current
   DESCRIPTION
      "By way of this field, some manipulations
       on this table may be performed."
   ::= {er1645v2Lan2FGUIpHEntry 2}

er1645v2Lan2FGUIpHTableIx OBJECT-TYPE
   SYNTAX      TableIndex
   MAX-ACCESS  not-accessible
   STATUS      current
   DESCRIPTION
      ""
   ::= {er1645v2Lan2FGUIpHEntry 11}

er1645v2Lan2FGUIpHAddress OBJECT-TYPE
   SYNTAX      IpAddress
   MAX-ACCESS  read-write
   STATUS      current
   DESCRIPTION
      "Path: ethernet2.editConf.ip.helpers.address"
   ::= {er1645v2Lan2FGUIpHEntry 16777216}

er1645v2Lan2FGUIpHDhcpRelayOptionSubscriberId OBJECT-TYPE
   SYNTAX      DisplayString
   MAX-ACCESS  read-write
   STATUS      current
   DESCRIPTION
      "Path: ethernet2.editConf.ip.helpers.dhcpRelayOption.subscriberId"
   ::= {er1645v2Lan2FGUIpHEntry 33947648}


er1645v2Lan2FGUVlan OBJECT IDENTIFIER ::= {er1645v2Lan2FGU 33}

er1645v2Lan2FGUVlanSSCTable OBJECT-TYPE
   SYNTAX      SEQUENCE OF Er1645v2Lan2FGUVlanEntry
   MAX-ACCESS  not-accessible
   STATUS      current
   DESCRIPTION
      ""
   ::= {er1645v2Lan2FGUVlan 1}

er1645v2Lan2FGUVlanEntry OBJECT-TYPE
   SYNTAX      Er1645v2Lan2FGUVlanEntry
   MAX-ACCESS  not-accessible
   STATUS      current
   DESCRIPTION
      ""
   INDEX      { er1645v2Lan2FGUVlanTableIx }
   ::= {er1645v2Lan2FGUVlanSSCTable 1}

Er1645v2Lan2FGUVlanEntry ::=
   SEQUENCE
      {
      er1645v2Lan2FGUVlanActions
         VariableLengthTableActions,
      er1645v2Lan2FGUVlanTableIx
         TableIndex,
      er1645v2Lan2FGUVlanName
         DisplayString,
      er1645v2Lan2FGUVlanRemark
         DisplayString,
      er1645v2Lan2FGUVlanAdminStatus
         INTEGER,
      er1645v2Lan2FGUVlanMode
         INTEGER,
      er1645v2Lan2FGUVlanPriorityPolicy
         DisplayString,
      er1645v2Lan2FGUVlanIpVrfRouter
         DisplayString,
      er1645v2Lan2FGUVlanIpAdr
         IpAddress,
      er1645v2Lan2FGUVlanIpNetm
         IpAddress,
      er1645v2Lan2FGUVlanIpSNetName
         INTEGER,
      er1645v2Lan2FGUVlanIpSNetCust
         DisplayString,
      er1645v2Lan2FGUVlanIpDhcpC
         INTEGER,
      er1645v2Lan2FGUVlanIpDhcpGatewayPreference
         Integer32,
      er1645v2Lan2FGUVlanIpDhcpRoutePreference
         Integer32,
      er1645v2Lan2FGUVlanIpDhcpDnsPreference
         Integer32,
      er1645v2Lan2FGUVlanIpMtu
         Integer32,
      er1645v2Lan2FGUVlanIpMssAdjust
         INTEGER,
      er1645v2Lan2FGUVlanIpRipMetric
         Integer32,
      er1645v2Lan2FGUVlanIpRipMetricOut
         Integer32,
      er1645v2Lan2FGUVlanIpRipMode
         INTEGER,
      er1645v2Lan2FGUVlanIpRipTxVer
         INTEGER,
      er1645v2Lan2FGUVlanIpRipRxVer
         INTEGER,
      er1645v2Lan2FGUVlanIpRipSplitH
         INTEGER,
      er1645v2Lan2FGUVlanIpRipAuth
         INTEGER,
      er1645v2Lan2FGUVlanIpRipFilter
         DisplayString,
      er1645v2Lan2FGUVlanIpRipFilterIn
         DisplayString,
      er1645v2Lan2FGUVlanIpRipClearNextHop
         INTEGER,
      er1645v2Lan2FGUVlanIpAccPol
         DisplayString,
      er1645v2Lan2FGUVlanIpAB
         DisplayString,
      er1645v2Lan2FGUVlanIpMA
         INTEGER,
      er1645v2Lan2FGUVlanIpMF
         Integer32,
      er1645v2Lan2FGUVlanIpDB
         INTEGER,
      er1645v2Lan2FGUVlanIpIR
         INTEGER,
      er1645v2Lan2FGUVlanIpIgmp
         INTEGER,
      er1645v2Lan2FGUVlanIpNN
         DisplayString,
      er1645v2Lan2FGUVlanIpVrrp
         INTEGER,
      er1645v2Lan2FGUVlanIpPimMode
         INTEGER,
      er1645v2Lan2FGUVlanIpPimDrPriority
         Counter32,
      er1645v2Lan2FGUVlanIpPimHelloTime
         TimeTicks,
      er1645v2Lan2FGUVlanIpPimPropagationDelay
         TimeTicks,
      er1645v2Lan2FGUVlanIpPimOverrideInterval
         TimeTicks,
      er1645v2Lan2FGUVlanIpPimBsrBorder
         INTEGER,
      er1645v2Lan2FGUVlanIpPimTtlThreshold
         Integer32,
      er1645v2Lan2FGUVlanIpIMNetworkUnreachable
         INTEGER,
      er1645v2Lan2FGUVlanIpIMHostUnreachable
         INTEGER,
      er1645v2Lan2FGUVlanIpIMProtocolUnreachable
         INTEGER,
      er1645v2Lan2FGUVlanIpIMPortUnreachable
         INTEGER,
      er1645v2Lan2FGUVlanIpIMMtuExceeded
         INTEGER,
      er1645v2Lan2FGUVlanIpIMAdminProhibited
         INTEGER,
      er1645v2Lan2FGUVlanIpIMTtlExceeded
         INTEGER,
      er1645v2Lan2FGUVlanIpIMRedirect
         INTEGER,
      er1645v2Lan2FGUVlanIpV6VrfRouter
         DisplayString,
      er1645v2Lan2FGUVlanIpV6AddrAutoConfigNrDupAddrDetects
         Integer32,
      er1645v2Lan2FGUVlanIpV6AddrAutoConfigAcceptRa
         INTEGER,
      er1645v2Lan2FGUVlanIpV6AddrAutoConfigAcceptRaRdnss
         INTEGER,
      er1645v2Lan2FGUVlanIpV6AddrAutoConfigAcceptRaDnssl
         INTEGER,
      er1645v2Lan2FGUVlanIpV6DefaultRoute
         INTEGER,
      er1645v2Lan2FGUVlanIpV6RaSend
         INTEGER,
      er1645v2Lan2FGUVlanIpV6RaMinInterval
         TimeTicks,
      er1645v2Lan2FGUVlanIpV6RaMaxInterval
         TimeTicks,
      er1645v2Lan2FGUVlanIpV6RaManagedFlag
         INTEGER,
      er1645v2Lan2FGUVlanIpV6RaOtherConfFlag
         INTEGER,
      er1645v2Lan2FGUVlanIpV6RaLinkMtu
         Integer32,
      er1645v2Lan2FGUVlanIpV6RaReachableTime
         TimeTicks,
      er1645v2Lan2FGUVlanIpV6RaRetransmitTime
         TimeTicks,
      er1645v2Lan2FGUVlanIpV6RaHopLimit
         Integer32,
      er1645v2Lan2FGUVlanIpV6RaDefaultLifeTime
         TimeTicks,
      er1645v2Lan2FGUVlanIpV6RaDnsOptionsRdnssLifeTime
         TimeTicks,
      er1645v2Lan2FGUVlanIpV6RaDnsOptionsRdnssImportServers
         INTEGER,
      er1645v2Lan2FGUVlanIpV6RaDnsOptionsDnsslLifeTime
         TimeTicks,
      er1645v2Lan2FGUVlanIpV6RaDnsOptionsDnsslImportDomains
         INTEGER,
      er1645v2Lan2FGUVlanIpV6RsSend
         INTEGER,
      er1645v2Lan2FGUVlanIpV6RsMaxRandomDelay
         TimeTicks,
      er1645v2Lan2FGUVlanIpV6RsInterval
         TimeTicks,
      er1645v2Lan2FGUVlanIpV6RsMaxSolicitations
         Integer32,
      er1645v2Lan2FGUVlanIpV6TrafficPolicyInbound
         DisplayString,
      er1645v2Lan2FGUVlanIpV6TrafficPolicyOutbound
         DisplayString,
      er1645v2Lan2FGUVlanIpV6FirewallZone
         DisplayString,
      er1645v2Lan2FGUVlanIpV6DhcpClientAddrAC
         INTEGER,
      er1645v2Lan2FGUVlanIpV6DhcpClientPrDelMode
         INTEGER,
      er1645v2Lan2FGUVlanIpV6DhcpClientPrDelPool
         DisplayString,
      er1645v2Lan2FGUVlanIpV6DhcpClientPrDelPdExclOpt
         INTEGER,
      er1645v2Lan2FGUVlanIpV6DhcpClientDnsServerPref
         Integer32,
      er1645v2Lan2FGUVlanIpV6DhcpClientRapidCommit
         INTEGER,
      er1645v2Lan2FGUVlanIpV6DhcpClientTimersSolTimeOut
         TimeTicks,
      er1645v2Lan2FGUVlanIpV6DhcpClientTimersSolMaxRt
         TimeTicks,
      er1645v2Lan2FGUVlanIpV6DhcpClientTimersInfoRefresh
         TimeTicks,
      er1645v2Lan2FGUVlanIpV6DhcpServerMode
         INTEGER,
      er1645v2Lan2FGUVlanIpV6DhcpServerPreference
         Integer32,
      er1645v2Lan2FGUVlanIpV6DhcpServerPool
         DisplayString,
      er1645v2Lan2FGUVlanIpV6DhcpServerRapidCommit
         INTEGER,
      er1645v2Lan2FGUVlanIpV6DhcpServerTimersInfoRefresh
         TimeTicks,
      er1645v2Lan2FGUVlanIpV6DhcpRelayMode
         INTEGER,
      er1645v2Lan2FGUVlanIpV6SendRedirect
         INTEGER,
      er1645v2Lan2FGUVlanIpV6LinkMtu
         Integer32,
      er1645v2Lan2FGUVlanIpV6InterfaceId
         OCTET STRING,
      er1645v2Lan2FGUVlanIpV6MF
         Integer32,
      er1645v2Lan2FGUVlanIpV6IcmpMessagesNoRoute
         INTEGER,
      er1645v2Lan2FGUVlanIpV6IcmpMessagesBeyondScope
         INTEGER,
      er1645v2Lan2FGUVlanIpV6IcmpMessagesAddressUnreachable
         INTEGER,
      er1645v2Lan2FGUVlanIpV6IcmpMessagesPortUnreachable
         INTEGER,
      er1645v2Lan2FGUVlanIpV6IcmpMessagesPacketTooBig
         INTEGER,
      er1645v2Lan2FGUVlanIpV6IcmpMessagesHopLimitExceeded
         INTEGER,
      er1645v2Lan2FGUVlanIpV6IcmpMessagesFragTimeExceeded
         INTEGER,
      er1645v2Lan2FGUVlanIpV6IcmpMessagesHeaderFieldErr
         INTEGER,
      er1645v2Lan2FGUVlanIpV6IcmpMessagesOptionUnrecognized
         INTEGER,
      er1645v2Lan2FGUVlanIpV6IcmpMessagesRedirect
         INTEGER,
      er1645v2Lan2FGUVlanBridgingAccList
         DisplayString,
      er1645v2Lan2FGUVlanBridgingInACL
         DisplayString,
      er1645v2Lan2FGUVlanBridgingTp
         DisplayString,
      er1645v2Lan2FGUVlanBridgingBrGrp
         DisplayString,
      er1645v2Lan2FGUVlanBridgingLimBC
         INTEGER,
      er1645v2Lan2FGUVlanBridgingPrivateMode
         INTEGER,
      er1645v2Lan2FGUVlanBridgingLearning
         INTEGER,
      er1645v2Lan2FGUVlanBridgingMaxCacheSize
         INTEGER,
      er1645v2Lan2FGUVlanBridgingRelearnDropOnRelearn
         INTEGER,
      er1645v2Lan2FGUVlanBridgingRelearnShutdownThreshold
         Integer32,
      er1645v2Lan2FGUVlanBridgingRelearnShutdownTime
         TimeTicks,
      er1645v2Lan2FGUVlanBridgingRelearnLoopDetection
         INTEGER,
      er1645v2Lan2FGUVlanBridgingRelearnLoopDetectionInterval
         TimeTicks,
      er1645v2Lan2FGUVlanBridgingVlanMemberShip
         INTEGER,
      er1645v2Lan2FGUVlanBridgingVlTUntaggedAction
         INTEGER,
      er1645v2Lan2FGUVlanBridgingVlTUntaggedTagInfoTpid
         INTEGER,
      er1645v2Lan2FGUVlanBridgingVlTUntaggedTagInfoVid
         Integer32,
      er1645v2Lan2FGUVlanBridgingVlTUnknownVlansAction
         INTEGER,
      er1645v2Lan2FGUVlanBridgingVlTUnknownVlansTagInfoTpid
         INTEGER,
      er1645v2Lan2FGUVlanBridgingVlTUnknownVlansTagInfoVid
         Integer32,
      er1645v2Lan2FGUVlanBridgingDot1adType
         INTEGER,
      er1645v2Lan2FGUVlanBridgingPriority
         Integer32,
      er1645v2Lan2FGUVlanBridgingPathCost
         Integer32,
      er1645v2Lan2FGUVlanBridgingInternalPathCost
         Integer32,
      er1645v2Lan2FGUVlanBridgingTCD
         INTEGER,
      er1645v2Lan2FGUVlanBridgingRestrictedRole
         INTEGER,
      er1645v2Lan2FGUVlanBridgingAdminEdge
         INTEGER,
      er1645v2Lan2FGUVlanBridgingOamMacDeviceMac
         DisplayString,
      er1645v2Lan2FGUVlanBridgingOamMacUserMac
         OCTET STRING,
      er1645v2Lan2FGUVlanBridgingOamMacBridgeMac
         DisplayString,
      er1645v2Lan2FGUVlanBridgingMgmtInline
         INTEGER,
      er1645v2Lan2FGUVlanBridgingL2ptMode
         INTEGER,
      er1645v2Lan2FGUVlanBridgingL2ptProtocols
         Integer32,
      er1645v2Lan2FGUVlanBridgingL2ptDestMac
         OCTET STRING,
      er1645v2Lan2FGUVlanBridgingL2ptCos
         INTEGER,
      er1645v2Lan2FGUVlanBridgingL2ptDropThrStp
         INTEGER,
      er1645v2Lan2FGUVlanBridgingL2ptDropThrLldp
         INTEGER,
      er1645v2Lan2FGUVlanBridgingL2ptDropThrOam
         INTEGER,
      er1645v2Lan2FGUVlanBridgingL2ptDropThrCdp
         INTEGER,
      er1645v2Lan2FGUVlanBridgingL2ptDropThrVtp
         INTEGER,
      er1645v2Lan2FGUVlanBridgingL2ptDropThrLacp
         INTEGER,
      er1645v2Lan2FGUVlanBridgingL2ptDropThrEfmOam
         INTEGER,
      er1645v2Lan2FGUVlanBridgingL2ptDropThrPvst
         INTEGER,
      er1645v2Lan2FGUVlanBridgingL2ptDropThrMmrp
         INTEGER,
      er1645v2Lan2FGUVlanBridgingL2ptDropThrMvrp
         INTEGER,
      er1645v2Lan2FGUVlanBridgingL2ptDropThrGvrp
         INTEGER,
      er1645v2Lan2FGUVlanBridgingL2ptDropThrGmrp
         INTEGER,
      er1645v2Lan2FGUVlanBridgingL2ptDropThrDtp
         INTEGER,
      er1645v2Lan2FGUVlanBridgingL2ptDropThrPagp
         INTEGER,
      er1645v2Lan2FGUVlanBridgingL2ptDropThrUdld
         INTEGER,
      er1645v2Lan2FGUVlanVlanVid
         INTEGER,
      er1645v2Lan2FGUVlanVlanVidExtensionSingle
         OCTET STRING,
      er1645v2Lan2FGUVlanVlanVidExtensionEndVid
         Integer32,
      er1645v2Lan2FGUVlanVlanTpid
         INTEGER,
      er1645v2Lan2FGUVlanVlanTagSign
         INTEGER,
      er1645v2Lan2FGUVlanVlanChTos
         INTEGER,
      er1645v2Lan2FGUVlanVlanCTMapP0
         INTEGER,
      er1645v2Lan2FGUVlanVlanCTMapP1
         INTEGER,
      er1645v2Lan2FGUVlanVlanCTMapP2
         INTEGER,
      er1645v2Lan2FGUVlanVlanCTMapP3
         INTEGER,
      er1645v2Lan2FGUVlanVlanCTMapP4
         INTEGER,
      er1645v2Lan2FGUVlanVlanCTMapP5
         INTEGER,
      er1645v2Lan2FGUVlanVlanCTMapP6
         INTEGER,
      er1645v2Lan2FGUVlanVlanCTMapP7
         INTEGER,
      er1645v2Lan2FGUVlanVlanTxCos
         INTEGER,
      er1645v2Lan2FGUVlanVlanCCMapP0
         Integer32,
      er1645v2Lan2FGUVlanVlanCCMapP1
         Integer32,
      er1645v2Lan2FGUVlanVlanCCMapP2
         Integer32,
      er1645v2Lan2FGUVlanVlanCCMapP3
         Integer32,
      er1645v2Lan2FGUVlanVlanCCMapP4
         Integer32,
      er1645v2Lan2FGUVlanVlanCCMapP5
         Integer32,
      er1645v2Lan2FGUVlanVlanCCMapP6
         Integer32,
      er1645v2Lan2FGUVlanVlanCCMapP7
         Integer32,
      er1645v2Lan2FGUVlanVlanQCMapQueue1
         Integer32,
      er1645v2Lan2FGUVlanVlanQCMapQueue2
         Integer32,
      er1645v2Lan2FGUVlanVlanQCMapQueue3
         Integer32,
      er1645v2Lan2FGUVlanVlanQCMapQueue4
         Integer32,
      er1645v2Lan2FGUVlanVlanQCMapQueue5
         Integer32,
      er1645v2Lan2FGUVlanVlanQCMapLowDelayQueue
         Integer32,
      er1645v2Lan2FGUVlanVlanQCMapLowDelay2Queue
         Integer32,
      er1645v2Lan2FGUVlanVlanQCMapSystemQueue
         Integer32,
      er1645v2Lan2FGUVlanVlanQinQSVid
         Integer32,
      er1645v2Lan2FGUVlanVlanQinQSTpid
         INTEGER,
      er1645v2Lan2FGUVlanVlanArpTimeOut
         TimeTicks,
      er1645v2Lan2FGUVlanVlanArpProxyArp
         INTEGER,
      er1645v2Lan2FGUVlanBandwidthMode
         INTEGER,
      er1645v2Lan2FGUVlanBandwidthCir
         Integer32,
      er1645v2Lan2FGUVlanBandwidthEir
         Integer32,
      er1645v2Lan2FGUVlanBandwidthUnit
         INTEGER,
      er1645v2Lan2FGUVlanBandwidthTc
         INTEGER,
      er1645v2Lan2FGUVlanBandwidthTcFactor
         INTEGER,
      er1645v2Lan2FGUVlanBandwidthCorrType
         INTEGER,
      er1645v2Lan2FGUVlanBandwidthCorrPredefEncapsFrameRelay
         DisplayString,
      er1645v2Lan2FGUVlanBandwidthCorrPredefEncapsPpp
         DisplayString,
      er1645v2Lan2FGUVlanBandwidthCorrPredefEncapsAtmHl
         INTEGER,
      er1645v2Lan2FGUVlanBandwidthCorrPredefEncapsAtmMp
         INTEGER,
      er1645v2Lan2FGUVlanBandwidthCorrPredefEncapsHdlc
         DisplayString,
      er1645v2Lan2FGUVlanBandwidthCorrPredefEncapsEfmFs
         Integer32,
      er1645v2Lan2FGUVlanBandwidthCorrPredefEncapsEfmIb
         Integer32,
      er1645v2Lan2FGUVlanBandwidthCorrPredefMode
         INTEGER,
      er1645v2Lan2FGUVlanBandwidthCorrManualOverhead
         Integer32,
      er1645v2Lan2FGUVlanBandwidthCorrManualFrameData
         Counter32,
      er1645v2Lan2FGUVlanBandwidthCorrManualFrameHeader
         Counter32,
      er1645v2Lan2FGUVlanBandwidthMaxFifoQLen
         Integer32,
      er1645v2Lan2FGUVlanBandwidthDeFlagCir
         INTEGER,
      er1645v2Lan2FGUVlanBandwidthDeFlagEir
         INTEGER,
      er1645v2Lan2FGUVlanBandwidthDeFlagViolate
         INTEGER,
      er1645v2Lan2FGUVlanBandwidthActCirActNone
         OCTET STRING,
      er1645v2Lan2FGUVlanBandwidthActCirActEthCos1
         INTEGER,
      er1645v2Lan2FGUVlanBandwidthActCirActEthDei1
         INTEGER,
      er1645v2Lan2FGUVlanBandwidthActCirActEthCos2
         INTEGER,
      er1645v2Lan2FGUVlanBandwidthActCirActEthDei2
         INTEGER,
      er1645v2Lan2FGUVlanBandwidthActCirActEthCos3
         INTEGER,
      er1645v2Lan2FGUVlanBandwidthActCirActEthDei3
         INTEGER,
      er1645v2Lan2FGUVlanBandwidthActCirActEthCos4
         INTEGER,
      er1645v2Lan2FGUVlanBandwidthActCirActEthDei4
         INTEGER,
      er1645v2Lan2FGUVlanBandwidthActCirActEthCos5
         INTEGER,
      er1645v2Lan2FGUVlanBandwidthActCirActEthDei5
         INTEGER,
      er1645v2Lan2FGUVlanBandwidthActCirActEthCos6
         INTEGER,
      er1645v2Lan2FGUVlanBandwidthActCirActEthDei6
         INTEGER,
      er1645v2Lan2FGUVlanBandwidthActCirActEthCos7
         INTEGER,
      er1645v2Lan2FGUVlanBandwidthActCirActEthDei7
         INTEGER,
      er1645v2Lan2FGUVlanBandwidthActCirActEthCos8
         INTEGER,
      er1645v2Lan2FGUVlanBandwidthActCirActEthDei8
         INTEGER,
      er1645v2Lan2FGUVlanBandwidthActCirActEthTos
         INTEGER,
      er1645v2Lan2FGUVlanBandwidthActCirActEthQueue
         INTEGER,
      er1645v2Lan2FGUVlanBandwidthActCirActEthDrpLev
         INTEGER,
      er1645v2Lan2FGUVlanBandwidthActCirActEthDeFlag
         INTEGER,
      er1645v2Lan2FGUVlanBandwidthActCirActIpTos
         INTEGER,
      er1645v2Lan2FGUVlanBandwidthActCirActIpQueue
         INTEGER,
      er1645v2Lan2FGUVlanBandwidthActCirActIpDrpLev
         INTEGER,
      er1645v2Lan2FGUVlanBandwidthActCirActIpDeFlag
         INTEGER,
      er1645v2Lan2FGUVlanBandwidthActEirActNone
         OCTET STRING,
      er1645v2Lan2FGUVlanBandwidthActEirActEthCos1
         INTEGER,
      er1645v2Lan2FGUVlanBandwidthActEirActEthDei1
         INTEGER,
      er1645v2Lan2FGUVlanBandwidthActEirActEthCos2
         INTEGER,
      er1645v2Lan2FGUVlanBandwidthActEirActEthDei2
         INTEGER,
      er1645v2Lan2FGUVlanBandwidthActEirActEthCos3
         INTEGER,
      er1645v2Lan2FGUVlanBandwidthActEirActEthDei3
         INTEGER,
      er1645v2Lan2FGUVlanBandwidthActEirActEthCos4
         INTEGER,
      er1645v2Lan2FGUVlanBandwidthActEirActEthDei4
         INTEGER,
      er1645v2Lan2FGUVlanBandwidthActEirActEthCos5
         INTEGER,
      er1645v2Lan2FGUVlanBandwidthActEirActEthDei5
         INTEGER,
      er1645v2Lan2FGUVlanBandwidthActEirActEthCos6
         INTEGER,
      er1645v2Lan2FGUVlanBandwidthActEirActEthDei6
         INTEGER,
      er1645v2Lan2FGUVlanBandwidthActEirActEthCos7
         INTEGER,
      er1645v2Lan2FGUVlanBandwidthActEirActEthDei7
         INTEGER,
      er1645v2Lan2FGUVlanBandwidthActEirActEthCos8
         INTEGER,
      er1645v2Lan2FGUVlanBandwidthActEirActEthDei8
         INTEGER,
      er1645v2Lan2FGUVlanBandwidthActEirActEthTos
         INTEGER,
      er1645v2Lan2FGUVlanBandwidthActEirActEthQueue
         INTEGER,
      er1645v2Lan2FGUVlanBandwidthActEirActEthDrpLev
         INTEGER,
      er1645v2Lan2FGUVlanBandwidthActEirActEthDeFlag
         INTEGER,
      er1645v2Lan2FGUVlanBandwidthActEirActIpTos
         INTEGER,
      er1645v2Lan2FGUVlanBandwidthActEirActIpQueue
         INTEGER,
      er1645v2Lan2FGUVlanBandwidthActEirActIpDrpLev
         INTEGER,
      er1645v2Lan2FGUVlanBandwidthActEirActIpDeFlag
         INTEGER,
      er1645v2Lan2FGUVlanBandwidthActViolActNone
         OCTET STRING,
      er1645v2Lan2FGUVlanBandwidthActViolActDrop
         OCTET STRING,
      er1645v2Lan2FGUVlanBandwidthActViolActEthCos1
         INTEGER,
      er1645v2Lan2FGUVlanBandwidthActViolActEthDei1
         INTEGER,
      er1645v2Lan2FGUVlanBandwidthActViolActEthCos2
         INTEGER,
      er1645v2Lan2FGUVlanBandwidthActViolActEthDei2
         INTEGER,
      er1645v2Lan2FGUVlanBandwidthActViolActEthCos3
         INTEGER,
      er1645v2Lan2FGUVlanBandwidthActViolActEthDei3
         INTEGER,
      er1645v2Lan2FGUVlanBandwidthActViolActEthCos4
         INTEGER,
      er1645v2Lan2FGUVlanBandwidthActViolActEthDei4
         INTEGER,
      er1645v2Lan2FGUVlanBandwidthActViolActEthCos5
         INTEGER,
      er1645v2Lan2FGUVlanBandwidthActViolActEthDei5
         INTEGER,
      er1645v2Lan2FGUVlanBandwidthActViolActEthCos6
         INTEGER,
      er1645v2Lan2FGUVlanBandwidthActViolActEthDei6
         INTEGER,
      er1645v2Lan2FGUVlanBandwidthActViolActEthCos7
         INTEGER,
      er1645v2Lan2FGUVlanBandwidthActViolActEthDei7
         INTEGER,
      er1645v2Lan2FGUVlanBandwidthActViolActEthCos8
         INTEGER,
      er1645v2Lan2FGUVlanBandwidthActViolActEthDei8
         INTEGER,
      er1645v2Lan2FGUVlanBandwidthActViolActEthTos
         INTEGER,
      er1645v2Lan2FGUVlanBandwidthActViolActEthQueue
         INTEGER,
      er1645v2Lan2FGUVlanBandwidthActViolActEthDrpLev
         INTEGER,
      er1645v2Lan2FGUVlanBandwidthActViolActEthDeFlag
         INTEGER,
      er1645v2Lan2FGUVlanBandwidthActViolActIpTos
         INTEGER,
      er1645v2Lan2FGUVlanBandwidthActViolActIpQueue
         INTEGER,
      er1645v2Lan2FGUVlanBandwidthActViolActIpDrpLev
         INTEGER,
      er1645v2Lan2FGUVlanBandwidthActViolActIpDeFlag
         INTEGER,
      er1645v2Lan2FGUVlanInbBwMode
         INTEGER,
      er1645v2Lan2FGUVlanInbBwCir
         Integer32,
      er1645v2Lan2FGUVlanInbBwEir
         Integer32,
      er1645v2Lan2FGUVlanInbBwUnit
         INTEGER,
      er1645v2Lan2FGUVlanInbBwTc
         INTEGER,
      er1645v2Lan2FGUVlanInbBwTcFactor
         INTEGER,
      er1645v2Lan2FGUVlanInbBwCorrType
         INTEGER,
      er1645v2Lan2FGUVlanInbBwCorrPredefEncapsFrameRelay
         DisplayString,
      er1645v2Lan2FGUVlanInbBwCorrPredefEncapsPpp
         DisplayString,
      er1645v2Lan2FGUVlanInbBwCorrPredefEncapsAtmHl
         INTEGER,
      er1645v2Lan2FGUVlanInbBwCorrPredefEncapsAtmMp
         INTEGER,
      er1645v2Lan2FGUVlanInbBwCorrPredefEncapsHdlc
         DisplayString,
      er1645v2Lan2FGUVlanInbBwCorrPredefEncapsEfmFs
         Integer32,
      er1645v2Lan2FGUVlanInbBwCorrPredefEncapsEfmIb
         Integer32,
      er1645v2Lan2FGUVlanInbBwCorrPredefMode
         INTEGER,
      er1645v2Lan2FGUVlanInbBwCorrManualOverhead
         Integer32,
      er1645v2Lan2FGUVlanInbBwCorrManualFrameData
         Counter32,
      er1645v2Lan2FGUVlanInbBwCorrManualFrameHeader
         Counter32,
      er1645v2Lan2FGUVlanInbBwMaxFifoQLen
         Integer32,
      er1645v2Lan2FGUVlanInbBwPriorityPolicy
         DisplayString,
      er1645v2Lan2FGUVlanInbBwDeFlagCir
         INTEGER,
      er1645v2Lan2FGUVlanInbBwDeFlagEir
         INTEGER,
      er1645v2Lan2FGUVlanInbBwDeFlagViolate
         INTEGER,
      er1645v2Lan2FGUVlanInbBwActCirActNone
         OCTET STRING,
      er1645v2Lan2FGUVlanInbBwActCirActEthCos1
         INTEGER,
      er1645v2Lan2FGUVlanInbBwActCirActEthDei1
         INTEGER,
      er1645v2Lan2FGUVlanInbBwActCirActEthCos2
         INTEGER,
      er1645v2Lan2FGUVlanInbBwActCirActEthDei2
         INTEGER,
      er1645v2Lan2FGUVlanInbBwActCirActEthCos3
         INTEGER,
      er1645v2Lan2FGUVlanInbBwActCirActEthDei3
         INTEGER,
      er1645v2Lan2FGUVlanInbBwActCirActEthCos4
         INTEGER,
      er1645v2Lan2FGUVlanInbBwActCirActEthDei4
         INTEGER,
      er1645v2Lan2FGUVlanInbBwActCirActEthCos5
         INTEGER,
      er1645v2Lan2FGUVlanInbBwActCirActEthDei5
         INTEGER,
      er1645v2Lan2FGUVlanInbBwActCirActEthCos6
         INTEGER,
      er1645v2Lan2FGUVlanInbBwActCirActEthDei6
         INTEGER,
      er1645v2Lan2FGUVlanInbBwActCirActEthCos7
         INTEGER,
      er1645v2Lan2FGUVlanInbBwActCirActEthDei7
         INTEGER,
      er1645v2Lan2FGUVlanInbBwActCirActEthCos8
         INTEGER,
      er1645v2Lan2FGUVlanInbBwActCirActEthDei8
         INTEGER,
      er1645v2Lan2FGUVlanInbBwActCirActEthTos
         INTEGER,
      er1645v2Lan2FGUVlanInbBwActCirActEthQueue
         INTEGER,
      er1645v2Lan2FGUVlanInbBwActCirActEthDrpLev
         INTEGER,
      er1645v2Lan2FGUVlanInbBwActCirActEthDeFlag
         INTEGER,
      er1645v2Lan2FGUVlanInbBwActCirActIpTos
         INTEGER,
      er1645v2Lan2FGUVlanInbBwActCirActIpQueue
         INTEGER,
      er1645v2Lan2FGUVlanInbBwActCirActIpDrpLev
         INTEGER,
      er1645v2Lan2FGUVlanInbBwActCirActIpDeFlag
         INTEGER,
      er1645v2Lan2FGUVlanInbBwActEirActNone
         OCTET STRING,
      er1645v2Lan2FGUVlanInbBwActEirActEthCos1
         INTEGER,
      er1645v2Lan2FGUVlanInbBwActEirActEthDei1
         INTEGER,
      er1645v2Lan2FGUVlanInbBwActEirActEthCos2
         INTEGER,
      er1645v2Lan2FGUVlanInbBwActEirActEthDei2
         INTEGER,
      er1645v2Lan2FGUVlanInbBwActEirActEthCos3
         INTEGER,
      er1645v2Lan2FGUVlanInbBwActEirActEthDei3
         INTEGER,
      er1645v2Lan2FGUVlanInbBwActEirActEthCos4
         INTEGER,
      er1645v2Lan2FGUVlanInbBwActEirActEthDei4
         INTEGER,
      er1645v2Lan2FGUVlanInbBwActEirActEthCos5
         INTEGER,
      er1645v2Lan2FGUVlanInbBwActEirActEthDei5
         INTEGER,
      er1645v2Lan2FGUVlanInbBwActEirActEthCos6
         INTEGER,
      er1645v2Lan2FGUVlanInbBwActEirActEthDei6
         INTEGER,
      er1645v2Lan2FGUVlanInbBwActEirActEthCos7
         INTEGER,
      er1645v2Lan2FGUVlanInbBwActEirActEthDei7
         INTEGER,
      er1645v2Lan2FGUVlanInbBwActEirActEthCos8
         INTEGER,
      er1645v2Lan2FGUVlanInbBwActEirActEthDei8
         INTEGER,
      er1645v2Lan2FGUVlanInbBwActEirActEthTos
         INTEGER,
      er1645v2Lan2FGUVlanInbBwActEirActEthQueue
         INTEGER,
      er1645v2Lan2FGUVlanInbBwActEirActEthDrpLev
         INTEGER,
      er1645v2Lan2FGUVlanInbBwActEirActEthDeFlag
         INTEGER,
      er1645v2Lan2FGUVlanInbBwActEirActIpTos
         INTEGER,
      er1645v2Lan2FGUVlanInbBwActEirActIpQueue
         INTEGER,
      er1645v2Lan2FGUVlanInbBwActEirActIpDrpLev
         INTEGER,
      er1645v2Lan2FGUVlanInbBwActEirActIpDeFlag
         INTEGER,
      er1645v2Lan2FGUVlanInbBwActViolActNone
         OCTET STRING,
      er1645v2Lan2FGUVlanInbBwActViolActDrop
         OCTET STRING,
      er1645v2Lan2FGUVlanInbBwActViolActEthCos1
         INTEGER,
      er1645v2Lan2FGUVlanInbBwActViolActEthDei1
         INTEGER,
      er1645v2Lan2FGUVlanInbBwActViolActEthCos2
         INTEGER,
      er1645v2Lan2FGUVlanInbBwActViolActEthDei2
         INTEGER,
      er1645v2Lan2FGUVlanInbBwActViolActEthCos3
         INTEGER,
      er1645v2Lan2FGUVlanInbBwActViolActEthDei3
         INTEGER,
      er1645v2Lan2FGUVlanInbBwActViolActEthCos4
         INTEGER,
      er1645v2Lan2FGUVlanInbBwActViolActEthDei4
         INTEGER,
      er1645v2Lan2FGUVlanInbBwActViolActEthCos5
         INTEGER,
      er1645v2Lan2FGUVlanInbBwActViolActEthDei5
         INTEGER,
      er1645v2Lan2FGUVlanInbBwActViolActEthCos6
         INTEGER,
      er1645v2Lan2FGUVlanInbBwActViolActEthDei6
         INTEGER,
      er1645v2Lan2FGUVlanInbBwActViolActEthCos7
         INTEGER,
      er1645v2Lan2FGUVlanInbBwActViolActEthDei7
         INTEGER,
      er1645v2Lan2FGUVlanInbBwActViolActEthCos8
         INTEGER,
      er1645v2Lan2FGUVlanInbBwActViolActEthDei8
         INTEGER,
      er1645v2Lan2FGUVlanInbBwActViolActEthTos
         INTEGER,
      er1645v2Lan2FGUVlanInbBwActViolActEthQueue
         INTEGER,
      er1645v2Lan2FGUVlanInbBwActViolActEthDrpLev
         INTEGER,
      er1645v2Lan2FGUVlanInbBwActViolActEthDeFlag
         INTEGER,
      er1645v2Lan2FGUVlanInbBwActViolActIpTos
         INTEGER,
      er1645v2Lan2FGUVlanInbBwActViolActIpQueue
         INTEGER,
      er1645v2Lan2FGUVlanInbBwActViolActIpDrpLev
         INTEGER,
      er1645v2Lan2FGUVlanInbBwActViolActIpDeFlag
         INTEGER,
      er1645v2Lan2FGUVlanPppoE
         INTEGER,
      er1645v2Lan2FGUVlanPppLnkMOperation
         INTEGER,
      er1645v2Lan2FGUVlanPppLnkMInterval
         TimeTicks,
      er1645v2Lan2FGUVlanPppLnkMRepTimeOut
         TimeTicks,
      er1645v2Lan2FGUVlanPppLnkMFailsPrmt
         Integer32,
      er1645v2Lan2FGUVlanPppAuthentication
         INTEGER,
      er1645v2Lan2FGUVlanPppAuthenPeriod
         TimeTicks,
      er1645v2Lan2FGUVlanPppSessionName
         DisplayString,
      er1645v2Lan2FGUVlanPppSessionSecret
         DisplayString,
      er1645v2Lan2FGUVlanPppEncModeSessionSecret
         INTEGER,
      er1645v2Lan2FGUVlanPppEncSessionSecret
         DisplayString,
      er1645v2Lan2FGUVlanPppServiceName
         DisplayString,
      er1645v2Lan2FGUVlanPbbMode
         INTEGER,
      er1645v2Lan2FGUVlanPbbTxCos
         Integer32,
      er1645v2Lan2FGUVlanPbbIsid
         Integer32,
      er1645v2Lan2FGUVlanPbbDestMac
         OCTET STRING,
      er1645v2Lan2FGUVlanPbbCustomGroupMac
         OCTET STRING
      }

er1645v2Lan2FGUVlanActions OBJECT-TYPE
   SYNTAX      VariableLengthTableActions
   MAX-ACCESS  read-write
   STATUS      current
   DESCRIPTION
      "By way of this field, some manipulations
       on this table may be performed."
   ::= {er1645v2Lan2FGUVlanEntry 2}

er1645v2Lan2FGUVlanTableIx OBJECT-TYPE
   SYNTAX      TableIndex
   MAX-ACCESS  not-accessible
   STATUS      current
   DESCRIPTION
      ""
   ::= {er1645v2Lan2FGUVlanEntry 11}

er1645v2Lan2FGUVlanName OBJECT-TYPE
   SYNTAX      DisplayString
   MAX-ACCESS  read-write
   STATUS      current
   DESCRIPTION
      "Path: ethernet2.editConf.vlan.name"
   ::= {er1645v2Lan2FGUVlanEntry 16777216}

er1645v2Lan2FGUVlanRemark OBJECT-TYPE
   SYNTAX      DisplayString
   MAX-ACCESS  read-write
   STATUS      current
   DESCRIPTION
      "Path: ethernet2.editConf.vlan.remark"
   ::= {er1645v2Lan2FGUVlanEntry 1157627904}

er1645v2Lan2FGUVlanAdminStatus OBJECT-TYPE
   SYNTAX      INTEGER
               {
               up (1),
               down (2)
               }
   MAX-ACCESS  read-write
   STATUS      current
   DESCRIPTION
      "Path: ethernet2.editConf.vlan.adminStatus

       Possibilities:
               up   (1)
               down   (2)"
   ::= {er1645v2Lan2FGUVlanEntry 33554432}

er1645v2Lan2FGUVlanMode OBJECT-TYPE
   SYNTAX      INTEGER
               {
               routing (1),
               bridging (2),
               ipV6 (16),
               ipV6ipV4 (17),
               multilink (8)
               }
   MAX-ACCESS  read-write
   STATUS      current
   DESCRIPTION
      "Path: ethernet2.editConf.vlan.mode

       Possibilities:
               routing   (1)
               bridging   (2)
               ipV6   (16)
               ipV6/ipV4   (17)
               multilink   (8)"
   ::= {er1645v2Lan2FGUVlanEntry 67108864}

er1645v2Lan2FGUVlanPriorityPolicy OBJECT-TYPE
   SYNTAX      DisplayString
   MAX-ACCESS  read-write
   STATUS      current
   DESCRIPTION
      "Path: ethernet2.editConf.vlan.priorityPolicy"
   ::= {er1645v2Lan2FGUVlanEntry 83886080}

er1645v2Lan2FGUVlanIpVrfRouter OBJECT-TYPE
   SYNTAX      DisplayString
   MAX-ACCESS  read-write
   STATUS      current
   DESCRIPTION
      "Path: ethernet2.editConf.vlan.ip.vrfRouter"
   ::= {er1645v2Lan2FGUVlanEntry 53215232}

er1645v2Lan2FGUVlanIpAdr OBJECT-TYPE
   SYNTAX      IpAddress
   MAX-ACCESS  read-write
   STATUS      current
   DESCRIPTION
      "Path: ethernet2.editConf.vlan.ip.address"
   ::= {er1645v2Lan2FGUVlanEntry 58261504}

er1645v2Lan2FGUVlanIpNetm OBJECT-TYPE
   SYNTAX      IpAddress
   MAX-ACCESS  read-write
   STATUS      current
   DESCRIPTION
      "Path: ethernet2.editConf.vlan.ip.netMask"
   ::= {er1645v2Lan2FGUVlanEntry 58392576}

er1645v2Lan2FGUVlanIpSNetName OBJECT-TYPE
   SYNTAX      INTEGER
               {
               slOPTg (0),
               corp (2),
               dmz (3),
               internet (1)
               }
   MAX-ACCESS  read-write
   STATUS      current
   DESCRIPTION
      "Path: ethernet2.editConf.vlan.ip.sNet.name

       Possibilities:
               <OPT>   (0)
               corp   (2)
               dmz   (3)
               internet   (1)"
   ::= {er1645v2Lan2FGUVlanEntry 53674240}

er1645v2Lan2FGUVlanIpSNetCust OBJECT-TYPE
   SYNTAX      DisplayString
   MAX-ACCESS  read-write
   STATUS      current
   DESCRIPTION
      "Path: ethernet2.editConf.vlan.ip.sNet.custom"
   ::= {er1645v2Lan2FGUVlanEntry 53674496}

er1645v2Lan2FGUVlanIpDhcpC OBJECT-TYPE
   SYNTAX      INTEGER
               {
               disabled (0),
               enabled (1)
               }
   MAX-ACCESS  read-write
   STATUS      current
   DESCRIPTION
      "Path: ethernet2.editConf.vlan.ip.dhcpClient

       Possibilities:
               disabled   (0)
               enabled   (1)"
   ::= {er1645v2Lan2FGUVlanEntry 53608448}

er1645v2Lan2FGUVlanIpDhcpGatewayPreference OBJECT-TYPE
   SYNTAX      Integer32
   MAX-ACCESS  read-write
   STATUS      current
   DESCRIPTION
      "Path: ethernet2.editConf.vlan.ip.dhcp.gatewayPreference"
   ::= {er1645v2Lan2FGUVlanEntry 53739776}

er1645v2Lan2FGUVlanIpDhcpRoutePreference OBJECT-TYPE
   SYNTAX      Integer32
   MAX-ACCESS  read-write
   STATUS      current
   DESCRIPTION
      "Path: ethernet2.editConf.vlan.ip.dhcp.routePreference"
   ::= {er1645v2Lan2FGUVlanEntry 53740032}

er1645v2Lan2FGUVlanIpDhcpDnsPreference OBJECT-TYPE
   SYNTAX      Integer32
   MAX-ACCESS  read-write
   STATUS      current
   DESCRIPTION
      "Path: ethernet2.editConf.vlan.ip.dhcp.dnsPreference"
   ::= {er1645v2Lan2FGUVlanEntry 53740288}

er1645v2Lan2FGUVlanIpMtu OBJECT-TYPE
   SYNTAX      Integer32
   MAX-ACCESS  read-write
   STATUS      current
   DESCRIPTION
      "Path: ethernet2.editConf.vlan.ip.mtu"
   ::= {er1645v2Lan2FGUVlanEntry 52953088}

er1645v2Lan2FGUVlanIpMssAdjust OBJECT-TYPE
   SYNTAX      INTEGER
               {
               disabled (0),
               auto (65536)
               }
   MAX-ACCESS  read-write
   STATUS      current
   DESCRIPTION
      "Path: ethernet2.editConf.vlan.ip.mssAdjust

       Possibilities:
               disabled   (0)
               auto   (65536)"
   ::= {er1645v2Lan2FGUVlanEntry 53280768}

er1645v2Lan2FGUVlanIpRipMetric OBJECT-TYPE
   SYNTAX      Integer32
   MAX-ACCESS  read-write
   STATUS      current
   DESCRIPTION
      "Path: ethernet2.editConf.vlan.ip.rip.metric"
   ::= {er1645v2Lan2FGUVlanEntry 51712768}

er1645v2Lan2FGUVlanIpRipMetricOut OBJECT-TYPE
   SYNTAX      Integer32
   MAX-ACCESS  read-write
   STATUS      current
   DESCRIPTION
      "Path: ethernet2.editConf.vlan.ip.rip.metricOut"
   ::= {er1645v2Lan2FGUVlanEntry 51713024}

er1645v2Lan2FGUVlanIpRipMode OBJECT-TYPE
   SYNTAX      INTEGER
               {
               disabled (0),
               passive (1),
               active (2)
               }
   MAX-ACCESS  read-write
   STATUS      current
   DESCRIPTION
      "Path: ethernet2.editConf.vlan.ip.rip.mode

       Possibilities:
               disabled   (0)
               passive   (1)
               active   (2)"
   ::= {er1645v2Lan2FGUVlanEntry 51713280}

er1645v2Lan2FGUVlanIpRipTxVer OBJECT-TYPE
   SYNTAX      INTEGER
               {
               rip1 (0),
               rip2 (1),
               rip1mcompatible (2)
               }
   MAX-ACCESS  read-write
   STATUS      current
   DESCRIPTION
      "Path: ethernet2.editConf.vlan.ip.rip.txVersion

       Possibilities:
               rip1   (0)
               rip2   (1)
               rip1-compatible   (2)"
   ::= {er1645v2Lan2FGUVlanEntry 51716864}

er1645v2Lan2FGUVlanIpRipRxVer OBJECT-TYPE
   SYNTAX      INTEGER
               {
               rip1only (0),
               rip2only (1),
               rip12 (2)
               }
   MAX-ACCESS  read-write
   STATUS      current
   DESCRIPTION
      "Path: ethernet2.editConf.vlan.ip.rip.rxVersion

       Possibilities:
               rip1only   (0)
               rip2only   (1)
               rip1&2   (2)"
   ::= {er1645v2Lan2FGUVlanEntry 51717120}

er1645v2Lan2FGUVlanIpRipSplitH OBJECT-TYPE
   SYNTAX      INTEGER
               {
               disabled (0),
               enabled (1),
               poisonedReverse (2)
               }
   MAX-ACCESS  read-write
   STATUS      current
   DESCRIPTION
      "Path: ethernet2.editConf.vlan.ip.rip.splitHorizon

       Possibilities:
               disabled   (0)
               enabled   (1)
               poisonedReverse   (2)"
   ::= {er1645v2Lan2FGUVlanEntry 51713792}

er1645v2Lan2FGUVlanIpRipAuth OBJECT-TYPE
   SYNTAX      INTEGER
               {
               disabled (0),
               texts (1),
               md5 (2)
               }
   MAX-ACCESS  read-write
   STATUS      current
   DESCRIPTION
      "Path: ethernet2.editConf.vlan.ip.rip.authentication

       Possibilities:
               disabled   (0)
               text    (1)
               md5   (2)"
   ::= {er1645v2Lan2FGUVlanEntry 51712512}

er1645v2Lan2FGUVlanIpRipFilter OBJECT-TYPE
   SYNTAX      DisplayString
   MAX-ACCESS  read-write
   STATUS      current
   DESCRIPTION
      "Path: ethernet2.editConf.vlan.ip.rip.filter"
   ::= {er1645v2Lan2FGUVlanEntry 51716096}

er1645v2Lan2FGUVlanIpRipFilterIn OBJECT-TYPE
   SYNTAX      DisplayString
   MAX-ACCESS  read-write
   STATUS      current
   DESCRIPTION
      "Path: ethernet2.editConf.vlan.ip.rip.filterIn"
   ::= {er1645v2Lan2FGUVlanEntry 51716352}

er1645v2Lan2FGUVlanIpRipClearNextHop OBJECT-TYPE
   SYNTAX      INTEGER
               {
               disabled (0),
               enabled (1)
               }
   MAX-ACCESS  read-write
   STATUS      current
   DESCRIPTION
      "Path: ethernet2.editConf.vlan.ip.rip.clearNextHop

       Possibilities:
               disabled   (0)
               enabled   (1)"
   ::= {er1645v2Lan2FGUVlanEntry 51708416}

er1645v2Lan2FGUVlanIpAccPol OBJECT-TYPE
   SYNTAX      DisplayString
   MAX-ACCESS  read-write
   STATUS      current
   DESCRIPTION
      "Path: ethernet2.editConf.vlan.ip.accessPolicy"
   ::= {er1645v2Lan2FGUVlanEntry 53084160}

er1645v2Lan2FGUVlanIpAB OBJECT-TYPE
   SYNTAX      DisplayString
   MAX-ACCESS  read-write
   STATUS      current
   DESCRIPTION
      "Path: ethernet2.editConf.vlan.ip.trafficPolicy"
   ::= {er1645v2Lan2FGUVlanEntry 51249152}

er1645v2Lan2FGUVlanIpMA OBJECT-TYPE
   SYNTAX      INTEGER
               {
               disabled (0),
               enabled (1)
               }
   MAX-ACCESS  read-write
   STATUS      current
   DESCRIPTION
      "Path: ethernet2.editConf.vlan.ip.mgmtAccess

       Possibilities:
               disabled   (0)
               enabled   (1)"
   ::= {er1645v2Lan2FGUVlanEntry 51380224}

er1645v2Lan2FGUVlanIpMF OBJECT-TYPE
   SYNTAX      Integer32
   MAX-ACCESS  read-write
   STATUS      current
   DESCRIPTION
      "Path: ethernet2.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGUVlanEntry 51445760}

er1645v2Lan2FGUVlanIpDB OBJECT-TYPE
   SYNTAX      INTEGER
               {
               disabled (0),
               enabled (1)
               }
   MAX-ACCESS  read-write
   STATUS      current
   DESCRIPTION
      "Path: ethernet2.editConf.vlan.ip.directedBroadcasts

       Possibilities:
               disabled   (0)
               enabled   (1)"
   ::= {er1645v2Lan2FGUVlanEntry 51773440}

er1645v2Lan2FGUVlanIpIR OBJECT-TYPE
   SYNTAX      INTEGER
               {
               disabled (0),
               enabled (1)
               }
   MAX-ACCESS  read-write
   STATUS      current
   DESCRIPTION
      "Path: ethernet2.editConf.vlan.ip.icmpRedirects

       Possibilities:
               disabled   (0)
               enabled   (1)"
   ::= {er1645v2Lan2FGUVlanEntry 52035584}

er1645v2Lan2FGUVlanIpIgmp OBJECT-TYPE
   SYNTAX      INTEGER
               {
               disabled (0),
               proxy (1),
               router (2),
               v3Router (5)
               }
   MAX-ACCESS  read-write
   STATUS      current
   DESCRIPTION
      "Path: ethernet2.editConf.vlan.ip.igmp

       Possibilities:
               disabled   (0)
               proxy   (1)
               router   (2)
               v3Router   (5)"
   ::= {er1645v2Lan2FGUVlanEntry 52428800}

er1645v2Lan2FGUVlanIpNN OBJECT-TYPE
   SYNTAX      DisplayString
   MAX-ACCESS  read-write
   STATUS      current
   DESCRIPTION
      "Path: ethernet2.editConf.vlan.ip.nat"
   ::= {er1645v2Lan2FGUVlanEntry 52101120}

er1645v2Lan2FGUVlanIpVrrp OBJECT-TYPE
   SYNTAX      INTEGER
               {
               disabled (0),
               enabled (1)
               }
   MAX-ACCESS  read-write
   STATUS      current
   DESCRIPTION
      "Path: ethernet2.editConf.vlan.ip.vrrp

       Possibilities:
               disabled   (0)
               enabled   (1)"
   ::= {er1645v2Lan2FGUVlanEntry 53149696}

er1645v2Lan2FGUVlanIpPimMode OBJECT-TYPE
   SYNTAX      INTEGER
               {
               disabled (0),
               sparse (1),
               passive (2)
               }
   MAX-ACCESS  read-write
   STATUS      current
   DESCRIPTION
      "Path: ethernet2.editConf.vlan.ip.pim.mode

       Possibilities:
               disabled   (0)
               sparse   (1)
               passive   (2)"
   ::= {er1645v2Lan2FGUVlanEntry 53346560}

er1645v2Lan2FGUVlanIpPimDrPriority OBJECT-TYPE
   SYNTAX      Counter32
   MAX-ACCESS  read-write
   STATUS      current
   DESCRIPTION
      "Path: ethernet2.editConf.vlan.ip.pim.drPriority

       32 bit unsigned wrappable counter."
   ::= {er1645v2Lan2FGUVlanEntry 53346816}

er1645v2Lan2FGUVlanIpPimHelloTime OBJECT-TYPE
   SYNTAX      TimeTicks
   MAX-ACCESS  read-write
   STATUS      current
   DESCRIPTION
      "Path: ethernet2.editConf.vlan.ip.pim.helloTime

       Time in centi-second."
   ::= {er1645v2Lan2FGUVlanEntry 53347072}

er1645v2Lan2FGUVlanIpPimPropagationDelay OBJECT-TYPE
   SYNTAX      TimeTicks
   MAX-ACCESS  read-write
   STATUS      current
   DESCRIPTION
      "Path: ethernet2.editConf.vlan.ip.pim.propagationDelay

       Time in centi-second."
   ::= {er1645v2Lan2FGUVlanEntry 53347328}

er1645v2Lan2FGUVlanIpPimOverrideInterval OBJECT-TYPE
   SYNTAX      TimeTicks
   MAX-ACCESS  read-write
   STATUS      current
   DESCRIPTION
      "Path: ethernet2.editConf.vlan.ip.pim.overrideInterval

       Time in centi-second."
   ::= {er1645v2Lan2FGUVlanEntry 53347584}

er1645v2Lan2FGUVlanIpPimBsrBorder OBJECT-TYPE
   SYNTAX      INTEGER
               {
               disabled (0),
               enabled (1)
               }
   MAX-ACCESS  read-write
   STATUS      current
   DESCRIPTION
      "Path: ethernet2.editConf.vlan.ip.pim.bsrBorder

       Possibilities:
               disabled   (0)
               enabled   (1)"
   ::= {er1645v2Lan2FGUVlanEntry 53347840}

er1645v2Lan2FGUVlanIpPimTtlThreshold OBJECT-TYPE
   SYNTAX      Integer32
   MAX-ACCESS  read-write
   STATUS      current
   DESCRIPTION
      "Path: ethernet2.editConf.vlan.ip.pim.ttlThreshold"
   ::= {er1645v2Lan2FGUVlanEntry 53348096}

er1645v2Lan2FGUVlanIpIMNetworkUnreachable OBJECT-TYPE
   SYNTAX      INTEGER
               {
               disabled (0),
               enabled (1)
               }
   MAX-ACCESS  read-write
   STATUS      current
   DESCRIPTION
      "Path: ethernet2.editConf.vlan.ip.icmpMessages.networkUnreachable

       Possibilities:
               disabled   (0)
               enabled   (1)"
   ::= {er1645v2Lan2FGUVlanEntry 53412096}

er1645v2Lan2FGUVlanIpIMHostUnreachable OBJECT-TYPE
   SYNTAX      INTEGER
               {
               disabled (0),
               enabled (1)
               }
   MAX-ACCESS  read-write
   STATUS      current
   DESCRIPTION
      "Path: ethernet2.editConf.vlan.ip.icmpMessages.hostUnreachable

       Possibilities:
               disabled   (0)
               enabled   (1)"
   ::= {er1645v2Lan2FGUVlanEntry 53412352}

er1645v2Lan2FGUVlanIpIMProtocolUnreachable OBJECT-TYPE
   SYNTAX      INTEGER
               {
               disabled (0),
               enabled (1)
               }
   MAX-ACCESS  read-write
   STATUS      current
   DESCRIPTION
      "Path: ethernet2.editConf.vlan.ip.icmpMessages.protocolUnreachable

       Possibilities:
               disabled   (0)
               enabled   (1)"
   ::= {er1645v2Lan2FGUVlanEntry 53412608}

er1645v2Lan2FGUVlanIpIMPortUnreachable OBJECT-TYPE
   SYNTAX      INTEGER
               {
               disabled (0),
               enabled (1)
               }
   MAX-ACCESS  read-write
   STATUS      current
   DESCRIPTION
      "Path: ethernet2.editConf.vlan.ip.icmpMessages.portUnreachable

       Possibilities:
               disabled   (0)
               enabled   (1)"
   ::= {er1645v2Lan2FGUVlanEntry 53412864}

er1645v2Lan2FGUVlanIpIMMtuExceeded OBJECT-TYPE
   SYNTAX      INTEGER
               {
               disabled (0),
               enabled (1)
               }
   MAX-ACCESS  read-write
   STATUS      current
   DESCRIPTION
      "Path: ethernet2.editConf.vlan.ip.icmpMessages.mtuExceeded

       Possibilities:
               disabled   (0)
               enabled   (1)"
   ::= {er1645v2Lan2FGUVlanEntry 53413120}

er1645v2Lan2FGUVlanIpIMAdminProhibited OBJECT-TYPE
   SYNTAX      INTEGER
               {
               disabled (0),
               enabled (1)
               }
   MAX-ACCESS  read-write
   STATUS      current
   DESCRIPTION
      "Path: ethernet2.editConf.vlan.ip.icmpMessages.adminProhibited

       Possibilities:
               disabled   (0)
               enabled   (1)"
   ::= {er1645v2Lan2FGUVlanEntry 53413376}

er1645v2Lan2FGUVlanIpIMTtlExceeded OBJECT-TYPE
   SYNTAX      INTEGER
               {
               disabled (0),
               enabled (1)
               }
   MAX-ACCESS  read-write
   STATUS      current
   DESCRIPTION
      "Path: ethernet2.editConf.vlan.ip.icmpMessages.ttlExceeded

       Possibilities:
               disabled   (0)
               enabled   (1)"
   ::= {er1645v2Lan2FGUVlanEntry 53413632}

er1645v2Lan2FGUVlanIpIMRedirect OBJECT-TYPE
   SYNTAX      INTEGER
               {
               disabled (0),
               enabled (1)
               }
   MAX-ACCESS  read-write
   STATUS      current
   DESCRIPTION
      "Path: ethernet2.editConf.vlan.ip.icmpMessages.redirect

       Possibilities:
               disabled   (0)
               enabled   (1)"
   ::= {er1645v2Lan2FGUVlanEntry 53413888}

er1645v2Lan2FGUVlanIpV6VrfRouter OBJECT-TYPE
   SYNTAX      DisplayString
   MAX-ACCESS  read-write
   STATUS      current
   DESCRIPTION
      "Path: ethernet2.editConf.vlan.ipV6.vrfRouter"
   ::= {er1645v2Lan2FGUVlanEntry 704708608}

er1645v2Lan2FGUVlanIpV6AddrAutoConfigNrDupAddrDetects OBJECT-TYPE
   SYNTAX      Integer32
   MAX-ACCESS  read-write
   STATUS      current
   DESCRIPTION
      "Path: ethernet2.editConf.vlan.ipV6.addrAutoConfig.nrDupAddrDetects"
   ::= {er1645v2Lan2FGUVlanEntry 704905472}

er1645v2Lan2FGUVlanIpV6AddrAutoConfigAcceptRa OBJECT-TYPE
   SYNTAX      INTEGER
               {
               disabled (0),
               enabled (1)
               }
   MAX-ACCESS  read-write
   STATUS      current
   DESCRIPTION
      "Path: ethernet2.editConf.vlan.ipV6.addrAutoConfig.acceptRa

       Possibilities:
               disabled   (0)
               enabled   (1)"
   ::= {er1645v2Lan2FGUVlanEntry 704905728}

er1645v2Lan2FGUVlanIpV6AddrAutoConfigAcceptRaRdnss OBJECT-TYPE
   SYNTAX      INTEGER
               {
               disabled (0),
               enabled (1)
               }
   MAX-ACCESS  read-write
   STATUS      current
   DESCRIPTION
      "Path: ethernet2.editConf.vlan.ipV6.addrAutoConfig.acceptRaRdnss

       Possibilities:
               disabled   (0)
               enabled   (1)"
   ::= {er1645v2Lan2FGUVlanEntry 704905984}

er1645v2Lan2FGUVlanIpV6AddrAutoConfigAcceptRaDnssl OBJECT-TYPE
   SYNTAX      INTEGER
               {
               disabled (0),
               enabled (1)
               }
   MAX-ACCESS  read-write
   STATUS      current
   DESCRIPTION
      "Path: ethernet2.editConf.vlan.ipV6.addrAutoConfig.acceptRaDnssl

       Possibilities:
               disabled   (0)
               enabled   (1)"
   ::= {er1645v2Lan2FGUVlanEntry 704906240}

er1645v2Lan2FGUVlanIpV6DefaultRoute OBJECT-TYPE
   SYNTAX      INTEGER
               {
               disabled (0),
               enabled (1)
               }
   MAX-ACCESS  read-write
   STATUS      current
   DESCRIPTION
      "Path: ethernet2.editConf.vlan.ipV6.defaultRoute

       Possibilities:
               disabled   (0)
               enabled   (1)"
   ::= {er1645v2Lan2FGUVlanEntry 704970752}

er1645v2Lan2FGUVlanIpV6RaSend OBJECT-TYPE
   SYNTAX      INTEGER
               {
               disabled (0),
               enabled (1)
               }
   MAX-ACCESS  read-write
   STATUS      current
   DESCRIPTION
      "Path: ethernet2.editConf.vlan.ipV6.ra.send

       Possibilities:
               disabled   (0)
               enabled   (1)"
   ::= {er1645v2Lan2FGUVlanEntry 705036544}

er1645v2Lan2FGUVlanIpV6RaMinInterval OBJECT-TYPE
   SYNTAX      TimeTicks
   MAX-ACCESS  read-write
   STATUS      current
   DESCRIPTION
      "Path: ethernet2.editConf.vlan.ipV6.ra.minInterval

       Time in centi-second."
   ::= {er1645v2Lan2FGUVlanEntry 705036800}

er1645v2Lan2FGUVlanIpV6RaMaxInterval OBJECT-TYPE
   SYNTAX      TimeTicks
   MAX-ACCESS  read-write
   STATUS      current
   DESCRIPTION
      "Path: ethernet2.editConf.vlan.ipV6.ra.maxInterval

       Time in centi-second."
   ::= {er1645v2Lan2FGUVlanEntry 705037056}

er1645v2Lan2FGUVlanIpV6RaManagedFlag OBJECT-TYPE
   SYNTAX      INTEGER
               {
               disabled (0),
               enabled (1)
               }
   MAX-ACCESS  read-write
   STATUS      current
   DESCRIPTION
      "Path: ethernet2.editConf.vlan.ipV6.ra.managedFlag

       Possibilities:
               disabled   (0)
               enabled   (1)"
   ::= {er1645v2Lan2FGUVlanEntry 705037312}

er1645v2Lan2FGUVlanIpV6RaOtherConfFlag OBJECT-TYPE
   SYNTAX      INTEGER
               {
               disabled (0),
               enabled (1)
               }
   MAX-ACCESS  read-write
   STATUS      current
   DESCRIPTION
      "Path: ethernet2.editConf.vlan.ipV6.ra.otherConfFlag

       Possibilities:
               disabled   (0)
               enabled   (1)"
   ::= {er1645v2Lan2FGUVlanEntry 705037568}

er1645v2Lan2FGUVlanIpV6RaLinkMtu OBJECT-TYPE
   SYNTAX      Integer32
   MAX-ACCESS  read-write
   STATUS      current
   DESCRIPTION
      "Path: ethernet2.editConf.vlan.ipV6.ra.linkMtu"
   ::= {er1645v2Lan2FGUVlanEntry 705037824}

er1645v2Lan2FGUVlanIpV6RaReachableTime OBJECT-TYPE
   SYNTAX      TimeTicks
   MAX-ACCESS  read-write
   STATUS      current
   DESCRIPTION
      "Path: ethernet2.editConf.vlan.ipV6.ra.reachableTime

       Time in centi-second."
   ::= {er1645v2Lan2FGUVlanEntry 705038080}

er1645v2Lan2FGUVlanIpV6RaRetransmitTime OBJECT-TYPE
   SYNTAX      TimeTicks
   MAX-ACCESS  read-write
   STATUS      current
   DESCRIPTION
      "Path: ethernet2.editConf.vlan.ipV6.ra.retransmitTime

       Time in centi-second."
   ::= {er1645v2Lan2FGUVlanEntry 705038336}

er1645v2Lan2FGUVlanIpV6RaHopLimit OBJECT-TYPE
   SYNTAX      Integer32
   MAX-ACCESS  read-write
   STATUS      current
   DESCRIPTION
      "Path: ethernet2.editConf.vlan.ipV6.ra.hopLimit"
   ::= {er1645v2Lan2FGUVlanEntry 705038592}

er1645v2Lan2FGUVlanIpV6RaDefaultLifeTime OBJECT-TYPE
   SYNTAX      TimeTicks
   MAX-ACCESS  read-write
   STATUS      current
   DESCRIPTION
      "Path: ethernet2.editConf.vlan.ipV6.ra.defaultLifeTime

       Time in centi-second."
   ::= {er1645v2Lan2FGUVlanEntry 705038848}

er1645v2Lan2FGUVlanIpV6RaDnsOptionsRdnssLifeTime OBJECT-TYPE
   SYNTAX      TimeTicks
   MAX-ACCESS  read-write
   STATUS      current
   DESCRIPTION
      "Path: ethernet2.editConf.vlan.ipV6.ra.dnsOptions.rdnss.lifeTime

       Time in centi-second."
   ::= {er1645v2Lan2FGUVlanEntry 705039140}

er1645v2Lan2FGUVlanIpV6RaDnsOptionsRdnssImportServers OBJECT-TYPE
   SYNTAX      INTEGER
               {
               disabled (0),
               enabled (1)
               }
   MAX-ACCESS  read-write
   STATUS      current
   DESCRIPTION
      "Path: ethernet2.editConf.vlan.ipV6.ra.dnsOptions.rdnss.importServers

       Possibilities:
               disabled   (0)
               enabled   (1)"
   ::= {er1645v2Lan2FGUVlanEntry 705039148}

er1645v2Lan2FGUVlanIpV6RaDnsOptionsDnsslLifeTime OBJECT-TYPE
   SYNTAX      TimeTicks
   MAX-ACCESS  read-write
   STATUS      current
   DESCRIPTION
      "Path: ethernet2.editConf.vlan.ipV6.ra.dnsOptions.dnssl.lifeTime

       Time in centi-second."
   ::= {er1645v2Lan2FGUVlanEntry 705039172}

er1645v2Lan2FGUVlanIpV6RaDnsOptionsDnsslImportDomains OBJECT-TYPE
   SYNTAX      INTEGER
               {
               disabled (0),
               enabled (1)
               }
   MAX-ACCESS  read-write
   STATUS      current
   DESCRIPTION
      "Path: ethernet2.editConf.vlan.ipV6.ra.dnsOptions.dnssl.importDomains

       Possibilities:
               disabled   (0)
               enabled   (1)"
   ::= {er1645v2Lan2FGUVlanEntry 705039180}

er1645v2Lan2FGUVlanIpV6RsSend OBJECT-TYPE
   SYNTAX      INTEGER
               {
               disabled (0),
               enabled (1)
               }
   MAX-ACCESS  read-write
   STATUS      current
   DESCRIPTION
      "Path: ethernet2.editConf.vlan.ipV6.rs.send

       Possibilities:
               disabled   (0)
               enabled   (1)"
   ::= {er1645v2Lan2FGUVlanEntry 705954048}

er1645v2Lan2FGUVlanIpV6RsMaxRandomDelay OBJECT-TYPE
   SYNTAX      TimeTicks
   MAX-ACCESS  read-write
   STATUS      current
   DESCRIPTION
      "Path: ethernet2.editConf.vlan.ipV6.rs.maxRandomDelay

       Time in centi-second."
   ::= {er1645v2Lan2FGUVlanEntry 705954304}

er1645v2Lan2FGUVlanIpV6RsInterval OBJECT-TYPE
   SYNTAX      TimeTicks
   MAX-ACCESS  read-write
   STATUS      current
   DESCRIPTION
      "Path: ethernet2.editConf.vlan.ipV6.rs.interval

       Time in centi-second."
   ::= {er1645v2Lan2FGUVlanEntry 705954560}

er1645v2Lan2FGUVlanIpV6RsMaxSolicitations OBJECT-TYPE
   SYNTAX      Integer32
   MAX-ACCESS  read-write
   STATUS      current
   DESCRIPTION
      "Path: ethernet2.editConf.vlan.ipV6.rs.maxSolicitations"
   ::= {er1645v2Lan2FGUVlanEntry 705954816}

er1645v2Lan2FGUVlanIpV6TrafficPolicyInbound OBJECT-TYPE
   SYNTAX      DisplayString
   MAX-ACCESS  read-write
   STATUS      current
   DESCRIPTION
      "Path: ethernet2.editConf.vlan.ipV6.trafficPolicy.inbound"
   ::= {er1645v2Lan2FGUVlanEntry 705364224}

er1645v2Lan2FGUVlanIpV6TrafficPolicyOutbound OBJECT-TYPE
   SYNTAX      DisplayString
   MAX-ACCESS  read-write
   STATUS      current
   DESCRIPTION
      "Path: ethernet2.editConf.vlan.ipV6.trafficPolicy.outbound"
   ::= {er1645v2Lan2FGUVlanEntry 705364480}

er1645v2Lan2FGUVlanIpV6FirewallZone OBJECT-TYPE
   SYNTAX      DisplayString
   MAX-ACCESS  read-write
   STATUS      current
   DESCRIPTION
      "Path: ethernet2.editConf.vlan.ipV6.firewall.zone"
   ::= {er1645v2Lan2FGUVlanEntry 705429760}

er1645v2Lan2FGUVlanIpV6DhcpClientAddrAC OBJECT-TYPE
   SYNTAX      INTEGER
               {
               disabled (0),
               enabled (1)
               }
   MAX-ACCESS  read-write
   STATUS      current
   DESCRIPTION
      "Path: ethernet2.editConf.vlan.ipV6.dhcp.client.addrAutoConfig

       Possibilities:
               disabled   (0)
               enabled   (1)"
   ::= {er1645v2Lan2FGUVlanEntry 705307648}

er1645v2Lan2FGUVlanIpV6DhcpClientPrDelMode OBJECT-TYPE
   SYNTAX      INTEGER
               {
               disabled (0),
               enabled (1)
               }
   MAX-ACCESS  read-write
   STATUS      current
   DESCRIPTION
      "Path: ethernet2.editConf.vlan.ipV6.dhcp.client.pd.mode

       Possibilities:
               disabled   (0)
               enabled   (1)"
   ::= {er1645v2Lan2FGUVlanEntry 705308676}

er1645v2Lan2FGUVlanIpV6DhcpClientPrDelPool OBJECT-TYPE
   SYNTAX      DisplayString
   MAX-ACCESS  read-write
   STATUS      current
   DESCRIPTION
      "Path: ethernet2.editConf.vlan.ipV6.dhcp.client.pd.pool"
   ::= {er1645v2Lan2FGUVlanEntry 705308680}

er1645v2Lan2FGUVlanIpV6DhcpClientPrDelPdExclOpt OBJECT-TYPE
   SYNTAX      INTEGER
               {
               disabled (0),
               enabled (1)
               }
   MAX-ACCESS  read-write
   STATUS      current
   DESCRIPTION
      "Path: ethernet2.editConf.vlan.ipV6.dhcp.client.pd.pdExclOpt

       Possibilities:
               disabled   (0)
               enabled   (1)"
   ::= {er1645v2Lan2FGUVlanEntry 705308684}

er1645v2Lan2FGUVlanIpV6DhcpClientDnsServerPref OBJECT-TYPE
   SYNTAX      Integer32
   MAX-ACCESS  read-write
   STATUS      current
   DESCRIPTION
      "Path: ethernet2.editConf.vlan.ipV6.dhcp.client.dns.serverPref"
   ::= {er1645v2Lan2FGUVlanEntry 705310724}

er1645v2Lan2FGUVlanIpV6DhcpClientRapidCommit OBJECT-TYPE
   SYNTAX      INTEGER
               {
               disabled (0),
               enabled (1)
               }
   MAX-ACCESS  read-write
   STATUS      current
   DESCRIPTION
      "Path: ethernet2.editConf.vlan.ipV6.dhcp.client.rapidCommit

       Possibilities:
               disabled   (0)
               enabled   (1)"
   ::= {er1645v2Lan2FGUVlanEntry 705309696}

er1645v2Lan2FGUVlanIpV6DhcpClientTimersSolTimeOut OBJECT-TYPE
   SYNTAX      TimeTicks
   MAX-ACCESS  read-write
   STATUS      current
   DESCRIPTION
      "Path: ethernet2.editConf.vlan.ipV6.dhcp.client.timers.solTimeOut

       Time in centi-second."
   ::= {er1645v2Lan2FGUVlanEntry 705311748}

er1645v2Lan2FGUVlanIpV6DhcpClientTimersSolMaxRt OBJECT-TYPE
   SYNTAX      TimeTicks
   MAX-ACCESS  read-write
   STATUS      current
   DESCRIPTION
      "Path: ethernet2.editConf.vlan.ipV6.dhcp.client.timers.solMaxRt

       Time in centi-second."
   ::= {er1645v2Lan2FGUVlanEntry 705311752}

er1645v2Lan2FGUVlanIpV6DhcpClientTimersInfoRefresh OBJECT-TYPE
   SYNTAX      TimeTicks
   MAX-ACCESS  read-write
   STATUS      current
   DESCRIPTION
      "Path: ethernet2.editConf.vlan.ipV6.dhcp.client.timers.infoRefresh

       Time in centi-second."
   ::= {er1645v2Lan2FGUVlanEntry 705311756}

er1645v2Lan2FGUVlanIpV6DhcpServerMode OBJECT-TYPE
   SYNTAX      INTEGER
               {
               disabled (0),
               enabled (1)
               }
   MAX-ACCESS  read-write
   STATUS      current
   DESCRIPTION
      "Path: ethernet2.editConf.vlan.ipV6.dhcp.server.mode

       Possibilities:
               disabled   (0)
               enabled   (1)"
   ::= {er1645v2Lan2FGUVlanEntry 705315840}

er1645v2Lan2FGUVlanIpV6DhcpServerPreference OBJECT-TYPE
   SYNTAX      Integer32
   MAX-ACCESS  read-write
   STATUS      current
   DESCRIPTION
      "Path: ethernet2.editConf.vlan.ipV6.dhcp.server.preference"
   ::= {er1645v2Lan2FGUVlanEntry 705316864}

er1645v2Lan2FGUVlanIpV6DhcpServerPool OBJECT-TYPE
   SYNTAX      DisplayString
   MAX-ACCESS  read-write
   STATUS      current
   DESCRIPTION
      "Path: ethernet2.editConf.vlan.ipV6.dhcp.server.pool"
   ::= {er1645v2Lan2FGUVlanEntry 705317888}

er1645v2Lan2FGUVlanIpV6DhcpServerRapidCommit OBJECT-TYPE
   SYNTAX      INTEGER
               {
               disabled (0),
               enabled (1)
               }
   MAX-ACCESS  read-write
   STATUS      current
   DESCRIPTION
      "Path: ethernet2.editConf.vlan.ipV6.dhcp.server.rapidCommit

       Possibilities:
               disabled   (0)
               enabled   (1)"
   ::= {er1645v2Lan2FGUVlanEntry 705318912}

er1645v2Lan2FGUVlanIpV6DhcpServerTimersInfoRefresh OBJECT-TYPE
   SYNTAX      TimeTicks
   MAX-ACCESS  read-write
   STATUS      current
   DESCRIPTION
      "Path: ethernet2.editConf.vlan.ipV6.dhcp.server.timers.infoRefresh

       Time in centi-second."
   ::= {er1645v2Lan2FGUVlanEntry 705319940}

er1645v2Lan2FGUVlanIpV6DhcpRelayMode OBJECT-TYPE
   SYNTAX      INTEGER
               {
               disabled (0),
               enabled (1)
               }
   MAX-ACCESS  read-write
   STATUS      current
   DESCRIPTION
      "Path: ethernet2.editConf.vlan.ipV6.dhcp.relay.mode

       Possibilities:
               disabled   (0)
               enabled   (1)"
   ::= {er1645v2Lan2FGUVlanEntry 705323040}

er1645v2Lan2FGUVlanIpV6SendRedirect OBJECT-TYPE
   SYNTAX      INTEGER
               {
               disabled (0),
               enabled (1)
               }
   MAX-ACCESS  read-write
   STATUS      current
   DESCRIPTION
      "Path: ethernet2.editConf.vlan.ipV6.sendRedirect

       Possibilities:
               disabled   (0)
               enabled   (1)"
   ::= {er1645v2Lan2FGUVlanEntry 705101824}

er1645v2Lan2FGUVlanIpV6LinkMtu OBJECT-TYPE
   SYNTAX      Integer32
   MAX-ACCESS  read-write
   STATUS      current
   DESCRIPTION
      "Path: ethernet2.editConf.vlan.ipV6.linkMtu"
   ::= {er1645v2Lan2FGUVlanEntry 705167360}

er1645v2Lan2FGUVlanIpV6InterfaceId OBJECT-TYPE
   SYNTAX      OCTET STRING
   MAX-ACCESS  read-write
   STATUS      current
   DESCRIPTION
      "Path: ethernet2.editConf.vlan.ipV6.interfaceId"
   ::= {er1645v2Lan2FGUVlanEntry 705232896}

er1645v2Lan2FGUVlanIpV6MF OBJECT-TYPE
   SYNTAX      Integer32
   MAX-ACCESS  read-write
   STATUS      current
   DESCRIPTION
      "Path: ethernet2.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGUVlanEntry 705757184}

er1645v2Lan2FGUVlanIpV6IcmpMessagesNoRoute OBJECT-TYPE
   SYNTAX      INTEGER
               {
               disabled (0),
               enabled (1)
               }
   MAX-ACCESS  read-write
   STATUS      current
   DESCRIPTION
      "Path: ethernet2.editConf.vlan.ipV6.icmpMessages.noRoute

       Possibilities:
               disabled   (0)
               enabled   (1)"
   ::= {er1645v2Lan2FGUVlanEntry 705822976}

er1645v2Lan2FGUVlanIpV6IcmpMessagesBeyondScope OBJECT-TYPE
   SYNTAX      INTEGER
               {
               disabled (0),
               enabled (1)
               }
   MAX-ACCESS  read-write
   STATUS      current
   DESCRIPTION
      "Path: ethernet2.editConf.vlan.ipV6.icmpMessages.beyondScope

       Possibilities:
               disabled   (0)
               enabled   (1)"
   ::= {er1645v2Lan2FGUVlanEntry 705823488}

er1645v2Lan2FGUVlanIpV6IcmpMessagesAddressUnreachable OBJECT-TYPE
   SYNTAX      INTEGER
               {
               disabled (0),
               enabled (1)
               }
   MAX-ACCESS  read-write
   STATUS      current
   DESCRIPTION
      "Path: ethernet2.editConf.vlan.ipV6.icmpMessages.addressUnreachable

       Possibilities:
               disabled   (0)
               enabled   (1)"
   ::= {er1645v2Lan2FGUVlanEntry 705823744}

er1645v2Lan2FGUVlanIpV6IcmpMessagesPortUnreachable OBJECT-TYPE
   SYNTAX      INTEGER
               {
               disabled (0),
               enabled (1)
               }
   MAX-ACCESS  read-write
   STATUS      current
   DESCRIPTION
      "Path: ethernet2.editConf.vlan.ipV6.icmpMessages.portUnreachable

       Possibilities:
               disabled   (0)
               enabled   (1)"
   ::= {er1645v2Lan2FGUVlanEntry 705824000}

er1645v2Lan2FGUVlanIpV6IcmpMessagesPacketTooBig OBJECT-TYPE
   SYNTAX      INTEGER
               {
               disabled (0),
               enabled (1)
               }
   MAX-ACCESS  read-write
   STATUS      current
   DESCRIPTION
      "Path: ethernet2.editConf.vlan.ipV6.icmpMessages.packetTooBig

       Possibilities:
               disabled   (0)
               enabled   (1)"
   ::= {er1645v2Lan2FGUVlanEntry 705825280}

er1645v2Lan2FGUVlanIpV6IcmpMessagesHopLimitExceeded OBJECT-TYPE
   SYNTAX      INTEGER
               {
               disabled (0),
               enabled (1)
               }
   MAX-ACCESS  read-write
   STATUS      current
   DESCRIPTION
      "Path: ethernet2.editConf.vlan.ipV6.icmpMessages.hopLimitExceeded

       Possibilities:
               disabled   (0)
               enabled   (1)"
   ::= {er1645v2Lan2FGUVlanEntry 705827840}

er1645v2Lan2FGUVlanIpV6IcmpMessagesFragTimeExceeded OBJECT-TYPE
   SYNTAX      INTEGER
               {
               disabled (0),
               enabled (1)
               }
   MAX-ACCESS  read-write
   STATUS      current
   DESCRIPTION
      "Path: ethernet2.editConf.vlan.ipV6.icmpMessages.fragTimeExceeded

       Possibilities:
               disabled   (0)
               enabled   (1)"
   ::= {er1645v2Lan2FGUVlanEntry 705828096}

er1645v2Lan2FGUVlanIpV6IcmpMessagesHeaderFieldErr OBJECT-TYPE
   SYNTAX      INTEGER
               {
               disabled (0),
               enabled (1)
               }
   MAX-ACCESS  read-write
   STATUS      current
   DESCRIPTION
      "Path: ethernet2.editConf.vlan.ipV6.icmpMessages.headerFieldErr

       Possibilities:
               disabled   (0)
               enabled   (1)"
   ::= {er1645v2Lan2FGUVlanEntry 705830400}

er1645v2Lan2FGUVlanIpV6IcmpMessagesOptionUnrecognized OBJECT-TYPE
   SYNTAX      INTEGER
               {
               disabled (0),
               enabled (1)
               }
   MAX-ACCESS  read-write
   STATUS      current
   DESCRIPTION
      "Path: ethernet2.editConf.vlan.ipV6.icmpMessages.optionUnrecognized

       Possibilities:
               disabled   (0)
               enabled   (1)"
   ::= {er1645v2Lan2FGUVlanEntry 705830912}

er1645v2Lan2FGUVlanIpV6IcmpMessagesRedirect OBJECT-TYPE
   SYNTAX      INTEGER
               {
               disabled (0),
               enabled (1)
               }
   MAX-ACCESS  read-write
   STATUS      current
   DESCRIPTION
      "Path: ethernet2.editConf.vlan.ipV6.icmpMessages.redirect

       Possibilities:
               disabled   (0)
               enabled   (1)"
   ::= {er1645v2Lan2FGUVlanEntry 705832960}

er1645v2Lan2FGUVlanBridgingAccList OBJECT-TYPE
   SYNTAX      DisplayString
   MAX-ACCESS  read-write
   STATUS      current
   DESCRIPTION
      "Path: ethernet2.editConf.vlan.bridging.accessList"
   ::= {er1645v2Lan2FGUVlanEntry 453246976}

er1645v2Lan2FGUVlanBridgingInACL OBJECT-TYPE
   SYNTAX      DisplayString
   MAX-ACCESS  read-write
   STATUS      current
   DESCRIPTION
      "Path: ethernet2.editConf.vlan.bridging.inAccessList"
   ::= {er1645v2Lan2FGUVlanEntry 456916992}

er1645v2Lan2FGUVlanBridgingTp OBJECT-TYPE
   SYNTAX      DisplayString
   MAX-ACCESS  read-write
   STATUS      current
   DESCRIPTION
      "Path: ethernet2.editConf.vlan.bridging.trafficPolicy"
   ::= {er1645v2Lan2FGUVlanEntry 454295552}

er1645v2Lan2FGUVlanBridgingBrGrp OBJECT-TYPE
   SYNTAX      DisplayString
   MAX-ACCESS  read-write
   STATUS      current
   DESCRIPTION
      "Path: ethernet2.editConf.vlan.bridging.bridgeGroup"
   ::= {er1645v2Lan2FGUVlanEntry 454819840}

er1645v2Lan2FGUVlanBridgingLimBC OBJECT-TYPE
   SYNTAX      INTEGER
               {
               disabled (0),
               enabled (1)
               }
   MAX-ACCESS  read-write
   STATUS      current
   DESCRIPTION
      "Path: ethernet2.editConf.vlan.bridging.limitBroadcasts

       Possibilities:
               disabled   (0)
               enabled   (1)"
   ::= {er1645v2Lan2FGUVlanEntry 455081984}

er1645v2Lan2FGUVlanBridgingPrivateMode OBJECT-TYPE
   SYNTAX      INTEGER
               {
               disabled (0),
               enabled (1)
               }
   MAX-ACCESS  read-write
   STATUS      current
   DESCRIPTION
      "Path: ethernet2.editConf.vlan.bridging.privateMode

       Possibilities:
               disabled   (0)
               enabled   (1)"
   ::= {er1645v2Lan2FGUVlanEntry 459538432}

er1645v2Lan2FGUVlanBridgingLearning OBJECT-TYPE
   SYNTAX      INTEGER
               {
               disabled (0),
               enabled (1)
               }
   MAX-ACCESS  read-write
   STATUS      current
   DESCRIPTION
      "Path: ethernet2.editConf.vlan.bridging.learning

       Possibilities:
               disabled   (0)
               enabled   (1)"
   ::= {er1645v2Lan2FGUVlanEntry 456130560}

er1645v2Lan2FGUVlanBridgingMaxCacheSize OBJECT-TYPE
   SYNTAX      INTEGER
               {
               unlimited (0)
               }
   MAX-ACCESS  read-write
   STATUS      current
   DESCRIPTION
      "Path: ethernet2.editConf.vlan.bridging.maxCacheSize

       Possibilities:
               unlimited   (0)"
   ::= {er1645v2Lan2FGUVlanEntry 456392704}

er1645v2Lan2FGUVlanBridgingRelearnDropOnRelearn OBJECT-TYPE
   SYNTAX      INTEGER
               {
               disabled (0),
               enabled (1)
               }
   MAX-ACCESS  read-write
   STATUS      current
   DESCRIPTION
      "Path: ethernet2.editConf.vlan.bridging.relearn.dropOnRelearn

       Possibilities:
               disabled   (0)
               enabled   (1)"
   ::= {er1645v2Lan2FGUVlanEntry 456655872}

er1645v2Lan2FGUVlanBridgingRelearnShutdownThreshold OBJECT-TYPE
   SYNTAX      Integer32
   MAX-ACCESS  read-write
   STATUS      current
   DESCRIPTION
      "Path: ethernet2.editConf.vlan.bridging.relearn.shutdownThreshold"
   ::= {er1645v2Lan2FGUVlanEntry 456656896}

er1645v2Lan2FGUVlanBridgingRelearnShutdownTime OBJECT-TYPE
   SYNTAX      TimeTicks
   MAX-ACCESS  read-write
   STATUS      current
   DESCRIPTION
      "Path: ethernet2.editConf.vlan.bridging.relearn.shutdownTime

       Time in centi-second."
   ::= {er1645v2Lan2FGUVlanEntry 456657920}

er1645v2Lan2FGUVlanBridgingRelearnLoopDetection OBJECT-TYPE
   SYNTAX      INTEGER
               {
               disabled (0),
               passive (1),
               active (2)
               }
   MAX-ACCESS  read-write
   STATUS      current
   DESCRIPTION
      "Path: ethernet2.editConf.vlan.bridging.relearn.loopDetection

       Possibilities:
               disabled   (0)
               passive   (1)
               active   (2)"
   ::= {er1645v2Lan2FGUVlanEntry 456658944}

er1645v2Lan2FGUVlanBridgingRelearnLoopDetectionInterval OBJECT-TYPE
   SYNTAX      TimeTicks
   MAX-ACCESS  read-write
   STATUS      current
   DESCRIPTION
      "Path: ethernet2.editConf.vlan.bridging.relearn.loopDetectionInterval

       Time in centi-second."
   ::= {er1645v2Lan2FGUVlanEntry 456659968}

er1645v2Lan2FGUVlanBridgingVlanMemberShip OBJECT-TYPE
   SYNTAX      INTEGER
               {
               all (0),
               none (1),
               grouped (2)
               }
   MAX-ACCESS  read-write
   STATUS      current
   DESCRIPTION
      "Path: ethernet2.editConf.vlan.bridging.vlanMemberShip

       Possibilities:
               all   (0)
               none   (1)
               grouped   (2)"
   ::= {er1645v2Lan2FGUVlanEntry 457965568}

er1645v2Lan2FGUVlanBridgingVlTUntaggedAction OBJECT-TYPE
   SYNTAX      INTEGER
               {
               discard (0),
               accept (1),
               tag (2)
               }
   MAX-ACCESS  read-write
   STATUS      current
   DESCRIPTION
      "Path: ethernet2.editConf.vlan.bridging.vlanTagging.untagged.action

       Possibilities:
               discard   (0)
               accept   (1)
               tag   (2)"
   ::= {er1645v2Lan2FGUVlanEntry 459055104}

er1645v2Lan2FGUVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.untagged.tagInfo.tpid

       Possibilities:
               dot1Q   (33024)
               dot1ad   (34984)
               0x9100   (37120)
               0x9200   (37376)
               0x9300   (37632)"
   ::= {er1645v2Lan2FGUVlanEntry 459059712}

er1645v2Lan2FGUVlanBridgingVlTUntaggedTagInfoVid OBJECT-TYPE
   SYNTAX      Integer32
   MAX-ACCESS  read-write
   STATUS      current
   DESCRIPTION
      "Path: ethernet2.editConf.vlan.bridging.vlanTagging.untagged.tagInfo.vid"
   ::= {er1645v2Lan2FGUVlanEntry 459060224}

er1645v2Lan2FGUVlanBridgingVlTUnknownVlansAction OBJECT-TYPE
   SYNTAX      INTEGER
               {
               discard (0),
               accept (1),
               tag (2)
               }
   MAX-ACCESS  read-write
   STATUS      current
   DESCRIPTION
      "Path: ethernet2.editConf.vlan.bridging.vlanTagging.unknownVlans.action

       Possibilities:
               discard   (0)
               accept   (1)
               tag   (2)"
   ::= {er1645v2Lan2FGUVlanEntry 459120640}

er1645v2Lan2FGUVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.unknownVlans.tagInfo.tpid

       Possibilities:
               dot1Q   (33024)
               dot1ad   (34984)
               0x9100   (37120)
               0x9200   (37376)
               0x9300   (37632)"
   ::= {er1645v2Lan2FGUVlanEntry 459125248}

er1645v2Lan2FGUVlanBridgingVlTUnknownVlansTagInfoVid OBJECT-TYPE
   SYNTAX      Integer32
   MAX-ACCESS  read-write
   STATUS      current
   DESCRIPTION
      "Path: ethernet2.editConf.vlan.bridging.vlanTagging.unknownVlans.tagInfo.vid"
   ::= {er1645v2Lan2FGUVlanEntry 459125760}

er1645v2Lan2FGUVlanBridgingDot1adType OBJECT-TYPE
   SYNTAX      INTEGER
               {
               slOPTg (0),
               cPort (4),
               sPort (1),
               nni (2)
               }
   MAX-ACCESS  read-write
   STATUS      current
   DESCRIPTION
      "Path: ethernet2.editConf.vlan.bridging.dot1ad.type

       Possibilities:
               <OPT>   (0)
               cPort   (4)
               sPort   (1)
               nni   (2)"
   ::= {er1645v2Lan2FGUVlanEntry 460850176}

er1645v2Lan2FGUVlanBridgingPriority OBJECT-TYPE
   SYNTAX      Integer32
   MAX-ACCESS  read-write
   STATUS      current
   DESCRIPTION
      "Path: ethernet2.editConf.vlan.bridging.priority"
   ::= {er1645v2Lan2FGUVlanEntry 453509120}

er1645v2Lan2FGUVlanBridgingPathCost OBJECT-TYPE
   SYNTAX      Integer32
   MAX-ACCESS  read-write
   STATUS      current
   DESCRIPTION
      "Path: ethernet2.editConf.vlan.bridging.pathCost"
   ::= {er1645v2Lan2FGUVlanEntry 453771264}

er1645v2Lan2FGUVlanBridgingInternalPathCost OBJECT-TYPE
   SYNTAX      Integer32
   MAX-ACCESS  read-write
   STATUS      current
   DESCRIPTION
      "Path: ethernet2.editConf.vlan.bridging.internalPathCost"
   ::= {er1645v2Lan2FGUVlanEntry 457703424}

er1645v2Lan2FGUVlanBridgingTCD OBJECT-TYPE
   SYNTAX      INTEGER
               {
               disabled (0),
               enabled (1)
               }
   MAX-ACCESS  read-write
   STATUS      current
   DESCRIPTION
      "Path: ethernet2.editConf.vlan.bridging.topologyChangeDetection

       Possibilities:
               disabled   (0)
               enabled   (1)"
   ::= {er1645v2Lan2FGUVlanEntry 454033408}

er1645v2Lan2FGUVlanBridgingRestrictedRole OBJECT-TYPE
   SYNTAX      INTEGER
               {
               disabled (0),
               enabled (1)
               }
   MAX-ACCESS  read-write
   STATUS      current
   DESCRIPTION
      "Path: ethernet2.editConf.vlan.bridging.restrictedRole

       Possibilities:
               disabled   (0)
               enabled   (1)"
   ::= {er1645v2Lan2FGUVlanEntry 458227712}

er1645v2Lan2FGUVlanBridgingAdminEdge OBJECT-TYPE
   SYNTAX      INTEGER
               {
               disabled (0),
               enabled (1)
               }
   MAX-ACCESS  read-write
   STATUS      current
   DESCRIPTION
      "Path: ethernet2.editConf.vlan.bridging.adminEdge

       Possibilities:
               disabled   (0)
               enabled   (1)"
   ::= {er1645v2Lan2FGUVlanEntry 457179136}

er1645v2Lan2FGUVlanBridgingOamMacDeviceMac OBJECT-TYPE
   SYNTAX      DisplayString
   MAX-ACCESS  read-write
   STATUS      current
   DESCRIPTION
      "Path: ethernet2.editConf.vlan.bridging.ethOam.macAddress.deviceMac"
   ::= {er1645v2Lan2FGUVlanEntry 458506496}

er1645v2Lan2FGUVlanBridgingOamMacUserMac OBJECT-TYPE
   SYNTAX      OCTET STRING
   MAX-ACCESS  read-write
   STATUS      current
   DESCRIPTION
      "Path: ethernet2.editConf.vlan.bridging.ethOam.macAddress.userMac

       MAC address."
   ::= {er1645v2Lan2FGUVlanEntry 458506368}

er1645v2Lan2FGUVlanBridgingOamMacBridgeMac OBJECT-TYPE
   SYNTAX      DisplayString
   MAX-ACCESS  read-write
   STATUS      current
   DESCRIPTION
      "Path: ethernet2.editConf.vlan.bridging.ethOam.macAddress.bridgeMac"
   ::= {er1645v2Lan2FGUVlanEntry 458506432}

er1645v2Lan2FGUVlanBridgingMgmtInline OBJECT-TYPE
   SYNTAX      INTEGER
               {
               disabled (0),
               enabled (1)
               }
   MAX-ACCESS  read-write
   STATUS      current
   DESCRIPTION
      "Path: ethernet2.editConf.vlan.bridging.mgmtInline

       Possibilities:
               disabled   (0)
               enabled   (1)"
   ::= {er1645v2Lan2FGUVlanEntry 458752000}

er1645v2Lan2FGUVlanBridgingL2ptMode OBJECT-TYPE
   SYNTAX      INTEGER
               {
               disabled (0),
               enabled (1)
               }
   MAX-ACCESS  read-write
   STATUS      current
   DESCRIPTION
      "Path: ethernet2.editConf.vlan.bridging.l2ProtTunnel.mode

       Possibilities:
               disabled   (0)
               enabled   (1)"
   ::= {er1645v2Lan2FGUVlanEntry 459292672}

er1645v2Lan2FGUVlanBridgingL2ptProtocols OBJECT-TYPE
   SYNTAX      Integer32
   MAX-ACCESS  read-write
   STATUS      current
   DESCRIPTION
      "Path: ethernet2.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2FGUVlanEntry 459309056}

er1645v2Lan2FGUVlanBridgingL2ptDestMac OBJECT-TYPE
   SYNTAX      OCTET STRING
   MAX-ACCESS  read-write
   STATUS      current
   DESCRIPTION
      "Path: ethernet2.editConf.vlan.bridging.l2ProtTunnel.destinationMac

       MAC address."
   ::= {er1645v2Lan2FGUVlanEntry 459325440}

er1645v2Lan2FGUVlanBridgingL2ptCos OBJECT-TYPE
   SYNTAX      INTEGER
               {
               unchanged (255)
               }
   MAX-ACCESS  read-write
   STATUS      current
   DESCRIPTION
      "Path: ethernet2.editConf.vlan.bridging.l2ProtTunnel.cos

       Possibilities:
               unchanged   (255)"
   ::= {er1645v2Lan2FGUVlanEntry 459341824}

er1645v2Lan2FGUVlanBridgingL2ptDropThrStp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.stp

       unit name = packets/sec

       Possibilities:
               unlimited   (0)"
   ::= {er1645v2Lan2FGUVlanEntry 459358272}

er1645v2Lan2FGUVlanBridgingL2ptDropThrLldp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lldp

       unit name = packets/sec

       Possibilities:
               unlimited   (0)"
   ::= {er1645v2Lan2FGUVlanEntry 459358336}

er1645v2Lan2FGUVlanBridgingL2ptDropThrOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.oam

       unit name = packets/sec

       Possibilities:
               unlimited   (0)"
   ::= {er1645v2Lan2FGUVlanEntry 459358400}

er1645v2Lan2FGUVlanBridgingL2ptDropThrCdp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.cdp

       unit name = packets/sec

       Possibilities:
               unlimited   (0)"
   ::= {er1645v2Lan2FGUVlanEntry 459358464}

er1645v2Lan2FGUVlanBridgingL2ptDropThrVtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.vtp

       unit name = packets/sec

       Possibilities:
               unlimited   (0)"
   ::= {er1645v2Lan2FGUVlanEntry 459358528}

er1645v2Lan2FGUVlanBridgingL2ptDropThrLacp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lacp

       unit name = packets/sec

       Possibilities:
               unlimited   (0)"
   ::= {er1645v2Lan2FGUVlanEntry 459358592}

er1645v2Lan2FGUVlanBridgingL2ptDropThrEfmOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.efmOam

       unit name = packets/sec

       Possibilities:
               unlimited   (0)"
   ::= {er1645v2Lan2FGUVlanEntry 459358656}

er1645v2Lan2FGUVlanBridgingL2ptDropThrPvst OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pvst

       unit name = packets/sec

       Possibilities:
               unlimited   (0)"
   ::= {er1645v2Lan2FGUVlanEntry 459358720}

er1645v2Lan2FGUVlanBridgingL2ptDropThrMmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mmrp

       unit name = packets/sec

       Possibilities:
               unlimited   (0)"
   ::= {er1645v2Lan2FGUVlanEntry 459358784}

er1645v2Lan2FGUVlanBridgingL2ptDropThrMvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mvrp

       unit name = packets/sec

       Possibilities:
               unlimited   (0)"
   ::= {er1645v2Lan2FGUVlanEntry 459358848}

er1645v2Lan2FGUVlanBridgingL2ptDropThrGvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gvrp

       unit name = packets/sec

       Possibilities:
               unlimited   (0)"
   ::= {er1645v2Lan2FGUVlanEntry 459358912}

er1645v2Lan2FGUVlanBridgingL2ptDropThrGmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gmrp

       unit name = packets/sec

       Possibilities:
               unlimited   (0)"
   ::= {er1645v2Lan2FGUVlanEntry 459358976}

er1645v2Lan2FGUVlanBridgingL2ptDropThrDtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.dtp

       unit name = packets/sec

       Possibilities:
               unlimited   (0)"
   ::= {er1645v2Lan2FGUVlanEntry 459359040}

er1645v2Lan2FGUVlanBridgingL2ptDropThrPagp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pagp

       unit name = packets/sec

       Possibilities:
               unlimited   (0)"
   ::= {er1645v2Lan2FGUVlanEntry 459359104}

er1645v2Lan2FGUVlanBridgingL2ptDropThrUdld OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.udld

       unit name = packets/sec

       Possibilities:
               unlimited   (0)"
   ::= {er1645v2Lan2FGUVlanEntry 459359168}

er1645v2Lan2FGUVlanVlanVid OBJECT-TYPE
   SYNTAX      INTEGER
               {
               untagged (0),
               prioTagged (4096),
               notUsed (4097)
               }
   MAX-ACCESS  read-write
   STATUS      current
   DESCRIPTION
      "Path: ethernet2.editConf.vlan.vlan.vid

       Possibilities:
               untagged   (0)
               prioTagged   (4096)
               notUsed   (4097)"
   ::= {er1645v2Lan2FGUVlanEntry 234946560}

er1645v2Lan2FGUVlanVlanVidExtensionSingle OBJECT-TYPE
   SYNTAX      OCTET STRING
   MAX-ACCESS  read-write
   STATUS      current
   DESCRIPTION
      "Path: ethernet2.editConf.vlan.vlan.vidExtension.single"
   ::= {er1645v2Lan2FGUVlanEntry 235340032}

er1645v2Lan2FGUVlanVlanVidExtensionEndVid OBJECT-TYPE
   SYNTAX      Integer32
   MAX-ACCESS  read-write
   STATUS      current
   DESCRIPTION
      "Path: ethernet2.editConf.vlan.vlan.vidExtension.endVid"
   ::= {er1645v2Lan2FGUVlanEntry 235340288}

er1645v2Lan2FGUVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tpid

       Possibilities:
               dot1Q   (33024)
               dot1ad   (34984)
               0x9100   (37120)
               0x9200   (37376)
               0x9300   (37632)"
   ::= {er1645v2Lan2FGUVlanEntry 241238016}

er1645v2Lan2FGUVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet2.editConf.vlan.vlan.tagSignificance

       Possibilities:
               global   (0)
               local   (1)
               sVlan   (2)
               sVlanGlobal   (6)
               cVlan   (3)
               scVlan   (5)
               cVlanLocal   (4)"
   ::= {er1645v2Lan2FGUVlanEntry 235012096}

er1645v2Lan2FGUVlanVlanChTos OBJECT-TYPE
   SYNTAX      INTEGER
               {
               disabled (0),
               enabled (1)
               }
   MAX-ACCESS  read-write
   STATUS      current
   DESCRIPTION
      "Path: ethernet2.editConf.vlan.vlan.changeTos

       Possibilities:
               disabled   (0)
               enabled   (1)"
   ::= {er1645v2Lan2FGUVlanEntry 235208704}

er1645v2Lan2FGUVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235143424}

er1645v2Lan2FGUVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235143680}

er1645v2Lan2FGUVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235143936}

er1645v2Lan2FGUVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235144192}

er1645v2Lan2FGUVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235144448}

er1645v2Lan2FGUVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235144704}

er1645v2Lan2FGUVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235144960}

er1645v2Lan2FGUVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGUVlanEntry 235145216}

er1645v2Lan2FGUVlanVlanTxCos OBJECT-TYPE
   SYNTAX      INTEGER
               {
               tosCosMap (8),
               queueCosMap (16)
               }
   MAX-ACCESS  read-write
   STATUS      current
   DESCRIPTION
      "Path: ethernet2.editConf.vlan.vlan.txCos

       Possibilities:
               tosCosMap   (8)
               queueCosMap   (16)"
   ::= {er1645v2Lan2FGUVlanEntry 235077632}

er1645v2Lan2FGUVlanVlanCCMapP0 OBJECT-TYPE
   SYNTAX      Integer32
   MAX-ACCESS  read-write
   STATUS      current
   DESCRIPTION
      "Path: ethernet2.editConf.vlan.vlan.cosCosMap.p0"
   ::= {er1645v2Lan2FGUVlanEntry 241303808}

er1645v2Lan2FGUVlanVlanCCMapP1 OBJECT-TYPE
   SYNTAX      Integer32
   MAX-ACCESS  read-write
   STATUS      current
   DESCRIPTION
      "Path: ethernet2.editConf.vlan.vlan.cosCosMap.p1"
   ::= {er1645v2Lan2FGUVlanEntry 241304064}

er1645v2Lan2FGUVlanVlanCCMapP2 OBJECT-TYPE
   SYNTAX      Integer32
   MAX-ACCESS  read-write
   STATUS      current
   DESCRIPTION
      "Path: ethernet2.editConf.vlan.vlan.cosCosMap.p2"
   ::= {er1645v2Lan2FGUVlanEntry 241304320}

er1645v2Lan2FGUVlanVlanCCMapP3 OBJECT-TYPE
   SYNTAX      Integer32
   MAX-ACCESS  read-write
   STATUS      current
   DESCRIPTION
      "Path: ethernet2.editConf.vlan.vlan.cosCosMap.p3"
   ::= {er1645v2Lan2FGUVlanEntry 241304576}

er1645v2Lan2FGUVlanVlanCCMapP4 OBJECT-TYPE
   SYNTAX      Integer32
   MAX-ACCESS  read-write
   STATUS      current
   DESCRIPTION
      "Path: ethernet2.editConf.vlan.vlan.cosCosMap.p4"
   ::= {er1645v2Lan2FGUVlanEntry 241304832}

er1645v2Lan2FGUVlanVlanCCMapP5 OBJECT-TYPE
   SYNTAX      Integer32
   MAX-ACCESS  read-write
   STATUS      current
   DESCRIPTION
      "Path: ethernet2.editConf.vlan.vlan.cosCosMap.p5"
   ::= {er1645v2Lan2FGUVlanEntry 241305088}

er1645v2Lan2FGUVlanVlanCCMapP6 OBJECT-TYPE
   SYNTAX      Integer32
   MAX-ACCESS  read-write
   STATUS      current
   DESCRIPTION
      "Path: ethernet2.editConf.vlan.vlan.cosCosMap.p6"
   ::= {er1645v2Lan2FGUVlanEntry 241305344}

er1645v2Lan2FGUVlanVlanCCMapP7 OBJECT-TYPE
   SYNTAX      Integer32
   MAX-ACCESS  read-write
   STATUS      current
   DESCRIPTION
      "Path: ethernet2.editConf.vlan.vlan.cosCosMap.p7"
   ::= {er1645v2Lan2FGUVlanEntry 241305600}

er1645v2Lan2FGUVlanVlanQCMapQueue1 OBJECT-TYPE
   SYNTAX      Integer32
   MAX-ACCESS  read-write
   STATUS      current
   DESCRIPTION
      "Path: ethernet2.editConf.vlan.vlan.queueCosMap.queue1"
   ::= {er1645v2Lan2FGUVlanEntry 241434880}

er1645v2Lan2FGUVlanVlanQCMapQueue2 OBJECT-TYPE
   SYNTAX      Integer32
   MAX-ACCESS  read-write
   STATUS      current
   DESCRIPTION
      "Path: ethernet2.editConf.vlan.vlan.queueCosMap.queue2"
   ::= {er1645v2Lan2FGUVlanEntry 241435136}

er1645v2Lan2FGUVlanVlanQCMapQueue3 OBJECT-TYPE
   SYNTAX      Integer32
   MAX-ACCESS  read-write
   STATUS      current
   DESCRIPTION
      "Path: ethernet2.editConf.vlan.vlan.queueCosMap.queue3"
   ::= {er1645v2Lan2FGUVlanEntry 241435392}

er1645v2Lan2FGUVlanVlanQCMapQueue4 OBJECT-TYPE
   SYNTAX      Integer32
   MAX-ACCESS  read-write
   STATUS      current
   DESCRIPTION
      "Path: ethernet2.editConf.vlan.vlan.queueCosMap.queue4"
   ::= {er1645v2Lan2FGUVlanEntry 241435648}

er1645v2Lan2FGUVlanVlanQCMapQueue5 OBJECT-TYPE
   SYNTAX      Integer32
   MAX-ACCESS  read-write
   STATUS      current
   DESCRIPTION
      "Path: ethernet2.editConf.vlan.vlan.queueCosMap.queue5"
   ::= {er1645v2Lan2FGUVlanEntry 241435904}

er1645v2Lan2FGUVlanVlanQCMapLowDelayQueue OBJECT-TYPE
   SYNTAX      Integer32
   MAX-ACCESS  read-write
   STATUS      current
   DESCRIPTION
      "Path: ethernet2.editConf.vlan.vlan.queueCosMap.lowDelayQueue"
   ::= {er1645v2Lan2FGUVlanEntry 241436160}

er1645v2Lan2FGUVlanVlanQCMapLowDelay2Queue OBJECT-TYPE
   SYNTAX      Integer32
   MAX-ACCESS  read-write
   STATUS      current
   DESCRIPTION
      "Path: ethernet2.editConf.vlan.vlan.queueCosMap.lowDelay2Queue"
   ::= {er1645v2Lan2FGUVlanEntry 241436416}

er1645v2Lan2FGUVlanVlanQCMapSystemQueue OBJECT-TYPE
   SYNTAX      Integer32
   MAX-ACCESS  read-write
   STATUS      current
   DESCRIPTION
      "Path: ethernet2.editConf.vlan.vlan.queueCosMap.systemQueue"
   ::= {er1645v2Lan2FGUVlanEntry 241436672}

er1645v2Lan2FGUVlanVlanQinQSVid OBJECT-TYPE
   SYNTAX      Integer32
   MAX-ACCESS  read-write
   STATUS      current
   DESCRIPTION
      "Path: ethernet2.editConf.vlan.vlan.tunnel.sVid"
   ::= {er1645v2Lan2FGUVlanEntry 241172736}

er1645v2Lan2FGUVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tunnel.sTpid

       Possibilities:
               dot1Q   (33024)
               dot1ad   (34984)
               0x9100   (37120)
               0x9200   (37376)
               0x9300   (37632)"
   ::= {er1645v2Lan2FGUVlanEntry 241172992}

er1645v2Lan2FGUVlanVlanArpTimeOut OBJECT-TYPE
   SYNTAX      TimeTicks
   MAX-ACCESS  read-write
   STATUS      current
   DESCRIPTION
      "Path: ethernet2.editConf.vlan.vlan.arp.timeOut

       Time in centi-second."
   ::= {er1645v2Lan2FGUVlanEntry 235277312}

er1645v2Lan2FGUVlanVlanArpProxyArp OBJECT-TYPE
   SYNTAX      INTEGER
               {
               disabled (0),
               enabled (1)
               }
   MAX-ACCESS  read-write
   STATUS      current
   DESCRIPTION
      "Path: ethernet2.editConf.vlan.vlan.arp.proxyArp

       Possibilities:
               disabled   (0)
               enabled   (1)"
   ::= {er1645v2Lan2FGUVlanEntry 235287040}

er1645v2Lan2FGUVlanBandwidthMode OBJECT-TYPE
   SYNTAX      INTEGER
               {
               reshaping (1),
               policing (2),
               policingReshape (3)
               }
   MAX-ACCESS  read-write
   STATUS      current
   DESCRIPTION
      "Path: ethernet2.editConf.vlan.bandwidth.mode

       Possibilities:
               reshaping   (1)
               policing   (2)
               policingReshape   (3)"
   ::= {er1645v2Lan2FGUVlanEntry 148897792}

er1645v2Lan2FGUVlanBandwidthCir OBJECT-TYPE
   SYNTAX      Integer32
   MAX-ACCESS  read-write
   STATUS      current
   DESCRIPTION
      "Path: ethernet2.editConf.vlan.bandwidth.cir"
   ::= {er1645v2Lan2FGUVlanEntry 135266304}

er1645v2Lan2FGUVlanBandwidthEir OBJECT-TYPE
   SYNTAX      Integer32
   MAX-ACCESS  read-write
   STATUS      current
   DESCRIPTION
      "Path: ethernet2.editConf.vlan.bandwidth.eir"
   ::= {er1645v2Lan2FGUVlanEntry 141557760}

er1645v2Lan2FGUVlanBandwidthUnit OBJECT-TYPE
   SYNTAX      INTEGER
               {
               bitssec (1),
               percent (2)
               }
   MAX-ACCESS  read-write
   STATUS      current
   DESCRIPTION
      "Path: ethernet2.editConf.vlan.bandwidth.unit

       Possibilities:
               bits/sec   (1)
               percent   (2)"
   ::= {er1645v2Lan2FGUVlanEntry 139460608}

er1645v2Lan2FGUVlanBandwidthTc OBJECT-TYPE
   SYNTAX      INTEGER
               {
               auto (0)
               }
   MAX-ACCESS  read-write
   STATUS      current
   DESCRIPTION
      "Path: ethernet2.editConf.vlan.bandwidth.tc

       Possibilities:
               auto   (0)"
   ::= {er1645v2Lan2FGUVlanEntry 140509184}

er1645v2Lan2FGUVlanBandwidthTcFactor OBJECT-TYPE
   SYNTAX      INTEGER
               {
               ms (10),
               s100us (1)
               }
   MAX-ACCESS  read-write
   STATUS      current
   DESCRIPTION
      "Path: ethernet2.editConf.vlan.bandwidth.tcFactor

       Possibilities:
               ms   (10)
               *100us   (1)"
   ::= {er1645v2Lan2FGUVlanEntry 142606336}

er1645v2Lan2FGUVlanBandwidthCorrType OBJECT-TYPE
   SYNTAX      INTEGER
               {
               noCorrection (0),
               predefined (1),
               manual (2)
               }
   MAX-ACCESS  read-write
   STATUS      current
   DESCRIPTION
      "Path: ethernet2.editConf.vlan.bandwidth.correction.type

       Possibilities:
               noCorrection   (0)
               predefined   (1)
               manual   (2)"
   ::= {er1645v2Lan2FGUVlanEntry 136445952}

er1645v2Lan2FGUVlanBandwidthCorrPredefEncapsFrameRelay OBJECT-TYPE
   SYNTAX      DisplayString
   MAX-ACCESS  read-write
   STATUS      current
   DESCRIPTION
      "Path: ethernet2.editConf.vlan.bandwidth.correction.predefined.encapsulation.frameRelay"
   ::= {er1645v2Lan2FGUVlanEntry 136594432}

er1645v2Lan2FGUVlanBandwidthCorrPredefEncapsPpp OBJECT-TYPE
   SYNTAX      DisplayString
   MAX-ACCESS  read-write
   STATUS      current
   DESCRIPTION
      "Path: ethernet2.editConf.vlan.bandwidth.correction.predefined.encapsulation.ppp"
   ::= {er1645v2Lan2FGUVlanEntry 136595456}

er1645v2Lan2FGUVlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.bandwidth.correction.predefined.encapsulation.atm.higherLayer

       Possibilities:
               rfc2684   (0)
               ppp   (1)
               pppOverEthernet   (2)"
   ::= {er1645v2Lan2FGUVlanEntry 136596608}

er1645v2Lan2FGUVlanBandwidthCorrPredefEncapsAtmMp OBJECT-TYPE
   SYNTAX      INTEGER
               {
               llcEncapsulation (0),
               vcMultiplexing (1)
               }
   MAX-ACCESS  read-write
   STATUS      current
   DESCRIPTION
      "Path: ethernet2.editConf.vlan.bandwidth.correction.predefined.encapsulation.atm.multiProtocol

       Possibilities:
               llcEncapsulation   (0)
               vcMultiplexing   (1)"
   ::= {er1645v2Lan2FGUVlanEntry 136596736}

er1645v2Lan2FGUVlanBandwidthCorrPredefEncapsHdlc OBJECT-TYPE
   SYNTAX      DisplayString
   MAX-ACCESS  read-write
   STATUS      current
   DESCRIPTION
      "Path: ethernet2.editConf.vlan.bandwidth.correction.predefined.encapsulation.hdlc"
   ::= {er1645v2Lan2FGUVlanEntry 136597504}

er1645v2Lan2FGUVlanBandwidthCorrPredefEncapsEfmFs OBJECT-TYPE
   SYNTAX      Integer32
   MAX-ACCESS  read-write
   STATUS      current
   DESCRIPTION
      "Path: ethernet2.editConf.vlan.bandwidth.correction.predefined.encapsulation.efm.fragmentSize"
   ::= {er1645v2Lan2FGUVlanEntry 136598656}

er1645v2Lan2FGUVlanBandwidthCorrPredefEncapsEfmIb OBJECT-TYPE
   SYNTAX      Integer32
   MAX-ACCESS  read-write
   STATUS      current
   DESCRIPTION
      "Path: ethernet2.editConf.vlan.bandwidth.correction.predefined.encapsulation.efm.idleBytes"
   ::= {er1645v2Lan2FGUVlanEntry 136598784}

er1645v2Lan2FGUVlanBandwidthCorrPredefMode OBJECT-TYPE
   SYNTAX      INTEGER
               {
               routing (0),
               bridging (1)
               }
   MAX-ACCESS  read-write
   STATUS      current
   DESCRIPTION
      "Path: ethernet2.editConf.vlan.bandwidth.correction.predefined.mode

       Possibilities:
               routing   (0)
               bridging   (1)"
   ::= {er1645v2Lan2FGUVlanEntry 136609792}

er1645v2Lan2FGUVlanBandwidthCorrManualOverhead OBJECT-TYPE
   SYNTAX      Integer32
   MAX-ACCESS  read-write
   STATUS      current
   DESCRIPTION
      "Path: ethernet2.editConf.vlan.bandwidth.correction.manual.overhead"
   ::= {er1645v2Lan2FGUVlanEntry 136708608}

er1645v2Lan2FGUVlanBandwidthCorrManualFrameData OBJECT-TYPE
   SYNTAX      Counter32
   MAX-ACCESS  read-write
   STATUS      current
   DESCRIPTION
      "Path: ethernet2.editConf.vlan.bandwidth.correction.manual.frameData

       32 bit unsigned wrappable counter."
   ::= {er1645v2Lan2FGUVlanEntry 136709120}

er1645v2Lan2FGUVlanBandwidthCorrManualFrameHeader OBJECT-TYPE
   SYNTAX      Counter32
   MAX-ACCESS  read-write
   STATUS      current
   DESCRIPTION
      "Path: ethernet2.editConf.vlan.bandwidth.correction.manual.frameHeader

       32 bit unsigned wrappable counter."
   ::= {er1645v2Lan2FGUVlanEntry 136709632}

er1645v2Lan2FGUVlanBandwidthMaxFifoQLen OBJECT-TYPE
   SYNTAX      Integer32
   MAX-ACCESS  read-write
   STATUS      current
   DESCRIPTION
      "Path: ethernet2.editConf.vlan.bandwidth.maxFifoQLen"
   ::= {er1645v2Lan2FGUVlanEntry 137363456}

er1645v2Lan2FGUVlanBandwidthDeFlagCir OBJECT-TYPE
   SYNTAX      INTEGER
               {
               allowed (1),
               notAllowed (2)
               }
   MAX-ACCESS  read-write
   STATUS      current
   DESCRIPTION
      "Path: ethernet2.editConf.vlan.bandwidth.deFlag.cir

       Possibilities:
               allowed   (1)
               notAllowed   (2)"
   ::= {er1645v2Lan2FGUVlanEntry 147853312}

er1645v2Lan2FGUVlanBandwidthDeFlagEir OBJECT-TYPE
   SYNTAX      INTEGER
               {
               allowed (1),
               notAllowed (2)
               }
   MAX-ACCESS  read-write
   STATUS      current
   DESCRIPTION
      "Path: ethernet2.editConf.vlan.bandwidth.deFlag.eir

       Possibilities:
               allowed   (1)
               notAllowed   (2)"
   ::= {er1645v2Lan2FGUVlanEntry 147857408}

er1645v2Lan2FGUVlanBandwidthDeFlagViolate OBJECT-TYPE
   SYNTAX      INTEGER
               {
               allowed (1),
               notAllowed (2)
               }
   MAX-ACCESS  read-write
   STATUS      current
   DESCRIPTION
      "Path: ethernet2.editConf.vlan.bandwidth.deFlag.violate

       Possibilities:
               allowed   (1)
               notAllowed   (2)"
   ::= {er1645v2Lan2FGUVlanEntry 147861504}

er1645v2Lan2FGUVlanBandwidthActCirActNone OBJECT-TYPE
   SYNTAX      OCTET STRING
   MAX-ACCESS  read-write
   STATUS      current
   DESCRIPTION
      "Path: ethernet2.editConf.vlan.bandwidth.action.cirAction.none"
   ::= {er1645v2Lan2FGUVlanEntry 150085632}

er1645v2Lan2FGUVlanBandwidthActCirActEthCos1 OBJECT-TYPE
   SYNTAX      INTEGER
               {
               unchanged (256)
               }
   MAX-ACCESS  read-write
   STATUS      current
   DESCRIPTION
      "Path: ethernet2.editConf.vlan.bandwidth.action.cirAction.ethernet.cosDepth1

       Possibilities:
               unchanged   (256)"
   ::= {er1645v2Lan2FGUVlanEntry 150094080}

er1645v2Lan2FGUVlanBandwidthActCirActEthDei1 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth1

       Possibilities:
               unchanged   (255)
               clear   (0)
               set   (1)"
   ::= {er1645v2Lan2FGUVlanEntry 150099200}

er1645v2Lan2FGUVlanBandwidthActCirActEthCos2 OBJECT-TYPE
   SYNTAX      INTEGER
               {
               unchanged (256)
               }
   MAX-ACCESS  read-write
   STATUS      current
   DESCRIPTION
      "Path: ethernet2.editConf.vlan.bandwidth.action.cirAction.ethernet.cosDepth2

       Possibilities:
               unchanged   (256)"
   ::= {er1645v2Lan2FGUVlanEntry 150094336}

er1645v2Lan2FGUVlanBandwidthActCirActEthDei2 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth2

       Possibilities:
               unchanged   (255)
               clear   (0)
               set   (1)"
   ::= {er1645v2Lan2FGUVlanEntry 150099456}

er1645v2Lan2FGUVlanBandwidthActCirActEthCos3 OBJECT-TYPE
   SYNTAX      INTEGER
               {
               unchanged (256)
               }
   MAX-ACCESS  read-write
   STATUS      current
   DESCRIPTION
      "Path: ethernet2.editConf.vlan.bandwidth.action.cirAction.ethernet.cosDepth3

       Possibilities:
               unchanged   (256)"
   ::= {er1645v2Lan2FGUVlanEntry 150094592}

er1645v2Lan2FGUVlanBandwidthActCirActEthDei3 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth3

       Possibilities:
               unchanged   (255)
               clear   (0)
               set   (1)"
   ::= {er1645v2Lan2FGUVlanEntry 150099712}

er1645v2Lan2FGUVlanBandwidthActCirActEthCos4 OBJECT-TYPE
   SYNTAX      INTEGER
               {
               unchanged (256)
               }
   MAX-ACCESS  read-write
   STATUS      current
   DESCRIPTION
      "Path: ethernet2.editConf.vlan.bandwidth.action.cirAction.ethernet.cosDepth4

       Possibilities:
               unchanged   (256)"
   ::= {er1645v2Lan2FGUVlanEntry 150094848}

er1645v2Lan2FGUVlanBandwidthActCirActEthDei4 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth4

       Possibilities:
               unchanged   (255)
               clear   (0)
               set   (1)"
   ::= {er1645v2Lan2FGUVlanEntry 150099968}

er1645v2Lan2FGUVlanBandwidthActCirActEthCos5 OBJECT-TYPE
   SYNTAX      INTEGER
               {
               unchanged (256)
               }
   MAX-ACCESS  read-write
   STATUS      current
   DESCRIPTION
      "Path: ethernet2.editConf.vlan.bandwidth.action.cirAction.ethernet.cosDepth5

       Possibilities:
               unchanged   (256)"
   ::= {er1645v2Lan2FGUVlanEntry 150095104}

er1645v2Lan2FGUVlanBandwidthActCirActEthDei5 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth5

       Possibilities:
               unchanged   (255)
               clear   (0)
               set   (1)"
   ::= {er1645v2Lan2FGUVlanEntry 150100224}

er1645v2Lan2FGUVlanBandwidthActCirActEthCos6 OBJECT-TYPE
   SYNTAX      INTEGER
               {
               unchanged (256)
               }
   MAX-ACCESS  read-write
   STATUS      current
   DESCRIPTION
      "Path: ethernet2.editConf.vlan.bandwidth.action.cirAction.ethernet.cosDepth6

       Possibilities:
               unchanged   (256)"
   ::= {er1645v2Lan2FGUVlanEntry 150095360}

er1645v2Lan2FGUVlanBandwidthActCirActEthDei6 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth6

       Possibilities:
               unchanged   (255)
               clear   (0)
               set   (1)"
   ::= {er1645v2Lan2FGUVlanEntry 150100480}

er1645v2Lan2FGUVlanBandwidthActCirActEthCos7 OBJECT-TYPE
   SYNTAX      INTEGER
               {
               unchanged (256)
               }
   MAX-ACCESS  read-write
   STATUS      current
   DESCRIPTION
      "Path: ethernet2.editConf.vlan.bandwidth.action.cirAction.ethernet.cosDepth7

       Possibilities:
               unchanged   (256)"
   ::= {er1645v2Lan2FGUVlanEntry 150095616}

er1645v2Lan2FGUVlanBandwidthActCirActEthDei7 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth7

       Possibilities:
               unchanged   (255)
               clear   (0)
               set   (1)"
   ::= {er1645v2Lan2FGUVlanEntry 150100736}

er1645v2Lan2FGUVlanBandwidthActCirActEthCos8 OBJECT-TYPE
   SYNTAX      INTEGER
               {
               unchanged (256)
               }
   MAX-ACCESS  read-write
   STATUS      current
   DESCRIPTION
      "Path: ethernet2.editConf.vlan.bandwidth.action.cirAction.ethernet.cosDepth8

       Possibilities:
               unchanged   (256)"
   ::= {er1645v2Lan2FGUVlanEntry 150095872}

er1645v2Lan2FGUVlanBandwidthActCirActEthDei8 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth8

       Possibilities:
               unchanged   (255)
               clear   (0)
               set   (1)"
   ::= {er1645v2Lan2FGUVlanEntry 150100992}

er1645v2Lan2FGUVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150096128}

er1645v2Lan2FGUVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150096384}

er1645v2Lan2FGUVlanBandwidthActCirActEthDrpLev OBJECT-TYPE
   SYNTAX      INTEGER
               {
               unchanged (0)
               }
   MAX-ACCESS  read-write
   STATUS      current
   DESCRIPTION
      "Path: ethernet2.editConf.vlan.bandwidth.action.cirAction.ethernet.dropLevel

       Possibilities:
               unchanged   (0)"
   ::= {er1645v2Lan2FGUVlanEntry 150096640}

er1645v2Lan2FGUVlanBandwidthActCirActEthDeFlag OBJECT-TYPE
   SYNTAX      INTEGER
               {
               unchanged (255),
               clear (0),
               set (1)
               }
   MAX-ACCESS  read-write
   STATUS      current
   DESCRIPTION
      "Path: ethernet2.editConf.vlan.bandwidth.action.cirAction.ethernet.deFlag

       Possibilities:
               unchanged   (255)
               clear   (0)
               set   (1)"
   ::= {er1645v2Lan2FGUVlanEntry 150097408}

er1645v2Lan2FGUVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150120704}

er1645v2Lan2FGUVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150120960}

er1645v2Lan2FGUVlanBandwidthActCirActIpDrpLev OBJECT-TYPE
   SYNTAX      INTEGER
               {
               unchanged (0)
               }
   MAX-ACCESS  read-write
   STATUS      current
   DESCRIPTION
      "Path: ethernet2.editConf.vlan.bandwidth.action.cirAction.ip.dropLevel

       Possibilities:
               unchanged   (0)"
   ::= {er1645v2Lan2FGUVlanEntry 150121216}

er1645v2Lan2FGUVlanBandwidthActCirActIpDeFlag OBJECT-TYPE
   SYNTAX      INTEGER
               {
               unchanged (255),
               clear (0),
               set (1)
               }
   MAX-ACCESS  read-write
   STATUS      current
   DESCRIPTION
      "Path: ethernet2.editConf.vlan.bandwidth.action.cirAction.ip.deFlag

       Possibilities:
               unchanged   (255)
               clear   (0)
               set   (1)"
   ::= {er1645v2Lan2FGUVlanEntry 150121984}

er1645v2Lan2FGUVlanBandwidthActEirActNone OBJECT-TYPE
   SYNTAX      OCTET STRING
   MAX-ACCESS  read-write
   STATUS      current
   DESCRIPTION
      "Path: ethernet2.editConf.vlan.bandwidth.action.eirAction.none"
   ::= {er1645v2Lan2FGUVlanEntry 150216704}

er1645v2Lan2FGUVlanBandwidthActEirActEthCos1 OBJECT-TYPE
   SYNTAX      INTEGER
               {
               unchanged (256)
               }
   MAX-ACCESS  read-write
   STATUS      current
   DESCRIPTION
      "Path: ethernet2.editConf.vlan.bandwidth.action.eirAction.ethernet.cosDepth1

       Possibilities:
               unchanged   (256)"
   ::= {er1645v2Lan2FGUVlanEntry 150225152}

er1645v2Lan2FGUVlanBandwidthActEirActEthDei1 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth1

       Possibilities:
               unchanged   (255)
               clear   (0)
               set   (1)"
   ::= {er1645v2Lan2FGUVlanEntry 150230272}

er1645v2Lan2FGUVlanBandwidthActEirActEthCos2 OBJECT-TYPE
   SYNTAX      INTEGER
               {
               unchanged (256)
               }
   MAX-ACCESS  read-write
   STATUS      current
   DESCRIPTION
      "Path: ethernet2.editConf.vlan.bandwidth.action.eirAction.ethernet.cosDepth2

       Possibilities:
               unchanged   (256)"
   ::= {er1645v2Lan2FGUVlanEntry 150225408}

er1645v2Lan2FGUVlanBandwidthActEirActEthDei2 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth2

       Possibilities:
               unchanged   (255)
               clear   (0)
               set   (1)"
   ::= {er1645v2Lan2FGUVlanEntry 150230528}

er1645v2Lan2FGUVlanBandwidthActEirActEthCos3 OBJECT-TYPE
   SYNTAX      INTEGER
               {
               unchanged (256)
               }
   MAX-ACCESS  read-write
   STATUS      current
   DESCRIPTION
      "Path: ethernet2.editConf.vlan.bandwidth.action.eirAction.ethernet.cosDepth3

       Possibilities:
               unchanged   (256)"
   ::= {er1645v2Lan2FGUVlanEntry 150225664}

er1645v2Lan2FGUVlanBandwidthActEirActEthDei3 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth3

       Possibilities:
               unchanged   (255)
               clear   (0)
               set   (1)"
   ::= {er1645v2Lan2FGUVlanEntry 150230784}

er1645v2Lan2FGUVlanBandwidthActEirActEthCos4 OBJECT-TYPE
   SYNTAX      INTEGER
               {
               unchanged (256)
               }
   MAX-ACCESS  read-write
   STATUS      current
   DESCRIPTION
      "Path: ethernet2.editConf.vlan.bandwidth.action.eirAction.ethernet.cosDepth4

       Possibilities:
               unchanged   (256)"
   ::= {er1645v2Lan2FGUVlanEntry 150225920}

er1645v2Lan2FGUVlanBandwidthActEirActEthDei4 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth4

       Possibilities:
               unchanged   (255)
               clear   (0)
               set   (1)"
   ::= {er1645v2Lan2FGUVlanEntry 150231040}

er1645v2Lan2FGUVlanBandwidthActEirActEthCos5 OBJECT-TYPE
   SYNTAX      INTEGER
               {
               unchanged (256)
               }
   MAX-ACCESS  read-write
   STATUS      current
   DESCRIPTION
      "Path: ethernet2.editConf.vlan.bandwidth.action.eirAction.ethernet.cosDepth5

       Possibilities:
               unchanged   (256)"
   ::= {er1645v2Lan2FGUVlanEntry 150226176}

er1645v2Lan2FGUVlanBandwidthActEirActEthDei5 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth5

       Possibilities:
               unchanged   (255)
               clear   (0)
               set   (1)"
   ::= {er1645v2Lan2FGUVlanEntry 150231296}

er1645v2Lan2FGUVlanBandwidthActEirActEthCos6 OBJECT-TYPE
   SYNTAX      INTEGER
               {
               unchanged (256)
               }
   MAX-ACCESS  read-write
   STATUS      current
   DESCRIPTION
      "Path: ethernet2.editConf.vlan.bandwidth.action.eirAction.ethernet.cosDepth6

       Possibilities:
               unchanged   (256)"
   ::= {er1645v2Lan2FGUVlanEntry 150226432}

er1645v2Lan2FGUVlanBandwidthActEirActEthDei6 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth6

       Possibilities:
               unchanged   (255)
               clear   (0)
               set   (1)"
   ::= {er1645v2Lan2FGUVlanEntry 150231552}

er1645v2Lan2FGUVlanBandwidthActEirActEthCos7 OBJECT-TYPE
   SYNTAX      INTEGER
               {
               unchanged (256)
               }
   MAX-ACCESS  read-write
   STATUS      current
   DESCRIPTION
      "Path: ethernet2.editConf.vlan.bandwidth.action.eirAction.ethernet.cosDepth7

       Possibilities:
               unchanged   (256)"
   ::= {er1645v2Lan2FGUVlanEntry 150226688}

er1645v2Lan2FGUVlanBandwidthActEirActEthDei7 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth7

       Possibilities:
               unchanged   (255)
               clear   (0)
               set   (1)"
   ::= {er1645v2Lan2FGUVlanEntry 150231808}

er1645v2Lan2FGUVlanBandwidthActEirActEthCos8 OBJECT-TYPE
   SYNTAX      INTEGER
               {
               unchanged (256)
               }
   MAX-ACCESS  read-write
   STATUS      current
   DESCRIPTION
      "Path: ethernet2.editConf.vlan.bandwidth.action.eirAction.ethernet.cosDepth8

       Possibilities:
               unchanged   (256)"
   ::= {er1645v2Lan2FGUVlanEntry 150226944}

er1645v2Lan2FGUVlanBandwidthActEirActEthDei8 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth8

       Possibilities:
               unchanged   (255)
               clear   (0)
               set   (1)"
   ::= {er1645v2Lan2FGUVlanEntry 150232064}

er1645v2Lan2FGUVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150227200}

er1645v2Lan2FGUVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150227456}

er1645v2Lan2FGUVlanBandwidthActEirActEthDrpLev OBJECT-TYPE
   SYNTAX      INTEGER
               {
               unchanged (0)
               }
   MAX-ACCESS  read-write
   STATUS      current
   DESCRIPTION
      "Path: ethernet2.editConf.vlan.bandwidth.action.eirAction.ethernet.dropLevel

       Possibilities:
               unchanged   (0)"
   ::= {er1645v2Lan2FGUVlanEntry 150227712}

er1645v2Lan2FGUVlanBandwidthActEirActEthDeFlag OBJECT-TYPE
   SYNTAX      INTEGER
               {
               unchanged (255),
               clear (0),
               set (1)
               }
   MAX-ACCESS  read-write
   STATUS      current
   DESCRIPTION
      "Path: ethernet2.editConf.vlan.bandwidth.action.eirAction.ethernet.deFlag

       Possibilities:
               unchanged   (255)
               clear   (0)
               set   (1)"
   ::= {er1645v2Lan2FGUVlanEntry 150228480}

er1645v2Lan2FGUVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150251776}

er1645v2Lan2FGUVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150252032}

er1645v2Lan2FGUVlanBandwidthActEirActIpDrpLev OBJECT-TYPE
   SYNTAX      INTEGER
               {
               unchanged (0)
               }
   MAX-ACCESS  read-write
   STATUS      current
   DESCRIPTION
      "Path: ethernet2.editConf.vlan.bandwidth.action.eirAction.ip.dropLevel

       Possibilities:
               unchanged   (0)"
   ::= {er1645v2Lan2FGUVlanEntry 150252288}

er1645v2Lan2FGUVlanBandwidthActEirActIpDeFlag OBJECT-TYPE
   SYNTAX      INTEGER
               {
               unchanged (255),
               clear (0),
               set (1)
               }
   MAX-ACCESS  read-write
   STATUS      current
   DESCRIPTION
      "Path: ethernet2.editConf.vlan.bandwidth.action.eirAction.ip.deFlag

       Possibilities:
               unchanged   (255)
               clear   (0)
               set   (1)"
   ::= {er1645v2Lan2FGUVlanEntry 150253056}

er1645v2Lan2FGUVlanBandwidthActViolActNone OBJECT-TYPE
   SYNTAX      OCTET STRING
   MAX-ACCESS  read-write
   STATUS      current
   DESCRIPTION
      "Path: ethernet2.editConf.vlan.bandwidth.action.violateAction.none"
   ::= {er1645v2Lan2FGUVlanEntry 150347776}

er1645v2Lan2FGUVlanBandwidthActViolActDrop OBJECT-TYPE
   SYNTAX      OCTET STRING
   MAX-ACCESS  read-write
   STATUS      current
   DESCRIPTION
      "Path: ethernet2.editConf.vlan.bandwidth.action.violateAction.drop"
   ::= {er1645v2Lan2FGUVlanEntry 150364160}

er1645v2Lan2FGUVlanBandwidthActViolActEthCos1 OBJECT-TYPE
   SYNTAX      INTEGER
               {
               unchanged (256)
               }
   MAX-ACCESS  read-write
   STATUS      current
   DESCRIPTION
      "Path: ethernet2.editConf.vlan.bandwidth.action.violateAction.ethernet.cosDepth1

       Possibilities:
               unchanged   (256)"
   ::= {er1645v2Lan2FGUVlanEntry 150356224}

er1645v2Lan2FGUVlanBandwidthActViolActEthDei1 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth1

       Possibilities:
               unchanged   (255)
               clear   (0)
               set   (1)"
   ::= {er1645v2Lan2FGUVlanEntry 150361344}

er1645v2Lan2FGUVlanBandwidthActViolActEthCos2 OBJECT-TYPE
   SYNTAX      INTEGER
               {
               unchanged (256)
               }
   MAX-ACCESS  read-write
   STATUS      current
   DESCRIPTION
      "Path: ethernet2.editConf.vlan.bandwidth.action.violateAction.ethernet.cosDepth2

       Possibilities:
               unchanged   (256)"
   ::= {er1645v2Lan2FGUVlanEntry 150356480}

er1645v2Lan2FGUVlanBandwidthActViolActEthDei2 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth2

       Possibilities:
               unchanged   (255)
               clear   (0)
               set   (1)"
   ::= {er1645v2Lan2FGUVlanEntry 150361600}

er1645v2Lan2FGUVlanBandwidthActViolActEthCos3 OBJECT-TYPE
   SYNTAX      INTEGER
               {
               unchanged (256)
               }
   MAX-ACCESS  read-write
   STATUS      current
   DESCRIPTION
      "Path: ethernet2.editConf.vlan.bandwidth.action.violateAction.ethernet.cosDepth3

       Possibilities:
               unchanged   (256)"
   ::= {er1645v2Lan2FGUVlanEntry 150356736}

er1645v2Lan2FGUVlanBandwidthActViolActEthDei3 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth3

       Possibilities:
               unchanged   (255)
               clear   (0)
               set   (1)"
   ::= {er1645v2Lan2FGUVlanEntry 150361856}

er1645v2Lan2FGUVlanBandwidthActViolActEthCos4 OBJECT-TYPE
   SYNTAX      INTEGER
               {
               unchanged (256)
               }
   MAX-ACCESS  read-write
   STATUS      current
   DESCRIPTION
      "Path: ethernet2.editConf.vlan.bandwidth.action.violateAction.ethernet.cosDepth4

       Possibilities:
               unchanged   (256)"
   ::= {er1645v2Lan2FGUVlanEntry 150356992}

er1645v2Lan2FGUVlanBandwidthActViolActEthDei4 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth4

       Possibilities:
               unchanged   (255)
               clear   (0)
               set   (1)"
   ::= {er1645v2Lan2FGUVlanEntry 150362112}

er1645v2Lan2FGUVlanBandwidthActViolActEthCos5 OBJECT-TYPE
   SYNTAX      INTEGER
               {
               unchanged (256)
               }
   MAX-ACCESS  read-write
   STATUS      current
   DESCRIPTION
      "Path: ethernet2.editConf.vlan.bandwidth.action.violateAction.ethernet.cosDepth5

       Possibilities:
               unchanged   (256)"
   ::= {er1645v2Lan2FGUVlanEntry 150357248}

er1645v2Lan2FGUVlanBandwidthActViolActEthDei5 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth5

       Possibilities:
               unchanged   (255)
               clear   (0)
               set   (1)"
   ::= {er1645v2Lan2FGUVlanEntry 150362368}

er1645v2Lan2FGUVlanBandwidthActViolActEthCos6 OBJECT-TYPE
   SYNTAX      INTEGER
               {
               unchanged (256)
               }
   MAX-ACCESS  read-write
   STATUS      current
   DESCRIPTION
      "Path: ethernet2.editConf.vlan.bandwidth.action.violateAction.ethernet.cosDepth6

       Possibilities:
               unchanged   (256)"
   ::= {er1645v2Lan2FGUVlanEntry 150357504}

er1645v2Lan2FGUVlanBandwidthActViolActEthDei6 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth6

       Possibilities:
               unchanged   (255)
               clear   (0)
               set   (1)"
   ::= {er1645v2Lan2FGUVlanEntry 150362624}

er1645v2Lan2FGUVlanBandwidthActViolActEthCos7 OBJECT-TYPE
   SYNTAX      INTEGER
               {
               unchanged (256)
               }
   MAX-ACCESS  read-write
   STATUS      current
   DESCRIPTION
      "Path: ethernet2.editConf.vlan.bandwidth.action.violateAction.ethernet.cosDepth7

       Possibilities:
               unchanged   (256)"
   ::= {er1645v2Lan2FGUVlanEntry 150357760}

er1645v2Lan2FGUVlanBandwidthActViolActEthDei7 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth7

       Possibilities:
               unchanged   (255)
               clear   (0)
               set   (1)"
   ::= {er1645v2Lan2FGUVlanEntry 150362880}

er1645v2Lan2FGUVlanBandwidthActViolActEthCos8 OBJECT-TYPE
   SYNTAX      INTEGER
               {
               unchanged (256)
               }
   MAX-ACCESS  read-write
   STATUS      current
   DESCRIPTION
      "Path: ethernet2.editConf.vlan.bandwidth.action.violateAction.ethernet.cosDepth8

       Possibilities:
               unchanged   (256)"
   ::= {er1645v2Lan2FGUVlanEntry 150358016}

er1645v2Lan2FGUVlanBandwidthActViolActEthDei8 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth8

       Possibilities:
               unchanged   (255)
               clear   (0)
               set   (1)"
   ::= {er1645v2Lan2FGUVlanEntry 150363136}

er1645v2Lan2FGUVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150358272}

er1645v2Lan2FGUVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150358528}

er1645v2Lan2FGUVlanBandwidthActViolActEthDrpLev OBJECT-TYPE
   SYNTAX      INTEGER
               {
               unchanged (0)
               }
   MAX-ACCESS  read-write
   STATUS      current
   DESCRIPTION
      "Path: ethernet2.editConf.vlan.bandwidth.action.violateAction.ethernet.dropLevel

       Possibilities:
               unchanged   (0)"
   ::= {er1645v2Lan2FGUVlanEntry 150358784}

er1645v2Lan2FGUVlanBandwidthActViolActEthDeFlag OBJECT-TYPE
   SYNTAX      INTEGER
               {
               unchanged (255),
               clear (0),
               set (1)
               }
   MAX-ACCESS  read-write
   STATUS      current
   DESCRIPTION
      "Path: ethernet2.editConf.vlan.bandwidth.action.violateAction.ethernet.deFlag

       Possibilities:
               unchanged   (255)
               clear   (0)
               set   (1)"
   ::= {er1645v2Lan2FGUVlanEntry 150359552}

er1645v2Lan2FGUVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 150382848}

er1645v2Lan2FGUVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 150383104}

er1645v2Lan2FGUVlanBandwidthActViolActIpDrpLev OBJECT-TYPE
   SYNTAX      INTEGER
               {
               unchanged (0)
               }
   MAX-ACCESS  read-write
   STATUS      current
   DESCRIPTION
      "Path: ethernet2.editConf.vlan.bandwidth.action.violateAction.ip.dropLevel

       Possibilities:
               unchanged   (0)"
   ::= {er1645v2Lan2FGUVlanEntry 150383360}

er1645v2Lan2FGUVlanBandwidthActViolActIpDeFlag OBJECT-TYPE
   SYNTAX      INTEGER
               {
               unchanged (255),
               clear (0),
               set (1)
               }
   MAX-ACCESS  read-write
   STATUS      current
   DESCRIPTION
      "Path: ethernet2.editConf.vlan.bandwidth.action.violateAction.ip.deFlag

       Possibilities:
               unchanged   (255)
               clear   (0)
               set   (1)"
   ::= {er1645v2Lan2FGUVlanEntry 150384128}

er1645v2Lan2FGUVlanInbBwMode OBJECT-TYPE
   SYNTAX      INTEGER
               {
               reshaping (1),
               policing (2)
               }
   MAX-ACCESS  read-write
   STATUS      current
   DESCRIPTION
      "Path: ethernet2.editConf.vlan.inboundBandwidth.mode

       Possibilities:
               reshaping   (1)
               policing   (2)"
   ::= {er1645v2Lan2FGUVlanEntry 132120576}

er1645v2Lan2FGUVlanInbBwCir OBJECT-TYPE
   SYNTAX      Integer32
   MAX-ACCESS  read-write
   STATUS      current
   DESCRIPTION
      "Path: ethernet2.editConf.vlan.inboundBandwidth.cir"
   ::= {er1645v2Lan2FGUVlanEntry 118489088}

er1645v2Lan2FGUVlanInbBwEir OBJECT-TYPE
   SYNTAX      Integer32
   MAX-ACCESS  read-write
   STATUS      current
   DESCRIPTION
      "Path: ethernet2.editConf.vlan.inboundBandwidth.eir"
   ::= {er1645v2Lan2FGUVlanEntry 124780544}

er1645v2Lan2FGUVlanInbBwUnit OBJECT-TYPE
   SYNTAX      INTEGER
               {
               bitssec (1),
               percent (2)
               }
   MAX-ACCESS  read-write
   STATUS      current
   DESCRIPTION
      "Path: ethernet2.editConf.vlan.inboundBandwidth.unit

       Possibilities:
               bits/sec   (1)
               percent   (2)"
   ::= {er1645v2Lan2FGUVlanEntry 122683392}

er1645v2Lan2FGUVlanInbBwTc OBJECT-TYPE
   SYNTAX      INTEGER
               {
               auto (0)
               }
   MAX-ACCESS  read-write
   STATUS      current
   DESCRIPTION
      "Path: ethernet2.editConf.vlan.inboundBandwidth.tc

       Possibilities:
               auto   (0)"
   ::= {er1645v2Lan2FGUVlanEntry 123731968}

er1645v2Lan2FGUVlanInbBwTcFactor OBJECT-TYPE
   SYNTAX      INTEGER
               {
               ms (10),
               s100us (1)
               }
   MAX-ACCESS  read-write
   STATUS      current
   DESCRIPTION
      "Path: ethernet2.editConf.vlan.inboundBandwidth.tcFactor

       Possibilities:
               ms   (10)
               *100us   (1)"
   ::= {er1645v2Lan2FGUVlanEntry 125829120}

er1645v2Lan2FGUVlanInbBwCorrType OBJECT-TYPE
   SYNTAX      INTEGER
               {
               noCorrection (0),
               predefined (1),
               manual (2)
               }
   MAX-ACCESS  read-write
   STATUS      current
   DESCRIPTION
      "Path: ethernet2.editConf.vlan.inboundBandwidth.correction.type

       Possibilities:
               noCorrection   (0)
               predefined   (1)
               manual   (2)"
   ::= {er1645v2Lan2FGUVlanEntry 119668736}

er1645v2Lan2FGUVlanInbBwCorrPredefEncapsFrameRelay OBJECT-TYPE
   SYNTAX      DisplayString
   MAX-ACCESS  read-write
   STATUS      current
   DESCRIPTION
      "Path: ethernet2.editConf.vlan.inboundBandwidth.correction.predefined.encapsulation.frameRelay"
   ::= {er1645v2Lan2FGUVlanEntry 119817216}

er1645v2Lan2FGUVlanInbBwCorrPredefEncapsPpp OBJECT-TYPE
   SYNTAX      DisplayString
   MAX-ACCESS  read-write
   STATUS      current
   DESCRIPTION
      "Path: ethernet2.editConf.vlan.inboundBandwidth.correction.predefined.encapsulation.ppp"
   ::= {er1645v2Lan2FGUVlanEntry 119818240}

er1645v2Lan2FGUVlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.inboundBandwidth.correction.predefined.encapsulation.atm.higherLayer

       Possibilities:
               rfc2684   (0)
               ppp   (1)
               pppOverEthernet   (2)"
   ::= {er1645v2Lan2FGUVlanEntry 119819392}

er1645v2Lan2FGUVlanInbBwCorrPredefEncapsAtmMp OBJECT-TYPE
   SYNTAX      INTEGER
               {
               llcEncapsulation (0),
               vcMultiplexing (1)
               }
   MAX-ACCESS  read-write
   STATUS      current
   DESCRIPTION
      "Path: ethernet2.editConf.vlan.inboundBandwidth.correction.predefined.encapsulation.atm.multiProtocol

       Possibilities:
               llcEncapsulation   (0)
               vcMultiplexing   (1)"
   ::= {er1645v2Lan2FGUVlanEntry 119819520}

er1645v2Lan2FGUVlanInbBwCorrPredefEncapsHdlc OBJECT-TYPE
   SYNTAX      DisplayString
   MAX-ACCESS  read-write
   STATUS      current
   DESCRIPTION
      "Path: ethernet2.editConf.vlan.inboundBandwidth.correction.predefined.encapsulation.hdlc"
   ::= {er1645v2Lan2FGUVlanEntry 119820288}

er1645v2Lan2FGUVlanInbBwCorrPredefEncapsEfmFs OBJECT-TYPE
   SYNTAX      Integer32
   MAX-ACCESS  read-write
   STATUS      current
   DESCRIPTION
      "Path: ethernet2.editConf.vlan.inboundBandwidth.correction.predefined.encapsulation.efm.fragmentSize"
   ::= {er1645v2Lan2FGUVlanEntry 119821440}

er1645v2Lan2FGUVlanInbBwCorrPredefEncapsEfmIb OBJECT-TYPE
   SYNTAX      Integer32
   MAX-ACCESS  read-write
   STATUS      current
   DESCRIPTION
      "Path: ethernet2.editConf.vlan.inboundBandwidth.correction.predefined.encapsulation.efm.idleBytes"
   ::= {er1645v2Lan2FGUVlanEntry 119821568}

er1645v2Lan2FGUVlanInbBwCorrPredefMode OBJECT-TYPE
   SYNTAX      INTEGER
               {
               routing (0),
               bridging (1)
               }
   MAX-ACCESS  read-write
   STATUS      current
   DESCRIPTION
      "Path: ethernet2.editConf.vlan.inboundBandwidth.correction.predefined.mode

       Possibilities:
               routing   (0)
               bridging   (1)"
   ::= {er1645v2Lan2FGUVlanEntry 119832576}

er1645v2Lan2FGUVlanInbBwCorrManualOverhead OBJECT-TYPE
   SYNTAX      Integer32
   MAX-ACCESS  read-write
   STATUS      current
   DESCRIPTION
      "Path: ethernet2.editConf.vlan.inboundBandwidth.correction.manual.overhead"
   ::= {er1645v2Lan2FGUVlanEntry 119931392}

er1645v2Lan2FGUVlanInbBwCorrManualFrameData OBJECT-TYPE
   SYNTAX      Counter32
   MAX-ACCESS  read-write
   STATUS      current
   DESCRIPTION
      "Path: ethernet2.editConf.vlan.inboundBandwidth.correction.manual.frameData

       32 bit unsigned wrappable counter."
   ::= {er1645v2Lan2FGUVlanEntry 119931904}

er1645v2Lan2FGUVlanInbBwCorrManualFrameHeader OBJECT-TYPE
   SYNTAX      Counter32
   MAX-ACCESS  read-write
   STATUS      current
   DESCRIPTION
      "Path: ethernet2.editConf.vlan.inboundBandwidth.correction.manual.frameHeader

       32 bit unsigned wrappable counter."
   ::= {er1645v2Lan2FGUVlanEntry 119932416}

er1645v2Lan2FGUVlanInbBwMaxFifoQLen OBJECT-TYPE
   SYNTAX      Integer32
   MAX-ACCESS  read-write
   STATUS      current
   DESCRIPTION
      "Path: ethernet2.editConf.vlan.inboundBandwidth.maxFifoQLen"
   ::= {er1645v2Lan2FGUVlanEntry 120586240}

er1645v2Lan2FGUVlanInbBwPriorityPolicy OBJECT-TYPE
   SYNTAX      DisplayString
   MAX-ACCESS  read-write
   STATUS      current
   DESCRIPTION
      "Path: ethernet2.editConf.vlan.inboundBandwidth.priorityPolicy"
   ::= {er1645v2Lan2FGUVlanEntry 121634816}

er1645v2Lan2FGUVlanInbBwDeFlagCir OBJECT-TYPE
   SYNTAX      INTEGER
               {
               allowed (1),
               notAllowed (2)
               }
   MAX-ACCESS  read-write
   STATUS      current
   DESCRIPTION
      "Path: ethernet2.editConf.vlan.inboundBandwidth.deFlag.cir

       Possibilities:
               allowed   (1)
               notAllowed   (2)"
   ::= {er1645v2Lan2FGUVlanEntry 131076096}

er1645v2Lan2FGUVlanInbBwDeFlagEir OBJECT-TYPE
   SYNTAX      INTEGER
               {
               allowed (1),
               notAllowed (2)
               }
   MAX-ACCESS  read-write
   STATUS      current
   DESCRIPTION
      "Path: ethernet2.editConf.vlan.inboundBandwidth.deFlag.eir

       Possibilities:
               allowed   (1)
               notAllowed   (2)"
   ::= {er1645v2Lan2FGUVlanEntry 131080192}

er1645v2Lan2FGUVlanInbBwDeFlagViolate OBJECT-TYPE
   SYNTAX      INTEGER
               {
               allowed (1),
               notAllowed (2)
               }
   MAX-ACCESS  read-write
   STATUS      current
   DESCRIPTION
      "Path: ethernet2.editConf.vlan.inboundBandwidth.deFlag.violate

       Possibilities:
               allowed   (1)
               notAllowed   (2)"
   ::= {er1645v2Lan2FGUVlanEntry 131084288}

er1645v2Lan2FGUVlanInbBwActCirActNone OBJECT-TYPE
   SYNTAX      OCTET STRING
   MAX-ACCESS  read-write
   STATUS      current
   DESCRIPTION
      "Path: ethernet2.editConf.vlan.inboundBandwidth.action.cirAction.none"
   ::= {er1645v2Lan2FGUVlanEntry 133308416}

er1645v2Lan2FGUVlanInbBwActCirActEthCos1 OBJECT-TYPE
   SYNTAX      INTEGER
               {
               unchanged (256)
               }
   MAX-ACCESS  read-write
   STATUS      current
   DESCRIPTION
      "Path: ethernet2.editConf.vlan.inboundBandwidth.action.cirAction.ethernet.cosDepth1

       Possibilities:
               unchanged   (256)"
   ::= {er1645v2Lan2FGUVlanEntry 133316864}

er1645v2Lan2FGUVlanInbBwActCirActEthDei1 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth1

       Possibilities:
               unchanged   (255)
               clear   (0)
               set   (1)"
   ::= {er1645v2Lan2FGUVlanEntry 133321984}

er1645v2Lan2FGUVlanInbBwActCirActEthCos2 OBJECT-TYPE
   SYNTAX      INTEGER
               {
               unchanged (256)
               }
   MAX-ACCESS  read-write
   STATUS      current
   DESCRIPTION
      "Path: ethernet2.editConf.vlan.inboundBandwidth.action.cirAction.ethernet.cosDepth2

       Possibilities:
               unchanged   (256)"
   ::= {er1645v2Lan2FGUVlanEntry 133317120}

er1645v2Lan2FGUVlanInbBwActCirActEthDei2 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth2

       Possibilities:
               unchanged   (255)
               clear   (0)
               set   (1)"
   ::= {er1645v2Lan2FGUVlanEntry 133322240}

er1645v2Lan2FGUVlanInbBwActCirActEthCos3 OBJECT-TYPE
   SYNTAX      INTEGER
               {
               unchanged (256)
               }
   MAX-ACCESS  read-write
   STATUS      current
   DESCRIPTION
      "Path: ethernet2.editConf.vlan.inboundBandwidth.action.cirAction.ethernet.cosDepth3

       Possibilities:
               unchanged   (256)"
   ::= {er1645v2Lan2FGUVlanEntry 133317376}

er1645v2Lan2FGUVlanInbBwActCirActEthDei3 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth3

       Possibilities:
               unchanged   (255)
               clear   (0)
               set   (1)"
   ::= {er1645v2Lan2FGUVlanEntry 133322496}

er1645v2Lan2FGUVlanInbBwActCirActEthCos4 OBJECT-TYPE
   SYNTAX      INTEGER
               {
               unchanged (256)
               }
   MAX-ACCESS  read-write
   STATUS      current
   DESCRIPTION
      "Path: ethernet2.editConf.vlan.inboundBandwidth.action.cirAction.ethernet.cosDepth4

       Possibilities:
               unchanged   (256)"
   ::= {er1645v2Lan2FGUVlanEntry 133317632}

er1645v2Lan2FGUVlanInbBwActCirActEthDei4 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth4

       Possibilities:
               unchanged   (255)
               clear   (0)
               set   (1)"
   ::= {er1645v2Lan2FGUVlanEntry 133322752}

er1645v2Lan2FGUVlanInbBwActCirActEthCos5 OBJECT-TYPE
   SYNTAX      INTEGER
               {
               unchanged (256)
               }
   MAX-ACCESS  read-write
   STATUS      current
   DESCRIPTION
      "Path: ethernet2.editConf.vlan.inboundBandwidth.action.cirAction.ethernet.cosDepth5

       Possibilities:
               unchanged   (256)"
   ::= {er1645v2Lan2FGUVlanEntry 133317888}

er1645v2Lan2FGUVlanInbBwActCirActEthDei5 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth5

       Possibilities:
               unchanged   (255)
               clear   (0)
               set   (1)"
   ::= {er1645v2Lan2FGUVlanEntry 133323008}

er1645v2Lan2FGUVlanInbBwActCirActEthCos6 OBJECT-TYPE
   SYNTAX      INTEGER
               {
               unchanged (256)
               }
   MAX-ACCESS  read-write
   STATUS      current
   DESCRIPTION
      "Path: ethernet2.editConf.vlan.inboundBandwidth.action.cirAction.ethernet.cosDepth6

       Possibilities:
               unchanged   (256)"
   ::= {er1645v2Lan2FGUVlanEntry 133318144}

er1645v2Lan2FGUVlanInbBwActCirActEthDei6 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth6

       Possibilities:
               unchanged   (255)
               clear   (0)
               set   (1)"
   ::= {er1645v2Lan2FGUVlanEntry 133323264}

er1645v2Lan2FGUVlanInbBwActCirActEthCos7 OBJECT-TYPE
   SYNTAX      INTEGER
               {
               unchanged (256)
               }
   MAX-ACCESS  read-write
   STATUS      current
   DESCRIPTION
      "Path: ethernet2.editConf.vlan.inboundBandwidth.action.cirAction.ethernet.cosDepth7

       Possibilities:
               unchanged   (256)"
   ::= {er1645v2Lan2FGUVlanEntry 133318400}

er1645v2Lan2FGUVlanInbBwActCirActEthDei7 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth7

       Possibilities:
               unchanged   (255)
               clear   (0)
               set   (1)"
   ::= {er1645v2Lan2FGUVlanEntry 133323520}

er1645v2Lan2FGUVlanInbBwActCirActEthCos8 OBJECT-TYPE
   SYNTAX      INTEGER
               {
               unchanged (256)
               }
   MAX-ACCESS  read-write
   STATUS      current
   DESCRIPTION
      "Path: ethernet2.editConf.vlan.inboundBandwidth.action.cirAction.ethernet.cosDepth8

       Possibilities:
               unchanged   (256)"
   ::= {er1645v2Lan2FGUVlanEntry 133318656}

er1645v2Lan2FGUVlanInbBwActCirActEthDei8 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth8

       Possibilities:
               unchanged   (255)
               clear   (0)
               set   (1)"
   ::= {er1645v2Lan2FGUVlanEntry 133323776}

er1645v2Lan2FGUVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133318912}

er1645v2Lan2FGUVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133319168}

er1645v2Lan2FGUVlanInbBwActCirActEthDrpLev OBJECT-TYPE
   SYNTAX      INTEGER
               {
               unchanged (0)
               }
   MAX-ACCESS  read-write
   STATUS      current
   DESCRIPTION
      "Path: ethernet2.editConf.vlan.inboundBandwidth.action.cirAction.ethernet.dropLevel

       Possibilities:
               unchanged   (0)"
   ::= {er1645v2Lan2FGUVlanEntry 133319424}

er1645v2Lan2FGUVlanInbBwActCirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deFlag

       Possibilities:
               unchanged   (255)
               clear   (0)
               set   (1)"
   ::= {er1645v2Lan2FGUVlanEntry 133320192}

er1645v2Lan2FGUVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133343488}

er1645v2Lan2FGUVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133343744}

er1645v2Lan2FGUVlanInbBwActCirActIpDrpLev OBJECT-TYPE
   SYNTAX      INTEGER
               {
               unchanged (0)
               }
   MAX-ACCESS  read-write
   STATUS      current
   DESCRIPTION
      "Path: ethernet2.editConf.vlan.inboundBandwidth.action.cirAction.ip.dropLevel

       Possibilities:
               unchanged   (0)"
   ::= {er1645v2Lan2FGUVlanEntry 133344000}

er1645v2Lan2FGUVlanInbBwActCirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ip.deFlag

       Possibilities:
               unchanged   (255)
               clear   (0)
               set   (1)"
   ::= {er1645v2Lan2FGUVlanEntry 133344768}

er1645v2Lan2FGUVlanInbBwActEirActNone OBJECT-TYPE
   SYNTAX      OCTET STRING
   MAX-ACCESS  read-write
   STATUS      current
   DESCRIPTION
      "Path: ethernet2.editConf.vlan.inboundBandwidth.action.eirAction.none"
   ::= {er1645v2Lan2FGUVlanEntry 133439488}

er1645v2Lan2FGUVlanInbBwActEirActEthCos1 OBJECT-TYPE
   SYNTAX      INTEGER
               {
               unchanged (256)
               }
   MAX-ACCESS  read-write
   STATUS      current
   DESCRIPTION
      "Path: ethernet2.editConf.vlan.inboundBandwidth.action.eirAction.ethernet.cosDepth1

       Possibilities:
               unchanged   (256)"
   ::= {er1645v2Lan2FGUVlanEntry 133447936}

er1645v2Lan2FGUVlanInbBwActEirActEthDei1 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth1

       Possibilities:
               unchanged   (255)
               clear   (0)
               set   (1)"
   ::= {er1645v2Lan2FGUVlanEntry 133453056}

er1645v2Lan2FGUVlanInbBwActEirActEthCos2 OBJECT-TYPE
   SYNTAX      INTEGER
               {
               unchanged (256)
               }
   MAX-ACCESS  read-write
   STATUS      current
   DESCRIPTION
      "Path: ethernet2.editConf.vlan.inboundBandwidth.action.eirAction.ethernet.cosDepth2

       Possibilities:
               unchanged   (256)"
   ::= {er1645v2Lan2FGUVlanEntry 133448192}

er1645v2Lan2FGUVlanInbBwActEirActEthDei2 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth2

       Possibilities:
               unchanged   (255)
               clear   (0)
               set   (1)"
   ::= {er1645v2Lan2FGUVlanEntry 133453312}

er1645v2Lan2FGUVlanInbBwActEirActEthCos3 OBJECT-TYPE
   SYNTAX      INTEGER
               {
               unchanged (256)
               }
   MAX-ACCESS  read-write
   STATUS      current
   DESCRIPTION
      "Path: ethernet2.editConf.vlan.inboundBandwidth.action.eirAction.ethernet.cosDepth3

       Possibilities:
               unchanged   (256)"
   ::= {er1645v2Lan2FGUVlanEntry 133448448}

er1645v2Lan2FGUVlanInbBwActEirActEthDei3 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth3

       Possibilities:
               unchanged   (255)
               clear   (0)
               set   (1)"
   ::= {er1645v2Lan2FGUVlanEntry 133453568}

er1645v2Lan2FGUVlanInbBwActEirActEthCos4 OBJECT-TYPE
   SYNTAX      INTEGER
               {
               unchanged (256)
               }
   MAX-ACCESS  read-write
   STATUS      current
   DESCRIPTION
      "Path: ethernet2.editConf.vlan.inboundBandwidth.action.eirAction.ethernet.cosDepth4

       Possibilities:
               unchanged   (256)"
   ::= {er1645v2Lan2FGUVlanEntry 133448704}

er1645v2Lan2FGUVlanInbBwActEirActEthDei4 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth4

       Possibilities:
               unchanged   (255)
               clear   (0)
               set   (1)"
   ::= {er1645v2Lan2FGUVlanEntry 133453824}

er1645v2Lan2FGUVlanInbBwActEirActEthCos5 OBJECT-TYPE
   SYNTAX      INTEGER
               {
               unchanged (256)
               }
   MAX-ACCESS  read-write
   STATUS      current
   DESCRIPTION
      "Path: ethernet2.editConf.vlan.inboundBandwidth.action.eirAction.ethernet.cosDepth5

       Possibilities:
               unchanged   (256)"
   ::= {er1645v2Lan2FGUVlanEntry 133448960}

er1645v2Lan2FGUVlanInbBwActEirActEthDei5 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth5

       Possibilities:
               unchanged   (255)
               clear   (0)
               set   (1)"
   ::= {er1645v2Lan2FGUVlanEntry 133454080}

er1645v2Lan2FGUVlanInbBwActEirActEthCos6 OBJECT-TYPE
   SYNTAX      INTEGER
               {
               unchanged (256)
               }
   MAX-ACCESS  read-write
   STATUS      current
   DESCRIPTION
      "Path: ethernet2.editConf.vlan.inboundBandwidth.action.eirAction.ethernet.cosDepth6

       Possibilities:
               unchanged   (256)"
   ::= {er1645v2Lan2FGUVlanEntry 133449216}

er1645v2Lan2FGUVlanInbBwActEirActEthDei6 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth6

       Possibilities:
               unchanged   (255)
               clear   (0)
               set   (1)"
   ::= {er1645v2Lan2FGUVlanEntry 133454336}

er1645v2Lan2FGUVlanInbBwActEirActEthCos7 OBJECT-TYPE
   SYNTAX      INTEGER
               {
               unchanged (256)
               }
   MAX-ACCESS  read-write
   STATUS      current
   DESCRIPTION
      "Path: ethernet2.editConf.vlan.inboundBandwidth.action.eirAction.ethernet.cosDepth7

       Possibilities:
               unchanged   (256)"
   ::= {er1645v2Lan2FGUVlanEntry 133449472}

er1645v2Lan2FGUVlanInbBwActEirActEthDei7 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth7

       Possibilities:
               unchanged   (255)
               clear   (0)
               set   (1)"
   ::= {er1645v2Lan2FGUVlanEntry 133454592}

er1645v2Lan2FGUVlanInbBwActEirActEthCos8 OBJECT-TYPE
   SYNTAX      INTEGER
               {
               unchanged (256)
               }
   MAX-ACCESS  read-write
   STATUS      current
   DESCRIPTION
      "Path: ethernet2.editConf.vlan.inboundBandwidth.action.eirAction.ethernet.cosDepth8

       Possibilities:
               unchanged   (256)"
   ::= {er1645v2Lan2FGUVlanEntry 133449728}

er1645v2Lan2FGUVlanInbBwActEirActEthDei8 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth8

       Possibilities:
               unchanged   (255)
               clear   (0)
               set   (1)"
   ::= {er1645v2Lan2FGUVlanEntry 133454848}

er1645v2Lan2FGUVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133449984}

er1645v2Lan2FGUVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133450240}

er1645v2Lan2FGUVlanInbBwActEirActEthDrpLev OBJECT-TYPE
   SYNTAX      INTEGER
               {
               unchanged (0)
               }
   MAX-ACCESS  read-write
   STATUS      current
   DESCRIPTION
      "Path: ethernet2.editConf.vlan.inboundBandwidth.action.eirAction.ethernet.dropLevel

       Possibilities:
               unchanged   (0)"
   ::= {er1645v2Lan2FGUVlanEntry 133450496}

er1645v2Lan2FGUVlanInbBwActEirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deFlag

       Possibilities:
               unchanged   (255)
               clear   (0)
               set   (1)"
   ::= {er1645v2Lan2FGUVlanEntry 133451264}

er1645v2Lan2FGUVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133474560}

er1645v2Lan2FGUVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133474816}

er1645v2Lan2FGUVlanInbBwActEirActIpDrpLev OBJECT-TYPE
   SYNTAX      INTEGER
               {
               unchanged (0)
               }
   MAX-ACCESS  read-write
   STATUS      current
   DESCRIPTION
      "Path: ethernet2.editConf.vlan.inboundBandwidth.action.eirAction.ip.dropLevel

       Possibilities:
               unchanged   (0)"
   ::= {er1645v2Lan2FGUVlanEntry 133475072}

er1645v2Lan2FGUVlanInbBwActEirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ip.deFlag

       Possibilities:
               unchanged   (255)
               clear   (0)
               set   (1)"
   ::= {er1645v2Lan2FGUVlanEntry 133475840}

er1645v2Lan2FGUVlanInbBwActViolActNone OBJECT-TYPE
   SYNTAX      OCTET STRING
   MAX-ACCESS  read-write
   STATUS      current
   DESCRIPTION
      "Path: ethernet2.editConf.vlan.inboundBandwidth.action.violateAction.none"
   ::= {er1645v2Lan2FGUVlanEntry 133570560}

er1645v2Lan2FGUVlanInbBwActViolActDrop OBJECT-TYPE
   SYNTAX      OCTET STRING
   MAX-ACCESS  read-write
   STATUS      current
   DESCRIPTION
      "Path: ethernet2.editConf.vlan.inboundBandwidth.action.violateAction.drop"
   ::= {er1645v2Lan2FGUVlanEntry 133586944}

er1645v2Lan2FGUVlanInbBwActViolActEthCos1 OBJECT-TYPE
   SYNTAX      INTEGER
               {
               unchanged (256)
               }
   MAX-ACCESS  read-write
   STATUS      current
   DESCRIPTION
      "Path: ethernet2.editConf.vlan.inboundBandwidth.action.violateAction.ethernet.cosDepth1

       Possibilities:
               unchanged   (256)"
   ::= {er1645v2Lan2FGUVlanEntry 133579008}

er1645v2Lan2FGUVlanInbBwActViolActEthDei1 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth1

       Possibilities:
               unchanged   (255)
               clear   (0)
               set   (1)"
   ::= {er1645v2Lan2FGUVlanEntry 133584128}

er1645v2Lan2FGUVlanInbBwActViolActEthCos2 OBJECT-TYPE
   SYNTAX      INTEGER
               {
               unchanged (256)
               }
   MAX-ACCESS  read-write
   STATUS      current
   DESCRIPTION
      "Path: ethernet2.editConf.vlan.inboundBandwidth.action.violateAction.ethernet.cosDepth2

       Possibilities:
               unchanged   (256)"
   ::= {er1645v2Lan2FGUVlanEntry 133579264}

er1645v2Lan2FGUVlanInbBwActViolActEthDei2 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth2

       Possibilities:
               unchanged   (255)
               clear   (0)
               set   (1)"
   ::= {er1645v2Lan2FGUVlanEntry 133584384}

er1645v2Lan2FGUVlanInbBwActViolActEthCos3 OBJECT-TYPE
   SYNTAX      INTEGER
               {
               unchanged (256)
               }
   MAX-ACCESS  read-write
   STATUS      current
   DESCRIPTION
      "Path: ethernet2.editConf.vlan.inboundBandwidth.action.violateAction.ethernet.cosDepth3

       Possibilities:
               unchanged   (256)"
   ::= {er1645v2Lan2FGUVlanEntry 133579520}

er1645v2Lan2FGUVlanInbBwActViolActEthDei3 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth3

       Possibilities:
               unchanged   (255)
               clear   (0)
               set   (1)"
   ::= {er1645v2Lan2FGUVlanEntry 133584640}

er1645v2Lan2FGUVlanInbBwActViolActEthCos4 OBJECT-TYPE
   SYNTAX      INTEGER
               {
               unchanged (256)
               }
   MAX-ACCESS  read-write
   STATUS      current
   DESCRIPTION
      "Path: ethernet2.editConf.vlan.inboundBandwidth.action.violateAction.ethernet.cosDepth4

       Possibilities:
               unchanged   (256)"
   ::= {er1645v2Lan2FGUVlanEntry 133579776}

er1645v2Lan2FGUVlanInbBwActViolActEthDei4 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth4

       Possibilities:
               unchanged   (255)
               clear   (0)
               set   (1)"
   ::= {er1645v2Lan2FGUVlanEntry 133584896}

er1645v2Lan2FGUVlanInbBwActViolActEthCos5 OBJECT-TYPE
   SYNTAX      INTEGER
               {
               unchanged (256)
               }
   MAX-ACCESS  read-write
   STATUS      current
   DESCRIPTION
      "Path: ethernet2.editConf.vlan.inboundBandwidth.action.violateAction.ethernet.cosDepth5

       Possibilities:
               unchanged   (256)"
   ::= {er1645v2Lan2FGUVlanEntry 133580032}

er1645v2Lan2FGUVlanInbBwActViolActEthDei5 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth5

       Possibilities:
               unchanged   (255)
               clear   (0)
               set   (1)"
   ::= {er1645v2Lan2FGUVlanEntry 133585152}

er1645v2Lan2FGUVlanInbBwActViolActEthCos6 OBJECT-TYPE
   SYNTAX      INTEGER
               {
               unchanged (256)
               }
   MAX-ACCESS  read-write
   STATUS      current
   DESCRIPTION
      "Path: ethernet2.editConf.vlan.inboundBandwidth.action.violateAction.ethernet.cosDepth6

       Possibilities:
               unchanged   (256)"
   ::= {er1645v2Lan2FGUVlanEntry 133580288}

er1645v2Lan2FGUVlanInbBwActViolActEthDei6 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth6

       Possibilities:
               unchanged   (255)
               clear   (0)
               set   (1)"
   ::= {er1645v2Lan2FGUVlanEntry 133585408}

er1645v2Lan2FGUVlanInbBwActViolActEthCos7 OBJECT-TYPE
   SYNTAX      INTEGER
               {
               unchanged (256)
               }
   MAX-ACCESS  read-write
   STATUS      current
   DESCRIPTION
      "Path: ethernet2.editConf.vlan.inboundBandwidth.action.violateAction.ethernet.cosDepth7

       Possibilities:
               unchanged   (256)"
   ::= {er1645v2Lan2FGUVlanEntry 133580544}

er1645v2Lan2FGUVlanInbBwActViolActEthDei7 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth7

       Possibilities:
               unchanged   (255)
               clear   (0)
               set   (1)"
   ::= {er1645v2Lan2FGUVlanEntry 133585664}

er1645v2Lan2FGUVlanInbBwActViolActEthCos8 OBJECT-TYPE
   SYNTAX      INTEGER
               {
               unchanged (256)
               }
   MAX-ACCESS  read-write
   STATUS      current
   DESCRIPTION
      "Path: ethernet2.editConf.vlan.inboundBandwidth.action.violateAction.ethernet.cosDepth8

       Possibilities:
               unchanged   (256)"
   ::= {er1645v2Lan2FGUVlanEntry 133580800}

er1645v2Lan2FGUVlanInbBwActViolActEthDei8 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth8

       Possibilities:
               unchanged   (255)
               clear   (0)
               set   (1)"
   ::= {er1645v2Lan2FGUVlanEntry 133585920}

er1645v2Lan2FGUVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133581056}

er1645v2Lan2FGUVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133581312}

er1645v2Lan2FGUVlanInbBwActViolActEthDrpLev OBJECT-TYPE
   SYNTAX      INTEGER
               {
               unchanged (0)
               }
   MAX-ACCESS  read-write
   STATUS      current
   DESCRIPTION
      "Path: ethernet2.editConf.vlan.inboundBandwidth.action.violateAction.ethernet.dropLevel

       Possibilities:
               unchanged   (0)"
   ::= {er1645v2Lan2FGUVlanEntry 133581568}

er1645v2Lan2FGUVlanInbBwActViolActEthDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deFlag

       Possibilities:
               unchanged   (255)
               clear   (0)
               set   (1)"
   ::= {er1645v2Lan2FGUVlanEntry 133582336}

er1645v2Lan2FGUVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanEntry 133605632}

er1645v2Lan2FGUVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanEntry 133605888}

er1645v2Lan2FGUVlanInbBwActViolActIpDrpLev OBJECT-TYPE
   SYNTAX      INTEGER
               {
               unchanged (0)
               }
   MAX-ACCESS  read-write
   STATUS      current
   DESCRIPTION
      "Path: ethernet2.editConf.vlan.inboundBandwidth.action.violateAction.ip.dropLevel

       Possibilities:
               unchanged   (0)"
   ::= {er1645v2Lan2FGUVlanEntry 133606144}

er1645v2Lan2FGUVlanInbBwActViolActIpDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ip.deFlag

       Possibilities:
               unchanged   (255)
               clear   (0)
               set   (1)"
   ::= {er1645v2Lan2FGUVlanEntry 133606912}

er1645v2Lan2FGUVlanPppoE OBJECT-TYPE
   SYNTAX      INTEGER
               {
               disabled (0),
               enabled (1)
               }
   MAX-ACCESS  read-write
   STATUS      current
   DESCRIPTION
      "Path: ethernet2.editConf.vlan.pppoE

       Possibilities:
               disabled   (0)
               enabled   (1)"
   ::= {er1645v2Lan2FGUVlanEntry 838860800}

er1645v2Lan2FGUVlanPppLnkMOperation OBJECT-TYPE
   SYNTAX      INTEGER
               {
               disabled (0),
               enabled (1)
               }
   MAX-ACCESS  read-write
   STATUS      current
   DESCRIPTION
      "Path: ethernet2.editConf.vlan.ppp.linkMonitoring.operation

       Possibilities:
               disabled   (0)
               enabled   (1)"
   ::= {er1645v2Lan2FGUVlanEntry 251724032}

er1645v2Lan2FGUVlanPppLnkMInterval OBJECT-TYPE
   SYNTAX      TimeTicks
   MAX-ACCESS  read-write
   STATUS      current
   DESCRIPTION
      "Path: ethernet2.editConf.vlan.ppp.linkMonitoring.interval

       Time in centi-second."
   ::= {er1645v2Lan2FGUVlanEntry 251724288}

er1645v2Lan2FGUVlanPppLnkMRepTimeOut OBJECT-TYPE
   SYNTAX      TimeTicks
   MAX-ACCESS  read-write
   STATUS      current
   DESCRIPTION
      "Path: ethernet2.editConf.vlan.ppp.linkMonitoring.replyTimeOut

       Time in centi-second."
   ::= {er1645v2Lan2FGUVlanEntry 251724544}

er1645v2Lan2FGUVlanPppLnkMFailsPrmt OBJECT-TYPE
   SYNTAX      Integer32
   MAX-ACCESS  read-write
   STATUS      current
   DESCRIPTION
      "Path: ethernet2.editConf.vlan.ppp.linkMonitoring.failsPermitted"
   ::= {er1645v2Lan2FGUVlanEntry 251724800}

er1645v2Lan2FGUVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.vlan.ppp.authentication

       Possibilities:
               disabled   (0)
               chap   (1)
               pap   (2)
               chapOrPap   (3)
               msChap   (4)
               msChapV2   (5)"
   ::= {er1645v2Lan2FGUVlanEntry 251789312}

er1645v2Lan2FGUVlanPppAuthenPeriod OBJECT-TYPE
   SYNTAX      TimeTicks
   MAX-ACCESS  read-write
   STATUS      current
   DESCRIPTION
      "Path: ethernet2.editConf.vlan.ppp.authenPeriod

       Time in centi-second."
   ::= {er1645v2Lan2FGUVlanEntry 251854848}

er1645v2Lan2FGUVlanPppSessionName OBJECT-TYPE
   SYNTAX      DisplayString
   MAX-ACCESS  read-write
   STATUS      current
   DESCRIPTION
      "Path: ethernet2.editConf.vlan.ppp.sessionName"
   ::= {er1645v2Lan2FGUVlanEntry 251985920}

er1645v2Lan2FGUVlanPppSessionSecret OBJECT-TYPE
   SYNTAX      DisplayString
   MAX-ACCESS  read-write
   STATUS      current
   DESCRIPTION
      "Path: ethernet2.editConf.vlan.ppp.sessionSecret"
   ::= {er1645v2Lan2FGUVlanEntry 252051456}

er1645v2Lan2FGUVlanPppEncModeSessionSecret OBJECT-TYPE
   SYNTAX      INTEGER
               {
               none (1),
               encrypt (2),
               encType1 (3),
               invalid (128)
               }
   MAX-ACCESS  read-write
   STATUS      current
   DESCRIPTION
      "Path: ethernet2.editConf.vlan.ppp.encModeSessionSecret

       Possibilities:
               none   (1)
               encrypt   (2)
               encType1   (3)
               invalid   (128)"
   ::= {er1645v2Lan2FGUVlanEntry 252182528}

er1645v2Lan2FGUVlanPppEncSessionSecret OBJECT-TYPE
   SYNTAX      DisplayString
   MAX-ACCESS  read-write
   STATUS      current
   DESCRIPTION
      "Path: ethernet2.editConf.vlan.ppp.encSessionSecret"
   ::= {er1645v2Lan2FGUVlanEntry 252248064}

er1645v2Lan2FGUVlanPppServiceName OBJECT-TYPE
   SYNTAX      DisplayString
   MAX-ACCESS  read-write
   STATUS      current
   DESCRIPTION
      "Path: ethernet2.editConf.vlan.ppp.serviceName"
   ::= {er1645v2Lan2FGUVlanEntry 252116992}

er1645v2Lan2FGUVlanPbbMode OBJECT-TYPE
   SYNTAX      INTEGER
               {
               disabled (0),
               static (1),
               dynamicPtp (2),
               dynamicPtmp (3)
               }
   MAX-ACCESS  read-write
   STATUS      current
   DESCRIPTION
      "Path: ethernet2.editConf.vlan.pbb.mode

       Possibilities:
               disabled   (0)
               static   (1)
               dynamicPtp   (2)
               dynamicPtmp   (3)"
   ::= {er1645v2Lan2FGUVlanEntry 1174667264}

er1645v2Lan2FGUVlanPbbTxCos OBJECT-TYPE
   SYNTAX      Integer32
   MAX-ACCESS  read-write
   STATUS      current
   DESCRIPTION
      "Path: ethernet2.editConf.vlan.pbb.txCos"
   ::= {er1645v2Lan2FGUVlanEntry 1175191552}

er1645v2Lan2FGUVlanPbbIsid OBJECT-TYPE
   SYNTAX      Integer32
   MAX-ACCESS  read-write
   STATUS      current
   DESCRIPTION
      "Path: ethernet2.editConf.vlan.pbb.isid"
   ::= {er1645v2Lan2FGUVlanEntry 1175453696}

er1645v2Lan2FGUVlanPbbDestMac OBJECT-TYPE
   SYNTAX      OCTET STRING
   MAX-ACCESS  read-write
   STATUS      current
   DESCRIPTION
      "Path: ethernet2.editConf.vlan.pbb.destMac

       MAC address."
   ::= {er1645v2Lan2FGUVlanEntry 1175715840}

er1645v2Lan2FGUVlanPbbCustomGroupMac OBJECT-TYPE
   SYNTAX      OCTET STRING
   MAX-ACCESS  read-write
   STATUS      current
   DESCRIPTION
      "Path: ethernet2.editConf.vlan.pbb.customGroupMac

       MAC address."
   ::= {er1645v2Lan2FGUVlanEntry 1175977984}

er1645v2Lan2FGUVlanIpSaddr OBJECT-TYPE
   SYNTAX      SEQUENCE OF Er1645v2Lan2FGUVlanIpSaddrEntry
   MAX-ACCESS  not-accessible
   STATUS      current
   DESCRIPTION
      ""
   ::= {er1645v2Lan2FGUVlan 51838976}

er1645v2Lan2FGUVlanIpSaddrEntry OBJECT-TYPE
   SYNTAX      Er1645v2Lan2FGUVlanIpSaddrEntry
   MAX-ACCESS  not-accessible
   STATUS      current
   DESCRIPTION
      ""
   INDEX      { er1645v2Lan2FGUVlanTableIx,
                er1645v2Lan2FGUVlanIpSaddrTableIx }
   ::= {er1645v2Lan2FGUVlanIpSaddr 1}

Er1645v2Lan2FGUVlanIpSaddrEntry ::=
   SEQUENCE
      {
      er1645v2Lan2FGUVlanIpSaddrActions
         VariableLengthTableActions,
      er1645v2Lan2FGUVlanIpSaddrTableIx
         TableIndex,
      er1645v2Lan2FGUVlanIpSaddrAddress
         IpAddress,
      er1645v2Lan2FGUVlanIpSaddrNetMask
         IpAddress
      }

er1645v2Lan2FGUVlanIpSaddrActions OBJECT-TYPE
   SYNTAX      VariableLengthTableActions
   MAX-ACCESS  read-write
   STATUS      current
   DESCRIPTION
      "By way of this field, some manipulations
       on this table may be performed."
   ::= {er1645v2Lan2FGUVlanIpSaddrEntry 2}

er1645v2Lan2FGUVlanIpSaddrTableIx OBJECT-TYPE
   SYNTAX      TableIndex
   MAX-ACCESS  not-accessible
   STATUS      current
   DESCRIPTION
      ""
   ::= {er1645v2Lan2FGUVlanIpSaddrEntry 11}

er1645v2Lan2FGUVlanIpSaddrAddress OBJECT-TYPE
   SYNTAX      IpAddress
   MAX-ACCESS  read-write
   STATUS      current
   DESCRIPTION
      "Path: ethernet2.editConf.vlan.ip.secondaryIp.address"
   ::= {er1645v2Lan2FGUVlanIpSaddrEntry 2030043136}

er1645v2Lan2FGUVlanIpSaddrNetMask OBJECT-TYPE
   SYNTAX      IpAddress
   MAX-ACCESS  read-write
   STATUS      current
   DESCRIPTION
      "Path: ethernet2.editConf.vlan.ip.secondaryIp.netMask"
   ::= {er1645v2Lan2FGUVlanIpSaddrEntry 2063597568}

er1645v2Lan2FGUVlanIpH OBJECT-TYPE
   SYNTAX      SEQUENCE OF Er1645v2Lan2FGUVlanIpHEntry
   MAX-ACCESS  not-accessible
   STATUS      current
   DESCRIPTION
      ""
   ::= {er1645v2Lan2FGUVlan 51314688}

er1645v2Lan2FGUVlanIpHEntry OBJECT-TYPE
   SYNTAX      Er1645v2Lan2FGUVlanIpHEntry
   MAX-ACCESS  not-accessible
   STATUS      current
   DESCRIPTION
      ""
   INDEX      { er1645v2Lan2FGUVlanTableIx,
                er1645v2Lan2FGUVlanIpHTableIx }
   ::= {er1645v2Lan2FGUVlanIpH 1}

Er1645v2Lan2FGUVlanIpHEntry ::=
   SEQUENCE
      {
      er1645v2Lan2FGUVlanIpHActions
         VariableLengthTableActions,
      er1645v2Lan2FGUVlanIpHTableIx
         TableIndex,
      er1645v2Lan2FGUVlanIpHAddress
         IpAddress,
      er1645v2Lan2FGUVlanIpHDhcpRelayOptionSubscriberId
         DisplayString
      }

er1645v2Lan2FGUVlanIpHActions OBJECT-TYPE
   SYNTAX      VariableLengthTableActions
   MAX-ACCESS  read-write
   STATUS      current
   DESCRIPTION
      "By way of this field, some manipulations
       on this table may be performed."
   ::= {er1645v2Lan2FGUVlanIpHEntry 2}

er1645v2Lan2FGUVlanIpHTableIx OBJECT-TYPE
   SYNTAX      TableIndex
   MAX-ACCESS  not-accessible
   STATUS      current
   DESCRIPTION
      ""
   ::= {er1645v2Lan2FGUVlanIpHEntry 11}

er1645v2Lan2FGUVlanIpHAddress OBJECT-TYPE
   SYNTAX      IpAddress
   MAX-ACCESS  read-write
   STATUS      current
   DESCRIPTION
      "Path: ethernet2.editConf.vlan.ip.helpers.address"
   ::= {er1645v2Lan2FGUVlanIpHEntry 16777216}

er1645v2Lan2FGUVlanIpHDhcpRelayOptionSubscriberId OBJECT-TYPE
   SYNTAX      DisplayString
   MAX-ACCESS  read-write
   STATUS      current
   DESCRIPTION
      "Path: ethernet2.editConf.vlan.ip.helpers.dhcpRelayOption.subscriberId"
   ::= {er1645v2Lan2FGUVlanIpHEntry 33947648}

er1645v2Lan2FGUVlanIpV6Addresses OBJECT-TYPE
   SYNTAX      SEQUENCE OF Er1645v2Lan2FGUVlanIpV6AddressesEntry
   MAX-ACCESS  not-accessible
   STATUS      current
   DESCRIPTION
      ""
   ::= {er1645v2Lan2FGUVlan 704839680}

er1645v2Lan2FGUVlanIpV6AddressesEntry OBJECT-TYPE
   SYNTAX      Er1645v2Lan2FGUVlanIpV6AddressesEntry
   MAX-ACCESS  not-accessible
   STATUS      current
   DESCRIPTION
      ""
   INDEX      { er1645v2Lan2FGUVlanTableIx,
                er1645v2Lan2FGUVlanIpV6AddressesTableIx }
   ::= {er1645v2Lan2FGUVlanIpV6Addresses 1}

Er1645v2Lan2FGUVlanIpV6AddressesEntry ::=
   SEQUENCE
      {
      er1645v2Lan2FGUVlanIpV6AddressesActions
         VariableLengthTableActions,
      er1645v2Lan2FGUVlanIpV6AddressesTableIx
         TableIndex,
      er1645v2Lan2FGUVlanIpV6AddressesType
         INTEGER,
      er1645v2Lan2FGUVlanIpV6AddressesAddress
         Ipv6Address,
      er1645v2Lan2FGUVlanIpV6AddressesPrefixLength
         Integer32,
      er1645v2Lan2FGUVlanIpV6AddressesGeneralPrefix
         DisplayString,
      er1645v2Lan2FGUVlanIpV6AddressesRaSend
         INTEGER,
      er1645v2Lan2FGUVlanIpV6AddressesRaOnLinkFlag
         INTEGER,
      er1645v2Lan2FGUVlanIpV6AddressesRaAutoFlag
         INTEGER,
      er1645v2Lan2FGUVlanIpV6AddressesRaValidLifeTime
         TimeTicks,
      er1645v2Lan2FGUVlanIpV6AddressesRaValidLTMode
         INTEGER,
      er1645v2Lan2FGUVlanIpV6AddressesRaPrefLifeTime
         TimeTicks,
      er1645v2Lan2FGUVlanIpV6AddressesRaPrefLTMode
         INTEGER
      }

er1645v2Lan2FGUVlanIpV6AddressesActions OBJECT-TYPE
   SYNTAX      VariableLengthTableActions
   MAX-ACCESS  read-write
   STATUS      current
   DESCRIPTION
      "By way of this field, some manipulations
       on this table may be performed."
   ::= {er1645v2Lan2FGUVlanIpV6AddressesEntry 2}

er1645v2Lan2FGUVlanIpV6AddressesTableIx OBJECT-TYPE
   SYNTAX      TableIndex
   MAX-ACCESS  not-accessible
   STATUS      current
   DESCRIPTION
      ""
   ::= {er1645v2Lan2FGUVlanIpV6AddressesEntry 11}

er1645v2Lan2FGUVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.vlan.ipV6.addresses.type

       Possibilities:
               unicast   (0)
               eui64   (1)
               anycast   (2)
               linkLocal   (3)
               generalPrefix   (4)"
   ::= {er1645v2Lan2FGUVlanIpV6AddressesEntry 50331648}

er1645v2Lan2FGUVlanIpV6AddressesAddress OBJECT-TYPE
   SYNTAX      Ipv6Address
   MAX-ACCESS  read-write
   STATUS      current
   DESCRIPTION
      "Path: ethernet2.editConf.vlan.ipV6.addresses.address

       ipv6 address"
   ::= {er1645v2Lan2FGUVlanIpV6AddressesEntry 16777216}

er1645v2Lan2FGUVlanIpV6AddressesPrefixLength OBJECT-TYPE
   SYNTAX      Integer32
   MAX-ACCESS  read-write
   STATUS      current
   DESCRIPTION
      "Path: ethernet2.editConf.vlan.ipV6.addresses.prefixLength"
   ::= {er1645v2Lan2FGUVlanIpV6AddressesEntry 33554432}

er1645v2Lan2FGUVlanIpV6AddressesGeneralPrefix OBJECT-TYPE
   SYNTAX      DisplayString
   MAX-ACCESS  read-write
   STATUS      current
   DESCRIPTION
      "Path: ethernet2.editConf.vlan.ipV6.addresses.generalPrefix"
   ::= {er1645v2Lan2FGUVlanIpV6AddressesEntry 83886080}

er1645v2Lan2FGUVlanIpV6AddressesRaSend OBJECT-TYPE
   SYNTAX      INTEGER
               {
               disabled (0),
               enabled (1)
               }
   MAX-ACCESS  read-write
   STATUS      current
   DESCRIPTION
      "Path: ethernet2.editConf.vlan.ipV6.addresses.ra.send

       Possibilities:
               disabled   (0)
               enabled   (1)"
   ::= {er1645v2Lan2FGUVlanIpV6AddressesEntry 67174400}

er1645v2Lan2FGUVlanIpV6AddressesRaOnLinkFlag OBJECT-TYPE
   SYNTAX      INTEGER
               {
               disabled (0),
               enabled (1)
               }
   MAX-ACCESS  read-write
   STATUS      current
   DESCRIPTION
      "Path: ethernet2.editConf.vlan.ipV6.addresses.ra.onLinkFlag

       Possibilities:
               disabled   (0)
               enabled   (1)"
   ::= {er1645v2Lan2FGUVlanIpV6AddressesEntry 67371008}

er1645v2Lan2FGUVlanIpV6AddressesRaAutoFlag OBJECT-TYPE
   SYNTAX      INTEGER
               {
               disabled (0),
               enabled (1)
               }
   MAX-ACCESS  read-write
   STATUS      current
   DESCRIPTION
      "Path: ethernet2.editConf.vlan.ipV6.addresses.ra.autonomousFlag

       Possibilities:
               disabled   (0)
               enabled   (1)"
   ::= {er1645v2Lan2FGUVlanIpV6AddressesEntry 67567616}

er1645v2Lan2FGUVlanIpV6AddressesRaValidLifeTime OBJECT-TYPE
   SYNTAX      TimeTicks
   MAX-ACCESS  read-write
   STATUS      current
   DESCRIPTION
      "Path: ethernet2.editConf.vlan.ipV6.addresses.ra.validLifeTime

       Time in centi-second."
   ::= {er1645v2Lan2FGUVlanIpV6AddressesEntry 67239936}

er1645v2Lan2FGUVlanIpV6AddressesRaValidLTMode OBJECT-TYPE
   SYNTAX      INTEGER
               {
               fixed (0),
               infinite (2)
               }
   MAX-ACCESS  read-write
   STATUS      current
   DESCRIPTION
      "Path: ethernet2.editConf.vlan.ipV6.addresses.ra.validLifeTimeMode

       Possibilities:
               fixed   (0)
               infinite   (2)"
   ::= {er1645v2Lan2FGUVlanIpV6AddressesEntry 67305472}

er1645v2Lan2FGUVlanIpV6AddressesRaPrefLifeTime OBJECT-TYPE
   SYNTAX      TimeTicks
   MAX-ACCESS  read-write
   STATUS      current
   DESCRIPTION
      "Path: ethernet2.editConf.vlan.ipV6.addresses.ra.prefLifeTime

       Time in centi-second."
   ::= {er1645v2Lan2FGUVlanIpV6AddressesEntry 67436544}

er1645v2Lan2FGUVlanIpV6AddressesRaPrefLTMode OBJECT-TYPE
   SYNTAX      INTEGER
               {
               fixed (0),
               infinite (2)
               }
   MAX-ACCESS  read-write
   STATUS      current
   DESCRIPTION
      "Path: ethernet2.editConf.vlan.ipV6.addresses.ra.prefLifeTimeMode

       Possibilities:
               fixed   (0)
               infinite   (2)"
   ::= {er1645v2Lan2FGUVlanIpV6AddressesEntry 67502080}

er1645v2Lan2FGUVlanIpV6RaDnsOptionsRdnssServers OBJECT-TYPE
   SYNTAX      SEQUENCE OF Er1645v2Lan2FGUVlanIpV6RaDnsOptionsRdnssServersEntry
   MAX-ACCESS  not-accessible
   STATUS      current
   DESCRIPTION
      ""
   ::= {er1645v2Lan2FGUVlan 705039144}

er1645v2Lan2FGUVlanIpV6RaDnsOptionsRdnssServersEntry OBJECT-TYPE
   SYNTAX      Er1645v2Lan2FGUVlanIpV6RaDnsOptionsRdnssServersEntry
   MAX-ACCESS  not-accessible
   STATUS      current
   DESCRIPTION
      ""
   INDEX      { er1645v2Lan2FGUVlanTableIx,
                er1645v2Lan2FGUVlanIpV6RaDnsOptionsRdnssServersTableIx }
   ::= {er1645v2Lan2FGUVlanIpV6RaDnsOptionsRdnssServers 1}

Er1645v2Lan2FGUVlanIpV6RaDnsOptionsRdnssServersEntry ::=
   SEQUENCE
      {
      er1645v2Lan2FGUVlanIpV6RaDnsOptionsRdnssServersActions
         VariableLengthTableActions,
      er1645v2Lan2FGUVlanIpV6RaDnsOptionsRdnssServersTableIx
         TableIndex,
      er1645v2Lan2FGUVlanIpV6RaDnsOptionsRdnssServersAddress
         Ipv6Address
      }

er1645v2Lan2FGUVlanIpV6RaDnsOptionsRdnssServersActions OBJECT-TYPE
   SYNTAX      VariableLengthTableActions
   MAX-ACCESS  read-write
   STATUS      current
   DESCRIPTION
      "By way of this field, some manipulations
       on this table may be performed."
   ::= {er1645v2Lan2FGUVlanIpV6RaDnsOptionsRdnssServersEntry 2}

er1645v2Lan2FGUVlanIpV6RaDnsOptionsRdnssServersTableIx OBJECT-TYPE
   SYNTAX      TableIndex
   MAX-ACCESS  not-accessible
   STATUS      current
   DESCRIPTION
      ""
   ::= {er1645v2Lan2FGUVlanIpV6RaDnsOptionsRdnssServersEntry 11}

er1645v2Lan2FGUVlanIpV6RaDnsOptionsRdnssServersAddress OBJECT-TYPE
   SYNTAX      Ipv6Address
   MAX-ACCESS  read-write
   STATUS      current
   DESCRIPTION
      "Path: ethernet2.editConf.vlan.ipV6.ra.dnsOptions.rdnss.servers.address

       ipv6 address"
   ::= {er1645v2Lan2FGUVlanIpV6RaDnsOptionsRdnssServersEntry 16777216}

er1645v2Lan2FGUVlanIpV6RaDnsOptionsDnsslDomains OBJECT-TYPE
   SYNTAX      SEQUENCE OF Er1645v2Lan2FGUVlanIpV6RaDnsOptionsDnsslDomainsEntry
   MAX-ACCESS  not-accessible
   STATUS      current
   DESCRIPTION
      ""
   ::= {er1645v2Lan2FGUVlan 705039176}

er1645v2Lan2FGUVlanIpV6RaDnsOptionsDnsslDomainsEntry OBJECT-TYPE
   SYNTAX      Er1645v2Lan2FGUVlanIpV6RaDnsOptionsDnsslDomainsEntry
   MAX-ACCESS  not-accessible
   STATUS      current
   DESCRIPTION
      ""
   INDEX      { er1645v2Lan2FGUVlanTableIx,
                er1645v2Lan2FGUVlanIpV6RaDnsOptionsDnsslDomainsTableIx }
   ::= {er1645v2Lan2FGUVlanIpV6RaDnsOptionsDnsslDomains 1}

Er1645v2Lan2FGUVlanIpV6RaDnsOptionsDnsslDomainsEntry ::=
   SEQUENCE
      {
      er1645v2Lan2FGUVlanIpV6RaDnsOptionsDnsslDomainsActions
         VariableLengthTableActions,
      er1645v2Lan2FGUVlanIpV6RaDnsOptionsDnsslDomainsTableIx
         TableIndex,
      er1645v2Lan2FGUVlanIpV6RaDnsOptionsDnsslDomainsName
         DisplayString
      }

er1645v2Lan2FGUVlanIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGUVlanIpV6RaDnsOptionsDnsslDomainsEntry 2}

er1645v2Lan2FGUVlanIpV6RaDnsOptionsDnsslDomainsTableIx OBJECT-TYPE
   SYNTAX      TableIndex
   MAX-ACCESS  not-accessible
   STATUS      current
   DESCRIPTION
      ""
   ::= {er1645v2Lan2FGUVlanIpV6RaDnsOptionsDnsslDomainsEntry 11}

er1645v2Lan2FGUVlanIpV6RaDnsOptionsDnsslDomainsName OBJECT-TYPE
   SYNTAX      DisplayString
   MAX-ACCESS  read-write
   STATUS      current
   DESCRIPTION
      "Path: ethernet2.editConf.vlan.ipV6.ra.dnsOptions.dnssl.domains.name"
   ::= {er1645v2Lan2FGUVlanIpV6RaDnsOptionsDnsslDomainsEntry 16777216}

er1645v2Lan2FGUVlanIpV6DhcpClientUserClassOpt OBJECT-TYPE
   SYNTAX      SEQUENCE OF Er1645v2Lan2FGUVlanIpV6DhcpClientUserClassOptEntry
   MAX-ACCESS  not-accessible
   STATUS      current
   DESCRIPTION
      ""
   ::= {er1645v2Lan2FGUVlan 705312768}

er1645v2Lan2FGUVlanIpV6DhcpClientUserClassOptEntry OBJECT-TYPE
   SYNTAX      Er1645v2Lan2FGUVlanIpV6DhcpClientUserClassOptEntry
   MAX-ACCESS  not-accessible
   STATUS      current
   DESCRIPTION
      ""
   INDEX      { er1645v2Lan2FGUVlanTableIx,
                er1645v2Lan2FGUVlanIpV6DhcpClientUserClassOptTableIx }
   ::= {er1645v2Lan2FGUVlanIpV6DhcpClientUserClassOpt 1}

Er1645v2Lan2FGUVlanIpV6DhcpClientUserClassOptEntry ::=
   SEQUENCE
      {
      er1645v2Lan2FGUVlanIpV6DhcpClientUserClassOptActions
         VariableLengthTableActions,
      er1645v2Lan2FGUVlanIpV6DhcpClientUserClassOptTableIx
         TableIndex,
      er1645v2Lan2FGUVlanIpV6DhcpClientUserClassOptValueAscii
         DisplayString,
      er1645v2Lan2FGUVlanIpV6DhcpClientUserClassOptValueDecimal
         Integer32,
      er1645v2Lan2FGUVlanIpV6DhcpClientUserClassOptValueHexData
         OCTET STRING
      }

er1645v2Lan2FGUVlanIpV6DhcpClientUserClassOptActions OBJECT-TYPE
   SYNTAX      VariableLengthTableActions
   MAX-ACCESS  read-write
   STATUS      current
   DESCRIPTION
      "By way of this field, some manipulations
       on this table may be performed."
   ::= {er1645v2Lan2FGUVlanIpV6DhcpClientUserClassOptEntry 2}

er1645v2Lan2FGUVlanIpV6DhcpClientUserClassOptTableIx OBJECT-TYPE
   SYNTAX      TableIndex
   MAX-ACCESS  not-accessible
   STATUS      current
   DESCRIPTION
      ""
   ::= {er1645v2Lan2FGUVlanIpV6DhcpClientUserClassOptEntry 11}

er1645v2Lan2FGUVlanIpV6DhcpClientUserClassOptValueAscii OBJECT-TYPE
   SYNTAX      DisplayString
   MAX-ACCESS  read-write
   STATUS      current
   DESCRIPTION
      "Path: ethernet2.editConf.vlan.ipV6.dhcp.client.userClassOpt.value.ascii"
   ::= {er1645v2Lan2FGUVlanIpV6DhcpClientUserClassOptEntry 16842752}

er1645v2Lan2FGUVlanIpV6DhcpClientUserClassOptValueDecimal OBJECT-TYPE
   SYNTAX      Integer32
   MAX-ACCESS  read-write
   STATUS      current
   DESCRIPTION
      "Path: ethernet2.editConf.vlan.ipV6.dhcp.client.userClassOpt.value.decimal"
   ::= {er1645v2Lan2FGUVlanIpV6DhcpClientUserClassOptEntry 16908288}

er1645v2Lan2FGUVlanIpV6DhcpClientUserClassOptValueHexData OBJECT-TYPE
   SYNTAX      OCTET STRING
   MAX-ACCESS  read-write
   STATUS      current
   DESCRIPTION
      "Path: ethernet2.editConf.vlan.ipV6.dhcp.client.userClassOpt.value.hexData"
   ::= {er1645v2Lan2FGUVlanIpV6DhcpClientUserClassOptEntry 16973824}

er1645v2Lan2FGUVlanIpV6DhcpClientVendorCl OBJECT-TYPE
   SYNTAX      SEQUENCE OF Er1645v2Lan2FGUVlanIpV6DhcpClientVendorClEntry
   MAX-ACCESS  not-accessible
   STATUS      current
   DESCRIPTION
      ""
   ::= {er1645v2Lan2FGUVlan 705313792}

er1645v2Lan2FGUVlanIpV6DhcpClientVendorClEntry OBJECT-TYPE
   SYNTAX      Er1645v2Lan2FGUVlanIpV6DhcpClientVendorClEntry
   MAX-ACCESS  not-accessible
   STATUS      current
   DESCRIPTION
      ""
   INDEX      { er1645v2Lan2FGUVlanTableIx,
                er1645v2Lan2FGUVlanIpV6DhcpClientVendorClTableIx }
   ::= {er1645v2Lan2FGUVlanIpV6DhcpClientVendorCl 1}

Er1645v2Lan2FGUVlanIpV6DhcpClientVendorClEntry ::=
   SEQUENCE
      {
      er1645v2Lan2FGUVlanIpV6DhcpClientVendorClActions
         VariableLengthTableActions,
      er1645v2Lan2FGUVlanIpV6DhcpClientVendorClTableIx
         TableIndex,
      er1645v2Lan2FGUVlanIpV6DhcpClientVendorClValueAscii
         DisplayString,
      er1645v2Lan2FGUVlanIpV6DhcpClientVendorClValueDecimal
         Integer32,
      er1645v2Lan2FGUVlanIpV6DhcpClientVendorClValueHexData
         OCTET STRING
      }

er1645v2Lan2FGUVlanIpV6DhcpClientVendorClActions OBJECT-TYPE
   SYNTAX      VariableLengthTableActions
   MAX-ACCESS  read-write
   STATUS      current
   DESCRIPTION
      "By way of this field, some manipulations
       on this table may be performed."
   ::= {er1645v2Lan2FGUVlanIpV6DhcpClientVendorClEntry 2}

er1645v2Lan2FGUVlanIpV6DhcpClientVendorClTableIx OBJECT-TYPE
   SYNTAX      TableIndex
   MAX-ACCESS  not-accessible
   STATUS      current
   DESCRIPTION
      ""
   ::= {er1645v2Lan2FGUVlanIpV6DhcpClientVendorClEntry 11}

er1645v2Lan2FGUVlanIpV6DhcpClientVendorClValueAscii OBJECT-TYPE
   SYNTAX      DisplayString
   MAX-ACCESS  read-write
   STATUS      current
   DESCRIPTION
      "Path: ethernet2.editConf.vlan.ipV6.dhcp.client.vendorClassOpt.value.ascii"
   ::= {er1645v2Lan2FGUVlanIpV6DhcpClientVendorClEntry 16842752}

er1645v2Lan2FGUVlanIpV6DhcpClientVendorClValueDecimal OBJECT-TYPE
   SYNTAX      Integer32
   MAX-ACCESS  read-write
   STATUS      current
   DESCRIPTION
      "Path: ethernet2.editConf.vlan.ipV6.dhcp.client.vendorClassOpt.value.decimal"
   ::= {er1645v2Lan2FGUVlanIpV6DhcpClientVendorClEntry 16908288}

er1645v2Lan2FGUVlanIpV6DhcpClientVendorClValueHexData OBJECT-TYPE
   SYNTAX      OCTET STRING
   MAX-ACCESS  read-write
   STATUS      current
   DESCRIPTION
      "Path: ethernet2.editConf.vlan.ipV6.dhcp.client.vendorClassOpt.value.hexData"
   ::= {er1645v2Lan2FGUVlanIpV6DhcpClientVendorClEntry 16973824}

er1645v2Lan2FGUVlanIpV6DhcpRelayDestinations OBJECT-TYPE
   SYNTAX      SEQUENCE OF Er1645v2Lan2FGUVlanIpV6DhcpRelayDestinationsEntry
   MAX-ACCESS  not-accessible
   STATUS      current
   DESCRIPTION
      ""
   ::= {er1645v2Lan2FGUVlan 705323072}

er1645v2Lan2FGUVlanIpV6DhcpRelayDestinationsEntry OBJECT-TYPE
   SYNTAX      Er1645v2Lan2FGUVlanIpV6DhcpRelayDestinationsEntry
   MAX-ACCESS  not-accessible
   STATUS      current
   DESCRIPTION
      ""
   INDEX      { er1645v2Lan2FGUVlanTableIx,
                er1645v2Lan2FGUVlanIpV6DhcpRelayDestinationsTableIx }
   ::= {er1645v2Lan2FGUVlanIpV6DhcpRelayDestinations 1}

Er1645v2Lan2FGUVlanIpV6DhcpRelayDestinationsEntry ::=
   SEQUENCE
      {
      er1645v2Lan2FGUVlanIpV6DhcpRelayDestinationsActions
         VariableLengthTableActions,
      er1645v2Lan2FGUVlanIpV6DhcpRelayDestinationsTableIx
         TableIndex,
      er1645v2Lan2FGUVlanIpV6DhcpRelayDestinationsAddress
         Ipv6Address,
      er1645v2Lan2FGUVlanIpV6DhcpRelayDestinationsInterface
         DisplayString
      }

er1645v2Lan2FGUVlanIpV6DhcpRelayDestinationsActions OBJECT-TYPE
   SYNTAX      VariableLengthTableActions
   MAX-ACCESS  read-write
   STATUS      current
   DESCRIPTION
      "By way of this field, some manipulations
       on this table may be performed."
   ::= {er1645v2Lan2FGUVlanIpV6DhcpRelayDestinationsEntry 2}

er1645v2Lan2FGUVlanIpV6DhcpRelayDestinationsTableIx OBJECT-TYPE
   SYNTAX      TableIndex
   MAX-ACCESS  not-accessible
   STATUS      current
   DESCRIPTION
      ""
   ::= {er1645v2Lan2FGUVlanIpV6DhcpRelayDestinationsEntry 11}

er1645v2Lan2FGUVlanIpV6DhcpRelayDestinationsAddress OBJECT-TYPE
   SYNTAX      Ipv6Address
   MAX-ACCESS  read-write
   STATUS      current
   DESCRIPTION
      "Path: ethernet2.editConf.vlan.ipV6.dhcp.relay.destinations.address

       ipv6 address"
   ::= {er1645v2Lan2FGUVlanIpV6DhcpRelayDestinationsEntry 16777216}

er1645v2Lan2FGUVlanIpV6DhcpRelayDestinationsInterface OBJECT-TYPE
   SYNTAX      DisplayString
   MAX-ACCESS  read-write
   STATUS      current
   DESCRIPTION
      "Path: ethernet2.editConf.vlan.ipV6.dhcp.relay.destinations.interface"
   ::= {er1645v2Lan2FGUVlanIpV6DhcpRelayDestinationsEntry 33554432}

er1645v2Lan2FGUVlanBridgingVlTVlans OBJECT-TYPE
   SYNTAX      SEQUENCE OF Er1645v2Lan2FGUVlanBridgingVlTVlansEntry
   MAX-ACCESS  not-accessible
   STATUS      current
   DESCRIPTION
      ""
   ::= {er1645v2Lan2FGUVlan 459079680}

er1645v2Lan2FGUVlanBridgingVlTVlansEntry OBJECT-TYPE
   SYNTAX      Er1645v2Lan2FGUVlanBridgingVlTVlansEntry
   MAX-ACCESS  not-accessible
   STATUS      current
   DESCRIPTION
      ""
   INDEX      { er1645v2Lan2FGUVlanTableIx,
                er1645v2Lan2FGUVlanBridgingVlTVlansTableIx }
   ::= {er1645v2Lan2FGUVlanBridgingVlTVlans 1}

Er1645v2Lan2FGUVlanBridgingVlTVlansEntry ::=
   SEQUENCE
      {
      er1645v2Lan2FGUVlanBridgingVlTVlansActions
         VariableLengthTableActions,
      er1645v2Lan2FGUVlanBridgingVlTVlansTableIx
         TableIndex,
      er1645v2Lan2FGUVlanBridgingVlTVlansVid
         Integer32,
      er1645v2Lan2FGUVlanBridgingVlTVlansEndVid
         Integer32,
      er1645v2Lan2FGUVlanBridgingVlTVlansAction
         INTEGER,
      er1645v2Lan2FGUVlanBridgingVlTVlansTagInfoTpid
         INTEGER,
      er1645v2Lan2FGUVlanBridgingVlTVlansTagInfoVid
         Integer32
      }

er1645v2Lan2FGUVlanBridgingVlTVlansActions OBJECT-TYPE
   SYNTAX      VariableLengthTableActions
   MAX-ACCESS  read-write
   STATUS      current
   DESCRIPTION
      "By way of this field, some manipulations
       on this table may be performed."
   ::= {er1645v2Lan2FGUVlanBridgingVlTVlansEntry 2}

er1645v2Lan2FGUVlanBridgingVlTVlansTableIx OBJECT-TYPE
   SYNTAX      TableIndex
   MAX-ACCESS  not-accessible
   STATUS      current
   DESCRIPTION
      ""
   ::= {er1645v2Lan2FGUVlanBridgingVlTVlansEntry 11}

er1645v2Lan2FGUVlanBridgingVlTVlansVid OBJECT-TYPE
   SYNTAX      Integer32
   MAX-ACCESS  read-write
   STATUS      current
   DESCRIPTION
      "Path: ethernet2.editConf.vlan.bridging.vlanTagging.vlans.vid"
   ::= {er1645v2Lan2FGUVlanBridgingVlTVlansEntry 536870912}

er1645v2Lan2FGUVlanBridgingVlTVlansEndVid OBJECT-TYPE
   SYNTAX      Integer32
   MAX-ACCESS  read-write
   STATUS      current
   DESCRIPTION
      "Path: ethernet2.editConf.vlan.bridging.vlanTagging.vlans.endVid"
   ::= {er1645v2Lan2FGUVlanBridgingVlTVlansEntry 2147483648}

er1645v2Lan2FGUVlanBridgingVlTVlansAction OBJECT-TYPE
   SYNTAX      INTEGER
               {
               discard (0),
               accept (1),
               tag (2)
               }
   MAX-ACCESS  read-write
   STATUS      current
   DESCRIPTION
      "Path: ethernet2.editConf.vlan.bridging.vlanTagging.vlans.action

       Possibilities:
               discard   (0)
               accept   (1)
               tag   (2)"
   ::= {er1645v2Lan2FGUVlanBridgingVlTVlansEntry 1073741824}

er1645v2Lan2FGUVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.vlans.tagInfo.tpid

       Possibilities:
               dot1Q   (33024)
               dot1ad   (34984)
               0x9100   (37120)
               0x9200   (37376)
               0x9300   (37632)"
   ::= {er1645v2Lan2FGUVlanBridgingVlTVlansEntry 1677721600}

er1645v2Lan2FGUVlanBridgingVlTVlansTagInfoVid OBJECT-TYPE
   SYNTAX      Integer32
   MAX-ACCESS  read-write
   STATUS      current
   DESCRIPTION
      "Path: ethernet2.editConf.vlan.bridging.vlanTagging.vlans.tagInfo.vid"
   ::= {er1645v2Lan2FGUVlanBridgingVlTVlansEntry 1744830464}

er1645v2Lan2FGUVlanVlanVidExtensionTable OBJECT-TYPE
   SYNTAX      SEQUENCE OF Er1645v2Lan2FGUVlanVlanVidExtensionTableEntry
   MAX-ACCESS  not-accessible
   STATUS      current
   DESCRIPTION
      ""
   ::= {er1645v2Lan2FGUVlan 235340544}

er1645v2Lan2FGUVlanVlanVidExtensionTableEntry OBJECT-TYPE
   SYNTAX      Er1645v2Lan2FGUVlanVlanVidExtensionTableEntry
   MAX-ACCESS  not-accessible
   STATUS      current
   DESCRIPTION
      ""
   INDEX      { er1645v2Lan2FGUVlanTableIx,
                er1645v2Lan2FGUVlanVlanVidExtensionTableTableIx }
   ::= {er1645v2Lan2FGUVlanVlanVidExtensionTable 1}

Er1645v2Lan2FGUVlanVlanVidExtensionTableEntry ::=
   SEQUENCE
      {
      er1645v2Lan2FGUVlanVlanVidExtensionTableActions
         VariableLengthTableActions,
      er1645v2Lan2FGUVlanVlanVidExtensionTableTableIx
         TableIndex,
      er1645v2Lan2FGUVlanVlanVidExtensionTableTpid
         INTEGER,
      er1645v2Lan2FGUVlanVlanVidExtensionTableVid
         Integer32,
      er1645v2Lan2FGUVlanVlanVidExtensionTableEndVid
         Integer32
      }

er1645v2Lan2FGUVlanVlanVidExtensionTableActions OBJECT-TYPE
   SYNTAX      VariableLengthTableActions
   MAX-ACCESS  read-write
   STATUS      current
   DESCRIPTION
      "By way of this field, some manipulations
       on this table may be performed."
   ::= {er1645v2Lan2FGUVlanVlanVidExtensionTableEntry 2}

er1645v2Lan2FGUVlanVlanVidExtensionTableTableIx OBJECT-TYPE
   SYNTAX      TableIndex
   MAX-ACCESS  not-accessible
   STATUS      current
   DESCRIPTION
      ""
   ::= {er1645v2Lan2FGUVlanVlanVidExtensionTableEntry 11}

er1645v2Lan2FGUVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.vidExtension.table.tpid

       Possibilities:
               dot1Q   (33024)
               dot1ad   (34984)
               0x9100   (37120)
               0x9200   (37376)
               0x9300   (37632)"
   ::= {er1645v2Lan2FGUVlanVlanVidExtensionTableEntry 16777216}

er1645v2Lan2FGUVlanVlanVidExtensionTableVid OBJECT-TYPE
   SYNTAX      Integer32
   MAX-ACCESS  read-write
   STATUS      current
   DESCRIPTION
      "Path: ethernet2.editConf.vlan.vlan.vidExtension.table.vid"
   ::= {er1645v2Lan2FGUVlanVlanVidExtensionTableEntry 33554432}

er1645v2Lan2FGUVlanVlanVidExtensionTableEndVid OBJECT-TYPE
   SYNTAX      Integer32
   MAX-ACCESS  read-write
   STATUS      current
   DESCRIPTION
      "Path: ethernet2.editConf.vlan.vlan.vidExtension.table.endVid"
   ::= {er1645v2Lan2FGUVlanVlanVidExtensionTableEntry 50331648}

er1645v2Lan2FGUVlanVlanCSMap OBJECT-TYPE
   SYNTAX      SEQUENCE OF Er1645v2Lan2FGUVlanVlanCSMapEntry
   MAX-ACCESS  not-accessible
   STATUS      current
   DESCRIPTION
      ""
   ::= {er1645v2Lan2FGUVlan 235405312}

er1645v2Lan2FGUVlanVlanCSMapEntry OBJECT-TYPE
   SYNTAX      Er1645v2Lan2FGUVlanVlanCSMapEntry
   MAX-ACCESS  not-accessible
   STATUS      current
   DESCRIPTION
      ""
   INDEX      { er1645v2Lan2FGUVlanTableIx,
                er1645v2Lan2FGUVlanVlanCSMapTableIx }
   ::= {er1645v2Lan2FGUVlanVlanCSMap 1}

Er1645v2Lan2FGUVlanVlanCSMapEntry ::=
   SEQUENCE
      {
      er1645v2Lan2FGUVlanVlanCSMapActions
         VariableLengthTableActions,
      er1645v2Lan2FGUVlanVlanCSMapTableIx
         TableIndex,
      er1645v2Lan2FGUVlanVlanCSMapCos
         INTEGER,
      er1645v2Lan2FGUVlanVlanCSMapDei
         INTEGER,
      er1645v2Lan2FGUVlanVlanCSMapTos
         INTEGER,
      er1645v2Lan2FGUVlanVlanCSMapQueue
         INTEGER,
      er1645v2Lan2FGUVlanVlanCSMapDropLevel
         INTEGER,
      er1645v2Lan2FGUVlanVlanCSMapDeFlag
         INTEGER
      }

er1645v2Lan2FGUVlanVlanCSMapActions OBJECT-TYPE
   SYNTAX      VariableLengthTableActions
   MAX-ACCESS  read-write
   STATUS      current
   DESCRIPTION
      "By way of this field, some manipulations
       on this table may be performed."
   ::= {er1645v2Lan2FGUVlanVlanCSMapEntry 2}

er1645v2Lan2FGUVlanVlanCSMapTableIx OBJECT-TYPE
   SYNTAX      TableIndex
   MAX-ACCESS  not-accessible
   STATUS      current
   DESCRIPTION
      ""
   ::= {er1645v2Lan2FGUVlanVlanCSMapEntry 11}

er1645v2Lan2FGUVlanVlanCSMapCos OBJECT-TYPE
   SYNTAX      INTEGER
               {
               any (8)
               }
   MAX-ACCESS  read-write
   STATUS      current
   DESCRIPTION
      "Path: ethernet2.editConf.vlan.vlan.cosMap.cos

       Possibilities:
               any   (8)"
   ::= {er1645v2Lan2FGUVlanVlanCSMapEntry 16777216}

er1645v2Lan2FGUVlanVlanCSMapDei OBJECT-TYPE
   SYNTAX      INTEGER
               {
               clear (0),
               set (1),
               any (2)
               }
   MAX-ACCESS  read-write
   STATUS      current
   DESCRIPTION
      "Path: ethernet2.editConf.vlan.vlan.cosMap.dei

       Possibilities:
               clear   (0)
               set   (1)
               any   (2)"
   ::= {er1645v2Lan2FGUVlanVlanCSMapEntry 33554432}

er1645v2Lan2FGUVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGUVlanVlanCSMapEntry 50331648}

er1645v2Lan2FGUVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGUVlanVlanCSMapEntry 67108864}

er1645v2Lan2FGUVlanVlanCSMapDropLevel OBJECT-TYPE
   SYNTAX      INTEGER
               {
               unchanged (-1),
               dropOnQueue (0)
               }
   MAX-ACCESS  read-write
   STATUS      current
   DESCRIPTION
      "Path: ethernet2.editConf.vlan.vlan.cosMap.dropLevel

       Possibilities:
               unchanged   (-1)
               dropOnQueue   (0)"
   ::= {er1645v2Lan2FGUVlanVlanCSMapEntry 83886080}

er1645v2Lan2FGUVlanVlanCSMapDeFlag OBJECT-TYPE
   SYNTAX      INTEGER
               {
               unchanged (255),
               clear (0),
               set (1)
               }
   MAX-ACCESS  read-write
   STATUS      current
   DESCRIPTION
      "Path: ethernet2.editConf.vlan.vlan.cosMap.deFlag

       Possibilities:
               unchanged   (255)
               clear   (0)
               set   (1)"
   ::= {er1645v2Lan2FGUVlanVlanCSMapEntry 117440512}

er1645v2Lan2FGUVlanVlanTCMap OBJECT-TYPE
   SYNTAX      SEQUENCE OF Er1645v2Lan2FGUVlanVlanTCMapEntry
   MAX-ACCESS  not-accessible
   STATUS      current
   DESCRIPTION
      ""
   ::= {er1645v2Lan2FGUVlan 241369088}

er1645v2Lan2FGUVlanVlanTCMapEntry OBJECT-TYPE
   SYNTAX      Er1645v2Lan2FGUVlanVlanTCMapEntry
   MAX-ACCESS  not-accessible
   STATUS      current
   DESCRIPTION
      ""
   INDEX      { er1645v2Lan2FGUVlanTableIx,
                er1645v2Lan2FGUVlanVlanTCMapTableIx }
   ::= {er1645v2Lan2FGUVlanVlanTCMap 1}

Er1645v2Lan2FGUVlanVlanTCMapEntry ::=
   SEQUENCE
      {
      er1645v2Lan2FGUVlanVlanTCMapActions
         VariableLengthTableActions,
      er1645v2Lan2FGUVlanVlanTCMapTableIx
         TableIndex,
      er1645v2Lan2FGUVlanVlanTCMapStartTos
         INTEGER,
      er1645v2Lan2FGUVlanVlanTCMapEndTos
         INTEGER,
      er1645v2Lan2FGUVlanVlanTCMapCos
         INTEGER
      }

er1645v2Lan2FGUVlanVlanTCMapActions OBJECT-TYPE
   SYNTAX      VariableLengthTableActions
   MAX-ACCESS  read-write
   STATUS      current
   DESCRIPTION
      "By way of this field, some manipulations
       on this table may be performed."
   ::= {er1645v2Lan2FGUVlanVlanTCMapEntry 2}

er1645v2Lan2FGUVlanVlanTCMapTableIx OBJECT-TYPE
   SYNTAX      TableIndex
   MAX-ACCESS  not-accessible
   STATUS      current
   DESCRIPTION
      ""
   ::= {er1645v2Lan2FGUVlanVlanTCMapEntry 11}

er1645v2Lan2FGUVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2FGUVlanVlanTCMapEntry 16777216}

er1645v2Lan2FGUVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2FGUVlanVlanTCMapEntry 33554432}

er1645v2Lan2FGUVlanVlanTCMapCos OBJECT-TYPE
   SYNTAX      INTEGER
               {
               queueCosMap (8)
               }
   MAX-ACCESS  read-write
   STATUS      current
   DESCRIPTION
      "Path: ethernet2.editConf.vlan.vlan.tosCosMap.cos

       Possibilities:
               queueCosMap   (8)"
   ::= {er1645v2Lan2FGUVlanVlanTCMapEntry 50331648}

er1645v2Lan2FGUVlanVlanArpStaticArp OBJECT-TYPE
   SYNTAX      SEQUENCE OF Er1645v2Lan2FGUVlanVlanArpStaticArpEntry
   MAX-ACCESS  not-accessible
   STATUS      current
   DESCRIPTION
      ""
   ::= {er1645v2Lan2FGUVlan 235275008}

er1645v2Lan2FGUVlanVlanArpStaticArpEntry OBJECT-TYPE
   SYNTAX      Er1645v2Lan2FGUVlanVlanArpStaticArpEntry
   MAX-ACCESS  not-accessible
   STATUS      current
   DESCRIPTION
      ""
   INDEX      { er1645v2Lan2FGUVlanTableIx,
                er1645v2Lan2FGUVlanVlanArpStaticArpTableIx }
   ::= {er1645v2Lan2FGUVlanVlanArpStaticArp 1}

Er1645v2Lan2FGUVlanVlanArpStaticArpEntry ::=
   SEQUENCE
      {
      er1645v2Lan2FGUVlanVlanArpStaticArpActions
         VariableLengthTableActions,
      er1645v2Lan2FGUVlanVlanArpStaticArpTableIx
         TableIndex,
      er1645v2Lan2FGUVlanVlanArpStaticArpMacAddress
         OCTET STRING,
      er1645v2Lan2FGUVlanVlanArpStaticArpIpAddress
         IpAddress
      }

er1645v2Lan2FGUVlanVlanArpStaticArpActions OBJECT-TYPE
   SYNTAX      VariableLengthTableActions
   MAX-ACCESS  read-write
   STATUS      current
   DESCRIPTION
      "By way of this field, some manipulations
       on this table may be performed."
   ::= {er1645v2Lan2FGUVlanVlanArpStaticArpEntry 2}

er1645v2Lan2FGUVlanVlanArpStaticArpTableIx OBJECT-TYPE
   SYNTAX      TableIndex
   MAX-ACCESS  not-accessible
   STATUS      current
   DESCRIPTION
      ""
   ::= {er1645v2Lan2FGUVlanVlanArpStaticArpEntry 11}

er1645v2Lan2FGUVlanVlanArpStaticArpMacAddress OBJECT-TYPE
   SYNTAX      OCTET STRING
   MAX-ACCESS  read-write
   STATUS      current
   DESCRIPTION
      "Path: ethernet2.editConf.vlan.vlan.arp.staticArp.macAddress

       MAC address."
   ::= {er1645v2Lan2FGUVlanVlanArpStaticArpEntry 16777216}

er1645v2Lan2FGUVlanVlanArpStaticArpIpAddress OBJECT-TYPE
   SYNTAX      IpAddress
   MAX-ACCESS  read-write
   STATUS      current
   DESCRIPTION
      "Path: ethernet2.editConf.vlan.vlan.arp.staticArp.ipAddress"
   ::= {er1645v2Lan2FGUVlanVlanArpStaticArpEntry 33554432}


er1645v2Lan2FGUPppOE OBJECT IDENTIFIER ::= {er1645v2Lan2FGU 35}

er1645v2Lan2FGUPppOESSCTable OBJECT-TYPE
   SYNTAX      SEQUENCE OF Er1645v2Lan2FGUPppOEEntry
   MAX-ACCESS  not-accessible
   STATUS      current
   DESCRIPTION
      ""
   ::= {er1645v2Lan2FGUPppOE 1}

er1645v2Lan2FGUPppOEEntry OBJECT-TYPE
   SYNTAX      Er1645v2Lan2FGUPppOEEntry
   MAX-ACCESS  not-accessible
   STATUS      current
   DESCRIPTION
      ""
   INDEX      { er1645v2Lan2FGUPppOETableIx }
   ::= {er1645v2Lan2FGUPppOESSCTable 1}

Er1645v2Lan2FGUPppOEEntry ::=
   SEQUENCE
      {
      er1645v2Lan2FGUPppOEActions
         VariableLengthTableActions,
      er1645v2Lan2FGUPppOETableIx
         TableIndex,
      er1645v2Lan2FGUPppOEName
         DisplayString,
      er1645v2Lan2FGUPppOERemark
         DisplayString,
      er1645v2Lan2FGUPppOEAdminStatus
         INTEGER,
      er1645v2Lan2FGUPppOEMode
         INTEGER,
      er1645v2Lan2FGUPppOEIpVrfRouter
         DisplayString,
      er1645v2Lan2FGUPppOEIpAdr
         IpAddress,
      er1645v2Lan2FGUPppOEIpNetm
         IpAddress,
      er1645v2Lan2FGUPppOEIpSNetName
         INTEGER,
      er1645v2Lan2FGUPppOEIpSNetCust
         DisplayString,
      er1645v2Lan2FGUPppOEIpRem
         IpAddress,
      er1645v2Lan2FGUPppOEIpUnnumbered
         DisplayString,
      er1645v2Lan2FGUPppOEIpGwPref
         Integer32,
      er1645v2Lan2FGUPppOEIpRsn
         INTEGER,
      er1645v2Lan2FGUPppOEIpMtu
         Integer32,
      er1645v2Lan2FGUPppOEIpMssAdjust
         INTEGER,
      er1645v2Lan2FGUPppOEIpRipMetric
         Integer32,
      er1645v2Lan2FGUPppOEIpRipMetricOut
         Integer32,
      er1645v2Lan2FGUPppOEIpRipMode
         INTEGER,
      er1645v2Lan2FGUPppOEIpRipTxVer
         INTEGER,
      er1645v2Lan2FGUPppOEIpRipRxVer
         INTEGER,
      er1645v2Lan2FGUPppOEIpRipSplitH
         INTEGER,
      er1645v2Lan2FGUPppOEIpRipAuth
         INTEGER,
      er1645v2Lan2FGUPppOEIpRipFilter
         DisplayString,
      er1645v2Lan2FGUPppOEIpRipFilterIn
         DisplayString,
      er1645v2Lan2FGUPppOEIpRipClearNextHop
         INTEGER,
      er1645v2Lan2FGUPppOEIpAccPol
         DisplayString,
      er1645v2Lan2FGUPppOEIpAB
         DisplayString,
      er1645v2Lan2FGUPppOEIpMA
         INTEGER,
      er1645v2Lan2FGUPppOEIpMF
         Integer32,
      er1645v2Lan2FGUPppOEIpDB
         INTEGER,
      er1645v2Lan2FGUPppOEIpIR
         INTEGER,
      er1645v2Lan2FGUPppOEIpIgmp
         INTEGER,
      er1645v2Lan2FGUPppOEIpNN
         DisplayString,
      er1645v2Lan2FGUPppOEIpPimMode
         INTEGER,
      er1645v2Lan2FGUPppOEIpPimDrPriority
         Counter32,
      er1645v2Lan2FGUPppOEIpPimHelloTime
         TimeTicks,
      er1645v2Lan2FGUPppOEIpPimPropagationDelay
         TimeTicks,
      er1645v2Lan2FGUPppOEIpPimOverrideInterval
         TimeTicks,
      er1645v2Lan2FGUPppOEIpPimBsrBorder
         INTEGER,
      er1645v2Lan2FGUPppOEIpPimTtlThreshold
         Integer32,
      er1645v2Lan2FGUPppOEIpIMNetworkUnreachable
         INTEGER,
      er1645v2Lan2FGUPppOEIpIMHostUnreachable
         INTEGER,
      er1645v2Lan2FGUPppOEIpIMProtocolUnreachable
         INTEGER,
      er1645v2Lan2FGUPppOEIpIMPortUnreachable
         INTEGER,
      er1645v2Lan2FGUPppOEIpIMMtuExceeded
         INTEGER,
      er1645v2Lan2FGUPppOEIpIMAdminProhibited
         INTEGER,
      er1645v2Lan2FGUPppOEIpIMTtlExceeded
         INTEGER,
      er1645v2Lan2FGUPppOEIpIMRedirect
         INTEGER,
      er1645v2Lan2FGUPppOEIpV6VrfRouter
         DisplayString,
      er1645v2Lan2FGUPppOEIpV6AddrAutoConfigNrDupAddrDetects
         Integer32,
      er1645v2Lan2FGUPppOEIpV6AddrAutoConfigAcceptRa
         INTEGER,
      er1645v2Lan2FGUPppOEIpV6AddrAutoConfigAcceptRaRdnss
         INTEGER,
      er1645v2Lan2FGUPppOEIpV6AddrAutoConfigAcceptRaDnssl
         INTEGER,
      er1645v2Lan2FGUPppOEIpV6DefaultRoute
         INTEGER,
      er1645v2Lan2FGUPppOEIpV6RaSend
         INTEGER,
      er1645v2Lan2FGUPppOEIpV6RaMinInterval
         TimeTicks,
      er1645v2Lan2FGUPppOEIpV6RaMaxInterval
         TimeTicks,
      er1645v2Lan2FGUPppOEIpV6RaManagedFlag
         INTEGER,
      er1645v2Lan2FGUPppOEIpV6RaOtherConfFlag
         INTEGER,
      er1645v2Lan2FGUPppOEIpV6RaLinkMtu
         Integer32,
      er1645v2Lan2FGUPppOEIpV6RaReachableTime
         TimeTicks,
      er1645v2Lan2FGUPppOEIpV6RaRetransmitTime
         TimeTicks,
      er1645v2Lan2FGUPppOEIpV6RaHopLimit
         Integer32,
      er1645v2Lan2FGUPppOEIpV6RaDefaultLifeTime
         TimeTicks,
      er1645v2Lan2FGUPppOEIpV6RaDnsOptionsRdnssLifeTime
         TimeTicks,
      er1645v2Lan2FGUPppOEIpV6RaDnsOptionsRdnssImportServers
         INTEGER,
      er1645v2Lan2FGUPppOEIpV6RaDnsOptionsDnsslLifeTime
         TimeTicks,
      er1645v2Lan2FGUPppOEIpV6RaDnsOptionsDnsslImportDomains
         INTEGER,
      er1645v2Lan2FGUPppOEIpV6RsSend
         INTEGER,
      er1645v2Lan2FGUPppOEIpV6RsMaxRandomDelay
         TimeTicks,
      er1645v2Lan2FGUPppOEIpV6RsInterval
         TimeTicks,
      er1645v2Lan2FGUPppOEIpV6RsMaxSolicitations
         Integer32,
      er1645v2Lan2FGUPppOEIpV6TrafficPolicyInbound
         DisplayString,
      er1645v2Lan2FGUPppOEIpV6TrafficPolicyOutbound
         DisplayString,
      er1645v2Lan2FGUPppOEIpV6FirewallZone
         DisplayString,
      er1645v2Lan2FGUPppOEIpV6DhcpClientAddrAC
         INTEGER,
      er1645v2Lan2FGUPppOEIpV6DhcpClientPrDelMode
         INTEGER,
      er1645v2Lan2FGUPppOEIpV6DhcpClientPrDelPool
         DisplayString,
      er1645v2Lan2FGUPppOEIpV6DhcpClientPrDelPdExclOpt
         INTEGER,
      er1645v2Lan2FGUPppOEIpV6DhcpClientDnsServerPref
         Integer32,
      er1645v2Lan2FGUPppOEIpV6DhcpClientRapidCommit
         INTEGER,
      er1645v2Lan2FGUPppOEIpV6DhcpClientTimersSolTimeOut
         TimeTicks,
      er1645v2Lan2FGUPppOEIpV6DhcpClientTimersSolMaxRt
         TimeTicks,
      er1645v2Lan2FGUPppOEIpV6DhcpClientTimersInfoRefresh
         TimeTicks,
      er1645v2Lan2FGUPppOEIpV6DhcpServerMode
         INTEGER,
      er1645v2Lan2FGUPppOEIpV6DhcpServerPreference
         Integer32,
      er1645v2Lan2FGUPppOEIpV6DhcpServerPool
         DisplayString,
      er1645v2Lan2FGUPppOEIpV6DhcpServerRapidCommit
         INTEGER,
      er1645v2Lan2FGUPppOEIpV6DhcpServerTimersInfoRefresh
         TimeTicks,
      er1645v2Lan2FGUPppOEIpV6DhcpRelayMode
         INTEGER,
      er1645v2Lan2FGUPppOEIpV6SendRedirect
         INTEGER,
      er1645v2Lan2FGUPppOEIpV6LinkMtu
         Integer32,
      er1645v2Lan2FGUPppOEIpV6InterfaceId
         OCTET STRING,
      er1645v2Lan2FGUPppOEIpV6MF
         Integer32,
      er1645v2Lan2FGUPppOEIpV6IcmpMessagesNoRoute
         INTEGER,
      er1645v2Lan2FGUPppOEIpV6IcmpMessagesBeyondScope
         INTEGER,
      er1645v2Lan2FGUPppOEIpV6IcmpMessagesAddressUnreachable
         INTEGER,
      er1645v2Lan2FGUPppOEIpV6IcmpMessagesPortUnreachable
         INTEGER,
      er1645v2Lan2FGUPppOEIpV6IcmpMessagesPacketTooBig
         INTEGER,
      er1645v2Lan2FGUPppOEIpV6IcmpMessagesHopLimitExceeded
         INTEGER,
      er1645v2Lan2FGUPppOEIpV6IcmpMessagesFragTimeExceeded
         INTEGER,
      er1645v2Lan2FGUPppOEIpV6IcmpMessagesHeaderFieldErr
         INTEGER,
      er1645v2Lan2FGUPppOEIpV6IcmpMessagesOptionUnrecognized
         INTEGER,
      er1645v2Lan2FGUPppOEIpV6IcmpMessagesRedirect
         INTEGER,
      er1645v2Lan2FGUPppOEPppLnkMOperation
         INTEGER,
      er1645v2Lan2FGUPppOEPppLnkMInterval
         TimeTicks,
      er1645v2Lan2FGUPppOEPppLnkMRepTimeOut
         TimeTicks,
      er1645v2Lan2FGUPppOEPppLnkMFailsPrmt
         Integer32,
      er1645v2Lan2FGUPppOEPppAuthentication
         INTEGER,
      er1645v2Lan2FGUPppOEPppAuthenPeriod
         TimeTicks,
      er1645v2Lan2FGUPppOEPppSessionName
         DisplayString,
      er1645v2Lan2FGUPppOEPppSessionSecret
         DisplayString,
      er1645v2Lan2FGUPppOEPppEncModeSessionSecret
         INTEGER,
      er1645v2Lan2FGUPppOEPppEncSessionSecret
         DisplayString,
      er1645v2Lan2FGUPppOEPppServiceName
         DisplayString
      }

er1645v2Lan2FGUPppOEActions OBJECT-TYPE
   SYNTAX      VariableLengthTableActions
   MAX-ACCESS  read-write
   STATUS      current
   DESCRIPTION
      "By way of this field, some manipulations
       on this table may be performed."
   ::= {er1645v2Lan2FGUPppOEEntry 2}

er1645v2Lan2FGUPppOETableIx OBJECT-TYPE
   SYNTAX      TableIndex
   MAX-ACCESS  not-accessible
   STATUS      current
   DESCRIPTION
      ""
   ::= {er1645v2Lan2FGUPppOEEntry 11}

er1645v2Lan2FGUPppOEName OBJECT-TYPE
   SYNTAX      DisplayString
   MAX-ACCESS  read-write
   STATUS      current
   DESCRIPTION
      "Path: ethernet2.editConf.pppoEClient.name"
   ::= {er1645v2Lan2FGUPppOEEntry 16777216}

er1645v2Lan2FGUPppOERemark OBJECT-TYPE
   SYNTAX      DisplayString
   MAX-ACCESS  read-write
   STATUS      current
   DESCRIPTION
      "Path: ethernet2.editConf.pppoEClient.remark"
   ::= {er1645v2Lan2FGUPppOEEntry 1157627904}

er1645v2Lan2FGUPppOEAdminStatus OBJECT-TYPE
   SYNTAX      INTEGER
               {
               up (1),
               down (2)
               }
   MAX-ACCESS  read-write
   STATUS      current
   DESCRIPTION
      "Path: ethernet2.editConf.pppoEClient.adminStatus

       Possibilities:
               up   (1)
               down   (2)"
   ::= {er1645v2Lan2FGUPppOEEntry 33554432}

er1645v2Lan2FGUPppOEMode OBJECT-TYPE
   SYNTAX      INTEGER
               {
               routing (1),
               multilink (8),
               ipV6 (16),
               ipV6ipV4 (17)
               }
   MAX-ACCESS  read-write
   STATUS      current
   DESCRIPTION
      "Path: ethernet2.editConf.pppoEClient.mode

       Possibilities:
               routing   (1)
               multilink   (8)
               ipV6   (16)
               ipV6/ipV4   (17)"
   ::= {er1645v2Lan2FGUPppOEEntry 67108864}

er1645v2Lan2FGUPppOEIpVrfRouter OBJECT-TYPE
   SYNTAX      DisplayString
   MAX-ACCESS  read-write
   STATUS      current
   DESCRIPTION
      "Path: ethernet2.editConf.pppoEClient.ip.vrfRouter"
   ::= {er1645v2Lan2FGUPppOEEntry 53215232}

er1645v2Lan2FGUPppOEIpAdr OBJECT-TYPE
   SYNTAX      IpAddress
   MAX-ACCESS  read-write
   STATUS      current
   DESCRIPTION
      "Path: ethernet2.editConf.pppoEClient.ip.address"
   ::= {er1645v2Lan2FGUPppOEEntry 58261504}

er1645v2Lan2FGUPppOEIpNetm OBJECT-TYPE
   SYNTAX      IpAddress
   MAX-ACCESS  read-write
   STATUS      current
   DESCRIPTION
      "Path: ethernet2.editConf.pppoEClient.ip.netMask"
   ::= {er1645v2Lan2FGUPppOEEntry 58392576}

er1645v2Lan2FGUPppOEIpSNetName OBJECT-TYPE
   SYNTAX      INTEGER
               {
               slOPTg (0),
               corp (2),
               dmz (3),
               internet (1)
               }
   MAX-ACCESS  read-write
   STATUS      current
   DESCRIPTION
      "Path: ethernet2.editConf.pppoEClient.ip.sNet.name

       Possibilities:
               <OPT>   (0)
               corp   (2)
               dmz   (3)
               internet   (1)"
   ::= {er1645v2Lan2FGUPppOEEntry 53674240}

er1645v2Lan2FGUPppOEIpSNetCust OBJECT-TYPE
   SYNTAX      DisplayString
   MAX-ACCESS  read-write
   STATUS      current
   DESCRIPTION
      "Path: ethernet2.editConf.pppoEClient.ip.sNet.custom"
   ::= {er1645v2Lan2FGUPppOEEntry 53674496}

er1645v2Lan2FGUPppOEIpRem OBJECT-TYPE
   SYNTAX      IpAddress
   MAX-ACCESS  read-write
   STATUS      current
   DESCRIPTION
      "Path: ethernet2.editConf.pppoEClient.ip.remote"
   ::= {er1645v2Lan2FGUPppOEEntry 58458112}

er1645v2Lan2FGUPppOEIpUnnumbered OBJECT-TYPE
   SYNTAX      DisplayString
   MAX-ACCESS  read-write
   STATUS      current
   DESCRIPTION
      "Path: ethernet2.editConf.pppoEClient.ip.unnumbered"
   ::= {er1645v2Lan2FGUPppOEEntry 52625408}

er1645v2Lan2FGUPppOEIpGwPref OBJECT-TYPE
   SYNTAX      Integer32
   MAX-ACCESS  read-write
   STATUS      current
   DESCRIPTION
      "Path: ethernet2.editConf.pppoEClient.ip.gatewayPreference"
   ::= {er1645v2Lan2FGUPppOEEntry 52690944}

er1645v2Lan2FGUPppOEIpRsn OBJECT-TYPE
   SYNTAX      INTEGER
               {
               disabled (0),
               enabled (1)
               }
   MAX-ACCESS  read-write
   STATUS      current
   DESCRIPTION
      "Path: ethernet2.editConf.pppoEClient.ip.requestSubnet

       Possibilities:
               disabled   (0)
               enabled   (1)"
   ::= {er1645v2Lan2FGUPppOEEntry 56688640}

er1645v2Lan2FGUPppOEIpMtu OBJECT-TYPE
   SYNTAX      Integer32
   MAX-ACCESS  read-write
   STATUS      current
   DESCRIPTION
      "Path: ethernet2.editConf.pppoEClient.ip.mtu"
   ::= {er1645v2Lan2FGUPppOEEntry 52953088}

er1645v2Lan2FGUPppOEIpMssAdjust OBJECT-TYPE
   SYNTAX      INTEGER
               {
               disabled (0),
               auto (65536)
               }
   MAX-ACCESS  read-write
   STATUS      current
   DESCRIPTION
      "Path: ethernet2.editConf.pppoEClient.ip.mssAdjust

       Possibilities:
               disabled   (0)
               auto   (65536)"
   ::= {er1645v2Lan2FGUPppOEEntry 53280768}

er1645v2Lan2FGUPppOEIpRipMetric OBJECT-TYPE
   SYNTAX      Integer32
   MAX-ACCESS  read-write
   STATUS      current
   DESCRIPTION
      "Path: ethernet2.editConf.pppoEClient.ip.rip.metric"
   ::= {er1645v2Lan2FGUPppOEEntry 51712768}

er1645v2Lan2FGUPppOEIpRipMetricOut OBJECT-TYPE
   SYNTAX      Integer32
   MAX-ACCESS  read-write
   STATUS      current
   DESCRIPTION
      "Path: ethernet2.editConf.pppoEClient.ip.rip.metricOut"
   ::= {er1645v2Lan2FGUPppOEEntry 51713024}

er1645v2Lan2FGUPppOEIpRipMode OBJECT-TYPE
   SYNTAX      INTEGER
               {
               disabled (0),
               passive (1),
               active (2)
               }
   MAX-ACCESS  read-write
   STATUS      current
   DESCRIPTION
      "Path: ethernet2.editConf.pppoEClient.ip.rip.mode

       Possibilities:
               disabled   (0)
               passive   (1)
               active   (2)"
   ::= {er1645v2Lan2FGUPppOEEntry 51713280}

er1645v2Lan2FGUPppOEIpRipTxVer OBJECT-TYPE
   SYNTAX      INTEGER
               {
               rip1 (0),
               rip2 (1),
               rip1mcompatible (2)
               }
   MAX-ACCESS  read-write
   STATUS      current
   DESCRIPTION
      "Path: ethernet2.editConf.pppoEClient.ip.rip.txVersion

       Possibilities:
               rip1   (0)
               rip2   (1)
               rip1-compatible   (2)"
   ::= {er1645v2Lan2FGUPppOEEntry 51716864}

er1645v2Lan2FGUPppOEIpRipRxVer OBJECT-TYPE
   SYNTAX      INTEGER
               {
               rip1only (0),
               rip2only (1),
               rip12 (2)
               }
   MAX-ACCESS  read-write
   STATUS      current
   DESCRIPTION
      "Path: ethernet2.editConf.pppoEClient.ip.rip.rxVersion

       Possibilities:
               rip1only   (0)
               rip2only   (1)
               rip1&2   (2)"
   ::= {er1645v2Lan2FGUPppOEEntry 51717120}

er1645v2Lan2FGUPppOEIpRipSplitH OBJECT-TYPE
   SYNTAX      INTEGER
               {
               disabled (0),
               enabled (1),
               poisonedReverse (2)
               }
   MAX-ACCESS  read-write
   STATUS      current
   DESCRIPTION
      "Path: ethernet2.editConf.pppoEClient.ip.rip.splitHorizon

       Possibilities:
               disabled   (0)
               enabled   (1)
               poisonedReverse   (2)"
   ::= {er1645v2Lan2FGUPppOEEntry 51713792}

er1645v2Lan2FGUPppOEIpRipAuth OBJECT-TYPE
   SYNTAX      INTEGER
               {
               disabled (0),
               texts (1),
               md5 (2)
               }
   MAX-ACCESS  read-write
   STATUS      current
   DESCRIPTION
      "Path: ethernet2.editConf.pppoEClient.ip.rip.authentication

       Possibilities:
               disabled   (0)
               text    (1)
               md5   (2)"
   ::= {er1645v2Lan2FGUPppOEEntry 51712512}

er1645v2Lan2FGUPppOEIpRipFilter OBJECT-TYPE
   SYNTAX      DisplayString
   MAX-ACCESS  read-write
   STATUS      current
   DESCRIPTION
      "Path: ethernet2.editConf.pppoEClient.ip.rip.filter"
   ::= {er1645v2Lan2FGUPppOEEntry 51716096}

er1645v2Lan2FGUPppOEIpRipFilterIn OBJECT-TYPE
   SYNTAX      DisplayString
   MAX-ACCESS  read-write
   STATUS      current
   DESCRIPTION
      "Path: ethernet2.editConf.pppoEClient.ip.rip.filterIn"
   ::= {er1645v2Lan2FGUPppOEEntry 51716352}

er1645v2Lan2FGUPppOEIpRipClearNextHop OBJECT-TYPE
   SYNTAX      INTEGER
               {
               disabled (0),
               enabled (1)
               }
   MAX-ACCESS  read-write
   STATUS      current
   DESCRIPTION
      "Path: ethernet2.editConf.pppoEClient.ip.rip.clearNextHop

       Possibilities:
               disabled   (0)
               enabled   (1)"
   ::= {er1645v2Lan2FGUPppOEEntry 51708416}

er1645v2Lan2FGUPppOEIpAccPol OBJECT-TYPE
   SYNTAX      DisplayString
   MAX-ACCESS  read-write
   STATUS      current
   DESCRIPTION
      "Path: ethernet2.editConf.pppoEClient.ip.accessPolicy"
   ::= {er1645v2Lan2FGUPppOEEntry 53084160}

er1645v2Lan2FGUPppOEIpAB OBJECT-TYPE
   SYNTAX      DisplayString
   MAX-ACCESS  read-write
   STATUS      current
   DESCRIPTION
      "Path: ethernet2.editConf.pppoEClient.ip.trafficPolicy"
   ::= {er1645v2Lan2FGUPppOEEntry 51249152}

er1645v2Lan2FGUPppOEIpMA OBJECT-TYPE
   SYNTAX      INTEGER
               {
               disabled (0),
               enabled (1)
               }
   MAX-ACCESS  read-write
   STATUS      current
   DESCRIPTION
      "Path: ethernet2.editConf.pppoEClient.ip.mgmtAccess

       Possibilities:
               disabled   (0)
               enabled   (1)"
   ::= {er1645v2Lan2FGUPppOEEntry 51380224}

er1645v2Lan2FGUPppOEIpMF OBJECT-TYPE
   SYNTAX      Integer32
   MAX-ACCESS  read-write
   STATUS      current
   DESCRIPTION
      "Path: ethernet2.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGUPppOEEntry 51445760}

er1645v2Lan2FGUPppOEIpDB OBJECT-TYPE
   SYNTAX      INTEGER
               {
               disabled (0),
               enabled (1)
               }
   MAX-ACCESS  read-write
   STATUS      current
   DESCRIPTION
      "Path: ethernet2.editConf.pppoEClient.ip.directedBroadcasts

       Possibilities:
               disabled   (0)
               enabled   (1)"
   ::= {er1645v2Lan2FGUPppOEEntry 51773440}

er1645v2Lan2FGUPppOEIpIR OBJECT-TYPE
   SYNTAX      INTEGER
               {
               disabled (0),
               enabled (1)
               }
   MAX-ACCESS  read-write
   STATUS      current
   DESCRIPTION
      "Path: ethernet2.editConf.pppoEClient.ip.icmpRedirects

       Possibilities:
               disabled   (0)
               enabled   (1)"
   ::= {er1645v2Lan2FGUPppOEEntry 52035584}

er1645v2Lan2FGUPppOEIpIgmp OBJECT-TYPE
   SYNTAX      INTEGER
               {
               disabled (0),
               proxy (1),
               router (2),
               v3Router (5)
               }
   MAX-ACCESS  read-write
   STATUS      current
   DESCRIPTION
      "Path: ethernet2.editConf.pppoEClient.ip.igmp

       Possibilities:
               disabled   (0)
               proxy   (1)
               router   (2)
               v3Router   (5)"
   ::= {er1645v2Lan2FGUPppOEEntry 52428800}

er1645v2Lan2FGUPppOEIpNN OBJECT-TYPE
   SYNTAX      DisplayString
   MAX-ACCESS  read-write
   STATUS      current
   DESCRIPTION
      "Path: ethernet2.editConf.pppoEClient.ip.nat"
   ::= {er1645v2Lan2FGUPppOEEntry 52101120}

er1645v2Lan2FGUPppOEIpPimMode OBJECT-TYPE
   SYNTAX      INTEGER
               {
               disabled (0),
               sparse (1),
               passive (2)
               }
   MAX-ACCESS  read-write
   STATUS      current
   DESCRIPTION
      "Path: ethernet2.editConf.pppoEClient.ip.pim.mode

       Possibilities:
               disabled   (0)
               sparse   (1)
               passive   (2)"
   ::= {er1645v2Lan2FGUPppOEEntry 53346560}

er1645v2Lan2FGUPppOEIpPimDrPriority OBJECT-TYPE
   SYNTAX      Counter32
   MAX-ACCESS  read-write
   STATUS      current
   DESCRIPTION
      "Path: ethernet2.editConf.pppoEClient.ip.pim.drPriority

       32 bit unsigned wrappable counter."
   ::= {er1645v2Lan2FGUPppOEEntry 53346816}

er1645v2Lan2FGUPppOEIpPimHelloTime OBJECT-TYPE
   SYNTAX      TimeTicks
   MAX-ACCESS  read-write
   STATUS      current
   DESCRIPTION
      "Path: ethernet2.editConf.pppoEClient.ip.pim.helloTime

       Time in centi-second."
   ::= {er1645v2Lan2FGUPppOEEntry 53347072}

er1645v2Lan2FGUPppOEIpPimPropagationDelay OBJECT-TYPE
   SYNTAX      TimeTicks
   MAX-ACCESS  read-write
   STATUS      current
   DESCRIPTION
      "Path: ethernet2.editConf.pppoEClient.ip.pim.propagationDelay

       Time in centi-second."
   ::= {er1645v2Lan2FGUPppOEEntry 53347328}

er1645v2Lan2FGUPppOEIpPimOverrideInterval OBJECT-TYPE
   SYNTAX      TimeTicks
   MAX-ACCESS  read-write
   STATUS      current
   DESCRIPTION
      "Path: ethernet2.editConf.pppoEClient.ip.pim.overrideInterval

       Time in centi-second."
   ::= {er1645v2Lan2FGUPppOEEntry 53347584}

er1645v2Lan2FGUPppOEIpPimBsrBorder OBJECT-TYPE
   SYNTAX      INTEGER
               {
               disabled (0),
               enabled (1)
               }
   MAX-ACCESS  read-write
   STATUS      current
   DESCRIPTION
      "Path: ethernet2.editConf.pppoEClient.ip.pim.bsrBorder

       Possibilities:
               disabled   (0)
               enabled   (1)"
   ::= {er1645v2Lan2FGUPppOEEntry 53347840}

er1645v2Lan2FGUPppOEIpPimTtlThreshold OBJECT-TYPE
   SYNTAX      Integer32
   MAX-ACCESS  read-write
   STATUS      current
   DESCRIPTION
      "Path: ethernet2.editConf.pppoEClient.ip.pim.ttlThreshold"
   ::= {er1645v2Lan2FGUPppOEEntry 53348096}

er1645v2Lan2FGUPppOEIpIMNetworkUnreachable OBJECT-TYPE
   SYNTAX      INTEGER
               {
               disabled (0),
               enabled (1)
               }
   MAX-ACCESS  read-write
   STATUS      current
   DESCRIPTION
      "Path: ethernet2.editConf.pppoEClient.ip.icmpMessages.networkUnreachable

       Possibilities:
               disabled   (0)
               enabled   (1)"
   ::= {er1645v2Lan2FGUPppOEEntry 53412096}

er1645v2Lan2FGUPppOEIpIMHostUnreachable OBJECT-TYPE
   SYNTAX      INTEGER
               {
               disabled (0),
               enabled (1)
               }
   MAX-ACCESS  read-write
   STATUS      current
   DESCRIPTION
      "Path: ethernet2.editConf.pppoEClient.ip.icmpMessages.hostUnreachable

       Possibilities:
               disabled   (0)
               enabled   (1)"
   ::= {er1645v2Lan2FGUPppOEEntry 53412352}

er1645v2Lan2FGUPppOEIpIMProtocolUnreachable OBJECT-TYPE
   SYNTAX      INTEGER
               {
               disabled (0),
               enabled (1)
               }
   MAX-ACCESS  read-write
   STATUS      current
   DESCRIPTION
      "Path: ethernet2.editConf.pppoEClient.ip.icmpMessages.protocolUnreachable

       Possibilities:
               disabled   (0)
               enabled   (1)"
   ::= {er1645v2Lan2FGUPppOEEntry 53412608}

er1645v2Lan2FGUPppOEIpIMPortUnreachable OBJECT-TYPE
   SYNTAX      INTEGER
               {
               disabled (0),
               enabled (1)
               }
   MAX-ACCESS  read-write
   STATUS      current
   DESCRIPTION
      "Path: ethernet2.editConf.pppoEClient.ip.icmpMessages.portUnreachable

       Possibilities:
               disabled   (0)
               enabled   (1)"
   ::= {er1645v2Lan2FGUPppOEEntry 53412864}

er1645v2Lan2FGUPppOEIpIMMtuExceeded OBJECT-TYPE
   SYNTAX      INTEGER
               {
               disabled (0),
               enabled (1)
               }
   MAX-ACCESS  read-write
   STATUS      current
   DESCRIPTION
      "Path: ethernet2.editConf.pppoEClient.ip.icmpMessages.mtuExceeded

       Possibilities:
               disabled   (0)
               enabled   (1)"
   ::= {er1645v2Lan2FGUPppOEEntry 53413120}

er1645v2Lan2FGUPppOEIpIMAdminProhibited OBJECT-TYPE
   SYNTAX      INTEGER
               {
               disabled (0),
               enabled (1)
               }
   MAX-ACCESS  read-write
   STATUS      current
   DESCRIPTION
      "Path: ethernet2.editConf.pppoEClient.ip.icmpMessages.adminProhibited

       Possibilities:
               disabled   (0)
               enabled   (1)"
   ::= {er1645v2Lan2FGUPppOEEntry 53413376}

er1645v2Lan2FGUPppOEIpIMTtlExceeded OBJECT-TYPE
   SYNTAX      INTEGER
               {
               disabled (0),
               enabled (1)
               }
   MAX-ACCESS  read-write
   STATUS      current
   DESCRIPTION
      "Path: ethernet2.editConf.pppoEClient.ip.icmpMessages.ttlExceeded

       Possibilities:
               disabled   (0)
               enabled   (1)"
   ::= {er1645v2Lan2FGUPppOEEntry 53413632}

er1645v2Lan2FGUPppOEIpIMRedirect OBJECT-TYPE
   SYNTAX      INTEGER
               {
               disabled (0),
               enabled (1)
               }
   MAX-ACCESS  read-write
   STATUS      current
   DESCRIPTION
      "Path: ethernet2.editConf.pppoEClient.ip.icmpMessages.redirect

       Possibilities:
               disabled   (0)
               enabled   (1)"
   ::= {er1645v2Lan2FGUPppOEEntry 53413888}

er1645v2Lan2FGUPppOEIpV6VrfRouter OBJECT-TYPE
   SYNTAX      DisplayString
   MAX-ACCESS  read-write
   STATUS      current
   DESCRIPTION
      "Path: ethernet2.editConf.pppoEClient.ipV6.vrfRouter"
   ::= {er1645v2Lan2FGUPppOEEntry 704708608}

er1645v2Lan2FGUPppOEIpV6AddrAutoConfigNrDupAddrDetects OBJECT-TYPE
   SYNTAX      Integer32
   MAX-ACCESS  read-write
   STATUS      current
   DESCRIPTION
      "Path: ethernet2.editConf.pppoEClient.ipV6.addrAutoConfig.nrDupAddrDetects"
   ::= {er1645v2Lan2FGUPppOEEntry 704905472}

er1645v2Lan2FGUPppOEIpV6AddrAutoConfigAcceptRa OBJECT-TYPE
   SYNTAX      INTEGER
               {
               disabled (0),
               enabled (1)
               }
   MAX-ACCESS  read-write
   STATUS      current
   DESCRIPTION
      "Path: ethernet2.editConf.pppoEClient.ipV6.addrAutoConfig.acceptRa

       Possibilities:
               disabled   (0)
               enabled   (1)"
   ::= {er1645v2Lan2FGUPppOEEntry 704905728}

er1645v2Lan2FGUPppOEIpV6AddrAutoConfigAcceptRaRdnss OBJECT-TYPE
   SYNTAX      INTEGER
               {
               disabled (0),
               enabled (1)
               }
   MAX-ACCESS  read-write
   STATUS      current
   DESCRIPTION
      "Path: ethernet2.editConf.pppoEClient.ipV6.addrAutoConfig.acceptRaRdnss

       Possibilities:
               disabled   (0)
               enabled   (1)"
   ::= {er1645v2Lan2FGUPppOEEntry 704905984}

er1645v2Lan2FGUPppOEIpV6AddrAutoConfigAcceptRaDnssl OBJECT-TYPE
   SYNTAX      INTEGER
               {
               disabled (0),
               enabled (1)
               }
   MAX-ACCESS  read-write
   STATUS      current
   DESCRIPTION
      "Path: ethernet2.editConf.pppoEClient.ipV6.addrAutoConfig.acceptRaDnssl

       Possibilities:
               disabled   (0)
               enabled   (1)"
   ::= {er1645v2Lan2FGUPppOEEntry 704906240}

er1645v2Lan2FGUPppOEIpV6DefaultRoute OBJECT-TYPE
   SYNTAX      INTEGER
               {
               disabled (0),
               enabled (1)
               }
   MAX-ACCESS  read-write
   STATUS      current
   DESCRIPTION
      "Path: ethernet2.editConf.pppoEClient.ipV6.defaultRoute

       Possibilities:
               disabled   (0)
               enabled   (1)"
   ::= {er1645v2Lan2FGUPppOEEntry 704970752}

er1645v2Lan2FGUPppOEIpV6RaSend OBJECT-TYPE
   SYNTAX      INTEGER
               {
               disabled (0),
               enabled (1)
               }
   MAX-ACCESS  read-write
   STATUS      current
   DESCRIPTION
      "Path: ethernet2.editConf.pppoEClient.ipV6.ra.send

       Possibilities:
               disabled   (0)
               enabled   (1)"
   ::= {er1645v2Lan2FGUPppOEEntry 705036544}

er1645v2Lan2FGUPppOEIpV6RaMinInterval OBJECT-TYPE
   SYNTAX      TimeTicks
   MAX-ACCESS  read-write
   STATUS      current
   DESCRIPTION
      "Path: ethernet2.editConf.pppoEClient.ipV6.ra.minInterval

       Time in centi-second."
   ::= {er1645v2Lan2FGUPppOEEntry 705036800}

er1645v2Lan2FGUPppOEIpV6RaMaxInterval OBJECT-TYPE
   SYNTAX      TimeTicks
   MAX-ACCESS  read-write
   STATUS      current
   DESCRIPTION
      "Path: ethernet2.editConf.pppoEClient.ipV6.ra.maxInterval

       Time in centi-second."
   ::= {er1645v2Lan2FGUPppOEEntry 705037056}

er1645v2Lan2FGUPppOEIpV6RaManagedFlag OBJECT-TYPE
   SYNTAX      INTEGER
               {
               disabled (0),
               enabled (1)
               }
   MAX-ACCESS  read-write
   STATUS      current
   DESCRIPTION
      "Path: ethernet2.editConf.pppoEClient.ipV6.ra.managedFlag

       Possibilities:
               disabled   (0)
               enabled   (1)"
   ::= {er1645v2Lan2FGUPppOEEntry 705037312}

er1645v2Lan2FGUPppOEIpV6RaOtherConfFlag OBJECT-TYPE
   SYNTAX      INTEGER
               {
               disabled (0),
               enabled (1)
               }
   MAX-ACCESS  read-write
   STATUS      current
   DESCRIPTION
      "Path: ethernet2.editConf.pppoEClient.ipV6.ra.otherConfFlag

       Possibilities:
               disabled   (0)
               enabled   (1)"
   ::= {er1645v2Lan2FGUPppOEEntry 705037568}

er1645v2Lan2FGUPppOEIpV6RaLinkMtu OBJECT-TYPE
   SYNTAX      Integer32
   MAX-ACCESS  read-write
   STATUS      current
   DESCRIPTION
      "Path: ethernet2.editConf.pppoEClient.ipV6.ra.linkMtu"
   ::= {er1645v2Lan2FGUPppOEEntry 705037824}

er1645v2Lan2FGUPppOEIpV6RaReachableTime OBJECT-TYPE
   SYNTAX      TimeTicks
   MAX-ACCESS  read-write
   STATUS      current
   DESCRIPTION
      "Path: ethernet2.editConf.pppoEClient.ipV6.ra.reachableTime

       Time in centi-second."
   ::= {er1645v2Lan2FGUPppOEEntry 705038080}

er1645v2Lan2FGUPppOEIpV6RaRetransmitTime OBJECT-TYPE
   SYNTAX      TimeTicks
   MAX-ACCESS  read-write
   STATUS      current
   DESCRIPTION
      "Path: ethernet2.editConf.pppoEClient.ipV6.ra.retransmitTime

       Time in centi-second."
   ::= {er1645v2Lan2FGUPppOEEntry 705038336}

er1645v2Lan2FGUPppOEIpV6RaHopLimit OBJECT-TYPE
   SYNTAX      Integer32
   MAX-ACCESS  read-write
   STATUS      current
   DESCRIPTION
      "Path: ethernet2.editConf.pppoEClient.ipV6.ra.hopLimit"
   ::= {er1645v2Lan2FGUPppOEEntry 705038592}

er1645v2Lan2FGUPppOEIpV6RaDefaultLifeTime OBJECT-TYPE
   SYNTAX      TimeTicks
   MAX-ACCESS  read-write
   STATUS      current
   DESCRIPTION
      "Path: ethernet2.editConf.pppoEClient.ipV6.ra.defaultLifeTime

       Time in centi-second."
   ::= {er1645v2Lan2FGUPppOEEntry 705038848}

er1645v2Lan2FGUPppOEIpV6RaDnsOptionsRdnssLifeTime OBJECT-TYPE
   SYNTAX      TimeTicks
   MAX-ACCESS  read-write
   STATUS      current
   DESCRIPTION
      "Path: ethernet2.editConf.pppoEClient.ipV6.ra.dnsOptions.rdnss.lifeTime

       Time in centi-second."
   ::= {er1645v2Lan2FGUPppOEEntry 705039140}

er1645v2Lan2FGUPppOEIpV6RaDnsOptionsRdnssImportServers OBJECT-TYPE
   SYNTAX      INTEGER
               {
               disabled (0),
               enabled (1)
               }
   MAX-ACCESS  read-write
   STATUS      current
   DESCRIPTION
      "Path: ethernet2.editConf.pppoEClient.ipV6.ra.dnsOptions.rdnss.importServers

       Possibilities:
               disabled   (0)
               enabled   (1)"
   ::= {er1645v2Lan2FGUPppOEEntry 705039148}

er1645v2Lan2FGUPppOEIpV6RaDnsOptionsDnsslLifeTime OBJECT-TYPE
   SYNTAX      TimeTicks
   MAX-ACCESS  read-write
   STATUS      current
   DESCRIPTION
      "Path: ethernet2.editConf.pppoEClient.ipV6.ra.dnsOptions.dnssl.lifeTime

       Time in centi-second."
   ::= {er1645v2Lan2FGUPppOEEntry 705039172}

er1645v2Lan2FGUPppOEIpV6RaDnsOptionsDnsslImportDomains OBJECT-TYPE
   SYNTAX      INTEGER
               {
               disabled (0),
               enabled (1)
               }
   MAX-ACCESS  read-write
   STATUS      current
   DESCRIPTION
      "Path: ethernet2.editConf.pppoEClient.ipV6.ra.dnsOptions.dnssl.importDomains

       Possibilities:
               disabled   (0)
               enabled   (1)"
   ::= {er1645v2Lan2FGUPppOEEntry 705039180}

er1645v2Lan2FGUPppOEIpV6RsSend OBJECT-TYPE
   SYNTAX      INTEGER
               {
               disabled (0),
               enabled (1)
               }
   MAX-ACCESS  read-write
   STATUS      current
   DESCRIPTION
      "Path: ethernet2.editConf.pppoEClient.ipV6.rs.send

       Possibilities:
               disabled   (0)
               enabled   (1)"
   ::= {er1645v2Lan2FGUPppOEEntry 705954048}

er1645v2Lan2FGUPppOEIpV6RsMaxRandomDelay OBJECT-TYPE
   SYNTAX      TimeTicks
   MAX-ACCESS  read-write
   STATUS      current
   DESCRIPTION
      "Path: ethernet2.editConf.pppoEClient.ipV6.rs.maxRandomDelay

       Time in centi-second."
   ::= {er1645v2Lan2FGUPppOEEntry 705954304}

er1645v2Lan2FGUPppOEIpV6RsInterval OBJECT-TYPE
   SYNTAX      TimeTicks
   MAX-ACCESS  read-write
   STATUS      current
   DESCRIPTION
      "Path: ethernet2.editConf.pppoEClient.ipV6.rs.interval

       Time in centi-second."
   ::= {er1645v2Lan2FGUPppOEEntry 705954560}

er1645v2Lan2FGUPppOEIpV6RsMaxSolicitations OBJECT-TYPE
   SYNTAX      Integer32
   MAX-ACCESS  read-write
   STATUS      current
   DESCRIPTION
      "Path: ethernet2.editConf.pppoEClient.ipV6.rs.maxSolicitations"
   ::= {er1645v2Lan2FGUPppOEEntry 705954816}

er1645v2Lan2FGUPppOEIpV6TrafficPolicyInbound OBJECT-TYPE
   SYNTAX      DisplayString
   MAX-ACCESS  read-write
   STATUS      current
   DESCRIPTION
      "Path: ethernet2.editConf.pppoEClient.ipV6.trafficPolicy.inbound"
   ::= {er1645v2Lan2FGUPppOEEntry 705364224}

er1645v2Lan2FGUPppOEIpV6TrafficPolicyOutbound OBJECT-TYPE
   SYNTAX      DisplayString
   MAX-ACCESS  read-write
   STATUS      current
   DESCRIPTION
      "Path: ethernet2.editConf.pppoEClient.ipV6.trafficPolicy.outbound"
   ::= {er1645v2Lan2FGUPppOEEntry 705364480}

er1645v2Lan2FGUPppOEIpV6FirewallZone OBJECT-TYPE
   SYNTAX      DisplayString
   MAX-ACCESS  read-write
   STATUS      current
   DESCRIPTION
      "Path: ethernet2.editConf.pppoEClient.ipV6.firewall.zone"
   ::= {er1645v2Lan2FGUPppOEEntry 705429760}

er1645v2Lan2FGUPppOEIpV6DhcpClientAddrAC OBJECT-TYPE
   SYNTAX      INTEGER
               {
               disabled (0),
               enabled (1)
               }
   MAX-ACCESS  read-write
   STATUS      current
   DESCRIPTION
      "Path: ethernet2.editConf.pppoEClient.ipV6.dhcp.client.addrAutoConfig

       Possibilities:
               disabled   (0)
               enabled   (1)"
   ::= {er1645v2Lan2FGUPppOEEntry 705307648}

er1645v2Lan2FGUPppOEIpV6DhcpClientPrDelMode OBJECT-TYPE
   SYNTAX      INTEGER
               {
               disabled (0),
               enabled (1)
               }
   MAX-ACCESS  read-write
   STATUS      current
   DESCRIPTION
      "Path: ethernet2.editConf.pppoEClient.ipV6.dhcp.client.pd.mode

       Possibilities:
               disabled   (0)
               enabled   (1)"
   ::= {er1645v2Lan2FGUPppOEEntry 705308676}

er1645v2Lan2FGUPppOEIpV6DhcpClientPrDelPool OBJECT-TYPE
   SYNTAX      DisplayString
   MAX-ACCESS  read-write
   STATUS      current
   DESCRIPTION
      "Path: ethernet2.editConf.pppoEClient.ipV6.dhcp.client.pd.pool"
   ::= {er1645v2Lan2FGUPppOEEntry 705308680}

er1645v2Lan2FGUPppOEIpV6DhcpClientPrDelPdExclOpt OBJECT-TYPE
   SYNTAX      INTEGER
               {
               disabled (0),
               enabled (1)
               }
   MAX-ACCESS  read-write
   STATUS      current
   DESCRIPTION
      "Path: ethernet2.editConf.pppoEClient.ipV6.dhcp.client.pd.pdExclOpt

       Possibilities:
               disabled   (0)
               enabled   (1)"
   ::= {er1645v2Lan2FGUPppOEEntry 705308684}

er1645v2Lan2FGUPppOEIpV6DhcpClientDnsServerPref OBJECT-TYPE
   SYNTAX      Integer32
   MAX-ACCESS  read-write
   STATUS      current
   DESCRIPTION
      "Path: ethernet2.editConf.pppoEClient.ipV6.dhcp.client.dns.serverPref"
   ::= {er1645v2Lan2FGUPppOEEntry 705310724}

er1645v2Lan2FGUPppOEIpV6DhcpClientRapidCommit OBJECT-TYPE
   SYNTAX      INTEGER
               {
               disabled (0),
               enabled (1)
               }
   MAX-ACCESS  read-write
   STATUS      current
   DESCRIPTION
      "Path: ethernet2.editConf.pppoEClient.ipV6.dhcp.client.rapidCommit

       Possibilities:
               disabled   (0)
               enabled   (1)"
   ::= {er1645v2Lan2FGUPppOEEntry 705309696}

er1645v2Lan2FGUPppOEIpV6DhcpClientTimersSolTimeOut OBJECT-TYPE
   SYNTAX      TimeTicks
   MAX-ACCESS  read-write
   STATUS      current
   DESCRIPTION
      "Path: ethernet2.editConf.pppoEClient.ipV6.dhcp.client.timers.solTimeOut

       Time in centi-second."
   ::= {er1645v2Lan2FGUPppOEEntry 705311748}

er1645v2Lan2FGUPppOEIpV6DhcpClientTimersSolMaxRt OBJECT-TYPE
   SYNTAX      TimeTicks
   MAX-ACCESS  read-write
   STATUS      current
   DESCRIPTION
      "Path: ethernet2.editConf.pppoEClient.ipV6.dhcp.client.timers.solMaxRt

       Time in centi-second."
   ::= {er1645v2Lan2FGUPppOEEntry 705311752}

er1645v2Lan2FGUPppOEIpV6DhcpClientTimersInfoRefresh OBJECT-TYPE
   SYNTAX      TimeTicks
   MAX-ACCESS  read-write
   STATUS      current
   DESCRIPTION
      "Path: ethernet2.editConf.pppoEClient.ipV6.dhcp.client.timers.infoRefresh

       Time in centi-second."
   ::= {er1645v2Lan2FGUPppOEEntry 705311756}

er1645v2Lan2FGUPppOEIpV6DhcpServerMode OBJECT-TYPE
   SYNTAX      INTEGER
               {
               disabled (0),
               enabled (1)
               }
   MAX-ACCESS  read-write
   STATUS      current
   DESCRIPTION
      "Path: ethernet2.editConf.pppoEClient.ipV6.dhcp.server.mode

       Possibilities:
               disabled   (0)
               enabled   (1)"
   ::= {er1645v2Lan2FGUPppOEEntry 705315840}

er1645v2Lan2FGUPppOEIpV6DhcpServerPreference OBJECT-TYPE
   SYNTAX      Integer32
   MAX-ACCESS  read-write
   STATUS      current
   DESCRIPTION
      "Path: ethernet2.editConf.pppoEClient.ipV6.dhcp.server.preference"
   ::= {er1645v2Lan2FGUPppOEEntry 705316864}

er1645v2Lan2FGUPppOEIpV6DhcpServerPool OBJECT-TYPE
   SYNTAX      DisplayString
   MAX-ACCESS  read-write
   STATUS      current
   DESCRIPTION
      "Path: ethernet2.editConf.pppoEClient.ipV6.dhcp.server.pool"
   ::= {er1645v2Lan2FGUPppOEEntry 705317888}

er1645v2Lan2FGUPppOEIpV6DhcpServerRapidCommit OBJECT-TYPE
   SYNTAX      INTEGER
               {
               disabled (0),
               enabled (1)
               }
   MAX-ACCESS  read-write
   STATUS      current
   DESCRIPTION
      "Path: ethernet2.editConf.pppoEClient.ipV6.dhcp.server.rapidCommit

       Possibilities:
               disabled   (0)
               enabled   (1)"
   ::= {er1645v2Lan2FGUPppOEEntry 705318912}

er1645v2Lan2FGUPppOEIpV6DhcpServerTimersInfoRefresh OBJECT-TYPE
   SYNTAX      TimeTicks
   MAX-ACCESS  read-write
   STATUS      current
   DESCRIPTION
      "Path: ethernet2.editConf.pppoEClient.ipV6.dhcp.server.timers.infoRefresh

       Time in centi-second."
   ::= {er1645v2Lan2FGUPppOEEntry 705319940}

er1645v2Lan2FGUPppOEIpV6DhcpRelayMode OBJECT-TYPE
   SYNTAX      INTEGER
               {
               disabled (0),
               enabled (1)
               }
   MAX-ACCESS  read-write
   STATUS      current
   DESCRIPTION
      "Path: ethernet2.editConf.pppoEClient.ipV6.dhcp.relay.mode

       Possibilities:
               disabled   (0)
               enabled   (1)"
   ::= {er1645v2Lan2FGUPppOEEntry 705323040}

er1645v2Lan2FGUPppOEIpV6SendRedirect OBJECT-TYPE
   SYNTAX      INTEGER
               {
               disabled (0),
               enabled (1)
               }
   MAX-ACCESS  read-write
   STATUS      current
   DESCRIPTION
      "Path: ethernet2.editConf.pppoEClient.ipV6.sendRedirect

       Possibilities:
               disabled   (0)
               enabled   (1)"
   ::= {er1645v2Lan2FGUPppOEEntry 705101824}

er1645v2Lan2FGUPppOEIpV6LinkMtu OBJECT-TYPE
   SYNTAX      Integer32
   MAX-ACCESS  read-write
   STATUS      current
   DESCRIPTION
      "Path: ethernet2.editConf.pppoEClient.ipV6.linkMtu"
   ::= {er1645v2Lan2FGUPppOEEntry 705167360}

er1645v2Lan2FGUPppOEIpV6InterfaceId OBJECT-TYPE
   SYNTAX      OCTET STRING
   MAX-ACCESS  read-write
   STATUS      current
   DESCRIPTION
      "Path: ethernet2.editConf.pppoEClient.ipV6.interfaceId"
   ::= {er1645v2Lan2FGUPppOEEntry 705232896}

er1645v2Lan2FGUPppOEIpV6MF OBJECT-TYPE
   SYNTAX      Integer32
   MAX-ACCESS  read-write
   STATUS      current
   DESCRIPTION
      "Path: ethernet2.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGUPppOEEntry 705757184}

er1645v2Lan2FGUPppOEIpV6IcmpMessagesNoRoute OBJECT-TYPE
   SYNTAX      INTEGER
               {
               disabled (0),
               enabled (1)
               }
   MAX-ACCESS  read-write
   STATUS      current
   DESCRIPTION
      "Path: ethernet2.editConf.pppoEClient.ipV6.icmpMessages.noRoute

       Possibilities:
               disabled   (0)
               enabled   (1)"
   ::= {er1645v2Lan2FGUPppOEEntry 705822976}

er1645v2Lan2FGUPppOEIpV6IcmpMessagesBeyondScope OBJECT-TYPE
   SYNTAX      INTEGER
               {
               disabled (0),
               enabled (1)
               }
   MAX-ACCESS  read-write
   STATUS      current
   DESCRIPTION
      "Path: ethernet2.editConf.pppoEClient.ipV6.icmpMessages.beyondScope

       Possibilities:
               disabled   (0)
               enabled   (1)"
   ::= {er1645v2Lan2FGUPppOEEntry 705823488}

er1645v2Lan2FGUPppOEIpV6IcmpMessagesAddressUnreachable OBJECT-TYPE
   SYNTAX      INTEGER
               {
               disabled (0),
               enabled (1)
               }
   MAX-ACCESS  read-write
   STATUS      current
   DESCRIPTION
      "Path: ethernet2.editConf.pppoEClient.ipV6.icmpMessages.addressUnreachable

       Possibilities:
               disabled   (0)
               enabled   (1)"
   ::= {er1645v2Lan2FGUPppOEEntry 705823744}

er1645v2Lan2FGUPppOEIpV6IcmpMessagesPortUnreachable OBJECT-TYPE
   SYNTAX      INTEGER
               {
               disabled (0),
               enabled (1)
               }
   MAX-ACCESS  read-write
   STATUS      current
   DESCRIPTION
      "Path: ethernet2.editConf.pppoEClient.ipV6.icmpMessages.portUnreachable

       Possibilities:
               disabled   (0)
               enabled   (1)"
   ::= {er1645v2Lan2FGUPppOEEntry 705824000}

er1645v2Lan2FGUPppOEIpV6IcmpMessagesPacketTooBig OBJECT-TYPE
   SYNTAX      INTEGER
               {
               disabled (0),
               enabled (1)
               }
   MAX-ACCESS  read-write
   STATUS      current
   DESCRIPTION
      "Path: ethernet2.editConf.pppoEClient.ipV6.icmpMessages.packetTooBig

       Possibilities:
               disabled   (0)
               enabled   (1)"
   ::= {er1645v2Lan2FGUPppOEEntry 705825280}

er1645v2Lan2FGUPppOEIpV6IcmpMessagesHopLimitExceeded OBJECT-TYPE
   SYNTAX      INTEGER
               {
               disabled (0),
               enabled (1)
               }
   MAX-ACCESS  read-write
   STATUS      current
   DESCRIPTION
      "Path: ethernet2.editConf.pppoEClient.ipV6.icmpMessages.hopLimitExceeded

       Possibilities:
               disabled   (0)
               enabled   (1)"
   ::= {er1645v2Lan2FGUPppOEEntry 705827840}

er1645v2Lan2FGUPppOEIpV6IcmpMessagesFragTimeExceeded OBJECT-TYPE
   SYNTAX      INTEGER
               {
               disabled (0),
               enabled (1)
               }
   MAX-ACCESS  read-write
   STATUS      current
   DESCRIPTION
      "Path: ethernet2.editConf.pppoEClient.ipV6.icmpMessages.fragTimeExceeded

       Possibilities:
               disabled   (0)
               enabled   (1)"
   ::= {er1645v2Lan2FGUPppOEEntry 705828096}

er1645v2Lan2FGUPppOEIpV6IcmpMessagesHeaderFieldErr OBJECT-TYPE
   SYNTAX      INTEGER
               {
               disabled (0),
               enabled (1)
               }
   MAX-ACCESS  read-write
   STATUS      current
   DESCRIPTION
      "Path: ethernet2.editConf.pppoEClient.ipV6.icmpMessages.headerFieldErr

       Possibilities:
               disabled   (0)
               enabled   (1)"
   ::= {er1645v2Lan2FGUPppOEEntry 705830400}

er1645v2Lan2FGUPppOEIpV6IcmpMessagesOptionUnrecognized OBJECT-TYPE
   SYNTAX      INTEGER
               {
               disabled (0),
               enabled (1)
               }
   MAX-ACCESS  read-write
   STATUS      current
   DESCRIPTION
      "Path: ethernet2.editConf.pppoEClient.ipV6.icmpMessages.optionUnrecognized

       Possibilities:
               disabled   (0)
               enabled   (1)"
   ::= {er1645v2Lan2FGUPppOEEntry 705830912}

er1645v2Lan2FGUPppOEIpV6IcmpMessagesRedirect OBJECT-TYPE
   SYNTAX      INTEGER
               {
               disabled (0),
               enabled (1)
               }
   MAX-ACCESS  read-write
   STATUS      current
   DESCRIPTION
      "Path: ethernet2.editConf.pppoEClient.ipV6.icmpMessages.redirect

       Possibilities:
               disabled   (0)
               enabled   (1)"
   ::= {er1645v2Lan2FGUPppOEEntry 705832960}

er1645v2Lan2FGUPppOEPppLnkMOperation OBJECT-TYPE
   SYNTAX      INTEGER
               {
               disabled (0),
               enabled (1)
               }
   MAX-ACCESS  read-write
   STATUS      current
   DESCRIPTION
      "Path: ethernet2.editConf.pppoEClient.ppp.linkMonitoring.operation

       Possibilities:
               disabled   (0)
               enabled   (1)"
   ::= {er1645v2Lan2FGUPppOEEntry 251724032}

er1645v2Lan2FGUPppOEPppLnkMInterval OBJECT-TYPE
   SYNTAX      TimeTicks
   MAX-ACCESS  read-write
   STATUS      current
   DESCRIPTION
      "Path: ethernet2.editConf.pppoEClient.ppp.linkMonitoring.interval

       Time in centi-second."
   ::= {er1645v2Lan2FGUPppOEEntry 251724288}

er1645v2Lan2FGUPppOEPppLnkMRepTimeOut OBJECT-TYPE
   SYNTAX      TimeTicks
   MAX-ACCESS  read-write
   STATUS      current
   DESCRIPTION
      "Path: ethernet2.editConf.pppoEClient.ppp.linkMonitoring.replyTimeOut

       Time in centi-second."
   ::= {er1645v2Lan2FGUPppOEEntry 251724544}

er1645v2Lan2FGUPppOEPppLnkMFailsPrmt OBJECT-TYPE
   SYNTAX      Integer32
   MAX-ACCESS  read-write
   STATUS      current
   DESCRIPTION
      "Path: ethernet2.editConf.pppoEClient.ppp.linkMonitoring.failsPermitted"
   ::= {er1645v2Lan2FGUPppOEEntry 251724800}

er1645v2Lan2FGUPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.pppoEClient.ppp.authentication

       Possibilities:
               disabled   (0)
               chap   (1)
               pap   (2)
               chapOrPap   (3)
               msChap   (4)
               msChapV2   (5)"
   ::= {er1645v2Lan2FGUPppOEEntry 251789312}

er1645v2Lan2FGUPppOEPppAuthenPeriod OBJECT-TYPE
   SYNTAX      TimeTicks
   MAX-ACCESS  read-write
   STATUS      current
   DESCRIPTION
      "Path: ethernet2.editConf.pppoEClient.ppp.authenPeriod

       Time in centi-second."
   ::= {er1645v2Lan2FGUPppOEEntry 251854848}

er1645v2Lan2FGUPppOEPppSessionName OBJECT-TYPE
   SYNTAX      DisplayString
   MAX-ACCESS  read-write
   STATUS      current
   DESCRIPTION
      "Path: ethernet2.editConf.pppoEClient.ppp.sessionName"
   ::= {er1645v2Lan2FGUPppOEEntry 251985920}

er1645v2Lan2FGUPppOEPppSessionSecret OBJECT-TYPE
   SYNTAX      DisplayString
   MAX-ACCESS  read-write
   STATUS      current
   DESCRIPTION
      "Path: ethernet2.editConf.pppoEClient.ppp.sessionSecret"
   ::= {er1645v2Lan2FGUPppOEEntry 252051456}

er1645v2Lan2FGUPppOEPppEncModeSessionSecret OBJECT-TYPE
   SYNTAX      INTEGER
               {
               none (1),
               encrypt (2),
               encType1 (3),
               invalid (128)
               }
   MAX-ACCESS  read-write
   STATUS      current
   DESCRIPTION
      "Path: ethernet2.editConf.pppoEClient.ppp.encModeSessionSecret

       Possibilities:
               none   (1)
               encrypt   (2)
               encType1   (3)
               invalid   (128)"
   ::= {er1645v2Lan2FGUPppOEEntry 252182528}

er1645v2Lan2FGUPppOEPppEncSessionSecret OBJECT-TYPE
   SYNTAX      DisplayString
   MAX-ACCESS  read-write
   STATUS      current
   DESCRIPTION
      "Path: ethernet2.editConf.pppoEClient.ppp.encSessionSecret"
   ::= {er1645v2Lan2FGUPppOEEntry 252248064}

er1645v2Lan2FGUPppOEPppServiceName OBJECT-TYPE
   SYNTAX      DisplayString
   MAX-ACCESS  read-write
   STATUS      current
   DESCRIPTION
      "Path: ethernet2.editConf.pppoEClient.ppp.serviceName"
   ::= {er1645v2Lan2FGUPppOEEntry 252116992}

er1645v2Lan2FGUPppOEIpH OBJECT-TYPE
   SYNTAX      SEQUENCE OF Er1645v2Lan2FGUPppOEIpHEntry
   MAX-ACCESS  not-accessible
   STATUS      current
   DESCRIPTION
      ""
   ::= {er1645v2Lan2FGUPppOE 51314688}

er1645v2Lan2FGUPppOEIpHEntry OBJECT-TYPE
   SYNTAX      Er1645v2Lan2FGUPppOEIpHEntry
   MAX-ACCESS  not-accessible
   STATUS      current
   DESCRIPTION
      ""
   INDEX      { er1645v2Lan2FGUPppOETableIx,
                er1645v2Lan2FGUPppOEIpHTableIx }
   ::= {er1645v2Lan2FGUPppOEIpH 1}

Er1645v2Lan2FGUPppOEIpHEntry ::=
   SEQUENCE
      {
      er1645v2Lan2FGUPppOEIpHActions
         VariableLengthTableActions,
      er1645v2Lan2FGUPppOEIpHTableIx
         TableIndex,
      er1645v2Lan2FGUPppOEIpHAddress
         IpAddress,
      er1645v2Lan2FGUPppOEIpHDhcpRelayOptionSubscriberId
         DisplayString
      }

er1645v2Lan2FGUPppOEIpHActions OBJECT-TYPE
   SYNTAX      VariableLengthTableActions
   MAX-ACCESS  read-write
   STATUS      current
   DESCRIPTION
      "By way of this field, some manipulations
       on this table may be performed."
   ::= {er1645v2Lan2FGUPppOEIpHEntry 2}

er1645v2Lan2FGUPppOEIpHTableIx OBJECT-TYPE
   SYNTAX      TableIndex
   MAX-ACCESS  not-accessible
   STATUS      current
   DESCRIPTION
      ""
   ::= {er1645v2Lan2FGUPppOEIpHEntry 11}

er1645v2Lan2FGUPppOEIpHAddress OBJECT-TYPE
   SYNTAX      IpAddress
   MAX-ACCESS  read-write
   STATUS      current
   DESCRIPTION
      "Path: ethernet2.editConf.pppoEClient.ip.helpers.address"
   ::= {er1645v2Lan2FGUPppOEIpHEntry 16777216}

er1645v2Lan2FGUPppOEIpHDhcpRelayOptionSubscriberId OBJECT-TYPE
   SYNTAX      DisplayString
   MAX-ACCESS  read-write
   STATUS      current
   DESCRIPTION
      "Path: ethernet2.editConf.pppoEClient.ip.helpers.dhcpRelayOption.subscriberId"
   ::= {er1645v2Lan2FGUPppOEIpHEntry 33947648}

er1645v2Lan2FGUPppOEIpV6Addresses OBJECT-TYPE
   SYNTAX      SEQUENCE OF Er1645v2Lan2FGUPppOEIpV6AddressesEntry
   MAX-ACCESS  not-accessible
   STATUS      current
   DESCRIPTION
      ""
   ::= {er1645v2Lan2FGUPppOE 704839680}

er1645v2Lan2FGUPppOEIpV6AddressesEntry OBJECT-TYPE
   SYNTAX      Er1645v2Lan2FGUPppOEIpV6AddressesEntry
   MAX-ACCESS  not-accessible
   STATUS      current
   DESCRIPTION
      ""
   INDEX      { er1645v2Lan2FGUPppOETableIx,
                er1645v2Lan2FGUPppOEIpV6AddressesTableIx }
   ::= {er1645v2Lan2FGUPppOEIpV6Addresses 1}

Er1645v2Lan2FGUPppOEIpV6AddressesEntry ::=
   SEQUENCE
      {
      er1645v2Lan2FGUPppOEIpV6AddressesActions
         VariableLengthTableActions,
      er1645v2Lan2FGUPppOEIpV6AddressesTableIx
         TableIndex,
      er1645v2Lan2FGUPppOEIpV6AddressesType
         INTEGER,
      er1645v2Lan2FGUPppOEIpV6AddressesAddress
         Ipv6Address,
      er1645v2Lan2FGUPppOEIpV6AddressesPrefixLength
         Integer32,
      er1645v2Lan2FGUPppOEIpV6AddressesGeneralPrefix
         DisplayString,
      er1645v2Lan2FGUPppOEIpV6AddressesRaSend
         INTEGER,
      er1645v2Lan2FGUPppOEIpV6AddressesRaOnLinkFlag
         INTEGER,
      er1645v2Lan2FGUPppOEIpV6AddressesRaAutoFlag
         INTEGER,
      er1645v2Lan2FGUPppOEIpV6AddressesRaValidLifeTime
         TimeTicks,
      er1645v2Lan2FGUPppOEIpV6AddressesRaValidLTMode
         INTEGER,
      er1645v2Lan2FGUPppOEIpV6AddressesRaPrefLifeTime
         TimeTicks,
      er1645v2Lan2FGUPppOEIpV6AddressesRaPrefLTMode
         INTEGER
      }

er1645v2Lan2FGUPppOEIpV6AddressesActions OBJECT-TYPE
   SYNTAX      VariableLengthTableActions
   MAX-ACCESS  read-write
   STATUS      current
   DESCRIPTION
      "By way of this field, some manipulations
       on this table may be performed."
   ::= {er1645v2Lan2FGUPppOEIpV6AddressesEntry 2}

er1645v2Lan2FGUPppOEIpV6AddressesTableIx OBJECT-TYPE
   SYNTAX      TableIndex
   MAX-ACCESS  not-accessible
   STATUS      current
   DESCRIPTION
      ""
   ::= {er1645v2Lan2FGUPppOEIpV6AddressesEntry 11}

er1645v2Lan2FGUPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.pppoEClient.ipV6.addresses.type

       Possibilities:
               unicast   (0)
               eui64   (1)
               anycast   (2)
               linkLocal   (3)
               generalPrefix   (4)"
   ::= {er1645v2Lan2FGUPppOEIpV6AddressesEntry 50331648}

er1645v2Lan2FGUPppOEIpV6AddressesAddress OBJECT-TYPE
   SYNTAX      Ipv6Address
   MAX-ACCESS  read-write
   STATUS      current
   DESCRIPTION
      "Path: ethernet2.editConf.pppoEClient.ipV6.addresses.address

       ipv6 address"
   ::= {er1645v2Lan2FGUPppOEIpV6AddressesEntry 16777216}

er1645v2Lan2FGUPppOEIpV6AddressesPrefixLength OBJECT-TYPE
   SYNTAX      Integer32
   MAX-ACCESS  read-write
   STATUS      current
   DESCRIPTION
      "Path: ethernet2.editConf.pppoEClient.ipV6.addresses.prefixLength"
   ::= {er1645v2Lan2FGUPppOEIpV6AddressesEntry 33554432}

er1645v2Lan2FGUPppOEIpV6AddressesGeneralPrefix OBJECT-TYPE
   SYNTAX      DisplayString
   MAX-ACCESS  read-write
   STATUS      current
   DESCRIPTION
      "Path: ethernet2.editConf.pppoEClient.ipV6.addresses.generalPrefix"
   ::= {er1645v2Lan2FGUPppOEIpV6AddressesEntry 83886080}

er1645v2Lan2FGUPppOEIpV6AddressesRaSend OBJECT-TYPE
   SYNTAX      INTEGER
               {
               disabled (0),
               enabled (1)
               }
   MAX-ACCESS  read-write
   STATUS      current
   DESCRIPTION
      "Path: ethernet2.editConf.pppoEClient.ipV6.addresses.ra.send

       Possibilities:
               disabled   (0)
               enabled   (1)"
   ::= {er1645v2Lan2FGUPppOEIpV6AddressesEntry 67174400}

er1645v2Lan2FGUPppOEIpV6AddressesRaOnLinkFlag OBJECT-TYPE
   SYNTAX      INTEGER
               {
               disabled (0),
               enabled (1)
               }
   MAX-ACCESS  read-write
   STATUS      current
   DESCRIPTION
      "Path: ethernet2.editConf.pppoEClient.ipV6.addresses.ra.onLinkFlag

       Possibilities:
               disabled   (0)
               enabled   (1)"
   ::= {er1645v2Lan2FGUPppOEIpV6AddressesEntry 67371008}

er1645v2Lan2FGUPppOEIpV6AddressesRaAutoFlag OBJECT-TYPE
   SYNTAX      INTEGER
               {
               disabled (0),
               enabled (1)
               }
   MAX-ACCESS  read-write
   STATUS      current
   DESCRIPTION
      "Path: ethernet2.editConf.pppoEClient.ipV6.addresses.ra.autonomousFlag

       Possibilities:
               disabled   (0)
               enabled   (1)"
   ::= {er1645v2Lan2FGUPppOEIpV6AddressesEntry 67567616}

er1645v2Lan2FGUPppOEIpV6AddressesRaValidLifeTime OBJECT-TYPE
   SYNTAX      TimeTicks
   MAX-ACCESS  read-write
   STATUS      current
   DESCRIPTION
      "Path: ethernet2.editConf.pppoEClient.ipV6.addresses.ra.validLifeTime

       Time in centi-second."
   ::= {er1645v2Lan2FGUPppOEIpV6AddressesEntry 67239936}

er1645v2Lan2FGUPppOEIpV6AddressesRaValidLTMode OBJECT-TYPE
   SYNTAX      INTEGER
               {
               fixed (0),
               infinite (2)
               }
   MAX-ACCESS  read-write
   STATUS      current
   DESCRIPTION
      "Path: ethernet2.editConf.pppoEClient.ipV6.addresses.ra.validLifeTimeMode

       Possibilities:
               fixed   (0)
               infinite   (2)"
   ::= {er1645v2Lan2FGUPppOEIpV6AddressesEntry 67305472}

er1645v2Lan2FGUPppOEIpV6AddressesRaPrefLifeTime OBJECT-TYPE
   SYNTAX      TimeTicks
   MAX-ACCESS  read-write
   STATUS      current
   DESCRIPTION
      "Path: ethernet2.editConf.pppoEClient.ipV6.addresses.ra.prefLifeTime

       Time in centi-second."
   ::= {er1645v2Lan2FGUPppOEIpV6AddressesEntry 67436544}

er1645v2Lan2FGUPppOEIpV6AddressesRaPrefLTMode OBJECT-TYPE
   SYNTAX      INTEGER
               {
               fixed (0),
               infinite (2)
               }
   MAX-ACCESS  read-write
   STATUS      current
   DESCRIPTION
      "Path: ethernet2.editConf.pppoEClient.ipV6.addresses.ra.prefLifeTimeMode

       Possibilities:
               fixed   (0)
               infinite   (2)"
   ::= {er1645v2Lan2FGUPppOEIpV6AddressesEntry 67502080}

er1645v2Lan2FGUPppOEIpV6RaDnsOptionsRdnssServers OBJECT-TYPE
   SYNTAX      SEQUENCE OF Er1645v2Lan2FGUPppOEIpV6RaDnsOptionsRdnssServersEntry
   MAX-ACCESS  not-accessible
   STATUS      current
   DESCRIPTION
      ""
   ::= {er1645v2Lan2FGUPppOE 705039144}

er1645v2Lan2FGUPppOEIpV6RaDnsOptionsRdnssServersEntry OBJECT-TYPE
   SYNTAX      Er1645v2Lan2FGUPppOEIpV6RaDnsOptionsRdnssServersEntry
   MAX-ACCESS  not-accessible
   STATUS      current
   DESCRIPTION
      ""
   INDEX      { er1645v2Lan2FGUPppOETableIx,
                er1645v2Lan2FGUPppOEIpV6RaDnsOptionsRdnssServersTableIx }
   ::= {er1645v2Lan2FGUPppOEIpV6RaDnsOptionsRdnssServers 1}

Er1645v2Lan2FGUPppOEIpV6RaDnsOptionsRdnssServersEntry ::=
   SEQUENCE
      {
      er1645v2Lan2FGUPppOEIpV6RaDnsOptionsRdnssServersActions
         VariableLengthTableActions,
      er1645v2Lan2FGUPppOEIpV6RaDnsOptionsRdnssServersTableIx
         TableIndex,
      er1645v2Lan2FGUPppOEIpV6RaDnsOptionsRdnssServersAddress
         Ipv6Address
      }

er1645v2Lan2FGUPppOEIpV6RaDnsOptionsRdnssServersActions OBJECT-TYPE
   SYNTAX      VariableLengthTableActions
   MAX-ACCESS  read-write
   STATUS      current
   DESCRIPTION
      "By way of this field, some manipulations
       on this table may be performed."
   ::= {er1645v2Lan2FGUPppOEIpV6RaDnsOptionsRdnssServersEntry 2}

er1645v2Lan2FGUPppOEIpV6RaDnsOptionsRdnssServersTableIx OBJECT-TYPE
   SYNTAX      TableIndex
   MAX-ACCESS  not-accessible
   STATUS      current
   DESCRIPTION
      ""
   ::= {er1645v2Lan2FGUPppOEIpV6RaDnsOptionsRdnssServersEntry 11}

er1645v2Lan2FGUPppOEIpV6RaDnsOptionsRdnssServersAddress OBJECT-TYPE
   SYNTAX      Ipv6Address
   MAX-ACCESS  read-write
   STATUS      current
   DESCRIPTION
      "Path: ethernet2.editConf.pppoEClient.ipV6.ra.dnsOptions.rdnss.servers.address

       ipv6 address"
   ::= {er1645v2Lan2FGUPppOEIpV6RaDnsOptionsRdnssServersEntry 16777216}

er1645v2Lan2FGUPppOEIpV6RaDnsOptionsDnsslDomains OBJECT-TYPE
   SYNTAX      SEQUENCE OF Er1645v2Lan2FGUPppOEIpV6RaDnsOptionsDnsslDomainsEntry
   MAX-ACCESS  not-accessible
   STATUS      current
   DESCRIPTION
      ""
   ::= {er1645v2Lan2FGUPppOE 705039176}

er1645v2Lan2FGUPppOEIpV6RaDnsOptionsDnsslDomainsEntry OBJECT-TYPE
   SYNTAX      Er1645v2Lan2FGUPppOEIpV6RaDnsOptionsDnsslDomainsEntry
   MAX-ACCESS  not-accessible
   STATUS      current
   DESCRIPTION
      ""
   INDEX      { er1645v2Lan2FGUPppOETableIx,
                er1645v2Lan2FGUPppOEIpV6RaDnsOptionsDnsslDomainsTableIx }
   ::= {er1645v2Lan2FGUPppOEIpV6RaDnsOptionsDnsslDomains 1}

Er1645v2Lan2FGUPppOEIpV6RaDnsOptionsDnsslDomainsEntry ::=
   SEQUENCE
      {
      er1645v2Lan2FGUPppOEIpV6RaDnsOptionsDnsslDomainsActions
         VariableLengthTableActions,
      er1645v2Lan2FGUPppOEIpV6RaDnsOptionsDnsslDomainsTableIx
         TableIndex,
      er1645v2Lan2FGUPppOEIpV6RaDnsOptionsDnsslDomainsName
         DisplayString
      }

er1645v2Lan2FGUPppOEIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGUPppOEIpV6RaDnsOptionsDnsslDomainsEntry 2}

er1645v2Lan2FGUPppOEIpV6RaDnsOptionsDnsslDomainsTableIx OBJECT-TYPE
   SYNTAX      TableIndex
   MAX-ACCESS  not-accessible
   STATUS      current
   DESCRIPTION
      ""
   ::= {er1645v2Lan2FGUPppOEIpV6RaDnsOptionsDnsslDomainsEntry 11}

er1645v2Lan2FGUPppOEIpV6RaDnsOptionsDnsslDomainsName OBJECT-TYPE
   SYNTAX      DisplayString
   MAX-ACCESS  read-write
   STATUS      current
   DESCRIPTION
      "Path: ethernet2.editConf.pppoEClient.ipV6.ra.dnsOptions.dnssl.domains.name"
   ::= {er1645v2Lan2FGUPppOEIpV6RaDnsOptionsDnsslDomainsEntry 16777216}

er1645v2Lan2FGUPppOEIpV6DhcpClientUserClassOpt OBJECT-TYPE
   SYNTAX      SEQUENCE OF Er1645v2Lan2FGUPppOEIpV6DhcpClientUserClassOptEntry
   MAX-ACCESS  not-accessible
   STATUS      current
   DESCRIPTION
      ""
   ::= {er1645v2Lan2FGUPppOE 705312768}

er1645v2Lan2FGUPppOEIpV6DhcpClientUserClassOptEntry OBJECT-TYPE
   SYNTAX      Er1645v2Lan2FGUPppOEIpV6DhcpClientUserClassOptEntry
   MAX-ACCESS  not-accessible
   STATUS      current
   DESCRIPTION
      ""
   INDEX      { er1645v2Lan2FGUPppOETableIx,
                er1645v2Lan2FGUPppOEIpV6DhcpClientUserClassOptTableIx }
   ::= {er1645v2Lan2FGUPppOEIpV6DhcpClientUserClassOpt 1}

Er1645v2Lan2FGUPppOEIpV6DhcpClientUserClassOptEntry ::=
   SEQUENCE
      {
      er1645v2Lan2FGUPppOEIpV6DhcpClientUserClassOptActions
         VariableLengthTableActions,
      er1645v2Lan2FGUPppOEIpV6DhcpClientUserClassOptTableIx
         TableIndex,
      er1645v2Lan2FGUPppOEIpV6DhcpClientUserClassOptValueAscii
         DisplayString,
      er1645v2Lan2FGUPppOEIpV6DhcpClientUserClassOptValueDecimal
         Integer32,
      er1645v2Lan2FGUPppOEIpV6DhcpClientUserClassOptValueHexData
         OCTET STRING
      }

er1645v2Lan2FGUPppOEIpV6DhcpClientUserClassOptActions OBJECT-TYPE
   SYNTAX      VariableLengthTableActions
   MAX-ACCESS  read-write
   STATUS      current
   DESCRIPTION
      "By way of this field, some manipulations
       on this table may be performed."
   ::= {er1645v2Lan2FGUPppOEIpV6DhcpClientUserClassOptEntry 2}

er1645v2Lan2FGUPppOEIpV6DhcpClientUserClassOptTableIx OBJECT-TYPE
   SYNTAX      TableIndex
   MAX-ACCESS  not-accessible
   STATUS      current
   DESCRIPTION
      ""
   ::= {er1645v2Lan2FGUPppOEIpV6DhcpClientUserClassOptEntry 11}

er1645v2Lan2FGUPppOEIpV6DhcpClientUserClassOptValueAscii OBJECT-TYPE
   SYNTAX      DisplayString
   MAX-ACCESS  read-write
   STATUS      current
   DESCRIPTION
      "Path: ethernet2.editConf.pppoEClient.ipV6.dhcp.client.userClassOpt.value.ascii"
   ::= {er1645v2Lan2FGUPppOEIpV6DhcpClientUserClassOptEntry 16842752}

er1645v2Lan2FGUPppOEIpV6DhcpClientUserClassOptValueDecimal OBJECT-TYPE
   SYNTAX      Integer32
   MAX-ACCESS  read-write
   STATUS      current
   DESCRIPTION
      "Path: ethernet2.editConf.pppoEClient.ipV6.dhcp.client.userClassOpt.value.decimal"
   ::= {er1645v2Lan2FGUPppOEIpV6DhcpClientUserClassOptEntry 16908288}

er1645v2Lan2FGUPppOEIpV6DhcpClientUserClassOptValueHexData OBJECT-TYPE
   SYNTAX      OCTET STRING
   MAX-ACCESS  read-write
   STATUS      current
   DESCRIPTION
      "Path: ethernet2.editConf.pppoEClient.ipV6.dhcp.client.userClassOpt.value.hexData"
   ::= {er1645v2Lan2FGUPppOEIpV6DhcpClientUserClassOptEntry 16973824}

er1645v2Lan2FGUPppOEIpV6DhcpClientVendorCl OBJECT-TYPE
   SYNTAX      SEQUENCE OF Er1645v2Lan2FGUPppOEIpV6DhcpClientVendorClEntry
   MAX-ACCESS  not-accessible
   STATUS      current
   DESCRIPTION
      ""
   ::= {er1645v2Lan2FGUPppOE 705313792}

er1645v2Lan2FGUPppOEIpV6DhcpClientVendorClEntry OBJECT-TYPE
   SYNTAX      Er1645v2Lan2FGUPppOEIpV6DhcpClientVendorClEntry
   MAX-ACCESS  not-accessible
   STATUS      current
   DESCRIPTION
      ""
   INDEX      { er1645v2Lan2FGUPppOETableIx,
                er1645v2Lan2FGUPppOEIpV6DhcpClientVendorClTableIx }
   ::= {er1645v2Lan2FGUPppOEIpV6DhcpClientVendorCl 1}

Er1645v2Lan2FGUPppOEIpV6DhcpClientVendorClEntry ::=
   SEQUENCE
      {
      er1645v2Lan2FGUPppOEIpV6DhcpClientVendorClActions
         VariableLengthTableActions,
      er1645v2Lan2FGUPppOEIpV6DhcpClientVendorClTableIx
         TableIndex,
      er1645v2Lan2FGUPppOEIpV6DhcpClientVendorClValueAscii
         DisplayString,
      er1645v2Lan2FGUPppOEIpV6DhcpClientVendorClValueDecimal
         Integer32,
      er1645v2Lan2FGUPppOEIpV6DhcpClientVendorClValueHexData
         OCTET STRING
      }

er1645v2Lan2FGUPppOEIpV6DhcpClientVendorClActions OBJECT-TYPE
   SYNTAX      VariableLengthTableActions
   MAX-ACCESS  read-write
   STATUS      current
   DESCRIPTION
      "By way of this field, some manipulations
       on this table may be performed."
   ::= {er1645v2Lan2FGUPppOEIpV6DhcpClientVendorClEntry 2}

er1645v2Lan2FGUPppOEIpV6DhcpClientVendorClTableIx OBJECT-TYPE
   SYNTAX      TableIndex
   MAX-ACCESS  not-accessible
   STATUS      current
   DESCRIPTION
      ""
   ::= {er1645v2Lan2FGUPppOEIpV6DhcpClientVendorClEntry 11}

er1645v2Lan2FGUPppOEIpV6DhcpClientVendorClValueAscii OBJECT-TYPE
   SYNTAX      DisplayString
   MAX-ACCESS  read-write
   STATUS      current
   DESCRIPTION
      "Path: ethernet2.editConf.pppoEClient.ipV6.dhcp.client.vendorClassOpt.value.ascii"
   ::= {er1645v2Lan2FGUPppOEIpV6DhcpClientVendorClEntry 16842752}

er1645v2Lan2FGUPppOEIpV6DhcpClientVendorClValueDecimal OBJECT-TYPE
   SYNTAX      Integer32
   MAX-ACCESS  read-write
   STATUS      current
   DESCRIPTION
      "Path: ethernet2.editConf.pppoEClient.ipV6.dhcp.client.vendorClassOpt.value.decimal"
   ::= {er1645v2Lan2FGUPppOEIpV6DhcpClientVendorClEntry 16908288}

er1645v2Lan2FGUPppOEIpV6DhcpClientVendorClValueHexData OBJECT-TYPE
   SYNTAX      OCTET STRING
   MAX-ACCESS  read-write
   STATUS      current
   DESCRIPTION
      "Path: ethernet2.editConf.pppoEClient.ipV6.dhcp.client.vendorClassOpt.value.hexData"
   ::= {er1645v2Lan2FGUPppOEIpV6DhcpClientVendorClEntry 16973824}

er1645v2Lan2FGUPppOEIpV6DhcpRelayDestinations OBJECT-TYPE
   SYNTAX      SEQUENCE OF Er1645v2Lan2FGUPppOEIpV6DhcpRelayDestinationsEntry
   MAX-ACCESS  not-accessible
   STATUS      current
   DESCRIPTION
      ""
   ::= {er1645v2Lan2FGUPppOE 705323072}

er1645v2Lan2FGUPppOEIpV6DhcpRelayDestinationsEntry OBJECT-TYPE
   SYNTAX      Er1645v2Lan2FGUPppOEIpV6DhcpRelayDestinationsEntry
   MAX-ACCESS  not-accessible
   STATUS      current
   DESCRIPTION
      ""
   INDEX      { er1645v2Lan2FGUPppOETableIx,
                er1645v2Lan2FGUPppOEIpV6DhcpRelayDestinationsTableIx }
   ::= {er1645v2Lan2FGUPppOEIpV6DhcpRelayDestinations 1}

Er1645v2Lan2FGUPppOEIpV6DhcpRelayDestinationsEntry ::=
   SEQUENCE
      {
      er1645v2Lan2FGUPppOEIpV6DhcpRelayDestinationsActions
         VariableLengthTableActions,
      er1645v2Lan2FGUPppOEIpV6DhcpRelayDestinationsTableIx
         TableIndex,
      er1645v2Lan2FGUPppOEIpV6DhcpRelayDestinationsAddress
         Ipv6Address,
      er1645v2Lan2FGUPppOEIpV6DhcpRelayDestinationsInterface
         DisplayString
      }

er1645v2Lan2FGUPppOEIpV6DhcpRelayDestinationsActions OBJECT-TYPE
   SYNTAX      VariableLengthTableActions
   MAX-ACCESS  read-write
   STATUS      current
   DESCRIPTION
      "By way of this field, some manipulations
       on this table may be performed."
   ::= {er1645v2Lan2FGUPppOEIpV6DhcpRelayDestinationsEntry 2}

er1645v2Lan2FGUPppOEIpV6DhcpRelayDestinationsTableIx OBJECT-TYPE
   SYNTAX      TableIndex
   MAX-ACCESS  not-accessible
   STATUS      current
   DESCRIPTION
      ""
   ::= {er1645v2Lan2FGUPppOEIpV6DhcpRelayDestinationsEntry 11}

er1645v2Lan2FGUPppOEIpV6DhcpRelayDestinationsAddress OBJECT-TYPE
   SYNTAX      Ipv6Address
   MAX-ACCESS  read-write
   STATUS      current
   DESCRIPTION
      "Path: ethernet2.editConf.pppoEClient.ipV6.dhcp.relay.destinations.address

       ipv6 address"
   ::= {er1645v2Lan2FGUPppOEIpV6DhcpRelayDestinationsEntry 16777216}

er1645v2Lan2FGUPppOEIpV6DhcpRelayDestinationsInterface OBJECT-TYPE
   SYNTAX      DisplayString
   MAX-ACCESS  read-write
   STATUS      current
   DESCRIPTION
      "Path: ethernet2.editConf.pppoEClient.ipV6.dhcp.relay.destinations.interface"
   ::= {er1645v2Lan2FGUPppOEIpV6DhcpRelayDestinationsEntry 33554432}


er1645v2Lan2FGUPppoEServer OBJECT-TYPE
   SYNTAX      DisplayString
   MAX-ACCESS  read-write
   STATUS      current
   DESCRIPTION
      "Path: ethernet2.editConf.pppoEServer
       Info: ppp server name on interface"
   ::= {er1645v2Lan2FGU 37}


er1645v2Lan2FGUInboundHwPriority OBJECT IDENTIFIER ::= {er1645v2Lan2FGU 231}

er1645v2Lan2FGUInboundHwPrioritySSC OBJECT IDENTIFIER ::= {er1645v2Lan2FGUInboundHwPriority 1}

er1645v2Lan2FGUInboundHwPriorityEntry OBJECT IDENTIFIER ::= {er1645v2Lan2FGUInboundHwPrioritySSC 1}

er1645v2Lan2FGUInboundHwPriorityNone OBJECT-TYPE
   SYNTAX      OCTET STRING
   MAX-ACCESS  read-write
   STATUS      current
   DESCRIPTION
      "Path: ethernet2.editConf.inboundHwPriority.none"
   ::= {er1645v2Lan2FGUInboundHwPriorityEntry 16777216}

er1645v2Lan2FGUInboundHwPriorityMapCosToQueueP0 OBJECT-TYPE
   SYNTAX      INTEGER
               {
               queue1 (1),
               queue2 (2)
               }
   MAX-ACCESS  read-write
   STATUS      current
   DESCRIPTION
      "Path: ethernet2.editConf.inboundHwPriority.mapCosToQueue.p0

       Possibilities:
               queue1   (1)
               queue2   (2)"
   ::= {er1645v2Lan2FGUInboundHwPriorityEntry 33619968}

er1645v2Lan2FGUInboundHwPriorityMapCosToQueueP1 OBJECT-TYPE
   SYNTAX      INTEGER
               {
               queue1 (1),
               queue2 (2)
               }
   MAX-ACCESS  read-write
   STATUS      current
   DESCRIPTION
      "Path: ethernet2.editConf.inboundHwPriority.mapCosToQueue.p1

       Possibilities:
               queue1   (1)
               queue2   (2)"
   ::= {er1645v2Lan2FGUInboundHwPriorityEntry 33685504}

er1645v2Lan2FGUInboundHwPriorityMapCosToQueueP2 OBJECT-TYPE
   SYNTAX      INTEGER
               {
               queue1 (1),
               queue2 (2)
               }
   MAX-ACCESS  read-write
   STATUS      current
   DESCRIPTION
      "Path: ethernet2.editConf.inboundHwPriority.mapCosToQueue.p2

       Possibilities:
               queue1   (1)
               queue2   (2)"
   ::= {er1645v2Lan2FGUInboundHwPriorityEntry 33751040}

er1645v2Lan2FGUInboundHwPriorityMapCosToQueueP3 OBJECT-TYPE
   SYNTAX      INTEGER
               {
               queue1 (1),
               queue2 (2)
               }
   MAX-ACCESS  read-write
   STATUS      current
   DESCRIPTION
      "Path: ethernet2.editConf.inboundHwPriority.mapCosToQueue.p3

       Possibilities:
               queue1   (1)
               queue2   (2)"
   ::= {er1645v2Lan2FGUInboundHwPriorityEntry 33816576}

er1645v2Lan2FGUInboundHwPriorityMapCosToQueueP4 OBJECT-TYPE
   SYNTAX      INTEGER
               {
               queue1 (1),
               queue2 (2)
               }
   MAX-ACCESS  read-write
   STATUS      current
   DESCRIPTION
      "Path: ethernet2.editConf.inboundHwPriority.mapCosToQueue.p4

       Possibilities:
               queue1   (1)
               queue2   (2)"
   ::= {er1645v2Lan2FGUInboundHwPriorityEntry 33882112}

er1645v2Lan2FGUInboundHwPriorityMapCosToQueueP5 OBJECT-TYPE
   SYNTAX      INTEGER
               {
               queue1 (1),
               queue2 (2)
               }
   MAX-ACCESS  read-write
   STATUS      current
   DESCRIPTION
      "Path: ethernet2.editConf.inboundHwPriority.mapCosToQueue.p5

       Possibilities:
               queue1   (1)
               queue2   (2)"
   ::= {er1645v2Lan2FGUInboundHwPriorityEntry 33947648}

er1645v2Lan2FGUInboundHwPriorityMapCosToQueueP6 OBJECT-TYPE
   SYNTAX      INTEGER
               {
               queue1 (1),
               queue2 (2)
               }
   MAX-ACCESS  read-write
   STATUS      current
   DESCRIPTION
      "Path: ethernet2.editConf.inboundHwPriority.mapCosToQueue.p6

       Possibilities:
               queue1   (1)
               queue2   (2)"
   ::= {er1645v2Lan2FGUInboundHwPriorityEntry 34013184}

er1645v2Lan2FGUInboundHwPriorityMapCosToQueueP7 OBJECT-TYPE
   SYNTAX      INTEGER
               {
               queue1 (1),
               queue2 (2)
               }
   MAX-ACCESS  read-write
   STATUS      current
   DESCRIPTION
      "Path: ethernet2.editConf.inboundHwPriority.mapCosToQueue.p7

       Possibilities:
               queue1   (1)
               queue2   (2)"
   ::= {er1645v2Lan2FGUInboundHwPriorityEntry 34078720}

er1645v2Lan2FGUInboundHwPriorityMapDscpToQueue OBJECT-TYPE
   SYNTAX      SEQUENCE OF Er1645v2Lan2FGUInboundHwPriorityMapDscpToQueueEntry
   MAX-ACCESS  not-accessible
   STATUS      current
   DESCRIPTION
      ""
   ::= {er1645v2Lan2FGUInboundHwPriority 50331648}

er1645v2Lan2FGUInboundHwPriorityMapDscpToQueueEntry OBJECT-TYPE
   SYNTAX      Er1645v2Lan2FGUInboundHwPriorityMapDscpToQueueEntry
   MAX-ACCESS  not-accessible
   STATUS      current
   DESCRIPTION
      ""
   INDEX      { er1645v2Lan2FGUInboundHwPriorityMapDscpToQueueTableIx }
   ::= {er1645v2Lan2FGUInboundHwPriorityMapDscpToQueue 1}

Er1645v2Lan2FGUInboundHwPriorityMapDscpToQueueEntry ::=
   SEQUENCE
      {
      er1645v2Lan2FGUInboundHwPriorityMapDscpToQueueActions
         VariableLengthTableActions,
      er1645v2Lan2FGUInboundHwPriorityMapDscpToQueueTableIx
         TableIndex,
      er1645v2Lan2FGUInboundHwPriorityMapDscpToQueueStartDscp
         INTEGER,
      er1645v2Lan2FGUInboundHwPriorityMapDscpToQueueEndDscp
         INTEGER,
      er1645v2Lan2FGUInboundHwPriorityMapDscpToQueueQueue
         INTEGER
      }

er1645v2Lan2FGUInboundHwPriorityMapDscpToQueueActions OBJECT-TYPE
   SYNTAX      VariableLengthTableActions
   MAX-ACCESS  read-write
   STATUS      current
   DESCRIPTION
      "By way of this field, some manipulations
       on this table may be performed."
   ::= {er1645v2Lan2FGUInboundHwPriorityMapDscpToQueueEntry 2}

er1645v2Lan2FGUInboundHwPriorityMapDscpToQueueTableIx OBJECT-TYPE
   SYNTAX      TableIndex
   MAX-ACCESS  not-accessible
   STATUS      current
   DESCRIPTION
      ""
   ::= {er1645v2Lan2FGUInboundHwPriorityMapDscpToQueueEntry 11}

er1645v2Lan2FGUInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2FGUInboundHwPriorityMapDscpToQueueEntry 16777216}

er1645v2Lan2FGUInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2FGUInboundHwPriorityMapDscpToQueueEntry 33554432}

er1645v2Lan2FGUInboundHwPriorityMapDscpToQueueQueue OBJECT-TYPE
   SYNTAX      INTEGER
               {
               queue1 (1),
               queue2 (2)
               }
   MAX-ACCESS  read-write
   STATUS      current
   DESCRIPTION
      "Path: ethernet2.editConf.inboundHwPriority.mapDscpToQueue.queue

       Possibilities:
               queue1   (1)
               queue2   (2)"
   ::= {er1645v2Lan2FGUInboundHwPriorityMapDscpToQueueEntry 50331648}


er1645v2Lan2FGUName OBJECT-TYPE
   SYNTAX      DisplayString
   MAX-ACCESS  read-write
   STATUS      current
   DESCRIPTION
      "Path: ethernet2.editConf.name
       Info: config interface name"
   ::= {er1645v2Lan2FGU 2}


er1645v2Lan2FGUAdapter OBJECT-TYPE
   SYNTAX      INTEGER
               {
               autoDetect (0),
               s10MbhalfDuplex (1),
               s10MbfullDuplex (2),
               s100MbhalfDuplex (3),
               s100MbfullDuplex (4)
               }
   MAX-ACCESS  read-write
   STATUS      current
   DESCRIPTION
      "Path: ethernet2.editConf.adapter

       Possibilities:
               autoDetect   (0)
               10Mb/halfDuplex   (1)
               10Mb/fullDuplex   (2)
               100Mb/halfDuplex   (3)
               100Mb/fullDuplex   (4)"
   ::= {er1645v2Lan2FGU 32}



sr1645v2Lan2FGU OBJECT IDENTIFIER ::= {r1645v2Lan2FGU 14}


sr1645v2Lan2FGUDescr OBJECT-TYPE
   SYNTAX      DisplayString
   MAX-ACCESS  read-only
   STATUS      current
   DESCRIPTION
      "Path: ethernet2.status.ifDescr
       Info: ifDescr"
   ::= {sr1645v2Lan2FGU 101}


sr1645v2Lan2FGUType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet2.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2Lan2FGU 102}


sr1645v2Lan2FGUMtu OBJECT-TYPE
   SYNTAX      Integer32
   MAX-ACCESS  read-only
   STATUS      current
   DESCRIPTION
      "Path: ethernet2.status.ifMtu
       Info: ifMtu"
   ::= {sr1645v2Lan2FGU 103}


sr1645v2Lan2FGUOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ifOperStatus
       Info: ifOperStatus

       Possibilities:
               up   (1)
               down   (2)
               testing   (3)
               unknown   (4)
               dormant   (5)
               notPresent   (6)
               lowerLayerDown   (7)"
   ::= {sr1645v2Lan2FGU 107}


sr1645v2Lan2FGULastChange OBJECT-TYPE
   SYNTAX      TimeTicks
   MAX-ACCESS  read-only
   STATUS      current
   DESCRIPTION
      "Path: ethernet2.status.ifLastChange
       Info: ifLastChange

       Time in centi-second."
   ::= {sr1645v2Lan2FGU 108}


sr1645v2Lan2FGULastChangeD OBJECT-TYPE
   SYNTAX      DisplayString
   MAX-ACCESS  read-only
   STATUS      current
   DESCRIPTION
      "Path: ethernet2.status.ifLastChangeDate
       Info: ifLastChangeDate"
   ::= {sr1645v2Lan2FGU 183}


sr1645v2Lan2FGUSpeed OBJECT-TYPE
   SYNTAX      Gauge32
   MAX-ACCESS  read-only
   STATUS      current
   DESCRIPTION
      "Path: ethernet2.status.ifSpeed
       Info: ifSpeed

       32 bit unsigned gauge value."
   ::= {sr1645v2Lan2FGU 104}


sr1645v2Lan2FGUSnmpIndex OBJECT-TYPE
   SYNTAX      Integer32
   MAX-ACCESS  read-only
   STATUS      current
   DESCRIPTION
      "Path: ethernet2.status.snmpIndex
       Info: SNMP index assigned to this object"
   ::= {sr1645v2Lan2FGU 269}


sr1645v2Lan2FGUIp OBJECT IDENTIFIER ::= {sr1645v2Lan2FGU 16}

sr1645v2Lan2FGUIpSSC OBJECT IDENTIFIER ::= {sr1645v2Lan2FGUIp 1}

sr1645v2Lan2FGUIpEntry OBJECT IDENTIFIER ::= {sr1645v2Lan2FGUIpSSC 1}

sr1645v2Lan2FGUIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ip.status

       Possibilities:
               up   (1)
               down   (2)
               testing   (3)
               unknown   (4)
               dormant   (5)
               notPresent   (6)
               lowerLayerDown   (7)"
   ::= {sr1645v2Lan2FGUIpEntry 1795162112}

sr1645v2Lan2FGUIpAddress OBJECT-TYPE
   SYNTAX      IpAddress
   MAX-ACCESS  read-only
   STATUS      current
   DESCRIPTION
      "Path: ethernet2.status.ip.address"
   ::= {sr1645v2Lan2FGUIpEntry 2030043136}

sr1645v2Lan2FGUIpNetMask OBJECT-TYPE
   SYNTAX      IpAddress
   MAX-ACCESS  read-only
   STATUS      current
   DESCRIPTION
      "Path: ethernet2.status.ip.netMask"
   ::= {sr1645v2Lan2FGUIpEntry 2063597568}

sr1645v2Lan2FGUIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.ip.dhcp.status

       Possibilities:
               none   (0)
               selecting   (1)
               requesting   (2)
               rebinding   (3)
               bound   (4)
               renewing   (5)
               rebooting   (6)
               initreboot   (7)"
   ::= {sr1645v2Lan2FGUIpEntry 402718720}

sr1645v2Lan2FGUIpDhcpLeaseTime OBJECT-TYPE
   SYNTAX      TimeTicks
   MAX-ACCESS  read-only
   STATUS      current
   DESCRIPTION
      "Path: ethernet2.status.ip.dhcp.leaseTime

       Time in centi-second."
   ::= {sr1645v2Lan2FGUIpEntry 402784256}

sr1645v2Lan2FGUIpSecondaryIp OBJECT-TYPE
   SYNTAX      SEQUENCE OF Sr1645v2Lan2FGUIpSecondaryIpEntry
   MAX-ACCESS  not-accessible
   STATUS      current
   DESCRIPTION
      ""
   ::= {sr1645v2Lan2FGUIp 385875968}

sr1645v2Lan2FGUIpSecondaryIpEntry OBJECT-TYPE
   SYNTAX      Sr1645v2Lan2FGUIpSecondaryIpEntry
   MAX-ACCESS  not-accessible
   STATUS      current
   DESCRIPTION
      ""
   INDEX      { sr1645v2Lan2FGUIpSecondaryIpTableIx }
   ::= {sr1645v2Lan2FGUIpSecondaryIp 1}

Sr1645v2Lan2FGUIpSecondaryIpEntry ::=
   SEQUENCE
      {
      sr1645v2Lan2FGUIpSecondaryIpTableIx
         TableIndex,
      sr1645v2Lan2FGUIpSecondaryIpAddress
         IpAddress,
      sr1645v2Lan2FGUIpSecondaryIpNetMask
         IpAddress
      }

sr1645v2Lan2FGUIpSecondaryIpTableIx OBJECT-TYPE
   SYNTAX      TableIndex
   MAX-ACCESS  not-accessible
   STATUS      current
   DESCRIPTION
      ""
   ::= {sr1645v2Lan2FGUIpSecondaryIpEntry 11}

sr1645v2Lan2FGUIpSecondaryIpAddress OBJECT-TYPE
   SYNTAX      IpAddress
   MAX-ACCESS  read-only
   STATUS      current
   DESCRIPTION
      "Path: ethernet2.status.ip.secondaryIp.address"
   ::= {sr1645v2Lan2FGUIpSecondaryIpEntry 2030043136}

sr1645v2Lan2FGUIpSecondaryIpNetMask OBJECT-TYPE
   SYNTAX      IpAddress
   MAX-ACCESS  read-only
   STATUS      current
   DESCRIPTION
      "Path: ethernet2.status.ip.secondaryIp.netMask"
   ::= {sr1645v2Lan2FGUIpSecondaryIpEntry 2063597568}


sr1645v2Lan2FGUArpCache OBJECT IDENTIFIER ::= {sr1645v2Lan2FGU 11}

sr1645v2Lan2FGUArpCacheSSCTable OBJECT-TYPE
   SYNTAX      SEQUENCE OF Sr1645v2Lan2FGUArpCacheEntry
   MAX-ACCESS  not-accessible
   STATUS      current
   DESCRIPTION
      "arp cache of ethernet interface"
   ::= {sr1645v2Lan2FGUArpCache 1}

sr1645v2Lan2FGUArpCacheEntry OBJECT-TYPE
   SYNTAX      Sr1645v2Lan2FGUArpCacheEntry
   MAX-ACCESS  not-accessible
   STATUS      current
   DESCRIPTION
      ""
   INDEX      { sr1645v2Lan2FGUArpCacheTableIx }
   ::= {sr1645v2Lan2FGUArpCacheSSCTable 1}

Sr1645v2Lan2FGUArpCacheEntry ::=
   SEQUENCE
      {
      sr1645v2Lan2FGUArpCacheTableIx
         TableIndex,
      sr1645v2Lan2FGUArpCacheMacAddress
         OCTET STRING,
      sr1645v2Lan2FGUArpCacheIpAddress
         IpAddress,
      sr1645v2Lan2FGUArpCacheType
         INTEGER,
      sr1645v2Lan2FGUArpCacheTimeOut
         TimeTicks
      }

sr1645v2Lan2FGUArpCacheTableIx OBJECT-TYPE
   SYNTAX      TableIndex
   MAX-ACCESS  not-accessible
   STATUS      current
   DESCRIPTION
      ""
   ::= {sr1645v2Lan2FGUArpCacheEntry 11}

sr1645v2Lan2FGUArpCacheMacAddress OBJECT-TYPE
   SYNTAX      OCTET STRING
   MAX-ACCESS  read-only
   STATUS      current
   DESCRIPTION
      "Path: ethernet2.status.arpCache.macAddress

       MAC address."
   ::= {sr1645v2Lan2FGUArpCacheEntry 16777216}

sr1645v2Lan2FGUArpCacheIpAddress OBJECT-TYPE
   SYNTAX      IpAddress
   MAX-ACCESS  read-only
   STATUS      current
   DESCRIPTION
      "Path: ethernet2.status.arpCache.ipAddress"
   ::= {sr1645v2Lan2FGUArpCacheEntry 33554432}

sr1645v2Lan2FGUArpCacheType OBJECT-TYPE
   SYNTAX      INTEGER
               {
               static (0),
               dynamic (1)
               }
   MAX-ACCESS  read-only
   STATUS      current
   DESCRIPTION
      "Path: ethernet2.status.arpCache.type

       Possibilities:
               static   (0)
               dynamic   (1)"
   ::= {sr1645v2Lan2FGUArpCacheEntry 50331648}

sr1645v2Lan2FGUArpCacheTimeOut OBJECT-TYPE
   SYNTAX      TimeTicks
   MAX-ACCESS  read-only
   STATUS      current
   DESCRIPTION
      "Path: ethernet2.status.arpCache.timeOut

       Time in centi-second."
   ::= {sr1645v2Lan2FGUArpCacheEntry 67108864}


sr1645v2Lan2FGUBrS OBJECT IDENTIFIER ::= {sr1645v2Lan2FGU 28}

sr1645v2Lan2FGUBrSSSC OBJECT IDENTIFIER ::= {sr1645v2Lan2FGUBrS 1}

sr1645v2Lan2FGUBrSEntry OBJECT IDENTIFIER ::= {sr1645v2Lan2FGUBrSSSC 1}

sr1645v2Lan2FGUBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.bridging.status

       Possibilities:
               disabled   (0)
               discarding   (1)
               learning   (2)
               forwarding   (3)
               backupBlockedIntfDown   (256)
               backupBlockedIntfUp   (259)
               shutdown   (255)"
   ::= {sr1645v2Lan2FGUBrSEntry 16777216}

sr1645v2Lan2FGUBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.bridging.spanningTree.portRole

       Possibilities:
               none   (0)
               root   (1)
               designated   (2)
               alternate   (3)
               backup   (4)
               disabled   (5)
               master   (6)"
   ::= {sr1645v2Lan2FGUBrSEntry 33619968}

sr1645v2Lan2FGUBrSStPortId OBJECT-TYPE
   SYNTAX      Integer32
   MAX-ACCESS  read-only
   STATUS      current
   DESCRIPTION
      "Path: ethernet2.status.bridging.spanningTree.portId"
   ::= {sr1645v2Lan2FGUBrSEntry 33685504}

sr1645v2Lan2FGUBrSStPpCostExtPathCost OBJECT-TYPE
   SYNTAX      Integer32
   MAX-ACCESS  read-only
   STATUS      current
   DESCRIPTION
      "Path: ethernet2.status.bridging.spanningTree.portPathCosts.extPathCost"
   ::= {sr1645v2Lan2FGUBrSEntry 33751296}

sr1645v2Lan2FGUBrSStPpCostIntPathCost OBJECT-TYPE
   SYNTAX      Integer32
   MAX-ACCESS  read-only
   STATUS      current
   DESCRIPTION
      "Path: ethernet2.status.bridging.spanningTree.portPathCosts.intPathCost"
   ::= {sr1645v2Lan2FGUBrSEntry 33751552}

sr1645v2Lan2FGUBrSStExtRpCost OBJECT-TYPE
   SYNTAX      Integer32
   MAX-ACCESS  read-only
   STATUS      current
   DESCRIPTION
      "Path: ethernet2.status.bridging.spanningTree.extRootPathCost"
   ::= {sr1645v2Lan2FGUBrSEntry 33816576}

sr1645v2Lan2FGUBrSStIntRpCost OBJECT-TYPE
   SYNTAX      Integer32
   MAX-ACCESS  read-only
   STATUS      current
   DESCRIPTION
      "Path: ethernet2.status.bridging.spanningTree.intRootPathCost"
   ::= {sr1645v2Lan2FGUBrSEntry 33882112}

sr1645v2Lan2FGUBrSStDesBrIdPriority OBJECT-TYPE
   SYNTAX      Integer32
   MAX-ACCESS  read-only
   STATUS      current
   DESCRIPTION
      "Path: ethernet2.status.bridging.spanningTree.designatedBridgeId.priority"
   ::= {sr1645v2Lan2FGUBrSEntry 33947904}

sr1645v2Lan2FGUBrSStDesBrIdMacAddress OBJECT-TYPE
   SYNTAX      OCTET STRING
   MAX-ACCESS  read-only
   STATUS      current
   DESCRIPTION
      "Path: ethernet2.status.bridging.spanningTree.designatedBridgeId.macAddress

       MAC address."
   ::= {sr1645v2Lan2FGUBrSEntry 33948160}

sr1645v2Lan2FGUBrSStDesPrtId OBJECT-TYPE
   SYNTAX      Integer32
   MAX-ACCESS  read-only
   STATUS      current
   DESCRIPTION
      "Path: ethernet2.status.bridging.spanningTree.designatedPortId"
   ::= {sr1645v2Lan2FGUBrSEntry 34013184}

sr1645v2Lan2FGUBrSStDesInt OBJECT-TYPE
   SYNTAX      INTEGER
               {
               no (0),
               yes (1)
               }
   MAX-ACCESS  read-only
   STATUS      current
   DESCRIPTION
      "Path: ethernet2.status.bridging.spanningTree.designatedOrInternal

       Possibilities:
               no   (0)
               yes   (1)"
   ::= {sr1645v2Lan2FGUBrSEntry 34078720}

sr1645v2Lan2FGUBrSStEdgeDetection OBJECT-TYPE
   SYNTAX      INTEGER
               {
               none (0),
               edge (1),
               notEdge (2)
               }
   MAX-ACCESS  read-only
   STATUS      current
   DESCRIPTION
      "Path: ethernet2.status.bridging.spanningTree.edgeDetection

       Possibilities:
               none   (0)
               edge   (1)
               notEdge   (2)"
   ::= {sr1645v2Lan2FGUBrSEntry 34144256}


sr1645v2Lan2FGUMacAddress OBJECT-TYPE
   SYNTAX      OCTET STRING
   MAX-ACCESS  read-only
   STATUS      current
   DESCRIPTION
      "Path: ethernet2.status.macAddress
       Info: ifPhysAddress

       MAC address."
   ::= {sr1645v2Lan2FGU 105}


sr1645v2Lan2FGUIpAdEntBcastAddr OBJECT-TYPE
   SYNTAX      Integer32
   MAX-ACCESS  read-only
   STATUS      current
   DESCRIPTION
      "Path: ethernet2.status.ipAdEntBcastAddr
       Info: ipAdEntBcastAddr"
   ::= {sr1645v2Lan2FGU 124}


sr1645v2Lan2FGUIpAdEntReasmMaxSize OBJECT-TYPE
   SYNTAX      Integer32
   MAX-ACCESS  read-only
   STATUS      current
   DESCRIPTION
      "Path: ethernet2.status.ipAdEntReasmMaxSize
       Info: ipAdEntReasmMaxSize"
   ::= {sr1645v2Lan2FGU 125}


sr1645v2Lan2FGUAdapter OBJECT IDENTIFIER ::= {sr1645v2Lan2FGU 145}

sr1645v2Lan2FGUAdapterSSC OBJECT IDENTIFIER ::= {sr1645v2Lan2FGUAdapter 1}

sr1645v2Lan2FGUAdapterEntry OBJECT IDENTIFIER ::= {sr1645v2Lan2FGUAdapterSSC 1}

sr1645v2Lan2FGUAdapterSpeed OBJECT-TYPE
   SYNTAX      INTEGER
               {
               s10 (0),
               s100 (1),
               s1000 (2),
               s200 (3)
               }
   MAX-ACCESS  read-only
   STATUS      current
   DESCRIPTION
      "Path: ethernet2.status.adapter.speed

       Possibilities:
               10   (0)
               100   (1)
               1000   (2)
               200   (3)"
   ::= {sr1645v2Lan2FGUAdapterEntry 16777216}

sr1645v2Lan2FGUAdapterDuplex OBJECT-TYPE
   SYNTAX      INTEGER
               {
               halfDuplex (0),
               fullDuplex (1)
               }
   MAX-ACCESS  read-only
   STATUS      current
   DESCRIPTION
      "Path: ethernet2.status.adapter.duplex

       Possibilities:
               halfDuplex   (0)
               fullDuplex   (1)"
   ::= {sr1645v2Lan2FGUAdapterEntry 33554432}


sr1645v2Lan2FGUOam OBJECT IDENTIFIER ::= {sr1645v2Lan2FGU 901}

sr1645v2Lan2FGUOamSSC OBJECT IDENTIFIER ::= {sr1645v2Lan2FGUOam 1}

sr1645v2Lan2FGUOamEntry OBJECT IDENTIFIER ::= {sr1645v2Lan2FGUOamSSC 1}

sr1645v2Lan2FGUOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet2.status.oam.discovery

       Possibilities:
               fault   (0)
               sendLocal   (1)
               passiveWait   (2)
               sendLocalRemote   (3)
               sendLocalRemoteOk   (4)
               sendAny   (5)"
   ::= {sr1645v2Lan2FGUOamEntry 16777216}

sr1645v2Lan2FGUOamLoopback OBJECT-TYPE
   SYNTAX      INTEGER
               {
               idle (0),
               waiting (1),
               localRunning (2),
               remoteRunning (3)
               }
   MAX-ACCESS  read-only
   STATUS      current
   DESCRIPTION
      "Path: ethernet2.status.oam.loopback

       Possibilities:
               idle   (0)
               waiting   (1)
               localRunning   (2)
               remoteRunning   (3)"
   ::= {sr1645v2Lan2FGUOamEntry 33554432}

sr1645v2Lan2FGUOamLocalInfoVersion OBJECT-TYPE
   SYNTAX      Integer32
   MAX-ACCESS  read-only
   STATUS      current
   DESCRIPTION
      "Path: ethernet2.status.oam.localInfo.version"
   ::= {sr1645v2Lan2FGUOamEntry 50397184}

sr1645v2Lan2FGUOamLocalInfoRevision OBJECT-TYPE
   SYNTAX      Integer32
   MAX-ACCESS  read-only
   STATUS      current
   DESCRIPTION
      "Path: ethernet2.status.oam.localInfo.revision"
   ::= {sr1645v2Lan2FGUOamEntry 50462720}

sr1645v2Lan2FGUOamLocalInfoStateMuxAction OBJECT-TYPE
   SYNTAX      INTEGER
               {
               forwarding (0),
               discarding (1)
               }
   MAX-ACCESS  read-only
   STATUS      current
   DESCRIPTION
      "Path: ethernet2.status.oam.localInfo.state.muxAction

       Possibilities:
               forwarding   (0)
               discarding   (1)"
   ::= {sr1645v2Lan2FGUOamEntry 50528512}

sr1645v2Lan2FGUOamLocalInfoStateParserAction OBJECT-TYPE
   SYNTAX      INTEGER
               {
               forwarding (0),
               loopback (1),
               discarding (2),
               reserved (3)
               }
   MAX-ACCESS  read-only
   STATUS      current
   DESCRIPTION
      "Path: ethernet2.status.oam.localInfo.state.parserAction

       Possibilities:
               forwarding   (0)
               loopback   (1)
               discarding   (2)
               reserved   (3)"
   ::= {sr1645v2Lan2FGUOamEntry 50528768}

sr1645v2Lan2FGUOamLocalInfoOui OBJECT-TYPE
   SYNTAX      OCTET STRING
   MAX-ACCESS  read-only
   STATUS      current
   DESCRIPTION
      "Path: ethernet2.status.oam.localInfo.oui"
   ::= {sr1645v2Lan2FGUOamEntry 50593792}

sr1645v2Lan2FGUOamLocalInfoVendorInfo OBJECT-TYPE
   SYNTAX      OCTET STRING
   MAX-ACCESS  read-only
   STATUS      current
   DESCRIPTION
      "Path: ethernet2.status.oam.localInfo.vendorInfo"
   ::= {sr1645v2Lan2FGUOamEntry 50659328}

sr1645v2Lan2FGUOamLocalInfoVarRetrieval OBJECT-TYPE
   SYNTAX      INTEGER
               {
               notSupported (0),
               supported (1)
               }
   MAX-ACCESS  read-only
   STATUS      current
   DESCRIPTION
      "Path: ethernet2.status.oam.localInfo.varRetrieval

       Possibilities:
               notSupported   (0)
               supported   (1)"
   ::= {sr1645v2Lan2FGUOamEntry 50724864}

sr1645v2Lan2FGUOamLocalInfoLinkEvents OBJECT-TYPE
   SYNTAX      INTEGER
               {
               ignored (0),
               interpreted (1)
               }
   MAX-ACCESS  read-only
   STATUS      current
   DESCRIPTION
      "Path: ethernet2.status.oam.localInfo.linkEvents

       Possibilities:
               ignored   (0)
               interpreted   (1)"
   ::= {sr1645v2Lan2FGUOamEntry 50790400}

sr1645v2Lan2FGUOamLocalInfoLoopback OBJECT-TYPE
   SYNTAX      INTEGER
               {
               notSupported (0),
               supported (1)
               }
   MAX-ACCESS  read-only
   STATUS      current
   DESCRIPTION
      "Path: ethernet2.status.oam.localInfo.loopback

       Possibilities:
               notSupported   (0)
               supported   (1)"
   ::= {sr1645v2Lan2FGUOamEntry 50855936}

sr1645v2Lan2FGUOamLocalInfoUnidirectional OBJECT-TYPE
   SYNTAX      INTEGER
               {
               notSupported (0),
               supported (1)
               }
   MAX-ACCESS  read-only
   STATUS      current
   DESCRIPTION
      "Path: ethernet2.status.oam.localInfo.unidirectional

       Possibilities:
               notSupported   (0)
               supported   (1)"
   ::= {sr1645v2Lan2FGUOamEntry 50921472}

sr1645v2Lan2FGUOamLocalInfoMode OBJECT-TYPE
   SYNTAX      INTEGER
               {
               passive (0),
               active (1)
               }
   MAX-ACCESS  read-only
   STATUS      current
   DESCRIPTION
      "Path: ethernet2.status.oam.localInfo.mode

       Possibilities:
               passive   (0)
               active   (1)"
   ::= {sr1645v2Lan2FGUOamEntry 50987008}

sr1645v2Lan2FGUOamLocalInfoMaxPduSize OBJECT-TYPE
   SYNTAX      Integer32
   MAX-ACCESS  read-only
   STATUS      current
   DESCRIPTION
      "Path: ethernet2.status.oam.localInfo.maxPduSize"
   ::= {sr1645v2Lan2FGUOamEntry 51052544}

sr1645v2Lan2FGUOamRemoteInfoVersion OBJECT-TYPE
   SYNTAX      Integer32
   MAX-ACCESS  read-only
   STATUS      current
   DESCRIPTION
      "Path: ethernet2.status.oam.remoteInfo.version"
   ::= {sr1645v2Lan2FGUOamEntry 67174400}

sr1645v2Lan2FGUOamRemoteInfoRevision OBJECT-TYPE
   SYNTAX      Integer32
   MAX-ACCESS  read-only
   STATUS      current
   DESCRIPTION
      "Path: ethernet2.status.oam.remoteInfo.revision"
   ::= {sr1645v2Lan2FGUOamEntry 67239936}

sr1645v2Lan2FGUOamRemoteInfoStateMuxAction OBJECT-TYPE
   SYNTAX      INTEGER
               {
               forwarding (0),
               discarding (1)
               }
   MAX-ACCESS  read-only
   STATUS      current
   DESCRIPTION
      "Path: ethernet2.status.oam.remoteInfo.state.muxAction

       Possibilities:
               forwarding   (0)
               discarding   (1)"
   ::= {sr1645v2Lan2FGUOamEntry 67305728}

sr1645v2Lan2FGUOamRemoteInfoStateParserAction OBJECT-TYPE
   SYNTAX      INTEGER
               {
               forwarding (0),
               loopback (1),
               discarding (2),
               reserved (3)
               }
   MAX-ACCESS  read-only
   STATUS      current
   DESCRIPTION
      "Path: ethernet2.status.oam.remoteInfo.state.parserAction

       Possibilities:
               forwarding   (0)
               loopback   (1)
               discarding   (2)
               reserved   (3)"
   ::= {sr1645v2Lan2FGUOamEntry 67305984}

sr1645v2Lan2FGUOamRemoteInfoOui OBJECT-TYPE
   SYNTAX      OCTET STRING
   MAX-ACCESS  read-only
   STATUS      current
   DESCRIPTION
      "Path: ethernet2.status.oam.remoteInfo.oui"
   ::= {sr1645v2Lan2FGUOamEntry 67371008}

sr1645v2Lan2FGUOamRemoteInfoVendorInfo OBJECT-TYPE
   SYNTAX      OCTET STRING
   MAX-ACCESS  read-only
   STATUS      current
   DESCRIPTION
      "Path: ethernet2.status.oam.remoteInfo.vendorInfo"
   ::= {sr1645v2Lan2FGUOamEntry 67436544}

sr1645v2Lan2FGUOamRemoteInfoVarRetrieval OBJECT-TYPE
   SYNTAX      INTEGER
               {
               notSupported (0),
               supported (1)
               }
   MAX-ACCESS  read-only
   STATUS      current
   DESCRIPTION
      "Path: ethernet2.status.oam.remoteInfo.varRetrieval

       Possibilities:
               notSupported   (0)
               supported   (1)"
   ::= {sr1645v2Lan2FGUOamEntry 67502080}

sr1645v2Lan2FGUOamRemoteInfoLinkEvents OBJECT-TYPE
   SYNTAX      INTEGER
               {
               ignored (0),
               interpreted (1)
               }
   MAX-ACCESS  read-only
   STATUS      current
   DESCRIPTION
      "Path: ethernet2.status.oam.remoteInfo.linkEvents

       Possibilities:
               ignored   (0)
               interpreted   (1)"
   ::= {sr1645v2Lan2FGUOamEntry 67567616}

sr1645v2Lan2FGUOamRemoteInfoLoopback OBJECT-TYPE
   SYNTAX      INTEGER
               {
               notSupported (0),
               supported (1)
               }
   MAX-ACCESS  read-only
   STATUS      current
   DESCRIPTION
      "Path: ethernet2.status.oam.remoteInfo.loopback

       Possibilities:
               notSupported   (0)
               supported   (1)"
   ::= {sr1645v2Lan2FGUOamEntry 67633152}

sr1645v2Lan2FGUOamRemoteInfoUnidirectional OBJECT-TYPE
   SYNTAX      INTEGER
               {
               notSupported (0),
               supported (1)
               }
   MAX-ACCESS  read-only
   STATUS      current
   DESCRIPTION
      "Path: ethernet2.status.oam.remoteInfo.unidirectional

       Possibilities:
               notSupported   (0)
               supported   (1)"
   ::= {sr1645v2Lan2FGUOamEntry 67698688}

sr1645v2Lan2FGUOamRemoteInfoMode OBJECT-TYPE
   SYNTAX      INTEGER
               {
               passive (0),
               active (1)
               }
   MAX-ACCESS  read-only
   STATUS      current
   DESCRIPTION
      "Path: ethernet2.status.oam.remoteInfo.mode

       Possibilities:
               passive   (0)
               active   (1)"
   ::= {sr1645v2Lan2FGUOamEntry 67764224}

sr1645v2Lan2FGUOamRemoteInfoMaxPduSize OBJECT-TYPE
   SYNTAX      Integer32
   MAX-ACCESS  read-only
   STATUS      current
   DESCRIPTION
      "Path: ethernet2.status.oam.remoteInfo.maxPduSize"
   ::= {sr1645v2Lan2FGUOamEntry 67829760}

sr1645v2Lan2FGUOamEventsErroredSymbolWindow OBJECT-TYPE
   SYNTAX      Integer32
   UNITS       "symbols"
   MAX-ACCESS  read-only
   STATUS      current
   DESCRIPTION
      "Path: ethernet2.status.oam.events.erroredSymbol.window

       unit name = symbols"
   ::= {sr1645v2Lan2FGUOamEntry 83951872}

sr1645v2Lan2FGUOamEventsErroredSymbolThreshold OBJECT-TYPE
   SYNTAX      OCTET STRING
   UNITS       "symbols"
   MAX-ACCESS  read-only
   STATUS      current
   DESCRIPTION
      "Path: ethernet2.status.oam.events.erroredSymbol.threshold

       unit name = symbols"
   ::= {sr1645v2Lan2FGUOamEntry 83952128}

sr1645v2Lan2FGUOamEventsErroredFramePeriodWindow OBJECT-TYPE
   SYNTAX      INTEGER
               {
               default (0)
               }
   UNITS       "frames"
   MAX-ACCESS  read-only
   STATUS      current
   DESCRIPTION
      "Path: ethernet2.status.oam.events.erroredFramePeriod.window

       unit name = frames

       Possibilities:
               default   (0)"
   ::= {sr1645v2Lan2FGUOamEntry 84017408}

sr1645v2Lan2FGUOamEventsErroredFramePeriodThreshold OBJECT-TYPE
   SYNTAX      Integer32
   UNITS       "frames"
   MAX-ACCESS  read-only
   STATUS      current
   DESCRIPTION
      "Path: ethernet2.status.oam.events.erroredFramePeriod.threshold

       unit name = frames"
   ::= {sr1645v2Lan2FGUOamEntry 84017664}

sr1645v2Lan2FGUOamEventsErroredFrameWindow OBJECT-TYPE
   SYNTAX      Integer32
   UNITS       "100msec"
   MAX-ACCESS  read-only
   STATUS      current
   DESCRIPTION
      "Path: ethernet2.status.oam.events.erroredFrame.window

       unit name = 100msec"
   ::= {sr1645v2Lan2FGUOamEntry 84082944}

sr1645v2Lan2FGUOamEventsErroredFrameThreshold OBJECT-TYPE
   SYNTAX      Integer32
   UNITS       "frames"
   MAX-ACCESS  read-only
   STATUS      current
   DESCRIPTION
      "Path: ethernet2.status.oam.events.erroredFrame.threshold

       unit name = frames"
   ::= {sr1645v2Lan2FGUOamEntry 84083200}

sr1645v2Lan2FGUOamEventsErroredFrameSecondsWindow OBJECT-TYPE
   SYNTAX      Integer32
   UNITS       "100msec"
   MAX-ACCESS  read-only
   STATUS      current
   DESCRIPTION
      "Path: ethernet2.status.oam.events.erroredFrameSeconds.window

       unit name = 100msec"
   ::= {sr1645v2Lan2FGUOamEntry 84148480}

sr1645v2Lan2FGUOamEventsErroredFrameSecondsThreshold OBJECT-TYPE
   SYNTAX      Integer32
   UNITS       "frames"
   MAX-ACCESS  read-only
   STATUS      current
   DESCRIPTION
      "Path: ethernet2.status.oam.events.erroredFrameSeconds.threshold

       unit name = frames"
   ::= {sr1645v2Lan2FGUOamEntry 84148736}


sr1645v2Lan2FGUOamEventLog OBJECT IDENTIFIER ::= {sr1645v2Lan2FGU 911}

sr1645v2Lan2FGUOamEventLogSSCTable OBJECT-TYPE
   SYNTAX      SEQUENCE OF Sr1645v2Lan2FGUOamEventLogEntry
   MAX-ACCESS  not-accessible
   STATUS      current
   DESCRIPTION
      "OAM event log"
   ::= {sr1645v2Lan2FGUOamEventLog 1}

sr1645v2Lan2FGUOamEventLogEntry OBJECT-TYPE
   SYNTAX      Sr1645v2Lan2FGUOamEventLogEntry
   MAX-ACCESS  not-accessible
   STATUS      current
   DESCRIPTION
      ""
   INDEX      { sr1645v2Lan2FGUOamEventLogTableIx }
   ::= {sr1645v2Lan2FGUOamEventLogSSCTable 1}

Sr1645v2Lan2FGUOamEventLogEntry ::=
   SEQUENCE
      {
      sr1645v2Lan2FGUOamEventLogTableIx
         TableIndex,
      sr1645v2Lan2FGUOamEventLogSysUpTime
         TimeTicks,
      sr1645v2Lan2FGUOamEventLogLocation
         INTEGER,
      sr1645v2Lan2FGUOamEventLogType
         INTEGER,
      sr1645v2Lan2FGUOamEventLogOui
         OCTET STRING,
      sr1645v2Lan2FGUOamEventLogWindow
         Counter64,
      sr1645v2Lan2FGUOamEventLogThreshold
         Counter64,
      sr1645v2Lan2FGUOamEventLogTotal
         Counter32,
      sr1645v2Lan2FGUOamEventLogValue
         Counter64,
      sr1645v2Lan2FGUOamEventLogRunningTotal
         Counter64
      }

sr1645v2Lan2FGUOamEventLogTableIx OBJECT-TYPE
   SYNTAX      TableIndex
   MAX-ACCESS  not-accessible
   STATUS      current
   DESCRIPTION
      ""
   ::= {sr1645v2Lan2FGUOamEventLogEntry 11}

sr1645v2Lan2FGUOamEventLogSysUpTime OBJECT-TYPE
   SYNTAX      TimeTicks
   MAX-ACCESS  read-only
   STATUS      current
   DESCRIPTION
      "Path: ethernet2.status.oamEventLog.sysUpTime

       Time in centi-second."
   ::= {sr1645v2Lan2FGUOamEventLogEntry 16777216}

sr1645v2Lan2FGUOamEventLogLocation OBJECT-TYPE
   SYNTAX      INTEGER
               {
               local (1),
               remote (2)
               }
   MAX-ACCESS  read-only
   STATUS      current
   DESCRIPTION
      "Path: ethernet2.status.oamEventLog.location

       Possibilities:
               local   (1)
               remote   (2)"
   ::= {sr1645v2Lan2FGUOamEventLogEntry 33554432}

sr1645v2Lan2FGUOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet2.status.oamEventLog.type

       Possibilities:
               erroredSymbols   (1)
               erroredFramePeriod   (2)
               erroredFrame   (3)
               erroredFrameSeconds   (4)
               linkFault   (256)
               dyingGasp   (257)
               criticalLink   (258)"
   ::= {sr1645v2Lan2FGUOamEventLogEntry 50331648}

sr1645v2Lan2FGUOamEventLogOui OBJECT-TYPE
   SYNTAX      OCTET STRING
   MAX-ACCESS  read-only
   STATUS      current
   DESCRIPTION
      "Path: ethernet2.status.oamEventLog.oui"
   ::= {sr1645v2Lan2FGUOamEventLogEntry 67108864}

sr1645v2Lan2FGUOamEventLogWindow OBJECT-TYPE
   SYNTAX      Counter64
   MAX-ACCESS  read-only
   STATUS      current
   DESCRIPTION
      "Path: ethernet2.status.oamEventLog.window

       64 bit unsigned wrappable counter."
   ::= {sr1645v2Lan2FGUOamEventLogEntry 83886080}

sr1645v2Lan2FGUOamEventLogThreshold OBJECT-TYPE
   SYNTAX      Counter64
   MAX-ACCESS  read-only
   STATUS      current
   DESCRIPTION
      "Path: ethernet2.status.oamEventLog.threshold

       64 bit unsigned wrappable counter."
   ::= {sr1645v2Lan2FGUOamEventLogEntry 100663296}

sr1645v2Lan2FGUOamEventLogTotal OBJECT-TYPE
   SYNTAX      Counter32
   MAX-ACCESS  read-only
   STATUS      current
   DESCRIPTION
      "Path: ethernet2.status.oamEventLog.total

       32 bit unsigned wrappable counter."
   ::= {sr1645v2Lan2FGUOamEventLogEntry 117440512}

sr1645v2Lan2FGUOamEventLogValue OBJECT-TYPE
   SYNTAX      Counter64
   MAX-ACCESS  read-only
   STATUS      current
   DESCRIPTION
      "Path: ethernet2.status.oamEventLog.value

       64 bit unsigned wrappable counter."
   ::= {sr1645v2Lan2FGUOamEventLogEntry 134217728}

sr1645v2Lan2FGUOamEventLogRunningTotal OBJECT-TYPE
   SYNTAX      Counter64
   MAX-ACCESS  read-only
   STATUS      current
   DESCRIPTION
      "Path: ethernet2.status.oamEventLog.runningTotal

       64 bit unsigned wrappable counter."
   ::= {sr1645v2Lan2FGUOamEventLogEntry 150994944}


sr1645v2Lan2FGULst OBJECT IDENTIFIER ::= {sr1645v2Lan2FGU 18}

sr1645v2Lan2FGULstSSC OBJECT IDENTIFIER ::= {sr1645v2Lan2FGULst 1}

sr1645v2Lan2FGULstEntry OBJECT IDENTIFIER ::= {sr1645v2Lan2FGULstSSC 1}

sr1645v2Lan2FGULstTrackedInterface OBJECT-TYPE
   SYNTAX      DisplayString
   MAX-ACCESS  read-only
   STATUS      current
   DESCRIPTION
      "Path: ethernet2.status.linkStateTracking.trackedInterface"
   ::= {sr1645v2Lan2FGULstEntry 16777216}

sr1645v2Lan2FGULstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet2.status.linkStateTracking.ifOperStatus

       Possibilities:
               up   (1)
               down   (2)
               testing   (3)
               unknown   (4)
               dormant   (5)
               notPresent   (6)
               lowerLayerDown   (7)
                  (255)"
   ::= {sr1645v2Lan2FGULstEntry 50331648}


sr1645v2Lan2FGUVlan OBJECT IDENTIFIER ::= {sr1645v2Lan2FGU 34}

sr1645v2Lan2FGUVlanSSCTable OBJECT-TYPE
   SYNTAX      SEQUENCE OF Sr1645v2Lan2FGUVlanEntry
   MAX-ACCESS  not-accessible
   STATUS      current
   DESCRIPTION
      ""
   ::= {sr1645v2Lan2FGUVlan 1}

sr1645v2Lan2FGUVlanEntry OBJECT-TYPE
   SYNTAX      Sr1645v2Lan2FGUVlanEntry
   MAX-ACCESS  not-accessible
   STATUS      current
   DESCRIPTION
      ""
   INDEX      { sr1645v2Lan2FGUVlanTableIx }
   ::= {sr1645v2Lan2FGUVlanSSCTable 1}

Sr1645v2Lan2FGUVlanEntry ::=
   SEQUENCE
      {
      sr1645v2Lan2FGUVlanTableIx
         TableIndex,
      sr1645v2Lan2FGUVlanName
         DisplayString,
      sr1645v2Lan2FGUVlanMode
         INTEGER,
      sr1645v2Lan2FGUVlanIfOperStatus
         INTEGER,
      sr1645v2Lan2FGUVlanIfLastChange
         TimeTicks,
      sr1645v2Lan2FGUVlanIfLastChangeDate
         DisplayString,
      sr1645v2Lan2FGUVlanIpAddress
         IpAddress,
      sr1645v2Lan2FGUVlanIpNetMask
         IpAddress,
      sr1645v2Lan2FGUVlanIpRemote
         IpAddress,
      sr1645v2Lan2FGUVlanIpDhcpStatus
         INTEGER,
      sr1645v2Lan2FGUVlanIpDhcpLeaseTime
         TimeTicks,
      sr1645v2Lan2FGUVlanIpV6State
         INTEGER,
      sr1645v2Lan2FGUVlanIpV6InterfaceId
         OCTET STRING,
      sr1645v2Lan2FGUVlanIpV6LinkMtu
         Integer32,
      sr1645v2Lan2FGUVlanIpV6HopLimit
         Integer32,
      sr1645v2Lan2FGUVlanIpV6DhcpIaid
         Counter32,
      sr1645v2Lan2FGUVlanIpV6RaRcvOption
         Integer32,
      sr1645v2Lan2FGUVlanBridgingStatus
         INTEGER,
      sr1645v2Lan2FGUVlanBridgingSpanningTreePortRole
         INTEGER,
      sr1645v2Lan2FGUVlanBridgingSpanningTreePortId
         Integer32,
      sr1645v2Lan2FGUVlanBridgingSpanningTreePpCostExtPathCost
         Integer32,
      sr1645v2Lan2FGUVlanBridgingSpanningTreePpCostIntPathCost
         Integer32,
      sr1645v2Lan2FGUVlanBridgingSpanningTreeExtRpCost
         Integer32,
      sr1645v2Lan2FGUVlanBridgingSpanningTreeIntRpCost
         Integer32,
      sr1645v2Lan2FGUVlanBridgingSpanningTreeDesBrIdPriority
         Integer32,
      sr1645v2Lan2FGUVlanBridgingSpanningTreeDesBrIdMacAddress
         OCTET STRING,
      sr1645v2Lan2FGUVlanBridgingSpanningTreeDesPrtId
         Integer32,
      sr1645v2Lan2FGUVlanBridgingSpanningTreeDesInt
         INTEGER,
      sr1645v2Lan2FGUVlanBridgingSpanningTreeEdgeDetection
         INTEGER,
      sr1645v2Lan2FGUVlanVlanVid
         Integer32,
      sr1645v2Lan2FGUVlanPppOEthDiscState
         INTEGER,
      sr1645v2Lan2FGUVlanPppOEthPeerMac
         OCTET STRING,
      sr1645v2Lan2FGUVlanPppOEthServiceName
         DisplayString,
      sr1645v2Lan2FGUVlanPppLcpState
         INTEGER,
      sr1645v2Lan2FGUVlanPppIpcpState
         INTEGER,
      sr1645v2Lan2FGUVlanPppIp6cpState
         INTEGER,
      sr1645v2Lan2FGUVlanPppMyAutSt
         INTEGER,
      sr1645v2Lan2FGUVlanPppHisAutSt
         INTEGER,
      sr1645v2Lan2FGUVlanPppMru
         Integer32
      }

sr1645v2Lan2FGUVlanTableIx OBJECT-TYPE
   SYNTAX      TableIndex
   MAX-ACCESS  not-accessible
   STATUS      current
   DESCRIPTION
      ""
   ::= {sr1645v2Lan2FGUVlanEntry 11}

sr1645v2Lan2FGUVlanName OBJECT-TYPE
   SYNTAX      DisplayString
   MAX-ACCESS  read-only
   STATUS      current
   DESCRIPTION
      "Path: ethernet2.status.vlan.name"
   ::= {sr1645v2Lan2FGUVlanEntry 16777216}

sr1645v2Lan2FGUVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2FGUVlanEntry 335544320}

sr1645v2Lan2FGUVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.vlan.ifOperStatus

       Possibilities:
               up   (1)
               down   (2)
               testing   (3)
               unknown   (4)
               dormant   (5)
               notPresent   (6)
               lowerLayerDown   (7)"
   ::= {sr1645v2Lan2FGUVlanEntry 1795162112}

sr1645v2Lan2FGUVlanIfLastChange OBJECT-TYPE
   SYNTAX      TimeTicks
   MAX-ACCESS  read-only
   STATUS      current
   DESCRIPTION
      "Path: ethernet2.status.vlan.ifLastChange

       Time in centi-second."
   ::= {sr1645v2Lan2FGUVlanEntry 1811939328}

sr1645v2Lan2FGUVlanIfLastChangeDate OBJECT-TYPE
   SYNTAX      DisplayString
   MAX-ACCESS  read-only
   STATUS      current
   DESCRIPTION
      "Path: ethernet2.status.vlan.ifLastChangeDate"
   ::= {sr1645v2Lan2FGUVlanEntry 3070230528}

sr1645v2Lan2FGUVlanIpAddress OBJECT-TYPE
   SYNTAX      IpAddress
   MAX-ACCESS  read-only
   STATUS      current
   DESCRIPTION
      "Path: ethernet2.status.vlan.ip.address"
   ::= {sr1645v2Lan2FGUVlanEntry 51380224}

sr1645v2Lan2FGUVlanIpNetMask OBJECT-TYPE
   SYNTAX      IpAddress
   MAX-ACCESS  read-only
   STATUS      current
   DESCRIPTION
      "Path: ethernet2.status.vlan.ip.netMask"
   ::= {sr1645v2Lan2FGUVlanEntry 51445760}

sr1645v2Lan2FGUVlanIpRemote OBJECT-TYPE
   SYNTAX      IpAddress
   MAX-ACCESS  read-only
   STATUS      current
   DESCRIPTION
      "Path: ethernet2.status.vlan.ip.remote"
   ::= {sr1645v2Lan2FGUVlanEntry 51511296}

sr1645v2Lan2FGUVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.vlan.ip.dhcp.status

       Possibilities:
               none   (0)
               selecting   (1)
               requesting   (2)
               rebinding   (3)
               bound   (4)
               renewing   (5)
               rebooting   (6)
               initreboot   (7)"
   ::= {sr1645v2Lan2FGUVlanEntry 51904768}

sr1645v2Lan2FGUVlanIpDhcpLeaseTime OBJECT-TYPE
   SYNTAX      TimeTicks
   MAX-ACCESS  read-only
   STATUS      current
   DESCRIPTION
      "Path: ethernet2.status.vlan.ip.dhcp.leaseTime

       Time in centi-second."
   ::= {sr1645v2Lan2FGUVlanEntry 51905024}

sr1645v2Lan2FGUVlanIpV6State OBJECT-TYPE
   SYNTAX      INTEGER
               {
               disabled (0),
               enabled (1)
               }
   MAX-ACCESS  read-only
   STATUS      current
   DESCRIPTION
      "Path: ethernet2.status.vlan.ipV6.state

       Possibilities:
               disabled   (0)
               enabled   (1)"
   ::= {sr1645v2Lan2FGUVlanEntry 100728832}

sr1645v2Lan2FGUVlanIpV6InterfaceId OBJECT-TYPE
   SYNTAX      OCTET STRING
   MAX-ACCESS  read-only
   STATUS      current
   DESCRIPTION
      "Path: ethernet2.status.vlan.ipV6.interfaceId"
   ::= {sr1645v2Lan2FGUVlanEntry 100794368}

sr1645v2Lan2FGUVlanIpV6LinkMtu OBJECT-TYPE
   SYNTAX      Integer32
   MAX-ACCESS  read-only
   STATUS      current
   DESCRIPTION
      "Path: ethernet2.status.vlan.ipV6.linkMtu"
   ::= {sr1645v2Lan2FGUVlanEntry 100925440}

sr1645v2Lan2FGUVlanIpV6HopLimit OBJECT-TYPE
   SYNTAX      Integer32
   MAX-ACCESS  read-only
   STATUS      current
   DESCRIPTION
      "Path: ethernet2.status.vlan.ipV6.hopLimit"
   ::= {sr1645v2Lan2FGUVlanEntry 100990976}

sr1645v2Lan2FGUVlanIpV6DhcpIaid OBJECT-TYPE
   SYNTAX      Counter32
   MAX-ACCESS  read-only
   STATUS      current
   DESCRIPTION
      "Path: ethernet2.status.vlan.ipV6.dhcp.iaid

       32 bit unsigned wrappable counter."
   ::= {sr1645v2Lan2FGUVlanEntry 101056768}

sr1645v2Lan2FGUVlanIpV6RaRcvOption OBJECT-TYPE
   SYNTAX      Integer32
   MAX-ACCESS  read-only
   STATUS      current
   DESCRIPTION
      "Path: ethernet2.status.vlan.ipV6.raRcvOption

       Bit meanings:
               bit 0 = linkMtu,
               bit 1 = srcLinkLayer,
               bit 2 = prefixInfo,
               bit 3 = rdnss,
               bit 4 = dnssl"
   ::= {sr1645v2Lan2FGUVlanEntry 101122048}

sr1645v2Lan2FGUVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.vlan.bridging.status

       Possibilities:
               disabled   (0)
               discarding   (1)
               learning   (2)
               forwarding   (3)
               backupBlockedIntfDown   (256)
               backupBlockedIntfUp   (259)
               shutdown   (255)"
   ::= {sr1645v2Lan2FGUVlanEntry 453050368}

sr1645v2Lan2FGUVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.vlan.bridging.spanningTree.portRole

       Possibilities:
               none   (0)
               root   (1)
               designated   (2)
               alternate   (3)
               backup   (4)
               disabled   (5)
               master   (6)"
   ::= {sr1645v2Lan2FGUVlanEntry 453116160}

sr1645v2Lan2FGUVlanBridgingSpanningTreePortId OBJECT-TYPE
   SYNTAX      Integer32
   MAX-ACCESS  read-only
   STATUS      current
   DESCRIPTION
      "Path: ethernet2.status.vlan.bridging.spanningTree.portId"
   ::= {sr1645v2Lan2FGUVlanEntry 453116416}

sr1645v2Lan2FGUVlanBridgingSpanningTreePpCostExtPathCost OBJECT-TYPE
   SYNTAX      Integer32
   MAX-ACCESS  read-only
   STATUS      current
   DESCRIPTION
      "Path: ethernet2.status.vlan.bridging.spanningTree.portPathCosts.extPathCost"
   ::= {sr1645v2Lan2FGUVlanEntry 453116673}

sr1645v2Lan2FGUVlanBridgingSpanningTreePpCostIntPathCost OBJECT-TYPE
   SYNTAX      Integer32
   MAX-ACCESS  read-only
   STATUS      current
   DESCRIPTION
      "Path: ethernet2.status.vlan.bridging.spanningTree.portPathCosts.intPathCost"
   ::= {sr1645v2Lan2FGUVlanEntry 453116674}

sr1645v2Lan2FGUVlanBridgingSpanningTreeExtRpCost OBJECT-TYPE
   SYNTAX      Integer32
   MAX-ACCESS  read-only
   STATUS      current
   DESCRIPTION
      "Path: ethernet2.status.vlan.bridging.spanningTree.extRootPathCost"
   ::= {sr1645v2Lan2FGUVlanEntry 453116928}

sr1645v2Lan2FGUVlanBridgingSpanningTreeIntRpCost OBJECT-TYPE
   SYNTAX      Integer32
   MAX-ACCESS  read-only
   STATUS      current
   DESCRIPTION
      "Path: ethernet2.status.vlan.bridging.spanningTree.intRootPathCost"
   ::= {sr1645v2Lan2FGUVlanEntry 453117184}

sr1645v2Lan2FGUVlanBridgingSpanningTreeDesBrIdPriority OBJECT-TYPE
   SYNTAX      Integer32
   MAX-ACCESS  read-only
   STATUS      current
   DESCRIPTION
      "Path: ethernet2.status.vlan.bridging.spanningTree.designatedBridgeId.priority"
   ::= {sr1645v2Lan2FGUVlanEntry 453117441}

sr1645v2Lan2FGUVlanBridgingSpanningTreeDesBrIdMacAddress OBJECT-TYPE
   SYNTAX      OCTET STRING
   MAX-ACCESS  read-only
   STATUS      current
   DESCRIPTION
      "Path: ethernet2.status.vlan.bridging.spanningTree.designatedBridgeId.macAddress

       MAC address."
   ::= {sr1645v2Lan2FGUVlanEntry 453117442}

sr1645v2Lan2FGUVlanBridgingSpanningTreeDesPrtId OBJECT-TYPE
   SYNTAX      Integer32
   MAX-ACCESS  read-only
   STATUS      current
   DESCRIPTION
      "Path: ethernet2.status.vlan.bridging.spanningTree.designatedPortId"
   ::= {sr1645v2Lan2FGUVlanEntry 453117696}

sr1645v2Lan2FGUVlanBridgingSpanningTreeDesInt OBJECT-TYPE
   SYNTAX      INTEGER
               {
               no (0),
               yes (1)
               }
   MAX-ACCESS  read-only
   STATUS      current
   DESCRIPTION
      "Path: ethernet2.status.vlan.bridging.spanningTree.designatedOrInternal

       Possibilities:
               no   (0)
               yes   (1)"
   ::= {sr1645v2Lan2FGUVlanEntry 453117952}

sr1645v2Lan2FGUVlanBridgingSpanningTreeEdgeDetection OBJECT-TYPE
   SYNTAX      INTEGER
               {
               none (0),
               edge (1),
               notEdge (2)
               }
   MAX-ACCESS  read-only
   STATUS      current
   DESCRIPTION
      "Path: ethernet2.status.vlan.bridging.spanningTree.edgeDetection

       Possibilities:
               none   (0)
               edge   (1)
               notEdge   (2)"
   ::= {sr1645v2Lan2FGUVlanEntry 453118208}

sr1645v2Lan2FGUVlanVlanVid OBJECT-TYPE
   SYNTAX      Integer32
   MAX-ACCESS  read-only
   STATUS      current
   DESCRIPTION
      "Path: ethernet2.status.vlan.vlan.vid"
   ::= {sr1645v2Lan2FGUVlanEntry 234946560}

sr1645v2Lan2FGUVlanPppOEthDiscState OBJECT-TYPE
   SYNTAX      INTEGER
               {
               idle (0),
               waitForPADO (1),
               waitForPADS (2),
               established (3)
               }
   MAX-ACCESS  read-only
   STATUS      current
   DESCRIPTION
      "Path: ethernet2.status.vlan.pppOverEth.discState

       Possibilities:
               idle   (0)
               waitForPADO   (1)
               waitForPADS   (2)
               established   (3)"
   ::= {sr1645v2Lan2FGUVlanEntry 67174400}

sr1645v2Lan2FGUVlanPppOEthPeerMac OBJECT-TYPE
   SYNTAX      OCTET STRING
   MAX-ACCESS  read-only
   STATUS      current
   DESCRIPTION
      "Path: ethernet2.status.vlan.pppOverEth.remoteMacAddress

       MAC address."
   ::= {sr1645v2Lan2FGUVlanEntry 67239936}

sr1645v2Lan2FGUVlanPppOEthServiceName OBJECT-TYPE
   SYNTAX      DisplayString
   MAX-ACCESS  read-only
   STATUS      current
   DESCRIPTION
      "Path: ethernet2.status.vlan.pppOverEth.serviceName"
   ::= {sr1645v2Lan2FGUVlanEntry 67305472}

sr1645v2Lan2FGUVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUVlanEntry 83951616}

sr1645v2Lan2FGUVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUVlanEntry 84017152}

sr1645v2Lan2FGUVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUVlanEntry 84869120}

sr1645v2Lan2FGUVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2FGUVlanEntry 84541440}

sr1645v2Lan2FGUVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2FGUVlanEntry 84606976}

sr1645v2Lan2FGUVlanPppMru OBJECT-TYPE
   SYNTAX      Integer32
   MAX-ACCESS  read-only
   STATUS      current
   DESCRIPTION
      "Path: ethernet2.status.vlan.ppp.mru"
   ::= {sr1645v2Lan2FGUVlanEntry 84934656}

sr1645v2Lan2FGUVlanIpSecondaryIp OBJECT-TYPE
   SYNTAX      SEQUENCE OF Sr1645v2Lan2FGUVlanIpSecondaryIpEntry
   MAX-ACCESS  not-accessible
   STATUS      current
   DESCRIPTION
      ""
   ::= {sr1645v2Lan2FGUVlan 51838976}

sr1645v2Lan2FGUVlanIpSecondaryIpEntry OBJECT-TYPE
   SYNTAX      Sr1645v2Lan2FGUVlanIpSecondaryIpEntry
   MAX-ACCESS  not-accessible
   STATUS      current
   DESCRIPTION
      ""
   INDEX      { sr1645v2Lan2FGUVlanTableIx,
                sr1645v2Lan2FGUVlanIpSecondaryIpTableIx }
   ::= {sr1645v2Lan2FGUVlanIpSecondaryIp 1}

Sr1645v2Lan2FGUVlanIpSecondaryIpEntry ::=
   SEQUENCE
      {
      sr1645v2Lan2FGUVlanIpSecondaryIpTableIx
         TableIndex,
      sr1645v2Lan2FGUVlanIpSecondaryIpAddress
         IpAddress,
      sr1645v2Lan2FGUVlanIpSecondaryIpNetMask
         IpAddress
      }

sr1645v2Lan2FGUVlanIpSecondaryIpTableIx OBJECT-TYPE
   SYNTAX      TableIndex
   MAX-ACCESS  not-accessible
   STATUS      current
   DESCRIPTION
      ""
   ::= {sr1645v2Lan2FGUVlanIpSecondaryIpEntry 11}

sr1645v2Lan2FGUVlanIpSecondaryIpAddress OBJECT-TYPE
   SYNTAX      IpAddress
   MAX-ACCESS  read-only
   STATUS      current
   DESCRIPTION
      "Path: ethernet2.status.vlan.ip.secondaryIp.address"
   ::= {sr1645v2Lan2FGUVlanIpSecondaryIpEntry 2030043136}

sr1645v2Lan2FGUVlanIpSecondaryIpNetMask OBJECT-TYPE
   SYNTAX      IpAddress
   MAX-ACCESS  read-only
   STATUS      current
   DESCRIPTION
      "Path: ethernet2.status.vlan.ip.secondaryIp.netMask"
   ::= {sr1645v2Lan2FGUVlanIpSecondaryIpEntry 2063597568}

sr1645v2Lan2FGUVlanIpV6Addresses OBJECT-TYPE
   SYNTAX      SEQUENCE OF Sr1645v2Lan2FGUVlanIpV6AddressesEntry
   MAX-ACCESS  not-accessible
   STATUS      current
   DESCRIPTION
      ""
   ::= {sr1645v2Lan2FGUVlan 100859904}

sr1645v2Lan2FGUVlanIpV6AddressesEntry OBJECT-TYPE
   SYNTAX      Sr1645v2Lan2FGUVlanIpV6AddressesEntry
   MAX-ACCESS  not-accessible
   STATUS      current
   DESCRIPTION
      ""
   INDEX      { sr1645v2Lan2FGUVlanTableIx,
                sr1645v2Lan2FGUVlanIpV6AddressesTableIx }
   ::= {sr1645v2Lan2FGUVlanIpV6Addresses 1}

Sr1645v2Lan2FGUVlanIpV6AddressesEntry ::=
   SEQUENCE
      {
      sr1645v2Lan2FGUVlanIpV6AddressesTableIx
         TableIndex,
      sr1645v2Lan2FGUVlanIpV6AddressesAddress
         Ipv6Address,
      sr1645v2Lan2FGUVlanIpV6AddressesPrefixLength
         Integer32,
      sr1645v2Lan2FGUVlanIpV6AddressesStatus
         INTEGER,
      sr1645v2Lan2FGUVlanIpV6AddressesOrigin
         INTEGER,
      sr1645v2Lan2FGUVlanIpV6AddressesFlagsInterfaceId
         INTEGER,
      sr1645v2Lan2FGUVlanIpV6AddressesFlagsAnycast
         INTEGER,
      sr1645v2Lan2FGUVlanIpV6AddressesTimersValidLifeTime
         TimeTicks,
      sr1645v2Lan2FGUVlanIpV6AddressesTimersPrefLifeTime
         TimeTicks
      }

sr1645v2Lan2FGUVlanIpV6AddressesTableIx OBJECT-TYPE
   SYNTAX      TableIndex
   MAX-ACCESS  not-accessible
   STATUS      current
   DESCRIPTION
      ""
   ::= {sr1645v2Lan2FGUVlanIpV6AddressesEntry 11}

sr1645v2Lan2FGUVlanIpV6AddressesAddress OBJECT-TYPE
   SYNTAX      Ipv6Address
   MAX-ACCESS  read-only
   STATUS      current
   DESCRIPTION
      "Path: ethernet2.status.vlan.ipV6.addresses.address

       ipv6 address"
   ::= {sr1645v2Lan2FGUVlanIpV6AddressesEntry 16777216}

sr1645v2Lan2FGUVlanIpV6AddressesPrefixLength OBJECT-TYPE
   SYNTAX      Integer32
   MAX-ACCESS  read-only
   STATUS      current
   DESCRIPTION
      "Path: ethernet2.status.vlan.ipV6.addresses.prefixLength"
   ::= {sr1645v2Lan2FGUVlanIpV6AddressesEntry 33554432}

sr1645v2Lan2FGUVlanIpV6AddressesStatus OBJECT-TYPE
   SYNTAX      INTEGER
               {
               invalid (0),
               tentative (1),
               deprecated (2),
               preferred (3)
               }
   MAX-ACCESS  read-only
   STATUS      current
   DESCRIPTION
      "Path: ethernet2.status.vlan.ipV6.addresses.status

       Possibilities:
               invalid   (0)
               tentative   (1)
               deprecated   (2)
               preferred   (3)"
   ::= {sr1645v2Lan2FGUVlanIpV6AddressesEntry 50331648}

sr1645v2Lan2FGUVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.vlan.ipV6.addresses.origin

       Possibilities:
               unknown   (0)
               manual   (1)
               generalPrefix   (2)
               statelessAuto   (3)
               statefullAuto   (4)"
   ::= {sr1645v2Lan2FGUVlanIpV6AddressesEntry 67108864}

sr1645v2Lan2FGUVlanIpV6AddressesFlagsInterfaceId OBJECT-TYPE
   SYNTAX      INTEGER
               {
               no (0),
               yes (1)
               }
   MAX-ACCESS  read-only
   STATUS      current
   DESCRIPTION
      "Path: ethernet2.status.vlan.ipV6.addresses.flags.interfaceId

       Possibilities:
               no   (0)
               yes   (1)"
   ::= {sr1645v2Lan2FGUVlanIpV6AddressesEntry 83951616}

sr1645v2Lan2FGUVlanIpV6AddressesFlagsAnycast OBJECT-TYPE
   SYNTAX      INTEGER
               {
               no (0),
               yes (1)
               }
   MAX-ACCESS  read-only
   STATUS      current
   DESCRIPTION
      "Path: ethernet2.status.vlan.ipV6.addresses.flags.anycast

       Possibilities:
               no   (0)
               yes   (1)"
   ::= {sr1645v2Lan2FGUVlanIpV6AddressesEntry 84017152}

sr1645v2Lan2FGUVlanIpV6AddressesTimersValidLifeTime OBJECT-TYPE
   SYNTAX      TimeTicks
   MAX-ACCESS  read-only
   STATUS      current
   DESCRIPTION
      "Path: ethernet2.status.vlan.ipV6.addresses.timers.validLifeTime

       Time in centi-second."
   ::= {sr1645v2Lan2FGUVlanIpV6AddressesEntry 100794368}

sr1645v2Lan2FGUVlanIpV6AddressesTimersPrefLifeTime OBJECT-TYPE
   SYNTAX      TimeTicks
   MAX-ACCESS  read-only
   STATUS      current
   DESCRIPTION
      "Path: ethernet2.status.vlan.ipV6.addresses.timers.prefLifeTime

       Time in centi-second."
   ::= {sr1645v2Lan2FGUVlanIpV6AddressesEntry 100728832}

sr1645v2Lan2FGUVlanVlanArpCache OBJECT-TYPE
   SYNTAX      SEQUENCE OF Sr1645v2Lan2FGUVlanVlanArpCacheEntry
   MAX-ACCESS  not-accessible
   STATUS      current
   DESCRIPTION
      ""
   ::= {sr1645v2Lan2FGUVlan 235601920}

sr1645v2Lan2FGUVlanVlanArpCacheEntry OBJECT-TYPE
   SYNTAX      Sr1645v2Lan2FGUVlanVlanArpCacheEntry
   MAX-ACCESS  not-accessible
   STATUS      current
   DESCRIPTION
      ""
   INDEX      { sr1645v2Lan2FGUVlanTableIx,
                sr1645v2Lan2FGUVlanVlanArpCacheTableIx }
   ::= {sr1645v2Lan2FGUVlanVlanArpCache 1}

Sr1645v2Lan2FGUVlanVlanArpCacheEntry ::=
   SEQUENCE
      {
      sr1645v2Lan2FGUVlanVlanArpCacheTableIx
         TableIndex,
      sr1645v2Lan2FGUVlanVlanArpCacheMacAddress
         OCTET STRING,
      sr1645v2Lan2FGUVlanVlanArpCacheIpAddress
         IpAddress,
      sr1645v2Lan2FGUVlanVlanArpCacheType
         INTEGER,
      sr1645v2Lan2FGUVlanVlanArpCacheTimeOut
         TimeTicks
      }

sr1645v2Lan2FGUVlanVlanArpCacheTableIx OBJECT-TYPE
   SYNTAX      TableIndex
   MAX-ACCESS  not-accessible
   STATUS      current
   DESCRIPTION
      ""
   ::= {sr1645v2Lan2FGUVlanVlanArpCacheEntry 11}

sr1645v2Lan2FGUVlanVlanArpCacheMacAddress OBJECT-TYPE
   SYNTAX      OCTET STRING
   MAX-ACCESS  read-only
   STATUS      current
   DESCRIPTION
      "Path: ethernet2.status.vlan.vlan.arpCache.macAddress

       MAC address."
   ::= {sr1645v2Lan2FGUVlanVlanArpCacheEntry 16777216}

sr1645v2Lan2FGUVlanVlanArpCacheIpAddress OBJECT-TYPE
   SYNTAX      IpAddress
   MAX-ACCESS  read-only
   STATUS      current
   DESCRIPTION
      "Path: ethernet2.status.vlan.vlan.arpCache.ipAddress"
   ::= {sr1645v2Lan2FGUVlanVlanArpCacheEntry 33554432}

sr1645v2Lan2FGUVlanVlanArpCacheType OBJECT-TYPE
   SYNTAX      INTEGER
               {
               static (0),
               dynamic (1)
               }
   MAX-ACCESS  read-only
   STATUS      current
   DESCRIPTION
      "Path: ethernet2.status.vlan.vlan.arpCache.type

       Possibilities:
               static   (0)
               dynamic   (1)"
   ::= {sr1645v2Lan2FGUVlanVlanArpCacheEntry 50331648}

sr1645v2Lan2FGUVlanVlanArpCacheTimeOut OBJECT-TYPE
   SYNTAX      TimeTicks
   MAX-ACCESS  read-only
   STATUS      current
   DESCRIPTION
      "Path: ethernet2.status.vlan.vlan.arpCache.timeOut

       Time in centi-second."
   ::= {sr1645v2Lan2FGUVlanVlanArpCacheEntry 67108864}


sr1645v2Lan2FGUPppOE OBJECT IDENTIFIER ::= {sr1645v2Lan2FGU 36}

sr1645v2Lan2FGUPppOESSCTable OBJECT-TYPE
   SYNTAX      SEQUENCE OF Sr1645v2Lan2FGUPppOEEntry
   MAX-ACCESS  not-accessible
   STATUS      current
   DESCRIPTION
      ""
   ::= {sr1645v2Lan2FGUPppOE 1}

sr1645v2Lan2FGUPppOEEntry OBJECT-TYPE
   SYNTAX      Sr1645v2Lan2FGUPppOEEntry
   MAX-ACCESS  not-accessible
   STATUS      current
   DESCRIPTION
      ""
   INDEX      { sr1645v2Lan2FGUPppOETableIx }
   ::= {sr1645v2Lan2FGUPppOESSCTable 1}

Sr1645v2Lan2FGUPppOEEntry ::=
   SEQUENCE
      {
      sr1645v2Lan2FGUPppOETableIx
         TableIndex,
      sr1645v2Lan2FGUPppOEName
         DisplayString,
      sr1645v2Lan2FGUPppOEMode
         INTEGER,
      sr1645v2Lan2FGUPppOEIfOperStatus
         INTEGER,
      sr1645v2Lan2FGUPppOEIfLastChange
         TimeTicks,
      sr1645v2Lan2FGUPppOEIfLastChangeDate
         DisplayString,
      sr1645v2Lan2FGUPppOEIpAddress
         IpAddress,
      sr1645v2Lan2FGUPppOEIpNetMask
         IpAddress,
      sr1645v2Lan2FGUPppOEIpRemote
         IpAddress,
      sr1645v2Lan2FGUPppOEPppOEthDiscState
         INTEGER,
      sr1645v2Lan2FGUPppOEPppOEthPeerMac
         OCTET STRING,
      sr1645v2Lan2FGUPppOEPppOEthServiceName
         DisplayString,
      sr1645v2Lan2FGUPppOEPppLcpState
         INTEGER,
      sr1645v2Lan2FGUPppOEPppIpcpState
         INTEGER,
      sr1645v2Lan2FGUPppOEPppIp6cpState
         INTEGER,
      sr1645v2Lan2FGUPppOEPppMyAutSt
         INTEGER,
      sr1645v2Lan2FGUPppOEPppHisAutSt
         INTEGER,
      sr1645v2Lan2FGUPppOEPppMru
         Integer32,
      sr1645v2Lan2FGUPppOEIpV6State
         INTEGER,
      sr1645v2Lan2FGUPppOEIpV6InterfaceId
         OCTET STRING,
      sr1645v2Lan2FGUPppOEIpV6LinkMtu
         Integer32,
      sr1645v2Lan2FGUPppOEIpV6HopLimit
         Integer32,
      sr1645v2Lan2FGUPppOEIpV6DhcpIaid
         Counter32,
      sr1645v2Lan2FGUPppOEIpV6RaRcvOption
         Integer32
      }

sr1645v2Lan2FGUPppOETableIx OBJECT-TYPE
   SYNTAX      TableIndex
   MAX-ACCESS  not-accessible
   STATUS      current
   DESCRIPTION
      ""
   ::= {sr1645v2Lan2FGUPppOEEntry 11}

sr1645v2Lan2FGUPppOEName OBJECT-TYPE
   SYNTAX      DisplayString
   MAX-ACCESS  read-only
   STATUS      current
   DESCRIPTION
      "Path: ethernet2.status.pppoEClient.name"
   ::= {sr1645v2Lan2FGUPppOEEntry 16777216}

sr1645v2Lan2FGUPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2FGUPppOEEntry 335544320}

sr1645v2Lan2FGUPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.pppoEClient.ifOperStatus

       Possibilities:
               up   (1)
               down   (2)
               testing   (3)
               unknown   (4)
               dormant   (5)
               notPresent   (6)
               lowerLayerDown   (7)"
   ::= {sr1645v2Lan2FGUPppOEEntry 1795162112}

sr1645v2Lan2FGUPppOEIfLastChange OBJECT-TYPE
   SYNTAX      TimeTicks
   MAX-ACCESS  read-only
   STATUS      current
   DESCRIPTION
      "Path: ethernet2.status.pppoEClient.ifLastChange

       Time in centi-second."
   ::= {sr1645v2Lan2FGUPppOEEntry 1811939328}

sr1645v2Lan2FGUPppOEIfLastChangeDate OBJECT-TYPE
   SYNTAX      DisplayString
   MAX-ACCESS  read-only
   STATUS      current
   DESCRIPTION
      "Path: ethernet2.status.pppoEClient.ifLastChangeDate"
   ::= {sr1645v2Lan2FGUPppOEEntry 3070230528}

sr1645v2Lan2FGUPppOEIpAddress OBJECT-TYPE
   SYNTAX      IpAddress
   MAX-ACCESS  read-only
   STATUS      current
   DESCRIPTION
      "Path: ethernet2.status.pppoEClient.ip.address"
   ::= {sr1645v2Lan2FGUPppOEEntry 51380224}

sr1645v2Lan2FGUPppOEIpNetMask OBJECT-TYPE
   SYNTAX      IpAddress
   MAX-ACCESS  read-only
   STATUS      current
   DESCRIPTION
      "Path: ethernet2.status.pppoEClient.ip.netMask"
   ::= {sr1645v2Lan2FGUPppOEEntry 51445760}

sr1645v2Lan2FGUPppOEIpRemote OBJECT-TYPE
   SYNTAX      IpAddress
   MAX-ACCESS  read-only
   STATUS      current
   DESCRIPTION
      "Path: ethernet2.status.pppoEClient.ip.remote"
   ::= {sr1645v2Lan2FGUPppOEEntry 51511296}

sr1645v2Lan2FGUPppOEPppOEthDiscState OBJECT-TYPE
   SYNTAX      INTEGER
               {
               idle (0),
               waitForPADO (1),
               waitForPADS (2),
               established (3)
               }
   MAX-ACCESS  read-only
   STATUS      current
   DESCRIPTION
      "Path: ethernet2.status.pppoEClient.pppOverEth.discState

       Possibilities:
               idle   (0)
               waitForPADO   (1)
               waitForPADS   (2)
               established   (3)"
   ::= {sr1645v2Lan2FGUPppOEEntry 67174400}

sr1645v2Lan2FGUPppOEPppOEthPeerMac OBJECT-TYPE
   SYNTAX      OCTET STRING
   MAX-ACCESS  read-only
   STATUS      current
   DESCRIPTION
      "Path: ethernet2.status.pppoEClient.pppOverEth.remoteMacAddress

       MAC address."
   ::= {sr1645v2Lan2FGUPppOEEntry 67239936}

sr1645v2Lan2FGUPppOEPppOEthServiceName OBJECT-TYPE
   SYNTAX      DisplayString
   MAX-ACCESS  read-only
   STATUS      current
   DESCRIPTION
      "Path: ethernet2.status.pppoEClient.pppOverEth.serviceName"
   ::= {sr1645v2Lan2FGUPppOEEntry 67305472}

sr1645v2Lan2FGUPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUPppOEEntry 83951616}

sr1645v2Lan2FGUPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUPppOEEntry 84017152}

sr1645v2Lan2FGUPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGUPppOEEntry 84869120}

sr1645v2Lan2FGUPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2FGUPppOEEntry 84541440}

sr1645v2Lan2FGUPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2FGUPppOEEntry 84606976}

sr1645v2Lan2FGUPppOEPppMru OBJECT-TYPE
   SYNTAX      Integer32
   MAX-ACCESS  read-only
   STATUS      current
   DESCRIPTION
      "Path: ethernet2.status.pppoEClient.ppp.mru"
   ::= {sr1645v2Lan2FGUPppOEEntry 84934656}

sr1645v2Lan2FGUPppOEIpV6State OBJECT-TYPE
   SYNTAX      INTEGER
               {
               disabled (0),
               enabled (1)
               }
   MAX-ACCESS  read-only
   STATUS      current
   DESCRIPTION
      "Path: ethernet2.status.pppoEClient.ipV6.state

       Possibilities:
               disabled   (0)
               enabled   (1)"
   ::= {sr1645v2Lan2FGUPppOEEntry 100728832}

sr1645v2Lan2FGUPppOEIpV6InterfaceId OBJECT-TYPE
   SYNTAX      OCTET STRING
   MAX-ACCESS  read-only
   STATUS      current
   DESCRIPTION
      "Path: ethernet2.status.pppoEClient.ipV6.interfaceId"
   ::= {sr1645v2Lan2FGUPppOEEntry 100794368}

sr1645v2Lan2FGUPppOEIpV6LinkMtu OBJECT-TYPE
   SYNTAX      Integer32
   MAX-ACCESS  read-only
   STATUS      current
   DESCRIPTION
      "Path: ethernet2.status.pppoEClient.ipV6.linkMtu"
   ::= {sr1645v2Lan2FGUPppOEEntry 100925440}

sr1645v2Lan2FGUPppOEIpV6HopLimit OBJECT-TYPE
   SYNTAX      Integer32
   MAX-ACCESS  read-only
   STATUS      current
   DESCRIPTION
      "Path: ethernet2.status.pppoEClient.ipV6.hopLimit"
   ::= {sr1645v2Lan2FGUPppOEEntry 100990976}

sr1645v2Lan2FGUPppOEIpV6DhcpIaid OBJECT-TYPE
   SYNTAX      Counter32
   MAX-ACCESS  read-only
   STATUS      current
   DESCRIPTION
      "Path: ethernet2.status.pppoEClient.ipV6.dhcp.iaid

       32 bit unsigned wrappable counter."
   ::= {sr1645v2Lan2FGUPppOEEntry 101056768}

sr1645v2Lan2FGUPppOEIpV6RaRcvOption OBJECT-TYPE
   SYNTAX      Integer32
   MAX-ACCESS  read-only
   STATUS      current
   DESCRIPTION
      "Path: ethernet2.status.pppoEClient.ipV6.raRcvOption

       Bit meanings:
               bit 0 = linkMtu,
               bit 1 = srcLinkLayer,
               bit 2 = prefixInfo,
               bit 3 = rdnss,
               bit 4 = dnssl"
   ::= {sr1645v2Lan2FGUPppOEEntry 101122048}

sr1645v2Lan2FGUPppOEIpV6Addresses OBJECT-TYPE
   SYNTAX      SEQUENCE OF Sr1645v2Lan2FGUPppOEIpV6AddressesEntry
   MAX-ACCESS  not-accessible
   STATUS      current
   DESCRIPTION
      ""
   ::= {sr1645v2Lan2FGUPppOE 100859904}

sr1645v2Lan2FGUPppOEIpV6AddressesEntry OBJECT-TYPE
   SYNTAX      Sr1645v2Lan2FGUPppOEIpV6AddressesEntry
   MAX-ACCESS  not-accessible
   STATUS      current
   DESCRIPTION
      ""
   INDEX      { sr1645v2Lan2FGUPppOETableIx,
                sr1645v2Lan2FGUPppOEIpV6AddressesTableIx }
   ::= {sr1645v2Lan2FGUPppOEIpV6Addresses 1}

Sr1645v2Lan2FGUPppOEIpV6AddressesEntry ::=
   SEQUENCE
      {
      sr1645v2Lan2FGUPppOEIpV6AddressesTableIx
         TableIndex,
      sr1645v2Lan2FGUPppOEIpV6AddressesAddress
         Ipv6Address,
      sr1645v2Lan2FGUPppOEIpV6AddressesPrefixLength
         Integer32,
      sr1645v2Lan2FGUPppOEIpV6AddressesStatus
         INTEGER,
      sr1645v2Lan2FGUPppOEIpV6AddressesOrigin
         INTEGER,
      sr1645v2Lan2FGUPppOEIpV6AddressesFlagsInterfaceId
         INTEGER,
      sr1645v2Lan2FGUPppOEIpV6AddressesFlagsAnycast
         INTEGER,
      sr1645v2Lan2FGUPppOEIpV6AddressesTimersValidLifeTime
         TimeTicks,
      sr1645v2Lan2FGUPppOEIpV6AddressesTimersPrefLifeTime
         TimeTicks
      }

sr1645v2Lan2FGUPppOEIpV6AddressesTableIx OBJECT-TYPE
   SYNTAX      TableIndex
   MAX-ACCESS  not-accessible
   STATUS      current
   DESCRIPTION
      ""
   ::= {sr1645v2Lan2FGUPppOEIpV6AddressesEntry 11}

sr1645v2Lan2FGUPppOEIpV6AddressesAddress OBJECT-TYPE
   SYNTAX      Ipv6Address
   MAX-ACCESS  read-only
   STATUS      current
   DESCRIPTION
      "Path: ethernet2.status.pppoEClient.ipV6.addresses.address

       ipv6 address"
   ::= {sr1645v2Lan2FGUPppOEIpV6AddressesEntry 16777216}

sr1645v2Lan2FGUPppOEIpV6AddressesPrefixLength OBJECT-TYPE
   SYNTAX      Integer32
   MAX-ACCESS  read-only
   STATUS      current
   DESCRIPTION
      "Path: ethernet2.status.pppoEClient.ipV6.addresses.prefixLength"
   ::= {sr1645v2Lan2FGUPppOEIpV6AddressesEntry 33554432}

sr1645v2Lan2FGUPppOEIpV6AddressesStatus OBJECT-TYPE
   SYNTAX      INTEGER
               {
               invalid (0),
               tentative (1),
               deprecated (2),
               preferred (3)
               }
   MAX-ACCESS  read-only
   STATUS      current
   DESCRIPTION
      "Path: ethernet2.status.pppoEClient.ipV6.addresses.status

       Possibilities:
               invalid   (0)
               tentative   (1)
               deprecated   (2)
               preferred   (3)"
   ::= {sr1645v2Lan2FGUPppOEIpV6AddressesEntry 50331648}

sr1645v2Lan2FGUPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.pppoEClient.ipV6.addresses.origin

       Possibilities:
               unknown   (0)
               manual   (1)
               generalPrefix   (2)
               statelessAuto   (3)
               statefullAuto   (4)"
   ::= {sr1645v2Lan2FGUPppOEIpV6AddressesEntry 67108864}

sr1645v2Lan2FGUPppOEIpV6AddressesFlagsInterfaceId OBJECT-TYPE
   SYNTAX      INTEGER
               {
               no (0),
               yes (1)
               }
   MAX-ACCESS  read-only
   STATUS      current
   DESCRIPTION
      "Path: ethernet2.status.pppoEClient.ipV6.addresses.flags.interfaceId

       Possibilities:
               no   (0)
               yes   (1)"
   ::= {sr1645v2Lan2FGUPppOEIpV6AddressesEntry 83951616}

sr1645v2Lan2FGUPppOEIpV6AddressesFlagsAnycast OBJECT-TYPE
   SYNTAX      INTEGER
               {
               no (0),
               yes (1)
               }
   MAX-ACCESS  read-only
   STATUS      current
   DESCRIPTION
      "Path: ethernet2.status.pppoEClient.ipV6.addresses.flags.anycast

       Possibilities:
               no   (0)
               yes   (1)"
   ::= {sr1645v2Lan2FGUPppOEIpV6AddressesEntry 84017152}

sr1645v2Lan2FGUPppOEIpV6AddressesTimersValidLifeTime OBJECT-TYPE
   SYNTAX      TimeTicks
   MAX-ACCESS  read-only
   STATUS      current
   DESCRIPTION
      "Path: ethernet2.status.pppoEClient.ipV6.addresses.timers.validLifeTime

       Time in centi-second."
   ::= {sr1645v2Lan2FGUPppOEIpV6AddressesEntry 100794368}

sr1645v2Lan2FGUPppOEIpV6AddressesTimersPrefLifeTime OBJECT-TYPE
   SYNTAX      TimeTicks
   MAX-ACCESS  read-only
   STATUS      current
   DESCRIPTION
      "Path: ethernet2.status.pppoEClient.ipV6.addresses.timers.prefLifeTime

       Time in centi-second."
   ::= {sr1645v2Lan2FGUPppOEIpV6AddressesEntry 100728832}


sr1645v2Lan2FGUDot1x OBJECT IDENTIFIER ::= {sr1645v2Lan2FGU 190}

sr1645v2Lan2FGUDot1xSSCTable OBJECT-TYPE
   SYNTAX      SEQUENCE OF Sr1645v2Lan2FGUDot1xEntry
   MAX-ACCESS  not-accessible
   STATUS      current
   DESCRIPTION
      "Ethernet Switch VLAN Table"
   ::= {sr1645v2Lan2FGUDot1x 1}

sr1645v2Lan2FGUDot1xEntry OBJECT-TYPE
   SYNTAX      Sr1645v2Lan2FGUDot1xEntry
   MAX-ACCESS  not-accessible
   STATUS      current
   DESCRIPTION
      ""
   INDEX      { sr1645v2Lan2FGUDot1xTableIx }
   ::= {sr1645v2Lan2FGUDot1xSSCTable 1}

Sr1645v2Lan2FGUDot1xEntry ::=
   SEQUENCE
      {
      sr1645v2Lan2FGUDot1xTableIx
         TableIndex,
      sr1645v2Lan2FGUDot1xRemote
         OCTET STRING,
      sr1645v2Lan2FGUDot1xAuthorized
         INTEGER,
      sr1645v2Lan2FGUDot1xAuthenticator
         INTEGER,
      sr1645v2Lan2FGUDot1xBackEnd
         INTEGER,
      sr1645v2Lan2FGUDot1xRetries
         Integer32,
      sr1645v2Lan2FGUDot1xReAuthTime
         TimeTicks,
      sr1645v2Lan2FGUDot1xHoldTime
         TimeTicks
      }

sr1645v2Lan2FGUDot1xTableIx OBJECT-TYPE
   SYNTAX      TableIndex
   MAX-ACCESS  not-accessible
   STATUS      current
   DESCRIPTION
      ""
   ::= {sr1645v2Lan2FGUDot1xEntry 11}

sr1645v2Lan2FGUDot1xRemote OBJECT-TYPE
   SYNTAX      OCTET STRING
   MAX-ACCESS  read-only
   STATUS      current
   DESCRIPTION
      "Path: ethernet2.status.dot1x.remote

       MAC address."
   ::= {sr1645v2Lan2FGUDot1xEntry 16777216}

sr1645v2Lan2FGUDot1xAuthorized OBJECT-TYPE
   SYNTAX      INTEGER
               {
               no (0),
               yes (1)
               }
   MAX-ACCESS  read-only
   STATUS      current
   DESCRIPTION
      "Path: ethernet2.status.dot1x.authorized

       Possibilities:
               no   (0)
               yes   (1)"
   ::= {sr1645v2Lan2FGUDot1xEntry 33554432}

sr1645v2Lan2FGUDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet2.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2Lan2FGUDot1xEntry 50331648}

sr1645v2Lan2FGUDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet2.status.dot1x.backEnd

       Possibilities:
               preInit   (0)
               initialize   (1)
               idle   (2)
               request   (3)
               response   (4)
               success   (5)
               failure   (6)
               radiusTimeout   (7)
               timeout   (8)"
   ::= {sr1645v2Lan2FGUDot1xEntry 67108864}

sr1645v2Lan2FGUDot1xRetries OBJECT-TYPE
   SYNTAX      Integer32
   MAX-ACCESS  read-only
   STATUS      current
   DESCRIPTION
      "Path: ethernet2.status.dot1x.retries"
   ::= {sr1645v2Lan2FGUDot1xEntry 83886080}

sr1645v2Lan2FGUDot1xReAuthTime OBJECT-TYPE
   SYNTAX      TimeTicks
   MAX-ACCESS  read-only
   STATUS      current
   DESCRIPTION
      "Path: ethernet2.status.dot1x.reAuthTime

       Time in centi-second."
   ::= {sr1645v2Lan2FGUDot1xEntry 100663296}

sr1645v2Lan2FGUDot1xHoldTime OBJECT-TYPE
   SYNTAX      TimeTicks
   MAX-ACCESS  read-only
   STATUS      current
   DESCRIPTION
      "Path: ethernet2.status.dot1x.holdTime

       Time in centi-second."
   ::= {sr1645v2Lan2FGUDot1xEntry 117440512}


sr1645v2Lan2FGUIpV6 OBJECT IDENTIFIER ::= {sr1645v2Lan2FGU 17}

sr1645v2Lan2FGUIpV6SSC OBJECT IDENTIFIER ::= {sr1645v2Lan2FGUIpV6 1}

sr1645v2Lan2FGUIpV6Entry OBJECT IDENTIFIER ::= {sr1645v2Lan2FGUIpV6SSC 1}

sr1645v2Lan2FGUIpV6State OBJECT-TYPE
   SYNTAX      INTEGER
               {
               disabled (0),
               enabled (1)
               }
   MAX-ACCESS  read-only
   STATUS      current
   DESCRIPTION
      "Path: ethernet2.status.ipV6.state

       Possibilities:
               disabled   (0)
               enabled   (1)"
   ::= {sr1645v2Lan2FGUIpV6Entry 16777216}

sr1645v2Lan2FGUIpV6InterfaceId OBJECT-TYPE
   SYNTAX      OCTET STRING
   MAX-ACCESS  read-only
   STATUS      current
   DESCRIPTION
      "Path: ethernet2.status.ipV6.interfaceId"
   ::= {sr1645v2Lan2FGUIpV6Entry 33554432}

sr1645v2Lan2FGUIpV6LinkMtu OBJECT-TYPE
   SYNTAX      Integer32
   MAX-ACCESS  read-only
   STATUS      current
   DESCRIPTION
      "Path: ethernet2.status.ipV6.linkMtu"
   ::= {sr1645v2Lan2FGUIpV6Entry 67108864}

sr1645v2Lan2FGUIpV6HopLimit OBJECT-TYPE
   SYNTAX      Integer32
   MAX-ACCESS  read-only
   STATUS      current
   DESCRIPTION
      "Path: ethernet2.status.ipV6.hopLimit"
   ::= {sr1645v2Lan2FGUIpV6Entry 83886080}

sr1645v2Lan2FGUIpV6DhcpIaid OBJECT-TYPE
   SYNTAX      Counter32
   MAX-ACCESS  read-only
   STATUS      current
   DESCRIPTION
      "Path: ethernet2.status.ipV6.dhcp.iaid

       32 bit unsigned wrappable counter."
   ::= {sr1645v2Lan2FGUIpV6Entry 100728832}

sr1645v2Lan2FGUIpV6RaRcvOption OBJECT-TYPE
   SYNTAX      Integer32
   MAX-ACCESS  read-only
   STATUS      current
   DESCRIPTION
      "Path: ethernet2.status.ipV6.raRcvOption

       Bit meanings:
               bit 0 = linkMtu,
               bit 1 = srcLinkLayer,
               bit 2 = prefixInfo,
               bit 3 = rdnss,
               bit 4 = dnssl"
   ::= {sr1645v2Lan2FGUIpV6Entry 117440512}

sr1645v2Lan2FGUIpV6Addresses OBJECT-TYPE
   SYNTAX      SEQUENCE OF Sr1645v2Lan2FGUIpV6AddressesEntry
   MAX-ACCESS  not-accessible
   STATUS      current
   DESCRIPTION
      ""
   ::= {sr1645v2Lan2FGUIpV6 50331648}

sr1645v2Lan2FGUIpV6AddressesEntry OBJECT-TYPE
   SYNTAX      Sr1645v2Lan2FGUIpV6AddressesEntry
   MAX-ACCESS  not-accessible
   STATUS      current
   DESCRIPTION
      ""
   INDEX      { sr1645v2Lan2FGUIpV6AddressesTableIx }
   ::= {sr1645v2Lan2FGUIpV6Addresses 1}

Sr1645v2Lan2FGUIpV6AddressesEntry ::=
   SEQUENCE
      {
      sr1645v2Lan2FGUIpV6AddressesTableIx
         TableIndex,
      sr1645v2Lan2FGUIpV6AddressesAddress
         Ipv6Address,
      sr1645v2Lan2FGUIpV6AddressesPrefixLength
         Integer32,
      sr1645v2Lan2FGUIpV6AddressesStatus
         INTEGER,
      sr1645v2Lan2FGUIpV6AddressesOrigin
         INTEGER,
      sr1645v2Lan2FGUIpV6AddressesFlagsInterfaceId
         INTEGER,
      sr1645v2Lan2FGUIpV6AddressesFlagsAnycast
         INTEGER,
      sr1645v2Lan2FGUIpV6AddressesTimersValidLifeTime
         TimeTicks,
      sr1645v2Lan2FGUIpV6AddressesTimersPrefLifeTime
         TimeTicks
      }

sr1645v2Lan2FGUIpV6AddressesTableIx OBJECT-TYPE
   SYNTAX      TableIndex
   MAX-ACCESS  not-accessible
   STATUS      current
   DESCRIPTION
      ""
   ::= {sr1645v2Lan2FGUIpV6AddressesEntry 11}

sr1645v2Lan2FGUIpV6AddressesAddress OBJECT-TYPE
   SYNTAX      Ipv6Address
   MAX-ACCESS  read-only
   STATUS      current
   DESCRIPTION
      "Path: ethernet2.status.ipV6.addresses.address

       ipv6 address"
   ::= {sr1645v2Lan2FGUIpV6AddressesEntry 16777216}

sr1645v2Lan2FGUIpV6AddressesPrefixLength OBJECT-TYPE
   SYNTAX      Integer32
   MAX-ACCESS  read-only
   STATUS      current
   DESCRIPTION
      "Path: ethernet2.status.ipV6.addresses.prefixLength"
   ::= {sr1645v2Lan2FGUIpV6AddressesEntry 33554432}

sr1645v2Lan2FGUIpV6AddressesStatus OBJECT-TYPE
   SYNTAX      INTEGER
               {
               invalid (0),
               tentative (1),
               deprecated (2),
               preferred (3)
               }
   MAX-ACCESS  read-only
   STATUS      current
   DESCRIPTION
      "Path: ethernet2.status.ipV6.addresses.status

       Possibilities:
               invalid   (0)
               tentative   (1)
               deprecated   (2)
               preferred   (3)"
   ::= {sr1645v2Lan2FGUIpV6AddressesEntry 50331648}

sr1645v2Lan2FGUIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.ipV6.addresses.origin

       Possibilities:
               unknown   (0)
               manual   (1)
               generalPrefix   (2)
               statelessAuto   (3)
               statefullAuto   (4)"
   ::= {sr1645v2Lan2FGUIpV6AddressesEntry 67108864}

sr1645v2Lan2FGUIpV6AddressesFlagsInterfaceId OBJECT-TYPE
   SYNTAX      INTEGER
               {
               no (0),
               yes (1)
               }
   MAX-ACCESS  read-only
   STATUS      current
   DESCRIPTION
      "Path: ethernet2.status.ipV6.addresses.flags.interfaceId

       Possibilities:
               no   (0)
               yes   (1)"
   ::= {sr1645v2Lan2FGUIpV6AddressesEntry 83951616}

sr1645v2Lan2FGUIpV6AddressesFlagsAnycast OBJECT-TYPE
   SYNTAX      INTEGER
               {
               no (0),
               yes (1)
               }
   MAX-ACCESS  read-only
   STATUS      current
   DESCRIPTION
      "Path: ethernet2.status.ipV6.addresses.flags.anycast

       Possibilities:
               no   (0)
               yes   (1)"
   ::= {sr1645v2Lan2FGUIpV6AddressesEntry 84017152}

sr1645v2Lan2FGUIpV6AddressesTimersValidLifeTime OBJECT-TYPE
   SYNTAX      TimeTicks
   MAX-ACCESS  read-only
   STATUS      current
   DESCRIPTION
      "Path: ethernet2.status.ipV6.addresses.timers.validLifeTime

       Time in centi-second."
   ::= {sr1645v2Lan2FGUIpV6AddressesEntry 100794368}

sr1645v2Lan2FGUIpV6AddressesTimersPrefLifeTime OBJECT-TYPE
   SYNTAX      TimeTicks
   MAX-ACCESS  read-only
   STATUS      current
   DESCRIPTION
      "Path: ethernet2.status.ipV6.addresses.timers.prefLifeTime

       Time in centi-second."
   ::= {sr1645v2Lan2FGUIpV6AddressesEntry 100728832}



pr1645v2Lan2FGU OBJECT IDENTIFIER ::= {r1645v2Lan2FGU 12}


pr1645v2Lan2FGUInOctets OBJECT-TYPE
   SYNTAX      Counter64
   MAX-ACCESS  read-only
   STATUS      current
   DESCRIPTION
      "Path: ethernet2.performance.ifInOctets
       Info: ifInOctets

       64 bit unsigned wrappable counter."
   ::= {pr1645v2Lan2FGU 109}


pr1645v2Lan2FGUInUcast OBJECT-TYPE
   SYNTAX      Counter64
   MAX-ACCESS  read-only
   STATUS      current
   DESCRIPTION
      "Path: ethernet2.performance.ifInUcastPkts
       Info: ifInUcastPkts

       64 bit unsigned wrappable counter."
   ::= {pr1645v2Lan2FGU 110}


pr1645v2Lan2FGUInNUcastPkts OBJECT-TYPE
   SYNTAX      Counter64
   MAX-ACCESS  read-only
   STATUS      current
   DESCRIPTION
      "Path: ethernet2.performance.ifInNUcastPkts
       Info: ifInNUcastPkts

       64 bit unsigned wrappable counter."
   ::= {pr1645v2Lan2FGU 111}


pr1645v2Lan2FGUInBcastPkts OBJECT-TYPE
   SYNTAX      Counter64
   MAX-ACCESS  read-only
   STATUS      current
   DESCRIPTION
      "Path: ethernet2.performance.ifInBcastPkts
       Info: ifInBcastPkts

       64 bit unsigned wrappable counter."
   ::= {pr1645v2Lan2FGU 211}


pr1645v2Lan2FGUInMcastPkts OBJECT-TYPE
   SYNTAX      Counter64
   MAX-ACCESS  read-only
   STATUS      current
   DESCRIPTION
      "Path: ethernet2.performance.ifInMcastPkts
       Info: ifInNUcastPkts

       64 bit unsigned wrappable counter."
   ::= {pr1645v2Lan2FGU 221}


pr1645v2Lan2FGUInDiscards OBJECT-TYPE
   SYNTAX      Counter64
   MAX-ACCESS  read-only
   STATUS      current
   DESCRIPTION
      "Path: ethernet2.performance.ifInDiscards
       Info: ifInDiscards

       64 bit unsigned wrappable counter."
   ::= {pr1645v2Lan2FGU 112}


pr1645v2Lan2FGUInErrors OBJECT-TYPE
   SYNTAX      Counter64
   MAX-ACCESS  read-only
   STATUS      current
   DESCRIPTION
      "Path: ethernet2.performance.ifInErrors
       Info: ifInErrors

       64 bit unsigned wrappable counter."
   ::= {pr1645v2Lan2FGU 113}


pr1645v2Lan2FGUInUnknownProtos OBJECT-TYPE
   SYNTAX      Counter64
   MAX-ACCESS  read-only
   STATUS      current
   DESCRIPTION
      "Path: ethernet2.performance.ifInUnknownProtos
       Info: ifInUnknownprotos

       64 bit unsigned wrappable counter."
   ::= {pr1645v2Lan2FGU 114}


pr1645v2Lan2FGUInQLen OBJECT-TYPE
   SYNTAX      Gauge32
   MAX-ACCESS  read-only
   STATUS      current
   DESCRIPTION
      "Path: ethernet2.performance.ifInQLen
       Info: ifInQLen

       32 bit unsigned gauge value."
   ::= {pr1645v2Lan2FGU 128}


pr1645v2Lan2FGUInDropEx OBJECT-TYPE
   SYNTAX      Counter64
   MAX-ACCESS  read-only
   STATUS      current
   DESCRIPTION
      "Path: ethernet2.performance.ifInDropLevelExceeded
       Info: ifInDiscards

       64 bit unsigned wrappable counter."
   ::= {pr1645v2Lan2FGU 130}


pr1645v2Lan2FGUInDropNoMac OBJECT-TYPE
   SYNTAX      Counter64
   MAX-ACCESS  read-only
   STATUS      current
   DESCRIPTION
      "Path: ethernet2.performance.ifInDiscardsNoMacFit
       Info: ifInDiscards

       64 bit unsigned wrappable counter."
   ::= {pr1645v2Lan2FGU 133}


pr1645v2Lan2FGUInDropNUCast OBJECT-TYPE
   SYNTAX      Counter64
   MAX-ACCESS  read-only
   STATUS      current
   DESCRIPTION
      "Path: ethernet2.performance.ifInDiscardsNUCast
       Info: ifInDiscards

       64 bit unsigned wrappable counter."
   ::= {pr1645v2Lan2FGU 136}


pr1645v2Lan2FGUInDropFilter OBJECT-TYPE
   SYNTAX      Counter64
   MAX-ACCESS  read-only
   STATUS      current
   DESCRIPTION
      "Path: ethernet2.performance.ifInDiscardsFilter
       Info: ifInDiscards

       64 bit unsigned wrappable counter."
   ::= {pr1645v2Lan2FGU 137}


pr1645v2Lan2FGUInQueues OBJECT IDENTIFIER ::= {pr1645v2Lan2FGU 131}

pr1645v2Lan2FGUInQueuesSSCTable OBJECT-TYPE
   SYNTAX      SEQUENCE OF Pr1645v2Lan2FGUInQueuesEntry
   MAX-ACCESS  not-accessible
   STATUS      current
   DESCRIPTION
      "Queue Lengths"
   ::= {pr1645v2Lan2FGUInQueues 1}

pr1645v2Lan2FGUInQueuesEntry OBJECT-TYPE
   SYNTAX      Pr1645v2Lan2FGUInQueuesEntry
   MAX-ACCESS  not-accessible
   STATUS      current
   DESCRIPTION
      ""
   INDEX      { pr1645v2Lan2FGUInQueuesTableIx }
   ::= {pr1645v2Lan2FGUInQueuesSSCTable 1}

Pr1645v2Lan2FGUInQueuesEntry ::=
   SEQUENCE
      {
      pr1645v2Lan2FGUInQueuesTableIx
         TableIndex,
      pr1645v2Lan2FGUInQueuesName
         INTEGER,
      pr1645v2Lan2FGUInQueuesLength
         Integer32,
      pr1645v2Lan2FGUInQueuesOctetLength
         Integer32,
      pr1645v2Lan2FGUInQueuesRedLength
         Integer32,
      pr1645v2Lan2FGUInQueuesPacketsTotal
         Counter64,
      pr1645v2Lan2FGUInQueuesPacketsDirectTx
         Counter64,
      pr1645v2Lan2FGUInQueuesPacketsQueued
         Counter64,
      pr1645v2Lan2FGUInQueuesPacketsDropped
         Counter64,
      pr1645v2Lan2FGUInQueuesPacketsRedDropped
         Counter64,
      pr1645v2Lan2FGUInQueuesPacketsCirTx
         Counter64,
      pr1645v2Lan2FGUInQueuesPacketsEirTx
         Counter64,
      pr1645v2Lan2FGUInQueuesPacketsViolateTx
         Counter64,
      pr1645v2Lan2FGUInQueuesOctetsTotal
         Counter64,
      pr1645v2Lan2FGUInQueuesOctetsDirectTx
         Counter64,
      pr1645v2Lan2FGUInQueuesOctetsQueued
         Counter64,
      pr1645v2Lan2FGUInQueuesOctetsDropped
         Counter64,
      pr1645v2Lan2FGUInQueuesOctetsRedDropped
         Counter64,
      pr1645v2Lan2FGUInQueuesOctetsCirTx
         Counter64,
      pr1645v2Lan2FGUInQueuesOctetsEirTx
         Counter64,
      pr1645v2Lan2FGUInQueuesOctetsViolateTx
         Counter64,
      pr1645v2Lan2FGUInQueuesOctetsBandwidth15sec
         Integer32,
      pr1645v2Lan2FGUInQueuesOctetsBandwidth30sec
         Integer32,
      pr1645v2Lan2FGUInQueuesOctetsBandwidth1min
         Integer32,
      pr1645v2Lan2FGUInQueuesOctetsBandwidth2min
         Integer32,
      pr1645v2Lan2FGUInQueuesOctetsBandwidth5min
         Integer32
      }

pr1645v2Lan2FGUInQueuesTableIx OBJECT-TYPE
   SYNTAX      TableIndex
   MAX-ACCESS  not-accessible
   STATUS      current
   DESCRIPTION
      ""
   ::= {pr1645v2Lan2FGUInQueuesEntry 11}

pr1645v2Lan2FGUInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGUInQueuesEntry 16777216}

pr1645v2Lan2FGUInQueuesLength OBJECT-TYPE
   SYNTAX      Integer32
   MAX-ACCESS  read-only
   STATUS      current
   DESCRIPTION
      "Path: ethernet2.performance.ifInPriorityQueues.length"
   ::= {pr1645v2Lan2FGUInQueuesEntry 33554432}

pr1645v2Lan2FGUInQueuesOctetLength OBJECT-TYPE
   SYNTAX      Integer32
   MAX-ACCESS  read-only
   STATUS      current
   DESCRIPTION
      "Path: ethernet2.performance.ifInPriorityQueues.octetLength"
   ::= {pr1645v2Lan2FGUInQueuesEntry 150994944}

pr1645v2Lan2FGUInQueuesRedLength OBJECT-TYPE
   SYNTAX      Integer32
   MAX-ACCESS  read-only
   STATUS      current
   DESCRIPTION
      "Path: ethernet2.performance.ifInPriorityQueues.redLength"
   ::= {pr1645v2Lan2FGUInQueuesEntry 134217728}

pr1645v2Lan2FGUInQueuesPacketsTotal OBJECT-TYPE
   SYNTAX      Counter64
   MAX-ACCESS  read-only
   STATUS      current
   DESCRIPTION
      "Path: ethernet2.performance.ifInPriorityQueues.packets.total

       64 bit unsigned wrappable counter."
   ::= {pr1645v2Lan2FGUInQueuesEntry 50790400}

pr1645v2Lan2FGUInQueuesPacketsDirectTx OBJECT-TYPE
   SYNTAX      Counter64
   MAX-ACCESS  read-only
   STATUS      current
   DESCRIPTION
      "Path: ethernet2.performance.ifInPriorityQueues.packets.directTx

       64 bit unsigned wrappable counter."
   ::= {pr1645v2Lan2FGUInQueuesEntry 50397184}

pr1645v2Lan2FGUInQueuesPacketsQueued OBJECT-TYPE
   SYNTAX      Counter64
   MAX-ACCESS  read-only
   STATUS      current
   DESCRIPTION
      "Path: ethernet2.performance.ifInPriorityQueues.packets.queued

       64 bit unsigned wrappable counter."
   ::= {pr1645v2Lan2FGUInQueuesEntry 50462720}

pr1645v2Lan2FGUInQueuesPacketsDropped OBJECT-TYPE
   SYNTAX      Counter64
   MAX-ACCESS  read-only
   STATUS      current
   DESCRIPTION
      "Path: ethernet2.performance.ifInPriorityQueues.packets.dropped

       64 bit unsigned wrappable counter."
   ::= {pr1645v2Lan2FGUInQueuesEntry 50528256}

pr1645v2Lan2FGUInQueuesPacketsRedDropped OBJECT-TYPE
   SYNTAX      Counter64
   MAX-ACCESS  read-only
   STATUS      current
   DESCRIPTION
      "Path: ethernet2.performance.ifInPriorityQueues.packets.redDropped

       64 bit unsigned wrappable counter."
   ::= {pr1645v2Lan2FGUInQueuesEntry 50724864}

pr1645v2Lan2FGUInQueuesPacketsCirTx OBJECT-TYPE
   SYNTAX      Counter64
   MAX-ACCESS  read-only
   STATUS      current
   DESCRIPTION
      "Path: ethernet2.performance.ifInPriorityQueues.packets.cirTx

       64 bit unsigned wrappable counter."
   ::= {pr1645v2Lan2FGUInQueuesEntry 50593792}

pr1645v2Lan2FGUInQueuesPacketsEirTx OBJECT-TYPE
   SYNTAX      Counter64
   MAX-ACCESS  read-only
   STATUS      current
   DESCRIPTION
      "Path: ethernet2.performance.ifInPriorityQueues.packets.eirTx

       64 bit unsigned wrappable counter."
   ::= {pr1645v2Lan2FGUInQueuesEntry 50659328}

pr1645v2Lan2FGUInQueuesPacketsViolateTx OBJECT-TYPE
   SYNTAX      Counter64
   MAX-ACCESS  read-only
   STATUS      current
   DESCRIPTION
      "Path: ethernet2.performance.ifInPriorityQueues.packets.violateTx

       64 bit unsigned wrappable counter."
   ::= {pr1645v2Lan2FGUInQueuesEntry 50855936}

pr1645v2Lan2FGUInQueuesOctetsTotal OBJECT-TYPE
   SYNTAX      Counter64
   MAX-ACCESS  read-only
   STATUS      current
   DESCRIPTION
      "Path: ethernet2.performance.ifInPriorityQueues.octets.total

       64 bit unsigned wrappable counter."
   ::= {pr1645v2Lan2FGUInQueuesEntry 67567616}

pr1645v2Lan2FGUInQueuesOctetsDirectTx OBJECT-TYPE
   SYNTAX      Counter64
   MAX-ACCESS  read-only
   STATUS      current
   DESCRIPTION
      "Path: ethernet2.performance.ifInPriorityQueues.octets.directTx

       64 bit unsigned wrappable counter."
   ::= {pr1645v2Lan2FGUInQueuesEntry 67174400}

pr1645v2Lan2FGUInQueuesOctetsQueued OBJECT-TYPE
   SYNTAX      Counter64
   MAX-ACCESS  read-only
   STATUS      current
   DESCRIPTION
      "Path: ethernet2.performance.ifInPriorityQueues.octets.queued

       64 bit unsigned wrappable counter."
   ::= {pr1645v2Lan2FGUInQueuesEntry 67239936}

pr1645v2Lan2FGUInQueuesOctetsDropped OBJECT-TYPE
   SYNTAX      Counter64
   MAX-ACCESS  read-only
   STATUS      current
   DESCRIPTION
      "Path: ethernet2.performance.ifInPriorityQueues.octets.dropped

       64 bit unsigned wrappable counter."
   ::= {pr1645v2Lan2FGUInQueuesEntry 67305472}

pr1645v2Lan2FGUInQueuesOctetsRedDropped OBJECT-TYPE
   SYNTAX      Counter64
   MAX-ACCESS  read-only
   STATUS      current
   DESCRIPTION
      "Path: ethernet2.performance.ifInPriorityQueues.octets.redDropped

       64 bit unsigned wrappable counter."
   ::= {pr1645v2Lan2FGUInQueuesEntry 67502080}

pr1645v2Lan2FGUInQueuesOctetsCirTx OBJECT-TYPE
   SYNTAX      Counter64
   MAX-ACCESS  read-only
   STATUS      current
   DESCRIPTION
      "Path: ethernet2.performance.ifInPriorityQueues.octets.cirTx

       64 bit unsigned wrappable counter."
   ::= {pr1645v2Lan2FGUInQueuesEntry 67371008}

pr1645v2Lan2FGUInQueuesOctetsEirTx OBJECT-TYPE
   SYNTAX      Counter64
   MAX-ACCESS  read-only
   STATUS      current
   DESCRIPTION
      "Path: ethernet2.performance.ifInPriorityQueues.octets.eirTx

       64 bit unsigned wrappable counter."
   ::= {pr1645v2Lan2FGUInQueuesEntry 67436544}

pr1645v2Lan2FGUInQueuesOctetsViolateTx OBJECT-TYPE
   SYNTAX      Counter64
   MAX-ACCESS  read-only
   STATUS      current
   DESCRIPTION
      "Path: ethernet2.performance.ifInPriorityQueues.octets.violateTx

       64 bit unsigned wrappable counter."
   ::= {pr1645v2Lan2FGUInQueuesEntry 67633152}

pr1645v2Lan2FGUInQueuesOctetsBandwidth15sec OBJECT-TYPE
   SYNTAX      Integer32
   MAX-ACCESS  read-only
   STATUS      current
   DESCRIPTION
      "Path: ethernet2.performance.ifInPriorityQueues.octets.bandwidth.15sec

       unit name = bps
       formula = 8 * ; 8 /"
   ::= {pr1645v2Lan2FGUInQueuesEntry 70386944}

pr1645v2Lan2FGUInQueuesOctetsBandwidth30sec OBJECT-TYPE
   SYNTAX      Integer32
   MAX-ACCESS  read-only
   STATUS      current
   DESCRIPTION
      "Path: ethernet2.performance.ifInPriorityQueues.octets.bandwidth.30sec

       unit name = bps
       formula = 8 * ; 8 /"
   ::= {pr1645v2Lan2FGUInQueuesEntry 70388224}

pr1645v2Lan2FGUInQueuesOctetsBandwidth1min OBJECT-TYPE
   SYNTAX      Integer32
   MAX-ACCESS  read-only
   STATUS      current
   DESCRIPTION
      "Path: ethernet2.performance.ifInPriorityQueues.octets.bandwidth.1min

       unit name = bps
       formula = 8 * ; 8 /"
   ::= {pr1645v2Lan2FGUInQueuesEntry 70390784}

pr1645v2Lan2FGUInQueuesOctetsBandwidth2min OBJECT-TYPE
   SYNTAX      Integer32
   MAX-ACCESS  read-only
   STATUS      current
   DESCRIPTION
      "Path: ethernet2.performance.ifInPriorityQueues.octets.bandwidth.2min

       unit name = bps
       formula = 8 * ; 8 /"
   ::= {pr1645v2Lan2FGUInQueuesEntry 70395904}

pr1645v2Lan2FGUInQueuesOctetsBandwidth5min OBJECT-TYPE
   SYNTAX      Integer32
   MAX-ACCESS  read-only
   STATUS      current
   DESCRIPTION
      "Path: ethernet2.performance.ifInPriorityQueues.octets.bandwidth.5min

       unit name = bps
       formula = 8 * ; 8 /"
   ::= {pr1645v2Lan2FGUInQueuesEntry 70411264}

pr1645v2Lan2FGUInQueuesH2Performance OBJECT-TYPE
   SYNTAX      SEQUENCE OF Pr1645v2Lan2FGUInQueuesH2PerformanceEntry
   MAX-ACCESS  not-accessible
   STATUS      current
   DESCRIPTION
      ""
   ::= {pr1645v2Lan2FGUInQueues 83886080}

pr1645v2Lan2FGUInQueuesH2PerformanceEntry OBJECT-TYPE
   SYNTAX      Pr1645v2Lan2FGUInQueuesH2PerformanceEntry
   MAX-ACCESS  not-accessible
   STATUS      current
   DESCRIPTION
      ""
   INDEX      { pr1645v2Lan2FGUInQueuesTableIx,
                pr1645v2Lan2FGUInQueuesH2PerformanceTableIx }
   ::= {pr1645v2Lan2FGUInQueuesH2Performance 1}

Pr1645v2Lan2FGUInQueuesH2PerformanceEntry ::=
   SEQUENCE
      {
      pr1645v2Lan2FGUInQueuesH2PerformanceTableIx
         TableIndex,
      pr1645v2Lan2FGUInQueuesH2PerformanceSysUpTime
         TimeTicks,
      pr1645v2Lan2FGUInQueuesH2PerformanceTotPkts
         Counter64,
      pr1645v2Lan2FGUInQueuesH2PerformanceDirTxPkts
         Counter64,
      pr1645v2Lan2FGUInQueuesH2PerformanceQdPkts
         Counter64,
      pr1645v2Lan2FGUInQueuesH2PerformanceDropPkts
         Counter64,
      pr1645v2Lan2FGUInQueuesH2PerformanceRDropPkts
         Counter64,
      pr1645v2Lan2FGUInQueuesH2PerformanceCirTxPkts
         Counter64,
      pr1645v2Lan2FGUInQueuesH2PerformanceEirTxPkts
         Counter64,
      pr1645v2Lan2FGUInQueuesH2PerformanceViolTxPkts
         Counter64,
      pr1645v2Lan2FGUInQueuesH2PerformanceTotOcts
         Counter64,
      pr1645v2Lan2FGUInQueuesH2PerformanceDirTxOcts
         Counter64,
      pr1645v2Lan2FGUInQueuesH2PerformanceQdOcts
         Counter64,
      pr1645v2Lan2FGUInQueuesH2PerformanceDropOcts
         Counter64,
      pr1645v2Lan2FGUInQueuesH2PerformanceRDropOcts
         Counter64,
      pr1645v2Lan2FGUInQueuesH2PerformanceCirTxOcts
         Counter64,
      pr1645v2Lan2FGUInQueuesH2PerformanceEirTxOcts
         Counter64,
      pr1645v2Lan2FGUInQueuesH2PerformanceViolTxOcts
         Counter64,
      pr1645v2Lan2FGUInQueuesH2PerformanceBandwidth
         Integer32
      }

pr1645v2Lan2FGUInQueuesH2PerformanceTableIx OBJECT-TYPE
   SYNTAX      TableIndex
   MAX-ACCESS  not-accessible
   STATUS      current
   DESCRIPTION
      ""
   ::= {pr1645v2Lan2FGUInQueuesH2PerformanceEntry 11}

pr1645v2Lan2FGUInQueuesH2PerformanceSysUpTime OBJECT-TYPE
   SYNTAX      TimeTicks
   MAX-ACCESS  read-only
   STATUS      current
   DESCRIPTION
      "Path: ethernet2.performance.ifInPriorityQueues.h2Performance.sysUpTime

       Time in centi-second."
   ::= {pr1645v2Lan2FGUInQueuesH2PerformanceEntry 16777216}

pr1645v2Lan2FGUInQueuesH2PerformanceTotPkts OBJECT-TYPE
   SYNTAX      Counter64
   MAX-ACCESS  read-only
   STATUS      current
   DESCRIPTION
      "Path: ethernet2.performance.ifInPriorityQueues.h2Performance.totalPkts

       64 bit unsigned wrappable counter."
   ::= {pr1645v2Lan2FGUInQueuesH2PerformanceEntry 234881024}

pr1645v2Lan2FGUInQueuesH2PerformanceDirTxPkts OBJECT-TYPE
   SYNTAX      Counter64
   MAX-ACCESS  read-only
   STATUS      current
   DESCRIPTION
      "Path: ethernet2.performance.ifInPriorityQueues.h2Performance.directTxPkts

       64 bit unsigned wrappable counter."
   ::= {pr1645v2Lan2FGUInQueuesH2PerformanceEntry 33554432}

pr1645v2Lan2FGUInQueuesH2PerformanceQdPkts OBJECT-TYPE
   SYNTAX      Counter64
   MAX-ACCESS  read-only
   STATUS      current
   DESCRIPTION
      "Path: ethernet2.performance.ifInPriorityQueues.h2Performance.queuedPkts

       64 bit unsigned wrappable counter."
   ::= {pr1645v2Lan2FGUInQueuesH2PerformanceEntry 50331648}

pr1645v2Lan2FGUInQueuesH2PerformanceDropPkts OBJECT-TYPE
   SYNTAX      Counter64
   MAX-ACCESS  read-only
   STATUS      current
   DESCRIPTION
      "Path: ethernet2.performance.ifInPriorityQueues.h2Performance.droppedPkts

       64 bit unsigned wrappable counter."
   ::= {pr1645v2Lan2FGUInQueuesH2PerformanceEntry 67108864}

pr1645v2Lan2FGUInQueuesH2PerformanceRDropPkts OBJECT-TYPE
   SYNTAX      Counter64
   MAX-ACCESS  read-only
   STATUS      current
   DESCRIPTION
      "Path: ethernet2.performance.ifInPriorityQueues.h2Performance.redDroppedPkts

       64 bit unsigned wrappable counter."
   ::= {pr1645v2Lan2FGUInQueuesH2PerformanceEntry 201326592}

pr1645v2Lan2FGUInQueuesH2PerformanceCirTxPkts OBJECT-TYPE
   SYNTAX      Counter64
   MAX-ACCESS  read-only
   STATUS      current
   DESCRIPTION
      "Path: ethernet2.performance.ifInPriorityQueues.h2Performance.cirTxPkts

       64 bit unsigned wrappable counter."
   ::= {pr1645v2Lan2FGUInQueuesH2PerformanceEntry 83886080}

pr1645v2Lan2FGUInQueuesH2PerformanceEirTxPkts OBJECT-TYPE
   SYNTAX      Counter64
   MAX-ACCESS  read-only
   STATUS      current
   DESCRIPTION
      "Path: ethernet2.performance.ifInPriorityQueues.h2Performance.eirTxPkts

       64 bit unsigned wrappable counter."
   ::= {pr1645v2Lan2FGUInQueuesH2PerformanceEntry 100663296}

pr1645v2Lan2FGUInQueuesH2PerformanceViolTxPkts OBJECT-TYPE
   SYNTAX      Counter64
   MAX-ACCESS  read-only
   STATUS      current
   DESCRIPTION
      "Path: ethernet2.performance.ifInPriorityQueues.h2Performance.violateTxPkts

       64 bit unsigned wrappable counter."
   ::= {pr1645v2Lan2FGUInQueuesH2PerformanceEntry 301989888}

pr1645v2Lan2FGUInQueuesH2PerformanceTotOcts OBJECT-TYPE
   SYNTAX      Counter64
   MAX-ACCESS  read-only
   STATUS      current
   DESCRIPTION
      "Path: ethernet2.performance.ifInPriorityQueues.h2Performance.totalOctets

       64 bit unsigned wrappable counter."
   ::= {pr1645v2Lan2FGUInQueuesH2PerformanceEntry 251658240}

pr1645v2Lan2FGUInQueuesH2PerformanceDirTxOcts OBJECT-TYPE
   SYNTAX      Counter64
   MAX-ACCESS  read-only
   STATUS      current
   DESCRIPTION
      "Path: ethernet2.performance.ifInPriorityQueues.h2Performance.directTxOctets

       64 bit unsigned wrappable counter."
   ::= {pr1645v2Lan2FGUInQueuesH2PerformanceEntry 117440512}

pr1645v2Lan2FGUInQueuesH2PerformanceQdOcts OBJECT-TYPE
   SYNTAX      Counter64
   MAX-ACCESS  read-only
   STATUS      current
   DESCRIPTION
      "Path: ethernet2.performance.ifInPriorityQueues.h2Performance.queuedOctets

       64 bit unsigned wrappable counter."
   ::= {pr1645v2Lan2FGUInQueuesH2PerformanceEntry 134217728}

pr1645v2Lan2FGUInQueuesH2PerformanceDropOcts OBJECT-TYPE
   SYNTAX      Counter64
   MAX-ACCESS  read-only
   STATUS      current
   DESCRIPTION
      "Path: ethernet2.performance.ifInPriorityQueues.h2Performance.droppedOctets

       64 bit unsigned wrappable counter."
   ::= {pr1645v2Lan2FGUInQueuesH2PerformanceEntry 150994944}

pr1645v2Lan2FGUInQueuesH2PerformanceRDropOcts OBJECT-TYPE
   SYNTAX      Counter64
   MAX-ACCESS  read-only
   STATUS      current
   DESCRIPTION
      "Path: ethernet2.performance.ifInPriorityQueues.h2Performance.redDroppedOctets

       64 bit unsigned wrappable counter."
   ::= {pr1645v2Lan2FGUInQueuesH2PerformanceEntry 218103808}

pr1645v2Lan2FGUInQueuesH2PerformanceCirTxOcts OBJECT-TYPE
   SYNTAX      Counter64
   MAX-ACCESS  read-only
   STATUS      current
   DESCRIPTION
      "Path: ethernet2.performance.ifInPriorityQueues.h2Performance.cirTxOctets

       64 bit unsigned wrappable counter."
   ::= {pr1645v2Lan2FGUInQueuesH2PerformanceEntry 167772160}

pr1645v2Lan2FGUInQueuesH2PerformanceEirTxOcts OBJECT-TYPE
   SYNTAX      Counter64
   MAX-ACCESS  read-only
   STATUS      current
   DESCRIPTION
      "Path: ethernet2.performance.ifInPriorityQueues.h2Performance.eirTxOctets

       64 bit unsigned wrappable counter."
   ::= {pr1645v2Lan2FGUInQueuesH2PerformanceEntry 184549376}

pr1645v2Lan2FGUInQueuesH2PerformanceViolTxOcts OBJECT-TYPE
   SYNTAX      Counter64
   MAX-ACCESS  read-only
   STATUS      current
   DESCRIPTION
      "Path: ethernet2.performance.ifInPriorityQueues.h2Performance.violateTxOctets

       64 bit unsigned wrappable counter."
   ::= {pr1645v2Lan2FGUInQueuesH2PerformanceEntry 318767104}

pr1645v2Lan2FGUInQueuesH2PerformanceBandwidth OBJECT-TYPE
   SYNTAX      Integer32
   MAX-ACCESS  read-only
   STATUS      current
   DESCRIPTION
      "Path: ethernet2.performance.ifInPriorityQueues.h2Performance.bandwidth

       unit name = bps
       formula = 8 * ; 8 /"
   ::= {pr1645v2Lan2FGUInQueuesH2PerformanceEntry 268435456}

pr1645v2Lan2FGUInQueuesH24Performance OBJECT-TYPE
   SYNTAX      SEQUENCE OF Pr1645v2Lan2FGUInQueuesH24PerformanceEntry
   MAX-ACCESS  not-accessible
   STATUS      current
   DESCRIPTION
      ""
   ::= {pr1645v2Lan2FGUInQueues 100663296}

pr1645v2Lan2FGUInQueuesH24PerformanceEntry OBJECT-TYPE
   SYNTAX      Pr1645v2Lan2FGUInQueuesH24PerformanceEntry
   MAX-ACCESS  not-accessible
   STATUS      current
   DESCRIPTION
      ""
   INDEX      { pr1645v2Lan2FGUInQueuesTableIx,
                pr1645v2Lan2FGUInQueuesH24PerformanceTableIx }
   ::= {pr1645v2Lan2FGUInQueuesH24Performance 1}

Pr1645v2Lan2FGUInQueuesH24PerformanceEntry ::=
   SEQUENCE
      {
      pr1645v2Lan2FGUInQueuesH24PerformanceTableIx
         TableIndex,
      pr1645v2Lan2FGUInQueuesH24PerformanceSysUpTime
         TimeTicks,
      pr1645v2Lan2FGUInQueuesH24PerformanceTotPkts
         Counter64,
      pr1645v2Lan2FGUInQueuesH24PerformanceDirTxPkts
         Counter64,
      pr1645v2Lan2FGUInQueuesH24PerformanceQdPkts
         Counter64,
      pr1645v2Lan2FGUInQueuesH24PerformanceDropPkts
         Counter64,
      pr1645v2Lan2FGUInQueuesH24PerformanceRDropPkts
         Counter64,
      pr1645v2Lan2FGUInQueuesH24PerformanceCirTxPkts
         Counter64,
      pr1645v2Lan2FGUInQueuesH24PerformanceEirTxPkts
         Counter64,
      pr1645v2Lan2FGUInQueuesH24PerformanceViolTxPkts
         Counter64,
      pr1645v2Lan2FGUInQueuesH24PerformanceTotOcts
         Counter64,
      pr1645v2Lan2FGUInQueuesH24PerformanceDirTxOcts
         Counter64,
      pr1645v2Lan2FGUInQueuesH24PerformanceQdOcts
         Counter64,
      pr1645v2Lan2FGUInQueuesH24PerformanceDropOcts
         Counter64,
      pr1645v2Lan2FGUInQueuesH24PerformanceRDropOcts
         Counter64,
      pr1645v2Lan2FGUInQueuesH24PerformanceCirTxOcts
         Counter64,
      pr1645v2Lan2FGUInQueuesH24PerformanceEirTxOcts
         Counter64,
      pr1645v2Lan2FGUInQueuesH24PerformanceViolTxOcts
         Counter64,
      pr1645v2Lan2FGUInQueuesH24PerformanceBandwidth
         Integer32
      }

pr1645v2Lan2FGUInQueuesH24PerformanceTableIx OBJECT-TYPE
   SYNTAX      TableIndex
   MAX-ACCESS  not-accessible
   STATUS      current
   DESCRIPTION
      ""
   ::= {pr1645v2Lan2FGUInQueuesH24PerformanceEntry 11}

pr1645v2Lan2FGUInQueuesH24PerformanceSysUpTime OBJECT-TYPE
   SYNTAX      TimeTicks
   MAX-ACCESS  read-only
   STATUS      current
   DESCRIPTION
      "Path: ethernet2.performance.ifInPriorityQueues.h24Performance.sysUpTime

       Time in centi-second."
   ::= {pr1645v2Lan2FGUInQueuesH24PerformanceEntry 16777216}

pr1645v2Lan2FGUInQueuesH24PerformanceTotPkts OBJECT-TYPE
   SYNTAX      Counter64
   MAX-ACCESS  read-only
   STATUS      current
   DESCRIPTION
      "Path: ethernet2.performance.ifInPriorityQueues.h24Performance.totalPkts

       64 bit unsigned wrappable counter."
   ::= {pr1645v2Lan2FGUInQueuesH24PerformanceEntry 234881024}

pr1645v2Lan2FGUInQueuesH24PerformanceDirTxPkts OBJECT-TYPE
   SYNTAX      Counter64
   MAX-ACCESS  read-only
   STATUS      current
   DESCRIPTION
      "Path: ethernet2.performance.ifInPriorityQueues.h24Performance.directTxPkts

       64 bit unsigned wrappable counter."
   ::= {pr1645v2Lan2FGUInQueuesH24PerformanceEntry 33554432}

pr1645v2Lan2FGUInQueuesH24PerformanceQdPkts OBJECT-TYPE
   SYNTAX      Counter64
   MAX-ACCESS  read-only
   STATUS      current
   DESCRIPTION
      "Path: ethernet2.performance.ifInPriorityQueues.h24Performance.queuedPkts

       64 bit unsigned wrappable counter."
   ::= {pr1645v2Lan2FGUInQueuesH24PerformanceEntry 50331648}

pr1645v2Lan2FGUInQueuesH24PerformanceDropPkts OBJECT-TYPE
   SYNTAX      Counter64
   MAX-ACCESS  read-only
   STATUS      current
   DESCRIPTION
      "Path: ethernet2.performance.ifInPriorityQueues.h24Performance.droppedPkts

       64 bit unsigned wrappable counter."
   ::= {pr1645v2Lan2FGUInQueuesH24PerformanceEntry 67108864}

pr1645v2Lan2FGUInQueuesH24PerformanceRDropPkts OBJECT-TYPE
   SYNTAX      Counter64
   MAX-ACCESS  read-only
   STATUS      current
   DESCRIPTION
      "Path: ethernet2.performance.ifInPriorityQueues.h24Performance.redDroppedPkts

       64 bit unsigned wrappable counter."
   ::= {pr1645v2Lan2FGUInQueuesH24PerformanceEntry 201326592}

pr1645v2Lan2FGUInQueuesH24PerformanceCirTxPkts OBJECT-TYPE
   SYNTAX      Counter64
   MAX-ACCESS  read-only
   STATUS      current
   DESCRIPTION
      "Path: ethernet2.performance.ifInPriorityQueues.h24Performance.cirTxPkts

       64 bit unsigned wrappable counter."
   ::= {pr1645v2Lan2FGUInQueuesH24PerformanceEntry 83886080}

pr1645v2Lan2FGUInQueuesH24PerformanceEirTxPkts OBJECT-TYPE
   SYNTAX      Counter64
   MAX-ACCESS  read-only
   STATUS      current
   DESCRIPTION
      "Path: ethernet2.performance.ifInPriorityQueues.h24Performance.eirTxPkts

       64 bit unsigned wrappable counter."
   ::= {pr1645v2Lan2FGUInQueuesH24PerformanceEntry 100663296}

pr1645v2Lan2FGUInQueuesH24PerformanceViolTxPkts OBJECT-TYPE
   SYNTAX      Counter64
   MAX-ACCESS  read-only
   STATUS      current
   DESCRIPTION
      "Path: ethernet2.performance.ifInPriorityQueues.h24Performance.violateTxPkts

       64 bit unsigned wrappable counter."
   ::= {pr1645v2Lan2FGUInQueuesH24PerformanceEntry 301989888}

pr1645v2Lan2FGUInQueuesH24PerformanceTotOcts OBJECT-TYPE
   SYNTAX      Counter64
   MAX-ACCESS  read-only
   STATUS      current
   DESCRIPTION
      "Path: ethernet2.performance.ifInPriorityQueues.h24Performance.totalOctets

       64 bit unsigned wrappable counter."
   ::= {pr1645v2Lan2FGUInQueuesH24PerformanceEntry 251658240}

pr1645v2Lan2FGUInQueuesH24PerformanceDirTxOcts OBJECT-TYPE
   SYNTAX      Counter64
   MAX-ACCESS  read-only
   STATUS      current
   DESCRIPTION
      "Path: ethernet2.performance.ifInPriorityQueues.h24Performance.directTxOctets

       64 bit unsigned wrappable counter."
   ::= {pr1645v2Lan2FGUInQueuesH24PerformanceEntry 117440512}

pr1645v2Lan2FGUInQueuesH24PerformanceQdOcts OBJECT-TYPE
   SYNTAX      Counter64
   MAX-ACCESS  read-only
   STATUS      current
   DESCRIPTION
      "Path: ethernet2.performance.ifInPriorityQueues.h24Performance.queuedOctets

       64 bit unsigned wrappable counter."
   ::= {pr1645v2Lan2FGUInQueuesH24PerformanceEntry 134217728}

pr1645v2Lan2FGUInQueuesH24PerformanceDropOcts OBJECT-TYPE
   SYNTAX      Counter64
   MAX-ACCESS  read-only
   STATUS      current
   DESCRIPTION
      "Path: ethernet2.performance.ifInPriorityQueues.h24Performance.droppedOctets

       64 bit unsigned wrappable counter."
   ::= {pr1645v2Lan2FGUInQueuesH24PerformanceEntry 150994944}

pr1645v2Lan2FGUInQueuesH24PerformanceRDropOcts OBJECT-TYPE
   SYNTAX      Counter64
   MAX-ACCESS  read-only
   STATUS      current
   DESCRIPTION
      "Path: ethernet2.performance.ifInPriorityQueues.h24Performance.redDroppedOctets

       64 bit unsigned wrappable counter."
   ::= {pr1645v2Lan2FGUInQueuesH24PerformanceEntry 218103808}

pr1645v2Lan2FGUInQueuesH24PerformanceCirTxOcts OBJECT-TYPE
   SYNTAX      Counter64
   MAX-ACCESS  read-only
   STATUS      current
   DESCRIPTION
      "Path: ethernet2.performance.ifInPriorityQueues.h24Performance.cirTxOctets

       64 bit unsigned wrappable counter."
   ::= {pr1645v2Lan2FGUInQueuesH24PerformanceEntry 167772160}

pr1645v2Lan2FGUInQueuesH24PerformanceEirTxOcts OBJECT-TYPE
   SYNTAX      Counter64
   MAX-ACCESS  read-only
   STATUS      current
   DESCRIPTION
      "Path: ethernet2.performance.ifInPriorityQueues.h24Performance.eirTxOctets

       64 bit unsigned wrappable counter."
   ::= {pr1645v2Lan2FGUInQueuesH24PerformanceEntry 184549376}

pr1645v2Lan2FGUInQueuesH24PerformanceViolTxOcts OBJECT-TYPE
   SYNTAX      Counter64
   MAX-ACCESS  read-only
   STATUS      current
   DESCRIPTION
      "Path: ethernet2.performance.ifInPriorityQueues.h24Performance.violateTxOctets

       64 bit unsigned wrappable counter."
   ::= {pr1645v2Lan2FGUInQueuesH24PerformanceEntry 318767104}

pr1645v2Lan2FGUInQueuesH24PerformanceBandwidth OBJECT-TYPE
   SYNTAX      Integer32
   MAX-ACCESS  read-only
   STATUS      current
   DESCRIPTION
      "Path: ethernet2.performance.ifInPriorityQueues.h24Performance.bandwidth

       unit name = bps
       formula = 8 * ; 8 /"
   ::= {pr1645v2Lan2FGUInQueuesH24PerformanceEntry 268435456}

pr1645v2Lan2FGUInQueuesD7Performance OBJECT-TYPE
   SYNTAX      SEQUENCE OF Pr1645v2Lan2FGUInQueuesD7PerformanceEntry
   MAX-ACCESS  not-accessible
   STATUS      current
   DESCRIPTION
      ""
   ::= {pr1645v2Lan2FGUInQueues 117440512}

pr1645v2Lan2FGUInQueuesD7PerformanceEntry OBJECT-TYPE
   SYNTAX      Pr1645v2Lan2FGUInQueuesD7PerformanceEntry
   MAX-ACCESS  not-accessible
   STATUS      current
   DESCRIPTION
      ""
   INDEX      { pr1645v2Lan2FGUInQueuesTableIx,
                pr1645v2Lan2FGUInQueuesD7PerformanceTableIx }
   ::= {pr1645v2Lan2FGUInQueuesD7Performance 1}

Pr1645v2Lan2FGUInQueuesD7PerformanceEntry ::=
   SEQUENCE
      {
      pr1645v2Lan2FGUInQueuesD7PerformanceTableIx
         TableIndex,
      pr1645v2Lan2FGUInQueuesD7PerformanceSysUpTime
         TimeTicks,
      pr1645v2Lan2FGUInQueuesD7PerformanceTotPkts
         Counter64,
      pr1645v2Lan2FGUInQueuesD7PerformanceDirTxPkts
         Counter64,
      pr1645v2Lan2FGUInQueuesD7PerformanceQdPkts
         Counter64,
      pr1645v2Lan2FGUInQueuesD7PerformanceDropPkts
         Counter64,
      pr1645v2Lan2FGUInQueuesD7PerformanceRDropPkts
         Counter64,
      pr1645v2Lan2FGUInQueuesD7PerformanceCirTxPkts
         Counter64,
      pr1645v2Lan2FGUInQueuesD7PerformanceEirTxPkts
         Counter64,
      pr1645v2Lan2FGUInQueuesD7PerformanceViolTxPkts
         Counter64,
      pr1645v2Lan2FGUInQueuesD7PerformanceTotOcts
         Counter64,
      pr1645v2Lan2FGUInQueuesD7PerformanceDirTxOcts
         Counter64,
      pr1645v2Lan2FGUInQueuesD7PerformanceQdOcts
         Counter64,
      pr1645v2Lan2FGUInQueuesD7PerformanceDropOcts
         Counter64,
      pr1645v2Lan2FGUInQueuesD7PerformanceRDropOcts
         Counter64,
      pr1645v2Lan2FGUInQueuesD7PerformanceCirTxOcts
         Counter64,
      pr1645v2Lan2FGUInQueuesD7PerformanceEirTxOcts
         Counter64,
      pr1645v2Lan2FGUInQueuesD7PerformanceViolTxOcts
         Counter64,
      pr1645v2Lan2FGUInQueuesD7PerformanceBandwidth
         Integer32
      }

pr1645v2Lan2FGUInQueuesD7PerformanceTableIx OBJECT-TYPE
   SYNTAX      TableIndex
   MAX-ACCESS  not-accessible
   STATUS      current
   DESCRIPTION
      ""
   ::= {pr1645v2Lan2FGUInQueuesD7PerformanceEntry 11}

pr1645v2Lan2FGUInQueuesD7PerformanceSysUpTime OBJECT-TYPE
   SYNTAX      TimeTicks
   MAX-ACCESS  read-only
   STATUS      current
   DESCRIPTION
      "Path: ethernet2.performance.ifInPriorityQueues.d7Performance.sysUpTime

       Time in centi-second."
   ::= {pr1645v2Lan2FGUInQueuesD7PerformanceEntry 16777216}

pr1645v2Lan2FGUInQueuesD7PerformanceTotPkts OBJECT-TYPE
   SYNTAX      Counter64
   MAX-ACCESS  read-only
   STATUS      current
   DESCRIPTION
      "Path: ethernet2.performance.ifInPriorityQueues.d7Performance.totalPkts

       64 bit unsigned wrappable counter."
   ::= {pr1645v2Lan2FGUInQueuesD7PerformanceEntry 234881024}

pr1645v2Lan2FGUInQueuesD7PerformanceDirTxPkts OBJECT-TYPE
   SYNTAX      Counter64
   MAX-ACCESS  read-only
   STATUS      current
   DESCRIPTION
      "Path: ethernet2.performance.ifInPriorityQueues.d7Performance.directTxPkts

       64 bit unsigned wrappable counter."
   ::= {pr1645v2Lan2FGUInQueuesD7PerformanceEntry 33554432}

pr1645v2Lan2FGUInQueuesD7PerformanceQdPkts OBJECT-TYPE
   SYNTAX      Counter64
   MAX-ACCESS  read-only
   STATUS      current
   DESCRIPTION
      "Path: ethernet2.performance.ifInPriorityQueues.d7Performance.queuedPkts

       64 bit unsigned wrappable counter."
   ::= {pr1645v2Lan2FGUInQueuesD7PerformanceEntry 50331648}

pr1645v2Lan2FGUInQueuesD7PerformanceDropPkts OBJECT-TYPE
   SYNTAX      Counter64
   MAX-ACCESS  read-only
   STATUS      current
   DESCRIPTION
      "Path: ethernet2.performance.ifInPriorityQueues.d7Performance.droppedPkts

       64 bit unsigned wrappable counter."
   ::= {pr1645v2Lan2FGUInQueuesD7PerformanceEntry 67108864}

pr1645v2Lan2FGUInQueuesD7PerformanceRDropPkts OBJECT-TYPE
   SYNTAX      Counter64
   MAX-ACCESS  read-only
   STATUS      current
   DESCRIPTION
      "Path: ethernet2.performance.ifInPriorityQueues.d7Performance.redDroppedPkts

       64 bit unsigned wrappable counter."
   ::= {pr1645v2Lan2FGUInQueuesD7PerformanceEntry 201326592}

pr1645v2Lan2FGUInQueuesD7PerformanceCirTxPkts OBJECT-TYPE
   SYNTAX      Counter64
   MAX-ACCESS  read-only
   STATUS      current
   DESCRIPTION
      "Path: ethernet2.performance.ifInPriorityQueues.d7Performance.cirTxPkts

       64 bit unsigned wrappable counter."
   ::= {pr1645v2Lan2FGUInQueuesD7PerformanceEntry 83886080}

pr1645v2Lan2FGUInQueuesD7PerformanceEirTxPkts OBJECT-TYPE
   SYNTAX      Counter64
   MAX-ACCESS  read-only
   STATUS      current
   DESCRIPTION
      "Path: ethernet2.performance.ifInPriorityQueues.d7Performance.eirTxPkts

       64 bit unsigned wrappable counter."
   ::= {pr1645v2Lan2FGUInQueuesD7PerformanceEntry 100663296}

pr1645v2Lan2FGUInQueuesD7PerformanceViolTxPkts OBJECT-TYPE
   SYNTAX      Counter64
   MAX-ACCESS  read-only
   STATUS      current
   DESCRIPTION
      "Path: ethernet2.performance.ifInPriorityQueues.d7Performance.violateTxPkts

       64 bit unsigned wrappable counter."
   ::= {pr1645v2Lan2FGUInQueuesD7PerformanceEntry 301989888}

pr1645v2Lan2FGUInQueuesD7PerformanceTotOcts OBJECT-TYPE
   SYNTAX      Counter64
   MAX-ACCESS  read-only
   STATUS      current
   DESCRIPTION
      "Path: ethernet2.performance.ifInPriorityQueues.d7Performance.totalOctets

       64 bit unsigned wrappable counter."
   ::= {pr1645v2Lan2FGUInQueuesD7PerformanceEntry 251658240}

pr1645v2Lan2FGUInQueuesD7PerformanceDirTxOcts OBJECT-TYPE
   SYNTAX      Counter64
   MAX-ACCESS  read-only
   STATUS      current
   DESCRIPTION
      "Path: ethernet2.performance.ifInPriorityQueues.d7Performance.directTxOctets

       64 bit unsigned wrappable counter."
   ::= {pr1645v2Lan2FGUInQueuesD7PerformanceEntry 117440512}

pr1645v2Lan2FGUInQueuesD7PerformanceQdOcts OBJECT-TYPE
   SYNTAX      Counter64
   MAX-ACCESS  read-only
   STATUS      current
   DESCRIPTION
      "Path: ethernet2.performance.ifInPriorityQueues.d7Performance.queuedOctets

       64 bit unsigned wrappable counter."
   ::= {pr1645v2Lan2FGUInQueuesD7PerformanceEntry 134217728}

pr1645v2Lan2FGUInQueuesD7PerformanceDropOcts OBJECT-TYPE
   SYNTAX      Counter64
   MAX-ACCESS  read-only
   STATUS      current
   DESCRIPTION
      "Path: ethernet2.performance.ifInPriorityQueues.d7Performance.droppedOctets

       64 bit unsigned wrappable counter."
   ::= {pr1645v2Lan2FGUInQueuesD7PerformanceEntry 150994944}

pr1645v2Lan2FGUInQueuesD7PerformanceRDropOcts OBJECT-TYPE
   SYNTAX      Counter64
   MAX-ACCESS  read-only
   STATUS      current
   DESCRIPTION
      "Path: ethernet2.performance.ifInPriorityQueues.d7Performance.redDroppedOctets

       64 bit unsigned wrappable counter."
   ::= {pr1645v2Lan2FGUInQueuesD7PerformanceEntry 218103808}

pr1645v2Lan2FGUInQueuesD7PerformanceCirTxOcts OBJECT-TYPE
   SYNTAX      Counter64
   MAX-ACCESS  read-only
   STATUS      current
   DESCRIPTION
      "Path: ethernet2.performance.ifInPriorityQueues.d7Performance.cirTxOctets

       64 bit unsigned wrappable counter."
   ::= {pr1645v2Lan2FGUInQueuesD7PerformanceEntry 167772160}

pr1645v2Lan2FGUInQueuesD7PerformanceEirTxOcts OBJECT-TYPE
   SYNTAX      Counter64
   MAX-ACCESS  read-only
   STATUS      current
   DESCRIPTION
      "Path: ethernet2.performance.ifInPriorityQueues.d7Performance.eirTxOctets

       64 bit unsigned wrappable counter."
   ::= {pr1645v2Lan2FGUInQueuesD7PerformanceEntry 184549376}

pr1645v2Lan2FGUInQueuesD7PerformanceViolTxOcts OBJECT-TYPE
   SYNTAX      Counter64
   MAX-ACCESS  read-only
   STATUS      current
   DESCRIPTION
      "Path: ethernet2.performance.ifInPriorityQueues.d7Performance.violateTxOctets

       64 bit unsigned wrappable counter."
   ::= {pr1645v2Lan2FGUInQueuesD7PerformanceEntry 318767104}

pr1645v2Lan2FGUInQueuesD7PerformanceBandwidth OBJECT-TYPE
   SYNTAX      Integer32
   MAX-ACCESS  read-only
   STATUS      current
   DESCRIPTION
      "Path: ethernet2.performance.ifInPriorityQueues.d7Performance.bandwidth

       unit name = bps
       formula = 8 * ; 8 /"
   ::= {pr1645v2Lan2FGUInQueuesD7PerformanceEntry 268435456}


pr1645v2Lan2FGUInBandwidth OBJECT IDENTIFIER ::= {pr1645v2Lan2FGU 181}

pr1645v2Lan2FGUInBandwidthSSC OBJECT IDENTIFIER ::= {pr1645v2Lan2FGUInBandwidth 1}

pr1645v2Lan2FGUInBandwidthEntry OBJECT IDENTIFIER ::= {pr1645v2Lan2FGUInBandwidthSSC 1}

pr1645v2Lan2FGUInBandwidth15sec OBJECT-TYPE
   SYNTAX      Integer32
   MAX-ACCESS  read-only
   STATUS      current
   DESCRIPTION
      "Path: ethernet2.performance.ifInBandwidth.15sec

       unit name = bps
       formula = 8 * ; 8 /"
   ::= {pr1645v2Lan2FGUInBandwidthEntry 83886080}

pr1645v2Lan2FGUInBandwidth30sec OBJECT-TYPE
   SYNTAX      Integer32
   MAX-ACCESS  read-only
   STATUS      current
   DESCRIPTION
      "Path: ethernet2.performance.ifInBandwidth.30sec

       unit name = bps
       formula = 8 * ; 8 /"
   ::= {pr1645v2Lan2FGUInBandwidthEntry 167772160}

pr1645v2Lan2FGUInBandwidth1min OBJECT-TYPE
   SYNTAX      Integer32
   MAX-ACCESS  read-only
   STATUS      current
   DESCRIPTION
      "Path: ethernet2.performance.ifInBandwidth.1min

       unit name = bps
       formula = 8 * ; 8 /"
   ::= {pr1645v2Lan2FGUInBandwidthEntry 335544320}

pr1645v2Lan2FGUInBandwidth2min OBJECT-TYPE
   SYNTAX      Integer32
   MAX-ACCESS  read-only
   STATUS      current
   DESCRIPTION
      "Path: ethernet2.performance.ifInBandwidth.2min

       unit name = bps
       formula = 8 * ; 8 /"
   ::= {pr1645v2Lan2FGUInBandwidthEntry 671088640}

pr1645v2Lan2FGUInBandwidth5min OBJECT-TYPE
   SYNTAX      Integer32
   MAX-ACCESS  read-only
   STATUS      current
   DESCRIPTION
      "Path: ethernet2.performance.ifInBandwidth.5min

       unit name = bps
       formula = 8 * ; 8 /"
   ::= {pr1645v2Lan2FGUInBandwidthEntry 1677721600}


pr1645v2Lan2FGUOutOctets OBJECT-TYPE
   SYNTAX      Counter64
   MAX-ACCESS  read-only
   STATUS      current
   DESCRIPTION
      "Path: ethernet2.performance.ifOutOctets
       Info: ifOutOctets

       64 bit unsigned wrappable counter."
   ::= {pr1645v2Lan2FGU 115}


pr1645v2Lan2FGUOutUcastPkts OBJECT-TYPE
   SYNTAX      Counter64
   MAX-ACCESS  read-only
   STATUS      current
   DESCRIPTION
      "Path: ethernet2.performance.ifOutUcastPkts
       Info: ifOutUcastPkts

       64 bit unsigned wrappable counter."
   ::= {pr1645v2Lan2FGU 116}


pr1645v2Lan2FGUOutNUcastPkts OBJECT-TYPE
   SYNTAX      Counter64
   MAX-ACCESS  read-only
   STATUS      current
   DESCRIPTION
      "Path: ethernet2.performance.ifOutNUcastPkts
       Info: ifOutNUcastPkts

       64 bit unsigned wrappable counter."
   ::= {pr1645v2Lan2FGU 117}


pr1645v2Lan2FGUOutBcastPkts OBJECT-TYPE
   SYNTAX      Counter64
   MAX-ACCESS  read-only
   STATUS      current
   DESCRIPTION
      "Path: ethernet2.performance.ifOutBcastPkts
       Info: ifOutBcastPkts

       64 bit unsigned wrappable counter."
   ::= {pr1645v2Lan2FGU 217}


pr1645v2Lan2FGUOutMcastPkts OBJECT-TYPE
   SYNTAX      Counter64
   MAX-ACCESS  read-only
   STATUS      current
   DESCRIPTION
      "Path: ethernet2.performance.ifOutMcastPkts
       Info: ifOutMcastPkts

       64 bit unsigned wrappable counter."
   ::= {pr1645v2Lan2FGU 227}


pr1645v2Lan2FGUOutDiscards OBJECT-TYPE
   SYNTAX      Counter64
   MAX-ACCESS  read-only
   STATUS      current
   DESCRIPTION
      "Path: ethernet2.performance.ifOutDiscards
       Info: ifOutDiscards

       64 bit unsigned wrappable counter."
   ::= {pr1645v2Lan2FGU 118}


pr1645v2Lan2FGUOutErrors OBJECT-TYPE
   SYNTAX      Counter64
   MAX-ACCESS  read-only
   STATUS      current
   DESCRIPTION
      "Path: ethernet2.performance.ifOutErrors
       Info: ifOutErrors

       64 bit unsigned wrappable counter."
   ::= {pr1645v2Lan2FGU 119}


pr1645v2Lan2FGUOutQLen OBJECT-TYPE
   SYNTAX      Gauge32
   MAX-ACCESS  read-only
   STATUS      current
   DESCRIPTION
      "Path: ethernet2.performance.ifOutQLen
       Info: ifOutQLen

       32 bit unsigned gauge value."
   ::= {pr1645v2Lan2FGU 120}


pr1645v2Lan2FGUOutDropEx OBJECT-TYPE
   SYNTAX      Counter64
   MAX-ACCESS  read-only
   STATUS      current
   DESCRIPTION
      "Path: ethernet2.performance.ifOutDropLevelExceeded
       Info: ifOutDiscards

       64 bit unsigned wrappable counter."
   ::= {pr1645v2Lan2FGU 127}


pr1645v2Lan2FGUOutDropNoArp OBJECT-TYPE
   SYNTAX      Counter64
   MAX-ACCESS  read-only
   STATUS      current
   DESCRIPTION
      "Path: ethernet2.performance.ifOutDiscardsNoArp
       Info: ifOutDiscards

       64 bit unsigned wrappable counter."
   ::= {pr1645v2Lan2FGU 134}


pr1645v2Lan2FGUOutDropFilter OBJECT-TYPE
   SYNTAX      Counter64
   MAX-ACCESS  read-only
   STATUS      current
   DESCRIPTION
      "Path: ethernet2.performance.ifOutDiscardsFilter
       Info: ifOutDiscards

       64 bit unsigned wrappable counter."
   ::= {pr1645v2Lan2FGU 138}


pr1645v2Lan2FGUOutQueues OBJECT IDENTIFIER ::= {pr1645v2Lan2FGU 129}

pr1645v2Lan2FGUOutQueuesSSCTable OBJECT-TYPE
   SYNTAX      SEQUENCE OF Pr1645v2Lan2FGUOutQueuesEntry
   MAX-ACCESS  not-accessible
   STATUS      current
   DESCRIPTION
      "Queue Lengths"
   ::= {pr1645v2Lan2FGUOutQueues 1}

pr1645v2Lan2FGUOutQueuesEntry OBJECT-TYPE
   SYNTAX      Pr1645v2Lan2FGUOutQueuesEntry
   MAX-ACCESS  not-accessible
   STATUS      current
   DESCRIPTION
      ""
   INDEX      { pr1645v2Lan2FGUOutQueuesTableIx }
   ::= {pr1645v2Lan2FGUOutQueuesSSCTable 1}

Pr1645v2Lan2FGUOutQueuesEntry ::=
   SEQUENCE
      {
      pr1645v2Lan2FGUOutQueuesTableIx
         TableIndex,
      pr1645v2Lan2FGUOutQueuesName
         INTEGER,
      pr1645v2Lan2FGUOutQueuesLength
         Integer32,
      pr1645v2Lan2FGUOutQueuesOctetLength
         Integer32,
      pr1645v2Lan2FGUOutQueuesRedLength
         Integer32,
      pr1645v2Lan2FGUOutQueuesPacketsTotal
         Counter64,
      pr1645v2Lan2FGUOutQueuesPacketsDirectTx
         Counter64,
      pr1645v2Lan2FGUOutQueuesPacketsQueued
         Counter64,
      pr1645v2Lan2FGUOutQueuesPacketsDropped
         Counter64,
      pr1645v2Lan2FGUOutQueuesPacketsRedDropped
         Counter64,
      pr1645v2Lan2FGUOutQueuesPacketsCirTx
         Counter64,
      pr1645v2Lan2FGUOutQueuesPacketsEirTx
         Counter64,
      pr1645v2Lan2FGUOutQueuesPacketsViolateTx
         Counter64,
      pr1645v2Lan2FGUOutQueuesOctetsTotal
         Counter64,
      pr1645v2Lan2FGUOutQueuesOctetsDirectTx
         Counter64,
      pr1645v2Lan2FGUOutQueuesOctetsQueued
         Counter64,
      pr1645v2Lan2FGUOutQueuesOctetsDropped
         Counter64,
      pr1645v2Lan2FGUOutQueuesOctetsRedDropped
         Counter64,
      pr1645v2Lan2FGUOutQueuesOctetsCirTx
         Counter64,
      pr1645v2Lan2FGUOutQueuesOctetsEirTx
         Counter64,
      pr1645v2Lan2FGUOutQueuesOctetsViolateTx
         Counter64,
      pr1645v2Lan2FGUOutQueuesOctetsBandwidth15sec
         Integer32,
      pr1645v2Lan2FGUOutQueuesOctetsBandwidth30sec
         Integer32,
      pr1645v2Lan2FGUOutQueuesOctetsBandwidth1min
         Integer32,
      pr1645v2Lan2FGUOutQueuesOctetsBandwidth2min
         Integer32,
      pr1645v2Lan2FGUOutQueuesOctetsBandwidth5min
         Integer32
      }

pr1645v2Lan2FGUOutQueuesTableIx OBJECT-TYPE
   SYNTAX      TableIndex
   MAX-ACCESS  not-accessible
   STATUS      current
   DESCRIPTION
      ""
   ::= {pr1645v2Lan2FGUOutQueuesEntry 11}

pr1645v2Lan2FGUOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGUOutQueuesEntry 16777216}

pr1645v2Lan2FGUOutQueuesLength OBJECT-TYPE
   SYNTAX      Integer32
   MAX-ACCESS  read-only
   STATUS      current
   DESCRIPTION
      "Path: ethernet2.performance.ifOutPriorityQueues.length"
   ::= {pr1645v2Lan2FGUOutQueuesEntry 33554432}

pr1645v2Lan2FGUOutQueuesOctetLength OBJECT-TYPE
   SYNTAX      Integer32
   MAX-ACCESS  read-only
   STATUS      current
   DESCRIPTION
      "Path: ethernet2.performance.ifOutPriorityQueues.octetLength"
   ::= {pr1645v2Lan2FGUOutQueuesEntry 150994944}

pr1645v2Lan2FGUOutQueuesRedLength OBJECT-TYPE
   SYNTAX      Integer32
   MAX-ACCESS  read-only
   STATUS      current
   DESCRIPTION
      "Path: ethernet2.performance.ifOutPriorityQueues.redLength"
   ::= {pr1645v2Lan2FGUOutQueuesEntry 134217728}

pr1645v2Lan2FGUOutQueuesPacketsTotal OBJECT-TYPE
   SYNTAX      Counter64
   MAX-ACCESS  read-only
   STATUS      current
   DESCRIPTION
      "Path: ethernet2.performance.ifOutPriorityQueues.packets.total

       64 bit unsigned wrappable counter."
   ::= {pr1645v2Lan2FGUOutQueuesEntry 50790400}

pr1645v2Lan2FGUOutQueuesPacketsDirectTx OBJECT-TYPE
   SYNTAX      Counter64
   MAX-ACCESS  read-only
   STATUS      current
   DESCRIPTION
      "Path: ethernet2.performance.ifOutPriorityQueues.packets.directTx

       64 bit unsigned wrappable counter."
   ::= {pr1645v2Lan2FGUOutQueuesEntry 50397184}

pr1645v2Lan2FGUOutQueuesPacketsQueued OBJECT-TYPE
   SYNTAX      Counter64
   MAX-ACCESS  read-only
   STATUS      current
   DESCRIPTION
      "Path: ethernet2.performance.ifOutPriorityQueues.packets.queued

       64 bit unsigned wrappable counter."
   ::= {pr1645v2Lan2FGUOutQueuesEntry 50462720}

pr1645v2Lan2FGUOutQueuesPacketsDropped OBJECT-TYPE
   SYNTAX      Counter64
   MAX-ACCESS  read-only
   STATUS      current
   DESCRIPTION
      "Path: ethernet2.performance.ifOutPriorityQueues.packets.dropped

       64 bit unsigned wrappable counter."
   ::= {pr1645v2Lan2FGUOutQueuesEntry 50528256}

pr1645v2Lan2FGUOutQueuesPacketsRedDropped OBJECT-TYPE
   SYNTAX      Counter64
   MAX-ACCESS  read-only
   STATUS      current
   DESCRIPTION
      "Path: ethernet2.performance.ifOutPriorityQueues.packets.redDropped

       64 bit unsigned wrappable counter."
   ::= {pr1645v2Lan2FGUOutQueuesEntry 50724864}

pr1645v2Lan2FGUOutQueuesPacketsCirTx OBJECT-TYPE
   SYNTAX      Counter64
   MAX-ACCESS  read-only
   STATUS      current
   DESCRIPTION
      "Path: ethernet2.performance.ifOutPriorityQueues.packets.cirTx

       64 bit unsigned wrappable counter."
   ::= {pr1645v2Lan2FGUOutQueuesEntry 50593792}

pr1645v2Lan2FGUOutQueuesPacketsEirTx OBJECT-TYPE
   SYNTAX      Counter64
   MAX-ACCESS  read-only
   STATUS      current
   DESCRIPTION
      "Path: ethernet2.performance.ifOutPriorityQueues.packets.eirTx

       64 bit unsigned wrappable counter."
   ::= {pr1645v2Lan2FGUOutQueuesEntry 50659328}

pr1645v2Lan2FGUOutQueuesPacketsViolateTx OBJECT-TYPE
   SYNTAX      Counter64
   MAX-ACCESS  read-only
   STATUS      current
   DESCRIPTION
      "Path: ethernet2.performance.ifOutPriorityQueues.packets.violateTx

       64 bit unsigned wrappable counter."
   ::= {pr1645v2Lan2FGUOutQueuesEntry 50855936}

pr1645v2Lan2FGUOutQueuesOctetsTotal OBJECT-TYPE
   SYNTAX      Counter64
   MAX-ACCESS  read-only
   STATUS      current
   DESCRIPTION
      "Path: ethernet2.performance.ifOutPriorityQueues.octets.total

       64 bit unsigned wrappable counter."
   ::= {pr1645v2Lan2FGUOutQueuesEntry 67567616}

pr1645v2Lan2FGUOutQueuesOctetsDirectTx OBJECT-TYPE
   SYNTAX      Counter64
   MAX-ACCESS  read-only
   STATUS      current
   DESCRIPTION
      "Path: ethernet2.performance.ifOutPriorityQueues.octets.directTx

       64 bit unsigned wrappable counter."
   ::= {pr1645v2Lan2FGUOutQueuesEntry 67174400}

pr1645v2Lan2FGUOutQueuesOctetsQueued OBJECT-TYPE
   SYNTAX      Counter64
   MAX-ACCESS  read-only
   STATUS      current
   DESCRIPTION
      "Path: ethernet2.performance.ifOutPriorityQueues.octets.queued

       64 bit unsigned wrappable counter."
   ::= {pr1645v2Lan2FGUOutQueuesEntry 67239936}

pr1645v2Lan2FGUOutQueuesOctetsDropped OBJECT-TYPE
   SYNTAX      Counter64
   MAX-ACCESS  read-only
   STATUS      current
   DESCRIPTION
      "Path: ethernet2.performance.ifOutPriorityQueues.octets.dropped

       64 bit unsigned wrappable counter."
   ::= {pr1645v2Lan2FGUOutQueuesEntry 67305472}

pr1645v2Lan2FGUOutQueuesOctetsRedDropped OBJECT-TYPE
   SYNTAX      Counter64
   MAX-ACCESS  read-only
   STATUS      current
   DESCRIPTION
      "Path: ethernet2.performance.ifOutPriorityQueues.octets.redDropped

       64 bit unsigned wrappable counter."
   ::= {pr1645v2Lan2FGUOutQueuesEntry 67502080}

pr1645v2Lan2FGUOutQueuesOctetsCirTx OBJECT-TYPE
   SYNTAX      Counter64
   MAX-ACCESS  read-only
   STATUS      current
   DESCRIPTION
      "Path: ethernet2.performance.ifOutPriorityQueues.octets.cirTx

       64 bit unsigned wrappable counter."
   ::= {pr1645v2Lan2FGUOutQueuesEntry 67371008}

pr1645v2Lan2FGUOutQueuesOctetsEirTx OBJECT-TYPE
   SYNTAX      Counter64
   MAX-ACCESS  read-only
   STATUS      current
   DESCRIPTION
      "Path: ethernet2.performance.ifOutPriorityQueues.octets.eirTx

       64 bit unsigned wrappable counter."
   ::= {pr1645v2Lan2FGUOutQueuesEntry 67436544}

pr1645v2Lan2FGUOutQueuesOctetsViolateTx OBJECT-TYPE
   SYNTAX      Counter64
   MAX-ACCESS  read-only
   STATUS      current
   DESCRIPTION
      "Path: ethernet2.performance.ifOutPriorityQueues.octets.violateTx

       64 bit unsigned wrappable counter."
   ::= {pr1645v2Lan2FGUOutQueuesEntry 67633152}

pr1645v2Lan2FGUOutQueuesOctetsBandwidth15sec OBJECT-TYPE
   SYNTAX      Integer32
   MAX-ACCESS  read-only
   STATUS      current
   DESCRIPTION
      "Path: ethernet2.performance.ifOutPriorityQueues.octets.bandwidth.15sec

       unit name = bps
       formula = 8 * ; 8 /"
   ::= {pr1645v2Lan2FGUOutQueuesEntry 70386944}

pr1645v2Lan2FGUOutQueuesOctetsBandwidth30sec OBJECT-TYPE
   SYNTAX      Integer32
   MAX-ACCESS  read-only
   STATUS      current
   DESCRIPTION
      "Path: ethernet2.performance.ifOutPriorityQueues.octets.bandwidth.30sec

       unit name = bps
       formula = 8 * ; 8 /"
   ::= {pr1645v2Lan2FGUOutQueuesEntry 70388224}

pr1645v2Lan2FGUOutQueuesOctetsBandwidth1min OBJECT-TYPE
   SYNTAX      Integer32
   MAX-ACCESS  read-only
   STATUS      current
   DESCRIPTION
      "Path: ethernet2.performance.ifOutPriorityQueues.octets.bandwidth.1min

       unit name = bps
       formula = 8 * ; 8 /"
   ::= {pr1645v2Lan2FGUOutQueuesEntry 70390784}

pr1645v2Lan2FGUOutQueuesOctetsBandwidth2min OBJECT-TYPE
   SYNTAX      Integer32
   MAX-ACCESS  read-only
   STATUS      current
   DESCRIPTION
      "Path: ethernet2.performance.ifOutPriorityQueues.octets.bandwidth.2min

       unit name = bps
       formula = 8 * ; 8 /"
   ::= {pr1645v2Lan2FGUOutQueuesEntry 70395904}

pr1645v2Lan2FGUOutQueuesOctetsBandwidth5min OBJECT-TYPE
   SYNTAX      Integer32
   MAX-ACCESS  read-only
   STATUS      current
   DESCRIPTION
      "Path: ethernet2.performance.ifOutPriorityQueues.octets.bandwidth.5min

       unit name = bps
       formula = 8 * ; 8 /"
   ::= {pr1645v2Lan2FGUOutQueuesEntry 70411264}

pr1645v2Lan2FGUOutQueuesH2Performance OBJECT-TYPE
   SYNTAX      SEQUENCE OF Pr1645v2Lan2FGUOutQueuesH2PerformanceEntry
   MAX-ACCESS  not-accessible
   STATUS      current
   DESCRIPTION
      ""
   ::= {pr1645v2Lan2FGUOutQueues 83886080}

pr1645v2Lan2FGUOutQueuesH2PerformanceEntry OBJECT-TYPE
   SYNTAX      Pr1645v2Lan2FGUOutQueuesH2PerformanceEntry
   MAX-ACCESS  not-accessible
   STATUS      current
   DESCRIPTION
      ""
   INDEX      { pr1645v2Lan2FGUOutQueuesTableIx,
                pr1645v2Lan2FGUOutQueuesH2PerformanceTableIx }
   ::= {pr1645v2Lan2FGUOutQueuesH2Performance 1}

Pr1645v2Lan2FGUOutQueuesH2PerformanceEntry ::=
   SEQUENCE
      {
      pr1645v2Lan2FGUOutQueuesH2PerformanceTableIx
         TableIndex,
      pr1645v2Lan2FGUOutQueuesH2PerformanceSysUpTime
         TimeTicks,
      pr1645v2Lan2FGUOutQueuesH2PerformanceTotPkts
         Counter64,
      pr1645v2Lan2FGUOutQueuesH2PerformanceDirTxPkts
         Counter64,
      pr1645v2Lan2FGUOutQueuesH2PerformanceQdPkts
         Counter64,
      pr1645v2Lan2FGUOutQueuesH2PerformanceDropPkts
         Counter64,
      pr1645v2Lan2FGUOutQueuesH2PerformanceRDropPkts
         Counter64,
      pr1645v2Lan2FGUOutQueuesH2PerformanceCirTxPkts
         Counter64,
      pr1645v2Lan2FGUOutQueuesH2PerformanceEirTxPkts
         Counter64,
      pr1645v2Lan2FGUOutQueuesH2PerformanceViolTxPkts
         Counter64,
      pr1645v2Lan2FGUOutQueuesH2PerformanceTotOcts
         Counter64,
      pr1645v2Lan2FGUOutQueuesH2PerformanceDirTxOcts
         Counter64,
      pr1645v2Lan2FGUOutQueuesH2PerformanceQdOcts
         Counter64,
      pr1645v2Lan2FGUOutQueuesH2PerformanceDropOcts
         Counter64,
      pr1645v2Lan2FGUOutQueuesH2PerformanceRDropOcts
         Counter64,
      pr1645v2Lan2FGUOutQueuesH2PerformanceCirTxOcts
         Counter64,
      pr1645v2Lan2FGUOutQueuesH2PerformanceEirTxOcts
         Counter64,
      pr1645v2Lan2FGUOutQueuesH2PerformanceViolTxOcts
         Counter64,
      pr1645v2Lan2FGUOutQueuesH2PerformanceBandwidth
         Integer32
      }

pr1645v2Lan2FGUOutQueuesH2PerformanceTableIx OBJECT-TYPE
   SYNTAX      TableIndex
   MAX-ACCESS  not-accessible
   STATUS      current
   DESCRIPTION
      ""
   ::= {pr1645v2Lan2FGUOutQueuesH2PerformanceEntry 11}

pr1645v2Lan2FGUOutQueuesH2PerformanceSysUpTime OBJECT-TYPE
   SYNTAX      TimeTicks
   MAX-ACCESS  read-only
   STATUS      current
   DESCRIPTION
      "Path: ethernet2.performance.ifOutPriorityQueues.h2Performance.sysUpTime

       Time in centi-second."
   ::= {pr1645v2Lan2FGUOutQueuesH2PerformanceEntry 16777216}

pr1645v2Lan2FGUOutQueuesH2PerformanceTotPkts OBJECT-TYPE
   SYNTAX      Counter64
   MAX-ACCESS  read-only
   STATUS      current
   DESCRIPTION
      "Path: ethernet2.performance.ifOutPriorityQueues.h2Performance.totalPkts

       64 bit unsigned wrappable counter."
   ::= {pr1645v2Lan2FGUOutQueuesH2PerformanceEntry 234881024}

pr1645v2Lan2FGUOutQueuesH2PerformanceDirTxPkts OBJECT-TYPE
   SYNTAX      Counter64
   MAX-ACCESS  read-only
   STATUS      current
   DESCRIPTION
      "Path: ethernet2.performance.ifOutPriorityQueues.h2Performance.directTxPkts

       64 bit unsigned wrappable counter."
   ::= {pr1645v2Lan2FGUOutQueuesH2PerformanceEntry 33554432}

pr1645v2Lan2FGUOutQueuesH2PerformanceQdPkts OBJECT-TYPE
   SYNTAX      Counter64
   MAX-ACCESS  read-only
   STATUS      current
   DESCRIPTION
      "Path: ethernet2.performance.ifOutPriorityQueues.h2Performance.queuedPkts

       64 bit unsigned wrappable counter."
   ::= {pr1645v2Lan2FGUOutQueuesH2PerformanceEntry 50331648}

pr1645v2Lan2FGUOutQueuesH2PerformanceDropPkts OBJECT-TYPE
   SYNTAX      Counter64
   MAX-ACCESS  read-only
   STATUS      current
   DESCRIPTION
      "Path: ethernet2.performance.ifOutPriorityQueues.h2Performance.droppedPkts

       64 bit unsigned wrappable counter."
   ::= {pr1645v2Lan2FGUOutQueuesH2PerformanceEntry 67108864}

pr1645v2Lan2FGUOutQueuesH2PerformanceRDropPkts OBJECT-TYPE
   SYNTAX      Counter64
   MAX-ACCESS  read-only
   STATUS      current
   DESCRIPTION
      "Path: ethernet2.performance.ifOutPriorityQueues.h2Performance.redDroppedPkts

       64 bit unsigned wrappable counter."
   ::= {pr1645v2Lan2FGUOutQueuesH2PerformanceEntry 201326592}

pr1645v2Lan2FGUOutQueuesH2PerformanceCirTxPkts OBJECT-TYPE
   SYNTAX      Counter64
   MAX-ACCESS  read-only
   STATUS      current
   DESCRIPTION
      "Path: ethernet2.performance.ifOutPriorityQueues.h2Performance.cirTxPkts

       64 bit unsigned wrappable counter."
   ::= {pr1645v2Lan2FGUOutQueuesH2PerformanceEntry 83886080}

pr1645v2Lan2FGUOutQueuesH2PerformanceEirTxPkts OBJECT-TYPE
   SYNTAX      Counter64
   MAX-ACCESS  read-only
   STATUS      current
   DESCRIPTION
      "Path: ethernet2.performance.ifOutPriorityQueues.h2Performance.eirTxPkts

       64 bit unsigned wrappable counter."
   ::= {pr1645v2Lan2FGUOutQueuesH2PerformanceEntry 100663296}

pr1645v2Lan2FGUOutQueuesH2PerformanceViolTxPkts OBJECT-TYPE
   SYNTAX      Counter64
   MAX-ACCESS  read-only
   STATUS      current
   DESCRIPTION
      "Path: ethernet2.performance.ifOutPriorityQueues.h2Performance.violateTxPkts

       64 bit unsigned wrappable counter."
   ::= {pr1645v2Lan2FGUOutQueuesH2PerformanceEntry 301989888}

pr1645v2Lan2FGUOutQueuesH2PerformanceTotOcts OBJECT-TYPE
   SYNTAX      Counter64
   MAX-ACCESS  read-only
   STATUS      current
   DESCRIPTION
      "Path: ethernet2.performance.ifOutPriorityQueues.h2Performance.totalOctets

       64 bit unsigned wrappable counter."
   ::= {pr1645v2Lan2FGUOutQueuesH2PerformanceEntry 251658240}

pr1645v2Lan2FGUOutQueuesH2PerformanceDirTxOcts OBJECT-TYPE
   SYNTAX      Counter64
   MAX-ACCESS  read-only
   STATUS      current
   DESCRIPTION
      "Path: ethernet2.performance.ifOutPriorityQueues.h2Performance.directTxOctets

       64 bit unsigned wrappable counter."
   ::= {pr1645v2Lan2FGUOutQueuesH2PerformanceEntry 117440512}

pr1645v2Lan2FGUOutQueuesH2PerformanceQdOcts OBJECT-TYPE
   SYNTAX      Counter64
   MAX-ACCESS  read-only
   STATUS      current
   DESCRIPTION
      "Path: ethernet2.performance.ifOutPriorityQueues.h2Performance.queuedOctets

       64 bit unsigned wrappable counter."
   ::= {pr1645v2Lan2FGUOutQueuesH2PerformanceEntry 134217728}

pr1645v2Lan2FGUOutQueuesH2PerformanceDropOcts OBJECT-TYPE
   SYNTAX      Counter64
   MAX-ACCESS  read-only
   STATUS      current
   DESCRIPTION
      "Path: ethernet2.performance.ifOutPriorityQueues.h2Performance.droppedOctets

       64 bit unsigned wrappable counter."
   ::= {pr1645v2Lan2FGUOutQueuesH2PerformanceEntry 150994944}

pr1645v2Lan2FGUOutQueuesH2PerformanceRDropOcts OBJECT-TYPE
   SYNTAX      Counter64
   MAX-ACCESS  read-only
   STATUS      current
   DESCRIPTION
      "Path: ethernet2.performance.ifOutPriorityQueues.h2Performance.redDroppedOctets

       64 bit unsigned wrappable counter."
   ::= {pr1645v2Lan2FGUOutQueuesH2PerformanceEntry 218103808}

pr1645v2Lan2FGUOutQueuesH2PerformanceCirTxOcts OBJECT-TYPE
   SYNTAX      Counter64
   MAX-ACCESS  read-only
   STATUS      current
   DESCRIPTION
      "Path: ethernet2.performance.ifOutPriorityQueues.h2Performance.cirTxOctets

       64 bit unsigned wrappable counter."
   ::= {pr1645v2Lan2FGUOutQueuesH2PerformanceEntry 167772160}

pr1645v2Lan2FGUOutQueuesH2PerformanceEirTxOcts OBJECT-TYPE
   SYNTAX      Counter64
   MAX-ACCESS  read-only
   STATUS      current
   DESCRIPTION
      "Path: ethernet2.performance.ifOutPriorityQueues.h2Performance.eirTxOctets

       64 bit unsigned wrappable counter."
   ::= {pr1645v2Lan2FGUOutQueuesH2PerformanceEntry 184549376}

pr1645v2Lan2FGUOutQueuesH2PerformanceViolTxOcts OBJECT-TYPE
   SYNTAX      Counter64
   MAX-ACCESS  read-only
   STATUS      current
   DESCRIPTION
      "Path: ethernet2.performance.ifOutPriorityQueues.h2Performance.violateTxOctets

       64 bit unsigned wrappable counter."
   ::= {pr1645v2Lan2FGUOutQueuesH2PerformanceEntry 318767104}

pr1645v2Lan2FGUOutQueuesH2PerformanceBandwidth OBJECT-TYPE
   SYNTAX      Integer32
   MAX-ACCESS  read-only
   STATUS      current
   DESCRIPTION
      "Path: ethernet2.performance.ifOutPriorityQueues.h2Performance.bandwidth

       unit name = bps
       formula = 8 * ; 8 /"
   ::= {pr1645v2Lan2FGUOutQueuesH2PerformanceEntry 268435456}

pr1645v2Lan2FGUOutQueuesH24Performance OBJECT-TYPE
   SYNTAX      SEQUENCE OF Pr1645v2Lan2FGUOutQueuesH24PerformanceEntry
   MAX-ACCESS  not-accessible
   STATUS      current
   DESCRIPTION
      ""
   ::= {pr1645v2Lan2FGUOutQueues 100663296}

pr1645v2Lan2FGUOutQueuesH24PerformanceEntry OBJECT-TYPE
   SYNTAX      Pr1645v2Lan2FGUOutQueuesH24PerformanceEntry
   MAX-ACCESS  not-accessible
   STATUS      current
   DESCRIPTION
      ""
   INDEX      { pr1645v2Lan2FGUOutQueuesTableIx,
                pr1645v2Lan2FGUOutQueuesH24PerformanceTableIx }
   ::= {pr1645v2Lan2FGUOutQueuesH24Performance 1}

Pr1645v2Lan2FGUOutQueuesH24PerformanceEntry ::=
   SEQUENCE
      {
      pr1645v2Lan2FGUOutQueuesH24PerformanceTableIx
         TableIndex,
      pr1645v2Lan2FGUOutQueuesH24PerformanceSysUpTime
         TimeTicks,
      pr1645v2Lan2FGUOutQueuesH24PerformanceTotPkts
         Counter64,
      pr1645v2Lan2FGUOutQueuesH24PerformanceDirTxPkts
         Counter64,
      pr1645v2Lan2FGUOutQueuesH24PerformanceQdPkts
         Counter64,
      pr1645v2Lan2FGUOutQueuesH24PerformanceDropPkts
         Counter64,
      pr1645v2Lan2FGUOutQueuesH24PerformanceRDropPkts
         Counter64,
      pr1645v2Lan2FGUOutQueuesH24PerformanceCirTxPkts
         Counter64,
      pr1645v2Lan2FGUOutQueuesH24PerformanceEirTxPkts
         Counter64,
      pr1645v2Lan2FGUOutQueuesH24PerformanceViolTxPkts
         Counter64,
      pr1645v2Lan2FGUOutQueuesH24PerformanceTotOcts
         Counter64,
      pr1645v2Lan2FGUOutQueuesH24PerformanceDirTxOcts
         Counter64,
      pr1645v2Lan2FGUOutQueuesH24PerformanceQdOcts
         Counter64,
      pr1645v2Lan2FGUOutQueuesH24PerformanceDropOcts
         Counter64,
      pr1645v2Lan2FGUOutQueuesH24PerformanceRDropOcts
         Counter64,
      pr1645v2Lan2FGUOutQueuesH24PerformanceCirTxOcts
         Counter64,
      pr1645v2Lan2FGUOutQueuesH24PerformanceEirTxOcts
         Counter64,
      pr1645v2Lan2FGUOutQueuesH24PerformanceViolTxOcts
         Counter64,
      pr1645v2Lan2FGUOutQueuesH24PerformanceBandwidth
         Integer32
      }

pr1645v2Lan2FGUOutQueuesH24PerformanceTableIx OBJECT-TYPE
   SYNTAX      TableIndex
   MAX-ACCESS  not-accessible
   STATUS      current
   DESCRIPTION
      ""
   ::= {pr1645v2Lan2FGUOutQueuesH24PerformanceEntry 11}

pr1645v2Lan2FGUOutQueuesH24PerformanceSysUpTime OBJECT-TYPE
   SYNTAX      TimeTicks
   MAX-ACCESS  read-only
   STATUS      current
   DESCRIPTION
      "Path: ethernet2.performance.ifOutPriorityQueues.h24Performance.sysUpTime

       Time in centi-second."
   ::= {pr1645v2Lan2FGUOutQueuesH24PerformanceEntry 16777216}

pr1645v2Lan2FGUOutQueuesH24PerformanceTotPkts OBJECT-TYPE
   SYNTAX      Counter64
   MAX-ACCESS  read-only
   STATUS      current
   DESCRIPTION
      "Path: ethernet2.performance.ifOutPriorityQueues.h24Performance.totalPkts

       64 bit unsigned wrappable counter."
   ::= {pr1645v2Lan2FGUOutQueuesH24PerformanceEntry 234881024}

pr1645v2Lan2FGUOutQueuesH24PerformanceDirTxPkts OBJECT-TYPE
   SYNTAX      Counter64
   MAX-ACCESS  read-only
   STATUS      current
   DESCRIPTION
      "Path: ethernet2.performance.ifOutPriorityQueues.h24Performance.directTxPkts

       64 bit unsigned wrappable counter."
   ::= {pr1645v2Lan2FGUOutQueuesH24PerformanceEntry 33554432}

pr1645v2Lan2FGUOutQueuesH24PerformanceQdPkts OBJECT-TYPE
   SYNTAX      Counter64
   MAX-ACCESS  read-only
   STATUS      current
   DESCRIPTION
      "Path: ethernet2.performance.ifOutPriorityQueues.h24Performance.queuedPkts

       64 bit unsigned wrappable counter."
   ::= {pr1645v2Lan2FGUOutQueuesH24PerformanceEntry 50331648}

pr1645v2Lan2FGUOutQueuesH24PerformanceDropPkts OBJECT-TYPE
   SYNTAX      Counter64
   MAX-ACCESS  read-only
   STATUS      current
   DESCRIPTION
      "Path: ethernet2.performance.ifOutPriorityQueues.h24Performance.droppedPkts

       64 bit unsigned wrappable counter."
   ::= {pr1645v2Lan2FGUOutQueuesH24PerformanceEntry 67108864}

pr1645v2Lan2FGUOutQueuesH24PerformanceRDropPkts OBJECT-TYPE
   SYNTAX      Counter64
   MAX-ACCESS  read-only
   STATUS      current
   DESCRIPTION
      "Path: ethernet2.performance.ifOutPriorityQueues.h24Performance.redDroppedPkts

       64 bit unsigned wrappable counter."
   ::= {pr1645v2Lan2FGUOutQueuesH24PerformanceEntry 201326592}

pr1645v2Lan2FGUOutQueuesH24PerformanceCirTxPkts OBJECT-TYPE
   SYNTAX      Counter64
   MAX-ACCESS  read-only
   STATUS      current
   DESCRIPTION
      "Path: ethernet2.performance.ifOutPriorityQueues.h24Performance.cirTxPkts

       64 bit unsigned wrappable counter."
   ::= {pr1645v2Lan2FGUOutQueuesH24PerformanceEntry 83886080}

pr1645v2Lan2FGUOutQueuesH24PerformanceEirTxPkts OBJECT-TYPE
   SYNTAX      Counter64
   MAX-ACCESS  read-only
   STATUS      current
   DESCRIPTION
      "Path: ethernet2.performance.ifOutPriorityQueues.h24Performance.eirTxPkts

       64 bit unsigned wrappable counter."
   ::= {pr1645v2Lan2FGUOutQueuesH24PerformanceEntry 100663296}

pr1645v2Lan2FGUOutQueuesH24PerformanceViolTxPkts OBJECT-TYPE
   SYNTAX      Counter64
   MAX-ACCESS  read-only
   STATUS      current
   DESCRIPTION
      "Path: ethernet2.performance.ifOutPriorityQueues.h24Performance.violateTxPkts

       64 bit unsigned wrappable counter."
   ::= {pr1645v2Lan2FGUOutQueuesH24PerformanceEntry 301989888}

pr1645v2Lan2FGUOutQueuesH24PerformanceTotOcts OBJECT-TYPE
   SYNTAX      Counter64
   MAX-ACCESS  read-only
   STATUS      current
   DESCRIPTION
      "Path: ethernet2.performance.ifOutPriorityQueues.h24Performance.totalOctets

       64 bit unsigned wrappable counter."
   ::= {pr1645v2Lan2FGUOutQueuesH24PerformanceEntry 251658240}

pr1645v2Lan2FGUOutQueuesH24PerformanceDirTxOcts OBJECT-TYPE
   SYNTAX      Counter64
   MAX-ACCESS  read-only
   STATUS      current
   DESCRIPTION
      "Path: ethernet2.performance.ifOutPriorityQueues.h24Performance.directTxOctets

       64 bit unsigned wrappable counter."
   ::= {pr1645v2Lan2FGUOutQueuesH24PerformanceEntry 117440512}

pr1645v2Lan2FGUOutQueuesH24PerformanceQdOcts OBJECT-TYPE
   SYNTAX      Counter64
   MAX-ACCESS  read-only
   STATUS      current
   DESCRIPTION
      "Path: ethernet2.performance.ifOutPriorityQueues.h24Performance.queuedOctets

       64 bit unsigned wrappable counter."
   ::= {pr1645v2Lan2FGUOutQueuesH24PerformanceEntry 134217728}

pr1645v2Lan2FGUOutQueuesH24PerformanceDropOcts OBJECT-TYPE
   SYNTAX      Counter64
   MAX-ACCESS  read-only
   STATUS      current
   DESCRIPTION
      "Path: ethernet2.performance.ifOutPriorityQueues.h24Performance.droppedOctets

       64 bit unsigned wrappable counter."
   ::= {pr1645v2Lan2FGUOutQueuesH24PerformanceEntry 150994944}

pr1645v2Lan2FGUOutQueuesH24PerformanceRDropOcts OBJECT-TYPE
   SYNTAX      Counter64
   MAX-ACCESS  read-only
   STATUS      current
   DESCRIPTION
      "Path: ethernet2.performance.ifOutPriorityQueues.h24Performance.redDroppedOctets

       64 bit unsigned wrappable counter."
   ::= {pr1645v2Lan2FGUOutQueuesH24PerformanceEntry 218103808}

pr1645v2Lan2FGUOutQueuesH24PerformanceCirTxOcts OBJECT-TYPE
   SYNTAX      Counter64
   MAX-ACCESS  read-only
   STATUS      current
   DESCRIPTION
      "Path: ethernet2.performance.ifOutPriorityQueues.h24Performance.cirTxOctets

       64 bit unsigned wrappable counter."
   ::= {pr1645v2Lan2FGUOutQueuesH24PerformanceEntry 167772160}

pr1645v2Lan2FGUOutQueuesH24PerformanceEirTxOcts OBJECT-TYPE
   SYNTAX      Counter64
   MAX-ACCESS  read-only
   STATUS      current
   DESCRIPTION
      "Path: ethernet2.performance.ifOutPriorityQueues.h24Performance.eirTxOctets

       64 bit unsigned wrappable counter."
   ::= {pr1645v2Lan2FGUOutQueuesH24PerformanceEntry 184549376}

pr1645v2Lan2FGUOutQueuesH24PerformanceViolTxOcts OBJECT-TYPE
   SYNTAX      Counter64
   MAX-ACCESS  read-only
   STATUS      current
   DESCRIPTION
      "Path: ethernet2.performance.ifOutPriorityQueues.h24Performance.violateTxOctets

       64 bit unsigned wrappable counter."
   ::= {pr1645v2Lan2FGUOutQueuesH24PerformanceEntry 318767104}

pr1645v2Lan2FGUOutQueuesH24PerformanceBandwidth OBJECT-TYPE
   SYNTAX      Integer32
   MAX-ACCESS  read-only
   STATUS      current
   DESCRIPTION
      "Path: ethernet2.performance.ifOutPriorityQueues.h24Performance.bandwidth

       unit name = bps
       formula = 8 * ; 8 /"
   ::= {pr1645v2Lan2FGUOutQueuesH24PerformanceEntry 268435456}

pr1645v2Lan2FGUOutQueuesD7Performance OBJECT-TYPE
   SYNTAX      SEQUENCE OF Pr1645v2Lan2FGUOutQueuesD7PerformanceEntry
   MAX-ACCESS  not-accessible
   STATUS      current
   DESCRIPTION
      ""
   ::= {pr1645v2Lan2FGUOutQueues 117440512}

pr1645v2Lan2FGUOutQueuesD7PerformanceEntry OBJECT-TYPE
   SYNTAX      Pr1645v2Lan2FGUOutQueuesD7PerformanceEntry
   MAX-ACCESS  not-accessible
   STATUS      current
   DESCRIPTION
      ""
   INDEX      { pr1645v2Lan2FGUOutQueuesTableIx,
                pr1645v2Lan2FGUOutQueuesD7PerformanceTableIx }
   ::= {pr1645v2Lan2FGUOutQueuesD7Performance 1}

Pr1645v2Lan2FGUOutQueuesD7PerformanceEntry ::=
   SEQUENCE
      {
      pr1645v2Lan2FGUOutQueuesD7PerformanceTableIx
         TableIndex,
      pr1645v2Lan2FGUOutQueuesD7PerformanceSysUpTime
         TimeTicks,
      pr1645v2Lan2FGUOutQueuesD7PerformanceTotPkts
         Counter64,
      pr1645v2Lan2FGUOutQueuesD7PerformanceDirTxPkts
         Counter64,
      pr1645v2Lan2FGUOutQueuesD7PerformanceQdPkts
         Counter64,
      pr1645v2Lan2FGUOutQueuesD7PerformanceDropPkts
         Counter64,
      pr1645v2Lan2FGUOutQueuesD7PerformanceRDropPkts
         Counter64,
      pr1645v2Lan2FGUOutQueuesD7PerformanceCirTxPkts
         Counter64,
      pr1645v2Lan2FGUOutQueuesD7PerformanceEirTxPkts
         Counter64,
      pr1645v2Lan2FGUOutQueuesD7PerformanceViolTxPkts
         Counter64,
      pr1645v2Lan2FGUOutQueuesD7PerformanceTotOcts
         Counter64,
      pr1645v2Lan2FGUOutQueuesD7PerformanceDirTxOcts
         Counter64,
      pr1645v2Lan2FGUOutQueuesD7PerformanceQdOcts
         Counter64,
      pr1645v2Lan2FGUOutQueuesD7PerformanceDropOcts
         Counter64,
      pr1645v2Lan2FGUOutQueuesD7PerformanceRDropOcts
         Counter64,
      pr1645v2Lan2FGUOutQueuesD7PerformanceCirTxOcts
         Counter64,
      pr1645v2Lan2FGUOutQueuesD7PerformanceEirTxOcts
         Counter64,
      pr1645v2Lan2FGUOutQueuesD7PerformanceViolTxOcts
         Counter64,
      pr1645v2Lan2FGUOutQueuesD7PerformanceBandwidth
         Integer32
      }

pr1645v2Lan2FGUOutQueuesD7PerformanceTableIx OBJECT-TYPE
   SYNTAX      TableIndex
   MAX-ACCESS  not-accessible
   STATUS      current
   DESCRIPTION
      ""
   ::= {pr1645v2Lan2FGUOutQueuesD7PerformanceEntry 11}

pr1645v2Lan2FGUOutQueuesD7PerformanceSysUpTime OBJECT-TYPE
   SYNTAX      TimeTicks
   MAX-ACCESS  read-only
   STATUS      current
   DESCRIPTION
      "Path: ethernet2.performance.ifOutPriorityQueues.d7Performance.sysUpTime

       Time in centi-second."
   ::= {pr1645v2Lan2FGUOutQueuesD7PerformanceEntry 16777216}

pr1645v2Lan2FGUOutQueuesD7PerformanceTotPkts OBJECT-TYPE
   SYNTAX      Counter64
   MAX-ACCESS  read-only
   STATUS      current
   DESCRIPTION
      "Path: ethernet2.performance.ifOutPriorityQueues.d7Performance.totalPkts

       64 bit unsigned wrappable counter."
   ::= {pr1645v2Lan2FGUOutQueuesD7PerformanceEntry 234881024}

pr1645v2Lan2FGUOutQueuesD7PerformanceDirTxPkts OBJECT-TYPE
   SYNTAX      Counter64
   MAX-ACCESS  read-only
   STATUS      current
   DESCRIPTION
      "Path: ethernet2.performance.ifOutPriorityQueues.d7Performance.directTxPkts

       64 bit unsigned wrappable counter."
   ::= {pr1645v2Lan2FGUOutQueuesD7PerformanceEntry 33554432}

pr1645v2Lan2FGUOutQueuesD7PerformanceQdPkts OBJECT-TYPE
   SYNTAX      Counter64
   MAX-ACCESS  read-only
   STATUS      current
   DESCRIPTION
      "Path: ethernet2.performance.ifOutPriorityQueues.d7Performance.queuedPkts

       64 bit unsigned wrappable counter."
   ::= {pr1645v2Lan2FGUOutQueuesD7PerformanceEntry 50331648}

pr1645v2Lan2FGUOutQueuesD7PerformanceDropPkts OBJECT-TYPE
   SYNTAX      Counter64
   MAX-ACCESS  read-only
   STATUS      current
   DESCRIPTION
      "Path: ethernet2.performance.ifOutPriorityQueues.d7Performance.droppedPkts

       64 bit unsigned wrappable counter."
   ::= {pr1645v2Lan2FGUOutQueuesD7PerformanceEntry 67108864}

pr1645v2Lan2FGUOutQueuesD7PerformanceRDropPkts OBJECT-TYPE
   SYNTAX      Counter64
   MAX-ACCESS  read-only
   STATUS      current
   DESCRIPTION
      "Path: ethernet2.performance.ifOutPriorityQueues.d7Performance.redDroppedPkts

       64 bit unsigned wrappable counter."
   ::= {pr1645v2Lan2FGUOutQueuesD7PerformanceEntry 201326592}

pr1645v2Lan2FGUOutQueuesD7PerformanceCirTxPkts OBJECT-TYPE
   SYNTAX      Counter64
   MAX-ACCESS  read-only
   STATUS      current
   DESCRIPTION
      "Path: ethernet2.performance.ifOutPriorityQueues.d7Performance.cirTxPkts

       64 bit unsigned wrappable counter."
   ::= {pr1645v2Lan2FGUOutQueuesD7PerformanceEntry 83886080}

pr1645v2Lan2FGUOutQueuesD7PerformanceEirTxPkts OBJECT-TYPE
   SYNTAX      Counter64
   MAX-ACCESS  read-only
   STATUS      current
   DESCRIPTION
      "Path: ethernet2.performance.ifOutPriorityQueues.d7Performance.eirTxPkts

       64 bit unsigned wrappable counter."
   ::= {pr1645v2Lan2FGUOutQueuesD7PerformanceEntry 100663296}

pr1645v2Lan2FGUOutQueuesD7PerformanceViolTxPkts OBJECT-TYPE
   SYNTAX      Counter64
   MAX-ACCESS  read-only
   STATUS      current
   DESCRIPTION
      "Path: ethernet2.performance.ifOutPriorityQueues.d7Performance.violateTxPkts

       64 bit unsigned wrappable counter."
   ::= {pr1645v2Lan2FGUOutQueuesD7PerformanceEntry 301989888}

pr1645v2Lan2FGUOutQueuesD7PerformanceTotOcts OBJECT-TYPE
   SYNTAX      Counter64
   MAX-ACCESS  read-only
   STATUS      current
   DESCRIPTION
      "Path: ethernet2.performance.ifOutPriorityQueues.d7Performance.totalOctets

       64 bit unsigned wrappable counter."
   ::= {pr1645v2Lan2FGUOutQueuesD7PerformanceEntry 251658240}

pr1645v2Lan2FGUOutQueuesD7PerformanceDirTxOcts OBJECT-TYPE
   SYNTAX      Counter64
   MAX-ACCESS  read-only
   STATUS      current
   DESCRIPTION
      "Path: ethernet2.performance.ifOutPriorityQueues.d7Performance.directTxOctets

       64 bit unsigned wrappable counter."
   ::= {pr1645v2Lan2FGUOutQueuesD7PerformanceEntry 117440512}

pr1645v2Lan2FGUOutQueuesD7PerformanceQdOcts OBJECT-TYPE
   SYNTAX      Counter64
   MAX-ACCESS  read-only
   STATUS      current
   DESCRIPTION
      "Path: ethernet2.performance.ifOutPriorityQueues.d7Performance.queuedOctets

       64 bit unsigned wrappable counter."
   ::= {pr1645v2Lan2FGUOutQueuesD7PerformanceEntry 134217728}

pr1645v2Lan2FGUOutQueuesD7PerformanceDropOcts OBJECT-TYPE
   SYNTAX      Counter64
   MAX-ACCESS  read-only
   STATUS      current
   DESCRIPTION
      "Path: ethernet2.performance.ifOutPriorityQueues.d7Performance.droppedOctets

       64 bit unsigned wrappable counter."
   ::= {pr1645v2Lan2FGUOutQueuesD7PerformanceEntry 150994944}

pr1645v2Lan2FGUOutQueuesD7PerformanceRDropOcts OBJECT-TYPE
   SYNTAX      Counter64
   MAX-ACCESS  read-only
   STATUS      current
   DESCRIPTION
      "Path: ethernet2.performance.ifOutPriorityQueues.d7Performance.redDroppedOctets

       64 bit unsigned wrappable counter."
   ::= {pr1645v2Lan2FGUOutQueuesD7PerformanceEntry 218103808}

pr1645v2Lan2FGUOutQueuesD7PerformanceCirTxOcts OBJECT-TYPE
   SYNTAX      Counter64
   MAX-ACCESS  read-only
   STATUS      current
   DESCRIPTION
      "Path: ethernet2.performance.ifOutPriorityQueues.d7Performance.cirTxOctets

       64 bit unsigned wrappable counter."
   ::= {pr1645v2Lan2FGUOutQueuesD7PerformanceEntry 167772160}

pr1645v2Lan2FGUOutQueuesD7PerformanceEirTxOcts OBJECT-TYPE
   SYNTAX      Counter64
   MAX-ACCESS  read-only
   STATUS      current
   DESCRIPTION
      "Path: ethernet2.performance.ifOutPriorityQueues.d7Performance.eirTxOctets

       64 bit unsigned wrappable counter."
   ::= {pr1645v2Lan2FGUOutQueuesD7PerformanceEntry 184549376}

pr1645v2Lan2FGUOutQueuesD7PerformanceViolTxOcts OBJECT-TYPE
   SYNTAX      Counter64
   MAX-ACCESS  read-only
   STATUS      current
   DESCRIPTION
      "Path: ethernet2.performance.ifOutPriorityQueues.d7Performance.violateTxOctets

       64 bit unsigned wrappable counter."
   ::= {pr1645v2Lan2FGUOutQueuesD7PerformanceEntry 318767104}

pr1645v2Lan2FGUOutQueuesD7PerformanceBandwidth OBJECT-TYPE
   SYNTAX      Integer32
   MAX-ACCESS  read-only
   STATUS      current
   DESCRIPTION
      "Path: ethernet2.performance.ifOutPriorityQueues.d7Performance.bandwidth

       unit name = bps
       formula = 8 * ; 8 /"
   ::= {pr1645v2Lan2FGUOutQueuesD7PerformanceEntry 268435456}


pr1645v2Lan2FGUOutBandwidth OBJECT IDENTIFIER ::= {pr1645v2Lan2FGU 182}

pr1645v2Lan2FGUOutBandwidthSSC OBJECT IDENTIFIER ::= {pr1645v2Lan2FGUOutBandwidth 1}

pr1645v2Lan2FGUOutBandwidthEntry OBJECT IDENTIFIER ::= {pr1645v2Lan2FGUOutBandwidthSSC 1}

pr1645v2Lan2FGUOutBandwidth15sec OBJECT-TYPE
   SYNTAX      Integer32
   MAX-ACCESS  read-only
   STATUS      current
   DESCRIPTION
      "Path: ethernet2.performance.ifOutBandwidth.15sec

       unit name = bps
       formula = 8 * ; 8 /"
   ::= {pr1645v2Lan2FGUOutBandwidthEntry 83886080}

pr1645v2Lan2FGUOutBandwidth30sec OBJECT-TYPE
   SYNTAX      Integer32
   MAX-ACCESS  read-only
   STATUS      current
   DESCRIPTION
      "Path: ethernet2.performance.ifOutBandwidth.30sec

       unit name = bps
       formula = 8 * ; 8 /"
   ::= {pr1645v2Lan2FGUOutBandwidthEntry 167772160}

pr1645v2Lan2FGUOutBandwidth1min OBJECT-TYPE
   SYNTAX      Integer32
   MAX-ACCESS  read-only
   STATUS      current
   DESCRIPTION
      "Path: ethernet2.performance.ifOutBandwidth.1min

       unit name = bps
       formula = 8 * ; 8 /"
   ::= {pr1645v2Lan2FGUOutBandwidthEntry 335544320}

pr1645v2Lan2FGUOutBandwidth2min OBJECT-TYPE
   SYNTAX      Integer32
   MAX-ACCESS  read-only
   STATUS      current
   DESCRIPTION
      "Path: ethernet2.performance.ifOutBandwidth.2min

       unit name = bps
       formula = 8 * ; 8 /"
   ::= {pr1645v2Lan2FGUOutBandwidthEntry 671088640}

pr1645v2Lan2FGUOutBandwidth5min OBJECT-TYPE
   SYNTAX      Integer32
   MAX-ACCESS  read-only
   STATUS      current
   DESCRIPTION
      "Path: ethernet2.performance.ifOutBandwidth.5min

       unit name = bps
       formula = 8 * ; 8 /"
   ::= {pr1645v2Lan2FGUOutBandwidthEntry 1677721600}


pr1645v2Lan2FGUInP OBJECT IDENTIFIER ::= {pr1645v2Lan2FGU 307}

pr1645v2Lan2FGUInPSSCTable OBJECT-TYPE
   SYNTAX      SEQUENCE OF Pr1645v2Lan2FGUInPEntry
   MAX-ACCESS  not-accessible
   STATUS      current
   DESCRIPTION
      "h2IfInPerformance"
   ::= {pr1645v2Lan2FGUInP 1}

pr1645v2Lan2FGUInPEntry OBJECT-TYPE
   SYNTAX      Pr1645v2Lan2FGUInPEntry
   MAX-ACCESS  not-accessible
   STATUS      current
   DESCRIPTION
      ""
   INDEX      { pr1645v2Lan2FGUInPTableIx }
   ::= {pr1645v2Lan2FGUInPSSCTable 1}

Pr1645v2Lan2FGUInPEntry ::=
   SEQUENCE
      {
      pr1645v2Lan2FGUInPTableIx
         TableIndex,
      pr1645v2Lan2FGUInPSysUpTime
         TimeTicks,
      pr1645v2Lan2FGUInPIfUpTime
         TimeTicks,
      pr1645v2Lan2FGUInPIfStatChanges
         Counter32,
      pr1645v2Lan2FGUInPIfInOctets
         Counter64,
      pr1645v2Lan2FGUInPIfInUCPkts
         Counter64,
      pr1645v2Lan2FGUInPIfInNUCPkts
         Counter64,
      pr1645v2Lan2FGUInPIfInBCPkts
         Counter64,
      pr1645v2Lan2FGUInPIfInMCPkts
         Counter64,
      pr1645v2Lan2FGUInPIfInDiscards
         Counter64,
      pr1645v2Lan2FGUInPIfInErrors
         Counter64,
      pr1645v2Lan2FGUInPIfInUnkwn
         Counter64,
      pr1645v2Lan2FGUInPInDropEx
         Counter64,
      pr1645v2Lan2FGUInPInDropNoMac
         Counter64,
      pr1645v2Lan2FGUInPInDropNUCast
         Counter64,
      pr1645v2Lan2FGUInPInDropFilter
         Counter64,
      pr1645v2Lan2FGUInPIfInBandwidth
         Integer32,
      pr1645v2Lan2FGUInPIfOutOctets
         Counter64,
      pr1645v2Lan2FGUInPIfOutUCPkts
         Counter64,
      pr1645v2Lan2FGUInPIfOutNUCPkts
         Counter64,
      pr1645v2Lan2FGUInPIfOutBCPkts
         Counter64,
      pr1645v2Lan2FGUInPIfOutMCPkts
         Counter64,
      pr1645v2Lan2FGUInPIfOutDiscards
         Counter64,
      pr1645v2Lan2FGUInPIfOutErrors
         Counter64,
      pr1645v2Lan2FGUInPOutDropEx
         Counter64,
      pr1645v2Lan2FGUInPOutDropNoArp
         Counter64,
      pr1645v2Lan2FGUInPOutDropFilter
         Counter64,
      pr1645v2Lan2FGUInPIfOutBandwidth
         Integer32,
      pr1645v2Lan2FGUInPIfErrSec
         Counter32
      }

pr1645v2Lan2FGUInPTableIx OBJECT-TYPE
   SYNTAX      TableIndex
   MAX-ACCESS  not-accessible
   STATUS      current
   DESCRIPTION
      ""
   ::= {pr1645v2Lan2FGUInPEntry 11}

pr1645v2Lan2FGUInPSysUpTime OBJECT-TYPE
   SYNTAX      TimeTicks
   MAX-ACCESS  read-only
   STATUS      current
   DESCRIPTION
      "Path: ethernet2.performance.h2Performance.sysUpTime

       Time in centi-second."
   ::= {pr1645v2Lan2FGUInPEntry 16777216}

pr1645v2Lan2FGUInPIfUpTime OBJECT-TYPE
   SYNTAX      TimeTicks
   MAX-ACCESS  read-only
   STATUS      current
   DESCRIPTION
      "Path: ethernet2.performance.h2Performance.ifUpTime

       Time in centi-second."
   ::= {pr1645v2Lan2FGUInPEntry 33554432}

pr1645v2Lan2FGUInPIfStatChanges OBJECT-TYPE
   SYNTAX      Counter32
   MAX-ACCESS  read-only
   STATUS      current
   DESCRIPTION
      "Path: ethernet2.performance.h2Performance.ifStatusChanges

       32 bit unsigned wrappable counter."
   ::= {pr1645v2Lan2FGUInPEntry 50331648}

pr1645v2Lan2FGUInPIfInOctets OBJECT-TYPE
   SYNTAX      Counter64
   MAX-ACCESS  read-only
   STATUS      current
   DESCRIPTION
      "Path: ethernet2.performance.h2Performance.ifInOctets

       64 bit unsigned wrappable counter."
   ::= {pr1645v2Lan2FGUInPEntry 67108864}

pr1645v2Lan2FGUInPIfInUCPkts OBJECT-TYPE
   SYNTAX      Counter64
   MAX-ACCESS  read-only
   STATUS      current
   DESCRIPTION
      "Path: ethernet2.performance.h2Performance.ifInUcastPkts

       64 bit unsigned wrappable counter."
   ::= {pr1645v2Lan2FGUInPEntry 83886080}

pr1645v2Lan2FGUInPIfInNUCPkts OBJECT-TYPE
   SYNTAX      Counter64
   MAX-ACCESS  read-only
   STATUS      current
   DESCRIPTION
      "Path: ethernet2.performance.h2Performance.ifInNUcastPkts

       64 bit unsigned wrappable counter."
   ::= {pr1645v2Lan2FGUInPEntry 100663296}

pr1645v2Lan2FGUInPIfInBCPkts OBJECT-TYPE
   SYNTAX      Counter64
   MAX-ACCESS  read-only
   STATUS      current
   DESCRIPTION
      "Path: ethernet2.performance.h2Performance.ifInBcastPkts

       64 bit unsigned wrappable counter."
   ::= {pr1645v2Lan2FGUInPEntry 419430400}

pr1645v2Lan2FGUInPIfInMCPkts OBJECT-TYPE
   SYNTAX      Counter64
   MAX-ACCESS  read-only
   STATUS      current
   DESCRIPTION
      "Path: ethernet2.performance.h2Performance.ifInMcastPkts

       64 bit unsigned wrappable counter."
   ::= {pr1645v2Lan2FGUInPEntry 436207616}

pr1645v2Lan2FGUInPIfInDiscards OBJECT-TYPE
   SYNTAX      Counter64
   MAX-ACCESS  read-only
   STATUS      current
   DESCRIPTION
      "Path: ethernet2.performance.h2Performance.ifInDiscards

       64 bit unsigned wrappable counter."
   ::= {pr1645v2Lan2FGUInPEntry 117440512}

pr1645v2Lan2FGUInPIfInErrors OBJECT-TYPE
   SYNTAX      Counter64
   MAX-ACCESS  read-only
   STATUS      current
   DESCRIPTION
      "Path: ethernet2.performance.h2Performance.ifInErrors

       64 bit unsigned wrappable counter."
   ::= {pr1645v2Lan2FGUInPEntry 134217728}

pr1645v2Lan2FGUInPIfInUnkwn OBJECT-TYPE
   SYNTAX      Counter64
   MAX-ACCESS  read-only
   STATUS      current
   DESCRIPTION
      "Path: ethernet2.performance.h2Performance.ifInUnknownProtos

       64 bit unsigned wrappable counter."
   ::= {pr1645v2Lan2FGUInPEntry 150994944}

pr1645v2Lan2FGUInPInDropEx OBJECT-TYPE
   SYNTAX      Counter64
   MAX-ACCESS  read-only
   STATUS      current
   DESCRIPTION
      "Path: ethernet2.performance.h2Performance.ifInDropLevelExceeded

       64 bit unsigned wrappable counter."
   ::= {pr1645v2Lan2FGUInPEntry 335544320}

pr1645v2Lan2FGUInPInDropNoMac OBJECT-TYPE
   SYNTAX      Counter64
   MAX-ACCESS  read-only
   STATUS      current
   DESCRIPTION
      "Path: ethernet2.performance.h2Performance.fInDiscardsNoMacFit

       64 bit unsigned wrappable counter."
   ::= {pr1645v2Lan2FGUInPEntry 301989888}

pr1645v2Lan2FGUInPInDropNUCast OBJECT-TYPE
   SYNTAX      Counter64
   MAX-ACCESS  read-only
   STATUS      current
   DESCRIPTION
      "Path: ethernet2.performance.h2Performance.fInDiscardsNUCast

       64 bit unsigned wrappable counter."
   ::= {pr1645v2Lan2FGUInPEntry 318767104}

pr1645v2Lan2FGUInPInDropFilter OBJECT-TYPE
   SYNTAX      Counter64
   MAX-ACCESS  read-only
   STATUS      current
   DESCRIPTION
      "Path: ethernet2.performance.h2Performance.fInDiscardsFilter

       64 bit unsigned wrappable counter."
   ::= {pr1645v2Lan2FGUInPEntry 385875968}

pr1645v2Lan2FGUInPIfInBandwidth OBJECT-TYPE
   SYNTAX      Integer32
   MAX-ACCESS  read-only
   STATUS      current
   DESCRIPTION
      "Path: ethernet2.performance.h2Performance.ifInBandwidth

       unit name = bps
       formula = 8 * ; 8 /"
   ::= {pr1645v2Lan2FGUInPEntry 268435456}

pr1645v2Lan2FGUInPIfOutOctets OBJECT-TYPE
   SYNTAX      Counter64
   MAX-ACCESS  read-only
   STATUS      current
   DESCRIPTION
      "Path: ethernet2.performance.h2Performance.ifOutOctets

       64 bit unsigned wrappable counter."
   ::= {pr1645v2Lan2FGUInPEntry 167772160}

pr1645v2Lan2FGUInPIfOutUCPkts OBJECT-TYPE
   SYNTAX      Counter64
   MAX-ACCESS  read-only
   STATUS      current
   DESCRIPTION
      "Path: ethernet2.performance.h2Performance.ifOutUcastPkts

       64 bit unsigned wrappable counter."
   ::= {pr1645v2Lan2FGUInPEntry 184549376}

pr1645v2Lan2FGUInPIfOutNUCPkts OBJECT-TYPE
   SYNTAX      Counter64
   MAX-ACCESS  read-only
   STATUS      current
   DESCRIPTION
      "Path: ethernet2.performance.h2Performance.ifOutNUcastPkts

       64 bit unsigned wrappable counter."
   ::= {pr1645v2Lan2FGUInPEntry 201326592}

pr1645v2Lan2FGUInPIfOutBCPkts OBJECT-TYPE
   SYNTAX      Counter64
   MAX-ACCESS  read-only
   STATUS      current
   DESCRIPTION
      "Path: ethernet2.performance.h2Performance.ifOutBcastPkts

       64 bit unsigned wrappable counter."
   ::= {pr1645v2Lan2FGUInPEntry 452984832}

pr1645v2Lan2FGUInPIfOutMCPkts OBJECT-TYPE
   SYNTAX      Counter64
   MAX-ACCESS  read-only
   STATUS      current
   DESCRIPTION
      "Path: ethernet2.performance.h2Performance.ifOutMcastPkts

       64 bit unsigned wrappable counter."
   ::= {pr1645v2Lan2FGUInPEntry 469762048}

pr1645v2Lan2FGUInPIfOutDiscards OBJECT-TYPE
   SYNTAX      Counter64
   MAX-ACCESS  read-only
   STATUS      current
   DESCRIPTION
      "Path: ethernet2.performance.h2Performance.ifOutDiscards

       64 bit unsigned wrappable counter."
   ::= {pr1645v2Lan2FGUInPEntry 218103808}

pr1645v2Lan2FGUInPIfOutErrors OBJECT-TYPE
   SYNTAX      Counter64
   MAX-ACCESS  read-only
   STATUS      current
   DESCRIPTION
      "Path: ethernet2.performance.h2Performance.ifOutErrors

       64 bit unsigned wrappable counter."
   ::= {pr1645v2Lan2FGUInPEntry 234881024}

pr1645v2Lan2FGUInPOutDropEx OBJECT-TYPE
   SYNTAX      Counter64
   MAX-ACCESS  read-only
   STATUS      current
   DESCRIPTION
      "Path: ethernet2.performance.h2Performance.ifOutDropLevelExceeded

       64 bit unsigned wrappable counter."
   ::= {pr1645v2Lan2FGUInPEntry 352321536}

pr1645v2Lan2FGUInPOutDropNoArp OBJECT-TYPE
   SYNTAX      Counter64
   MAX-ACCESS  read-only
   STATUS      current
   DESCRIPTION
      "Path: ethernet2.performance.h2Performance.ifOutDiscardsNoArp

       64 bit unsigned wrappable counter."
   ::= {pr1645v2Lan2FGUInPEntry 369098752}

pr1645v2Lan2FGUInPOutDropFilter OBJECT-TYPE
   SYNTAX      Counter64
   MAX-ACCESS  read-only
   STATUS      current
   DESCRIPTION
      "Path: ethernet2.performance.h2Performance.ifOutDiscardsFilter

       64 bit unsigned wrappable counter."
   ::= {pr1645v2Lan2FGUInPEntry 402653184}

pr1645v2Lan2FGUInPIfOutBandwidth OBJECT-TYPE
   SYNTAX      Integer32
   MAX-ACCESS  read-only
   STATUS      current
   DESCRIPTION
      "Path: ethernet2.performance.h2Performance.ifOutBandwidth

       unit name = bps
       formula = 8 * ; 8 /"
   ::= {pr1645v2Lan2FGUInPEntry 285212672}

pr1645v2Lan2FGUInPIfErrSec OBJECT-TYPE
   SYNTAX      Counter32
   MAX-ACCESS  read-only
   STATUS      current
   DESCRIPTION
      "Path: ethernet2.performance.h2Performance.ifErrSec

       32 bit unsigned wrappable counter."
   ::= {pr1645v2Lan2FGUInPEntry 251658240}


pr1645v2Lan2FGUH24InP OBJECT IDENTIFIER ::= {pr1645v2Lan2FGU 308}

pr1645v2Lan2FGUH24InPSSCTable OBJECT-TYPE
   SYNTAX      SEQUENCE OF Pr1645v2Lan2FGUH24InPEntry
   MAX-ACCESS  not-accessible
   STATUS      current
   DESCRIPTION
      "h24IfInPerformance"
   ::= {pr1645v2Lan2FGUH24InP 1}

pr1645v2Lan2FGUH24InPEntry OBJECT-TYPE
   SYNTAX      Pr1645v2Lan2FGUH24InPEntry
   MAX-ACCESS  not-accessible
   STATUS      current
   DESCRIPTION
      ""
   INDEX      { pr1645v2Lan2FGUH24InPTableIx }
   ::= {pr1645v2Lan2FGUH24InPSSCTable 1}

Pr1645v2Lan2FGUH24InPEntry ::=
   SEQUENCE
      {
      pr1645v2Lan2FGUH24InPTableIx
         TableIndex,
      pr1645v2Lan2FGUH24InPSysUpTime
         TimeTicks,
      pr1645v2Lan2FGUH24InPIfUpTime
         TimeTicks,
      pr1645v2Lan2FGUH24InPIfStatChanges
         Counter32,
      pr1645v2Lan2FGUH24InPIfInOctets
         Counter64,
      pr1645v2Lan2FGUH24InPIfInUCPkts
         Counter64,
      pr1645v2Lan2FGUH24InPIfInNUCPkts
         Counter64,
      pr1645v2Lan2FGUH24InPIfInBCPkts
         Counter64,
      pr1645v2Lan2FGUH24InPIfInMCPkts
         Counter64,
      pr1645v2Lan2FGUH24InPIfInDiscards
         Counter64,
      pr1645v2Lan2FGUH24InPIfInErrors
         Counter64,
      pr1645v2Lan2FGUH24InPIfInUnkwn
         Counter64,
      pr1645v2Lan2FGUH24InPInDropEx
         Counter64,
      pr1645v2Lan2FGUH24InPInDropNoMac
         Counter64,
      pr1645v2Lan2FGUH24InPInDropNUCast
         Counter64,
      pr1645v2Lan2FGUH24InPInDropFilter
         Counter64,
      pr1645v2Lan2FGUH24InPIfInBandwidth
         Integer32,
      pr1645v2Lan2FGUH24InPIfOutOctets
         Counter64,
      pr1645v2Lan2FGUH24InPIfOutUCPkts
         Counter64,
      pr1645v2Lan2FGUH24InPIfOutNUCPkts
         Counter64,
      pr1645v2Lan2FGUH24InPIfOutBCPkts
         Counter64,
      pr1645v2Lan2FGUH24InPIfOutMCPkts
         Counter64,
      pr1645v2Lan2FGUH24InPIfOutDiscards
         Counter64,
      pr1645v2Lan2FGUH24InPIfOutErrors
         Counter64,
      pr1645v2Lan2FGUH24InPOutDropEx
         Counter64,
      pr1645v2Lan2FGUH24InPOutDropNoArp
         Counter64,
      pr1645v2Lan2FGUH24InPOutDropFilter
         Counter64,
      pr1645v2Lan2FGUH24InPIfOutBandwidth
         Integer32,
      pr1645v2Lan2FGUH24InPIfErrSec
         Counter32
      }

pr1645v2Lan2FGUH24InPTableIx OBJECT-TYPE
   SYNTAX      TableIndex
   MAX-ACCESS  not-accessible
   STATUS      current
   DESCRIPTION
      ""
   ::= {pr1645v2Lan2FGUH24InPEntry 11}

pr1645v2Lan2FGUH24InPSysUpTime OBJECT-TYPE
   SYNTAX      TimeTicks
   MAX-ACCESS  read-only
   STATUS      current
   DESCRIPTION
      "Path: ethernet2.performance.h24Performance.sysUpTime

       Time in centi-second."
   ::= {pr1645v2Lan2FGUH24InPEntry 16777216}

pr1645v2Lan2FGUH24InPIfUpTime OBJECT-TYPE
   SYNTAX      TimeTicks
   MAX-ACCESS  read-only
   STATUS      current
   DESCRIPTION
      "Path: ethernet2.performance.h24Performance.ifUpTime

       Time in centi-second."
   ::= {pr1645v2Lan2FGUH24InPEntry 33554432}

pr1645v2Lan2FGUH24InPIfStatChanges OBJECT-TYPE
   SYNTAX      Counter32
   MAX-ACCESS  read-only
   STATUS      current
   DESCRIPTION
      "Path: ethernet2.performance.h24Performance.ifStatusChanges

       32 bit unsigned wrappable counter."
   ::= {pr1645v2Lan2FGUH24InPEntry 50331648}

pr1645v2Lan2FGUH24InPIfInOctets OBJECT-TYPE
   SYNTAX      Counter64
   MAX-ACCESS  read-only
   STATUS      current
   DESCRIPTION
      "Path: ethernet2.performance.h24Performance.ifInOctets

       64 bit unsigned wrappable counter."
   ::= {pr1645v2Lan2FGUH24InPEntry 67108864}

pr1645v2Lan2FGUH24InPIfInUCPkts OBJECT-TYPE
   SYNTAX      Counter64
   MAX-ACCESS  read-only
   STATUS      current
   DESCRIPTION
      "Path: ethernet2.performance.h24Performance.ifInUcastPkts

       64 bit unsigned wrappable counter."
   ::= {pr1645v2Lan2FGUH24InPEntry 83886080}

pr1645v2Lan2FGUH24InPIfInNUCPkts OBJECT-TYPE
   SYNTAX      Counter64
   MAX-ACCESS  read-only
   STATUS      current
   DESCRIPTION
      "Path: ethernet2.performance.h24Performance.ifInNUcastPkts

       64 bit unsigned wrappable counter."
   ::= {pr1645v2Lan2FGUH24InPEntry 100663296}

pr1645v2Lan2FGUH24InPIfInBCPkts OBJECT-TYPE
   SYNTAX      Counter64
   MAX-ACCESS  read-only
   STATUS      current
   DESCRIPTION
      "Path: ethernet2.performance.h24Performance.ifInBcastPkts

       64 bit unsigned wrappable counter."
   ::= {pr1645v2Lan2FGUH24InPEntry 419430400}

pr1645v2Lan2FGUH24InPIfInMCPkts OBJECT-TYPE
   SYNTAX      Counter64
   MAX-ACCESS  read-only
   STATUS      current
   DESCRIPTION
      "Path: ethernet2.performance.h24Performance.ifInMcastPkts

       64 bit unsigned wrappable counter."
   ::= {pr1645v2Lan2FGUH24InPEntry 436207616}

pr1645v2Lan2FGUH24InPIfInDiscards OBJECT-TYPE
   SYNTAX      Counter64
   MAX-ACCESS  read-only
   STATUS      current
   DESCRIPTION
      "Path: ethernet2.performance.h24Performance.ifInDiscards

       64 bit unsigned wrappable counter."
   ::= {pr1645v2Lan2FGUH24InPEntry 117440512}

pr1645v2Lan2FGUH24InPIfInErrors OBJECT-TYPE
   SYNTAX      Counter64
   MAX-ACCESS  read-only
   STATUS      current
   DESCRIPTION
      "Path: ethernet2.performance.h24Performance.ifInErrors

       64 bit unsigned wrappable counter."
   ::= {pr1645v2Lan2FGUH24InPEntry 134217728}

pr1645v2Lan2FGUH24InPIfInUnkwn OBJECT-TYPE
   SYNTAX      Counter64
   MAX-ACCESS  read-only
   STATUS      current
   DESCRIPTION
      "Path: ethernet2.performance.h24Performance.ifInUnknownProtos

       64 bit unsigned wrappable counter."
   ::= {pr1645v2Lan2FGUH24InPEntry 150994944}

pr1645v2Lan2FGUH24InPInDropEx OBJECT-TYPE
   SYNTAX      Counter64
   MAX-ACCESS  read-only
   STATUS      current
   DESCRIPTION
      "Path: ethernet2.performance.h24Performance.ifInDropLevelExceeded

       64 bit unsigned wrappable counter."
   ::= {pr1645v2Lan2FGUH24InPEntry 335544320}

pr1645v2Lan2FGUH24InPInDropNoMac OBJECT-TYPE
   SYNTAX      Counter64
   MAX-ACCESS  read-only
   STATUS      current
   DESCRIPTION
      "Path: ethernet2.performance.h24Performance.fInDiscardsNoMacFit

       64 bit unsigned wrappable counter."
   ::= {pr1645v2Lan2FGUH24InPEntry 301989888}

pr1645v2Lan2FGUH24InPInDropNUCast OBJECT-TYPE
   SYNTAX      Counter64
   MAX-ACCESS  read-only
   STATUS      current
   DESCRIPTION
      "Path: ethernet2.performance.h24Performance.fInDiscardsNUCast

       64 bit unsigned wrappable counter."
   ::= {pr1645v2Lan2FGUH24InPEntry 318767104}

pr1645v2Lan2FGUH24InPInDropFilter OBJECT-TYPE
   SYNTAX      Counter64
   MAX-ACCESS  read-only
   STATUS      current
   DESCRIPTION
      "Path: ethernet2.performance.h24Performance.fInDiscardsFilter

       64 bit unsigned wrappable counter."
   ::= {pr1645v2Lan2FGUH24InPEntry 385875968}

pr1645v2Lan2FGUH24InPIfInBandwidth OBJECT-TYPE
   SYNTAX      Integer32
   MAX-ACCESS  read-only
   STATUS      current
   DESCRIPTION
      "Path: ethernet2.performance.h24Performance.ifInBandwidth

       unit name = bps
       formula = 8 * ; 8 /"
   ::= {pr1645v2Lan2FGUH24InPEntry 268435456}

pr1645v2Lan2FGUH24InPIfOutOctets OBJECT-TYPE
   SYNTAX      Counter64
   MAX-ACCESS  read-only
   STATUS      current
   DESCRIPTION
      "Path: ethernet2.performance.h24Performance.ifOutOctets

       64 bit unsigned wrappable counter."
   ::= {pr1645v2Lan2FGUH24InPEntry 167772160}

pr1645v2Lan2FGUH24InPIfOutUCPkts OBJECT-TYPE
   SYNTAX      Counter64
   MAX-ACCESS  read-only
   STATUS      current
   DESCRIPTION
      "Path: ethernet2.performance.h24Performance.ifOutUcastPkts

       64 bit unsigned wrappable counter."
   ::= {pr1645v2Lan2FGUH24InPEntry 184549376}

pr1645v2Lan2FGUH24InPIfOutNUCPkts OBJECT-TYPE
   SYNTAX      Counter64
   MAX-ACCESS  read-only
   STATUS      current
   DESCRIPTION
      "Path: ethernet2.performance.h24Performance.ifOutNUcastPkts

       64 bit unsigned wrappable counter."
   ::= {pr1645v2Lan2FGUH24InPEntry 201326592}

pr1645v2Lan2FGUH24InPIfOutBCPkts OBJECT-TYPE
   SYNTAX      Counter64
   MAX-ACCESS  read-only
   STATUS      current
   DESCRIPTION
      "Path: ethernet2.performance.h24Performance.ifOutBcastPkts

       64 bit unsigned wrappable counter."
   ::= {pr1645v2Lan2FGUH24InPEntry 452984832}

pr1645v2Lan2FGUH24InPIfOutMCPkts OBJECT-TYPE
   SYNTAX      Counter64
   MAX-ACCESS  read-only
   STATUS      current
   DESCRIPTION
      "Path: ethernet2.performance.h24Performance.ifOutMcastPkts

       64 bit unsigned wrappable counter."
   ::= {pr1645v2Lan2FGUH24InPEntry 469762048}

pr1645v2Lan2FGUH24InPIfOutDiscards OBJECT-TYPE
   SYNTAX      Counter64
   MAX-ACCESS  read-only
   STATUS      current
   DESCRIPTION
      "Path: ethernet2.performance.h24Performance.ifOutDiscards

       64 bit unsigned wrappable counter."
   ::= {pr1645v2Lan2FGUH24InPEntry 218103808}

pr1645v2Lan2FGUH24InPIfOutErrors OBJECT-TYPE
   SYNTAX      Counter64
   MAX-ACCESS  read-only
   STATUS      current
   DESCRIPTION
      "Path: ethernet2.performance.h24Performance.ifOutErrors

       64 bit unsigned wrappable counter."
   ::= {pr1645v2Lan2FGUH24InPEntry 234881024}

pr1645v2Lan2FGUH24InPOutDropEx OBJECT-TYPE
   SYNTAX      Counter64
   MAX-ACCESS  read-only
   STATUS      current
   DESCRIPTION
      "Path: ethernet2.performance.h24Performance.ifOutDropLevelExceeded

       64 bit unsigned wrappable counter."
   ::= {pr1645v2Lan2FGUH24InPEntry 352321536}

pr1645v2Lan2FGUH24InPOutDropNoArp OBJECT-TYPE
   SYNTAX      Counter64
   MAX-ACCESS  read-only
   STATUS      current
   DESCRIPTION
      "Path: ethernet2.performance.h24Performance.ifOutDiscardsNoArp

       64 bit unsigned wrappable counter."
   ::= {pr1645v2Lan2FGUH24InPEntry 369098752}

pr1645v2Lan2FGUH24InPOutDropFilter OBJECT-TYPE
   SYNTAX      Counter64
   MAX-ACCESS  read-only
   STATUS      current
   DESCRIPTION
      "Path: ethernet2.performance.h24Performance.ifOutDiscardsFilter

       64 bit unsigned wrappable counter."
   ::= {pr1645v2Lan2FGUH24InPEntry 402653184}

pr1645v2Lan2FGUH24InPIfOutBandwidth OBJECT-TYPE
   SYNTAX      Integer32
   MAX-ACCESS  read-only
   STATUS      current
   DESCRIPTION
      "Path: ethernet2.performance.h24Performance.ifOutBandwidth

       unit name = bps
       formula = 8 * ; 8 /"
   ::= {pr1645v2Lan2FGUH24InPEntry 285212672}

pr1645v2Lan2FGUH24InPIfErrSec OBJECT-TYPE
   SYNTAX      Counter32
   MAX-ACCESS  read-only
   STATUS      current
   DESCRIPTION
      "Path: ethernet2.performance.h24Performance.ifErrSec

       32 bit unsigned wrappable counter."
   ::= {pr1645v2Lan2FGUH24InPEntry 251658240}


pr1645v2Lan2FGUD7InP OBJECT IDENTIFIER ::= {pr1645v2Lan2FGU 309}

pr1645v2Lan2FGUD7InPSSCTable OBJECT-TYPE
   SYNTAX      SEQUENCE OF Pr1645v2Lan2FGUD7InPEntry
   MAX-ACCESS  not-accessible
   STATUS      current
   DESCRIPTION
      "d7IfInPerformance"
   ::= {pr1645v2Lan2FGUD7InP 1}

pr1645v2Lan2FGUD7InPEntry OBJECT-TYPE
   SYNTAX      Pr1645v2Lan2FGUD7InPEntry
   MAX-ACCESS  not-accessible
   STATUS      current
   DESCRIPTION
      ""
   INDEX      { pr1645v2Lan2FGUD7InPTableIx }
   ::= {pr1645v2Lan2FGUD7InPSSCTable 1}

Pr1645v2Lan2FGUD7InPEntry ::=
   SEQUENCE
      {
      pr1645v2Lan2FGUD7InPTableIx
         TableIndex,
      pr1645v2Lan2FGUD7InPSysUpTime
         TimeTicks,
      pr1645v2Lan2FGUD7InPIfUpTime
         TimeTicks,
      pr1645v2Lan2FGUD7InPIfStatChanges
         Counter32,
      pr1645v2Lan2FGUD7InPIfInOctets
         Counter64,
      pr1645v2Lan2FGUD7InPIfInUCPkts
         Counter64,
      pr1645v2Lan2FGUD7InPIfInNUCPkts
         Counter64,
      pr1645v2Lan2FGUD7InPIfInBCPkts
         Counter64,
      pr1645v2Lan2FGUD7InPIfInMCPkts
         Counter64,
      pr1645v2Lan2FGUD7InPIfInDiscards
         Counter64,
      pr1645v2Lan2FGUD7InPIfInErrors
         Counter64,
      pr1645v2Lan2FGUD7InPIfInUnkwn
         Counter64,
      pr1645v2Lan2FGUD7InPInDropEx
         Counter64,
      pr1645v2Lan2FGUD7InPInDropNoMac
         Counter64,
      pr1645v2Lan2FGUD7InPInDropNUCast
         Counter64,
      pr1645v2Lan2FGUD7InPInDropFilter
         Counter64,
      pr1645v2Lan2FGUD7InPIfInBandwidth
         Integer32,
      pr1645v2Lan2FGUD7InPIfOutOctets
         Counter64,
      pr1645v2Lan2FGUD7InPIfOutUCPkts
         Counter64,
      pr1645v2Lan2FGUD7InPIfOutNUCPkts
         Counter64,
      pr1645v2Lan2FGUD7InPIfOutBCPkts
         Counter64,
      pr1645v2Lan2FGUD7InPIfOutMCPkts
         Counter64,
      pr1645v2Lan2FGUD7InPIfOutDiscards
         Counter64,
      pr1645v2Lan2FGUD7InPIfOutErrors
         Counter64,
      pr1645v2Lan2FGUD7InPOutDropEx
         Counter64,
      pr1645v2Lan2FGUD7InPOutDropNoArp
         Counter64,
      pr1645v2Lan2FGUD7InPOutDropFilter
         Counter64,
      pr1645v2Lan2FGUD7InPIfOutBandwidth
         Integer32,
      pr1645v2Lan2FGUD7InPIfErrSec
         Counter32
      }

pr1645v2Lan2FGUD7InPTableIx OBJECT-TYPE
   SYNTAX      TableIndex
   MAX-ACCESS  not-accessible
   STATUS      current
   DESCRIPTION
      ""
   ::= {pr1645v2Lan2FGUD7InPEntry 11}

pr1645v2Lan2FGUD7InPSysUpTime OBJECT-TYPE
   SYNTAX      TimeTicks
   MAX-ACCESS  read-only
   STATUS      current
   DESCRIPTION
      "Path: ethernet2.performance.d7Performance.sysUpTime

       Time in centi-second."
   ::= {pr1645v2Lan2FGUD7InPEntry 16777216}

pr1645v2Lan2FGUD7InPIfUpTime OBJECT-TYPE
   SYNTAX      TimeTicks
   MAX-ACCESS  read-only
   STATUS      current
   DESCRIPTION
      "Path: ethernet2.performance.d7Performance.ifUpTime

       Time in centi-second."
   ::= {pr1645v2Lan2FGUD7InPEntry 33554432}

pr1645v2Lan2FGUD7InPIfStatChanges OBJECT-TYPE
   SYNTAX      Counter32
   MAX-ACCESS  read-only
   STATUS      current
   DESCRIPTION
      "Path: ethernet2.performance.d7Performance.ifStatusChanges

       32 bit unsigned wrappable counter."
   ::= {pr1645v2Lan2FGUD7InPEntry 50331648}

pr1645v2Lan2FGUD7InPIfInOctets OBJECT-TYPE
   SYNTAX      Counter64
   MAX-ACCESS  read-only
   STATUS      current
   DESCRIPTION
      "Path: ethernet2.performance.d7Performance.ifInOctets

       64 bit unsigned wrappable counter."
   ::= {pr1645v2Lan2FGUD7InPEntry 67108864}

pr1645v2Lan2FGUD7InPIfInUCPkts OBJECT-TYPE
   SYNTAX      Counter64
   MAX-ACCESS  read-only
   STATUS      current
   DESCRIPTION
      "Path: ethernet2.performance.d7Performance.ifInUcastPkts

       64 bit unsigned wrappable counter."
   ::= {pr1645v2Lan2FGUD7InPEntry 83886080}

pr1645v2Lan2FGUD7InPIfInNUCPkts OBJECT-TYPE
   SYNTAX      Counter64
   MAX-ACCESS  read-only
   STATUS      current
   DESCRIPTION
      "Path: ethernet2.performance.d7Performance.ifInNUcastPkts

       64 bit unsigned wrappable counter."
   ::= {pr1645v2Lan2FGUD7InPEntry 100663296}

pr1645v2Lan2FGUD7InPIfInBCPkts OBJECT-TYPE
   SYNTAX      Counter64
   MAX-ACCESS  read-only
   STATUS      current
   DESCRIPTION
      "Path: ethernet2.performance.d7Performance.ifInBcastPkts

       64 bit unsigned wrappable counter."
   ::= {pr1645v2Lan2FGUD7InPEntry 419430400}

pr1645v2Lan2FGUD7InPIfInMCPkts OBJECT-TYPE
   SYNTAX      Counter64
   MAX-ACCESS  read-only
   STATUS      current
   DESCRIPTION
      "Path: ethernet2.performance.d7Performance.ifInMcastPkts

       64 bit unsigned wrappable counter."
   ::= {pr1645v2Lan2FGUD7InPEntry 436207616}

pr1645v2Lan2FGUD7InPIfInDiscards OBJECT-TYPE
   SYNTAX      Counter64
   MAX-ACCESS  read-only
   STATUS      current
   DESCRIPTION
      "Path: ethernet2.performance.d7Performance.ifInDiscards

       64 bit unsigned wrappable counter."
   ::= {pr1645v2Lan2FGUD7InPEntry 117440512}

pr1645v2Lan2FGUD7InPIfInErrors OBJECT-TYPE
   SYNTAX      Counter64
   MAX-ACCESS  read-only
   STATUS      current
   DESCRIPTION
      "Path: ethernet2.performance.d7Performance.ifInErrors

       64 bit unsigned wrappable counter."
   ::= {pr1645v2Lan2FGUD7InPEntry 134217728}

pr1645v2Lan2FGUD7InPIfInUnkwn OBJECT-TYPE
   SYNTAX      Counter64
   MAX-ACCESS  read-only
   STATUS      current
   DESCRIPTION
      "Path: ethernet2.performance.d7Performance.ifInUnknownProtos

       64 bit unsigned wrappable counter."
   ::= {pr1645v2Lan2FGUD7InPEntry 150994944}

pr1645v2Lan2FGUD7InPInDropEx OBJECT-TYPE
   SYNTAX      Counter64
   MAX-ACCESS  read-only
   STATUS      current
   DESCRIPTION
      "Path: ethernet2.performance.d7Performance.ifInDropLevelExceeded

       64 bit unsigned wrappable counter."
   ::= {pr1645v2Lan2FGUD7InPEntry 335544320}

pr1645v2Lan2FGUD7InPInDropNoMac OBJECT-TYPE
   SYNTAX      Counter64
   MAX-ACCESS  read-only
   STATUS      current
   DESCRIPTION
      "Path: ethernet2.performance.d7Performance.fInDiscardsNoMacFit

       64 bit unsigned wrappable counter."
   ::= {pr1645v2Lan2FGUD7InPEntry 301989888}

pr1645v2Lan2FGUD7InPInDropNUCast OBJECT-TYPE
   SYNTAX      Counter64
   MAX-ACCESS  read-only
   STATUS      current
   DESCRIPTION
      "Path: ethernet2.performance.d7Performance.fInDiscardsNUCast

       64 bit unsigned wrappable counter."
   ::= {pr1645v2Lan2FGUD7InPEntry 318767104}

pr1645v2Lan2FGUD7InPInDropFilter OBJECT-TYPE
   SYNTAX      Counter64
   MAX-ACCESS  read-only
   STATUS      current
   DESCRIPTION
      "Path: ethernet2.performance.d7Performance.fInDiscardsFilter

       64 bit unsigned wrappable counter."
   ::= {pr1645v2Lan2FGUD7InPEntry 385875968}

pr1645v2Lan2FGUD7InPIfInBandwidth OBJECT-TYPE
   SYNTAX      Integer32
   MAX-ACCESS  read-only
   STATUS      current
   DESCRIPTION
      "Path: ethernet2.performance.d7Performance.ifInBandwidth

       unit name = bps
       formula = 8 * ; 8 /"
   ::= {pr1645v2Lan2FGUD7InPEntry 268435456}

pr1645v2Lan2FGUD7InPIfOutOctets OBJECT-TYPE
   SYNTAX      Counter64
   MAX-ACCESS  read-only
   STATUS      current
   DESCRIPTION
      "Path: ethernet2.performance.d7Performance.ifOutOctets

       64 bit unsigned wrappable counter."
   ::= {pr1645v2Lan2FGUD7InPEntry 167772160}

pr1645v2Lan2FGUD7InPIfOutUCPkts OBJECT-TYPE
   SYNTAX      Counter64
   MAX-ACCESS  read-only
   STATUS      current
   DESCRIPTION
      "Path: ethernet2.performance.d7Performance.ifOutUcastPkts

       64 bit unsigned wrappable counter."
   ::= {pr1645v2Lan2FGUD7InPEntry 184549376}

pr1645v2Lan2FGUD7InPIfOutNUCPkts OBJECT-TYPE
   SYNTAX      Counter64
   MAX-ACCESS  read-only
   STATUS      current
   DESCRIPTION
      "Path: ethernet2.performance.d7Performance.ifOutNUcastPkts

       64 bit unsigned wrappable counter."
   ::= {pr1645v2Lan2FGUD7InPEntry 201326592}

pr1645v2Lan2FGUD7InPIfOutBCPkts OBJECT-TYPE
   SYNTAX      Counter64
   MAX-ACCESS  read-only
   STATUS      current
   DESCRIPTION
      "Path: ethernet2.performance.d7Performance.ifOutBcastPkts

       64 bit unsigned wrappable counter."
   ::= {pr1645v2Lan2FGUD7InPEntry 452984832}

pr1645v2Lan2FGUD7InPIfOutMCPkts OBJECT-TYPE
   SYNTAX      Counter64
   MAX-ACCESS  read-only
   STATUS      current
   DESCRIPTION
      "Path: ethernet2.performance.d7Performance.ifOutMcastPkts

       64 bit unsigned wrappable counter."
   ::= {pr1645v2Lan2FGUD7InPEntry 469762048}

pr1645v2Lan2FGUD7InPIfOutDiscards OBJECT-TYPE
   SYNTAX      Counter64
   MAX-ACCESS  read-only
   STATUS      current
   DESCRIPTION
      "Path: ethernet2.performance.d7Performance.ifOutDiscards

       64 bit unsigned wrappable counter."
   ::= {pr1645v2Lan2FGUD7InPEntry 218103808}

pr1645v2Lan2FGUD7InPIfOutErrors OBJECT-TYPE
   SYNTAX      Counter64
   MAX-ACCESS  read-only
   STATUS      current
   DESCRIPTION
      "Path: ethernet2.performance.d7Performance.ifOutErrors

       64 bit unsigned wrappable counter."
   ::= {pr1645v2Lan2FGUD7InPEntry 234881024}

pr1645v2Lan2FGUD7InPOutDropEx OBJECT-TYPE
   SYNTAX      Counter64
   MAX-ACCESS  read-only
   STATUS      current
   DESCRIPTION
      "Path: ethernet2.performance.d7Performance.ifOutDropLevelExceeded

       64 bit unsigned wrappable counter."
   ::= {pr1645v2Lan2FGUD7InPEntry 352321536}

pr1645v2Lan2FGUD7InPOutDropNoArp OBJECT-TYPE
   SYNTAX      Counter64
   MAX-ACCESS  read-only
   STATUS      current
   DESCRIPTION
      "Path: ethernet2.performance.d7Performance.ifOutDiscardsNoArp

       64 bit unsigned wrappable counter."
   ::= {pr1645v2Lan2FGUD7InPEntry 369098752}

pr1645v2Lan2FGUD7InPOutDropFilter OBJECT-TYPE
   SYNTAX      Counter64
   MAX-ACCESS  read-only
   STATUS      current
   DESCRIPTION
      "Path: ethernet2.performance.d7Performance.ifOutDiscardsFilter

       64 bit unsigned wrappable counter."
   ::= {pr1645v2Lan2FGUD7InPEntry 402653184}

pr1645v2Lan2FGUD7InPIfOutBandwidth OBJECT-TYPE
   SYNTAX      Integer32
   MAX-ACCESS  read-only
   STATUS      current
   DESCRIPTION
      "Path: ethernet2.performance.d7Performance.ifOutBandwidth

       unit name = bps
       formula = 8 * ; 8 /"
   ::= {pr1645v2Lan2FGUD7InPEntry 285212672}

pr1645v2Lan2FGUD7InPIfErrSec OBJECT-TYPE
   SYNTAX      Counter32
   MAX-ACCESS  read-only
   STATUS      current
   DESCRIPTION
      "Path: ethernet2.performance.d7Performance.ifErrSec

       32 bit unsigned wrappable counter."
   ::= {pr1645v2Lan2FGUD7InPEntry 251658240}


pr1645v2Lan2FGUOam OBJECT IDENTIFIER ::= {pr1645v2Lan2FGU 910}

pr1645v2Lan2FGUOamSSC OBJECT IDENTIFIER ::= {pr1645v2Lan2FGUOam 1}

pr1645v2Lan2FGUOamEntry OBJECT IDENTIFIER ::= {pr1645v2Lan2FGUOamSSC 1}

pr1645v2Lan2FGUOamInformationTx OBJECT-TYPE
   SYNTAX      Counter32
   MAX-ACCESS  read-only
   STATUS      current
   DESCRIPTION
      "Path: ethernet2.performance.oam.informationTx

       32 bit unsigned wrappable counter."
   ::= {pr1645v2Lan2FGUOamEntry 16777216}

pr1645v2Lan2FGUOamInformationRx OBJECT-TYPE
   SYNTAX      Counter32
   MAX-ACCESS  read-only
   STATUS      current
   DESCRIPTION
      "Path: ethernet2.performance.oam.informationRx

       32 bit unsigned wrappable counter."
   ::= {pr1645v2Lan2FGUOamEntry 33554432}

pr1645v2Lan2FGUOamUniqueEventNotifTx OBJECT-TYPE
   SYNTAX      Counter32
   MAX-ACCESS  read-only
   STATUS      current
   DESCRIPTION
      "Path: ethernet2.performance.oam.uniqueEventNotifTx

       32 bit unsigned wrappable counter."
   ::= {pr1645v2Lan2FGUOamEntry 50331648}

pr1645v2Lan2FGUOamUniqueEventNotifRx OBJECT-TYPE
   SYNTAX      Counter32
   MAX-ACCESS  read-only
   STATUS      current
   DESCRIPTION
      "Path: ethernet2.performance.oam.uniqueEventNotifRx

       32 bit unsigned wrappable counter."
   ::= {pr1645v2Lan2FGUOamEntry 67108864}

pr1645v2Lan2FGUOamLoopbackCtrlTx OBJECT-TYPE
   SYNTAX      Counter32
   MAX-ACCESS  read-only
   STATUS      current
   DESCRIPTION
      "Path: ethernet2.performance.oam.loopbackCtrlTx

       32 bit unsigned wrappable counter."
   ::= {pr1645v2Lan2FGUOamEntry 117440512}

pr1645v2Lan2FGUOamLoopbackCtrlRx OBJECT-TYPE
   SYNTAX      Counter32
   MAX-ACCESS  read-only
   STATUS      current
   DESCRIPTION
      "Path: ethernet2.performance.oam.loopbackCtrlRx

       32 bit unsigned wrappable counter."
   ::= {pr1645v2Lan2FGUOamEntry 134217728}

pr1645v2Lan2FGUOamVarReqTx OBJECT-TYPE
   SYNTAX      Counter32
   MAX-ACCESS  read-only
   STATUS      current
   DESCRIPTION
      "Path: ethernet2.performance.oam.varReqTx

       32 bit unsigned wrappable counter."
   ::= {pr1645v2Lan2FGUOamEntry 150994944}

pr1645v2Lan2FGUOamVarReqRx OBJECT-TYPE
   SYNTAX      Counter32
   MAX-ACCESS  read-only
   STATUS      current
   DESCRIPTION
      "Path: ethernet2.performance.oam.varReqRx

       32 bit unsigned wrappable counter."
   ::= {pr1645v2Lan2FGUOamEntry 167772160}

pr1645v2Lan2FGUOamVarRespTx OBJECT-TYPE
   SYNTAX      Counter32
   MAX-ACCESS  read-only
   STATUS      current
   DESCRIPTION
      "Path: ethernet2.performance.oam.varRespTx

       32 bit unsigned wrappable counter."
   ::= {pr1645v2Lan2FGUOamEntry 184549376}

pr1645v2Lan2FGUOamVarRespRx OBJECT-TYPE
   SYNTAX      Counter32
   MAX-ACCESS  read-only
   STATUS      current
   DESCRIPTION
      "Path: ethernet2.performance.oam.varRespRx

       32 bit unsigned wrappable counter."
   ::= {pr1645v2Lan2FGUOamEntry 201326592}

pr1645v2Lan2FGUOamOrgSpecificTx OBJECT-TYPE
   SYNTAX      Counter32
   MAX-ACCESS  read-only
   STATUS      current
   DESCRIPTION
      "Path: ethernet2.performance.oam.orgSpecificTx

       32 bit unsigned wrappable counter."
   ::= {pr1645v2Lan2FGUOamEntry 218103808}

pr1645v2Lan2FGUOamOrgSpecificRx OBJECT-TYPE
   SYNTAX      Counter32
   MAX-ACCESS  read-only
   STATUS      current
   DESCRIPTION
      "Path: ethernet2.performance.oam.orgSpecificRx

       32 bit unsigned wrappable counter."
   ::= {pr1645v2Lan2FGUOamEntry 234881024}

pr1645v2Lan2FGUOamUnsupportedCodesTx OBJECT-TYPE
   SYNTAX      Counter32
   MAX-ACCESS  read-only
   STATUS      current
   DESCRIPTION
      "Path: ethernet2.performance.oam.unsupportedCodesTx

       32 bit unsigned wrappable counter."
   ::= {pr1645v2Lan2FGUOamEntry 251658240}

pr1645v2Lan2FGUOamUnsupportedCodesRx OBJECT-TYPE
   SYNTAX      Counter32
   MAX-ACCESS  read-only
   STATUS      current
   DESCRIPTION
      "Path: ethernet2.performance.oam.unsupportedCodesRx

       32 bit unsigned wrappable counter."
   ::= {pr1645v2Lan2FGUOamEntry 268435456}

pr1645v2Lan2FGUOamPduDiscardRx OBJECT-TYPE
   SYNTAX      Counter32
   MAX-ACCESS  read-only
   STATUS      current
   DESCRIPTION
      "Path: ethernet2.performance.oam.pduDiscardRx

       32 bit unsigned wrappable counter."
   ::= {pr1645v2Lan2FGUOamEntry 1694498816}

pr1645v2Lan2FGUOamDataDiscardTx OBJECT-TYPE
   SYNTAX      Counter32
   MAX-ACCESS  read-only
   STATUS      current
   DESCRIPTION
      "Path: ethernet2.performance.oam.dataDiscardTx

       32 bit unsigned wrappable counter."
   ::= {pr1645v2Lan2FGUOamEntry 1711276032}

pr1645v2Lan2FGUOamDataDiscardRx OBJECT-TYPE
   SYNTAX      Counter32
   MAX-ACCESS  read-only
   STATUS      current
   DESCRIPTION
      "Path: ethernet2.performance.oam.dataDiscardRx

       32 bit unsigned wrappable counter."
   ::= {pr1645v2Lan2FGUOamEntry 1728053248}


pr1645v2Lan2FGUVlan OBJECT IDENTIFIER ::= {pr1645v2Lan2FGU 310}

pr1645v2Lan2FGUVlanSSCTable OBJECT-TYPE
   SYNTAX      SEQUENCE OF Pr1645v2Lan2FGUVlanEntry
   MAX-ACCESS  not-accessible
   STATUS      current
   DESCRIPTION
      ""
   ::= {pr1645v2Lan2FGUVlan 1}

pr1645v2Lan2FGUVlanEntry OBJECT-TYPE
   SYNTAX      Pr1645v2Lan2FGUVlanEntry
   MAX-ACCESS  not-accessible
   STATUS      current
   DESCRIPTION
      ""
   INDEX      { pr1645v2Lan2FGUVlanTableIx }
   ::= {pr1645v2Lan2FGUVlanSSCTable 1}

Pr1645v2Lan2FGUVlanEntry ::=
   SEQUENCE
      {
      pr1645v2Lan2FGUVlanTableIx
         TableIndex,
      pr1645v2Lan2FGUVlanName
         DisplayString,
      pr1645v2Lan2FGUVlanMCInOctets
         Counter64,
      pr1645v2Lan2FGUVlanMCInUcast
         Counter64,
      pr1645v2Lan2FGUVlanMCInNUcastPkts
         Counter64,
      pr1645v2Lan2FGUVlanMCInBcastPkts
         Counter64,
      pr1645v2Lan2FGUVlanMCInMcastPkts
         Counter64,
      pr1645v2Lan2FGUVlanMCInDiscards
         Counter64,
      pr1645v2Lan2FGUVlanMCInErrors
         Counter64,
      pr1645v2Lan2FGUVlanMCInUnknownProtos
         Counter64,
      pr1645v2Lan2FGUVlanMCInDropEx
         Counter64,
      pr1645v2Lan2FGUVlanMCInDropNoMac
         Counter64,
      pr1645v2Lan2FGUVlanMCInDropNUCast
         Counter64,
      pr1645v2Lan2FGUVlanMCInDropFilter
         Counter64,
      pr1645v2Lan2FGUVlanMCInBandwidth15sec
         Integer32,
      pr1645v2Lan2FGUVlanMCInBandwidth30sec
         Integer32,
      pr1645v2Lan2FGUVlanMCInBandwidth1min
         Integer32,
      pr1645v2Lan2FGUVlanMCInBandwidth2min
         Integer32,
      pr1645v2Lan2FGUVlanMCInBandwidth5min
         Integer32,
      pr1645v2Lan2FGUVlanMCOutOctets
         Counter64,
      pr1645v2Lan2FGUVlanMCOutUcastPkts
         Counter64,
      pr1645v2Lan2FGUVlanMCOutNUcastPkts
         Counter64,
      pr1645v2Lan2FGUVlanMCOutBcastPkts
         Counter64,
      pr1645v2Lan2FGUVlanMCOutMcastPkts
         Counter64,
      pr1645v2Lan2FGUVlanMCOutDiscards
         Counter64,
      pr1645v2Lan2FGUVlanMCOutErrors
         Counter64,
      pr1645v2Lan2FGUVlanMCOutQLen
         Counter32,
      pr1645v2Lan2FGUVlanMCOutDropEx
         Counter64,
      pr1645v2Lan2FGUVlanMCOutDropNoArp
         Counter64,
      pr1645v2Lan2FGUVlanMCOutDropFilter
         Counter64,
      pr1645v2Lan2FGUVlanMCOutBandwidth15sec
         Integer32,
      pr1645v2Lan2FGUVlanMCOutBandwidth30sec
         Integer32,
      pr1645v2Lan2FGUVlanMCOutBandwidth1min
         Integer32,
      pr1645v2Lan2FGUVlanMCOutBandwidth2min
         Integer32,
      pr1645v2Lan2FGUVlanMCOutBandwidth5min
         Integer32,
      pr1645v2Lan2FGUVlanVlanVid
         Integer32,
      pr1645v2Lan2FGUVlanPppLinkMonitoringRequestsSent
         Gauge32,
      pr1645v2Lan2FGUVlanPppLinkMonitoringRepliesRcvd
         Gauge32,
      pr1645v2Lan2FGUVlanPppLinkMonitoringRequestsRcvd
         Gauge32,
      pr1645v2Lan2FGUVlanPppLinkMonitoringRepliesSent
         Gauge32
      }

pr1645v2Lan2FGUVlanTableIx OBJECT-TYPE
   SYNTAX      TableIndex
   MAX-ACCESS  not-accessible
   STATUS      current
   DESCRIPTION
      ""
   ::= {pr1645v2Lan2FGUVlanEntry 11}

pr1645v2Lan2FGUVlanName OBJECT-TYPE
   SYNTAX      DisplayString
   MAX-ACCESS  read-only
   STATUS      current
   DESCRIPTION
      "Path: ethernet2.performance.vlan.name"
   ::= {pr1645v2Lan2FGUVlanEntry 16777216}

pr1645v2Lan2FGUVlanMCInOctets OBJECT-TYPE
   SYNTAX      Counter64
   MAX-ACCESS  read-only
   STATUS      current
   DESCRIPTION
      "Path: ethernet2.performance.vlan.mibCounters.ifInOctets

       64 bit unsigned wrappable counter."
   ::= {pr1645v2Lan2FGUVlanEntry 40697856}

pr1645v2Lan2FGUVlanMCInUcast OBJECT-TYPE
   SYNTAX      Counter64
   MAX-ACCESS  read-only
   STATUS      current
   DESCRIPTION
      "Path: ethernet2.performance.vlan.mibCounters.ifInUcastPkts

       64 bit unsigned wrappable counter."
   ::= {pr1645v2Lan2FGUVlanEntry 40763392}

pr1645v2Lan2FGUVlanMCInNUcastPkts OBJECT-TYPE
   SYNTAX      Counter64
   MAX-ACCESS  read-only
   STATUS      current
   DESCRIPTION
      "Path: ethernet2.performance.vlan.mibCounters.ifInNUcastPkts

       64 bit unsigned wrappable counter."
   ::= {pr1645v2Lan2FGUVlanEntry 40828928}

pr1645v2Lan2FGUVlanMCInBcastPkts OBJECT-TYPE
   SYNTAX      Counter64
   MAX-ACCESS  read-only
   STATUS      current
   DESCRIPTION
      "Path: ethernet2.performance.vlan.mibCounters.ifInBcastPkts

       64 bit unsigned wrappable counter."
   ::= {pr1645v2Lan2FGUVlanEntry 47382528}

pr1645v2Lan2FGUVlanMCInMcastPkts OBJECT-TYPE
   SYNTAX      Counter64
   MAX-ACCESS  read-only
   STATUS      current
   DESCRIPTION
      "Path: ethernet2.performance.vlan.mibCounters.ifInMcastPkts

       64 bit unsigned wrappable counter."
   ::= {pr1645v2Lan2FGUVlanEntry 48037888}

pr1645v2Lan2FGUVlanMCInDiscards OBJECT-TYPE
   SYNTAX      Counter64
   MAX-ACCESS  read-only
   STATUS      current
   DESCRIPTION
      "Path: ethernet2.performance.vlan.mibCounters.ifInDiscards

       64 bit unsigned wrappable counter."
   ::= {pr1645v2Lan2FGUVlanEntry 40894464}

pr1645v2Lan2FGUVlanMCInErrors OBJECT-TYPE
   SYNTAX      Counter64
   MAX-ACCESS  read-only
   STATUS      current
   DESCRIPTION
      "Path: ethernet2.performance.vlan.mibCounters.ifInErrors

       64 bit unsigned wrappable counter."
   ::= {pr1645v2Lan2FGUVlanEntry 40960000}

pr1645v2Lan2FGUVlanMCInUnknownProtos OBJECT-TYPE
   SYNTAX      Counter64
   MAX-ACCESS  read-only
   STATUS      current
   DESCRIPTION
      "Path: ethernet2.performance.vlan.mibCounters.ifInUnknownProtos

       64 bit unsigned wrappable counter."
   ::= {pr1645v2Lan2FGUVlanEntry 41025536}

pr1645v2Lan2FGUVlanMCInDropEx OBJECT-TYPE
   SYNTAX      Counter64
   MAX-ACCESS  read-only
   STATUS      current
   DESCRIPTION
      "Path: ethernet2.performance.vlan.mibCounters.ifInDropLevelExceeded

       64 bit unsigned wrappable counter."
   ::= {pr1645v2Lan2FGUVlanEntry 42074112}

pr1645v2Lan2FGUVlanMCInDropNoMac OBJECT-TYPE
   SYNTAX      Counter64
   MAX-ACCESS  read-only
   STATUS      current
   DESCRIPTION
      "Path: ethernet2.performance.vlan.mibCounters.ifInDiscardsNoMacFit

       64 bit unsigned wrappable counter."
   ::= {pr1645v2Lan2FGUVlanEntry 42270720}

pr1645v2Lan2FGUVlanMCInDropNUCast OBJECT-TYPE
   SYNTAX      Counter64
   MAX-ACCESS  read-only
   STATUS      current
   DESCRIPTION
      "Path: ethernet2.performance.vlan.mibCounters.ifInDiscardsNUCast

       64 bit unsigned wrappable counter."
   ::= {pr1645v2Lan2FGUVlanEntry 42467328}

pr1645v2Lan2FGUVlanMCInDropFilter OBJECT-TYPE
   SYNTAX      Counter64
   MAX-ACCESS  read-only
   STATUS      current
   DESCRIPTION
      "Path: ethernet2.performance.vlan.mibCounters.ifInDiscardsFilter

       64 bit unsigned wrappable counter."
   ::= {pr1645v2Lan2FGUVlanEntry 42532864}

pr1645v2Lan2FGUVlanMCInBandwidth15sec OBJECT-TYPE
   SYNTAX      Integer32
   MAX-ACCESS  read-only
   STATUS      current
   DESCRIPTION
      "Path: ethernet2.performance.vlan.mibCounters.ifInBandwidth.15sec

       unit name = bps
       formula = 8 * ; 8 /"
   ::= {pr1645v2Lan2FGUVlanEntry 45417728}

pr1645v2Lan2FGUVlanMCInBandwidth30sec OBJECT-TYPE
   SYNTAX      Integer32
   MAX-ACCESS  read-only
   STATUS      current
   DESCRIPTION
      "Path: ethernet2.performance.vlan.mibCounters.ifInBandwidth.30sec

       unit name = bps
       formula = 8 * ; 8 /"
   ::= {pr1645v2Lan2FGUVlanEntry 45419008}

pr1645v2Lan2FGUVlanMCInBandwidth1min OBJECT-TYPE
   SYNTAX      Integer32
   MAX-ACCESS  read-only
   STATUS      current
   DESCRIPTION
      "Path: ethernet2.performance.vlan.mibCounters.ifInBandwidth.1min

       unit name = bps
       formula = 8 * ; 8 /"
   ::= {pr1645v2Lan2FGUVlanEntry 45421568}

pr1645v2Lan2FGUVlanMCInBandwidth2min OBJECT-TYPE
   SYNTAX      Integer32
   MAX-ACCESS  read-only
   STATUS      current
   DESCRIPTION
      "Path: ethernet2.performance.vlan.mibCounters.ifInBandwidth.2min

       unit name = bps
       formula = 8 * ; 8 /"
   ::= {pr1645v2Lan2FGUVlanEntry 45426688}

pr1645v2Lan2FGUVlanMCInBandwidth5min OBJECT-TYPE
   SYNTAX      Integer32
   MAX-ACCESS  read-only
   STATUS      current
   DESCRIPTION
      "Path: ethernet2.performance.vlan.mibCounters.ifInBandwidth.5min

       unit name = bps
       formula = 8 * ; 8 /"
   ::= {pr1645v2Lan2FGUVlanEntry 45442048}

pr1645v2Lan2FGUVlanMCOutOctets OBJECT-TYPE
   SYNTAX      Counter64
   MAX-ACCESS  read-only
   STATUS      current
   DESCRIPTION
      "Path: ethernet2.performance.vlan.mibCounters.ifOutOctets

       64 bit unsigned wrappable counter."
   ::= {pr1645v2Lan2FGUVlanEntry 41091072}

pr1645v2Lan2FGUVlanMCOutUcastPkts OBJECT-TYPE
   SYNTAX      Counter64
   MAX-ACCESS  read-only
   STATUS      current
   DESCRIPTION
      "Path: ethernet2.performance.vlan.mibCounters.ifOutUcastPkts

       64 bit unsigned wrappable counter."
   ::= {pr1645v2Lan2FGUVlanEntry 41156608}

pr1645v2Lan2FGUVlanMCOutNUcastPkts OBJECT-TYPE
   SYNTAX      Counter64
   MAX-ACCESS  read-only
   STATUS      current
   DESCRIPTION
      "Path: ethernet2.performance.vlan.mibCounters.ifOutNUcastPkts

       64 bit unsigned wrappable counter."
   ::= {pr1645v2Lan2FGUVlanEntry 41222144}

pr1645v2Lan2FGUVlanMCOutBcastPkts OBJECT-TYPE
   SYNTAX      Counter64
   MAX-ACCESS  read-only
   STATUS      current
   DESCRIPTION
      "Path: ethernet2.performance.vlan.mibCounters.ifOutBcastPkts

       64 bit unsigned wrappable counter."
   ::= {pr1645v2Lan2FGUVlanEntry 47775744}

pr1645v2Lan2FGUVlanMCOutMcastPkts OBJECT-TYPE
   SYNTAX      Counter64
   MAX-ACCESS  read-only
   STATUS      current
   DESCRIPTION
      "Path: ethernet2.performance.vlan.mibCounters.ifOutMcastPkts

       64 bit unsigned wrappable counter."
   ::= {pr1645v2Lan2FGUVlanEntry 48431104}

pr1645v2Lan2FGUVlanMCOutDiscards OBJECT-TYPE
   SYNTAX      Counter64
   MAX-ACCESS  read-only
   STATUS      current
   DESCRIPTION
      "Path: ethernet2.performance.vlan.mibCounters.ifOutDiscards

       64 bit unsigned wrappable counter."
   ::= {pr1645v2Lan2FGUVlanEntry 41287680}

pr1645v2Lan2FGUVlanMCOutErrors OBJECT-TYPE
   SYNTAX      Counter64
   MAX-ACCESS  read-only
   STATUS      current
   DESCRIPTION
      "Path: ethernet2.performance.vlan.mibCounters.ifOutErrors

       64 bit unsigned wrappable counter."
   ::= {pr1645v2Lan2FGUVlanEntry 41353216}

pr1645v2Lan2FGUVlanMCOutQLen OBJECT-TYPE
   SYNTAX      Counter32
   MAX-ACCESS  read-only
   STATUS      current
   DESCRIPTION
      "Path: ethernet2.performance.vlan.mibCounters.ifOutQLen

       32 bit unsigned wrappable counter."
   ::= {pr1645v2Lan2FGUVlanEntry 41418752}

pr1645v2Lan2FGUVlanMCOutDropEx OBJECT-TYPE
   SYNTAX      Counter64
   MAX-ACCESS  read-only
   STATUS      current
   DESCRIPTION
      "Path: ethernet2.performance.vlan.mibCounters.ifOutDropLevelExceeded

       64 bit unsigned wrappable counter."
   ::= {pr1645v2Lan2FGUVlanEntry 41484288}

pr1645v2Lan2FGUVlanMCOutDropNoArp OBJECT-TYPE
   SYNTAX      Counter64
   MAX-ACCESS  read-only
   STATUS      current
   DESCRIPTION
      "Path: ethernet2.performance.vlan.mibCounters.ifOutDiscardsNoArp

       64 bit unsigned wrappable counter."
   ::= {pr1645v2Lan2FGUVlanEntry 42336256}

pr1645v2Lan2FGUVlanMCOutDropFilter OBJECT-TYPE
   SYNTAX      Counter64
   MAX-ACCESS  read-only
   STATUS      current
   DESCRIPTION
      "Path: ethernet2.performance.vlan.mibCounters.ifOutDiscardsFilter

       64 bit unsigned wrappable counter."
   ::= {pr1645v2Lan2FGUVlanEntry 42598400}

pr1645v2Lan2FGUVlanMCOutBandwidth15sec OBJECT-TYPE
   SYNTAX      Integer32
   MAX-ACCESS  read-only
   STATUS      current
   DESCRIPTION
      "Path: ethernet2.performance.vlan.mibCounters.ifOutBandwidth.15sec

       unit name = bps
       formula = 8 * ; 8 /"
   ::= {pr1645v2Lan2FGUVlanEntry 45483264}

pr1645v2Lan2FGUVlanMCOutBandwidth30sec OBJECT-TYPE
   SYNTAX      Integer32
   MAX-ACCESS  read-only
   STATUS      current
   DESCRIPTION
      "Path: ethernet2.performance.vlan.mibCounters.ifOutBandwidth.30sec

       unit name = bps
       formula = 8 * ; 8 /"
   ::= {pr1645v2Lan2FGUVlanEntry 45484544}

pr1645v2Lan2FGUVlanMCOutBandwidth1min OBJECT-TYPE
   SYNTAX      Integer32
   MAX-ACCESS  read-only
   STATUS      current
   DESCRIPTION
      "Path: ethernet2.performance.vlan.mibCounters.ifOutBandwidth.1min

       unit name = bps
       formula = 8 * ; 8 /"
   ::= {pr1645v2Lan2FGUVlanEntry 45487104}

pr1645v2Lan2FGUVlanMCOutBandwidth2min OBJECT-TYPE
   SYNTAX      Integer32
   MAX-ACCESS  read-only
   STATUS      current
   DESCRIPTION
      "Path: ethernet2.performance.vlan.mibCounters.ifOutBandwidth.2min

       unit name = bps
       formula = 8 * ; 8 /"
   ::= {pr1645v2Lan2FGUVlanEntry 45492224}

pr1645v2Lan2FGUVlanMCOutBandwidth5min OBJECT-TYPE
   SYNTAX      Integer32
   MAX-ACCESS  read-only
   STATUS      current
   DESCRIPTION
      "Path: ethernet2.performance.vlan.mibCounters.ifOutBandwidth.5min

       unit name = bps
       formula = 8 * ; 8 /"
   ::= {pr1645v2Lan2FGUVlanEntry 45507584}

pr1645v2Lan2FGUVlanVlanVid OBJECT-TYPE
   SYNTAX      Integer32
   MAX-ACCESS  read-only
   STATUS      current
   DESCRIPTION
      "Path: ethernet2.performance.vlan.vlan.vid"
   ::= {pr1645v2Lan2FGUVlanEntry 234946560}

pr1645v2Lan2FGUVlanPppLinkMonitoringRequestsSent OBJECT-TYPE
   SYNTAX      Gauge32
   MAX-ACCESS  read-only
   STATUS      current
   DESCRIPTION
      "Path: ethernet2.performance.vlan.ppp.linkMonitoring.requestsSent

       32 bit unsigned gauge value."
   ::= {pr1645v2Lan2FGUVlanEntry 50397440}

pr1645v2Lan2FGUVlanPppLinkMonitoringRepliesRcvd OBJECT-TYPE
   SYNTAX      Gauge32
   MAX-ACCESS  read-only
   STATUS      current
   DESCRIPTION
      "Path: ethernet2.performance.vlan.ppp.linkMonitoring.repliesRcvd

       32 bit unsigned gauge value."
   ::= {pr1645v2Lan2FGUVlanEntry 50397696}

pr1645v2Lan2FGUVlanPppLinkMonitoringRequestsRcvd OBJECT-TYPE
   SYNTAX      Gauge32
   MAX-ACCESS  read-only
   STATUS      current
   DESCRIPTION
      "Path: ethernet2.performance.vlan.ppp.linkMonitoring.requestsRcvd

       32 bit unsigned gauge value."
   ::= {pr1645v2Lan2FGUVlanEntry 50397952}

pr1645v2Lan2FGUVlanPppLinkMonitoringRepliesSent OBJECT-TYPE
   SYNTAX      Gauge32
   MAX-ACCESS  read-only
   STATUS      current
   DESCRIPTION
      "Path: ethernet2.performance.vlan.ppp.linkMonitoring.repliesSent

       32 bit unsigned gauge value."
   ::= {pr1645v2Lan2FGUVlanEntry 50398208}

pr1645v2Lan2FGUVlanMCH2P OBJECT-TYPE
   SYNTAX      SEQUENCE OF Pr1645v2Lan2FGUVlanMCH2PEntry
   MAX-ACCESS  not-accessible
   STATUS      current
   DESCRIPTION
      ""
   ::= {pr1645v2Lan2FGUVlan 41549824}

pr1645v2Lan2FGUVlanMCH2PEntry OBJECT-TYPE
   SYNTAX      Pr1645v2Lan2FGUVlanMCH2PEntry
   MAX-ACCESS  not-accessible
   STATUS      current
   DESCRIPTION
      ""
   INDEX      { pr1645v2Lan2FGUVlanTableIx,
                pr1645v2Lan2FGUVlanMCH2PTableIx }
   ::= {pr1645v2Lan2FGUVlanMCH2P 1}

Pr1645v2Lan2FGUVlanMCH2PEntry ::=
   SEQUENCE
      {
      pr1645v2Lan2FGUVlanMCH2PTableIx
         TableIndex,
      pr1645v2Lan2FGUVlanMCH2PSysUpTime
         TimeTicks,
      pr1645v2Lan2FGUVlanMCH2PIfUpTime
         TimeTicks,
      pr1645v2Lan2FGUVlanMCH2PIfStatChanges
         Counter32,
      pr1645v2Lan2FGUVlanMCH2PIfInOctets
         Counter64,
      pr1645v2Lan2FGUVlanMCH2PIfInUCPkts
         Counter64,
      pr1645v2Lan2FGUVlanMCH2PIfInNUCPkts
         Counter64,
      pr1645v2Lan2FGUVlanMCH2PIfInBCPkts
         Counter64,
      pr1645v2Lan2FGUVlanMCH2PIfInMCPkts
         Counter64,
      pr1645v2Lan2FGUVlanMCH2PIfInDiscards
         Counter64,
      pr1645v2Lan2FGUVlanMCH2PIfInErrors
         Counter64,
      pr1645v2Lan2FGUVlanMCH2PIfInUnkwn
         Counter64,
      pr1645v2Lan2FGUVlanMCH2PInDropEx
         Counter64,
      pr1645v2Lan2FGUVlanMCH2PInDropNoMac
         Counter64,
      pr1645v2Lan2FGUVlanMCH2PInDropNUCast
         Counter64,
      pr1645v2Lan2FGUVlanMCH2PInDropFilter
         Counter64,
      pr1645v2Lan2FGUVlanMCH2PIfInBandwidth
         Integer32,
      pr1645v2Lan2FGUVlanMCH2PIfOutOctets
         Counter64,
      pr1645v2Lan2FGUVlanMCH2PIfOutUCPkts
         Counter64,
      pr1645v2Lan2FGUVlanMCH2PIfOutNUCPkts
         Counter64,
      pr1645v2Lan2FGUVlanMCH2PIfOutBCPkts
         Counter64,
      pr1645v2Lan2FGUVlanMCH2PIfOutMCPkts
         Counter64,
      pr1645v2Lan2FGUVlanMCH2PIfOutDiscards
         Counter64,
      pr1645v2Lan2FGUVlanMCH2PIfOutErrors
         Counter64,
      pr1645v2Lan2FGUVlanMCH2POutDropEx
         Counter64,
      pr1645v2Lan2FGUVlanMCH2POutDropNoArp
         Counter64,
      pr1645v2Lan2FGUVlanMCH2POutDropFilter
         Counter64,
      pr1645v2Lan2FGUVlanMCH2PIfOutBandwidth
         Integer32,
      pr1645v2Lan2FGUVlanMCH2PIfErrSec
         Counter32
      }

pr1645v2Lan2FGUVlanMCH2PTableIx OBJECT-TYPE
   SYNTAX      TableIndex
   MAX-ACCESS  not-accessible
   STATUS      current
   DESCRIPTION
      ""
   ::= {pr1645v2Lan2FGUVlanMCH2PEntry 11}

pr1645v2Lan2FGUVlanMCH2PSysUpTime OBJECT-TYPE
   SYNTAX      TimeTicks
   MAX-ACCESS  read-only
   STATUS      current
   DESCRIPTION
      "Path: ethernet2.performance.vlan.mibCounters.h2Performance.sysUpTime

       Time in centi-second."
   ::= {pr1645v2Lan2FGUVlanMCH2PEntry 16777216}

pr1645v2Lan2FGUVlanMCH2PIfUpTime OBJECT-TYPE
   SYNTAX      TimeTicks
   MAX-ACCESS  read-only
   STATUS      current
   DESCRIPTION
      "Path: ethernet2.performance.vlan.mibCounters.h2Performance.ifUpTime

       Time in centi-second."
   ::= {pr1645v2Lan2FGUVlanMCH2PEntry 33554432}

pr1645v2Lan2FGUVlanMCH2PIfStatChanges OBJECT-TYPE
   SYNTAX      Counter32
   MAX-ACCESS  read-only
   STATUS      current
   DESCRIPTION
      "Path: ethernet2.performance.vlan.mibCounters.h2Performance.ifStatusChanges

       32 bit unsigned wrappable counter."
   ::= {pr1645v2Lan2FGUVlanMCH2PEntry 50331648}

pr1645v2Lan2FGUVlanMCH2PIfInOctets OBJECT-TYPE
   SYNTAX      Counter64
   MAX-ACCESS  read-only
   STATUS      current
   DESCRIPTION
      "Path: ethernet2.performance.vlan.mibCounters.h2Performance.ifInOctets

       64 bit unsigned wrappable counter."
   ::= {pr1645v2Lan2FGUVlanMCH2PEntry 67108864}

pr1645v2Lan2FGUVlanMCH2PIfInUCPkts OBJECT-TYPE
   SYNTAX      Counter64
   MAX-ACCESS  read-only
   STATUS      current
   DESCRIPTION
      "Path: ethernet2.performance.vlan.mibCounters.h2Performance.ifInUcastPkts

       64 bit unsigned wrappable counter."
   ::= {pr1645v2Lan2FGUVlanMCH2PEntry 83886080}

pr1645v2Lan2FGUVlanMCH2PIfInNUCPkts OBJECT-TYPE
   SYNTAX      Counter64
   MAX-ACCESS  read-only
   STATUS      current
   DESCRIPTION
      "Path: ethernet2.performance.vlan.mibCounters.h2Performance.ifInNUcastPkts

       64 bit unsigned wrappable counter."
   ::= {pr1645v2Lan2FGUVlanMCH2PEntry 100663296}

pr1645v2Lan2FGUVlanMCH2PIfInBCPkts OBJECT-TYPE
   SYNTAX      Counter64
   MAX-ACCESS  read-only
   STATUS      current
   DESCRIPTION
      "Path: ethernet2.performance.vlan.mibCounters.h2Performance.ifInBcastPkts

       64 bit unsigned wrappable counter."
   ::= {pr1645v2Lan2FGUVlanMCH2PEntry 419430400}

pr1645v2Lan2FGUVlanMCH2PIfInMCPkts OBJECT-TYPE
   SYNTAX      Counter64
   MAX-ACCESS  read-only
   STATUS      current
   DESCRIPTION
      "Path: ethernet2.performance.vlan.mibCounters.h2Performance.ifInMcastPkts

       64 bit unsigned wrappable counter."
   ::= {pr1645v2Lan2FGUVlanMCH2PEntry 436207616}

pr1645v2Lan2FGUVlanMCH2PIfInDiscards OBJECT-TYPE
   SYNTAX      Counter64
   MAX-ACCESS  read-only
   STATUS      current
   DESCRIPTION
      "Path: ethernet2.performance.vlan.mibCounters.h2Performance.ifInDiscards

       64 bit unsigned wrappable counter."
   ::= {pr1645v2Lan2FGUVlanMCH2PEntry 117440512}

pr1645v2Lan2FGUVlanMCH2PIfInErrors OBJECT-TYPE
   SYNTAX      Counter64
   MAX-ACCESS  read-only
   STATUS      current
   DESCRIPTION
      "Path: ethernet2.performance.vlan.mibCounters.h2Performance.ifInErrors

       64 bit unsigned wrappable counter."
   ::= {pr1645v2Lan2FGUVlanMCH2PEntry 134217728}

pr1645v2Lan2FGUVlanMCH2PIfInUnkwn OBJECT-TYPE
   SYNTAX      Counter64
   MAX-ACCESS  read-only
   STATUS      current
   DESCRIPTION
      "Path: ethernet2.performance.vlan.mibCounters.h2Performance.ifInUnknownProtos

       64 bit unsigned wrappable counter."
   ::= {pr1645v2Lan2FGUVlanMCH2PEntry 150994944}

pr1645v2Lan2FGUVlanMCH2PInDropEx OBJECT-TYPE
   SYNTAX      Counter64
   MAX-ACCESS  read-only
   STATUS      current
   DESCRIPTION
      "Path: ethernet2.performance.vlan.mibCounters.h2Performance.ifInDropLevelExceeded

       64 bit unsigned wrappable counter."
   ::= {pr1645v2Lan2FGUVlanMCH2PEntry 335544320}

pr1645v2Lan2FGUVlanMCH2PInDropNoMac OBJECT-TYPE
   SYNTAX      Counter64
   MAX-ACCESS  read-only
   STATUS      current
   DESCRIPTION
      "Path: ethernet2.performance.vlan.mibCounters.h2Performance.fInDiscardsNoMacFit

       64 bit unsigned wrappable counter."
   ::= {pr1645v2Lan2FGUVlanMCH2PEntry 301989888}

pr1645v2Lan2FGUVlanMCH2PInDropNUCast OBJECT-TYPE
   SYNTAX      Counter64
   MAX-ACCESS  read-only
   STATUS      current
   DESCRIPTION
      "Path: ethernet2.performance.vlan.mibCounters.h2Performance.fInDiscardsNUCast

       64 bit unsigned wrappable counter."
   ::= {pr1645v2Lan2FGUVlanMCH2PEntry 318767104}

pr1645v2Lan2FGUVlanMCH2PInDropFilter OBJECT-TYPE
   SYNTAX      Counter64
   MAX-ACCESS  read-only
   STATUS      current
   DESCRIPTION
      "Path: ethernet2.performance.vlan.mibCounters.h2Performance.fInDiscardsFilter

       64 bit unsigned wrappable counter."
   ::= {pr1645v2Lan2FGUVlanMCH2PEntry 385875968}

pr1645v2Lan2FGUVlanMCH2PIfInBandwidth OBJECT-TYPE
   SYNTAX      Integer32
   MAX-ACCESS  read-only
   STATUS      current
   DESCRIPTION
      "Path: ethernet2.performance.vlan.mibCounters.h2Performance.ifInBandwidth

       unit name = bps
       formula = 8 * ; 8 /"
   ::= {pr1645v2Lan2FGUVlanMCH2PEntry 268435456}

pr1645v2Lan2FGUVlanMCH2PIfOutOctets OBJECT-TYPE
   SYNTAX      Counter64
   MAX-ACCESS  read-only
   STATUS      current
   DESCRIPTION
      "Path: ethernet2.performance.vlan.mibCounters.h2Performance.ifOutOctets

       64 bit unsigned wrappable counter."
   ::= {pr1645v2Lan2FGUVlanMCH2PEntry 167772160}

pr1645v2Lan2FGUVlanMCH2PIfOutUCPkts OBJECT-TYPE
   SYNTAX      Counter64
   MAX-ACCESS  read-only
   STATUS      current
   DESCRIPTION
      "Path: ethernet2.performance.vlan.mibCounters.h2Performance.ifOutUcastPkts

       64 bit unsigned wrappable counter."
   ::= {pr1645v2Lan2FGUVlanMCH2PEntry 184549376}

pr1645v2Lan2FGUVlanMCH2PIfOutNUCPkts OBJECT-TYPE
   SYNTAX      Counter64
   MAX-ACCESS  read-only
   STATUS      current
   DESCRIPTION
      "Path: ethernet2.performance.vlan.mibCounters.h2Performance.ifOutNUcastPkts

       64 bit unsigned wrappable counter."
   ::= {pr1645v2Lan2FGUVlanMCH2PEntry 201326592}

pr1645v2Lan2FGUVlanMCH2PIfOutBCPkts OBJECT-TYPE
   SYNTAX      Counter64
   MAX-ACCESS  read-only
   STATUS      current
   DESCRIPTION
      "Path: ethernet2.performance.vlan.mibCounters.h2Performance.ifOutBcastPkts

       64 bit unsigned wrappable counter."
   ::= {pr1645v2Lan2FGUVlanMCH2PEntry 452984832}

pr1645v2Lan2FGUVlanMCH2PIfOutMCPkts OBJECT-TYPE
   SYNTAX      Counter64
   MAX-ACCESS  read-only
   STATUS      current
   DESCRIPTION
      "Path: ethernet2.performance.vlan.mibCounters.h2Performance.ifOutMcastPkts

       64 bit unsigned wrappable counter."
   ::= {pr1645v2Lan2FGUVlanMCH2PEntry 469762048}

pr1645v2Lan2FGUVlanMCH2PIfOutDiscards OBJECT-TYPE
   SYNTAX      Counter64
   MAX-ACCESS  read-only
   STATUS      current
   DESCRIPTION
      "Path: ethernet2.performance.vlan.mibCounters.h2Performance.ifOutDiscards

       64 bit unsigned wrappable counter."
   ::= {pr1645v2Lan2FGUVlanMCH2PEntry 218103808}

pr1645v2Lan2FGUVlanMCH2PIfOutErrors OBJECT-TYPE
   SYNTAX      Counter64
   MAX-ACCESS  read-only
   STATUS      current
   DESCRIPTION
      "Path: ethernet2.performance.vlan.mibCounters.h2Performance.ifOutErrors

       64 bit unsigned wrappable counter."
   ::= {pr1645v2Lan2FGUVlanMCH2PEntry 234881024}

pr1645v2Lan2FGUVlanMCH2POutDropEx OBJECT-TYPE
   SYNTAX      Counter64
   MAX-ACCESS  read-only
   STATUS      current
   DESCRIPTION
      "Path: ethernet2.performance.vlan.mibCounters.h2Performance.ifOutDropLevelExceeded

       64 bit unsigned wrappable counter."
   ::= {pr1645v2Lan2FGUVlanMCH2PEntry 352321536}

pr1645v2Lan2FGUVlanMCH2POutDropNoArp OBJECT-TYPE
   SYNTAX      Counter64
   MAX-ACCESS  read-only
   STATUS      current
   DESCRIPTION
      "Path: ethernet2.performance.vlan.mibCounters.h2Performance.ifOutDiscardsNoArp

       64 bit unsigned wrappable counter."
   ::= {pr1645v2Lan2FGUVlanMCH2PEntry 369098752}

pr1645v2Lan2FGUVlanMCH2POutDropFilter OBJECT-TYPE
   SYNTAX      Counter64
   MAX-ACCESS  read-only
   STATUS      current
   DESCRIPTION
      "Path: ethernet2.performance.vlan.mibCounters.h2Performance.ifOutDiscardsFilter

       64 bit unsigned wrappable counter."
   ::= {pr1645v2Lan2FGUVlanMCH2PEntry 402653184}

pr1645v2Lan2FGUVlanMCH2PIfOutBandwidth OBJECT-TYPE
   SYNTAX      Integer32
   MAX-ACCESS  read-only
   STATUS      current
   DESCRIPTION
      "Path: ethernet2.performance.vlan.mibCounters.h2Performance.ifOutBandwidth

       unit name = bps
       formula = 8 * ; 8 /"
   ::= {pr1645v2Lan2FGUVlanMCH2PEntry 285212672}

pr1645v2Lan2FGUVlanMCH2PIfErrSec OBJECT-TYPE
   SYNTAX      Counter32
   MAX-ACCESS  read-only
   STATUS      current
   DESCRIPTION
      "Path: ethernet2.performance.vlan.mibCounters.h2Performance.ifErrSec

       32 bit unsigned wrappable counter."
   ::= {pr1645v2Lan2FGUVlanMCH2PEntry 251658240}

pr1645v2Lan2FGUVlanMCH24P OBJECT-TYPE
   SYNTAX      SEQUENCE OF Pr1645v2Lan2FGUVlanMCH24PEntry
   MAX-ACCESS  not-accessible
   STATUS      current
   DESCRIPTION
      ""
   ::= {pr1645v2Lan2FGUVlan 41615360}

pr1645v2Lan2FGUVlanMCH24PEntry OBJECT-TYPE
   SYNTAX      Pr1645v2Lan2FGUVlanMCH24PEntry
   MAX-ACCESS  not-accessible
   STATUS      current
   DESCRIPTION
      ""
   INDEX      { pr1645v2Lan2FGUVlanTableIx,
                pr1645v2Lan2FGUVlanMCH24PTableIx }
   ::= {pr1645v2Lan2FGUVlanMCH24P 1}

Pr1645v2Lan2FGUVlanMCH24PEntry ::=
   SEQUENCE
      {
      pr1645v2Lan2FGUVlanMCH24PTableIx
         TableIndex,
      pr1645v2Lan2FGUVlanMCH24PSysUpTime
         TimeTicks,
      pr1645v2Lan2FGUVlanMCH24PIfUpTime
         TimeTicks,
      pr1645v2Lan2FGUVlanMCH24PIfStatChanges
         Counter32,
      pr1645v2Lan2FGUVlanMCH24PIfInOctets
         Counter64,
      pr1645v2Lan2FGUVlanMCH24PIfInUCPkts
         Counter64,
      pr1645v2Lan2FGUVlanMCH24PIfInNUCPkts
         Counter64,
      pr1645v2Lan2FGUVlanMCH24PIfInBCPkts
         Counter64,
      pr1645v2Lan2FGUVlanMCH24PIfInMCPkts
         Counter64,
      pr1645v2Lan2FGUVlanMCH24PIfInDiscards
         Counter64,
      pr1645v2Lan2FGUVlanMCH24PIfInErrors
         Counter64,
      pr1645v2Lan2FGUVlanMCH24PIfInUnkwn
         Counter64,
      pr1645v2Lan2FGUVlanMCH24PInDropEx
         Counter64,
      pr1645v2Lan2FGUVlanMCH24PInDropNoMac
         Counter64,
      pr1645v2Lan2FGUVlanMCH24PInDropNUCast
         Counter64,
      pr1645v2Lan2FGUVlanMCH24PInDropFilter
         Counter64,
      pr1645v2Lan2FGUVlanMCH24PIfInBandwidth
         Integer32,
      pr1645v2Lan2FGUVlanMCH24PIfOutOctets
         Counter64,
      pr1645v2Lan2FGUVlanMCH24PIfOutUCPkts
         Counter64,
      pr1645v2Lan2FGUVlanMCH24PIfOutNUCPkts
         Counter64,
      pr1645v2Lan2FGUVlanMCH24PIfOutBCPkts
         Counter64,
      pr1645v2Lan2FGUVlanMCH24PIfOutMCPkts
         Counter64,
      pr1645v2Lan2FGUVlanMCH24PIfOutDiscards
         Counter64,
      pr1645v2Lan2FGUVlanMCH24PIfOutErrors
         Counter64,
      pr1645v2Lan2FGUVlanMCH24POutDropEx
         Counter64,
      pr1645v2Lan2FGUVlanMCH24POutDropNoArp
         Counter64,
      pr1645v2Lan2FGUVlanMCH24POutDropFilter
         Counter64,
      pr1645v2Lan2FGUVlanMCH24PIfOutBandwidth
         Integer32,
      pr1645v2Lan2FGUVlanMCH24PIfErrSec
         Counter32
      }

pr1645v2Lan2FGUVlanMCH24PTableIx OBJECT-TYPE
   SYNTAX      TableIndex
   MAX-ACCESS  not-accessible
   STATUS      current
   DESCRIPTION
      ""
   ::= {pr1645v2Lan2FGUVlanMCH24PEntry 11}

pr1645v2Lan2FGUVlanMCH24PSysUpTime OBJECT-TYPE
   SYNTAX      TimeTicks
   MAX-ACCESS  read-only
   STATUS      current
   DESCRIPTION
      "Path: ethernet2.performance.vlan.mibCounters.h24Performance.sysUpTime

       Time in centi-second."
   ::= {pr1645v2Lan2FGUVlanMCH24PEntry 16777216}

pr1645v2Lan2FGUVlanMCH24PIfUpTime OBJECT-TYPE
   SYNTAX      TimeTicks
   MAX-ACCESS  read-only
   STATUS      current
   DESCRIPTION
      "Path: ethernet2.performance.vlan.mibCounters.h24Performance.ifUpTime

       Time in centi-second."
   ::= {pr1645v2Lan2FGUVlanMCH24PEntry 33554432}

pr1645v2Lan2FGUVlanMCH24PIfStatChanges OBJECT-TYPE
   SYNTAX      Counter32
   MAX-ACCESS  read-only
   STATUS      current
   DESCRIPTION
      "Path: ethernet2.performance.vlan.mibCounters.h24Performance.ifStatusChanges

       32 bit unsigned wrappable counter."
   ::= {pr1645v2Lan2FGUVlanMCH24PEntry 50331648}

pr1645v2Lan2FGUVlanMCH24PIfInOctets OBJECT-TYPE
   SYNTAX      Counter64
   MAX-ACCESS  read-only
   STATUS      current
   DESCRIPTION
      "Path: ethernet2.performance.vlan.mibCounters.h24Performance.ifInOctets

       64 bit unsigned wrappable counter."
   ::= {pr1645v2Lan2FGUVlanMCH24PEntry 67108864}

pr1645v2Lan2FGUVlanMCH24PIfInUCPkts OBJECT-TYPE
   SYNTAX      Counter64
   MAX-ACCESS  read-only
   STATUS      current
   DESCRIPTION
      "Path: ethernet2.performance.vlan.mibCounters.h24Performance.ifInUcastPkts

       64 bit unsigned wrappable counter."
   ::= {pr1645v2Lan2FGUVlanMCH24PEntry 83886080}

pr1645v2Lan2FGUVlanMCH24PIfInNUCPkts OBJECT-TYPE
   SYNTAX      Counter64
   MAX-ACCESS  read-only
   STATUS      current
   DESCRIPTION
      "Path: ethernet2.performance.vlan.mibCounters.h24Performance.ifInNUcastPkts

       64 bit unsigned wrappable counter."
   ::= {pr1645v2Lan2FGUVlanMCH24PEntry 100663296}

pr1645v2Lan2FGUVlanMCH24PIfInBCPkts OBJECT-TYPE
   SYNTAX      Counter64
   MAX-ACCESS  read-only
   STATUS      current
   DESCRIPTION
      "Path: ethernet2.performance.vlan.mibCounters.h24Performance.ifInBcastPkts

       64 bit unsigned wrappable counter."
   ::= {pr1645v2Lan2FGUVlanMCH24PEntry 419430400}

pr1645v2Lan2FGUVlanMCH24PIfInMCPkts OBJECT-TYPE
   SYNTAX      Counter64
   MAX-ACCESS  read-only
   STATUS      current
   DESCRIPTION
      "Path: ethernet2.performance.vlan.mibCounters.h24Performance.ifInMcastPkts

       64 bit unsigned wrappable counter."
   ::= {pr1645v2Lan2FGUVlanMCH24PEntry 436207616}

pr1645v2Lan2FGUVlanMCH24PIfInDiscards OBJECT-TYPE
   SYNTAX      Counter64
   MAX-ACCESS  read-only
   STATUS      current
   DESCRIPTION
      "Path: ethernet2.performance.vlan.mibCounters.h24Performance.ifInDiscards

       64 bit unsigned wrappable counter."
   ::= {pr1645v2Lan2FGUVlanMCH24PEntry 117440512}

pr1645v2Lan2FGUVlanMCH24PIfInErrors OBJECT-TYPE
   SYNTAX      Counter64
   MAX-ACCESS  read-only
   STATUS      current
   DESCRIPTION
      "Path: ethernet2.performance.vlan.mibCounters.h24Performance.ifInErrors

       64 bit unsigned wrappable counter."
   ::= {pr1645v2Lan2FGUVlanMCH24PEntry 134217728}

pr1645v2Lan2FGUVlanMCH24PIfInUnkwn OBJECT-TYPE
   SYNTAX      Counter64
   MAX-ACCESS  read-only
   STATUS      current
   DESCRIPTION
      "Path: ethernet2.performance.vlan.mibCounters.h24Performance.ifInUnknownProtos

       64 bit unsigned wrappable counter."
   ::= {pr1645v2Lan2FGUVlanMCH24PEntry 150994944}

pr1645v2Lan2FGUVlanMCH24PInDropEx OBJECT-TYPE
   SYNTAX      Counter64
   MAX-ACCESS  read-only
   STATUS      current
   DESCRIPTION
      "Path: ethernet2.performance.vlan.mibCounters.h24Performance.ifInDropLevelExceeded

       64 bit unsigned wrappable counter."
   ::= {pr1645v2Lan2FGUVlanMCH24PEntry 335544320}

pr1645v2Lan2FGUVlanMCH24PInDropNoMac OBJECT-TYPE
   SYNTAX      Counter64
   MAX-ACCESS  read-only
   STATUS      current
   DESCRIPTION
      "Path: ethernet2.performance.vlan.mibCounters.h24Performance.fInDiscardsNoMacFit

       64 bit unsigned wrappable counter."
   ::= {pr1645v2Lan2FGUVlanMCH24PEntry 301989888}

pr1645v2Lan2FGUVlanMCH24PInDropNUCast OBJECT-TYPE
   SYNTAX      Counter64
   MAX-ACCESS  read-only
   STATUS      current
   DESCRIPTION
      "Path: ethernet2.performance.vlan.mibCounters.h24Performance.fInDiscardsNUCast

       64 bit unsigned wrappable counter."
   ::= {pr1645v2Lan2FGUVlanMCH24PEntry 318767104}

pr1645v2Lan2FGUVlanMCH24PInDropFilter OBJECT-TYPE
   SYNTAX      Counter64
   MAX-ACCESS  read-only
   STATUS      current
   DESCRIPTION
      "Path: ethernet2.performance.vlan.mibCounters.h24Performance.fInDiscardsFilter

       64 bit unsigned wrappable counter."
   ::= {pr1645v2Lan2FGUVlanMCH24PEntry 385875968}

pr1645v2Lan2FGUVlanMCH24PIfInBandwidth OBJECT-TYPE
   SYNTAX      Integer32
   MAX-ACCESS  read-only
   STATUS      current
   DESCRIPTION
      "Path: ethernet2.performance.vlan.mibCounters.h24Performance.ifInBandwidth

       unit name = bps
       formula = 8 * ; 8 /"
   ::= {pr1645v2Lan2FGUVlanMCH24PEntry 268435456}

pr1645v2Lan2FGUVlanMCH24PIfOutOctets OBJECT-TYPE
   SYNTAX      Counter64
   MAX-ACCESS  read-only
   STATUS      current
   DESCRIPTION
      "Path: ethernet2.performance.vlan.mibCounters.h24Performance.ifOutOctets

       64 bit unsigned wrappable counter."
   ::= {pr1645v2Lan2FGUVlanMCH24PEntry 167772160}

pr1645v2Lan2FGUVlanMCH24PIfOutUCPkts OBJECT-TYPE
   SYNTAX      Counter64
   MAX-ACCESS  read-only
   STATUS      current
   DESCRIPTION
      "Path: ethernet2.performance.vlan.mibCounters.h24Performance.ifOutUcastPkts

       64 bit unsigned wrappable counter."
   ::= {pr1645v2Lan2FGUVlanMCH24PEntry 184549376}

pr1645v2Lan2FGUVlanMCH24PIfOutNUCPkts OBJECT-TYPE
   SYNTAX      Counter64
   MAX-ACCESS  read-only
   STATUS      current
   DESCRIPTION
      "Path: ethernet2.performance.vlan.mibCounters.h24Performance.ifOutNUcastPkts

       64 bit unsigned wrappable counter."
   ::= {pr1645v2Lan2FGUVlanMCH24PEntry 201326592}

pr1645v2Lan2FGUVlanMCH24PIfOutBCPkts OBJECT-TYPE
   SYNTAX      Counter64
   MAX-ACCESS  read-only
   STATUS      current
   DESCRIPTION
      "Path: ethernet2.performance.vlan.mibCounters.h24Performance.ifOutBcastPkts

       64 bit unsigned wrappable counter."
   ::= {pr1645v2Lan2FGUVlanMCH24PEntry 452984832}

pr1645v2Lan2FGUVlanMCH24PIfOutMCPkts OBJECT-TYPE
   SYNTAX      Counter64
   MAX-ACCESS  read-only
   STATUS      current
   DESCRIPTION
      "Path: ethernet2.performance.vlan.mibCounters.h24Performance.ifOutMcastPkts

       64 bit unsigned wrappable counter."
   ::= {pr1645v2Lan2FGUVlanMCH24PEntry 469762048}

pr1645v2Lan2FGUVlanMCH24PIfOutDiscards OBJECT-TYPE
   SYNTAX      Counter64
   MAX-ACCESS  read-only
   STATUS      current
   DESCRIPTION
      "Path: ethernet2.performance.vlan.mibCounters.h24Performance.ifOutDiscards

       64 bit unsigned wrappable counter."
   ::= {pr1645v2Lan2FGUVlanMCH24PEntry 218103808}

pr1645v2Lan2FGUVlanMCH24PIfOutErrors OBJECT-TYPE
   SYNTAX      Counter64
   MAX-ACCESS  read-only
   STATUS      current
   DESCRIPTION
      "Path: ethernet2.performance.vlan.mibCounters.h24Performance.ifOutErrors

       64 bit unsigned wrappable counter."
   ::= {pr1645v2Lan2FGUVlanMCH24PEntry 234881024}

pr1645v2Lan2FGUVlanMCH24POutDropEx OBJECT-TYPE
   SYNTAX      Counter64
   MAX-ACCESS  read-only
   STATUS      current
   DESCRIPTION
      "Path: ethernet2.performance.vlan.mibCounters.h24Performance.ifOutDropLevelExceeded

       64 bit unsigned wrappable counter."
   ::= {pr1645v2Lan2FGUVlanMCH24PEntry 352321536}

pr1645v2Lan2FGUVlanMCH24POutDropNoArp OBJECT-TYPE
   SYNTAX      Counter64
   MAX-ACCESS  read-only
   STATUS      current
   DESCRIPTION
      "Path: ethernet2.performance.vlan.mibCounters.h24Performance.ifOutDiscardsNoArp

       64 bit unsigned wrappable counter."
   ::= {pr1645v2Lan2FGUVlanMCH24PEntry 369098752}

pr1645v2Lan2FGUVlanMCH24POutDropFilter OBJECT-TYPE
   SYNTAX      Counter64
   MAX-ACCESS  read-only
   STATUS      current
   DESCRIPTION
      "Path: ethernet2.performance.vlan.mibCounters.h24Performance.ifOutDiscardsFilter

       64 bit unsigned wrappable counter."
   ::= {pr1645v2Lan2FGUVlanMCH24PEntry 402653184}

pr1645v2Lan2FGUVlanMCH24PIfOutBandwidth OBJECT-TYPE
   SYNTAX      Integer32
   MAX-ACCESS  read-only
   STATUS      current
   DESCRIPTION
      "Path: ethernet2.performance.vlan.mibCounters.h24Performance.ifOutBandwidth

       unit name = bps
       formula = 8 * ; 8 /"
   ::= {pr1645v2Lan2FGUVlanMCH24PEntry 285212672}

pr1645v2Lan2FGUVlanMCH24PIfErrSec OBJECT-TYPE
   SYNTAX      Counter32
   MAX-ACCESS  read-only
   STATUS      current
   DESCRIPTION
      "Path: ethernet2.performance.vlan.mibCounters.h24Performance.ifErrSec

       32 bit unsigned wrappable counter."
   ::= {pr1645v2Lan2FGUVlanMCH24PEntry 251658240}

pr1645v2Lan2FGUVlanMCD7P OBJECT-TYPE
   SYNTAX      SEQUENCE OF Pr1645v2Lan2FGUVlanMCD7PEntry
   MAX-ACCESS  not-accessible
   STATUS      current
   DESCRIPTION
      ""
   ::= {pr1645v2Lan2FGUVlan 41680896}

pr1645v2Lan2FGUVlanMCD7PEntry OBJECT-TYPE
   SYNTAX      Pr1645v2Lan2FGUVlanMCD7PEntry
   MAX-ACCESS  not-accessible
   STATUS      current
   DESCRIPTION
      ""
   INDEX      { pr1645v2Lan2FGUVlanTableIx,
                pr1645v2Lan2FGUVlanMCD7PTableIx }
   ::= {pr1645v2Lan2FGUVlanMCD7P 1}

Pr1645v2Lan2FGUVlanMCD7PEntry ::=
   SEQUENCE
      {
      pr1645v2Lan2FGUVlanMCD7PTableIx
         TableIndex,
      pr1645v2Lan2FGUVlanMCD7PSysUpTime
         TimeTicks,
      pr1645v2Lan2FGUVlanMCD7PIfUpTime
         TimeTicks,
      pr1645v2Lan2FGUVlanMCD7PIfStatChanges
         Counter32,
      pr1645v2Lan2FGUVlanMCD7PIfInOctets
         Counter64,
      pr1645v2Lan2FGUVlanMCD7PIfInUCPkts
         Counter64,
      pr1645v2Lan2FGUVlanMCD7PIfInNUCPkts
         Counter64,
      pr1645v2Lan2FGUVlanMCD7PIfInBCPkts
         Counter64,
      pr1645v2Lan2FGUVlanMCD7PIfInMCPkts
         Counter64,
      pr1645v2Lan2FGUVlanMCD7PIfInDiscards
         Counter64,
      pr1645v2Lan2FGUVlanMCD7PIfInErrors
         Counter64,
      pr1645v2Lan2FGUVlanMCD7PIfInUnkwn
         Counter64,
      pr1645v2Lan2FGUVlanMCD7PInDropEx
         Counter64,
      pr1645v2Lan2FGUVlanMCD7PInDropNoMac
         Counter64,
      pr1645v2Lan2FGUVlanMCD7PInDropNUCast
         Counter64,
      pr1645v2Lan2FGUVlanMCD7PInDropFilter
         Counter64,
      pr1645v2Lan2FGUVlanMCD7PIfInBandwidth
         Integer32,
      pr1645v2Lan2FGUVlanMCD7PIfOutOctets
         Counter64,
      pr1645v2Lan2FGUVlanMCD7PIfOutUCPkts
         Counter64,
      pr1645v2Lan2FGUVlanMCD7PIfOutNUCPkts
         Counter64,
      pr1645v2Lan2FGUVlanMCD7PIfOutBCPkts
         Counter64,
      pr1645v2Lan2FGUVlanMCD7PIfOutMCPkts
         Counter64,
      pr1645v2Lan2FGUVlanMCD7PIfOutDiscards
         Counter64,
      pr1645v2Lan2FGUVlanMCD7PIfOutErrors
         Counter64,
      pr1645v2Lan2FGUVlanMCD7POutDropEx
         Counter64,
      pr1645v2Lan2FGUVlanMCD7POutDropNoArp
         Counter64,
      pr1645v2Lan2FGUVlanMCD7POutDropFilter
         Counter64,
      pr1645v2Lan2FGUVlanMCD7PIfOutBandwidth
         Integer32,
      pr1645v2Lan2FGUVlanMCD7PIfErrSec
         Counter32
      }

pr1645v2Lan2FGUVlanMCD7PTableIx OBJECT-TYPE
   SYNTAX      TableIndex
   MAX-ACCESS  not-accessible
   STATUS      current
   DESCRIPTION
      ""
   ::= {pr1645v2Lan2FGUVlanMCD7PEntry 11}

pr1645v2Lan2FGUVlanMCD7PSysUpTime OBJECT-TYPE
   SYNTAX      TimeTicks
   MAX-ACCESS  read-only
   STATUS      current
   DESCRIPTION
      "Path: ethernet2.performance.vlan.mibCounters.d7Performance.sysUpTime

       Time in centi-second."
   ::= {pr1645v2Lan2FGUVlanMCD7PEntry 16777216}

pr1645v2Lan2FGUVlanMCD7PIfUpTime OBJECT-TYPE
   SYNTAX      TimeTicks
   MAX-ACCESS  read-only
   STATUS      current
   DESCRIPTION
      "Path: ethernet2.performance.vlan.mibCounters.d7Performance.ifUpTime

       Time in centi-second."
   ::= {pr1645v2Lan2FGUVlanMCD7PEntry 33554432}

pr1645v2Lan2FGUVlanMCD7PIfStatChanges OBJECT-TYPE
   SYNTAX      Counter32
   MAX-ACCESS  read-only
   STATUS      current
   DESCRIPTION
      "Path: ethernet2.performance.vlan.mibCounters.d7Performance.ifStatusChanges

       32 bit unsigned wrappable counter."
   ::= {pr1645v2Lan2FGUVlanMCD7PEntry 50331648}

pr1645v2Lan2FGUVlanMCD7PIfInOctets OBJECT-TYPE
   SYNTAX      Counter64
   MAX-ACCESS  read-only
   STATUS      current
   DESCRIPTION
      "Path: ethernet2.performance.vlan.mibCounters.d7Performance.ifInOctets

       64 bit unsigned wrappable counter."
   ::= {pr1645v2Lan2FGUVlanMCD7PEntry 67108864}

pr1645v2Lan2FGUVlanMCD7PIfInUCPkts OBJECT-TYPE
   SYNTAX      Counter64
   MAX-ACCESS  read-only
   STATUS      current
   DESCRIPTION
      "Path: ethernet2.performance.vlan.mibCounters.d7Performance.ifInUcastPkts

       64 bit unsigned wrappable counter."
   ::= {pr1645v2Lan2FGUVlanMCD7PEntry 83886080}

pr1645v2Lan2FGUVlanMCD7PIfInNUCPkts OBJECT-TYPE
   SYNTAX      Counter64
   MAX-ACCESS  read-only
   STATUS      current
   DESCRIPTION
      "Path: ethernet2.performance.vlan.mibCounters.d7Performance.ifInNUcastPkts

       64 bit unsigned wrappable counter."
   ::= {pr1645v2Lan2FGUVlanMCD7PEntry 100663296}

pr1645v2Lan2FGUVlanMCD7PIfInBCPkts OBJECT-TYPE
   SYNTAX      Counter64
   MAX-ACCESS  read-only
   STATUS      current
   DESCRIPTION
      "Path: ethernet2.performance.vlan.mibCounters.d7Performance.ifInBcastPkts

       64 bit unsigned wrappable counter."
   ::= {pr1645v2Lan2FGUVlanMCD7PEntry 419430400}

pr1645v2Lan2FGUVlanMCD7PIfInMCPkts OBJECT-TYPE
   SYNTAX      Counter64
   MAX-ACCESS  read-only
   STATUS      current
   DESCRIPTION
      "Path: ethernet2.performance.vlan.mibCounters.d7Performance.ifInMcastPkts

       64 bit unsigned wrappable counter."
   ::= {pr1645v2Lan2FGUVlanMCD7PEntry 436207616}

pr1645v2Lan2FGUVlanMCD7PIfInDiscards OBJECT-TYPE
   SYNTAX      Counter64
   MAX-ACCESS  read-only
   STATUS      current
   DESCRIPTION
      "Path: ethernet2.performance.vlan.mibCounters.d7Performance.ifInDiscards

       64 bit unsigned wrappable counter."
   ::= {pr1645v2Lan2FGUVlanMCD7PEntry 117440512}

pr1645v2Lan2FGUVlanMCD7PIfInErrors OBJECT-TYPE
   SYNTAX      Counter64
   MAX-ACCESS  read-only
   STATUS      current
   DESCRIPTION
      "Path: ethernet2.performance.vlan.mibCounters.d7Performance.ifInErrors

       64 bit unsigned wrappable counter."
   ::= {pr1645v2Lan2FGUVlanMCD7PEntry 134217728}

pr1645v2Lan2FGUVlanMCD7PIfInUnkwn OBJECT-TYPE
   SYNTAX      Counter64
   MAX-ACCESS  read-only
   STATUS      current
   DESCRIPTION
      "Path: ethernet2.performance.vlan.mibCounters.d7Performance.ifInUnknownProtos

       64 bit unsigned wrappable counter."
   ::= {pr1645v2Lan2FGUVlanMCD7PEntry 150994944}

pr1645v2Lan2FGUVlanMCD7PInDropEx OBJECT-TYPE
   SYNTAX      Counter64
   MAX-ACCESS  read-only
   STATUS      current
   DESCRIPTION
      "Path: ethernet2.performance.vlan.mibCounters.d7Performance.ifInDropLevelExceeded

       64 bit unsigned wrappable counter."
   ::= {pr1645v2Lan2FGUVlanMCD7PEntry 335544320}

pr1645v2Lan2FGUVlanMCD7PInDropNoMac OBJECT-TYPE
   SYNTAX      Counter64
   MAX-ACCESS  read-only
   STATUS      current
   DESCRIPTION
      "Path: ethernet2.performance.vlan.mibCounters.d7Performance.fInDiscardsNoMacFit

       64 bit unsigned wrappable counter."
   ::= {pr1645v2Lan2FGUVlanMCD7PEntry 301989888}

pr1645v2Lan2FGUVlanMCD7PInDropNUCast OBJECT-TYPE
   SYNTAX      Counter64
   MAX-ACCESS  read-only
   STATUS      current
   DESCRIPTION
      "Path: ethernet2.performance.vlan.mibCounters.d7Performance.fInDiscardsNUCast

       64 bit unsigned wrappable counter."
   ::= {pr1645v2Lan2FGUVlanMCD7PEntry 318767104}

pr1645v2Lan2FGUVlanMCD7PInDropFilter OBJECT-TYPE
   SYNTAX      Counter64
   MAX-ACCESS  read-only
   STATUS      current
   DESCRIPTION
      "Path: ethernet2.performance.vlan.mibCounters.d7Performance.fInDiscardsFilter

       64 bit unsigned wrappable counter."
   ::= {pr1645v2Lan2FGUVlanMCD7PEntry 385875968}

pr1645v2Lan2FGUVlanMCD7PIfInBandwidth OBJECT-TYPE
   SYNTAX      Integer32
   MAX-ACCESS  read-only
   STATUS      current
   DESCRIPTION
      "Path: ethernet2.performance.vlan.mibCounters.d7Performance.ifInBandwidth

       unit name = bps
       formula = 8 * ; 8 /"
   ::= {pr1645v2Lan2FGUVlanMCD7PEntry 268435456}

pr1645v2Lan2FGUVlanMCD7PIfOutOctets OBJECT-TYPE
   SYNTAX      Counter64
   MAX-ACCESS  read-only
   STATUS      current
   DESCRIPTION
      "Path: ethernet2.performance.vlan.mibCounters.d7Performance.ifOutOctets

       64 bit unsigned wrappable counter."
   ::= {pr1645v2Lan2FGUVlanMCD7PEntry 167772160}

pr1645v2Lan2FGUVlanMCD7PIfOutUCPkts OBJECT-TYPE
   SYNTAX      Counter64
   MAX-ACCESS  read-only
   STATUS      current
   DESCRIPTION
      "Path: ethernet2.performance.vlan.mibCounters.d7Performance.ifOutUcastPkts

       64 bit unsigned wrappable counter."
   ::= {pr1645v2Lan2FGUVlanMCD7PEntry 184549376}

pr1645v2Lan2FGUVlanMCD7PIfOutNUCPkts OBJECT-TYPE
   SYNTAX      Counter64
   MAX-ACCESS  read-only
   STATUS      current
   DESCRIPTION
      "Path: ethernet2.performance.vlan.mibCounters.d7Performance.ifOutNUcastPkts

       64 bit unsigned wrappable counter."
   ::= {pr1645v2Lan2FGUVlanMCD7PEntry 201326592}

pr1645v2Lan2FGUVlanMCD7PIfOutBCPkts OBJECT-TYPE
   SYNTAX      Counter64
   MAX-ACCESS  read-only
   STATUS      current
   DESCRIPTION
      "Path: ethernet2.performance.vlan.mibCounters.d7Performance.ifOutBcastPkts

       64 bit unsigned wrappable counter."
   ::= {pr1645v2Lan2FGUVlanMCD7PEntry 452984832}

pr1645v2Lan2FGUVlanMCD7PIfOutMCPkts OBJECT-TYPE
   SYNTAX      Counter64
   MAX-ACCESS  read-only
   STATUS      current
   DESCRIPTION
      "Path: ethernet2.performance.vlan.mibCounters.d7Performance.ifOutMcastPkts

       64 bit unsigned wrappable counter."
   ::= {pr1645v2Lan2FGUVlanMCD7PEntry 469762048}

pr1645v2Lan2FGUVlanMCD7PIfOutDiscards OBJECT-TYPE
   SYNTAX      Counter64
   MAX-ACCESS  read-only
   STATUS      current
   DESCRIPTION
      "Path: ethernet2.performance.vlan.mibCounters.d7Performance.ifOutDiscards

       64 bit unsigned wrappable counter."
   ::= {pr1645v2Lan2FGUVlanMCD7PEntry 218103808}

pr1645v2Lan2FGUVlanMCD7PIfOutErrors OBJECT-TYPE
   SYNTAX      Counter64
   MAX-ACCESS  read-only
   STATUS      current
   DESCRIPTION
      "Path: ethernet2.performance.vlan.mibCounters.d7Performance.ifOutErrors

       64 bit unsigned wrappable counter."
   ::= {pr1645v2Lan2FGUVlanMCD7PEntry 234881024}

pr1645v2Lan2FGUVlanMCD7POutDropEx OBJECT-TYPE
   SYNTAX      Counter64
   MAX-ACCESS  read-only
   STATUS      current
   DESCRIPTION
      "Path: ethernet2.performance.vlan.mibCounters.d7Performance.ifOutDropLevelExceeded

       64 bit unsigned wrappable counter."
   ::= {pr1645v2Lan2FGUVlanMCD7PEntry 352321536}

pr1645v2Lan2FGUVlanMCD7POutDropNoArp OBJECT-TYPE
   SYNTAX      Counter64
   MAX-ACCESS  read-only
   STATUS      current
   DESCRIPTION
      "Path: ethernet2.performance.vlan.mibCounters.d7Performance.ifOutDiscardsNoArp

       64 bit unsigned wrappable counter."
   ::= {pr1645v2Lan2FGUVlanMCD7PEntry 369098752}

pr1645v2Lan2FGUVlanMCD7POutDropFilter OBJECT-TYPE
   SYNTAX      Counter64
   MAX-ACCESS  read-only
   STATUS      current
   DESCRIPTION
      "Path: ethernet2.performance.vlan.mibCounters.d7Performance.ifOutDiscardsFilter

       64 bit unsigned wrappable counter."
   ::= {pr1645v2Lan2FGUVlanMCD7PEntry 402653184}

pr1645v2Lan2FGUVlanMCD7PIfOutBandwidth OBJECT-TYPE
   SYNTAX      Integer32
   MAX-ACCESS  read-only
   STATUS      current
   DESCRIPTION
      "Path: ethernet2.performance.vlan.mibCounters.d7Performance.ifOutBandwidth

       unit name = bps
       formula = 8 * ; 8 /"
   ::= {pr1645v2Lan2FGUVlanMCD7PEntry 285212672}

pr1645v2Lan2FGUVlanMCD7PIfErrSec OBJECT-TYPE
   SYNTAX      Counter32
   MAX-ACCESS  read-only
   STATUS      current
   DESCRIPTION
      "Path: ethernet2.performance.vlan.mibCounters.d7Performance.ifErrSec

       32 bit unsigned wrappable counter."
   ::= {pr1645v2Lan2FGUVlanMCD7PEntry 251658240}

pr1645v2Lan2FGUVlanInPQs OBJECT-TYPE
   SYNTAX      SEQUENCE OF Pr1645v2Lan2FGUVlanInPQsEntry
   MAX-ACCESS  not-accessible
   STATUS      current
   DESCRIPTION
      ""
   ::= {pr1645v2Lan2FGUVlan 100663296}

pr1645v2Lan2FGUVlanInPQsEntry OBJECT-TYPE
   SYNTAX      Pr1645v2Lan2FGUVlanInPQsEntry
   MAX-ACCESS  not-accessible
   STATUS      current
   DESCRIPTION
      ""
   INDEX      { pr1645v2Lan2FGUVlanTableIx,
                pr1645v2Lan2FGUVlanInPQsTableIx }
   ::= {pr1645v2Lan2FGUVlanInPQs 1}

Pr1645v2Lan2FGUVlanInPQsEntry ::=
   SEQUENCE
      {
      pr1645v2Lan2FGUVlanInPQsTableIx
         TableIndex,
      pr1645v2Lan2FGUVlanInPQsName
         INTEGER,
      pr1645v2Lan2FGUVlanInPQsLength
         Integer32,
      pr1645v2Lan2FGUVlanInPQsOctetLength
         Integer32,
      pr1645v2Lan2FGUVlanInPQsRedLength
         Integer32,
      pr1645v2Lan2FGUVlanInPQsPacketsTotal
         Counter64,
      pr1645v2Lan2FGUVlanInPQsPacketsDirectTx
         Counter64,
      pr1645v2Lan2FGUVlanInPQsPacketsQueued
         Counter64,
      pr1645v2Lan2FGUVlanInPQsPacketsDropped
         Counter64,
      pr1645v2Lan2FGUVlanInPQsPacketsRedDropped
         Counter64,
      pr1645v2Lan2FGUVlanInPQsPacketsCirTx
         Counter64,
      pr1645v2Lan2FGUVlanInPQsPacketsEirTx
         Counter64,
      pr1645v2Lan2FGUVlanInPQsPacketsViolateTx
         Counter64,
      pr1645v2Lan2FGUVlanInPQsOctetsTotal
         Counter64,
      pr1645v2Lan2FGUVlanInPQsOctetsDirectTx
         Counter64,
      pr1645v2Lan2FGUVlanInPQsOctetsQueued
         Counter64,
      pr1645v2Lan2FGUVlanInPQsOctetsDropped
         Counter64,
      pr1645v2Lan2FGUVlanInPQsOctetsRedDropped
         Counter64,
      pr1645v2Lan2FGUVlanInPQsOctetsCirTx
         Counter64,
      pr1645v2Lan2FGUVlanInPQsOctetsEirTx
         Counter64,
      pr1645v2Lan2FGUVlanInPQsOctetsViolateTx
         Counter64,
      pr1645v2Lan2FGUVlanInPQsOctetsBandwidth15sec
         Integer32,
      pr1645v2Lan2FGUVlanInPQsOctetsBandwidth30sec
         Integer32,
      pr1645v2Lan2FGUVlanInPQsOctetsBandwidth1min
         Integer32,
      pr1645v2Lan2FGUVlanInPQsOctetsBandwidth2min
         Integer32,
      pr1645v2Lan2FGUVlanInPQsOctetsBandwidth5min
         Integer32
      }

pr1645v2Lan2FGUVlanInPQsTableIx OBJECT-TYPE
   SYNTAX      TableIndex
   MAX-ACCESS  not-accessible
   STATUS      current
   DESCRIPTION
      ""
   ::= {pr1645v2Lan2FGUVlanInPQsEntry 11}

pr1645v2Lan2FGUVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGUVlanInPQsEntry 16777216}

pr1645v2Lan2FGUVlanInPQsLength OBJECT-TYPE
   SYNTAX      Integer32
   MAX-ACCESS  read-only
   STATUS      current
   DESCRIPTION
      "Path: ethernet2.performance.vlan.inPriorityQueues.length"
   ::= {pr1645v2Lan2FGUVlanInPQsEntry 33554432}

pr1645v2Lan2FGUVlanInPQsOctetLength OBJECT-TYPE
   SYNTAX      Integer32
   MAX-ACCESS  read-only
   STATUS      current
   DESCRIPTION
      "Path: ethernet2.performance.vlan.inPriorityQueues.octetLength"
   ::= {pr1645v2Lan2FGUVlanInPQsEntry 150994944}

pr1645v2Lan2FGUVlanInPQsRedLength OBJECT-TYPE
   SYNTAX      Integer32
   MAX-ACCESS  read-only
   STATUS      current
   DESCRIPTION
      "Path: ethernet2.performance.vlan.inPriorityQueues.redLength"
   ::= {pr1645v2Lan2FGUVlanInPQsEntry 134217728}

pr1645v2Lan2FGUVlanInPQsPacketsTotal OBJECT-TYPE
   SYNTAX      Counter64
   MAX-ACCESS  read-only
   STATUS      current
   DESCRIPTION
      "Path: ethernet2.performance.vlan.inPriorityQueues.packets.total

       64 bit unsigned wrappable counter."
   ::= {pr1645v2Lan2FGUVlanInPQsEntry 50790400}

pr1645v2Lan2FGUVlanInPQsPacketsDirectTx OBJECT-TYPE
   SYNTAX      Counter64
   MAX-ACCESS  read-only
   STATUS      current
   DESCRIPTION
      "Path: ethernet2.performance.vlan.inPriorityQueues.packets.directTx

       64 bit unsigned wrappable counter."
   ::= {pr1645v2Lan2FGUVlanInPQsEntry 50397184}

pr1645v2Lan2FGUVlanInPQsPacketsQueued OBJECT-TYPE
   SYNTAX      Counter64
   MAX-ACCESS  read-only
   STATUS      current
   DESCRIPTION
      "Path: ethernet2.performance.vlan.inPriorityQueues.packets.queued

       64 bit unsigned wrappable counter."
   ::= {pr1645v2Lan2FGUVlanInPQsEntry 50462720}

pr1645v2Lan2FGUVlanInPQsPacketsDropped OBJECT-TYPE
   SYNTAX      Counter64
   MAX-ACCESS  read-only
   STATUS      current
   DESCRIPTION
      "Path: ethernet2.performance.vlan.inPriorityQueues.packets.dropped

       64 bit unsigned wrappable counter."
   ::= {pr1645v2Lan2FGUVlanInPQsEntry 50528256}

pr1645v2Lan2FGUVlanInPQsPacketsRedDropped OBJECT-TYPE
   SYNTAX      Counter64
   MAX-ACCESS  read-only
   STATUS      current
   DESCRIPTION
      "Path: ethernet2.performance.vlan.inPriorityQueues.packets.redDropped

       64 bit unsigned wrappable counter."
   ::= {pr1645v2Lan2FGUVlanInPQsEntry 50724864}

pr1645v2Lan2FGUVlanInPQsPacketsCirTx OBJECT-TYPE
   SYNTAX      Counter64
   MAX-ACCESS  read-only
   STATUS      current
   DESCRIPTION
      "Path: ethernet2.performance.vlan.inPriorityQueues.packets.cirTx

       64 bit unsigned wrappable counter."
   ::= {pr1645v2Lan2FGUVlanInPQsEntry 50593792}

pr1645v2Lan2FGUVlanInPQsPacketsEirTx OBJECT-TYPE
   SYNTAX      Counter64
   MAX-ACCESS  read-only
   STATUS      current
   DESCRIPTION
      "Path: ethernet2.performance.vlan.inPriorityQueues.packets.eirTx

       64 bit unsigned wrappable counter."
   ::= {pr1645v2Lan2FGUVlanInPQsEntry 50659328}

pr1645v2Lan2FGUVlanInPQsPacketsViolateTx OBJECT-TYPE
   SYNTAX      Counter64
   MAX-ACCESS  read-only
   STATUS      current
   DESCRIPTION
      "Path: ethernet2.performance.vlan.inPriorityQueues.packets.violateTx

       64 bit unsigned wrappable counter."
   ::= {pr1645v2Lan2FGUVlanInPQsEntry 50855936}

pr1645v2Lan2FGUVlanInPQsOctetsTotal OBJECT-TYPE
   SYNTAX      Counter64
   MAX-ACCESS  read-only
   STATUS      current
   DESCRIPTION
      "Path: ethernet2.performance.vlan.inPriorityQueues.octets.total

       64 bit unsigned wrappable counter."
   ::= {pr1645v2Lan2FGUVlanInPQsEntry 67567616}

pr1645v2Lan2FGUVlanInPQsOctetsDirectTx OBJECT-TYPE
   SYNTAX      Counter64
   MAX-ACCESS  read-only
   STATUS      current
   DESCRIPTION
      "Path: ethernet2.performance.vlan.inPriorityQueues.octets.directTx

       64 bit unsigned wrappable counter."
   ::= {pr1645v2Lan2FGUVlanInPQsEntry 67174400}

pr1645v2Lan2FGUVlanInPQsOctetsQueued OBJECT-TYPE
   SYNTAX      Counter64
   MAX-ACCESS  read-only
   STATUS      current
   DESCRIPTION
      "Path: ethernet2.performance.vlan.inPriorityQueues.octets.queued

       64 bit unsigned wrappable counter."
   ::= {pr1645v2Lan2FGUVlanInPQsEntry 67239936}

pr1645v2Lan2FGUVlanInPQsOctetsDropped OBJECT-TYPE
   SYNTAX      Counter64
   MAX-ACCESS  read-only
   STATUS      current
   DESCRIPTION
      "Path: ethernet2.performance.vlan.inPriorityQueues.octets.dropped

       64 bit unsigned wrappable counter."
   ::= {pr1645v2Lan2FGUVlanInPQsEntry 67305472}

pr1645v2Lan2FGUVlanInPQsOctetsRedDropped OBJECT-TYPE
   SYNTAX      Counter64
   MAX-ACCESS  read-only
   STATUS      current
   DESCRIPTION
      "Path: ethernet2.performance.vlan.inPriorityQueues.octets.redDropped

       64 bit unsigned wrappable counter."
   ::= {pr1645v2Lan2FGUVlanInPQsEntry 67502080}

pr1645v2Lan2FGUVlanInPQsOctetsCirTx OBJECT-TYPE
   SYNTAX      Counter64
   MAX-ACCESS  read-only
   STATUS      current
   DESCRIPTION
      "Path: ethernet2.performance.vlan.inPriorityQueues.octets.cirTx

       64 bit unsigned wrappable counter."
   ::= {pr1645v2Lan2FGUVlanInPQsEntry 67371008}

pr1645v2Lan2FGUVlanInPQsOctetsEirTx OBJECT-TYPE
   SYNTAX      Counter64
   MAX-ACCESS  read-only
   STATUS      current
   DESCRIPTION
      "Path: ethernet2.performance.vlan.inPriorityQueues.octets.eirTx

       64 bit unsigned wrappable counter."
   ::= {pr1645v2Lan2FGUVlanInPQsEntry 67436544}

pr1645v2Lan2FGUVlanInPQsOctetsViolateTx OBJECT-TYPE
   SYNTAX      Counter64
   MAX-ACCESS  read-only
   STATUS      current
   DESCRIPTION
      "Path: ethernet2.performance.vlan.inPriorityQueues.octets.violateTx

       64 bit unsigned wrappable counter."
   ::= {pr1645v2Lan2FGUVlanInPQsEntry 67633152}

pr1645v2Lan2FGUVlanInPQsOctetsBandwidth15sec OBJECT-TYPE
   SYNTAX      Integer32
   MAX-ACCESS  read-only
   STATUS      current
   DESCRIPTION
      "Path: ethernet2.performance.vlan.inPriorityQueues.octets.bandwidth.15sec

       unit name = bps
       formula = 8 * ; 8 /"
   ::= {pr1645v2Lan2FGUVlanInPQsEntry 70386944}

pr1645v2Lan2FGUVlanInPQsOctetsBandwidth30sec OBJECT-TYPE
   SYNTAX      Integer32
   MAX-ACCESS  read-only
   STATUS      current
   DESCRIPTION
      "Path: ethernet2.performance.vlan.inPriorityQueues.octets.bandwidth.30sec

       unit name = bps
       formula = 8 * ; 8 /"
   ::= {pr1645v2Lan2FGUVlanInPQsEntry 70388224}

pr1645v2Lan2FGUVlanInPQsOctetsBandwidth1min OBJECT-TYPE
   SYNTAX      Integer32
   MAX-ACCESS  read-only
   STATUS      current
   DESCRIPTION
      "Path: ethernet2.performance.vlan.inPriorityQueues.octets.bandwidth.1min

       unit name = bps
       formula = 8 * ; 8 /"
   ::= {pr1645v2Lan2FGUVlanInPQsEntry 70390784}

pr1645v2Lan2FGUVlanInPQsOctetsBandwidth2min OBJECT-TYPE
   SYNTAX      Integer32
   MAX-ACCESS  read-only
   STATUS      current
   DESCRIPTION
      "Path: ethernet2.performance.vlan.inPriorityQueues.octets.bandwidth.2min

       unit name = bps
       formula = 8 * ; 8 /"
   ::= {pr1645v2Lan2FGUVlanInPQsEntry 70395904}

pr1645v2Lan2FGUVlanInPQsOctetsBandwidth5min OBJECT-TYPE
   SYNTAX      Integer32
   MAX-ACCESS  read-only
   STATUS      current
   DESCRIPTION
      "Path: ethernet2.performance.vlan.inPriorityQueues.octets.bandwidth.5min

       unit name = bps
       formula = 8 * ; 8 /"
   ::= {pr1645v2Lan2FGUVlanInPQsEntry 70411264}

pr1645v2Lan2FGUVlanInPQsH2Performance OBJECT-TYPE
   SYNTAX      SEQUENCE OF Pr1645v2Lan2FGUVlanInPQsH2PerformanceEntry
   MAX-ACCESS  not-accessible
   STATUS      current
   DESCRIPTION
      ""
   ::= {pr1645v2Lan2FGUVlan 100990976}

pr1645v2Lan2FGUVlanInPQsH2PerformanceEntry OBJECT-TYPE
   SYNTAX      Pr1645v2Lan2FGUVlanInPQsH2PerformanceEntry
   MAX-ACCESS  not-accessible
   STATUS      current
   DESCRIPTION
      ""
   INDEX      { pr1645v2Lan2FGUVlanTableIx,
                pr1645v2Lan2FGUVlanInPQsTableIx,
                pr1645v2Lan2FGUVlanInPQsH2PerformanceTableIx }
   ::= {pr1645v2Lan2FGUVlanInPQsH2Performance 1}

Pr1645v2Lan2FGUVlanInPQsH2PerformanceEntry ::=
   SEQUENCE
      {
      pr1645v2Lan2FGUVlanInPQsH2PerformanceTableIx
         TableIndex,
      pr1645v2Lan2FGUVlanInPQsH2PerformanceSysUpTime
         TimeTicks,
      pr1645v2Lan2FGUVlanInPQsH2PerformanceTotPkts
         Counter64,
      pr1645v2Lan2FGUVlanInPQsH2PerformanceDirTxPkts
         Counter64,
      pr1645v2Lan2FGUVlanInPQsH2PerformanceQdPkts
         Counter64,
      pr1645v2Lan2FGUVlanInPQsH2PerformanceDropPkts
         Counter64,
      pr1645v2Lan2FGUVlanInPQsH2PerformanceRDropPkts
         Counter64,
      pr1645v2Lan2FGUVlanInPQsH2PerformanceCirTxPkts
         Counter64,
      pr1645v2Lan2FGUVlanInPQsH2PerformanceEirTxPkts
         Counter64,
      pr1645v2Lan2FGUVlanInPQsH2PerformanceViolTxPkts
         Counter64,
      pr1645v2Lan2FGUVlanInPQsH2PerformanceTotOcts
         Counter64,
      pr1645v2Lan2FGUVlanInPQsH2PerformanceDirTxOcts
         Counter64,
      pr1645v2Lan2FGUVlanInPQsH2PerformanceQdOcts
         Counter64,
      pr1645v2Lan2FGUVlanInPQsH2PerformanceDropOcts
         Counter64,
      pr1645v2Lan2FGUVlanInPQsH2PerformanceRDropOcts
         Counter64,
      pr1645v2Lan2FGUVlanInPQsH2PerformanceCirTxOcts
         Counter64,
      pr1645v2Lan2FGUVlanInPQsH2PerformanceEirTxOcts
         Counter64,
      pr1645v2Lan2FGUVlanInPQsH2PerformanceViolTxOcts
         Counter64,
      pr1645v2Lan2FGUVlanInPQsH2PerformanceBandwidth
         Integer32
      }

pr1645v2Lan2FGUVlanInPQsH2PerformanceTableIx OBJECT-TYPE
   SYNTAX      TableIndex
   MAX-ACCESS  not-accessible
   STATUS      current
   DESCRIPTION
      ""
   ::= {pr1645v2Lan2FGUVlanInPQsH2PerformanceEntry 11}

pr1645v2Lan2FGUVlanInPQsH2PerformanceSysUpTime OBJECT-TYPE
   SYNTAX      TimeTicks
   MAX-ACCESS  read-only
   STATUS      current
   DESCRIPTION
      "Path: ethernet2.performance.vlan.inPriorityQueues.h2Performance.sysUpTime

       Time in centi-second."
   ::= {pr1645v2Lan2FGUVlanInPQsH2PerformanceEntry 16777216}

pr1645v2Lan2FGUVlanInPQsH2PerformanceTotPkts OBJECT-TYPE
   SYNTAX      Counter64
   MAX-ACCESS  read-only
   STATUS      current
   DESCRIPTION
      "Path: ethernet2.performance.vlan.inPriorityQueues.h2Performance.totalPkts

       64 bit unsigned wrappable counter."
   ::= {pr1645v2Lan2FGUVlanInPQsH2PerformanceEntry 234881024}

pr1645v2Lan2FGUVlanInPQsH2PerformanceDirTxPkts OBJECT-TYPE
   SYNTAX      Counter64
   MAX-ACCESS  read-only
   STATUS      current
   DESCRIPTION
      "Path: ethernet2.performance.vlan.inPriorityQueues.h2Performance.directTxPkts

       64 bit unsigned wrappable counter."
   ::= {pr1645v2Lan2FGUVlanInPQsH2PerformanceEntry 33554432}

pr1645v2Lan2FGUVlanInPQsH2PerformanceQdPkts OBJECT-TYPE
   SYNTAX      Counter64
   MAX-ACCESS  read-only
   STATUS      current
   DESCRIPTION
      "Path: ethernet2.performance.vlan.inPriorityQueues.h2Performance.queuedPkts

       64 bit unsigned wrappable counter."
   ::= {pr1645v2Lan2FGUVlanInPQsH2PerformanceEntry 50331648}

pr1645v2Lan2FGUVlanInPQsH2PerformanceDropPkts OBJECT-TYPE
   SYNTAX      Counter64
   MAX-ACCESS  read-only
   STATUS      current
   DESCRIPTION
      "Path: ethernet2.performance.vlan.inPriorityQueues.h2Performance.droppedPkts

       64 bit unsigned wrappable counter."
   ::= {pr1645v2Lan2FGUVlanInPQsH2PerformanceEntry 67108864}

pr1645v2Lan2FGUVlanInPQsH2PerformanceRDropPkts OBJECT-TYPE
   SYNTAX      Counter64
   MAX-ACCESS  read-only
   STATUS      current
   DESCRIPTION
      "Path: ethernet2.performance.vlan.inPriorityQueues.h2Performance.redDroppedPkts

       64 bit unsigned wrappable counter."
   ::= {pr1645v2Lan2FGUVlanInPQsH2PerformanceEntry 201326592}

pr1645v2Lan2FGUVlanInPQsH2PerformanceCirTxPkts OBJECT-TYPE
   SYNTAX      Counter64
   MAX-ACCESS  read-only
   STATUS      current
   DESCRIPTION
      "Path: ethernet2.performance.vlan.inPriorityQueues.h2Performance.cirTxPkts

       64 bit unsigned wrappable counter."
   ::= {pr1645v2Lan2FGUVlanInPQsH2PerformanceEntry 83886080}

pr1645v2Lan2FGUVlanInPQsH2PerformanceEirTxPkts OBJECT-TYPE
   SYNTAX      Counter64
   MAX-ACCESS  read-only
   STATUS      current
   DESCRIPTION
      "Path: ethernet2.performance.vlan.inPriorityQueues.h2Performance.eirTxPkts

       64 bit unsigned wrappable counter."
   ::= {pr1645v2Lan2FGUVlanInPQsH2PerformanceEntry 100663296}

pr1645v2Lan2FGUVlanInPQsH2PerformanceViolTxPkts OBJECT-TYPE
   SYNTAX      Counter64
   MAX-ACCESS  read-only
   STATUS      current
   DESCRIPTION
      "Path: ethernet2.performance.vlan.inPriorityQueues.h2Performance.violateTxPkts

       64 bit unsigned wrappable counter."
   ::= {pr1645v2Lan2FGUVlanInPQsH2PerformanceEntry 301989888}

pr1645v2Lan2FGUVlanInPQsH2PerformanceTotOcts OBJECT-TYPE
   SYNTAX      Counter64
   MAX-ACCESS  read-only
   STATUS      current
   DESCRIPTION
      "Path: ethernet2.performance.vlan.inPriorityQueues.h2Performance.totalOctets

       64 bit unsigned wrappable counter."
   ::= {pr1645v2Lan2FGUVlanInPQsH2PerformanceEntry 251658240}

pr1645v2Lan2FGUVlanInPQsH2PerformanceDirTxOcts OBJECT-TYPE
   SYNTAX      Counter64
   MAX-ACCESS  read-only
   STATUS      current
   DESCRIPTION
      "Path: ethernet2.performance.vlan.inPriorityQueues.h2Performance.directTxOctets

       64 bit unsigned wrappable counter."
   ::= {pr1645v2Lan2FGUVlanInPQsH2PerformanceEntry 117440512}

pr1645v2Lan2FGUVlanInPQsH2PerformanceQdOcts OBJECT-TYPE
   SYNTAX      Counter64
   MAX-ACCESS  read-only
   STATUS      current
   DESCRIPTION
      "Path: ethernet2.performance.vlan.inPriorityQueues.h2Performance.queuedOctets

       64 bit unsigned wrappable counter."
   ::= {pr1645v2Lan2FGUVlanInPQsH2PerformanceEntry 134217728}

pr1645v2Lan2FGUVlanInPQsH2PerformanceDropOcts OBJECT-TYPE
   SYNTAX      Counter64
   MAX-ACCESS  read-only
   STATUS      current
   DESCRIPTION
      "Path: ethernet2.performance.vlan.inPriorityQueues.h2Performance.droppedOctets

       64 bit unsigned wrappable counter."
   ::= {pr1645v2Lan2FGUVlanInPQsH2PerformanceEntry 150994944}

pr1645v2Lan2FGUVlanInPQsH2PerformanceRDropOcts OBJECT-TYPE
   SYNTAX      Counter64
   MAX-ACCESS  read-only
   STATUS      current
   DESCRIPTION
      "Path: ethernet2.performance.vlan.inPriorityQueues.h2Performance.redDroppedOctets

       64 bit unsigned wrappable counter."
   ::= {pr1645v2Lan2FGUVlanInPQsH2PerformanceEntry 218103808}

pr1645v2Lan2FGUVlanInPQsH2PerformanceCirTxOcts OBJECT-TYPE
   SYNTAX      Counter64
   MAX-ACCESS  read-only
   STATUS      current
   DESCRIPTION
      "Path: ethernet2.performance.vlan.inPriorityQueues.h2Performance.cirTxOctets

       64 bit unsigned wrappable counter."
   ::= {pr1645v2Lan2FGUVlanInPQsH2PerformanceEntry 167772160}

pr1645v2Lan2FGUVlanInPQsH2PerformanceEirTxOcts OBJECT-TYPE
   SYNTAX      Counter64
   MAX-ACCESS  read-only
   STATUS      current
   DESCRIPTION
      "Path: ethernet2.performance.vlan.inPriorityQueues.h2Performance.eirTxOctets

       64 bit unsigned wrappable counter."
   ::= {pr1645v2Lan2FGUVlanInPQsH2PerformanceEntry 184549376}

pr1645v2Lan2FGUVlanInPQsH2PerformanceViolTxOcts OBJECT-TYPE
   SYNTAX      Counter64
   MAX-ACCESS  read-only
   STATUS      current
   DESCRIPTION
      "Path: ethernet2.performance.vlan.inPriorityQueues.h2Performance.violateTxOctets

       64 bit unsigned wrappable counter."
   ::= {pr1645v2Lan2FGUVlanInPQsH2PerformanceEntry 318767104}

pr1645v2Lan2FGUVlanInPQsH2PerformanceBandwidth OBJECT-TYPE
   SYNTAX      Integer32
   MAX-ACCESS  read-only
   STATUS      current
   DESCRIPTION
      "Path: ethernet2.performance.vlan.inPriorityQueues.h2Performance.bandwidth

       unit name = bps
       formula = 8 * ; 8 /"
   ::= {pr1645v2Lan2FGUVlanInPQsH2PerformanceEntry 268435456}

pr1645v2Lan2FGUVlanInPQsH24Performance OBJECT-TYPE
   SYNTAX      SEQUENCE OF Pr1645v2Lan2FGUVlanInPQsH24PerformanceEntry
   MAX-ACCESS  not-accessible
   STATUS      current
   DESCRIPTION
      ""
   ::= {pr1645v2Lan2FGUVlan 101056512}

pr1645v2Lan2FGUVlanInPQsH24PerformanceEntry OBJECT-TYPE
   SYNTAX      Pr1645v2Lan2FGUVlanInPQsH24PerformanceEntry
   MAX-ACCESS  not-accessible
   STATUS      current
   DESCRIPTION
      ""
   INDEX      { pr1645v2Lan2FGUVlanTableIx,
                pr1645v2Lan2FGUVlanInPQsTableIx,
                pr1645v2Lan2FGUVlanInPQsH24PerformanceTableIx }
   ::= {pr1645v2Lan2FGUVlanInPQsH24Performance 1}

Pr1645v2Lan2FGUVlanInPQsH24PerformanceEntry ::=
   SEQUENCE
      {
      pr1645v2Lan2FGUVlanInPQsH24PerformanceTableIx
         TableIndex,
      pr1645v2Lan2FGUVlanInPQsH24PerformanceSysUpTime
         TimeTicks,
      pr1645v2Lan2FGUVlanInPQsH24PerformanceTotPkts
         Counter64,
      pr1645v2Lan2FGUVlanInPQsH24PerformanceDirTxPkts
         Counter64,
      pr1645v2Lan2FGUVlanInPQsH24PerformanceQdPkts
         Counter64,
      pr1645v2Lan2FGUVlanInPQsH24PerformanceDropPkts
         Counter64,
      pr1645v2Lan2FGUVlanInPQsH24PerformanceRDropPkts
         Counter64,
      pr1645v2Lan2FGUVlanInPQsH24PerformanceCirTxPkts
         Counter64,
      pr1645v2Lan2FGUVlanInPQsH24PerformanceEirTxPkts
         Counter64,
      pr1645v2Lan2FGUVlanInPQsH24PerformanceViolTxPkts
         Counter64,
      pr1645v2Lan2FGUVlanInPQsH24PerformanceTotOcts
         Counter64,
      pr1645v2Lan2FGUVlanInPQsH24PerformanceDirTxOcts
         Counter64,
      pr1645v2Lan2FGUVlanInPQsH24PerformanceQdOcts
         Counter64,
      pr1645v2Lan2FGUVlanInPQsH24PerformanceDropOcts
         Counter64,
      pr1645v2Lan2FGUVlanInPQsH24PerformanceRDropOcts
         Counter64,
      pr1645v2Lan2FGUVlanInPQsH24PerformanceCirTxOcts
         Counter64,
      pr1645v2Lan2FGUVlanInPQsH24PerformanceEirTxOcts
         Counter64,
      pr1645v2Lan2FGUVlanInPQsH24PerformanceViolTxOcts
         Counter64,
      pr1645v2Lan2FGUVlanInPQsH24PerformanceBandwidth
         Integer32
      }

pr1645v2Lan2FGUVlanInPQsH24PerformanceTableIx OBJECT-TYPE
   SYNTAX      TableIndex
   MAX-ACCESS  not-accessible
   STATUS      current
   DESCRIPTION
      ""
   ::= {pr1645v2Lan2FGUVlanInPQsH24PerformanceEntry 11}

pr1645v2Lan2FGUVlanInPQsH24PerformanceSysUpTime OBJECT-TYPE
   SYNTAX      TimeTicks
   MAX-ACCESS  read-only
   STATUS      current
   DESCRIPTION
      "Path: ethernet2.performance.vlan.inPriorityQueues.h24Performance.sysUpTime

       Time in centi-second."
   ::= {pr1645v2Lan2FGUVlanInPQsH24PerformanceEntry 16777216}

pr1645v2Lan2FGUVlanInPQsH24PerformanceTotPkts OBJECT-TYPE
   SYNTAX      Counter64
   MAX-ACCESS  read-only
   STATUS      current
   DESCRIPTION
      "Path: ethernet2.performance.vlan.inPriorityQueues.h24Performance.totalPkts

       64 bit unsigned wrappable counter."
   ::= {pr1645v2Lan2FGUVlanInPQsH24PerformanceEntry 234881024}

pr1645v2Lan2FGUVlanInPQsH24PerformanceDirTxPkts OBJECT-TYPE
   SYNTAX      Counter64
   MAX-ACCESS  read-only
   STATUS      current
   DESCRIPTION
      "Path: ethernet2.performance.vlan.inPriorityQueues.h24Performance.directTxPkts

       64 bit unsigned wrappable counter."
   ::= {pr1645v2Lan2FGUVlanInPQsH24PerformanceEntry 33554432}

pr1645v2Lan2FGUVlanInPQsH24PerformanceQdPkts OBJECT-TYPE
   SYNTAX      Counter64
   MAX-ACCESS  read-only
   STATUS      current
   DESCRIPTION
      "Path: ethernet2.performance.vlan.inPriorityQueues.h24Performance.queuedPkts

       64 bit unsigned wrappable counter."
   ::= {pr1645v2Lan2FGUVlanInPQsH24PerformanceEntry 50331648}

pr1645v2Lan2FGUVlanInPQsH24PerformanceDropPkts OBJECT-TYPE
   SYNTAX      Counter64
   MAX-ACCESS  read-only
   STATUS      current
   DESCRIPTION
      "Path: ethernet2.performance.vlan.inPriorityQueues.h24Performance.droppedPkts

       64 bit unsigned wrappable counter."
   ::= {pr1645v2Lan2FGUVlanInPQsH24PerformanceEntry 67108864}

pr1645v2Lan2FGUVlanInPQsH24PerformanceRDropPkts OBJECT-TYPE
   SYNTAX      Counter64
   MAX-ACCESS  read-only
   STATUS      current
   DESCRIPTION
      "Path: ethernet2.performance.vlan.inPriorityQueues.h24Performance.redDroppedPkts

       64 bit unsigned wrappable counter."
   ::= {pr1645v2Lan2FGUVlanInPQsH24PerformanceEntry 201326592}

pr1645v2Lan2FGUVlanInPQsH24PerformanceCirTxPkts OBJECT-TYPE
   SYNTAX      Counter64
   MAX-ACCESS  read-only
   STATUS      current
   DESCRIPTION
      "Path: ethernet2.performance.vlan.inPriorityQueues.h24Performance.cirTxPkts

       64 bit unsigned wrappable counter."
   ::= {pr1645v2Lan2FGUVlanInPQsH24PerformanceEntry 83886080}

pr1645v2Lan2FGUVlanInPQsH24PerformanceEirTxPkts OBJECT-TYPE
   SYNTAX      Counter64
   MAX-ACCESS  read-only
   STATUS      current
   DESCRIPTION
      "Path: ethernet2.performance.vlan.inPriorityQueues.h24Performance.eirTxPkts

       64 bit unsigned wrappable counter."
   ::= {pr1645v2Lan2FGUVlanInPQsH24PerformanceEntry 100663296}

pr1645v2Lan2FGUVlanInPQsH24PerformanceViolTxPkts OBJECT-TYPE
   SYNTAX      Counter64
   MAX-ACCESS  read-only
   STATUS      current
   DESCRIPTION
      "Path: ethernet2.performance.vlan.inPriorityQueues.h24Performance.violateTxPkts

       64 bit unsigned wrappable counter."
   ::= {pr1645v2Lan2FGUVlanInPQsH24PerformanceEntry 301989888}

pr1645v2Lan2FGUVlanInPQsH24PerformanceTotOcts OBJECT-TYPE
   SYNTAX      Counter64
   MAX-ACCESS  read-only
   STATUS      current
   DESCRIPTION
      "Path: ethernet2.performance.vlan.inPriorityQueues.h24Performance.totalOctets

       64 bit unsigned wrappable counter."
   ::= {pr1645v2Lan2FGUVlanInPQsH24PerformanceEntry 251658240}

pr1645v2Lan2FGUVlanInPQsH24PerformanceDirTxOcts OBJECT-TYPE
   SYNTAX      Counter64
   MAX-ACCESS  read-only
   STATUS      current
   DESCRIPTION
      "Path: ethernet2.performance.vlan.inPriorityQueues.h24Performance.directTxOctets

       64 bit unsigned wrappable counter."
   ::= {pr1645v2Lan2FGUVlanInPQsH24PerformanceEntry 117440512}

pr1645v2Lan2FGUVlanInPQsH24PerformanceQdOcts OBJECT-TYPE
   SYNTAX      Counter64
   MAX-ACCESS  read-only
   STATUS      current
   DESCRIPTION
      "Path: ethernet2.performance.vlan.inPriorityQueues.h24Performance.queuedOctets

       64 bit unsigned wrappable counter."
   ::= {pr1645v2Lan2FGUVlanInPQsH24PerformanceEntry 134217728}

pr1645v2Lan2FGUVlanInPQsH24PerformanceDropOcts OBJECT-TYPE
   SYNTAX      Counter64
   MAX-ACCESS  read-only
   STATUS      current
   DESCRIPTION
      "Path: ethernet2.performance.vlan.inPriorityQueues.h24Performance.droppedOctets

       64 bit unsigned wrappable counter."
   ::= {pr1645v2Lan2FGUVlanInPQsH24PerformanceEntry 150994944}

pr1645v2Lan2FGUVlanInPQsH24PerformanceRDropOcts OBJECT-TYPE
   SYNTAX      Counter64
   MAX-ACCESS  read-only
   STATUS      current
   DESCRIPTION
      "Path: ethernet2.performance.vlan.inPriorityQueues.h24Performance.redDroppedOctets

       64 bit unsigned wrappable counter."
   ::= {pr1645v2Lan2FGUVlanInPQsH24PerformanceEntry 218103808}

pr1645v2Lan2FGUVlanInPQsH24PerformanceCirTxOcts OBJECT-TYPE
   SYNTAX      Counter64
   MAX-ACCESS  read-only
   STATUS      current
   DESCRIPTION
      "Path: ethernet2.performance.vlan.inPriorityQueues.h24Performance.cirTxOctets

       64 bit unsigned wrappable counter."
   ::= {pr1645v2Lan2FGUVlanInPQsH24PerformanceEntry 167772160}

pr1645v2Lan2FGUVlanInPQsH24PerformanceEirTxOcts OBJECT-TYPE
   SYNTAX      Counter64
   MAX-ACCESS  read-only
   STATUS      current
   DESCRIPTION
      "Path: ethernet2.performance.vlan.inPriorityQueues.h24Performance.eirTxOctets

       64 bit unsigned wrappable counter."
   ::= {pr1645v2Lan2FGUVlanInPQsH24PerformanceEntry 184549376}

pr1645v2Lan2FGUVlanInPQsH24PerformanceViolTxOcts OBJECT-TYPE
   SYNTAX      Counter64
   MAX-ACCESS  read-only
   STATUS      current
   DESCRIPTION
      "Path: ethernet2.performance.vlan.inPriorityQueues.h24Performance.violateTxOctets

       64 bit unsigned wrappable counter."
   ::= {pr1645v2Lan2FGUVlanInPQsH24PerformanceEntry 318767104}

pr1645v2Lan2FGUVlanInPQsH24PerformanceBandwidth OBJECT-TYPE
   SYNTAX      Integer32
   MAX-ACCESS  read-only
   STATUS      current
   DESCRIPTION
      "Path: ethernet2.performance.vlan.inPriorityQueues.h24Performance.bandwidth

       unit name = bps
       formula = 8 * ; 8 /"
   ::= {pr1645v2Lan2FGUVlanInPQsH24PerformanceEntry 268435456}

pr1645v2Lan2FGUVlanInPQsD7Performance OBJECT-TYPE
   SYNTAX      SEQUENCE OF Pr1645v2Lan2FGUVlanInPQsD7PerformanceEntry
   MAX-ACCESS  not-accessible
   STATUS      current
   DESCRIPTION
      ""
   ::= {pr1645v2Lan2FGUVlan 101122048}

pr1645v2Lan2FGUVlanInPQsD7PerformanceEntry OBJECT-TYPE
   SYNTAX      Pr1645v2Lan2FGUVlanInPQsD7PerformanceEntry
   MAX-ACCESS  not-accessible
   STATUS      current
   DESCRIPTION
      ""
   INDEX      { pr1645v2Lan2FGUVlanTableIx,
                pr1645v2Lan2FGUVlanInPQsTableIx,
                pr1645v2Lan2FGUVlanInPQsD7PerformanceTableIx }
   ::= {pr1645v2Lan2FGUVlanInPQsD7Performance 1}

Pr1645v2Lan2FGUVlanInPQsD7PerformanceEntry ::=
   SEQUENCE
      {
      pr1645v2Lan2FGUVlanInPQsD7PerformanceTableIx
         TableIndex,
      pr1645v2Lan2FGUVlanInPQsD7PerformanceSysUpTime
         TimeTicks,
      pr1645v2Lan2FGUVlanInPQsD7PerformanceTotPkts
         Counter64,
      pr1645v2Lan2FGUVlanInPQsD7PerformanceDirTxPkts
         Counter64,
      pr1645v2Lan2FGUVlanInPQsD7PerformanceQdPkts
         Counter64,
      pr1645v2Lan2FGUVlanInPQsD7PerformanceDropPkts
         Counter64,
      pr1645v2Lan2FGUVlanInPQsD7PerformanceRDropPkts
         Counter64,
      pr1645v2Lan2FGUVlanInPQsD7PerformanceCirTxPkts
         Counter64,
      pr1645v2Lan2FGUVlanInPQsD7PerformanceEirTxPkts
         Counter64,
      pr1645v2Lan2FGUVlanInPQsD7PerformanceViolTxPkts
         Counter64,
      pr1645v2Lan2FGUVlanInPQsD7PerformanceTotOcts
         Counter64,
      pr1645v2Lan2FGUVlanInPQsD7PerformanceDirTxOcts
         Counter64,
      pr1645v2Lan2FGUVlanInPQsD7PerformanceQdOcts
         Counter64,
      pr1645v2Lan2FGUVlanInPQsD7PerformanceDropOcts
         Counter64,
      pr1645v2Lan2FGUVlanInPQsD7PerformanceRDropOcts
         Counter64,
      pr1645v2Lan2FGUVlanInPQsD7PerformanceCirTxOcts
         Counter64,
      pr1645v2Lan2FGUVlanInPQsD7PerformanceEirTxOcts
         Counter64,
      pr1645v2Lan2FGUVlanInPQsD7PerformanceViolTxOcts
         Counter64,
      pr1645v2Lan2FGUVlanInPQsD7PerformanceBandwidth
         Integer32
      }

pr1645v2Lan2FGUVlanInPQsD7PerformanceTableIx OBJECT-TYPE
   SYNTAX      TableIndex
   MAX-ACCESS  not-accessible
   STATUS      current
   DESCRIPTION
      ""
   ::= {pr1645v2Lan2FGUVlanInPQsD7PerformanceEntry 11}

pr1645v2Lan2FGUVlanInPQsD7PerformanceSysUpTime OBJECT-TYPE
   SYNTAX      TimeTicks
   MAX-ACCESS  read-only
   STATUS      current
   DESCRIPTION
      "Path: ethernet2.performance.vlan.inPriorityQueues.d7Performance.sysUpTime

       Time in centi-second."
   ::= {pr1645v2Lan2FGUVlanInPQsD7PerformanceEntry 16777216}

pr1645v2Lan2FGUVlanInPQsD7PerformanceTotPkts OBJECT-TYPE
   SYNTAX      Counter64
   MAX-ACCESS  read-only
   STATUS      current
   DESCRIPTION
      "Path: ethernet2.performance.vlan.inPriorityQueues.d7Performance.totalPkts

       64 bit unsigned wrappable counter."
   ::= {pr1645v2Lan2FGUVlanInPQsD7PerformanceEntry 234881024}

pr1645v2Lan2FGUVlanInPQsD7PerformanceDirTxPkts OBJECT-TYPE
   SYNTAX      Counter64
   MAX-ACCESS  read-only
   STATUS      current
   DESCRIPTION
      "Path: ethernet2.performance.vlan.inPriorityQueues.d7Performance.directTxPkts

       64 bit unsigned wrappable counter."
   ::= {pr1645v2Lan2FGUVlanInPQsD7PerformanceEntry 33554432}

pr1645v2Lan2FGUVlanInPQsD7PerformanceQdPkts OBJECT-TYPE
   SYNTAX      Counter64
   MAX-ACCESS  read-only
   STATUS      current
   DESCRIPTION
      "Path: ethernet2.performance.vlan.inPriorityQueues.d7Performance.queuedPkts

       64 bit unsigned wrappable counter."
   ::= {pr1645v2Lan2FGUVlanInPQsD7PerformanceEntry 50331648}

pr1645v2Lan2FGUVlanInPQsD7PerformanceDropPkts OBJECT-TYPE
   SYNTAX      Counter64
   MAX-ACCESS  read-only
   STATUS      current
   DESCRIPTION
      "Path: ethernet2.performance.vlan.inPriorityQueues.d7Performance.droppedPkts

       64 bit unsigned wrappable counter."
   ::= {pr1645v2Lan2FGUVlanInPQsD7PerformanceEntry 67108864}

pr1645v2Lan2FGUVlanInPQsD7PerformanceRDropPkts OBJECT-TYPE
   SYNTAX      Counter64
   MAX-ACCESS  read-only
   STATUS      current
   DESCRIPTION
      "Path: ethernet2.performance.vlan.inPriorityQueues.d7Performance.redDroppedPkts

       64 bit unsigned wrappable counter."
   ::= {pr1645v2Lan2FGUVlanInPQsD7PerformanceEntry 201326592}

pr1645v2Lan2FGUVlanInPQsD7PerformanceCirTxPkts OBJECT-TYPE
   SYNTAX      Counter64
   MAX-ACCESS  read-only
   STATUS      current
   DESCRIPTION
      "Path: ethernet2.performance.vlan.inPriorityQueues.d7Performance.cirTxPkts

       64 bit unsigned wrappable counter."
   ::= {pr1645v2Lan2FGUVlanInPQsD7PerformanceEntry 83886080}

pr1645v2Lan2FGUVlanInPQsD7PerformanceEirTxPkts OBJECT-TYPE
   SYNTAX      Counter64
   MAX-ACCESS  read-only
   STATUS      current
   DESCRIPTION
      "Path: ethernet2.performance.vlan.inPriorityQueues.d7Performance.eirTxPkts

       64 bit unsigned wrappable counter."
   ::= {pr1645v2Lan2FGUVlanInPQsD7PerformanceEntry 100663296}

pr1645v2Lan2FGUVlanInPQsD7PerformanceViolTxPkts OBJECT-TYPE
   SYNTAX      Counter64
   MAX-ACCESS  read-only
   STATUS      current
   DESCRIPTION
      "Path: ethernet2.performance.vlan.inPriorityQueues.d7Performance.violateTxPkts

       64 bit unsigned wrappable counter."
   ::= {pr1645v2Lan2FGUVlanInPQsD7PerformanceEntry 301989888}

pr1645v2Lan2FGUVlanInPQsD7PerformanceTotOcts OBJECT-TYPE
   SYNTAX      Counter64
   MAX-ACCESS  read-only
   STATUS      current
   DESCRIPTION
      "Path: ethernet2.performance.vlan.inPriorityQueues.d7Performance.totalOctets

       64 bit unsigned wrappable counter."
   ::= {pr1645v2Lan2FGUVlanInPQsD7PerformanceEntry 251658240}

pr1645v2Lan2FGUVlanInPQsD7PerformanceDirTxOcts OBJECT-TYPE
   SYNTAX      Counter64
   MAX-ACCESS  read-only
   STATUS      current
   DESCRIPTION
      "Path: ethernet2.performance.vlan.inPriorityQueues.d7Performance.directTxOctets

       64 bit unsigned wrappable counter."
   ::= {pr1645v2Lan2FGUVlanInPQsD7PerformanceEntry 117440512}

pr1645v2Lan2FGUVlanInPQsD7PerformanceQdOcts OBJECT-TYPE
   SYNTAX      Counter64
   MAX-ACCESS  read-only
   STATUS      current
   DESCRIPTION
      "Path: ethernet2.performance.vlan.inPriorityQueues.d7Performance.queuedOctets

       64 bit unsigned wrappable counter."
   ::= {pr1645v2Lan2FGUVlanInPQsD7PerformanceEntry 134217728}

pr1645v2Lan2FGUVlanInPQsD7PerformanceDropOcts OBJECT-TYPE
   SYNTAX      Counter64
   MAX-ACCESS  read-only
   STATUS      current
   DESCRIPTION
      "Path: ethernet2.performance.vlan.inPriorityQueues.d7Performance.droppedOctets

       64 bit unsigned wrappable counter."
   ::= {pr1645v2Lan2FGUVlanInPQsD7PerformanceEntry 150994944}

pr1645v2Lan2FGUVlanInPQsD7PerformanceRDropOcts OBJECT-TYPE
   SYNTAX      Counter64
   MAX-ACCESS  read-only
   STATUS      current
   DESCRIPTION
      "Path: ethernet2.performance.vlan.inPriorityQueues.d7Performance.redDroppedOctets

       64 bit unsigned wrappable counter."
   ::= {pr1645v2Lan2FGUVlanInPQsD7PerformanceEntry 218103808}

pr1645v2Lan2FGUVlanInPQsD7PerformanceCirTxOcts OBJECT-TYPE
   SYNTAX      Counter64
   MAX-ACCESS  read-only
   STATUS      current
   DESCRIPTION
      "Path: ethernet2.performance.vlan.inPriorityQueues.d7Performance.cirTxOctets

       64 bit unsigned wrappable counter."
   ::= {pr1645v2Lan2FGUVlanInPQsD7PerformanceEntry 167772160}

pr1645v2Lan2FGUVlanInPQsD7PerformanceEirTxOcts OBJECT-TYPE
   SYNTAX      Counter64
   MAX-ACCESS  read-only
   STATUS      current
   DESCRIPTION
      "Path: ethernet2.performance.vlan.inPriorityQueues.d7Performance.eirTxOctets

       64 bit unsigned wrappable counter."
   ::= {pr1645v2Lan2FGUVlanInPQsD7PerformanceEntry 184549376}

pr1645v2Lan2FGUVlanInPQsD7PerformanceViolTxOcts OBJECT-TYPE
   SYNTAX      Counter64
   MAX-ACCESS  read-only
   STATUS      current
   DESCRIPTION
      "Path: ethernet2.performance.vlan.inPriorityQueues.d7Performance.violateTxOctets

       64 bit unsigned wrappable counter."
   ::= {pr1645v2Lan2FGUVlanInPQsD7PerformanceEntry 318767104}

pr1645v2Lan2FGUVlanInPQsD7PerformanceBandwidth OBJECT-TYPE
   SYNTAX      Integer32
   MAX-ACCESS  read-only
   STATUS      current
   DESCRIPTION
      "Path: ethernet2.performance.vlan.inPriorityQueues.d7Performance.bandwidth

       unit name = bps
       formula = 8 * ; 8 /"
   ::= {pr1645v2Lan2FGUVlanInPQsD7PerformanceEntry 268435456}

pr1645v2Lan2FGUVlanOutPQs OBJECT-TYPE
   SYNTAX      SEQUENCE OF Pr1645v2Lan2FGUVlanOutPQsEntry
   MAX-ACCESS  not-accessible
   STATUS      current
   DESCRIPTION
      ""
   ::= {pr1645v2Lan2FGUVlan 83886080}

pr1645v2Lan2FGUVlanOutPQsEntry OBJECT-TYPE
   SYNTAX      Pr1645v2Lan2FGUVlanOutPQsEntry
   MAX-ACCESS  not-accessible
   STATUS      current
   DESCRIPTION
      ""
   INDEX      { pr1645v2Lan2FGUVlanTableIx,
                pr1645v2Lan2FGUVlanOutPQsTableIx }
   ::= {pr1645v2Lan2FGUVlanOutPQs 1}

Pr1645v2Lan2FGUVlanOutPQsEntry ::=
   SEQUENCE
      {
      pr1645v2Lan2FGUVlanOutPQsTableIx
         TableIndex,
      pr1645v2Lan2FGUVlanOutPQsName
         INTEGER,
      pr1645v2Lan2FGUVlanOutPQsLength
         Integer32,
      pr1645v2Lan2FGUVlanOutPQsOctetLength
         Integer32,
      pr1645v2Lan2FGUVlanOutPQsRedLength
         Integer32,
      pr1645v2Lan2FGUVlanOutPQsPacketsTotal
         Counter64,
      pr1645v2Lan2FGUVlanOutPQsPacketsDirectTx
         Counter64,
      pr1645v2Lan2FGUVlanOutPQsPacketsQueued
         Counter64,
      pr1645v2Lan2FGUVlanOutPQsPacketsDropped
         Counter64,
      pr1645v2Lan2FGUVlanOutPQsPacketsRedDropped
         Counter64,
      pr1645v2Lan2FGUVlanOutPQsPacketsCirTx
         Counter64,
      pr1645v2Lan2FGUVlanOutPQsPacketsEirTx
         Counter64,
      pr1645v2Lan2FGUVlanOutPQsPacketsViolateTx
         Counter64,
      pr1645v2Lan2FGUVlanOutPQsOctetsTotal
         Counter64,
      pr1645v2Lan2FGUVlanOutPQsOctetsDirectTx
         Counter64,
      pr1645v2Lan2FGUVlanOutPQsOctetsQueued
         Counter64,
      pr1645v2Lan2FGUVlanOutPQsOctetsDropped
         Counter64,
      pr1645v2Lan2FGUVlanOutPQsOctetsRedDropped
         Counter64,
      pr1645v2Lan2FGUVlanOutPQsOctetsCirTx
         Counter64,
      pr1645v2Lan2FGUVlanOutPQsOctetsEirTx
         Counter64,
      pr1645v2Lan2FGUVlanOutPQsOctetsViolateTx
         Counter64,
      pr1645v2Lan2FGUVlanOutPQsOctetsBandwidth15sec
         Integer32,
      pr1645v2Lan2FGUVlanOutPQsOctetsBandwidth30sec
         Integer32,
      pr1645v2Lan2FGUVlanOutPQsOctetsBandwidth1min
         Integer32,
      pr1645v2Lan2FGUVlanOutPQsOctetsBandwidth2min
         Integer32,
      pr1645v2Lan2FGUVlanOutPQsOctetsBandwidth5min
         Integer32
      }

pr1645v2Lan2FGUVlanOutPQsTableIx OBJECT-TYPE
   SYNTAX      TableIndex
   MAX-ACCESS  not-accessible
   STATUS      current
   DESCRIPTION
      ""
   ::= {pr1645v2Lan2FGUVlanOutPQsEntry 11}

pr1645v2Lan2FGUVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGUVlanOutPQsEntry 16777216}

pr1645v2Lan2FGUVlanOutPQsLength OBJECT-TYPE
   SYNTAX      Integer32
   MAX-ACCESS  read-only
   STATUS      current
   DESCRIPTION
      "Path: ethernet2.performance.vlan.outPriorityQueues.length"
   ::= {pr1645v2Lan2FGUVlanOutPQsEntry 33554432}

pr1645v2Lan2FGUVlanOutPQsOctetLength OBJECT-TYPE
   SYNTAX      Integer32
   MAX-ACCESS  read-only
   STATUS      current
   DESCRIPTION
      "Path: ethernet2.performance.vlan.outPriorityQueues.octetLength"
   ::= {pr1645v2Lan2FGUVlanOutPQsEntry 150994944}

pr1645v2Lan2FGUVlanOutPQsRedLength OBJECT-TYPE
   SYNTAX      Integer32
   MAX-ACCESS  read-only
   STATUS      current
   DESCRIPTION
      "Path: ethernet2.performance.vlan.outPriorityQueues.redLength"
   ::= {pr1645v2Lan2FGUVlanOutPQsEntry 134217728}

pr1645v2Lan2FGUVlanOutPQsPacketsTotal OBJECT-TYPE
   SYNTAX      Counter64
   MAX-ACCESS  read-only
   STATUS      current
   DESCRIPTION
      "Path: ethernet2.performance.vlan.outPriorityQueues.packets.total

       64 bit unsigned wrappable counter."
   ::= {pr1645v2Lan2FGUVlanOutPQsEntry 50790400}

pr1645v2Lan2FGUVlanOutPQsPacketsDirectTx OBJECT-TYPE
   SYNTAX      Counter64
   MAX-ACCESS  read-only
   STATUS      current
   DESCRIPTION
      "Path: ethernet2.performance.vlan.outPriorityQueues.packets.directTx

       64 bit unsigned wrappable counter."
   ::= {pr1645v2Lan2FGUVlanOutPQsEntry 50397184}

pr1645v2Lan2FGUVlanOutPQsPacketsQueued OBJECT-TYPE
   SYNTAX      Counter64
   MAX-ACCESS  read-only
   STATUS      current
   DESCRIPTION
      "Path: ethernet2.performance.vlan.outPriorityQueues.packets.queued

       64 bit unsigned wrappable counter."
   ::= {pr1645v2Lan2FGUVlanOutPQsEntry 50462720}

pr1645v2Lan2FGUVlanOutPQsPacketsDropped OBJECT-TYPE
   SYNTAX      Counter64
   MAX-ACCESS  read-only
   STATUS      current
   DESCRIPTION
      "Path: ethernet2.performance.vlan.outPriorityQueues.packets.dropped

       64 bit unsigned wrappable counter."
   ::= {pr1645v2Lan2FGUVlanOutPQsEntry 50528256}

pr1645v2Lan2FGUVlanOutPQsPacketsRedDropped OBJECT-TYPE
   SYNTAX      Counter64
   MAX-ACCESS  read-only
   STATUS      current
   DESCRIPTION
      "Path: ethernet2.performance.vlan.outPriorityQueues.packets.redDropped

       64 bit unsigned wrappable counter."
   ::= {pr1645v2Lan2FGUVlanOutPQsEntry 50724864}

pr1645v2Lan2FGUVlanOutPQsPacketsCirTx OBJECT-TYPE
   SYNTAX      Counter64
   MAX-ACCESS  read-only
   STATUS      current
   DESCRIPTION
      "Path: ethernet2.performance.vlan.outPriorityQueues.packets.cirTx

       64 bit unsigned wrappable counter."
   ::= {pr1645v2Lan2FGUVlanOutPQsEntry 50593792}

pr1645v2Lan2FGUVlanOutPQsPacketsEirTx OBJECT-TYPE
   SYNTAX      Counter64
   MAX-ACCESS  read-only
   STATUS      current
   DESCRIPTION
      "Path: ethernet2.performance.vlan.outPriorityQueues.packets.eirTx

       64 bit unsigned wrappable counter."
   ::= {pr1645v2Lan2FGUVlanOutPQsEntry 50659328}

pr1645v2Lan2FGUVlanOutPQsPacketsViolateTx OBJECT-TYPE
   SYNTAX      Counter64
   MAX-ACCESS  read-only
   STATUS      current
   DESCRIPTION
      "Path: ethernet2.performance.vlan.outPriorityQueues.packets.violateTx

       64 bit unsigned wrappable counter."
   ::= {pr1645v2Lan2FGUVlanOutPQsEntry 50855936}

pr1645v2Lan2FGUVlanOutPQsOctetsTotal OBJECT-TYPE
   SYNTAX      Counter64
   MAX-ACCESS  read-only
   STATUS      current
   DESCRIPTION
      "Path: ethernet2.performance.vlan.outPriorityQueues.octets.total

       64 bit unsigned wrappable counter."
   ::= {pr1645v2Lan2FGUVlanOutPQsEntry 67567616}

pr1645v2Lan2FGUVlanOutPQsOctetsDirectTx OBJECT-TYPE
   SYNTAX      Counter64
   MAX-ACCESS  read-only
   STATUS      current
   DESCRIPTION
      "Path: ethernet2.performance.vlan.outPriorityQueues.octets.directTx

       64 bit unsigned wrappable counter."
   ::= {pr1645v2Lan2FGUVlanOutPQsEntry 67174400}

pr1645v2Lan2FGUVlanOutPQsOctetsQueued OBJECT-TYPE
   SYNTAX      Counter64
   MAX-ACCESS  read-only
   STATUS      current
   DESCRIPTION
      "Path: ethernet2.performance.vlan.outPriorityQueues.octets.queued

       64 bit unsigned wrappable counter."
   ::= {pr1645v2Lan2FGUVlanOutPQsEntry 67239936}

pr1645v2Lan2FGUVlanOutPQsOctetsDropped OBJECT-TYPE
   SYNTAX      Counter64
   MAX-ACCESS  read-only
   STATUS      current
   DESCRIPTION
      "Path: ethernet2.performance.vlan.outPriorityQueues.octets.dropped

       64 bit unsigned wrappable counter."
   ::= {pr1645v2Lan2FGUVlanOutPQsEntry 67305472}

pr1645v2Lan2FGUVlanOutPQsOctetsRedDropped OBJECT-TYPE
   SYNTAX      Counter64
   MAX-ACCESS  read-only
   STATUS      current
   DESCRIPTION
      "Path: ethernet2.performance.vlan.outPriorityQueues.octets.redDropped

       64 bit unsigned wrappable counter."
   ::= {pr1645v2Lan2FGUVlanOutPQsEntry 67502080}

pr1645v2Lan2FGUVlanOutPQsOctetsCirTx OBJECT-TYPE
   SYNTAX      Counter64
   MAX-ACCESS  read-only
   STATUS      current
   DESCRIPTION
      "Path: ethernet2.performance.vlan.outPriorityQueues.octets.cirTx

       64 bit unsigned wrappable counter."
   ::= {pr1645v2Lan2FGUVlanOutPQsEntry 67371008}

pr1645v2Lan2FGUVlanOutPQsOctetsEirTx OBJECT-TYPE
   SYNTAX      Counter64
   MAX-ACCESS  read-only
   STATUS      current
   DESCRIPTION
      "Path: ethernet2.performance.vlan.outPriorityQueues.octets.eirTx

       64 bit unsigned wrappable counter."
   ::= {pr1645v2Lan2FGUVlanOutPQsEntry 67436544}

pr1645v2Lan2FGUVlanOutPQsOctetsViolateTx OBJECT-TYPE
   SYNTAX      Counter64
   MAX-ACCESS  read-only
   STATUS      current
   DESCRIPTION
      "Path: ethernet2.performance.vlan.outPriorityQueues.octets.violateTx

       64 bit unsigned wrappable counter."
   ::= {pr1645v2Lan2FGUVlanOutPQsEntry 67633152}

pr1645v2Lan2FGUVlanOutPQsOctetsBandwidth15sec OBJECT-TYPE
   SYNTAX      Integer32
   MAX-ACCESS  read-only
   STATUS      current
   DESCRIPTION
      "Path: ethernet2.performance.vlan.outPriorityQueues.octets.bandwidth.15sec

       unit name = bps
       formula = 8 * ; 8 /"
   ::= {pr1645v2Lan2FGUVlanOutPQsEntry 70386944}

pr1645v2Lan2FGUVlanOutPQsOctetsBandwidth30sec OBJECT-TYPE
   SYNTAX      Integer32
   MAX-ACCESS  read-only
   STATUS      current
   DESCRIPTION
      "Path: ethernet2.performance.vlan.outPriorityQueues.octets.bandwidth.30sec

       unit name = bps
       formula = 8 * ; 8 /"
   ::= {pr1645v2Lan2FGUVlanOutPQsEntry 70388224}

pr1645v2Lan2FGUVlanOutPQsOctetsBandwidth1min OBJECT-TYPE
   SYNTAX      Integer32
   MAX-ACCESS  read-only
   STATUS      current
   DESCRIPTION
      "Path: ethernet2.performance.vlan.outPriorityQueues.octets.bandwidth.1min

       unit name = bps
       formula = 8 * ; 8 /"
   ::= {pr1645v2Lan2FGUVlanOutPQsEntry 70390784}

pr1645v2Lan2FGUVlanOutPQsOctetsBandwidth2min OBJECT-TYPE
   SYNTAX      Integer32
   MAX-ACCESS  read-only
   STATUS      current
   DESCRIPTION
      "Path: ethernet2.performance.vlan.outPriorityQueues.octets.bandwidth.2min

       unit name = bps
       formula = 8 * ; 8 /"
   ::= {pr1645v2Lan2FGUVlanOutPQsEntry 70395904}

pr1645v2Lan2FGUVlanOutPQsOctetsBandwidth5min OBJECT-TYPE
   SYNTAX      Integer32
   MAX-ACCESS  read-only
   STATUS      current
   DESCRIPTION
      "Path: ethernet2.performance.vlan.outPriorityQueues.octets.bandwidth.5min

       unit name = bps
       formula = 8 * ; 8 /"
   ::= {pr1645v2Lan2FGUVlanOutPQsEntry 70411264}

pr1645v2Lan2FGUVlanOutPQsH2Performance OBJECT-TYPE
   SYNTAX      SEQUENCE OF Pr1645v2Lan2FGUVlanOutPQsH2PerformanceEntry
   MAX-ACCESS  not-accessible
   STATUS      current
   DESCRIPTION
      ""
   ::= {pr1645v2Lan2FGUVlan 84213760}

pr1645v2Lan2FGUVlanOutPQsH2PerformanceEntry OBJECT-TYPE
   SYNTAX      Pr1645v2Lan2FGUVlanOutPQsH2PerformanceEntry
   MAX-ACCESS  not-accessible
   STATUS      current
   DESCRIPTION
      ""
   INDEX      { pr1645v2Lan2FGUVlanTableIx,
                pr1645v2Lan2FGUVlanOutPQsTableIx,
                pr1645v2Lan2FGUVlanOutPQsH2PerformanceTableIx }
   ::= {pr1645v2Lan2FGUVlanOutPQsH2Performance 1}

Pr1645v2Lan2FGUVlanOutPQsH2PerformanceEntry ::=
   SEQUENCE
      {
      pr1645v2Lan2FGUVlanOutPQsH2PerformanceTableIx
         TableIndex,
      pr1645v2Lan2FGUVlanOutPQsH2PerformanceSysUpTime
         TimeTicks,
      pr1645v2Lan2FGUVlanOutPQsH2PerformanceTotPkts
         Counter64,
      pr1645v2Lan2FGUVlanOutPQsH2PerformanceDirTxPkts
         Counter64,
      pr1645v2Lan2FGUVlanOutPQsH2PerformanceQdPkts
         Counter64,
      pr1645v2Lan2FGUVlanOutPQsH2PerformanceDropPkts
         Counter64,
      pr1645v2Lan2FGUVlanOutPQsH2PerformanceRDropPkts
         Counter64,
      pr1645v2Lan2FGUVlanOutPQsH2PerformanceCirTxPkts
         Counter64,
      pr1645v2Lan2FGUVlanOutPQsH2PerformanceEirTxPkts
         Counter64,
      pr1645v2Lan2FGUVlanOutPQsH2PerformanceViolTxPkts
         Counter64,
      pr1645v2Lan2FGUVlanOutPQsH2PerformanceTotOcts
         Counter64,
      pr1645v2Lan2FGUVlanOutPQsH2PerformanceDirTxOcts
         Counter64,
      pr1645v2Lan2FGUVlanOutPQsH2PerformanceQdOcts
         Counter64,
      pr1645v2Lan2FGUVlanOutPQsH2PerformanceDropOcts
         Counter64,
      pr1645v2Lan2FGUVlanOutPQsH2PerformanceRDropOcts
         Counter64,
      pr1645v2Lan2FGUVlanOutPQsH2PerformanceCirTxOcts
         Counter64,
      pr1645v2Lan2FGUVlanOutPQsH2PerformanceEirTxOcts
         Counter64,
      pr1645v2Lan2FGUVlanOutPQsH2PerformanceViolTxOcts
         Counter64,
      pr1645v2Lan2FGUVlanOutPQsH2PerformanceBandwidth
         Integer32
      }

pr1645v2Lan2FGUVlanOutPQsH2PerformanceTableIx OBJECT-TYPE
   SYNTAX      TableIndex
   MAX-ACCESS  not-accessible
   STATUS      current
   DESCRIPTION
      ""
   ::= {pr1645v2Lan2FGUVlanOutPQsH2PerformanceEntry 11}

pr1645v2Lan2FGUVlanOutPQsH2PerformanceSysUpTime OBJECT-TYPE
   SYNTAX      TimeTicks
   MAX-ACCESS  read-only
   STATUS      current
   DESCRIPTION
      "Path: ethernet2.performance.vlan.outPriorityQueues.h2Performance.sysUpTime

       Time in centi-second."
   ::= {pr1645v2Lan2FGUVlanOutPQsH2PerformanceEntry 16777216}

pr1645v2Lan2FGUVlanOutPQsH2PerformanceTotPkts OBJECT-TYPE
   SYNTAX      Counter64
   MAX-ACCESS  read-only
   STATUS      current
   DESCRIPTION
      "Path: ethernet2.performance.vlan.outPriorityQueues.h2Performance.totalPkts

       64 bit unsigned wrappable counter."
   ::= {pr1645v2Lan2FGUVlanOutPQsH2PerformanceEntry 234881024}

pr1645v2Lan2FGUVlanOutPQsH2PerformanceDirTxPkts OBJECT-TYPE
   SYNTAX      Counter64
   MAX-ACCESS  read-only
   STATUS      current
   DESCRIPTION
      "Path: ethernet2.performance.vlan.outPriorityQueues.h2Performance.directTxPkts

       64 bit unsigned wrappable counter."
   ::= {pr1645v2Lan2FGUVlanOutPQsH2PerformanceEntry 33554432}

pr1645v2Lan2FGUVlanOutPQsH2PerformanceQdPkts OBJECT-TYPE
   SYNTAX      Counter64
   MAX-ACCESS  read-only
   STATUS      current
   DESCRIPTION
      "Path: ethernet2.performance.vlan.outPriorityQueues.h2Performance.queuedPkts

       64 bit unsigned wrappable counter."
   ::= {pr1645v2Lan2FGUVlanOutPQsH2PerformanceEntry 50331648}

pr1645v2Lan2FGUVlanOutPQsH2PerformanceDropPkts OBJECT-TYPE
   SYNTAX      Counter64
   MAX-ACCESS  read-only
   STATUS      current
   DESCRIPTION
      "Path: ethernet2.performance.vlan.outPriorityQueues.h2Performance.droppedPkts

       64 bit unsigned wrappable counter."
   ::= {pr1645v2Lan2FGUVlanOutPQsH2PerformanceEntry 67108864}

pr1645v2Lan2FGUVlanOutPQsH2PerformanceRDropPkts OBJECT-TYPE
   SYNTAX      Counter64
   MAX-ACCESS  read-only
   STATUS      current
   DESCRIPTION
      "Path: ethernet2.performance.vlan.outPriorityQueues.h2Performance.redDroppedPkts

       64 bit unsigned wrappable counter."
   ::= {pr1645v2Lan2FGUVlanOutPQsH2PerformanceEntry 201326592}

pr1645v2Lan2FGUVlanOutPQsH2PerformanceCirTxPkts OBJECT-TYPE
   SYNTAX      Counter64
   MAX-ACCESS  read-only
   STATUS      current
   DESCRIPTION
      "Path: ethernet2.performance.vlan.outPriorityQueues.h2Performance.cirTxPkts

       64 bit unsigned wrappable counter."
   ::= {pr1645v2Lan2FGUVlanOutPQsH2PerformanceEntry 83886080}

pr1645v2Lan2FGUVlanOutPQsH2PerformanceEirTxPkts OBJECT-TYPE
   SYNTAX      Counter64
   MAX-ACCESS  read-only
   STATUS      current
   DESCRIPTION
      "Path: ethernet2.performance.vlan.outPriorityQueues.h2Performance.eirTxPkts

       64 bit unsigned wrappable counter."
   ::= {pr1645v2Lan2FGUVlanOutPQsH2PerformanceEntry 100663296}

pr1645v2Lan2FGUVlanOutPQsH2PerformanceViolTxPkts OBJECT-TYPE
   SYNTAX      Counter64
   MAX-ACCESS  read-only
   STATUS      current
   DESCRIPTION
      "Path: ethernet2.performance.vlan.outPriorityQueues.h2Performance.violateTxPkts

       64 bit unsigned wrappable counter."
   ::= {pr1645v2Lan2FGUVlanOutPQsH2PerformanceEntry 301989888}

pr1645v2Lan2FGUVlanOutPQsH2PerformanceTotOcts OBJECT-TYPE
   SYNTAX      Counter64
   MAX-ACCESS  read-only
   STATUS      current
   DESCRIPTION
      "Path: ethernet2.performance.vlan.outPriorityQueues.h2Performance.totalOctets

       64 bit unsigned wrappable counter."
   ::= {pr1645v2Lan2FGUVlanOutPQsH2PerformanceEntry 251658240}

pr1645v2Lan2FGUVlanOutPQsH2PerformanceDirTxOcts OBJECT-TYPE
   SYNTAX      Counter64
   MAX-ACCESS  read-only
   STATUS      current
   DESCRIPTION
      "Path: ethernet2.performance.vlan.outPriorityQueues.h2Performance.directTxOctets

       64 bit unsigned wrappable counter."
   ::= {pr1645v2Lan2FGUVlanOutPQsH2PerformanceEntry 117440512}

pr1645v2Lan2FGUVlanOutPQsH2PerformanceQdOcts OBJECT-TYPE
   SYNTAX      Counter64
   MAX-ACCESS  read-only
   STATUS      current
   DESCRIPTION
      "Path: ethernet2.performance.vlan.outPriorityQueues.h2Performance.queuedOctets

       64 bit unsigned wrappable counter."
   ::= {pr1645v2Lan2FGUVlanOutPQsH2PerformanceEntry 134217728}

pr1645v2Lan2FGUVlanOutPQsH2PerformanceDropOcts OBJECT-TYPE
   SYNTAX      Counter64
   MAX-ACCESS  read-only
   STATUS      current
   DESCRIPTION
      "Path: ethernet2.performance.vlan.outPriorityQueues.h2Performance.droppedOctets

       64 bit unsigned wrappable counter."
   ::= {pr1645v2Lan2FGUVlanOutPQsH2PerformanceEntry 150994944}

pr1645v2Lan2FGUVlanOutPQsH2PerformanceRDropOcts OBJECT-TYPE
   SYNTAX      Counter64
   MAX-ACCESS  read-only
   STATUS      current
   DESCRIPTION
      "Path: ethernet2.performance.vlan.outPriorityQueues.h2Performance.redDroppedOctets

       64 bit unsigned wrappable counter."
   ::= {pr1645v2Lan2FGUVlanOutPQsH2PerformanceEntry 218103808}

pr1645v2Lan2FGUVlanOutPQsH2PerformanceCirTxOcts OBJECT-TYPE
   SYNTAX      Counter64
   MAX-ACCESS  read-only
   STATUS      current
   DESCRIPTION
      "Path: ethernet2.performance.vlan.outPriorityQueues.h2Performance.cirTxOctets

       64 bit unsigned wrappable counter."
   ::= {pr1645v2Lan2FGUVlanOutPQsH2PerformanceEntry 167772160}

pr1645v2Lan2FGUVlanOutPQsH2PerformanceEirTxOcts OBJECT-TYPE
   SYNTAX      Counter64
   MAX-ACCESS  read-only
   STATUS      current
   DESCRIPTION
      "Path: ethernet2.performance.vlan.outPriorityQueues.h2Performance.eirTxOctets

       64 bit unsigned wrappable counter."
   ::= {pr1645v2Lan2FGUVlanOutPQsH2PerformanceEntry 184549376}

pr1645v2Lan2FGUVlanOutPQsH2PerformanceViolTxOcts OBJECT-TYPE
   SYNTAX      Counter64
   MAX-ACCESS  read-only
   STATUS      current
   DESCRIPTION
      "Path: ethernet2.performance.vlan.outPriorityQueues.h2Performance.violateTxOctets

       64 bit unsigned wrappable counter."
   ::= {pr1645v2Lan2FGUVlanOutPQsH2PerformanceEntry 318767104}

pr1645v2Lan2FGUVlanOutPQsH2PerformanceBandwidth OBJECT-TYPE
   SYNTAX      Integer32
   MAX-ACCESS  read-only
   STATUS      current
   DESCRIPTION
      "Path: ethernet2.performance.vlan.outPriorityQueues.h2Performance.bandwidth

       unit name = bps
       formula = 8 * ; 8 /"
   ::= {pr1645v2Lan2FGUVlanOutPQsH2PerformanceEntry 268435456}

pr1645v2Lan2FGUVlanOutPQsH24Performance OBJECT-TYPE
   SYNTAX      SEQUENCE OF Pr1645v2Lan2FGUVlanOutPQsH24PerformanceEntry
   MAX-ACCESS  not-accessible
   STATUS      current
   DESCRIPTION
      ""
   ::= {pr1645v2Lan2FGUVlan 84279296}

pr1645v2Lan2FGUVlanOutPQsH24PerformanceEntry OBJECT-TYPE
   SYNTAX      Pr1645v2Lan2FGUVlanOutPQsH24PerformanceEntry
   MAX-ACCESS  not-accessible
   STATUS      current
   DESCRIPTION
      ""
   INDEX      { pr1645v2Lan2FGUVlanTableIx,
                pr1645v2Lan2FGUVlanOutPQsTableIx,
                pr1645v2Lan2FGUVlanOutPQsH24PerformanceTableIx }
   ::= {pr1645v2Lan2FGUVlanOutPQsH24Performance 1}

Pr1645v2Lan2FGUVlanOutPQsH24PerformanceEntry ::=
   SEQUENCE
      {
      pr1645v2Lan2FGUVlanOutPQsH24PerformanceTableIx
         TableIndex,
      pr1645v2Lan2FGUVlanOutPQsH24PerformanceSysUpTime
         TimeTicks,
      pr1645v2Lan2FGUVlanOutPQsH24PerformanceTotPkts
         Counter64,
      pr1645v2Lan2FGUVlanOutPQsH24PerformanceDirTxPkts
         Counter64,
      pr1645v2Lan2FGUVlanOutPQsH24PerformanceQdPkts
         Counter64,
      pr1645v2Lan2FGUVlanOutPQsH24PerformanceDropPkts
         Counter64,
      pr1645v2Lan2FGUVlanOutPQsH24PerformanceRDropPkts
         Counter64,
      pr1645v2Lan2FGUVlanOutPQsH24PerformanceCirTxPkts
         Counter64,
      pr1645v2Lan2FGUVlanOutPQsH24PerformanceEirTxPkts
         Counter64,
      pr1645v2Lan2FGUVlanOutPQsH24PerformanceViolTxPkts
         Counter64,
      pr1645v2Lan2FGUVlanOutPQsH24PerformanceTotOcts
         Counter64,
      pr1645v2Lan2FGUVlanOutPQsH24PerformanceDirTxOcts
         Counter64,
      pr1645v2Lan2FGUVlanOutPQsH24PerformanceQdOcts
         Counter64,
      pr1645v2Lan2FGUVlanOutPQsH24PerformanceDropOcts
         Counter64,
      pr1645v2Lan2FGUVlanOutPQsH24PerformanceRDropOcts
         Counter64,
      pr1645v2Lan2FGUVlanOutPQsH24PerformanceCirTxOcts
         Counter64,
      pr1645v2Lan2FGUVlanOutPQsH24PerformanceEirTxOcts
         Counter64,
      pr1645v2Lan2FGUVlanOutPQsH24PerformanceViolTxOcts
         Counter64,
      pr1645v2Lan2FGUVlanOutPQsH24PerformanceBandwidth
         Integer32
      }

pr1645v2Lan2FGUVlanOutPQsH24PerformanceTableIx OBJECT-TYPE
   SYNTAX      TableIndex
   MAX-ACCESS  not-accessible
   STATUS      current
   DESCRIPTION
      ""
   ::= {pr1645v2Lan2FGUVlanOutPQsH24PerformanceEntry 11}

pr1645v2Lan2FGUVlanOutPQsH24PerformanceSysUpTime OBJECT-TYPE
   SYNTAX      TimeTicks
   MAX-ACCESS  read-only
   STATUS      current
   DESCRIPTION
      "Path: ethernet2.performance.vlan.outPriorityQueues.h24Performance.sysUpTime

       Time in centi-second."
   ::= {pr1645v2Lan2FGUVlanOutPQsH24PerformanceEntry 16777216}

pr1645v2Lan2FGUVlanOutPQsH24PerformanceTotPkts OBJECT-TYPE
   SYNTAX      Counter64
   MAX-ACCESS  read-only
   STATUS      current
   DESCRIPTION
      "Path: ethernet2.performance.vlan.outPriorityQueues.h24Performance.totalPkts

       64 bit unsigned wrappable counter."
   ::= {pr1645v2Lan2FGUVlanOutPQsH24PerformanceEntry 234881024}

pr1645v2Lan2FGUVlanOutPQsH24PerformanceDirTxPkts OBJECT-TYPE
   SYNTAX      Counter64
   MAX-ACCESS  read-only
   STATUS      current
   DESCRIPTION
      "Path: ethernet2.performance.vlan.outPriorityQueues.h24Performance.directTxPkts

       64 bit unsigned wrappable counter."
   ::= {pr1645v2Lan2FGUVlanOutPQsH24PerformanceEntry 33554432}

pr1645v2Lan2FGUVlanOutPQsH24PerformanceQdPkts OBJECT-TYPE
   SYNTAX      Counter64
   MAX-ACCESS  read-only
   STATUS      current
   DESCRIPTION
      "Path: ethernet2.performance.vlan.outPriorityQueues.h24Performance.queuedPkts

       64 bit unsigned wrappable counter."
   ::= {pr1645v2Lan2FGUVlanOutPQsH24PerformanceEntry 50331648}

pr1645v2Lan2FGUVlanOutPQsH24PerformanceDropPkts OBJECT-TYPE
   SYNTAX      Counter64
   MAX-ACCESS  read-only
   STATUS      current
   DESCRIPTION
      "Path: ethernet2.performance.vlan.outPriorityQueues.h24Performance.droppedPkts

       64 bit unsigned wrappable counter."
   ::= {pr1645v2Lan2FGUVlanOutPQsH24PerformanceEntry 67108864}

pr1645v2Lan2FGUVlanOutPQsH24PerformanceRDropPkts OBJECT-TYPE
   SYNTAX      Counter64
   MAX-ACCESS  read-only
   STATUS      current
   DESCRIPTION
      "Path: ethernet2.performance.vlan.outPriorityQueues.h24Performance.redDroppedPkts

       64 bit unsigned wrappable counter."
   ::= {pr1645v2Lan2FGUVlanOutPQsH24PerformanceEntry 201326592}

pr1645v2Lan2FGUVlanOutPQsH24PerformanceCirTxPkts OBJECT-TYPE
   SYNTAX      Counter64
   MAX-ACCESS  read-only
   STATUS      current
   DESCRIPTION
      "Path: ethernet2.performance.vlan.outPriorityQueues.h24Performance.cirTxPkts

       64 bit unsigned wrappable counter."
   ::= {pr1645v2Lan2FGUVlanOutPQsH24PerformanceEntry 83886080}

pr1645v2Lan2FGUVlanOutPQsH24PerformanceEirTxPkts OBJECT-TYPE
   SYNTAX      Counter64
   MAX-ACCESS  read-only
   STATUS      current
   DESCRIPTION
      "Path: ethernet2.performance.vlan.outPriorityQueues.h24Performance.eirTxPkts

       64 bit unsigned wrappable counter."
   ::= {pr1645v2Lan2FGUVlanOutPQsH24PerformanceEntry 100663296}

pr1645v2Lan2FGUVlanOutPQsH24PerformanceViolTxPkts OBJECT-TYPE
   SYNTAX      Counter64
   MAX-ACCESS  read-only
   STATUS      current
   DESCRIPTION
      "Path: ethernet2.performance.vlan.outPriorityQueues.h24Performance.violateTxPkts

       64 bit unsigned wrappable counter."
   ::= {pr1645v2Lan2FGUVlanOutPQsH24PerformanceEntry 301989888}

pr1645v2Lan2FGUVlanOutPQsH24PerformanceTotOcts OBJECT-TYPE
   SYNTAX      Counter64
   MAX-ACCESS  read-only
   STATUS      current
   DESCRIPTION
      "Path: ethernet2.performance.vlan.outPriorityQueues.h24Performance.totalOctets

       64 bit unsigned wrappable counter."
   ::= {pr1645v2Lan2FGUVlanOutPQsH24PerformanceEntry 251658240}

pr1645v2Lan2FGUVlanOutPQsH24PerformanceDirTxOcts OBJECT-TYPE
   SYNTAX      Counter64
   MAX-ACCESS  read-only
   STATUS      current
   DESCRIPTION
      "Path: ethernet2.performance.vlan.outPriorityQueues.h24Performance.directTxOctets

       64 bit unsigned wrappable counter."
   ::= {pr1645v2Lan2FGUVlanOutPQsH24PerformanceEntry 117440512}

pr1645v2Lan2FGUVlanOutPQsH24PerformanceQdOcts OBJECT-TYPE
   SYNTAX      Counter64
   MAX-ACCESS  read-only
   STATUS      current
   DESCRIPTION
      "Path: ethernet2.performance.vlan.outPriorityQueues.h24Performance.queuedOctets

       64 bit unsigned wrappable counter."
   ::= {pr1645v2Lan2FGUVlanOutPQsH24PerformanceEntry 134217728}

pr1645v2Lan2FGUVlanOutPQsH24PerformanceDropOcts OBJECT-TYPE
   SYNTAX      Counter64
   MAX-ACCESS  read-only
   STATUS      current
   DESCRIPTION
      "Path: ethernet2.performance.vlan.outPriorityQueues.h24Performance.droppedOctets

       64 bit unsigned wrappable counter."
   ::= {pr1645v2Lan2FGUVlanOutPQsH24PerformanceEntry 150994944}

pr1645v2Lan2FGUVlanOutPQsH24PerformanceRDropOcts OBJECT-TYPE
   SYNTAX      Counter64
   MAX-ACCESS  read-only
   STATUS      current
   DESCRIPTION
      "Path: ethernet2.performance.vlan.outPriorityQueues.h24Performance.redDroppedOctets

       64 bit unsigned wrappable counter."
   ::= {pr1645v2Lan2FGUVlanOutPQsH24PerformanceEntry 218103808}

pr1645v2Lan2FGUVlanOutPQsH24PerformanceCirTxOcts OBJECT-TYPE
   SYNTAX      Counter64
   MAX-ACCESS  read-only
   STATUS      current
   DESCRIPTION
      "Path: ethernet2.performance.vlan.outPriorityQueues.h24Performance.cirTxOctets

       64 bit unsigned wrappable counter."
   ::= {pr1645v2Lan2FGUVlanOutPQsH24PerformanceEntry 167772160}

pr1645v2Lan2FGUVlanOutPQsH24PerformanceEirTxOcts OBJECT-TYPE
   SYNTAX      Counter64
   MAX-ACCESS  read-only
   STATUS      current
   DESCRIPTION
      "Path: ethernet2.performance.vlan.outPriorityQueues.h24Performance.eirTxOctets

       64 bit unsigned wrappable counter."
   ::= {pr1645v2Lan2FGUVlanOutPQsH24PerformanceEntry 184549376}

pr1645v2Lan2FGUVlanOutPQsH24PerformanceViolTxOcts OBJECT-TYPE
   SYNTAX      Counter64
   MAX-ACCESS  read-only
   STATUS      current
   DESCRIPTION
      "Path: ethernet2.performance.vlan.outPriorityQueues.h24Performance.violateTxOctets

       64 bit unsigned wrappable counter."
   ::= {pr1645v2Lan2FGUVlanOutPQsH24PerformanceEntry 318767104}

pr1645v2Lan2FGUVlanOutPQsH24PerformanceBandwidth OBJECT-TYPE
   SYNTAX      Integer32
   MAX-ACCESS  read-only
   STATUS      current
   DESCRIPTION
      "Path: ethernet2.performance.vlan.outPriorityQueues.h24Performance.bandwidth

       unit name = bps
       formula = 8 * ; 8 /"
   ::= {pr1645v2Lan2FGUVlanOutPQsH24PerformanceEntry 268435456}

pr1645v2Lan2FGUVlanOutPQsD7Performance OBJECT-TYPE
   SYNTAX      SEQUENCE OF Pr1645v2Lan2FGUVlanOutPQsD7PerformanceEntry
   MAX-ACCESS  not-accessible
   STATUS      current
   DESCRIPTION
      ""
   ::= {pr1645v2Lan2FGUVlan 84344832}

pr1645v2Lan2FGUVlanOutPQsD7PerformanceEntry OBJECT-TYPE
   SYNTAX      Pr1645v2Lan2FGUVlanOutPQsD7PerformanceEntry
   MAX-ACCESS  not-accessible
   STATUS      current
   DESCRIPTION
      ""
   INDEX      { pr1645v2Lan2FGUVlanTableIx,
                pr1645v2Lan2FGUVlanOutPQsTableIx,
                pr1645v2Lan2FGUVlanOutPQsD7PerformanceTableIx }
   ::= {pr1645v2Lan2FGUVlanOutPQsD7Performance 1}

Pr1645v2Lan2FGUVlanOutPQsD7PerformanceEntry ::=
   SEQUENCE
      {
      pr1645v2Lan2FGUVlanOutPQsD7PerformanceTableIx
         TableIndex,
      pr1645v2Lan2FGUVlanOutPQsD7PerformanceSysUpTime
         TimeTicks,
      pr1645v2Lan2FGUVlanOutPQsD7PerformanceTotPkts
         Counter64,
      pr1645v2Lan2FGUVlanOutPQsD7PerformanceDirTxPkts
         Counter64,
      pr1645v2Lan2FGUVlanOutPQsD7PerformanceQdPkts
         Counter64,
      pr1645v2Lan2FGUVlanOutPQsD7PerformanceDropPkts
         Counter64,
      pr1645v2Lan2FGUVlanOutPQsD7PerformanceRDropPkts
         Counter64,
      pr1645v2Lan2FGUVlanOutPQsD7PerformanceCirTxPkts
         Counter64,
      pr1645v2Lan2FGUVlanOutPQsD7PerformanceEirTxPkts
         Counter64,
      pr1645v2Lan2FGUVlanOutPQsD7PerformanceViolTxPkts
         Counter64,
      pr1645v2Lan2FGUVlanOutPQsD7PerformanceTotOcts
         Counter64,
      pr1645v2Lan2FGUVlanOutPQsD7PerformanceDirTxOcts
         Counter64,
      pr1645v2Lan2FGUVlanOutPQsD7PerformanceQdOcts
         Counter64,
      pr1645v2Lan2FGUVlanOutPQsD7PerformanceDropOcts
         Counter64,
      pr1645v2Lan2FGUVlanOutPQsD7PerformanceRDropOcts
         Counter64,
      pr1645v2Lan2FGUVlanOutPQsD7PerformanceCirTxOcts
         Counter64,
      pr1645v2Lan2FGUVlanOutPQsD7PerformanceEirTxOcts
         Counter64,
      pr1645v2Lan2FGUVlanOutPQsD7PerformanceViolTxOcts
         Counter64,
      pr1645v2Lan2FGUVlanOutPQsD7PerformanceBandwidth
         Integer32
      }

pr1645v2Lan2FGUVlanOutPQsD7PerformanceTableIx OBJECT-TYPE
   SYNTAX      TableIndex
   MAX-ACCESS  not-accessible
   STATUS      current
   DESCRIPTION
      ""
   ::= {pr1645v2Lan2FGUVlanOutPQsD7PerformanceEntry 11}

pr1645v2Lan2FGUVlanOutPQsD7PerformanceSysUpTime OBJECT-TYPE
   SYNTAX      TimeTicks
   MAX-ACCESS  read-only
   STATUS      current
   DESCRIPTION
      "Path: ethernet2.performance.vlan.outPriorityQueues.d7Performance.sysUpTime

       Time in centi-second."
   ::= {pr1645v2Lan2FGUVlanOutPQsD7PerformanceEntry 16777216}

pr1645v2Lan2FGUVlanOutPQsD7PerformanceTotPkts OBJECT-TYPE
   SYNTAX      Counter64
   MAX-ACCESS  read-only
   STATUS      current
   DESCRIPTION
      "Path: ethernet2.performance.vlan.outPriorityQueues.d7Performance.totalPkts

       64 bit unsigned wrappable counter."
   ::= {pr1645v2Lan2FGUVlanOutPQsD7PerformanceEntry 234881024}

pr1645v2Lan2FGUVlanOutPQsD7PerformanceDirTxPkts OBJECT-TYPE
   SYNTAX      Counter64
   MAX-ACCESS  read-only
   STATUS      current
   DESCRIPTION
      "Path: ethernet2.performance.vlan.outPriorityQueues.d7Performance.directTxPkts

       64 bit unsigned wrappable counter."
   ::= {pr1645v2Lan2FGUVlanOutPQsD7PerformanceEntry 33554432}

pr1645v2Lan2FGUVlanOutPQsD7PerformanceQdPkts OBJECT-TYPE
   SYNTAX      Counter64
   MAX-ACCESS  read-only
   STATUS      current
   DESCRIPTION
      "Path: ethernet2.performance.vlan.outPriorityQueues.d7Performance.queuedPkts

       64 bit unsigned wrappable counter."
   ::= {pr1645v2Lan2FGUVlanOutPQsD7PerformanceEntry 50331648}

pr1645v2Lan2FGUVlanOutPQsD7PerformanceDropPkts OBJECT-TYPE
   SYNTAX      Counter64
   MAX-ACCESS  read-only
   STATUS      current
   DESCRIPTION
      "Path: ethernet2.performance.vlan.outPriorityQueues.d7Performance.droppedPkts

       64 bit unsigned wrappable counter."
   ::= {pr1645v2Lan2FGUVlanOutPQsD7PerformanceEntry 67108864}

pr1645v2Lan2FGUVlanOutPQsD7PerformanceRDropPkts OBJECT-TYPE
   SYNTAX      Counter64
   MAX-ACCESS  read-only
   STATUS      current
   DESCRIPTION
      "Path: ethernet2.performance.vlan.outPriorityQueues.d7Performance.redDroppedPkts

       64 bit unsigned wrappable counter."
   ::= {pr1645v2Lan2FGUVlanOutPQsD7PerformanceEntry 201326592}

pr1645v2Lan2FGUVlanOutPQsD7PerformanceCirTxPkts OBJECT-TYPE
   SYNTAX      Counter64
   MAX-ACCESS  read-only
   STATUS      current
   DESCRIPTION
      "Path: ethernet2.performance.vlan.outPriorityQueues.d7Performance.cirTxPkts

       64 bit unsigned wrappable counter."
   ::= {pr1645v2Lan2FGUVlanOutPQsD7PerformanceEntry 83886080}

pr1645v2Lan2FGUVlanOutPQsD7PerformanceEirTxPkts OBJECT-TYPE
   SYNTAX      Counter64
   MAX-ACCESS  read-only
   STATUS      current
   DESCRIPTION
      "Path: ethernet2.performance.vlan.outPriorityQueues.d7Performance.eirTxPkts

       64 bit unsigned wrappable counter."
   ::= {pr1645v2Lan2FGUVlanOutPQsD7PerformanceEntry 100663296}

pr1645v2Lan2FGUVlanOutPQsD7PerformanceViolTxPkts OBJECT-TYPE
   SYNTAX      Counter64
   MAX-ACCESS  read-only
   STATUS      current
   DESCRIPTION
      "Path: ethernet2.performance.vlan.outPriorityQueues.d7Performance.violateTxPkts

       64 bit unsigned wrappable counter."
   ::= {pr1645v2Lan2FGUVlanOutPQsD7PerformanceEntry 301989888}

pr1645v2Lan2FGUVlanOutPQsD7PerformanceTotOcts OBJECT-TYPE
   SYNTAX      Counter64
   MAX-ACCESS  read-only
   STATUS      current
   DESCRIPTION
      "Path: ethernet2.performance.vlan.outPriorityQueues.d7Performance.totalOctets

       64 bit unsigned wrappable counter."
   ::= {pr1645v2Lan2FGUVlanOutPQsD7PerformanceEntry 251658240}

pr1645v2Lan2FGUVlanOutPQsD7PerformanceDirTxOcts OBJECT-TYPE
   SYNTAX      Counter64
   MAX-ACCESS  read-only
   STATUS      current
   DESCRIPTION
      "Path: ethernet2.performance.vlan.outPriorityQueues.d7Performance.directTxOctets

       64 bit unsigned wrappable counter."
   ::= {pr1645v2Lan2FGUVlanOutPQsD7PerformanceEntry 117440512}

pr1645v2Lan2FGUVlanOutPQsD7PerformanceQdOcts OBJECT-TYPE
   SYNTAX      Counter64
   MAX-ACCESS  read-only
   STATUS      current
   DESCRIPTION
      "Path: ethernet2.performance.vlan.outPriorityQueues.d7Performance.queuedOctets

       64 bit unsigned wrappable counter."
   ::= {pr1645v2Lan2FGUVlanOutPQsD7PerformanceEntry 134217728}

pr1645v2Lan2FGUVlanOutPQsD7PerformanceDropOcts OBJECT-TYPE
   SYNTAX      Counter64
   MAX-ACCESS  read-only
   STATUS      current
   DESCRIPTION
      "Path: ethernet2.performance.vlan.outPriorityQueues.d7Performance.droppedOctets

       64 bit unsigned wrappable counter."
   ::= {pr1645v2Lan2FGUVlanOutPQsD7PerformanceEntry 150994944}

pr1645v2Lan2FGUVlanOutPQsD7PerformanceRDropOcts OBJECT-TYPE
   SYNTAX      Counter64
   MAX-ACCESS  read-only
   STATUS      current
   DESCRIPTION
      "Path: ethernet2.performance.vlan.outPriorityQueues.d7Performance.redDroppedOctets

       64 bit unsigned wrappable counter."
   ::= {pr1645v2Lan2FGUVlanOutPQsD7PerformanceEntry 218103808}

pr1645v2Lan2FGUVlanOutPQsD7PerformanceCirTxOcts OBJECT-TYPE
   SYNTAX      Counter64
   MAX-ACCESS  read-only
   STATUS      current
   DESCRIPTION
      "Path: ethernet2.performance.vlan.outPriorityQueues.d7Performance.cirTxOctets

       64 bit unsigned wrappable counter."
   ::= {pr1645v2Lan2FGUVlanOutPQsD7PerformanceEntry 167772160}

pr1645v2Lan2FGUVlanOutPQsD7PerformanceEirTxOcts OBJECT-TYPE
   SYNTAX      Counter64
   MAX-ACCESS  read-only
   STATUS      current
   DESCRIPTION
      "Path: ethernet2.performance.vlan.outPriorityQueues.d7Performance.eirTxOctets

       64 bit unsigned wrappable counter."
   ::= {pr1645v2Lan2FGUVlanOutPQsD7PerformanceEntry 184549376}

pr1645v2Lan2FGUVlanOutPQsD7PerformanceViolTxOcts OBJECT-TYPE
   SYNTAX      Counter64
   MAX-ACCESS  read-only
   STATUS      current
   DESCRIPTION
      "Path: ethernet2.performance.vlan.outPriorityQueues.d7Performance.violateTxOctets

       64 bit unsigned wrappable counter."
   ::= {pr1645v2Lan2FGUVlanOutPQsD7PerformanceEntry 318767104}

pr1645v2Lan2FGUVlanOutPQsD7PerformanceBandwidth OBJECT-TYPE
   SYNTAX      Integer32
   MAX-ACCESS  read-only
   STATUS      current
   DESCRIPTION
      "Path: ethernet2.performance.vlan.outPriorityQueues.d7Performance.bandwidth

       unit name = bps
       formula = 8 * ; 8 /"
   ::= {pr1645v2Lan2FGUVlanOutPQsD7PerformanceEntry 268435456}


pr1645v2Lan2FGUPPPoE OBJECT IDENTIFIER ::= {pr1645v2Lan2FGU 53}

pr1645v2Lan2FGUPPPoESSCTable OBJECT-TYPE
   SYNTAX      SEQUENCE OF Pr1645v2Lan2FGUPPPoEEntry
   MAX-ACCESS  not-accessible
   STATUS      current
   DESCRIPTION
      ""
   ::= {pr1645v2Lan2FGUPPPoE 1}

pr1645v2Lan2FGUPPPoEEntry OBJECT-TYPE
   SYNTAX      Pr1645v2Lan2FGUPPPoEEntry
   MAX-ACCESS  not-accessible
   STATUS      current
   DESCRIPTION
      ""
   INDEX      { pr1645v2Lan2FGUPPPoETableIx }
   ::= {pr1645v2Lan2FGUPPPoESSCTable 1}

Pr1645v2Lan2FGUPPPoEEntry ::=
   SEQUENCE
      {
      pr1645v2Lan2FGUPPPoETableIx
         TableIndex,
      pr1645v2Lan2FGUPPPoEName
         DisplayString,
      pr1645v2Lan2FGUPPPoEMCInOctets
         Counter64,
      pr1645v2Lan2FGUPPPoEMCInUcast
         Counter64,
      pr1645v2Lan2FGUPPPoEMCInNUcastPkts
         Counter64,
      pr1645v2Lan2FGUPPPoEMCInBcastPkts
         Counter64,
      pr1645v2Lan2FGUPPPoEMCInMcastPkts
         Counter64,
      pr1645v2Lan2FGUPPPoEMCInDiscards
         Counter64,
      pr1645v2Lan2FGUPPPoEMCInErrors
         Counter64,
      pr1645v2Lan2FGUPPPoEMCInUnknownProtos
         Counter64,
      pr1645v2Lan2FGUPPPoEMCInDropEx
         Counter64,
      pr1645v2Lan2FGUPPPoEMCInDropNoMac
         Counter64,
      pr1645v2Lan2FGUPPPoEMCInDropNUCast
         Counter64,
      pr1645v2Lan2FGUPPPoEMCInDropFilter
         Counter64,
      pr1645v2Lan2FGUPPPoEMCInBandwidth15sec
         Integer32,
      pr1645v2Lan2FGUPPPoEMCInBandwidth30sec
         Integer32,
      pr1645v2Lan2FGUPPPoEMCInBandwidth1min
         Integer32,
      pr1645v2Lan2FGUPPPoEMCInBandwidth2min
         Integer32,
      pr1645v2Lan2FGUPPPoEMCInBandwidth5min
         Integer32,
      pr1645v2Lan2FGUPPPoEMCOutOctets
         Counter64,
      pr1645v2Lan2FGUPPPoEMCOutUcastPkts
         Counter64,
      pr1645v2Lan2FGUPPPoEMCOutNUcastPkts
         Counter64,
      pr1645v2Lan2FGUPPPoEMCOutBcastPkts
         Counter64,
      pr1645v2Lan2FGUPPPoEMCOutMcastPkts
         Counter64,
      pr1645v2Lan2FGUPPPoEMCOutDiscards
         Counter64,
      pr1645v2Lan2FGUPPPoEMCOutErrors
         Counter64,
      pr1645v2Lan2FGUPPPoEMCOutQLen
         Counter32,
      pr1645v2Lan2FGUPPPoEMCOutDropEx
         Counter64,
      pr1645v2Lan2FGUPPPoEMCOutDropNoArp
         Counter64,
      pr1645v2Lan2FGUPPPoEMCOutDropFilter
         Counter64,
      pr1645v2Lan2FGUPPPoEMCOutBandwidth15sec
         Integer32,
      pr1645v2Lan2FGUPPPoEMCOutBandwidth30sec
         Integer32,
      pr1645v2Lan2FGUPPPoEMCOutBandwidth1min
         Integer32,
      pr1645v2Lan2FGUPPPoEMCOutBandwidth2min
         Integer32,
      pr1645v2Lan2FGUPPPoEMCOutBandwidth5min
         Integer32,
      pr1645v2Lan2FGUPPPoEPppLinkMonitoringRequestsSent
         Gauge32,
      pr1645v2Lan2FGUPPPoEPppLinkMonitoringRepliesRcvd
         Gauge32,
      pr1645v2Lan2FGUPPPoEPppLinkMonitoringRequestsRcvd
         Gauge32,
      pr1645v2Lan2FGUPPPoEPppLinkMonitoringRepliesSent
         Gauge32
      }

pr1645v2Lan2FGUPPPoETableIx OBJECT-TYPE
   SYNTAX      TableIndex
   MAX-ACCESS  not-accessible
   STATUS      current
   DESCRIPTION
      ""
   ::= {pr1645v2Lan2FGUPPPoEEntry 11}

pr1645v2Lan2FGUPPPoEName OBJECT-TYPE
   SYNTAX      DisplayString
   MAX-ACCESS  read-only
   STATUS      current
   DESCRIPTION
      "Path: ethernet2.performance.pppoEClient.name"
   ::= {pr1645v2Lan2FGUPPPoEEntry 16777216}

pr1645v2Lan2FGUPPPoEMCInOctets OBJECT-TYPE
   SYNTAX      Counter64
   MAX-ACCESS  read-only
   STATUS      current
   DESCRIPTION
      "Path: ethernet2.performance.pppoEClient.mibCounters.ifInOctets

       64 bit unsigned wrappable counter."
   ::= {pr1645v2Lan2FGUPPPoEEntry 40697856}

pr1645v2Lan2FGUPPPoEMCInUcast OBJECT-TYPE
   SYNTAX      Counter64
   MAX-ACCESS  read-only
   STATUS      current
   DESCRIPTION
      "Path: ethernet2.performance.pppoEClient.mibCounters.ifInUcastPkts

       64 bit unsigned wrappable counter."
   ::= {pr1645v2Lan2FGUPPPoEEntry 40763392}

pr1645v2Lan2FGUPPPoEMCInNUcastPkts OBJECT-TYPE
   SYNTAX      Counter64
   MAX-ACCESS  read-only
   STATUS      current
   DESCRIPTION
      "Path: ethernet2.performance.pppoEClient.mibCounters.ifInNUcastPkts

       64 bit unsigned wrappable counter."
   ::= {pr1645v2Lan2FGUPPPoEEntry 40828928}

pr1645v2Lan2FGUPPPoEMCInBcastPkts OBJECT-TYPE
   SYNTAX      Counter64
   MAX-ACCESS  read-only
   STATUS      current
   DESCRIPTION
      "Path: ethernet2.performance.pppoEClient.mibCounters.ifInBcastPkts

       64 bit unsigned wrappable counter."
   ::= {pr1645v2Lan2FGUPPPoEEntry 47382528}

pr1645v2Lan2FGUPPPoEMCInMcastPkts OBJECT-TYPE
   SYNTAX      Counter64
   MAX-ACCESS  read-only
   STATUS      current
   DESCRIPTION
      "Path: ethernet2.performance.pppoEClient.mibCounters.ifInMcastPkts

       64 bit unsigned wrappable counter."
   ::= {pr1645v2Lan2FGUPPPoEEntry 48037888}

pr1645v2Lan2FGUPPPoEMCInDiscards OBJECT-TYPE
   SYNTAX      Counter64
   MAX-ACCESS  read-only
   STATUS      current
   DESCRIPTION
      "Path: ethernet2.performance.pppoEClient.mibCounters.ifInDiscards

       64 bit unsigned wrappable counter."
   ::= {pr1645v2Lan2FGUPPPoEEntry 40894464}

pr1645v2Lan2FGUPPPoEMCInErrors OBJECT-TYPE
   SYNTAX      Counter64
   MAX-ACCESS  read-only
   STATUS      current
   DESCRIPTION
      "Path: ethernet2.performance.pppoEClient.mibCounters.ifInErrors

       64 bit unsigned wrappable counter."
   ::= {pr1645v2Lan2FGUPPPoEEntry 40960000}

pr1645v2Lan2FGUPPPoEMCInUnknownProtos OBJECT-TYPE
   SYNTAX      Counter64
   MAX-ACCESS  read-only
   STATUS      current
   DESCRIPTION
      "Path: ethernet2.performance.pppoEClient.mibCounters.ifInUnknownProtos

       64 bit unsigned wrappable counter."
   ::= {pr1645v2Lan2FGUPPPoEEntry 41025536}

pr1645v2Lan2FGUPPPoEMCInDropEx OBJECT-TYPE
   SYNTAX      Counter64
   MAX-ACCESS  read-only
   STATUS      current
   DESCRIPTION
      "Path: ethernet2.performance.pppoEClient.mibCounters.ifInDropLevelExceeded

       64 bit unsigned wrappable counter."
   ::= {pr1645v2Lan2FGUPPPoEEntry 42074112}

pr1645v2Lan2FGUPPPoEMCInDropNoMac OBJECT-TYPE
   SYNTAX      Counter64
   MAX-ACCESS  read-only
   STATUS      current
   DESCRIPTION
      "Path: ethernet2.performance.pppoEClient.mibCounters.ifInDiscardsNoMacFit

       64 bit unsigned wrappable counter."
   ::= {pr1645v2Lan2FGUPPPoEEntry 42270720}

pr1645v2Lan2FGUPPPoEMCInDropNUCast OBJECT-TYPE
   SYNTAX      Counter64
   MAX-ACCESS  read-only
   STATUS      current
   DESCRIPTION
      "Path: ethernet2.performance.pppoEClient.mibCounters.ifInDiscardsNUCast

       64 bit unsigned wrappable counter."
   ::= {pr1645v2Lan2FGUPPPoEEntry 42467328}

pr1645v2Lan2FGUPPPoEMCInDropFilter OBJECT-TYPE
   SYNTAX      Counter64
   MAX-ACCESS  read-only
   STATUS      current
   DESCRIPTION
      "Path: ethernet2.performance.pppoEClient.mibCounters.ifInDiscardsFilter

       64 bit unsigned wrappable counter."
   ::= {pr1645v2Lan2FGUPPPoEEntry 42532864}

pr1645v2Lan2FGUPPPoEMCInBandwidth15sec OBJECT-TYPE
   SYNTAX      Integer32
   MAX-ACCESS  read-only
   STATUS      current
   DESCRIPTION
      "Path: ethernet2.performance.pppoEClient.mibCounters.ifInBandwidth.15sec

       unit name = bps
       formula = 8 * ; 8 /"
   ::= {pr1645v2Lan2FGUPPPoEEntry 45417728}

pr1645v2Lan2FGUPPPoEMCInBandwidth30sec OBJECT-TYPE
   SYNTAX      Integer32
   MAX-ACCESS  read-only
   STATUS      current
   DESCRIPTION
      "Path: ethernet2.performance.pppoEClient.mibCounters.ifInBandwidth.30sec

       unit name = bps
       formula = 8 * ; 8 /"
   ::= {pr1645v2Lan2FGUPPPoEEntry 45419008}

pr1645v2Lan2FGUPPPoEMCInBandwidth1min OBJECT-TYPE
   SYNTAX      Integer32
   MAX-ACCESS  read-only
   STATUS      current
   DESCRIPTION
      "Path: ethernet2.performance.pppoEClient.mibCounters.ifInBandwidth.1min

       unit name = bps
       formula = 8 * ; 8 /"
   ::= {pr1645v2Lan2FGUPPPoEEntry 45421568}

pr1645v2Lan2FGUPPPoEMCInBandwidth2min OBJECT-TYPE
   SYNTAX      Integer32
   MAX-ACCESS  read-only
   STATUS      current
   DESCRIPTION
      "Path: ethernet2.performance.pppoEClient.mibCounters.ifInBandwidth.2min

       unit name = bps
       formula = 8 * ; 8 /"
   ::= {pr1645v2Lan2FGUPPPoEEntry 45426688}

pr1645v2Lan2FGUPPPoEMCInBandwidth5min OBJECT-TYPE
   SYNTAX      Integer32
   MAX-ACCESS  read-only
   STATUS      current
   DESCRIPTION
      "Path: ethernet2.performance.pppoEClient.mibCounters.ifInBandwidth.5min

       unit name = bps
       formula = 8 * ; 8 /"
   ::= {pr1645v2Lan2FGUPPPoEEntry 45442048}

pr1645v2Lan2FGUPPPoEMCOutOctets OBJECT-TYPE
   SYNTAX      Counter64
   MAX-ACCESS  read-only
   STATUS      current
   DESCRIPTION
      "Path: ethernet2.performance.pppoEClient.mibCounters.ifOutOctets

       64 bit unsigned wrappable counter."
   ::= {pr1645v2Lan2FGUPPPoEEntry 41091072}

pr1645v2Lan2FGUPPPoEMCOutUcastPkts OBJECT-TYPE
   SYNTAX      Counter64
   MAX-ACCESS  read-only
   STATUS      current
   DESCRIPTION
      "Path: ethernet2.performance.pppoEClient.mibCounters.ifOutUcastPkts

       64 bit unsigned wrappable counter."
   ::= {pr1645v2Lan2FGUPPPoEEntry 41156608}

pr1645v2Lan2FGUPPPoEMCOutNUcastPkts OBJECT-TYPE
   SYNTAX      Counter64
   MAX-ACCESS  read-only
   STATUS      current
   DESCRIPTION
      "Path: ethernet2.performance.pppoEClient.mibCounters.ifOutNUcastPkts

       64 bit unsigned wrappable counter."
   ::= {pr1645v2Lan2FGUPPPoEEntry 41222144}

pr1645v2Lan2FGUPPPoEMCOutBcastPkts OBJECT-TYPE
   SYNTAX      Counter64
   MAX-ACCESS  read-only
   STATUS      current
   DESCRIPTION
      "Path: ethernet2.performance.pppoEClient.mibCounters.ifOutBcastPkts

       64 bit unsigned wrappable counter."
   ::= {pr1645v2Lan2FGUPPPoEEntry 47775744}

pr1645v2Lan2FGUPPPoEMCOutMcastPkts OBJECT-TYPE
   SYNTAX      Counter64
   MAX-ACCESS  read-only
   STATUS      current
   DESCRIPTION
      "Path: ethernet2.performance.pppoEClient.mibCounters.ifOutMcastPkts

       64 bit unsigned wrappable counter."
   ::= {pr1645v2Lan2FGUPPPoEEntry 48431104}

pr1645v2Lan2FGUPPPoEMCOutDiscards OBJECT-TYPE
   SYNTAX      Counter64
   MAX-ACCESS  read-only
   STATUS      current
   DESCRIPTION
      "Path: ethernet2.performance.pppoEClient.mibCounters.ifOutDiscards

       64 bit unsigned wrappable counter."
   ::= {pr1645v2Lan2FGUPPPoEEntry 41287680}

pr1645v2Lan2FGUPPPoEMCOutErrors OBJECT-TYPE
   SYNTAX      Counter64
   MAX-ACCESS  read-only
   STATUS      current
   DESCRIPTION
      "Path: ethernet2.performance.pppoEClient.mibCounters.ifOutErrors

       64 bit unsigned wrappable counter."
   ::= {pr1645v2Lan2FGUPPPoEEntry 41353216}

pr1645v2Lan2FGUPPPoEMCOutQLen OBJECT-TYPE
   SYNTAX      Counter32
   MAX-ACCESS  read-only
   STATUS      current
   DESCRIPTION
      "Path: ethernet2.performance.pppoEClient.mibCounters.ifOutQLen

       32 bit unsigned wrappable counter."
   ::= {pr1645v2Lan2FGUPPPoEEntry 41418752}

pr1645v2Lan2FGUPPPoEMCOutDropEx OBJECT-TYPE
   SYNTAX      Counter64
   MAX-ACCESS  read-only
   STATUS      current
   DESCRIPTION
      "Path: ethernet2.performance.pppoEClient.mibCounters.ifOutDropLevelExceeded

       64 bit unsigned wrappable counter."
   ::= {pr1645v2Lan2FGUPPPoEEntry 41484288}

pr1645v2Lan2FGUPPPoEMCOutDropNoArp OBJECT-TYPE
   SYNTAX      Counter64
   MAX-ACCESS  read-only
   STATUS      current
   DESCRIPTION
      "Path: ethernet2.performance.pppoEClient.mibCounters.ifOutDiscardsNoArp

       64 bit unsigned wrappable counter."
   ::= {pr1645v2Lan2FGUPPPoEEntry 42336256}

pr1645v2Lan2FGUPPPoEMCOutDropFilter OBJECT-TYPE
   SYNTAX      Counter64
   MAX-ACCESS  read-only
   STATUS      current
   DESCRIPTION
      "Path: ethernet2.performance.pppoEClient.mibCounters.ifOutDiscardsFilter

       64 bit unsigned wrappable counter."
   ::= {pr1645v2Lan2FGUPPPoEEntry 42598400}

pr1645v2Lan2FGUPPPoEMCOutBandwidth15sec OBJECT-TYPE
   SYNTAX      Integer32
   MAX-ACCESS  read-only
   STATUS      current
   DESCRIPTION
      "Path: ethernet2.performance.pppoEClient.mibCounters.ifOutBandwidth.15sec

       unit name = bps
       formula = 8 * ; 8 /"
   ::= {pr1645v2Lan2FGUPPPoEEntry 45483264}

pr1645v2Lan2FGUPPPoEMCOutBandwidth30sec OBJECT-TYPE
   SYNTAX      Integer32
   MAX-ACCESS  read-only
   STATUS      current
   DESCRIPTION
      "Path: ethernet2.performance.pppoEClient.mibCounters.ifOutBandwidth.30sec

       unit name = bps
       formula = 8 * ; 8 /"
   ::= {pr1645v2Lan2FGUPPPoEEntry 45484544}

pr1645v2Lan2FGUPPPoEMCOutBandwidth1min OBJECT-TYPE
   SYNTAX      Integer32
   MAX-ACCESS  read-only
   STATUS      current
   DESCRIPTION
      "Path: ethernet2.performance.pppoEClient.mibCounters.ifOutBandwidth.1min

       unit name = bps
       formula = 8 * ; 8 /"
   ::= {pr1645v2Lan2FGUPPPoEEntry 45487104}

pr1645v2Lan2FGUPPPoEMCOutBandwidth2min OBJECT-TYPE
   SYNTAX      Integer32
   MAX-ACCESS  read-only
   STATUS      current
   DESCRIPTION
      "Path: ethernet2.performance.pppoEClient.mibCounters.ifOutBandwidth.2min

       unit name = bps
       formula = 8 * ; 8 /"
   ::= {pr1645v2Lan2FGUPPPoEEntry 45492224}

pr1645v2Lan2FGUPPPoEMCOutBandwidth5min OBJECT-TYPE
   SYNTAX      Integer32
   MAX-ACCESS  read-only
   STATUS      current
   DESCRIPTION
      "Path: ethernet2.performance.pppoEClient.mibCounters.ifOutBandwidth.5min

       unit name = bps
       formula = 8 * ; 8 /"
   ::= {pr1645v2Lan2FGUPPPoEEntry 45507584}

pr1645v2Lan2FGUPPPoEPppLinkMonitoringRequestsSent OBJECT-TYPE
   SYNTAX      Gauge32
   MAX-ACCESS  read-only
   STATUS      current
   DESCRIPTION
      "Path: ethernet2.performance.pppoEClient.ppp.linkMonitoring.requestsSent

       32 bit unsigned gauge value."
   ::= {pr1645v2Lan2FGUPPPoEEntry 50397440}

pr1645v2Lan2FGUPPPoEPppLinkMonitoringRepliesRcvd OBJECT-TYPE
   SYNTAX      Gauge32
   MAX-ACCESS  read-only
   STATUS      current
   DESCRIPTION
      "Path: ethernet2.performance.pppoEClient.ppp.linkMonitoring.repliesRcvd

       32 bit unsigned gauge value."
   ::= {pr1645v2Lan2FGUPPPoEEntry 50397696}

pr1645v2Lan2FGUPPPoEPppLinkMonitoringRequestsRcvd OBJECT-TYPE
   SYNTAX      Gauge32
   MAX-ACCESS  read-only
   STATUS      current
   DESCRIPTION
      "Path: ethernet2.performance.pppoEClient.ppp.linkMonitoring.requestsRcvd

       32 bit unsigned gauge value."
   ::= {pr1645v2Lan2FGUPPPoEEntry 50397952}

pr1645v2Lan2FGUPPPoEPppLinkMonitoringRepliesSent OBJECT-TYPE
   SYNTAX      Gauge32
   MAX-ACCESS  read-only
   STATUS      current
   DESCRIPTION
      "Path: ethernet2.performance.pppoEClient.ppp.linkMonitoring.repliesSent

       32 bit unsigned gauge value."
   ::= {pr1645v2Lan2FGUPPPoEEntry 50398208}

pr1645v2Lan2FGUPPPoEMCH2P OBJECT-TYPE
   SYNTAX      SEQUENCE OF Pr1645v2Lan2FGUPPPoEMCH2PEntry
   MAX-ACCESS  not-accessible
   STATUS      current
   DESCRIPTION
      ""
   ::= {pr1645v2Lan2FGUPPPoE 41549824}

pr1645v2Lan2FGUPPPoEMCH2PEntry OBJECT-TYPE
   SYNTAX      Pr1645v2Lan2FGUPPPoEMCH2PEntry
   MAX-ACCESS  not-accessible
   STATUS      current
   DESCRIPTION
      ""
   INDEX      { pr1645v2Lan2FGUPPPoETableIx,
                pr1645v2Lan2FGUPPPoEMCH2PTableIx }
   ::= {pr1645v2Lan2FGUPPPoEMCH2P 1}

Pr1645v2Lan2FGUPPPoEMCH2PEntry ::=
   SEQUENCE
      {
      pr1645v2Lan2FGUPPPoEMCH2PTableIx
         TableIndex,
      pr1645v2Lan2FGUPPPoEMCH2PSysUpTime
         TimeTicks,
      pr1645v2Lan2FGUPPPoEMCH2PIfUpTime
         TimeTicks,
      pr1645v2Lan2FGUPPPoEMCH2PIfStatChanges
         Counter32,
      pr1645v2Lan2FGUPPPoEMCH2PIfInOctets
         Counter64,
      pr1645v2Lan2FGUPPPoEMCH2PIfInUCPkts
         Counter64,
      pr1645v2Lan2FGUPPPoEMCH2PIfInNUCPkts
         Counter64,
      pr1645v2Lan2FGUPPPoEMCH2PIfInBCPkts
         Counter64,
      pr1645v2Lan2FGUPPPoEMCH2PIfInMCPkts
         Counter64,
      pr1645v2Lan2FGUPPPoEMCH2PIfInDiscards
         Counter64,
      pr1645v2Lan2FGUPPPoEMCH2PIfInErrors
         Counter64,
      pr1645v2Lan2FGUPPPoEMCH2PIfInUnkwn
         Counter64,
      pr1645v2Lan2FGUPPPoEMCH2PInDropEx
         Counter64,
      pr1645v2Lan2FGUPPPoEMCH2PInDropNoMac
         Counter64,
      pr1645v2Lan2FGUPPPoEMCH2PInDropNUCast
         Counter64,
      pr1645v2Lan2FGUPPPoEMCH2PInDropFilter
         Counter64,
      pr1645v2Lan2FGUPPPoEMCH2PIfInBandwidth
         Integer32,
      pr1645v2Lan2FGUPPPoEMCH2PIfOutOctets
         Counter64,
      pr1645v2Lan2FGUPPPoEMCH2PIfOutUCPkts
         Counter64,
      pr1645v2Lan2FGUPPPoEMCH2PIfOutNUCPkts
         Counter64,
      pr1645v2Lan2FGUPPPoEMCH2PIfOutBCPkts
         Counter64,
      pr1645v2Lan2FGUPPPoEMCH2PIfOutMCPkts
         Counter64,
      pr1645v2Lan2FGUPPPoEMCH2PIfOutDiscards
         Counter64,
      pr1645v2Lan2FGUPPPoEMCH2PIfOutErrors
         Counter64,
      pr1645v2Lan2FGUPPPoEMCH2POutDropEx
         Counter64,
      pr1645v2Lan2FGUPPPoEMCH2POutDropNoArp
         Counter64,
      pr1645v2Lan2FGUPPPoEMCH2POutDropFilter
         Counter64,
      pr1645v2Lan2FGUPPPoEMCH2PIfOutBandwidth
         Integer32,
      pr1645v2Lan2FGUPPPoEMCH2PIfErrSec
         Counter32
      }

pr1645v2Lan2FGUPPPoEMCH2PTableIx OBJECT-TYPE
   SYNTAX      TableIndex
   MAX-ACCESS  not-accessible
   STATUS      current
   DESCRIPTION
      ""
   ::= {pr1645v2Lan2FGUPPPoEMCH2PEntry 11}

pr1645v2Lan2FGUPPPoEMCH2PSysUpTime OBJECT-TYPE
   SYNTAX      TimeTicks
   MAX-ACCESS  read-only
   STATUS      current
   DESCRIPTION
      "Path: ethernet2.performance.pppoEClient.mibCounters.h2Performance.sysUpTime

       Time in centi-second."
   ::= {pr1645v2Lan2FGUPPPoEMCH2PEntry 16777216}

pr1645v2Lan2FGUPPPoEMCH2PIfUpTime OBJECT-TYPE
   SYNTAX      TimeTicks
   MAX-ACCESS  read-only
   STATUS      current
   DESCRIPTION
      "Path: ethernet2.performance.pppoEClient.mibCounters.h2Performance.ifUpTime

       Time in centi-second."
   ::= {pr1645v2Lan2FGUPPPoEMCH2PEntry 33554432}

pr1645v2Lan2FGUPPPoEMCH2PIfStatChanges OBJECT-TYPE
   SYNTAX      Counter32
   MAX-ACCESS  read-only
   STATUS      current
   DESCRIPTION
      "Path: ethernet2.performance.pppoEClient.mibCounters.h2Performance.ifStatusChanges

       32 bit unsigned wrappable counter."
   ::= {pr1645v2Lan2FGUPPPoEMCH2PEntry 50331648}

pr1645v2Lan2FGUPPPoEMCH2PIfInOctets OBJECT-TYPE
   SYNTAX      Counter64
   MAX-ACCESS  read-only
   STATUS      current
   DESCRIPTION
      "Path: ethernet2.performance.pppoEClient.mibCounters.h2Performance.ifInOctets

       64 bit unsigned wrappable counter."
   ::= {pr1645v2Lan2FGUPPPoEMCH2PEntry 67108864}

pr1645v2Lan2FGUPPPoEMCH2PIfInUCPkts OBJECT-TYPE
   SYNTAX      Counter64
   MAX-ACCESS  read-only
   STATUS      current
   DESCRIPTION
      "Path: ethernet2.performance.pppoEClient.mibCounters.h2Performance.ifInUcastPkts

       64 bit unsigned wrappable counter."
   ::= {pr1645v2Lan2FGUPPPoEMCH2PEntry 83886080}

pr1645v2Lan2FGUPPPoEMCH2PIfInNUCPkts OBJECT-TYPE
   SYNTAX      Counter64
   MAX-ACCESS  read-only
   STATUS      current
   DESCRIPTION
      "Path: ethernet2.performance.pppoEClient.mibCounters.h2Performance.ifInNUcastPkts

       64 bit unsigned wrappable counter."
   ::= {pr1645v2Lan2FGUPPPoEMCH2PEntry 100663296}

pr1645v2Lan2FGUPPPoEMCH2PIfInBCPkts OBJECT-TYPE
   SYNTAX      Counter64
   MAX-ACCESS  read-only
   STATUS      current
   DESCRIPTION
      "Path: ethernet2.performance.pppoEClient.mibCounters.h2Performance.ifInBcastPkts

       64 bit unsigned wrappable counter."
   ::= {pr1645v2Lan2FGUPPPoEMCH2PEntry 419430400}

pr1645v2Lan2FGUPPPoEMCH2PIfInMCPkts OBJECT-TYPE
   SYNTAX      Counter64
   MAX-ACCESS  read-only
   STATUS      current
   DESCRIPTION
      "Path: ethernet2.performance.pppoEClient.mibCounters.h2Performance.ifInMcastPkts

       64 bit unsigned wrappable counter."
   ::= {pr1645v2Lan2FGUPPPoEMCH2PEntry 436207616}

pr1645v2Lan2FGUPPPoEMCH2PIfInDiscards OBJECT-TYPE
   SYNTAX      Counter64
   MAX-ACCESS  read-only
   STATUS      current
   DESCRIPTION
      "Path: ethernet2.performance.pppoEClient.mibCounters.h2Performance.ifInDiscards

       64 bit unsigned wrappable counter."
   ::= {pr1645v2Lan2FGUPPPoEMCH2PEntry 117440512}

pr1645v2Lan2FGUPPPoEMCH2PIfInErrors OBJECT-TYPE
   SYNTAX      Counter64
   MAX-ACCESS  read-only
   STATUS      current
   DESCRIPTION
      "Path: ethernet2.performance.pppoEClient.mibCounters.h2Performance.ifInErrors

       64 bit unsigned wrappable counter."
   ::= {pr1645v2Lan2FGUPPPoEMCH2PEntry 134217728}

pr1645v2Lan2FGUPPPoEMCH2PIfInUnkwn OBJECT-TYPE
   SYNTAX      Counter64
   MAX-ACCESS  read-only
   STATUS      current
   DESCRIPTION
      "Path: ethernet2.performance.pppoEClient.mibCounters.h2Performance.ifInUnknownProtos

       64 bit unsigned wrappable counter."
   ::= {pr1645v2Lan2FGUPPPoEMCH2PEntry 150994944}

pr1645v2Lan2FGUPPPoEMCH2PInDropEx OBJECT-TYPE
   SYNTAX      Counter64
   MAX-ACCESS  read-only
   STATUS      current
   DESCRIPTION
      "Path: ethernet2.performance.pppoEClient.mibCounters.h2Performance.ifInDropLevelExceeded

       64 bit unsigned wrappable counter."
   ::= {pr1645v2Lan2FGUPPPoEMCH2PEntry 335544320}

pr1645v2Lan2FGUPPPoEMCH2PInDropNoMac OBJECT-TYPE
   SYNTAX      Counter64
   MAX-ACCESS  read-only
   STATUS      current
   DESCRIPTION
      "Path: ethernet2.performance.pppoEClient.mibCounters.h2Performance.fInDiscardsNoMacFit

       64 bit unsigned wrappable counter."
   ::= {pr1645v2Lan2FGUPPPoEMCH2PEntry 301989888}

pr1645v2Lan2FGUPPPoEMCH2PInDropNUCast OBJECT-TYPE
   SYNTAX      Counter64
   MAX-ACCESS  read-only
   STATUS      current
   DESCRIPTION
      "Path: ethernet2.performance.pppoEClient.mibCounters.h2Performance.fInDiscardsNUCast

       64 bit unsigned wrappable counter."
   ::= {pr1645v2Lan2FGUPPPoEMCH2PEntry 318767104}

pr1645v2Lan2FGUPPPoEMCH2PInDropFilter OBJECT-TYPE
   SYNTAX      Counter64
   MAX-ACCESS  read-only
   STATUS      current
   DESCRIPTION
      "Path: ethernet2.performance.pppoEClient.mibCounters.h2Performance.fInDiscardsFilter

       64 bit unsigned wrappable counter."
   ::= {pr1645v2Lan2FGUPPPoEMCH2PEntry 385875968}

pr1645v2Lan2FGUPPPoEMCH2PIfInBandwidth OBJECT-TYPE
   SYNTAX      Integer32
   MAX-ACCESS  read-only
   STATUS      current
   DESCRIPTION
      "Path: ethernet2.performance.pppoEClient.mibCounters.h2Performance.ifInBandwidth

       unit name = bps
       formula = 8 * ; 8 /"
   ::= {pr1645v2Lan2FGUPPPoEMCH2PEntry 268435456}

pr1645v2Lan2FGUPPPoEMCH2PIfOutOctets OBJECT-TYPE
   SYNTAX      Counter64
   MAX-ACCESS  read-only
   STATUS      current
   DESCRIPTION
      "Path: ethernet2.performance.pppoEClient.mibCounters.h2Performance.ifOutOctets

       64 bit unsigned wrappable counter."
   ::= {pr1645v2Lan2FGUPPPoEMCH2PEntry 167772160}

pr1645v2Lan2FGUPPPoEMCH2PIfOutUCPkts OBJECT-TYPE
   SYNTAX      Counter64
   MAX-ACCESS  read-only
   STATUS      current
   DESCRIPTION
      "Path: ethernet2.performance.pppoEClient.mibCounters.h2Performance.ifOutUcastPkts

       64 bit unsigned wrappable counter."
   ::= {pr1645v2Lan2FGUPPPoEMCH2PEntry 184549376}

pr1645v2Lan2FGUPPPoEMCH2PIfOutNUCPkts OBJECT-TYPE
   SYNTAX      Counter64
   MAX-ACCESS  read-only
   STATUS      current
   DESCRIPTION
      "Path: ethernet2.performance.pppoEClient.mibCounters.h2Performance.ifOutNUcastPkts

       64 bit unsigned wrappable counter."
   ::= {pr1645v2Lan2FGUPPPoEMCH2PEntry 201326592}

pr1645v2Lan2FGUPPPoEMCH2PIfOutBCPkts OBJECT-TYPE
   SYNTAX      Counter64
   MAX-ACCESS  read-only
   STATUS      current
   DESCRIPTION
      "Path: ethernet2.performance.pppoEClient.mibCounters.h2Performance.ifOutBcastPkts

       64 bit unsigned wrappable counter."
   ::= {pr1645v2Lan2FGUPPPoEMCH2PEntry 452984832}

pr1645v2Lan2FGUPPPoEMCH2PIfOutMCPkts OBJECT-TYPE
   SYNTAX      Counter64
   MAX-ACCESS  read-only
   STATUS      current
   DESCRIPTION
      "Path: ethernet2.performance.pppoEClient.mibCounters.h2Performance.ifOutMcastPkts

       64 bit unsigned wrappable counter."
   ::= {pr1645v2Lan2FGUPPPoEMCH2PEntry 469762048}

pr1645v2Lan2FGUPPPoEMCH2PIfOutDiscards OBJECT-TYPE
   SYNTAX      Counter64
   MAX-ACCESS  read-only
   STATUS      current
   DESCRIPTION
      "Path: ethernet2.performance.pppoEClient.mibCounters.h2Performance.ifOutDiscards

       64 bit unsigned wrappable counter."
   ::= {pr1645v2Lan2FGUPPPoEMCH2PEntry 218103808}

pr1645v2Lan2FGUPPPoEMCH2PIfOutErrors OBJECT-TYPE
   SYNTAX      Counter64
   MAX-ACCESS  read-only
   STATUS      current
   DESCRIPTION
      "Path: ethernet2.performance.pppoEClient.mibCounters.h2Performance.ifOutErrors

       64 bit unsigned wrappable counter."
   ::= {pr1645v2Lan2FGUPPPoEMCH2PEntry 234881024}

pr1645v2Lan2FGUPPPoEMCH2POutDropEx OBJECT-TYPE
   SYNTAX      Counter64
   MAX-ACCESS  read-only
   STATUS      current
   DESCRIPTION
      "Path: ethernet2.performance.pppoEClient.mibCounters.h2Performance.ifOutDropLevelExceeded

       64 bit unsigned wrappable counter."
   ::= {pr1645v2Lan2FGUPPPoEMCH2PEntry 352321536}

pr1645v2Lan2FGUPPPoEMCH2POutDropNoArp OBJECT-TYPE
   SYNTAX      Counter64
   MAX-ACCESS  read-only
   STATUS      current
   DESCRIPTION
      "Path: ethernet2.performance.pppoEClient.mibCounters.h2Performance.ifOutDiscardsNoArp

       64 bit unsigned wrappable counter."
   ::= {pr1645v2Lan2FGUPPPoEMCH2PEntry 369098752}

pr1645v2Lan2FGUPPPoEMCH2POutDropFilter OBJECT-TYPE
   SYNTAX      Counter64
   MAX-ACCESS  read-only
   STATUS      current
   DESCRIPTION
      "Path: ethernet2.performance.pppoEClient.mibCounters.h2Performance.ifOutDiscardsFilter

       64 bit unsigned wrappable counter."
   ::= {pr1645v2Lan2FGUPPPoEMCH2PEntry 402653184}

pr1645v2Lan2FGUPPPoEMCH2PIfOutBandwidth OBJECT-TYPE
   SYNTAX      Integer32
   MAX-ACCESS  read-only
   STATUS      current
   DESCRIPTION
      "Path: ethernet2.performance.pppoEClient.mibCounters.h2Performance.ifOutBandwidth

       unit name = bps
       formula = 8 * ; 8 /"
   ::= {pr1645v2Lan2FGUPPPoEMCH2PEntry 285212672}

pr1645v2Lan2FGUPPPoEMCH2PIfErrSec OBJECT-TYPE
   SYNTAX      Counter32
   MAX-ACCESS  read-only
   STATUS      current
   DESCRIPTION
      "Path: ethernet2.performance.pppoEClient.mibCounters.h2Performance.ifErrSec

       32 bit unsigned wrappable counter."
   ::= {pr1645v2Lan2FGUPPPoEMCH2PEntry 251658240}

pr1645v2Lan2FGUPPPoEMCH24P OBJECT-TYPE
   SYNTAX      SEQUENCE OF Pr1645v2Lan2FGUPPPoEMCH24PEntry
   MAX-ACCESS  not-accessible
   STATUS      current
   DESCRIPTION
      ""
   ::= {pr1645v2Lan2FGUPPPoE 41615360}

pr1645v2Lan2FGUPPPoEMCH24PEntry OBJECT-TYPE
   SYNTAX      Pr1645v2Lan2FGUPPPoEMCH24PEntry
   MAX-ACCESS  not-accessible
   STATUS      current
   DESCRIPTION
      ""
   INDEX      { pr1645v2Lan2FGUPPPoETableIx,
                pr1645v2Lan2FGUPPPoEMCH24PTableIx }
   ::= {pr1645v2Lan2FGUPPPoEMCH24P 1}

Pr1645v2Lan2FGUPPPoEMCH24PEntry ::=
   SEQUENCE
      {
      pr1645v2Lan2FGUPPPoEMCH24PTableIx
         TableIndex,
      pr1645v2Lan2FGUPPPoEMCH24PSysUpTime
         TimeTicks,
      pr1645v2Lan2FGUPPPoEMCH24PIfUpTime
         TimeTicks,
      pr1645v2Lan2FGUPPPoEMCH24PIfStatChanges
         Counter32,
      pr1645v2Lan2FGUPPPoEMCH24PIfInOctets
         Counter64,
      pr1645v2Lan2FGUPPPoEMCH24PIfInUCPkts
         Counter64,
      pr1645v2Lan2FGUPPPoEMCH24PIfInNUCPkts
         Counter64,
      pr1645v2Lan2FGUPPPoEMCH24PIfInBCPkts
         Counter64,
      pr1645v2Lan2FGUPPPoEMCH24PIfInMCPkts
         Counter64,
      pr1645v2Lan2FGUPPPoEMCH24PIfInDiscards
         Counter64,
      pr1645v2Lan2FGUPPPoEMCH24PIfInErrors
         Counter64,
      pr1645v2Lan2FGUPPPoEMCH24PIfInUnkwn
         Counter64,
      pr1645v2Lan2FGUPPPoEMCH24PInDropEx
         Counter64,
      pr1645v2Lan2FGUPPPoEMCH24PInDropNoMac
         Counter64,
      pr1645v2Lan2FGUPPPoEMCH24PInDropNUCast
         Counter64,
      pr1645v2Lan2FGUPPPoEMCH24PInDropFilter
         Counter64,
      pr1645v2Lan2FGUPPPoEMCH24PIfInBandwidth
         Integer32,
      pr1645v2Lan2FGUPPPoEMCH24PIfOutOctets
         Counter64,
      pr1645v2Lan2FGUPPPoEMCH24PIfOutUCPkts
         Counter64,
      pr1645v2Lan2FGUPPPoEMCH24PIfOutNUCPkts
         Counter64,
      pr1645v2Lan2FGUPPPoEMCH24PIfOutBCPkts
         Counter64,
      pr1645v2Lan2FGUPPPoEMCH24PIfOutMCPkts
         Counter64,
      pr1645v2Lan2FGUPPPoEMCH24PIfOutDiscards
         Counter64,
      pr1645v2Lan2FGUPPPoEMCH24PIfOutErrors
         Counter64,
      pr1645v2Lan2FGUPPPoEMCH24POutDropEx
         Counter64,
      pr1645v2Lan2FGUPPPoEMCH24POutDropNoArp
         Counter64,
      pr1645v2Lan2FGUPPPoEMCH24POutDropFilter
         Counter64,
      pr1645v2Lan2FGUPPPoEMCH24PIfOutBandwidth
         Integer32,
      pr1645v2Lan2FGUPPPoEMCH24PIfErrSec
         Counter32
      }

pr1645v2Lan2FGUPPPoEMCH24PTableIx OBJECT-TYPE
   SYNTAX      TableIndex
   MAX-ACCESS  not-accessible
   STATUS      current
   DESCRIPTION
      ""
   ::= {pr1645v2Lan2FGUPPPoEMCH24PEntry 11}

pr1645v2Lan2FGUPPPoEMCH24PSysUpTime OBJECT-TYPE
   SYNTAX      TimeTicks
   MAX-ACCESS  read-only
   STATUS      current
   DESCRIPTION
      "Path: ethernet2.performance.pppoEClient.mibCounters.h24Performance.sysUpTime

       Time in centi-second."
   ::= {pr1645v2Lan2FGUPPPoEMCH24PEntry 16777216}

pr1645v2Lan2FGUPPPoEMCH24PIfUpTime OBJECT-TYPE
   SYNTAX      TimeTicks
   MAX-ACCESS  read-only
   STATUS      current
   DESCRIPTION
      "Path: ethernet2.performance.pppoEClient.mibCounters.h24Performance.ifUpTime

       Time in centi-second."
   ::= {pr1645v2Lan2FGUPPPoEMCH24PEntry 33554432}

pr1645v2Lan2FGUPPPoEMCH24PIfStatChanges OBJECT-TYPE
   SYNTAX      Counter32
   MAX-ACCESS  read-only
   STATUS      current
   DESCRIPTION
      "Path: ethernet2.performance.pppoEClient.mibCounters.h24Performance.ifStatusChanges

       32 bit unsigned wrappable counter."
   ::= {pr1645v2Lan2FGUPPPoEMCH24PEntry 50331648}

pr1645v2Lan2FGUPPPoEMCH24PIfInOctets OBJECT-TYPE
   SYNTAX      Counter64
   MAX-ACCESS  read-only
   STATUS      current
   DESCRIPTION
      "Path: ethernet2.performance.pppoEClient.mibCounters.h24Performance.ifInOctets

       64 bit unsigned wrappable counter."
   ::= {pr1645v2Lan2FGUPPPoEMCH24PEntry 67108864}

pr1645v2Lan2FGUPPPoEMCH24PIfInUCPkts OBJECT-TYPE
   SYNTAX      Counter64
   MAX-ACCESS  read-only
   STATUS      current
   DESCRIPTION
      "Path: ethernet2.performance.pppoEClient.mibCounters.h24Performance.ifInUcastPkts

       64 bit unsigned wrappable counter."
   ::= {pr1645v2Lan2FGUPPPoEMCH24PEntry 83886080}

pr1645v2Lan2FGUPPPoEMCH24PIfInNUCPkts OBJECT-TYPE
   SYNTAX      Counter64
   MAX-ACCESS  read-only
   STATUS      current
   DESCRIPTION
      "Path: ethernet2.performance.pppoEClient.mibCounters.h24Performance.ifInNUcastPkts

       64 bit unsigned wrappable counter."
   ::= {pr1645v2Lan2FGUPPPoEMCH24PEntry 100663296}

pr1645v2Lan2FGUPPPoEMCH24PIfInBCPkts OBJECT-TYPE
   SYNTAX      Counter64
   MAX-ACCESS  read-only
   STATUS      current
   DESCRIPTION
      "Path: ethernet2.performance.pppoEClient.mibCounters.h24Performance.ifInBcastPkts

       64 bit unsigned wrappable counter."
   ::= {pr1645v2Lan2FGUPPPoEMCH24PEntry 419430400}

pr1645v2Lan2FGUPPPoEMCH24PIfInMCPkts OBJECT-TYPE
   SYNTAX      Counter64
   MAX-ACCESS  read-only
   STATUS      current
   DESCRIPTION
      "Path: ethernet2.performance.pppoEClient.mibCounters.h24Performance.ifInMcastPkts

       64 bit unsigned wrappable counter."
   ::= {pr1645v2Lan2FGUPPPoEMCH24PEntry 436207616}

pr1645v2Lan2FGUPPPoEMCH24PIfInDiscards OBJECT-TYPE
   SYNTAX      Counter64
   MAX-ACCESS  read-only
   STATUS      current
   DESCRIPTION
      "Path: ethernet2.performance.pppoEClient.mibCounters.h24Performance.ifInDiscards

       64 bit unsigned wrappable counter."
   ::= {pr1645v2Lan2FGUPPPoEMCH24PEntry 117440512}

pr1645v2Lan2FGUPPPoEMCH24PIfInErrors OBJECT-TYPE
   SYNTAX      Counter64
   MAX-ACCESS  read-only
   STATUS      current
   DESCRIPTION
      "Path: ethernet2.performance.pppoEClient.mibCounters.h24Performance.ifInErrors

       64 bit unsigned wrappable counter."
   ::= {pr1645v2Lan2FGUPPPoEMCH24PEntry 134217728}

pr1645v2Lan2FGUPPPoEMCH24PIfInUnkwn OBJECT-TYPE
   SYNTAX      Counter64
   MAX-ACCESS  read-only
   STATUS      current
   DESCRIPTION
      "Path: ethernet2.performance.pppoEClient.mibCounters.h24Performance.ifInUnknownProtos

       64 bit unsigned wrappable counter."
   ::= {pr1645v2Lan2FGUPPPoEMCH24PEntry 150994944}

pr1645v2Lan2FGUPPPoEMCH24PInDropEx OBJECT-TYPE
   SYNTAX      Counter64
   MAX-ACCESS  read-only
   STATUS      current
   DESCRIPTION
      "Path: ethernet2.performance.pppoEClient.mibCounters.h24Performance.ifInDropLevelExceeded

       64 bit unsigned wrappable counter."
   ::= {pr1645v2Lan2FGUPPPoEMCH24PEntry 335544320}

pr1645v2Lan2FGUPPPoEMCH24PInDropNoMac OBJECT-TYPE
   SYNTAX      Counter64
   MAX-ACCESS  read-only
   STATUS      current
   DESCRIPTION
      "Path: ethernet2.performance.pppoEClient.mibCounters.h24Performance.fInDiscardsNoMacFit

       64 bit unsigned wrappable counter."
   ::= {pr1645v2Lan2FGUPPPoEMCH24PEntry 301989888}

pr1645v2Lan2FGUPPPoEMCH24PInDropNUCast OBJECT-TYPE
   SYNTAX      Counter64
   MAX-ACCESS  read-only
   STATUS      current
   DESCRIPTION
      "Path: ethernet2.performance.pppoEClient.mibCounters.h24Performance.fInDiscardsNUCast

       64 bit unsigned wrappable counter."
   ::= {pr1645v2Lan2FGUPPPoEMCH24PEntry 318767104}

pr1645v2Lan2FGUPPPoEMCH24PInDropFilter OBJECT-TYPE
   SYNTAX      Counter64
   MAX-ACCESS  read-only
   STATUS      current
   DESCRIPTION
      "Path: ethernet2.performance.pppoEClient.mibCounters.h24Performance.fInDiscardsFilter

       64 bit unsigned wrappable counter."
   ::= {pr1645v2Lan2FGUPPPoEMCH24PEntry 385875968}

pr1645v2Lan2FGUPPPoEMCH24PIfInBandwidth OBJECT-TYPE
   SYNTAX      Integer32
   MAX-ACCESS  read-only
   STATUS      current
   DESCRIPTION
      "Path: ethernet2.performance.pppoEClient.mibCounters.h24Performance.ifInBandwidth

       unit name = bps
       formula = 8 * ; 8 /"
   ::= {pr1645v2Lan2FGUPPPoEMCH24PEntry 268435456}

pr1645v2Lan2FGUPPPoEMCH24PIfOutOctets OBJECT-TYPE
   SYNTAX      Counter64
   MAX-ACCESS  read-only
   STATUS      current
   DESCRIPTION
      "Path: ethernet2.performance.pppoEClient.mibCounters.h24Performance.ifOutOctets

       64 bit unsigned wrappable counter."
   ::= {pr1645v2Lan2FGUPPPoEMCH24PEntry 167772160}

pr1645v2Lan2FGUPPPoEMCH24PIfOutUCPkts OBJECT-TYPE
   SYNTAX      Counter64
   MAX-ACCESS  read-only
   STATUS      current
   DESCRIPTION
      "Path: ethernet2.performance.pppoEClient.mibCounters.h24Performance.ifOutUcastPkts

       64 bit unsigned wrappable counter."
   ::= {pr1645v2Lan2FGUPPPoEMCH24PEntry 184549376}

pr1645v2Lan2FGUPPPoEMCH24PIfOutNUCPkts OBJECT-TYPE
   SYNTAX      Counter64
   MAX-ACCESS  read-only
   STATUS      current
   DESCRIPTION
      "Path: ethernet2.performance.pppoEClient.mibCounters.h24Performance.ifOutNUcastPkts

       64 bit unsigned wrappable counter."
   ::= {pr1645v2Lan2FGUPPPoEMCH24PEntry 201326592}

pr1645v2Lan2FGUPPPoEMCH24PIfOutBCPkts OBJECT-TYPE
   SYNTAX      Counter64
   MAX-ACCESS  read-only
   STATUS      current
   DESCRIPTION
      "Path: ethernet2.performance.pppoEClient.mibCounters.h24Performance.ifOutBcastPkts

       64 bit unsigned wrappable counter."
   ::= {pr1645v2Lan2FGUPPPoEMCH24PEntry 452984832}

pr1645v2Lan2FGUPPPoEMCH24PIfOutMCPkts OBJECT-TYPE
   SYNTAX      Counter64
   MAX-ACCESS  read-only
   STATUS      current
   DESCRIPTION
      "Path: ethernet2.performance.pppoEClient.mibCounters.h24Performance.ifOutMcastPkts

       64 bit unsigned wrappable counter."
   ::= {pr1645v2Lan2FGUPPPoEMCH24PEntry 469762048}

pr1645v2Lan2FGUPPPoEMCH24PIfOutDiscards OBJECT-TYPE
   SYNTAX      Counter64
   MAX-ACCESS  read-only
   STATUS      current
   DESCRIPTION
      "Path: ethernet2.performance.pppoEClient.mibCounters.h24Performance.ifOutDiscards

       64 bit unsigned wrappable counter."
   ::= {pr1645v2Lan2FGUPPPoEMCH24PEntry 218103808}

pr1645v2Lan2FGUPPPoEMCH24PIfOutErrors OBJECT-TYPE
   SYNTAX      Counter64
   MAX-ACCESS  read-only
   STATUS      current
   DESCRIPTION
      "Path: ethernet2.performance.pppoEClient.mibCounters.h24Performance.ifOutErrors

       64 bit unsigned wrappable counter."
   ::= {pr1645v2Lan2FGUPPPoEMCH24PEntry 234881024}

pr1645v2Lan2FGUPPPoEMCH24POutDropEx OBJECT-TYPE
   SYNTAX      Counter64
   MAX-ACCESS  read-only
   STATUS      current
   DESCRIPTION
      "Path: ethernet2.performance.pppoEClient.mibCounters.h24Performance.ifOutDropLevelExceeded

       64 bit unsigned wrappable counter."
   ::= {pr1645v2Lan2FGUPPPoEMCH24PEntry 352321536}

pr1645v2Lan2FGUPPPoEMCH24POutDropNoArp OBJECT-TYPE
   SYNTAX      Counter64
   MAX-ACCESS  read-only
   STATUS      current
   DESCRIPTION
      "Path: ethernet2.performance.pppoEClient.mibCounters.h24Performance.ifOutDiscardsNoArp

       64 bit unsigned wrappable counter."
   ::= {pr1645v2Lan2FGUPPPoEMCH24PEntry 369098752}

pr1645v2Lan2FGUPPPoEMCH24POutDropFilter OBJECT-TYPE
   SYNTAX      Counter64
   MAX-ACCESS  read-only
   STATUS      current
   DESCRIPTION
      "Path: ethernet2.performance.pppoEClient.mibCounters.h24Performance.ifOutDiscardsFilter

       64 bit unsigned wrappable counter."
   ::= {pr1645v2Lan2FGUPPPoEMCH24PEntry 402653184}

pr1645v2Lan2FGUPPPoEMCH24PIfOutBandwidth OBJECT-TYPE
   SYNTAX      Integer32
   MAX-ACCESS  read-only
   STATUS      current
   DESCRIPTION
      "Path: ethernet2.performance.pppoEClient.mibCounters.h24Performance.ifOutBandwidth

       unit name = bps
       formula = 8 * ; 8 /"
   ::= {pr1645v2Lan2FGUPPPoEMCH24PEntry 285212672}

pr1645v2Lan2FGUPPPoEMCH24PIfErrSec OBJECT-TYPE
   SYNTAX      Counter32
   MAX-ACCESS  read-only
   STATUS      current
   DESCRIPTION
      "Path: ethernet2.performance.pppoEClient.mibCounters.h24Performance.ifErrSec

       32 bit unsigned wrappable counter."
   ::= {pr1645v2Lan2FGUPPPoEMCH24PEntry 251658240}

pr1645v2Lan2FGUPPPoEMCD7P OBJECT-TYPE
   SYNTAX      SEQUENCE OF Pr1645v2Lan2FGUPPPoEMCD7PEntry
   MAX-ACCESS  not-accessible
   STATUS      current
   DESCRIPTION
      ""
   ::= {pr1645v2Lan2FGUPPPoE 41680896}

pr1645v2Lan2FGUPPPoEMCD7PEntry OBJECT-TYPE
   SYNTAX      Pr1645v2Lan2FGUPPPoEMCD7PEntry
   MAX-ACCESS  not-accessible
   STATUS      current
   DESCRIPTION
      ""
   INDEX      { pr1645v2Lan2FGUPPPoETableIx,
                pr1645v2Lan2FGUPPPoEMCD7PTableIx }
   ::= {pr1645v2Lan2FGUPPPoEMCD7P 1}

Pr1645v2Lan2FGUPPPoEMCD7PEntry ::=
   SEQUENCE
      {
      pr1645v2Lan2FGUPPPoEMCD7PTableIx
         TableIndex,
      pr1645v2Lan2FGUPPPoEMCD7PSysUpTime
         TimeTicks,
      pr1645v2Lan2FGUPPPoEMCD7PIfUpTime
         TimeTicks,
      pr1645v2Lan2FGUPPPoEMCD7PIfStatChanges
         Counter32,
      pr1645v2Lan2FGUPPPoEMCD7PIfInOctets
         Counter64,
      pr1645v2Lan2FGUPPPoEMCD7PIfInUCPkts
         Counter64,
      pr1645v2Lan2FGUPPPoEMCD7PIfInNUCPkts
         Counter64,
      pr1645v2Lan2FGUPPPoEMCD7PIfInBCPkts
         Counter64,
      pr1645v2Lan2FGUPPPoEMCD7PIfInMCPkts
         Counter64,
      pr1645v2Lan2FGUPPPoEMCD7PIfInDiscards
         Counter64,
      pr1645v2Lan2FGUPPPoEMCD7PIfInErrors
         Counter64,
      pr1645v2Lan2FGUPPPoEMCD7PIfInUnkwn
         Counter64,
      pr1645v2Lan2FGUPPPoEMCD7PInDropEx
         Counter64,
      pr1645v2Lan2FGUPPPoEMCD7PInDropNoMac
         Counter64,
      pr1645v2Lan2FGUPPPoEMCD7PInDropNUCast
         Counter64,
      pr1645v2Lan2FGUPPPoEMCD7PInDropFilter
         Counter64,
      pr1645v2Lan2FGUPPPoEMCD7PIfInBandwidth
         Integer32,
      pr1645v2Lan2FGUPPPoEMCD7PIfOutOctets
         Counter64,
      pr1645v2Lan2FGUPPPoEMCD7PIfOutUCPkts
         Counter64,
      pr1645v2Lan2FGUPPPoEMCD7PIfOutNUCPkts
         Counter64,
      pr1645v2Lan2FGUPPPoEMCD7PIfOutBCPkts
         Counter64,
      pr1645v2Lan2FGUPPPoEMCD7PIfOutMCPkts
         Counter64,
      pr1645v2Lan2FGUPPPoEMCD7PIfOutDiscards
         Counter64,
      pr1645v2Lan2FGUPPPoEMCD7PIfOutErrors
         Counter64,
      pr1645v2Lan2FGUPPPoEMCD7POutDropEx
         Counter64,
      pr1645v2Lan2FGUPPPoEMCD7POutDropNoArp
         Counter64,
      pr1645v2Lan2FGUPPPoEMCD7POutDropFilter
         Counter64,
      pr1645v2Lan2FGUPPPoEMCD7PIfOutBandwidth
         Integer32,
      pr1645v2Lan2FGUPPPoEMCD7PIfErrSec
         Counter32
      }

pr1645v2Lan2FGUPPPoEMCD7PTableIx OBJECT-TYPE
   SYNTAX      TableIndex
   MAX-ACCESS  not-accessible
   STATUS      current
   DESCRIPTION
      ""
   ::= {pr1645v2Lan2FGUPPPoEMCD7PEntry 11}

pr1645v2Lan2FGUPPPoEMCD7PSysUpTime OBJECT-TYPE
   SYNTAX      TimeTicks
   MAX-ACCESS  read-only
   STATUS      current
   DESCRIPTION
      "Path: ethernet2.performance.pppoEClient.mibCounters.d7Performance.sysUpTime

       Time in centi-second."
   ::= {pr1645v2Lan2FGUPPPoEMCD7PEntry 16777216}

pr1645v2Lan2FGUPPPoEMCD7PIfUpTime OBJECT-TYPE
   SYNTAX      TimeTicks
   MAX-ACCESS  read-only
   STATUS      current
   DESCRIPTION
      "Path: ethernet2.performance.pppoEClient.mibCounters.d7Performance.ifUpTime

       Time in centi-second."
   ::= {pr1645v2Lan2FGUPPPoEMCD7PEntry 33554432}

pr1645v2Lan2FGUPPPoEMCD7PIfStatChanges OBJECT-TYPE
   SYNTAX      Counter32
   MAX-ACCESS  read-only
   STATUS      current
   DESCRIPTION
      "Path: ethernet2.performance.pppoEClient.mibCounters.d7Performance.ifStatusChanges

       32 bit unsigned wrappable counter."
   ::= {pr1645v2Lan2FGUPPPoEMCD7PEntry 50331648}

pr1645v2Lan2FGUPPPoEMCD7PIfInOctets OBJECT-TYPE
   SYNTAX      Counter64
   MAX-ACCESS  read-only
   STATUS      current
   DESCRIPTION
      "Path: ethernet2.performance.pppoEClient.mibCounters.d7Performance.ifInOctets

       64 bit unsigned wrappable counter."
   ::= {pr1645v2Lan2FGUPPPoEMCD7PEntry 67108864}

pr1645v2Lan2FGUPPPoEMCD7PIfInUCPkts OBJECT-TYPE
   SYNTAX      Counter64
   MAX-ACCESS  read-only
   STATUS      current
   DESCRIPTION
      "Path: ethernet2.performance.pppoEClient.mibCounters.d7Performance.ifInUcastPkts

       64 bit unsigned wrappable counter."
   ::= {pr1645v2Lan2FGUPPPoEMCD7PEntry 83886080}

pr1645v2Lan2FGUPPPoEMCD7PIfInNUCPkts OBJECT-TYPE
   SYNTAX      Counter64
   MAX-ACCESS  read-only
   STATUS      current
   DESCRIPTION
      "Path: ethernet2.performance.pppoEClient.mibCounters.d7Performance.ifInNUcastPkts

       64 bit unsigned wrappable counter."
   ::= {pr1645v2Lan2FGUPPPoEMCD7PEntry 100663296}

pr1645v2Lan2FGUPPPoEMCD7PIfInBCPkts OBJECT-TYPE
   SYNTAX      Counter64
   MAX-ACCESS  read-only
   STATUS      current
   DESCRIPTION
      "Path: ethernet2.performance.pppoEClient.mibCounters.d7Performance.ifInBcastPkts

       64 bit unsigned wrappable counter."
   ::= {pr1645v2Lan2FGUPPPoEMCD7PEntry 419430400}

pr1645v2Lan2FGUPPPoEMCD7PIfInMCPkts OBJECT-TYPE
   SYNTAX      Counter64
   MAX-ACCESS  read-only
   STATUS      current
   DESCRIPTION
      "Path: ethernet2.performance.pppoEClient.mibCounters.d7Performance.ifInMcastPkts

       64 bit unsigned wrappable counter."
   ::= {pr1645v2Lan2FGUPPPoEMCD7PEntry 436207616}

pr1645v2Lan2FGUPPPoEMCD7PIfInDiscards OBJECT-TYPE
   SYNTAX      Counter64
   MAX-ACCESS  read-only
   STATUS      current
   DESCRIPTION
      "Path: ethernet2.performance.pppoEClient.mibCounters.d7Performance.ifInDiscards

       64 bit unsigned wrappable counter."
   ::= {pr1645v2Lan2FGUPPPoEMCD7PEntry 117440512}

pr1645v2Lan2FGUPPPoEMCD7PIfInErrors OBJECT-TYPE
   SYNTAX      Counter64
   MAX-ACCESS  read-only
   STATUS      current
   DESCRIPTION
      "Path: ethernet2.performance.pppoEClient.mibCounters.d7Performance.ifInErrors

       64 bit unsigned wrappable counter."
   ::= {pr1645v2Lan2FGUPPPoEMCD7PEntry 134217728}

pr1645v2Lan2FGUPPPoEMCD7PIfInUnkwn OBJECT-TYPE
   SYNTAX      Counter64
   MAX-ACCESS  read-only
   STATUS      current
   DESCRIPTION
      "Path: ethernet2.performance.pppoEClient.mibCounters.d7Performance.ifInUnknownProtos

       64 bit unsigned wrappable counter."
   ::= {pr1645v2Lan2FGUPPPoEMCD7PEntry 150994944}

pr1645v2Lan2FGUPPPoEMCD7PInDropEx OBJECT-TYPE
   SYNTAX      Counter64
   MAX-ACCESS  read-only
   STATUS      current
   DESCRIPTION
      "Path: ethernet2.performance.pppoEClient.mibCounters.d7Performance.ifInDropLevelExceeded

       64 bit unsigned wrappable counter."
   ::= {pr1645v2Lan2FGUPPPoEMCD7PEntry 335544320}

pr1645v2Lan2FGUPPPoEMCD7PInDropNoMac OBJECT-TYPE
   SYNTAX      Counter64
   MAX-ACCESS  read-only
   STATUS      current
   DESCRIPTION
      "Path: ethernet2.performance.pppoEClient.mibCounters.d7Performance.fInDiscardsNoMacFit

       64 bit unsigned wrappable counter."
   ::= {pr1645v2Lan2FGUPPPoEMCD7PEntry 301989888}

pr1645v2Lan2FGUPPPoEMCD7PInDropNUCast OBJECT-TYPE
   SYNTAX      Counter64
   MAX-ACCESS  read-only
   STATUS      current
   DESCRIPTION
      "Path: ethernet2.performance.pppoEClient.mibCounters.d7Performance.fInDiscardsNUCast

       64 bit unsigned wrappable counter."
   ::= {pr1645v2Lan2FGUPPPoEMCD7PEntry 318767104}

pr1645v2Lan2FGUPPPoEMCD7PInDropFilter OBJECT-TYPE
   SYNTAX      Counter64
   MAX-ACCESS  read-only
   STATUS      current
   DESCRIPTION
      "Path: ethernet2.performance.pppoEClient.mibCounters.d7Performance.fInDiscardsFilter

       64 bit unsigned wrappable counter."
   ::= {pr1645v2Lan2FGUPPPoEMCD7PEntry 385875968}

pr1645v2Lan2FGUPPPoEMCD7PIfInBandwidth OBJECT-TYPE
   SYNTAX      Integer32
   MAX-ACCESS  read-only
   STATUS      current
   DESCRIPTION
      "Path: ethernet2.performance.pppoEClient.mibCounters.d7Performance.ifInBandwidth

       unit name = bps
       formula = 8 * ; 8 /"
   ::= {pr1645v2Lan2FGUPPPoEMCD7PEntry 268435456}

pr1645v2Lan2FGUPPPoEMCD7PIfOutOctets OBJECT-TYPE
   SYNTAX      Counter64
   MAX-ACCESS  read-only
   STATUS      current
   DESCRIPTION
      "Path: ethernet2.performance.pppoEClient.mibCounters.d7Performance.ifOutOctets

       64 bit unsigned wrappable counter."
   ::= {pr1645v2Lan2FGUPPPoEMCD7PEntry 167772160}

pr1645v2Lan2FGUPPPoEMCD7PIfOutUCPkts OBJECT-TYPE
   SYNTAX      Counter64
   MAX-ACCESS  read-only
   STATUS      current
   DESCRIPTION
      "Path: ethernet2.performance.pppoEClient.mibCounters.d7Performance.ifOutUcastPkts

       64 bit unsigned wrappable counter."
   ::= {pr1645v2Lan2FGUPPPoEMCD7PEntry 184549376}

pr1645v2Lan2FGUPPPoEMCD7PIfOutNUCPkts OBJECT-TYPE
   SYNTAX      Counter64
   MAX-ACCESS  read-only
   STATUS      current
   DESCRIPTION
      "Path: ethernet2.performance.pppoEClient.mibCounters.d7Performance.ifOutNUcastPkts

       64 bit unsigned wrappable counter."
   ::= {pr1645v2Lan2FGUPPPoEMCD7PEntry 201326592}

pr1645v2Lan2FGUPPPoEMCD7PIfOutBCPkts OBJECT-TYPE
   SYNTAX      Counter64
   MAX-ACCESS  read-only
   STATUS      current
   DESCRIPTION
      "Path: ethernet2.performance.pppoEClient.mibCounters.d7Performance.ifOutBcastPkts

       64 bit unsigned wrappable counter."
   ::= {pr1645v2Lan2FGUPPPoEMCD7PEntry 452984832}

pr1645v2Lan2FGUPPPoEMCD7PIfOutMCPkts OBJECT-TYPE
   SYNTAX      Counter64
   MAX-ACCESS  read-only
   STATUS      current
   DESCRIPTION
      "Path: ethernet2.performance.pppoEClient.mibCounters.d7Performance.ifOutMcastPkts

       64 bit unsigned wrappable counter."
   ::= {pr1645v2Lan2FGUPPPoEMCD7PEntry 469762048}

pr1645v2Lan2FGUPPPoEMCD7PIfOutDiscards OBJECT-TYPE
   SYNTAX      Counter64
   MAX-ACCESS  read-only
   STATUS      current
   DESCRIPTION
      "Path: ethernet2.performance.pppoEClient.mibCounters.d7Performance.ifOutDiscards

       64 bit unsigned wrappable counter."
   ::= {pr1645v2Lan2FGUPPPoEMCD7PEntry 218103808}

pr1645v2Lan2FGUPPPoEMCD7PIfOutErrors OBJECT-TYPE
   SYNTAX      Counter64
   MAX-ACCESS  read-only
   STATUS      current
   DESCRIPTION
      "Path: ethernet2.performance.pppoEClient.mibCounters.d7Performance.ifOutErrors

       64 bit unsigned wrappable counter."
   ::= {pr1645v2Lan2FGUPPPoEMCD7PEntry 234881024}

pr1645v2Lan2FGUPPPoEMCD7POutDropEx OBJECT-TYPE
   SYNTAX      Counter64
   MAX-ACCESS  read-only
   STATUS      current
   DESCRIPTION
      "Path: ethernet2.performance.pppoEClient.mibCounters.d7Performance.ifOutDropLevelExceeded

       64 bit unsigned wrappable counter."
   ::= {pr1645v2Lan2FGUPPPoEMCD7PEntry 352321536}

pr1645v2Lan2FGUPPPoEMCD7POutDropNoArp OBJECT-TYPE
   SYNTAX      Counter64
   MAX-ACCESS  read-only
   STATUS      current
   DESCRIPTION
      "Path: ethernet2.performance.pppoEClient.mibCounters.d7Performance.ifOutDiscardsNoArp

       64 bit unsigned wrappable counter."
   ::= {pr1645v2Lan2FGUPPPoEMCD7PEntry 369098752}

pr1645v2Lan2FGUPPPoEMCD7POutDropFilter OBJECT-TYPE
   SYNTAX      Counter64
   MAX-ACCESS  read-only
   STATUS      current
   DESCRIPTION
      "Path: ethernet2.performance.pppoEClient.mibCounters.d7Performance.ifOutDiscardsFilter

       64 bit unsigned wrappable counter."
   ::= {pr1645v2Lan2FGUPPPoEMCD7PEntry 402653184}

pr1645v2Lan2FGUPPPoEMCD7PIfOutBandwidth OBJECT-TYPE
   SYNTAX      Integer32
   MAX-ACCESS  read-only
   STATUS      current
   DESCRIPTION
      "Path: ethernet2.performance.pppoEClient.mibCounters.d7Performance.ifOutBandwidth

       unit name = bps
       formula = 8 * ; 8 /"
   ::= {pr1645v2Lan2FGUPPPoEMCD7PEntry 285212672}

pr1645v2Lan2FGUPPPoEMCD7PIfErrSec OBJECT-TYPE
   SYNTAX      Counter32
   MAX-ACCESS  read-only
   STATUS      current
   DESCRIPTION
      "Path: ethernet2.performance.pppoEClient.mibCounters.d7Performance.ifErrSec

       32 bit unsigned wrappable counter."
   ::= {pr1645v2Lan2FGUPPPoEMCD7PEntry 251658240}


pr1645v2Lan2FGUIfInHwPriorityQueues OBJECT IDENTIFIER ::= {pr1645v2Lan2FGU 132}

pr1645v2Lan2FGUIfInHwPriorityQueuesSSCTable OBJECT-TYPE
   SYNTAX      SEQUENCE OF Pr1645v2Lan2FGUIfInHwPriorityQueuesEntry
   MAX-ACCESS  not-accessible
   STATUS      current
   DESCRIPTION
      "hwPriorityQueues"
   ::= {pr1645v2Lan2FGUIfInHwPriorityQueues 1}

pr1645v2Lan2FGUIfInHwPriorityQueuesEntry OBJECT-TYPE
   SYNTAX      Pr1645v2Lan2FGUIfInHwPriorityQueuesEntry
   MAX-ACCESS  not-accessible
   STATUS      current
   DESCRIPTION
      ""
   INDEX      { pr1645v2Lan2FGUIfInHwPriorityQueuesTableIx }
   ::= {pr1645v2Lan2FGUIfInHwPriorityQueuesSSCTable 1}

Pr1645v2Lan2FGUIfInHwPriorityQueuesEntry ::=
   SEQUENCE
      {
      pr1645v2Lan2FGUIfInHwPriorityQueuesTableIx
         TableIndex,
      pr1645v2Lan2FGUIfInHwPriorityQueuesName
         INTEGER,
      pr1645v2Lan2FGUIfInHwPriorityQueuesLength
         Integer32,
      pr1645v2Lan2FGUIfInHwPriorityQueuesPacketsTotal
         Counter64,
      pr1645v2Lan2FGUIfInHwPriorityQueuesOctetsTotal
         Counter64,
      pr1645v2Lan2FGUIfInHwPriorityQueuesOctetsBandwidth15sec
         Integer32,
      pr1645v2Lan2FGUIfInHwPriorityQueuesOctetsBandwidth30sec
         Integer32,
      pr1645v2Lan2FGUIfInHwPriorityQueuesOctetsBandwidth1min
         Integer32,
      pr1645v2Lan2FGUIfInHwPriorityQueuesOctetsBandwidth2min
         Integer32,
      pr1645v2Lan2FGUIfInHwPriorityQueuesOctetsBandwidth5min
         Integer32
      }

pr1645v2Lan2FGUIfInHwPriorityQueuesTableIx OBJECT-TYPE
   SYNTAX      TableIndex
   MAX-ACCESS  not-accessible
   STATUS      current
   DESCRIPTION
      ""
   ::= {pr1645v2Lan2FGUIfInHwPriorityQueuesEntry 11}

pr1645v2Lan2FGUIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGUIfInHwPriorityQueuesEntry 16777216}

pr1645v2Lan2FGUIfInHwPriorityQueuesLength OBJECT-TYPE
   SYNTAX      Integer32
   MAX-ACCESS  read-only
   STATUS      current
   DESCRIPTION
      "Path: ethernet2.performance.ifInHwPriorityQueues.length"
   ::= {pr1645v2Lan2FGUIfInHwPriorityQueuesEntry 33554432}

pr1645v2Lan2FGUIfInHwPriorityQueuesPacketsTotal OBJECT-TYPE
   SYNTAX      Counter64
   MAX-ACCESS  read-only
   STATUS      current
   DESCRIPTION
      "Path: ethernet2.performance.ifInHwPriorityQueues.packets.total

       64 bit unsigned wrappable counter."
   ::= {pr1645v2Lan2FGUIfInHwPriorityQueuesEntry 50790400}

pr1645v2Lan2FGUIfInHwPriorityQueuesOctetsTotal OBJECT-TYPE
   SYNTAX      Counter64
   MAX-ACCESS  read-only
   STATUS      current
   DESCRIPTION
      "Path: ethernet2.performance.ifInHwPriorityQueues.octets.total

       64 bit unsigned wrappable counter."
   ::= {pr1645v2Lan2FGUIfInHwPriorityQueuesEntry 67567616}

pr1645v2Lan2FGUIfInHwPriorityQueuesOctetsBandwidth15sec OBJECT-TYPE
   SYNTAX      Integer32
   MAX-ACCESS  read-only
   STATUS      current
   DESCRIPTION
      "Path: ethernet2.performance.ifInHwPriorityQueues.octets.bandwidth.15sec

       unit name = bps
       formula = 8 * ; 8 /"
   ::= {pr1645v2Lan2FGUIfInHwPriorityQueuesEntry 70386944}

pr1645v2Lan2FGUIfInHwPriorityQueuesOctetsBandwidth30sec OBJECT-TYPE
   SYNTAX      Integer32
   MAX-ACCESS  read-only
   STATUS      current
   DESCRIPTION
      "Path: ethernet2.performance.ifInHwPriorityQueues.octets.bandwidth.30sec

       unit name = bps
       formula = 8 * ; 8 /"
   ::= {pr1645v2Lan2FGUIfInHwPriorityQueuesEntry 70388224}

pr1645v2Lan2FGUIfInHwPriorityQueuesOctetsBandwidth1min OBJECT-TYPE
   SYNTAX      Integer32
   MAX-ACCESS  read-only
   STATUS      current
   DESCRIPTION
      "Path: ethernet2.performance.ifInHwPriorityQueues.octets.bandwidth.1min

       unit name = bps
       formula = 8 * ; 8 /"
   ::= {pr1645v2Lan2FGUIfInHwPriorityQueuesEntry 70390784}

pr1645v2Lan2FGUIfInHwPriorityQueuesOctetsBandwidth2min OBJECT-TYPE
   SYNTAX      Integer32
   MAX-ACCESS  read-only
   STATUS      current
   DESCRIPTION
      "Path: ethernet2.performance.ifInHwPriorityQueues.octets.bandwidth.2min

       unit name = bps
       formula = 8 * ; 8 /"
   ::= {pr1645v2Lan2FGUIfInHwPriorityQueuesEntry 70395904}

pr1645v2Lan2FGUIfInHwPriorityQueuesOctetsBandwidth5min OBJECT-TYPE
   SYNTAX      Integer32
   MAX-ACCESS  read-only
   STATUS      current
   DESCRIPTION
      "Path: ethernet2.performance.ifInHwPriorityQueues.octets.bandwidth.5min

       unit name = bps
       formula = 8 * ; 8 /"
   ::= {pr1645v2Lan2FGUIfInHwPriorityQueuesEntry 70411264}

pr1645v2Lan2FGUIfInHwPriorityQueuesH2Performance OBJECT-TYPE
   SYNTAX      SEQUENCE OF Pr1645v2Lan2FGUIfInHwPriorityQueuesH2PerformanceEntry
   MAX-ACCESS  not-accessible
   STATUS      current
   DESCRIPTION
      ""
   ::= {pr1645v2Lan2FGUIfInHwPriorityQueues 83886080}

pr1645v2Lan2FGUIfInHwPriorityQueuesH2PerformanceEntry OBJECT-TYPE
   SYNTAX      Pr1645v2Lan2FGUIfInHwPriorityQueuesH2PerformanceEntry
   MAX-ACCESS  not-accessible
   STATUS      current
   DESCRIPTION
      ""
   INDEX      { pr1645v2Lan2FGUIfInHwPriorityQueuesTableIx,
                pr1645v2Lan2FGUIfInHwPriorityQueuesH2PerformanceTableIx }
   ::= {pr1645v2Lan2FGUIfInHwPriorityQueuesH2Performance 1}

Pr1645v2Lan2FGUIfInHwPriorityQueuesH2PerformanceEntry ::=
   SEQUENCE
      {
      pr1645v2Lan2FGUIfInHwPriorityQueuesH2PerformanceTableIx
         TableIndex,
      pr1645v2Lan2FGUIfInHwPriorityQueuesH2PerformanceSysUpTime
         TimeTicks,
      pr1645v2Lan2FGUIfInHwPriorityQueuesH2PerformanceTotPkts
         Counter64,
      pr1645v2Lan2FGUIfInHwPriorityQueuesH2PerformanceTotOcts
         Counter64,
      pr1645v2Lan2FGUIfInHwPriorityQueuesH2PerformanceBandwidth
         Integer32
      }

pr1645v2Lan2FGUIfInHwPriorityQueuesH2PerformanceTableIx OBJECT-TYPE
   SYNTAX      TableIndex
   MAX-ACCESS  not-accessible
   STATUS      current
   DESCRIPTION
      ""
   ::= {pr1645v2Lan2FGUIfInHwPriorityQueuesH2PerformanceEntry 11}

pr1645v2Lan2FGUIfInHwPriorityQueuesH2PerformanceSysUpTime OBJECT-TYPE
   SYNTAX      TimeTicks
   MAX-ACCESS  read-only
   STATUS      current
   DESCRIPTION
      "Path: ethernet2.performance.ifInHwPriorityQueues.h2Performance.sysUpTime

       Time in centi-second."
   ::= {pr1645v2Lan2FGUIfInHwPriorityQueuesH2PerformanceEntry 16777216}

pr1645v2Lan2FGUIfInHwPriorityQueuesH2PerformanceTotPkts OBJECT-TYPE
   SYNTAX      Counter64
   MAX-ACCESS  read-only
   STATUS      current
   DESCRIPTION
      "Path: ethernet2.performance.ifInHwPriorityQueues.h2Performance.totalPkts

       64 bit unsigned wrappable counter."
   ::= {pr1645v2Lan2FGUIfInHwPriorityQueuesH2PerformanceEntry 234881024}

pr1645v2Lan2FGUIfInHwPriorityQueuesH2PerformanceTotOcts OBJECT-TYPE
   SYNTAX      Counter64
   MAX-ACCESS  read-only
   STATUS      current
   DESCRIPTION
      "Path: ethernet2.performance.ifInHwPriorityQueues.h2Performance.totalOctets

       64 bit unsigned wrappable counter."
   ::= {pr1645v2Lan2FGUIfInHwPriorityQueuesH2PerformanceEntry 251658240}

pr1645v2Lan2FGUIfInHwPriorityQueuesH2PerformanceBandwidth OBJECT-TYPE
   SYNTAX      Integer32
   MAX-ACCESS  read-only
   STATUS      current
   DESCRIPTION
      "Path: ethernet2.performance.ifInHwPriorityQueues.h2Performance.bandwidth

       unit name = bps
       formula = 8 * ; 8 /"
   ::= {pr1645v2Lan2FGUIfInHwPriorityQueuesH2PerformanceEntry 268435456}

pr1645v2Lan2FGUIfInHwPriorityQueuesH24Performance OBJECT-TYPE
   SYNTAX      SEQUENCE OF Pr1645v2Lan2FGUIfInHwPriorityQueuesH24PerformanceEntry
   MAX-ACCESS  not-accessible
   STATUS      current
   DESCRIPTION
      ""
   ::= {pr1645v2Lan2FGUIfInHwPriorityQueues 100663296}

pr1645v2Lan2FGUIfInHwPriorityQueuesH24PerformanceEntry OBJECT-TYPE
   SYNTAX      Pr1645v2Lan2FGUIfInHwPriorityQueuesH24PerformanceEntry
   MAX-ACCESS  not-accessible
   STATUS      current
   DESCRIPTION
      ""
   INDEX      { pr1645v2Lan2FGUIfInHwPriorityQueuesTableIx,
                pr1645v2Lan2FGUIfInHwPriorityQueuesH24PerformanceTableIx }
   ::= {pr1645v2Lan2FGUIfInHwPriorityQueuesH24Performance 1}

Pr1645v2Lan2FGUIfInHwPriorityQueuesH24PerformanceEntry ::=
   SEQUENCE
      {
      pr1645v2Lan2FGUIfInHwPriorityQueuesH24PerformanceTableIx
         TableIndex,
      pr1645v2Lan2FGUIfInHwPriorityQueuesH24PerformanceSysUpTime
         TimeTicks,
      pr1645v2Lan2FGUIfInHwPriorityQueuesH24PerformanceTotPkts
         Counter64,
      pr1645v2Lan2FGUIfInHwPriorityQueuesH24PerformanceTotOcts
         Counter64,
      pr1645v2Lan2FGUIfInHwPriorityQueuesH24PerformanceBandwidth
         Integer32
      }

pr1645v2Lan2FGUIfInHwPriorityQueuesH24PerformanceTableIx OBJECT-TYPE
   SYNTAX      TableIndex
   MAX-ACCESS  not-accessible
   STATUS      current
   DESCRIPTION
      ""
   ::= {pr1645v2Lan2FGUIfInHwPriorityQueuesH24PerformanceEntry 11}

pr1645v2Lan2FGUIfInHwPriorityQueuesH24PerformanceSysUpTime OBJECT-TYPE
   SYNTAX      TimeTicks
   MAX-ACCESS  read-only
   STATUS      current
   DESCRIPTION
      "Path: ethernet2.performance.ifInHwPriorityQueues.h24Performance.sysUpTime

       Time in centi-second."
   ::= {pr1645v2Lan2FGUIfInHwPriorityQueuesH24PerformanceEntry 16777216}

pr1645v2Lan2FGUIfInHwPriorityQueuesH24PerformanceTotPkts OBJECT-TYPE
   SYNTAX      Counter64
   MAX-ACCESS  read-only
   STATUS      current
   DESCRIPTION
      "Path: ethernet2.performance.ifInHwPriorityQueues.h24Performance.totalPkts

       64 bit unsigned wrappable counter."
   ::= {pr1645v2Lan2FGUIfInHwPriorityQueuesH24PerformanceEntry 234881024}

pr1645v2Lan2FGUIfInHwPriorityQueuesH24PerformanceTotOcts OBJECT-TYPE
   SYNTAX      Counter64
   MAX-ACCESS  read-only
   STATUS      current
   DESCRIPTION
      "Path: ethernet2.performance.ifInHwPriorityQueues.h24Performance.totalOctets

       64 bit unsigned wrappable counter."
   ::= {pr1645v2Lan2FGUIfInHwPriorityQueuesH24PerformanceEntry 251658240}

pr1645v2Lan2FGUIfInHwPriorityQueuesH24PerformanceBandwidth OBJECT-TYPE
   SYNTAX      Integer32
   MAX-ACCESS  read-only
   STATUS      current
   DESCRIPTION
      "Path: ethernet2.performance.ifInHwPriorityQueues.h24Performance.bandwidth

       unit name = bps
       formula = 8 * ; 8 /"
   ::= {pr1645v2Lan2FGUIfInHwPriorityQueuesH24PerformanceEntry 268435456}

pr1645v2Lan2FGUIfInHwPriorityQueuesD7Performance OBJECT-TYPE
   SYNTAX      SEQUENCE OF Pr1645v2Lan2FGUIfInHwPriorityQueuesD7PerformanceEntry
   MAX-ACCESS  not-accessible
   STATUS      current
   DESCRIPTION
      ""
   ::= {pr1645v2Lan2FGUIfInHwPriorityQueues 117440512}

pr1645v2Lan2FGUIfInHwPriorityQueuesD7PerformanceEntry OBJECT-TYPE
   SYNTAX      Pr1645v2Lan2FGUIfInHwPriorityQueuesD7PerformanceEntry
   MAX-ACCESS  not-accessible
   STATUS      current
   DESCRIPTION
      ""
   INDEX      { pr1645v2Lan2FGUIfInHwPriorityQueuesTableIx,
                pr1645v2Lan2FGUIfInHwPriorityQueuesD7PerformanceTableIx }
   ::= {pr1645v2Lan2FGUIfInHwPriorityQueuesD7Performance 1}

Pr1645v2Lan2FGUIfInHwPriorityQueuesD7PerformanceEntry ::=
   SEQUENCE
      {
      pr1645v2Lan2FGUIfInHwPriorityQueuesD7PerformanceTableIx
         TableIndex,
      pr1645v2Lan2FGUIfInHwPriorityQueuesD7PerformanceSysUpTime
         TimeTicks,
      pr1645v2Lan2FGUIfInHwPriorityQueuesD7PerformanceTotPkts
         Counter64,
      pr1645v2Lan2FGUIfInHwPriorityQueuesD7PerformanceTotOcts
         Counter64,
      pr1645v2Lan2FGUIfInHwPriorityQueuesD7PerformanceBandwidth
         Integer32
      }

pr1645v2Lan2FGUIfInHwPriorityQueuesD7PerformanceTableIx OBJECT-TYPE
   SYNTAX      TableIndex
   MAX-ACCESS  not-accessible
   STATUS      current
   DESCRIPTION
      ""
   ::= {pr1645v2Lan2FGUIfInHwPriorityQueuesD7PerformanceEntry 11}

pr1645v2Lan2FGUIfInHwPriorityQueuesD7PerformanceSysUpTime OBJECT-TYPE
   SYNTAX      TimeTicks
   MAX-ACCESS  read-only
   STATUS      current
   DESCRIPTION
      "Path: ethernet2.performance.ifInHwPriorityQueues.d7Performance.sysUpTime

       Time in centi-second."
   ::= {pr1645v2Lan2FGUIfInHwPriorityQueuesD7PerformanceEntry 16777216}

pr1645v2Lan2FGUIfInHwPriorityQueuesD7PerformanceTotPkts OBJECT-TYPE
   SYNTAX      Counter64
   MAX-ACCESS  read-only
   STATUS      current
   DESCRIPTION
      "Path: ethernet2.performance.ifInHwPriorityQueues.d7Performance.totalPkts

       64 bit unsigned wrappable counter."
   ::= {pr1645v2Lan2FGUIfInHwPriorityQueuesD7PerformanceEntry 234881024}

pr1645v2Lan2FGUIfInHwPriorityQueuesD7PerformanceTotOcts OBJECT-TYPE
   SYNTAX      Counter64
   MAX-ACCESS  read-only
   STATUS      current
   DESCRIPTION
      "Path: ethernet2.performance.ifInHwPriorityQueues.d7Performance.totalOctets

       64 bit unsigned wrappable counter."
   ::= {pr1645v2Lan2FGUIfInHwPriorityQueuesD7PerformanceEntry 251658240}

pr1645v2Lan2FGUIfInHwPriorityQueuesD7PerformanceBandwidth OBJECT-TYPE
   SYNTAX      Integer32
   MAX-ACCESS  read-only
   STATUS      current
   DESCRIPTION
      "Path: ethernet2.performance.ifInHwPriorityQueues.d7Performance.bandwidth

       unit name = bps
       formula = 8 * ; 8 /"
   ::= {pr1645v2Lan2FGUIfInHwPriorityQueuesD7PerformanceEntry 268435456}



ar1645v2Lan2FGU OBJECT IDENTIFIER ::= {r1645v2Lan2FGU 16}


ar1645v2Lan2FGUClearCounters OBJECT-TYPE
   SYNTAX      Integer32
   MAX-ACCESS  read-write
   STATUS      current
   DESCRIPTION
      "Path: ethernet2.actions.clearCounters
       Info: reset counters"
   ::= {ar1645v2Lan2FGU 263}


ar1645v2Lan2FGUPowerToggle OBJECT-TYPE
   SYNTAX      Integer32
   MAX-ACCESS  read-write
   STATUS      current
   DESCRIPTION
      "Path: ethernet2.actions.powerToggle
       Info: action in the debug group"
   ::= {ar1645v2Lan2FGU 68}


ar1645v2Lan2FGURestartIntf OBJECT-TYPE
   SYNTAX      Integer32
   MAX-ACCESS  read-write
   STATUS      current
   DESCRIPTION
      "Path: ethernet2.actions.restartIntf
       Info: action in the debug group"
   ::= {ar1645v2Lan2FGU 67}


ar1645v2Lan2FGUClearOamEventLog OBJECT-TYPE
   SYNTAX      Integer32
   MAX-ACCESS  read-write
   STATUS      current
   DESCRIPTION
      "Path: ethernet2.actions.clearOamEventLog
       Info: clear the OAM event log"
   ::= {ar1645v2Lan2FGU 916}


ar1645v2Lan2FGULoopback OBJECT-TYPE
   SYNTAX      Integer32
   MAX-ACCESS  read-write
   STATUS      current
   DESCRIPTION
      "Path: ethernet2.actions.loopback
       Info: ethernet loopback"
   ::= {ar1645v2Lan2FGU 914}


ar1645v2Lan2FGULoop OBJECT IDENTIFIER ::= {ar1645v2Lan2FGU 915}

ar1645v2Lan2FGULoopSSC OBJECT IDENTIFIER ::= {ar1645v2Lan2FGULoop 1}

ar1645v2Lan2FGULoopEntry OBJECT IDENTIFIER ::= {ar1645v2Lan2FGULoopSSC 1}

ar1645v2Lan2FGULoopAction OBJECT-TYPE
   SYNTAX      INTEGER
               {
               start (1),
               stop (2)
               }
   MAX-ACCESS  read-write
   STATUS      current
   DESCRIPTION
      "Path: ethernet2.actions.loop.action

       Possibilities:
               start   (1)
               stop   (2)"
   ::= {ar1645v2Lan2FGULoopEntry 16777216}

ar1645v2Lan2FGULoopTime OBJECT-TYPE
   SYNTAX      TimeTicks
   MAX-ACCESS  read-write
   STATUS      current
   DESCRIPTION
      "Path: ethernet2.actions.loop.time

       Time in centi-second."
   ::= {ar1645v2Lan2FGULoopEntry 50331648}

ar1645v2Lan2FGULoopIntfName OBJECT-TYPE
   SYNTAX      DisplayString
   MAX-ACCESS  read-write
   STATUS      current
   DESCRIPTION
      "Path: ethernet2.actions.loop.intfName"
   ::= {ar1645v2Lan2FGULoopEntry 67108864}


ar1645v2Lan2FGUOamRemLoopback OBJECT-TYPE
   SYNTAX      Integer32
   MAX-ACCESS  read-write
   STATUS      current
   DESCRIPTION
      "Path: ethernet2.actions.oamRemLoopback
       Info: OAM Remote Loopback"
   ::= {ar1645v2Lan2FGU 912}


ar1645v2Lan2FGUType OBJECT-TYPE
   SYNTAX      INTEGER
               {
               start (0),
               stop (1)
               }
   MAX-ACCESS  read-write
   STATUS      current
   DESCRIPTION
      "Path: ethernet2.actions.type
       Info: OAM Remote Loopback type

       Possibilities:
               start   (0)
               stop   (1)"
   ::= {ar1645v2Lan2FGU 913}


ar1645v2Lan2FGUSendWOL OBJECT-TYPE
   SYNTAX      Integer32
   MAX-ACCESS  read-write
   STATUS      current
   DESCRIPTION
      "Path: ethernet2.actions.sendWOL
       Info: send a WakeOnLan message on this interface"
   ::= {ar1645v2Lan2FGU 333}


ar1645v2Lan2FGUWolInfo OBJECT IDENTIFIER ::= {ar1645v2Lan2FGU 332}

ar1645v2Lan2FGUWolInfoSSC OBJECT IDENTIFIER ::= {ar1645v2Lan2FGUWolInfo 1}

ar1645v2Lan2FGUWolInfoEntry OBJECT IDENTIFIER ::= {ar1645v2Lan2FGUWolInfoSSC 1}

ar1645v2Lan2FGUWolInfoTargetMAC OBJECT-TYPE
   SYNTAX      OCTET STRING
   MAX-ACCESS  read-write
   STATUS      current
   DESCRIPTION
      "Path: ethernet2.actions.wolInfo.targetMAC

       MAC address."
   ::= {ar1645v2Lan2FGUWolInfoEntry 16777216}

ar1645v2Lan2FGUWolInfoPassword OBJECT-TYPE
   SYNTAX      OCTET STRING
   MAX-ACCESS  read-write
   STATUS      current
   DESCRIPTION
      "Path: ethernet2.actions.wolInfo.password"
   ::= {ar1645v2Lan2FGUWolInfoEntry 33554432}


ar1645v2Lan2FGUClearArpCache OBJECT-TYPE
   SYNTAX      Integer32
   MAX-ACCESS  read-write
   STATUS      current
   DESCRIPTION
      "Path: ethernet2.actions.clearArpCache
       Info: clear all dynamic enties in ARP cache table"
   ::= {ar1645v2Lan2FGU 25}


ar1645v2Lan2FGUClearDebugCounters OBJECT-TYPE
   SYNTAX      Integer32
   MAX-ACCESS  read-write
   STATUS      current
   DESCRIPTION
      "Path: ethernet2.actions.clearDebugCounters
       Info: action in the debug group"
   ::= {ar1645v2Lan2FGU 76}


ar1645v2Lan2FGUEnableRds OBJECT-TYPE
   SYNTAX      Integer32
   MAX-ACCESS  read-write
   STATUS      current
   DESCRIPTION
      "Path: ethernet2.actions.enableRds
       Info: action in the debug group"
   ::= {ar1645v2Lan2FGU 367}


ar1645v2Lan2FGUDisableRds OBJECT-TYPE
   SYNTAX      Integer32
   MAX-ACCESS  read-write
   STATUS      current
   DESCRIPTION
      "Path: ethernet2.actions.disableRds
       Info: action in the debug group"
   ::= {ar1645v2Lan2FGU 366}


ar1645v2Lan2FGUEnableTds OBJECT-TYPE
   SYNTAX      Integer32
   MAX-ACCESS  read-write
   STATUS      current
   DESCRIPTION
      "Path: ethernet2.actions.enableTds
       Info: action in the debug group"
   ::= {ar1645v2Lan2FGU 365}


ar1645v2Lan2FGUDisableTds OBJECT-TYPE
   SYNTAX      Integer32
   MAX-ACCESS  read-write
   STATUS      current
   DESCRIPTION
      "Path: ethernet2.actions.disableTds
       Info: action in the debug group"
   ::= {ar1645v2Lan2FGU 364}


ar1645v2Lan2FGUClearTsecStats OBJECT-TYPE
   SYNTAX      Integer32
   MAX-ACCESS  read-write
   STATUS      current
   DESCRIPTION
      "Path: ethernet2.actions.clearTsecStats
       Info: action in the debug group"
   ::= {ar1645v2Lan2FGU 363}


ar1645v2Lan2FGUStopTsecStats OBJECT-TYPE
   SYNTAX      Integer32
   MAX-ACCESS  read-write
   STATUS      current
   DESCRIPTION
      "Path: ethernet2.actions.stopTsecStats
       Info: action in the debug group"
   ::= {ar1645v2Lan2FGU 362}


ar1645v2Lan2FGUStartTsecStats OBJECT-TYPE
   SYNTAX      Integer32
   MAX-ACCESS  read-write
   STATUS      current
   DESCRIPTION
      "Path: ethernet2.actions.startTsecStats
       Info: action in the debug group"
   ::= {ar1645v2Lan2FGU 361}


ar1645v2Lan2FGUPhyAction OBJECT-TYPE
   SYNTAX      Integer32
   MAX-ACCESS  read-write
   STATUS      current
   DESCRIPTION
      "Path: ethernet2.actions.phyAction
       Info: action in the debug group"
   ::= {ar1645v2Lan2FGU 90}



fr1645v2Lan2FGU OBJECT IDENTIFIER ::= {r1645v2Lan2FGU 13}


fr1645v2Lan2FGUAlarm OBJECT IDENTIFIER ::= {fr1645v2Lan2FGU 207}

fr1645v2Lan2FGUAlarmSSC OBJECT IDENTIFIER ::= {fr1645v2Lan2FGUAlarm 1}

fr1645v2Lan2FGUAlarmEntry OBJECT IDENTIFIER ::= {fr1645v2Lan2FGUAlarmSSC 1}

fr1645v2Lan2FGUAlarmDiscriminator OBJECT-TYPE
   SYNTAX      Integer32
   MAX-ACCESS  read-only
   STATUS      current
   DESCRIPTION
      "Path: ethernet2.alarms.alarmInfo.discriminator"
   ::= {fr1645v2Lan2FGUAlarmEntry 16777216}

fr1645v2Lan2FGUAlarmCurrent OBJECT-TYPE
   SYNTAX      Integer32
   MAX-ACCESS  read-only
   STATUS      current
   DESCRIPTION
      "Path: ethernet2.alarms.alarmInfo.currentAlarms

       Bit meanings:
               bit 0 = linkDown,
               bit 9 = pppoEDown"
   ::= {fr1645v2Lan2FGUAlarmEntry 33554432}

fr1645v2Lan2FGUAlarmPrevious OBJECT-TYPE
   SYNTAX      Integer32
   MAX-ACCESS  read-only
   STATUS      current
   DESCRIPTION
      "Path: ethernet2.alarms.alarmInfo.previousAlarms

       Bit meanings:
               bit 0 = linkDown,
               bit 9 = pppoEDown"
   ::= {fr1645v2Lan2FGUAlarmEntry 50331648}

fr1645v2Lan2FGUAlarmMask OBJECT-TYPE
   SYNTAX      Integer32
   MAX-ACCESS  read-only
   STATUS      current
   DESCRIPTION
      "Path: ethernet2.alarms.alarmInfo.alarmMask

       Bit meanings:
               bit 0 = linkDown,
               bit 9 = pppoEDown"
   ::= {fr1645v2Lan2FGUAlarmEntry 67108864}

fr1645v2Lan2FGUAlarmLevLinkDown OBJECT-TYPE
   SYNTAX      Integer32
   MAX-ACCESS  read-only
   STATUS      current
   DESCRIPTION
      "Path: ethernet2.alarms.alarmInfo.alarmLevel.linkDown"
   ::= {fr1645v2Lan2FGUAlarmEntry 83951616}

fr1645v2Lan2FGUAlarmLevPppoEDown OBJECT-TYPE
   SYNTAX      Integer32
   MAX-ACCESS  read-only
   STATUS      current
   DESCRIPTION
      "Path: ethernet2.alarms.alarmInfo.alarmLevel.pppoEDown"
   ::= {fr1645v2Lan2FGUAlarmEntry 84541440}


fr1645v2Lan2FGUAlarmE2 OBJECT IDENTIFIER ::= {fr1645v2Lan2FGUAlarm 2}

fr1645v2Lan2FGUAlarmE2Entry OBJECT IDENTIFIER ::= {fr1645v2Lan2FGUAlarmE2 1}

fr1645v2Lan2FGUAlarmE2LinkDown OBJECT IDENTIFIER ::= {fr1645v2Lan2FGUAlarmE2Entry 10}

fr1645v2Lan2FGUAlarmE2LinkDownPfx OBJECT IDENTIFIER ::= {fr1645v2Lan2FGUAlarmE2LinkDown 0}

fr1645v2Lan2FGUAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2GigaUtp'
                (root='router1645') has changed from the ON to the OFF state."
   ::= {fr1645v2Lan2FGUAlarmE2LinkDownPfx 1}

fr1645v2Lan2FGUAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2GigaUtp'
                (root='router1645') has changed from the OFF to the ON state."
   ::= {fr1645v2Lan2FGUAlarmE2LinkDownPfx 2}

fr1645v2Lan2FGUAlarmE2PppoEDown OBJECT IDENTIFIER ::= {fr1645v2Lan2FGUAlarmE2Entry 19}

fr1645v2Lan2FGUAlarmE2PppoEDownPfx OBJECT IDENTIFIER ::= {fr1645v2Lan2FGUAlarmE2PppoEDown 0}

fr1645v2Lan2FGUAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2GigaUtp'
                (root='router1645') has changed from the ON to the OFF state."
   ::= {fr1645v2Lan2FGUAlarmE2PppoEDownPfx 1}

fr1645v2Lan2FGUAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2GigaUtp'
                (root='router1645') has changed from the OFF to the ON state."
   ::= {fr1645v2Lan2FGUAlarmE2PppoEDownPfx 2}



END
