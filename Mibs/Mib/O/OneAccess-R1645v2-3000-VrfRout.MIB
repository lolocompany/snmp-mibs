OneAccess-R1645v2-3000-VrfRout DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2VrfRout OBJECT IDENTIFIER ::= {r1645Rootv2 3000}

r1645v2VrfRoutMOProp OBJECT-TYPE
   SYNTAX      SEQUENCE OF R1645v2VrfRoutMOPropEntry
   MAX-ACCESS  not-accessible
   STATUS      current
   DESCRIPTION
      ""
   ::= {r1645v2VrfRout 1}

r1645v2VrfRoutMOPropEntry OBJECT-TYPE
   SYNTAX      R1645v2VrfRoutMOPropEntry
   MAX-ACCESS  not-accessible
   STATUS      current
   DESCRIPTION
      ""
   INDEX      { r1645v2VrfRoutMOPropGlobalIx }
   ::= {r1645v2VrfRoutMOProp 1}

R1645v2VrfRoutMOPropEntry ::=
   SEQUENCE
      {
      r1645v2VrfRoutMOPropPath
         ContainmentPath,
      r1645v2VrfRoutMOPropRev
         ObjectRevision,
      r1645v2VrfRoutMOPropGlobalIx
         GlobalIndex
      }

r1645v2VrfRoutMOPropPath OBJECT-TYPE
   SYNTAX      ContainmentPath
   MAX-ACCESS  read-only
   STATUS      current
   DESCRIPTION
      "Textual description of the containment tree from the instance of
       the root object down to the instance of the current object."
   ::= {r1645v2VrfRoutMOPropEntry 3}

r1645v2VrfRoutMOPropRev OBJECT-TYPE
   SYNTAX      ObjectRevision
   MAX-ACCESS  read-only
   STATUS      current
   DESCRIPTION
      "This value corresponds with the revision of the MANAGED OBJECT."
   ::= {r1645v2VrfRoutMOPropEntry 4}

r1645v2VrfRoutMOPropGlobalIx OBJECT-TYPE
   SYNTAX      GlobalIndex
   MAX-ACCESS  read-only
   STATUS      current
   DESCRIPTION
      "The value of the tlsCntTreeGlobalIndex of the MANAGED OBJECT."
   ::= {r1645v2VrfRoutMOPropEntry 10}



er1645v2VrfRout OBJECT IDENTIFIER ::= {r1645v2VrfRout 11}


er1645v2VrfRoutSnmpIndexOffset OBJECT IDENTIFIER ::= {er1645v2VrfRout 268}

er1645v2VrfRoutSnmpIndexOffsetTable OBJECT-TYPE
   SYNTAX      SEQUENCE OF Er1645v2VrfRoutSnmpIndexOffsetEntry
   MAX-ACCESS  not-accessible
   STATUS      current
   DESCRIPTION
      "Preferred offset in the range of SNMP indices for this SWinst, 0 means automatic"
   ::= {er1645v2VrfRoutSnmpIndexOffset 1}

er1645v2VrfRoutSnmpIndexOffsetEntry OBJECT-TYPE
   SYNTAX      Er1645v2VrfRoutSnmpIndexOffsetEntry
   MAX-ACCESS  not-accessible
   STATUS      current
   DESCRIPTION
      ""
   INDEX      { er1645v2VrfRoutSnmpIndexOffsetGlobalIx }
   ::= {er1645v2VrfRoutSnmpIndexOffsetTable 1}

Er1645v2VrfRoutSnmpIndexOffsetEntry ::=
   SEQUENCE
      {
      er1645v2VrfRoutSnmpIndexOffsetGlobalIx
         GlobalIndex,
      er1645v2VrfRoutSnmpIndexOffsetValue
         Integer32
      }

er1645v2VrfRoutSnmpIndexOffsetGlobalIx OBJECT-TYPE
   SYNTAX      GlobalIndex
   MAX-ACCESS  not-accessible
   STATUS      current
   DESCRIPTION
      "The value of the tlsCntTreeGlobalIndex of the MANAGED OBJECT."
   ::= {er1645v2VrfRoutSnmpIndexOffsetEntry 10}

er1645v2VrfRoutSnmpIndexOffsetValue OBJECT-TYPE
   SYNTAX      Integer32
   MAX-ACCESS  read-write
   STATUS      current
   DESCRIPTION
      "Path: vrfRouter.editConf.snmpIndexOffset"
   ::= {er1645v2VrfRoutSnmpIndexOffsetEntry 2147483648}


er1645v2VrfRoutDefaultRoute OBJECT IDENTIFIER ::= {er1645v2VrfRout 13}

er1645v2VrfRoutDefaultRouteSSCTable OBJECT-TYPE
   SYNTAX      SEQUENCE OF Er1645v2VrfRoutDefaultRouteEntry
   MAX-ACCESS  not-accessible
   STATUS      current
   DESCRIPTION
      "defaultRoute"
   ::= {er1645v2VrfRoutDefaultRoute 1}

er1645v2VrfRoutDefaultRouteEntry OBJECT-TYPE
   SYNTAX      Er1645v2VrfRoutDefaultRouteEntry
   MAX-ACCESS  not-accessible
   STATUS      current
   DESCRIPTION
      ""
   INDEX      { er1645v2VrfRoutDefaultRouteGlobalIx }
   ::= {er1645v2VrfRoutDefaultRouteSSCTable 1}

Er1645v2VrfRoutDefaultRouteEntry ::=
   SEQUENCE
      {
      er1645v2VrfRoutDefaultRouteGlobalIx
         GlobalIndex,
      er1645v2VrfRoutDefaultRouteGateway
         IpAddress,
      er1645v2VrfRoutDefaultRouteInterface
         DisplayString,
      er1645v2VrfRoutDefaultRoutePreference
         Integer32,
      er1645v2VrfRoutDefaultRouteMetric
         Integer32
      }

er1645v2VrfRoutDefaultRouteGlobalIx OBJECT-TYPE
   SYNTAX      GlobalIndex
   MAX-ACCESS  not-accessible
   STATUS      current
   DESCRIPTION
      "The value of the tlsCntTreeGlobalIndex of the MANAGED OBJECT."
   ::= {er1645v2VrfRoutDefaultRouteEntry 10}

er1645v2VrfRoutDefaultRouteGateway OBJECT-TYPE
   SYNTAX      IpAddress
   MAX-ACCESS  read-write
   STATUS      current
   DESCRIPTION
      "Path: vrfRouter.editConf.defaultRoute.gateway"
   ::= {er1645v2VrfRoutDefaultRouteEntry 16777216}

er1645v2VrfRoutDefaultRouteInterface OBJECT-TYPE
   SYNTAX      DisplayString
   MAX-ACCESS  read-write
   STATUS      current
   DESCRIPTION
      "Path: vrfRouter.editConf.defaultRoute.interface"
   ::= {er1645v2VrfRoutDefaultRouteEntry 33554432}

er1645v2VrfRoutDefaultRoutePreference OBJECT-TYPE
   SYNTAX      Integer32
   MAX-ACCESS  read-write
   STATUS      current
   DESCRIPTION
      "Path: vrfRouter.editConf.defaultRoute.preference"
   ::= {er1645v2VrfRoutDefaultRouteEntry 50331648}

er1645v2VrfRoutDefaultRouteMetric OBJECT-TYPE
   SYNTAX      Integer32
   MAX-ACCESS  read-write
   STATUS      current
   DESCRIPTION
      "Path: vrfRouter.editConf.defaultRoute.metric"
   ::= {er1645v2VrfRoutDefaultRouteEntry 67108864}


er1645v2VrfRoutRoutingTable OBJECT IDENTIFIER ::= {er1645v2VrfRout 14}

er1645v2VrfRoutRoutingTableSSCTable OBJECT-TYPE
   SYNTAX      SEQUENCE OF Er1645v2VrfRoutRoutingTableEntry
   MAX-ACCESS  not-accessible
   STATUS      current
   DESCRIPTION
      "routingTable"
   ::= {er1645v2VrfRoutRoutingTable 1}

er1645v2VrfRoutRoutingTableEntry OBJECT-TYPE
   SYNTAX      Er1645v2VrfRoutRoutingTableEntry
   MAX-ACCESS  not-accessible
   STATUS      current
   DESCRIPTION
      ""
   INDEX      { er1645v2VrfRoutRoutingTableGlobalIx,
                er1645v2VrfRoutRoutingTableTableIx }
   ::= {er1645v2VrfRoutRoutingTableSSCTable 1}

Er1645v2VrfRoutRoutingTableEntry ::=
   SEQUENCE
      {
      er1645v2VrfRoutRoutingTableActions
         VariableLengthTableActions,
      er1645v2VrfRoutRoutingTableGlobalIx
         GlobalIndex,
      er1645v2VrfRoutRoutingTableTableIx
         TableIndex,
      er1645v2VrfRoutRoutingTableRemark
         DisplayString,
      er1645v2VrfRoutRoutingTableNetwork
         IpAddress,
      er1645v2VrfRoutRoutingTableMask
         IpAddress,
      er1645v2VrfRoutRoutingTableGateway
         IpAddress,
      er1645v2VrfRoutRoutingTableIf
         DisplayString,
      er1645v2VrfRoutRoutingTablePref
         Integer32,
      er1645v2VrfRoutRoutingTableMetric
         Integer32,
      er1645v2VrfRoutRoutingTableProxyArp
         INTEGER,
      er1645v2VrfRoutRoutingTableTimeWindow
         DisplayString,
      er1645v2VrfRoutRoutingTablePermanent
         INTEGER,
      er1645v2VrfRoutRoutingTableTrack
         INTEGER,
      er1645v2VrfRoutRoutingTableTag
         DisplayString
      }

er1645v2VrfRoutRoutingTableActions OBJECT-TYPE
   SYNTAX      VariableLengthTableActions
   MAX-ACCESS  read-write
   STATUS      current
   DESCRIPTION
      "By way of this field, some manipulations
       on this table may be performed."
   ::= {er1645v2VrfRoutRoutingTableEntry 2}

er1645v2VrfRoutRoutingTableGlobalIx OBJECT-TYPE
   SYNTAX      GlobalIndex
   MAX-ACCESS  not-accessible
   STATUS      current
   DESCRIPTION
      "The value of the tlsCntTreeGlobalIndex of the MANAGED OBJECT."
   ::= {er1645v2VrfRoutRoutingTableEntry 10}

er1645v2VrfRoutRoutingTableTableIx OBJECT-TYPE
   SYNTAX      TableIndex
   MAX-ACCESS  not-accessible
   STATUS      current
   DESCRIPTION
      ""
   ::= {er1645v2VrfRoutRoutingTableEntry 11}

er1645v2VrfRoutRoutingTableRemark OBJECT-TYPE
   SYNTAX      DisplayString
   MAX-ACCESS  read-write
   STATUS      current
   DESCRIPTION
      "Path: vrfRouter.editConf.routingTable.remark"
   ::= {er1645v2VrfRoutRoutingTableEntry 117440512}

er1645v2VrfRoutRoutingTableNetwork OBJECT-TYPE
   SYNTAX      IpAddress
   MAX-ACCESS  read-write
   STATUS      current
   DESCRIPTION
      "Path: vrfRouter.editConf.routingTable.network"
   ::= {er1645v2VrfRoutRoutingTableEntry 16777216}

er1645v2VrfRoutRoutingTableMask OBJECT-TYPE
   SYNTAX      IpAddress
   MAX-ACCESS  read-write
   STATUS      current
   DESCRIPTION
      "Path: vrfRouter.editConf.routingTable.mask"
   ::= {er1645v2VrfRoutRoutingTableEntry 33554432}

er1645v2VrfRoutRoutingTableGateway OBJECT-TYPE
   SYNTAX      IpAddress
   MAX-ACCESS  read-write
   STATUS      current
   DESCRIPTION
      "Path: vrfRouter.editConf.routingTable.gateway"
   ::= {er1645v2VrfRoutRoutingTableEntry 50331648}

er1645v2VrfRoutRoutingTableIf OBJECT-TYPE
   SYNTAX      DisplayString
   MAX-ACCESS  read-write
   STATUS      current
   DESCRIPTION
      "Path: vrfRouter.editConf.routingTable.interface"
   ::= {er1645v2VrfRoutRoutingTableEntry 67108864}

er1645v2VrfRoutRoutingTablePref OBJECT-TYPE
   SYNTAX      Integer32
   MAX-ACCESS  read-write
   STATUS      current
   DESCRIPTION
      "Path: vrfRouter.editConf.routingTable.preference"
   ::= {er1645v2VrfRoutRoutingTableEntry 83886080}

er1645v2VrfRoutRoutingTableMetric OBJECT-TYPE
   SYNTAX      Integer32
   MAX-ACCESS  read-write
   STATUS      current
   DESCRIPTION
      "Path: vrfRouter.editConf.routingTable.metric"
   ::= {er1645v2VrfRoutRoutingTableEntry 100663296}

er1645v2VrfRoutRoutingTableProxyArp OBJECT-TYPE
   SYNTAX      INTEGER
               {
               disabled (0),
               enabled (1)
               }
   MAX-ACCESS  read-write
   STATUS      current
   DESCRIPTION
      "Path: vrfRouter.editConf.routingTable.proxyArp

       Possibilities:
               disabled   (0)
               enabled   (1)"
   ::= {er1645v2VrfRoutRoutingTableEntry 134217728}

er1645v2VrfRoutRoutingTableTimeWindow OBJECT-TYPE
   SYNTAX      DisplayString
   MAX-ACCESS  read-write
   STATUS      current
   DESCRIPTION
      "Path: vrfRouter.editConf.routingTable.timeWindow"
   ::= {er1645v2VrfRoutRoutingTableEntry 150994944}

er1645v2VrfRoutRoutingTablePermanent OBJECT-TYPE
   SYNTAX      INTEGER
               {
               disabled (0),
               enabled (1)
               }
   MAX-ACCESS  read-write
   STATUS      current
   DESCRIPTION
      "Path: vrfRouter.editConf.routingTable.permanent

       Possibilities:
               disabled   (0)
               enabled   (1)"
   ::= {er1645v2VrfRoutRoutingTableEntry 184549376}

er1645v2VrfRoutRoutingTableTrack OBJECT-TYPE
   SYNTAX      INTEGER
               {
               disabled (0)
               }
   MAX-ACCESS  read-write
   STATUS      current
   DESCRIPTION
      "Path: vrfRouter.editConf.routingTable.track

       Possibilities:
               disabled   (0)"
   ::= {er1645v2VrfRoutRoutingTableEntry 167772160}

er1645v2VrfRoutRoutingTableTag OBJECT-TYPE
   SYNTAX      DisplayString
   MAX-ACCESS  read-write
   STATUS      current
   DESCRIPTION
      "Path: vrfRouter.editConf.routingTable.tag"
   ::= {er1645v2VrfRoutRoutingTableEntry 201326592}


er1645v2VrfRoutSendTtlExceeded OBJECT IDENTIFIER ::= {er1645v2VrfRout 30}

er1645v2VrfRoutSendTtlExceededTable OBJECT-TYPE
   SYNTAX      SEQUENCE OF Er1645v2VrfRoutSendTtlExceededEntry
   MAX-ACCESS  not-accessible
   STATUS      current
   DESCRIPTION
      "indicates if a ICMP TTL exceeded must be returned to a packet's spurce if the TTL reaches 0 "
   ::= {er1645v2VrfRoutSendTtlExceeded 1}

er1645v2VrfRoutSendTtlExceededEntry OBJECT-TYPE
   SYNTAX      Er1645v2VrfRoutSendTtlExceededEntry
   MAX-ACCESS  not-accessible
   STATUS      current
   DESCRIPTION
      ""
   INDEX      { er1645v2VrfRoutSendTtlExceededGlobalIx }
   ::= {er1645v2VrfRoutSendTtlExceededTable 1}

Er1645v2VrfRoutSendTtlExceededEntry ::=
   SEQUENCE
      {
      er1645v2VrfRoutSendTtlExceededGlobalIx
         GlobalIndex,
      er1645v2VrfRoutSendTtlExceededValue
         INTEGER
      }

er1645v2VrfRoutSendTtlExceededGlobalIx OBJECT-TYPE
   SYNTAX      GlobalIndex
   MAX-ACCESS  not-accessible
   STATUS      current
   DESCRIPTION
      "The value of the tlsCntTreeGlobalIndex of the MANAGED OBJECT."
   ::= {er1645v2VrfRoutSendTtlExceededEntry 10}

er1645v2VrfRoutSendTtlExceededValue OBJECT-TYPE
   SYNTAX      INTEGER
               {
               disabled (0),
               enabled (1)
               }
   MAX-ACCESS  read-write
   STATUS      current
   DESCRIPTION
      "Path: vrfRouter.editConf.sendTtlExceeded

       Possibilities:
               disabled   (0)
               enabled   (1)"
   ::= {er1645v2VrfRoutSendTtlExceededEntry 2147483648}


er1645v2VrfRoutSendPortUnreachable OBJECT IDENTIFIER ::= {er1645v2VrfRout 31}

er1645v2VrfRoutSendPortUnreachableTable OBJECT-TYPE
   SYNTAX      SEQUENCE OF Er1645v2VrfRoutSendPortUnreachableEntry
   MAX-ACCESS  not-accessible
   STATUS      current
   DESCRIPTION
      "indicates if a ICMP Port Unreachable must be returned to a packet's source if
                        the destination port is unknown"
   ::= {er1645v2VrfRoutSendPortUnreachable 1}

er1645v2VrfRoutSendPortUnreachableEntry OBJECT-TYPE
   SYNTAX      Er1645v2VrfRoutSendPortUnreachableEntry
   MAX-ACCESS  not-accessible
   STATUS      current
   DESCRIPTION
      ""
   INDEX      { er1645v2VrfRoutSendPortUnreachableGlobalIx }
   ::= {er1645v2VrfRoutSendPortUnreachableTable 1}

Er1645v2VrfRoutSendPortUnreachableEntry ::=
   SEQUENCE
      {
      er1645v2VrfRoutSendPortUnreachableGlobalIx
         GlobalIndex,
      er1645v2VrfRoutSendPortUnreachableValue
         INTEGER
      }

er1645v2VrfRoutSendPortUnreachableGlobalIx OBJECT-TYPE
   SYNTAX      GlobalIndex
   MAX-ACCESS  not-accessible
   STATUS      current
   DESCRIPTION
      "The value of the tlsCntTreeGlobalIndex of the MANAGED OBJECT."
   ::= {er1645v2VrfRoutSendPortUnreachableEntry 10}

er1645v2VrfRoutSendPortUnreachableValue OBJECT-TYPE
   SYNTAX      INTEGER
               {
               disabled (0),
               enabled (1)
               }
   MAX-ACCESS  read-write
   STATUS      current
   DESCRIPTION
      "Path: vrfRouter.editConf.sendPortUnreachable

       Possibilities:
               disabled   (0)
               enabled   (1)"
   ::= {er1645v2VrfRoutSendPortUnreachableEntry 2147483648}


er1645v2VrfRoutSendAdminUnreachable OBJECT IDENTIFIER ::= {er1645v2VrfRout 56}

er1645v2VrfRoutSendAdminUnreachableTable OBJECT-TYPE
   SYNTAX      SEQUENCE OF Er1645v2VrfRoutSendAdminUnreachableEntry
   MAX-ACCESS  not-accessible
   STATUS      current
   DESCRIPTION
      "indicates if an ICMP can be returned to a packet's source if
                        the packet is discarded"
   ::= {er1645v2VrfRoutSendAdminUnreachable 1}

er1645v2VrfRoutSendAdminUnreachableEntry OBJECT-TYPE
   SYNTAX      Er1645v2VrfRoutSendAdminUnreachableEntry
   MAX-ACCESS  not-accessible
   STATUS      current
   DESCRIPTION
      ""
   INDEX      { er1645v2VrfRoutSendAdminUnreachableGlobalIx }
   ::= {er1645v2VrfRoutSendAdminUnreachableTable 1}

Er1645v2VrfRoutSendAdminUnreachableEntry ::=
   SEQUENCE
      {
      er1645v2VrfRoutSendAdminUnreachableGlobalIx
         GlobalIndex,
      er1645v2VrfRoutSendAdminUnreachableValue
         INTEGER
      }

er1645v2VrfRoutSendAdminUnreachableGlobalIx OBJECT-TYPE
   SYNTAX      GlobalIndex
   MAX-ACCESS  not-accessible
   STATUS      current
   DESCRIPTION
      "The value of the tlsCntTreeGlobalIndex of the MANAGED OBJECT."
   ::= {er1645v2VrfRoutSendAdminUnreachableEntry 10}

er1645v2VrfRoutSendAdminUnreachableValue OBJECT-TYPE
   SYNTAX      INTEGER
               {
               disabled (0),
               enabled (1)
               }
   MAX-ACCESS  read-write
   STATUS      current
   DESCRIPTION
      "Path: vrfRouter.editConf.sendAdminUnreachable

       Possibilities:
               disabled   (0)
               enabled   (1)"
   ::= {er1645v2VrfRoutSendAdminUnreachableEntry 2147483648}


er1645v2VrfRoutSendHostUnreachable OBJECT IDENTIFIER ::= {er1645v2VrfRout 36}

er1645v2VrfRoutSendHostUnreachableTable OBJECT-TYPE
   SYNTAX      SEQUENCE OF Er1645v2VrfRoutSendHostUnreachableEntry
   MAX-ACCESS  not-accessible
   STATUS      current
   DESCRIPTION
      "indicates if a ICMP Host Unreachable must be returned to a packet's source if
                        the destination host is unknown"
   ::= {er1645v2VrfRoutSendHostUnreachable 1}

er1645v2VrfRoutSendHostUnreachableEntry OBJECT-TYPE
   SYNTAX      Er1645v2VrfRoutSendHostUnreachableEntry
   MAX-ACCESS  not-accessible
   STATUS      current
   DESCRIPTION
      ""
   INDEX      { er1645v2VrfRoutSendHostUnreachableGlobalIx }
   ::= {er1645v2VrfRoutSendHostUnreachableTable 1}

Er1645v2VrfRoutSendHostUnreachableEntry ::=
   SEQUENCE
      {
      er1645v2VrfRoutSendHostUnreachableGlobalIx
         GlobalIndex,
      er1645v2VrfRoutSendHostUnreachableValue
         INTEGER
      }

er1645v2VrfRoutSendHostUnreachableGlobalIx OBJECT-TYPE
   SYNTAX      GlobalIndex
   MAX-ACCESS  not-accessible
   STATUS      current
   DESCRIPTION
      "The value of the tlsCntTreeGlobalIndex of the MANAGED OBJECT."
   ::= {er1645v2VrfRoutSendHostUnreachableEntry 10}

er1645v2VrfRoutSendHostUnreachableValue OBJECT-TYPE
   SYNTAX      INTEGER
               {
               disabled (0),
               enabled (1)
               }
   MAX-ACCESS  read-write
   STATUS      current
   DESCRIPTION
      "Path: vrfRouter.editConf.sendHostUnreachable

       Possibilities:
               disabled   (0)
               enabled   (1)"
   ::= {er1645v2VrfRoutSendHostUnreachableEntry 2147483648}


er1645v2VrfRoutAlternativeRoutes OBJECT IDENTIFIER ::= {er1645v2VrfRout 57}

er1645v2VrfRoutAlternativeRoutesTable OBJECT-TYPE
   SYNTAX      SEQUENCE OF Er1645v2VrfRoutAlternativeRoutesEntry
   MAX-ACCESS  not-accessible
   STATUS      current
   DESCRIPTION
      "indicates if load balancing has to be applied whenever multiple
                        routes are available"
   ::= {er1645v2VrfRoutAlternativeRoutes 1}

er1645v2VrfRoutAlternativeRoutesEntry OBJECT-TYPE
   SYNTAX      Er1645v2VrfRoutAlternativeRoutesEntry
   MAX-ACCESS  not-accessible
   STATUS      current
   DESCRIPTION
      ""
   INDEX      { er1645v2VrfRoutAlternativeRoutesGlobalIx }
   ::= {er1645v2VrfRoutAlternativeRoutesTable 1}

Er1645v2VrfRoutAlternativeRoutesEntry ::=
   SEQUENCE
      {
      er1645v2VrfRoutAlternativeRoutesGlobalIx
         GlobalIndex,
      er1645v2VrfRoutAlternativeRoutesValue
         INTEGER
      }

er1645v2VrfRoutAlternativeRoutesGlobalIx OBJECT-TYPE
   SYNTAX      GlobalIndex
   MAX-ACCESS  not-accessible
   STATUS      current
   DESCRIPTION
      "The value of the tlsCntTreeGlobalIndex of the MANAGED OBJECT."
   ::= {er1645v2VrfRoutAlternativeRoutesEntry 10}

er1645v2VrfRoutAlternativeRoutesValue OBJECT-TYPE
   SYNTAX      INTEGER
               {
               backup (0),
               roundRobin (1)
               }
   MAX-ACCESS  read-write
   STATUS      current
   DESCRIPTION
      "Path: vrfRouter.editConf.alternativeRoutes

       Possibilities:
               backup   (0)
               roundRobin   (1)"
   ::= {er1645v2VrfRoutAlternativeRoutesEntry 2147483648}


er1645v2VrfRoutRoutingProtocol OBJECT IDENTIFIER ::= {er1645v2VrfRout 34}

er1645v2VrfRoutRoutingProtocolTable OBJECT-TYPE
   SYNTAX      SEQUENCE OF Er1645v2VrfRoutRoutingProtocolEntry
   MAX-ACCESS  not-accessible
   STATUS      current
   DESCRIPTION
      "indicates which dynamic routing protocol should be used"
   ::= {er1645v2VrfRoutRoutingProtocol 1}

er1645v2VrfRoutRoutingProtocolEntry OBJECT-TYPE
   SYNTAX      Er1645v2VrfRoutRoutingProtocolEntry
   MAX-ACCESS  not-accessible
   STATUS      current
   DESCRIPTION
      ""
   INDEX      { er1645v2VrfRoutRoutingProtocolGlobalIx }
   ::= {er1645v2VrfRoutRoutingProtocolTable 1}

Er1645v2VrfRoutRoutingProtocolEntry ::=
   SEQUENCE
      {
      er1645v2VrfRoutRoutingProtocolGlobalIx
         GlobalIndex,
      er1645v2VrfRoutRoutingProtocolValue
         INTEGER
      }

er1645v2VrfRoutRoutingProtocolGlobalIx OBJECT-TYPE
   SYNTAX      GlobalIndex
   MAX-ACCESS  not-accessible
   STATUS      current
   DESCRIPTION
      "The value of the tlsCntTreeGlobalIndex of the MANAGED OBJECT."
   ::= {er1645v2VrfRoutRoutingProtocolEntry 10}

er1645v2VrfRoutRoutingProtocolValue OBJECT-TYPE
   SYNTAX      INTEGER
               {
               none (0),
               rip2 (1)
               }
   MAX-ACCESS  read-write
   STATUS      current
   DESCRIPTION
      "Path: vrfRouter.editConf.routingProtocol

       Possibilities:
               none   (0)
               rip2   (1)"
   ::= {er1645v2VrfRoutRoutingProtocolEntry 2147483648}


er1645v2VrfRoutRipUpInt OBJECT IDENTIFIER ::= {er1645v2VrfRout 35}

er1645v2VrfRoutRipUpIntTable OBJECT-TYPE
   SYNTAX      SEQUENCE OF Er1645v2VrfRoutRipUpIntEntry
   MAX-ACCESS  not-accessible
   STATUS      current
   DESCRIPTION
      "delay between RIP updates sent"
   ::= {er1645v2VrfRoutRipUpInt 1}

er1645v2VrfRoutRipUpIntEntry OBJECT-TYPE
   SYNTAX      Er1645v2VrfRoutRipUpIntEntry
   MAX-ACCESS  not-accessible
   STATUS      current
   DESCRIPTION
      ""
   INDEX      { er1645v2VrfRoutRipUpIntGlobalIx }
   ::= {er1645v2VrfRoutRipUpIntTable 1}

Er1645v2VrfRoutRipUpIntEntry ::=
   SEQUENCE
      {
      er1645v2VrfRoutRipUpIntGlobalIx
         GlobalIndex,
      er1645v2VrfRoutRipUpIntValue
         TimeTicks
      }

er1645v2VrfRoutRipUpIntGlobalIx OBJECT-TYPE
   SYNTAX      GlobalIndex
   MAX-ACCESS  not-accessible
   STATUS      current
   DESCRIPTION
      "The value of the tlsCntTreeGlobalIndex of the MANAGED OBJECT."
   ::= {er1645v2VrfRoutRipUpIntEntry 10}

er1645v2VrfRoutRipUpIntValue OBJECT-TYPE
   SYNTAX      TimeTicks
   MAX-ACCESS  read-write
   STATUS      current
   DESCRIPTION
      "Path: vrfRouter.editConf.ripUpdateInterval

       Time in centi-second."
   ::= {er1645v2VrfRoutRipUpIntEntry 2147483648}


er1645v2VrfRoutRipHoldDownTime OBJECT IDENTIFIER ::= {er1645v2VrfRout 78}

er1645v2VrfRoutRipHoldDownTimeTable OBJECT-TYPE
   SYNTAX      SEQUENCE OF Er1645v2VrfRoutRipHoldDownTimeEntry
   MAX-ACCESS  not-accessible
   STATUS      current
   DESCRIPTION
      "Time to wait before accepting better routes in order to prevent instable route-flapping"
   ::= {er1645v2VrfRoutRipHoldDownTime 1}

er1645v2VrfRoutRipHoldDownTimeEntry OBJECT-TYPE
   SYNTAX      Er1645v2VrfRoutRipHoldDownTimeEntry
   MAX-ACCESS  not-accessible
   STATUS      current
   DESCRIPTION
      ""
   INDEX      { er1645v2VrfRoutRipHoldDownTimeGlobalIx }
   ::= {er1645v2VrfRoutRipHoldDownTimeTable 1}

Er1645v2VrfRoutRipHoldDownTimeEntry ::=
   SEQUENCE
      {
      er1645v2VrfRoutRipHoldDownTimeGlobalIx
         GlobalIndex,
      er1645v2VrfRoutRipHoldDownTimeValue
         TimeTicks
      }

er1645v2VrfRoutRipHoldDownTimeGlobalIx OBJECT-TYPE
   SYNTAX      GlobalIndex
   MAX-ACCESS  not-accessible
   STATUS      current
   DESCRIPTION
      "The value of the tlsCntTreeGlobalIndex of the MANAGED OBJECT."
   ::= {er1645v2VrfRoutRipHoldDownTimeEntry 10}

er1645v2VrfRoutRipHoldDownTimeValue OBJECT-TYPE
   SYNTAX      TimeTicks
   MAX-ACCESS  read-write
   STATUS      current
   DESCRIPTION
      "Path: vrfRouter.editConf.ripHoldDownTime

       Time in centi-second."
   ::= {er1645v2VrfRoutRipHoldDownTimeEntry 2147483648}


er1645v2VrfRoutR2ScrtTbl OBJECT IDENTIFIER ::= {er1645v2VrfRout 42}

er1645v2VrfRoutR2ScrtTblSSCTable OBJECT-TYPE
   SYNTAX      SEQUENCE OF Er1645v2VrfRoutR2ScrtTblEntry
   MAX-ACCESS  not-accessible
   STATUS      current
   DESCRIPTION
      "table to store secret values for RIPv2 authentication"
   ::= {er1645v2VrfRoutR2ScrtTbl 1}

er1645v2VrfRoutR2ScrtTblEntry OBJECT-TYPE
   SYNTAX      Er1645v2VrfRoutR2ScrtTblEntry
   MAX-ACCESS  not-accessible
   STATUS      current
   DESCRIPTION
      ""
   INDEX      { er1645v2VrfRoutR2ScrtTblGlobalIx,
                er1645v2VrfRoutR2ScrtTblTableIx }
   ::= {er1645v2VrfRoutR2ScrtTblSSCTable 1}

Er1645v2VrfRoutR2ScrtTblEntry ::=
   SEQUENCE
      {
      er1645v2VrfRoutR2ScrtTblActions
         VariableLengthTableActions,
      er1645v2VrfRoutR2ScrtTblGlobalIx
         GlobalIndex,
      er1645v2VrfRoutR2ScrtTblTableIx
         TableIndex,
      er1645v2VrfRoutR2ScrtTblKeyId
         Integer32,
      er1645v2VrfRoutR2ScrtTblSecret
         DisplayString,
      er1645v2VrfRoutR2ScrtTblIf
         DisplayString
      }

er1645v2VrfRoutR2ScrtTblActions OBJECT-TYPE
   SYNTAX      VariableLengthTableActions
   MAX-ACCESS  read-write
   STATUS      current
   DESCRIPTION
      "By way of this field, some manipulations
       on this table may be performed."
   ::= {er1645v2VrfRoutR2ScrtTblEntry 2}

er1645v2VrfRoutR2ScrtTblGlobalIx OBJECT-TYPE
   SYNTAX      GlobalIndex
   MAX-ACCESS  not-accessible
   STATUS      current
   DESCRIPTION
      "The value of the tlsCntTreeGlobalIndex of the MANAGED OBJECT."
   ::= {er1645v2VrfRoutR2ScrtTblEntry 10}

er1645v2VrfRoutR2ScrtTblTableIx OBJECT-TYPE
   SYNTAX      TableIndex
   MAX-ACCESS  not-accessible
   STATUS      current
   DESCRIPTION
      ""
   ::= {er1645v2VrfRoutR2ScrtTblEntry 11}

er1645v2VrfRoutR2ScrtTblKeyId OBJECT-TYPE
   SYNTAX      Integer32
   MAX-ACCESS  read-write
   STATUS      current
   DESCRIPTION
      "Path: vrfRouter.editConf.ripv2SecretTable.keyId"
   ::= {er1645v2VrfRoutR2ScrtTblEntry 16777216}

er1645v2VrfRoutR2ScrtTblSecret OBJECT-TYPE
   SYNTAX      DisplayString
   MAX-ACCESS  read-write
   STATUS      current
   DESCRIPTION
      "Path: vrfRouter.editConf.ripv2SecretTable.secret"
   ::= {er1645v2VrfRoutR2ScrtTblEntry 33554432}

er1645v2VrfRoutR2ScrtTblIf OBJECT-TYPE
   SYNTAX      DisplayString
   MAX-ACCESS  read-write
   STATUS      current
   DESCRIPTION
      "Path: vrfRouter.editConf.ripv2SecretTable.interface"
   ::= {er1645v2VrfRoutR2ScrtTblEntry 50331648}


er1645v2VrfRoutRipPreference OBJECT IDENTIFIER ::= {er1645v2VrfRout 83}

er1645v2VrfRoutRipPreferenceTable OBJECT-TYPE
   SYNTAX      SEQUENCE OF Er1645v2VrfRoutRipPreferenceEntry
   MAX-ACCESS  not-accessible
   STATUS      current
   DESCRIPTION
      "preference"
   ::= {er1645v2VrfRoutRipPreference 1}

er1645v2VrfRoutRipPreferenceEntry OBJECT-TYPE
   SYNTAX      Er1645v2VrfRoutRipPreferenceEntry
   MAX-ACCESS  not-accessible
   STATUS      current
   DESCRIPTION
      ""
   INDEX      { er1645v2VrfRoutRipPreferenceGlobalIx }
   ::= {er1645v2VrfRoutRipPreferenceTable 1}

Er1645v2VrfRoutRipPreferenceEntry ::=
   SEQUENCE
      {
      er1645v2VrfRoutRipPreferenceGlobalIx
         GlobalIndex,
      er1645v2VrfRoutRipPreferenceValue
         Gauge32
      }

er1645v2VrfRoutRipPreferenceGlobalIx OBJECT-TYPE
   SYNTAX      GlobalIndex
   MAX-ACCESS  not-accessible
   STATUS      current
   DESCRIPTION
      "The value of the tlsCntTreeGlobalIndex of the MANAGED OBJECT."
   ::= {er1645v2VrfRoutRipPreferenceEntry 10}

er1645v2VrfRoutRipPreferenceValue OBJECT-TYPE
   SYNTAX      Gauge32
   MAX-ACCESS  read-write
   STATUS      current
   DESCRIPTION
      "Path: vrfRouter.editConf.ripPreference

       32 bit unsigned gauge value."
   ::= {er1645v2VrfRoutRipPreferenceEntry 2147483648}


er1645v2VrfRoutRipNeighbors OBJECT IDENTIFIER ::= {er1645v2VrfRout 50}

er1645v2VrfRoutRipNeighborsSSCTable OBJECT-TYPE
   SYNTAX      SEQUENCE OF Er1645v2VrfRoutRipNeighborsEntry
   MAX-ACCESS  not-accessible
   STATUS      current
   DESCRIPTION
      "rip neighbor table"
   ::= {er1645v2VrfRoutRipNeighbors 1}

er1645v2VrfRoutRipNeighborsEntry OBJECT-TYPE
   SYNTAX      Er1645v2VrfRoutRipNeighborsEntry
   MAX-ACCESS  not-accessible
   STATUS      current
   DESCRIPTION
      ""
   INDEX      { er1645v2VrfRoutRipNeighborsGlobalIx,
                er1645v2VrfRoutRipNeighborsTableIx }
   ::= {er1645v2VrfRoutRipNeighborsSSCTable 1}

Er1645v2VrfRoutRipNeighborsEntry ::=
   SEQUENCE
      {
      er1645v2VrfRoutRipNeighborsActions
         VariableLengthTableActions,
      er1645v2VrfRoutRipNeighborsGlobalIx
         GlobalIndex,
      er1645v2VrfRoutRipNeighborsTableIx
         TableIndex,
      er1645v2VrfRoutRipNeighborsIpAddress
         IpAddress
      }

er1645v2VrfRoutRipNeighborsActions OBJECT-TYPE
   SYNTAX      VariableLengthTableActions
   MAX-ACCESS  read-write
   STATUS      current
   DESCRIPTION
      "By way of this field, some manipulations
       on this table may be performed."
   ::= {er1645v2VrfRoutRipNeighborsEntry 2}

er1645v2VrfRoutRipNeighborsGlobalIx OBJECT-TYPE
   SYNTAX      GlobalIndex
   MAX-ACCESS  not-accessible
   STATUS      current
   DESCRIPTION
      "The value of the tlsCntTreeGlobalIndex of the MANAGED OBJECT."
   ::= {er1645v2VrfRoutRipNeighborsEntry 10}

er1645v2VrfRoutRipNeighborsTableIx OBJECT-TYPE
   SYNTAX      TableIndex
   MAX-ACCESS  not-accessible
   STATUS      current
   DESCRIPTION
      ""
   ::= {er1645v2VrfRoutRipNeighborsEntry 11}

er1645v2VrfRoutRipNeighborsIpAddress OBJECT-TYPE
   SYNTAX      IpAddress
   MAX-ACCESS  read-write
   STATUS      current
   DESCRIPTION
      "Path: vrfRouter.editConf.ripNeighbors.ipAddress"
   ::= {er1645v2VrfRoutRipNeighborsEntry 67108864}


er1645v2VrfRoutMulticastRouting OBJECT IDENTIFIER ::= {er1645v2VrfRout 17}

er1645v2VrfRoutMulticastRoutingTable OBJECT-TYPE
   SYNTAX      SEQUENCE OF Er1645v2VrfRoutMulticastRoutingEntry
   MAX-ACCESS  not-accessible
   STATUS      current
   DESCRIPTION
      "indicates if multicast routing (PIM/IGMP) is supported"
   ::= {er1645v2VrfRoutMulticastRouting 1}

er1645v2VrfRoutMulticastRoutingEntry OBJECT-TYPE
   SYNTAX      Er1645v2VrfRoutMulticastRoutingEntry
   MAX-ACCESS  not-accessible
   STATUS      current
   DESCRIPTION
      ""
   INDEX      { er1645v2VrfRoutMulticastRoutingGlobalIx }
   ::= {er1645v2VrfRoutMulticastRoutingTable 1}

Er1645v2VrfRoutMulticastRoutingEntry ::=
   SEQUENCE
      {
      er1645v2VrfRoutMulticastRoutingGlobalIx
         GlobalIndex,
      er1645v2VrfRoutMulticastRoutingValue
         INTEGER
      }

er1645v2VrfRoutMulticastRoutingGlobalIx OBJECT-TYPE
   SYNTAX      GlobalIndex
   MAX-ACCESS  not-accessible
   STATUS      current
   DESCRIPTION
      "The value of the tlsCntTreeGlobalIndex of the MANAGED OBJECT."
   ::= {er1645v2VrfRoutMulticastRoutingEntry 10}

er1645v2VrfRoutMulticastRoutingValue OBJECT-TYPE
   SYNTAX      INTEGER
               {
               disabled (0),
               enabled (1)
               }
   MAX-ACCESS  read-write
   STATUS      current
   DESCRIPTION
      "Path: vrfRouter.editConf.multicastRouting

       Possibilities:
               disabled   (0)
               enabled   (1)"
   ::= {er1645v2VrfRoutMulticastRoutingEntry 2147483648}


er1645v2VrfRoutDhcpStat OBJECT IDENTIFIER ::= {er1645v2VrfRout 51}

er1645v2VrfRoutDhcpStatSSCTable OBJECT-TYPE
   SYNTAX      SEQUENCE OF Er1645v2VrfRoutDhcpStatEntry
   MAX-ACCESS  not-accessible
   STATUS      current
   DESCRIPTION
      "Initialisation DHCP server"
   ::= {er1645v2VrfRoutDhcpStat 1}

er1645v2VrfRoutDhcpStatEntry OBJECT-TYPE
   SYNTAX      Er1645v2VrfRoutDhcpStatEntry
   MAX-ACCESS  not-accessible
   STATUS      current
   DESCRIPTION
      ""
   INDEX      { er1645v2VrfRoutDhcpStatGlobalIx,
                er1645v2VrfRoutDhcpStatTableIx }
   ::= {er1645v2VrfRoutDhcpStatSSCTable 1}

Er1645v2VrfRoutDhcpStatEntry ::=
   SEQUENCE
      {
      er1645v2VrfRoutDhcpStatActions
         VariableLengthTableActions,
      er1645v2VrfRoutDhcpStatGlobalIx
         GlobalIndex,
      er1645v2VrfRoutDhcpStatTableIx
         TableIndex,
      er1645v2VrfRoutDhcpStatIpAddress
         IpAddress,
      er1645v2VrfRoutDhcpStatMask
         IpAddress,
      er1645v2VrfRoutDhcpStatGateway
         IpAddress,
      er1645v2VrfRoutDhcpStatInterface
         DisplayString,
      er1645v2VrfRoutDhcpStatDnsSetting
         INTEGER,
      er1645v2VrfRoutDhcpStatNameServer
         IpAddress,
      er1645v2VrfRoutDhcpStatNameServer2
         IpAddress,
      er1645v2VrfRoutDhcpStatTftpServer
         IpAddress,
      er1645v2VrfRoutDhcpStatTftpServerOption
         DisplayString,
      er1645v2VrfRoutDhcpStatMacAddress
         OCTET STRING,
      er1645v2VrfRoutDhcpStatBootFile
         DisplayString,
      er1645v2VrfRoutDhcpStatBootFileOption
         DisplayString,
      er1645v2VrfRoutDhcpStatHostName
         DisplayString,
      er1645v2VrfRoutDhcpStatDomainName
         DisplayString,
      er1645v2VrfRoutDhcpStatNetbiosNS
         IpAddress,
      er1645v2VrfRoutDhcpStatNetbiosNS2
         IpAddress,
      er1645v2VrfRoutDhcpStatNetbiosNT
         INTEGER
      }

er1645v2VrfRoutDhcpStatActions OBJECT-TYPE
   SYNTAX      VariableLengthTableActions
   MAX-ACCESS  read-write
   STATUS      current
   DESCRIPTION
      "By way of this field, some manipulations
       on this table may be performed."
   ::= {er1645v2VrfRoutDhcpStatEntry 2}

er1645v2VrfRoutDhcpStatGlobalIx OBJECT-TYPE
   SYNTAX      GlobalIndex
   MAX-ACCESS  not-accessible
   STATUS      current
   DESCRIPTION
      "The value of the tlsCntTreeGlobalIndex of the MANAGED OBJECT."
   ::= {er1645v2VrfRoutDhcpStatEntry 10}

er1645v2VrfRoutDhcpStatTableIx OBJECT-TYPE
   SYNTAX      TableIndex
   MAX-ACCESS  not-accessible
   STATUS      current
   DESCRIPTION
      ""
   ::= {er1645v2VrfRoutDhcpStatEntry 11}

er1645v2VrfRoutDhcpStatIpAddress OBJECT-TYPE
   SYNTAX      IpAddress
   MAX-ACCESS  read-write
   STATUS      current
   DESCRIPTION
      "Path: vrfRouter.editConf.dhcpStatic.ipAddress"
   ::= {er1645v2VrfRoutDhcpStatEntry 16777216}

er1645v2VrfRoutDhcpStatMask OBJECT-TYPE
   SYNTAX      IpAddress
   MAX-ACCESS  read-write
   STATUS      current
   DESCRIPTION
      "Path: vrfRouter.editConf.dhcpStatic.mask"
   ::= {er1645v2VrfRoutDhcpStatEntry 33554432}

er1645v2VrfRoutDhcpStatGateway OBJECT-TYPE
   SYNTAX      IpAddress
   MAX-ACCESS  read-write
   STATUS      current
   DESCRIPTION
      "Path: vrfRouter.editConf.dhcpStatic.gateway"
   ::= {er1645v2VrfRoutDhcpStatEntry 50331648}

er1645v2VrfRoutDhcpStatInterface OBJECT-TYPE
   SYNTAX      DisplayString
   MAX-ACCESS  read-write
   STATUS      current
   DESCRIPTION
      "Path: vrfRouter.editConf.dhcpStatic.interface"
   ::= {er1645v2VrfRoutDhcpStatEntry 268435456}

er1645v2VrfRoutDhcpStatDnsSetting OBJECT-TYPE
   SYNTAX      INTEGER
               {
               configured (0),
               learned (1),
               relay (2)
               }
   MAX-ACCESS  read-write
   STATUS      current
   DESCRIPTION
      "Path: vrfRouter.editConf.dhcpStatic.dnsSetting

       Possibilities:
               configured   (0)
               learned   (1)
               relay   (2)"
   ::= {er1645v2VrfRoutDhcpStatEntry 285212672}

er1645v2VrfRoutDhcpStatNameServer OBJECT-TYPE
   SYNTAX      IpAddress
   MAX-ACCESS  read-write
   STATUS      current
   DESCRIPTION
      "Path: vrfRouter.editConf.dhcpStatic.nameServer"
   ::= {er1645v2VrfRoutDhcpStatEntry 67108864}

er1645v2VrfRoutDhcpStatNameServer2 OBJECT-TYPE
   SYNTAX      IpAddress
   MAX-ACCESS  read-write
   STATUS      current
   DESCRIPTION
      "Path: vrfRouter.editConf.dhcpStatic.nameServer2"
   ::= {er1645v2VrfRoutDhcpStatEntry 234881024}

er1645v2VrfRoutDhcpStatTftpServer OBJECT-TYPE
   SYNTAX      IpAddress
   MAX-ACCESS  read-write
   STATUS      current
   DESCRIPTION
      "Path: vrfRouter.editConf.dhcpStatic.tftpServer"
   ::= {er1645v2VrfRoutDhcpStatEntry 83886080}

er1645v2VrfRoutDhcpStatTftpServerOption OBJECT-TYPE
   SYNTAX      DisplayString
   MAX-ACCESS  read-write
   STATUS      current
   DESCRIPTION
      "Path: vrfRouter.editConf.dhcpStatic.tftpServerOption"
   ::= {er1645v2VrfRoutDhcpStatEntry 335544320}

er1645v2VrfRoutDhcpStatMacAddress OBJECT-TYPE
   SYNTAX      OCTET STRING
   MAX-ACCESS  read-write
   STATUS      current
   DESCRIPTION
      "Path: vrfRouter.editConf.dhcpStatic.macAddress

       MAC address."
   ::= {er1645v2VrfRoutDhcpStatEntry 100663296}

er1645v2VrfRoutDhcpStatBootFile OBJECT-TYPE
   SYNTAX      DisplayString
   MAX-ACCESS  read-write
   STATUS      current
   DESCRIPTION
      "Path: vrfRouter.editConf.dhcpStatic.bootFile"
   ::= {er1645v2VrfRoutDhcpStatEntry 117440512}

er1645v2VrfRoutDhcpStatBootFileOption OBJECT-TYPE
   SYNTAX      DisplayString
   MAX-ACCESS  read-write
   STATUS      current
   DESCRIPTION
      "Path: vrfRouter.editConf.dhcpStatic.bootFileOption"
   ::= {er1645v2VrfRoutDhcpStatEntry 352321536}

er1645v2VrfRoutDhcpStatHostName OBJECT-TYPE
   SYNTAX      DisplayString
   MAX-ACCESS  read-write
   STATUS      current
   DESCRIPTION
      "Path: vrfRouter.editConf.dhcpStatic.hostName"
   ::= {er1645v2VrfRoutDhcpStatEntry 134217728}

er1645v2VrfRoutDhcpStatDomainName OBJECT-TYPE
   SYNTAX      DisplayString
   MAX-ACCESS  read-write
   STATUS      current
   DESCRIPTION
      "Path: vrfRouter.editConf.dhcpStatic.domainName"
   ::= {er1645v2VrfRoutDhcpStatEntry 150994944}

er1645v2VrfRoutDhcpStatNetbiosNS OBJECT-TYPE
   SYNTAX      IpAddress
   MAX-ACCESS  read-write
   STATUS      current
   DESCRIPTION
      "Path: vrfRouter.editConf.dhcpStatic.netbiosNameServer"
   ::= {er1645v2VrfRoutDhcpStatEntry 167772160}

er1645v2VrfRoutDhcpStatNetbiosNS2 OBJECT-TYPE
   SYNTAX      IpAddress
   MAX-ACCESS  read-write
   STATUS      current
   DESCRIPTION
      "Path: vrfRouter.editConf.dhcpStatic.netbiosNameServer2"
   ::= {er1645v2VrfRoutDhcpStatEntry 251658240}

er1645v2VrfRoutDhcpStatNetbiosNT OBJECT-TYPE
   SYNTAX      INTEGER
               {
               nomnode (0),
               bmnode (1),
               pmnode (2),
               mmnode (4),
               hmnode (8)
               }
   MAX-ACCESS  read-write
   STATUS      current
   DESCRIPTION
      "Path: vrfRouter.editConf.dhcpStatic.netbiosNodeType

       Possibilities:
               no-node   (0)
               B-node   (1)
               P-node   (2)
               M-node   (4)
               H-node   (8)"
   ::= {er1645v2VrfRoutDhcpStatEntry 184549376}

er1645v2VrfRoutDhcpStatOptions OBJECT-TYPE
   SYNTAX      SEQUENCE OF Er1645v2VrfRoutDhcpStatOptionsEntry
   MAX-ACCESS  not-accessible
   STATUS      current
   DESCRIPTION
      ""
   ::= {er1645v2VrfRoutDhcpStat 402653184}

er1645v2VrfRoutDhcpStatOptionsEntry OBJECT-TYPE
   SYNTAX      Er1645v2VrfRoutDhcpStatOptionsEntry
   MAX-ACCESS  not-accessible
   STATUS      current
   DESCRIPTION
      ""
   INDEX      { er1645v2VrfRoutDhcpStatOptionsGlobalIx,
                er1645v2VrfRoutDhcpStatTableIx,
                er1645v2VrfRoutDhcpStatOptionsTableIx }
   ::= {er1645v2VrfRoutDhcpStatOptions 1}

Er1645v2VrfRoutDhcpStatOptionsEntry ::=
   SEQUENCE
      {
      er1645v2VrfRoutDhcpStatOptionsActions
         VariableLengthTableActions,
      er1645v2VrfRoutDhcpStatOptionsGlobalIx
         GlobalIndex,
      er1645v2VrfRoutDhcpStatOptionsTableIx
         TableIndex,
      er1645v2VrfRoutDhcpStatOptionsCode
         Integer32,
      er1645v2VrfRoutDhcpStatOptionsValueAscii
         DisplayString,
      er1645v2VrfRoutDhcpStatOptionsValueDecimal
         Integer32,
      er1645v2VrfRoutDhcpStatOptionsValueHexData
         OCTET STRING,
      er1645v2VrfRoutDhcpStatOptionsValueIpAddress
         IpAddress
      }

er1645v2VrfRoutDhcpStatOptionsActions OBJECT-TYPE
   SYNTAX      VariableLengthTableActions
   MAX-ACCESS  read-write
   STATUS      current
   DESCRIPTION
      "By way of this field, some manipulations
       on this table may be performed."
   ::= {er1645v2VrfRoutDhcpStatOptionsEntry 2}

er1645v2VrfRoutDhcpStatOptionsGlobalIx OBJECT-TYPE
   SYNTAX      GlobalIndex
   MAX-ACCESS  not-accessible
   STATUS      current
   DESCRIPTION
      "The value of the tlsCntTreeGlobalIndex of the MANAGED OBJECT."
   ::= {er1645v2VrfRoutDhcpStatOptionsEntry 10}

er1645v2VrfRoutDhcpStatOptionsTableIx OBJECT-TYPE
   SYNTAX      TableIndex
   MAX-ACCESS  not-accessible
   STATUS      current
   DESCRIPTION
      ""
   ::= {er1645v2VrfRoutDhcpStatOptionsEntry 11}

er1645v2VrfRoutDhcpStatOptionsCode OBJECT-TYPE
   SYNTAX      Integer32
   MAX-ACCESS  read-write
   STATUS      current
   DESCRIPTION
      "Path: vrfRouter.editConf.dhcpStatic.options.code"
   ::= {er1645v2VrfRoutDhcpStatOptionsEntry 16777216}

er1645v2VrfRoutDhcpStatOptionsValueAscii OBJECT-TYPE
   SYNTAX      DisplayString
   MAX-ACCESS  read-write
   STATUS      current
   DESCRIPTION
      "Path: vrfRouter.editConf.dhcpStatic.options.value.ascii"
   ::= {er1645v2VrfRoutDhcpStatOptionsEntry 33619968}

er1645v2VrfRoutDhcpStatOptionsValueDecimal OBJECT-TYPE
   SYNTAX      Integer32
   MAX-ACCESS  read-write
   STATUS      current
   DESCRIPTION
      "Path: vrfRouter.editConf.dhcpStatic.options.value.decimal"
   ::= {er1645v2VrfRoutDhcpStatOptionsEntry 33685504}

er1645v2VrfRoutDhcpStatOptionsValueHexData OBJECT-TYPE
   SYNTAX      OCTET STRING
   MAX-ACCESS  read-write
   STATUS      current
   DESCRIPTION
      "Path: vrfRouter.editConf.dhcpStatic.options.value.hexData"
   ::= {er1645v2VrfRoutDhcpStatOptionsEntry 33751040}

er1645v2VrfRoutDhcpStatOptionsValueIpAddress OBJECT-TYPE
   SYNTAX      IpAddress
   MAX-ACCESS  read-write
   STATUS      current
   DESCRIPTION
      "Path: vrfRouter.editConf.dhcpStatic.options.value.ipAddress"
   ::= {er1645v2VrfRoutDhcpStatOptionsEntry 33816576}


er1645v2VrfRoutDhcpDyn OBJECT IDENTIFIER ::= {er1645v2VrfRout 52}

er1645v2VrfRoutDhcpDynSSCTable OBJECT-TYPE
   SYNTAX      SEQUENCE OF Er1645v2VrfRoutDhcpDynEntry
   MAX-ACCESS  not-accessible
   STATUS      current
   DESCRIPTION
      "Initialisation DHCP server"
   ::= {er1645v2VrfRoutDhcpDyn 1}

er1645v2VrfRoutDhcpDynEntry OBJECT-TYPE
   SYNTAX      Er1645v2VrfRoutDhcpDynEntry
   MAX-ACCESS  not-accessible
   STATUS      current
   DESCRIPTION
      ""
   INDEX      { er1645v2VrfRoutDhcpDynGlobalIx,
                er1645v2VrfRoutDhcpDynTableIx }
   ::= {er1645v2VrfRoutDhcpDynSSCTable 1}

Er1645v2VrfRoutDhcpDynEntry ::=
   SEQUENCE
      {
      er1645v2VrfRoutDhcpDynActions
         VariableLengthTableActions,
      er1645v2VrfRoutDhcpDynGlobalIx
         GlobalIndex,
      er1645v2VrfRoutDhcpDynTableIx
         TableIndex,
      er1645v2VrfRoutDhcpDynIpcpSubnet
         DisplayString,
      er1645v2VrfRoutDhcpDynIpStartAddress
         IpAddress,
      er1645v2VrfRoutDhcpDynIpEndAddress
         IpAddress,
      er1645v2VrfRoutDhcpDynMask
         IpAddress,
      er1645v2VrfRoutDhcpDynGateway
         IpAddress,
      er1645v2VrfRoutDhcpDynInterface
         DisplayString,
      er1645v2VrfRoutDhcpDynDnsSetting
         INTEGER,
      er1645v2VrfRoutDhcpDynNameServer
         IpAddress,
      er1645v2VrfRoutDhcpDynNameServer2
         IpAddress,
      er1645v2VrfRoutDhcpDynTftpServer
         IpAddress,
      er1645v2VrfRoutDhcpDynTftpServerOption
         DisplayString,
      er1645v2VrfRoutDhcpDynLeaseTime
         TimeTicks,
      er1645v2VrfRoutDhcpDynHoldTime
         TimeTicks,
      er1645v2VrfRoutDhcpDynBootFile
         DisplayString,
      er1645v2VrfRoutDhcpDynBootFileOption
         DisplayString,
      er1645v2VrfRoutDhcpDynHostName
         DisplayString,
      er1645v2VrfRoutDhcpDynDomainName
         DisplayString,
      er1645v2VrfRoutDhcpDynNetbiosNS
         IpAddress,
      er1645v2VrfRoutDhcpDynNetbiosNS2
         IpAddress,
      er1645v2VrfRoutDhcpDynNetbiosNT
         INTEGER
      }

er1645v2VrfRoutDhcpDynActions OBJECT-TYPE
   SYNTAX      VariableLengthTableActions
   MAX-ACCESS  read-write
   STATUS      current
   DESCRIPTION
      "By way of this field, some manipulations
       on this table may be performed."
   ::= {er1645v2VrfRoutDhcpDynEntry 2}

er1645v2VrfRoutDhcpDynGlobalIx OBJECT-TYPE
   SYNTAX      GlobalIndex
   MAX-ACCESS  not-accessible
   STATUS      current
   DESCRIPTION
      "The value of the tlsCntTreeGlobalIndex of the MANAGED OBJECT."
   ::= {er1645v2VrfRoutDhcpDynEntry 10}

er1645v2VrfRoutDhcpDynTableIx OBJECT-TYPE
   SYNTAX      TableIndex
   MAX-ACCESS  not-accessible
   STATUS      current
   DESCRIPTION
      ""
   ::= {er1645v2VrfRoutDhcpDynEntry 11}

er1645v2VrfRoutDhcpDynIpcpSubnet OBJECT-TYPE
   SYNTAX      DisplayString
   MAX-ACCESS  read-write
   STATUS      current
   DESCRIPTION
      "Path: vrfRouter.editConf.dhcpDynamic.ipcpSubnet"
   ::= {er1645v2VrfRoutDhcpDynEntry 301989888}

er1645v2VrfRoutDhcpDynIpStartAddress OBJECT-TYPE
   SYNTAX      IpAddress
   MAX-ACCESS  read-write
   STATUS      current
   DESCRIPTION
      "Path: vrfRouter.editConf.dhcpDynamic.ipStartAddress"
   ::= {er1645v2VrfRoutDhcpDynEntry 16777216}

er1645v2VrfRoutDhcpDynIpEndAddress OBJECT-TYPE
   SYNTAX      IpAddress
   MAX-ACCESS  read-write
   STATUS      current
   DESCRIPTION
      "Path: vrfRouter.editConf.dhcpDynamic.ipEndAddress"
   ::= {er1645v2VrfRoutDhcpDynEntry 33554432}

er1645v2VrfRoutDhcpDynMask OBJECT-TYPE
   SYNTAX      IpAddress
   MAX-ACCESS  read-write
   STATUS      current
   DESCRIPTION
      "Path: vrfRouter.editConf.dhcpDynamic.mask"
   ::= {er1645v2VrfRoutDhcpDynEntry 50331648}

er1645v2VrfRoutDhcpDynGateway OBJECT-TYPE
   SYNTAX      IpAddress
   MAX-ACCESS  read-write
   STATUS      current
   DESCRIPTION
      "Path: vrfRouter.editConf.dhcpDynamic.gateway"
   ::= {er1645v2VrfRoutDhcpDynEntry 67108864}

er1645v2VrfRoutDhcpDynInterface OBJECT-TYPE
   SYNTAX      DisplayString
   MAX-ACCESS  read-write
   STATUS      current
   DESCRIPTION
      "Path: vrfRouter.editConf.dhcpDynamic.interface"
   ::= {er1645v2VrfRoutDhcpDynEntry 268435456}

er1645v2VrfRoutDhcpDynDnsSetting OBJECT-TYPE
   SYNTAX      INTEGER
               {
               configured (0),
               learned (1),
               relay (2)
               }
   MAX-ACCESS  read-write
   STATUS      current
   DESCRIPTION
      "Path: vrfRouter.editConf.dhcpDynamic.dnsSetting

       Possibilities:
               configured   (0)
               learned   (1)
               relay   (2)"
   ::= {er1645v2VrfRoutDhcpDynEntry 285212672}

er1645v2VrfRoutDhcpDynNameServer OBJECT-TYPE
   SYNTAX      IpAddress
   MAX-ACCESS  read-write
   STATUS      current
   DESCRIPTION
      "Path: vrfRouter.editConf.dhcpDynamic.nameServer"
   ::= {er1645v2VrfRoutDhcpDynEntry 83886080}

er1645v2VrfRoutDhcpDynNameServer2 OBJECT-TYPE
   SYNTAX      IpAddress
   MAX-ACCESS  read-write
   STATUS      current
   DESCRIPTION
      "Path: vrfRouter.editConf.dhcpDynamic.nameServer2"
   ::= {er1645v2VrfRoutDhcpDynEntry 234881024}

er1645v2VrfRoutDhcpDynTftpServer OBJECT-TYPE
   SYNTAX      IpAddress
   MAX-ACCESS  read-write
   STATUS      current
   DESCRIPTION
      "Path: vrfRouter.editConf.dhcpDynamic.tftpServer"
   ::= {er1645v2VrfRoutDhcpDynEntry 100663296}

er1645v2VrfRoutDhcpDynTftpServerOption OBJECT-TYPE
   SYNTAX      DisplayString
   MAX-ACCESS  read-write
   STATUS      current
   DESCRIPTION
      "Path: vrfRouter.editConf.dhcpDynamic.tftpServerOption"
   ::= {er1645v2VrfRoutDhcpDynEntry 335544320}

er1645v2VrfRoutDhcpDynLeaseTime OBJECT-TYPE
   SYNTAX      TimeTicks
   MAX-ACCESS  read-write
   STATUS      current
   DESCRIPTION
      "Path: vrfRouter.editConf.dhcpDynamic.leaseTime

       Time in centi-second."
   ::= {er1645v2VrfRoutDhcpDynEntry 117440512}

er1645v2VrfRoutDhcpDynHoldTime OBJECT-TYPE
   SYNTAX      TimeTicks
   MAX-ACCESS  read-write
   STATUS      current
   DESCRIPTION
      "Path: vrfRouter.editConf.dhcpDynamic.holdTime

       Time in centi-second."
   ::= {er1645v2VrfRoutDhcpDynEntry 134217728}

er1645v2VrfRoutDhcpDynBootFile OBJECT-TYPE
   SYNTAX      DisplayString
   MAX-ACCESS  read-write
   STATUS      current
   DESCRIPTION
      "Path: vrfRouter.editConf.dhcpDynamic.bootFile"
   ::= {er1645v2VrfRoutDhcpDynEntry 150994944}

er1645v2VrfRoutDhcpDynBootFileOption OBJECT-TYPE
   SYNTAX      DisplayString
   MAX-ACCESS  read-write
   STATUS      current
   DESCRIPTION
      "Path: vrfRouter.editConf.dhcpDynamic.bootFileOption"
   ::= {er1645v2VrfRoutDhcpDynEntry 352321536}

er1645v2VrfRoutDhcpDynHostName OBJECT-TYPE
   SYNTAX      DisplayString
   MAX-ACCESS  read-write
   STATUS      current
   DESCRIPTION
      "Path: vrfRouter.editConf.dhcpDynamic.hostName"
   ::= {er1645v2VrfRoutDhcpDynEntry 167772160}

er1645v2VrfRoutDhcpDynDomainName OBJECT-TYPE
   SYNTAX      DisplayString
   MAX-ACCESS  read-write
   STATUS      current
   DESCRIPTION
      "Path: vrfRouter.editConf.dhcpDynamic.domainName"
   ::= {er1645v2VrfRoutDhcpDynEntry 184549376}

er1645v2VrfRoutDhcpDynNetbiosNS OBJECT-TYPE
   SYNTAX      IpAddress
   MAX-ACCESS  read-write
   STATUS      current
   DESCRIPTION
      "Path: vrfRouter.editConf.dhcpDynamic.netbiosNameServer"
   ::= {er1645v2VrfRoutDhcpDynEntry 201326592}

er1645v2VrfRoutDhcpDynNetbiosNS2 OBJECT-TYPE
   SYNTAX      IpAddress
   MAX-ACCESS  read-write
   STATUS      current
   DESCRIPTION
      "Path: vrfRouter.editConf.dhcpDynamic.netbiosNameServer2"
   ::= {er1645v2VrfRoutDhcpDynEntry 251658240}

er1645v2VrfRoutDhcpDynNetbiosNT OBJECT-TYPE
   SYNTAX      INTEGER
               {
               nomnode (0),
               bmnode (1),
               pmnode (2),
               mmnode (4),
               hmnode (8)
               }
   MAX-ACCESS  read-write
   STATUS      current
   DESCRIPTION
      "Path: vrfRouter.editConf.dhcpDynamic.netbiosNodeType

       Possibilities:
               no-node   (0)
               B-node   (1)
               P-node   (2)
               M-node   (4)
               H-node   (8)"
   ::= {er1645v2VrfRoutDhcpDynEntry 218103808}

er1645v2VrfRoutDhcpDynOptions OBJECT-TYPE
   SYNTAX      SEQUENCE OF Er1645v2VrfRoutDhcpDynOptionsEntry
   MAX-ACCESS  not-accessible
   STATUS      current
   DESCRIPTION
      ""
   ::= {er1645v2VrfRoutDhcpDyn 402653184}

er1645v2VrfRoutDhcpDynOptionsEntry OBJECT-TYPE
   SYNTAX      Er1645v2VrfRoutDhcpDynOptionsEntry
   MAX-ACCESS  not-accessible
   STATUS      current
   DESCRIPTION
      ""
   INDEX      { er1645v2VrfRoutDhcpDynOptionsGlobalIx,
                er1645v2VrfRoutDhcpDynTableIx,
                er1645v2VrfRoutDhcpDynOptionsTableIx }
   ::= {er1645v2VrfRoutDhcpDynOptions 1}

Er1645v2VrfRoutDhcpDynOptionsEntry ::=
   SEQUENCE
      {
      er1645v2VrfRoutDhcpDynOptionsActions
         VariableLengthTableActions,
      er1645v2VrfRoutDhcpDynOptionsGlobalIx
         GlobalIndex,
      er1645v2VrfRoutDhcpDynOptionsTableIx
         TableIndex,
      er1645v2VrfRoutDhcpDynOptionsCode
         Integer32,
      er1645v2VrfRoutDhcpDynOptionsValueAscii
         DisplayString,
      er1645v2VrfRoutDhcpDynOptionsValueDecimal
         Integer32,
      er1645v2VrfRoutDhcpDynOptionsValueHexData
         OCTET STRING,
      er1645v2VrfRoutDhcpDynOptionsValueIpAddress
         IpAddress
      }

er1645v2VrfRoutDhcpDynOptionsActions OBJECT-TYPE
   SYNTAX      VariableLengthTableActions
   MAX-ACCESS  read-write
   STATUS      current
   DESCRIPTION
      "By way of this field, some manipulations
       on this table may be performed."
   ::= {er1645v2VrfRoutDhcpDynOptionsEntry 2}

er1645v2VrfRoutDhcpDynOptionsGlobalIx OBJECT-TYPE
   SYNTAX      GlobalIndex
   MAX-ACCESS  not-accessible
   STATUS      current
   DESCRIPTION
      "The value of the tlsCntTreeGlobalIndex of the MANAGED OBJECT."
   ::= {er1645v2VrfRoutDhcpDynOptionsEntry 10}

er1645v2VrfRoutDhcpDynOptionsTableIx OBJECT-TYPE
   SYNTAX      TableIndex
   MAX-ACCESS  not-accessible
   STATUS      current
   DESCRIPTION
      ""
   ::= {er1645v2VrfRoutDhcpDynOptionsEntry 11}

er1645v2VrfRoutDhcpDynOptionsCode OBJECT-TYPE
   SYNTAX      Integer32
   MAX-ACCESS  read-write
   STATUS      current
   DESCRIPTION
      "Path: vrfRouter.editConf.dhcpDynamic.options.code"
   ::= {er1645v2VrfRoutDhcpDynOptionsEntry 16777216}

er1645v2VrfRoutDhcpDynOptionsValueAscii OBJECT-TYPE
   SYNTAX      DisplayString
   MAX-ACCESS  read-write
   STATUS      current
   DESCRIPTION
      "Path: vrfRouter.editConf.dhcpDynamic.options.value.ascii"
   ::= {er1645v2VrfRoutDhcpDynOptionsEntry 33619968}

er1645v2VrfRoutDhcpDynOptionsValueDecimal OBJECT-TYPE
   SYNTAX      Integer32
   MAX-ACCESS  read-write
   STATUS      current
   DESCRIPTION
      "Path: vrfRouter.editConf.dhcpDynamic.options.value.decimal"
   ::= {er1645v2VrfRoutDhcpDynOptionsEntry 33685504}

er1645v2VrfRoutDhcpDynOptionsValueHexData OBJECT-TYPE
   SYNTAX      OCTET STRING
   MAX-ACCESS  read-write
   STATUS      current
   DESCRIPTION
      "Path: vrfRouter.editConf.dhcpDynamic.options.value.hexData"
   ::= {er1645v2VrfRoutDhcpDynOptionsEntry 33751040}

er1645v2VrfRoutDhcpDynOptionsValueIpAddress OBJECT-TYPE
   SYNTAX      IpAddress
   MAX-ACCESS  read-write
   STATUS      current
   DESCRIPTION
      "Path: vrfRouter.editConf.dhcpDynamic.options.value.ipAddress"
   ::= {er1645v2VrfRoutDhcpDynOptionsEntry 33816576}


er1645v2VrfRoutDhcpCheckAddress OBJECT IDENTIFIER ::= {er1645v2VrfRout 53}

er1645v2VrfRoutDhcpCheckAddressTable OBJECT-TYPE
   SYNTAX      SEQUENCE OF Er1645v2VrfRoutDhcpCheckAddressEntry
   MAX-ACCESS  not-accessible
   STATUS      current
   DESCRIPTION
      "Should the DCHP server check if the given address is free"
   ::= {er1645v2VrfRoutDhcpCheckAddress 1}

er1645v2VrfRoutDhcpCheckAddressEntry OBJECT-TYPE
   SYNTAX      Er1645v2VrfRoutDhcpCheckAddressEntry
   MAX-ACCESS  not-accessible
   STATUS      current
   DESCRIPTION
      ""
   INDEX      { er1645v2VrfRoutDhcpCheckAddressGlobalIx }
   ::= {er1645v2VrfRoutDhcpCheckAddressTable 1}

Er1645v2VrfRoutDhcpCheckAddressEntry ::=
   SEQUENCE
      {
      er1645v2VrfRoutDhcpCheckAddressGlobalIx
         GlobalIndex,
      er1645v2VrfRoutDhcpCheckAddressValue
         INTEGER
      }

er1645v2VrfRoutDhcpCheckAddressGlobalIx OBJECT-TYPE
   SYNTAX      GlobalIndex
   MAX-ACCESS  not-accessible
   STATUS      current
   DESCRIPTION
      "The value of the tlsCntTreeGlobalIndex of the MANAGED OBJECT."
   ::= {er1645v2VrfRoutDhcpCheckAddressEntry 10}

er1645v2VrfRoutDhcpCheckAddressValue OBJECT-TYPE
   SYNTAX      INTEGER
               {
               disabled (0),
               enabled (1),
               arpOnly (2)
               }
   MAX-ACCESS  read-write
   STATUS      current
   DESCRIPTION
      "Path: vrfRouter.editConf.dhcpCheckAddress

       Possibilities:
               disabled   (0)
               enabled   (1)
               arpOnly   (2)"
   ::= {er1645v2VrfRoutDhcpCheckAddressEntry 2147483648}


er1645v2VrfRoutDhcpCustomVendorId OBJECT IDENTIFIER ::= {er1645v2VrfRout 81}

er1645v2VrfRoutDhcpCustomVendorIdTable OBJECT-TYPE
   SYNTAX      SEQUENCE OF Er1645v2VrfRoutDhcpCustomVendorIdEntry
   MAX-ACCESS  not-accessible
   STATUS      current
   DESCRIPTION
      "custom-defined DCHP Vendor Id"
   ::= {er1645v2VrfRoutDhcpCustomVendorId 1}

er1645v2VrfRoutDhcpCustomVendorIdEntry OBJECT-TYPE
   SYNTAX      Er1645v2VrfRoutDhcpCustomVendorIdEntry
   MAX-ACCESS  not-accessible
   STATUS      current
   DESCRIPTION
      ""
   INDEX      { er1645v2VrfRoutDhcpCustomVendorIdGlobalIx }
   ::= {er1645v2VrfRoutDhcpCustomVendorIdTable 1}

Er1645v2VrfRoutDhcpCustomVendorIdEntry ::=
   SEQUENCE
      {
      er1645v2VrfRoutDhcpCustomVendorIdGlobalIx
         GlobalIndex,
      er1645v2VrfRoutDhcpCustomVendorIdValue
         DisplayString
      }

er1645v2VrfRoutDhcpCustomVendorIdGlobalIx OBJECT-TYPE
   SYNTAX      GlobalIndex
   MAX-ACCESS  not-accessible
   STATUS      current
   DESCRIPTION
      "The value of the tlsCntTreeGlobalIndex of the MANAGED OBJECT."
   ::= {er1645v2VrfRoutDhcpCustomVendorIdEntry 10}

er1645v2VrfRoutDhcpCustomVendorIdValue OBJECT-TYPE
   SYNTAX      DisplayString
   MAX-ACCESS  read-write
   STATUS      current
   DESCRIPTION
      "Path: vrfRouter.editConf.dhcpCustomVendorId"
   ::= {er1645v2VrfRoutDhcpCustomVendorIdEntry 2147483648}


er1645v2VrfRoutDhcpClientIdentifier OBJECT IDENTIFIER ::= {er1645v2VrfRout 91}

er1645v2VrfRoutDhcpClientIdentifierTable OBJECT-TYPE
   SYNTAX      SEQUENCE OF Er1645v2VrfRoutDhcpClientIdentifierEntry
   MAX-ACCESS  not-accessible
   STATUS      current
   DESCRIPTION
      "custom-defined DCHP Vendor Id"
   ::= {er1645v2VrfRoutDhcpClientIdentifier 1}

er1645v2VrfRoutDhcpClientIdentifierEntry OBJECT-TYPE
   SYNTAX      Er1645v2VrfRoutDhcpClientIdentifierEntry
   MAX-ACCESS  not-accessible
   STATUS      current
   DESCRIPTION
      ""
   INDEX      { er1645v2VrfRoutDhcpClientIdentifierGlobalIx }
   ::= {er1645v2VrfRoutDhcpClientIdentifierTable 1}

Er1645v2VrfRoutDhcpClientIdentifierEntry ::=
   SEQUENCE
      {
      er1645v2VrfRoutDhcpClientIdentifierGlobalIx
         GlobalIndex,
      er1645v2VrfRoutDhcpClientIdentifierValue
         INTEGER
      }

er1645v2VrfRoutDhcpClientIdentifierGlobalIx OBJECT-TYPE
   SYNTAX      GlobalIndex
   MAX-ACCESS  not-accessible
   STATUS      current
   DESCRIPTION
      "The value of the tlsCntTreeGlobalIndex of the MANAGED OBJECT."
   ::= {er1645v2VrfRoutDhcpClientIdentifierEntry 10}

er1645v2VrfRoutDhcpClientIdentifierValue OBJECT-TYPE
   SYNTAX      INTEGER
               {
               default (0),
               lowest (1),
               interfaceMac (2)
               }
   MAX-ACCESS  read-write
   STATUS      current
   DESCRIPTION
      "Path: vrfRouter.editConf.dhcpClientIdentifier

       Possibilities:
               default   (0)
               lowest   (1)
               interfaceMac   (2)"
   ::= {er1645v2VrfRoutDhcpClientIdentifierEntry 2147483648}


er1645v2VrfRoutAddrPools OBJECT IDENTIFIER ::= {er1645v2VrfRout 108}

er1645v2VrfRoutAddrPoolsSSCTable OBJECT-TYPE
   SYNTAX      SEQUENCE OF Er1645v2VrfRoutAddrPoolsEntry
   MAX-ACCESS  not-accessible
   STATUS      current
   DESCRIPTION
      "ip address pool union"
   ::= {er1645v2VrfRoutAddrPools 1}

er1645v2VrfRoutAddrPoolsEntry OBJECT-TYPE
   SYNTAX      Er1645v2VrfRoutAddrPoolsEntry
   MAX-ACCESS  not-accessible
   STATUS      current
   DESCRIPTION
      ""
   INDEX      { er1645v2VrfRoutAddrPoolsGlobalIx,
                er1645v2VrfRoutAddrPoolsTableIx }
   ::= {er1645v2VrfRoutAddrPoolsSSCTable 1}

Er1645v2VrfRoutAddrPoolsEntry ::=
   SEQUENCE
      {
      er1645v2VrfRoutAddrPoolsActions
         VariableLengthTableActions,
      er1645v2VrfRoutAddrPoolsGlobalIx
         GlobalIndex,
      er1645v2VrfRoutAddrPoolsTableIx
         TableIndex,
      er1645v2VrfRoutAddrPoolsName
         DisplayString,
      er1645v2VrfRoutAddrPoolsPoolIntervalFrom
         IpAddress,
      er1645v2VrfRoutAddrPoolsPoolIntervalTo
         IpAddress
      }

er1645v2VrfRoutAddrPoolsActions OBJECT-TYPE
   SYNTAX      VariableLengthTableActions
   MAX-ACCESS  read-write
   STATUS      current
   DESCRIPTION
      "By way of this field, some manipulations
       on this table may be performed."
   ::= {er1645v2VrfRoutAddrPoolsEntry 2}

er1645v2VrfRoutAddrPoolsGlobalIx OBJECT-TYPE
   SYNTAX      GlobalIndex
   MAX-ACCESS  not-accessible
   STATUS      current
   DESCRIPTION
      "The value of the tlsCntTreeGlobalIndex of the MANAGED OBJECT."
   ::= {er1645v2VrfRoutAddrPoolsEntry 10}

er1645v2VrfRoutAddrPoolsTableIx OBJECT-TYPE
   SYNTAX      TableIndex
   MAX-ACCESS  not-accessible
   STATUS      current
   DESCRIPTION
      ""
   ::= {er1645v2VrfRoutAddrPoolsEntry 11}

er1645v2VrfRoutAddrPoolsName OBJECT-TYPE
   SYNTAX      DisplayString
   MAX-ACCESS  read-write
   STATUS      current
   DESCRIPTION
      "Path: vrfRouter.editConf.addrPools.name"
   ::= {er1645v2VrfRoutAddrPoolsEntry 16777216}

er1645v2VrfRoutAddrPoolsPoolIntervalFrom OBJECT-TYPE
   SYNTAX      IpAddress
   MAX-ACCESS  read-write
   STATUS      current
   DESCRIPTION
      "Path: vrfRouter.editConf.addrPools.pool.interval.from"
   ::= {er1645v2VrfRoutAddrPoolsEntry 33686016}

er1645v2VrfRoutAddrPoolsPoolIntervalTo OBJECT-TYPE
   SYNTAX      IpAddress
   MAX-ACCESS  read-write
   STATUS      current
   DESCRIPTION
      "Path: vrfRouter.editConf.addrPools.pool.interval.to"
   ::= {er1645v2VrfRoutAddrPoolsEntry 33686272}

er1645v2VrfRoutAddrPoolsPoolList OBJECT-TYPE
   SYNTAX      SEQUENCE OF Er1645v2VrfRoutAddrPoolsPoolListEntry
   MAX-ACCESS  not-accessible
   STATUS      current
   DESCRIPTION
      ""
   ::= {er1645v2VrfRoutAddrPools 33619968}

er1645v2VrfRoutAddrPoolsPoolListEntry OBJECT-TYPE
   SYNTAX      Er1645v2VrfRoutAddrPoolsPoolListEntry
   MAX-ACCESS  not-accessible
   STATUS      current
   DESCRIPTION
      ""
   INDEX      { er1645v2VrfRoutAddrPoolsPoolListGlobalIx,
                er1645v2VrfRoutAddrPoolsTableIx,
                er1645v2VrfRoutAddrPoolsPoolListTableIx }
   ::= {er1645v2VrfRoutAddrPoolsPoolList 1}

Er1645v2VrfRoutAddrPoolsPoolListEntry ::=
   SEQUENCE
      {
      er1645v2VrfRoutAddrPoolsPoolListActions
         VariableLengthTableActions,
      er1645v2VrfRoutAddrPoolsPoolListGlobalIx
         GlobalIndex,
      er1645v2VrfRoutAddrPoolsPoolListTableIx
         TableIndex,
      er1645v2VrfRoutAddrPoolsPoolListLocal
         IpAddress,
      er1645v2VrfRoutAddrPoolsPoolListRemote
         IpAddress,
      er1645v2VrfRoutAddrPoolsPoolListNetMask
         IpAddress
      }

er1645v2VrfRoutAddrPoolsPoolListActions OBJECT-TYPE
   SYNTAX      VariableLengthTableActions
   MAX-ACCESS  read-write
   STATUS      current
   DESCRIPTION
      "By way of this field, some manipulations
       on this table may be performed."
   ::= {er1645v2VrfRoutAddrPoolsPoolListEntry 2}

er1645v2VrfRoutAddrPoolsPoolListGlobalIx OBJECT-TYPE
   SYNTAX      GlobalIndex
   MAX-ACCESS  not-accessible
   STATUS      current
   DESCRIPTION
      "The value of the tlsCntTreeGlobalIndex of the MANAGED OBJECT."
   ::= {er1645v2VrfRoutAddrPoolsPoolListEntry 10}

er1645v2VrfRoutAddrPoolsPoolListTableIx OBJECT-TYPE
   SYNTAX      TableIndex
   MAX-ACCESS  not-accessible
   STATUS      current
   DESCRIPTION
      ""
   ::= {er1645v2VrfRoutAddrPoolsPoolListEntry 11}

er1645v2VrfRoutAddrPoolsPoolListLocal OBJECT-TYPE
   SYNTAX      IpAddress
   MAX-ACCESS  read-write
   STATUS      current
   DESCRIPTION
      "Path: vrfRouter.editConf.addrPools.pool.list.local"
   ::= {er1645v2VrfRoutAddrPoolsPoolListEntry 33554432}

er1645v2VrfRoutAddrPoolsPoolListRemote OBJECT-TYPE
   SYNTAX      IpAddress
   MAX-ACCESS  read-write
   STATUS      current
   DESCRIPTION
      "Path: vrfRouter.editConf.addrPools.pool.list.remote"
   ::= {er1645v2VrfRoutAddrPoolsPoolListEntry 50331648}

er1645v2VrfRoutAddrPoolsPoolListNetMask OBJECT-TYPE
   SYNTAX      IpAddress
   MAX-ACCESS  read-write
   STATUS      current
   DESCRIPTION
      "Path: vrfRouter.editConf.addrPools.pool.list.netMask"
   ::= {er1645v2VrfRoutAddrPoolsPoolListEntry 67108864}


er1645v2VrfRoutDns OBJECT IDENTIFIER ::= {er1645v2VrfRout 64}

er1645v2VrfRoutDnsSSCTable OBJECT-TYPE
   SYNTAX      SEQUENCE OF Er1645v2VrfRoutDnsEntry
   MAX-ACCESS  not-accessible
   STATUS      current
   DESCRIPTION
      "Domain Name System"
   ::= {er1645v2VrfRoutDns 1}

er1645v2VrfRoutDnsEntry OBJECT-TYPE
   SYNTAX      Er1645v2VrfRoutDnsEntry
   MAX-ACCESS  not-accessible
   STATUS      current
   DESCRIPTION
      ""
   INDEX      { er1645v2VrfRoutDnsGlobalIx }
   ::= {er1645v2VrfRoutDnsSSCTable 1}

Er1645v2VrfRoutDnsEntry ::=
   SEQUENCE
      {
      er1645v2VrfRoutDnsGlobalIx
         GlobalIndex,
      er1645v2VrfRoutDnsPrimaryDns
         IpAddress,
      er1645v2VrfRoutDnsSecondaryDns
         IpAddress,
      er1645v2VrfRoutDnsDomainName
         DisplayString,
      er1645v2VrfRoutDnsIpV6Router
         DisplayString,
      er1645v2VrfRoutDnsPreference
         Integer32,
      er1645v2VrfRoutDnsProxy
         INTEGER,
      er1645v2VrfRoutDnsCacheSize
         Integer32
      }

er1645v2VrfRoutDnsGlobalIx OBJECT-TYPE
   SYNTAX      GlobalIndex
   MAX-ACCESS  not-accessible
   STATUS      current
   DESCRIPTION
      "The value of the tlsCntTreeGlobalIndex of the MANAGED OBJECT."
   ::= {er1645v2VrfRoutDnsEntry 10}

er1645v2VrfRoutDnsPrimaryDns OBJECT-TYPE
   SYNTAX      IpAddress
   MAX-ACCESS  read-write
   STATUS      current
   DESCRIPTION
      "Path: vrfRouter.editConf.dns.primaryDns"
   ::= {er1645v2VrfRoutDnsEntry 16777216}

er1645v2VrfRoutDnsSecondaryDns OBJECT-TYPE
   SYNTAX      IpAddress
   MAX-ACCESS  read-write
   STATUS      current
   DESCRIPTION
      "Path: vrfRouter.editConf.dns.secondaryDns"
   ::= {er1645v2VrfRoutDnsEntry 33554432}

er1645v2VrfRoutDnsDomainName OBJECT-TYPE
   SYNTAX      DisplayString
   MAX-ACCESS  read-write
   STATUS      current
   DESCRIPTION
      "Path: vrfRouter.editConf.dns.domainName"
   ::= {er1645v2VrfRoutDnsEntry 50331648}

er1645v2VrfRoutDnsIpV6Router OBJECT-TYPE
   SYNTAX      DisplayString
   MAX-ACCESS  read-write
   STATUS      current
   DESCRIPTION
      "Path: vrfRouter.editConf.dns.ipV6Router"
   ::= {er1645v2VrfRoutDnsEntry 67108864}

er1645v2VrfRoutDnsPreference OBJECT-TYPE
   SYNTAX      Integer32
   MAX-ACCESS  read-write
   STATUS      current
   DESCRIPTION
      "Path: vrfRouter.editConf.dns.preference"
   ::= {er1645v2VrfRoutDnsEntry 83886080}

er1645v2VrfRoutDnsProxy OBJECT-TYPE
   SYNTAX      INTEGER
               {
               disabled (0),
               enabled (1)
               }
   MAX-ACCESS  read-write
   STATUS      current
   DESCRIPTION
      "Path: vrfRouter.editConf.dns.proxy

       Possibilities:
               disabled   (0)
               enabled   (1)"
   ::= {er1645v2VrfRoutDnsEntry 100663296}

er1645v2VrfRoutDnsCacheSize OBJECT-TYPE
   SYNTAX      Integer32
   MAX-ACCESS  read-write
   STATUS      current
   DESCRIPTION
      "Path: vrfRouter.editConf.dns.cacheSize"
   ::= {er1645v2VrfRoutDnsEntry 117440512}


er1645v2VrfRoutLog OBJECT IDENTIFIER ::= {er1645v2VrfRout 67}

er1645v2VrfRoutLogSSCTable OBJECT-TYPE
   SYNTAX      SEQUENCE OF Er1645v2VrfRoutLogEntry
   MAX-ACCESS  not-accessible
   STATUS      current
   DESCRIPTION
      "router logging"
   ::= {er1645v2VrfRoutLog 1}

er1645v2VrfRoutLogEntry OBJECT-TYPE
   SYNTAX      Er1645v2VrfRoutLogEntry
   MAX-ACCESS  not-accessible
   STATUS      current
   DESCRIPTION
      ""
   INDEX      { er1645v2VrfRoutLogGlobalIx }
   ::= {er1645v2VrfRoutLogSSCTable 1}

Er1645v2VrfRoutLogEntry ::=
   SEQUENCE
      {
      er1645v2VrfRoutLogGlobalIx
         GlobalIndex,
      er1645v2VrfRoutLogMode
         INTEGER,
      er1645v2VrfRoutLogDhcpSyslogMask
         Integer32
      }

er1645v2VrfRoutLogGlobalIx OBJECT-TYPE
   SYNTAX      GlobalIndex
   MAX-ACCESS  not-accessible
   STATUS      current
   DESCRIPTION
      "The value of the tlsCntTreeGlobalIndex of the MANAGED OBJECT."
   ::= {er1645v2VrfRoutLogEntry 10}

er1645v2VrfRoutLogMode OBJECT-TYPE
   SYNTAX      INTEGER
               {
               disabled (0),
               enabled (1)
               }
   MAX-ACCESS  read-write
   STATUS      current
   DESCRIPTION
      "Path: vrfRouter.editConf.log.mode

       Possibilities:
               disabled   (0)
               enabled   (1)"
   ::= {er1645v2VrfRoutLogEntry 16777216}

er1645v2VrfRoutLogDhcpSyslogMask OBJECT-TYPE
   SYNTAX      Integer32
   MAX-ACCESS  read-write
   STATUS      current
   DESCRIPTION
      "Path: vrfRouter.editConf.log.dhcpSyslogMask

       Bit meanings:
               bit 0 = lease,
               bit 1 = renew,
               bit 2 = rebind,
               bit 3 = expired"
   ::= {er1645v2VrfRoutLogEntry 33554432}


er1645v2VrfRoutHelperProtocols OBJECT IDENTIFIER ::= {er1645v2VrfRout 15}

er1645v2VrfRoutHelperProtocolsSSCTable OBJECT-TYPE
   SYNTAX      SEQUENCE OF Er1645v2VrfRoutHelperProtocolsEntry
   MAX-ACCESS  not-accessible
   STATUS      current
   DESCRIPTION
      "list of protocols to be forwarded by the IP helpers"
   ::= {er1645v2VrfRoutHelperProtocols 1}

er1645v2VrfRoutHelperProtocolsEntry OBJECT-TYPE
   SYNTAX      Er1645v2VrfRoutHelperProtocolsEntry
   MAX-ACCESS  not-accessible
   STATUS      current
   DESCRIPTION
      ""
   INDEX      { er1645v2VrfRoutHelperProtocolsGlobalIx,
                er1645v2VrfRoutHelperProtocolsTableIx }
   ::= {er1645v2VrfRoutHelperProtocolsSSCTable 1}

Er1645v2VrfRoutHelperProtocolsEntry ::=
   SEQUENCE
      {
      er1645v2VrfRoutHelperProtocolsActions
         VariableLengthTableActions,
      er1645v2VrfRoutHelperProtocolsGlobalIx
         GlobalIndex,
      er1645v2VrfRoutHelperProtocolsTableIx
         TableIndex,
      er1645v2VrfRoutHelperProtocolsType
         Integer32
      }

er1645v2VrfRoutHelperProtocolsActions OBJECT-TYPE
   SYNTAX      VariableLengthTableActions
   MAX-ACCESS  read-write
   STATUS      current
   DESCRIPTION
      "By way of this field, some manipulations
       on this table may be performed."
   ::= {er1645v2VrfRoutHelperProtocolsEntry 2}

er1645v2VrfRoutHelperProtocolsGlobalIx OBJECT-TYPE
   SYNTAX      GlobalIndex
   MAX-ACCESS  not-accessible
   STATUS      current
   DESCRIPTION
      "The value of the tlsCntTreeGlobalIndex of the MANAGED OBJECT."
   ::= {er1645v2VrfRoutHelperProtocolsEntry 10}

er1645v2VrfRoutHelperProtocolsTableIx OBJECT-TYPE
   SYNTAX      TableIndex
   MAX-ACCESS  not-accessible
   STATUS      current
   DESCRIPTION
      ""
   ::= {er1645v2VrfRoutHelperProtocolsEntry 11}

er1645v2VrfRoutHelperProtocolsType OBJECT-TYPE
   SYNTAX      Integer32
   MAX-ACCESS  read-write
   STATUS      current
   DESCRIPTION
      "Path: vrfRouter.editConf.helperProtocols.protocol"
   ::= {er1645v2VrfRoutHelperProtocolsEntry 16777216}


er1645v2VrfRoutHosts OBJECT IDENTIFIER ::= {er1645v2VrfRout 49}

er1645v2VrfRoutHostsSSCTable OBJECT-TYPE
   SYNTAX      SEQUENCE OF Er1645v2VrfRoutHostsEntry
   MAX-ACCESS  not-accessible
   STATUS      current
   DESCRIPTION
      "table of hosts with their ip address"
   ::= {er1645v2VrfRoutHosts 1}

er1645v2VrfRoutHostsEntry OBJECT-TYPE
   SYNTAX      Er1645v2VrfRoutHostsEntry
   MAX-ACCESS  not-accessible
   STATUS      current
   DESCRIPTION
      ""
   INDEX      { er1645v2VrfRoutHostsGlobalIx,
                er1645v2VrfRoutHostsTableIx }
   ::= {er1645v2VrfRoutHostsSSCTable 1}

Er1645v2VrfRoutHostsEntry ::=
   SEQUENCE
      {
      er1645v2VrfRoutHostsActions
         VariableLengthTableActions,
      er1645v2VrfRoutHostsGlobalIx
         GlobalIndex,
      er1645v2VrfRoutHostsTableIx
         TableIndex,
      er1645v2VrfRoutHostsHostname
         DisplayString,
      er1645v2VrfRoutHostsIpAddress
         IpAddress
      }

er1645v2VrfRoutHostsActions OBJECT-TYPE
   SYNTAX      VariableLengthTableActions
   MAX-ACCESS  read-write
   STATUS      current
   DESCRIPTION
      "By way of this field, some manipulations
       on this table may be performed."
   ::= {er1645v2VrfRoutHostsEntry 2}

er1645v2VrfRoutHostsGlobalIx OBJECT-TYPE
   SYNTAX      GlobalIndex
   MAX-ACCESS  not-accessible
   STATUS      current
   DESCRIPTION
      "The value of the tlsCntTreeGlobalIndex of the MANAGED OBJECT."
   ::= {er1645v2VrfRoutHostsEntry 10}

er1645v2VrfRoutHostsTableIx OBJECT-TYPE
   SYNTAX      TableIndex
   MAX-ACCESS  not-accessible
   STATUS      current
   DESCRIPTION
      ""
   ::= {er1645v2VrfRoutHostsEntry 11}

er1645v2VrfRoutHostsHostname OBJECT-TYPE
   SYNTAX      DisplayString
   MAX-ACCESS  read-write
   STATUS      current
   DESCRIPTION
      "Path: vrfRouter.editConf.hosts.hostname"
   ::= {er1645v2VrfRoutHostsEntry 16777216}

er1645v2VrfRoutHostsIpAddress OBJECT-TYPE
   SYNTAX      IpAddress
   MAX-ACCESS  read-write
   STATUS      current
   DESCRIPTION
      "Path: vrfRouter.editConf.hosts.ipAddress"
   ::= {er1645v2VrfRoutHostsEntry 33554432}


er1645v2VrfRoutQm OBJECT IDENTIFIER ::= {er1645v2VrfRout 77}

er1645v2VrfRoutQmSSCTable OBJECT-TYPE
   SYNTAX      SEQUENCE OF Er1645v2VrfRoutQmEntry
   MAX-ACCESS  not-accessible
   STATUS      current
   DESCRIPTION
      "quality monitor"
   ::= {er1645v2VrfRoutQm 1}

er1645v2VrfRoutQmEntry OBJECT-TYPE
   SYNTAX      Er1645v2VrfRoutQmEntry
   MAX-ACCESS  not-accessible
   STATUS      current
   DESCRIPTION
      ""
   INDEX      { er1645v2VrfRoutQmGlobalIx }
   ::= {er1645v2VrfRoutQmSSCTable 1}

Er1645v2VrfRoutQmEntry ::=
   SEQUENCE
      {
      er1645v2VrfRoutQmGlobalIx
         GlobalIndex,
      er1645v2VrfRoutQmMonitor
         INTEGER,
      er1645v2VrfRoutQmType
         INTEGER,
      er1645v2VrfRoutQmStartDelay
         TimeTicks
      }

er1645v2VrfRoutQmGlobalIx OBJECT-TYPE
   SYNTAX      GlobalIndex
   MAX-ACCESS  not-accessible
   STATUS      current
   DESCRIPTION
      "The value of the tlsCntTreeGlobalIndex of the MANAGED OBJECT."
   ::= {er1645v2VrfRoutQmEntry 10}

er1645v2VrfRoutQmMonitor OBJECT-TYPE
   SYNTAX      INTEGER
               {
               disabled (0),
               enabled (1)
               }
   MAX-ACCESS  read-write
   STATUS      current
   DESCRIPTION
      "Path: vrfRouter.editConf.qualityMonitor.monitor

       Possibilities:
               disabled   (0)
               enabled   (1)"
   ::= {er1645v2VrfRoutQmEntry 33554432}

er1645v2VrfRoutQmType OBJECT-TYPE
   SYNTAX      INTEGER
               {
               sequential (0),
               concurrent (1)
               }
   MAX-ACCESS  read-write
   STATUS      current
   DESCRIPTION
      "Path: vrfRouter.editConf.qualityMonitor.type

       Possibilities:
               sequential   (0)
               concurrent   (1)"
   ::= {er1645v2VrfRoutQmEntry 16777216}

er1645v2VrfRoutQmStartDelay OBJECT-TYPE
   SYNTAX      TimeTicks
   MAX-ACCESS  read-write
   STATUS      current
   DESCRIPTION
      "Path: vrfRouter.editConf.qualityMonitor.startDelay

       Time in centi-second."
   ::= {er1645v2VrfRoutQmEntry 83886080}

er1645v2VrfRoutQmDest OBJECT-TYPE
   SYNTAX      SEQUENCE OF Er1645v2VrfRoutQmDestEntry
   MAX-ACCESS  not-accessible
   STATUS      current
   DESCRIPTION
      ""
   ::= {er1645v2VrfRoutQm 50331648}

er1645v2VrfRoutQmDestEntry OBJECT-TYPE
   SYNTAX      Er1645v2VrfRoutQmDestEntry
   MAX-ACCESS  not-accessible
   STATUS      current
   DESCRIPTION
      ""
   INDEX      { er1645v2VrfRoutQmDestGlobalIx,
                er1645v2VrfRoutQmDestTableIx }
   ::= {er1645v2VrfRoutQmDest 1}

Er1645v2VrfRoutQmDestEntry ::=
   SEQUENCE
      {
      er1645v2VrfRoutQmDestActions
         VariableLengthTableActions,
      er1645v2VrfRoutQmDestGlobalIx
         GlobalIndex,
      er1645v2VrfRoutQmDestTableIx
         TableIndex,
      er1645v2VrfRoutQmDestName
         DisplayString,
      er1645v2VrfRoutQmDestAdminStatus
         INTEGER,
      er1645v2VrfRoutQmDestIpAddress
         IpAddress,
      er1645v2VrfRoutQmDestHostName
         DisplayString,
      er1645v2VrfRoutQmDestSource
         IpAddress,
      er1645v2VrfRoutQmDestTos
         INTEGER,
      er1645v2VrfRoutQmDestPriority
         INTEGER,
      er1645v2VrfRoutQmDestProtocolIcmp
         OCTET STRING,
      er1645v2VrfRoutQmDestProtocolUdpEcho
         OCTET STRING,
      er1645v2VrfRoutQmDestProtocolUdpServerPort
         Integer32,
      er1645v2VrfRoutQmDestProtocolTwampLightPort
         Integer32,
      er1645v2VrfRoutQmDestProtocolBfdInterval
         Integer32,
      er1645v2VrfRoutQmDestProtocolBfdMinRx
         Integer32,
      er1645v2VrfRoutQmDestProtocolBfdMultiplier
         Integer32,
      er1645v2VrfRoutQmDestProtocolBfdEcho
         INTEGER,
      er1645v2VrfRoutQmDestTxInterface
         DisplayString,
      er1645v2VrfRoutQmDestTxGateway
         IpAddress,
      er1645v2VrfRoutQmDestInterval
         Integer32,
      er1645v2VrfRoutQmDestTimeOut
         Integer32,
      er1645v2VrfRoutQmDestLength
         Integer32,
      er1645v2VrfRoutQmDestIdleSamples
         Integer32,
      er1645v2VrfRoutQmDestLossAlarmSamples
         Integer32,
      er1645v2VrfRoutQmDestLossAlarmAlarmOn
         Integer32,
      er1645v2VrfRoutQmDestLossAlarmAlarmOff
         Integer32,
      er1645v2VrfRoutQmDestLossAlarmAlarmUpOn
         Integer32,
      er1645v2VrfRoutQmDestLossAlarmAlarmUpOff
         Integer32,
      er1645v2VrfRoutQmDestLossAlarmAlarmDownOn
         Integer32,
      er1645v2VrfRoutQmDestLossAlarmAlarmDownOff
         Integer32,
      er1645v2VrfRoutQmDestDelayAlarmSamples
         Integer32,
      er1645v2VrfRoutQmDestDelayAlarmDelayAvrgOn
         Integer32,
      er1645v2VrfRoutQmDestDelayAlarmDelayAvrgOff
         Integer32,
      er1645v2VrfRoutQmDestDelayAlarmDelayMaxOn
         Integer32,
      er1645v2VrfRoutQmDestDelayAlarmDelayMaxOff
         Integer32,
      er1645v2VrfRoutQmDestDelayAlarmDelayMinMaxOn
         Integer32,
      er1645v2VrfRoutQmDestDelayAlarmDelayMinMaxOff
         Integer32,
      er1645v2VrfRoutQmDestDelayAlarmDsType
         INTEGER,
      er1645v2VrfRoutQmDestDelayAlarmDsBinsN
         INTEGER,
      er1645v2VrfRoutQmDestDelayAlarmDsBinsNMn
         Integer32,
      er1645v2VrfRoutQmDestDelayAlarmDsBinsNMx
         Integer32,
      er1645v2VrfRoutQmDestDelayAlarmDsBinsTB1
         Integer32,
      er1645v2VrfRoutQmDestDelayAlarmDsBinsTB2
         Integer32,
      er1645v2VrfRoutQmDestDelayAlarmDsBinsTB3
         Integer32,
      er1645v2VrfRoutQmDestDelayAlarmDsBinsTB4
         Integer32,
      er1645v2VrfRoutQmDestDelayAlarmDsBinsTB5
         Integer32,
      er1645v2VrfRoutQmDestDelayAlarmDsBinsTB6
         Integer32,
      er1645v2VrfRoutQmDestDelayAlarmDsBinsTB7
         Integer32,
      er1645v2VrfRoutQmDestDelayAlarmDsBinsTB8
         Integer32,
      er1645v2VrfRoutQmDestDelayAlarmDsBinsTMx
         Integer32,
      er1645v2VrfRoutQmDestDelayAlarmJitterAvrgOn
         Integer32,
      er1645v2VrfRoutQmDestDelayAlarmJitterAvrgOff
         Integer32,
      er1645v2VrfRoutQmDestDelayAlarmJitterMaxOn
         Integer32,
      er1645v2VrfRoutQmDestDelayAlarmJitterMaxOff
         Integer32,
      er1645v2VrfRoutQmDestDelayAlarmJsN
         INTEGER,
      er1645v2VrfRoutQmDestDelayAlarmJsNMn
         Integer32,
      er1645v2VrfRoutQmDestDelayAlarmJsNMx
         Integer32,
      er1645v2VrfRoutQmDestDelayAlarmJsTB1
         Integer32,
      er1645v2VrfRoutQmDestDelayAlarmJsTB2
         Integer32,
      er1645v2VrfRoutQmDestDelayAlarmJsTB3
         Integer32,
      er1645v2VrfRoutQmDestDelayAlarmJsTB4
         Integer32,
      er1645v2VrfRoutQmDestDelayAlarmJsTB5
         Integer32,
      er1645v2VrfRoutQmDestDelayAlarmJsTB6
         Integer32,
      er1645v2VrfRoutQmDestDelayAlarmJsTB7
         Integer32,
      er1645v2VrfRoutQmDestDelayAlarmJsTB8
         Integer32,
      er1645v2VrfRoutQmDestDelayAlarmJsTMx
         Integer32,
      er1645v2VrfRoutQmDestDelayAlarmJitterUpAvrgOn
         Integer32,
      er1645v2VrfRoutQmDestDelayAlarmJitterUpAvrgOff
         Integer32,
      er1645v2VrfRoutQmDestDelayAlarmJitterUpMaxOn
         Integer32,
      er1645v2VrfRoutQmDestDelayAlarmJitterUpMaxOff
         Integer32,
      er1645v2VrfRoutQmDestDelayAlarmJupsN
         INTEGER,
      er1645v2VrfRoutQmDestDelayAlarmJupsNMn
         Integer32,
      er1645v2VrfRoutQmDestDelayAlarmJupsNMx
         Integer32,
      er1645v2VrfRoutQmDestDelayAlarmJupsTB1
         Integer32,
      er1645v2VrfRoutQmDestDelayAlarmJupsTB2
         Integer32,
      er1645v2VrfRoutQmDestDelayAlarmJupsTB3
         Integer32,
      er1645v2VrfRoutQmDestDelayAlarmJupsTB4
         Integer32,
      er1645v2VrfRoutQmDestDelayAlarmJupsTB5
         Integer32,
      er1645v2VrfRoutQmDestDelayAlarmJupsTB6
         Integer32,
      er1645v2VrfRoutQmDestDelayAlarmJupsTB7
         Integer32,
      er1645v2VrfRoutQmDestDelayAlarmJupsTB8
         Integer32,
      er1645v2VrfRoutQmDestDelayAlarmJupsTMx
         Integer32,
      er1645v2VrfRoutQmDestDelayAlarmJitterDownAvrgOn
         Integer32,
      er1645v2VrfRoutQmDestDelayAlarmJitterDownAvrgOff
         Integer32,
      er1645v2VrfRoutQmDestDelayAlarmJitterDownMaxOn
         Integer32,
      er1645v2VrfRoutQmDestDelayAlarmJitterDownMaxOff
         Integer32,
      er1645v2VrfRoutQmDestDelayAlarmJdownsN
         INTEGER,
      er1645v2VrfRoutQmDestDelayAlarmJdownsNMn
         Integer32,
      er1645v2VrfRoutQmDestDelayAlarmJdownsNMx
         Integer32,
      er1645v2VrfRoutQmDestDelayAlarmJdownsTB1
         Integer32,
      er1645v2VrfRoutQmDestDelayAlarmJdownsTB2
         Integer32,
      er1645v2VrfRoutQmDestDelayAlarmJdownsTB3
         Integer32,
      er1645v2VrfRoutQmDestDelayAlarmJdownsTB4
         Integer32,
      er1645v2VrfRoutQmDestDelayAlarmJdownsTB5
         Integer32,
      er1645v2VrfRoutQmDestDelayAlarmJdownsTB6
         Integer32,
      er1645v2VrfRoutQmDestDelayAlarmJdownsTB7
         Integer32,
      er1645v2VrfRoutQmDestDelayAlarmJdownsTB8
         Integer32,
      er1645v2VrfRoutQmDestDelayAlarmJdownsTMx
         Integer32,
      er1645v2VrfRoutQmDestDelayAlarmDelayUpAvrgOn
         Integer32,
      er1645v2VrfRoutQmDestDelayAlarmDelayUpAvrgOff
         Integer32,
      er1645v2VrfRoutQmDestDelayAlarmDelayUpMaxOn
         Integer32,
      er1645v2VrfRoutQmDestDelayAlarmDelayUpMaxOff
         Integer32,
      er1645v2VrfRoutQmDestDelayAlarmDupsType
         INTEGER,
      er1645v2VrfRoutQmDestDelayAlarmDupsBinsN
         INTEGER,
      er1645v2VrfRoutQmDestDelayAlarmDupsBinsNMn
         Integer32,
      er1645v2VrfRoutQmDestDelayAlarmDupsBinsNMx
         Integer32,
      er1645v2VrfRoutQmDestDelayAlarmDupsBinsTB1
         Integer32,
      er1645v2VrfRoutQmDestDelayAlarmDupsBinsTB2
         Integer32,
      er1645v2VrfRoutQmDestDelayAlarmDupsBinsTB3
         Integer32,
      er1645v2VrfRoutQmDestDelayAlarmDupsBinsTB4
         Integer32,
      er1645v2VrfRoutQmDestDelayAlarmDupsBinsTB5
         Integer32,
      er1645v2VrfRoutQmDestDelayAlarmDupsBinsTB6
         Integer32,
      er1645v2VrfRoutQmDestDelayAlarmDupsBinsTB7
         Integer32,
      er1645v2VrfRoutQmDestDelayAlarmDupsBinsTB8
         Integer32,
      er1645v2VrfRoutQmDestDelayAlarmDupsBinsTMx
         Integer32,
      er1645v2VrfRoutQmDestDelayAlarmDelayDownAvrgOn
         Integer32,
      er1645v2VrfRoutQmDestDelayAlarmDelayDownAvrgOff
         Integer32,
      er1645v2VrfRoutQmDestDelayAlarmDelayDownMaxOn
         Integer32,
      er1645v2VrfRoutQmDestDelayAlarmDelayDownMaxOff
         Integer32,
      er1645v2VrfRoutQmDestDelayAlarmDdownsType
         INTEGER,
      er1645v2VrfRoutQmDestDelayAlarmDdownsBinsN
         INTEGER,
      er1645v2VrfRoutQmDestDelayAlarmDdownsBinsNMn
         Integer32,
      er1645v2VrfRoutQmDestDelayAlarmDdownsBinsNMx
         Integer32,
      er1645v2VrfRoutQmDestDelayAlarmDdownsBinsTB1
         Integer32,
      er1645v2VrfRoutQmDestDelayAlarmDdownsBinsTB2
         Integer32,
      er1645v2VrfRoutQmDestDelayAlarmDdownsBinsTB3
         Integer32,
      er1645v2VrfRoutQmDestDelayAlarmDdownsBinsTB4
         Integer32,
      er1645v2VrfRoutQmDestDelayAlarmDdownsBinsTB5
         Integer32,
      er1645v2VrfRoutQmDestDelayAlarmDdownsBinsTB6
         Integer32,
      er1645v2VrfRoutQmDestDelayAlarmDdownsBinsTB7
         Integer32,
      er1645v2VrfRoutQmDestDelayAlarmDdownsBinsTB8
         Integer32,
      er1645v2VrfRoutQmDestDelayAlarmDdownsBinsTMx
         Integer32,
      er1645v2VrfRoutQmDestAlarmMask
         Integer32,
      er1645v2VrfRoutQmDestLogging
         INTEGER,
      er1645v2VrfRoutQmDestLoggingDepth
         INTEGER
      }

er1645v2VrfRoutQmDestActions OBJECT-TYPE
   SYNTAX      VariableLengthTableActions
   MAX-ACCESS  read-write
   STATUS      current
   DESCRIPTION
      "By way of this field, some manipulations
       on this table may be performed."
   ::= {er1645v2VrfRoutQmDestEntry 2}

er1645v2VrfRoutQmDestGlobalIx OBJECT-TYPE
   SYNTAX      GlobalIndex
   MAX-ACCESS  not-accessible
   STATUS      current
   DESCRIPTION
      "The value of the tlsCntTreeGlobalIndex of the MANAGED OBJECT."
   ::= {er1645v2VrfRoutQmDestEntry 10}

er1645v2VrfRoutQmDestTableIx OBJECT-TYPE
   SYNTAX      TableIndex
   MAX-ACCESS  not-accessible
   STATUS      current
   DESCRIPTION
      ""
   ::= {er1645v2VrfRoutQmDestEntry 11}

er1645v2VrfRoutQmDestName OBJECT-TYPE
   SYNTAX      DisplayString
   MAX-ACCESS  read-write
   STATUS      current
   DESCRIPTION
      "Path: vrfRouter.editConf.qualityMonitor.destinations.name"
   ::= {er1645v2VrfRoutQmDestEntry 234881024}

er1645v2VrfRoutQmDestAdminStatus OBJECT-TYPE
   SYNTAX      INTEGER
               {
               enabled (1),
               onDemand (2),
               disabled (3)
               }
   MAX-ACCESS  read-write
   STATUS      current
   DESCRIPTION
      "Path: vrfRouter.editConf.qualityMonitor.destinations.adminStatus

       Possibilities:
               enabled   (1)
               onDemand   (2)
               disabled   (3)"
   ::= {er1645v2VrfRoutQmDestEntry 369098752}

er1645v2VrfRoutQmDestIpAddress OBJECT-TYPE
   SYNTAX      IpAddress
   MAX-ACCESS  read-write
   STATUS      current
   DESCRIPTION
      "Path: vrfRouter.editConf.qualityMonitor.destinations.ipAddress"
   ::= {er1645v2VrfRoutQmDestEntry 16777216}

er1645v2VrfRoutQmDestHostName OBJECT-TYPE
   SYNTAX      DisplayString
   MAX-ACCESS  read-write
   STATUS      current
   DESCRIPTION
      "Path: vrfRouter.editConf.qualityMonitor.destinations.hostName"
   ::= {er1645v2VrfRoutQmDestEntry 33554432}

er1645v2VrfRoutQmDestSource OBJECT-TYPE
   SYNTAX      IpAddress
   MAX-ACCESS  read-write
   STATUS      current
   DESCRIPTION
      "Path: vrfRouter.editConf.qualityMonitor.destinations.source"
   ::= {er1645v2VrfRoutQmDestEntry 184549376}

er1645v2VrfRoutQmDestTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouter.editConf.qualityMonitor.destinations.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VrfRoutQmDestEntry 167772160}

er1645v2VrfRoutQmDestPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfRouter.editConf.qualityMonitor.destinations.priority

       Possibilities:
               queue1   (0)
               queue2   (1)
               queue3   (2)
               queue4   (3)
               queue5   (4)
               lowDelayQueue   (5)
               lowDelay2Queue   (6)
               systemQueue   (7)"
   ::= {er1645v2VrfRoutQmDestEntry 218103808}

er1645v2VrfRoutQmDestProtocolIcmp OBJECT-TYPE
   SYNTAX      OCTET STRING
   MAX-ACCESS  read-write
   STATUS      current
   DESCRIPTION
      "Path: vrfRouter.editConf.qualityMonitor.destinations.protocol.icmp"
   ::= {er1645v2VrfRoutQmDestEntry 50397184}

er1645v2VrfRoutQmDestProtocolUdpEcho OBJECT-TYPE
   SYNTAX      OCTET STRING
   MAX-ACCESS  read-write
   STATUS      current
   DESCRIPTION
      "Path: vrfRouter.editConf.qualityMonitor.destinations.protocol.udpEcho"
   ::= {er1645v2VrfRoutQmDestEntry 50462720}

er1645v2VrfRoutQmDestProtocolUdpServerPort OBJECT-TYPE
   SYNTAX      Integer32
   MAX-ACCESS  read-write
   STATUS      current
   DESCRIPTION
      "Path: vrfRouter.editConf.qualityMonitor.destinations.protocol.udpServerPort"
   ::= {er1645v2VrfRoutQmDestEntry 50528256}

er1645v2VrfRoutQmDestProtocolTwampLightPort OBJECT-TYPE
   SYNTAX      Integer32
   MAX-ACCESS  read-write
   STATUS      current
   DESCRIPTION
      "Path: vrfRouter.editConf.qualityMonitor.destinations.protocol.twampLightPort"
   ::= {er1645v2VrfRoutQmDestEntry 50593792}

er1645v2VrfRoutQmDestProtocolBfdInterval OBJECT-TYPE
   SYNTAX      Integer32
   UNITS       "ms"
   MAX-ACCESS  read-write
   STATUS      current
   DESCRIPTION
      "Path: vrfRouter.editConf.qualityMonitor.destinations.protocol.bfd.interval

       unit name = ms"
   ::= {er1645v2VrfRoutQmDestEntry 50659584}

er1645v2VrfRoutQmDestProtocolBfdMinRx OBJECT-TYPE
   SYNTAX      Integer32
   UNITS       "ms"
   MAX-ACCESS  read-write
   STATUS      current
   DESCRIPTION
      "Path: vrfRouter.editConf.qualityMonitor.destinations.protocol.bfd.minRx

       unit name = ms"
   ::= {er1645v2VrfRoutQmDestEntry 50659840}

er1645v2VrfRoutQmDestProtocolBfdMultiplier OBJECT-TYPE
   SYNTAX      Integer32
   MAX-ACCESS  read-write
   STATUS      current
   DESCRIPTION
      "Path: vrfRouter.editConf.qualityMonitor.destinations.protocol.bfd.multiplier"
   ::= {er1645v2VrfRoutQmDestEntry 50660096}

er1645v2VrfRoutQmDestProtocolBfdEcho OBJECT-TYPE
   SYNTAX      INTEGER
               {
               txRx (1),
               tx (2),
               rx (3),
               no (4)
               }
   MAX-ACCESS  read-write
   STATUS      current
   DESCRIPTION
      "Path: vrfRouter.editConf.qualityMonitor.destinations.protocol.bfd.echo

       Possibilities:
               txRx   (1)
               tx   (2)
               rx   (3)
               no   (4)"
   ::= {er1645v2VrfRoutQmDestEntry 50660352}

er1645v2VrfRoutQmDestTxInterface OBJECT-TYPE
   SYNTAX      DisplayString
   MAX-ACCESS  read-write
   STATUS      current
   DESCRIPTION
      "Path: vrfRouter.editConf.qualityMonitor.destinations.txInterface"
   ::= {er1645v2VrfRoutQmDestEntry 402653184}

er1645v2VrfRoutQmDestTxGateway OBJECT-TYPE
   SYNTAX      IpAddress
   MAX-ACCESS  read-write
   STATUS      current
   DESCRIPTION
      "Path: vrfRouter.editConf.qualityMonitor.destinations.txGateway"
   ::= {er1645v2VrfRoutQmDestEntry 419430400}

er1645v2VrfRoutQmDestInterval OBJECT-TYPE
   SYNTAX      Integer32
   UNITS       "100msec"
   MAX-ACCESS  read-write
   STATUS      current
   DESCRIPTION
      "Path: vrfRouter.editConf.qualityMonitor.destinations.interval

       unit name = 100msec"
   ::= {er1645v2VrfRoutQmDestEntry 67108864}

er1645v2VrfRoutQmDestTimeOut OBJECT-TYPE
   SYNTAX      Integer32
   UNITS       "100msec"
   MAX-ACCESS  read-write
   STATUS      current
   DESCRIPTION
      "Path: vrfRouter.editConf.qualityMonitor.destinations.timeOut

       unit name = 100msec"
   ::= {er1645v2VrfRoutQmDestEntry 150994944}

er1645v2VrfRoutQmDestLength OBJECT-TYPE
   SYNTAX      Integer32
   MAX-ACCESS  read-write
   STATUS      current
   DESCRIPTION
      "Path: vrfRouter.editConf.qualityMonitor.destinations.length"
   ::= {er1645v2VrfRoutQmDestEntry 83886080}

er1645v2VrfRoutQmDestIdleSamples OBJECT-TYPE
   SYNTAX      Integer32
   MAX-ACCESS  read-write
   STATUS      current
   DESCRIPTION
      "Path: vrfRouter.editConf.qualityMonitor.destinations.idleSamples"
   ::= {er1645v2VrfRoutQmDestEntry 268435456}

er1645v2VrfRoutQmDestLossAlarmSamples OBJECT-TYPE
   SYNTAX      Integer32
   MAX-ACCESS  read-write
   STATUS      current
   DESCRIPTION
      "Path: vrfRouter.editConf.qualityMonitor.destinations.lossAlarm.samples"
   ::= {er1645v2VrfRoutQmDestEntry 100728832}

er1645v2VrfRoutQmDestLossAlarmAlarmOn OBJECT-TYPE
   SYNTAX      Integer32
   MAX-ACCESS  read-write
   STATUS      current
   DESCRIPTION
      "Path: vrfRouter.editConf.qualityMonitor.destinations.lossAlarm.alarmOn"
   ::= {er1645v2VrfRoutQmDestEntry 100794368}

er1645v2VrfRoutQmDestLossAlarmAlarmOff OBJECT-TYPE
   SYNTAX      Integer32
   MAX-ACCESS  read-write
   STATUS      current
   DESCRIPTION
      "Path: vrfRouter.editConf.qualityMonitor.destinations.lossAlarm.alarmOff"
   ::= {er1645v2VrfRoutQmDestEntry 100859904}

er1645v2VrfRoutQmDestLossAlarmAlarmUpOn OBJECT-TYPE
   SYNTAX      Integer32
   MAX-ACCESS  read-write
   STATUS      current
   DESCRIPTION
      "Path: vrfRouter.editConf.qualityMonitor.destinations.lossAlarm.alarmUpOn"
   ::= {er1645v2VrfRoutQmDestEntry 100925440}

er1645v2VrfRoutQmDestLossAlarmAlarmUpOff OBJECT-TYPE
   SYNTAX      Integer32
   MAX-ACCESS  read-write
   STATUS      current
   DESCRIPTION
      "Path: vrfRouter.editConf.qualityMonitor.destinations.lossAlarm.alarmUpOff"
   ::= {er1645v2VrfRoutQmDestEntry 100990976}

er1645v2VrfRoutQmDestLossAlarmAlarmDownOn OBJECT-TYPE
   SYNTAX      Integer32
   MAX-ACCESS  read-write
   STATUS      current
   DESCRIPTION
      "Path: vrfRouter.editConf.qualityMonitor.destinations.lossAlarm.alarmDownOn"
   ::= {er1645v2VrfRoutQmDestEntry 101056512}

er1645v2VrfRoutQmDestLossAlarmAlarmDownOff OBJECT-TYPE
   SYNTAX      Integer32
   MAX-ACCESS  read-write
   STATUS      current
   DESCRIPTION
      "Path: vrfRouter.editConf.qualityMonitor.destinations.lossAlarm.alarmDownOff"
   ::= {er1645v2VrfRoutQmDestEntry 101122048}

er1645v2VrfRoutQmDestDelayAlarmSamples OBJECT-TYPE
   SYNTAX      Integer32
   MAX-ACCESS  read-write
   STATUS      current
   DESCRIPTION
      "Path: vrfRouter.editConf.qualityMonitor.destinations.delayAlarm.samples"
   ::= {er1645v2VrfRoutQmDestEntry 117506048}

er1645v2VrfRoutQmDestDelayAlarmDelayAvrgOn OBJECT-TYPE
   SYNTAX      Integer32
   UNITS       "msec"
   MAX-ACCESS  read-write
   STATUS      current
   DESCRIPTION
      "Path: vrfRouter.editConf.qualityMonitor.destinations.delayAlarm.delayAvrgOn

       unit name = msec"
   ::= {er1645v2VrfRoutQmDestEntry 117571584}

er1645v2VrfRoutQmDestDelayAlarmDelayAvrgOff OBJECT-TYPE
   SYNTAX      Integer32
   UNITS       "msec"
   MAX-ACCESS  read-write
   STATUS      current
   DESCRIPTION
      "Path: vrfRouter.editConf.qualityMonitor.destinations.delayAlarm.delayAvrgOff

       unit name = msec"
   ::= {er1645v2VrfRoutQmDestEntry 117637120}

er1645v2VrfRoutQmDestDelayAlarmDelayMaxOn OBJECT-TYPE
   SYNTAX      Integer32
   UNITS       "msec"
   MAX-ACCESS  read-write
   STATUS      current
   DESCRIPTION
      "Path: vrfRouter.editConf.qualityMonitor.destinations.delayAlarm.delayMaxOn

       unit name = msec"
   ::= {er1645v2VrfRoutQmDestEntry 117702656}

er1645v2VrfRoutQmDestDelayAlarmDelayMaxOff OBJECT-TYPE
   SYNTAX      Integer32
   UNITS       "msec"
   MAX-ACCESS  read-write
   STATUS      current
   DESCRIPTION
      "Path: vrfRouter.editConf.qualityMonitor.destinations.delayAlarm.delayMaxOff

       unit name = msec"
   ::= {er1645v2VrfRoutQmDestEntry 117768192}

er1645v2VrfRoutQmDestDelayAlarmDelayMinMaxOn OBJECT-TYPE
   SYNTAX      Integer32
   UNITS       "msec"
   MAX-ACCESS  read-write
   STATUS      current
   DESCRIPTION
      "Path: vrfRouter.editConf.qualityMonitor.destinations.delayAlarm.delayMinMaxOn

       unit name = msec"
   ::= {er1645v2VrfRoutQmDestEntry 118095872}

er1645v2VrfRoutQmDestDelayAlarmDelayMinMaxOff OBJECT-TYPE
   SYNTAX      Integer32
   UNITS       "msec"
   MAX-ACCESS  read-write
   STATUS      current
   DESCRIPTION
      "Path: vrfRouter.editConf.qualityMonitor.destinations.delayAlarm.delayMinMaxOff

       unit name = msec"
   ::= {er1645v2VrfRoutQmDestEntry 118161408}

er1645v2VrfRoutQmDestDelayAlarmDsType OBJECT-TYPE
   SYNTAX      INTEGER
               {
               fd (1),
               fdr (2)
               }
   MAX-ACCESS  read-write
   STATUS      current
   DESCRIPTION
      "Path: vrfRouter.editConf.qualityMonitor.destinations.delayAlarm.delayStat.type

       Possibilities:
               fd   (1)
               fdr   (2)"
   ::= {er1645v2VrfRoutQmDestEntry 119283712}

er1645v2VrfRoutQmDestDelayAlarmDsBinsN OBJECT-TYPE
   SYNTAX      INTEGER
               {
               none (0)
               }
   MAX-ACCESS  read-write
   STATUS      current
   DESCRIPTION
      "Path: vrfRouter.editConf.qualityMonitor.destinations.delayAlarm.delayStat.bins.none

       Possibilities:
               none   (0)"
   ::= {er1645v2VrfRoutQmDestEntry 119292928}

er1645v2VrfRoutQmDestDelayAlarmDsBinsNMn OBJECT-TYPE
   SYNTAX      Integer32
   UNITS       "msec"
   MAX-ACCESS  read-write
   STATUS      current
   DESCRIPTION
      "Path: vrfRouter.editConf.qualityMonitor.destinations.delayAlarm.delayStat.bins.range.min

       unit name = msec"
   ::= {er1645v2VrfRoutQmDestEntry 119294080}

er1645v2VrfRoutQmDestDelayAlarmDsBinsNMx OBJECT-TYPE
   SYNTAX      Integer32
   UNITS       "msec"
   MAX-ACCESS  read-write
   STATUS      current
   DESCRIPTION
      "Path: vrfRouter.editConf.qualityMonitor.destinations.delayAlarm.delayStat.bins.range.max

       unit name = msec"
   ::= {er1645v2VrfRoutQmDestEntry 119294208}

er1645v2VrfRoutQmDestDelayAlarmDsBinsTB1 OBJECT-TYPE
   SYNTAX      Integer32
   UNITS       "msec"
   MAX-ACCESS  read-write
   STATUS      current
   DESCRIPTION
      "Path: vrfRouter.editConf.qualityMonitor.destinations.delayAlarm.delayStat.bins.table.bin1

       unit name = msec"
   ::= {er1645v2VrfRoutQmDestEntry 119295040}

er1645v2VrfRoutQmDestDelayAlarmDsBinsTB2 OBJECT-TYPE
   SYNTAX      Integer32
   UNITS       "msec"
   MAX-ACCESS  read-write
   STATUS      current
   DESCRIPTION
      "Path: vrfRouter.editConf.qualityMonitor.destinations.delayAlarm.delayStat.bins.table.bin2

       unit name = msec"
   ::= {er1645v2VrfRoutQmDestEntry 119295104}

er1645v2VrfRoutQmDestDelayAlarmDsBinsTB3 OBJECT-TYPE
   SYNTAX      Integer32
   UNITS       "msec"
   MAX-ACCESS  read-write
   STATUS      current
   DESCRIPTION
      "Path: vrfRouter.editConf.qualityMonitor.destinations.delayAlarm.delayStat.bins.table.bin3

       unit name = msec"
   ::= {er1645v2VrfRoutQmDestEntry 119295168}

er1645v2VrfRoutQmDestDelayAlarmDsBinsTB4 OBJECT-TYPE
   SYNTAX      Integer32
   UNITS       "msec"
   MAX-ACCESS  read-write
   STATUS      current
   DESCRIPTION
      "Path: vrfRouter.editConf.qualityMonitor.destinations.delayAlarm.delayStat.bins.table.bin4

       unit name = msec"
   ::= {er1645v2VrfRoutQmDestEntry 119295232}

er1645v2VrfRoutQmDestDelayAlarmDsBinsTB5 OBJECT-TYPE
   SYNTAX      Integer32
   UNITS       "msec"
   MAX-ACCESS  read-write
   STATUS      current
   DESCRIPTION
      "Path: vrfRouter.editConf.qualityMonitor.destinations.delayAlarm.delayStat.bins.table.bin5

       unit name = msec"
   ::= {er1645v2VrfRoutQmDestEntry 119295296}

er1645v2VrfRoutQmDestDelayAlarmDsBinsTB6 OBJECT-TYPE
   SYNTAX      Integer32
   UNITS       "msec"
   MAX-ACCESS  read-write
   STATUS      current
   DESCRIPTION
      "Path: vrfRouter.editConf.qualityMonitor.destinations.delayAlarm.delayStat.bins.table.bin6

       unit name = msec"
   ::= {er1645v2VrfRoutQmDestEntry 119295360}

er1645v2VrfRoutQmDestDelayAlarmDsBinsTB7 OBJECT-TYPE
   SYNTAX      Integer32
   UNITS       "msec"
   MAX-ACCESS  read-write
   STATUS      current
   DESCRIPTION
      "Path: vrfRouter.editConf.qualityMonitor.destinations.delayAlarm.delayStat.bins.table.bin7

       unit name = msec"
   ::= {er1645v2VrfRoutQmDestEntry 119295424}

er1645v2VrfRoutQmDestDelayAlarmDsBinsTB8 OBJECT-TYPE
   SYNTAX      Integer32
   UNITS       "msec"
   MAX-ACCESS  read-write
   STATUS      current
   DESCRIPTION
      "Path: vrfRouter.editConf.qualityMonitor.destinations.delayAlarm.delayStat.bins.table.bin8

       unit name = msec"
   ::= {er1645v2VrfRoutQmDestEntry 119295488}

er1645v2VrfRoutQmDestDelayAlarmDsBinsTMx OBJECT-TYPE
   SYNTAX      Integer32
   UNITS       "msec"
   MAX-ACCESS  read-write
   STATUS      current
   DESCRIPTION
      "Path: vrfRouter.editConf.qualityMonitor.destinations.delayAlarm.delayStat.bins.table.max

       unit name = msec"
   ::= {er1645v2VrfRoutQmDestEntry 119295552}

er1645v2VrfRoutQmDestDelayAlarmJitterAvrgOn OBJECT-TYPE
   SYNTAX      Integer32
   UNITS       "msec"
   MAX-ACCESS  read-write
   STATUS      current
   DESCRIPTION
      "Path: vrfRouter.editConf.qualityMonitor.destinations.delayAlarm.jitterAvrgOn

       unit name = msec"
   ::= {er1645v2VrfRoutQmDestEntry 117833728}

er1645v2VrfRoutQmDestDelayAlarmJitterAvrgOff OBJECT-TYPE
   SYNTAX      Integer32
   UNITS       "msec"
   MAX-ACCESS  read-write
   STATUS      current
   DESCRIPTION
      "Path: vrfRouter.editConf.qualityMonitor.destinations.delayAlarm.jitterAvrgOff

       unit name = msec"
   ::= {er1645v2VrfRoutQmDestEntry 117899264}

er1645v2VrfRoutQmDestDelayAlarmJitterMaxOn OBJECT-TYPE
   SYNTAX      Integer32
   UNITS       "msec"
   MAX-ACCESS  read-write
   STATUS      current
   DESCRIPTION
      "Path: vrfRouter.editConf.qualityMonitor.destinations.delayAlarm.jitterMaxOn

       unit name = msec"
   ::= {er1645v2VrfRoutQmDestEntry 117964800}

er1645v2VrfRoutQmDestDelayAlarmJitterMaxOff OBJECT-TYPE
   SYNTAX      Integer32
   UNITS       "msec"
   MAX-ACCESS  read-write
   STATUS      current
   DESCRIPTION
      "Path: vrfRouter.editConf.qualityMonitor.destinations.delayAlarm.jitterMaxOff

       unit name = msec"
   ::= {er1645v2VrfRoutQmDestEntry 118030336}

er1645v2VrfRoutQmDestDelayAlarmJsN OBJECT-TYPE
   SYNTAX      INTEGER
               {
               none (0)
               }
   MAX-ACCESS  read-write
   STATUS      current
   DESCRIPTION
      "Path: vrfRouter.editConf.qualityMonitor.destinations.delayAlarm.jitterStat.none

       Possibilities:
               none   (0)"
   ::= {er1645v2VrfRoutQmDestEntry 119676928}

er1645v2VrfRoutQmDestDelayAlarmJsNMn OBJECT-TYPE
   SYNTAX      Integer32
   UNITS       "msec"
   MAX-ACCESS  read-write
   STATUS      current
   DESCRIPTION
      "Path: vrfRouter.editConf.qualityMonitor.destinations.delayAlarm.jitterStat.range.min

       unit name = msec"
   ::= {er1645v2VrfRoutQmDestEntry 119686144}

er1645v2VrfRoutQmDestDelayAlarmJsNMx OBJECT-TYPE
   SYNTAX      Integer32
   UNITS       "msec"
   MAX-ACCESS  read-write
   STATUS      current
   DESCRIPTION
      "Path: vrfRouter.editConf.qualityMonitor.destinations.delayAlarm.jitterStat.range.max

       unit name = msec"
   ::= {er1645v2VrfRoutQmDestEntry 119687168}

er1645v2VrfRoutQmDestDelayAlarmJsTB1 OBJECT-TYPE
   SYNTAX      Integer32
   UNITS       "msec"
   MAX-ACCESS  read-write
   STATUS      current
   DESCRIPTION
      "Path: vrfRouter.editConf.qualityMonitor.destinations.delayAlarm.jitterStat.table.bin1

       unit name = msec"
   ::= {er1645v2VrfRoutQmDestEntry 119693824}

er1645v2VrfRoutQmDestDelayAlarmJsTB2 OBJECT-TYPE
   SYNTAX      Integer32
   UNITS       "msec"
   MAX-ACCESS  read-write
   STATUS      current
   DESCRIPTION
      "Path: vrfRouter.editConf.qualityMonitor.destinations.delayAlarm.jitterStat.table.bin2

       unit name = msec"
   ::= {er1645v2VrfRoutQmDestEntry 119694336}

er1645v2VrfRoutQmDestDelayAlarmJsTB3 OBJECT-TYPE
   SYNTAX      Integer32
   UNITS       "msec"
   MAX-ACCESS  read-write
   STATUS      current
   DESCRIPTION
      "Path: vrfRouter.editConf.qualityMonitor.destinations.delayAlarm.jitterStat.table.bin3

       unit name = msec"
   ::= {er1645v2VrfRoutQmDestEntry 119694848}

er1645v2VrfRoutQmDestDelayAlarmJsTB4 OBJECT-TYPE
   SYNTAX      Integer32
   UNITS       "msec"
   MAX-ACCESS  read-write
   STATUS      current
   DESCRIPTION
      "Path: vrfRouter.editConf.qualityMonitor.destinations.delayAlarm.jitterStat.table.bin4

       unit name = msec"
   ::= {er1645v2VrfRoutQmDestEntry 119695360}

er1645v2VrfRoutQmDestDelayAlarmJsTB5 OBJECT-TYPE
   SYNTAX      Integer32
   UNITS       "msec"
   MAX-ACCESS  read-write
   STATUS      current
   DESCRIPTION
      "Path: vrfRouter.editConf.qualityMonitor.destinations.delayAlarm.jitterStat.table.bin5

       unit name = msec"
   ::= {er1645v2VrfRoutQmDestEntry 119695872}

er1645v2VrfRoutQmDestDelayAlarmJsTB6 OBJECT-TYPE
   SYNTAX      Integer32
   UNITS       "msec"
   MAX-ACCESS  read-write
   STATUS      current
   DESCRIPTION
      "Path: vrfRouter.editConf.qualityMonitor.destinations.delayAlarm.jitterStat.table.bin6

       unit name = msec"
   ::= {er1645v2VrfRoutQmDestEntry 119696384}

er1645v2VrfRoutQmDestDelayAlarmJsTB7 OBJECT-TYPE
   SYNTAX      Integer32
   UNITS       "msec"
   MAX-ACCESS  read-write
   STATUS      current
   DESCRIPTION
      "Path: vrfRouter.editConf.qualityMonitor.destinations.delayAlarm.jitterStat.table.bin7

       unit name = msec"
   ::= {er1645v2VrfRoutQmDestEntry 119696896}

er1645v2VrfRoutQmDestDelayAlarmJsTB8 OBJECT-TYPE
   SYNTAX      Integer32
   UNITS       "msec"
   MAX-ACCESS  read-write
   STATUS      current
   DESCRIPTION
      "Path: vrfRouter.editConf.qualityMonitor.destinations.delayAlarm.jitterStat.table.bin8

       unit name = msec"
   ::= {er1645v2VrfRoutQmDestEntry 119697408}

er1645v2VrfRoutQmDestDelayAlarmJsTMx OBJECT-TYPE
   SYNTAX      Integer32
   UNITS       "msec"
   MAX-ACCESS  read-write
   STATUS      current
   DESCRIPTION
      "Path: vrfRouter.editConf.qualityMonitor.destinations.delayAlarm.jitterStat.table.max

       unit name = msec"
   ::= {er1645v2VrfRoutQmDestEntry 119697920}

er1645v2VrfRoutQmDestDelayAlarmJitterUpAvrgOn OBJECT-TYPE
   SYNTAX      Integer32
   UNITS       "msec"
   MAX-ACCESS  read-write
   STATUS      current
   DESCRIPTION
      "Path: vrfRouter.editConf.qualityMonitor.destinations.delayAlarm.jitterUpAvrgOn

       unit name = msec"
   ::= {er1645v2VrfRoutQmDestEntry 118226944}

er1645v2VrfRoutQmDestDelayAlarmJitterUpAvrgOff OBJECT-TYPE
   SYNTAX      Integer32
   UNITS       "msec"
   MAX-ACCESS  read-write
   STATUS      current
   DESCRIPTION
      "Path: vrfRouter.editConf.qualityMonitor.destinations.delayAlarm.jitterUpAvrgOff

       unit name = msec"
   ::= {er1645v2VrfRoutQmDestEntry 118292480}

er1645v2VrfRoutQmDestDelayAlarmJitterUpMaxOn OBJECT-TYPE
   SYNTAX      Integer32
   UNITS       "msec"
   MAX-ACCESS  read-write
   STATUS      current
   DESCRIPTION
      "Path: vrfRouter.editConf.qualityMonitor.destinations.delayAlarm.jitterUpMaxOn

       unit name = msec"
   ::= {er1645v2VrfRoutQmDestEntry 118358016}

er1645v2VrfRoutQmDestDelayAlarmJitterUpMaxOff OBJECT-TYPE
   SYNTAX      Integer32
   UNITS       "msec"
   MAX-ACCESS  read-write
   STATUS      current
   DESCRIPTION
      "Path: vrfRouter.editConf.qualityMonitor.destinations.delayAlarm.jitterUpMaxOff

       unit name = msec"
   ::= {er1645v2VrfRoutQmDestEntry 118423552}

er1645v2VrfRoutQmDestDelayAlarmJupsN OBJECT-TYPE
   SYNTAX      INTEGER
               {
               none (0)
               }
   MAX-ACCESS  read-write
   STATUS      current
   DESCRIPTION
      "Path: vrfRouter.editConf.qualityMonitor.destinations.delayAlarm.jitterUpStat.none

       Possibilities:
               none   (0)"
   ::= {er1645v2VrfRoutQmDestEntry 119808000}

er1645v2VrfRoutQmDestDelayAlarmJupsNMn OBJECT-TYPE
   SYNTAX      Integer32
   UNITS       "msec"
   MAX-ACCESS  read-write
   STATUS      current
   DESCRIPTION
      "Path: vrfRouter.editConf.qualityMonitor.destinations.delayAlarm.jitterUpStat.range.min

       unit name = msec"
   ::= {er1645v2VrfRoutQmDestEntry 119817216}

er1645v2VrfRoutQmDestDelayAlarmJupsNMx OBJECT-TYPE
   SYNTAX      Integer32
   UNITS       "msec"
   MAX-ACCESS  read-write
   STATUS      current
   DESCRIPTION
      "Path: vrfRouter.editConf.qualityMonitor.destinations.delayAlarm.jitterUpStat.range.max

       unit name = msec"
   ::= {er1645v2VrfRoutQmDestEntry 119818240}

er1645v2VrfRoutQmDestDelayAlarmJupsTB1 OBJECT-TYPE
   SYNTAX      Integer32
   UNITS       "msec"
   MAX-ACCESS  read-write
   STATUS      current
   DESCRIPTION
      "Path: vrfRouter.editConf.qualityMonitor.destinations.delayAlarm.jitterUpStat.table.bin1

       unit name = msec"
   ::= {er1645v2VrfRoutQmDestEntry 119824896}

er1645v2VrfRoutQmDestDelayAlarmJupsTB2 OBJECT-TYPE
   SYNTAX      Integer32
   UNITS       "msec"
   MAX-ACCESS  read-write
   STATUS      current
   DESCRIPTION
      "Path: vrfRouter.editConf.qualityMonitor.destinations.delayAlarm.jitterUpStat.table.bin2

       unit name = msec"
   ::= {er1645v2VrfRoutQmDestEntry 119825408}

er1645v2VrfRoutQmDestDelayAlarmJupsTB3 OBJECT-TYPE
   SYNTAX      Integer32
   UNITS       "msec"
   MAX-ACCESS  read-write
   STATUS      current
   DESCRIPTION
      "Path: vrfRouter.editConf.qualityMonitor.destinations.delayAlarm.jitterUpStat.table.bin3

       unit name = msec"
   ::= {er1645v2VrfRoutQmDestEntry 119825920}

er1645v2VrfRoutQmDestDelayAlarmJupsTB4 OBJECT-TYPE
   SYNTAX      Integer32
   UNITS       "msec"
   MAX-ACCESS  read-write
   STATUS      current
   DESCRIPTION
      "Path: vrfRouter.editConf.qualityMonitor.destinations.delayAlarm.jitterUpStat.table.bin4

       unit name = msec"
   ::= {er1645v2VrfRoutQmDestEntry 119826432}

er1645v2VrfRoutQmDestDelayAlarmJupsTB5 OBJECT-TYPE
   SYNTAX      Integer32
   UNITS       "msec"
   MAX-ACCESS  read-write
   STATUS      current
   DESCRIPTION
      "Path: vrfRouter.editConf.qualityMonitor.destinations.delayAlarm.jitterUpStat.table.bin5

       unit name = msec"
   ::= {er1645v2VrfRoutQmDestEntry 119826944}

er1645v2VrfRoutQmDestDelayAlarmJupsTB6 OBJECT-TYPE
   SYNTAX      Integer32
   UNITS       "msec"
   MAX-ACCESS  read-write
   STATUS      current
   DESCRIPTION
      "Path: vrfRouter.editConf.qualityMonitor.destinations.delayAlarm.jitterUpStat.table.bin6

       unit name = msec"
   ::= {er1645v2VrfRoutQmDestEntry 119827456}

er1645v2VrfRoutQmDestDelayAlarmJupsTB7 OBJECT-TYPE
   SYNTAX      Integer32
   UNITS       "msec"
   MAX-ACCESS  read-write
   STATUS      current
   DESCRIPTION
      "Path: vrfRouter.editConf.qualityMonitor.destinations.delayAlarm.jitterUpStat.table.bin7

       unit name = msec"
   ::= {er1645v2VrfRoutQmDestEntry 119827968}

er1645v2VrfRoutQmDestDelayAlarmJupsTB8 OBJECT-TYPE
   SYNTAX      Integer32
   UNITS       "msec"
   MAX-ACCESS  read-write
   STATUS      current
   DESCRIPTION
      "Path: vrfRouter.editConf.qualityMonitor.destinations.delayAlarm.jitterUpStat.table.bin8

       unit name = msec"
   ::= {er1645v2VrfRoutQmDestEntry 119828480}

er1645v2VrfRoutQmDestDelayAlarmJupsTMx OBJECT-TYPE
   SYNTAX      Integer32
   UNITS       "msec"
   MAX-ACCESS  read-write
   STATUS      current
   DESCRIPTION
      "Path: vrfRouter.editConf.qualityMonitor.destinations.delayAlarm.jitterUpStat.table.max

       unit name = msec"
   ::= {er1645v2VrfRoutQmDestEntry 119828992}

er1645v2VrfRoutQmDestDelayAlarmJitterDownAvrgOn OBJECT-TYPE
   SYNTAX      Integer32
   UNITS       "msec"
   MAX-ACCESS  read-write
   STATUS      current
   DESCRIPTION
      "Path: vrfRouter.editConf.qualityMonitor.destinations.delayAlarm.jitterDownAvrgOn

       unit name = msec"
   ::= {er1645v2VrfRoutQmDestEntry 118489088}

er1645v2VrfRoutQmDestDelayAlarmJitterDownAvrgOff OBJECT-TYPE
   SYNTAX      Integer32
   UNITS       "msec"
   MAX-ACCESS  read-write
   STATUS      current
   DESCRIPTION
      "Path: vrfRouter.editConf.qualityMonitor.destinations.delayAlarm.jitterDownAvrgOff

       unit name = msec"
   ::= {er1645v2VrfRoutQmDestEntry 118554624}

er1645v2VrfRoutQmDestDelayAlarmJitterDownMaxOn OBJECT-TYPE
   SYNTAX      Integer32
   UNITS       "msec"
   MAX-ACCESS  read-write
   STATUS      current
   DESCRIPTION
      "Path: vrfRouter.editConf.qualityMonitor.destinations.delayAlarm.jitterDownMaxOn

       unit name = msec"
   ::= {er1645v2VrfRoutQmDestEntry 118620160}

er1645v2VrfRoutQmDestDelayAlarmJitterDownMaxOff OBJECT-TYPE
   SYNTAX      Integer32
   UNITS       "msec"
   MAX-ACCESS  read-write
   STATUS      current
   DESCRIPTION
      "Path: vrfRouter.editConf.qualityMonitor.destinations.delayAlarm.jitterDownMaxOff

       unit name = msec"
   ::= {er1645v2VrfRoutQmDestEntry 118685696}

er1645v2VrfRoutQmDestDelayAlarmJdownsN OBJECT-TYPE
   SYNTAX      INTEGER
               {
               none (0)
               }
   MAX-ACCESS  read-write
   STATUS      current
   DESCRIPTION
      "Path: vrfRouter.editConf.qualityMonitor.destinations.delayAlarm.jitterDownStat.none

       Possibilities:
               none   (0)"
   ::= {er1645v2VrfRoutQmDestEntry 119939072}

er1645v2VrfRoutQmDestDelayAlarmJdownsNMn OBJECT-TYPE
   SYNTAX      Integer32
   UNITS       "msec"
   MAX-ACCESS  read-write
   STATUS      current
   DESCRIPTION
      "Path: vrfRouter.editConf.qualityMonitor.destinations.delayAlarm.jitterDownStat.range.min

       unit name = msec"
   ::= {er1645v2VrfRoutQmDestEntry 119948288}

er1645v2VrfRoutQmDestDelayAlarmJdownsNMx OBJECT-TYPE
   SYNTAX      Integer32
   UNITS       "msec"
   MAX-ACCESS  read-write
   STATUS      current
   DESCRIPTION
      "Path: vrfRouter.editConf.qualityMonitor.destinations.delayAlarm.jitterDownStat.range.max

       unit name = msec"
   ::= {er1645v2VrfRoutQmDestEntry 119949312}

er1645v2VrfRoutQmDestDelayAlarmJdownsTB1 OBJECT-TYPE
   SYNTAX      Integer32
   UNITS       "msec"
   MAX-ACCESS  read-write
   STATUS      current
   DESCRIPTION
      "Path: vrfRouter.editConf.qualityMonitor.destinations.delayAlarm.jitterDownStat.table.bin1

       unit name = msec"
   ::= {er1645v2VrfRoutQmDestEntry 119955968}

er1645v2VrfRoutQmDestDelayAlarmJdownsTB2 OBJECT-TYPE
   SYNTAX      Integer32
   UNITS       "msec"
   MAX-ACCESS  read-write
   STATUS      current
   DESCRIPTION
      "Path: vrfRouter.editConf.qualityMonitor.destinations.delayAlarm.jitterDownStat.table.bin2

       unit name = msec"
   ::= {er1645v2VrfRoutQmDestEntry 119956480}

er1645v2VrfRoutQmDestDelayAlarmJdownsTB3 OBJECT-TYPE
   SYNTAX      Integer32
   UNITS       "msec"
   MAX-ACCESS  read-write
   STATUS      current
   DESCRIPTION
      "Path: vrfRouter.editConf.qualityMonitor.destinations.delayAlarm.jitterDownStat.table.bin3

       unit name = msec"
   ::= {er1645v2VrfRoutQmDestEntry 119956992}

er1645v2VrfRoutQmDestDelayAlarmJdownsTB4 OBJECT-TYPE
   SYNTAX      Integer32
   UNITS       "msec"
   MAX-ACCESS  read-write
   STATUS      current
   DESCRIPTION
      "Path: vrfRouter.editConf.qualityMonitor.destinations.delayAlarm.jitterDownStat.table.bin4

       unit name = msec"
   ::= {er1645v2VrfRoutQmDestEntry 119957504}

er1645v2VrfRoutQmDestDelayAlarmJdownsTB5 OBJECT-TYPE
   SYNTAX      Integer32
   UNITS       "msec"
   MAX-ACCESS  read-write
   STATUS      current
   DESCRIPTION
      "Path: vrfRouter.editConf.qualityMonitor.destinations.delayAlarm.jitterDownStat.table.bin5

       unit name = msec"
   ::= {er1645v2VrfRoutQmDestEntry 119958016}

er1645v2VrfRoutQmDestDelayAlarmJdownsTB6 OBJECT-TYPE
   SYNTAX      Integer32
   UNITS       "msec"
   MAX-ACCESS  read-write
   STATUS      current
   DESCRIPTION
      "Path: vrfRouter.editConf.qualityMonitor.destinations.delayAlarm.jitterDownStat.table.bin6

       unit name = msec"
   ::= {er1645v2VrfRoutQmDestEntry 119958528}

er1645v2VrfRoutQmDestDelayAlarmJdownsTB7 OBJECT-TYPE
   SYNTAX      Integer32
   UNITS       "msec"
   MAX-ACCESS  read-write
   STATUS      current
   DESCRIPTION
      "Path: vrfRouter.editConf.qualityMonitor.destinations.delayAlarm.jitterDownStat.table.bin7

       unit name = msec"
   ::= {er1645v2VrfRoutQmDestEntry 119959040}

er1645v2VrfRoutQmDestDelayAlarmJdownsTB8 OBJECT-TYPE
   SYNTAX      Integer32
   UNITS       "msec"
   MAX-ACCESS  read-write
   STATUS      current
   DESCRIPTION
      "Path: vrfRouter.editConf.qualityMonitor.destinations.delayAlarm.jitterDownStat.table.bin8

       unit name = msec"
   ::= {er1645v2VrfRoutQmDestEntry 119959552}

er1645v2VrfRoutQmDestDelayAlarmJdownsTMx OBJECT-TYPE
   SYNTAX      Integer32
   UNITS       "msec"
   MAX-ACCESS  read-write
   STATUS      current
   DESCRIPTION
      "Path: vrfRouter.editConf.qualityMonitor.destinations.delayAlarm.jitterDownStat.table.max

       unit name = msec"
   ::= {er1645v2VrfRoutQmDestEntry 119960064}

er1645v2VrfRoutQmDestDelayAlarmDelayUpAvrgOn OBJECT-TYPE
   SYNTAX      Integer32
   UNITS       "msec"
   MAX-ACCESS  read-write
   STATUS      current
   DESCRIPTION
      "Path: vrfRouter.editConf.qualityMonitor.destinations.delayAlarm.delayUpAvrgOn

       unit name = msec"
   ::= {er1645v2VrfRoutQmDestEntry 118751232}

er1645v2VrfRoutQmDestDelayAlarmDelayUpAvrgOff OBJECT-TYPE
   SYNTAX      Integer32
   UNITS       "msec"
   MAX-ACCESS  read-write
   STATUS      current
   DESCRIPTION
      "Path: vrfRouter.editConf.qualityMonitor.destinations.delayAlarm.delayUpAvrgOff

       unit name = msec"
   ::= {er1645v2VrfRoutQmDestEntry 118816768}

er1645v2VrfRoutQmDestDelayAlarmDelayUpMaxOn OBJECT-TYPE
   SYNTAX      Integer32
   UNITS       "msec"
   MAX-ACCESS  read-write
   STATUS      current
   DESCRIPTION
      "Path: vrfRouter.editConf.qualityMonitor.destinations.delayAlarm.delayUpMaxOn

       unit name = msec"
   ::= {er1645v2VrfRoutQmDestEntry 118882304}

er1645v2VrfRoutQmDestDelayAlarmDelayUpMaxOff OBJECT-TYPE
   SYNTAX      Integer32
   UNITS       "msec"
   MAX-ACCESS  read-write
   STATUS      current
   DESCRIPTION
      "Path: vrfRouter.editConf.qualityMonitor.destinations.delayAlarm.delayUpMaxOff

       unit name = msec"
   ::= {er1645v2VrfRoutQmDestEntry 118947840}

er1645v2VrfRoutQmDestDelayAlarmDupsType OBJECT-TYPE
   SYNTAX      INTEGER
               {
               fd (1),
               fdr (2)
               }
   MAX-ACCESS  read-write
   STATUS      current
   DESCRIPTION
      "Path: vrfRouter.editConf.qualityMonitor.destinations.delayAlarm.delayUpStat.type

       Possibilities:
               fd   (1)
               fdr   (2)"
   ::= {er1645v2VrfRoutQmDestEntry 119414784}

er1645v2VrfRoutQmDestDelayAlarmDupsBinsN OBJECT-TYPE
   SYNTAX      INTEGER
               {
               none (0)
               }
   MAX-ACCESS  read-write
   STATUS      current
   DESCRIPTION
      "Path: vrfRouter.editConf.qualityMonitor.destinations.delayAlarm.delayUpStat.bins.none

       Possibilities:
               none   (0)"
   ::= {er1645v2VrfRoutQmDestEntry 119424000}

er1645v2VrfRoutQmDestDelayAlarmDupsBinsNMn OBJECT-TYPE
   SYNTAX      Integer32
   UNITS       "msec"
   MAX-ACCESS  read-write
   STATUS      current
   DESCRIPTION
      "Path: vrfRouter.editConf.qualityMonitor.destinations.delayAlarm.delayUpStat.bins.range.min

       unit name = msec"
   ::= {er1645v2VrfRoutQmDestEntry 119425152}

er1645v2VrfRoutQmDestDelayAlarmDupsBinsNMx OBJECT-TYPE
   SYNTAX      Integer32
   UNITS       "msec"
   MAX-ACCESS  read-write
   STATUS      current
   DESCRIPTION
      "Path: vrfRouter.editConf.qualityMonitor.destinations.delayAlarm.delayUpStat.bins.range.max

       unit name = msec"
   ::= {er1645v2VrfRoutQmDestEntry 119425280}

er1645v2VrfRoutQmDestDelayAlarmDupsBinsTB1 OBJECT-TYPE
   SYNTAX      Integer32
   UNITS       "msec"
   MAX-ACCESS  read-write
   STATUS      current
   DESCRIPTION
      "Path: vrfRouter.editConf.qualityMonitor.destinations.delayAlarm.delayUpStat.bins.table.bin1

       unit name = msec"
   ::= {er1645v2VrfRoutQmDestEntry 119426112}

er1645v2VrfRoutQmDestDelayAlarmDupsBinsTB2 OBJECT-TYPE
   SYNTAX      Integer32
   UNITS       "msec"
   MAX-ACCESS  read-write
   STATUS      current
   DESCRIPTION
      "Path: vrfRouter.editConf.qualityMonitor.destinations.delayAlarm.delayUpStat.bins.table.bin2

       unit name = msec"
   ::= {er1645v2VrfRoutQmDestEntry 119426176}

er1645v2VrfRoutQmDestDelayAlarmDupsBinsTB3 OBJECT-TYPE
   SYNTAX      Integer32
   UNITS       "msec"
   MAX-ACCESS  read-write
   STATUS      current
   DESCRIPTION
      "Path: vrfRouter.editConf.qualityMonitor.destinations.delayAlarm.delayUpStat.bins.table.bin3

       unit name = msec"
   ::= {er1645v2VrfRoutQmDestEntry 119426240}

er1645v2VrfRoutQmDestDelayAlarmDupsBinsTB4 OBJECT-TYPE
   SYNTAX      Integer32
   UNITS       "msec"
   MAX-ACCESS  read-write
   STATUS      current
   DESCRIPTION
      "Path: vrfRouter.editConf.qualityMonitor.destinations.delayAlarm.delayUpStat.bins.table.bin4

       unit name = msec"
   ::= {er1645v2VrfRoutQmDestEntry 119426304}

er1645v2VrfRoutQmDestDelayAlarmDupsBinsTB5 OBJECT-TYPE
   SYNTAX      Integer32
   UNITS       "msec"
   MAX-ACCESS  read-write
   STATUS      current
   DESCRIPTION
      "Path: vrfRouter.editConf.qualityMonitor.destinations.delayAlarm.delayUpStat.bins.table.bin5

       unit name = msec"
   ::= {er1645v2VrfRoutQmDestEntry 119426368}

er1645v2VrfRoutQmDestDelayAlarmDupsBinsTB6 OBJECT-TYPE
   SYNTAX      Integer32
   UNITS       "msec"
   MAX-ACCESS  read-write
   STATUS      current
   DESCRIPTION
      "Path: vrfRouter.editConf.qualityMonitor.destinations.delayAlarm.delayUpStat.bins.table.bin6

       unit name = msec"
   ::= {er1645v2VrfRoutQmDestEntry 119426432}

er1645v2VrfRoutQmDestDelayAlarmDupsBinsTB7 OBJECT-TYPE
   SYNTAX      Integer32
   UNITS       "msec"
   MAX-ACCESS  read-write
   STATUS      current
   DESCRIPTION
      "Path: vrfRouter.editConf.qualityMonitor.destinations.delayAlarm.delayUpStat.bins.table.bin7

       unit name = msec"
   ::= {er1645v2VrfRoutQmDestEntry 119426496}

er1645v2VrfRoutQmDestDelayAlarmDupsBinsTB8 OBJECT-TYPE
   SYNTAX      Integer32
   UNITS       "msec"
   MAX-ACCESS  read-write
   STATUS      current
   DESCRIPTION
      "Path: vrfRouter.editConf.qualityMonitor.destinations.delayAlarm.delayUpStat.bins.table.bin8

       unit name = msec"
   ::= {er1645v2VrfRoutQmDestEntry 119426560}

er1645v2VrfRoutQmDestDelayAlarmDupsBinsTMx OBJECT-TYPE
   SYNTAX      Integer32
   UNITS       "msec"
   MAX-ACCESS  read-write
   STATUS      current
   DESCRIPTION
      "Path: vrfRouter.editConf.qualityMonitor.destinations.delayAlarm.delayUpStat.bins.table.max

       unit name = msec"
   ::= {er1645v2VrfRoutQmDestEntry 119426624}

er1645v2VrfRoutQmDestDelayAlarmDelayDownAvrgOn OBJECT-TYPE
   SYNTAX      Integer32
   UNITS       "msec"
   MAX-ACCESS  read-write
   STATUS      current
   DESCRIPTION
      "Path: vrfRouter.editConf.qualityMonitor.destinations.delayAlarm.delayDownAvrgOn

       unit name = msec"
   ::= {er1645v2VrfRoutQmDestEntry 119013376}

er1645v2VrfRoutQmDestDelayAlarmDelayDownAvrgOff OBJECT-TYPE
   SYNTAX      Integer32
   UNITS       "msec"
   MAX-ACCESS  read-write
   STATUS      current
   DESCRIPTION
      "Path: vrfRouter.editConf.qualityMonitor.destinations.delayAlarm.delayDownAvrgOff

       unit name = msec"
   ::= {er1645v2VrfRoutQmDestEntry 119078912}

er1645v2VrfRoutQmDestDelayAlarmDelayDownMaxOn OBJECT-TYPE
   SYNTAX      Integer32
   UNITS       "msec"
   MAX-ACCESS  read-write
   STATUS      current
   DESCRIPTION
      "Path: vrfRouter.editConf.qualityMonitor.destinations.delayAlarm.delayDownMaxOn

       unit name = msec"
   ::= {er1645v2VrfRoutQmDestEntry 119144448}

er1645v2VrfRoutQmDestDelayAlarmDelayDownMaxOff OBJECT-TYPE
   SYNTAX      Integer32
   UNITS       "msec"
   MAX-ACCESS  read-write
   STATUS      current
   DESCRIPTION
      "Path: vrfRouter.editConf.qualityMonitor.destinations.delayAlarm.delayDownMaxOff

       unit name = msec"
   ::= {er1645v2VrfRoutQmDestEntry 119209984}

er1645v2VrfRoutQmDestDelayAlarmDdownsType OBJECT-TYPE
   SYNTAX      INTEGER
               {
               fd (1),
               fdr (2)
               }
   MAX-ACCESS  read-write
   STATUS      current
   DESCRIPTION
      "Path: vrfRouter.editConf.qualityMonitor.destinations.delayAlarm.delayDownStat.type

       Possibilities:
               fd   (1)
               fdr   (2)"
   ::= {er1645v2VrfRoutQmDestEntry 119545856}

er1645v2VrfRoutQmDestDelayAlarmDdownsBinsN OBJECT-TYPE
   SYNTAX      INTEGER
               {
               none (0)
               }
   MAX-ACCESS  read-write
   STATUS      current
   DESCRIPTION
      "Path: vrfRouter.editConf.qualityMonitor.destinations.delayAlarm.delayDownStat.bins.none

       Possibilities:
               none   (0)"
   ::= {er1645v2VrfRoutQmDestEntry 119555072}

er1645v2VrfRoutQmDestDelayAlarmDdownsBinsNMn OBJECT-TYPE
   SYNTAX      Integer32
   UNITS       "msec"
   MAX-ACCESS  read-write
   STATUS      current
   DESCRIPTION
      "Path: vrfRouter.editConf.qualityMonitor.destinations.delayAlarm.delayDownStat.bins.range.min

       unit name = msec"
   ::= {er1645v2VrfRoutQmDestEntry 119556224}

er1645v2VrfRoutQmDestDelayAlarmDdownsBinsNMx OBJECT-TYPE
   SYNTAX      Integer32
   UNITS       "msec"
   MAX-ACCESS  read-write
   STATUS      current
   DESCRIPTION
      "Path: vrfRouter.editConf.qualityMonitor.destinations.delayAlarm.delayDownStat.bins.range.max

       unit name = msec"
   ::= {er1645v2VrfRoutQmDestEntry 119556352}

er1645v2VrfRoutQmDestDelayAlarmDdownsBinsTB1 OBJECT-TYPE
   SYNTAX      Integer32
   UNITS       "msec"
   MAX-ACCESS  read-write
   STATUS      current
   DESCRIPTION
      "Path: vrfRouter.editConf.qualityMonitor.destinations.delayAlarm.delayDownStat.bins.table.bin1

       unit name = msec"
   ::= {er1645v2VrfRoutQmDestEntry 119557184}

er1645v2VrfRoutQmDestDelayAlarmDdownsBinsTB2 OBJECT-TYPE
   SYNTAX      Integer32
   UNITS       "msec"
   MAX-ACCESS  read-write
   STATUS      current
   DESCRIPTION
      "Path: vrfRouter.editConf.qualityMonitor.destinations.delayAlarm.delayDownStat.bins.table.bin2

       unit name = msec"
   ::= {er1645v2VrfRoutQmDestEntry 119557248}

er1645v2VrfRoutQmDestDelayAlarmDdownsBinsTB3 OBJECT-TYPE
   SYNTAX      Integer32
   UNITS       "msec"
   MAX-ACCESS  read-write
   STATUS      current
   DESCRIPTION
      "Path: vrfRouter.editConf.qualityMonitor.destinations.delayAlarm.delayDownStat.bins.table.bin3

       unit name = msec"
   ::= {er1645v2VrfRoutQmDestEntry 119557312}

er1645v2VrfRoutQmDestDelayAlarmDdownsBinsTB4 OBJECT-TYPE
   SYNTAX      Integer32
   UNITS       "msec"
   MAX-ACCESS  read-write
   STATUS      current
   DESCRIPTION
      "Path: vrfRouter.editConf.qualityMonitor.destinations.delayAlarm.delayDownStat.bins.table.bin4

       unit name = msec"
   ::= {er1645v2VrfRoutQmDestEntry 119557376}

er1645v2VrfRoutQmDestDelayAlarmDdownsBinsTB5 OBJECT-TYPE
   SYNTAX      Integer32
   UNITS       "msec"
   MAX-ACCESS  read-write
   STATUS      current
   DESCRIPTION
      "Path: vrfRouter.editConf.qualityMonitor.destinations.delayAlarm.delayDownStat.bins.table.bin5

       unit name = msec"
   ::= {er1645v2VrfRoutQmDestEntry 119557440}

er1645v2VrfRoutQmDestDelayAlarmDdownsBinsTB6 OBJECT-TYPE
   SYNTAX      Integer32
   UNITS       "msec"
   MAX-ACCESS  read-write
   STATUS      current
   DESCRIPTION
      "Path: vrfRouter.editConf.qualityMonitor.destinations.delayAlarm.delayDownStat.bins.table.bin6

       unit name = msec"
   ::= {er1645v2VrfRoutQmDestEntry 119557504}

er1645v2VrfRoutQmDestDelayAlarmDdownsBinsTB7 OBJECT-TYPE
   SYNTAX      Integer32
   UNITS       "msec"
   MAX-ACCESS  read-write
   STATUS      current
   DESCRIPTION
      "Path: vrfRouter.editConf.qualityMonitor.destinations.delayAlarm.delayDownStat.bins.table.bin7

       unit name = msec"
   ::= {er1645v2VrfRoutQmDestEntry 119557568}

er1645v2VrfRoutQmDestDelayAlarmDdownsBinsTB8 OBJECT-TYPE
   SYNTAX      Integer32
   UNITS       "msec"
   MAX-ACCESS  read-write
   STATUS      current
   DESCRIPTION
      "Path: vrfRouter.editConf.qualityMonitor.destinations.delayAlarm.delayDownStat.bins.table.bin8

       unit name = msec"
   ::= {er1645v2VrfRoutQmDestEntry 119557632}

er1645v2VrfRoutQmDestDelayAlarmDdownsBinsTMx OBJECT-TYPE
   SYNTAX      Integer32
   UNITS       "msec"
   MAX-ACCESS  read-write
   STATUS      current
   DESCRIPTION
      "Path: vrfRouter.editConf.qualityMonitor.destinations.delayAlarm.delayDownStat.bins.table.max

       unit name = msec"
   ::= {er1645v2VrfRoutQmDestEntry 119557696}

er1645v2VrfRoutQmDestAlarmMask OBJECT-TYPE
   SYNTAX      Integer32
   MAX-ACCESS  read-write
   STATUS      current
   DESCRIPTION
      "Path: vrfRouter.editConf.qualityMonitor.destinations.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1645v2VrfRoutQmDestEntry 251658240}

er1645v2VrfRoutQmDestLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: vrfRouter.editConf.qualityMonitor.destinations.logging

       Possibilities:
               disabled   (0)
               3min   (3)
               5min   (5)
               10min   (10)
               15min   (15)
               30min   (30)
               60min   (60)"
   ::= {er1645v2VrfRoutQmDestEntry 201326592}

er1645v2VrfRoutQmDestLoggingDepth OBJECT-TYPE
   SYNTAX      INTEGER
               {
               s2 (2),
               s4 (4),
               s8 (8),
               s16 (16),
               s32 (32),
               s128 (128),
               s512 (512),
               s1024 (1024)
               }
   MAX-ACCESS  read-write
   STATUS      current
   DESCRIPTION
      "Path: vrfRouter.editConf.qualityMonitor.destinations.loggingDepth

       Possibilities:
               2   (2)
               4   (4)
               8   (8)
               16   (16)
               32   (32)
               128   (128)
               512   (512)
               1024   (1024)"
   ::= {er1645v2VrfRoutQmDestEntry 503316480}

er1645v2VrfRoutQmUdpServerPort OBJECT-TYPE
   SYNTAX      SEQUENCE OF Er1645v2VrfRoutQmUdpServerPortEntry
   MAX-ACCESS  not-accessible
   STATUS      current
   DESCRIPTION
      ""
   ::= {er1645v2VrfRoutQm 67108864}

er1645v2VrfRoutQmUdpServerPortEntry OBJECT-TYPE
   SYNTAX      Er1645v2VrfRoutQmUdpServerPortEntry
   MAX-ACCESS  not-accessible
   STATUS      current
   DESCRIPTION
      ""
   INDEX      { er1645v2VrfRoutQmUdpServerPortGlobalIx,
                er1645v2VrfRoutQmUdpServerPortTableIx }
   ::= {er1645v2VrfRoutQmUdpServerPort 1}

Er1645v2VrfRoutQmUdpServerPortEntry ::=
   SEQUENCE
      {
      er1645v2VrfRoutQmUdpServerPortActions
         VariableLengthTableActions,
      er1645v2VrfRoutQmUdpServerPortGlobalIx
         GlobalIndex,
      er1645v2VrfRoutQmUdpServerPortTableIx
         TableIndex,
      er1645v2VrfRoutQmUdpServerPortDestinationPort
         Integer32,
      er1645v2VrfRoutQmUdpServerPortService
         INTEGER,
      er1645v2VrfRoutQmUdpServerPortPriority
         INTEGER,
      er1645v2VrfRoutQmUdpServerPortTos
         INTEGER
      }

er1645v2VrfRoutQmUdpServerPortActions OBJECT-TYPE
   SYNTAX      VariableLengthTableActions
   MAX-ACCESS  read-write
   STATUS      current
   DESCRIPTION
      "By way of this field, some manipulations
       on this table may be performed."
   ::= {er1645v2VrfRoutQmUdpServerPortEntry 2}

er1645v2VrfRoutQmUdpServerPortGlobalIx OBJECT-TYPE
   SYNTAX      GlobalIndex
   MAX-ACCESS  not-accessible
   STATUS      current
   DESCRIPTION
      "The value of the tlsCntTreeGlobalIndex of the MANAGED OBJECT."
   ::= {er1645v2VrfRoutQmUdpServerPortEntry 10}

er1645v2VrfRoutQmUdpServerPortTableIx OBJECT-TYPE
   SYNTAX      TableIndex
   MAX-ACCESS  not-accessible
   STATUS      current
   DESCRIPTION
      ""
   ::= {er1645v2VrfRoutQmUdpServerPortEntry 11}

er1645v2VrfRoutQmUdpServerPortDestinationPort OBJECT-TYPE
   SYNTAX      Integer32
   MAX-ACCESS  read-write
   STATUS      current
   DESCRIPTION
      "Path: vrfRouter.editConf.qualityMonitor.udpServerPort.destinationPort"
   ::= {er1645v2VrfRoutQmUdpServerPortEntry 16777216}

er1645v2VrfRoutQmUdpServerPortService OBJECT-TYPE
   SYNTAX      INTEGER
               {
               proprietary (1),
               twampLight (2)
               }
   MAX-ACCESS  read-write
   STATUS      current
   DESCRIPTION
      "Path: vrfRouter.editConf.qualityMonitor.udpServerPort.service

       Possibilities:
               proprietary   (1)
               twampLight   (2)"
   ::= {er1645v2VrfRoutQmUdpServerPortEntry 234881024}

er1645v2VrfRoutQmUdpServerPortPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfRouter.editConf.qualityMonitor.udpServerPort.priority

       Possibilities:
               queue1   (0)
               queue2   (1)
               queue3   (2)
               queue4   (3)
               queue5   (4)
               lowDelayQueue   (5)
               lowDelay2Queue   (6)
               systemQueue   (7)"
   ::= {er1645v2VrfRoutQmUdpServerPortEntry 218103808}

er1645v2VrfRoutQmUdpServerPortTos OBJECT-TYPE
   SYNTAX      INTEGER
               {
               keepTos (-1),
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouter.editConf.qualityMonitor.udpServerPort.tos

       Possibilities:
               keepTos   (-1)
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VrfRoutQmUdpServerPortEntry 167772160}


er1645v2VrfRoutForceMtu OBJECT IDENTIFIER ::= {er1645v2VrfRout 171}

er1645v2VrfRoutForceMtuTable OBJECT-TYPE
   SYNTAX      SEQUENCE OF Er1645v2VrfRoutForceMtuEntry
   MAX-ACCESS  not-accessible
   STATUS      current
   DESCRIPTION
      "force the configured mtu"
   ::= {er1645v2VrfRoutForceMtu 1}

er1645v2VrfRoutForceMtuEntry OBJECT-TYPE
   SYNTAX      Er1645v2VrfRoutForceMtuEntry
   MAX-ACCESS  not-accessible
   STATUS      current
   DESCRIPTION
      ""
   INDEX      { er1645v2VrfRoutForceMtuGlobalIx }
   ::= {er1645v2VrfRoutForceMtuTable 1}

Er1645v2VrfRoutForceMtuEntry ::=
   SEQUENCE
      {
      er1645v2VrfRoutForceMtuGlobalIx
         GlobalIndex,
      er1645v2VrfRoutForceMtuValue
         INTEGER
      }

er1645v2VrfRoutForceMtuGlobalIx OBJECT-TYPE
   SYNTAX      GlobalIndex
   MAX-ACCESS  not-accessible
   STATUS      current
   DESCRIPTION
      "The value of the tlsCntTreeGlobalIndex of the MANAGED OBJECT."
   ::= {er1645v2VrfRoutForceMtuEntry 10}

er1645v2VrfRoutForceMtuValue OBJECT-TYPE
   SYNTAX      INTEGER
               {
               disabled (0),
               enabled (1)
               }
   MAX-ACCESS  read-write
   STATUS      current
   DESCRIPTION
      "Path: vrfRouter.editConf.forceMtu

       Possibilities:
               disabled   (0)
               enabled   (1)"
   ::= {er1645v2VrfRoutForceMtuEntry 2147483648}


er1645v2VrfRoutAlarmMask OBJECT IDENTIFIER ::= {er1645v2VrfRout 135}

er1645v2VrfRoutAlarmMaskTable OBJECT-TYPE
   SYNTAX      SEQUENCE OF Er1645v2VrfRoutAlarmMaskEntry
   MAX-ACCESS  not-accessible
   STATUS      current
   DESCRIPTION
      "routAlarmMask"
   ::= {er1645v2VrfRoutAlarmMask 1}

er1645v2VrfRoutAlarmMaskEntry OBJECT-TYPE
   SYNTAX      Er1645v2VrfRoutAlarmMaskEntry
   MAX-ACCESS  not-accessible
   STATUS      current
   DESCRIPTION
      ""
   INDEX      { er1645v2VrfRoutAlarmMaskGlobalIx }
   ::= {er1645v2VrfRoutAlarmMaskTable 1}

Er1645v2VrfRoutAlarmMaskEntry ::=
   SEQUENCE
      {
      er1645v2VrfRoutAlarmMaskGlobalIx
         GlobalIndex,
      er1645v2VrfRoutAlarmMaskValue
         Integer32
      }

er1645v2VrfRoutAlarmMaskGlobalIx OBJECT-TYPE
   SYNTAX      GlobalIndex
   MAX-ACCESS  not-accessible
   STATUS      current
   DESCRIPTION
      "The value of the tlsCntTreeGlobalIndex of the MANAGED OBJECT."
   ::= {er1645v2VrfRoutAlarmMaskEntry 10}

er1645v2VrfRoutAlarmMaskValue OBJECT-TYPE
   SYNTAX      Integer32
   MAX-ACCESS  read-write
   STATUS      current
   DESCRIPTION
      "Path: vrfRouter.editConf.alarmMask

       Bit meanings:
               bit 0 = pingActive,
               bit 1 = qMonLoss,
               bit 2 = qMonDelay,
               bit 3 = qMonJitter"
   ::= {er1645v2VrfRoutAlarmMaskEntry 2147483648}


er1645v2VrfRoutAlarmLev OBJECT IDENTIFIER ::= {er1645v2VrfRout 170}

er1645v2VrfRoutAlarmLevSSCTable OBJECT-TYPE
   SYNTAX      SEQUENCE OF Er1645v2VrfRoutAlarmLevEntry
   MAX-ACCESS  not-accessible
   STATUS      current
   DESCRIPTION
      "routAlarmLevels"
   ::= {er1645v2VrfRoutAlarmLev 1}

er1645v2VrfRoutAlarmLevEntry OBJECT-TYPE
   SYNTAX      Er1645v2VrfRoutAlarmLevEntry
   MAX-ACCESS  not-accessible
   STATUS      current
   DESCRIPTION
      ""
   INDEX      { er1645v2VrfRoutAlarmLevGlobalIx }
   ::= {er1645v2VrfRoutAlarmLevSSCTable 1}

Er1645v2VrfRoutAlarmLevEntry ::=
   SEQUENCE
      {
      er1645v2VrfRoutAlarmLevGlobalIx
         GlobalIndex,
      er1645v2VrfRoutAlarmLevPingActive
         Integer32,
      er1645v2VrfRoutAlarmLevQMonLoss
         Integer32,
      er1645v2VrfRoutAlarmLevQMonDelay
         Integer32,
      er1645v2VrfRoutAlarmLevQMonJitter
         Integer32
      }

er1645v2VrfRoutAlarmLevGlobalIx OBJECT-TYPE
   SYNTAX      GlobalIndex
   MAX-ACCESS  not-accessible
   STATUS      current
   DESCRIPTION
      "The value of the tlsCntTreeGlobalIndex of the MANAGED OBJECT."
   ::= {er1645v2VrfRoutAlarmLevEntry 10}

er1645v2VrfRoutAlarmLevPingActive OBJECT-TYPE
   SYNTAX      Integer32
   MAX-ACCESS  read-write
   STATUS      current
   DESCRIPTION
      "Path: vrfRouter.editConf.alarmLevel.pingActive"
   ::= {er1645v2VrfRoutAlarmLevEntry 16777216}

er1645v2VrfRoutAlarmLevQMonLoss OBJECT-TYPE
   SYNTAX      Integer32
   MAX-ACCESS  read-write
   STATUS      current
   DESCRIPTION
      "Path: vrfRouter.editConf.alarmLevel.qMonLoss"
   ::= {er1645v2VrfRoutAlarmLevEntry 33554432}

er1645v2VrfRoutAlarmLevQMonDelay OBJECT-TYPE
   SYNTAX      Integer32
   MAX-ACCESS  read-write
   STATUS      current
   DESCRIPTION
      "Path: vrfRouter.editConf.alarmLevel.qMonDelay"
   ::= {er1645v2VrfRoutAlarmLevEntry 50331648}

er1645v2VrfRoutAlarmLevQMonJitter OBJECT-TYPE
   SYNTAX      Integer32
   MAX-ACCESS  read-write
   STATUS      current
   DESCRIPTION
      "Path: vrfRouter.editConf.alarmLevel.qMonJitter"
   ::= {er1645v2VrfRoutAlarmLevEntry 67108864}


er1645v2VrfRoutAccPol OBJECT IDENTIFIER ::= {er1645v2VrfRout 73}

er1645v2VrfRoutAccPolTable OBJECT-TYPE
   SYNTAX      SEQUENCE OF Er1645v2VrfRoutAccPolEntry
   MAX-ACCESS  not-accessible
   STATUS      current
   DESCRIPTION
      "trafficPolicy to be applied in the inbound direction for NAT"
   ::= {er1645v2VrfRoutAccPol 1}

er1645v2VrfRoutAccPolEntry OBJECT-TYPE
   SYNTAX      Er1645v2VrfRoutAccPolEntry
   MAX-ACCESS  not-accessible
   STATUS      current
   DESCRIPTION
      ""
   INDEX      { er1645v2VrfRoutAccPolGlobalIx }
   ::= {er1645v2VrfRoutAccPolTable 1}

Er1645v2VrfRoutAccPolEntry ::=
   SEQUENCE
      {
      er1645v2VrfRoutAccPolGlobalIx
         GlobalIndex,
      er1645v2VrfRoutAccPolValue
         DisplayString
      }

er1645v2VrfRoutAccPolGlobalIx OBJECT-TYPE
   SYNTAX      GlobalIndex
   MAX-ACCESS  not-accessible
   STATUS      current
   DESCRIPTION
      "The value of the tlsCntTreeGlobalIndex of the MANAGED OBJECT."
   ::= {er1645v2VrfRoutAccPolEntry 10}

er1645v2VrfRoutAccPolValue OBJECT-TYPE
   SYNTAX      DisplayString
   MAX-ACCESS  read-write
   STATUS      current
   DESCRIPTION
      "Path: vrfRouter.editConf.trafficPolicy"
   ::= {er1645v2VrfRoutAccPolEntry 2147483648}



sr1645v2VrfRout OBJECT IDENTIFIER ::= {r1645v2VrfRout 14}


sr1645v2VrfRoutSnmpIndex OBJECT IDENTIFIER ::= {sr1645v2VrfRout 269}

sr1645v2VrfRoutSnmpIndexTable OBJECT-TYPE
   SYNTAX      SEQUENCE OF Sr1645v2VrfRoutSnmpIndexEntry
   MAX-ACCESS  not-accessible
   STATUS      current
   DESCRIPTION
      "SNMP index assigned to this object"
   ::= {sr1645v2VrfRoutSnmpIndex 1}

sr1645v2VrfRoutSnmpIndexEntry OBJECT-TYPE
   SYNTAX      Sr1645v2VrfRoutSnmpIndexEntry
   MAX-ACCESS  not-accessible
   STATUS      current
   DESCRIPTION
      ""
   INDEX      { sr1645v2VrfRoutSnmpIndexGlobalIx }
   ::= {sr1645v2VrfRoutSnmpIndexTable 1}

Sr1645v2VrfRoutSnmpIndexEntry ::=
   SEQUENCE
      {
      sr1645v2VrfRoutSnmpIndexGlobalIx
         GlobalIndex,
      sr1645v2VrfRoutSnmpIndexValue
         Integer32
      }

sr1645v2VrfRoutSnmpIndexGlobalIx OBJECT-TYPE
   SYNTAX      GlobalIndex
   MAX-ACCESS  not-accessible
   STATUS      current
   DESCRIPTION
      "The value of the tlsCntTreeGlobalIndex of the MANAGED OBJECT."
   ::= {sr1645v2VrfRoutSnmpIndexEntry 10}

sr1645v2VrfRoutSnmpIndexValue OBJECT-TYPE
   SYNTAX      Integer32
   MAX-ACCESS  read-only
   STATUS      current
   DESCRIPTION
      "Path: vrfRouter.status.snmpIndex"
   ::= {sr1645v2VrfRoutSnmpIndexEntry 2147483648}


sr1645v2VrfRoutRoutingTable OBJECT IDENTIFIER ::= {sr1645v2VrfRout 32}

sr1645v2VrfRoutRoutingTableSSCTable OBJECT-TYPE
   SYNTAX      SEQUENCE OF Sr1645v2VrfRoutRoutingTableEntry
   MAX-ACCESS  not-accessible
   STATUS      current
   DESCRIPTION
      "routingTable"
   ::= {sr1645v2VrfRoutRoutingTable 1}

sr1645v2VrfRoutRoutingTableEntry OBJECT-TYPE
   SYNTAX      Sr1645v2VrfRoutRoutingTableEntry
   MAX-ACCESS  not-accessible
   STATUS      current
   DESCRIPTION
      ""
   INDEX      { sr1645v2VrfRoutRoutingTableGlobalIx,
                sr1645v2VrfRoutRoutingTableTableIx }
   ::= {sr1645v2VrfRoutRoutingTableSSCTable 1}

Sr1645v2VrfRoutRoutingTableEntry ::=
   SEQUENCE
      {
      sr1645v2VrfRoutRoutingTableGlobalIx
         GlobalIndex,
      sr1645v2VrfRoutRoutingTableTableIx
         TableIndex,
      sr1645v2VrfRoutRoutingTableNetwork
         IpAddress,
      sr1645v2VrfRoutRoutingTableMask
         IpAddress,
      sr1645v2VrfRoutRoutingTableGateway
         IpAddress,
      sr1645v2VrfRoutRoutingTableIf
         DisplayString,
      sr1645v2VrfRoutRoutingTableEncap
         INTEGER,
      sr1645v2VrfRoutRoutingTableStatus
         INTEGER,
      sr1645v2VrfRoutRoutingTablePref
         Integer32,
      sr1645v2VrfRoutRoutingTableType
         INTEGER,
      sr1645v2VrfRoutRoutingTableMetric
         Integer32,
      sr1645v2VrfRoutRoutingTableTimeOut
         TimeTicks,
      sr1645v2VrfRoutRoutingTableTag
         DisplayString
      }

sr1645v2VrfRoutRoutingTableGlobalIx OBJECT-TYPE
   SYNTAX      GlobalIndex
   MAX-ACCESS  not-accessible
   STATUS      current
   DESCRIPTION
      "The value of the tlsCntTreeGlobalIndex of the MANAGED OBJECT."
   ::= {sr1645v2VrfRoutRoutingTableEntry 10}

sr1645v2VrfRoutRoutingTableTableIx OBJECT-TYPE
   SYNTAX      TableIndex
   MAX-ACCESS  not-accessible
   STATUS      current
   DESCRIPTION
      ""
   ::= {sr1645v2VrfRoutRoutingTableEntry 11}

sr1645v2VrfRoutRoutingTableNetwork OBJECT-TYPE
   SYNTAX      IpAddress
   MAX-ACCESS  read-only
   STATUS      current
   DESCRIPTION
      "Path: vrfRouter.status.routingTable.network"
   ::= {sr1645v2VrfRoutRoutingTableEntry 16777216}

sr1645v2VrfRoutRoutingTableMask OBJECT-TYPE
   SYNTAX      IpAddress
   MAX-ACCESS  read-only
   STATUS      current
   DESCRIPTION
      "Path: vrfRouter.status.routingTable.mask"
   ::= {sr1645v2VrfRoutRoutingTableEntry 33554432}

sr1645v2VrfRoutRoutingTableGateway OBJECT-TYPE
   SYNTAX      IpAddress
   MAX-ACCESS  read-only
   STATUS      current
   DESCRIPTION
      "Path: vrfRouter.status.routingTable.gateway"
   ::= {sr1645v2VrfRoutRoutingTableEntry 50331648}

sr1645v2VrfRoutRoutingTableIf OBJECT-TYPE
   SYNTAX      DisplayString
   MAX-ACCESS  read-only
   STATUS      current
   DESCRIPTION
      "Path: vrfRouter.status.routingTable.interface"
   ::= {sr1645v2VrfRoutRoutingTableEntry 67108864}

sr1645v2VrfRoutRoutingTableEncap OBJECT-TYPE
   SYNTAX      INTEGER
               {
               none (0),
               framemrelay (1),
               ppp (2),
               ethernet (3),
               x25 (4),
               atm (5),
               policysdependent (6),
               pppoA (7),
               pppoE (8),
               sasdependent (9),
               gre (10)
               }
   MAX-ACCESS  read-only
   STATUS      current
   DESCRIPTION
      "Path: vrfRouter.status.routingTable.encapsulation

       Possibilities:
               none   (0)
               frame-relay   (1)
               ppp   (2)
               ethernet   (3)
               x25   (4)
               atm   (5)
               policy dependent   (6)
               pppoA   (7)
               pppoE   (8)
               sa dependent   (9)
               gre   (10)"
   ::= {sr1645v2VrfRoutRoutingTableEntry 83886080}

sr1645v2VrfRoutRoutingTableStatus OBJECT-TYPE
   SYNTAX      INTEGER
               {
               down (0),
               up (1),
               discard (2),
               spoofing (3),
               holdDown (4),
               closed (5)
               }
   MAX-ACCESS  read-only
   STATUS      current
   DESCRIPTION
      "Path: vrfRouter.status.routingTable.status

       Possibilities:
               down   (0)
               up   (1)
               discard   (2)
               spoofing   (3)
               holdDown   (4)
               closed   (5)"
   ::= {sr1645v2VrfRoutRoutingTableEntry 100663296}

sr1645v2VrfRoutRoutingTablePref OBJECT-TYPE
   SYNTAX      Integer32
   MAX-ACCESS  read-only
   STATUS      current
   DESCRIPTION
      "Path: vrfRouter.status.routingTable.preference"
   ::= {sr1645v2VrfRoutRoutingTableEntry 117440512}

sr1645v2VrfRoutRoutingTableType OBJECT-TYPE
   SYNTAX      INTEGER
               {
               internal (0),
               local (1),
               host (2),
               static (3),
               rip (4),
               ospf (5),
               bgp (6),
               float (7),
               dial (8),
               policy (9),
               nat (10),
               radius (11),
               orchid (12),
               reject (13),
               ipsec (14),
               floatIpsec (15),
               mgmtProxy (16),
               ipV6natpt (17),
               pim (18),
               none (19),
               fixedDial (20),
               fixedOutPolicy (21),
               fixedInterface (22),
               fixedIpsec (23),
               staticTimed (24),
               staticTracked (25),
               everyCat (26)
               }
   MAX-ACCESS  read-only
   STATUS      current
   DESCRIPTION
      "Path: vrfRouter.status.routingTable.type

       Possibilities:
               internal   (0)
               local   (1)
               host   (2)
               static   (3)
               rip   (4)
               ospf   (5)
               bgp   (6)
               float   (7)
               dial   (8)
               policy   (9)
               nat   (10)
               radius   (11)
               orchid   (12)
               reject   (13)
               ipsec   (14)
               floatIpsec   (15)
               mgmtProxy   (16)
               ipV6natpt   (17)
               pim   (18)
               none   (19)
               fixedDial   (20)
               fixedOutPolicy   (21)
               fixedInterface   (22)
               fixedIpsec   (23)
               staticTimed   (24)
               staticTracked   (25)
               everyCat   (26)"
   ::= {sr1645v2VrfRoutRoutingTableEntry 134217728}

sr1645v2VrfRoutRoutingTableMetric OBJECT-TYPE
   SYNTAX      Integer32
   MAX-ACCESS  read-only
   STATUS      current
   DESCRIPTION
      "Path: vrfRouter.status.routingTable.metric"
   ::= {sr1645v2VrfRoutRoutingTableEntry 150994944}

sr1645v2VrfRoutRoutingTableTimeOut OBJECT-TYPE
   SYNTAX      TimeTicks
   MAX-ACCESS  read-only
   STATUS      current
   DESCRIPTION
      "Path: vrfRouter.status.routingTable.timeOut

       Time in centi-second."
   ::= {sr1645v2VrfRoutRoutingTableEntry 167772160}

sr1645v2VrfRoutRoutingTableTag OBJECT-TYPE
   SYNTAX      DisplayString
   MAX-ACCESS  read-only
   STATUS      current
   DESCRIPTION
      "Path: vrfRouter.status.routingTable.tag"
   ::= {sr1645v2VrfRoutRoutingTableEntry 201326592}


sr1645v2VrfRoutDhcpBinding OBJECT IDENTIFIER ::= {sr1645v2VrfRout 54}

sr1645v2VrfRoutDhcpBindingSSCTable OBJECT-TYPE
   SYNTAX      SEQUENCE OF Sr1645v2VrfRoutDhcpBindingEntry
   MAX-ACCESS  not-accessible
   STATUS      current
   DESCRIPTION
      "table containing DHCP client information"
   ::= {sr1645v2VrfRoutDhcpBinding 1}

sr1645v2VrfRoutDhcpBindingEntry OBJECT-TYPE
   SYNTAX      Sr1645v2VrfRoutDhcpBindingEntry
   MAX-ACCESS  not-accessible
   STATUS      current
   DESCRIPTION
      ""
   INDEX      { sr1645v2VrfRoutDhcpBindingGlobalIx,
                sr1645v2VrfRoutDhcpBindingTableIx }
   ::= {sr1645v2VrfRoutDhcpBindingSSCTable 1}

Sr1645v2VrfRoutDhcpBindingEntry ::=
   SEQUENCE
      {
      sr1645v2VrfRoutDhcpBindingGlobalIx
         GlobalIndex,
      sr1645v2VrfRoutDhcpBindingTableIx
         TableIndex,
      sr1645v2VrfRoutDhcpBindingIpAddress
         IpAddress,
      sr1645v2VrfRoutDhcpBindingMacAddress
         OCTET STRING,
      sr1645v2VrfRoutDhcpBindingLeaseTime
         TimeTicks,
      sr1645v2VrfRoutDhcpBindingHostName
         DisplayString,
      sr1645v2VrfRoutDhcpBindingInterface
         DisplayString,
      sr1645v2VrfRoutDhcpBindingState
         INTEGER,
      sr1645v2VrfRoutDhcpBindingCheckAddress
         INTEGER
      }

sr1645v2VrfRoutDhcpBindingGlobalIx OBJECT-TYPE
   SYNTAX      GlobalIndex
   MAX-ACCESS  not-accessible
   STATUS      current
   DESCRIPTION
      "The value of the tlsCntTreeGlobalIndex of the MANAGED OBJECT."
   ::= {sr1645v2VrfRoutDhcpBindingEntry 10}

sr1645v2VrfRoutDhcpBindingTableIx OBJECT-TYPE
   SYNTAX      TableIndex
   MAX-ACCESS  not-accessible
   STATUS      current
   DESCRIPTION
      ""
   ::= {sr1645v2VrfRoutDhcpBindingEntry 11}

sr1645v2VrfRoutDhcpBindingIpAddress OBJECT-TYPE
   SYNTAX      IpAddress
   MAX-ACCESS  read-only
   STATUS      current
   DESCRIPTION
      "Path: vrfRouter.status.dhcpBinding.ipAddress"
   ::= {sr1645v2VrfRoutDhcpBindingEntry 16777216}

sr1645v2VrfRoutDhcpBindingMacAddress OBJECT-TYPE
   SYNTAX      OCTET STRING
   MAX-ACCESS  read-only
   STATUS      current
   DESCRIPTION
      "Path: vrfRouter.status.dhcpBinding.macAddress

       MAC address."
   ::= {sr1645v2VrfRoutDhcpBindingEntry 33554432}

sr1645v2VrfRoutDhcpBindingLeaseTime OBJECT-TYPE
   SYNTAX      TimeTicks
   MAX-ACCESS  read-only
   STATUS      current
   DESCRIPTION
      "Path: vrfRouter.status.dhcpBinding.leaseTime

       Time in centi-second."
   ::= {sr1645v2VrfRoutDhcpBindingEntry 50331648}

sr1645v2VrfRoutDhcpBindingHostName OBJECT-TYPE
   SYNTAX      DisplayString
   MAX-ACCESS  read-only
   STATUS      current
   DESCRIPTION
      "Path: vrfRouter.status.dhcpBinding.hostName"
   ::= {sr1645v2VrfRoutDhcpBindingEntry 67108864}

sr1645v2VrfRoutDhcpBindingInterface OBJECT-TYPE
   SYNTAX      DisplayString
   MAX-ACCESS  read-only
   STATUS      current
   DESCRIPTION
      "Path: vrfRouter.status.dhcpBinding.interface"
   ::= {sr1645v2VrfRoutDhcpBindingEntry 100663296}

sr1645v2VrfRoutDhcpBindingState OBJECT-TYPE
   SYNTAX      INTEGER
               {
               onHold (0),
               leased (1),
               reserved (2)
               }
   MAX-ACCESS  read-only
   STATUS      current
   DESCRIPTION
      "Path: vrfRouter.status.dhcpBinding.state

       Possibilities:
               onHold   (0)
               leased   (1)
               reserved   (2)"
   ::= {sr1645v2VrfRoutDhcpBindingEntry 83886080}

sr1645v2VrfRoutDhcpBindingCheckAddress OBJECT-TYPE
   SYNTAX      INTEGER
               {
               idle (0),
               pending (1),
               validated (2),
               rejected (3),
               skipped (4)
               }
   MAX-ACCESS  read-only
   STATUS      current
   DESCRIPTION
      "Path: vrfRouter.status.dhcpBinding.checkAddress

       Possibilities:
               idle   (0)
               pending   (1)
               validated   (2)
               rejected   (3)
               skipped   (4)"
   ::= {sr1645v2VrfRoutDhcpBindingEntry 117440512}


sr1645v2VrfRoutDhcpStat OBJECT IDENTIFIER ::= {sr1645v2VrfRout 55}

sr1645v2VrfRoutDhcpStatSSCTable OBJECT-TYPE
   SYNTAX      SEQUENCE OF Sr1645v2VrfRoutDhcpStatEntry
   MAX-ACCESS  not-accessible
   STATUS      current
   DESCRIPTION
      "DHCP statistics over addresses free, leased and in hold"
   ::= {sr1645v2VrfRoutDhcpStat 1}

sr1645v2VrfRoutDhcpStatEntry OBJECT-TYPE
   SYNTAX      Sr1645v2VrfRoutDhcpStatEntry
   MAX-ACCESS  not-accessible
   STATUS      current
   DESCRIPTION
      ""
   INDEX      { sr1645v2VrfRoutDhcpStatGlobalIx,
                sr1645v2VrfRoutDhcpStatTableIx }
   ::= {sr1645v2VrfRoutDhcpStatSSCTable 1}

Sr1645v2VrfRoutDhcpStatEntry ::=
   SEQUENCE
      {
      sr1645v2VrfRoutDhcpStatGlobalIx
         GlobalIndex,
      sr1645v2VrfRoutDhcpStatTableIx
         TableIndex,
      sr1645v2VrfRoutDhcpStatStartRange
         IpAddress,
      sr1645v2VrfRoutDhcpStatEndRange
         IpAddress,
      sr1645v2VrfRoutDhcpStatInterface
         DisplayString,
      sr1645v2VrfRoutDhcpStatFree
         Integer32,
      sr1645v2VrfRoutDhcpStatLeased
         Integer32,
      sr1645v2VrfRoutDhcpStatHold
         Integer32
      }

sr1645v2VrfRoutDhcpStatGlobalIx OBJECT-TYPE
   SYNTAX      GlobalIndex
   MAX-ACCESS  not-accessible
   STATUS      current
   DESCRIPTION
      "The value of the tlsCntTreeGlobalIndex of the MANAGED OBJECT."
   ::= {sr1645v2VrfRoutDhcpStatEntry 10}

sr1645v2VrfRoutDhcpStatTableIx OBJECT-TYPE
   SYNTAX      TableIndex
   MAX-ACCESS  not-accessible
   STATUS      current
   DESCRIPTION
      ""
   ::= {sr1645v2VrfRoutDhcpStatEntry 11}

sr1645v2VrfRoutDhcpStatStartRange OBJECT-TYPE
   SYNTAX      IpAddress
   MAX-ACCESS  read-only
   STATUS      current
   DESCRIPTION
      "Path: vrfRouter.status.dhcpStatistics.startRange"
   ::= {sr1645v2VrfRoutDhcpStatEntry 16777216}

sr1645v2VrfRoutDhcpStatEndRange OBJECT-TYPE
   SYNTAX      IpAddress
   MAX-ACCESS  read-only
   STATUS      current
   DESCRIPTION
      "Path: vrfRouter.status.dhcpStatistics.endRange"
   ::= {sr1645v2VrfRoutDhcpStatEntry 33554432}

sr1645v2VrfRoutDhcpStatInterface OBJECT-TYPE
   SYNTAX      DisplayString
   MAX-ACCESS  read-only
   STATUS      current
   DESCRIPTION
      "Path: vrfRouter.status.dhcpStatistics.interface"
   ::= {sr1645v2VrfRoutDhcpStatEntry 100663296}

sr1645v2VrfRoutDhcpStatFree OBJECT-TYPE
   SYNTAX      Integer32
   MAX-ACCESS  read-only
   STATUS      current
   DESCRIPTION
      "Path: vrfRouter.status.dhcpStatistics.free"
   ::= {sr1645v2VrfRoutDhcpStatEntry 50331648}

sr1645v2VrfRoutDhcpStatLeased OBJECT-TYPE
   SYNTAX      Integer32
   MAX-ACCESS  read-only
   STATUS      current
   DESCRIPTION
      "Path: vrfRouter.status.dhcpStatistics.leased"
   ::= {sr1645v2VrfRoutDhcpStatEntry 67108864}

sr1645v2VrfRoutDhcpStatHold OBJECT-TYPE
   SYNTAX      Integer32
   MAX-ACCESS  read-only
   STATUS      current
   DESCRIPTION
      "Path: vrfRouter.status.dhcpStatistics.hold"
   ::= {sr1645v2VrfRoutDhcpStatEntry 83886080}


sr1645v2VrfRoutDhcpRelay OBJECT IDENTIFIER ::= {sr1645v2VrfRout 71}

sr1645v2VrfRoutDhcpRelaySSCTable OBJECT-TYPE
   SYNTAX      SEQUENCE OF Sr1645v2VrfRoutDhcpRelayEntry
   MAX-ACCESS  not-accessible
   STATUS      current
   DESCRIPTION
      "dhcpRelayInfo"
   ::= {sr1645v2VrfRoutDhcpRelay 1}

sr1645v2VrfRoutDhcpRelayEntry OBJECT-TYPE
   SYNTAX      Sr1645v2VrfRoutDhcpRelayEntry
   MAX-ACCESS  not-accessible
   STATUS      current
   DESCRIPTION
      ""
   INDEX      { sr1645v2VrfRoutDhcpRelayGlobalIx,
                sr1645v2VrfRoutDhcpRelayTableIx }
   ::= {sr1645v2VrfRoutDhcpRelaySSCTable 1}

Sr1645v2VrfRoutDhcpRelayEntry ::=
   SEQUENCE
      {
      sr1645v2VrfRoutDhcpRelayGlobalIx
         GlobalIndex,
      sr1645v2VrfRoutDhcpRelayTableIx
         TableIndex,
      sr1645v2VrfRoutDhcpRelaySourceIntf
         DisplayString,
      sr1645v2VrfRoutDhcpRelayMac
         OCTET STRING,
      sr1645v2VrfRoutDhcpRelayAssignedIp
         IpAddress,
      sr1645v2VrfRoutDhcpRelayServerIp
         IpAddress,
      sr1645v2VrfRoutDhcpRelayDhcpStatus
         INTEGER,
      sr1645v2VrfRoutDhcpRelayLeaseTime
         TimeTicks
      }

sr1645v2VrfRoutDhcpRelayGlobalIx OBJECT-TYPE
   SYNTAX      GlobalIndex
   MAX-ACCESS  not-accessible
   STATUS      current
   DESCRIPTION
      "The value of the tlsCntTreeGlobalIndex of the MANAGED OBJECT."
   ::= {sr1645v2VrfRoutDhcpRelayEntry 10}

sr1645v2VrfRoutDhcpRelayTableIx OBJECT-TYPE
   SYNTAX      TableIndex
   MAX-ACCESS  not-accessible
   STATUS      current
   DESCRIPTION
      ""
   ::= {sr1645v2VrfRoutDhcpRelayEntry 11}

sr1645v2VrfRoutDhcpRelaySourceIntf OBJECT-TYPE
   SYNTAX      DisplayString
   MAX-ACCESS  read-only
   STATUS      current
   DESCRIPTION
      "Path: vrfRouter.status.dhcpRelayInfo.sourceIntf"
   ::= {sr1645v2VrfRoutDhcpRelayEntry 16777216}

sr1645v2VrfRoutDhcpRelayMac OBJECT-TYPE
   SYNTAX      OCTET STRING
   MAX-ACCESS  read-only
   STATUS      current
   DESCRIPTION
      "Path: vrfRouter.status.dhcpRelayInfo.mac

       MAC address."
   ::= {sr1645v2VrfRoutDhcpRelayEntry 33554432}

sr1645v2VrfRoutDhcpRelayAssignedIp OBJECT-TYPE
   SYNTAX      IpAddress
   MAX-ACCESS  read-only
   STATUS      current
   DESCRIPTION
      "Path: vrfRouter.status.dhcpRelayInfo.assignedIp"
   ::= {sr1645v2VrfRoutDhcpRelayEntry 50331648}

sr1645v2VrfRoutDhcpRelayServerIp OBJECT-TYPE
   SYNTAX      IpAddress
   MAX-ACCESS  read-only
   STATUS      current
   DESCRIPTION
      "Path: vrfRouter.status.dhcpRelayInfo.serverIp"
   ::= {sr1645v2VrfRoutDhcpRelayEntry 67108864}

sr1645v2VrfRoutDhcpRelayDhcpStatus OBJECT-TYPE
   SYNTAX      INTEGER
               {
               discover (1),
               offer (2),
               request (3),
               decline (4),
               ack (5),
               nak (6),
               release (7),
               inform (8),
               idle (9)
               }
   MAX-ACCESS  read-only
   STATUS      current
   DESCRIPTION
      "Path: vrfRouter.status.dhcpRelayInfo.dhcpStatus

       Possibilities:
               discover   (1)
               offer   (2)
               request   (3)
               decline   (4)
               ack   (5)
               nak   (6)
               release   (7)
               inform   (8)
               idle   (9)"
   ::= {sr1645v2VrfRoutDhcpRelayEntry 83886080}

sr1645v2VrfRoutDhcpRelayLeaseTime OBJECT-TYPE
   SYNTAX      TimeTicks
   MAX-ACCESS  read-only
   STATUS      current
   DESCRIPTION
      "Path: vrfRouter.status.dhcpRelayInfo.leaseTime

       Time in centi-second."
   ::= {sr1645v2VrfRoutDhcpRelayEntry 117440512}


sr1645v2VrfRoutDhcpBlacklist OBJECT IDENTIFIER ::= {sr1645v2VrfRout 75}

sr1645v2VrfRoutDhcpBlacklistSSCTable OBJECT-TYPE
   SYNTAX      SEQUENCE OF Sr1645v2VrfRoutDhcpBlacklistEntry
   MAX-ACCESS  not-accessible
   STATUS      current
   DESCRIPTION
      "table containing DHCP Blacklist information"
   ::= {sr1645v2VrfRoutDhcpBlacklist 1}

sr1645v2VrfRoutDhcpBlacklistEntry OBJECT-TYPE
   SYNTAX      Sr1645v2VrfRoutDhcpBlacklistEntry
   MAX-ACCESS  not-accessible
   STATUS      current
   DESCRIPTION
      ""
   INDEX      { sr1645v2VrfRoutDhcpBlacklistGlobalIx,
                sr1645v2VrfRoutDhcpBlacklistTableIx }
   ::= {sr1645v2VrfRoutDhcpBlacklistSSCTable 1}

Sr1645v2VrfRoutDhcpBlacklistEntry ::=
   SEQUENCE
      {
      sr1645v2VrfRoutDhcpBlacklistGlobalIx
         GlobalIndex,
      sr1645v2VrfRoutDhcpBlacklistTableIx
         TableIndex,
      sr1645v2VrfRoutDhcpBlacklistIpAddress
         IpAddress,
      sr1645v2VrfRoutDhcpBlacklistMacAddress
         OCTET STRING,
      sr1645v2VrfRoutDhcpBlacklistReason
         INTEGER
      }

sr1645v2VrfRoutDhcpBlacklistGlobalIx OBJECT-TYPE
   SYNTAX      GlobalIndex
   MAX-ACCESS  not-accessible
   STATUS      current
   DESCRIPTION
      "The value of the tlsCntTreeGlobalIndex of the MANAGED OBJECT."
   ::= {sr1645v2VrfRoutDhcpBlacklistEntry 10}

sr1645v2VrfRoutDhcpBlacklistTableIx OBJECT-TYPE
   SYNTAX      TableIndex
   MAX-ACCESS  not-accessible
   STATUS      current
   DESCRIPTION
      ""
   ::= {sr1645v2VrfRoutDhcpBlacklistEntry 11}

sr1645v2VrfRoutDhcpBlacklistIpAddress OBJECT-TYPE
   SYNTAX      IpAddress
   MAX-ACCESS  read-only
   STATUS      current
   DESCRIPTION
      "Path: vrfRouter.status.dhcpBlacklist.ipAddress"
   ::= {sr1645v2VrfRoutDhcpBlacklistEntry 16777216}

sr1645v2VrfRoutDhcpBlacklistMacAddress OBJECT-TYPE
   SYNTAX      OCTET STRING
   MAX-ACCESS  read-only
   STATUS      current
   DESCRIPTION
      "Path: vrfRouter.status.dhcpBlacklist.macAddress

       MAC address."
   ::= {sr1645v2VrfRoutDhcpBlacklistEntry 33554432}

sr1645v2VrfRoutDhcpBlacklistReason OBJECT-TYPE
   SYNTAX      INTEGER
               {
               none (0),
               arp (1),
               alienAck (2),
               declined (3),
               ping (4),
               networkOrBroadcast (5)
               }
   MAX-ACCESS  read-only
   STATUS      current
   DESCRIPTION
      "Path: vrfRouter.status.dhcpBlacklist.reason

       Possibilities:
               none   (0)
               arp   (1)
               alienAck   (2)
               declined   (3)
               ping   (4)
               networkOrBroadcast   (5)"
   ::= {sr1645v2VrfRoutDhcpBlacklistEntry 50331648}


sr1645v2VrfRoutAddrPools OBJECT IDENTIFIER ::= {sr1645v2VrfRout 109}

sr1645v2VrfRoutAddrPoolsSSCTable OBJECT-TYPE
   SYNTAX      SEQUENCE OF Sr1645v2VrfRoutAddrPoolsEntry
   MAX-ACCESS  not-accessible
   STATUS      current
   DESCRIPTION
      "ip pool status"
   ::= {sr1645v2VrfRoutAddrPools 1}

sr1645v2VrfRoutAddrPoolsEntry OBJECT-TYPE
   SYNTAX      Sr1645v2VrfRoutAddrPoolsEntry
   MAX-ACCESS  not-accessible
   STATUS      current
   DESCRIPTION
      ""
   INDEX      { sr1645v2VrfRoutAddrPoolsGlobalIx,
                sr1645v2VrfRoutAddrPoolsTableIx }
   ::= {sr1645v2VrfRoutAddrPoolsSSCTable 1}

Sr1645v2VrfRoutAddrPoolsEntry ::=
   SEQUENCE
      {
      sr1645v2VrfRoutAddrPoolsGlobalIx
         GlobalIndex,
      sr1645v2VrfRoutAddrPoolsTableIx
         TableIndex,
      sr1645v2VrfRoutAddrPoolsName
         DisplayString,
      sr1645v2VrfRoutAddrPoolsType
         INTEGER,
      sr1645v2VrfRoutAddrPoolsNrOfAddresses
         Counter32,
      sr1645v2VrfRoutAddrPoolsAvailAddresses
         Counter32
      }

sr1645v2VrfRoutAddrPoolsGlobalIx OBJECT-TYPE
   SYNTAX      GlobalIndex
   MAX-ACCESS  not-accessible
   STATUS      current
   DESCRIPTION
      "The value of the tlsCntTreeGlobalIndex of the MANAGED OBJECT."
   ::= {sr1645v2VrfRoutAddrPoolsEntry 10}

sr1645v2VrfRoutAddrPoolsTableIx OBJECT-TYPE
   SYNTAX      TableIndex
   MAX-ACCESS  not-accessible
   STATUS      current
   DESCRIPTION
      ""
   ::= {sr1645v2VrfRoutAddrPoolsEntry 11}

sr1645v2VrfRoutAddrPoolsName OBJECT-TYPE
   SYNTAX      DisplayString
   MAX-ACCESS  read-only
   STATUS      current
   DESCRIPTION
      "Path: vrfRouter.status.addrPools.name"
   ::= {sr1645v2VrfRoutAddrPoolsEntry 16777216}

sr1645v2VrfRoutAddrPoolsType OBJECT-TYPE
   SYNTAX      INTEGER
               {
               list (1),
               interval (2)
               }
   MAX-ACCESS  read-only
   STATUS      current
   DESCRIPTION
      "Path: vrfRouter.status.addrPools.type

       Possibilities:
               list   (1)
               interval   (2)"
   ::= {sr1645v2VrfRoutAddrPoolsEntry 33554432}

sr1645v2VrfRoutAddrPoolsNrOfAddresses OBJECT-TYPE
   SYNTAX      Counter32
   MAX-ACCESS  read-only
   STATUS      current
   DESCRIPTION
      "Path: vrfRouter.status.addrPools.nrOfAddresses

       32 bit unsigned wrappable counter."
   ::= {sr1645v2VrfRoutAddrPoolsEntry 50331648}

sr1645v2VrfRoutAddrPoolsAvailAddresses OBJECT-TYPE
   SYNTAX      Counter32
   MAX-ACCESS  read-only
   STATUS      current
   DESCRIPTION
      "Path: vrfRouter.status.addrPools.availAddresses

       32 bit unsigned wrappable counter."
   ::= {sr1645v2VrfRoutAddrPoolsEntry 67108864}


sr1645v2VrfRoutPoolReservations OBJECT IDENTIFIER ::= {sr1645v2VrfRout 103}

sr1645v2VrfRoutPoolReservationsSSCTable OBJECT-TYPE
   SYNTAX      SEQUENCE OF Sr1645v2VrfRoutPoolReservationsEntry
   MAX-ACCESS  not-accessible
   STATUS      current
   DESCRIPTION
      "ip pool occupied addresses"
   ::= {sr1645v2VrfRoutPoolReservations 1}

sr1645v2VrfRoutPoolReservationsEntry OBJECT-TYPE
   SYNTAX      Sr1645v2VrfRoutPoolReservationsEntry
   MAX-ACCESS  not-accessible
   STATUS      current
   DESCRIPTION
      ""
   INDEX      { sr1645v2VrfRoutPoolReservationsGlobalIx,
                sr1645v2VrfRoutPoolReservationsTableIx }
   ::= {sr1645v2VrfRoutPoolReservationsSSCTable 1}

Sr1645v2VrfRoutPoolReservationsEntry ::=
   SEQUENCE
      {
      sr1645v2VrfRoutPoolReservationsGlobalIx
         GlobalIndex,
      sr1645v2VrfRoutPoolReservationsTableIx
         TableIndex,
      sr1645v2VrfRoutPoolReservationsName
         DisplayString,
      sr1645v2VrfRoutPoolReservationsType
         INTEGER,
      sr1645v2VrfRoutPoolReservationsLocal
         IpAddress,
      sr1645v2VrfRoutPoolReservationsRemote
         IpAddress,
      sr1645v2VrfRoutPoolReservationsNetMask
         IpAddress,
      sr1645v2VrfRoutPoolReservationsInterface
         DisplayString
      }

sr1645v2VrfRoutPoolReservationsGlobalIx OBJECT-TYPE
   SYNTAX      GlobalIndex
   MAX-ACCESS  not-accessible
   STATUS      current
   DESCRIPTION
      "The value of the tlsCntTreeGlobalIndex of the MANAGED OBJECT."
   ::= {sr1645v2VrfRoutPoolReservationsEntry 10}

sr1645v2VrfRoutPoolReservationsTableIx OBJECT-TYPE
   SYNTAX      TableIndex
   MAX-ACCESS  not-accessible
   STATUS      current
   DESCRIPTION
      ""
   ::= {sr1645v2VrfRoutPoolReservationsEntry 11}

sr1645v2VrfRoutPoolReservationsName OBJECT-TYPE
   SYNTAX      DisplayString
   MAX-ACCESS  read-only
   STATUS      current
   DESCRIPTION
      "Path: vrfRouter.status.poolReservations.name"
   ::= {sr1645v2VrfRoutPoolReservationsEntry 16777216}

sr1645v2VrfRoutPoolReservationsType OBJECT-TYPE
   SYNTAX      INTEGER
               {
               list (1),
               interval (2)
               }
   MAX-ACCESS  read-only
   STATUS      current
   DESCRIPTION
      "Path: vrfRouter.status.poolReservations.type

       Possibilities:
               list   (1)
               interval   (2)"
   ::= {sr1645v2VrfRoutPoolReservationsEntry 33554432}

sr1645v2VrfRoutPoolReservationsLocal OBJECT-TYPE
   SYNTAX      IpAddress
   MAX-ACCESS  read-only
   STATUS      current
   DESCRIPTION
      "Path: vrfRouter.status.poolReservations.local"
   ::= {sr1645v2VrfRoutPoolReservationsEntry 50331648}

sr1645v2VrfRoutPoolReservationsRemote OBJECT-TYPE
   SYNTAX      IpAddress
   MAX-ACCESS  read-only
   STATUS      current
   DESCRIPTION
      "Path: vrfRouter.status.poolReservations.remote"
   ::= {sr1645v2VrfRoutPoolReservationsEntry 67108864}

sr1645v2VrfRoutPoolReservationsNetMask OBJECT-TYPE
   SYNTAX      IpAddress
   MAX-ACCESS  read-only
   STATUS      current
   DESCRIPTION
      "Path: vrfRouter.status.poolReservations.netMask"
   ::= {sr1645v2VrfRoutPoolReservationsEntry 83886080}

sr1645v2VrfRoutPoolReservationsInterface OBJECT-TYPE
   SYNTAX      DisplayString
   MAX-ACCESS  read-only
   STATUS      current
   DESCRIPTION
      "Path: vrfRouter.status.poolReservations.interface"
   ::= {sr1645v2VrfRoutPoolReservationsEntry 100663296}


sr1645v2VrfRoutDnsCache OBJECT IDENTIFIER ::= {sr1645v2VrfRout 65}

sr1645v2VrfRoutDnsCacheSSCTable OBJECT-TYPE
   SYNTAX      SEQUENCE OF Sr1645v2VrfRoutDnsCacheEntry
   MAX-ACCESS  not-accessible
   STATUS      current
   DESCRIPTION
      "DNS cache table"
   ::= {sr1645v2VrfRoutDnsCache 1}

sr1645v2VrfRoutDnsCacheEntry OBJECT-TYPE
   SYNTAX      Sr1645v2VrfRoutDnsCacheEntry
   MAX-ACCESS  not-accessible
   STATUS      current
   DESCRIPTION
      ""
   INDEX      { sr1645v2VrfRoutDnsCacheGlobalIx,
                sr1645v2VrfRoutDnsCacheTableIx }
   ::= {sr1645v2VrfRoutDnsCacheSSCTable 1}

Sr1645v2VrfRoutDnsCacheEntry ::=
   SEQUENCE
      {
      sr1645v2VrfRoutDnsCacheGlobalIx
         GlobalIndex,
      sr1645v2VrfRoutDnsCacheTableIx
         TableIndex,
      sr1645v2VrfRoutDnsCacheIpAddress
         IpAddress,
      sr1645v2VrfRoutDnsCacheIpV6Address
         Ipv6Address,
      sr1645v2VrfRoutDnsCacheHostname
         DisplayString,
      sr1645v2VrfRoutDnsCacheTtl
         TimeTicks,
      sr1645v2VrfRoutDnsCacheInfiniteTimeOut
         INTEGER,
      sr1645v2VrfRoutDnsCacheMatches
         Counter32
      }

sr1645v2VrfRoutDnsCacheGlobalIx OBJECT-TYPE
   SYNTAX      GlobalIndex
   MAX-ACCESS  not-accessible
   STATUS      current
   DESCRIPTION
      "The value of the tlsCntTreeGlobalIndex of the MANAGED OBJECT."
   ::= {sr1645v2VrfRoutDnsCacheEntry 10}

sr1645v2VrfRoutDnsCacheTableIx OBJECT-TYPE
   SYNTAX      TableIndex
   MAX-ACCESS  not-accessible
   STATUS      current
   DESCRIPTION
      ""
   ::= {sr1645v2VrfRoutDnsCacheEntry 11}

sr1645v2VrfRoutDnsCacheIpAddress OBJECT-TYPE
   SYNTAX      IpAddress
   MAX-ACCESS  read-only
   STATUS      current
   DESCRIPTION
      "Path: vrfRouter.status.dnsCache.ipAddress"
   ::= {sr1645v2VrfRoutDnsCacheEntry 16777216}

sr1645v2VrfRoutDnsCacheIpV6Address OBJECT-TYPE
   SYNTAX      Ipv6Address
   MAX-ACCESS  read-only
   STATUS      current
   DESCRIPTION
      "Path: vrfRouter.status.dnsCache.ipV6Address

       ipv6 address"
   ::= {sr1645v2VrfRoutDnsCacheEntry 83886080}

sr1645v2VrfRoutDnsCacheHostname OBJECT-TYPE
   SYNTAX      DisplayString
   MAX-ACCESS  read-only
   STATUS      current
   DESCRIPTION
      "Path: vrfRouter.status.dnsCache.hostname"
   ::= {sr1645v2VrfRoutDnsCacheEntry 33554432}

sr1645v2VrfRoutDnsCacheTtl OBJECT-TYPE
   SYNTAX      TimeTicks
   MAX-ACCESS  read-only
   STATUS      current
   DESCRIPTION
      "Path: vrfRouter.status.dnsCache.ttl

       Time in centi-second."
   ::= {sr1645v2VrfRoutDnsCacheEntry 50331648}

sr1645v2VrfRoutDnsCacheInfiniteTimeOut OBJECT-TYPE
   SYNTAX      INTEGER
               {
               disabled (0),
               enabled (1),
               static (2)
               }
   MAX-ACCESS  read-only
   STATUS      current
   DESCRIPTION
      "Path: vrfRouter.status.dnsCache.infiniteTimeOut

       Possibilities:
               disabled   (0)
               enabled   (1)
               static   (2)"
   ::= {sr1645v2VrfRoutDnsCacheEntry 67108864}

sr1645v2VrfRoutDnsCacheMatches OBJECT-TYPE
   SYNTAX      Counter32
   MAX-ACCESS  read-only
   STATUS      current
   DESCRIPTION
      "Path: vrfRouter.status.dnsCache.matches

       32 bit unsigned wrappable counter."
   ::= {sr1645v2VrfRoutDnsCacheEntry 100663296}


sr1645v2VrfRoutDnsServers OBJECT IDENTIFIER ::= {sr1645v2VrfRout 66}

sr1645v2VrfRoutDnsServersSSCTable OBJECT-TYPE
   SYNTAX      SEQUENCE OF Sr1645v2VrfRoutDnsServersEntry
   MAX-ACCESS  not-accessible
   STATUS      current
   DESCRIPTION
      "DNS server list"
   ::= {sr1645v2VrfRoutDnsServers 1}

sr1645v2VrfRoutDnsServersEntry OBJECT-TYPE
   SYNTAX      Sr1645v2VrfRoutDnsServersEntry
   MAX-ACCESS  not-accessible
   STATUS      current
   DESCRIPTION
      ""
   INDEX      { sr1645v2VrfRoutDnsServersGlobalIx,
                sr1645v2VrfRoutDnsServersTableIx }
   ::= {sr1645v2VrfRoutDnsServersSSCTable 1}

Sr1645v2VrfRoutDnsServersEntry ::=
   SEQUENCE
      {
      sr1645v2VrfRoutDnsServersGlobalIx
         GlobalIndex,
      sr1645v2VrfRoutDnsServersTableIx
         TableIndex,
      sr1645v2VrfRoutDnsServersPrimaryDns
         IpAddress,
      sr1645v2VrfRoutDnsServersSecondaryDns
         IpAddress,
      sr1645v2VrfRoutDnsServersType
         INTEGER,
      sr1645v2VrfRoutDnsServersRcvdInterface
         DisplayString,
      sr1645v2VrfRoutDnsServersPreference
         Integer32,
      sr1645v2VrfRoutDnsServersStatus
         INTEGER
      }

sr1645v2VrfRoutDnsServersGlobalIx OBJECT-TYPE
   SYNTAX      GlobalIndex
   MAX-ACCESS  not-accessible
   STATUS      current
   DESCRIPTION
      "The value of the tlsCntTreeGlobalIndex of the MANAGED OBJECT."
   ::= {sr1645v2VrfRoutDnsServersEntry 10}

sr1645v2VrfRoutDnsServersTableIx OBJECT-TYPE
   SYNTAX      TableIndex
   MAX-ACCESS  not-accessible
   STATUS      current
   DESCRIPTION
      ""
   ::= {sr1645v2VrfRoutDnsServersEntry 11}

sr1645v2VrfRoutDnsServersPrimaryDns OBJECT-TYPE
   SYNTAX      IpAddress
   MAX-ACCESS  read-only
   STATUS      current
   DESCRIPTION
      "Path: vrfRouter.status.dnsServers.primaryDns"
   ::= {sr1645v2VrfRoutDnsServersEntry 16777216}

sr1645v2VrfRoutDnsServersSecondaryDns OBJECT-TYPE
   SYNTAX      IpAddress
   MAX-ACCESS  read-only
   STATUS      current
   DESCRIPTION
      "Path: vrfRouter.status.dnsServers.secondaryDns"
   ::= {sr1645v2VrfRoutDnsServersEntry 33554432}

sr1645v2VrfRoutDnsServersType OBJECT-TYPE
   SYNTAX      INTEGER
               {
               static (0),
               dhcp (1),
               ppp (2)
               }
   MAX-ACCESS  read-only
   STATUS      current
   DESCRIPTION
      "Path: vrfRouter.status.dnsServers.type

       Possibilities:
               static   (0)
               dhcp   (1)
               ppp   (2)"
   ::= {sr1645v2VrfRoutDnsServersEntry 50331648}

sr1645v2VrfRoutDnsServersRcvdInterface OBJECT-TYPE
   SYNTAX      DisplayString
   MAX-ACCESS  read-only
   STATUS      current
   DESCRIPTION
      "Path: vrfRouter.status.dnsServers.rcvdInterface"
   ::= {sr1645v2VrfRoutDnsServersEntry 67108864}

sr1645v2VrfRoutDnsServersPreference OBJECT-TYPE
   SYNTAX      Integer32
   MAX-ACCESS  read-only
   STATUS      current
   DESCRIPTION
      "Path: vrfRouter.status.dnsServers.preference"
   ::= {sr1645v2VrfRoutDnsServersEntry 83886080}

sr1645v2VrfRoutDnsServersStatus OBJECT-TYPE
   SYNTAX      INTEGER
               {
               primActive (2),
               secActive (3),
               inactive (5),
               failed (6)
               }
   MAX-ACCESS  read-only
   STATUS      current
   DESCRIPTION
      "Path: vrfRouter.status.dnsServers.status

       Possibilities:
               primActive   (2)
               secActive   (3)
               inactive   (5)
               failed   (6)"
   ::= {sr1645v2VrfRoutDnsServersEntry 100663296}


sr1645v2VrfRoutDnsDomains OBJECT IDENTIFIER ::= {sr1645v2VrfRout 72}

sr1645v2VrfRoutDnsDomainsSSCTable OBJECT-TYPE
   SYNTAX      SEQUENCE OF Sr1645v2VrfRoutDnsDomainsEntry
   MAX-ACCESS  not-accessible
   STATUS      current
   DESCRIPTION
      "DNS domain table"
   ::= {sr1645v2VrfRoutDnsDomains 1}

sr1645v2VrfRoutDnsDomainsEntry OBJECT-TYPE
   SYNTAX      Sr1645v2VrfRoutDnsDomainsEntry
   MAX-ACCESS  not-accessible
   STATUS      current
   DESCRIPTION
      ""
   INDEX      { sr1645v2VrfRoutDnsDomainsGlobalIx,
                sr1645v2VrfRoutDnsDomainsTableIx }
   ::= {sr1645v2VrfRoutDnsDomainsSSCTable 1}

Sr1645v2VrfRoutDnsDomainsEntry ::=
   SEQUENCE
      {
      sr1645v2VrfRoutDnsDomainsGlobalIx
         GlobalIndex,
      sr1645v2VrfRoutDnsDomainsTableIx
         TableIndex,
      sr1645v2VrfRoutDnsDomainsName
         DisplayString,
      sr1645v2VrfRoutDnsDomainsType
         INTEGER,
      sr1645v2VrfRoutDnsDomainsRcvdInterface
         DisplayString
      }

sr1645v2VrfRoutDnsDomainsGlobalIx OBJECT-TYPE
   SYNTAX      GlobalIndex
   MAX-ACCESS  not-accessible
   STATUS      current
   DESCRIPTION
      "The value of the tlsCntTreeGlobalIndex of the MANAGED OBJECT."
   ::= {sr1645v2VrfRoutDnsDomainsEntry 10}

sr1645v2VrfRoutDnsDomainsTableIx OBJECT-TYPE
   SYNTAX      TableIndex
   MAX-ACCESS  not-accessible
   STATUS      current
   DESCRIPTION
      ""
   ::= {sr1645v2VrfRoutDnsDomainsEntry 11}

sr1645v2VrfRoutDnsDomainsName OBJECT-TYPE
   SYNTAX      DisplayString
   MAX-ACCESS  read-only
   STATUS      current
   DESCRIPTION
      "Path: vrfRouter.status.dnsDomains.name"
   ::= {sr1645v2VrfRoutDnsDomainsEntry 16777216}

sr1645v2VrfRoutDnsDomainsType OBJECT-TYPE
   SYNTAX      INTEGER
               {
               static (0),
               dhcp (1),
               ppp (2)
               }
   MAX-ACCESS  read-only
   STATUS      current
   DESCRIPTION
      "Path: vrfRouter.status.dnsDomains.type

       Possibilities:
               static   (0)
               dhcp   (1)
               ppp   (2)"
   ::= {sr1645v2VrfRoutDnsDomainsEntry 33554432}

sr1645v2VrfRoutDnsDomainsRcvdInterface OBJECT-TYPE
   SYNTAX      DisplayString
   MAX-ACCESS  read-only
   STATUS      current
   DESCRIPTION
      "Path: vrfRouter.status.dnsDomains.rcvdInterface"
   ::= {sr1645v2VrfRoutDnsDomainsEntry 50331648}


sr1645v2VrfRoutIgmpTable OBJECT IDENTIFIER ::= {sr1645v2VrfRout 58}

sr1645v2VrfRoutIgmpTableSSCTable OBJECT-TYPE
   SYNTAX      SEQUENCE OF Sr1645v2VrfRoutIgmpTableEntry
   MAX-ACCESS  not-accessible
   STATUS      current
   DESCRIPTION
      "igmpTable"
   ::= {sr1645v2VrfRoutIgmpTable 1}

sr1645v2VrfRoutIgmpTableEntry OBJECT-TYPE
   SYNTAX      Sr1645v2VrfRoutIgmpTableEntry
   MAX-ACCESS  not-accessible
   STATUS      current
   DESCRIPTION
      ""
   INDEX      { sr1645v2VrfRoutIgmpTableGlobalIx,
                sr1645v2VrfRoutIgmpTableTableIx }
   ::= {sr1645v2VrfRoutIgmpTableSSCTable 1}

Sr1645v2VrfRoutIgmpTableEntry ::=
   SEQUENCE
      {
      sr1645v2VrfRoutIgmpTableGlobalIx
         GlobalIndex,
      sr1645v2VrfRoutIgmpTableTableIx
         TableIndex,
      sr1645v2VrfRoutIgmpTableMulticast
         IpAddress,
      sr1645v2VrfRoutIgmpTableMembers
         Integer32,
      sr1645v2VrfRoutIgmpTableIf
         DisplayString,
      sr1645v2VrfRoutIgmpTableSourceRecordType
         INTEGER
      }

sr1645v2VrfRoutIgmpTableGlobalIx OBJECT-TYPE
   SYNTAX      GlobalIndex
   MAX-ACCESS  not-accessible
   STATUS      current
   DESCRIPTION
      "The value of the tlsCntTreeGlobalIndex of the MANAGED OBJECT."
   ::= {sr1645v2VrfRoutIgmpTableEntry 10}

sr1645v2VrfRoutIgmpTableTableIx OBJECT-TYPE
   SYNTAX      TableIndex
   MAX-ACCESS  not-accessible
   STATUS      current
   DESCRIPTION
      ""
   ::= {sr1645v2VrfRoutIgmpTableEntry 11}

sr1645v2VrfRoutIgmpTableMulticast OBJECT-TYPE
   SYNTAX      IpAddress
   MAX-ACCESS  read-only
   STATUS      current
   DESCRIPTION
      "Path: vrfRouter.status.igmpTable.multicast"
   ::= {sr1645v2VrfRoutIgmpTableEntry 16777216}

sr1645v2VrfRoutIgmpTableMembers OBJECT-TYPE
   SYNTAX      Integer32
   MAX-ACCESS  read-only
   STATUS      current
   DESCRIPTION
      "Path: vrfRouter.status.igmpTable.members"
   ::= {sr1645v2VrfRoutIgmpTableEntry 50331648}

sr1645v2VrfRoutIgmpTableIf OBJECT-TYPE
   SYNTAX      DisplayString
   MAX-ACCESS  read-only
   STATUS      current
   DESCRIPTION
      "Path: vrfRouter.status.igmpTable.interface"
   ::= {sr1645v2VrfRoutIgmpTableEntry 33554432}

sr1645v2VrfRoutIgmpTableSourceRecordType OBJECT-TYPE
   SYNTAX      INTEGER
               {
               exclude (1),
               include (0)
               }
   MAX-ACCESS  read-only
   STATUS      current
   DESCRIPTION
      "Path: vrfRouter.status.igmpTable.sourceRecordType

       Possibilities:
               exclude   (1)
               include   (0)"
   ::= {sr1645v2VrfRoutIgmpTableEntry 83886080}

sr1645v2VrfRoutIgmpTableSourceRecord OBJECT-TYPE
   SYNTAX      SEQUENCE OF Sr1645v2VrfRoutIgmpTableSourceRecordEntry
   MAX-ACCESS  not-accessible
   STATUS      current
   DESCRIPTION
      ""
   ::= {sr1645v2VrfRoutIgmpTable 67108864}

sr1645v2VrfRoutIgmpTableSourceRecordEntry OBJECT-TYPE
   SYNTAX      Sr1645v2VrfRoutIgmpTableSourceRecordEntry
   MAX-ACCESS  not-accessible
   STATUS      current
   DESCRIPTION
      ""
   INDEX      { sr1645v2VrfRoutIgmpTableSourceRecordGlobalIx,
                sr1645v2VrfRoutIgmpTableTableIx,
                sr1645v2VrfRoutIgmpTableSourceRecordTableIx }
   ::= {sr1645v2VrfRoutIgmpTableSourceRecord 1}

Sr1645v2VrfRoutIgmpTableSourceRecordEntry ::=
   SEQUENCE
      {
      sr1645v2VrfRoutIgmpTableSourceRecordGlobalIx
         GlobalIndex,
      sr1645v2VrfRoutIgmpTableSourceRecordTableIx
         TableIndex,
      sr1645v2VrfRoutIgmpTableSourceRecordIpAddress
         IpAddress
      }

sr1645v2VrfRoutIgmpTableSourceRecordGlobalIx OBJECT-TYPE
   SYNTAX      GlobalIndex
   MAX-ACCESS  not-accessible
   STATUS      current
   DESCRIPTION
      "The value of the tlsCntTreeGlobalIndex of the MANAGED OBJECT."
   ::= {sr1645v2VrfRoutIgmpTableSourceRecordEntry 10}

sr1645v2VrfRoutIgmpTableSourceRecordTableIx OBJECT-TYPE
   SYNTAX      TableIndex
   MAX-ACCESS  not-accessible
   STATUS      current
   DESCRIPTION
      ""
   ::= {sr1645v2VrfRoutIgmpTableSourceRecordEntry 11}

sr1645v2VrfRoutIgmpTableSourceRecordIpAddress OBJECT-TYPE
   SYNTAX      IpAddress
   MAX-ACCESS  read-only
   STATUS      current
   DESCRIPTION
      "Path: vrfRouter.status.igmpTable.sourceRecord.ipAddress"
   ::= {sr1645v2VrfRoutIgmpTableSourceRecordEntry 16777216}


sr1645v2VrfRoutInterfaces OBJECT IDENTIFIER ::= {sr1645v2VrfRout 199}

sr1645v2VrfRoutInterfacesSSCTable OBJECT-TYPE
   SYNTAX      SEQUENCE OF Sr1645v2VrfRoutInterfacesEntry
   MAX-ACCESS  not-accessible
   STATUS      current
   DESCRIPTION
      "info on routing interfaces"
   ::= {sr1645v2VrfRoutInterfaces 1}

sr1645v2VrfRoutInterfacesEntry OBJECT-TYPE
   SYNTAX      Sr1645v2VrfRoutInterfacesEntry
   MAX-ACCESS  not-accessible
   STATUS      current
   DESCRIPTION
      ""
   INDEX      { sr1645v2VrfRoutInterfacesGlobalIx,
                sr1645v2VrfRoutInterfacesTableIx }
   ::= {sr1645v2VrfRoutInterfacesSSCTable 1}

Sr1645v2VrfRoutInterfacesEntry ::=
   SEQUENCE
      {
      sr1645v2VrfRoutInterfacesGlobalIx
         GlobalIndex,
      sr1645v2VrfRoutInterfacesTableIx
         TableIndex,
      sr1645v2VrfRoutInterfacesIfDescr
         DisplayString,
      sr1645v2VrfRoutInterfacesIfType
         INTEGER,
      sr1645v2VrfRoutInterfacesIfOperStatus
         INTEGER,
      sr1645v2VrfRoutInterfacesIfLastChange
         TimeTicks,
      sr1645v2VrfRoutInterfacesIfLastChangeDate
         DisplayString,
      sr1645v2VrfRoutInterfacesAddress
         IpAddress,
      sr1645v2VrfRoutInterfacesMask
         IpAddress
      }

sr1645v2VrfRoutInterfacesGlobalIx OBJECT-TYPE
   SYNTAX      GlobalIndex
   MAX-ACCESS  not-accessible
   STATUS      current
   DESCRIPTION
      "The value of the tlsCntTreeGlobalIndex of the MANAGED OBJECT."
   ::= {sr1645v2VrfRoutInterfacesEntry 10}

sr1645v2VrfRoutInterfacesTableIx OBJECT-TYPE
   SYNTAX      TableIndex
   MAX-ACCESS  not-accessible
   STATUS      current
   DESCRIPTION
      ""
   ::= {sr1645v2VrfRoutInterfacesEntry 11}

sr1645v2VrfRoutInterfacesIfDescr OBJECT-TYPE
   SYNTAX      DisplayString
   MAX-ACCESS  read-only
   STATUS      current
   DESCRIPTION
      "Path: vrfRouter.status.interfaces.ifDescr"
   ::= {sr1645v2VrfRoutInterfacesEntry 1694498816}

sr1645v2VrfRoutInterfacesIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: vrfRouter.status.interfaces.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2VrfRoutInterfacesEntry 1711276032}

sr1645v2VrfRoutInterfacesIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vrfRouter.status.interfaces.ifOperStatus

       Possibilities:
               up   (1)
               down   (2)
               testing   (3)
               unknown   (4)
               dormant   (5)
               notPresent   (6)
               lowerLayerDown   (7)"
   ::= {sr1645v2VrfRoutInterfacesEntry 1795162112}

sr1645v2VrfRoutInterfacesIfLastChange OBJECT-TYPE
   SYNTAX      TimeTicks
   MAX-ACCESS  read-only
   STATUS      current
   DESCRIPTION
      "Path: vrfRouter.status.interfaces.ifLastChange

       Time in centi-second."
   ::= {sr1645v2VrfRoutInterfacesEntry 1811939328}

sr1645v2VrfRoutInterfacesIfLastChangeDate OBJECT-TYPE
   SYNTAX      DisplayString
   MAX-ACCESS  read-only
   STATUS      current
   DESCRIPTION
      "Path: vrfRouter.status.interfaces.ifLastChangeDate"
   ::= {sr1645v2VrfRoutInterfacesEntry 3070230528}

sr1645v2VrfRoutInterfacesAddress OBJECT-TYPE
   SYNTAX      IpAddress
   MAX-ACCESS  read-only
   STATUS      current
   DESCRIPTION
      "Path: vrfRouter.status.interfaces.address"
   ::= {sr1645v2VrfRoutInterfacesEntry 2030043136}

sr1645v2VrfRoutInterfacesMask OBJECT-TYPE
   SYNTAX      IpAddress
   MAX-ACCESS  read-only
   STATUS      current
   DESCRIPTION
      "Path: vrfRouter.status.interfaces.mask"
   ::= {sr1645v2VrfRoutInterfacesEntry 2063597568}

sr1645v2VrfRoutInterfacesSecondaryIp OBJECT-TYPE
   SYNTAX      SEQUENCE OF Sr1645v2VrfRoutInterfacesSecondaryIpEntry
   MAX-ACCESS  not-accessible
   STATUS      current
   DESCRIPTION
      ""
   ::= {sr1645v2VrfRoutInterfaces 385875968}

sr1645v2VrfRoutInterfacesSecondaryIpEntry OBJECT-TYPE
   SYNTAX      Sr1645v2VrfRoutInterfacesSecondaryIpEntry
   MAX-ACCESS  not-accessible
   STATUS      current
   DESCRIPTION
      ""
   INDEX      { sr1645v2VrfRoutInterfacesSecondaryIpGlobalIx,
                sr1645v2VrfRoutInterfacesTableIx,
                sr1645v2VrfRoutInterfacesSecondaryIpTableIx }
   ::= {sr1645v2VrfRoutInterfacesSecondaryIp 1}

Sr1645v2VrfRoutInterfacesSecondaryIpEntry ::=
   SEQUENCE
      {
      sr1645v2VrfRoutInterfacesSecondaryIpGlobalIx
         GlobalIndex,
      sr1645v2VrfRoutInterfacesSecondaryIpTableIx
         TableIndex,
      sr1645v2VrfRoutInterfacesSecondaryIpAddress
         IpAddress,
      sr1645v2VrfRoutInterfacesSecondaryIpNetMask
         IpAddress
      }

sr1645v2VrfRoutInterfacesSecondaryIpGlobalIx OBJECT-TYPE
   SYNTAX      GlobalIndex
   MAX-ACCESS  not-accessible
   STATUS      current
   DESCRIPTION
      "The value of the tlsCntTreeGlobalIndex of the MANAGED OBJECT."
   ::= {sr1645v2VrfRoutInterfacesSecondaryIpEntry 10}

sr1645v2VrfRoutInterfacesSecondaryIpTableIx OBJECT-TYPE
   SYNTAX      TableIndex
   MAX-ACCESS  not-accessible
   STATUS      current
   DESCRIPTION
      ""
   ::= {sr1645v2VrfRoutInterfacesSecondaryIpEntry 11}

sr1645v2VrfRoutInterfacesSecondaryIpAddress OBJECT-TYPE
   SYNTAX      IpAddress
   MAX-ACCESS  read-only
   STATUS      current
   DESCRIPTION
      "Path: vrfRouter.status.interfaces.secondaryIp.address"
   ::= {sr1645v2VrfRoutInterfacesSecondaryIpEntry 2030043136}

sr1645v2VrfRoutInterfacesSecondaryIpNetMask OBJECT-TYPE
   SYNTAX      IpAddress
   MAX-ACCESS  read-only
   STATUS      current
   DESCRIPTION
      "Path: vrfRouter.status.interfaces.secondaryIp.netMask"
   ::= {sr1645v2VrfRoutInterfacesSecondaryIpEntry 2063597568}



pr1645v2VrfRout OBJECT IDENTIFIER ::= {r1645v2VrfRout 12}


pr1645v2VrfRoutRoutingTable OBJECT IDENTIFIER ::= {pr1645v2VrfRout 33}

pr1645v2VrfRoutRoutingTableSSCTable OBJECT-TYPE
   SYNTAX      SEQUENCE OF Pr1645v2VrfRoutRoutingTableEntry
   MAX-ACCESS  not-accessible
   STATUS      current
   DESCRIPTION
      "routingTable"
   ::= {pr1645v2VrfRoutRoutingTable 1}

pr1645v2VrfRoutRoutingTableEntry OBJECT-TYPE
   SYNTAX      Pr1645v2VrfRoutRoutingTableEntry
   MAX-ACCESS  not-accessible
   STATUS      current
   DESCRIPTION
      ""
   INDEX      { pr1645v2VrfRoutRoutingTableGlobalIx,
                pr1645v2VrfRoutRoutingTableTableIx }
   ::= {pr1645v2VrfRoutRoutingTableSSCTable 1}

Pr1645v2VrfRoutRoutingTableEntry ::=
   SEQUENCE
      {
      pr1645v2VrfRoutRoutingTableGlobalIx
         GlobalIndex,
      pr1645v2VrfRoutRoutingTableTableIx
         TableIndex,
      pr1645v2VrfRoutRoutingTableNetwork
         IpAddress,
      pr1645v2VrfRoutRoutingTableMask
         IpAddress,
      pr1645v2VrfRoutRoutingTableGateway
         IpAddress,
      pr1645v2VrfRoutRoutingTableIf
         DisplayString,
      pr1645v2VrfRoutRoutingTableUses
         Gauge32,
      pr1645v2VrfRoutRoutingTableOctets
         Gauge32
      }

pr1645v2VrfRoutRoutingTableGlobalIx OBJECT-TYPE
   SYNTAX      GlobalIndex
   MAX-ACCESS  not-accessible
   STATUS      current
   DESCRIPTION
      "The value of the tlsCntTreeGlobalIndex of the MANAGED OBJECT."
   ::= {pr1645v2VrfRoutRoutingTableEntry 10}

pr1645v2VrfRoutRoutingTableTableIx OBJECT-TYPE
   SYNTAX      TableIndex
   MAX-ACCESS  not-accessible
   STATUS      current
   DESCRIPTION
      ""
   ::= {pr1645v2VrfRoutRoutingTableEntry 11}

pr1645v2VrfRoutRoutingTableNetwork OBJECT-TYPE
   SYNTAX      IpAddress
   MAX-ACCESS  read-only
   STATUS      current
   DESCRIPTION
      "Path: vrfRouter.performance.routingTable.network"
   ::= {pr1645v2VrfRoutRoutingTableEntry 16777216}

pr1645v2VrfRoutRoutingTableMask OBJECT-TYPE
   SYNTAX      IpAddress
   MAX-ACCESS  read-only
   STATUS      current
   DESCRIPTION
      "Path: vrfRouter.performance.routingTable.mask"
   ::= {pr1645v2VrfRoutRoutingTableEntry 33554432}

pr1645v2VrfRoutRoutingTableGateway OBJECT-TYPE
   SYNTAX      IpAddress
   MAX-ACCESS  read-only
   STATUS      current
   DESCRIPTION
      "Path: vrfRouter.performance.routingTable.gateway"
   ::= {pr1645v2VrfRoutRoutingTableEntry 50331648}

pr1645v2VrfRoutRoutingTableIf OBJECT-TYPE
   SYNTAX      DisplayString
   MAX-ACCESS  read-only
   STATUS      current
   DESCRIPTION
      "Path: vrfRouter.performance.routingTable.interface"
   ::= {pr1645v2VrfRoutRoutingTableEntry 67108864}

pr1645v2VrfRoutRoutingTableUses OBJECT-TYPE
   SYNTAX      Gauge32
   MAX-ACCESS  read-only
   STATUS      current
   DESCRIPTION
      "Path: vrfRouter.performance.routingTable.uses

       32 bit unsigned gauge value."
   ::= {pr1645v2VrfRoutRoutingTableEntry 83886080}

pr1645v2VrfRoutRoutingTableOctets OBJECT-TYPE
   SYNTAX      Gauge32
   MAX-ACCESS  read-only
   STATUS      current
   DESCRIPTION
      "Path: vrfRouter.performance.routingTable.octets

       32 bit unsigned gauge value."
   ::= {pr1645v2VrfRoutRoutingTableEntry 100663296}


pr1645v2VrfRoutPingResults OBJECT IDENTIFIER ::= {pr1645v2VrfRout 46}

pr1645v2VrfRoutPingResultsSSCTable OBJECT-TYPE
   SYNTAX      SEQUENCE OF Pr1645v2VrfRoutPingResultsEntry
   MAX-ACCESS  not-accessible
   STATUS      current
   DESCRIPTION
      "ping statistics"
   ::= {pr1645v2VrfRoutPingResults 1}

pr1645v2VrfRoutPingResultsEntry OBJECT-TYPE
   SYNTAX      Pr1645v2VrfRoutPingResultsEntry
   MAX-ACCESS  not-accessible
   STATUS      current
   DESCRIPTION
      ""
   INDEX      { pr1645v2VrfRoutPingResultsGlobalIx }
   ::= {pr1645v2VrfRoutPingResultsSSCTable 1}

Pr1645v2VrfRoutPingResultsEntry ::=
   SEQUENCE
      {
      pr1645v2VrfRoutPingResultsGlobalIx
         GlobalIndex,
      pr1645v2VrfRoutPingResultsIpAddr
         IpAddress,
      pr1645v2VrfRoutPingResultsNbrTxPckt
         Counter32,
      pr1645v2VrfRoutPingResultsNbrRxPckt
         Counter32,
      pr1645v2VrfRoutPingResultsRepTimMin
         TimeTicks,
      pr1645v2VrfRoutPingResultsRepTimMax
         TimeTicks,
      pr1645v2VrfRoutPingResultsRepTimAvrg
         TimeTicks,
      pr1645v2VrfRoutPingResultsLastError
         DisplayString
      }

pr1645v2VrfRoutPingResultsGlobalIx OBJECT-TYPE
   SYNTAX      GlobalIndex
   MAX-ACCESS  not-accessible
   STATUS      current
   DESCRIPTION
      "The value of the tlsCntTreeGlobalIndex of the MANAGED OBJECT."
   ::= {pr1645v2VrfRoutPingResultsEntry 10}

pr1645v2VrfRoutPingResultsIpAddr OBJECT-TYPE
   SYNTAX      IpAddress
   MAX-ACCESS  read-only
   STATUS      current
   DESCRIPTION
      "Path: vrfRouter.performance.pingResults.ipAddress"
   ::= {pr1645v2VrfRoutPingResultsEntry 16777216}

pr1645v2VrfRoutPingResultsNbrTxPckt OBJECT-TYPE
   SYNTAX      Counter32
   MAX-ACCESS  read-only
   STATUS      current
   DESCRIPTION
      "Path: vrfRouter.performance.pingResults.numOfTxPackets

       32 bit unsigned wrappable counter."
   ::= {pr1645v2VrfRoutPingResultsEntry 33554432}

pr1645v2VrfRoutPingResultsNbrRxPckt OBJECT-TYPE
   SYNTAX      Counter32
   MAX-ACCESS  read-only
   STATUS      current
   DESCRIPTION
      "Path: vrfRouter.performance.pingResults.numOfRxPackets

       32 bit unsigned wrappable counter."
   ::= {pr1645v2VrfRoutPingResultsEntry 50331648}

pr1645v2VrfRoutPingResultsRepTimMin OBJECT-TYPE
   SYNTAX      TimeTicks
   MAX-ACCESS  read-only
   STATUS      current
   DESCRIPTION
      "Path: vrfRouter.performance.pingResults.replyTimeMin

       Time in centi-second."
   ::= {pr1645v2VrfRoutPingResultsEntry 67108864}

pr1645v2VrfRoutPingResultsRepTimMax OBJECT-TYPE
   SYNTAX      TimeTicks
   MAX-ACCESS  read-only
   STATUS      current
   DESCRIPTION
      "Path: vrfRouter.performance.pingResults.replyTimeMax

       Time in centi-second."
   ::= {pr1645v2VrfRoutPingResultsEntry 83886080}

pr1645v2VrfRoutPingResultsRepTimAvrg OBJECT-TYPE
   SYNTAX      TimeTicks
   MAX-ACCESS  read-only
   STATUS      current
   DESCRIPTION
      "Path: vrfRouter.performance.pingResults.replyTimeAvrg

       Time in centi-second."
   ::= {pr1645v2VrfRoutPingResultsEntry 100663296}

pr1645v2VrfRoutPingResultsLastError OBJECT-TYPE
   SYNTAX      DisplayString
   MAX-ACCESS  read-only
   STATUS      current
   DESCRIPTION
      "Path: vrfRouter.performance.pingResults.lastError"
   ::= {pr1645v2VrfRoutPingResultsEntry 117440512}


pr1645v2VrfRoutQm OBJECT IDENTIFIER ::= {pr1645v2VrfRout 79}

pr1645v2VrfRoutQmSSCTable OBJECT-TYPE
   SYNTAX      SEQUENCE OF Pr1645v2VrfRoutQmEntry
   MAX-ACCESS  not-accessible
   STATUS      current
   DESCRIPTION
      "quality monitor"
   ::= {pr1645v2VrfRoutQm 1}

pr1645v2VrfRoutQmEntry OBJECT-TYPE
   SYNTAX      Pr1645v2VrfRoutQmEntry
   MAX-ACCESS  not-accessible
   STATUS      current
   DESCRIPTION
      ""
   INDEX      { pr1645v2VrfRoutQmGlobalIx,
                pr1645v2VrfRoutQmTableIx }
   ::= {pr1645v2VrfRoutQmSSCTable 1}

Pr1645v2VrfRoutQmEntry ::=
   SEQUENCE
      {
      pr1645v2VrfRoutQmGlobalIx
         GlobalIndex,
      pr1645v2VrfRoutQmTableIx
         TableIndex,
      pr1645v2VrfRoutQmName
         DisplayString,
      pr1645v2VrfRoutQmStatus
         INTEGER,
      pr1645v2VrfRoutQmIpAddress
         IpAddress,
      pr1645v2VrfRoutQmHostName
         DisplayString,
      pr1645v2VrfRoutQmSourceIp
         IpAddress,
      pr1645v2VrfRoutQmSourceId
         Gauge32,
      pr1645v2VrfRoutQmNbrTxPckt
         Counter32,
      pr1645v2VrfRoutQmNbrRxPckt
         Counter32,
      pr1645v2VrfRoutQmError
         Counter32,
      pr1645v2VrfRoutQmDelay
         Integer32,
      pr1645v2VrfRoutQmJitter
         Integer32,
      pr1645v2VrfRoutQmLoss
         Counter32,
      pr1645v2VrfRoutQmLossDelay
         Counter32,
      pr1645v2VrfRoutQmDelayMin
         Integer32,
      pr1645v2VrfRoutQmDelayAvrg
         Integer32,
      pr1645v2VrfRoutQmDelayMax
         Integer32,
      pr1645v2VrfRoutQmDelayBinsType
         INTEGER,
      pr1645v2VrfRoutQmDelayBinsMinMin
         Counter32,
      pr1645v2VrfRoutQmDelayBinsMin
         Integer32,
      pr1645v2VrfRoutQmDelayBinsMinBin1
         Counter32,
      pr1645v2VrfRoutQmDelayBinsBin2
         Counter32,
      pr1645v2VrfRoutQmDelayBinsBin3
         Counter32,
      pr1645v2VrfRoutQmDelayBinsBin4
         Counter32,
      pr1645v2VrfRoutQmDelayBinsBin5
         Counter32,
      pr1645v2VrfRoutQmDelayBinsBin6
         Counter32,
      pr1645v2VrfRoutQmDelayBinsBin7
         Counter32,
      pr1645v2VrfRoutQmDelayBinsMaxBin8
         Counter32,
      pr1645v2VrfRoutQmDelayBinsMax
         Integer32,
      pr1645v2VrfRoutQmDelayBinsPlusMax
         Counter32,
      pr1645v2VrfRoutQmJitterNegMax
         Integer32,
      pr1645v2VrfRoutQmJitterAvrg
         Integer32,
      pr1645v2VrfRoutQmJitterPosMax
         Integer32,
      pr1645v2VrfRoutQmJitterBinsType
         INTEGER,
      pr1645v2VrfRoutQmJitterBinsMinMin
         Counter32,
      pr1645v2VrfRoutQmJitterBinsMin
         Integer32,
      pr1645v2VrfRoutQmJitterBinsMinBin1
         Counter32,
      pr1645v2VrfRoutQmJitterBinsBin2
         Counter32,
      pr1645v2VrfRoutQmJitterBinsBin3
         Counter32,
      pr1645v2VrfRoutQmJitterBinsBin4
         Counter32,
      pr1645v2VrfRoutQmJitterBinsBin5
         Counter32,
      pr1645v2VrfRoutQmJitterBinsBin6
         Counter32,
      pr1645v2VrfRoutQmJitterBinsBin7
         Counter32,
      pr1645v2VrfRoutQmJitterBinsMaxBin8
         Counter32,
      pr1645v2VrfRoutQmJitterBinsMax
         Integer32,
      pr1645v2VrfRoutQmJitterBinsPlusMax
         Counter32,
      pr1645v2VrfRoutQmBfdCtrlOutPkts
         Integer32,
      pr1645v2VrfRoutQmBfdCtrlInPkts
         Integer32,
      pr1645v2VrfRoutQmBfdCtrlLocalState
         INTEGER,
      pr1645v2VrfRoutQmBfdCtrlLocalDiscriminator
         Integer32,
      pr1645v2VrfRoutQmBfdCtrlLocalTxInterval
         Integer32,
      pr1645v2VrfRoutQmBfdCtrlLocalMinTxInterval
         Integer32,
      pr1645v2VrfRoutQmBfdCtrlLocalDetectMultiplier
         Integer32,
      pr1645v2VrfRoutQmBfdCtrlRemoteState
         INTEGER,
      pr1645v2VrfRoutQmBfdCtrlRemoteDiscriminator
         Integer32,
      pr1645v2VrfRoutQmBfdCtrlRemoteMinTxInterval
         Integer32,
      pr1645v2VrfRoutQmBfdCtrlRemoteDetectMultiplier
         Integer32,
      pr1645v2VrfRoutQmBfdCtrlRemoteMinRxInterval
         Integer32,
      pr1645v2VrfRoutQmBfdCtrlRemoteMinRxEchoInterval
         Integer32,
      pr1645v2VrfRoutQmUpDownStatus
         INTEGER,
      pr1645v2VrfRoutQmUpDownLossUp
         Counter32,
      pr1645v2VrfRoutQmUpDownLossDelayUp
         Counter32,
      pr1645v2VrfRoutQmUpDownDelayUpMin
         Integer32,
      pr1645v2VrfRoutQmUpDownDelayUpAvrg
         Integer32,
      pr1645v2VrfRoutQmUpDownDelayUpMax
         Integer32,
      pr1645v2VrfRoutQmUpDownDelayUpBinsType
         INTEGER,
      pr1645v2VrfRoutQmUpDownDelayUpBinsMinMin
         Counter32,
      pr1645v2VrfRoutQmUpDownDelayUpBinsMin
         Integer32,
      pr1645v2VrfRoutQmUpDownDelayUpBinsMinBin1
         Counter32,
      pr1645v2VrfRoutQmUpDownDelayUpBinsBin2
         Counter32,
      pr1645v2VrfRoutQmUpDownDelayUpBinsBin3
         Counter32,
      pr1645v2VrfRoutQmUpDownDelayUpBinsBin4
         Counter32,
      pr1645v2VrfRoutQmUpDownDelayUpBinsBin5
         Counter32,
      pr1645v2VrfRoutQmUpDownDelayUpBinsBin6
         Counter32,
      pr1645v2VrfRoutQmUpDownDelayUpBinsBin7
         Counter32,
      pr1645v2VrfRoutQmUpDownDelayUpBinsMaxBin8
         Counter32,
      pr1645v2VrfRoutQmUpDownDelayUpBinsMax
         Integer32,
      pr1645v2VrfRoutQmUpDownDelayUpBinsPlusMax
         Counter32,
      pr1645v2VrfRoutQmUpDownJitterUp
         Integer32,
      pr1645v2VrfRoutQmUpDownJitterUpNegMax
         Integer32,
      pr1645v2VrfRoutQmUpDownJitterUpAvrg
         Integer32,
      pr1645v2VrfRoutQmUpDownJitterUpPosMax
         Integer32,
      pr1645v2VrfRoutQmUpDownJitterUpBinsType
         INTEGER,
      pr1645v2VrfRoutQmUpDownJitterUpBinsMinMin
         Counter32,
      pr1645v2VrfRoutQmUpDownJitterUpBinsMin
         Integer32,
      pr1645v2VrfRoutQmUpDownJitterUpBinsMinBin1
         Counter32,
      pr1645v2VrfRoutQmUpDownJitterUpBinsBin2
         Counter32,
      pr1645v2VrfRoutQmUpDownJitterUpBinsBin3
         Counter32,
      pr1645v2VrfRoutQmUpDownJitterUpBinsBin4
         Counter32,
      pr1645v2VrfRoutQmUpDownJitterUpBinsBin5
         Counter32,
      pr1645v2VrfRoutQmUpDownJitterUpBinsBin6
         Counter32,
      pr1645v2VrfRoutQmUpDownJitterUpBinsBin7
         Counter32,
      pr1645v2VrfRoutQmUpDownJitterUpBinsMaxBin8
         Counter32,
      pr1645v2VrfRoutQmUpDownJitterUpBinsMax
         Integer32,
      pr1645v2VrfRoutQmUpDownJitterUpBinsPlusMax
         Counter32,
      pr1645v2VrfRoutQmUpDownLossDown
         Counter32,
      pr1645v2VrfRoutQmUpDownLossDelayDown
         Counter32,
      pr1645v2VrfRoutQmUpDownDelayDownMin
         Integer32,
      pr1645v2VrfRoutQmUpDownDelayDownAvrg
         Integer32,
      pr1645v2VrfRoutQmUpDownDelayDownMax
         Integer32,
      pr1645v2VrfRoutQmUpDownDelayDownBinsType
         INTEGER,
      pr1645v2VrfRoutQmUpDownDelayDownBinsMinMin
         Counter32,
      pr1645v2VrfRoutQmUpDownDelayDownBinsMin
         Integer32,
      pr1645v2VrfRoutQmUpDownDelayDownBinsMinBin1
         Counter32,
      pr1645v2VrfRoutQmUpDownDelayDownBinsBin2
         Counter32,
      pr1645v2VrfRoutQmUpDownDelayDownBinsBin3
         Counter32,
      pr1645v2VrfRoutQmUpDownDelayDownBinsBin4
         Counter32,
      pr1645v2VrfRoutQmUpDownDelayDownBinsBin5
         Counter32,
      pr1645v2VrfRoutQmUpDownDelayDownBinsBin6
         Counter32,
      pr1645v2VrfRoutQmUpDownDelayDownBinsBin7
         Counter32,
      pr1645v2VrfRoutQmUpDownDelayDownBinsMaxBin8
         Counter32,
      pr1645v2VrfRoutQmUpDownDelayDownBinsMax
         Integer32,
      pr1645v2VrfRoutQmUpDownDelayDownBinsPlusMax
         Counter32,
      pr1645v2VrfRoutQmUpDownJitterDown
         Integer32,
      pr1645v2VrfRoutQmUpDownJitterDownNegMax
         Integer32,
      pr1645v2VrfRoutQmUpDownJitterDownAvrg
         Integer32,
      pr1645v2VrfRoutQmUpDownJitterDownPosMax
         Integer32,
      pr1645v2VrfRoutQmUpDownJitterDownBinsType
         INTEGER,
      pr1645v2VrfRoutQmUpDownJitterDownBinsMinMin
         Counter32,
      pr1645v2VrfRoutQmUpDownJitterDownBinsMin
         Integer32,
      pr1645v2VrfRoutQmUpDownJitterDownBinsMinBin1
         Counter32,
      pr1645v2VrfRoutQmUpDownJitterDownBinsBin2
         Counter32,
      pr1645v2VrfRoutQmUpDownJitterDownBinsBin3
         Counter32,
      pr1645v2VrfRoutQmUpDownJitterDownBinsBin4
         Counter32,
      pr1645v2VrfRoutQmUpDownJitterDownBinsBin5
         Counter32,
      pr1645v2VrfRoutQmUpDownJitterDownBinsBin6
         Counter32,
      pr1645v2VrfRoutQmUpDownJitterDownBinsBin7
         Counter32,
      pr1645v2VrfRoutQmUpDownJitterDownBinsMaxBin8
         Counter32,
      pr1645v2VrfRoutQmUpDownJitterDownBinsMax
         Integer32,
      pr1645v2VrfRoutQmUpDownJitterDownBinsPlusMax
         Counter32,
      pr1645v2VrfRoutQmLastLogSysUpTime
         TimeTicks,
      pr1645v2VrfRoutQmLastLogNbrTxPckt
         Counter32,
      pr1645v2VrfRoutQmLastLogNbrRxPckt
         Counter32,
      pr1645v2VrfRoutQmLastLogError
         Counter32,
      pr1645v2VrfRoutQmLastLogLoss
         Counter32,
      pr1645v2VrfRoutQmLastLogLossDelay
         Counter32,
      pr1645v2VrfRoutQmLastLogDelayMin
         Integer32,
      pr1645v2VrfRoutQmLastLogDelayAvrg
         Integer32,
      pr1645v2VrfRoutQmLastLogDelayMax
         Integer32,
      pr1645v2VrfRoutQmLastLogJitterNegMax
         Integer32,
      pr1645v2VrfRoutQmLastLogJitterAvrg
         Integer32,
      pr1645v2VrfRoutQmLastLogJitterPosMax
         Integer32,
      pr1645v2VrfRoutQmLastLogUpDownStatus
         INTEGER,
      pr1645v2VrfRoutQmLastLogUpDownLossUp
         Counter32,
      pr1645v2VrfRoutQmLastLogUpDownLossDelayUp
         Counter32,
      pr1645v2VrfRoutQmLastLogUpDownDelayUpMin
         Integer32,
      pr1645v2VrfRoutQmLastLogUpDownDelayUpAvrg
         Integer32,
      pr1645v2VrfRoutQmLastLogUpDownDelayUpMax
         Integer32,
      pr1645v2VrfRoutQmLastLogUpDownJitterUpNegMax
         Integer32,
      pr1645v2VrfRoutQmLastLogUpDownJitterUpAvrg
         Integer32,
      pr1645v2VrfRoutQmLastLogUpDownJitterUpPosMax
         Integer32,
      pr1645v2VrfRoutQmLastLogUpDownLossDown
         Counter32,
      pr1645v2VrfRoutQmLastLogUpDownLossDelayDown
         Counter32,
      pr1645v2VrfRoutQmLastLogUpDownDelayDownMin
         Integer32,
      pr1645v2VrfRoutQmLastLogUpDownDelayDownAvrg
         Integer32,
      pr1645v2VrfRoutQmLastLogUpDownDelayDownMax
         Integer32,
      pr1645v2VrfRoutQmLastLogUpDownJitterDownNegMax
         Integer32,
      pr1645v2VrfRoutQmLastLogUpDownJitterDownAvrg
         Integer32,
      pr1645v2VrfRoutQmLastLogUpDownJitterDownPosMax
         Integer32,
      pr1645v2VrfRoutQmLastLogDate
         DisplayString,
      pr1645v2VrfRoutQmAlarm
         Integer32,
      pr1645v2VrfRoutQmLastError
         DisplayString
      }

pr1645v2VrfRoutQmGlobalIx OBJECT-TYPE
   SYNTAX      GlobalIndex
   MAX-ACCESS  not-accessible
   STATUS      current
   DESCRIPTION
      "The value of the tlsCntTreeGlobalIndex of the MANAGED OBJECT."
   ::= {pr1645v2VrfRoutQmEntry 10}

pr1645v2VrfRoutQmTableIx OBJECT-TYPE
   SYNTAX      TableIndex
   MAX-ACCESS  not-accessible
   STATUS      current
   DESCRIPTION
      ""
   ::= {pr1645v2VrfRoutQmEntry 11}

pr1645v2VrfRoutQmName OBJECT-TYPE
   SYNTAX      DisplayString
   MAX-ACCESS  read-only
   STATUS      current
   DESCRIPTION
      "Path: vrfRouter.performance.qualityMonitor.name"
   ::= {pr1645v2VrfRoutQmEntry 301989888}

pr1645v2VrfRoutQmStatus OBJECT-TYPE
   SYNTAX      INTEGER
               {
               run (1),
               runOnDemand (3),
               halted (2),
               cleared (6),
               disabled (8),
               runIdle (9)
               }
   MAX-ACCESS  read-only
   STATUS      current
   DESCRIPTION
      "Path: vrfRouter.performance.qualityMonitor.status

       Possibilities:
               run   (1)
               runOnDemand   (3)
               halted   (2)
               cleared   (6)
               disabled   (8)
               runIdle   (9)"
   ::= {pr1645v2VrfRoutQmEntry 369098752}

pr1645v2VrfRoutQmIpAddress OBJECT-TYPE
   SYNTAX      IpAddress
   MAX-ACCESS  read-only
   STATUS      current
   DESCRIPTION
      "Path: vrfRouter.performance.qualityMonitor.ipAddress"
   ::= {pr1645v2VrfRoutQmEntry 16777216}

pr1645v2VrfRoutQmHostName OBJECT-TYPE
   SYNTAX      DisplayString
   MAX-ACCESS  read-only
   STATUS      current
   DESCRIPTION
      "Path: vrfRouter.performance.qualityMonitor.hostName"
   ::= {pr1645v2VrfRoutQmEntry 33554432}

pr1645v2VrfRoutQmSourceIp OBJECT-TYPE
   SYNTAX      IpAddress
   MAX-ACCESS  read-only
   STATUS      current
   DESCRIPTION
      "Path: vrfRouter.performance.qualityMonitor.sourceIp"
   ::= {pr1645v2VrfRoutQmEntry 83886080}

pr1645v2VrfRoutQmSourceId OBJECT-TYPE
   SYNTAX      Gauge32
   MAX-ACCESS  read-only
   STATUS      current
   DESCRIPTION
      "Path: vrfRouter.performance.qualityMonitor.sourceId

       32 bit unsigned gauge value."
   ::= {pr1645v2VrfRoutQmEntry 352321536}

pr1645v2VrfRoutQmNbrTxPckt OBJECT-TYPE
   SYNTAX      Counter32
   MAX-ACCESS  read-only
   STATUS      current
   DESCRIPTION
      "Path: vrfRouter.performance.qualityMonitor.nbrOfTxPackets

       32 bit unsigned wrappable counter."
   ::= {pr1645v2VrfRoutQmEntry 50331648}

pr1645v2VrfRoutQmNbrRxPckt OBJECT-TYPE
   SYNTAX      Counter32
   MAX-ACCESS  read-only
   STATUS      current
   DESCRIPTION
      "Path: vrfRouter.performance.qualityMonitor.nbrOfRxPackets

       32 bit unsigned wrappable counter."
   ::= {pr1645v2VrfRoutQmEntry 67108864}

pr1645v2VrfRoutQmError OBJECT-TYPE
   SYNTAX      Counter32
   MAX-ACCESS  read-only
   STATUS      current
   DESCRIPTION
      "Path: vrfRouter.performance.qualityMonitor.error

       32 bit unsigned wrappable counter."
   ::= {pr1645v2VrfRoutQmEntry 285212672}

pr1645v2VrfRoutQmDelay OBJECT-TYPE
   SYNTAX      Integer32
   MAX-ACCESS  read-only
   STATUS      current
   DESCRIPTION
      "Path: vrfRouter.performance.qualityMonitor.delay

       unit name = sec
       formula = 1000 / ; 1000 *"
   ::= {pr1645v2VrfRoutQmEntry 201326592}

pr1645v2VrfRoutQmJitter OBJECT-TYPE
   SYNTAX      Integer32
   MAX-ACCESS  read-only
   STATUS      current
   DESCRIPTION
      "Path: vrfRouter.performance.qualityMonitor.jitter

       unit name = sec
       formula = 1000 / ; 1000 *"
   ::= {pr1645v2VrfRoutQmEntry 218103808}

pr1645v2VrfRoutQmLoss OBJECT-TYPE
   SYNTAX      Counter32
   MAX-ACCESS  read-only
   STATUS      current
   DESCRIPTION
      "Path: vrfRouter.performance.qualityMonitor.loss

       32 bit unsigned wrappable counter."
   ::= {pr1645v2VrfRoutQmEntry 100663296}

pr1645v2VrfRoutQmLossDelay OBJECT-TYPE
   SYNTAX      Counter32
   MAX-ACCESS  read-only
   STATUS      current
   DESCRIPTION
      "Path: vrfRouter.performance.qualityMonitor.lossDelay

       32 bit unsigned wrappable counter."
   ::= {pr1645v2VrfRoutQmEntry 268435456}

pr1645v2VrfRoutQmDelayMin OBJECT-TYPE
   SYNTAX      Integer32
   MAX-ACCESS  read-only
   STATUS      current
   DESCRIPTION
      "Path: vrfRouter.performance.qualityMonitor.delayMin

       unit name = sec
       formula = 1000 / ; 1000 *"
   ::= {pr1645v2VrfRoutQmEntry 184549376}

pr1645v2VrfRoutQmDelayAvrg OBJECT-TYPE
   SYNTAX      Integer32
   MAX-ACCESS  read-only
   STATUS      current
   DESCRIPTION
      "Path: vrfRouter.performance.qualityMonitor.delayAvrg

       unit name = sec
       formula = 1000 / ; 1000 *"
   ::= {pr1645v2VrfRoutQmEntry 117440512}

pr1645v2VrfRoutQmDelayMax OBJECT-TYPE
   SYNTAX      Integer32
   MAX-ACCESS  read-only
   STATUS      current
   DESCRIPTION
      "Path: vrfRouter.performance.qualityMonitor.delayMax

       unit name = sec
       formula = 1000 / ; 1000 *"
   ::= {pr1645v2VrfRoutQmEntry 134217728}

pr1645v2VrfRoutQmDelayBinsType OBJECT-TYPE
   SYNTAX      INTEGER
               {
               fd (1),
               fdr (2),
               notInUse (3),
               ifdv (4)
               }
   MAX-ACCESS  read-only
   STATUS      current
   DESCRIPTION
      "Path: vrfRouter.performance.qualityMonitor.delayBins.type

       Possibilities:
               fd   (1)
               fdr   (2)
               notInUse   (3)
               ifdv   (4)"
   ::= {pr1645v2VrfRoutQmEntry 420937728}

pr1645v2VrfRoutQmDelayBinsMinMin OBJECT-TYPE
   SYNTAX      Counter32
   MAX-ACCESS  read-only
   STATUS      current
   DESCRIPTION
      "Path: vrfRouter.performance.qualityMonitor.delayBins.minMin

       32 bit unsigned wrappable counter."
   ::= {pr1645v2VrfRoutQmEntry 419495936}

pr1645v2VrfRoutQmDelayBinsMin OBJECT-TYPE
   SYNTAX      Integer32
   MAX-ACCESS  read-only
   STATUS      current
   DESCRIPTION
      "Path: vrfRouter.performance.qualityMonitor.delayBins.min

       unit name = sec
       formula = 1000 / ; 1000 *"
   ::= {pr1645v2VrfRoutQmEntry 420806656}

pr1645v2VrfRoutQmDelayBinsMinBin1 OBJECT-TYPE
   SYNTAX      Counter32
   MAX-ACCESS  read-only
   STATUS      current
   DESCRIPTION
      "Path: vrfRouter.performance.qualityMonitor.delayBins.minBin1

       32 bit unsigned wrappable counter."
   ::= {pr1645v2VrfRoutQmEntry 419561472}

pr1645v2VrfRoutQmDelayBinsBin2 OBJECT-TYPE
   SYNTAX      Counter32
   MAX-ACCESS  read-only
   STATUS      current
   DESCRIPTION
      "Path: vrfRouter.performance.qualityMonitor.delayBins.bin2

       32 bit unsigned wrappable counter."
   ::= {pr1645v2VrfRoutQmEntry 419627008}

pr1645v2VrfRoutQmDelayBinsBin3 OBJECT-TYPE
   SYNTAX      Counter32
   MAX-ACCESS  read-only
   STATUS      current
   DESCRIPTION
      "Path: vrfRouter.performance.qualityMonitor.delayBins.bin3

       32 bit unsigned wrappable counter."
   ::= {pr1645v2VrfRoutQmEntry 419692544}

pr1645v2VrfRoutQmDelayBinsBin4 OBJECT-TYPE
   SYNTAX      Counter32
   MAX-ACCESS  read-only
   STATUS      current
   DESCRIPTION
      "Path: vrfRouter.performance.qualityMonitor.delayBins.bin4

       32 bit unsigned wrappable counter."
   ::= {pr1645v2VrfRoutQmEntry 419758080}

pr1645v2VrfRoutQmDelayBinsBin5 OBJECT-TYPE
   SYNTAX      Counter32
   MAX-ACCESS  read-only
   STATUS      current
   DESCRIPTION
      "Path: vrfRouter.performance.qualityMonitor.delayBins.bin5

       32 bit unsigned wrappable counter."
   ::= {pr1645v2VrfRoutQmEntry 419823616}

pr1645v2VrfRoutQmDelayBinsBin6 OBJECT-TYPE
   SYNTAX      Counter32
   MAX-ACCESS  read-only
   STATUS      current
   DESCRIPTION
      "Path: vrfRouter.performance.qualityMonitor.delayBins.bin6

       32 bit unsigned wrappable counter."
   ::= {pr1645v2VrfRoutQmEntry 419889152}

pr1645v2VrfRoutQmDelayBinsBin7 OBJECT-TYPE
   SYNTAX      Counter32
   MAX-ACCESS  read-only
   STATUS      current
   DESCRIPTION
      "Path: vrfRouter.performance.qualityMonitor.delayBins.bin7

       32 bit unsigned wrappable counter."
   ::= {pr1645v2VrfRoutQmEntry 419954688}

pr1645v2VrfRoutQmDelayBinsMaxBin8 OBJECT-TYPE
   SYNTAX      Counter32
   MAX-ACCESS  read-only
   STATUS      current
   DESCRIPTION
      "Path: vrfRouter.performance.qualityMonitor.delayBins.maxBin8

       32 bit unsigned wrappable counter."
   ::= {pr1645v2VrfRoutQmEntry 420020224}

pr1645v2VrfRoutQmDelayBinsMax OBJECT-TYPE
   SYNTAX      Integer32
   MAX-ACCESS  read-only
   STATUS      current
   DESCRIPTION
      "Path: vrfRouter.performance.qualityMonitor.delayBins.max

       unit name = sec
       formula = 1000 / ; 1000 *"
   ::= {pr1645v2VrfRoutQmEntry 420872192}

pr1645v2VrfRoutQmDelayBinsPlusMax OBJECT-TYPE
   SYNTAX      Counter32
   MAX-ACCESS  read-only
   STATUS      current
   DESCRIPTION
      "Path: vrfRouter.performance.qualityMonitor.delayBins.plusMax

       32 bit unsigned wrappable counter."
   ::= {pr1645v2VrfRoutQmEntry 420085760}

pr1645v2VrfRoutQmJitterNegMax OBJECT-TYPE
   SYNTAX      Integer32
   MAX-ACCESS  read-only
   STATUS      current
   DESCRIPTION
      "Path: vrfRouter.performance.qualityMonitor.jitterNegMax

       unit name = sec
       formula = 1000 / ; 1000 *"
   ::= {pr1645v2VrfRoutQmEntry 234881024}

pr1645v2VrfRoutQmJitterAvrg OBJECT-TYPE
   SYNTAX      Integer32
   MAX-ACCESS  read-only
   STATUS      current
   DESCRIPTION
      "Path: vrfRouter.performance.qualityMonitor.jitterAvrg

       unit name = sec
       formula = 1000 / ; 1000 *"
   ::= {pr1645v2VrfRoutQmEntry 150994944}

pr1645v2VrfRoutQmJitterPosMax OBJECT-TYPE
   SYNTAX      Integer32
   MAX-ACCESS  read-only
   STATUS      current
   DESCRIPTION
      "Path: vrfRouter.performance.qualityMonitor.jitterPosMax

       unit name = sec
       formula = 1000 / ; 1000 *"
   ::= {pr1645v2VrfRoutQmEntry 167772160}

pr1645v2VrfRoutQmJitterBinsType OBJECT-TYPE
   SYNTAX      INTEGER
               {
               fd (1),
               fdr (2),
               notInUse (3),
               ifdv (4)
               }
   MAX-ACCESS  read-only
   STATUS      current
   DESCRIPTION
      "Path: vrfRouter.performance.qualityMonitor.jitterBins.type

       Possibilities:
               fd   (1)
               fdr   (2)
               notInUse   (3)
               ifdv   (4)"
   ::= {pr1645v2VrfRoutQmEntry 437714944}

pr1645v2VrfRoutQmJitterBinsMinMin OBJECT-TYPE
   SYNTAX      Counter32
   MAX-ACCESS  read-only
   STATUS      current
   DESCRIPTION
      "Path: vrfRouter.performance.qualityMonitor.jitterBins.minMin

       32 bit unsigned wrappable counter."
   ::= {pr1645v2VrfRoutQmEntry 436273152}

pr1645v2VrfRoutQmJitterBinsMin OBJECT-TYPE
   SYNTAX      Integer32
   MAX-ACCESS  read-only
   STATUS      current
   DESCRIPTION
      "Path: vrfRouter.performance.qualityMonitor.jitterBins.min

       unit name = sec
       formula = 1000 / ; 1000 *"
   ::= {pr1645v2VrfRoutQmEntry 437583872}

pr1645v2VrfRoutQmJitterBinsMinBin1 OBJECT-TYPE
   SYNTAX      Counter32
   MAX-ACCESS  read-only
   STATUS      current
   DESCRIPTION
      "Path: vrfRouter.performance.qualityMonitor.jitterBins.minBin1

       32 bit unsigned wrappable counter."
   ::= {pr1645v2VrfRoutQmEntry 436338688}

pr1645v2VrfRoutQmJitterBinsBin2 OBJECT-TYPE
   SYNTAX      Counter32
   MAX-ACCESS  read-only
   STATUS      current
   DESCRIPTION
      "Path: vrfRouter.performance.qualityMonitor.jitterBins.bin2

       32 bit unsigned wrappable counter."
   ::= {pr1645v2VrfRoutQmEntry 436404224}

pr1645v2VrfRoutQmJitterBinsBin3 OBJECT-TYPE
   SYNTAX      Counter32
   MAX-ACCESS  read-only
   STATUS      current
   DESCRIPTION
      "Path: vrfRouter.performance.qualityMonitor.jitterBins.bin3

       32 bit unsigned wrappable counter."
   ::= {pr1645v2VrfRoutQmEntry 436469760}

pr1645v2VrfRoutQmJitterBinsBin4 OBJECT-TYPE
   SYNTAX      Counter32
   MAX-ACCESS  read-only
   STATUS      current
   DESCRIPTION
      "Path: vrfRouter.performance.qualityMonitor.jitterBins.bin4

       32 bit unsigned wrappable counter."
   ::= {pr1645v2VrfRoutQmEntry 436535296}

pr1645v2VrfRoutQmJitterBinsBin5 OBJECT-TYPE
   SYNTAX      Counter32
   MAX-ACCESS  read-only
   STATUS      current
   DESCRIPTION
      "Path: vrfRouter.performance.qualityMonitor.jitterBins.bin5

       32 bit unsigned wrappable counter."
   ::= {pr1645v2VrfRoutQmEntry 436600832}

pr1645v2VrfRoutQmJitterBinsBin6 OBJECT-TYPE
   SYNTAX      Counter32
   MAX-ACCESS  read-only
   STATUS      current
   DESCRIPTION
      "Path: vrfRouter.performance.qualityMonitor.jitterBins.bin6

       32 bit unsigned wrappable counter."
   ::= {pr1645v2VrfRoutQmEntry 436666368}

pr1645v2VrfRoutQmJitterBinsBin7 OBJECT-TYPE
   SYNTAX      Counter32
   MAX-ACCESS  read-only
   STATUS      current
   DESCRIPTION
      "Path: vrfRouter.performance.qualityMonitor.jitterBins.bin7

       32 bit unsigned wrappable counter."
   ::= {pr1645v2VrfRoutQmEntry 436731904}

pr1645v2VrfRoutQmJitterBinsMaxBin8 OBJECT-TYPE
   SYNTAX      Counter32
   MAX-ACCESS  read-only
   STATUS      current
   DESCRIPTION
      "Path: vrfRouter.performance.qualityMonitor.jitterBins.maxBin8

       32 bit unsigned wrappable counter."
   ::= {pr1645v2VrfRoutQmEntry 436797440}

pr1645v2VrfRoutQmJitterBinsMax OBJECT-TYPE
   SYNTAX      Integer32
   MAX-ACCESS  read-only
   STATUS      current
   DESCRIPTION
      "Path: vrfRouter.performance.qualityMonitor.jitterBins.max

       unit name = sec
       formula = 1000 / ; 1000 *"
   ::= {pr1645v2VrfRoutQmEntry 437649408}

pr1645v2VrfRoutQmJitterBinsPlusMax OBJECT-TYPE
   SYNTAX      Counter32
   MAX-ACCESS  read-only
   STATUS      current
   DESCRIPTION
      "Path: vrfRouter.performance.qualityMonitor.jitterBins.plusMax

       32 bit unsigned wrappable counter."
   ::= {pr1645v2VrfRoutQmEntry 436862976}

pr1645v2VrfRoutQmBfdCtrlOutPkts OBJECT-TYPE
   SYNTAX      Integer32
   MAX-ACCESS  read-only
   STATUS      current
   DESCRIPTION
      "Path: vrfRouter.performance.qualityMonitor.bfdCtrl.outPkts"
   ::= {pr1645v2VrfRoutQmEntry 838926336}

pr1645v2VrfRoutQmBfdCtrlInPkts OBJECT-TYPE
   SYNTAX      Integer32
   MAX-ACCESS  read-only
   STATUS      current
   DESCRIPTION
      "Path: vrfRouter.performance.qualityMonitor.bfdCtrl.inPkts"
   ::= {pr1645v2VrfRoutQmEntry 838991872}

pr1645v2VrfRoutQmBfdCtrlLocalState OBJECT-TYPE
   SYNTAX      INTEGER
               {
               down (1),
               init (2),
               up (3)
               }
   MAX-ACCESS  read-only
   STATUS      current
   DESCRIPTION
      "Path: vrfRouter.performance.qualityMonitor.bfdCtrl.localState

       Possibilities:
               down   (1)
               init   (2)
               up   (3)"
   ::= {pr1645v2VrfRoutQmEntry 839057408}

pr1645v2VrfRoutQmBfdCtrlLocalDiscriminator OBJECT-TYPE
   SYNTAX      Integer32
   MAX-ACCESS  read-only
   STATUS      current
   DESCRIPTION
      "Path: vrfRouter.performance.qualityMonitor.bfdCtrl.localDiscriminator"
   ::= {pr1645v2VrfRoutQmEntry 839122944}

pr1645v2VrfRoutQmBfdCtrlLocalTxInterval OBJECT-TYPE
   SYNTAX      Integer32
   UNITS       "ms"
   MAX-ACCESS  read-only
   STATUS      current
   DESCRIPTION
      "Path: vrfRouter.performance.qualityMonitor.bfdCtrl.localTxInterval

       unit name = ms"
   ::= {pr1645v2VrfRoutQmEntry 839712768}

pr1645v2VrfRoutQmBfdCtrlLocalMinTxInterval OBJECT-TYPE
   SYNTAX      Integer32
   UNITS       "ms"
   MAX-ACCESS  read-only
   STATUS      current
   DESCRIPTION
      "Path: vrfRouter.performance.qualityMonitor.bfdCtrl.localMinTxInterval

       unit name = ms"
   ::= {pr1645v2VrfRoutQmEntry 839188480}

pr1645v2VrfRoutQmBfdCtrlLocalDetectMultiplier OBJECT-TYPE
   SYNTAX      Integer32
   MAX-ACCESS  read-only
   STATUS      current
   DESCRIPTION
      "Path: vrfRouter.performance.qualityMonitor.bfdCtrl.localDetectMultiplier"
   ::= {pr1645v2VrfRoutQmEntry 839254016}

pr1645v2VrfRoutQmBfdCtrlRemoteState OBJECT-TYPE
   SYNTAX      INTEGER
               {
               down (1),
               init (2),
               up (3)
               }
   MAX-ACCESS  read-only
   STATUS      current
   DESCRIPTION
      "Path: vrfRouter.performance.qualityMonitor.bfdCtrl.remoteState

       Possibilities:
               down   (1)
               init   (2)
               up   (3)"
   ::= {pr1645v2VrfRoutQmEntry 839319552}

pr1645v2VrfRoutQmBfdCtrlRemoteDiscriminator OBJECT-TYPE
   SYNTAX      Integer32
   MAX-ACCESS  read-only
   STATUS      current
   DESCRIPTION
      "Path: vrfRouter.performance.qualityMonitor.bfdCtrl.remoteDiscriminator"
   ::= {pr1645v2VrfRoutQmEntry 839450624}

pr1645v2VrfRoutQmBfdCtrlRemoteMinTxInterval OBJECT-TYPE
   SYNTAX      Integer32
   UNITS       "ms"
   MAX-ACCESS  read-only
   STATUS      current
   DESCRIPTION
      "Path: vrfRouter.performance.qualityMonitor.bfdCtrl.remoteMinTxInterval

       unit name = ms"
   ::= {pr1645v2VrfRoutQmEntry 839385088}

pr1645v2VrfRoutQmBfdCtrlRemoteDetectMultiplier OBJECT-TYPE
   SYNTAX      Integer32
   MAX-ACCESS  read-only
   STATUS      current
   DESCRIPTION
      "Path: vrfRouter.performance.qualityMonitor.bfdCtrl.remoteDetectMultiplier"
   ::= {pr1645v2VrfRoutQmEntry 839516160}

pr1645v2VrfRoutQmBfdCtrlRemoteMinRxInterval OBJECT-TYPE
   SYNTAX      Integer32
   UNITS       "ms"
   MAX-ACCESS  read-only
   STATUS      current
   DESCRIPTION
      "Path: vrfRouter.performance.qualityMonitor.bfdCtrl.remoteMinRxInterval

       unit name = ms"
   ::= {pr1645v2VrfRoutQmEntry 839581696}

pr1645v2VrfRoutQmBfdCtrlRemoteMinRxEchoInterval OBJECT-TYPE
   SYNTAX      Integer32
   UNITS       "ms"
   MAX-ACCESS  read-only
   STATUS      current
   DESCRIPTION
      "Path: vrfRouter.performance.qualityMonitor.bfdCtrl.remoteMinRxEchoInterval

       unit name = ms"
   ::= {pr1645v2VrfRoutQmEntry 839647232}

pr1645v2VrfRoutQmUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouter.performance.qualityMonitor.upDown.status

       Possibilities:
               notInUse   (3)
               onlyJitter   (1)
               jitterAndLoss   (2)
               all   (4)
               onlyLoss   (8)"
   ::= {pr1645v2VrfRoutQmEntry 504627200}

pr1645v2VrfRoutQmUpDownLossUp OBJECT-TYPE
   SYNTAX      Counter32
   MAX-ACCESS  read-only
   STATUS      current
   DESCRIPTION
      "Path: vrfRouter.performance.qualityMonitor.upDown.lossUp

       32 bit unsigned wrappable counter."
   ::= {pr1645v2VrfRoutQmEntry 503971840}

pr1645v2VrfRoutQmUpDownLossDelayUp OBJECT-TYPE
   SYNTAX      Counter32
   MAX-ACCESS  read-only
   STATUS      current
   DESCRIPTION
      "Path: vrfRouter.performance.qualityMonitor.upDown.lossDelayUp

       32 bit unsigned wrappable counter."
   ::= {pr1645v2VrfRoutQmEntry 504037376}

pr1645v2VrfRoutQmUpDownDelayUpMin OBJECT-TYPE
   SYNTAX      Integer32
   MAX-ACCESS  read-only
   STATUS      current
   DESCRIPTION
      "Path: vrfRouter.performance.qualityMonitor.upDown.delayUpMin

       unit name = sec
       formula = 1000 / ; 1000 *"
   ::= {pr1645v2VrfRoutQmEntry 505282560}

pr1645v2VrfRoutQmUpDownDelayUpAvrg OBJECT-TYPE
   SYNTAX      Integer32
   MAX-ACCESS  read-only
   STATUS      current
   DESCRIPTION
      "Path: vrfRouter.performance.qualityMonitor.upDown.delayUpAvrg

       unit name = sec
       formula = 1000 / ; 1000 *"
   ::= {pr1645v2VrfRoutQmEntry 505348096}

pr1645v2VrfRoutQmUpDownDelayUpMax OBJECT-TYPE
   SYNTAX      Integer32
   MAX-ACCESS  read-only
   STATUS      current
   DESCRIPTION
      "Path: vrfRouter.performance.qualityMonitor.upDown.delayUpMax

       unit name = sec
       formula = 1000 / ; 1000 *"
   ::= {pr1645v2VrfRoutQmEntry 505413632}

pr1645v2VrfRoutQmUpDownDelayUpBinsType OBJECT-TYPE
   SYNTAX      INTEGER
               {
               fd (1),
               fdr (2),
               notInUse (3),
               ifdv (4)
               }
   MAX-ACCESS  read-only
   STATUS      current
   DESCRIPTION
      "Path: vrfRouter.performance.qualityMonitor.upDown.delayUpBins.type

       Possibilities:
               fd   (1)
               fdr   (2)
               notInUse   (3)
               ifdv   (4)"
   ::= {pr1645v2VrfRoutQmEntry 505943808}

pr1645v2VrfRoutQmUpDownDelayUpBinsMinMin OBJECT-TYPE
   SYNTAX      Counter32
   MAX-ACCESS  read-only
   STATUS      current
   DESCRIPTION
      "Path: vrfRouter.performance.qualityMonitor.upDown.delayUpBins.minMin

       32 bit unsigned wrappable counter."
   ::= {pr1645v2VrfRoutQmEntry 505938176}

pr1645v2VrfRoutQmUpDownDelayUpBinsMin OBJECT-TYPE
   SYNTAX      Integer32
   MAX-ACCESS  read-only
   STATUS      current
   DESCRIPTION
      "Path: vrfRouter.performance.qualityMonitor.upDown.delayUpBins.min

       unit name = sec
       formula = 1000 / ; 1000 *"
   ::= {pr1645v2VrfRoutQmEntry 505943296}

pr1645v2VrfRoutQmUpDownDelayUpBinsMinBin1 OBJECT-TYPE
   SYNTAX      Counter32
   MAX-ACCESS  read-only
   STATUS      current
   DESCRIPTION
      "Path: vrfRouter.performance.qualityMonitor.upDown.delayUpBins.minBin1

       32 bit unsigned wrappable counter."
   ::= {pr1645v2VrfRoutQmEntry 505938432}

pr1645v2VrfRoutQmUpDownDelayUpBinsBin2 OBJECT-TYPE
   SYNTAX      Counter32
   MAX-ACCESS  read-only
   STATUS      current
   DESCRIPTION
      "Path: vrfRouter.performance.qualityMonitor.upDown.delayUpBins.bin2

       32 bit unsigned wrappable counter."
   ::= {pr1645v2VrfRoutQmEntry 505938688}

pr1645v2VrfRoutQmUpDownDelayUpBinsBin3 OBJECT-TYPE
   SYNTAX      Counter32
   MAX-ACCESS  read-only
   STATUS      current
   DESCRIPTION
      "Path: vrfRouter.performance.qualityMonitor.upDown.delayUpBins.bin3

       32 bit unsigned wrappable counter."
   ::= {pr1645v2VrfRoutQmEntry 505938944}

pr1645v2VrfRoutQmUpDownDelayUpBinsBin4 OBJECT-TYPE
   SYNTAX      Counter32
   MAX-ACCESS  read-only
   STATUS      current
   DESCRIPTION
      "Path: vrfRouter.performance.qualityMonitor.upDown.delayUpBins.bin4

       32 bit unsigned wrappable counter."
   ::= {pr1645v2VrfRoutQmEntry 505939200}

pr1645v2VrfRoutQmUpDownDelayUpBinsBin5 OBJECT-TYPE
   SYNTAX      Counter32
   MAX-ACCESS  read-only
   STATUS      current
   DESCRIPTION
      "Path: vrfRouter.performance.qualityMonitor.upDown.delayUpBins.bin5

       32 bit unsigned wrappable counter."
   ::= {pr1645v2VrfRoutQmEntry 505939456}

pr1645v2VrfRoutQmUpDownDelayUpBinsBin6 OBJECT-TYPE
   SYNTAX      Counter32
   MAX-ACCESS  read-only
   STATUS      current
   DESCRIPTION
      "Path: vrfRouter.performance.qualityMonitor.upDown.delayUpBins.bin6

       32 bit unsigned wrappable counter."
   ::= {pr1645v2VrfRoutQmEntry 505939712}

pr1645v2VrfRoutQmUpDownDelayUpBinsBin7 OBJECT-TYPE
   SYNTAX      Counter32
   MAX-ACCESS  read-only
   STATUS      current
   DESCRIPTION
      "Path: vrfRouter.performance.qualityMonitor.upDown.delayUpBins.bin7

       32 bit unsigned wrappable counter."
   ::= {pr1645v2VrfRoutQmEntry 505939968}

pr1645v2VrfRoutQmUpDownDelayUpBinsMaxBin8 OBJECT-TYPE
   SYNTAX      Counter32
   MAX-ACCESS  read-only
   STATUS      current
   DESCRIPTION
      "Path: vrfRouter.performance.qualityMonitor.upDown.delayUpBins.maxBin8

       32 bit unsigned wrappable counter."
   ::= {pr1645v2VrfRoutQmEntry 505940224}

pr1645v2VrfRoutQmUpDownDelayUpBinsMax OBJECT-TYPE
   SYNTAX      Integer32
   MAX-ACCESS  read-only
   STATUS      current
   DESCRIPTION
      "Path: vrfRouter.performance.qualityMonitor.upDown.delayUpBins.max

       unit name = sec
       formula = 1000 / ; 1000 *"
   ::= {pr1645v2VrfRoutQmEntry 505943552}

pr1645v2VrfRoutQmUpDownDelayUpBinsPlusMax OBJECT-TYPE
   SYNTAX      Counter32
   MAX-ACCESS  read-only
   STATUS      current
   DESCRIPTION
      "Path: vrfRouter.performance.qualityMonitor.upDown.delayUpBins.plusMax

       32 bit unsigned wrappable counter."
   ::= {pr1645v2VrfRoutQmEntry 505940480}

pr1645v2VrfRoutQmUpDownJitterUp OBJECT-TYPE
   SYNTAX      Integer32
   MAX-ACCESS  read-only
   STATUS      current
   DESCRIPTION
      "Path: vrfRouter.performance.qualityMonitor.upDown.jitterUp

       unit name = sec
       formula = 1000 / ; 1000 *"
   ::= {pr1645v2VrfRoutQmEntry 503775232}

pr1645v2VrfRoutQmUpDownJitterUpNegMax OBJECT-TYPE
   SYNTAX      Integer32
   MAX-ACCESS  read-only
   STATUS      current
   DESCRIPTION
      "Path: vrfRouter.performance.qualityMonitor.upDown.jitterUpNegMax

       unit name = sec
       formula = 1000 / ; 1000 *"
   ::= {pr1645v2VrfRoutQmEntry 503382016}

pr1645v2VrfRoutQmUpDownJitterUpAvrg OBJECT-TYPE
   SYNTAX      Integer32
   MAX-ACCESS  read-only
   STATUS      current
   DESCRIPTION
      "Path: vrfRouter.performance.qualityMonitor.upDown.jitterUpAvrg

       unit name = sec
       formula = 1000 / ; 1000 *"
   ::= {pr1645v2VrfRoutQmEntry 503447552}

pr1645v2VrfRoutQmUpDownJitterUpPosMax OBJECT-TYPE
   SYNTAX      Integer32
   MAX-ACCESS  read-only
   STATUS      current
   DESCRIPTION
      "Path: vrfRouter.performance.qualityMonitor.upDown.jitterUpPosMax

       unit name = sec
       formula = 1000 / ; 1000 *"
   ::= {pr1645v2VrfRoutQmEntry 503513088}

pr1645v2VrfRoutQmUpDownJitterUpBinsType OBJECT-TYPE
   SYNTAX      INTEGER
               {
               fd (1),
               fdr (2),
               notInUse (3),
               ifdv (4)
               }
   MAX-ACCESS  read-only
   STATUS      current
   DESCRIPTION
      "Path: vrfRouter.performance.qualityMonitor.upDown.jitterUpBins.type

       Possibilities:
               fd   (1)
               fdr   (2)
               notInUse   (3)
               ifdv   (4)"
   ::= {pr1645v2VrfRoutQmEntry 506074880}

pr1645v2VrfRoutQmUpDownJitterUpBinsMinMin OBJECT-TYPE
   SYNTAX      Counter32
   MAX-ACCESS  read-only
   STATUS      current
   DESCRIPTION
      "Path: vrfRouter.performance.qualityMonitor.upDown.jitterUpBins.minMin

       32 bit unsigned wrappable counter."
   ::= {pr1645v2VrfRoutQmEntry 506069248}

pr1645v2VrfRoutQmUpDownJitterUpBinsMin OBJECT-TYPE
   SYNTAX      Integer32
   MAX-ACCESS  read-only
   STATUS      current
   DESCRIPTION
      "Path: vrfRouter.performance.qualityMonitor.upDown.jitterUpBins.min

       unit name = sec
       formula = 1000 / ; 1000 *"
   ::= {pr1645v2VrfRoutQmEntry 506074368}

pr1645v2VrfRoutQmUpDownJitterUpBinsMinBin1 OBJECT-TYPE
   SYNTAX      Counter32
   MAX-ACCESS  read-only
   STATUS      current
   DESCRIPTION
      "Path: vrfRouter.performance.qualityMonitor.upDown.jitterUpBins.minBin1

       32 bit unsigned wrappable counter."
   ::= {pr1645v2VrfRoutQmEntry 506069504}

pr1645v2VrfRoutQmUpDownJitterUpBinsBin2 OBJECT-TYPE
   SYNTAX      Counter32
   MAX-ACCESS  read-only
   STATUS      current
   DESCRIPTION
      "Path: vrfRouter.performance.qualityMonitor.upDown.jitterUpBins.bin2

       32 bit unsigned wrappable counter."
   ::= {pr1645v2VrfRoutQmEntry 506069760}

pr1645v2VrfRoutQmUpDownJitterUpBinsBin3 OBJECT-TYPE
   SYNTAX      Counter32
   MAX-ACCESS  read-only
   STATUS      current
   DESCRIPTION
      "Path: vrfRouter.performance.qualityMonitor.upDown.jitterUpBins.bin3

       32 bit unsigned wrappable counter."
   ::= {pr1645v2VrfRoutQmEntry 506070016}

pr1645v2VrfRoutQmUpDownJitterUpBinsBin4 OBJECT-TYPE
   SYNTAX      Counter32
   MAX-ACCESS  read-only
   STATUS      current
   DESCRIPTION
      "Path: vrfRouter.performance.qualityMonitor.upDown.jitterUpBins.bin4

       32 bit unsigned wrappable counter."
   ::= {pr1645v2VrfRoutQmEntry 506070272}

pr1645v2VrfRoutQmUpDownJitterUpBinsBin5 OBJECT-TYPE
   SYNTAX      Counter32
   MAX-ACCESS  read-only
   STATUS      current
   DESCRIPTION
      "Path: vrfRouter.performance.qualityMonitor.upDown.jitterUpBins.bin5

       32 bit unsigned wrappable counter."
   ::= {pr1645v2VrfRoutQmEntry 506070528}

pr1645v2VrfRoutQmUpDownJitterUpBinsBin6 OBJECT-TYPE
   SYNTAX      Counter32
   MAX-ACCESS  read-only
   STATUS      current
   DESCRIPTION
      "Path: vrfRouter.performance.qualityMonitor.upDown.jitterUpBins.bin6

       32 bit unsigned wrappable counter."
   ::= {pr1645v2VrfRoutQmEntry 506070784}

pr1645v2VrfRoutQmUpDownJitterUpBinsBin7 OBJECT-TYPE
   SYNTAX      Counter32
   MAX-ACCESS  read-only
   STATUS      current
   DESCRIPTION
      "Path: vrfRouter.performance.qualityMonitor.upDown.jitterUpBins.bin7

       32 bit unsigned wrappable counter."
   ::= {pr1645v2VrfRoutQmEntry 506071040}

pr1645v2VrfRoutQmUpDownJitterUpBinsMaxBin8 OBJECT-TYPE
   SYNTAX      Counter32
   MAX-ACCESS  read-only
   STATUS      current
   DESCRIPTION
      "Path: vrfRouter.performance.qualityMonitor.upDown.jitterUpBins.maxBin8

       32 bit unsigned wrappable counter."
   ::= {pr1645v2VrfRoutQmEntry 506071296}

pr1645v2VrfRoutQmUpDownJitterUpBinsMax OBJECT-TYPE
   SYNTAX      Integer32
   MAX-ACCESS  read-only
   STATUS      current
   DESCRIPTION
      "Path: vrfRouter.performance.qualityMonitor.upDown.jitterUpBins.max

       unit name = sec
       formula = 1000 / ; 1000 *"
   ::= {pr1645v2VrfRoutQmEntry 506074624}

pr1645v2VrfRoutQmUpDownJitterUpBinsPlusMax OBJECT-TYPE
   SYNTAX      Counter32
   MAX-ACCESS  read-only
   STATUS      current
   DESCRIPTION
      "Path: vrfRouter.performance.qualityMonitor.upDown.jitterUpBins.plusMax

       32 bit unsigned wrappable counter."
   ::= {pr1645v2VrfRoutQmEntry 506071552}

pr1645v2VrfRoutQmUpDownLossDown OBJECT-TYPE
   SYNTAX      Counter32
   MAX-ACCESS  read-only
   STATUS      current
   DESCRIPTION
      "Path: vrfRouter.performance.qualityMonitor.upDown.lossDown

       32 bit unsigned wrappable counter."
   ::= {pr1645v2VrfRoutQmEntry 504102912}

pr1645v2VrfRoutQmUpDownLossDelayDown OBJECT-TYPE
   SYNTAX      Counter32
   MAX-ACCESS  read-only
   STATUS      current
   DESCRIPTION
      "Path: vrfRouter.performance.qualityMonitor.upDown.lossDelayDown

       32 bit unsigned wrappable counter."
   ::= {pr1645v2VrfRoutQmEntry 504168448}

pr1645v2VrfRoutQmUpDownDelayDownMin OBJECT-TYPE
   SYNTAX      Integer32
   MAX-ACCESS  read-only
   STATUS      current
   DESCRIPTION
      "Path: vrfRouter.performance.qualityMonitor.upDown.delayDownMin

       unit name = sec
       formula = 1000 / ; 1000 *"
   ::= {pr1645v2VrfRoutQmEntry 505610240}

pr1645v2VrfRoutQmUpDownDelayDownAvrg OBJECT-TYPE
   SYNTAX      Integer32
   MAX-ACCESS  read-only
   STATUS      current
   DESCRIPTION
      "Path: vrfRouter.performance.qualityMonitor.upDown.delayDownAvrg

       unit name = sec
       formula = 1000 / ; 1000 *"
   ::= {pr1645v2VrfRoutQmEntry 505675776}

pr1645v2VrfRoutQmUpDownDelayDownMax OBJECT-TYPE
   SYNTAX      Integer32
   MAX-ACCESS  read-only
   STATUS      current
   DESCRIPTION
      "Path: vrfRouter.performance.qualityMonitor.upDown.delayDownMax

       unit name = sec
       formula = 1000 / ; 1000 *"
   ::= {pr1645v2VrfRoutQmEntry 505741312}

pr1645v2VrfRoutQmUpDownDelayDownBinsType OBJECT-TYPE
   SYNTAX      INTEGER
               {
               fd (1),
               fdr (2),
               notInUse (3),
               ifdv (4)
               }
   MAX-ACCESS  read-only
   STATUS      current
   DESCRIPTION
      "Path: vrfRouter.performance.qualityMonitor.upDown.delayDownBins.type

       Possibilities:
               fd   (1)
               fdr   (2)
               notInUse   (3)
               ifdv   (4)"
   ::= {pr1645v2VrfRoutQmEntry 506009344}

pr1645v2VrfRoutQmUpDownDelayDownBinsMinMin OBJECT-TYPE
   SYNTAX      Counter32
   MAX-ACCESS  read-only
   STATUS      current
   DESCRIPTION
      "Path: vrfRouter.performance.qualityMonitor.upDown.delayDownBins.minMin

       32 bit unsigned wrappable counter."
   ::= {pr1645v2VrfRoutQmEntry 506003712}

pr1645v2VrfRoutQmUpDownDelayDownBinsMin OBJECT-TYPE
   SYNTAX      Integer32
   MAX-ACCESS  read-only
   STATUS      current
   DESCRIPTION
      "Path: vrfRouter.performance.qualityMonitor.upDown.delayDownBins.min

       unit name = sec
       formula = 1000 / ; 1000 *"
   ::= {pr1645v2VrfRoutQmEntry 506008832}

pr1645v2VrfRoutQmUpDownDelayDownBinsMinBin1 OBJECT-TYPE
   SYNTAX      Counter32
   MAX-ACCESS  read-only
   STATUS      current
   DESCRIPTION
      "Path: vrfRouter.performance.qualityMonitor.upDown.delayDownBins.minBin1

       32 bit unsigned wrappable counter."
   ::= {pr1645v2VrfRoutQmEntry 506003968}

pr1645v2VrfRoutQmUpDownDelayDownBinsBin2 OBJECT-TYPE
   SYNTAX      Counter32
   MAX-ACCESS  read-only
   STATUS      current
   DESCRIPTION
      "Path: vrfRouter.performance.qualityMonitor.upDown.delayDownBins.bin2

       32 bit unsigned wrappable counter."
   ::= {pr1645v2VrfRoutQmEntry 506004224}

pr1645v2VrfRoutQmUpDownDelayDownBinsBin3 OBJECT-TYPE
   SYNTAX      Counter32
   MAX-ACCESS  read-only
   STATUS      current
   DESCRIPTION
      "Path: vrfRouter.performance.qualityMonitor.upDown.delayDownBins.bin3

       32 bit unsigned wrappable counter."
   ::= {pr1645v2VrfRoutQmEntry 506004480}

pr1645v2VrfRoutQmUpDownDelayDownBinsBin4 OBJECT-TYPE
   SYNTAX      Counter32
   MAX-ACCESS  read-only
   STATUS      current
   DESCRIPTION
      "Path: vrfRouter.performance.qualityMonitor.upDown.delayDownBins.bin4

       32 bit unsigned wrappable counter."
   ::= {pr1645v2VrfRoutQmEntry 506004736}

pr1645v2VrfRoutQmUpDownDelayDownBinsBin5 OBJECT-TYPE
   SYNTAX      Counter32
   MAX-ACCESS  read-only
   STATUS      current
   DESCRIPTION
      "Path: vrfRouter.performance.qualityMonitor.upDown.delayDownBins.bin5

       32 bit unsigned wrappable counter."
   ::= {pr1645v2VrfRoutQmEntry 506004992}

pr1645v2VrfRoutQmUpDownDelayDownBinsBin6 OBJECT-TYPE
   SYNTAX      Counter32
   MAX-ACCESS  read-only
   STATUS      current
   DESCRIPTION
      "Path: vrfRouter.performance.qualityMonitor.upDown.delayDownBins.bin6

       32 bit unsigned wrappable counter."
   ::= {pr1645v2VrfRoutQmEntry 506005248}

pr1645v2VrfRoutQmUpDownDelayDownBinsBin7 OBJECT-TYPE
   SYNTAX      Counter32
   MAX-ACCESS  read-only
   STATUS      current
   DESCRIPTION
      "Path: vrfRouter.performance.qualityMonitor.upDown.delayDownBins.bin7

       32 bit unsigned wrappable counter."
   ::= {pr1645v2VrfRoutQmEntry 506005504}

pr1645v2VrfRoutQmUpDownDelayDownBinsMaxBin8 OBJECT-TYPE
   SYNTAX      Counter32
   MAX-ACCESS  read-only
   STATUS      current
   DESCRIPTION
      "Path: vrfRouter.performance.qualityMonitor.upDown.delayDownBins.maxBin8

       32 bit unsigned wrappable counter."
   ::= {pr1645v2VrfRoutQmEntry 506005760}

pr1645v2VrfRoutQmUpDownDelayDownBinsMax OBJECT-TYPE
   SYNTAX      Integer32
   MAX-ACCESS  read-only
   STATUS      current
   DESCRIPTION
      "Path: vrfRouter.performance.qualityMonitor.upDown.delayDownBins.max

       unit name = sec
       formula = 1000 / ; 1000 *"
   ::= {pr1645v2VrfRoutQmEntry 506009088}

pr1645v2VrfRoutQmUpDownDelayDownBinsPlusMax OBJECT-TYPE
   SYNTAX      Counter32
   MAX-ACCESS  read-only
   STATUS      current
   DESCRIPTION
      "Path: vrfRouter.performance.qualityMonitor.upDown.delayDownBins.plusMax

       32 bit unsigned wrappable counter."
   ::= {pr1645v2VrfRoutQmEntry 506006016}

pr1645v2VrfRoutQmUpDownJitterDown OBJECT-TYPE
   SYNTAX      Integer32
   MAX-ACCESS  read-only
   STATUS      current
   DESCRIPTION
      "Path: vrfRouter.performance.qualityMonitor.upDown.jitterDown

       unit name = sec
       formula = 1000 / ; 1000 *"
   ::= {pr1645v2VrfRoutQmEntry 503840768}

pr1645v2VrfRoutQmUpDownJitterDownNegMax OBJECT-TYPE
   SYNTAX      Integer32
   MAX-ACCESS  read-only
   STATUS      current
   DESCRIPTION
      "Path: vrfRouter.performance.qualityMonitor.upDown.jitterDownNegMax

       unit name = sec
       formula = 1000 / ; 1000 *"
   ::= {pr1645v2VrfRoutQmEntry 503578624}

pr1645v2VrfRoutQmUpDownJitterDownAvrg OBJECT-TYPE
   SYNTAX      Integer32
   MAX-ACCESS  read-only
   STATUS      current
   DESCRIPTION
      "Path: vrfRouter.performance.qualityMonitor.upDown.jitterDownAvrg

       unit name = sec
       formula = 1000 / ; 1000 *"
   ::= {pr1645v2VrfRoutQmEntry 503644160}

pr1645v2VrfRoutQmUpDownJitterDownPosMax OBJECT-TYPE
   SYNTAX      Integer32
   MAX-ACCESS  read-only
   STATUS      current
   DESCRIPTION
      "Path: vrfRouter.performance.qualityMonitor.upDown.jitterDownPosMax

       unit name = sec
       formula = 1000 / ; 1000 *"
   ::= {pr1645v2VrfRoutQmEntry 503709696}

pr1645v2VrfRoutQmUpDownJitterDownBinsType OBJECT-TYPE
   SYNTAX      INTEGER
               {
               fd (1),
               fdr (2),
               notInUse (3),
               ifdv (4)
               }
   MAX-ACCESS  read-only
   STATUS      current
   DESCRIPTION
      "Path: vrfRouter.performance.qualityMonitor.upDown.jitterDownBins.type

       Possibilities:
               fd   (1)
               fdr   (2)
               notInUse   (3)
               ifdv   (4)"
   ::= {pr1645v2VrfRoutQmEntry 506205952}

pr1645v2VrfRoutQmUpDownJitterDownBinsMinMin OBJECT-TYPE
   SYNTAX      Counter32
   MAX-ACCESS  read-only
   STATUS      current
   DESCRIPTION
      "Path: vrfRouter.performance.qualityMonitor.upDown.jitterDownBins.minMin

       32 bit unsigned wrappable counter."
   ::= {pr1645v2VrfRoutQmEntry 506200320}

pr1645v2VrfRoutQmUpDownJitterDownBinsMin OBJECT-TYPE
   SYNTAX      Integer32
   MAX-ACCESS  read-only
   STATUS      current
   DESCRIPTION
      "Path: vrfRouter.performance.qualityMonitor.upDown.jitterDownBins.min

       unit name = sec
       formula = 1000 / ; 1000 *"
   ::= {pr1645v2VrfRoutQmEntry 506205440}

pr1645v2VrfRoutQmUpDownJitterDownBinsMinBin1 OBJECT-TYPE
   SYNTAX      Counter32
   MAX-ACCESS  read-only
   STATUS      current
   DESCRIPTION
      "Path: vrfRouter.performance.qualityMonitor.upDown.jitterDownBins.minBin1

       32 bit unsigned wrappable counter."
   ::= {pr1645v2VrfRoutQmEntry 506200576}

pr1645v2VrfRoutQmUpDownJitterDownBinsBin2 OBJECT-TYPE
   SYNTAX      Counter32
   MAX-ACCESS  read-only
   STATUS      current
   DESCRIPTION
      "Path: vrfRouter.performance.qualityMonitor.upDown.jitterDownBins.bin2

       32 bit unsigned wrappable counter."
   ::= {pr1645v2VrfRoutQmEntry 506200832}

pr1645v2VrfRoutQmUpDownJitterDownBinsBin3 OBJECT-TYPE
   SYNTAX      Counter32
   MAX-ACCESS  read-only
   STATUS      current
   DESCRIPTION
      "Path: vrfRouter.performance.qualityMonitor.upDown.jitterDownBins.bin3

       32 bit unsigned wrappable counter."
   ::= {pr1645v2VrfRoutQmEntry 506201088}

pr1645v2VrfRoutQmUpDownJitterDownBinsBin4 OBJECT-TYPE
   SYNTAX      Counter32
   MAX-ACCESS  read-only
   STATUS      current
   DESCRIPTION
      "Path: vrfRouter.performance.qualityMonitor.upDown.jitterDownBins.bin4

       32 bit unsigned wrappable counter."
   ::= {pr1645v2VrfRoutQmEntry 506201344}

pr1645v2VrfRoutQmUpDownJitterDownBinsBin5 OBJECT-TYPE
   SYNTAX      Counter32
   MAX-ACCESS  read-only
   STATUS      current
   DESCRIPTION
      "Path: vrfRouter.performance.qualityMonitor.upDown.jitterDownBins.bin5

       32 bit unsigned wrappable counter."
   ::= {pr1645v2VrfRoutQmEntry 506201600}

pr1645v2VrfRoutQmUpDownJitterDownBinsBin6 OBJECT-TYPE
   SYNTAX      Counter32
   MAX-ACCESS  read-only
   STATUS      current
   DESCRIPTION
      "Path: vrfRouter.performance.qualityMonitor.upDown.jitterDownBins.bin6

       32 bit unsigned wrappable counter."
   ::= {pr1645v2VrfRoutQmEntry 506201856}

pr1645v2VrfRoutQmUpDownJitterDownBinsBin7 OBJECT-TYPE
   SYNTAX      Counter32
   MAX-ACCESS  read-only
   STATUS      current
   DESCRIPTION
      "Path: vrfRouter.performance.qualityMonitor.upDown.jitterDownBins.bin7

       32 bit unsigned wrappable counter."
   ::= {pr1645v2VrfRoutQmEntry 506202112}

pr1645v2VrfRoutQmUpDownJitterDownBinsMaxBin8 OBJECT-TYPE
   SYNTAX      Counter32
   MAX-ACCESS  read-only
   STATUS      current
   DESCRIPTION
      "Path: vrfRouter.performance.qualityMonitor.upDown.jitterDownBins.maxBin8

       32 bit unsigned wrappable counter."
   ::= {pr1645v2VrfRoutQmEntry 506202368}

pr1645v2VrfRoutQmUpDownJitterDownBinsMax OBJECT-TYPE
   SYNTAX      Integer32
   MAX-ACCESS  read-only
   STATUS      current
   DESCRIPTION
      "Path: vrfRouter.performance.qualityMonitor.upDown.jitterDownBins.max

       unit name = sec
       formula = 1000 / ; 1000 *"
   ::= {pr1645v2VrfRoutQmEntry 506205696}

pr1645v2VrfRoutQmUpDownJitterDownBinsPlusMax OBJECT-TYPE
   SYNTAX      Counter32
   MAX-ACCESS  read-only
   STATUS      current
   DESCRIPTION
      "Path: vrfRouter.performance.qualityMonitor.upDown.jitterDownBins.plusMax

       32 bit unsigned wrappable counter."
   ::= {pr1645v2VrfRoutQmEntry 506202624}

pr1645v2VrfRoutQmLastLogSysUpTime OBJECT-TYPE
   SYNTAX      TimeTicks
   MAX-ACCESS  read-only
   STATUS      current
   DESCRIPTION
      "Path: vrfRouter.performance.qualityMonitor.lastLog.sysUpTime

       Time in centi-second."
   ::= {pr1645v2VrfRoutQmEntry 671154176}

pr1645v2VrfRoutQmLastLogNbrTxPckt OBJECT-TYPE
   SYNTAX      Counter32
   MAX-ACCESS  read-only
   STATUS      current
   DESCRIPTION
      "Path: vrfRouter.performance.qualityMonitor.lastLog.nbrOfTxPackets

       32 bit unsigned wrappable counter."
   ::= {pr1645v2VrfRoutQmEntry 671285248}

pr1645v2VrfRoutQmLastLogNbrRxPckt OBJECT-TYPE
   SYNTAX      Counter32
   MAX-ACCESS  read-only
   STATUS      current
   DESCRIPTION
      "Path: vrfRouter.performance.qualityMonitor.lastLog.nbrOfRxPackets

       32 bit unsigned wrappable counter."
   ::= {pr1645v2VrfRoutQmEntry 671350784}

pr1645v2VrfRoutQmLastLogError OBJECT-TYPE
   SYNTAX      Counter32
   MAX-ACCESS  read-only
   STATUS      current
   DESCRIPTION
      "Path: vrfRouter.performance.qualityMonitor.lastLog.error

       32 bit unsigned wrappable counter."
   ::= {pr1645v2VrfRoutQmEntry 672202752}

pr1645v2VrfRoutQmLastLogLoss OBJECT-TYPE
   SYNTAX      Counter32
   MAX-ACCESS  read-only
   STATUS      current
   DESCRIPTION
      "Path: vrfRouter.performance.qualityMonitor.lastLog.loss

       32 bit unsigned wrappable counter."
   ::= {pr1645v2VrfRoutQmEntry 671481856}

pr1645v2VrfRoutQmLastLogLossDelay OBJECT-TYPE
   SYNTAX      Counter32
   MAX-ACCESS  read-only
   STATUS      current
   DESCRIPTION
      "Path: vrfRouter.performance.qualityMonitor.lastLog.lossDelay

       32 bit unsigned wrappable counter."
   ::= {pr1645v2VrfRoutQmEntry 672137216}

pr1645v2VrfRoutQmLastLogDelayMin OBJECT-TYPE
   SYNTAX      Integer32
   MAX-ACCESS  read-only
   STATUS      current
   DESCRIPTION
      "Path: vrfRouter.performance.qualityMonitor.lastLog.delayMin

       unit name = sec
       formula = 1000 / ; 1000 *"
   ::= {pr1645v2VrfRoutQmEntry 671809536}

pr1645v2VrfRoutQmLastLogDelayAvrg OBJECT-TYPE
   SYNTAX      Integer32
   MAX-ACCESS  read-only
   STATUS      current
   DESCRIPTION
      "Path: vrfRouter.performance.qualityMonitor.lastLog.delayAvrg

       unit name = sec
       formula = 1000 / ; 1000 *"
   ::= {pr1645v2VrfRoutQmEntry 671547392}

pr1645v2VrfRoutQmLastLogDelayMax OBJECT-TYPE
   SYNTAX      Integer32
   MAX-ACCESS  read-only
   STATUS      current
   DESCRIPTION
      "Path: vrfRouter.performance.qualityMonitor.lastLog.delayMax

       unit name = sec
       formula = 1000 / ; 1000 *"
   ::= {pr1645v2VrfRoutQmEntry 671612928}

pr1645v2VrfRoutQmLastLogJitterNegMax OBJECT-TYPE
   SYNTAX      Integer32
   MAX-ACCESS  read-only
   STATUS      current
   DESCRIPTION
      "Path: vrfRouter.performance.qualityMonitor.lastLog.jitterNegMax

       unit name = sec
       formula = 1000 / ; 1000 *"
   ::= {pr1645v2VrfRoutQmEntry 672006144}

pr1645v2VrfRoutQmLastLogJitterAvrg OBJECT-TYPE
   SYNTAX      Integer32
   MAX-ACCESS  read-only
   STATUS      current
   DESCRIPTION
      "Path: vrfRouter.performance.qualityMonitor.lastLog.jitterAvrg

       unit name = sec
       formula = 1000 / ; 1000 *"
   ::= {pr1645v2VrfRoutQmEntry 671678464}

pr1645v2VrfRoutQmLastLogJitterPosMax OBJECT-TYPE
   SYNTAX      Integer32
   MAX-ACCESS  read-only
   STATUS      current
   DESCRIPTION
      "Path: vrfRouter.performance.qualityMonitor.lastLog.jitterPosMax

       unit name = sec
       formula = 1000 / ; 1000 *"
   ::= {pr1645v2VrfRoutQmEntry 671744000}

pr1645v2VrfRoutQmLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouter.performance.qualityMonitor.lastLog.upDown.status

       Possibilities:
               notInUse   (3)
               onlyJitter   (1)
               jitterAndLoss   (2)
               all   (4)
               onlyLoss   (8)"
   ::= {pr1645v2VrfRoutQmEntry 673059840}

pr1645v2VrfRoutQmLastLogUpDownLossUp OBJECT-TYPE
   SYNTAX      Counter32
   MAX-ACCESS  read-only
   STATUS      current
   DESCRIPTION
      "Path: vrfRouter.performance.qualityMonitor.lastLog.upDown.lossUp

       32 bit unsigned wrappable counter."
   ::= {pr1645v2VrfRoutQmEntry 673057280}

pr1645v2VrfRoutQmLastLogUpDownLossDelayUp OBJECT-TYPE
   SYNTAX      Counter32
   MAX-ACCESS  read-only
   STATUS      current
   DESCRIPTION
      "Path: vrfRouter.performance.qualityMonitor.lastLog.upDown.lossDelayUp

       32 bit unsigned wrappable counter."
   ::= {pr1645v2VrfRoutQmEntry 673057536}

pr1645v2VrfRoutQmLastLogUpDownDelayUpMin OBJECT-TYPE
   SYNTAX      Integer32
   MAX-ACCESS  read-only
   STATUS      current
   DESCRIPTION
      "Path: vrfRouter.performance.qualityMonitor.lastLog.upDown.delayUpMin

       unit name = sec
       formula = 1000 / ; 1000 *"
   ::= {pr1645v2VrfRoutQmEntry 673062400}

pr1645v2VrfRoutQmLastLogUpDownDelayUpAvrg OBJECT-TYPE
   SYNTAX      Integer32
   MAX-ACCESS  read-only
   STATUS      current
   DESCRIPTION
      "Path: vrfRouter.performance.qualityMonitor.lastLog.upDown.delayUpAvrg

       unit name = sec
       formula = 1000 / ; 1000 *"
   ::= {pr1645v2VrfRoutQmEntry 673062656}

pr1645v2VrfRoutQmLastLogUpDownDelayUpMax OBJECT-TYPE
   SYNTAX      Integer32
   MAX-ACCESS  read-only
   STATUS      current
   DESCRIPTION
      "Path: vrfRouter.performance.qualityMonitor.lastLog.upDown.delayUpMax

       unit name = sec
       formula = 1000 / ; 1000 *"
   ::= {pr1645v2VrfRoutQmEntry 673062912}

pr1645v2VrfRoutQmLastLogUpDownJitterUpNegMax OBJECT-TYPE
   SYNTAX      Integer32
   MAX-ACCESS  read-only
   STATUS      current
   DESCRIPTION
      "Path: vrfRouter.performance.qualityMonitor.lastLog.upDown.jitterUpNegMax

       unit name = sec
       formula = 1000 / ; 1000 *"
   ::= {pr1645v2VrfRoutQmEntry 673054976}

pr1645v2VrfRoutQmLastLogUpDownJitterUpAvrg OBJECT-TYPE
   SYNTAX      Integer32
   MAX-ACCESS  read-only
   STATUS      current
   DESCRIPTION
      "Path: vrfRouter.performance.qualityMonitor.lastLog.upDown.jitterUpAvrg

       unit name = sec
       formula = 1000 / ; 1000 *"
   ::= {pr1645v2VrfRoutQmEntry 673055232}

pr1645v2VrfRoutQmLastLogUpDownJitterUpPosMax OBJECT-TYPE
   SYNTAX      Integer32
   MAX-ACCESS  read-only
   STATUS      current
   DESCRIPTION
      "Path: vrfRouter.performance.qualityMonitor.lastLog.upDown.jitterUpPosMax

       unit name = sec
       formula = 1000 / ; 1000 *"
   ::= {pr1645v2VrfRoutQmEntry 673055488}

pr1645v2VrfRoutQmLastLogUpDownLossDown OBJECT-TYPE
   SYNTAX      Counter32
   MAX-ACCESS  read-only
   STATUS      current
   DESCRIPTION
      "Path: vrfRouter.performance.qualityMonitor.lastLog.upDown.lossDown

       32 bit unsigned wrappable counter."
   ::= {pr1645v2VrfRoutQmEntry 673057792}

pr1645v2VrfRoutQmLastLogUpDownLossDelayDown OBJECT-TYPE
   SYNTAX      Counter32
   MAX-ACCESS  read-only
   STATUS      current
   DESCRIPTION
      "Path: vrfRouter.performance.qualityMonitor.lastLog.upDown.lossDelayDown

       32 bit unsigned wrappable counter."
   ::= {pr1645v2VrfRoutQmEntry 673058048}

pr1645v2VrfRoutQmLastLogUpDownDelayDownMin OBJECT-TYPE
   SYNTAX      Integer32
   MAX-ACCESS  read-only
   STATUS      current
   DESCRIPTION
      "Path: vrfRouter.performance.qualityMonitor.lastLog.upDown.delayDownMin

       unit name = sec
       formula = 1000 / ; 1000 *"
   ::= {pr1645v2VrfRoutQmEntry 673063680}

pr1645v2VrfRoutQmLastLogUpDownDelayDownAvrg OBJECT-TYPE
   SYNTAX      Integer32
   MAX-ACCESS  read-only
   STATUS      current
   DESCRIPTION
      "Path: vrfRouter.performance.qualityMonitor.lastLog.upDown.delayDownAvrg

       unit name = sec
       formula = 1000 / ; 1000 *"
   ::= {pr1645v2VrfRoutQmEntry 673063936}

pr1645v2VrfRoutQmLastLogUpDownDelayDownMax OBJECT-TYPE
   SYNTAX      Integer32
   MAX-ACCESS  read-only
   STATUS      current
   DESCRIPTION
      "Path: vrfRouter.performance.qualityMonitor.lastLog.upDown.delayDownMax

       unit name = sec
       formula = 1000 / ; 1000 *"
   ::= {pr1645v2VrfRoutQmEntry 673064192}

pr1645v2VrfRoutQmLastLogUpDownJitterDownNegMax OBJECT-TYPE
   SYNTAX      Integer32
   MAX-ACCESS  read-only
   STATUS      current
   DESCRIPTION
      "Path: vrfRouter.performance.qualityMonitor.lastLog.upDown.jitterDownNegMax

       unit name = sec
       formula = 1000 / ; 1000 *"
   ::= {pr1645v2VrfRoutQmEntry 673055744}

pr1645v2VrfRoutQmLastLogUpDownJitterDownAvrg OBJECT-TYPE
   SYNTAX      Integer32
   MAX-ACCESS  read-only
   STATUS      current
   DESCRIPTION
      "Path: vrfRouter.performance.qualityMonitor.lastLog.upDown.jitterDownAvrg

       unit name = sec
       formula = 1000 / ; 1000 *"
   ::= {pr1645v2VrfRoutQmEntry 673056000}

pr1645v2VrfRoutQmLastLogUpDownJitterDownPosMax OBJECT-TYPE
   SYNTAX      Integer32
   MAX-ACCESS  read-only
   STATUS      current
   DESCRIPTION
      "Path: vrfRouter.performance.qualityMonitor.lastLog.upDown.jitterDownPosMax

       unit name = sec
       formula = 1000 / ; 1000 *"
   ::= {pr1645v2VrfRoutQmEntry 673056256}

pr1645v2VrfRoutQmLastLogDate OBJECT-TYPE
   SYNTAX      DisplayString
   MAX-ACCESS  read-only
   STATUS      current
   DESCRIPTION
      "Path: vrfRouter.performance.qualityMonitor.lastLog.date"
   ::= {pr1645v2VrfRoutQmEntry 673120256}

pr1645v2VrfRoutQmAlarm OBJECT-TYPE
   SYNTAX      Integer32
   MAX-ACCESS  read-only
   STATUS      current
   DESCRIPTION
      "Path: vrfRouter.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1645v2VrfRoutQmEntry 251658240}

pr1645v2VrfRoutQmLastError OBJECT-TYPE
   SYNTAX      DisplayString
   MAX-ACCESS  read-only
   STATUS      current
   DESCRIPTION
      "Path: vrfRouter.performance.qualityMonitor.lastError"
   ::= {pr1645v2VrfRoutQmEntry 318767104}

pr1645v2VrfRoutQmLogging OBJECT-TYPE
   SYNTAX      SEQUENCE OF Pr1645v2VrfRoutQmLoggingEntry
   MAX-ACCESS  not-accessible
   STATUS      current
   DESCRIPTION
      ""
   ::= {pr1645v2VrfRoutQm 335544320}

pr1645v2VrfRoutQmLoggingEntry OBJECT-TYPE
   SYNTAX      Pr1645v2VrfRoutQmLoggingEntry
   MAX-ACCESS  not-accessible
   STATUS      current
   DESCRIPTION
      ""
   INDEX      { pr1645v2VrfRoutQmLoggingGlobalIx,
                pr1645v2VrfRoutQmTableIx,
                pr1645v2VrfRoutQmLoggingTableIx }
   ::= {pr1645v2VrfRoutQmLogging 1}

Pr1645v2VrfRoutQmLoggingEntry ::=
   SEQUENCE
      {
      pr1645v2VrfRoutQmLoggingGlobalIx
         GlobalIndex,
      pr1645v2VrfRoutQmLoggingTableIx
         TableIndex,
      pr1645v2VrfRoutQmLoggingSysUpTime
         TimeTicks,
      pr1645v2VrfRoutQmLoggingNbrTxPckt
         Counter32,
      pr1645v2VrfRoutQmLoggingNbrRxPckt
         Counter32,
      pr1645v2VrfRoutQmLoggingError
         Counter32,
      pr1645v2VrfRoutQmLoggingLoss
         Counter32,
      pr1645v2VrfRoutQmLoggingLossDelay
         Counter32,
      pr1645v2VrfRoutQmLoggingDelayMin
         Integer32,
      pr1645v2VrfRoutQmLoggingDelayAvrg
         Integer32,
      pr1645v2VrfRoutQmLoggingDelayMax
         Integer32,
      pr1645v2VrfRoutQmLoggingJitterNegMax
         Integer32,
      pr1645v2VrfRoutQmLoggingJitterAvrg
         Integer32,
      pr1645v2VrfRoutQmLoggingJitterPosMax
         Integer32,
      pr1645v2VrfRoutQmLoggingUpDownStatus
         INTEGER,
      pr1645v2VrfRoutQmLoggingUpDownLossUp
         Counter32,
      pr1645v2VrfRoutQmLoggingUpDownLossDelayUp
         Counter32,
      pr1645v2VrfRoutQmLoggingUpDownDelayUpMin
         Integer32,
      pr1645v2VrfRoutQmLoggingUpDownDelayUpAvrg
         Integer32,
      pr1645v2VrfRoutQmLoggingUpDownDelayUpMax
         Integer32,
      pr1645v2VrfRoutQmLoggingUpDownJitterUpNegMax
         Integer32,
      pr1645v2VrfRoutQmLoggingUpDownJitterUpAvrg
         Integer32,
      pr1645v2VrfRoutQmLoggingUpDownJitterUpPosMax
         Integer32,
      pr1645v2VrfRoutQmLoggingUpDownLossDown
         Counter32,
      pr1645v2VrfRoutQmLoggingUpDownLossDelayDown
         Counter32,
      pr1645v2VrfRoutQmLoggingUpDownDelayDownMin
         Integer32,
      pr1645v2VrfRoutQmLoggingUpDownDelayDownAvrg
         Integer32,
      pr1645v2VrfRoutQmLoggingUpDownDelayDownMax
         Integer32,
      pr1645v2VrfRoutQmLoggingUpDownJitterDownNegMax
         Integer32,
      pr1645v2VrfRoutQmLoggingUpDownJitterDownAvrg
         Integer32,
      pr1645v2VrfRoutQmLoggingUpDownJitterDownPosMax
         Integer32,
      pr1645v2VrfRoutQmLoggingDate
         DisplayString
      }

pr1645v2VrfRoutQmLoggingGlobalIx OBJECT-TYPE
   SYNTAX      GlobalIndex
   MAX-ACCESS  not-accessible
   STATUS      current
   DESCRIPTION
      "The value of the tlsCntTreeGlobalIndex of the MANAGED OBJECT."
   ::= {pr1645v2VrfRoutQmLoggingEntry 10}

pr1645v2VrfRoutQmLoggingTableIx OBJECT-TYPE
   SYNTAX      TableIndex
   MAX-ACCESS  not-accessible
   STATUS      current
   DESCRIPTION
      ""
   ::= {pr1645v2VrfRoutQmLoggingEntry 11}

pr1645v2VrfRoutQmLoggingSysUpTime OBJECT-TYPE
   SYNTAX      TimeTicks
   MAX-ACCESS  read-only
   STATUS      current
   DESCRIPTION
      "Path: vrfRouter.performance.qualityMonitor.logging.sysUpTime

       Time in centi-second."
   ::= {pr1645v2VrfRoutQmLoggingEntry 16777216}

pr1645v2VrfRoutQmLoggingNbrTxPckt OBJECT-TYPE
   SYNTAX      Counter32
   MAX-ACCESS  read-only
   STATUS      current
   DESCRIPTION
      "Path: vrfRouter.performance.qualityMonitor.logging.nbrOfTxPackets

       32 bit unsigned wrappable counter."
   ::= {pr1645v2VrfRoutQmLoggingEntry 50331648}

pr1645v2VrfRoutQmLoggingNbrRxPckt OBJECT-TYPE
   SYNTAX      Counter32
   MAX-ACCESS  read-only
   STATUS      current
   DESCRIPTION
      "Path: vrfRouter.performance.qualityMonitor.logging.nbrOfRxPackets

       32 bit unsigned wrappable counter."
   ::= {pr1645v2VrfRoutQmLoggingEntry 67108864}

pr1645v2VrfRoutQmLoggingError OBJECT-TYPE
   SYNTAX      Counter32
   MAX-ACCESS  read-only
   STATUS      current
   DESCRIPTION
      "Path: vrfRouter.performance.qualityMonitor.logging.error

       32 bit unsigned wrappable counter."
   ::= {pr1645v2VrfRoutQmLoggingEntry 285212672}

pr1645v2VrfRoutQmLoggingLoss OBJECT-TYPE
   SYNTAX      Counter32
   MAX-ACCESS  read-only
   STATUS      current
   DESCRIPTION
      "Path: vrfRouter.performance.qualityMonitor.logging.loss

       32 bit unsigned wrappable counter."
   ::= {pr1645v2VrfRoutQmLoggingEntry 100663296}

pr1645v2VrfRoutQmLoggingLossDelay OBJECT-TYPE
   SYNTAX      Counter32
   MAX-ACCESS  read-only
   STATUS      current
   DESCRIPTION
      "Path: vrfRouter.performance.qualityMonitor.logging.lossDelay

       32 bit unsigned wrappable counter."
   ::= {pr1645v2VrfRoutQmLoggingEntry 268435456}

pr1645v2VrfRoutQmLoggingDelayMin OBJECT-TYPE
   SYNTAX      Integer32
   MAX-ACCESS  read-only
   STATUS      current
   DESCRIPTION
      "Path: vrfRouter.performance.qualityMonitor.logging.delayMin

       unit name = sec
       formula = 1000 / ; 1000 *"
   ::= {pr1645v2VrfRoutQmLoggingEntry 184549376}

pr1645v2VrfRoutQmLoggingDelayAvrg OBJECT-TYPE
   SYNTAX      Integer32
   MAX-ACCESS  read-only
   STATUS      current
   DESCRIPTION
      "Path: vrfRouter.performance.qualityMonitor.logging.delayAvrg

       unit name = sec
       formula = 1000 / ; 1000 *"
   ::= {pr1645v2VrfRoutQmLoggingEntry 117440512}

pr1645v2VrfRoutQmLoggingDelayMax OBJECT-TYPE
   SYNTAX      Integer32
   MAX-ACCESS  read-only
   STATUS      current
   DESCRIPTION
      "Path: vrfRouter.performance.qualityMonitor.logging.delayMax

       unit name = sec
       formula = 1000 / ; 1000 *"
   ::= {pr1645v2VrfRoutQmLoggingEntry 134217728}

pr1645v2VrfRoutQmLoggingJitterNegMax OBJECT-TYPE
   SYNTAX      Integer32
   MAX-ACCESS  read-only
   STATUS      current
   DESCRIPTION
      "Path: vrfRouter.performance.qualityMonitor.logging.jitterNegMax

       unit name = sec
       formula = 1000 / ; 1000 *"
   ::= {pr1645v2VrfRoutQmLoggingEntry 234881024}

pr1645v2VrfRoutQmLoggingJitterAvrg OBJECT-TYPE
   SYNTAX      Integer32
   MAX-ACCESS  read-only
   STATUS      current
   DESCRIPTION
      "Path: vrfRouter.performance.qualityMonitor.logging.jitterAvrg

       unit name = sec
       formula = 1000 / ; 1000 *"
   ::= {pr1645v2VrfRoutQmLoggingEntry 150994944}

pr1645v2VrfRoutQmLoggingJitterPosMax OBJECT-TYPE
   SYNTAX      Integer32
   MAX-ACCESS  read-only
   STATUS      current
   DESCRIPTION
      "Path: vrfRouter.performance.qualityMonitor.logging.jitterPosMax

       unit name = sec
       formula = 1000 / ; 1000 *"
   ::= {pr1645v2VrfRoutQmLoggingEntry 167772160}

pr1645v2VrfRoutQmLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouter.performance.qualityMonitor.logging.upDown.status

       Possibilities:
               notInUse   (3)
               onlyJitter   (1)
               jitterAndLoss   (2)
               all   (4)
               onlyLoss   (8)"
   ::= {pr1645v2VrfRoutQmLoggingEntry 504627200}

pr1645v2VrfRoutQmLoggingUpDownLossUp OBJECT-TYPE
   SYNTAX      Counter32
   MAX-ACCESS  read-only
   STATUS      current
   DESCRIPTION
      "Path: vrfRouter.performance.qualityMonitor.logging.upDown.lossUp

       32 bit unsigned wrappable counter."
   ::= {pr1645v2VrfRoutQmLoggingEntry 503971840}

pr1645v2VrfRoutQmLoggingUpDownLossDelayUp OBJECT-TYPE
   SYNTAX      Counter32
   MAX-ACCESS  read-only
   STATUS      current
   DESCRIPTION
      "Path: vrfRouter.performance.qualityMonitor.logging.upDown.lossDelayUp

       32 bit unsigned wrappable counter."
   ::= {pr1645v2VrfRoutQmLoggingEntry 504037376}

pr1645v2VrfRoutQmLoggingUpDownDelayUpMin OBJECT-TYPE
   SYNTAX      Integer32
   MAX-ACCESS  read-only
   STATUS      current
   DESCRIPTION
      "Path: vrfRouter.performance.qualityMonitor.logging.upDown.delayUpMin

       unit name = sec
       formula = 1000 / ; 1000 *"
   ::= {pr1645v2VrfRoutQmLoggingEntry 505282560}

pr1645v2VrfRoutQmLoggingUpDownDelayUpAvrg OBJECT-TYPE
   SYNTAX      Integer32
   MAX-ACCESS  read-only
   STATUS      current
   DESCRIPTION
      "Path: vrfRouter.performance.qualityMonitor.logging.upDown.delayUpAvrg

       unit name = sec
       formula = 1000 / ; 1000 *"
   ::= {pr1645v2VrfRoutQmLoggingEntry 505348096}

pr1645v2VrfRoutQmLoggingUpDownDelayUpMax OBJECT-TYPE
   SYNTAX      Integer32
   MAX-ACCESS  read-only
   STATUS      current
   DESCRIPTION
      "Path: vrfRouter.performance.qualityMonitor.logging.upDown.delayUpMax

       unit name = sec
       formula = 1000 / ; 1000 *"
   ::= {pr1645v2VrfRoutQmLoggingEntry 505413632}

pr1645v2VrfRoutQmLoggingUpDownJitterUpNegMax OBJECT-TYPE
   SYNTAX      Integer32
   MAX-ACCESS  read-only
   STATUS      current
   DESCRIPTION
      "Path: vrfRouter.performance.qualityMonitor.logging.upDown.jitterUpNegMax

       unit name = sec
       formula = 1000 / ; 1000 *"
   ::= {pr1645v2VrfRoutQmLoggingEntry 503382016}

pr1645v2VrfRoutQmLoggingUpDownJitterUpAvrg OBJECT-TYPE
   SYNTAX      Integer32
   MAX-ACCESS  read-only
   STATUS      current
   DESCRIPTION
      "Path: vrfRouter.performance.qualityMonitor.logging.upDown.jitterUpAvrg

       unit name = sec
       formula = 1000 / ; 1000 *"
   ::= {pr1645v2VrfRoutQmLoggingEntry 503447552}

pr1645v2VrfRoutQmLoggingUpDownJitterUpPosMax OBJECT-TYPE
   SYNTAX      Integer32
   MAX-ACCESS  read-only
   STATUS      current
   DESCRIPTION
      "Path: vrfRouter.performance.qualityMonitor.logging.upDown.jitterUpPosMax

       unit name = sec
       formula = 1000 / ; 1000 *"
   ::= {pr1645v2VrfRoutQmLoggingEntry 503513088}

pr1645v2VrfRoutQmLoggingUpDownLossDown OBJECT-TYPE
   SYNTAX      Counter32
   MAX-ACCESS  read-only
   STATUS      current
   DESCRIPTION
      "Path: vrfRouter.performance.qualityMonitor.logging.upDown.lossDown

       32 bit unsigned wrappable counter."
   ::= {pr1645v2VrfRoutQmLoggingEntry 504102912}

pr1645v2VrfRoutQmLoggingUpDownLossDelayDown OBJECT-TYPE
   SYNTAX      Counter32
   MAX-ACCESS  read-only
   STATUS      current
   DESCRIPTION
      "Path: vrfRouter.performance.qualityMonitor.logging.upDown.lossDelayDown

       32 bit unsigned wrappable counter."
   ::= {pr1645v2VrfRoutQmLoggingEntry 504168448}

pr1645v2VrfRoutQmLoggingUpDownDelayDownMin OBJECT-TYPE
   SYNTAX      Integer32
   MAX-ACCESS  read-only
   STATUS      current
   DESCRIPTION
      "Path: vrfRouter.performance.qualityMonitor.logging.upDown.delayDownMin

       unit name = sec
       formula = 1000 / ; 1000 *"
   ::= {pr1645v2VrfRoutQmLoggingEntry 505610240}

pr1645v2VrfRoutQmLoggingUpDownDelayDownAvrg OBJECT-TYPE
   SYNTAX      Integer32
   MAX-ACCESS  read-only
   STATUS      current
   DESCRIPTION
      "Path: vrfRouter.performance.qualityMonitor.logging.upDown.delayDownAvrg

       unit name = sec
       formula = 1000 / ; 1000 *"
   ::= {pr1645v2VrfRoutQmLoggingEntry 505675776}

pr1645v2VrfRoutQmLoggingUpDownDelayDownMax OBJECT-TYPE
   SYNTAX      Integer32
   MAX-ACCESS  read-only
   STATUS      current
   DESCRIPTION
      "Path: vrfRouter.performance.qualityMonitor.logging.upDown.delayDownMax

       unit name = sec
       formula = 1000 / ; 1000 *"
   ::= {pr1645v2VrfRoutQmLoggingEntry 505741312}

pr1645v2VrfRoutQmLoggingUpDownJitterDownNegMax OBJECT-TYPE
   SYNTAX      Integer32
   MAX-ACCESS  read-only
   STATUS      current
   DESCRIPTION
      "Path: vrfRouter.performance.qualityMonitor.logging.upDown.jitterDownNegMax

       unit name = sec
       formula = 1000 / ; 1000 *"
   ::= {pr1645v2VrfRoutQmLoggingEntry 503578624}

pr1645v2VrfRoutQmLoggingUpDownJitterDownAvrg OBJECT-TYPE
   SYNTAX      Integer32
   MAX-ACCESS  read-only
   STATUS      current
   DESCRIPTION
      "Path: vrfRouter.performance.qualityMonitor.logging.upDown.jitterDownAvrg

       unit name = sec
       formula = 1000 / ; 1000 *"
   ::= {pr1645v2VrfRoutQmLoggingEntry 503644160}

pr1645v2VrfRoutQmLoggingUpDownJitterDownPosMax OBJECT-TYPE
   SYNTAX      Integer32
   MAX-ACCESS  read-only
   STATUS      current
   DESCRIPTION
      "Path: vrfRouter.performance.qualityMonitor.logging.upDown.jitterDownPosMax

       unit name = sec
       formula = 1000 / ; 1000 *"
   ::= {pr1645v2VrfRoutQmLoggingEntry 503709696}

pr1645v2VrfRoutQmLoggingDate OBJECT-TYPE
   SYNTAX      DisplayString
   MAX-ACCESS  read-only
   STATUS      current
   DESCRIPTION
      "Path: vrfRouter.performance.qualityMonitor.logging.date"
   ::= {pr1645v2VrfRoutQmLoggingEntry 520093696}

pr1645v2VrfRoutQmLoggingBin OBJECT-TYPE
   SYNTAX      SEQUENCE OF Pr1645v2VrfRoutQmLoggingBinEntry
   MAX-ACCESS  not-accessible
   STATUS      current
   DESCRIPTION
      ""
   ::= {pr1645v2VrfRoutQm 337641472}

pr1645v2VrfRoutQmLoggingBinEntry OBJECT-TYPE
   SYNTAX      Pr1645v2VrfRoutQmLoggingBinEntry
   MAX-ACCESS  not-accessible
   STATUS      current
   DESCRIPTION
      ""
   INDEX      { pr1645v2VrfRoutQmLoggingBinGlobalIx,
                pr1645v2VrfRoutQmTableIx,
                pr1645v2VrfRoutQmLoggingTableIx,
                pr1645v2VrfRoutQmLoggingBinTableIx }
   ::= {pr1645v2VrfRoutQmLoggingBin 1}

Pr1645v2VrfRoutQmLoggingBinEntry ::=
   SEQUENCE
      {
      pr1645v2VrfRoutQmLoggingBinGlobalIx
         GlobalIndex,
      pr1645v2VrfRoutQmLoggingBinTableIx
         TableIndex,
      pr1645v2VrfRoutQmLoggingBinName
         INTEGER,
      pr1645v2VrfRoutQmLoggingBinType
         INTEGER,
      pr1645v2VrfRoutQmLoggingBinMinMin
         Counter32,
      pr1645v2VrfRoutQmLoggingBinMin
         Integer32,
      pr1645v2VrfRoutQmLoggingBinMinBin1
         Counter32,
      pr1645v2VrfRoutQmLoggingBinBin2
         Counter32,
      pr1645v2VrfRoutQmLoggingBinBin3
         Counter32,
      pr1645v2VrfRoutQmLoggingBinBin4
         Counter32,
      pr1645v2VrfRoutQmLoggingBinBin5
         Counter32,
      pr1645v2VrfRoutQmLoggingBinBin6
         Counter32,
      pr1645v2VrfRoutQmLoggingBinBin7
         Counter32,
      pr1645v2VrfRoutQmLoggingBinMaxBin8
         Counter32,
      pr1645v2VrfRoutQmLoggingBinMax
         Integer32,
      pr1645v2VrfRoutQmLoggingBinPlusMax
         Counter32
      }

pr1645v2VrfRoutQmLoggingBinGlobalIx OBJECT-TYPE
   SYNTAX      GlobalIndex
   MAX-ACCESS  not-accessible
   STATUS      current
   DESCRIPTION
      "The value of the tlsCntTreeGlobalIndex of the MANAGED OBJECT."
   ::= {pr1645v2VrfRoutQmLoggingBinEntry 10}

pr1645v2VrfRoutQmLoggingBinTableIx OBJECT-TYPE
   SYNTAX      TableIndex
   MAX-ACCESS  not-accessible
   STATUS      current
   DESCRIPTION
      ""
   ::= {pr1645v2VrfRoutQmLoggingBinEntry 11}

pr1645v2VrfRoutQmLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfRouter.performance.qualityMonitor.logging.bin.name

       Possibilities:
               delay   (1)
               delayUp   (2)
               delayDown   (3)
               jitter   (4)
               jitterUp   (5)
               jitterDown   (6)"
   ::= {pr1645v2VrfRoutQmLoggingBinEntry 503316480}

pr1645v2VrfRoutQmLoggingBinType OBJECT-TYPE
   SYNTAX      INTEGER
               {
               fd (1),
               fdr (2),
               notInUse (3),
               ifdv (4)
               }
   MAX-ACCESS  read-only
   STATUS      current
   DESCRIPTION
      "Path: vrfRouter.performance.qualityMonitor.logging.bin.type

       Possibilities:
               fd   (1)
               fdr   (2)
               notInUse   (3)
               ifdv   (4)"
   ::= {pr1645v2VrfRoutQmLoggingBinEntry 520093696}

pr1645v2VrfRoutQmLoggingBinMinMin OBJECT-TYPE
   SYNTAX      Counter32
   MAX-ACCESS  read-only
   STATUS      current
   DESCRIPTION
      "Path: vrfRouter.performance.qualityMonitor.logging.bin.minMin

       32 bit unsigned wrappable counter."
   ::= {pr1645v2VrfRoutQmLoggingBinEntry 16777216}

pr1645v2VrfRoutQmLoggingBinMin OBJECT-TYPE
   SYNTAX      Integer32
   MAX-ACCESS  read-only
   STATUS      current
   DESCRIPTION
      "Path: vrfRouter.performance.qualityMonitor.logging.bin.min

       unit name = sec
       formula = 1000 / ; 1000 *"
   ::= {pr1645v2VrfRoutQmLoggingBinEntry 352321536}

pr1645v2VrfRoutQmLoggingBinMinBin1 OBJECT-TYPE
   SYNTAX      Counter32
   MAX-ACCESS  read-only
   STATUS      current
   DESCRIPTION
      "Path: vrfRouter.performance.qualityMonitor.logging.bin.minBin1

       32 bit unsigned wrappable counter."
   ::= {pr1645v2VrfRoutQmLoggingBinEntry 33554432}

pr1645v2VrfRoutQmLoggingBinBin2 OBJECT-TYPE
   SYNTAX      Counter32
   MAX-ACCESS  read-only
   STATUS      current
   DESCRIPTION
      "Path: vrfRouter.performance.qualityMonitor.logging.bin.bin2

       32 bit unsigned wrappable counter."
   ::= {pr1645v2VrfRoutQmLoggingBinEntry 50331648}

pr1645v2VrfRoutQmLoggingBinBin3 OBJECT-TYPE
   SYNTAX      Counter32
   MAX-ACCESS  read-only
   STATUS      current
   DESCRIPTION
      "Path: vrfRouter.performance.qualityMonitor.logging.bin.bin3

       32 bit unsigned wrappable counter."
   ::= {pr1645v2VrfRoutQmLoggingBinEntry 67108864}

pr1645v2VrfRoutQmLoggingBinBin4 OBJECT-TYPE
   SYNTAX      Counter32
   MAX-ACCESS  read-only
   STATUS      current
   DESCRIPTION
      "Path: vrfRouter.performance.qualityMonitor.logging.bin.bin4

       32 bit unsigned wrappable counter."
   ::= {pr1645v2VrfRoutQmLoggingBinEntry 83886080}

pr1645v2VrfRoutQmLoggingBinBin5 OBJECT-TYPE
   SYNTAX      Counter32
   MAX-ACCESS  read-only
   STATUS      current
   DESCRIPTION
      "Path: vrfRouter.performance.qualityMonitor.logging.bin.bin5

       32 bit unsigned wrappable counter."
   ::= {pr1645v2VrfRoutQmLoggingBinEntry 100663296}

pr1645v2VrfRoutQmLoggingBinBin6 OBJECT-TYPE
   SYNTAX      Counter32
   MAX-ACCESS  read-only
   STATUS      current
   DESCRIPTION
      "Path: vrfRouter.performance.qualityMonitor.logging.bin.bin6

       32 bit unsigned wrappable counter."
   ::= {pr1645v2VrfRoutQmLoggingBinEntry 117440512}

pr1645v2VrfRoutQmLoggingBinBin7 OBJECT-TYPE
   SYNTAX      Counter32
   MAX-ACCESS  read-only
   STATUS      current
   DESCRIPTION
      "Path: vrfRouter.performance.qualityMonitor.logging.bin.bin7

       32 bit unsigned wrappable counter."
   ::= {pr1645v2VrfRoutQmLoggingBinEntry 134217728}

pr1645v2VrfRoutQmLoggingBinMaxBin8 OBJECT-TYPE
   SYNTAX      Counter32
   MAX-ACCESS  read-only
   STATUS      current
   DESCRIPTION
      "Path: vrfRouter.performance.qualityMonitor.logging.bin.maxBin8

       32 bit unsigned wrappable counter."
   ::= {pr1645v2VrfRoutQmLoggingBinEntry 150994944}

pr1645v2VrfRoutQmLoggingBinMax OBJECT-TYPE
   SYNTAX      Integer32
   MAX-ACCESS  read-only
   STATUS      current
   DESCRIPTION
      "Path: vrfRouter.performance.qualityMonitor.logging.bin.max

       unit name = sec
       formula = 1000 / ; 1000 *"
   ::= {pr1645v2VrfRoutQmLoggingBinEntry 369098752}

pr1645v2VrfRoutQmLoggingBinPlusMax OBJECT-TYPE
   SYNTAX      Counter32
   MAX-ACCESS  read-only
   STATUS      current
   DESCRIPTION
      "Path: vrfRouter.performance.qualityMonitor.logging.bin.plusMax

       32 bit unsigned wrappable counter."
   ::= {pr1645v2VrfRoutQmLoggingBinEntry 167772160}

pr1645v2VrfRoutQmLastLogBin OBJECT-TYPE
   SYNTAX      SEQUENCE OF Pr1645v2VrfRoutQmLastLogBinEntry
   MAX-ACCESS  not-accessible
   STATUS      current
   DESCRIPTION
      ""
   ::= {pr1645v2VrfRoutQm 673185792}

pr1645v2VrfRoutQmLastLogBinEntry OBJECT-TYPE
   SYNTAX      Pr1645v2VrfRoutQmLastLogBinEntry
   MAX-ACCESS  not-accessible
   STATUS      current
   DESCRIPTION
      ""
   INDEX      { pr1645v2VrfRoutQmLastLogBinGlobalIx,
                pr1645v2VrfRoutQmTableIx,
                pr1645v2VrfRoutQmLastLogBinTableIx }
   ::= {pr1645v2VrfRoutQmLastLogBin 1}

Pr1645v2VrfRoutQmLastLogBinEntry ::=
   SEQUENCE
      {
      pr1645v2VrfRoutQmLastLogBinGlobalIx
         GlobalIndex,
      pr1645v2VrfRoutQmLastLogBinTableIx
         TableIndex,
      pr1645v2VrfRoutQmLastLogBinName
         INTEGER,
      pr1645v2VrfRoutQmLastLogBinType
         INTEGER,
      pr1645v2VrfRoutQmLastLogBinMinMin
         Counter32,
      pr1645v2VrfRoutQmLastLogBinMin
         Integer32,
      pr1645v2VrfRoutQmLastLogBinMinBin1
         Counter32,
      pr1645v2VrfRoutQmLastLogBinBin2
         Counter32,
      pr1645v2VrfRoutQmLastLogBinBin3
         Counter32,
      pr1645v2VrfRoutQmLastLogBinBin4
         Counter32,
      pr1645v2VrfRoutQmLastLogBinBin5
         Counter32,
      pr1645v2VrfRoutQmLastLogBinBin6
         Counter32,
      pr1645v2VrfRoutQmLastLogBinBin7
         Counter32,
      pr1645v2VrfRoutQmLastLogBinMaxBin8
         Counter32,
      pr1645v2VrfRoutQmLastLogBinMax
         Integer32,
      pr1645v2VrfRoutQmLastLogBinPlusMax
         Counter32
      }

pr1645v2VrfRoutQmLastLogBinGlobalIx OBJECT-TYPE
   SYNTAX      GlobalIndex
   MAX-ACCESS  not-accessible
   STATUS      current
   DESCRIPTION
      "The value of the tlsCntTreeGlobalIndex of the MANAGED OBJECT."
   ::= {pr1645v2VrfRoutQmLastLogBinEntry 10}

pr1645v2VrfRoutQmLastLogBinTableIx OBJECT-TYPE
   SYNTAX      TableIndex
   MAX-ACCESS  not-accessible
   STATUS      current
   DESCRIPTION
      ""
   ::= {pr1645v2VrfRoutQmLastLogBinEntry 11}

pr1645v2VrfRoutQmLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfRouter.performance.qualityMonitor.lastLog.bin.name

       Possibilities:
               delay   (1)
               delayUp   (2)
               delayDown   (3)
               jitter   (4)
               jitterUp   (5)
               jitterDown   (6)"
   ::= {pr1645v2VrfRoutQmLastLogBinEntry 503316480}

pr1645v2VrfRoutQmLastLogBinType OBJECT-TYPE
   SYNTAX      INTEGER
               {
               fd (1),
               fdr (2),
               notInUse (3),
               ifdv (4)
               }
   MAX-ACCESS  read-only
   STATUS      current
   DESCRIPTION
      "Path: vrfRouter.performance.qualityMonitor.lastLog.bin.type

       Possibilities:
               fd   (1)
               fdr   (2)
               notInUse   (3)
               ifdv   (4)"
   ::= {pr1645v2VrfRoutQmLastLogBinEntry 520093696}

pr1645v2VrfRoutQmLastLogBinMinMin OBJECT-TYPE
   SYNTAX      Counter32
   MAX-ACCESS  read-only
   STATUS      current
   DESCRIPTION
      "Path: vrfRouter.performance.qualityMonitor.lastLog.bin.minMin

       32 bit unsigned wrappable counter."
   ::= {pr1645v2VrfRoutQmLastLogBinEntry 16777216}

pr1645v2VrfRoutQmLastLogBinMin OBJECT-TYPE
   SYNTAX      Integer32
   MAX-ACCESS  read-only
   STATUS      current
   DESCRIPTION
      "Path: vrfRouter.performance.qualityMonitor.lastLog.bin.min

       unit name = sec
       formula = 1000 / ; 1000 *"
   ::= {pr1645v2VrfRoutQmLastLogBinEntry 352321536}

pr1645v2VrfRoutQmLastLogBinMinBin1 OBJECT-TYPE
   SYNTAX      Counter32
   MAX-ACCESS  read-only
   STATUS      current
   DESCRIPTION
      "Path: vrfRouter.performance.qualityMonitor.lastLog.bin.minBin1

       32 bit unsigned wrappable counter."
   ::= {pr1645v2VrfRoutQmLastLogBinEntry 33554432}

pr1645v2VrfRoutQmLastLogBinBin2 OBJECT-TYPE
   SYNTAX      Counter32
   MAX-ACCESS  read-only
   STATUS      current
   DESCRIPTION
      "Path: vrfRouter.performance.qualityMonitor.lastLog.bin.bin2

       32 bit unsigned wrappable counter."
   ::= {pr1645v2VrfRoutQmLastLogBinEntry 50331648}

pr1645v2VrfRoutQmLastLogBinBin3 OBJECT-TYPE
   SYNTAX      Counter32
   MAX-ACCESS  read-only
   STATUS      current
   DESCRIPTION
      "Path: vrfRouter.performance.qualityMonitor.lastLog.bin.bin3

       32 bit unsigned wrappable counter."
   ::= {pr1645v2VrfRoutQmLastLogBinEntry 67108864}

pr1645v2VrfRoutQmLastLogBinBin4 OBJECT-TYPE
   SYNTAX      Counter32
   MAX-ACCESS  read-only
   STATUS      current
   DESCRIPTION
      "Path: vrfRouter.performance.qualityMonitor.lastLog.bin.bin4

       32 bit unsigned wrappable counter."
   ::= {pr1645v2VrfRoutQmLastLogBinEntry 83886080}

pr1645v2VrfRoutQmLastLogBinBin5 OBJECT-TYPE
   SYNTAX      Counter32
   MAX-ACCESS  read-only
   STATUS      current
   DESCRIPTION
      "Path: vrfRouter.performance.qualityMonitor.lastLog.bin.bin5

       32 bit unsigned wrappable counter."
   ::= {pr1645v2VrfRoutQmLastLogBinEntry 100663296}

pr1645v2VrfRoutQmLastLogBinBin6 OBJECT-TYPE
   SYNTAX      Counter32
   MAX-ACCESS  read-only
   STATUS      current
   DESCRIPTION
      "Path: vrfRouter.performance.qualityMonitor.lastLog.bin.bin6

       32 bit unsigned wrappable counter."
   ::= {pr1645v2VrfRoutQmLastLogBinEntry 117440512}

pr1645v2VrfRoutQmLastLogBinBin7 OBJECT-TYPE
   SYNTAX      Counter32
   MAX-ACCESS  read-only
   STATUS      current
   DESCRIPTION
      "Path: vrfRouter.performance.qualityMonitor.lastLog.bin.bin7

       32 bit unsigned wrappable counter."
   ::= {pr1645v2VrfRoutQmLastLogBinEntry 134217728}

pr1645v2VrfRoutQmLastLogBinMaxBin8 OBJECT-TYPE
   SYNTAX      Counter32
   MAX-ACCESS  read-only
   STATUS      current
   DESCRIPTION
      "Path: vrfRouter.performance.qualityMonitor.lastLog.bin.maxBin8

       32 bit unsigned wrappable counter."
   ::= {pr1645v2VrfRoutQmLastLogBinEntry 150994944}

pr1645v2VrfRoutQmLastLogBinMax OBJECT-TYPE
   SYNTAX      Integer32
   MAX-ACCESS  read-only
   STATUS      current
   DESCRIPTION
      "Path: vrfRouter.performance.qualityMonitor.lastLog.bin.max

       unit name = sec
       formula = 1000 / ; 1000 *"
   ::= {pr1645v2VrfRoutQmLastLogBinEntry 369098752}

pr1645v2VrfRoutQmLastLogBinPlusMax OBJECT-TYPE
   SYNTAX      Counter32
   MAX-ACCESS  read-only
   STATUS      current
   DESCRIPTION
      "Path: vrfRouter.performance.qualityMonitor.lastLog.bin.plusMax

       32 bit unsigned wrappable counter."
   ::= {pr1645v2VrfRoutQmLastLogBinEntry 167772160}


pr1645v2VrfRoutUdpServer OBJECT IDENTIFIER ::= {pr1645v2VrfRout 16}

pr1645v2VrfRoutUdpServerSSCTable OBJECT-TYPE
   SYNTAX      SEQUENCE OF Pr1645v2VrfRoutUdpServerEntry
   MAX-ACCESS  not-accessible
   STATUS      current
   DESCRIPTION
      "udpServer"
   ::= {pr1645v2VrfRoutUdpServer 1}

pr1645v2VrfRoutUdpServerEntry OBJECT-TYPE
   SYNTAX      Pr1645v2VrfRoutUdpServerEntry
   MAX-ACCESS  not-accessible
   STATUS      current
   DESCRIPTION
      ""
   INDEX      { pr1645v2VrfRoutUdpServerGlobalIx,
                pr1645v2VrfRoutUdpServerTableIx }
   ::= {pr1645v2VrfRoutUdpServerSSCTable 1}

Pr1645v2VrfRoutUdpServerEntry ::=
   SEQUENCE
      {
      pr1645v2VrfRoutUdpServerGlobalIx
         GlobalIndex,
      pr1645v2VrfRoutUdpServerTableIx
         TableIndex,
      pr1645v2VrfRoutUdpServerDestinationPort
         Integer32,
      pr1645v2VrfRoutUdpServerActiveSessions
         Gauge32,
      pr1645v2VrfRoutUdpServerNbrPckt
         Counter64
      }

pr1645v2VrfRoutUdpServerGlobalIx OBJECT-TYPE
   SYNTAX      GlobalIndex
   MAX-ACCESS  not-accessible
   STATUS      current
   DESCRIPTION
      "The value of the tlsCntTreeGlobalIndex of the MANAGED OBJECT."
   ::= {pr1645v2VrfRoutUdpServerEntry 10}

pr1645v2VrfRoutUdpServerTableIx OBJECT-TYPE
   SYNTAX      TableIndex
   MAX-ACCESS  not-accessible
   STATUS      current
   DESCRIPTION
      ""
   ::= {pr1645v2VrfRoutUdpServerEntry 11}

pr1645v2VrfRoutUdpServerDestinationPort OBJECT-TYPE
   SYNTAX      Integer32
   MAX-ACCESS  read-only
   STATUS      current
   DESCRIPTION
      "Path: vrfRouter.performance.udpServer.destinationPort"
   ::= {pr1645v2VrfRoutUdpServerEntry 16777216}

pr1645v2VrfRoutUdpServerActiveSessions OBJECT-TYPE
   SYNTAX      Gauge32
   MAX-ACCESS  read-only
   STATUS      current
   DESCRIPTION
      "Path: vrfRouter.performance.udpServer.activeSessions

       32 bit unsigned gauge value."
   ::= {pr1645v2VrfRoutUdpServerEntry 33554432}

pr1645v2VrfRoutUdpServerNbrPckt OBJECT-TYPE
   SYNTAX      Counter64
   MAX-ACCESS  read-only
   STATUS      current
   DESCRIPTION
      "Path: vrfRouter.performance.udpServer.nbrOfPackets

       64 bit unsigned wrappable counter."
   ::= {pr1645v2VrfRoutUdpServerEntry 50331648}

pr1645v2VrfRoutUdpServerSessions OBJECT-TYPE
   SYNTAX      SEQUENCE OF Pr1645v2VrfRoutUdpServerSessionsEntry
   MAX-ACCESS  not-accessible
   STATUS      current
   DESCRIPTION
      ""
   ::= {pr1645v2VrfRoutUdpServer 67108864}

pr1645v2VrfRoutUdpServerSessionsEntry OBJECT-TYPE
   SYNTAX      Pr1645v2VrfRoutUdpServerSessionsEntry
   MAX-ACCESS  not-accessible
   STATUS      current
   DESCRIPTION
      ""
   INDEX      { pr1645v2VrfRoutUdpServerSessionsGlobalIx,
                pr1645v2VrfRoutUdpServerTableIx,
                pr1645v2VrfRoutUdpServerSessionsTableIx }
   ::= {pr1645v2VrfRoutUdpServerSessions 1}

Pr1645v2VrfRoutUdpServerSessionsEntry ::=
   SEQUENCE
      {
      pr1645v2VrfRoutUdpServerSessionsGlobalIx
         GlobalIndex,
      pr1645v2VrfRoutUdpServerSessionsTableIx
         TableIndex,
      pr1645v2VrfRoutUdpServerSessionsSourceIpAddress
         IpAddress,
      pr1645v2VrfRoutUdpServerSessionsSourcePort
         Integer32,
      pr1645v2VrfRoutUdpServerSessionsNbrPckt
         Counter64,
      pr1645v2VrfRoutUdpServerSessionsFirstActivityTime
         TimeTicks,
      pr1645v2VrfRoutUdpServerSessionsLastActivityTime
         TimeTicks,
      pr1645v2VrfRoutUdpServerSessionsHalfWayStatus
         INTEGER,
      pr1645v2VrfRoutUdpServerSessionsHalfWayReceived
         Counter64,
      pr1645v2VrfRoutUdpServerSessionsHalfWayPacketLoss
         Counter64,
      pr1645v2VrfRoutUdpServerSessionsHalfWayOutOfSequence
         Counter64,
      pr1645v2VrfRoutUdpServerSessionsHalfWayCrcErrors
         Counter64,
      pr1645v2VrfRoutUdpServerSessionsHalfWayLengthErrors
         Counter64,
      pr1645v2VrfRoutUdpServerSessionsHalfWayJitter
         INTEGER,
      pr1645v2VrfRoutUdpServerSessionsHalfWayJitterAvrg
         INTEGER,
      pr1645v2VrfRoutUdpServerSessionsHalfWayJitterMax
         INTEGER,
      pr1645v2VrfRoutUdpServerSessionsHalfWayReceivedLength
         Counter64,
      pr1645v2VrfRoutUdpServerSessionsHalfWayLastFault
         Counter64,
      pr1645v2VrfRoutUdpServerSessionsHalfWayLastSeqnr
         Counter64
      }

pr1645v2VrfRoutUdpServerSessionsGlobalIx OBJECT-TYPE
   SYNTAX      GlobalIndex
   MAX-ACCESS  not-accessible
   STATUS      current
   DESCRIPTION
      "The value of the tlsCntTreeGlobalIndex of the MANAGED OBJECT."
   ::= {pr1645v2VrfRoutUdpServerSessionsEntry 10}

pr1645v2VrfRoutUdpServerSessionsTableIx OBJECT-TYPE
   SYNTAX      TableIndex
   MAX-ACCESS  not-accessible
   STATUS      current
   DESCRIPTION
      ""
   ::= {pr1645v2VrfRoutUdpServerSessionsEntry 11}

pr1645v2VrfRoutUdpServerSessionsSourceIpAddress OBJECT-TYPE
   SYNTAX      IpAddress
   MAX-ACCESS  read-only
   STATUS      current
   DESCRIPTION
      "Path: vrfRouter.performance.udpServer.sessions.sourceIpAddress"
   ::= {pr1645v2VrfRoutUdpServerSessionsEntry 16777216}

pr1645v2VrfRoutUdpServerSessionsSourcePort OBJECT-TYPE
   SYNTAX      Integer32
   MAX-ACCESS  read-only
   STATUS      current
   DESCRIPTION
      "Path: vrfRouter.performance.udpServer.sessions.sourcePort"
   ::= {pr1645v2VrfRoutUdpServerSessionsEntry 33554432}

pr1645v2VrfRoutUdpServerSessionsNbrPckt OBJECT-TYPE
   SYNTAX      Counter64
   MAX-ACCESS  read-only
   STATUS      current
   DESCRIPTION
      "Path: vrfRouter.performance.udpServer.sessions.nbrOfPackets

       64 bit unsigned wrappable counter."
   ::= {pr1645v2VrfRoutUdpServerSessionsEntry 50331648}

pr1645v2VrfRoutUdpServerSessionsFirstActivityTime OBJECT-TYPE
   SYNTAX      TimeTicks
   MAX-ACCESS  read-only
   STATUS      current
   DESCRIPTION
      "Path: vrfRouter.performance.udpServer.sessions.firstActivityTime

       Time in centi-second."
   ::= {pr1645v2VrfRoutUdpServerSessionsEntry 67108864}

pr1645v2VrfRoutUdpServerSessionsLastActivityTime OBJECT-TYPE
   SYNTAX      TimeTicks
   MAX-ACCESS  read-only
   STATUS      current
   DESCRIPTION
      "Path: vrfRouter.performance.udpServer.sessions.lastActivityTime

       Time in centi-second."
   ::= {pr1645v2VrfRoutUdpServerSessionsEntry 83886080}

pr1645v2VrfRoutUdpServerSessionsHalfWayStatus OBJECT-TYPE
   SYNTAX      INTEGER
               {
               notInUse (1),
               inUse (2)
               }
   MAX-ACCESS  read-only
   STATUS      current
   DESCRIPTION
      "Path: vrfRouter.performance.udpServer.sessions.halfWay.status

       Possibilities:
               notInUse   (1)
               inUse   (2)"
   ::= {pr1645v2VrfRoutUdpServerSessionsEntry 100728832}

pr1645v2VrfRoutUdpServerSessionsHalfWayReceived OBJECT-TYPE
   SYNTAX      Counter64
   MAX-ACCESS  read-only
   STATUS      current
   DESCRIPTION
      "Path: vrfRouter.performance.udpServer.sessions.halfWay.received

       64 bit unsigned wrappable counter."
   ::= {pr1645v2VrfRoutUdpServerSessionsEntry 110166016}

pr1645v2VrfRoutUdpServerSessionsHalfWayPacketLoss OBJECT-TYPE
   SYNTAX      Counter64
   MAX-ACCESS  read-only
   STATUS      current
   DESCRIPTION
      "Path: vrfRouter.performance.udpServer.sessions.halfWay.packetLoss

       64 bit unsigned wrappable counter."
   ::= {pr1645v2VrfRoutUdpServerSessionsEntry 110231552}

pr1645v2VrfRoutUdpServerSessionsHalfWayOutOfSequence OBJECT-TYPE
   SYNTAX      Counter64
   MAX-ACCESS  read-only
   STATUS      current
   DESCRIPTION
      "Path: vrfRouter.performance.udpServer.sessions.halfWay.outOfSequence

       64 bit unsigned wrappable counter."
   ::= {pr1645v2VrfRoutUdpServerSessionsEntry 110362624}

pr1645v2VrfRoutUdpServerSessionsHalfWayCrcErrors OBJECT-TYPE
   SYNTAX      Counter64
   MAX-ACCESS  read-only
   STATUS      current
   DESCRIPTION
      "Path: vrfRouter.performance.udpServer.sessions.halfWay.crcErrors

       64 bit unsigned wrappable counter."
   ::= {pr1645v2VrfRoutUdpServerSessionsEntry 110493696}

pr1645v2VrfRoutUdpServerSessionsHalfWayLengthErrors OBJECT-TYPE
   SYNTAX      Counter64
   MAX-ACCESS  read-only
   STATUS      current
   DESCRIPTION
      "Path: vrfRouter.performance.udpServer.sessions.halfWay.lengthErrors

       64 bit unsigned wrappable counter."
   ::= {pr1645v2VrfRoutUdpServerSessionsEntry 110559232}

pr1645v2VrfRoutUdpServerSessionsHalfWayJitter OBJECT-TYPE
   SYNTAX      INTEGER
               {
               slnotsinsuseg (2147483647)
               }
   MAX-ACCESS  read-only
   STATUS      current
   DESCRIPTION
      "Path: vrfRouter.performance.udpServer.sessions.halfWay.jitter

       unit name = ms
       formula = 10 / ; 10 *

       Possibilities:
               <not in use>   (2147483647)"
   ::= {pr1645v2VrfRoutUdpServerSessionsEntry 111280128}

pr1645v2VrfRoutUdpServerSessionsHalfWayJitterAvrg OBJECT-TYPE
   SYNTAX      INTEGER
               {
               slnotsinsuseg (2147483647)
               }
   MAX-ACCESS  read-only
   STATUS      current
   DESCRIPTION
      "Path: vrfRouter.performance.udpServer.sessions.halfWay.jitterAvrg

       unit name = ms
       formula = 10 / ; 10 *

       Possibilities:
               <not in use>   (2147483647)"
   ::= {pr1645v2VrfRoutUdpServerSessionsEntry 111345664}

pr1645v2VrfRoutUdpServerSessionsHalfWayJitterMax OBJECT-TYPE
   SYNTAX      INTEGER
               {
               slnotsinsuseg (2147483647)
               }
   MAX-ACCESS  read-only
   STATUS      current
   DESCRIPTION
      "Path: vrfRouter.performance.udpServer.sessions.halfWay.jitterMax

       unit name = ms
       formula = 10 / ; 10 *

       Possibilities:
               <not in use>   (2147483647)"
   ::= {pr1645v2VrfRoutUdpServerSessionsEntry 111411200}

pr1645v2VrfRoutUdpServerSessionsHalfWayReceivedLength OBJECT-TYPE
   SYNTAX      Counter64
   MAX-ACCESS  read-only
   STATUS      current
   DESCRIPTION
      "Path: vrfRouter.performance.udpServer.sessions.halfWay.receivedLength

       64 bit unsigned wrappable counter."
   ::= {pr1645v2VrfRoutUdpServerSessionsEntry 111083520}

pr1645v2VrfRoutUdpServerSessionsHalfWayLastFault OBJECT-TYPE
   SYNTAX      Counter64
   MAX-ACCESS  read-only
   STATUS      current
   DESCRIPTION
      "Path: vrfRouter.performance.udpServer.sessions.halfWay.lastFault

       64 bit unsigned wrappable counter."
   ::= {pr1645v2VrfRoutUdpServerSessionsEntry 111804416}

pr1645v2VrfRoutUdpServerSessionsHalfWayLastSeqnr OBJECT-TYPE
   SYNTAX      Counter64
   MAX-ACCESS  read-only
   STATUS      current
   DESCRIPTION
      "Path: vrfRouter.performance.udpServer.sessions.halfWay.lastSeqnr

       64 bit unsigned wrappable counter."
   ::= {pr1645v2VrfRoutUdpServerSessionsEntry 111869952}


pr1645v2VrfRoutTracertResults OBJECT IDENTIFIER ::= {pr1645v2VrfRout 153}

pr1645v2VrfRoutTracertResultsSSCTable OBJECT-TYPE
   SYNTAX      SEQUENCE OF Pr1645v2VrfRoutTracertResultsEntry
   MAX-ACCESS  not-accessible
   STATUS      current
   DESCRIPTION
      "Traceroute statistics"
   ::= {pr1645v2VrfRoutTracertResults 1}

pr1645v2VrfRoutTracertResultsEntry OBJECT-TYPE
   SYNTAX      Pr1645v2VrfRoutTracertResultsEntry
   MAX-ACCESS  not-accessible
   STATUS      current
   DESCRIPTION
      ""
   INDEX      { pr1645v2VrfRoutTracertResultsGlobalIx,
                pr1645v2VrfRoutTracertResultsTableIx }
   ::= {pr1645v2VrfRoutTracertResultsSSCTable 1}

Pr1645v2VrfRoutTracertResultsEntry ::=
   SEQUENCE
      {
      pr1645v2VrfRoutTracertResultsGlobalIx
         GlobalIndex,
      pr1645v2VrfRoutTracertResultsTableIx
         TableIndex,
      pr1645v2VrfRoutTracertResultsTtl
         Integer32,
      pr1645v2VrfRoutTracertResultsIpAddress
         IpAddress,
      pr1645v2VrfRoutTracertResultsHostName
         DisplayString,
      pr1645v2VrfRoutTracertResultsNrTx
         Counter32,
      pr1645v2VrfRoutTracertResultsNrRx
         Counter32,
      pr1645v2VrfRoutTracertResultsRepTimMin
         TimeTicks,
      pr1645v2VrfRoutTracertResultsRepTimMax
         TimeTicks,
      pr1645v2VrfRoutTracertResultsRepTimAvrg
         TimeTicks,
      pr1645v2VrfRoutTracertResultsSr
         Integer32,
      pr1645v2VrfRoutTracertResultsComment
         DisplayString
      }

pr1645v2VrfRoutTracertResultsGlobalIx OBJECT-TYPE
   SYNTAX      GlobalIndex
   MAX-ACCESS  not-accessible
   STATUS      current
   DESCRIPTION
      "The value of the tlsCntTreeGlobalIndex of the MANAGED OBJECT."
   ::= {pr1645v2VrfRoutTracertResultsEntry 10}

pr1645v2VrfRoutTracertResultsTableIx OBJECT-TYPE
   SYNTAX      TableIndex
   MAX-ACCESS  not-accessible
   STATUS      current
   DESCRIPTION
      ""
   ::= {pr1645v2VrfRoutTracertResultsEntry 11}

pr1645v2VrfRoutTracertResultsTtl OBJECT-TYPE
   SYNTAX      Integer32
   MAX-ACCESS  read-only
   STATUS      current
   DESCRIPTION
      "Path: vrfRouter.performance.tracertResults.ttl"
   ::= {pr1645v2VrfRoutTracertResultsEntry 16777216}

pr1645v2VrfRoutTracertResultsIpAddress OBJECT-TYPE
   SYNTAX      IpAddress
   MAX-ACCESS  read-only
   STATUS      current
   DESCRIPTION
      "Path: vrfRouter.performance.tracertResults.ipAddress"
   ::= {pr1645v2VrfRoutTracertResultsEntry 33554432}

pr1645v2VrfRoutTracertResultsHostName OBJECT-TYPE
   SYNTAX      DisplayString
   MAX-ACCESS  read-only
   STATUS      current
   DESCRIPTION
      "Path: vrfRouter.performance.tracertResults.hostName"
   ::= {pr1645v2VrfRoutTracertResultsEntry 50331648}

pr1645v2VrfRoutTracertResultsNrTx OBJECT-TYPE
   SYNTAX      Counter32
   MAX-ACCESS  read-only
   STATUS      current
   DESCRIPTION
      "Path: vrfRouter.performance.tracertResults.numOfTxPackets

       32 bit unsigned wrappable counter."
   ::= {pr1645v2VrfRoutTracertResultsEntry 67108864}

pr1645v2VrfRoutTracertResultsNrRx OBJECT-TYPE
   SYNTAX      Counter32
   MAX-ACCESS  read-only
   STATUS      current
   DESCRIPTION
      "Path: vrfRouter.performance.tracertResults.numOfRxPackets

       32 bit unsigned wrappable counter."
   ::= {pr1645v2VrfRoutTracertResultsEntry 83886080}

pr1645v2VrfRoutTracertResultsRepTimMin OBJECT-TYPE
   SYNTAX      TimeTicks
   MAX-ACCESS  read-only
   STATUS      current
   DESCRIPTION
      "Path: vrfRouter.performance.tracertResults.replyTimeMin

       Time in centi-second."
   ::= {pr1645v2VrfRoutTracertResultsEntry 100663296}

pr1645v2VrfRoutTracertResultsRepTimMax OBJECT-TYPE
   SYNTAX      TimeTicks
   MAX-ACCESS  read-only
   STATUS      current
   DESCRIPTION
      "Path: vrfRouter.performance.tracertResults.replyTimeMax

       Time in centi-second."
   ::= {pr1645v2VrfRoutTracertResultsEntry 117440512}

pr1645v2VrfRoutTracertResultsRepTimAvrg OBJECT-TYPE
   SYNTAX      TimeTicks
   MAX-ACCESS  read-only
   STATUS      current
   DESCRIPTION
      "Path: vrfRouter.performance.tracertResults.replyTimeAvrg

       Time in centi-second."
   ::= {pr1645v2VrfRoutTracertResultsEntry 134217728}

pr1645v2VrfRoutTracertResultsSr OBJECT-TYPE
   SYNTAX      Integer32
   UNITS       "%"
   MAX-ACCESS  read-only
   STATUS      current
   DESCRIPTION
      "Path: vrfRouter.performance.tracertResults.successRate

       unit name = %"
   ::= {pr1645v2VrfRoutTracertResultsEntry 150994944}

pr1645v2VrfRoutTracertResultsComment OBJECT-TYPE
   SYNTAX      DisplayString
   MAX-ACCESS  read-only
   STATUS      current
   DESCRIPTION
      "Path: vrfRouter.performance.tracertResults.comment"
   ::= {pr1645v2VrfRoutTracertResultsEntry 167772160}


pr1645v2VrfRoutIgmpProxy OBJECT IDENTIFIER ::= {pr1645v2VrfRout 69}

pr1645v2VrfRoutIgmpProxySSCTable OBJECT-TYPE
   SYNTAX      SEQUENCE OF Pr1645v2VrfRoutIgmpProxyEntry
   MAX-ACCESS  not-accessible
   STATUS      current
   DESCRIPTION
      "igmp"
   ::= {pr1645v2VrfRoutIgmpProxy 1}

pr1645v2VrfRoutIgmpProxyEntry OBJECT-TYPE
   SYNTAX      Pr1645v2VrfRoutIgmpProxyEntry
   MAX-ACCESS  not-accessible
   STATUS      current
   DESCRIPTION
      ""
   INDEX      { pr1645v2VrfRoutIgmpProxyGlobalIx }
   ::= {pr1645v2VrfRoutIgmpProxySSCTable 1}

Pr1645v2VrfRoutIgmpProxyEntry ::=
   SEQUENCE
      {
      pr1645v2VrfRoutIgmpProxyGlobalIx
         GlobalIndex,
      pr1645v2VrfRoutIgmpProxyInIgmp
         Integer32,
      pr1645v2VrfRoutIgmpProxyOutIgmp
         Integer32,
      pr1645v2VrfRoutIgmpProxyInData
         Integer32,
      pr1645v2VrfRoutIgmpProxyInDiscards
         Integer32
      }

pr1645v2VrfRoutIgmpProxyGlobalIx OBJECT-TYPE
   SYNTAX      GlobalIndex
   MAX-ACCESS  not-accessible
   STATUS      current
   DESCRIPTION
      "The value of the tlsCntTreeGlobalIndex of the MANAGED OBJECT."
   ::= {pr1645v2VrfRoutIgmpProxyEntry 10}

pr1645v2VrfRoutIgmpProxyInIgmp OBJECT-TYPE
   SYNTAX      Integer32
   MAX-ACCESS  read-only
   STATUS      current
   DESCRIPTION
      "Path: vrfRouter.performance.igmpProxy.inIgmp"
   ::= {pr1645v2VrfRoutIgmpProxyEntry 16777216}

pr1645v2VrfRoutIgmpProxyOutIgmp OBJECT-TYPE
   SYNTAX      Integer32
   MAX-ACCESS  read-only
   STATUS      current
   DESCRIPTION
      "Path: vrfRouter.performance.igmpProxy.outIgmp"
   ::= {pr1645v2VrfRoutIgmpProxyEntry 33554432}

pr1645v2VrfRoutIgmpProxyInData OBJECT-TYPE
   SYNTAX      Integer32
   MAX-ACCESS  read-only
   STATUS      current
   DESCRIPTION
      "Path: vrfRouter.performance.igmpProxy.inData"
   ::= {pr1645v2VrfRoutIgmpProxyEntry 50331648}

pr1645v2VrfRoutIgmpProxyInDiscards OBJECT-TYPE
   SYNTAX      Integer32
   MAX-ACCESS  read-only
   STATUS      current
   DESCRIPTION
      "Path: vrfRouter.performance.igmpProxy.inDiscards"
   ::= {pr1645v2VrfRoutIgmpProxyEntry 67108864}


pr1645v2VrfRoutIpFragments OBJECT IDENTIFIER ::= {pr1645v2VrfRout 87}

pr1645v2VrfRoutIpFragmentsSSCTable OBJECT-TYPE
   SYNTAX      SEQUENCE OF Pr1645v2VrfRoutIpFragmentsEntry
   MAX-ACCESS  not-accessible
   STATUS      current
   DESCRIPTION
      "info on IP fragments"
   ::= {pr1645v2VrfRoutIpFragments 1}

pr1645v2VrfRoutIpFragmentsEntry OBJECT-TYPE
   SYNTAX      Pr1645v2VrfRoutIpFragmentsEntry
   MAX-ACCESS  not-accessible
   STATUS      current
   DESCRIPTION
      ""
   INDEX      { pr1645v2VrfRoutIpFragmentsGlobalIx }
   ::= {pr1645v2VrfRoutIpFragmentsSSCTable 1}

Pr1645v2VrfRoutIpFragmentsEntry ::=
   SEQUENCE
      {
      pr1645v2VrfRoutIpFragmentsGlobalIx
         GlobalIndex,
      pr1645v2VrfRoutIpFragmentsReceivedFrames
         Counter64,
      pr1645v2VrfRoutIpFragmentsReassembledFrames
         Counter64,
      pr1645v2VrfRoutIpFragmentsExpiredFrames
         Counter64,
      pr1645v2VrfRoutIpFragmentsPendingFrames
         Gauge32,
      pr1645v2VrfRoutIpFragmentsReceivedPackets
         Counter64,
      pr1645v2VrfRoutIpFragmentsExcessivelyFragPackets
         Counter64
      }

pr1645v2VrfRoutIpFragmentsGlobalIx OBJECT-TYPE
   SYNTAX      GlobalIndex
   MAX-ACCESS  not-accessible
   STATUS      current
   DESCRIPTION
      "The value of the tlsCntTreeGlobalIndex of the MANAGED OBJECT."
   ::= {pr1645v2VrfRoutIpFragmentsEntry 10}

pr1645v2VrfRoutIpFragmentsReceivedFrames OBJECT-TYPE
   SYNTAX      Counter64
   MAX-ACCESS  read-only
   STATUS      current
   DESCRIPTION
      "Path: vrfRouter.performance.ipFragments.receivedFrames

       64 bit unsigned wrappable counter."
   ::= {pr1645v2VrfRoutIpFragmentsEntry 16777216}

pr1645v2VrfRoutIpFragmentsReassembledFrames OBJECT-TYPE
   SYNTAX      Counter64
   MAX-ACCESS  read-only
   STATUS      current
   DESCRIPTION
      "Path: vrfRouter.performance.ipFragments.reassembledFrames

       64 bit unsigned wrappable counter."
   ::= {pr1645v2VrfRoutIpFragmentsEntry 33554432}

pr1645v2VrfRoutIpFragmentsExpiredFrames OBJECT-TYPE
   SYNTAX      Counter64
   MAX-ACCESS  read-only
   STATUS      current
   DESCRIPTION
      "Path: vrfRouter.performance.ipFragments.expiredFrames

       64 bit unsigned wrappable counter."
   ::= {pr1645v2VrfRoutIpFragmentsEntry 50331648}

pr1645v2VrfRoutIpFragmentsPendingFrames OBJECT-TYPE
   SYNTAX      Gauge32
   MAX-ACCESS  read-only
   STATUS      current
   DESCRIPTION
      "Path: vrfRouter.performance.ipFragments.pendingFrames

       32 bit unsigned gauge value."
   ::= {pr1645v2VrfRoutIpFragmentsEntry 67108864}

pr1645v2VrfRoutIpFragmentsReceivedPackets OBJECT-TYPE
   SYNTAX      Counter64
   MAX-ACCESS  read-only
   STATUS      current
   DESCRIPTION
      "Path: vrfRouter.performance.ipFragments.receivedPackets

       64 bit unsigned wrappable counter."
   ::= {pr1645v2VrfRoutIpFragmentsEntry 83886080}

pr1645v2VrfRoutIpFragmentsExcessivelyFragPackets OBJECT-TYPE
   SYNTAX      Counter64
   MAX-ACCESS  read-only
   STATUS      current
   DESCRIPTION
      "Path: vrfRouter.performance.ipFragments.excessivelyFragPackets

       64 bit unsigned wrappable counter."
   ::= {pr1645v2VrfRoutIpFragmentsEntry 100663296}



fr1645v2VrfRout OBJECT IDENTIFIER ::= {r1645v2VrfRout 13}


fr1645v2VrfRoutAlarm OBJECT IDENTIFIER ::= {fr1645v2VrfRout 202}

fr1645v2VrfRoutAlarmSSCTable OBJECT-TYPE
   SYNTAX      SEQUENCE OF Fr1645v2VrfRoutAlarmEntry
   MAX-ACCESS  not-accessible
   STATUS      current
   DESCRIPTION
      "routAlarmInfo"
   ::= {fr1645v2VrfRoutAlarm 1}

fr1645v2VrfRoutAlarmEntry OBJECT-TYPE
   SYNTAX      Fr1645v2VrfRoutAlarmEntry
   MAX-ACCESS  not-accessible
   STATUS      current
   DESCRIPTION
      ""
   INDEX      { fr1645v2VrfRoutAlarmGlobalIx }
   ::= {fr1645v2VrfRoutAlarmSSCTable 1}

Fr1645v2VrfRoutAlarmEntry ::=
   SEQUENCE
      {
      fr1645v2VrfRoutAlarmGlobalIx
         GlobalIndex,
      fr1645v2VrfRoutAlarmDiscriminator
         Integer32,
      fr1645v2VrfRoutAlarmCurrent
         Integer32,
      fr1645v2VrfRoutAlarmPrevious
         Integer32,
      fr1645v2VrfRoutAlarmMask
         Integer32,
      fr1645v2VrfRoutAlarmLevPingActive
         Integer32,
      fr1645v2VrfRoutAlarmLevQMonLoss
         Integer32,
      fr1645v2VrfRoutAlarmLevQMonDelay
         Integer32,
      fr1645v2VrfRoutAlarmLevQMonJitter
         Integer32
      }

fr1645v2VrfRoutAlarmGlobalIx OBJECT-TYPE
   SYNTAX      GlobalIndex
   MAX-ACCESS  not-accessible
   STATUS      current
   DESCRIPTION
      "The value of the tlsCntTreeGlobalIndex of the MANAGED OBJECT."
   ::= {fr1645v2VrfRoutAlarmEntry 10}

fr1645v2VrfRoutAlarmDiscriminator OBJECT-TYPE
   SYNTAX      Integer32
   MAX-ACCESS  read-only
   STATUS      current
   DESCRIPTION
      "Path: vrfRouter.alarms.alarmInfo.discriminator"
   ::= {fr1645v2VrfRoutAlarmEntry 16777216}

fr1645v2VrfRoutAlarmCurrent OBJECT-TYPE
   SYNTAX      Integer32
   MAX-ACCESS  read-only
   STATUS      current
   DESCRIPTION
      "Path: vrfRouter.alarms.alarmInfo.currentAlarms

       Bit meanings:
               bit 0 = pingActive,
               bit 1 = qMonLoss,
               bit 2 = qMonDelay,
               bit 3 = qMonJitter"
   ::= {fr1645v2VrfRoutAlarmEntry 33554432}

fr1645v2VrfRoutAlarmPrevious OBJECT-TYPE
   SYNTAX      Integer32
   MAX-ACCESS  read-only
   STATUS      current
   DESCRIPTION
      "Path: vrfRouter.alarms.alarmInfo.previousAlarms

       Bit meanings:
               bit 0 = pingActive,
               bit 1 = qMonLoss,
               bit 2 = qMonDelay,
               bit 3 = qMonJitter"
   ::= {fr1645v2VrfRoutAlarmEntry 50331648}

fr1645v2VrfRoutAlarmMask OBJECT-TYPE
   SYNTAX      Integer32
   MAX-ACCESS  read-only
   STATUS      current
   DESCRIPTION
      "Path: vrfRouter.alarms.alarmInfo.alarmMask

       Bit meanings:
               bit 0 = pingActive,
               bit 1 = qMonLoss,
               bit 2 = qMonDelay,
               bit 3 = qMonJitter"
   ::= {fr1645v2VrfRoutAlarmEntry 67108864}

fr1645v2VrfRoutAlarmLevPingActive OBJECT-TYPE
   SYNTAX      Integer32
   MAX-ACCESS  read-only
   STATUS      current
   DESCRIPTION
      "Path: vrfRouter.alarms.alarmInfo.alarmLevel.pingActive"
   ::= {fr1645v2VrfRoutAlarmEntry 83951616}

fr1645v2VrfRoutAlarmLevQMonLoss OBJECT-TYPE
   SYNTAX      Integer32
   MAX-ACCESS  read-only
   STATUS      current
   DESCRIPTION
      "Path: vrfRouter.alarms.alarmInfo.alarmLevel.qMonLoss"
   ::= {fr1645v2VrfRoutAlarmEntry 84017152}

fr1645v2VrfRoutAlarmLevQMonDelay OBJECT-TYPE
   SYNTAX      Integer32
   MAX-ACCESS  read-only
   STATUS      current
   DESCRIPTION
      "Path: vrfRouter.alarms.alarmInfo.alarmLevel.qMonDelay"
   ::= {fr1645v2VrfRoutAlarmEntry 84082688}

fr1645v2VrfRoutAlarmLevQMonJitter OBJECT-TYPE
   SYNTAX      Integer32
   MAX-ACCESS  read-only
   STATUS      current
   DESCRIPTION
      "Path: vrfRouter.alarms.alarmInfo.alarmLevel.qMonJitter"
   ::= {fr1645v2VrfRoutAlarmEntry 84148224}


fr1645v2VrfRoutAlarmE2 OBJECT IDENTIFIER ::= {fr1645v2VrfRoutAlarm 2}

fr1645v2VrfRoutAlarmE2Entry OBJECT IDENTIFIER ::= {fr1645v2VrfRoutAlarmE2 1}

fr1645v2VrfRoutAlarmE2PingActive OBJECT IDENTIFIER ::= {fr1645v2VrfRoutAlarmE2Entry 10}

fr1645v2VrfRoutAlarmE2PingActivePfx OBJECT IDENTIFIER ::= {fr1645v2VrfRoutAlarmE2PingActive 0}

fr1645v2VrfRoutAlarmE2PingActiveOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'vrfRouter'
                (root='router1645') has changed from the ON to the OFF state."
   ::= {fr1645v2VrfRoutAlarmE2PingActivePfx 1}

fr1645v2VrfRoutAlarmE2PingActiveOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'vrfRouter'
                (root='router1645') has changed from the OFF to the ON state."
   ::= {fr1645v2VrfRoutAlarmE2PingActivePfx 2}

fr1645v2VrfRoutAlarmE2QMonLoss OBJECT IDENTIFIER ::= {fr1645v2VrfRoutAlarmE2Entry 11}

fr1645v2VrfRoutAlarmE2QMonLossPfx OBJECT IDENTIFIER ::= {fr1645v2VrfRoutAlarmE2QMonLoss 0}

fr1645v2VrfRoutAlarmE2QMonLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'vrfRouter'
                (root='router1645') has changed from the ON to the OFF state."
   ::= {fr1645v2VrfRoutAlarmE2QMonLossPfx 1}

fr1645v2VrfRoutAlarmE2QMonLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'vrfRouter'
                (root='router1645') has changed from the OFF to the ON state."
   ::= {fr1645v2VrfRoutAlarmE2QMonLossPfx 2}

fr1645v2VrfRoutAlarmE2QMonDelay OBJECT IDENTIFIER ::= {fr1645v2VrfRoutAlarmE2Entry 12}

fr1645v2VrfRoutAlarmE2QMonDelayPfx OBJECT IDENTIFIER ::= {fr1645v2VrfRoutAlarmE2QMonDelay 0}

fr1645v2VrfRoutAlarmE2QMonDelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'vrfRouter'
                (root='router1645') has changed from the ON to the OFF state."
   ::= {fr1645v2VrfRoutAlarmE2QMonDelayPfx 1}

fr1645v2VrfRoutAlarmE2QMonDelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'vrfRouter'
                (root='router1645') has changed from the OFF to the ON state."
   ::= {fr1645v2VrfRoutAlarmE2QMonDelayPfx 2}

fr1645v2VrfRoutAlarmE2QMonJitter OBJECT IDENTIFIER ::= {fr1645v2VrfRoutAlarmE2Entry 13}

fr1645v2VrfRoutAlarmE2QMonJitterPfx OBJECT IDENTIFIER ::= {fr1645v2VrfRoutAlarmE2QMonJitter 0}

fr1645v2VrfRoutAlarmE2QMonJitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'vrfRouter'
                (root='router1645') has changed from the ON to the OFF state."
   ::= {fr1645v2VrfRoutAlarmE2QMonJitterPfx 1}

fr1645v2VrfRoutAlarmE2QMonJitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'vrfRouter'
                (root='router1645') has changed from the OFF to the ON state."
   ::= {fr1645v2VrfRoutAlarmE2QMonJitterPfx 2}



ar1645v2VrfRout OBJECT IDENTIFIER ::= {r1645v2VrfRout 16}


ar1645v2VrfRoutRestartDhcpClient OBJECT IDENTIFIER ::= {ar1645v2VrfRout 88}

ar1645v2VrfRoutRestartDhcpClientTable OBJECT-TYPE
   SYNTAX      SEQUENCE OF Ar1645v2VrfRoutRestartDhcpClientEntry
   MAX-ACCESS  not-accessible
   STATUS      current
   DESCRIPTION
      "restart the dhcp client"
   ::= {ar1645v2VrfRoutRestartDhcpClient 1}

ar1645v2VrfRoutRestartDhcpClientEntry OBJECT-TYPE
   SYNTAX      Ar1645v2VrfRoutRestartDhcpClientEntry
   MAX-ACCESS  not-accessible
   STATUS      current
   DESCRIPTION
      ""
   INDEX      { ar1645v2VrfRoutRestartDhcpClientGlobalIx }
   ::= {ar1645v2VrfRoutRestartDhcpClientTable 1}

Ar1645v2VrfRoutRestartDhcpClientEntry ::=
   SEQUENCE
      {
      ar1645v2VrfRoutRestartDhcpClientGlobalIx
         GlobalIndex,
      ar1645v2VrfRoutRestartDhcpClientValue
         Integer32
      }

ar1645v2VrfRoutRestartDhcpClientGlobalIx OBJECT-TYPE
   SYNTAX      GlobalIndex
   MAX-ACCESS  not-accessible
   STATUS      current
   DESCRIPTION
      "The value of the tlsCntTreeGlobalIndex of the MANAGED OBJECT."
   ::= {ar1645v2VrfRoutRestartDhcpClientEntry 10}

ar1645v2VrfRoutRestartDhcpClientValue OBJECT-TYPE
   SYNTAX      Integer32
   MAX-ACCESS  read-write
   STATUS      current
   DESCRIPTION
      "Path: vrfRouter.actions.restartDhcpClient"
   ::= {ar1645v2VrfRoutRestartDhcpClientEntry 2147483648}


ar1645v2VrfRoutInterfaceName OBJECT IDENTIFIER ::= {ar1645v2VrfRout 89}

ar1645v2VrfRoutInterfaceNameTable OBJECT-TYPE
   SYNTAX      SEQUENCE OF Ar1645v2VrfRoutInterfaceNameEntry
   MAX-ACCESS  not-accessible
   STATUS      current
   DESCRIPTION
      "Name of the interface"
   ::= {ar1645v2VrfRoutInterfaceName 1}

ar1645v2VrfRoutInterfaceNameEntry OBJECT-TYPE
   SYNTAX      Ar1645v2VrfRoutInterfaceNameEntry
   MAX-ACCESS  not-accessible
   STATUS      current
   DESCRIPTION
      ""
   INDEX      { ar1645v2VrfRoutInterfaceNameGlobalIx }
   ::= {ar1645v2VrfRoutInterfaceNameTable 1}

Ar1645v2VrfRoutInterfaceNameEntry ::=
   SEQUENCE
      {
      ar1645v2VrfRoutInterfaceNameGlobalIx
         GlobalIndex,
      ar1645v2VrfRoutInterfaceNameValue
         DisplayString
      }

ar1645v2VrfRoutInterfaceNameGlobalIx OBJECT-TYPE
   SYNTAX      GlobalIndex
   MAX-ACCESS  not-accessible
   STATUS      current
   DESCRIPTION
      "The value of the tlsCntTreeGlobalIndex of the MANAGED OBJECT."
   ::= {ar1645v2VrfRoutInterfaceNameEntry 10}

ar1645v2VrfRoutInterfaceNameValue OBJECT-TYPE
   SYNTAX      DisplayString
   MAX-ACCESS  read-write
   STATUS      current
   DESCRIPTION
      "Path: vrfRouter.actions.interfaceName"
   ::= {ar1645v2VrfRoutInterfaceNameEntry 2147483648}


ar1645v2VrfRoutSendIgmpLeave OBJECT IDENTIFIER ::= {ar1645v2VrfRout 114}

ar1645v2VrfRoutSendIgmpLeaveTable OBJECT-TYPE
   SYNTAX      SEQUENCE OF Ar1645v2VrfRoutSendIgmpLeaveEntry
   MAX-ACCESS  not-accessible
   STATUS      current
   DESCRIPTION
      "send igmp leave over selected interfaces"
   ::= {ar1645v2VrfRoutSendIgmpLeave 1}

ar1645v2VrfRoutSendIgmpLeaveEntry OBJECT-TYPE
   SYNTAX      Ar1645v2VrfRoutSendIgmpLeaveEntry
   MAX-ACCESS  not-accessible
   STATUS      current
   DESCRIPTION
      ""
   INDEX      { ar1645v2VrfRoutSendIgmpLeaveGlobalIx }
   ::= {ar1645v2VrfRoutSendIgmpLeaveTable 1}

Ar1645v2VrfRoutSendIgmpLeaveEntry ::=
   SEQUENCE
      {
      ar1645v2VrfRoutSendIgmpLeaveGlobalIx
         GlobalIndex,
      ar1645v2VrfRoutSendIgmpLeaveValue
         Integer32
      }

ar1645v2VrfRoutSendIgmpLeaveGlobalIx OBJECT-TYPE
   SYNTAX      GlobalIndex
   MAX-ACCESS  not-accessible
   STATUS      current
   DESCRIPTION
      "The value of the tlsCntTreeGlobalIndex of the MANAGED OBJECT."
   ::= {ar1645v2VrfRoutSendIgmpLeaveEntry 10}

ar1645v2VrfRoutSendIgmpLeaveValue OBJECT-TYPE
   SYNTAX      Integer32
   MAX-ACCESS  read-write
   STATUS      current
   DESCRIPTION
      "Path: vrfRouter.actions.sendIgmpLeave"
   ::= {ar1645v2VrfRoutSendIgmpLeaveEntry 2147483648}


ar1645v2VrfRoutIgmpDataLeave OBJECT IDENTIFIER ::= {ar1645v2VrfRout 115}

ar1645v2VrfRoutIgmpDataLeaveSSCTable OBJECT-TYPE
   SYNTAX      SEQUENCE OF Ar1645v2VrfRoutIgmpDataLeaveEntry
   MAX-ACCESS  not-accessible
   STATUS      current
   DESCRIPTION
      "data needed for igmp"
   ::= {ar1645v2VrfRoutIgmpDataLeave 1}

ar1645v2VrfRoutIgmpDataLeaveEntry OBJECT-TYPE
   SYNTAX      Ar1645v2VrfRoutIgmpDataLeaveEntry
   MAX-ACCESS  not-accessible
   STATUS      current
   DESCRIPTION
      ""
   INDEX      { ar1645v2VrfRoutIgmpDataLeaveGlobalIx }
   ::= {ar1645v2VrfRoutIgmpDataLeaveSSCTable 1}

Ar1645v2VrfRoutIgmpDataLeaveEntry ::=
   SEQUENCE
      {
      ar1645v2VrfRoutIgmpDataLeaveGlobalIx
         GlobalIndex,
      ar1645v2VrfRoutIgmpDataLeaveInterfaces
         DisplayString,
      ar1645v2VrfRoutIgmpDataLeaveIpAddress
         IpAddress
      }

ar1645v2VrfRoutIgmpDataLeaveGlobalIx OBJECT-TYPE
   SYNTAX      GlobalIndex
   MAX-ACCESS  not-accessible
   STATUS      current
   DESCRIPTION
      "The value of the tlsCntTreeGlobalIndex of the MANAGED OBJECT."
   ::= {ar1645v2VrfRoutIgmpDataLeaveEntry 10}

ar1645v2VrfRoutIgmpDataLeaveInterfaces OBJECT-TYPE
   SYNTAX      DisplayString
   MAX-ACCESS  read-write
   STATUS      current
   DESCRIPTION
      "Path: vrfRouter.actions.igmpDataLeave.interfaces"
   ::= {ar1645v2VrfRoutIgmpDataLeaveEntry 16777216}

ar1645v2VrfRoutIgmpDataLeaveIpAddress OBJECT-TYPE
   SYNTAX      IpAddress
   MAX-ACCESS  read-write
   STATUS      current
   DESCRIPTION
      "Path: vrfRouter.actions.igmpDataLeave.ipAddress"
   ::= {ar1645v2VrfRoutIgmpDataLeaveEntry 33554432}


ar1645v2VrfRoutSendIgmpRep OBJECT IDENTIFIER ::= {ar1645v2VrfRout 112}

ar1645v2VrfRoutSendIgmpRepTable OBJECT-TYPE
   SYNTAX      SEQUENCE OF Ar1645v2VrfRoutSendIgmpRepEntry
   MAX-ACCESS  not-accessible
   STATUS      current
   DESCRIPTION
      "send igmp report over selected interfaces"
   ::= {ar1645v2VrfRoutSendIgmpRep 1}

ar1645v2VrfRoutSendIgmpRepEntry OBJECT-TYPE
   SYNTAX      Ar1645v2VrfRoutSendIgmpRepEntry
   MAX-ACCESS  not-accessible
   STATUS      current
   DESCRIPTION
      ""
   INDEX      { ar1645v2VrfRoutSendIgmpRepGlobalIx }
   ::= {ar1645v2VrfRoutSendIgmpRepTable 1}

Ar1645v2VrfRoutSendIgmpRepEntry ::=
   SEQUENCE
      {
      ar1645v2VrfRoutSendIgmpRepGlobalIx
         GlobalIndex,
      ar1645v2VrfRoutSendIgmpRepValue
         Integer32
      }

ar1645v2VrfRoutSendIgmpRepGlobalIx OBJECT-TYPE
   SYNTAX      GlobalIndex
   MAX-ACCESS  not-accessible
   STATUS      current
   DESCRIPTION
      "The value of the tlsCntTreeGlobalIndex of the MANAGED OBJECT."
   ::= {ar1645v2VrfRoutSendIgmpRepEntry 10}

ar1645v2VrfRoutSendIgmpRepValue OBJECT-TYPE
   SYNTAX      Integer32
   MAX-ACCESS  read-write
   STATUS      current
   DESCRIPTION
      "Path: vrfRouter.actions.sendIgmpRep"
   ::= {ar1645v2VrfRoutSendIgmpRepEntry 2147483648}


ar1645v2VrfRoutIgmpDataRep OBJECT IDENTIFIER ::= {ar1645v2VrfRout 113}

ar1645v2VrfRoutIgmpDataRepSSCTable OBJECT-TYPE
   SYNTAX      SEQUENCE OF Ar1645v2VrfRoutIgmpDataRepEntry
   MAX-ACCESS  not-accessible
   STATUS      current
   DESCRIPTION
      "data needed for igmp"
   ::= {ar1645v2VrfRoutIgmpDataRep 1}

ar1645v2VrfRoutIgmpDataRepEntry OBJECT-TYPE
   SYNTAX      Ar1645v2VrfRoutIgmpDataRepEntry
   MAX-ACCESS  not-accessible
   STATUS      current
   DESCRIPTION
      ""
   INDEX      { ar1645v2VrfRoutIgmpDataRepGlobalIx }
   ::= {ar1645v2VrfRoutIgmpDataRepSSCTable 1}

Ar1645v2VrfRoutIgmpDataRepEntry ::=
   SEQUENCE
      {
      ar1645v2VrfRoutIgmpDataRepGlobalIx
         GlobalIndex,
      ar1645v2VrfRoutIgmpDataRepInterfaces
         DisplayString,
      ar1645v2VrfRoutIgmpDataRepIpAddress
         IpAddress
      }

ar1645v2VrfRoutIgmpDataRepGlobalIx OBJECT-TYPE
   SYNTAX      GlobalIndex
   MAX-ACCESS  not-accessible
   STATUS      current
   DESCRIPTION
      "The value of the tlsCntTreeGlobalIndex of the MANAGED OBJECT."
   ::= {ar1645v2VrfRoutIgmpDataRepEntry 10}

ar1645v2VrfRoutIgmpDataRepInterfaces OBJECT-TYPE
   SYNTAX      DisplayString
   MAX-ACCESS  read-write
   STATUS      current
   DESCRIPTION
      "Path: vrfRouter.actions.igmpDataRep.interfaces"
   ::= {ar1645v2VrfRoutIgmpDataRepEntry 16777216}

ar1645v2VrfRoutIgmpDataRepIpAddress OBJECT-TYPE
   SYNTAX      IpAddress
   MAX-ACCESS  read-write
   STATUS      current
   DESCRIPTION
      "Path: vrfRouter.actions.igmpDataRep.ipAddress"
   ::= {ar1645v2VrfRoutIgmpDataRepEntry 33554432}


ar1645v2VrfRoutSendRipReqAction OBJECT IDENTIFIER ::= {ar1645v2VrfRout 301}

ar1645v2VrfRoutSendRipReqActionTable OBJECT-TYPE
   SYNTAX      SEQUENCE OF Ar1645v2VrfRoutSendRipReqActionEntry
   MAX-ACCESS  not-accessible
   STATUS      current
   DESCRIPTION
      "send RIP request to specific router"
   ::= {ar1645v2VrfRoutSendRipReqAction 1}

ar1645v2VrfRoutSendRipReqActionEntry OBJECT-TYPE
   SYNTAX      Ar1645v2VrfRoutSendRipReqActionEntry
   MAX-ACCESS  not-accessible
   STATUS      current
   DESCRIPTION
      ""
   INDEX      { ar1645v2VrfRoutSendRipReqActionGlobalIx }
   ::= {ar1645v2VrfRoutSendRipReqActionTable 1}

Ar1645v2VrfRoutSendRipReqActionEntry ::=
   SEQUENCE
      {
      ar1645v2VrfRoutSendRipReqActionGlobalIx
         GlobalIndex,
      ar1645v2VrfRoutSendRipReqActionValue
         Integer32
      }

ar1645v2VrfRoutSendRipReqActionGlobalIx OBJECT-TYPE
   SYNTAX      GlobalIndex
   MAX-ACCESS  not-accessible
   STATUS      current
   DESCRIPTION
      "The value of the tlsCntTreeGlobalIndex of the MANAGED OBJECT."
   ::= {ar1645v2VrfRoutSendRipReqActionEntry 10}

ar1645v2VrfRoutSendRipReqActionValue OBJECT-TYPE
   SYNTAX      Integer32
   MAX-ACCESS  read-write
   STATUS      current
   DESCRIPTION
      "Path: vrfRouter.actions.sendRipReqAction"
   ::= {ar1645v2VrfRoutSendRipReqActionEntry 2147483648}


ar1645v2VrfRoutRequestArguments OBJECT IDENTIFIER ::= {ar1645v2VrfRout 302}

ar1645v2VrfRoutRequestArgumentsSSCTable OBJECT-TYPE
   SYNTAX      SEQUENCE OF Ar1645v2VrfRoutRequestArgumentsEntry
   MAX-ACCESS  not-accessible
   STATUS      current
   DESCRIPTION
      "attributes for the sendRipRequest action"
   ::= {ar1645v2VrfRoutRequestArguments 1}

ar1645v2VrfRoutRequestArgumentsEntry OBJECT-TYPE
   SYNTAX      Ar1645v2VrfRoutRequestArgumentsEntry
   MAX-ACCESS  not-accessible
   STATUS      current
   DESCRIPTION
      ""
   INDEX      { ar1645v2VrfRoutRequestArgumentsGlobalIx }
   ::= {ar1645v2VrfRoutRequestArgumentsSSCTable 1}

Ar1645v2VrfRoutRequestArgumentsEntry ::=
   SEQUENCE
      {
      ar1645v2VrfRoutRequestArgumentsGlobalIx
         GlobalIndex,
      ar1645v2VrfRoutRequestArgumentsRouterIp
         IpAddress,
      ar1645v2VrfRoutRequestArgumentsOutIf
         DisplayString
      }

ar1645v2VrfRoutRequestArgumentsGlobalIx OBJECT-TYPE
   SYNTAX      GlobalIndex
   MAX-ACCESS  not-accessible
   STATUS      current
   DESCRIPTION
      "The value of the tlsCntTreeGlobalIndex of the MANAGED OBJECT."
   ::= {ar1645v2VrfRoutRequestArgumentsEntry 10}

ar1645v2VrfRoutRequestArgumentsRouterIp OBJECT-TYPE
   SYNTAX      IpAddress
   MAX-ACCESS  read-write
   STATUS      current
   DESCRIPTION
      "Path: vrfRouter.actions.requestArguments.routerIp"
   ::= {ar1645v2VrfRoutRequestArgumentsEntry 16777216}

ar1645v2VrfRoutRequestArgumentsOutIf OBJECT-TYPE
   SYNTAX      DisplayString
   MAX-ACCESS  read-write
   STATUS      current
   DESCRIPTION
      "Path: vrfRouter.actions.requestArguments.outgoingInterface"
   ::= {ar1645v2VrfRoutRequestArgumentsEntry 33554432}


ar1645v2VrfRoutFreeIpAddress OBJECT IDENTIFIER ::= {ar1645v2VrfRout 106}

ar1645v2VrfRoutFreeIpAddressTable OBJECT-TYPE
   SYNTAX      SEQUENCE OF Ar1645v2VrfRoutFreeIpAddressEntry
   MAX-ACCESS  not-accessible
   STATUS      current
   DESCRIPTION
      "Free ip address"
   ::= {ar1645v2VrfRoutFreeIpAddress 1}

ar1645v2VrfRoutFreeIpAddressEntry OBJECT-TYPE
   SYNTAX      Ar1645v2VrfRoutFreeIpAddressEntry
   MAX-ACCESS  not-accessible
   STATUS      current
   DESCRIPTION
      ""
   INDEX      { ar1645v2VrfRoutFreeIpAddressGlobalIx }
   ::= {ar1645v2VrfRoutFreeIpAddressTable 1}

Ar1645v2VrfRoutFreeIpAddressEntry ::=
   SEQUENCE
      {
      ar1645v2VrfRoutFreeIpAddressGlobalIx
         GlobalIndex,
      ar1645v2VrfRoutFreeIpAddressValue
         Integer32
      }

ar1645v2VrfRoutFreeIpAddressGlobalIx OBJECT-TYPE
   SYNTAX      GlobalIndex
   MAX-ACCESS  not-accessible
   STATUS      current
   DESCRIPTION
      "The value of the tlsCntTreeGlobalIndex of the MANAGED OBJECT."
   ::= {ar1645v2VrfRoutFreeIpAddressEntry 10}

ar1645v2VrfRoutFreeIpAddressValue OBJECT-TYPE
   SYNTAX      Integer32
   MAX-ACCESS  read-write
   STATUS      current
   DESCRIPTION
      "Path: vrfRouter.actions.freeIpAddress"
   ::= {ar1645v2VrfRoutFreeIpAddressEntry 2147483648}


ar1645v2VrfRoutAddr OBJECT IDENTIFIER ::= {ar1645v2VrfRout 107}

ar1645v2VrfRoutAddrTable OBJECT-TYPE
   SYNTAX      SEQUENCE OF Ar1645v2VrfRoutAddrEntry
   MAX-ACCESS  not-accessible
   STATUS      current
   DESCRIPTION
      "ip address attribute"
   ::= {ar1645v2VrfRoutAddr 1}

ar1645v2VrfRoutAddrEntry OBJECT-TYPE
   SYNTAX      Ar1645v2VrfRoutAddrEntry
   MAX-ACCESS  not-accessible
   STATUS      current
   DESCRIPTION
      ""
   INDEX      { ar1645v2VrfRoutAddrGlobalIx }
   ::= {ar1645v2VrfRoutAddrTable 1}

Ar1645v2VrfRoutAddrEntry ::=
   SEQUENCE
      {
      ar1645v2VrfRoutAddrGlobalIx
         GlobalIndex,
      ar1645v2VrfRoutAddrValue
         IpAddress
      }

ar1645v2VrfRoutAddrGlobalIx OBJECT-TYPE
   SYNTAX      GlobalIndex
   MAX-ACCESS  not-accessible
   STATUS      current
   DESCRIPTION
      "The value of the tlsCntTreeGlobalIndex of the MANAGED OBJECT."
   ::= {ar1645v2VrfRoutAddrEntry 10}

ar1645v2VrfRoutAddrValue OBJECT-TYPE
   SYNTAX      IpAddress
   MAX-ACCESS  read-write
   STATUS      current
   DESCRIPTION
      "Path: vrfRouter.actions.address"
   ::= {ar1645v2VrfRoutAddrEntry 2147483648}


ar1645v2VrfRoutTakeIpAddress OBJECT IDENTIFIER ::= {ar1645v2VrfRout 104}

ar1645v2VrfRoutTakeIpAddressTable OBJECT-TYPE
   SYNTAX      SEQUENCE OF Ar1645v2VrfRoutTakeIpAddressEntry
   MAX-ACCESS  not-accessible
   STATUS      current
   DESCRIPTION
      "Take ip address from pool"
   ::= {ar1645v2VrfRoutTakeIpAddress 1}

ar1645v2VrfRoutTakeIpAddressEntry OBJECT-TYPE
   SYNTAX      Ar1645v2VrfRoutTakeIpAddressEntry
   MAX-ACCESS  not-accessible
   STATUS      current
   DESCRIPTION
      ""
   INDEX      { ar1645v2VrfRoutTakeIpAddressGlobalIx }
   ::= {ar1645v2VrfRoutTakeIpAddressTable 1}

Ar1645v2VrfRoutTakeIpAddressEntry ::=
   SEQUENCE
      {
      ar1645v2VrfRoutTakeIpAddressGlobalIx
         GlobalIndex,
      ar1645v2VrfRoutTakeIpAddressValue
         Integer32
      }

ar1645v2VrfRoutTakeIpAddressGlobalIx OBJECT-TYPE
   SYNTAX      GlobalIndex
   MAX-ACCESS  not-accessible
   STATUS      current
   DESCRIPTION
      "The value of the tlsCntTreeGlobalIndex of the MANAGED OBJECT."
   ::= {ar1645v2VrfRoutTakeIpAddressEntry 10}

ar1645v2VrfRoutTakeIpAddressValue OBJECT-TYPE
   SYNTAX      Integer32
   MAX-ACCESS  read-write
   STATUS      current
   DESCRIPTION
      "Path: vrfRouter.actions.takeIpAddress"
   ::= {ar1645v2VrfRoutTakeIpAddressEntry 2147483648}


ar1645v2VrfRoutPool OBJECT IDENTIFIER ::= {ar1645v2VrfRout 105}

ar1645v2VrfRoutPoolSSCTable OBJECT-TYPE
   SYNTAX      SEQUENCE OF Ar1645v2VrfRoutPoolEntry
   MAX-ACCESS  not-accessible
   STATUS      current
   DESCRIPTION
      "address pool type and name"
   ::= {ar1645v2VrfRoutPool 1}

ar1645v2VrfRoutPoolEntry OBJECT-TYPE
   SYNTAX      Ar1645v2VrfRoutPoolEntry
   MAX-ACCESS  not-accessible
   STATUS      current
   DESCRIPTION
      ""
   INDEX      { ar1645v2VrfRoutPoolGlobalIx }
   ::= {ar1645v2VrfRoutPoolSSCTable 1}

Ar1645v2VrfRoutPoolEntry ::=
   SEQUENCE
      {
      ar1645v2VrfRoutPoolGlobalIx
         GlobalIndex,
      ar1645v2VrfRoutPoolPoolType
         INTEGER,
      ar1645v2VrfRoutPoolPoolName
         DisplayString
      }

ar1645v2VrfRoutPoolGlobalIx OBJECT-TYPE
   SYNTAX      GlobalIndex
   MAX-ACCESS  not-accessible
   STATUS      current
   DESCRIPTION
      "The value of the tlsCntTreeGlobalIndex of the MANAGED OBJECT."
   ::= {ar1645v2VrfRoutPoolEntry 10}

ar1645v2VrfRoutPoolPoolType OBJECT-TYPE
   SYNTAX      INTEGER
               {
               list (1),
               interval (2)
               }
   MAX-ACCESS  read-write
   STATUS      current
   DESCRIPTION
      "Path: vrfRouter.actions.poolTypeName.poolType

       Possibilities:
               list   (1)
               interval   (2)"
   ::= {ar1645v2VrfRoutPoolEntry 16777216}

ar1645v2VrfRoutPoolPoolName OBJECT-TYPE
   SYNTAX      DisplayString
   MAX-ACCESS  read-write
   STATUS      current
   DESCRIPTION
      "Path: vrfRouter.actions.poolTypeName.poolName"
   ::= {ar1645v2VrfRoutPoolEntry 33554432}


ar1645v2VrfRoutQmOnDemand OBJECT IDENTIFIER ::= {ar1645v2VrfRout 8043}

ar1645v2VrfRoutQmOnDemandTable OBJECT-TYPE
   SYNTAX      SEQUENCE OF Ar1645v2VrfRoutQmOnDemandEntry
   MAX-ACCESS  not-accessible
   STATUS      current
   DESCRIPTION
      "start sending pings"
   ::= {ar1645v2VrfRoutQmOnDemand 1}

ar1645v2VrfRoutQmOnDemandEntry OBJECT-TYPE
   SYNTAX      Ar1645v2VrfRoutQmOnDemandEntry
   MAX-ACCESS  not-accessible
   STATUS      current
   DESCRIPTION
      ""
   INDEX      { ar1645v2VrfRoutQmOnDemandGlobalIx }
   ::= {ar1645v2VrfRoutQmOnDemandTable 1}

Ar1645v2VrfRoutQmOnDemandEntry ::=
   SEQUENCE
      {
      ar1645v2VrfRoutQmOnDemandGlobalIx
         GlobalIndex,
      ar1645v2VrfRoutQmOnDemandValue
         Integer32
      }

ar1645v2VrfRoutQmOnDemandGlobalIx OBJECT-TYPE
   SYNTAX      GlobalIndex
   MAX-ACCESS  not-accessible
   STATUS      current
   DESCRIPTION
      "The value of the tlsCntTreeGlobalIndex of the MANAGED OBJECT."
   ::= {ar1645v2VrfRoutQmOnDemandEntry 10}

ar1645v2VrfRoutQmOnDemandValue OBJECT-TYPE
   SYNTAX      Integer32
   MAX-ACCESS  read-write
   STATUS      current
   DESCRIPTION
      "Path: vrfRouter.actions.qmOnDemand"
   ::= {ar1645v2VrfRoutQmOnDemandEntry 2147483648}


ar1645v2VrfRoutAction OBJECT IDENTIFIER ::= {ar1645v2VrfRout 8044}

ar1645v2VrfRoutActionSSCTable OBJECT-TYPE
   SYNTAX      SEQUENCE OF Ar1645v2VrfRoutActionEntry
   MAX-ACCESS  not-accessible
   STATUS      current
   DESCRIPTION
      "data needed for ping"
   ::= {ar1645v2VrfRoutAction 1}

ar1645v2VrfRoutActionEntry OBJECT-TYPE
   SYNTAX      Ar1645v2VrfRoutActionEntry
   MAX-ACCESS  not-accessible
   STATUS      current
   DESCRIPTION
      ""
   INDEX      { ar1645v2VrfRoutActionGlobalIx }
   ::= {ar1645v2VrfRoutActionSSCTable 1}

Ar1645v2VrfRoutActionEntry ::=
   SEQUENCE
      {
      ar1645v2VrfRoutActionGlobalIx
         GlobalIndex,
      ar1645v2VrfRoutActionAction
         INTEGER,
      ar1645v2VrfRoutActionName
         DisplayString
      }

ar1645v2VrfRoutActionGlobalIx OBJECT-TYPE
   SYNTAX      GlobalIndex
   MAX-ACCESS  not-accessible
   STATUS      current
   DESCRIPTION
      "The value of the tlsCntTreeGlobalIndex of the MANAGED OBJECT."
   ::= {ar1645v2VrfRoutActionEntry 10}

ar1645v2VrfRoutActionAction OBJECT-TYPE
   SYNTAX      INTEGER
               {
               restart (1),
               restartLossWindow (2),
               stop (3),
               stopAndClear (4)
               }
   MAX-ACCESS  read-write
   STATUS      current
   DESCRIPTION
      "Path: vrfRouter.actions.action.action

       Possibilities:
               restart   (1)
               restartLossWindow   (2)
               stop   (3)
               stopAndClear   (4)"
   ::= {ar1645v2VrfRoutActionEntry 16777216}

ar1645v2VrfRoutActionName OBJECT-TYPE
   SYNTAX      DisplayString
   MAX-ACCESS  read-write
   STATUS      current
   DESCRIPTION
      "Path: vrfRouter.actions.action.name"
   ::= {ar1645v2VrfRoutActionEntry 33554432}


ar1645v2VrfRoutClearTracert OBJECT IDENTIFIER ::= {ar1645v2VrfRout 154}

ar1645v2VrfRoutClearTracertTable OBJECT-TYPE
   SYNTAX      SEQUENCE OF Ar1645v2VrfRoutClearTracertEntry
   MAX-ACCESS  not-accessible
   STATUS      current
   DESCRIPTION
      "Clear traceroute results"
   ::= {ar1645v2VrfRoutClearTracert 1}

ar1645v2VrfRoutClearTracertEntry OBJECT-TYPE
   SYNTAX      Ar1645v2VrfRoutClearTracertEntry
   MAX-ACCESS  not-accessible
   STATUS      current
   DESCRIPTION
      ""
   INDEX      { ar1645v2VrfRoutClearTracertGlobalIx }
   ::= {ar1645v2VrfRoutClearTracertTable 1}

Ar1645v2VrfRoutClearTracertEntry ::=
   SEQUENCE
      {
      ar1645v2VrfRoutClearTracertGlobalIx
         GlobalIndex,
      ar1645v2VrfRoutClearTracertValue
         Integer32
      }

ar1645v2VrfRoutClearTracertGlobalIx OBJECT-TYPE
   SYNTAX      GlobalIndex
   MAX-ACCESS  not-accessible
   STATUS      current
   DESCRIPTION
      "The value of the tlsCntTreeGlobalIndex of the MANAGED OBJECT."
   ::= {ar1645v2VrfRoutClearTracertEntry 10}

ar1645v2VrfRoutClearTracertValue OBJECT-TYPE
   SYNTAX      Integer32
   MAX-ACCESS  read-write
   STATUS      current
   DESCRIPTION
      "Path: vrfRouter.actions.clearTracert"
   ::= {ar1645v2VrfRoutClearTracertEntry 2147483648}


ar1645v2VrfRoutStopTracert OBJECT IDENTIFIER ::= {ar1645v2VrfRout 152}

ar1645v2VrfRoutStopTracertTable OBJECT-TYPE
   SYNTAX      SEQUENCE OF Ar1645v2VrfRoutStopTracertEntry
   MAX-ACCESS  not-accessible
   STATUS      current
   DESCRIPTION
      "stop ongoing traceroutes"
   ::= {ar1645v2VrfRoutStopTracert 1}

ar1645v2VrfRoutStopTracertEntry OBJECT-TYPE
   SYNTAX      Ar1645v2VrfRoutStopTracertEntry
   MAX-ACCESS  not-accessible
   STATUS      current
   DESCRIPTION
      ""
   INDEX      { ar1645v2VrfRoutStopTracertGlobalIx }
   ::= {ar1645v2VrfRoutStopTracertTable 1}

Ar1645v2VrfRoutStopTracertEntry ::=
   SEQUENCE
      {
      ar1645v2VrfRoutStopTracertGlobalIx
         GlobalIndex,
      ar1645v2VrfRoutStopTracertValue
         Integer32
      }

ar1645v2VrfRoutStopTracertGlobalIx OBJECT-TYPE
   SYNTAX      GlobalIndex
   MAX-ACCESS  not-accessible
   STATUS      current
   DESCRIPTION
      "The value of the tlsCntTreeGlobalIndex of the MANAGED OBJECT."
   ::= {ar1645v2VrfRoutStopTracertEntry 10}

ar1645v2VrfRoutStopTracertValue OBJECT-TYPE
   SYNTAX      Integer32
   MAX-ACCESS  read-write
   STATUS      current
   DESCRIPTION
      "Path: vrfRouter.actions.stopTracert"
   ::= {ar1645v2VrfRoutStopTracertEntry 2147483648}


ar1645v2VrfRoutStartTracert OBJECT IDENTIFIER ::= {ar1645v2VrfRout 150}

ar1645v2VrfRoutStartTracertTable OBJECT-TYPE
   SYNTAX      SEQUENCE OF Ar1645v2VrfRoutStartTracertEntry
   MAX-ACCESS  not-accessible
   STATUS      current
   DESCRIPTION
      "start traceroute"
   ::= {ar1645v2VrfRoutStartTracert 1}

ar1645v2VrfRoutStartTracertEntry OBJECT-TYPE
   SYNTAX      Ar1645v2VrfRoutStartTracertEntry
   MAX-ACCESS  not-accessible
   STATUS      current
   DESCRIPTION
      ""
   INDEX      { ar1645v2VrfRoutStartTracertGlobalIx }
   ::= {ar1645v2VrfRoutStartTracertTable 1}

Ar1645v2VrfRoutStartTracertEntry ::=
   SEQUENCE
      {
      ar1645v2VrfRoutStartTracertGlobalIx
         GlobalIndex,
      ar1645v2VrfRoutStartTracertValue
         Integer32
      }

ar1645v2VrfRoutStartTracertGlobalIx OBJECT-TYPE
   SYNTAX      GlobalIndex
   MAX-ACCESS  not-accessible
   STATUS      current
   DESCRIPTION
      "The value of the tlsCntTreeGlobalIndex of the MANAGED OBJECT."
   ::= {ar1645v2VrfRoutStartTracertEntry 10}

ar1645v2VrfRoutStartTracertValue OBJECT-TYPE
   SYNTAX      Integer32
   MAX-ACCESS  read-write
   STATUS      current
   DESCRIPTION
      "Path: vrfRouter.actions.startTracert"
   ::= {ar1645v2VrfRoutStartTracertEntry 2147483648}


ar1645v2VrfRoutTracertData OBJECT IDENTIFIER ::= {ar1645v2VrfRout 151}

ar1645v2VrfRoutTracertDataSSCTable OBJECT-TYPE
   SYNTAX      SEQUENCE OF Ar1645v2VrfRoutTracertDataEntry
   MAX-ACCESS  not-accessible
   STATUS      current
   DESCRIPTION
      "data needed for tracert"
   ::= {ar1645v2VrfRoutTracertData 1}

ar1645v2VrfRoutTracertDataEntry OBJECT-TYPE
   SYNTAX      Ar1645v2VrfRoutTracertDataEntry
   MAX-ACCESS  not-accessible
   STATUS      current
   DESCRIPTION
      ""
   INDEX      { ar1645v2VrfRoutTracertDataGlobalIx }
   ::= {ar1645v2VrfRoutTracertDataSSCTable 1}

Ar1645v2VrfRoutTracertDataEntry ::=
   SEQUENCE
      {
      ar1645v2VrfRoutTracertDataGlobalIx
         GlobalIndex,
      ar1645v2VrfRoutTracertDataIpAddress
         IpAddress,
      ar1645v2VrfRoutTracertDataHostName
         DisplayString,
      ar1645v2VrfRoutTracertDataSourceIp
         IpAddress,
      ar1645v2VrfRoutTracertDataStartTtl
         Integer32,
      ar1645v2VrfRoutTracertDataMaxHops
         Integer32,
      ar1645v2VrfRoutTracertDataQueriesPerHop
         Integer32,
      ar1645v2VrfRoutTracertDataResolveHosts
         INTEGER,
      ar1645v2VrfRoutTracertDataDnsTimeOut
         TimeTicks,
      ar1645v2VrfRoutTracertDataIcmpTimeOut
         TimeTicks,
      ar1645v2VrfRoutTracertDataTos
         INTEGER,
      ar1645v2VrfRoutTracertDataDataLength
         Integer32
      }

ar1645v2VrfRoutTracertDataGlobalIx OBJECT-TYPE
   SYNTAX      GlobalIndex
   MAX-ACCESS  not-accessible
   STATUS      current
   DESCRIPTION
      "The value of the tlsCntTreeGlobalIndex of the MANAGED OBJECT."
   ::= {ar1645v2VrfRoutTracertDataEntry 10}

ar1645v2VrfRoutTracertDataIpAddress OBJECT-TYPE
   SYNTAX      IpAddress
   MAX-ACCESS  read-write
   STATUS      current
   DESCRIPTION
      "Path: vrfRouter.actions.tracertData.ipAddress"
   ::= {ar1645v2VrfRoutTracertDataEntry 16777216}

ar1645v2VrfRoutTracertDataHostName OBJECT-TYPE
   SYNTAX      DisplayString
   MAX-ACCESS  read-write
   STATUS      current
   DESCRIPTION
      "Path: vrfRouter.actions.tracertData.hostName"
   ::= {ar1645v2VrfRoutTracertDataEntry 33554432}

ar1645v2VrfRoutTracertDataSourceIp OBJECT-TYPE
   SYNTAX      IpAddress
   MAX-ACCESS  read-write
   STATUS      current
   DESCRIPTION
      "Path: vrfRouter.actions.tracertData.sourceIp"
   ::= {ar1645v2VrfRoutTracertDataEntry 50331648}

ar1645v2VrfRoutTracertDataStartTtl OBJECT-TYPE
   SYNTAX      Integer32
   MAX-ACCESS  read-write
   STATUS      current
   DESCRIPTION
      "Path: vrfRouter.actions.tracertData.startTtl"
   ::= {ar1645v2VrfRoutTracertDataEntry 67108864}

ar1645v2VrfRoutTracertDataMaxHops OBJECT-TYPE
   SYNTAX      Integer32
   MAX-ACCESS  read-write
   STATUS      current
   DESCRIPTION
      "Path: vrfRouter.actions.tracertData.maxHops"
   ::= {ar1645v2VrfRoutTracertDataEntry 83886080}

ar1645v2VrfRoutTracertDataQueriesPerHop OBJECT-TYPE
   SYNTAX      Integer32
   MAX-ACCESS  read-write
   STATUS      current
   DESCRIPTION
      "Path: vrfRouter.actions.tracertData.queriesPerHop"
   ::= {ar1645v2VrfRoutTracertDataEntry 100663296}

ar1645v2VrfRoutTracertDataResolveHosts OBJECT-TYPE
   SYNTAX      INTEGER
               {
               disabled (0),
               enabled (1)
               }
   MAX-ACCESS  read-write
   STATUS      current
   DESCRIPTION
      "Path: vrfRouter.actions.tracertData.resolveHosts

       Possibilities:
               disabled   (0)
               enabled   (1)"
   ::= {ar1645v2VrfRoutTracertDataEntry 117440512}

ar1645v2VrfRoutTracertDataDnsTimeOut OBJECT-TYPE
   SYNTAX      TimeTicks
   MAX-ACCESS  read-write
   STATUS      current
   DESCRIPTION
      "Path: vrfRouter.actions.tracertData.dnsTimeOut

       Time in centi-second."
   ::= {ar1645v2VrfRoutTracertDataEntry 134217728}

ar1645v2VrfRoutTracertDataIcmpTimeOut OBJECT-TYPE
   SYNTAX      TimeTicks
   MAX-ACCESS  read-write
   STATUS      current
   DESCRIPTION
      "Path: vrfRouter.actions.tracertData.icmpTimeOut

       Time in centi-second."
   ::= {ar1645v2VrfRoutTracertDataEntry 150994944}

ar1645v2VrfRoutTracertDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouter.actions.tracertData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1645v2VrfRoutTracertDataEntry 167772160}

ar1645v2VrfRoutTracertDataDataLength OBJECT-TYPE
   SYNTAX      Integer32
   MAX-ACCESS  read-write
   STATUS      current
   DESCRIPTION
      "Path: vrfRouter.actions.tracertData.dataLength"
   ::= {ar1645v2VrfRoutTracertDataEntry 184549376}


ar1645v2VrfRoutStopPing OBJECT IDENTIFIER ::= {ar1645v2VrfRout 45}

ar1645v2VrfRoutStopPingTable OBJECT-TYPE
   SYNTAX      SEQUENCE OF Ar1645v2VrfRoutStopPingEntry
   MAX-ACCESS  not-accessible
   STATUS      current
   DESCRIPTION
      "stop sending pings"
   ::= {ar1645v2VrfRoutStopPing 1}

ar1645v2VrfRoutStopPingEntry OBJECT-TYPE
   SYNTAX      Ar1645v2VrfRoutStopPingEntry
   MAX-ACCESS  not-accessible
   STATUS      current
   DESCRIPTION
      ""
   INDEX      { ar1645v2VrfRoutStopPingGlobalIx }
   ::= {ar1645v2VrfRoutStopPingTable 1}

Ar1645v2VrfRoutStopPingEntry ::=
   SEQUENCE
      {
      ar1645v2VrfRoutStopPingGlobalIx
         GlobalIndex,
      ar1645v2VrfRoutStopPingValue
         Integer32
      }

ar1645v2VrfRoutStopPingGlobalIx OBJECT-TYPE
   SYNTAX      GlobalIndex
   MAX-ACCESS  not-accessible
   STATUS      current
   DESCRIPTION
      "The value of the tlsCntTreeGlobalIndex of the MANAGED OBJECT."
   ::= {ar1645v2VrfRoutStopPingEntry 10}

ar1645v2VrfRoutStopPingValue OBJECT-TYPE
   SYNTAX      Integer32
   MAX-ACCESS  read-write
   STATUS      current
   DESCRIPTION
      "Path: vrfRouter.actions.stopPing"
   ::= {ar1645v2VrfRoutStopPingEntry 2147483648}


ar1645v2VrfRoutStartPing OBJECT IDENTIFIER ::= {ar1645v2VrfRout 43}

ar1645v2VrfRoutStartPingTable OBJECT-TYPE
   SYNTAX      SEQUENCE OF Ar1645v2VrfRoutStartPingEntry
   MAX-ACCESS  not-accessible
   STATUS      current
   DESCRIPTION
      "start sending pings"
   ::= {ar1645v2VrfRoutStartPing 1}

ar1645v2VrfRoutStartPingEntry OBJECT-TYPE
   SYNTAX      Ar1645v2VrfRoutStartPingEntry
   MAX-ACCESS  not-accessible
   STATUS      current
   DESCRIPTION
      ""
   INDEX      { ar1645v2VrfRoutStartPingGlobalIx }
   ::= {ar1645v2VrfRoutStartPingTable 1}

Ar1645v2VrfRoutStartPingEntry ::=
   SEQUENCE
      {
      ar1645v2VrfRoutStartPingGlobalIx
         GlobalIndex,
      ar1645v2VrfRoutStartPingValue
         Integer32
      }

ar1645v2VrfRoutStartPingGlobalIx OBJECT-TYPE
   SYNTAX      GlobalIndex
   MAX-ACCESS  not-accessible
   STATUS      current
   DESCRIPTION
      "The value of the tlsCntTreeGlobalIndex of the MANAGED OBJECT."
   ::= {ar1645v2VrfRoutStartPingEntry 10}

ar1645v2VrfRoutStartPingValue OBJECT-TYPE
   SYNTAX      Integer32
   MAX-ACCESS  read-write
   STATUS      current
   DESCRIPTION
      "Path: vrfRouter.actions.startPing"
   ::= {ar1645v2VrfRoutStartPingEntry 2147483648}


ar1645v2VrfRoutPingData OBJECT IDENTIFIER ::= {ar1645v2VrfRout 44}

ar1645v2VrfRoutPingDataSSCTable OBJECT-TYPE
   SYNTAX      SEQUENCE OF Ar1645v2VrfRoutPingDataEntry
   MAX-ACCESS  not-accessible
   STATUS      current
   DESCRIPTION
      "data needed for ping"
   ::= {ar1645v2VrfRoutPingData 1}

ar1645v2VrfRoutPingDataEntry OBJECT-TYPE
   SYNTAX      Ar1645v2VrfRoutPingDataEntry
   MAX-ACCESS  not-accessible
   STATUS      current
   DESCRIPTION
      ""
   INDEX      { ar1645v2VrfRoutPingDataGlobalIx }
   ::= {ar1645v2VrfRoutPingDataSSCTable 1}

Ar1645v2VrfRoutPingDataEntry ::=
   SEQUENCE
      {
      ar1645v2VrfRoutPingDataGlobalIx
         GlobalIndex,
      ar1645v2VrfRoutPingDataIpAddress
         IpAddress,
      ar1645v2VrfRoutPingDataHostName
         DisplayString,
      ar1645v2VrfRoutPingDataSourceIp
         IpAddress,
      ar1645v2VrfRoutPingDataTos
         INTEGER,
      ar1645v2VrfRoutPingDataFragment
         INTEGER,
      ar1645v2VrfRoutPingDataTtl
         Integer32,
      ar1645v2VrfRoutPingDataIterations
         INTEGER,
      ar1645v2VrfRoutPingDataInterval
         Integer32,
      ar1645v2VrfRoutPingDataDataLength
         Integer32,
      ar1645v2VrfRoutPingDataTimeOut
         TimeTicks
      }

ar1645v2VrfRoutPingDataGlobalIx OBJECT-TYPE
   SYNTAX      GlobalIndex
   MAX-ACCESS  not-accessible
   STATUS      current
   DESCRIPTION
      "The value of the tlsCntTreeGlobalIndex of the MANAGED OBJECT."
   ::= {ar1645v2VrfRoutPingDataEntry 10}

ar1645v2VrfRoutPingDataIpAddress OBJECT-TYPE
   SYNTAX      IpAddress
   MAX-ACCESS  read-write
   STATUS      current
   DESCRIPTION
      "Path: vrfRouter.actions.pingData.ipAddress"
   ::= {ar1645v2VrfRoutPingDataEntry 16777216}

ar1645v2VrfRoutPingDataHostName OBJECT-TYPE
   SYNTAX      DisplayString
   MAX-ACCESS  read-write
   STATUS      current
   DESCRIPTION
      "Path: vrfRouter.actions.pingData.hostName"
   ::= {ar1645v2VrfRoutPingDataEntry 100663296}

ar1645v2VrfRoutPingDataSourceIp OBJECT-TYPE
   SYNTAX      IpAddress
   MAX-ACCESS  read-write
   STATUS      current
   DESCRIPTION
      "Path: vrfRouter.actions.pingData.sourceIp"
   ::= {ar1645v2VrfRoutPingDataEntry 117440512}

ar1645v2VrfRoutPingDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouter.actions.pingData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1645v2VrfRoutPingDataEntry 134217728}

ar1645v2VrfRoutPingDataFragment OBJECT-TYPE
   SYNTAX      INTEGER
               {
               yes (1),
               no (2)
               }
   MAX-ACCESS  read-write
   STATUS      current
   DESCRIPTION
      "Path: vrfRouter.actions.pingData.fragment

       Possibilities:
               yes   (1)
               no   (2)"
   ::= {ar1645v2VrfRoutPingDataEntry 150994944}

ar1645v2VrfRoutPingDataTtl OBJECT-TYPE
   SYNTAX      Integer32
   MAX-ACCESS  read-write
   STATUS      current
   DESCRIPTION
      "Path: vrfRouter.actions.pingData.ttl"
   ::= {ar1645v2VrfRoutPingDataEntry 167772160}

ar1645v2VrfRoutPingDataIterations OBJECT-TYPE
   SYNTAX      INTEGER
               {
               unlimited (0)
               }
   MAX-ACCESS  read-write
   STATUS      current
   DESCRIPTION
      "Path: vrfRouter.actions.pingData.iterations

       Possibilities:
               unlimited   (0)"
   ::= {ar1645v2VrfRoutPingDataEntry 33554432}

ar1645v2VrfRoutPingDataInterval OBJECT-TYPE
   SYNTAX      Integer32
   MAX-ACCESS  read-write
   STATUS      current
   DESCRIPTION
      "Path: vrfRouter.actions.pingData.interval"
   ::= {ar1645v2VrfRoutPingDataEntry 50331648}

ar1645v2VrfRoutPingDataDataLength OBJECT-TYPE
   SYNTAX      Integer32
   MAX-ACCESS  read-write
   STATUS      current
   DESCRIPTION
      "Path: vrfRouter.actions.pingData.dataLength"
   ::= {ar1645v2VrfRoutPingDataEntry 67108864}

ar1645v2VrfRoutPingDataTimeOut OBJECT-TYPE
   SYNTAX      TimeTicks
   MAX-ACCESS  read-write
   STATUS      current
   DESCRIPTION
      "Path: vrfRouter.actions.pingData.timeOut

       Time in centi-second."
   ::= {ar1645v2VrfRoutPingDataEntry 83886080}


ar1645v2VrfRoutClearCounters OBJECT IDENTIFIER ::= {ar1645v2VrfRout 263}

ar1645v2VrfRoutClearCountersTable OBJECT-TYPE
   SYNTAX      SEQUENCE OF Ar1645v2VrfRoutClearCountersEntry
   MAX-ACCESS  not-accessible
   STATUS      current
   DESCRIPTION
      "reset counters"
   ::= {ar1645v2VrfRoutClearCounters 1}

ar1645v2VrfRoutClearCountersEntry OBJECT-TYPE
   SYNTAX      Ar1645v2VrfRoutClearCountersEntry
   MAX-ACCESS  not-accessible
   STATUS      current
   DESCRIPTION
      ""
   INDEX      { ar1645v2VrfRoutClearCountersGlobalIx }
   ::= {ar1645v2VrfRoutClearCountersTable 1}

Ar1645v2VrfRoutClearCountersEntry ::=
   SEQUENCE
      {
      ar1645v2VrfRoutClearCountersGlobalIx
         GlobalIndex,
      ar1645v2VrfRoutClearCountersValue
         Integer32
      }

ar1645v2VrfRoutClearCountersGlobalIx OBJECT-TYPE
   SYNTAX      GlobalIndex
   MAX-ACCESS  not-accessible
   STATUS      current
   DESCRIPTION
      "The value of the tlsCntTreeGlobalIndex of the MANAGED OBJECT."
   ::= {ar1645v2VrfRoutClearCountersEntry 10}

ar1645v2VrfRoutClearCountersValue OBJECT-TYPE
   SYNTAX      Integer32
   MAX-ACCESS  read-write
   STATUS      current
   DESCRIPTION
      "Path: vrfRouter.actions.clearCounters"
   ::= {ar1645v2VrfRoutClearCountersEntry 2147483648}


ar1645v2VrfRoutClearDnsCache OBJECT IDENTIFIER ::= {ar1645v2VrfRout 155}

ar1645v2VrfRoutClearDnsCacheTable OBJECT-TYPE
   SYNTAX      SEQUENCE OF Ar1645v2VrfRoutClearDnsCacheEntry
   MAX-ACCESS  not-accessible
   STATUS      current
   DESCRIPTION
      "clear the DNS cache table"
   ::= {ar1645v2VrfRoutClearDnsCache 1}

ar1645v2VrfRoutClearDnsCacheEntry OBJECT-TYPE
   SYNTAX      Ar1645v2VrfRoutClearDnsCacheEntry
   MAX-ACCESS  not-accessible
   STATUS      current
   DESCRIPTION
      ""
   INDEX      { ar1645v2VrfRoutClearDnsCacheGlobalIx }
   ::= {ar1645v2VrfRoutClearDnsCacheTable 1}

Ar1645v2VrfRoutClearDnsCacheEntry ::=
   SEQUENCE
      {
      ar1645v2VrfRoutClearDnsCacheGlobalIx
         GlobalIndex,
      ar1645v2VrfRoutClearDnsCacheValue
         Integer32
      }

ar1645v2VrfRoutClearDnsCacheGlobalIx OBJECT-TYPE
   SYNTAX      GlobalIndex
   MAX-ACCESS  not-accessible
   STATUS      current
   DESCRIPTION
      "The value of the tlsCntTreeGlobalIndex of the MANAGED OBJECT."
   ::= {ar1645v2VrfRoutClearDnsCacheEntry 10}

ar1645v2VrfRoutClearDnsCacheValue OBJECT-TYPE
   SYNTAX      Integer32
   MAX-ACCESS  read-write
   STATUS      current
   DESCRIPTION
      "Path: vrfRouter.actions.clearDnsCache"
   ::= {ar1645v2VrfRoutClearDnsCacheEntry 2147483648}



END
