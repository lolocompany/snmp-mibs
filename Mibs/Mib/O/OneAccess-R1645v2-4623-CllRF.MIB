OneAccess-R1645v2-4623-CllRF DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2CllRF OBJECT IDENTIFIER ::= {r1645Rootv2 4623}

r1645v2CllRFMOProp OBJECT-TYPE
   SYNTAX      SEQUENCE OF R1645v2CllRFMOPropEntry
   MAX-ACCESS  not-accessible
   STATUS      current
   DESCRIPTION
      ""
   ::= {r1645v2CllRF 1}

r1645v2CllRFMOPropEntry OBJECT-TYPE
   SYNTAX      R1645v2CllRFMOPropEntry
   MAX-ACCESS  not-accessible
   STATUS      current
   DESCRIPTION
      ""
   INDEX      { r1645v2CllRFMOPropGlobalIx }
   ::= {r1645v2CllRFMOProp 1}

R1645v2CllRFMOPropEntry ::=
   SEQUENCE
      {
      r1645v2CllRFMOPropPath
         ContainmentPath,
      r1645v2CllRFMOPropRev
         ObjectRevision,
      r1645v2CllRFMOPropGlobalIx
         GlobalIndex
      }

r1645v2CllRFMOPropPath OBJECT-TYPE
   SYNTAX      ContainmentPath
   MAX-ACCESS  read-only
   STATUS      current
   DESCRIPTION
      "Textual description of the containment tree from the instance of
       the root object down to the instance of the current object."
   ::= {r1645v2CllRFMOPropEntry 3}

r1645v2CllRFMOPropRev OBJECT-TYPE
   SYNTAX      ObjectRevision
   MAX-ACCESS  read-only
   STATUS      current
   DESCRIPTION
      "This value corresponds with the revision of the MANAGED OBJECT."
   ::= {r1645v2CllRFMOPropEntry 4}

r1645v2CllRFMOPropGlobalIx OBJECT-TYPE
   SYNTAX      GlobalIndex
   MAX-ACCESS  read-only
   STATUS      current
   DESCRIPTION
      "The value of the tlsCntTreeGlobalIndex of the MANAGED OBJECT."
   ::= {r1645v2CllRFMOPropEntry 10}



er1645v2CllRF OBJECT IDENTIFIER ::= {r1645v2CllRF 11}


er1645v2CllRFRemark OBJECT IDENTIFIER ::= {er1645v2CllRF 321}

er1645v2CllRFRemarkTable OBJECT-TYPE
   SYNTAX      SEQUENCE OF Er1645v2CllRFRemarkEntry
   MAX-ACCESS  not-accessible
   STATUS      current
   DESCRIPTION
      "intfRemark"
   ::= {er1645v2CllRFRemark 1}

er1645v2CllRFRemarkEntry OBJECT-TYPE
   SYNTAX      Er1645v2CllRFRemarkEntry
   MAX-ACCESS  not-accessible
   STATUS      current
   DESCRIPTION
      ""
   INDEX      { er1645v2CllRFRemarkGlobalIx }
   ::= {er1645v2CllRFRemarkTable 1}

Er1645v2CllRFRemarkEntry ::=
   SEQUENCE
      {
      er1645v2CllRFRemarkGlobalIx
         GlobalIndex,
      er1645v2CllRFRemarkValue
         DisplayString
      }

er1645v2CllRFRemarkGlobalIx OBJECT-TYPE
   SYNTAX      GlobalIndex
   MAX-ACCESS  not-accessible
   STATUS      current
   DESCRIPTION
      "The value of the tlsCntTreeGlobalIndex of the MANAGED OBJECT."
   ::= {er1645v2CllRFRemarkEntry 10}

er1645v2CllRFRemarkValue OBJECT-TYPE
   SYNTAX      DisplayString
   MAX-ACCESS  read-write
   STATUS      current
   DESCRIPTION
      "Path: cellular.editConf.remark"
   ::= {er1645v2CllRFRemarkEntry 2147483648}


er1645v2CllRFRatMode OBJECT IDENTIFIER ::= {er1645v2CllRF 3}

er1645v2CllRFRatModeTable OBJECT-TYPE
   SYNTAX      SEQUENCE OF Er1645v2CllRFRatModeEntry
   MAX-ACCESS  not-accessible
   STATUS      current
   DESCRIPTION
      "Radio technology mode"
   ::= {er1645v2CllRFRatMode 1}

er1645v2CllRFRatModeEntry OBJECT-TYPE
   SYNTAX      Er1645v2CllRFRatModeEntry
   MAX-ACCESS  not-accessible
   STATUS      current
   DESCRIPTION
      ""
   INDEX      { er1645v2CllRFRatModeGlobalIx }
   ::= {er1645v2CllRFRatModeTable 1}

Er1645v2CllRFRatModeEntry ::=
   SEQUENCE
      {
      er1645v2CllRFRatModeGlobalIx
         GlobalIndex,
      er1645v2CllRFRatModeValue
         Integer32
      }

er1645v2CllRFRatModeGlobalIx OBJECT-TYPE
   SYNTAX      GlobalIndex
   MAX-ACCESS  not-accessible
   STATUS      current
   DESCRIPTION
      "The value of the tlsCntTreeGlobalIndex of the MANAGED OBJECT."
   ::= {er1645v2CllRFRatModeEntry 10}

er1645v2CllRFRatModeValue OBJECT-TYPE
   SYNTAX      Integer32
   MAX-ACCESS  read-write
   STATUS      current
   DESCRIPTION
      "Path: cellular.editConf.ratMode

       Bit meanings:
               bit 0 = 2g,
               bit 1 = 3g,
               bit 2 = 4g"
   ::= {er1645v2CllRFRatModeEntry 2147483648}


er1645v2CllRFOperation OBJECT IDENTIFIER ::= {er1645v2CllRF 4}

er1645v2CllRFOperationTable OBJECT-TYPE
   SYNTAX      SEQUENCE OF Er1645v2CllRFOperationEntry
   MAX-ACCESS  not-accessible
   STATUS      current
   DESCRIPTION
      "EthernetPdp or DefaultPdp"
   ::= {er1645v2CllRFOperation 1}

er1645v2CllRFOperationEntry OBJECT-TYPE
   SYNTAX      Er1645v2CllRFOperationEntry
   MAX-ACCESS  not-accessible
   STATUS      current
   DESCRIPTION
      ""
   INDEX      { er1645v2CllRFOperationGlobalIx }
   ::= {er1645v2CllRFOperationTable 1}

Er1645v2CllRFOperationEntry ::=
   SEQUENCE
      {
      er1645v2CllRFOperationGlobalIx
         GlobalIndex,
      er1645v2CllRFOperationValue
         INTEGER
      }

er1645v2CllRFOperationGlobalIx OBJECT-TYPE
   SYNTAX      GlobalIndex
   MAX-ACCESS  not-accessible
   STATUS      current
   DESCRIPTION
      "The value of the tlsCntTreeGlobalIndex of the MANAGED OBJECT."
   ::= {er1645v2CllRFOperationEntry 10}

er1645v2CllRFOperationValue OBJECT-TYPE
   SYNTAX      INTEGER
               {
               ethernetPdp (1),
               defaultPdp (2)
               }
   MAX-ACCESS  read-write
   STATUS      current
   DESCRIPTION
      "Path: cellular.editConf.operation

       Possibilities:
               ethernetPdp   (1)
               defaultPdp   (2)"
   ::= {er1645v2CllRFOperationEntry 2147483648}


er1645v2CllRFSimProfiles OBJECT IDENTIFIER ::= {er1645v2CllRF 5}

er1645v2CllRFSimProfilesSSCTable OBJECT-TYPE
   SYNTAX      SEQUENCE OF Er1645v2CllRFSimProfilesEntry
   MAX-ACCESS  not-accessible
   STATUS      current
   DESCRIPTION
      "cellular profile configuration table"
   ::= {er1645v2CllRFSimProfiles 1}

er1645v2CllRFSimProfilesEntry OBJECT-TYPE
   SYNTAX      Er1645v2CllRFSimProfilesEntry
   MAX-ACCESS  not-accessible
   STATUS      current
   DESCRIPTION
      ""
   INDEX      { er1645v2CllRFSimProfilesGlobalIx,
                er1645v2CllRFSimProfilesTableIx }
   ::= {er1645v2CllRFSimProfilesSSCTable 1}

Er1645v2CllRFSimProfilesEntry ::=
   SEQUENCE
      {
      er1645v2CllRFSimProfilesActions
         VariableLengthTableActions,
      er1645v2CllRFSimProfilesGlobalIx
         GlobalIndex,
      er1645v2CllRFSimProfilesTableIx
         TableIndex,
      er1645v2CllRFSimProfilesName
         DisplayString,
      er1645v2CllRFSimProfilesRemark
         DisplayString,
      er1645v2CllRFSimProfilesIpProtocol
         INTEGER,
      er1645v2CllRFSimProfilesApn
         DisplayString,
      er1645v2CllRFSimProfilesAuthenticationSessionAuthMethod
         INTEGER,
      er1645v2CllRFSimProfilesAuthenticationSessionName
         DisplayString,
      er1645v2CllRFSimProfilesAuthenticationSessionSecret
         DisplayString,
      er1645v2CllRFSimProfilesAuthenticationEncModeSessionSecret
         INTEGER,
      er1645v2CllRFSimProfilesAuthenticationEncSessionSecret
         DisplayString
      }

er1645v2CllRFSimProfilesActions OBJECT-TYPE
   SYNTAX      VariableLengthTableActions
   MAX-ACCESS  read-write
   STATUS      current
   DESCRIPTION
      "By way of this field, some manipulations
       on this table may be performed."
   ::= {er1645v2CllRFSimProfilesEntry 2}

er1645v2CllRFSimProfilesGlobalIx OBJECT-TYPE
   SYNTAX      GlobalIndex
   MAX-ACCESS  not-accessible
   STATUS      current
   DESCRIPTION
      "The value of the tlsCntTreeGlobalIndex of the MANAGED OBJECT."
   ::= {er1645v2CllRFSimProfilesEntry 10}

er1645v2CllRFSimProfilesTableIx OBJECT-TYPE
   SYNTAX      TableIndex
   MAX-ACCESS  not-accessible
   STATUS      current
   DESCRIPTION
      ""
   ::= {er1645v2CllRFSimProfilesEntry 11}

er1645v2CllRFSimProfilesName OBJECT-TYPE
   SYNTAX      DisplayString
   MAX-ACCESS  read-write
   STATUS      current
   DESCRIPTION
      "Path: cellular.editConf.simProfiles.name"
   ::= {er1645v2CllRFSimProfilesEntry 16777216}

er1645v2CllRFSimProfilesRemark OBJECT-TYPE
   SYNTAX      DisplayString
   MAX-ACCESS  read-write
   STATUS      current
   DESCRIPTION
      "Path: cellular.editConf.simProfiles.remark"
   ::= {er1645v2CllRFSimProfilesEntry 33554432}

er1645v2CllRFSimProfilesIpProtocol OBJECT-TYPE
   SYNTAX      INTEGER
               {
               ipV4 (1),
               ipV6 (2),
               ipV4ipV6 (3)
               }
   MAX-ACCESS  read-write
   STATUS      current
   DESCRIPTION
      "Path: cellular.editConf.simProfiles.ipProtocol

       Possibilities:
               ipV4   (1)
               ipV6   (2)
               ipV4/ipV6   (3)"
   ::= {er1645v2CllRFSimProfilesEntry 50331648}

er1645v2CllRFSimProfilesApn OBJECT-TYPE
   SYNTAX      DisplayString
   MAX-ACCESS  read-write
   STATUS      current
   DESCRIPTION
      "Path: cellular.editConf.simProfiles.apn"
   ::= {er1645v2CllRFSimProfilesEntry 67108864}

er1645v2CllRFSimProfilesAuthenticationSessionAuthMethod OBJECT-TYPE
   SYNTAX      INTEGER
               {
               none (1),
               pap (2),
               chap (3),
               chappap (4)
               }
   MAX-ACCESS  read-write
   STATUS      current
   DESCRIPTION
      "Path: cellular.editConf.simProfiles.authentication.sessionAuthMethod

       Possibilities:
               none   (1)
               pap   (2)
               chap   (3)
               chap/pap   (4)"
   ::= {er1645v2CllRFSimProfilesEntry 84738048}

er1645v2CllRFSimProfilesAuthenticationSessionName OBJECT-TYPE
   SYNTAX      DisplayString
   MAX-ACCESS  read-write
   STATUS      current
   DESCRIPTION
      "Path: cellular.editConf.simProfiles.authentication.sessionName"
   ::= {er1645v2CllRFSimProfilesEntry 84213760}

er1645v2CllRFSimProfilesAuthenticationSessionSecret OBJECT-TYPE
   SYNTAX      DisplayString
   MAX-ACCESS  read-write
   STATUS      current
   DESCRIPTION
      "Path: cellular.editConf.simProfiles.authentication.sessionSecret"
   ::= {er1645v2CllRFSimProfilesEntry 84279296}

er1645v2CllRFSimProfilesAuthenticationEncModeSessionSecret OBJECT-TYPE
   SYNTAX      INTEGER
               {
               none (1),
               encrypt (2),
               encType1 (3),
               invalid (128)
               }
   MAX-ACCESS  read-write
   STATUS      current
   DESCRIPTION
      "Path: cellular.editConf.simProfiles.authentication.encModeSessionSecret

       Possibilities:
               none   (1)
               encrypt   (2)
               encType1   (3)
               invalid   (128)"
   ::= {er1645v2CllRFSimProfilesEntry 84606976}

er1645v2CllRFSimProfilesAuthenticationEncSessionSecret OBJECT-TYPE
   SYNTAX      DisplayString
   MAX-ACCESS  read-write
   STATUS      current
   DESCRIPTION
      "Path: cellular.editConf.simProfiles.authentication.encSessionSecret"
   ::= {er1645v2CllRFSimProfilesEntry 84672512}


er1645v2CllRFAttachProfile OBJECT IDENTIFIER ::= {er1645v2CllRF 6}

er1645v2CllRFAttachProfileTable OBJECT-TYPE
   SYNTAX      SEQUENCE OF Er1645v2CllRFAttachProfileEntry
   MAX-ACCESS  not-accessible
   STATUS      current
   DESCRIPTION
      "cellular attach profile"
   ::= {er1645v2CllRFAttachProfile 1}

er1645v2CllRFAttachProfileEntry OBJECT-TYPE
   SYNTAX      Er1645v2CllRFAttachProfileEntry
   MAX-ACCESS  not-accessible
   STATUS      current
   DESCRIPTION
      ""
   INDEX      { er1645v2CllRFAttachProfileGlobalIx }
   ::= {er1645v2CllRFAttachProfileTable 1}

Er1645v2CllRFAttachProfileEntry ::=
   SEQUENCE
      {
      er1645v2CllRFAttachProfileGlobalIx
         GlobalIndex,
      er1645v2CllRFAttachProfileValue
         DisplayString
      }

er1645v2CllRFAttachProfileGlobalIx OBJECT-TYPE
   SYNTAX      GlobalIndex
   MAX-ACCESS  not-accessible
   STATUS      current
   DESCRIPTION
      "The value of the tlsCntTreeGlobalIndex of the MANAGED OBJECT."
   ::= {er1645v2CllRFAttachProfileEntry 10}

er1645v2CllRFAttachProfileValue OBJECT-TYPE
   SYNTAX      DisplayString
   MAX-ACCESS  read-write
   STATUS      current
   DESCRIPTION
      "Path: cellular.editConf.attachProfile"
   ::= {er1645v2CllRFAttachProfileEntry 2147483648}



sr1645v2CllRF OBJECT IDENTIFIER ::= {r1645v2CllRF 14}


sr1645v2CllRFState OBJECT IDENTIFIER ::= {sr1645v2CllRF 46}

sr1645v2CllRFStateTable OBJECT-TYPE
   SYNTAX      SEQUENCE OF Sr1645v2CllRFStateEntry
   MAX-ACCESS  not-accessible
   STATUS      current
   DESCRIPTION
      "monitor state"
   ::= {sr1645v2CllRFState 1}

sr1645v2CllRFStateEntry OBJECT-TYPE
   SYNTAX      Sr1645v2CllRFStateEntry
   MAX-ACCESS  not-accessible
   STATUS      current
   DESCRIPTION
      ""
   INDEX      { sr1645v2CllRFStateGlobalIx }
   ::= {sr1645v2CllRFStateTable 1}

Sr1645v2CllRFStateEntry ::=
   SEQUENCE
      {
      sr1645v2CllRFStateGlobalIx
         GlobalIndex,
      sr1645v2CllRFStateValue
         INTEGER
      }

sr1645v2CllRFStateGlobalIx OBJECT-TYPE
   SYNTAX      GlobalIndex
   MAX-ACCESS  not-accessible
   STATUS      current
   DESCRIPTION
      "The value of the tlsCntTreeGlobalIndex of the MANAGED OBJECT."
   ::= {sr1645v2CllRFStateEntry 10}

sr1645v2CllRFStateValue OBJECT-TYPE
   SYNTAX      INTEGER
               {
               sync (0),
               init (1),
               reset (2),
               meinfo (3),
               checkSim (4),
               enterPin (5),
               msInfo (6),
               lowPower (7),
               searching (8),
               attached (9),
               error (10),
               firmwareUpgrade (11),
               monitorStopped (12),
               networkScan (13),
               powerDown (14)
               }
   MAX-ACCESS  read-only
   STATUS      current
   DESCRIPTION
      "Path: cellular.status.state

       Possibilities:
               sync   (0)
               init   (1)
               reset   (2)
               meinfo   (3)
               checkSim   (4)
               enterPin   (5)
               msInfo   (6)
               lowPower   (7)
               searching   (8)
               attached   (9)
               error   (10)
               firmwareUpgrade   (11)
               monitorStopped   (12)
               networkScan   (13)
               powerDown   (14)"
   ::= {sr1645v2CllRFStateEntry 2147483648}


sr1645v2CllRFCurrentOperator OBJECT IDENTIFIER ::= {sr1645v2CllRF 40}

sr1645v2CllRFCurrentOperatorTable OBJECT-TYPE
   SYNTAX      SEQUENCE OF Sr1645v2CllRFCurrentOperatorEntry
   MAX-ACCESS  not-accessible
   STATUS      current
   DESCRIPTION
      "misc. string"
   ::= {sr1645v2CllRFCurrentOperator 1}

sr1645v2CllRFCurrentOperatorEntry OBJECT-TYPE
   SYNTAX      Sr1645v2CllRFCurrentOperatorEntry
   MAX-ACCESS  not-accessible
   STATUS      current
   DESCRIPTION
      ""
   INDEX      { sr1645v2CllRFCurrentOperatorGlobalIx }
   ::= {sr1645v2CllRFCurrentOperatorTable 1}

Sr1645v2CllRFCurrentOperatorEntry ::=
   SEQUENCE
      {
      sr1645v2CllRFCurrentOperatorGlobalIx
         GlobalIndex,
      sr1645v2CllRFCurrentOperatorValue
         DisplayString
      }

sr1645v2CllRFCurrentOperatorGlobalIx OBJECT-TYPE
   SYNTAX      GlobalIndex
   MAX-ACCESS  not-accessible
   STATUS      current
   DESCRIPTION
      "The value of the tlsCntTreeGlobalIndex of the MANAGED OBJECT."
   ::= {sr1645v2CllRFCurrentOperatorEntry 10}

sr1645v2CllRFCurrentOperatorValue OBJECT-TYPE
   SYNTAX      DisplayString
   MAX-ACCESS  read-only
   STATUS      current
   DESCRIPTION
      "Path: cellular.status.currentOperator"
   ::= {sr1645v2CllRFCurrentOperatorEntry 2147483648}


sr1645v2CllRFCurrentAccessTechnology OBJECT IDENTIFIER ::= {sr1645v2CllRF 41}

sr1645v2CllRFCurrentAccessTechnologyTable OBJECT-TYPE
   SYNTAX      SEQUENCE OF Sr1645v2CllRFCurrentAccessTechnologyEntry
   MAX-ACCESS  not-accessible
   STATUS      current
   DESCRIPTION
      "misc. string"
   ::= {sr1645v2CllRFCurrentAccessTechnology 1}

sr1645v2CllRFCurrentAccessTechnologyEntry OBJECT-TYPE
   SYNTAX      Sr1645v2CllRFCurrentAccessTechnologyEntry
   MAX-ACCESS  not-accessible
   STATUS      current
   DESCRIPTION
      ""
   INDEX      { sr1645v2CllRFCurrentAccessTechnologyGlobalIx }
   ::= {sr1645v2CllRFCurrentAccessTechnologyTable 1}

Sr1645v2CllRFCurrentAccessTechnologyEntry ::=
   SEQUENCE
      {
      sr1645v2CllRFCurrentAccessTechnologyGlobalIx
         GlobalIndex,
      sr1645v2CllRFCurrentAccessTechnologyValue
         DisplayString
      }

sr1645v2CllRFCurrentAccessTechnologyGlobalIx OBJECT-TYPE
   SYNTAX      GlobalIndex
   MAX-ACCESS  not-accessible
   STATUS      current
   DESCRIPTION
      "The value of the tlsCntTreeGlobalIndex of the MANAGED OBJECT."
   ::= {sr1645v2CllRFCurrentAccessTechnologyEntry 10}

sr1645v2CllRFCurrentAccessTechnologyValue OBJECT-TYPE
   SYNTAX      DisplayString
   MAX-ACCESS  read-only
   STATUS      current
   DESCRIPTION
      "Path: cellular.status.currentAccessTechnology"
   ::= {sr1645v2CllRFCurrentAccessTechnologyEntry 2147483648}


sr1645v2CllRFCsRegisterState OBJECT IDENTIFIER ::= {sr1645v2CllRF 42}

sr1645v2CllRFCsRegisterStateTable OBJECT-TYPE
   SYNTAX      SEQUENCE OF Sr1645v2CllRFCsRegisterStateEntry
   MAX-ACCESS  not-accessible
   STATUS      current
   DESCRIPTION
      "misc. string"
   ::= {sr1645v2CllRFCsRegisterState 1}

sr1645v2CllRFCsRegisterStateEntry OBJECT-TYPE
   SYNTAX      Sr1645v2CllRFCsRegisterStateEntry
   MAX-ACCESS  not-accessible
   STATUS      current
   DESCRIPTION
      ""
   INDEX      { sr1645v2CllRFCsRegisterStateGlobalIx }
   ::= {sr1645v2CllRFCsRegisterStateTable 1}

Sr1645v2CllRFCsRegisterStateEntry ::=
   SEQUENCE
      {
      sr1645v2CllRFCsRegisterStateGlobalIx
         GlobalIndex,
      sr1645v2CllRFCsRegisterStateValue
         DisplayString
      }

sr1645v2CllRFCsRegisterStateGlobalIx OBJECT-TYPE
   SYNTAX      GlobalIndex
   MAX-ACCESS  not-accessible
   STATUS      current
   DESCRIPTION
      "The value of the tlsCntTreeGlobalIndex of the MANAGED OBJECT."
   ::= {sr1645v2CllRFCsRegisterStateEntry 10}

sr1645v2CllRFCsRegisterStateValue OBJECT-TYPE
   SYNTAX      DisplayString
   MAX-ACCESS  read-only
   STATUS      current
   DESCRIPTION
      "Path: cellular.status.csRegisterState"
   ::= {sr1645v2CllRFCsRegisterStateEntry 2147483648}


sr1645v2CllRFPsAttachState OBJECT IDENTIFIER ::= {sr1645v2CllRF 43}

sr1645v2CllRFPsAttachStateTable OBJECT-TYPE
   SYNTAX      SEQUENCE OF Sr1645v2CllRFPsAttachStateEntry
   MAX-ACCESS  not-accessible
   STATUS      current
   DESCRIPTION
      "misc. string"
   ::= {sr1645v2CllRFPsAttachState 1}

sr1645v2CllRFPsAttachStateEntry OBJECT-TYPE
   SYNTAX      Sr1645v2CllRFPsAttachStateEntry
   MAX-ACCESS  not-accessible
   STATUS      current
   DESCRIPTION
      ""
   INDEX      { sr1645v2CllRFPsAttachStateGlobalIx }
   ::= {sr1645v2CllRFPsAttachStateTable 1}

Sr1645v2CllRFPsAttachStateEntry ::=
   SEQUENCE
      {
      sr1645v2CllRFPsAttachStateGlobalIx
         GlobalIndex,
      sr1645v2CllRFPsAttachStateValue
         DisplayString
      }

sr1645v2CllRFPsAttachStateGlobalIx OBJECT-TYPE
   SYNTAX      GlobalIndex
   MAX-ACCESS  not-accessible
   STATUS      current
   DESCRIPTION
      "The value of the tlsCntTreeGlobalIndex of the MANAGED OBJECT."
   ::= {sr1645v2CllRFPsAttachStateEntry 10}

sr1645v2CllRFPsAttachStateValue OBJECT-TYPE
   SYNTAX      DisplayString
   MAX-ACCESS  read-only
   STATUS      current
   DESCRIPTION
      "Path: cellular.status.psAttachState"
   ::= {sr1645v2CllRFPsAttachStateEntry 2147483648}


sr1645v2CllRFModule OBJECT IDENTIFIER ::= {sr1645v2CllRF 48}

sr1645v2CllRFModuleSSCTable OBJECT-TYPE
   SYNTAX      SEQUENCE OF Sr1645v2CllRFModuleEntry
   MAX-ACCESS  not-accessible
   STATUS      current
   DESCRIPTION
      "module information"
   ::= {sr1645v2CllRFModule 1}

sr1645v2CllRFModuleEntry OBJECT-TYPE
   SYNTAX      Sr1645v2CllRFModuleEntry
   MAX-ACCESS  not-accessible
   STATUS      current
   DESCRIPTION
      ""
   INDEX      { sr1645v2CllRFModuleGlobalIx }
   ::= {sr1645v2CllRFModuleSSCTable 1}

Sr1645v2CllRFModuleEntry ::=
   SEQUENCE
      {
      sr1645v2CllRFModuleGlobalIx
         GlobalIndex,
      sr1645v2CllRFModuleManufacturer
         DisplayString,
      sr1645v2CllRFModuleModel
         DisplayString,
      sr1645v2CllRFModuleBootCode
         DisplayString,
      sr1645v2CllRFModuleRevision
         DisplayString,
      sr1645v2CllRFModuleImei
         DisplayString
      }

sr1645v2CllRFModuleGlobalIx OBJECT-TYPE
   SYNTAX      GlobalIndex
   MAX-ACCESS  not-accessible
   STATUS      current
   DESCRIPTION
      "The value of the tlsCntTreeGlobalIndex of the MANAGED OBJECT."
   ::= {sr1645v2CllRFModuleEntry 10}

sr1645v2CllRFModuleManufacturer OBJECT-TYPE
   SYNTAX      DisplayString
   MAX-ACCESS  read-only
   STATUS      current
   DESCRIPTION
      "Path: cellular.status.module.manufacturer"
   ::= {sr1645v2CllRFModuleEntry 16777216}

sr1645v2CllRFModuleModel OBJECT-TYPE
   SYNTAX      DisplayString
   MAX-ACCESS  read-only
   STATUS      current
   DESCRIPTION
      "Path: cellular.status.module.model"
   ::= {sr1645v2CllRFModuleEntry 33554432}

sr1645v2CllRFModuleBootCode OBJECT-TYPE
   SYNTAX      DisplayString
   MAX-ACCESS  read-only
   STATUS      current
   DESCRIPTION
      "Path: cellular.status.module.bootCode"
   ::= {sr1645v2CllRFModuleEntry 50331648}

sr1645v2CllRFModuleRevision OBJECT-TYPE
   SYNTAX      DisplayString
   MAX-ACCESS  read-only
   STATUS      current
   DESCRIPTION
      "Path: cellular.status.module.revision"
   ::= {sr1645v2CllRFModuleEntry 67108864}

sr1645v2CllRFModuleImei OBJECT-TYPE
   SYNTAX      DisplayString
   MAX-ACCESS  read-only
   STATUS      current
   DESCRIPTION
      "Path: cellular.status.module.imei"
   ::= {sr1645v2CllRFModuleEntry 83886080}

sr1645v2CllRFModuleImages OBJECT-TYPE
   SYNTAX      SEQUENCE OF Sr1645v2CllRFModuleImagesEntry
   MAX-ACCESS  not-accessible
   STATUS      current
   DESCRIPTION
      ""
   ::= {sr1645v2CllRFModule 100663296}

sr1645v2CllRFModuleImagesEntry OBJECT-TYPE
   SYNTAX      Sr1645v2CllRFModuleImagesEntry
   MAX-ACCESS  not-accessible
   STATUS      current
   DESCRIPTION
      ""
   INDEX      { sr1645v2CllRFModuleImagesGlobalIx,
                sr1645v2CllRFModuleImagesTableIx }
   ::= {sr1645v2CllRFModuleImages 1}

Sr1645v2CllRFModuleImagesEntry ::=
   SEQUENCE
      {
      sr1645v2CllRFModuleImagesGlobalIx
         GlobalIndex,
      sr1645v2CllRFModuleImagesTableIx
         TableIndex,
      sr1645v2CllRFModuleImagesType
         INTEGER,
      sr1645v2CllRFModuleImagesRunning
         INTEGER,
      sr1645v2CllRFModuleImagesVersion
         DisplayString,
      sr1645v2CllRFModuleImagesBuild
         DisplayString
      }

sr1645v2CllRFModuleImagesGlobalIx OBJECT-TYPE
   SYNTAX      GlobalIndex
   MAX-ACCESS  not-accessible
   STATUS      current
   DESCRIPTION
      "The value of the tlsCntTreeGlobalIndex of the MANAGED OBJECT."
   ::= {sr1645v2CllRFModuleImagesEntry 10}

sr1645v2CllRFModuleImagesTableIx OBJECT-TYPE
   SYNTAX      TableIndex
   MAX-ACCESS  not-accessible
   STATUS      current
   DESCRIPTION
      ""
   ::= {sr1645v2CllRFModuleImagesEntry 11}

sr1645v2CllRFModuleImagesType OBJECT-TYPE
   SYNTAX      INTEGER
               {
               unknown (0),
               cWE (1),
               nVU (2),
               sPK (3)
               }
   MAX-ACCESS  read-only
   STATUS      current
   DESCRIPTION
      "Path: cellular.status.module.images.type

       Possibilities:
               unknown   (0)
               CWE   (1)
               NVU   (2)
               SPK   (3)"
   ::= {sr1645v2CllRFModuleImagesEntry 16777216}

sr1645v2CllRFModuleImagesRunning OBJECT-TYPE
   SYNTAX      INTEGER
               {
               no (0),
               yes (1)
               }
   MAX-ACCESS  read-only
   STATUS      current
   DESCRIPTION
      "Path: cellular.status.module.images.running

       Possibilities:
               no   (0)
               yes   (1)"
   ::= {sr1645v2CllRFModuleImagesEntry 33554432}

sr1645v2CllRFModuleImagesVersion OBJECT-TYPE
   SYNTAX      DisplayString
   MAX-ACCESS  read-only
   STATUS      current
   DESCRIPTION
      "Path: cellular.status.module.images.version"
   ::= {sr1645v2CllRFModuleImagesEntry 50331648}

sr1645v2CllRFModuleImagesBuild OBJECT-TYPE
   SYNTAX      DisplayString
   MAX-ACCESS  read-only
   STATUS      current
   DESCRIPTION
      "Path: cellular.status.module.images.build"
   ::= {sr1645v2CllRFModuleImagesEntry 67108864}

sr1645v2CllRFModuleCurrentImages OBJECT-TYPE
   SYNTAX      SEQUENCE OF Sr1645v2CllRFModuleCurrentImagesEntry
   MAX-ACCESS  not-accessible
   STATUS      current
   DESCRIPTION
      ""
   ::= {sr1645v2CllRFModule 117440512}

sr1645v2CllRFModuleCurrentImagesEntry OBJECT-TYPE
   SYNTAX      Sr1645v2CllRFModuleCurrentImagesEntry
   MAX-ACCESS  not-accessible
   STATUS      current
   DESCRIPTION
      ""
   INDEX      { sr1645v2CllRFModuleCurrentImagesGlobalIx,
                sr1645v2CllRFModuleCurrentImagesTableIx }
   ::= {sr1645v2CllRFModuleCurrentImages 1}

Sr1645v2CllRFModuleCurrentImagesEntry ::=
   SEQUENCE
      {
      sr1645v2CllRFModuleCurrentImagesGlobalIx
         GlobalIndex,
      sr1645v2CllRFModuleCurrentImagesTableIx
         TableIndex,
      sr1645v2CllRFModuleCurrentImagesType
         INTEGER,
      sr1645v2CllRFModuleCurrentImagesVersion
         DisplayString,
      sr1645v2CllRFModuleCurrentImagesBuild
         DisplayString
      }

sr1645v2CllRFModuleCurrentImagesGlobalIx OBJECT-TYPE
   SYNTAX      GlobalIndex
   MAX-ACCESS  not-accessible
   STATUS      current
   DESCRIPTION
      "The value of the tlsCntTreeGlobalIndex of the MANAGED OBJECT."
   ::= {sr1645v2CllRFModuleCurrentImagesEntry 10}

sr1645v2CllRFModuleCurrentImagesTableIx OBJECT-TYPE
   SYNTAX      TableIndex
   MAX-ACCESS  not-accessible
   STATUS      current
   DESCRIPTION
      ""
   ::= {sr1645v2CllRFModuleCurrentImagesEntry 11}

sr1645v2CllRFModuleCurrentImagesType OBJECT-TYPE
   SYNTAX      INTEGER
               {
               unknown (0),
               cWE (1),
               nVU (2),
               sPK (3)
               }
   MAX-ACCESS  read-only
   STATUS      current
   DESCRIPTION
      "Path: cellular.status.module.currentImages.type

       Possibilities:
               unknown   (0)
               CWE   (1)
               NVU   (2)
               SPK   (3)"
   ::= {sr1645v2CllRFModuleCurrentImagesEntry 16777216}

sr1645v2CllRFModuleCurrentImagesVersion OBJECT-TYPE
   SYNTAX      DisplayString
   MAX-ACCESS  read-only
   STATUS      current
   DESCRIPTION
      "Path: cellular.status.module.currentImages.version"
   ::= {sr1645v2CllRFModuleCurrentImagesEntry 33554432}

sr1645v2CllRFModuleCurrentImagesBuild OBJECT-TYPE
   SYNTAX      DisplayString
   MAX-ACCESS  read-only
   STATUS      current
   DESCRIPTION
      "Path: cellular.status.module.currentImages.build"
   ::= {sr1645v2CllRFModuleCurrentImagesEntry 50331648}


sr1645v2CllRFNetwork OBJECT IDENTIFIER ::= {sr1645v2CllRF 49}

sr1645v2CllRFNetworkSSCTable OBJECT-TYPE
   SYNTAX      SEQUENCE OF Sr1645v2CllRFNetworkEntry
   MAX-ACCESS  not-accessible
   STATUS      current
   DESCRIPTION
      "network information"
   ::= {sr1645v2CllRFNetwork 1}

sr1645v2CllRFNetworkEntry OBJECT-TYPE
   SYNTAX      Sr1645v2CllRFNetworkEntry
   MAX-ACCESS  not-accessible
   STATUS      current
   DESCRIPTION
      ""
   INDEX      { sr1645v2CllRFNetworkGlobalIx }
   ::= {sr1645v2CllRFNetworkSSCTable 1}

Sr1645v2CllRFNetworkEntry ::=
   SEQUENCE
      {
      sr1645v2CllRFNetworkGlobalIx
         GlobalIndex,
      sr1645v2CllRFNetworkPlmn
         DisplayString,
      sr1645v2CllRFNetworkLac
         Integer32,
      sr1645v2CllRFNetworkTac
         Integer32,
      sr1645v2CllRFNetworkCellId
         Integer32
      }

sr1645v2CllRFNetworkGlobalIx OBJECT-TYPE
   SYNTAX      GlobalIndex
   MAX-ACCESS  not-accessible
   STATUS      current
   DESCRIPTION
      "The value of the tlsCntTreeGlobalIndex of the MANAGED OBJECT."
   ::= {sr1645v2CllRFNetworkEntry 10}

sr1645v2CllRFNetworkPlmn OBJECT-TYPE
   SYNTAX      DisplayString
   MAX-ACCESS  read-only
   STATUS      current
   DESCRIPTION
      "Path: cellular.status.network.plmn"
   ::= {sr1645v2CllRFNetworkEntry 16777216}

sr1645v2CllRFNetworkLac OBJECT-TYPE
   SYNTAX      Integer32
   MAX-ACCESS  read-only
   STATUS      current
   DESCRIPTION
      "Path: cellular.status.network.lac"
   ::= {sr1645v2CllRFNetworkEntry 33554432}

sr1645v2CllRFNetworkTac OBJECT-TYPE
   SYNTAX      Integer32
   MAX-ACCESS  read-only
   STATUS      current
   DESCRIPTION
      "Path: cellular.status.network.tac"
   ::= {sr1645v2CllRFNetworkEntry 50331648}

sr1645v2CllRFNetworkCellId OBJECT-TYPE
   SYNTAX      Integer32
   MAX-ACCESS  read-only
   STATUS      current
   DESCRIPTION
      "Path: cellular.status.network.cellId"
   ::= {sr1645v2CllRFNetworkEntry 67108864}


sr1645v2CllRFSnmpIndex OBJECT IDENTIFIER ::= {sr1645v2CllRF 269}

sr1645v2CllRFSnmpIndexTable OBJECT-TYPE
   SYNTAX      SEQUENCE OF Sr1645v2CllRFSnmpIndexEntry
   MAX-ACCESS  not-accessible
   STATUS      current
   DESCRIPTION
      "SNMP index assigned to this object"
   ::= {sr1645v2CllRFSnmpIndex 1}

sr1645v2CllRFSnmpIndexEntry OBJECT-TYPE
   SYNTAX      Sr1645v2CllRFSnmpIndexEntry
   MAX-ACCESS  not-accessible
   STATUS      current
   DESCRIPTION
      ""
   INDEX      { sr1645v2CllRFSnmpIndexGlobalIx }
   ::= {sr1645v2CllRFSnmpIndexTable 1}

Sr1645v2CllRFSnmpIndexEntry ::=
   SEQUENCE
      {
      sr1645v2CllRFSnmpIndexGlobalIx
         GlobalIndex,
      sr1645v2CllRFSnmpIndexValue
         Integer32
      }

sr1645v2CllRFSnmpIndexGlobalIx OBJECT-TYPE
   SYNTAX      GlobalIndex
   MAX-ACCESS  not-accessible
   STATUS      current
   DESCRIPTION
      "The value of the tlsCntTreeGlobalIndex of the MANAGED OBJECT."
   ::= {sr1645v2CllRFSnmpIndexEntry 10}

sr1645v2CllRFSnmpIndexValue OBJECT-TYPE
   SYNTAX      Integer32
   MAX-ACCESS  read-only
   STATUS      current
   DESCRIPTION
      "Path: cellular.status.snmpIndex"
   ::= {sr1645v2CllRFSnmpIndexEntry 2147483648}


sr1645v2CllRFRssi OBJECT IDENTIFIER ::= {sr1645v2CllRF 70}

sr1645v2CllRFRssiTable OBJECT-TYPE
   SYNTAX      SEQUENCE OF Sr1645v2CllRFRssiEntry
   MAX-ACCESS  not-accessible
   STATUS      current
   DESCRIPTION
      "rssi"
   ::= {sr1645v2CllRFRssi 1}

sr1645v2CllRFRssiEntry OBJECT-TYPE
   SYNTAX      Sr1645v2CllRFRssiEntry
   MAX-ACCESS  not-accessible
   STATUS      current
   DESCRIPTION
      ""
   INDEX      { sr1645v2CllRFRssiGlobalIx }
   ::= {sr1645v2CllRFRssiTable 1}

Sr1645v2CllRFRssiEntry ::=
   SEQUENCE
      {
      sr1645v2CllRFRssiGlobalIx
         GlobalIndex,
      sr1645v2CllRFRssiValue
         INTEGER
      }

sr1645v2CllRFRssiGlobalIx OBJECT-TYPE
   SYNTAX      GlobalIndex
   MAX-ACCESS  not-accessible
   STATUS      current
   DESCRIPTION
      "The value of the tlsCntTreeGlobalIndex of the MANAGED OBJECT."
   ::= {sr1645v2CllRFRssiEntry 10}

sr1645v2CllRFRssiValue OBJECT-TYPE
   SYNTAX      INTEGER
               {
               slOPTg (-128)
               }
   MAX-ACCESS  read-only
   STATUS      current
   DESCRIPTION
      "Path: cellular.status.rssi

       unit name = dBm
       formula = 1 * ; 1 /

       Possibilities:
               <OPT>   (-128)"
   ::= {sr1645v2CllRFRssiEntry 2147483648}


sr1645v2CllRFEcio OBJECT IDENTIFIER ::= {sr1645v2CllRF 71}

sr1645v2CllRFEcioTable OBJECT-TYPE
   SYNTAX      SEQUENCE OF Sr1645v2CllRFEcioEntry
   MAX-ACCESS  not-accessible
   STATUS      current
   DESCRIPTION
      "EcIo"
   ::= {sr1645v2CllRFEcio 1}

sr1645v2CllRFEcioEntry OBJECT-TYPE
   SYNTAX      Sr1645v2CllRFEcioEntry
   MAX-ACCESS  not-accessible
   STATUS      current
   DESCRIPTION
      ""
   INDEX      { sr1645v2CllRFEcioGlobalIx }
   ::= {sr1645v2CllRFEcioTable 1}

Sr1645v2CllRFEcioEntry ::=
   SEQUENCE
      {
      sr1645v2CllRFEcioGlobalIx
         GlobalIndex,
      sr1645v2CllRFEcioValue
         INTEGER
      }

sr1645v2CllRFEcioGlobalIx OBJECT-TYPE
   SYNTAX      GlobalIndex
   MAX-ACCESS  not-accessible
   STATUS      current
   DESCRIPTION
      "The value of the tlsCntTreeGlobalIndex of the MANAGED OBJECT."
   ::= {sr1645v2CllRFEcioEntry 10}

sr1645v2CllRFEcioValue OBJECT-TYPE
   SYNTAX      INTEGER
               {
               slOPTg (-32767)
               }
   MAX-ACCESS  read-only
   STATUS      current
   DESCRIPTION
      "Path: cellular.status.ecio

       unit name = dB
       formula = 2 / NEG ; 2 * NEG

       Possibilities:
               <OPT>   (-32767)"
   ::= {sr1645v2CllRFEcioEntry 2147483648}


sr1645v2CllRFRsrq OBJECT IDENTIFIER ::= {sr1645v2CllRF 72}

sr1645v2CllRFRsrqTable OBJECT-TYPE
   SYNTAX      SEQUENCE OF Sr1645v2CllRFRsrqEntry
   MAX-ACCESS  not-accessible
   STATUS      current
   DESCRIPTION
      "RSRQ"
   ::= {sr1645v2CllRFRsrq 1}

sr1645v2CllRFRsrqEntry OBJECT-TYPE
   SYNTAX      Sr1645v2CllRFRsrqEntry
   MAX-ACCESS  not-accessible
   STATUS      current
   DESCRIPTION
      ""
   INDEX      { sr1645v2CllRFRsrqGlobalIx }
   ::= {sr1645v2CllRFRsrqTable 1}

Sr1645v2CllRFRsrqEntry ::=
   SEQUENCE
      {
      sr1645v2CllRFRsrqGlobalIx
         GlobalIndex,
      sr1645v2CllRFRsrqValue
         INTEGER
      }

sr1645v2CllRFRsrqGlobalIx OBJECT-TYPE
   SYNTAX      GlobalIndex
   MAX-ACCESS  not-accessible
   STATUS      current
   DESCRIPTION
      "The value of the tlsCntTreeGlobalIndex of the MANAGED OBJECT."
   ::= {sr1645v2CllRFRsrqEntry 10}

sr1645v2CllRFRsrqValue OBJECT-TYPE
   SYNTAX      INTEGER
               {
               slOPTg (0)
               }
   UNITS       "dB"
   MAX-ACCESS  read-only
   STATUS      current
   DESCRIPTION
      "Path: cellular.status.rsrq

       unit name = dB

       Possibilities:
               <OPT>   (0)"
   ::= {sr1645v2CllRFRsrqEntry 2147483648}


sr1645v2CllRFRsrp OBJECT IDENTIFIER ::= {sr1645v2CllRF 73}

sr1645v2CllRFRsrpTable OBJECT-TYPE
   SYNTAX      SEQUENCE OF Sr1645v2CllRFRsrpEntry
   MAX-ACCESS  not-accessible
   STATUS      current
   DESCRIPTION
      "RSRP"
   ::= {sr1645v2CllRFRsrp 1}

sr1645v2CllRFRsrpEntry OBJECT-TYPE
   SYNTAX      Sr1645v2CllRFRsrpEntry
   MAX-ACCESS  not-accessible
   STATUS      current
   DESCRIPTION
      ""
   INDEX      { sr1645v2CllRFRsrpGlobalIx }
   ::= {sr1645v2CllRFRsrpTable 1}

Sr1645v2CllRFRsrpEntry ::=
   SEQUENCE
      {
      sr1645v2CllRFRsrpGlobalIx
         GlobalIndex,
      sr1645v2CllRFRsrpValue
         INTEGER
      }

sr1645v2CllRFRsrpGlobalIx OBJECT-TYPE
   SYNTAX      GlobalIndex
   MAX-ACCESS  not-accessible
   STATUS      current
   DESCRIPTION
      "The value of the tlsCntTreeGlobalIndex of the MANAGED OBJECT."
   ::= {sr1645v2CllRFRsrpEntry 10}

sr1645v2CllRFRsrpValue OBJECT-TYPE
   SYNTAX      INTEGER
               {
               slOPTg (0)
               }
   UNITS       "dBm"
   MAX-ACCESS  read-only
   STATUS      current
   DESCRIPTION
      "Path: cellular.status.rsrp

       unit name = dBm

       Possibilities:
               <OPT>   (0)"
   ::= {sr1645v2CllRFRsrpEntry 2147483648}


sr1645v2CllRFSnr OBJECT IDENTIFIER ::= {sr1645v2CllRF 74}

sr1645v2CllRFSnrTable OBJECT-TYPE
   SYNTAX      SEQUENCE OF Sr1645v2CllRFSnrEntry
   MAX-ACCESS  not-accessible
   STATUS      current
   DESCRIPTION
      "SNR"
   ::= {sr1645v2CllRFSnr 1}

sr1645v2CllRFSnrEntry OBJECT-TYPE
   SYNTAX      Sr1645v2CllRFSnrEntry
   MAX-ACCESS  not-accessible
   STATUS      current
   DESCRIPTION
      ""
   INDEX      { sr1645v2CllRFSnrGlobalIx }
   ::= {sr1645v2CllRFSnrTable 1}

Sr1645v2CllRFSnrEntry ::=
   SEQUENCE
      {
      sr1645v2CllRFSnrGlobalIx
         GlobalIndex,
      sr1645v2CllRFSnrValue
         INTEGER
      }

sr1645v2CllRFSnrGlobalIx OBJECT-TYPE
   SYNTAX      GlobalIndex
   MAX-ACCESS  not-accessible
   STATUS      current
   DESCRIPTION
      "The value of the tlsCntTreeGlobalIndex of the MANAGED OBJECT."
   ::= {sr1645v2CllRFSnrEntry 10}

sr1645v2CllRFSnrValue OBJECT-TYPE
   SYNTAX      INTEGER
               {
               slOPTg (-32767)
               }
   MAX-ACCESS  read-only
   STATUS      current
   DESCRIPTION
      "Path: cellular.status.snr

       unit name = dB
       formula = 10 /  ; 10 *

       Possibilities:
               <OPT>   (-32767)"
   ::= {sr1645v2CllRFSnrEntry 2147483648}



ar1645v2CllRF OBJECT IDENTIFIER ::= {r1645v2CllRF 16}


ar1645v2CllRFHipReset OBJECT IDENTIFIER ::= {ar1645v2CllRF 501}

ar1645v2CllRFHipResetTable OBJECT-TYPE
   SYNTAX      SEQUENCE OF Ar1645v2CllRFHipResetEntry
   MAX-ACCESS  not-accessible
   STATUS      current
   DESCRIPTION
      "hip reset"
   ::= {ar1645v2CllRFHipReset 1}

ar1645v2CllRFHipResetEntry OBJECT-TYPE
   SYNTAX      Ar1645v2CllRFHipResetEntry
   MAX-ACCESS  not-accessible
   STATUS      current
   DESCRIPTION
      ""
   INDEX      { ar1645v2CllRFHipResetGlobalIx }
   ::= {ar1645v2CllRFHipResetTable 1}

Ar1645v2CllRFHipResetEntry ::=
   SEQUENCE
      {
      ar1645v2CllRFHipResetGlobalIx
         GlobalIndex,
      ar1645v2CllRFHipResetValue
         Integer32
      }

ar1645v2CllRFHipResetGlobalIx OBJECT-TYPE
   SYNTAX      GlobalIndex
   MAX-ACCESS  not-accessible
   STATUS      current
   DESCRIPTION
      "The value of the tlsCntTreeGlobalIndex of the MANAGED OBJECT."
   ::= {ar1645v2CllRFHipResetEntry 10}

ar1645v2CllRFHipResetValue OBJECT-TYPE
   SYNTAX      Integer32
   MAX-ACCESS  read-write
   STATUS      current
   DESCRIPTION
      "Path: cellular.actions.hipReset"
   ::= {ar1645v2CllRFHipResetEntry 2147483648}


ar1645v2CllRFUsbReset OBJECT IDENTIFIER ::= {ar1645v2CllRF 500}

ar1645v2CllRFUsbResetTable OBJECT-TYPE
   SYNTAX      SEQUENCE OF Ar1645v2CllRFUsbResetEntry
   MAX-ACCESS  not-accessible
   STATUS      current
   DESCRIPTION
      "usb reset"
   ::= {ar1645v2CllRFUsbReset 1}

ar1645v2CllRFUsbResetEntry OBJECT-TYPE
   SYNTAX      Ar1645v2CllRFUsbResetEntry
   MAX-ACCESS  not-accessible
   STATUS      current
   DESCRIPTION
      ""
   INDEX      { ar1645v2CllRFUsbResetGlobalIx }
   ::= {ar1645v2CllRFUsbResetTable 1}

Ar1645v2CllRFUsbResetEntry ::=
   SEQUENCE
      {
      ar1645v2CllRFUsbResetGlobalIx
         GlobalIndex,
      ar1645v2CllRFUsbResetValue
         Integer32
      }

ar1645v2CllRFUsbResetGlobalIx OBJECT-TYPE
   SYNTAX      GlobalIndex
   MAX-ACCESS  not-accessible
   STATUS      current
   DESCRIPTION
      "The value of the tlsCntTreeGlobalIndex of the MANAGED OBJECT."
   ::= {ar1645v2CllRFUsbResetEntry 10}

ar1645v2CllRFUsbResetValue OBJECT-TYPE
   SYNTAX      Integer32
   MAX-ACCESS  read-write
   STATUS      current
   DESCRIPTION
      "Path: cellular.actions.usbReset"
   ::= {ar1645v2CllRFUsbResetEntry 2147483648}


ar1645v2CllRFSelectCarrier OBJECT IDENTIFIER ::= {ar1645v2CllRF 414}

ar1645v2CllRFSelectCarrierTable OBJECT-TYPE
   SYNTAX      SEQUENCE OF Ar1645v2CllRFSelectCarrierEntry
   MAX-ACCESS  not-accessible
   STATUS      current
   DESCRIPTION
      "Sierra Wireless Modem - select carrier"
   ::= {ar1645v2CllRFSelectCarrier 1}

ar1645v2CllRFSelectCarrierEntry OBJECT-TYPE
   SYNTAX      Ar1645v2CllRFSelectCarrierEntry
   MAX-ACCESS  not-accessible
   STATUS      current
   DESCRIPTION
      ""
   INDEX      { ar1645v2CllRFSelectCarrierGlobalIx }
   ::= {ar1645v2CllRFSelectCarrierTable 1}

Ar1645v2CllRFSelectCarrierEntry ::=
   SEQUENCE
      {
      ar1645v2CllRFSelectCarrierGlobalIx
         GlobalIndex,
      ar1645v2CllRFSelectCarrierValue
         Integer32
      }

ar1645v2CllRFSelectCarrierGlobalIx OBJECT-TYPE
   SYNTAX      GlobalIndex
   MAX-ACCESS  not-accessible
   STATUS      current
   DESCRIPTION
      "The value of the tlsCntTreeGlobalIndex of the MANAGED OBJECT."
   ::= {ar1645v2CllRFSelectCarrierEntry 10}

ar1645v2CllRFSelectCarrierValue OBJECT-TYPE
   SYNTAX      Integer32
   MAX-ACCESS  read-write
   STATUS      current
   DESCRIPTION
      "Path: cellular.actions.selectCarrier"
   ::= {ar1645v2CllRFSelectCarrierEntry 2147483648}


ar1645v2CllRFCarrierName OBJECT IDENTIFIER ::= {ar1645v2CllRF 415}

ar1645v2CllRFCarrierNameTable OBJECT-TYPE
   SYNTAX      SEQUENCE OF Ar1645v2CllRFCarrierNameEntry
   MAX-ACCESS  not-accessible
   STATUS      current
   DESCRIPTION
      "Sierra Wireless Modem - carrier name"
   ::= {ar1645v2CllRFCarrierName 1}

ar1645v2CllRFCarrierNameEntry OBJECT-TYPE
   SYNTAX      Ar1645v2CllRFCarrierNameEntry
   MAX-ACCESS  not-accessible
   STATUS      current
   DESCRIPTION
      ""
   INDEX      { ar1645v2CllRFCarrierNameGlobalIx }
   ::= {ar1645v2CllRFCarrierNameTable 1}

Ar1645v2CllRFCarrierNameEntry ::=
   SEQUENCE
      {
      ar1645v2CllRFCarrierNameGlobalIx
         GlobalIndex,
      ar1645v2CllRFCarrierNameValue
         DisplayString
      }

ar1645v2CllRFCarrierNameGlobalIx OBJECT-TYPE
   SYNTAX      GlobalIndex
   MAX-ACCESS  not-accessible
   STATUS      current
   DESCRIPTION
      "The value of the tlsCntTreeGlobalIndex of the MANAGED OBJECT."
   ::= {ar1645v2CllRFCarrierNameEntry 10}

ar1645v2CllRFCarrierNameValue OBJECT-TYPE
   SYNTAX      DisplayString
   MAX-ACCESS  read-write
   STATUS      current
   DESCRIPTION
      "Path: cellular.actions.carrierName"
   ::= {ar1645v2CllRFCarrierNameEntry 2147483648}


ar1645v2CllRFSendSms OBJECT IDENTIFIER ::= {ar1645v2CllRF 412}

ar1645v2CllRFSendSmsTable OBJECT-TYPE
   SYNTAX      SEQUENCE OF Ar1645v2CllRFSendSmsEntry
   MAX-ACCESS  not-accessible
   STATUS      current
   DESCRIPTION
      "send SMS"
   ::= {ar1645v2CllRFSendSms 1}

ar1645v2CllRFSendSmsEntry OBJECT-TYPE
   SYNTAX      Ar1645v2CllRFSendSmsEntry
   MAX-ACCESS  not-accessible
   STATUS      current
   DESCRIPTION
      ""
   INDEX      { ar1645v2CllRFSendSmsGlobalIx }
   ::= {ar1645v2CllRFSendSmsTable 1}

Ar1645v2CllRFSendSmsEntry ::=
   SEQUENCE
      {
      ar1645v2CllRFSendSmsGlobalIx
         GlobalIndex,
      ar1645v2CllRFSendSmsValue
         Integer32
      }

ar1645v2CllRFSendSmsGlobalIx OBJECT-TYPE
   SYNTAX      GlobalIndex
   MAX-ACCESS  not-accessible
   STATUS      current
   DESCRIPTION
      "The value of the tlsCntTreeGlobalIndex of the MANAGED OBJECT."
   ::= {ar1645v2CllRFSendSmsEntry 10}

ar1645v2CllRFSendSmsValue OBJECT-TYPE
   SYNTAX      Integer32
   MAX-ACCESS  read-write
   STATUS      current
   DESCRIPTION
      "Path: cellular.actions.sendSms"
   ::= {ar1645v2CllRFSendSmsEntry 2147483648}


ar1645v2CllRFSmsData OBJECT IDENTIFIER ::= {ar1645v2CllRF 413}

ar1645v2CllRFSmsDataSSCTable OBJECT-TYPE
   SYNTAX      SEQUENCE OF Ar1645v2CllRFSmsDataEntry
   MAX-ACCESS  not-accessible
   STATUS      current
   DESCRIPTION
      "SMS to send"
   ::= {ar1645v2CllRFSmsData 1}

ar1645v2CllRFSmsDataEntry OBJECT-TYPE
   SYNTAX      Ar1645v2CllRFSmsDataEntry
   MAX-ACCESS  not-accessible
   STATUS      current
   DESCRIPTION
      ""
   INDEX      { ar1645v2CllRFSmsDataGlobalIx }
   ::= {ar1645v2CllRFSmsDataSSCTable 1}

Ar1645v2CllRFSmsDataEntry ::=
   SEQUENCE
      {
      ar1645v2CllRFSmsDataGlobalIx
         GlobalIndex,
      ar1645v2CllRFSmsDataTelephoneNumber
         DisplayString,
      ar1645v2CllRFSmsDataMessage
         DisplayString
      }

ar1645v2CllRFSmsDataGlobalIx OBJECT-TYPE
   SYNTAX      GlobalIndex
   MAX-ACCESS  not-accessible
   STATUS      current
   DESCRIPTION
      "The value of the tlsCntTreeGlobalIndex of the MANAGED OBJECT."
   ::= {ar1645v2CllRFSmsDataEntry 10}

ar1645v2CllRFSmsDataTelephoneNumber OBJECT-TYPE
   SYNTAX      DisplayString
   MAX-ACCESS  read-write
   STATUS      current
   DESCRIPTION
      "Path: cellular.actions.smsData.telephoneNumber"
   ::= {ar1645v2CllRFSmsDataEntry 16777216}

ar1645v2CllRFSmsDataMessage OBJECT-TYPE
   SYNTAX      DisplayString
   MAX-ACCESS  read-write
   STATUS      current
   DESCRIPTION
      "Path: cellular.actions.smsData.message"
   ::= {ar1645v2CllRFSmsDataEntry 33554432}


ar1645v2CllRFSendAtCommand OBJECT IDENTIFIER ::= {ar1645v2CllRF 410}

ar1645v2CllRFSendAtCommandTable OBJECT-TYPE
   SYNTAX      SEQUENCE OF Ar1645v2CllRFSendAtCommandEntry
   MAX-ACCESS  not-accessible
   STATUS      current
   DESCRIPTION
      "send AT command"
   ::= {ar1645v2CllRFSendAtCommand 1}

ar1645v2CllRFSendAtCommandEntry OBJECT-TYPE
   SYNTAX      Ar1645v2CllRFSendAtCommandEntry
   MAX-ACCESS  not-accessible
   STATUS      current
   DESCRIPTION
      ""
   INDEX      { ar1645v2CllRFSendAtCommandGlobalIx }
   ::= {ar1645v2CllRFSendAtCommandTable 1}

Ar1645v2CllRFSendAtCommandEntry ::=
   SEQUENCE
      {
      ar1645v2CllRFSendAtCommandGlobalIx
         GlobalIndex,
      ar1645v2CllRFSendAtCommandValue
         Integer32
      }

ar1645v2CllRFSendAtCommandGlobalIx OBJECT-TYPE
   SYNTAX      GlobalIndex
   MAX-ACCESS  not-accessible
   STATUS      current
   DESCRIPTION
      "The value of the tlsCntTreeGlobalIndex of the MANAGED OBJECT."
   ::= {ar1645v2CllRFSendAtCommandEntry 10}

ar1645v2CllRFSendAtCommandValue OBJECT-TYPE
   SYNTAX      Integer32
   MAX-ACCESS  read-write
   STATUS      current
   DESCRIPTION
      "Path: cellular.actions.sendAtCommand"
   ::= {ar1645v2CllRFSendAtCommandEntry 2147483648}


ar1645v2CllRFAtCommand OBJECT IDENTIFIER ::= {ar1645v2CllRF 411}

ar1645v2CllRFAtCommandTable OBJECT-TYPE
   SYNTAX      SEQUENCE OF Ar1645v2CllRFAtCommandEntry
   MAX-ACCESS  not-accessible
   STATUS      current
   DESCRIPTION
      "AT command to execute"
   ::= {ar1645v2CllRFAtCommand 1}

ar1645v2CllRFAtCommandEntry OBJECT-TYPE
   SYNTAX      Ar1645v2CllRFAtCommandEntry
   MAX-ACCESS  not-accessible
   STATUS      current
   DESCRIPTION
      ""
   INDEX      { ar1645v2CllRFAtCommandGlobalIx }
   ::= {ar1645v2CllRFAtCommandTable 1}

Ar1645v2CllRFAtCommandEntry ::=
   SEQUENCE
      {
      ar1645v2CllRFAtCommandGlobalIx
         GlobalIndex,
      ar1645v2CllRFAtCommandValue
         DisplayString
      }

ar1645v2CllRFAtCommandGlobalIx OBJECT-TYPE
   SYNTAX      GlobalIndex
   MAX-ACCESS  not-accessible
   STATUS      current
   DESCRIPTION
      "The value of the tlsCntTreeGlobalIndex of the MANAGED OBJECT."
   ::= {ar1645v2CllRFAtCommandEntry 10}

ar1645v2CllRFAtCommandValue OBJECT-TYPE
   SYNTAX      DisplayString
   MAX-ACCESS  read-write
   STATUS      current
   DESCRIPTION
      "Path: cellular.actions.atCommand"
   ::= {ar1645v2CllRFAtCommandEntry 2147483648}


ar1645v2CllRFResetModule OBJECT IDENTIFIER ::= {ar1645v2CllRF 409}

ar1645v2CllRFResetModuleTable OBJECT-TYPE
   SYNTAX      SEQUENCE OF Ar1645v2CllRFResetModuleEntry
   MAX-ACCESS  not-accessible
   STATUS      current
   DESCRIPTION
      "reset module"
   ::= {ar1645v2CllRFResetModule 1}

ar1645v2CllRFResetModuleEntry OBJECT-TYPE
   SYNTAX      Ar1645v2CllRFResetModuleEntry
   MAX-ACCESS  not-accessible
   STATUS      current
   DESCRIPTION
      ""
   INDEX      { ar1645v2CllRFResetModuleGlobalIx }
   ::= {ar1645v2CllRFResetModuleTable 1}

Ar1645v2CllRFResetModuleEntry ::=
   SEQUENCE
      {
      ar1645v2CllRFResetModuleGlobalIx
         GlobalIndex,
      ar1645v2CllRFResetModuleValue
         Integer32
      }

ar1645v2CllRFResetModuleGlobalIx OBJECT-TYPE
   SYNTAX      GlobalIndex
   MAX-ACCESS  not-accessible
   STATUS      current
   DESCRIPTION
      "The value of the tlsCntTreeGlobalIndex of the MANAGED OBJECT."
   ::= {ar1645v2CllRFResetModuleEntry 10}

ar1645v2CllRFResetModuleValue OBJECT-TYPE
   SYNTAX      Integer32
   MAX-ACCESS  read-write
   STATUS      current
   DESCRIPTION
      "Path: cellular.actions.resetModule"
   ::= {ar1645v2CllRFResetModuleEntry 2147483648}


ar1645v2CllRFUpgradeFirmware OBJECT IDENTIFIER ::= {ar1645v2CllRF 408}

ar1645v2CllRFUpgradeFirmwareTable OBJECT-TYPE
   SYNTAX      SEQUENCE OF Ar1645v2CllRFUpgradeFirmwareEntry
   MAX-ACCESS  not-accessible
   STATUS      current
   DESCRIPTION
      "Sierra Wireless Modem - upgrade firmware"
   ::= {ar1645v2CllRFUpgradeFirmware 1}

ar1645v2CllRFUpgradeFirmwareEntry OBJECT-TYPE
   SYNTAX      Ar1645v2CllRFUpgradeFirmwareEntry
   MAX-ACCESS  not-accessible
   STATUS      current
   DESCRIPTION
      ""
   INDEX      { ar1645v2CllRFUpgradeFirmwareGlobalIx }
   ::= {ar1645v2CllRFUpgradeFirmwareTable 1}

Ar1645v2CllRFUpgradeFirmwareEntry ::=
   SEQUENCE
      {
      ar1645v2CllRFUpgradeFirmwareGlobalIx
         GlobalIndex,
      ar1645v2CllRFUpgradeFirmwareValue
         Integer32
      }

ar1645v2CllRFUpgradeFirmwareGlobalIx OBJECT-TYPE
   SYNTAX      GlobalIndex
   MAX-ACCESS  not-accessible
   STATUS      current
   DESCRIPTION
      "The value of the tlsCntTreeGlobalIndex of the MANAGED OBJECT."
   ::= {ar1645v2CllRFUpgradeFirmwareEntry 10}

ar1645v2CllRFUpgradeFirmwareValue OBJECT-TYPE
   SYNTAX      Integer32
   MAX-ACCESS  read-write
   STATUS      current
   DESCRIPTION
      "Path: cellular.actions.upgradeFirmware"
   ::= {ar1645v2CllRFUpgradeFirmwareEntry 2147483648}


ar1645v2CllRFFwFilename OBJECT IDENTIFIER ::= {ar1645v2CllRF 418}

ar1645v2CllRFFwFilenameTable OBJECT-TYPE
   SYNTAX      SEQUENCE OF Ar1645v2CllRFFwFilenameEntry
   MAX-ACCESS  not-accessible
   STATUS      current
   DESCRIPTION
      "Sierra Wireless Modem - upgrade firmware: filename"
   ::= {ar1645v2CllRFFwFilename 1}

ar1645v2CllRFFwFilenameEntry OBJECT-TYPE
   SYNTAX      Ar1645v2CllRFFwFilenameEntry
   MAX-ACCESS  not-accessible
   STATUS      current
   DESCRIPTION
      ""
   INDEX      { ar1645v2CllRFFwFilenameGlobalIx }
   ::= {ar1645v2CllRFFwFilenameTable 1}

Ar1645v2CllRFFwFilenameEntry ::=
   SEQUENCE
      {
      ar1645v2CllRFFwFilenameGlobalIx
         GlobalIndex,
      ar1645v2CllRFFwFilenameValue
         DisplayString
      }

ar1645v2CllRFFwFilenameGlobalIx OBJECT-TYPE
   SYNTAX      GlobalIndex
   MAX-ACCESS  not-accessible
   STATUS      current
   DESCRIPTION
      "The value of the tlsCntTreeGlobalIndex of the MANAGED OBJECT."
   ::= {ar1645v2CllRFFwFilenameEntry 10}

ar1645v2CllRFFwFilenameValue OBJECT-TYPE
   SYNTAX      DisplayString
   MAX-ACCESS  read-write
   STATUS      current
   DESCRIPTION
      "Path: cellular.actions.fwFilename"
   ::= {ar1645v2CllRFFwFilenameEntry 2147483648}



END
