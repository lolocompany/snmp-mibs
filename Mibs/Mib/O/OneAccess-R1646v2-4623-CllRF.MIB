OneAccess-R1646v2-4623-CllRF DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2CllRF OBJECT IDENTIFIER ::= {r1646Rootv2 4623}

r1646v2CllRFMOProp OBJECT-TYPE
   SYNTAX      SEQUENCE OF R1646v2CllRFMOPropEntry
   MAX-ACCESS  not-accessible
   STATUS      current
   DESCRIPTION
      ""
   ::= {r1646v2CllRF 1}

r1646v2CllRFMOPropEntry OBJECT-TYPE
   SYNTAX      R1646v2CllRFMOPropEntry
   MAX-ACCESS  not-accessible
   STATUS      current
   DESCRIPTION
      ""
   INDEX      { r1646v2CllRFMOPropGlobalIx }
   ::= {r1646v2CllRFMOProp 1}

R1646v2CllRFMOPropEntry ::=
   SEQUENCE
      {
      r1646v2CllRFMOPropPath
         ContainmentPath,
      r1646v2CllRFMOPropRev
         ObjectRevision,
      r1646v2CllRFMOPropGlobalIx
         GlobalIndex
      }

r1646v2CllRFMOPropPath OBJECT-TYPE
   SYNTAX      ContainmentPath
   MAX-ACCESS  read-only
   STATUS      current
   DESCRIPTION
      "Textual description of the containment tree from the instance of
       the root object down to the instance of the current object."
   ::= {r1646v2CllRFMOPropEntry 3}

r1646v2CllRFMOPropRev OBJECT-TYPE
   SYNTAX      ObjectRevision
   MAX-ACCESS  read-only
   STATUS      current
   DESCRIPTION
      "This value corresponds with the revision of the MANAGED OBJECT."
   ::= {r1646v2CllRFMOPropEntry 4}

r1646v2CllRFMOPropGlobalIx OBJECT-TYPE
   SYNTAX      GlobalIndex
   MAX-ACCESS  read-only
   STATUS      current
   DESCRIPTION
      "The value of the tlsCntTreeGlobalIndex of the MANAGED OBJECT."
   ::= {r1646v2CllRFMOPropEntry 10}



er1646v2CllRF OBJECT IDENTIFIER ::= {r1646v2CllRF 11}


er1646v2CllRFRemark OBJECT IDENTIFIER ::= {er1646v2CllRF 321}

er1646v2CllRFRemarkTable OBJECT-TYPE
   SYNTAX      SEQUENCE OF Er1646v2CllRFRemarkEntry
   MAX-ACCESS  not-accessible
   STATUS      current
   DESCRIPTION
      "intfRemark"
   ::= {er1646v2CllRFRemark 1}

er1646v2CllRFRemarkEntry OBJECT-TYPE
   SYNTAX      Er1646v2CllRFRemarkEntry
   MAX-ACCESS  not-accessible
   STATUS      current
   DESCRIPTION
      ""
   INDEX      { er1646v2CllRFRemarkGlobalIx }
   ::= {er1646v2CllRFRemarkTable 1}

Er1646v2CllRFRemarkEntry ::=
   SEQUENCE
      {
      er1646v2CllRFRemarkGlobalIx
         GlobalIndex,
      er1646v2CllRFRemarkValue
         DisplayString
      }

er1646v2CllRFRemarkGlobalIx OBJECT-TYPE
   SYNTAX      GlobalIndex
   MAX-ACCESS  not-accessible
   STATUS      current
   DESCRIPTION
      "The value of the tlsCntTreeGlobalIndex of the MANAGED OBJECT."
   ::= {er1646v2CllRFRemarkEntry 10}

er1646v2CllRFRemarkValue OBJECT-TYPE
   SYNTAX      DisplayString
   MAX-ACCESS  read-write
   STATUS      current
   DESCRIPTION
      "Path: cellular.editConf.remark"
   ::= {er1646v2CllRFRemarkEntry 2147483648}


er1646v2CllRFRatMode OBJECT IDENTIFIER ::= {er1646v2CllRF 3}

er1646v2CllRFRatModeTable OBJECT-TYPE
   SYNTAX      SEQUENCE OF Er1646v2CllRFRatModeEntry
   MAX-ACCESS  not-accessible
   STATUS      current
   DESCRIPTION
      "Radio technology mode"
   ::= {er1646v2CllRFRatMode 1}

er1646v2CllRFRatModeEntry OBJECT-TYPE
   SYNTAX      Er1646v2CllRFRatModeEntry
   MAX-ACCESS  not-accessible
   STATUS      current
   DESCRIPTION
      ""
   INDEX      { er1646v2CllRFRatModeGlobalIx }
   ::= {er1646v2CllRFRatModeTable 1}

Er1646v2CllRFRatModeEntry ::=
   SEQUENCE
      {
      er1646v2CllRFRatModeGlobalIx
         GlobalIndex,
      er1646v2CllRFRatModeValue
         Integer32
      }

er1646v2CllRFRatModeGlobalIx OBJECT-TYPE
   SYNTAX      GlobalIndex
   MAX-ACCESS  not-accessible
   STATUS      current
   DESCRIPTION
      "The value of the tlsCntTreeGlobalIndex of the MANAGED OBJECT."
   ::= {er1646v2CllRFRatModeEntry 10}

er1646v2CllRFRatModeValue OBJECT-TYPE
   SYNTAX      Integer32
   MAX-ACCESS  read-write
   STATUS      current
   DESCRIPTION
      "Path: cellular.editConf.ratMode

       Bit meanings:
               bit 0 = 2g,
               bit 1 = 3g,
               bit 2 = 4g"
   ::= {er1646v2CllRFRatModeEntry 2147483648}


er1646v2CllRFOperation OBJECT IDENTIFIER ::= {er1646v2CllRF 4}

er1646v2CllRFOperationTable OBJECT-TYPE
   SYNTAX      SEQUENCE OF Er1646v2CllRFOperationEntry
   MAX-ACCESS  not-accessible
   STATUS      current
   DESCRIPTION
      "EthernetPdp or DefaultPdp"
   ::= {er1646v2CllRFOperation 1}

er1646v2CllRFOperationEntry OBJECT-TYPE
   SYNTAX      Er1646v2CllRFOperationEntry
   MAX-ACCESS  not-accessible
   STATUS      current
   DESCRIPTION
      ""
   INDEX      { er1646v2CllRFOperationGlobalIx }
   ::= {er1646v2CllRFOperationTable 1}

Er1646v2CllRFOperationEntry ::=
   SEQUENCE
      {
      er1646v2CllRFOperationGlobalIx
         GlobalIndex,
      er1646v2CllRFOperationValue
         INTEGER
      }

er1646v2CllRFOperationGlobalIx OBJECT-TYPE
   SYNTAX      GlobalIndex
   MAX-ACCESS  not-accessible
   STATUS      current
   DESCRIPTION
      "The value of the tlsCntTreeGlobalIndex of the MANAGED OBJECT."
   ::= {er1646v2CllRFOperationEntry 10}

er1646v2CllRFOperationValue OBJECT-TYPE
   SYNTAX      INTEGER
               {
               ethernetPdp (1),
               defaultPdp (2)
               }
   MAX-ACCESS  read-write
   STATUS      current
   DESCRIPTION
      "Path: cellular.editConf.operation

       Possibilities:
               ethernetPdp   (1)
               defaultPdp   (2)"
   ::= {er1646v2CllRFOperationEntry 2147483648}


er1646v2CllRFSimProfiles OBJECT IDENTIFIER ::= {er1646v2CllRF 5}

er1646v2CllRFSimProfilesSSCTable OBJECT-TYPE
   SYNTAX      SEQUENCE OF Er1646v2CllRFSimProfilesEntry
   MAX-ACCESS  not-accessible
   STATUS      current
   DESCRIPTION
      "cellular profile configuration table"
   ::= {er1646v2CllRFSimProfiles 1}

er1646v2CllRFSimProfilesEntry OBJECT-TYPE
   SYNTAX      Er1646v2CllRFSimProfilesEntry
   MAX-ACCESS  not-accessible
   STATUS      current
   DESCRIPTION
      ""
   INDEX      { er1646v2CllRFSimProfilesGlobalIx,
                er1646v2CllRFSimProfilesTableIx }
   ::= {er1646v2CllRFSimProfilesSSCTable 1}

Er1646v2CllRFSimProfilesEntry ::=
   SEQUENCE
      {
      er1646v2CllRFSimProfilesActions
         VariableLengthTableActions,
      er1646v2CllRFSimProfilesGlobalIx
         GlobalIndex,
      er1646v2CllRFSimProfilesTableIx
         TableIndex,
      er1646v2CllRFSimProfilesName
         DisplayString,
      er1646v2CllRFSimProfilesRemark
         DisplayString,
      er1646v2CllRFSimProfilesIpProtocol
         INTEGER,
      er1646v2CllRFSimProfilesApn
         DisplayString,
      er1646v2CllRFSimProfilesAuthenticationSessionAuthMethod
         INTEGER,
      er1646v2CllRFSimProfilesAuthenticationSessionName
         DisplayString,
      er1646v2CllRFSimProfilesAuthenticationSessionSecret
         DisplayString,
      er1646v2CllRFSimProfilesAuthenticationEncModeSessionSecret
         INTEGER,
      er1646v2CllRFSimProfilesAuthenticationEncSessionSecret
         DisplayString
      }

er1646v2CllRFSimProfilesActions OBJECT-TYPE
   SYNTAX      VariableLengthTableActions
   MAX-ACCESS  read-write
   STATUS      current
   DESCRIPTION
      "By way of this field, some manipulations
       on this table may be performed."
   ::= {er1646v2CllRFSimProfilesEntry 2}

er1646v2CllRFSimProfilesGlobalIx OBJECT-TYPE
   SYNTAX      GlobalIndex
   MAX-ACCESS  not-accessible
   STATUS      current
   DESCRIPTION
      "The value of the tlsCntTreeGlobalIndex of the MANAGED OBJECT."
   ::= {er1646v2CllRFSimProfilesEntry 10}

er1646v2CllRFSimProfilesTableIx OBJECT-TYPE
   SYNTAX      TableIndex
   MAX-ACCESS  not-accessible
   STATUS      current
   DESCRIPTION
      ""
   ::= {er1646v2CllRFSimProfilesEntry 11}

er1646v2CllRFSimProfilesName OBJECT-TYPE
   SYNTAX      DisplayString
   MAX-ACCESS  read-write
   STATUS      current
   DESCRIPTION
      "Path: cellular.editConf.simProfiles.name"
   ::= {er1646v2CllRFSimProfilesEntry 16777216}

er1646v2CllRFSimProfilesRemark OBJECT-TYPE
   SYNTAX      DisplayString
   MAX-ACCESS  read-write
   STATUS      current
   DESCRIPTION
      "Path: cellular.editConf.simProfiles.remark"
   ::= {er1646v2CllRFSimProfilesEntry 33554432}

er1646v2CllRFSimProfilesIpProtocol OBJECT-TYPE
   SYNTAX      INTEGER
               {
               ipV4 (1),
               ipV6 (2),
               ipV4ipV6 (3)
               }
   MAX-ACCESS  read-write
   STATUS      current
   DESCRIPTION
      "Path: cellular.editConf.simProfiles.ipProtocol

       Possibilities:
               ipV4   (1)
               ipV6   (2)
               ipV4/ipV6   (3)"
   ::= {er1646v2CllRFSimProfilesEntry 50331648}

er1646v2CllRFSimProfilesApn OBJECT-TYPE
   SYNTAX      DisplayString
   MAX-ACCESS  read-write
   STATUS      current
   DESCRIPTION
      "Path: cellular.editConf.simProfiles.apn"
   ::= {er1646v2CllRFSimProfilesEntry 67108864}

er1646v2CllRFSimProfilesAuthenticationSessionAuthMethod OBJECT-TYPE
   SYNTAX      INTEGER
               {
               none (1),
               pap (2),
               chap (3),
               chappap (4)
               }
   MAX-ACCESS  read-write
   STATUS      current
   DESCRIPTION
      "Path: cellular.editConf.simProfiles.authentication.sessionAuthMethod

       Possibilities:
               none   (1)
               pap   (2)
               chap   (3)
               chap/pap   (4)"
   ::= {er1646v2CllRFSimProfilesEntry 84738048}

er1646v2CllRFSimProfilesAuthenticationSessionName OBJECT-TYPE
   SYNTAX      DisplayString
   MAX-ACCESS  read-write
   STATUS      current
   DESCRIPTION
      "Path: cellular.editConf.simProfiles.authentication.sessionName"
   ::= {er1646v2CllRFSimProfilesEntry 84213760}

er1646v2CllRFSimProfilesAuthenticationSessionSecret OBJECT-TYPE
   SYNTAX      DisplayString
   MAX-ACCESS  read-write
   STATUS      current
   DESCRIPTION
      "Path: cellular.editConf.simProfiles.authentication.sessionSecret"
   ::= {er1646v2CllRFSimProfilesEntry 84279296}

er1646v2CllRFSimProfilesAuthenticationEncModeSessionSecret OBJECT-TYPE
   SYNTAX      INTEGER
               {
               none (1),
               encrypt (2),
               encType1 (3),
               invalid (128)
               }
   MAX-ACCESS  read-write
   STATUS      current
   DESCRIPTION
      "Path: cellular.editConf.simProfiles.authentication.encModeSessionSecret

       Possibilities:
               none   (1)
               encrypt   (2)
               encType1   (3)
               invalid   (128)"
   ::= {er1646v2CllRFSimProfilesEntry 84606976}

er1646v2CllRFSimProfilesAuthenticationEncSessionSecret OBJECT-TYPE
   SYNTAX      DisplayString
   MAX-ACCESS  read-write
   STATUS      current
   DESCRIPTION
      "Path: cellular.editConf.simProfiles.authentication.encSessionSecret"
   ::= {er1646v2CllRFSimProfilesEntry 84672512}


er1646v2CllRFAttachProfile OBJECT IDENTIFIER ::= {er1646v2CllRF 6}

er1646v2CllRFAttachProfileTable OBJECT-TYPE
   SYNTAX      SEQUENCE OF Er1646v2CllRFAttachProfileEntry
   MAX-ACCESS  not-accessible
   STATUS      current
   DESCRIPTION
      "cellular attach profile"
   ::= {er1646v2CllRFAttachProfile 1}

er1646v2CllRFAttachProfileEntry OBJECT-TYPE
   SYNTAX      Er1646v2CllRFAttachProfileEntry
   MAX-ACCESS  not-accessible
   STATUS      current
   DESCRIPTION
      ""
   INDEX      { er1646v2CllRFAttachProfileGlobalIx }
   ::= {er1646v2CllRFAttachProfileTable 1}

Er1646v2CllRFAttachProfileEntry ::=
   SEQUENCE
      {
      er1646v2CllRFAttachProfileGlobalIx
         GlobalIndex,
      er1646v2CllRFAttachProfileValue
         DisplayString
      }

er1646v2CllRFAttachProfileGlobalIx OBJECT-TYPE
   SYNTAX      GlobalIndex
   MAX-ACCESS  not-accessible
   STATUS      current
   DESCRIPTION
      "The value of the tlsCntTreeGlobalIndex of the MANAGED OBJECT."
   ::= {er1646v2CllRFAttachProfileEntry 10}

er1646v2CllRFAttachProfileValue OBJECT-TYPE
   SYNTAX      DisplayString
   MAX-ACCESS  read-write
   STATUS      current
   DESCRIPTION
      "Path: cellular.editConf.attachProfile"
   ::= {er1646v2CllRFAttachProfileEntry 2147483648}



sr1646v2CllRF OBJECT IDENTIFIER ::= {r1646v2CllRF 14}


sr1646v2CllRFState OBJECT IDENTIFIER ::= {sr1646v2CllRF 46}

sr1646v2CllRFStateTable OBJECT-TYPE
   SYNTAX      SEQUENCE OF Sr1646v2CllRFStateEntry
   MAX-ACCESS  not-accessible
   STATUS      current
   DESCRIPTION
      "monitor state"
   ::= {sr1646v2CllRFState 1}

sr1646v2CllRFStateEntry OBJECT-TYPE
   SYNTAX      Sr1646v2CllRFStateEntry
   MAX-ACCESS  not-accessible
   STATUS      current
   DESCRIPTION
      ""
   INDEX      { sr1646v2CllRFStateGlobalIx }
   ::= {sr1646v2CllRFStateTable 1}

Sr1646v2CllRFStateEntry ::=
   SEQUENCE
      {
      sr1646v2CllRFStateGlobalIx
         GlobalIndex,
      sr1646v2CllRFStateValue
         INTEGER
      }

sr1646v2CllRFStateGlobalIx OBJECT-TYPE
   SYNTAX      GlobalIndex
   MAX-ACCESS  not-accessible
   STATUS      current
   DESCRIPTION
      "The value of the tlsCntTreeGlobalIndex of the MANAGED OBJECT."
   ::= {sr1646v2CllRFStateEntry 10}

sr1646v2CllRFStateValue OBJECT-TYPE
   SYNTAX      INTEGER
               {
               sync (0),
               init (1),
               reset (2),
               meinfo (3),
               checkSim (4),
               enterPin (5),
               msInfo (6),
               lowPower (7),
               searching (8),
               attached (9),
               error (10),
               firmwareUpgrade (11),
               monitorStopped (12),
               networkScan (13),
               powerDown (14)
               }
   MAX-ACCESS  read-only
   STATUS      current
   DESCRIPTION
      "Path: cellular.status.state

       Possibilities:
               sync   (0)
               init   (1)
               reset   (2)
               meinfo   (3)
               checkSim   (4)
               enterPin   (5)
               msInfo   (6)
               lowPower   (7)
               searching   (8)
               attached   (9)
               error   (10)
               firmwareUpgrade   (11)
               monitorStopped   (12)
               networkScan   (13)
               powerDown   (14)"
   ::= {sr1646v2CllRFStateEntry 2147483648}


sr1646v2CllRFCurrentOperator OBJECT IDENTIFIER ::= {sr1646v2CllRF 40}

sr1646v2CllRFCurrentOperatorTable OBJECT-TYPE
   SYNTAX      SEQUENCE OF Sr1646v2CllRFCurrentOperatorEntry
   MAX-ACCESS  not-accessible
   STATUS      current
   DESCRIPTION
      "misc. string"
   ::= {sr1646v2CllRFCurrentOperator 1}

sr1646v2CllRFCurrentOperatorEntry OBJECT-TYPE
   SYNTAX      Sr1646v2CllRFCurrentOperatorEntry
   MAX-ACCESS  not-accessible
   STATUS      current
   DESCRIPTION
      ""
   INDEX      { sr1646v2CllRFCurrentOperatorGlobalIx }
   ::= {sr1646v2CllRFCurrentOperatorTable 1}

Sr1646v2CllRFCurrentOperatorEntry ::=
   SEQUENCE
      {
      sr1646v2CllRFCurrentOperatorGlobalIx
         GlobalIndex,
      sr1646v2CllRFCurrentOperatorValue
         DisplayString
      }

sr1646v2CllRFCurrentOperatorGlobalIx OBJECT-TYPE
   SYNTAX      GlobalIndex
   MAX-ACCESS  not-accessible
   STATUS      current
   DESCRIPTION
      "The value of the tlsCntTreeGlobalIndex of the MANAGED OBJECT."
   ::= {sr1646v2CllRFCurrentOperatorEntry 10}

sr1646v2CllRFCurrentOperatorValue OBJECT-TYPE
   SYNTAX      DisplayString
   MAX-ACCESS  read-only
   STATUS      current
   DESCRIPTION
      "Path: cellular.status.currentOperator"
   ::= {sr1646v2CllRFCurrentOperatorEntry 2147483648}


sr1646v2CllRFCurrentAccessTechnology OBJECT IDENTIFIER ::= {sr1646v2CllRF 41}

sr1646v2CllRFCurrentAccessTechnologyTable OBJECT-TYPE
   SYNTAX      SEQUENCE OF Sr1646v2CllRFCurrentAccessTechnologyEntry
   MAX-ACCESS  not-accessible
   STATUS      current
   DESCRIPTION
      "misc. string"
   ::= {sr1646v2CllRFCurrentAccessTechnology 1}

sr1646v2CllRFCurrentAccessTechnologyEntry OBJECT-TYPE
   SYNTAX      Sr1646v2CllRFCurrentAccessTechnologyEntry
   MAX-ACCESS  not-accessible
   STATUS      current
   DESCRIPTION
      ""
   INDEX      { sr1646v2CllRFCurrentAccessTechnologyGlobalIx }
   ::= {sr1646v2CllRFCurrentAccessTechnologyTable 1}

Sr1646v2CllRFCurrentAccessTechnologyEntry ::=
   SEQUENCE
      {
      sr1646v2CllRFCurrentAccessTechnologyGlobalIx
         GlobalIndex,
      sr1646v2CllRFCurrentAccessTechnologyValue
         DisplayString
      }

sr1646v2CllRFCurrentAccessTechnologyGlobalIx OBJECT-TYPE
   SYNTAX      GlobalIndex
   MAX-ACCESS  not-accessible
   STATUS      current
   DESCRIPTION
      "The value of the tlsCntTreeGlobalIndex of the MANAGED OBJECT."
   ::= {sr1646v2CllRFCurrentAccessTechnologyEntry 10}

sr1646v2CllRFCurrentAccessTechnologyValue OBJECT-TYPE
   SYNTAX      DisplayString
   MAX-ACCESS  read-only
   STATUS      current
   DESCRIPTION
      "Path: cellular.status.currentAccessTechnology"
   ::= {sr1646v2CllRFCurrentAccessTechnologyEntry 2147483648}


sr1646v2CllRFCsRegisterState OBJECT IDENTIFIER ::= {sr1646v2CllRF 42}

sr1646v2CllRFCsRegisterStateTable OBJECT-TYPE
   SYNTAX      SEQUENCE OF Sr1646v2CllRFCsRegisterStateEntry
   MAX-ACCESS  not-accessible
   STATUS      current
   DESCRIPTION
      "misc. string"
   ::= {sr1646v2CllRFCsRegisterState 1}

sr1646v2CllRFCsRegisterStateEntry OBJECT-TYPE
   SYNTAX      Sr1646v2CllRFCsRegisterStateEntry
   MAX-ACCESS  not-accessible
   STATUS      current
   DESCRIPTION
      ""
   INDEX      { sr1646v2CllRFCsRegisterStateGlobalIx }
   ::= {sr1646v2CllRFCsRegisterStateTable 1}

Sr1646v2CllRFCsRegisterStateEntry ::=
   SEQUENCE
      {
      sr1646v2CllRFCsRegisterStateGlobalIx
         GlobalIndex,
      sr1646v2CllRFCsRegisterStateValue
         DisplayString
      }

sr1646v2CllRFCsRegisterStateGlobalIx OBJECT-TYPE
   SYNTAX      GlobalIndex
   MAX-ACCESS  not-accessible
   STATUS      current
   DESCRIPTION
      "The value of the tlsCntTreeGlobalIndex of the MANAGED OBJECT."
   ::= {sr1646v2CllRFCsRegisterStateEntry 10}

sr1646v2CllRFCsRegisterStateValue OBJECT-TYPE
   SYNTAX      DisplayString
   MAX-ACCESS  read-only
   STATUS      current
   DESCRIPTION
      "Path: cellular.status.csRegisterState"
   ::= {sr1646v2CllRFCsRegisterStateEntry 2147483648}


sr1646v2CllRFPsAttachState OBJECT IDENTIFIER ::= {sr1646v2CllRF 43}

sr1646v2CllRFPsAttachStateTable OBJECT-TYPE
   SYNTAX      SEQUENCE OF Sr1646v2CllRFPsAttachStateEntry
   MAX-ACCESS  not-accessible
   STATUS      current
   DESCRIPTION
      "misc. string"
   ::= {sr1646v2CllRFPsAttachState 1}

sr1646v2CllRFPsAttachStateEntry OBJECT-TYPE
   SYNTAX      Sr1646v2CllRFPsAttachStateEntry
   MAX-ACCESS  not-accessible
   STATUS      current
   DESCRIPTION
      ""
   INDEX      { sr1646v2CllRFPsAttachStateGlobalIx }
   ::= {sr1646v2CllRFPsAttachStateTable 1}

Sr1646v2CllRFPsAttachStateEntry ::=
   SEQUENCE
      {
      sr1646v2CllRFPsAttachStateGlobalIx
         GlobalIndex,
      sr1646v2CllRFPsAttachStateValue
         DisplayString
      }

sr1646v2CllRFPsAttachStateGlobalIx OBJECT-TYPE
   SYNTAX      GlobalIndex
   MAX-ACCESS  not-accessible
   STATUS      current
   DESCRIPTION
      "The value of the tlsCntTreeGlobalIndex of the MANAGED OBJECT."
   ::= {sr1646v2CllRFPsAttachStateEntry 10}

sr1646v2CllRFPsAttachStateValue OBJECT-TYPE
   SYNTAX      DisplayString
   MAX-ACCESS  read-only
   STATUS      current
   DESCRIPTION
      "Path: cellular.status.psAttachState"
   ::= {sr1646v2CllRFPsAttachStateEntry 2147483648}


sr1646v2CllRFModule OBJECT IDENTIFIER ::= {sr1646v2CllRF 48}

sr1646v2CllRFModuleSSCTable OBJECT-TYPE
   SYNTAX      SEQUENCE OF Sr1646v2CllRFModuleEntry
   MAX-ACCESS  not-accessible
   STATUS      current
   DESCRIPTION
      "module information"
   ::= {sr1646v2CllRFModule 1}

sr1646v2CllRFModuleEntry OBJECT-TYPE
   SYNTAX      Sr1646v2CllRFModuleEntry
   MAX-ACCESS  not-accessible
   STATUS      current
   DESCRIPTION
      ""
   INDEX      { sr1646v2CllRFModuleGlobalIx }
   ::= {sr1646v2CllRFModuleSSCTable 1}

Sr1646v2CllRFModuleEntry ::=
   SEQUENCE
      {
      sr1646v2CllRFModuleGlobalIx
         GlobalIndex,
      sr1646v2CllRFModuleManufacturer
         DisplayString,
      sr1646v2CllRFModuleModel
         DisplayString,
      sr1646v2CllRFModuleBootCode
         DisplayString,
      sr1646v2CllRFModuleRevision
         DisplayString,
      sr1646v2CllRFModuleImei
         DisplayString
      }

sr1646v2CllRFModuleGlobalIx OBJECT-TYPE
   SYNTAX      GlobalIndex
   MAX-ACCESS  not-accessible
   STATUS      current
   DESCRIPTION
      "The value of the tlsCntTreeGlobalIndex of the MANAGED OBJECT."
   ::= {sr1646v2CllRFModuleEntry 10}

sr1646v2CllRFModuleManufacturer OBJECT-TYPE
   SYNTAX      DisplayString
   MAX-ACCESS  read-only
   STATUS      current
   DESCRIPTION
      "Path: cellular.status.module.manufacturer"
   ::= {sr1646v2CllRFModuleEntry 16777216}

sr1646v2CllRFModuleModel OBJECT-TYPE
   SYNTAX      DisplayString
   MAX-ACCESS  read-only
   STATUS      current
   DESCRIPTION
      "Path: cellular.status.module.model"
   ::= {sr1646v2CllRFModuleEntry 33554432}

sr1646v2CllRFModuleBootCode OBJECT-TYPE
   SYNTAX      DisplayString
   MAX-ACCESS  read-only
   STATUS      current
   DESCRIPTION
      "Path: cellular.status.module.bootCode"
   ::= {sr1646v2CllRFModuleEntry 50331648}

sr1646v2CllRFModuleRevision OBJECT-TYPE
   SYNTAX      DisplayString
   MAX-ACCESS  read-only
   STATUS      current
   DESCRIPTION
      "Path: cellular.status.module.revision"
   ::= {sr1646v2CllRFModuleEntry 67108864}

sr1646v2CllRFModuleImei OBJECT-TYPE
   SYNTAX      DisplayString
   MAX-ACCESS  read-only
   STATUS      current
   DESCRIPTION
      "Path: cellular.status.module.imei"
   ::= {sr1646v2CllRFModuleEntry 83886080}

sr1646v2CllRFModuleImages OBJECT-TYPE
   SYNTAX      SEQUENCE OF Sr1646v2CllRFModuleImagesEntry
   MAX-ACCESS  not-accessible
   STATUS      current
   DESCRIPTION
      ""
   ::= {sr1646v2CllRFModule 100663296}

sr1646v2CllRFModuleImagesEntry OBJECT-TYPE
   SYNTAX      Sr1646v2CllRFModuleImagesEntry
   MAX-ACCESS  not-accessible
   STATUS      current
   DESCRIPTION
      ""
   INDEX      { sr1646v2CllRFModuleImagesGlobalIx,
                sr1646v2CllRFModuleImagesTableIx }
   ::= {sr1646v2CllRFModuleImages 1}

Sr1646v2CllRFModuleImagesEntry ::=
   SEQUENCE
      {
      sr1646v2CllRFModuleImagesGlobalIx
         GlobalIndex,
      sr1646v2CllRFModuleImagesTableIx
         TableIndex,
      sr1646v2CllRFModuleImagesType
         INTEGER,
      sr1646v2CllRFModuleImagesRunning
         INTEGER,
      sr1646v2CllRFModuleImagesVersion
         DisplayString,
      sr1646v2CllRFModuleImagesBuild
         DisplayString
      }

sr1646v2CllRFModuleImagesGlobalIx OBJECT-TYPE
   SYNTAX      GlobalIndex
   MAX-ACCESS  not-accessible
   STATUS      current
   DESCRIPTION
      "The value of the tlsCntTreeGlobalIndex of the MANAGED OBJECT."
   ::= {sr1646v2CllRFModuleImagesEntry 10}

sr1646v2CllRFModuleImagesTableIx OBJECT-TYPE
   SYNTAX      TableIndex
   MAX-ACCESS  not-accessible
   STATUS      current
   DESCRIPTION
      ""
   ::= {sr1646v2CllRFModuleImagesEntry 11}

sr1646v2CllRFModuleImagesType OBJECT-TYPE
   SYNTAX      INTEGER
               {
               unknown (0),
               cWE (1),
               nVU (2),
               sPK (3)
               }
   MAX-ACCESS  read-only
   STATUS      current
   DESCRIPTION
      "Path: cellular.status.module.images.type

       Possibilities:
               unknown   (0)
               CWE   (1)
               NVU   (2)
               SPK   (3)"
   ::= {sr1646v2CllRFModuleImagesEntry 16777216}

sr1646v2CllRFModuleImagesRunning OBJECT-TYPE
   SYNTAX      INTEGER
               {
               no (0),
               yes (1)
               }
   MAX-ACCESS  read-only
   STATUS      current
   DESCRIPTION
      "Path: cellular.status.module.images.running

       Possibilities:
               no   (0)
               yes   (1)"
   ::= {sr1646v2CllRFModuleImagesEntry 33554432}

sr1646v2CllRFModuleImagesVersion OBJECT-TYPE
   SYNTAX      DisplayString
   MAX-ACCESS  read-only
   STATUS      current
   DESCRIPTION
      "Path: cellular.status.module.images.version"
   ::= {sr1646v2CllRFModuleImagesEntry 50331648}

sr1646v2CllRFModuleImagesBuild OBJECT-TYPE
   SYNTAX      DisplayString
   MAX-ACCESS  read-only
   STATUS      current
   DESCRIPTION
      "Path: cellular.status.module.images.build"
   ::= {sr1646v2CllRFModuleImagesEntry 67108864}

sr1646v2CllRFModuleCurrentImages OBJECT-TYPE
   SYNTAX      SEQUENCE OF Sr1646v2CllRFModuleCurrentImagesEntry
   MAX-ACCESS  not-accessible
   STATUS      current
   DESCRIPTION
      ""
   ::= {sr1646v2CllRFModule 117440512}

sr1646v2CllRFModuleCurrentImagesEntry OBJECT-TYPE
   SYNTAX      Sr1646v2CllRFModuleCurrentImagesEntry
   MAX-ACCESS  not-accessible
   STATUS      current
   DESCRIPTION
      ""
   INDEX      { sr1646v2CllRFModuleCurrentImagesGlobalIx,
                sr1646v2CllRFModuleCurrentImagesTableIx }
   ::= {sr1646v2CllRFModuleCurrentImages 1}

Sr1646v2CllRFModuleCurrentImagesEntry ::=
   SEQUENCE
      {
      sr1646v2CllRFModuleCurrentImagesGlobalIx
         GlobalIndex,
      sr1646v2CllRFModuleCurrentImagesTableIx
         TableIndex,
      sr1646v2CllRFModuleCurrentImagesType
         INTEGER,
      sr1646v2CllRFModuleCurrentImagesVersion
         DisplayString,
      sr1646v2CllRFModuleCurrentImagesBuild
         DisplayString
      }

sr1646v2CllRFModuleCurrentImagesGlobalIx OBJECT-TYPE
   SYNTAX      GlobalIndex
   MAX-ACCESS  not-accessible
   STATUS      current
   DESCRIPTION
      "The value of the tlsCntTreeGlobalIndex of the MANAGED OBJECT."
   ::= {sr1646v2CllRFModuleCurrentImagesEntry 10}

sr1646v2CllRFModuleCurrentImagesTableIx OBJECT-TYPE
   SYNTAX      TableIndex
   MAX-ACCESS  not-accessible
   STATUS      current
   DESCRIPTION
      ""
   ::= {sr1646v2CllRFModuleCurrentImagesEntry 11}

sr1646v2CllRFModuleCurrentImagesType OBJECT-TYPE
   SYNTAX      INTEGER
               {
               unknown (0),
               cWE (1),
               nVU (2),
               sPK (3)
               }
   MAX-ACCESS  read-only
   STATUS      current
   DESCRIPTION
      "Path: cellular.status.module.currentImages.type

       Possibilities:
               unknown   (0)
               CWE   (1)
               NVU   (2)
               SPK   (3)"
   ::= {sr1646v2CllRFModuleCurrentImagesEntry 16777216}

sr1646v2CllRFModuleCurrentImagesVersion OBJECT-TYPE
   SYNTAX      DisplayString
   MAX-ACCESS  read-only
   STATUS      current
   DESCRIPTION
      "Path: cellular.status.module.currentImages.version"
   ::= {sr1646v2CllRFModuleCurrentImagesEntry 33554432}

sr1646v2CllRFModuleCurrentImagesBuild OBJECT-TYPE
   SYNTAX      DisplayString
   MAX-ACCESS  read-only
   STATUS      current
   DESCRIPTION
      "Path: cellular.status.module.currentImages.build"
   ::= {sr1646v2CllRFModuleCurrentImagesEntry 50331648}


sr1646v2CllRFNetwork OBJECT IDENTIFIER ::= {sr1646v2CllRF 49}

sr1646v2CllRFNetworkSSCTable OBJECT-TYPE
   SYNTAX      SEQUENCE OF Sr1646v2CllRFNetworkEntry
   MAX-ACCESS  not-accessible
   STATUS      current
   DESCRIPTION
      "network information"
   ::= {sr1646v2CllRFNetwork 1}

sr1646v2CllRFNetworkEntry OBJECT-TYPE
   SYNTAX      Sr1646v2CllRFNetworkEntry
   MAX-ACCESS  not-accessible
   STATUS      current
   DESCRIPTION
      ""
   INDEX      { sr1646v2CllRFNetworkGlobalIx }
   ::= {sr1646v2CllRFNetworkSSCTable 1}

Sr1646v2CllRFNetworkEntry ::=
   SEQUENCE
      {
      sr1646v2CllRFNetworkGlobalIx
         GlobalIndex,
      sr1646v2CllRFNetworkPlmn
         DisplayString,
      sr1646v2CllRFNetworkLac
         Integer32,
      sr1646v2CllRFNetworkTac
         Integer32,
      sr1646v2CllRFNetworkCellId
         Integer32
      }

sr1646v2CllRFNetworkGlobalIx OBJECT-TYPE
   SYNTAX      GlobalIndex
   MAX-ACCESS  not-accessible
   STATUS      current
   DESCRIPTION
      "The value of the tlsCntTreeGlobalIndex of the MANAGED OBJECT."
   ::= {sr1646v2CllRFNetworkEntry 10}

sr1646v2CllRFNetworkPlmn OBJECT-TYPE
   SYNTAX      DisplayString
   MAX-ACCESS  read-only
   STATUS      current
   DESCRIPTION
      "Path: cellular.status.network.plmn"
   ::= {sr1646v2CllRFNetworkEntry 16777216}

sr1646v2CllRFNetworkLac OBJECT-TYPE
   SYNTAX      Integer32
   MAX-ACCESS  read-only
   STATUS      current
   DESCRIPTION
      "Path: cellular.status.network.lac"
   ::= {sr1646v2CllRFNetworkEntry 33554432}

sr1646v2CllRFNetworkTac OBJECT-TYPE
   SYNTAX      Integer32
   MAX-ACCESS  read-only
   STATUS      current
   DESCRIPTION
      "Path: cellular.status.network.tac"
   ::= {sr1646v2CllRFNetworkEntry 50331648}

sr1646v2CllRFNetworkCellId OBJECT-TYPE
   SYNTAX      Integer32
   MAX-ACCESS  read-only
   STATUS      current
   DESCRIPTION
      "Path: cellular.status.network.cellId"
   ::= {sr1646v2CllRFNetworkEntry 67108864}


sr1646v2CllRFSnmpIndex OBJECT IDENTIFIER ::= {sr1646v2CllRF 269}

sr1646v2CllRFSnmpIndexTable OBJECT-TYPE
   SYNTAX      SEQUENCE OF Sr1646v2CllRFSnmpIndexEntry
   MAX-ACCESS  not-accessible
   STATUS      current
   DESCRIPTION
      "SNMP index assigned to this object"
   ::= {sr1646v2CllRFSnmpIndex 1}

sr1646v2CllRFSnmpIndexEntry OBJECT-TYPE
   SYNTAX      Sr1646v2CllRFSnmpIndexEntry
   MAX-ACCESS  not-accessible
   STATUS      current
   DESCRIPTION
      ""
   INDEX      { sr1646v2CllRFSnmpIndexGlobalIx }
   ::= {sr1646v2CllRFSnmpIndexTable 1}

Sr1646v2CllRFSnmpIndexEntry ::=
   SEQUENCE
      {
      sr1646v2CllRFSnmpIndexGlobalIx
         GlobalIndex,
      sr1646v2CllRFSnmpIndexValue
         Integer32
      }

sr1646v2CllRFSnmpIndexGlobalIx OBJECT-TYPE
   SYNTAX      GlobalIndex
   MAX-ACCESS  not-accessible
   STATUS      current
   DESCRIPTION
      "The value of the tlsCntTreeGlobalIndex of the MANAGED OBJECT."
   ::= {sr1646v2CllRFSnmpIndexEntry 10}

sr1646v2CllRFSnmpIndexValue OBJECT-TYPE
   SYNTAX      Integer32
   MAX-ACCESS  read-only
   STATUS      current
   DESCRIPTION
      "Path: cellular.status.snmpIndex"
   ::= {sr1646v2CllRFSnmpIndexEntry 2147483648}


sr1646v2CllRFRssi OBJECT IDENTIFIER ::= {sr1646v2CllRF 70}

sr1646v2CllRFRssiTable OBJECT-TYPE
   SYNTAX      SEQUENCE OF Sr1646v2CllRFRssiEntry
   MAX-ACCESS  not-accessible
   STATUS      current
   DESCRIPTION
      "rssi"
   ::= {sr1646v2CllRFRssi 1}

sr1646v2CllRFRssiEntry OBJECT-TYPE
   SYNTAX      Sr1646v2CllRFRssiEntry
   MAX-ACCESS  not-accessible
   STATUS      current
   DESCRIPTION
      ""
   INDEX      { sr1646v2CllRFRssiGlobalIx }
   ::= {sr1646v2CllRFRssiTable 1}

Sr1646v2CllRFRssiEntry ::=
   SEQUENCE
      {
      sr1646v2CllRFRssiGlobalIx
         GlobalIndex,
      sr1646v2CllRFRssiValue
         INTEGER
      }

sr1646v2CllRFRssiGlobalIx OBJECT-TYPE
   SYNTAX      GlobalIndex
   MAX-ACCESS  not-accessible
   STATUS      current
   DESCRIPTION
      "The value of the tlsCntTreeGlobalIndex of the MANAGED OBJECT."
   ::= {sr1646v2CllRFRssiEntry 10}

sr1646v2CllRFRssiValue OBJECT-TYPE
   SYNTAX      INTEGER
               {
               slOPTg (-128)
               }
   MAX-ACCESS  read-only
   STATUS      current
   DESCRIPTION
      "Path: cellular.status.rssi

       unit name = dBm
       formula = 1 * ; 1 /

       Possibilities:
               <OPT>   (-128)"
   ::= {sr1646v2CllRFRssiEntry 2147483648}


sr1646v2CllRFEcio OBJECT IDENTIFIER ::= {sr1646v2CllRF 71}

sr1646v2CllRFEcioTable OBJECT-TYPE
   SYNTAX      SEQUENCE OF Sr1646v2CllRFEcioEntry
   MAX-ACCESS  not-accessible
   STATUS      current
   DESCRIPTION
      "EcIo"
   ::= {sr1646v2CllRFEcio 1}

sr1646v2CllRFEcioEntry OBJECT-TYPE
   SYNTAX      Sr1646v2CllRFEcioEntry
   MAX-ACCESS  not-accessible
   STATUS      current
   DESCRIPTION
      ""
   INDEX      { sr1646v2CllRFEcioGlobalIx }
   ::= {sr1646v2CllRFEcioTable 1}

Sr1646v2CllRFEcioEntry ::=
   SEQUENCE
      {
      sr1646v2CllRFEcioGlobalIx
         GlobalIndex,
      sr1646v2CllRFEcioValue
         INTEGER
      }

sr1646v2CllRFEcioGlobalIx OBJECT-TYPE
   SYNTAX      GlobalIndex
   MAX-ACCESS  not-accessible
   STATUS      current
   DESCRIPTION
      "The value of the tlsCntTreeGlobalIndex of the MANAGED OBJECT."
   ::= {sr1646v2CllRFEcioEntry 10}

sr1646v2CllRFEcioValue OBJECT-TYPE
   SYNTAX      INTEGER
               {
               slOPTg (-32767)
               }
   MAX-ACCESS  read-only
   STATUS      current
   DESCRIPTION
      "Path: cellular.status.ecio

       unit name = dB
       formula = 2 / NEG ; 2 * NEG

       Possibilities:
               <OPT>   (-32767)"
   ::= {sr1646v2CllRFEcioEntry 2147483648}


sr1646v2CllRFRsrq OBJECT IDENTIFIER ::= {sr1646v2CllRF 72}

sr1646v2CllRFRsrqTable OBJECT-TYPE
   SYNTAX      SEQUENCE OF Sr1646v2CllRFRsrqEntry
   MAX-ACCESS  not-accessible
   STATUS      current
   DESCRIPTION
      "RSRQ"
   ::= {sr1646v2CllRFRsrq 1}

sr1646v2CllRFRsrqEntry OBJECT-TYPE
   SYNTAX      Sr1646v2CllRFRsrqEntry
   MAX-ACCESS  not-accessible
   STATUS      current
   DESCRIPTION
      ""
   INDEX      { sr1646v2CllRFRsrqGlobalIx }
   ::= {sr1646v2CllRFRsrqTable 1}

Sr1646v2CllRFRsrqEntry ::=
   SEQUENCE
      {
      sr1646v2CllRFRsrqGlobalIx
         GlobalIndex,
      sr1646v2CllRFRsrqValue
         INTEGER
      }

sr1646v2CllRFRsrqGlobalIx OBJECT-TYPE
   SYNTAX      GlobalIndex
   MAX-ACCESS  not-accessible
   STATUS      current
   DESCRIPTION
      "The value of the tlsCntTreeGlobalIndex of the MANAGED OBJECT."
   ::= {sr1646v2CllRFRsrqEntry 10}

sr1646v2CllRFRsrqValue OBJECT-TYPE
   SYNTAX      INTEGER
               {
               slOPTg (0)
               }
   UNITS       "dB"
   MAX-ACCESS  read-only
   STATUS      current
   DESCRIPTION
      "Path: cellular.status.rsrq

       unit name = dB

       Possibilities:
               <OPT>   (0)"
   ::= {sr1646v2CllRFRsrqEntry 2147483648}


sr1646v2CllRFRsrp OBJECT IDENTIFIER ::= {sr1646v2CllRF 73}

sr1646v2CllRFRsrpTable OBJECT-TYPE
   SYNTAX      SEQUENCE OF Sr1646v2CllRFRsrpEntry
   MAX-ACCESS  not-accessible
   STATUS      current
   DESCRIPTION
      "RSRP"
   ::= {sr1646v2CllRFRsrp 1}

sr1646v2CllRFRsrpEntry OBJECT-TYPE
   SYNTAX      Sr1646v2CllRFRsrpEntry
   MAX-ACCESS  not-accessible
   STATUS      current
   DESCRIPTION
      ""
   INDEX      { sr1646v2CllRFRsrpGlobalIx }
   ::= {sr1646v2CllRFRsrpTable 1}

Sr1646v2CllRFRsrpEntry ::=
   SEQUENCE
      {
      sr1646v2CllRFRsrpGlobalIx
         GlobalIndex,
      sr1646v2CllRFRsrpValue
         INTEGER
      }

sr1646v2CllRFRsrpGlobalIx OBJECT-TYPE
   SYNTAX      GlobalIndex
   MAX-ACCESS  not-accessible
   STATUS      current
   DESCRIPTION
      "The value of the tlsCntTreeGlobalIndex of the MANAGED OBJECT."
   ::= {sr1646v2CllRFRsrpEntry 10}

sr1646v2CllRFRsrpValue OBJECT-TYPE
   SYNTAX      INTEGER
               {
               slOPTg (0)
               }
   UNITS       "dBm"
   MAX-ACCESS  read-only
   STATUS      current
   DESCRIPTION
      "Path: cellular.status.rsrp

       unit name = dBm

       Possibilities:
               <OPT>   (0)"
   ::= {sr1646v2CllRFRsrpEntry 2147483648}


sr1646v2CllRFSnr OBJECT IDENTIFIER ::= {sr1646v2CllRF 74}

sr1646v2CllRFSnrTable OBJECT-TYPE
   SYNTAX      SEQUENCE OF Sr1646v2CllRFSnrEntry
   MAX-ACCESS  not-accessible
   STATUS      current
   DESCRIPTION
      "SNR"
   ::= {sr1646v2CllRFSnr 1}

sr1646v2CllRFSnrEntry OBJECT-TYPE
   SYNTAX      Sr1646v2CllRFSnrEntry
   MAX-ACCESS  not-accessible
   STATUS      current
   DESCRIPTION
      ""
   INDEX      { sr1646v2CllRFSnrGlobalIx }
   ::= {sr1646v2CllRFSnrTable 1}

Sr1646v2CllRFSnrEntry ::=
   SEQUENCE
      {
      sr1646v2CllRFSnrGlobalIx
         GlobalIndex,
      sr1646v2CllRFSnrValue
         INTEGER
      }

sr1646v2CllRFSnrGlobalIx OBJECT-TYPE
   SYNTAX      GlobalIndex
   MAX-ACCESS  not-accessible
   STATUS      current
   DESCRIPTION
      "The value of the tlsCntTreeGlobalIndex of the MANAGED OBJECT."
   ::= {sr1646v2CllRFSnrEntry 10}

sr1646v2CllRFSnrValue OBJECT-TYPE
   SYNTAX      INTEGER
               {
               slOPTg (-32767)
               }
   MAX-ACCESS  read-only
   STATUS      current
   DESCRIPTION
      "Path: cellular.status.snr

       unit name = dB
       formula = 10 /  ; 10 *

       Possibilities:
               <OPT>   (-32767)"
   ::= {sr1646v2CllRFSnrEntry 2147483648}



ar1646v2CllRF OBJECT IDENTIFIER ::= {r1646v2CllRF 16}


ar1646v2CllRFHipReset OBJECT IDENTIFIER ::= {ar1646v2CllRF 501}

ar1646v2CllRFHipResetTable OBJECT-TYPE
   SYNTAX      SEQUENCE OF Ar1646v2CllRFHipResetEntry
   MAX-ACCESS  not-accessible
   STATUS      current
   DESCRIPTION
      "hip reset"
   ::= {ar1646v2CllRFHipReset 1}

ar1646v2CllRFHipResetEntry OBJECT-TYPE
   SYNTAX      Ar1646v2CllRFHipResetEntry
   MAX-ACCESS  not-accessible
   STATUS      current
   DESCRIPTION
      ""
   INDEX      { ar1646v2CllRFHipResetGlobalIx }
   ::= {ar1646v2CllRFHipResetTable 1}

Ar1646v2CllRFHipResetEntry ::=
   SEQUENCE
      {
      ar1646v2CllRFHipResetGlobalIx
         GlobalIndex,
      ar1646v2CllRFHipResetValue
         Integer32
      }

ar1646v2CllRFHipResetGlobalIx OBJECT-TYPE
   SYNTAX      GlobalIndex
   MAX-ACCESS  not-accessible
   STATUS      current
   DESCRIPTION
      "The value of the tlsCntTreeGlobalIndex of the MANAGED OBJECT."
   ::= {ar1646v2CllRFHipResetEntry 10}

ar1646v2CllRFHipResetValue OBJECT-TYPE
   SYNTAX      Integer32
   MAX-ACCESS  read-write
   STATUS      current
   DESCRIPTION
      "Path: cellular.actions.hipReset"
   ::= {ar1646v2CllRFHipResetEntry 2147483648}


ar1646v2CllRFUsbReset OBJECT IDENTIFIER ::= {ar1646v2CllRF 500}

ar1646v2CllRFUsbResetTable OBJECT-TYPE
   SYNTAX      SEQUENCE OF Ar1646v2CllRFUsbResetEntry
   MAX-ACCESS  not-accessible
   STATUS      current
   DESCRIPTION
      "usb reset"
   ::= {ar1646v2CllRFUsbReset 1}

ar1646v2CllRFUsbResetEntry OBJECT-TYPE
   SYNTAX      Ar1646v2CllRFUsbResetEntry
   MAX-ACCESS  not-accessible
   STATUS      current
   DESCRIPTION
      ""
   INDEX      { ar1646v2CllRFUsbResetGlobalIx }
   ::= {ar1646v2CllRFUsbResetTable 1}

Ar1646v2CllRFUsbResetEntry ::=
   SEQUENCE
      {
      ar1646v2CllRFUsbResetGlobalIx
         GlobalIndex,
      ar1646v2CllRFUsbResetValue
         Integer32
      }

ar1646v2CllRFUsbResetGlobalIx OBJECT-TYPE
   SYNTAX      GlobalIndex
   MAX-ACCESS  not-accessible
   STATUS      current
   DESCRIPTION
      "The value of the tlsCntTreeGlobalIndex of the MANAGED OBJECT."
   ::= {ar1646v2CllRFUsbResetEntry 10}

ar1646v2CllRFUsbResetValue OBJECT-TYPE
   SYNTAX      Integer32
   MAX-ACCESS  read-write
   STATUS      current
   DESCRIPTION
      "Path: cellular.actions.usbReset"
   ::= {ar1646v2CllRFUsbResetEntry 2147483648}


ar1646v2CllRFSelectCarrier OBJECT IDENTIFIER ::= {ar1646v2CllRF 414}

ar1646v2CllRFSelectCarrierTable OBJECT-TYPE
   SYNTAX      SEQUENCE OF Ar1646v2CllRFSelectCarrierEntry
   MAX-ACCESS  not-accessible
   STATUS      current
   DESCRIPTION
      "Sierra Wireless Modem - select carrier"
   ::= {ar1646v2CllRFSelectCarrier 1}

ar1646v2CllRFSelectCarrierEntry OBJECT-TYPE
   SYNTAX      Ar1646v2CllRFSelectCarrierEntry
   MAX-ACCESS  not-accessible
   STATUS      current
   DESCRIPTION
      ""
   INDEX      { ar1646v2CllRFSelectCarrierGlobalIx }
   ::= {ar1646v2CllRFSelectCarrierTable 1}

Ar1646v2CllRFSelectCarrierEntry ::=
   SEQUENCE
      {
      ar1646v2CllRFSelectCarrierGlobalIx
         GlobalIndex,
      ar1646v2CllRFSelectCarrierValue
         Integer32
      }

ar1646v2CllRFSelectCarrierGlobalIx OBJECT-TYPE
   SYNTAX      GlobalIndex
   MAX-ACCESS  not-accessible
   STATUS      current
   DESCRIPTION
      "The value of the tlsCntTreeGlobalIndex of the MANAGED OBJECT."
   ::= {ar1646v2CllRFSelectCarrierEntry 10}

ar1646v2CllRFSelectCarrierValue OBJECT-TYPE
   SYNTAX      Integer32
   MAX-ACCESS  read-write
   STATUS      current
   DESCRIPTION
      "Path: cellular.actions.selectCarrier"
   ::= {ar1646v2CllRFSelectCarrierEntry 2147483648}


ar1646v2CllRFCarrierName OBJECT IDENTIFIER ::= {ar1646v2CllRF 415}

ar1646v2CllRFCarrierNameTable OBJECT-TYPE
   SYNTAX      SEQUENCE OF Ar1646v2CllRFCarrierNameEntry
   MAX-ACCESS  not-accessible
   STATUS      current
   DESCRIPTION
      "Sierra Wireless Modem - carrier name"
   ::= {ar1646v2CllRFCarrierName 1}

ar1646v2CllRFCarrierNameEntry OBJECT-TYPE
   SYNTAX      Ar1646v2CllRFCarrierNameEntry
   MAX-ACCESS  not-accessible
   STATUS      current
   DESCRIPTION
      ""
   INDEX      { ar1646v2CllRFCarrierNameGlobalIx }
   ::= {ar1646v2CllRFCarrierNameTable 1}

Ar1646v2CllRFCarrierNameEntry ::=
   SEQUENCE
      {
      ar1646v2CllRFCarrierNameGlobalIx
         GlobalIndex,
      ar1646v2CllRFCarrierNameValue
         DisplayString
      }

ar1646v2CllRFCarrierNameGlobalIx OBJECT-TYPE
   SYNTAX      GlobalIndex
   MAX-ACCESS  not-accessible
   STATUS      current
   DESCRIPTION
      "The value of the tlsCntTreeGlobalIndex of the MANAGED OBJECT."
   ::= {ar1646v2CllRFCarrierNameEntry 10}

ar1646v2CllRFCarrierNameValue OBJECT-TYPE
   SYNTAX      DisplayString
   MAX-ACCESS  read-write
   STATUS      current
   DESCRIPTION
      "Path: cellular.actions.carrierName"
   ::= {ar1646v2CllRFCarrierNameEntry 2147483648}


ar1646v2CllRFSendSms OBJECT IDENTIFIER ::= {ar1646v2CllRF 412}

ar1646v2CllRFSendSmsTable OBJECT-TYPE
   SYNTAX      SEQUENCE OF Ar1646v2CllRFSendSmsEntry
   MAX-ACCESS  not-accessible
   STATUS      current
   DESCRIPTION
      "send SMS"
   ::= {ar1646v2CllRFSendSms 1}

ar1646v2CllRFSendSmsEntry OBJECT-TYPE
   SYNTAX      Ar1646v2CllRFSendSmsEntry
   MAX-ACCESS  not-accessible
   STATUS      current
   DESCRIPTION
      ""
   INDEX      { ar1646v2CllRFSendSmsGlobalIx }
   ::= {ar1646v2CllRFSendSmsTable 1}

Ar1646v2CllRFSendSmsEntry ::=
   SEQUENCE
      {
      ar1646v2CllRFSendSmsGlobalIx
         GlobalIndex,
      ar1646v2CllRFSendSmsValue
         Integer32
      }

ar1646v2CllRFSendSmsGlobalIx OBJECT-TYPE
   SYNTAX      GlobalIndex
   MAX-ACCESS  not-accessible
   STATUS      current
   DESCRIPTION
      "The value of the tlsCntTreeGlobalIndex of the MANAGED OBJECT."
   ::= {ar1646v2CllRFSendSmsEntry 10}

ar1646v2CllRFSendSmsValue OBJECT-TYPE
   SYNTAX      Integer32
   MAX-ACCESS  read-write
   STATUS      current
   DESCRIPTION
      "Path: cellular.actions.sendSms"
   ::= {ar1646v2CllRFSendSmsEntry 2147483648}


ar1646v2CllRFSmsData OBJECT IDENTIFIER ::= {ar1646v2CllRF 413}

ar1646v2CllRFSmsDataSSCTable OBJECT-TYPE
   SYNTAX      SEQUENCE OF Ar1646v2CllRFSmsDataEntry
   MAX-ACCESS  not-accessible
   STATUS      current
   DESCRIPTION
      "SMS to send"
   ::= {ar1646v2CllRFSmsData 1}

ar1646v2CllRFSmsDataEntry OBJECT-TYPE
   SYNTAX      Ar1646v2CllRFSmsDataEntry
   MAX-ACCESS  not-accessible
   STATUS      current
   DESCRIPTION
      ""
   INDEX      { ar1646v2CllRFSmsDataGlobalIx }
   ::= {ar1646v2CllRFSmsDataSSCTable 1}

Ar1646v2CllRFSmsDataEntry ::=
   SEQUENCE
      {
      ar1646v2CllRFSmsDataGlobalIx
         GlobalIndex,
      ar1646v2CllRFSmsDataTelephoneNumber
         DisplayString,
      ar1646v2CllRFSmsDataMessage
         DisplayString
      }

ar1646v2CllRFSmsDataGlobalIx OBJECT-TYPE
   SYNTAX      GlobalIndex
   MAX-ACCESS  not-accessible
   STATUS      current
   DESCRIPTION
      "The value of the tlsCntTreeGlobalIndex of the MANAGED OBJECT."
   ::= {ar1646v2CllRFSmsDataEntry 10}

ar1646v2CllRFSmsDataTelephoneNumber OBJECT-TYPE
   SYNTAX      DisplayString
   MAX-ACCESS  read-write
   STATUS      current
   DESCRIPTION
      "Path: cellular.actions.smsData.telephoneNumber"
   ::= {ar1646v2CllRFSmsDataEntry 16777216}

ar1646v2CllRFSmsDataMessage OBJECT-TYPE
   SYNTAX      DisplayString
   MAX-ACCESS  read-write
   STATUS      current
   DESCRIPTION
      "Path: cellular.actions.smsData.message"
   ::= {ar1646v2CllRFSmsDataEntry 33554432}


ar1646v2CllRFSendAtCommand OBJECT IDENTIFIER ::= {ar1646v2CllRF 410}

ar1646v2CllRFSendAtCommandTable OBJECT-TYPE
   SYNTAX      SEQUENCE OF Ar1646v2CllRFSendAtCommandEntry
   MAX-ACCESS  not-accessible
   STATUS      current
   DESCRIPTION
      "send AT command"
   ::= {ar1646v2CllRFSendAtCommand 1}

ar1646v2CllRFSendAtCommandEntry OBJECT-TYPE
   SYNTAX      Ar1646v2CllRFSendAtCommandEntry
   MAX-ACCESS  not-accessible
   STATUS      current
   DESCRIPTION
      ""
   INDEX      { ar1646v2CllRFSendAtCommandGlobalIx }
   ::= {ar1646v2CllRFSendAtCommandTable 1}

Ar1646v2CllRFSendAtCommandEntry ::=
   SEQUENCE
      {
      ar1646v2CllRFSendAtCommandGlobalIx
         GlobalIndex,
      ar1646v2CllRFSendAtCommandValue
         Integer32
      }

ar1646v2CllRFSendAtCommandGlobalIx OBJECT-TYPE
   SYNTAX      GlobalIndex
   MAX-ACCESS  not-accessible
   STATUS      current
   DESCRIPTION
      "The value of the tlsCntTreeGlobalIndex of the MANAGED OBJECT."
   ::= {ar1646v2CllRFSendAtCommandEntry 10}

ar1646v2CllRFSendAtCommandValue OBJECT-TYPE
   SYNTAX      Integer32
   MAX-ACCESS  read-write
   STATUS      current
   DESCRIPTION
      "Path: cellular.actions.sendAtCommand"
   ::= {ar1646v2CllRFSendAtCommandEntry 2147483648}


ar1646v2CllRFAtCommand OBJECT IDENTIFIER ::= {ar1646v2CllRF 411}

ar1646v2CllRFAtCommandTable OBJECT-TYPE
   SYNTAX      SEQUENCE OF Ar1646v2CllRFAtCommandEntry
   MAX-ACCESS  not-accessible
   STATUS      current
   DESCRIPTION
      "AT command to execute"
   ::= {ar1646v2CllRFAtCommand 1}

ar1646v2CllRFAtCommandEntry OBJECT-TYPE
   SYNTAX      Ar1646v2CllRFAtCommandEntry
   MAX-ACCESS  not-accessible
   STATUS      current
   DESCRIPTION
      ""
   INDEX      { ar1646v2CllRFAtCommandGlobalIx }
   ::= {ar1646v2CllRFAtCommandTable 1}

Ar1646v2CllRFAtCommandEntry ::=
   SEQUENCE
      {
      ar1646v2CllRFAtCommandGlobalIx
         GlobalIndex,
      ar1646v2CllRFAtCommandValue
         DisplayString
      }

ar1646v2CllRFAtCommandGlobalIx OBJECT-TYPE
   SYNTAX      GlobalIndex
   MAX-ACCESS  not-accessible
   STATUS      current
   DESCRIPTION
      "The value of the tlsCntTreeGlobalIndex of the MANAGED OBJECT."
   ::= {ar1646v2CllRFAtCommandEntry 10}

ar1646v2CllRFAtCommandValue OBJECT-TYPE
   SYNTAX      DisplayString
   MAX-ACCESS  read-write
   STATUS      current
   DESCRIPTION
      "Path: cellular.actions.atCommand"
   ::= {ar1646v2CllRFAtCommandEntry 2147483648}


ar1646v2CllRFResetModule OBJECT IDENTIFIER ::= {ar1646v2CllRF 409}

ar1646v2CllRFResetModuleTable OBJECT-TYPE
   SYNTAX      SEQUENCE OF Ar1646v2CllRFResetModuleEntry
   MAX-ACCESS  not-accessible
   STATUS      current
   DESCRIPTION
      "reset module"
   ::= {ar1646v2CllRFResetModule 1}

ar1646v2CllRFResetModuleEntry OBJECT-TYPE
   SYNTAX      Ar1646v2CllRFResetModuleEntry
   MAX-ACCESS  not-accessible
   STATUS      current
   DESCRIPTION
      ""
   INDEX      { ar1646v2CllRFResetModuleGlobalIx }
   ::= {ar1646v2CllRFResetModuleTable 1}

Ar1646v2CllRFResetModuleEntry ::=
   SEQUENCE
      {
      ar1646v2CllRFResetModuleGlobalIx
         GlobalIndex,
      ar1646v2CllRFResetModuleValue
         Integer32
      }

ar1646v2CllRFResetModuleGlobalIx OBJECT-TYPE
   SYNTAX      GlobalIndex
   MAX-ACCESS  not-accessible
   STATUS      current
   DESCRIPTION
      "The value of the tlsCntTreeGlobalIndex of the MANAGED OBJECT."
   ::= {ar1646v2CllRFResetModuleEntry 10}

ar1646v2CllRFResetModuleValue OBJECT-TYPE
   SYNTAX      Integer32
   MAX-ACCESS  read-write
   STATUS      current
   DESCRIPTION
      "Path: cellular.actions.resetModule"
   ::= {ar1646v2CllRFResetModuleEntry 2147483648}


ar1646v2CllRFUpgradeFirmware OBJECT IDENTIFIER ::= {ar1646v2CllRF 408}

ar1646v2CllRFUpgradeFirmwareTable OBJECT-TYPE
   SYNTAX      SEQUENCE OF Ar1646v2CllRFUpgradeFirmwareEntry
   MAX-ACCESS  not-accessible
   STATUS      current
   DESCRIPTION
      "Sierra Wireless Modem - upgrade firmware"
   ::= {ar1646v2CllRFUpgradeFirmware 1}

ar1646v2CllRFUpgradeFirmwareEntry OBJECT-TYPE
   SYNTAX      Ar1646v2CllRFUpgradeFirmwareEntry
   MAX-ACCESS  not-accessible
   STATUS      current
   DESCRIPTION
      ""
   INDEX      { ar1646v2CllRFUpgradeFirmwareGlobalIx }
   ::= {ar1646v2CllRFUpgradeFirmwareTable 1}

Ar1646v2CllRFUpgradeFirmwareEntry ::=
   SEQUENCE
      {
      ar1646v2CllRFUpgradeFirmwareGlobalIx
         GlobalIndex,
      ar1646v2CllRFUpgradeFirmwareValue
         Integer32
      }

ar1646v2CllRFUpgradeFirmwareGlobalIx OBJECT-TYPE
   SYNTAX      GlobalIndex
   MAX-ACCESS  not-accessible
   STATUS      current
   DESCRIPTION
      "The value of the tlsCntTreeGlobalIndex of the MANAGED OBJECT."
   ::= {ar1646v2CllRFUpgradeFirmwareEntry 10}

ar1646v2CllRFUpgradeFirmwareValue OBJECT-TYPE
   SYNTAX      Integer32
   MAX-ACCESS  read-write
   STATUS      current
   DESCRIPTION
      "Path: cellular.actions.upgradeFirmware"
   ::= {ar1646v2CllRFUpgradeFirmwareEntry 2147483648}


ar1646v2CllRFFwFilename OBJECT IDENTIFIER ::= {ar1646v2CllRF 418}

ar1646v2CllRFFwFilenameTable OBJECT-TYPE
   SYNTAX      SEQUENCE OF Ar1646v2CllRFFwFilenameEntry
   MAX-ACCESS  not-accessible
   STATUS      current
   DESCRIPTION
      "Sierra Wireless Modem - upgrade firmware: filename"
   ::= {ar1646v2CllRFFwFilename 1}

ar1646v2CllRFFwFilenameEntry OBJECT-TYPE
   SYNTAX      Ar1646v2CllRFFwFilenameEntry
   MAX-ACCESS  not-accessible
   STATUS      current
   DESCRIPTION
      ""
   INDEX      { ar1646v2CllRFFwFilenameGlobalIx }
   ::= {ar1646v2CllRFFwFilenameTable 1}

Ar1646v2CllRFFwFilenameEntry ::=
   SEQUENCE
      {
      ar1646v2CllRFFwFilenameGlobalIx
         GlobalIndex,
      ar1646v2CllRFFwFilenameValue
         DisplayString
      }

ar1646v2CllRFFwFilenameGlobalIx OBJECT-TYPE
   SYNTAX      GlobalIndex
   MAX-ACCESS  not-accessible
   STATUS      current
   DESCRIPTION
      "The value of the tlsCntTreeGlobalIndex of the MANAGED OBJECT."
   ::= {ar1646v2CllRFFwFilenameEntry 10}

ar1646v2CllRFFwFilenameValue OBJECT-TYPE
   SYNTAX      DisplayString
   MAX-ACCESS  read-write
   STATUS      current
   DESCRIPTION
      "Path: cellular.actions.fwFilename"
   ::= {ar1646v2CllRFFwFilenameEntry 2147483648}



END
