OneAccess-R1645v2-1423-Bali DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Bali OBJECT IDENTIFIER ::= {r1645Rootv2 1423}

r1645v2BaliMOProp OBJECT-TYPE
   SYNTAX      SEQUENCE OF R1645v2BaliMOPropEntry
   MAX-ACCESS  not-accessible
   STATUS      current
   DESCRIPTION
      ""
   ::= {r1645v2Bali 1}

r1645v2BaliMOPropEntry OBJECT-TYPE
   SYNTAX      R1645v2BaliMOPropEntry
   MAX-ACCESS  not-accessible
   STATUS      current
   DESCRIPTION
      ""
   INDEX      { r1645v2BaliMOPropGlobalIx }
   ::= {r1645v2BaliMOProp 1}

R1645v2BaliMOPropEntry ::=
   SEQUENCE
      {
      r1645v2BaliMOPropPath
         ContainmentPath,
      r1645v2BaliMOPropRev
         ObjectRevision,
      r1645v2BaliMOPropGlobalIx
         GlobalIndex
      }

r1645v2BaliMOPropPath OBJECT-TYPE
   SYNTAX      ContainmentPath
   MAX-ACCESS  read-only
   STATUS      current
   DESCRIPTION
      "Textual description of the containment tree from the instance of
       the root object down to the instance of the current object."
   ::= {r1645v2BaliMOPropEntry 3}

r1645v2BaliMOPropRev OBJECT-TYPE
   SYNTAX      ObjectRevision
   MAX-ACCESS  read-only
   STATUS      current
   DESCRIPTION
      "This value corresponds with the revision of the MANAGED OBJECT."
   ::= {r1645v2BaliMOPropEntry 4}

r1645v2BaliMOPropGlobalIx OBJECT-TYPE
   SYNTAX      GlobalIndex
   MAX-ACCESS  read-only
   STATUS      current
   DESCRIPTION
      "The value of the tlsCntTreeGlobalIndex of the MANAGED OBJECT."
   ::= {r1645v2BaliMOPropEntry 10}



er1645v2Bali OBJECT IDENTIFIER ::= {r1645v2Bali 11}


er1645v2BaliSnmpIndexOffset OBJECT IDENTIFIER ::= {er1645v2Bali 268}

er1645v2BaliSnmpIndexOffsetTable OBJECT-TYPE
   SYNTAX      SEQUENCE OF Er1645v2BaliSnmpIndexOffsetEntry
   MAX-ACCESS  not-accessible
   STATUS      current
   DESCRIPTION
      "Preferred offset in the range of SNMP indices for this SWinst, 0 means automatic"
   ::= {er1645v2BaliSnmpIndexOffset 1}

er1645v2BaliSnmpIndexOffsetEntry OBJECT-TYPE
   SYNTAX      Er1645v2BaliSnmpIndexOffsetEntry
   MAX-ACCESS  not-accessible
   STATUS      current
   DESCRIPTION
      ""
   INDEX      { er1645v2BaliSnmpIndexOffsetGlobalIx }
   ::= {er1645v2BaliSnmpIndexOffsetTable 1}

Er1645v2BaliSnmpIndexOffsetEntry ::=
   SEQUENCE
      {
      er1645v2BaliSnmpIndexOffsetGlobalIx
         GlobalIndex,
      er1645v2BaliSnmpIndexOffsetValue
         Integer32
      }

er1645v2BaliSnmpIndexOffsetGlobalIx OBJECT-TYPE
   SYNTAX      GlobalIndex
   MAX-ACCESS  not-accessible
   STATUS      current
   DESCRIPTION
      "The value of the tlsCntTreeGlobalIndex of the MANAGED OBJECT."
   ::= {er1645v2BaliSnmpIndexOffsetEntry 10}

er1645v2BaliSnmpIndexOffsetValue OBJECT-TYPE
   SYNTAX      Integer32
   MAX-ACCESS  read-write
   STATUS      current
   DESCRIPTION
      "Path: accessList.editConf.snmpIndexOffset"
   ::= {er1645v2BaliSnmpIndexOffsetEntry 2147483648}


er1645v2BaliRemark OBJECT IDENTIFIER ::= {er1645v2Bali 69}

er1645v2BaliRemarkTable OBJECT-TYPE
   SYNTAX      SEQUENCE OF Er1645v2BaliRemarkEntry
   MAX-ACCESS  not-accessible
   STATUS      current
   DESCRIPTION
      ""
   ::= {er1645v2BaliRemark 1}

er1645v2BaliRemarkEntry OBJECT-TYPE
   SYNTAX      Er1645v2BaliRemarkEntry
   MAX-ACCESS  not-accessible
   STATUS      current
   DESCRIPTION
      ""
   INDEX      { er1645v2BaliRemarkGlobalIx }
   ::= {er1645v2BaliRemarkTable 1}

Er1645v2BaliRemarkEntry ::=
   SEQUENCE
      {
      er1645v2BaliRemarkGlobalIx
         GlobalIndex,
      er1645v2BaliRemarkValue
         DisplayString
      }

er1645v2BaliRemarkGlobalIx OBJECT-TYPE
   SYNTAX      GlobalIndex
   MAX-ACCESS  not-accessible
   STATUS      current
   DESCRIPTION
      "The value of the tlsCntTreeGlobalIndex of the MANAGED OBJECT."
   ::= {er1645v2BaliRemarkEntry 10}

er1645v2BaliRemarkValue OBJECT-TYPE
   SYNTAX      DisplayString
   MAX-ACCESS  read-write
   STATUS      current
   DESCRIPTION
      "Path: accessList.editConf.remark"
   ::= {er1645v2BaliRemarkEntry 2147483648}


er1645v2BaliMacAddress OBJECT IDENTIFIER ::= {er1645v2Bali 2}

er1645v2BaliMacAddressSSCTable OBJECT-TYPE
   SYNTAX      SEQUENCE OF Er1645v2BaliMacAddressEntry
   MAX-ACCESS  not-accessible
   STATUS      current
   DESCRIPTION
      "MAC addresses to deny access"
   ::= {er1645v2BaliMacAddress 1}

er1645v2BaliMacAddressEntry OBJECT-TYPE
   SYNTAX      Er1645v2BaliMacAddressEntry
   MAX-ACCESS  not-accessible
   STATUS      current
   DESCRIPTION
      ""
   INDEX      { er1645v2BaliMacAddressGlobalIx,
                er1645v2BaliMacAddressTableIx }
   ::= {er1645v2BaliMacAddressSSCTable 1}

Er1645v2BaliMacAddressEntry ::=
   SEQUENCE
      {
      er1645v2BaliMacAddressActions
         VariableLengthTableActions,
      er1645v2BaliMacAddressGlobalIx
         GlobalIndex,
      er1645v2BaliMacAddressTableIx
         TableIndex,
      er1645v2BaliMacAddressMacAddress
         OCTET STRING
      }

er1645v2BaliMacAddressActions OBJECT-TYPE
   SYNTAX      VariableLengthTableActions
   MAX-ACCESS  read-write
   STATUS      current
   DESCRIPTION
      "By way of this field, some manipulations
       on this table may be performed."
   ::= {er1645v2BaliMacAddressEntry 2}

er1645v2BaliMacAddressGlobalIx OBJECT-TYPE
   SYNTAX      GlobalIndex
   MAX-ACCESS  not-accessible
   STATUS      current
   DESCRIPTION
      "The value of the tlsCntTreeGlobalIndex of the MANAGED OBJECT."
   ::= {er1645v2BaliMacAddressEntry 10}

er1645v2BaliMacAddressTableIx OBJECT-TYPE
   SYNTAX      TableIndex
   MAX-ACCESS  not-accessible
   STATUS      current
   DESCRIPTION
      ""
   ::= {er1645v2BaliMacAddressEntry 11}

er1645v2BaliMacAddressMacAddress OBJECT-TYPE
   SYNTAX      OCTET STRING
   MAX-ACCESS  read-write
   STATUS      current
   DESCRIPTION
      "Path: accessList.editConf.macAddress.macAddress

       MAC address."
   ::= {er1645v2BaliMacAddressEntry 16777216}


er1645v2BaliAdvancedFilter OBJECT IDENTIFIER ::= {er1645v2Bali 4}

er1645v2BaliAdvancedFilterSSCTable OBJECT-TYPE
   SYNTAX      SEQUENCE OF Er1645v2BaliAdvancedFilterEntry
   MAX-ACCESS  not-accessible
   STATUS      current
   DESCRIPTION
      "advanced filtering on Layer 2"
   ::= {er1645v2BaliAdvancedFilter 1}

er1645v2BaliAdvancedFilterEntry OBJECT-TYPE
   SYNTAX      Er1645v2BaliAdvancedFilterEntry
   MAX-ACCESS  not-accessible
   STATUS      current
   DESCRIPTION
      ""
   INDEX      { er1645v2BaliAdvancedFilterGlobalIx,
                er1645v2BaliAdvancedFilterTableIx }
   ::= {er1645v2BaliAdvancedFilterSSCTable 1}

Er1645v2BaliAdvancedFilterEntry ::=
   SEQUENCE
      {
      er1645v2BaliAdvancedFilterActions
         VariableLengthTableActions,
      er1645v2BaliAdvancedFilterGlobalIx
         GlobalIndex,
      er1645v2BaliAdvancedFilterTableIx
         TableIndex,
      er1645v2BaliAdvancedFilterName
         DisplayString,
      er1645v2BaliAdvancedFilterRemark
         DisplayString,
      er1645v2BaliAdvancedFilterSms
         OCTET STRING,
      er1645v2BaliAdvancedFilterSme
         OCTET STRING,
      er1645v2BaliAdvancedFilterDms
         OCTET STRING,
      er1645v2BaliAdvancedFilterDme
         OCTET STRING,
      er1645v2BaliAdvancedFilterVlanDepth
         Integer32,
      er1645v2BaliAdvancedFilterTpid
         INTEGER,
      er1645v2BaliAdvancedFilterVlan
         INTEGER,
      er1645v2BaliAdvancedFilterEndVlan
         Integer32,
      er1645v2BaliAdvancedFilterPriority
         INTEGER,
      er1645v2BaliAdvancedFilterDei
         INTEGER,
      er1645v2BaliAdvancedFilterPro
         INTEGER,
      er1645v2BaliAdvancedFilterAct
         INTEGER,
      er1645v2BaliAdvancedFilterAdvNone
         INTEGER,
      er1645v2BaliAdvancedFilterAdvLimitTcpSynMode
         INTEGER,
      er1645v2BaliAdvancedFilterAdvLimitTcpSynRate
         Integer32,
      er1645v2BaliAdvancedFilterAdvJumpOver
         Integer32,
      er1645v2BaliAdvancedFilterAdvJumpTo
         DisplayString,
      er1645v2BaliAdvancedFilterAdvMSetQueueQueue
         INTEGER,
      er1645v2BaliAdvancedFilterAdvMSetQueueDropLevel
         INTEGER,
      er1645v2BaliAdvancedFilterAdvMSetQueueDeFlag
         INTEGER,
      er1645v2BaliAdvancedFilterAdvMSetTosAndCosTos
         INTEGER,
      er1645v2BaliAdvancedFilterAdvMSetTosAndCosCos
         INTEGER,
      er1645v2BaliAdvancedFilterAdvMSetTosAndCosDei
         INTEGER,
      er1645v2BaliAdvancedFilterAdvMSetTosAndCosQueue
         INTEGER,
      er1645v2BaliAdvancedFilterAdvMSetTosAndCosDropLevel
         INTEGER,
      er1645v2BaliAdvancedFilterAdvMSetTosAndCosDeFlag
         INTEGER,
      er1645v2BaliAdvancedFilterAdvMMapCosToQueueP0Queue
         INTEGER,
      er1645v2BaliAdvancedFilterAdvMMapCosToQueueP0DropLevel
         INTEGER,
      er1645v2BaliAdvancedFilterAdvMMapCosToQueueP0DeFlag
         INTEGER,
      er1645v2BaliAdvancedFilterAdvMMapCosToQueueP0Cos
         INTEGER,
      er1645v2BaliAdvancedFilterAdvMMapCosToQueueP0Dei
         INTEGER,
      er1645v2BaliAdvancedFilterAdvMMapCosToQueueP1Queue
         INTEGER,
      er1645v2BaliAdvancedFilterAdvMMapCosToQueueP1DropLevel
         INTEGER,
      er1645v2BaliAdvancedFilterAdvMMapCosToQueueP1DeFlag
         INTEGER,
      er1645v2BaliAdvancedFilterAdvMMapCosToQueueP1Cos
         INTEGER,
      er1645v2BaliAdvancedFilterAdvMMapCosToQueueP1Dei
         INTEGER,
      er1645v2BaliAdvancedFilterAdvMMapCosToQueueP2Queue
         INTEGER,
      er1645v2BaliAdvancedFilterAdvMMapCosToQueueP2DropLevel
         INTEGER,
      er1645v2BaliAdvancedFilterAdvMMapCosToQueueP2DeFlag
         INTEGER,
      er1645v2BaliAdvancedFilterAdvMMapCosToQueueP2Cos
         INTEGER,
      er1645v2BaliAdvancedFilterAdvMMapCosToQueueP2Dei
         INTEGER,
      er1645v2BaliAdvancedFilterAdvMMapCosToQueueP3Queue
         INTEGER,
      er1645v2BaliAdvancedFilterAdvMMapCosToQueueP3DropLevel
         INTEGER,
      er1645v2BaliAdvancedFilterAdvMMapCosToQueueP3DeFlag
         INTEGER,
      er1645v2BaliAdvancedFilterAdvMMapCosToQueueP3Cos
         INTEGER,
      er1645v2BaliAdvancedFilterAdvMMapCosToQueueP3Dei
         INTEGER,
      er1645v2BaliAdvancedFilterAdvMMapCosToQueueP4Queue
         INTEGER,
      er1645v2BaliAdvancedFilterAdvMMapCosToQueueP4DropLevel
         INTEGER,
      er1645v2BaliAdvancedFilterAdvMMapCosToQueueP4DeFlag
         INTEGER,
      er1645v2BaliAdvancedFilterAdvMMapCosToQueueP4Cos
         INTEGER,
      er1645v2BaliAdvancedFilterAdvMMapCosToQueueP4Dei
         INTEGER,
      er1645v2BaliAdvancedFilterAdvMMapCosToQueueP5Queue
         INTEGER,
      er1645v2BaliAdvancedFilterAdvMMapCosToQueueP5DropLevel
         INTEGER,
      er1645v2BaliAdvancedFilterAdvMMapCosToQueueP5DeFlag
         INTEGER,
      er1645v2BaliAdvancedFilterAdvMMapCosToQueueP5Cos
         INTEGER,
      er1645v2BaliAdvancedFilterAdvMMapCosToQueueP5Dei
         INTEGER,
      er1645v2BaliAdvancedFilterAdvMMapCosToQueueP6Queue
         INTEGER,
      er1645v2BaliAdvancedFilterAdvMMapCosToQueueP6DropLevel
         INTEGER,
      er1645v2BaliAdvancedFilterAdvMMapCosToQueueP6DeFlag
         INTEGER,
      er1645v2BaliAdvancedFilterAdvMMapCosToQueueP6Cos
         INTEGER,
      er1645v2BaliAdvancedFilterAdvMMapCosToQueueP6Dei
         INTEGER,
      er1645v2BaliAdvancedFilterAdvMMapCosToQueueP7Queue
         INTEGER,
      er1645v2BaliAdvancedFilterAdvMMapCosToQueueP7DropLevel
         INTEGER,
      er1645v2BaliAdvancedFilterAdvMMapCosToQueueP7DeFlag
         INTEGER,
      er1645v2BaliAdvancedFilterAdvMMapCosToQueueP7Cos
         INTEGER,
      er1645v2BaliAdvancedFilterAdvMMapCosToQueueP7Dei
         INTEGER,
      er1645v2BaliAdvancedFilterAdvMMapCosToQueueUntaggedQueue
         INTEGER,
      er1645v2BaliAdvancedFilterAdvMMapCosToQueueUntaggedDropLevel
         INTEGER,
      er1645v2BaliAdvancedFilterAdvMMapCosToQueueUntaggedDeFlag
         INTEGER,
      er1645v2BaliAdvancedFilterAdvMMapDeiToQueueDeiClearQueue
         INTEGER,
      er1645v2BaliAdvancedFilterAdvMMapDeiToQueueDeiClearDropLevel
         INTEGER,
      er1645v2BaliAdvancedFilterAdvMMapDeiToQueueDeiClearDeFlag
         INTEGER,
      er1645v2BaliAdvancedFilterAdvMMapDeiToQueueDeiClearCos
         INTEGER,
      er1645v2BaliAdvancedFilterAdvMMapDeiToQueueDeiClearDei
         INTEGER,
      er1645v2BaliAdvancedFilterAdvMMapDeiToQueueDeiSetQueue
         INTEGER,
      er1645v2BaliAdvancedFilterAdvMMapDeiToQueueDeiSetDropLevel
         INTEGER,
      er1645v2BaliAdvancedFilterAdvMMapDeiToQueueDeiSetDeFlag
         INTEGER,
      er1645v2BaliAdvancedFilterAdvMMapDeiToQueueDeiSetCos
         INTEGER,
      er1645v2BaliAdvancedFilterAdvMMapDeiToQueueDeiSetDei
         INTEGER,
      er1645v2BaliAdvancedFilterAdvMMapDeiToQueueUntaggedQueue
         INTEGER,
      er1645v2BaliAdvancedFilterAdvMMapDeiToQueueUntaggedDropLevel
         INTEGER,
      er1645v2BaliAdvancedFilterAdvMMapDeiToQueueUntaggedDeFlag
         INTEGER,
      er1645v2BaliAdvancedFilterAdvIpTrafficPolicy
         DisplayString,
      er1645v2BaliAdvancedFilterAdvMTaSetQueueQueue
         INTEGER,
      er1645v2BaliAdvancedFilterAdvMTaSetQueueDropLevel
         INTEGER,
      er1645v2BaliAdvancedFilterAdvMTaSetQueueDeFlag
         INTEGER,
      er1645v2BaliAdvancedFilterAdvMTaSetTosAndCosTos
         INTEGER,
      er1645v2BaliAdvancedFilterAdvMTaSetTosAndCosCos
         INTEGER,
      er1645v2BaliAdvancedFilterAdvMTaSetTosAndCosDei
         INTEGER,
      er1645v2BaliAdvancedFilterAdvMTaSetTosAndCosQueue
         INTEGER,
      er1645v2BaliAdvancedFilterAdvMTaSetTosAndCosDropLevel
         INTEGER,
      er1645v2BaliAdvancedFilterAdvMTaSetTosAndCosDeFlag
         INTEGER,
      er1645v2BaliAdvancedFilterAdvMTaMapCosToQueueP0Queue
         INTEGER,
      er1645v2BaliAdvancedFilterAdvMTaMapCosToQueueP0DropLevel
         INTEGER,
      er1645v2BaliAdvancedFilterAdvMTaMapCosToQueueP0DeFlag
         INTEGER,
      er1645v2BaliAdvancedFilterAdvMTaMapCosToQueueP0Cos
         INTEGER,
      er1645v2BaliAdvancedFilterAdvMTaMapCosToQueueP0Dei
         INTEGER,
      er1645v2BaliAdvancedFilterAdvMTaMapCosToQueueP1Queue
         INTEGER,
      er1645v2BaliAdvancedFilterAdvMTaMapCosToQueueP1DropLevel
         INTEGER,
      er1645v2BaliAdvancedFilterAdvMTaMapCosToQueueP1DeFlag
         INTEGER,
      er1645v2BaliAdvancedFilterAdvMTaMapCosToQueueP1Cos
         INTEGER,
      er1645v2BaliAdvancedFilterAdvMTaMapCosToQueueP1Dei
         INTEGER,
      er1645v2BaliAdvancedFilterAdvMTaMapCosToQueueP2Queue
         INTEGER,
      er1645v2BaliAdvancedFilterAdvMTaMapCosToQueueP2DropLevel
         INTEGER,
      er1645v2BaliAdvancedFilterAdvMTaMapCosToQueueP2DeFlag
         INTEGER,
      er1645v2BaliAdvancedFilterAdvMTaMapCosToQueueP2Cos
         INTEGER,
      er1645v2BaliAdvancedFilterAdvMTaMapCosToQueueP2Dei
         INTEGER,
      er1645v2BaliAdvancedFilterAdvMTaMapCosToQueueP3Queue
         INTEGER,
      er1645v2BaliAdvancedFilterAdvMTaMapCosToQueueP3DropLevel
         INTEGER,
      er1645v2BaliAdvancedFilterAdvMTaMapCosToQueueP3DeFlag
         INTEGER,
      er1645v2BaliAdvancedFilterAdvMTaMapCosToQueueP3Cos
         INTEGER,
      er1645v2BaliAdvancedFilterAdvMTaMapCosToQueueP3Dei
         INTEGER,
      er1645v2BaliAdvancedFilterAdvMTaMapCosToQueueP4Queue
         INTEGER,
      er1645v2BaliAdvancedFilterAdvMTaMapCosToQueueP4DropLevel
         INTEGER,
      er1645v2BaliAdvancedFilterAdvMTaMapCosToQueueP4DeFlag
         INTEGER,
      er1645v2BaliAdvancedFilterAdvMTaMapCosToQueueP4Cos
         INTEGER,
      er1645v2BaliAdvancedFilterAdvMTaMapCosToQueueP4Dei
         INTEGER,
      er1645v2BaliAdvancedFilterAdvMTaMapCosToQueueP5Queue
         INTEGER,
      er1645v2BaliAdvancedFilterAdvMTaMapCosToQueueP5DropLevel
         INTEGER,
      er1645v2BaliAdvancedFilterAdvMTaMapCosToQueueP5DeFlag
         INTEGER,
      er1645v2BaliAdvancedFilterAdvMTaMapCosToQueueP5Cos
         INTEGER,
      er1645v2BaliAdvancedFilterAdvMTaMapCosToQueueP5Dei
         INTEGER,
      er1645v2BaliAdvancedFilterAdvMTaMapCosToQueueP6Queue
         INTEGER,
      er1645v2BaliAdvancedFilterAdvMTaMapCosToQueueP6DropLevel
         INTEGER,
      er1645v2BaliAdvancedFilterAdvMTaMapCosToQueueP6DeFlag
         INTEGER,
      er1645v2BaliAdvancedFilterAdvMTaMapCosToQueueP6Cos
         INTEGER,
      er1645v2BaliAdvancedFilterAdvMTaMapCosToQueueP6Dei
         INTEGER,
      er1645v2BaliAdvancedFilterAdvMTaMapCosToQueueP7Queue
         INTEGER,
      er1645v2BaliAdvancedFilterAdvMTaMapCosToQueueP7DropLevel
         INTEGER,
      er1645v2BaliAdvancedFilterAdvMTaMapCosToQueueP7DeFlag
         INTEGER,
      er1645v2BaliAdvancedFilterAdvMTaMapCosToQueueP7Cos
         INTEGER,
      er1645v2BaliAdvancedFilterAdvMTaMapCosToQueueP7Dei
         INTEGER,
      er1645v2BaliAdvancedFilterAdvMTaMapCosToQueueUntaggedQueue
         INTEGER,
      er1645v2BaliAdvancedFilterAdvMTaMapCosToQueueUntaggedDropLevel
         INTEGER,
      er1645v2BaliAdvancedFilterAdvMTaMapCosToQueueUntaggedDeFlag
         INTEGER,
      er1645v2BaliAdvancedFilterAdvMTaMapDeiToQueueDeiClearQueue
         INTEGER,
      er1645v2BaliAdvancedFilterAdvMTaMapDeiToQueueDeiClearDropLevel
         INTEGER,
      er1645v2BaliAdvancedFilterAdvMTaMapDeiToQueueDeiClearDeFlag
         INTEGER,
      er1645v2BaliAdvancedFilterAdvMTaMapDeiToQueueDeiClearCos
         INTEGER,
      er1645v2BaliAdvancedFilterAdvMTaMapDeiToQueueDeiClearDei
         INTEGER,
      er1645v2BaliAdvancedFilterAdvMTaMapDeiToQueueDeiSetQueue
         INTEGER,
      er1645v2BaliAdvancedFilterAdvMTaMapDeiToQueueDeiSetDropLevel
         INTEGER,
      er1645v2BaliAdvancedFilterAdvMTaMapDeiToQueueDeiSetDeFlag
         INTEGER,
      er1645v2BaliAdvancedFilterAdvMTaMapDeiToQueueDeiSetCos
         INTEGER,
      er1645v2BaliAdvancedFilterAdvMTaMapDeiToQueueDeiSetDei
         INTEGER,
      er1645v2BaliAdvancedFilterAdvMTaMapDeiToQueueUntaggedQueue
         INTEGER,
      er1645v2BaliAdvancedFilterAdvMTaMapDeiToQueueUntaggedDropLevel
         INTEGER,
      er1645v2BaliAdvancedFilterAdvMTaMapDeiToQueueUntaggedDeFlag
         INTEGER,
      er1645v2BaliAdvancedFilterAdvCapture
         Integer32,
      er1645v2BaliAdvancedFilterLimiterNone
         INTEGER,
      er1645v2BaliAdvancedFilterLimiterName
         DisplayString,
      er1645v2BaliAdvancedFilterLimiterQueueQueue1
         DisplayString,
      er1645v2BaliAdvancedFilterLimiterQueueQueue2
         DisplayString,
      er1645v2BaliAdvancedFilterLimiterQueueQueue3
         DisplayString,
      er1645v2BaliAdvancedFilterLimiterQueueQueue4
         DisplayString,
      er1645v2BaliAdvancedFilterLimiterQueueQueue5
         DisplayString,
      er1645v2BaliAdvancedFilterLimiterQueueLowDelayQueue
         DisplayString,
      er1645v2BaliAdvancedFilterLimiterQueueLowDelay2Queue
         DisplayString,
      er1645v2BaliAdvancedFilterLimiterQueueSystemQueue
         DisplayString
      }

er1645v2BaliAdvancedFilterActions OBJECT-TYPE
   SYNTAX      VariableLengthTableActions
   MAX-ACCESS  read-write
   STATUS      current
   DESCRIPTION
      "By way of this field, some manipulations
       on this table may be performed."
   ::= {er1645v2BaliAdvancedFilterEntry 2}

er1645v2BaliAdvancedFilterGlobalIx OBJECT-TYPE
   SYNTAX      GlobalIndex
   MAX-ACCESS  not-accessible
   STATUS      current
   DESCRIPTION
      "The value of the tlsCntTreeGlobalIndex of the MANAGED OBJECT."
   ::= {er1645v2BaliAdvancedFilterEntry 10}

er1645v2BaliAdvancedFilterTableIx OBJECT-TYPE
   SYNTAX      TableIndex
   MAX-ACCESS  not-accessible
   STATUS      current
   DESCRIPTION
      ""
   ::= {er1645v2BaliAdvancedFilterEntry 11}

er1645v2BaliAdvancedFilterName OBJECT-TYPE
   SYNTAX      DisplayString
   MAX-ACCESS  read-write
   STATUS      current
   DESCRIPTION
      "Path: accessList.editConf.advancedFilter.name"
   ::= {er1645v2BaliAdvancedFilterEntry 218103808}

er1645v2BaliAdvancedFilterRemark OBJECT-TYPE
   SYNTAX      DisplayString
   MAX-ACCESS  read-write
   STATUS      current
   DESCRIPTION
      "Path: accessList.editConf.advancedFilter.remark"
   ::= {er1645v2BaliAdvancedFilterEntry 1157627904}

er1645v2BaliAdvancedFilterSms OBJECT-TYPE
   SYNTAX      OCTET STRING
   MAX-ACCESS  read-write
   STATUS      current
   DESCRIPTION
      "Path: accessList.editConf.advancedFilter.sourceMacStart

       MAC address."
   ::= {er1645v2BaliAdvancedFilterEntry 16777216}

er1645v2BaliAdvancedFilterSme OBJECT-TYPE
   SYNTAX      OCTET STRING
   MAX-ACCESS  read-write
   STATUS      current
   DESCRIPTION
      "Path: accessList.editConf.advancedFilter.sourceMacEnd

       MAC address."
   ::= {er1645v2BaliAdvancedFilterEntry 33554432}

er1645v2BaliAdvancedFilterDms OBJECT-TYPE
   SYNTAX      OCTET STRING
   MAX-ACCESS  read-write
   STATUS      current
   DESCRIPTION
      "Path: accessList.editConf.advancedFilter.destinationMacStart

       MAC address."
   ::= {er1645v2BaliAdvancedFilterEntry 50331648}

er1645v2BaliAdvancedFilterDme OBJECT-TYPE
   SYNTAX      OCTET STRING
   MAX-ACCESS  read-write
   STATUS      current
   DESCRIPTION
      "Path: accessList.editConf.advancedFilter.destinationMacEnd

       MAC address."
   ::= {er1645v2BaliAdvancedFilterEntry 67108864}

er1645v2BaliAdvancedFilterVlanDepth OBJECT-TYPE
   SYNTAX      Integer32
   MAX-ACCESS  read-write
   STATUS      current
   DESCRIPTION
      "Path: accessList.editConf.advancedFilter.vlanDepth"
   ::= {er1645v2BaliAdvancedFilterEntry 234881024}

er1645v2BaliAdvancedFilterTpid OBJECT-TYPE
   SYNTAX      INTEGER
               {
               dot1q (33024),
               dot1ad (34984),
               s0x9100 (37120),
               s0x9200 (37376),
               s0x9300 (37632),
               dot1qOrDot1ad (65536)
               }
   MAX-ACCESS  read-write
   STATUS      current
   DESCRIPTION
      "Path: accessList.editConf.advancedFilter.tpid

       Possibilities:
               dot1q   (33024)
               dot1ad   (34984)
               0x9100   (37120)
               0x9200   (37376)
               0x9300   (37632)
               dot1qOrDot1ad   (65536)"
   ::= {er1645v2BaliAdvancedFilterEntry 268435456}

er1645v2BaliAdvancedFilterVlan OBJECT-TYPE
   SYNTAX      INTEGER
               {
               priorityTagged (0),
               untagged (4096),
               any (4097),
               anyVlan (4098)
               }
   MAX-ACCESS  read-write
   STATUS      current
   DESCRIPTION
      "Path: accessList.editConf.advancedFilter.vlan

       Possibilities:
               priorityTagged   (0)
               untagged   (4096)
               any   (4097)
               anyVlan   (4098)"
   ::= {er1645v2BaliAdvancedFilterEntry 150994944}

er1645v2BaliAdvancedFilterEndVlan OBJECT-TYPE
   SYNTAX      Integer32
   MAX-ACCESS  read-write
   STATUS      current
   DESCRIPTION
      "Path: accessList.editConf.advancedFilter.endVlan"
   ::= {er1645v2BaliAdvancedFilterEntry 251658240}

er1645v2BaliAdvancedFilterPriority OBJECT-TYPE
   SYNTAX      INTEGER
               {
               any (8)
               }
   MAX-ACCESS  read-write
   STATUS      current
   DESCRIPTION
      "Path: accessList.editConf.advancedFilter.priority

       Possibilities:
               any   (8)"
   ::= {er1645v2BaliAdvancedFilterEntry 167772160}

er1645v2BaliAdvancedFilterDei OBJECT-TYPE
   SYNTAX      INTEGER
               {
               clear (0),
               set (1),
               any (2)
               }
   MAX-ACCESS  read-write
   STATUS      current
   DESCRIPTION
      "Path: accessList.editConf.advancedFilter.dei

       Possibilities:
               clear   (0)
               set   (1)
               any   (2)"
   ::= {er1645v2BaliAdvancedFilterEntry 285212672}

er1645v2BaliAdvancedFilterPro OBJECT-TYPE
   SYNTAX      INTEGER
               {
               any (65536),
               ip (2048),
               arp (2054),
               rarp (32821),
               vlanTagged (33024),
               ipV6 (34525),
               slowProtocols (34825),
               mplsUnicast (34887),
               mplsMulticast (34888),
               pppoeControl (34915),
               pppoeData (34916),
               svlan802d1ad (34984),
               llcSnap (65537)
               }
   MAX-ACCESS  read-write
   STATUS      current
   DESCRIPTION
      "Path: accessList.editConf.advancedFilter.protocol

       Possibilities:
               any   (65536)
               ip   (2048)
               arp   (2054)
               rarp   (32821)
               vlanTagged   (33024)
               ipV6   (34525)
               slowProtocols   (34825)
               mplsUnicast   (34887)
               mplsMulticast   (34888)
               pppoeControl   (34915)
               pppoeData   (34916)
               svlan802.1ad   (34984)
               llcSnap   (65537)"
   ::= {er1645v2BaliAdvancedFilterEntry 83886080}

er1645v2BaliAdvancedFilterAct OBJECT-TYPE
   SYNTAX      INTEGER
               {
               deny (0),
               permit (1),
               continue (2)
               }
   MAX-ACCESS  read-write
   STATUS      current
   DESCRIPTION
      "Path: accessList.editConf.advancedFilter.action

       Possibilities:
               deny   (0)
               permit   (1)
               continue   (2)"
   ::= {er1645v2BaliAdvancedFilterEntry 100663296}

er1645v2BaliAdvancedFilterAdvNone OBJECT-TYPE
   SYNTAX      INTEGER
               {
               none (0)
               }
   MAX-ACCESS  read-write
   STATUS      current
   DESCRIPTION
      "Path: accessList.editConf.advancedFilter.advanced.none

       Possibilities:
               none   (0)"
   ::= {er1645v2BaliAdvancedFilterEntry 134283264}

er1645v2BaliAdvancedFilterAdvLimitTcpSynMode OBJECT-TYPE
   SYNTAX      INTEGER
               {
               global (1),
               perMac (2)
               }
   MAX-ACCESS  read-write
   STATUS      current
   DESCRIPTION
      "Path: accessList.editConf.advancedFilter.advanced.limitTcpSyn.mode

       Possibilities:
               global   (1)
               perMac   (2)"
   ::= {er1645v2BaliAdvancedFilterEntry 134349056}

er1645v2BaliAdvancedFilterAdvLimitTcpSynRate OBJECT-TYPE
   SYNTAX      Integer32
   UNITS       "SynPerMinute"
   MAX-ACCESS  read-write
   STATUS      current
   DESCRIPTION
      "Path: accessList.editConf.advancedFilter.advanced.limitTcpSyn.rate

       unit name = SynPerMinute"
   ::= {er1645v2BaliAdvancedFilterEntry 134349312}

er1645v2BaliAdvancedFilterAdvJumpOver OBJECT-TYPE
   SYNTAX      Integer32
   MAX-ACCESS  read-write
   STATUS      current
   DESCRIPTION
      "Path: accessList.editConf.advancedFilter.advanced.jumpOver"
   ::= {er1645v2BaliAdvancedFilterEntry 134414336}

er1645v2BaliAdvancedFilterAdvJumpTo OBJECT-TYPE
   SYNTAX      DisplayString
   MAX-ACCESS  read-write
   STATUS      current
   DESCRIPTION
      "Path: accessList.editConf.advancedFilter.advanced.jumpTo"
   ::= {er1645v2BaliAdvancedFilterEntry 134545408}

er1645v2BaliAdvancedFilterAdvMSetQueueQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: accessList.editConf.advancedFilter.advanced.mark.setQueue.queue

       Possibilities:
               queue1   (0)
               queue2   (1)
               queue3   (2)
               queue4   (3)
               queue5   (4)
               lowDelayQueue   (5)
               lowDelay2Queue   (6)
               systemQueue   (7)"
   ::= {er1645v2BaliAdvancedFilterEntry 134488192}

er1645v2BaliAdvancedFilterAdvMSetQueueDropLevel OBJECT-TYPE
   SYNTAX      INTEGER
               {
               dropOnQueue (0)
               }
   MAX-ACCESS  read-write
   STATUS      current
   DESCRIPTION
      "Path: accessList.editConf.advancedFilter.advanced.mark.setQueue.dropLevel

       Possibilities:
               dropOnQueue   (0)"
   ::= {er1645v2BaliAdvancedFilterEntry 134488224}

er1645v2BaliAdvancedFilterAdvMSetQueueDeFlag OBJECT-TYPE
   SYNTAX      INTEGER
               {
               unchanged (255),
               clear (0),
               set (1)
               }
   MAX-ACCESS  read-write
   STATUS      current
   DESCRIPTION
      "Path: accessList.editConf.advancedFilter.advanced.mark.setQueue.deFlag

       Possibilities:
               unchanged   (255)
               clear   (0)
               set   (1)"
   ::= {er1645v2BaliAdvancedFilterEntry 134488288}

er1645v2BaliAdvancedFilterAdvMSetTosAndCosTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: accessList.editConf.advancedFilter.advanced.mark.setTosAndCos.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2BaliAdvancedFilterEntry 134496320}

er1645v2BaliAdvancedFilterAdvMSetTosAndCosCos OBJECT-TYPE
   SYNTAX      INTEGER
               {
               unchanged (8)
               }
   MAX-ACCESS  read-write
   STATUS      current
   DESCRIPTION
      "Path: accessList.editConf.advancedFilter.advanced.mark.setTosAndCos.cos

       Possibilities:
               unchanged   (8)"
   ::= {er1645v2BaliAdvancedFilterEntry 134496352}

er1645v2BaliAdvancedFilterAdvMSetTosAndCosDei OBJECT-TYPE
   SYNTAX      INTEGER
               {
               unchanged (255),
               clear (0),
               set (1)
               }
   MAX-ACCESS  read-write
   STATUS      current
   DESCRIPTION
      "Path: accessList.editConf.advancedFilter.advanced.mark.setTosAndCos.dei

       Possibilities:
               unchanged   (255)
               clear   (0)
               set   (1)"
   ::= {er1645v2BaliAdvancedFilterEntry 134496448}

er1645v2BaliAdvancedFilterAdvMSetTosAndCosQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: accessList.editConf.advancedFilter.advanced.mark.setTosAndCos.queue

       Possibilities:
               queue1   (0)
               queue2   (1)
               queue3   (2)
               queue4   (3)
               queue5   (4)
               lowDelayQueue   (5)
               lowDelay2Queue   (6)
               systemQueue   (7)"
   ::= {er1645v2BaliAdvancedFilterEntry 134496384}

er1645v2BaliAdvancedFilterAdvMSetTosAndCosDropLevel OBJECT-TYPE
   SYNTAX      INTEGER
               {
               dropOnQueue (0)
               }
   MAX-ACCESS  read-write
   STATUS      current
   DESCRIPTION
      "Path: accessList.editConf.advancedFilter.advanced.mark.setTosAndCos.dropLevel

       Possibilities:
               dropOnQueue   (0)"
   ::= {er1645v2BaliAdvancedFilterEntry 134496416}

er1645v2BaliAdvancedFilterAdvMSetTosAndCosDeFlag OBJECT-TYPE
   SYNTAX      INTEGER
               {
               unchanged (255),
               clear (0),
               set (1)
               }
   MAX-ACCESS  read-write
   STATUS      current
   DESCRIPTION
      "Path: accessList.editConf.advancedFilter.advanced.mark.setTosAndCos.deFlag

       Possibilities:
               unchanged   (255)
               clear   (0)
               set   (1)"
   ::= {er1645v2BaliAdvancedFilterEntry 134496480}

er1645v2BaliAdvancedFilterAdvMMapCosToQueueP0Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p0.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134513160}

er1645v2BaliAdvancedFilterAdvMMapCosToQueueP0DropLevel OBJECT-TYPE
   SYNTAX      INTEGER
               {
               dropOnQueue (0)
               }
   MAX-ACCESS  read-write
   STATUS      current
   DESCRIPTION
      "Path: accessList.editConf.advancedFilter.advanced.mark.mapCosToQueue.p0.dropLevel

       Possibilities:
               dropOnQueue   (0)"
   ::= {er1645v2BaliAdvancedFilterEntry 134513162}

er1645v2BaliAdvancedFilterAdvMMapCosToQueueP0DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p0.deFlag

       Possibilities:
               unchanged   (255)
               clear   (0)
               set   (1)"
   ::= {er1645v2BaliAdvancedFilterEntry 134513166}

er1645v2BaliAdvancedFilterAdvMMapCosToQueueP0Cos OBJECT-TYPE
   SYNTAX      INTEGER
               {
               unchanged (8)
               }
   MAX-ACCESS  read-write
   STATUS      current
   DESCRIPTION
      "Path: accessList.editConf.advancedFilter.advanced.mark.mapCosToQueue.p0.cos

       Possibilities:
               unchanged   (8)"
   ::= {er1645v2BaliAdvancedFilterEntry 134513158}

er1645v2BaliAdvancedFilterAdvMMapCosToQueueP0Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p0.dei

       Possibilities:
               unchanged   (255)
               clear   (0)
               set   (1)"
   ::= {er1645v2BaliAdvancedFilterEntry 134513164}

er1645v2BaliAdvancedFilterAdvMMapCosToQueueP1Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p1.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134513672}

er1645v2BaliAdvancedFilterAdvMMapCosToQueueP1DropLevel OBJECT-TYPE
   SYNTAX      INTEGER
               {
               dropOnQueue (0)
               }
   MAX-ACCESS  read-write
   STATUS      current
   DESCRIPTION
      "Path: accessList.editConf.advancedFilter.advanced.mark.mapCosToQueue.p1.dropLevel

       Possibilities:
               dropOnQueue   (0)"
   ::= {er1645v2BaliAdvancedFilterEntry 134513674}

er1645v2BaliAdvancedFilterAdvMMapCosToQueueP1DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p1.deFlag

       Possibilities:
               unchanged   (255)
               clear   (0)
               set   (1)"
   ::= {er1645v2BaliAdvancedFilterEntry 134513678}

er1645v2BaliAdvancedFilterAdvMMapCosToQueueP1Cos OBJECT-TYPE
   SYNTAX      INTEGER
               {
               unchanged (8)
               }
   MAX-ACCESS  read-write
   STATUS      current
   DESCRIPTION
      "Path: accessList.editConf.advancedFilter.advanced.mark.mapCosToQueue.p1.cos

       Possibilities:
               unchanged   (8)"
   ::= {er1645v2BaliAdvancedFilterEntry 134513670}

er1645v2BaliAdvancedFilterAdvMMapCosToQueueP1Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p1.dei

       Possibilities:
               unchanged   (255)
               clear   (0)
               set   (1)"
   ::= {er1645v2BaliAdvancedFilterEntry 134513676}

er1645v2BaliAdvancedFilterAdvMMapCosToQueueP2Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p2.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134514184}

er1645v2BaliAdvancedFilterAdvMMapCosToQueueP2DropLevel OBJECT-TYPE
   SYNTAX      INTEGER
               {
               dropOnQueue (0)
               }
   MAX-ACCESS  read-write
   STATUS      current
   DESCRIPTION
      "Path: accessList.editConf.advancedFilter.advanced.mark.mapCosToQueue.p2.dropLevel

       Possibilities:
               dropOnQueue   (0)"
   ::= {er1645v2BaliAdvancedFilterEntry 134514186}

er1645v2BaliAdvancedFilterAdvMMapCosToQueueP2DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p2.deFlag

       Possibilities:
               unchanged   (255)
               clear   (0)
               set   (1)"
   ::= {er1645v2BaliAdvancedFilterEntry 134514190}

er1645v2BaliAdvancedFilterAdvMMapCosToQueueP2Cos OBJECT-TYPE
   SYNTAX      INTEGER
               {
               unchanged (8)
               }
   MAX-ACCESS  read-write
   STATUS      current
   DESCRIPTION
      "Path: accessList.editConf.advancedFilter.advanced.mark.mapCosToQueue.p2.cos

       Possibilities:
               unchanged   (8)"
   ::= {er1645v2BaliAdvancedFilterEntry 134514182}

er1645v2BaliAdvancedFilterAdvMMapCosToQueueP2Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p2.dei

       Possibilities:
               unchanged   (255)
               clear   (0)
               set   (1)"
   ::= {er1645v2BaliAdvancedFilterEntry 134514188}

er1645v2BaliAdvancedFilterAdvMMapCosToQueueP3Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p3.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134514696}

er1645v2BaliAdvancedFilterAdvMMapCosToQueueP3DropLevel OBJECT-TYPE
   SYNTAX      INTEGER
               {
               dropOnQueue (0)
               }
   MAX-ACCESS  read-write
   STATUS      current
   DESCRIPTION
      "Path: accessList.editConf.advancedFilter.advanced.mark.mapCosToQueue.p3.dropLevel

       Possibilities:
               dropOnQueue   (0)"
   ::= {er1645v2BaliAdvancedFilterEntry 134514698}

er1645v2BaliAdvancedFilterAdvMMapCosToQueueP3DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p3.deFlag

       Possibilities:
               unchanged   (255)
               clear   (0)
               set   (1)"
   ::= {er1645v2BaliAdvancedFilterEntry 134514702}

er1645v2BaliAdvancedFilterAdvMMapCosToQueueP3Cos OBJECT-TYPE
   SYNTAX      INTEGER
               {
               unchanged (8)
               }
   MAX-ACCESS  read-write
   STATUS      current
   DESCRIPTION
      "Path: accessList.editConf.advancedFilter.advanced.mark.mapCosToQueue.p3.cos

       Possibilities:
               unchanged   (8)"
   ::= {er1645v2BaliAdvancedFilterEntry 134514694}

er1645v2BaliAdvancedFilterAdvMMapCosToQueueP3Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p3.dei

       Possibilities:
               unchanged   (255)
               clear   (0)
               set   (1)"
   ::= {er1645v2BaliAdvancedFilterEntry 134514700}

er1645v2BaliAdvancedFilterAdvMMapCosToQueueP4Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p4.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134515208}

er1645v2BaliAdvancedFilterAdvMMapCosToQueueP4DropLevel OBJECT-TYPE
   SYNTAX      INTEGER
               {
               dropOnQueue (0)
               }
   MAX-ACCESS  read-write
   STATUS      current
   DESCRIPTION
      "Path: accessList.editConf.advancedFilter.advanced.mark.mapCosToQueue.p4.dropLevel

       Possibilities:
               dropOnQueue   (0)"
   ::= {er1645v2BaliAdvancedFilterEntry 134515210}

er1645v2BaliAdvancedFilterAdvMMapCosToQueueP4DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p4.deFlag

       Possibilities:
               unchanged   (255)
               clear   (0)
               set   (1)"
   ::= {er1645v2BaliAdvancedFilterEntry 134515214}

er1645v2BaliAdvancedFilterAdvMMapCosToQueueP4Cos OBJECT-TYPE
   SYNTAX      INTEGER
               {
               unchanged (8)
               }
   MAX-ACCESS  read-write
   STATUS      current
   DESCRIPTION
      "Path: accessList.editConf.advancedFilter.advanced.mark.mapCosToQueue.p4.cos

       Possibilities:
               unchanged   (8)"
   ::= {er1645v2BaliAdvancedFilterEntry 134515206}

er1645v2BaliAdvancedFilterAdvMMapCosToQueueP4Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p4.dei

       Possibilities:
               unchanged   (255)
               clear   (0)
               set   (1)"
   ::= {er1645v2BaliAdvancedFilterEntry 134515212}

er1645v2BaliAdvancedFilterAdvMMapCosToQueueP5Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p5.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134515720}

er1645v2BaliAdvancedFilterAdvMMapCosToQueueP5DropLevel OBJECT-TYPE
   SYNTAX      INTEGER
               {
               dropOnQueue (0)
               }
   MAX-ACCESS  read-write
   STATUS      current
   DESCRIPTION
      "Path: accessList.editConf.advancedFilter.advanced.mark.mapCosToQueue.p5.dropLevel

       Possibilities:
               dropOnQueue   (0)"
   ::= {er1645v2BaliAdvancedFilterEntry 134515722}

er1645v2BaliAdvancedFilterAdvMMapCosToQueueP5DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p5.deFlag

       Possibilities:
               unchanged   (255)
               clear   (0)
               set   (1)"
   ::= {er1645v2BaliAdvancedFilterEntry 134515726}

er1645v2BaliAdvancedFilterAdvMMapCosToQueueP5Cos OBJECT-TYPE
   SYNTAX      INTEGER
               {
               unchanged (8)
               }
   MAX-ACCESS  read-write
   STATUS      current
   DESCRIPTION
      "Path: accessList.editConf.advancedFilter.advanced.mark.mapCosToQueue.p5.cos

       Possibilities:
               unchanged   (8)"
   ::= {er1645v2BaliAdvancedFilterEntry 134515718}

er1645v2BaliAdvancedFilterAdvMMapCosToQueueP5Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p5.dei

       Possibilities:
               unchanged   (255)
               clear   (0)
               set   (1)"
   ::= {er1645v2BaliAdvancedFilterEntry 134515724}

er1645v2BaliAdvancedFilterAdvMMapCosToQueueP6Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p6.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134516232}

er1645v2BaliAdvancedFilterAdvMMapCosToQueueP6DropLevel OBJECT-TYPE
   SYNTAX      INTEGER
               {
               dropOnQueue (0)
               }
   MAX-ACCESS  read-write
   STATUS      current
   DESCRIPTION
      "Path: accessList.editConf.advancedFilter.advanced.mark.mapCosToQueue.p6.dropLevel

       Possibilities:
               dropOnQueue   (0)"
   ::= {er1645v2BaliAdvancedFilterEntry 134516234}

er1645v2BaliAdvancedFilterAdvMMapCosToQueueP6DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p6.deFlag

       Possibilities:
               unchanged   (255)
               clear   (0)
               set   (1)"
   ::= {er1645v2BaliAdvancedFilterEntry 134516238}

er1645v2BaliAdvancedFilterAdvMMapCosToQueueP6Cos OBJECT-TYPE
   SYNTAX      INTEGER
               {
               unchanged (8)
               }
   MAX-ACCESS  read-write
   STATUS      current
   DESCRIPTION
      "Path: accessList.editConf.advancedFilter.advanced.mark.mapCosToQueue.p6.cos

       Possibilities:
               unchanged   (8)"
   ::= {er1645v2BaliAdvancedFilterEntry 134516230}

er1645v2BaliAdvancedFilterAdvMMapCosToQueueP6Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p6.dei

       Possibilities:
               unchanged   (255)
               clear   (0)
               set   (1)"
   ::= {er1645v2BaliAdvancedFilterEntry 134516236}

er1645v2BaliAdvancedFilterAdvMMapCosToQueueP7Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.p7.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134516744}

er1645v2BaliAdvancedFilterAdvMMapCosToQueueP7DropLevel OBJECT-TYPE
   SYNTAX      INTEGER
               {
               dropOnQueue (0)
               }
   MAX-ACCESS  read-write
   STATUS      current
   DESCRIPTION
      "Path: accessList.editConf.advancedFilter.advanced.mark.mapCosToQueue.p7.dropLevel

       Possibilities:
               dropOnQueue   (0)"
   ::= {er1645v2BaliAdvancedFilterEntry 134516746}

er1645v2BaliAdvancedFilterAdvMMapCosToQueueP7DeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.p7.deFlag

       Possibilities:
               unchanged   (255)
               clear   (0)
               set   (1)"
   ::= {er1645v2BaliAdvancedFilterEntry 134516750}

er1645v2BaliAdvancedFilterAdvMMapCosToQueueP7Cos OBJECT-TYPE
   SYNTAX      INTEGER
               {
               unchanged (8)
               }
   MAX-ACCESS  read-write
   STATUS      current
   DESCRIPTION
      "Path: accessList.editConf.advancedFilter.advanced.mark.mapCosToQueue.p7.cos

       Possibilities:
               unchanged   (8)"
   ::= {er1645v2BaliAdvancedFilterEntry 134516742}

er1645v2BaliAdvancedFilterAdvMMapCosToQueueP7Dei OBJECT-TYPE
   SYNTAX      INTEGER
               {
               unchanged (255),
               clear (0),
               set (1)
               }
   MAX-ACCESS  read-write
   STATUS      current
   DESCRIPTION
      "Path: accessList.editConf.advancedFilter.advanced.mark.mapCosToQueue.p7.dei

       Possibilities:
               unchanged   (255)
               clear   (0)
               set   (1)"
   ::= {er1645v2BaliAdvancedFilterEntry 134516748}

er1645v2BaliAdvancedFilterAdvMMapCosToQueueUntaggedQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapCosToQueue.untagged.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134517256}

er1645v2BaliAdvancedFilterAdvMMapCosToQueueUntaggedDropLevel OBJECT-TYPE
   SYNTAX      INTEGER
               {
               dropOnQueue (0)
               }
   MAX-ACCESS  read-write
   STATUS      current
   DESCRIPTION
      "Path: accessList.editConf.advancedFilter.advanced.mark.mapCosToQueue.untagged.dropLevel

       Possibilities:
               dropOnQueue   (0)"
   ::= {er1645v2BaliAdvancedFilterEntry 134517258}

er1645v2BaliAdvancedFilterAdvMMapCosToQueueUntaggedDeFlag OBJECT-TYPE
   SYNTAX      INTEGER
               {
               unchanged (255),
               clear (0),
               set (1)
               }
   MAX-ACCESS  read-write
   STATUS      current
   DESCRIPTION
      "Path: accessList.editConf.advancedFilter.advanced.mark.mapCosToQueue.untagged.deFlag

       Possibilities:
               unchanged   (255)
               clear   (0)
               set   (1)"
   ::= {er1645v2BaliAdvancedFilterEntry 134517262}

er1645v2BaliAdvancedFilterAdvMMapDeiToQueueDeiClearQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapDeiToQueue.deiClear.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134521352}

er1645v2BaliAdvancedFilterAdvMMapDeiToQueueDeiClearDropLevel OBJECT-TYPE
   SYNTAX      INTEGER
               {
               dropOnQueue (0)
               }
   MAX-ACCESS  read-write
   STATUS      current
   DESCRIPTION
      "Path: accessList.editConf.advancedFilter.advanced.mark.mapDeiToQueue.deiClear.dropLevel

       Possibilities:
               dropOnQueue   (0)"
   ::= {er1645v2BaliAdvancedFilterEntry 134521354}

er1645v2BaliAdvancedFilterAdvMMapDeiToQueueDeiClearDeFlag OBJECT-TYPE
   SYNTAX      INTEGER
               {
               unchanged (255),
               clear (0),
               set (1)
               }
   MAX-ACCESS  read-write
   STATUS      current
   DESCRIPTION
      "Path: accessList.editConf.advancedFilter.advanced.mark.mapDeiToQueue.deiClear.deFlag

       Possibilities:
               unchanged   (255)
               clear   (0)
               set   (1)"
   ::= {er1645v2BaliAdvancedFilterEntry 134521358}

er1645v2BaliAdvancedFilterAdvMMapDeiToQueueDeiClearCos OBJECT-TYPE
   SYNTAX      INTEGER
               {
               unchanged (8)
               }
   MAX-ACCESS  read-write
   STATUS      current
   DESCRIPTION
      "Path: accessList.editConf.advancedFilter.advanced.mark.mapDeiToQueue.deiClear.cos

       Possibilities:
               unchanged   (8)"
   ::= {er1645v2BaliAdvancedFilterEntry 134521350}

er1645v2BaliAdvancedFilterAdvMMapDeiToQueueDeiClearDei OBJECT-TYPE
   SYNTAX      INTEGER
               {
               unchanged (255),
               clear (0),
               set (1)
               }
   MAX-ACCESS  read-write
   STATUS      current
   DESCRIPTION
      "Path: accessList.editConf.advancedFilter.advanced.mark.mapDeiToQueue.deiClear.dei

       Possibilities:
               unchanged   (255)
               clear   (0)
               set   (1)"
   ::= {er1645v2BaliAdvancedFilterEntry 134521356}

er1645v2BaliAdvancedFilterAdvMMapDeiToQueueDeiSetQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapDeiToQueue.deiSet.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134521864}

er1645v2BaliAdvancedFilterAdvMMapDeiToQueueDeiSetDropLevel OBJECT-TYPE
   SYNTAX      INTEGER
               {
               dropOnQueue (0)
               }
   MAX-ACCESS  read-write
   STATUS      current
   DESCRIPTION
      "Path: accessList.editConf.advancedFilter.advanced.mark.mapDeiToQueue.deiSet.dropLevel

       Possibilities:
               dropOnQueue   (0)"
   ::= {er1645v2BaliAdvancedFilterEntry 134521866}

er1645v2BaliAdvancedFilterAdvMMapDeiToQueueDeiSetDeFlag OBJECT-TYPE
   SYNTAX      INTEGER
               {
               unchanged (255),
               clear (0),
               set (1)
               }
   MAX-ACCESS  read-write
   STATUS      current
   DESCRIPTION
      "Path: accessList.editConf.advancedFilter.advanced.mark.mapDeiToQueue.deiSet.deFlag

       Possibilities:
               unchanged   (255)
               clear   (0)
               set   (1)"
   ::= {er1645v2BaliAdvancedFilterEntry 134521870}

er1645v2BaliAdvancedFilterAdvMMapDeiToQueueDeiSetCos OBJECT-TYPE
   SYNTAX      INTEGER
               {
               unchanged (8)
               }
   MAX-ACCESS  read-write
   STATUS      current
   DESCRIPTION
      "Path: accessList.editConf.advancedFilter.advanced.mark.mapDeiToQueue.deiSet.cos

       Possibilities:
               unchanged   (8)"
   ::= {er1645v2BaliAdvancedFilterEntry 134521862}

er1645v2BaliAdvancedFilterAdvMMapDeiToQueueDeiSetDei OBJECT-TYPE
   SYNTAX      INTEGER
               {
               unchanged (255),
               clear (0),
               set (1)
               }
   MAX-ACCESS  read-write
   STATUS      current
   DESCRIPTION
      "Path: accessList.editConf.advancedFilter.advanced.mark.mapDeiToQueue.deiSet.dei

       Possibilities:
               unchanged   (255)
               clear   (0)
               set   (1)"
   ::= {er1645v2BaliAdvancedFilterEntry 134521868}

er1645v2BaliAdvancedFilterAdvMMapDeiToQueueUntaggedQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapDeiToQueue.untagged.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134525448}

er1645v2BaliAdvancedFilterAdvMMapDeiToQueueUntaggedDropLevel OBJECT-TYPE
   SYNTAX      INTEGER
               {
               dropOnQueue (0)
               }
   MAX-ACCESS  read-write
   STATUS      current
   DESCRIPTION
      "Path: accessList.editConf.advancedFilter.advanced.mark.mapDeiToQueue.untagged.dropLevel

       Possibilities:
               dropOnQueue   (0)"
   ::= {er1645v2BaliAdvancedFilterEntry 134525450}

er1645v2BaliAdvancedFilterAdvMMapDeiToQueueUntaggedDeFlag OBJECT-TYPE
   SYNTAX      INTEGER
               {
               unchanged (255),
               clear (0),
               set (1)
               }
   MAX-ACCESS  read-write
   STATUS      current
   DESCRIPTION
      "Path: accessList.editConf.advancedFilter.advanced.mark.mapDeiToQueue.untagged.deFlag

       Possibilities:
               unchanged   (255)
               clear   (0)
               set   (1)"
   ::= {er1645v2BaliAdvancedFilterEntry 134525454}

er1645v2BaliAdvancedFilterAdvIpTrafficPolicy OBJECT-TYPE
   SYNTAX      DisplayString
   MAX-ACCESS  read-write
   STATUS      current
   DESCRIPTION
      "Path: accessList.editConf.advancedFilter.advanced.ipTrafficPolicy"
   ::= {er1645v2BaliAdvancedFilterEntry 134610944}

er1645v2BaliAdvancedFilterAdvMTaSetQueueQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: accessList.editConf.advancedFilter.advanced.markTcpAck.setQueue.queue

       Possibilities:
               queue1   (0)
               queue2   (1)
               queue3   (2)
               queue4   (3)
               queue5   (4)
               lowDelayQueue   (5)
               lowDelay2Queue   (6)
               systemQueue   (7)"
   ::= {er1645v2BaliAdvancedFilterEntry 134815872}

er1645v2BaliAdvancedFilterAdvMTaSetQueueDropLevel OBJECT-TYPE
   SYNTAX      INTEGER
               {
               dropOnQueue (0)
               }
   MAX-ACCESS  read-write
   STATUS      current
   DESCRIPTION
      "Path: accessList.editConf.advancedFilter.advanced.markTcpAck.setQueue.dropLevel

       Possibilities:
               dropOnQueue   (0)"
   ::= {er1645v2BaliAdvancedFilterEntry 134815904}

er1645v2BaliAdvancedFilterAdvMTaSetQueueDeFlag OBJECT-TYPE
   SYNTAX      INTEGER
               {
               unchanged (255),
               clear (0),
               set (1)
               }
   MAX-ACCESS  read-write
   STATUS      current
   DESCRIPTION
      "Path: accessList.editConf.advancedFilter.advanced.markTcpAck.setQueue.deFlag

       Possibilities:
               unchanged   (255)
               clear   (0)
               set   (1)"
   ::= {er1645v2BaliAdvancedFilterEntry 134815968}

er1645v2BaliAdvancedFilterAdvMTaSetTosAndCosTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: accessList.editConf.advancedFilter.advanced.markTcpAck.setTosAndCos.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2BaliAdvancedFilterEntry 134824000}

er1645v2BaliAdvancedFilterAdvMTaSetTosAndCosCos OBJECT-TYPE
   SYNTAX      INTEGER
               {
               unchanged (8)
               }
   MAX-ACCESS  read-write
   STATUS      current
   DESCRIPTION
      "Path: accessList.editConf.advancedFilter.advanced.markTcpAck.setTosAndCos.cos

       Possibilities:
               unchanged   (8)"
   ::= {er1645v2BaliAdvancedFilterEntry 134824032}

er1645v2BaliAdvancedFilterAdvMTaSetTosAndCosDei OBJECT-TYPE
   SYNTAX      INTEGER
               {
               unchanged (255),
               clear (0),
               set (1)
               }
   MAX-ACCESS  read-write
   STATUS      current
   DESCRIPTION
      "Path: accessList.editConf.advancedFilter.advanced.markTcpAck.setTosAndCos.dei

       Possibilities:
               unchanged   (255)
               clear   (0)
               set   (1)"
   ::= {er1645v2BaliAdvancedFilterEntry 134824128}

er1645v2BaliAdvancedFilterAdvMTaSetTosAndCosQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: accessList.editConf.advancedFilter.advanced.markTcpAck.setTosAndCos.queue

       Possibilities:
               queue1   (0)
               queue2   (1)
               queue3   (2)
               queue4   (3)
               queue5   (4)
               lowDelayQueue   (5)
               lowDelay2Queue   (6)
               systemQueue   (7)"
   ::= {er1645v2BaliAdvancedFilterEntry 134824064}

er1645v2BaliAdvancedFilterAdvMTaSetTosAndCosDropLevel OBJECT-TYPE
   SYNTAX      INTEGER
               {
               dropOnQueue (0)
               }
   MAX-ACCESS  read-write
   STATUS      current
   DESCRIPTION
      "Path: accessList.editConf.advancedFilter.advanced.markTcpAck.setTosAndCos.dropLevel

       Possibilities:
               dropOnQueue   (0)"
   ::= {er1645v2BaliAdvancedFilterEntry 134824096}

er1645v2BaliAdvancedFilterAdvMTaSetTosAndCosDeFlag OBJECT-TYPE
   SYNTAX      INTEGER
               {
               unchanged (255),
               clear (0),
               set (1)
               }
   MAX-ACCESS  read-write
   STATUS      current
   DESCRIPTION
      "Path: accessList.editConf.advancedFilter.advanced.markTcpAck.setTosAndCos.deFlag

       Possibilities:
               unchanged   (255)
               clear   (0)
               set   (1)"
   ::= {er1645v2BaliAdvancedFilterEntry 134824160}

er1645v2BaliAdvancedFilterAdvMTaMapCosToQueueP0Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p0.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134840840}

er1645v2BaliAdvancedFilterAdvMTaMapCosToQueueP0DropLevel OBJECT-TYPE
   SYNTAX      INTEGER
               {
               dropOnQueue (0)
               }
   MAX-ACCESS  read-write
   STATUS      current
   DESCRIPTION
      "Path: accessList.editConf.advancedFilter.advanced.markTcpAck.mapCosToQueue.p0.dropLevel

       Possibilities:
               dropOnQueue   (0)"
   ::= {er1645v2BaliAdvancedFilterEntry 134840842}

er1645v2BaliAdvancedFilterAdvMTaMapCosToQueueP0DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p0.deFlag

       Possibilities:
               unchanged   (255)
               clear   (0)
               set   (1)"
   ::= {er1645v2BaliAdvancedFilterEntry 134840846}

er1645v2BaliAdvancedFilterAdvMTaMapCosToQueueP0Cos OBJECT-TYPE
   SYNTAX      INTEGER
               {
               unchanged (8)
               }
   MAX-ACCESS  read-write
   STATUS      current
   DESCRIPTION
      "Path: accessList.editConf.advancedFilter.advanced.markTcpAck.mapCosToQueue.p0.cos

       Possibilities:
               unchanged   (8)"
   ::= {er1645v2BaliAdvancedFilterEntry 134840838}

er1645v2BaliAdvancedFilterAdvMTaMapCosToQueueP0Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p0.dei

       Possibilities:
               unchanged   (255)
               clear   (0)
               set   (1)"
   ::= {er1645v2BaliAdvancedFilterEntry 134840844}

er1645v2BaliAdvancedFilterAdvMTaMapCosToQueueP1Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p1.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134841352}

er1645v2BaliAdvancedFilterAdvMTaMapCosToQueueP1DropLevel OBJECT-TYPE
   SYNTAX      INTEGER
               {
               dropOnQueue (0)
               }
   MAX-ACCESS  read-write
   STATUS      current
   DESCRIPTION
      "Path: accessList.editConf.advancedFilter.advanced.markTcpAck.mapCosToQueue.p1.dropLevel

       Possibilities:
               dropOnQueue   (0)"
   ::= {er1645v2BaliAdvancedFilterEntry 134841354}

er1645v2BaliAdvancedFilterAdvMTaMapCosToQueueP1DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p1.deFlag

       Possibilities:
               unchanged   (255)
               clear   (0)
               set   (1)"
   ::= {er1645v2BaliAdvancedFilterEntry 134841358}

er1645v2BaliAdvancedFilterAdvMTaMapCosToQueueP1Cos OBJECT-TYPE
   SYNTAX      INTEGER
               {
               unchanged (8)
               }
   MAX-ACCESS  read-write
   STATUS      current
   DESCRIPTION
      "Path: accessList.editConf.advancedFilter.advanced.markTcpAck.mapCosToQueue.p1.cos

       Possibilities:
               unchanged   (8)"
   ::= {er1645v2BaliAdvancedFilterEntry 134841350}

er1645v2BaliAdvancedFilterAdvMTaMapCosToQueueP1Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p1.dei

       Possibilities:
               unchanged   (255)
               clear   (0)
               set   (1)"
   ::= {er1645v2BaliAdvancedFilterEntry 134841356}

er1645v2BaliAdvancedFilterAdvMTaMapCosToQueueP2Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p2.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134841864}

er1645v2BaliAdvancedFilterAdvMTaMapCosToQueueP2DropLevel OBJECT-TYPE
   SYNTAX      INTEGER
               {
               dropOnQueue (0)
               }
   MAX-ACCESS  read-write
   STATUS      current
   DESCRIPTION
      "Path: accessList.editConf.advancedFilter.advanced.markTcpAck.mapCosToQueue.p2.dropLevel

       Possibilities:
               dropOnQueue   (0)"
   ::= {er1645v2BaliAdvancedFilterEntry 134841866}

er1645v2BaliAdvancedFilterAdvMTaMapCosToQueueP2DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p2.deFlag

       Possibilities:
               unchanged   (255)
               clear   (0)
               set   (1)"
   ::= {er1645v2BaliAdvancedFilterEntry 134841870}

er1645v2BaliAdvancedFilterAdvMTaMapCosToQueueP2Cos OBJECT-TYPE
   SYNTAX      INTEGER
               {
               unchanged (8)
               }
   MAX-ACCESS  read-write
   STATUS      current
   DESCRIPTION
      "Path: accessList.editConf.advancedFilter.advanced.markTcpAck.mapCosToQueue.p2.cos

       Possibilities:
               unchanged   (8)"
   ::= {er1645v2BaliAdvancedFilterEntry 134841862}

er1645v2BaliAdvancedFilterAdvMTaMapCosToQueueP2Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p2.dei

       Possibilities:
               unchanged   (255)
               clear   (0)
               set   (1)"
   ::= {er1645v2BaliAdvancedFilterEntry 134841868}

er1645v2BaliAdvancedFilterAdvMTaMapCosToQueueP3Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p3.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134842376}

er1645v2BaliAdvancedFilterAdvMTaMapCosToQueueP3DropLevel OBJECT-TYPE
   SYNTAX      INTEGER
               {
               dropOnQueue (0)
               }
   MAX-ACCESS  read-write
   STATUS      current
   DESCRIPTION
      "Path: accessList.editConf.advancedFilter.advanced.markTcpAck.mapCosToQueue.p3.dropLevel

       Possibilities:
               dropOnQueue   (0)"
   ::= {er1645v2BaliAdvancedFilterEntry 134842378}

er1645v2BaliAdvancedFilterAdvMTaMapCosToQueueP3DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p3.deFlag

       Possibilities:
               unchanged   (255)
               clear   (0)
               set   (1)"
   ::= {er1645v2BaliAdvancedFilterEntry 134842382}

er1645v2BaliAdvancedFilterAdvMTaMapCosToQueueP3Cos OBJECT-TYPE
   SYNTAX      INTEGER
               {
               unchanged (8)
               }
   MAX-ACCESS  read-write
   STATUS      current
   DESCRIPTION
      "Path: accessList.editConf.advancedFilter.advanced.markTcpAck.mapCosToQueue.p3.cos

       Possibilities:
               unchanged   (8)"
   ::= {er1645v2BaliAdvancedFilterEntry 134842374}

er1645v2BaliAdvancedFilterAdvMTaMapCosToQueueP3Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p3.dei

       Possibilities:
               unchanged   (255)
               clear   (0)
               set   (1)"
   ::= {er1645v2BaliAdvancedFilterEntry 134842380}

er1645v2BaliAdvancedFilterAdvMTaMapCosToQueueP4Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p4.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134842888}

er1645v2BaliAdvancedFilterAdvMTaMapCosToQueueP4DropLevel OBJECT-TYPE
   SYNTAX      INTEGER
               {
               dropOnQueue (0)
               }
   MAX-ACCESS  read-write
   STATUS      current
   DESCRIPTION
      "Path: accessList.editConf.advancedFilter.advanced.markTcpAck.mapCosToQueue.p4.dropLevel

       Possibilities:
               dropOnQueue   (0)"
   ::= {er1645v2BaliAdvancedFilterEntry 134842890}

er1645v2BaliAdvancedFilterAdvMTaMapCosToQueueP4DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p4.deFlag

       Possibilities:
               unchanged   (255)
               clear   (0)
               set   (1)"
   ::= {er1645v2BaliAdvancedFilterEntry 134842894}

er1645v2BaliAdvancedFilterAdvMTaMapCosToQueueP4Cos OBJECT-TYPE
   SYNTAX      INTEGER
               {
               unchanged (8)
               }
   MAX-ACCESS  read-write
   STATUS      current
   DESCRIPTION
      "Path: accessList.editConf.advancedFilter.advanced.markTcpAck.mapCosToQueue.p4.cos

       Possibilities:
               unchanged   (8)"
   ::= {er1645v2BaliAdvancedFilterEntry 134842886}

er1645v2BaliAdvancedFilterAdvMTaMapCosToQueueP4Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p4.dei

       Possibilities:
               unchanged   (255)
               clear   (0)
               set   (1)"
   ::= {er1645v2BaliAdvancedFilterEntry 134842892}

er1645v2BaliAdvancedFilterAdvMTaMapCosToQueueP5Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p5.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134843400}

er1645v2BaliAdvancedFilterAdvMTaMapCosToQueueP5DropLevel OBJECT-TYPE
   SYNTAX      INTEGER
               {
               dropOnQueue (0)
               }
   MAX-ACCESS  read-write
   STATUS      current
   DESCRIPTION
      "Path: accessList.editConf.advancedFilter.advanced.markTcpAck.mapCosToQueue.p5.dropLevel

       Possibilities:
               dropOnQueue   (0)"
   ::= {er1645v2BaliAdvancedFilterEntry 134843402}

er1645v2BaliAdvancedFilterAdvMTaMapCosToQueueP5DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p5.deFlag

       Possibilities:
               unchanged   (255)
               clear   (0)
               set   (1)"
   ::= {er1645v2BaliAdvancedFilterEntry 134843406}

er1645v2BaliAdvancedFilterAdvMTaMapCosToQueueP5Cos OBJECT-TYPE
   SYNTAX      INTEGER
               {
               unchanged (8)
               }
   MAX-ACCESS  read-write
   STATUS      current
   DESCRIPTION
      "Path: accessList.editConf.advancedFilter.advanced.markTcpAck.mapCosToQueue.p5.cos

       Possibilities:
               unchanged   (8)"
   ::= {er1645v2BaliAdvancedFilterEntry 134843398}

er1645v2BaliAdvancedFilterAdvMTaMapCosToQueueP5Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p5.dei

       Possibilities:
               unchanged   (255)
               clear   (0)
               set   (1)"
   ::= {er1645v2BaliAdvancedFilterEntry 134843404}

er1645v2BaliAdvancedFilterAdvMTaMapCosToQueueP6Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p6.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134843912}

er1645v2BaliAdvancedFilterAdvMTaMapCosToQueueP6DropLevel OBJECT-TYPE
   SYNTAX      INTEGER
               {
               dropOnQueue (0)
               }
   MAX-ACCESS  read-write
   STATUS      current
   DESCRIPTION
      "Path: accessList.editConf.advancedFilter.advanced.markTcpAck.mapCosToQueue.p6.dropLevel

       Possibilities:
               dropOnQueue   (0)"
   ::= {er1645v2BaliAdvancedFilterEntry 134843914}

er1645v2BaliAdvancedFilterAdvMTaMapCosToQueueP6DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p6.deFlag

       Possibilities:
               unchanged   (255)
               clear   (0)
               set   (1)"
   ::= {er1645v2BaliAdvancedFilterEntry 134843918}

er1645v2BaliAdvancedFilterAdvMTaMapCosToQueueP6Cos OBJECT-TYPE
   SYNTAX      INTEGER
               {
               unchanged (8)
               }
   MAX-ACCESS  read-write
   STATUS      current
   DESCRIPTION
      "Path: accessList.editConf.advancedFilter.advanced.markTcpAck.mapCosToQueue.p6.cos

       Possibilities:
               unchanged   (8)"
   ::= {er1645v2BaliAdvancedFilterEntry 134843910}

er1645v2BaliAdvancedFilterAdvMTaMapCosToQueueP6Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p6.dei

       Possibilities:
               unchanged   (255)
               clear   (0)
               set   (1)"
   ::= {er1645v2BaliAdvancedFilterEntry 134843916}

er1645v2BaliAdvancedFilterAdvMTaMapCosToQueueP7Queue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.p7.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134844424}

er1645v2BaliAdvancedFilterAdvMTaMapCosToQueueP7DropLevel OBJECT-TYPE
   SYNTAX      INTEGER
               {
               dropOnQueue (0)
               }
   MAX-ACCESS  read-write
   STATUS      current
   DESCRIPTION
      "Path: accessList.editConf.advancedFilter.advanced.markTcpAck.mapCosToQueue.p7.dropLevel

       Possibilities:
               dropOnQueue   (0)"
   ::= {er1645v2BaliAdvancedFilterEntry 134844426}

er1645v2BaliAdvancedFilterAdvMTaMapCosToQueueP7DeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p7.deFlag

       Possibilities:
               unchanged   (255)
               clear   (0)
               set   (1)"
   ::= {er1645v2BaliAdvancedFilterEntry 134844430}

er1645v2BaliAdvancedFilterAdvMTaMapCosToQueueP7Cos OBJECT-TYPE
   SYNTAX      INTEGER
               {
               unchanged (8)
               }
   MAX-ACCESS  read-write
   STATUS      current
   DESCRIPTION
      "Path: accessList.editConf.advancedFilter.advanced.markTcpAck.mapCosToQueue.p7.cos

       Possibilities:
               unchanged   (8)"
   ::= {er1645v2BaliAdvancedFilterEntry 134844422}

er1645v2BaliAdvancedFilterAdvMTaMapCosToQueueP7Dei OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.p7.dei

       Possibilities:
               unchanged   (255)
               clear   (0)
               set   (1)"
   ::= {er1645v2BaliAdvancedFilterEntry 134844428}

er1645v2BaliAdvancedFilterAdvMTaMapCosToQueueUntaggedQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapCosToQueue.untagged.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134844936}

er1645v2BaliAdvancedFilterAdvMTaMapCosToQueueUntaggedDropLevel OBJECT-TYPE
   SYNTAX      INTEGER
               {
               dropOnQueue (0)
               }
   MAX-ACCESS  read-write
   STATUS      current
   DESCRIPTION
      "Path: accessList.editConf.advancedFilter.advanced.markTcpAck.mapCosToQueue.untagged.dropLevel

       Possibilities:
               dropOnQueue   (0)"
   ::= {er1645v2BaliAdvancedFilterEntry 134844938}

er1645v2BaliAdvancedFilterAdvMTaMapCosToQueueUntaggedDeFlag OBJECT-TYPE
   SYNTAX      INTEGER
               {
               unchanged (255),
               clear (0),
               set (1)
               }
   MAX-ACCESS  read-write
   STATUS      current
   DESCRIPTION
      "Path: accessList.editConf.advancedFilter.advanced.markTcpAck.mapCosToQueue.untagged.deFlag

       Possibilities:
               unchanged   (255)
               clear   (0)
               set   (1)"
   ::= {er1645v2BaliAdvancedFilterEntry 134844942}

er1645v2BaliAdvancedFilterAdvMTaMapDeiToQueueDeiClearQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapDeiToQueue.deiClear.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134849032}

er1645v2BaliAdvancedFilterAdvMTaMapDeiToQueueDeiClearDropLevel OBJECT-TYPE
   SYNTAX      INTEGER
               {
               dropOnQueue (0)
               }
   MAX-ACCESS  read-write
   STATUS      current
   DESCRIPTION
      "Path: accessList.editConf.advancedFilter.advanced.markTcpAck.mapDeiToQueue.deiClear.dropLevel

       Possibilities:
               dropOnQueue   (0)"
   ::= {er1645v2BaliAdvancedFilterEntry 134849034}

er1645v2BaliAdvancedFilterAdvMTaMapDeiToQueueDeiClearDeFlag OBJECT-TYPE
   SYNTAX      INTEGER
               {
               unchanged (255),
               clear (0),
               set (1)
               }
   MAX-ACCESS  read-write
   STATUS      current
   DESCRIPTION
      "Path: accessList.editConf.advancedFilter.advanced.markTcpAck.mapDeiToQueue.deiClear.deFlag

       Possibilities:
               unchanged   (255)
               clear   (0)
               set   (1)"
   ::= {er1645v2BaliAdvancedFilterEntry 134849038}

er1645v2BaliAdvancedFilterAdvMTaMapDeiToQueueDeiClearCos OBJECT-TYPE
   SYNTAX      INTEGER
               {
               unchanged (8)
               }
   MAX-ACCESS  read-write
   STATUS      current
   DESCRIPTION
      "Path: accessList.editConf.advancedFilter.advanced.markTcpAck.mapDeiToQueue.deiClear.cos

       Possibilities:
               unchanged   (8)"
   ::= {er1645v2BaliAdvancedFilterEntry 134849030}

er1645v2BaliAdvancedFilterAdvMTaMapDeiToQueueDeiClearDei OBJECT-TYPE
   SYNTAX      INTEGER
               {
               unchanged (255),
               clear (0),
               set (1)
               }
   MAX-ACCESS  read-write
   STATUS      current
   DESCRIPTION
      "Path: accessList.editConf.advancedFilter.advanced.markTcpAck.mapDeiToQueue.deiClear.dei

       Possibilities:
               unchanged   (255)
               clear   (0)
               set   (1)"
   ::= {er1645v2BaliAdvancedFilterEntry 134849036}

er1645v2BaliAdvancedFilterAdvMTaMapDeiToQueueDeiSetQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapDeiToQueue.deiSet.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134849544}

er1645v2BaliAdvancedFilterAdvMTaMapDeiToQueueDeiSetDropLevel OBJECT-TYPE
   SYNTAX      INTEGER
               {
               dropOnQueue (0)
               }
   MAX-ACCESS  read-write
   STATUS      current
   DESCRIPTION
      "Path: accessList.editConf.advancedFilter.advanced.markTcpAck.mapDeiToQueue.deiSet.dropLevel

       Possibilities:
               dropOnQueue   (0)"
   ::= {er1645v2BaliAdvancedFilterEntry 134849546}

er1645v2BaliAdvancedFilterAdvMTaMapDeiToQueueDeiSetDeFlag OBJECT-TYPE
   SYNTAX      INTEGER
               {
               unchanged (255),
               clear (0),
               set (1)
               }
   MAX-ACCESS  read-write
   STATUS      current
   DESCRIPTION
      "Path: accessList.editConf.advancedFilter.advanced.markTcpAck.mapDeiToQueue.deiSet.deFlag

       Possibilities:
               unchanged   (255)
               clear   (0)
               set   (1)"
   ::= {er1645v2BaliAdvancedFilterEntry 134849550}

er1645v2BaliAdvancedFilterAdvMTaMapDeiToQueueDeiSetCos OBJECT-TYPE
   SYNTAX      INTEGER
               {
               unchanged (8)
               }
   MAX-ACCESS  read-write
   STATUS      current
   DESCRIPTION
      "Path: accessList.editConf.advancedFilter.advanced.markTcpAck.mapDeiToQueue.deiSet.cos

       Possibilities:
               unchanged   (8)"
   ::= {er1645v2BaliAdvancedFilterEntry 134849542}

er1645v2BaliAdvancedFilterAdvMTaMapDeiToQueueDeiSetDei OBJECT-TYPE
   SYNTAX      INTEGER
               {
               unchanged (255),
               clear (0),
               set (1)
               }
   MAX-ACCESS  read-write
   STATUS      current
   DESCRIPTION
      "Path: accessList.editConf.advancedFilter.advanced.markTcpAck.mapDeiToQueue.deiSet.dei

       Possibilities:
               unchanged   (255)
               clear   (0)
               set   (1)"
   ::= {er1645v2BaliAdvancedFilterEntry 134849548}

er1645v2BaliAdvancedFilterAdvMTaMapDeiToQueueUntaggedQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapDeiToQueue.untagged.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterEntry 134853128}

er1645v2BaliAdvancedFilterAdvMTaMapDeiToQueueUntaggedDropLevel OBJECT-TYPE
   SYNTAX      INTEGER
               {
               dropOnQueue (0)
               }
   MAX-ACCESS  read-write
   STATUS      current
   DESCRIPTION
      "Path: accessList.editConf.advancedFilter.advanced.markTcpAck.mapDeiToQueue.untagged.dropLevel

       Possibilities:
               dropOnQueue   (0)"
   ::= {er1645v2BaliAdvancedFilterEntry 134853130}

er1645v2BaliAdvancedFilterAdvMTaMapDeiToQueueUntaggedDeFlag OBJECT-TYPE
   SYNTAX      INTEGER
               {
               unchanged (255),
               clear (0),
               set (1)
               }
   MAX-ACCESS  read-write
   STATUS      current
   DESCRIPTION
      "Path: accessList.editConf.advancedFilter.advanced.markTcpAck.mapDeiToQueue.untagged.deFlag

       Possibilities:
               unchanged   (255)
               clear   (0)
               set   (1)"
   ::= {er1645v2BaliAdvancedFilterEntry 134853134}

er1645v2BaliAdvancedFilterAdvCapture OBJECT-TYPE
   SYNTAX      Integer32
   MAX-ACCESS  read-write
   STATUS      current
   DESCRIPTION
      "Path: accessList.editConf.advancedFilter.advanced.capture"
   ::= {er1645v2BaliAdvancedFilterEntry 134676480}

er1645v2BaliAdvancedFilterLimiterNone OBJECT-TYPE
   SYNTAX      INTEGER
               {
               none (0)
               }
   MAX-ACCESS  read-write
   STATUS      current
   DESCRIPTION
      "Path: accessList.editConf.advancedFilter.limiter.none

       Possibilities:
               none   (0)"
   ::= {er1645v2BaliAdvancedFilterEntry 302055424}

er1645v2BaliAdvancedFilterLimiterName OBJECT-TYPE
   SYNTAX      DisplayString
   MAX-ACCESS  read-write
   STATUS      current
   DESCRIPTION
      "Path: accessList.editConf.advancedFilter.limiter.name"
   ::= {er1645v2BaliAdvancedFilterEntry 302120960}

er1645v2BaliAdvancedFilterLimiterQueueQueue1 OBJECT-TYPE
   SYNTAX      DisplayString
   MAX-ACCESS  read-write
   STATUS      current
   DESCRIPTION
      "Path: accessList.editConf.advancedFilter.limiter.queue.queue1"
   ::= {er1645v2BaliAdvancedFilterEntry 302186752}

er1645v2BaliAdvancedFilterLimiterQueueQueue2 OBJECT-TYPE
   SYNTAX      DisplayString
   MAX-ACCESS  read-write
   STATUS      current
   DESCRIPTION
      "Path: accessList.editConf.advancedFilter.limiter.queue.queue2"
   ::= {er1645v2BaliAdvancedFilterEntry 302187008}

er1645v2BaliAdvancedFilterLimiterQueueQueue3 OBJECT-TYPE
   SYNTAX      DisplayString
   MAX-ACCESS  read-write
   STATUS      current
   DESCRIPTION
      "Path: accessList.editConf.advancedFilter.limiter.queue.queue3"
   ::= {er1645v2BaliAdvancedFilterEntry 302187264}

er1645v2BaliAdvancedFilterLimiterQueueQueue4 OBJECT-TYPE
   SYNTAX      DisplayString
   MAX-ACCESS  read-write
   STATUS      current
   DESCRIPTION
      "Path: accessList.editConf.advancedFilter.limiter.queue.queue4"
   ::= {er1645v2BaliAdvancedFilterEntry 302187520}

er1645v2BaliAdvancedFilterLimiterQueueQueue5 OBJECT-TYPE
   SYNTAX      DisplayString
   MAX-ACCESS  read-write
   STATUS      current
   DESCRIPTION
      "Path: accessList.editConf.advancedFilter.limiter.queue.queue5"
   ::= {er1645v2BaliAdvancedFilterEntry 302187776}

er1645v2BaliAdvancedFilterLimiterQueueLowDelayQueue OBJECT-TYPE
   SYNTAX      DisplayString
   MAX-ACCESS  read-write
   STATUS      current
   DESCRIPTION
      "Path: accessList.editConf.advancedFilter.limiter.queue.lowDelayQueue"
   ::= {er1645v2BaliAdvancedFilterEntry 302188032}

er1645v2BaliAdvancedFilterLimiterQueueLowDelay2Queue OBJECT-TYPE
   SYNTAX      DisplayString
   MAX-ACCESS  read-write
   STATUS      current
   DESCRIPTION
      "Path: accessList.editConf.advancedFilter.limiter.queue.lowDelay2Queue"
   ::= {er1645v2BaliAdvancedFilterEntry 302188288}

er1645v2BaliAdvancedFilterLimiterQueueSystemQueue OBJECT-TYPE
   SYNTAX      DisplayString
   MAX-ACCESS  read-write
   STATUS      current
   DESCRIPTION
      "Path: accessList.editConf.advancedFilter.limiter.queue.systemQueue"
   ::= {er1645v2BaliAdvancedFilterEntry 302188544}

er1645v2BaliAdvancedFilterAdvMMapTosToCos OBJECT-TYPE
   SYNTAX      SEQUENCE OF Er1645v2BaliAdvancedFilterAdvMMapTosToCosEntry
   MAX-ACCESS  not-accessible
   STATUS      current
   DESCRIPTION
      ""
   ::= {er1645v2BaliAdvancedFilter 134504448}

er1645v2BaliAdvancedFilterAdvMMapTosToCosEntry OBJECT-TYPE
   SYNTAX      Er1645v2BaliAdvancedFilterAdvMMapTosToCosEntry
   MAX-ACCESS  not-accessible
   STATUS      current
   DESCRIPTION
      ""
   INDEX      { er1645v2BaliAdvancedFilterAdvMMapTosToCosGlobalIx,
                er1645v2BaliAdvancedFilterTableIx,
                er1645v2BaliAdvancedFilterAdvMMapTosToCosTableIx }
   ::= {er1645v2BaliAdvancedFilterAdvMMapTosToCos 1}

Er1645v2BaliAdvancedFilterAdvMMapTosToCosEntry ::=
   SEQUENCE
      {
      er1645v2BaliAdvancedFilterAdvMMapTosToCosActions
         VariableLengthTableActions,
      er1645v2BaliAdvancedFilterAdvMMapTosToCosGlobalIx
         GlobalIndex,
      er1645v2BaliAdvancedFilterAdvMMapTosToCosTableIx
         TableIndex,
      er1645v2BaliAdvancedFilterAdvMMapTosToCosStartTos
         INTEGER,
      er1645v2BaliAdvancedFilterAdvMMapTosToCosEndTos
         INTEGER,
      er1645v2BaliAdvancedFilterAdvMMapTosToCosCos
         INTEGER,
      er1645v2BaliAdvancedFilterAdvMMapTosToCosDei
         INTEGER,
      er1645v2BaliAdvancedFilterAdvMMapTosToCosQueue
         INTEGER,
      er1645v2BaliAdvancedFilterAdvMMapTosToCosDropLevel
         INTEGER,
      er1645v2BaliAdvancedFilterAdvMMapTosToCosDeFlag
         INTEGER
      }

er1645v2BaliAdvancedFilterAdvMMapTosToCosActions OBJECT-TYPE
   SYNTAX      VariableLengthTableActions
   MAX-ACCESS  read-write
   STATUS      current
   DESCRIPTION
      "By way of this field, some manipulations
       on this table may be performed."
   ::= {er1645v2BaliAdvancedFilterAdvMMapTosToCosEntry 2}

er1645v2BaliAdvancedFilterAdvMMapTosToCosGlobalIx OBJECT-TYPE
   SYNTAX      GlobalIndex
   MAX-ACCESS  not-accessible
   STATUS      current
   DESCRIPTION
      "The value of the tlsCntTreeGlobalIndex of the MANAGED OBJECT."
   ::= {er1645v2BaliAdvancedFilterAdvMMapTosToCosEntry 10}

er1645v2BaliAdvancedFilterAdvMMapTosToCosTableIx OBJECT-TYPE
   SYNTAX      TableIndex
   MAX-ACCESS  not-accessible
   STATUS      current
   DESCRIPTION
      ""
   ::= {er1645v2BaliAdvancedFilterAdvMMapTosToCosEntry 11}

er1645v2BaliAdvancedFilterAdvMMapTosToCosStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.mark.mapTosToCos.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvMMapTosToCosEntry 16777216}

er1645v2BaliAdvancedFilterAdvMMapTosToCosEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.mark.mapTosToCos.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvMMapTosToCosEntry 33554432}

er1645v2BaliAdvancedFilterAdvMMapTosToCosCos OBJECT-TYPE
   SYNTAX      INTEGER
               {
               unchanged (8)
               }
   MAX-ACCESS  read-write
   STATUS      current
   DESCRIPTION
      "Path: accessList.editConf.advancedFilter.advanced.mark.mapTosToCos.cos

       Possibilities:
               unchanged   (8)"
   ::= {er1645v2BaliAdvancedFilterAdvMMapTosToCosEntry 50331648}

er1645v2BaliAdvancedFilterAdvMMapTosToCosDei OBJECT-TYPE
   SYNTAX      INTEGER
               {
               unchanged (255),
               clear (0),
               set (1)
               }
   MAX-ACCESS  read-write
   STATUS      current
   DESCRIPTION
      "Path: accessList.editConf.advancedFilter.advanced.mark.mapTosToCos.dei

       Possibilities:
               unchanged   (255)
               clear   (0)
               set   (1)"
   ::= {er1645v2BaliAdvancedFilterAdvMMapTosToCosEntry 100663296}

er1645v2BaliAdvancedFilterAdvMMapTosToCosQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.mark.mapTosToCos.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterAdvMMapTosToCosEntry 67108864}

er1645v2BaliAdvancedFilterAdvMMapTosToCosDropLevel OBJECT-TYPE
   SYNTAX      INTEGER
               {
               dropOnQueue (0)
               }
   MAX-ACCESS  read-write
   STATUS      current
   DESCRIPTION
      "Path: accessList.editConf.advancedFilter.advanced.mark.mapTosToCos.dropLevel

       Possibilities:
               dropOnQueue   (0)"
   ::= {er1645v2BaliAdvancedFilterAdvMMapTosToCosEntry 83886080}

er1645v2BaliAdvancedFilterAdvMMapTosToCosDeFlag OBJECT-TYPE
   SYNTAX      INTEGER
               {
               unchanged (255),
               clear (0),
               set (1)
               }
   MAX-ACCESS  read-write
   STATUS      current
   DESCRIPTION
      "Path: accessList.editConf.advancedFilter.advanced.mark.mapTosToCos.deFlag

       Possibilities:
               unchanged   (255)
               clear   (0)
               set   (1)"
   ::= {er1645v2BaliAdvancedFilterAdvMMapTosToCosEntry 117440512}

er1645v2BaliAdvancedFilterAdvPolicyTosBased OBJECT-TYPE
   SYNTAX      SEQUENCE OF Er1645v2BaliAdvancedFilterAdvPolicyTosBasedEntry
   MAX-ACCESS  not-accessible
   STATUS      current
   DESCRIPTION
      ""
   ::= {er1645v2BaliAdvancedFilter 134742784}

er1645v2BaliAdvancedFilterAdvPolicyTosBasedEntry OBJECT-TYPE
   SYNTAX      Er1645v2BaliAdvancedFilterAdvPolicyTosBasedEntry
   MAX-ACCESS  not-accessible
   STATUS      current
   DESCRIPTION
      ""
   INDEX      { er1645v2BaliAdvancedFilterAdvPolicyTosBasedGlobalIx,
                er1645v2BaliAdvancedFilterTableIx,
                er1645v2BaliAdvancedFilterAdvPolicyTosBasedTableIx }
   ::= {er1645v2BaliAdvancedFilterAdvPolicyTosBased 1}

Er1645v2BaliAdvancedFilterAdvPolicyTosBasedEntry ::=
   SEQUENCE
      {
      er1645v2BaliAdvancedFilterAdvPolicyTosBasedActions
         VariableLengthTableActions,
      er1645v2BaliAdvancedFilterAdvPolicyTosBasedGlobalIx
         GlobalIndex,
      er1645v2BaliAdvancedFilterAdvPolicyTosBasedTableIx
         TableIndex,
      er1645v2BaliAdvancedFilterAdvPolicyTosBasedStartTos
         INTEGER,
      er1645v2BaliAdvancedFilterAdvPolicyTosBasedEndTos
         INTEGER,
      er1645v2BaliAdvancedFilterAdvPolicyTosBasedCos
         INTEGER,
      er1645v2BaliAdvancedFilterAdvPolicyTosBasedQueue
         INTEGER,
      er1645v2BaliAdvancedFilterAdvPolicyTosBasedDropLevel
         INTEGER,
      er1645v2BaliAdvancedFilterAdvPolicyTosBasedPort
         DisplayString
      }

er1645v2BaliAdvancedFilterAdvPolicyTosBasedActions OBJECT-TYPE
   SYNTAX      VariableLengthTableActions
   MAX-ACCESS  read-write
   STATUS      current
   DESCRIPTION
      "By way of this field, some manipulations
       on this table may be performed."
   ::= {er1645v2BaliAdvancedFilterAdvPolicyTosBasedEntry 2}

er1645v2BaliAdvancedFilterAdvPolicyTosBasedGlobalIx OBJECT-TYPE
   SYNTAX      GlobalIndex
   MAX-ACCESS  not-accessible
   STATUS      current
   DESCRIPTION
      "The value of the tlsCntTreeGlobalIndex of the MANAGED OBJECT."
   ::= {er1645v2BaliAdvancedFilterAdvPolicyTosBasedEntry 10}

er1645v2BaliAdvancedFilterAdvPolicyTosBasedTableIx OBJECT-TYPE
   SYNTAX      TableIndex
   MAX-ACCESS  not-accessible
   STATUS      current
   DESCRIPTION
      ""
   ::= {er1645v2BaliAdvancedFilterAdvPolicyTosBasedEntry 11}

er1645v2BaliAdvancedFilterAdvPolicyTosBasedStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.policy.tosBased.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvPolicyTosBasedEntry 16777216}

er1645v2BaliAdvancedFilterAdvPolicyTosBasedEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.policy.tosBased.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvPolicyTosBasedEntry 33554432}

er1645v2BaliAdvancedFilterAdvPolicyTosBasedCos OBJECT-TYPE
   SYNTAX      INTEGER
               {
               unchanged (8)
               }
   MAX-ACCESS  read-write
   STATUS      current
   DESCRIPTION
      "Path: accessList.editConf.advancedFilter.advanced.policy.tosBased.cos

       Possibilities:
               unchanged   (8)"
   ::= {er1645v2BaliAdvancedFilterAdvPolicyTosBasedEntry 50331648}

er1645v2BaliAdvancedFilterAdvPolicyTosBasedQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: accessList.editConf.advancedFilter.advanced.policy.tosBased.queue

       Possibilities:
               queue1   (0)
               queue2   (1)
               queue3   (2)
               queue4   (3)
               queue5   (4)
               lowDelayQueue   (5)
               lowDelay2Queue   (6)
               systemQueue   (7)"
   ::= {er1645v2BaliAdvancedFilterAdvPolicyTosBasedEntry 67108864}

er1645v2BaliAdvancedFilterAdvPolicyTosBasedDropLevel OBJECT-TYPE
   SYNTAX      INTEGER
               {
               dropOnQueue (0)
               }
   MAX-ACCESS  read-write
   STATUS      current
   DESCRIPTION
      "Path: accessList.editConf.advancedFilter.advanced.policy.tosBased.dropLevel

       Possibilities:
               dropOnQueue   (0)"
   ::= {er1645v2BaliAdvancedFilterAdvPolicyTosBasedEntry 83886080}

er1645v2BaliAdvancedFilterAdvPolicyTosBasedPort OBJECT-TYPE
   SYNTAX      DisplayString
   MAX-ACCESS  read-write
   STATUS      current
   DESCRIPTION
      "Path: accessList.editConf.advancedFilter.advanced.policy.tosBased.port"
   ::= {er1645v2BaliAdvancedFilterAdvPolicyTosBasedEntry 100663296}

er1645v2BaliAdvancedFilterAdvMTaMapTosToCos OBJECT-TYPE
   SYNTAX      SEQUENCE OF Er1645v2BaliAdvancedFilterAdvMTaMapTosToCosEntry
   MAX-ACCESS  not-accessible
   STATUS      current
   DESCRIPTION
      ""
   ::= {er1645v2BaliAdvancedFilter 134832128}

er1645v2BaliAdvancedFilterAdvMTaMapTosToCosEntry OBJECT-TYPE
   SYNTAX      Er1645v2BaliAdvancedFilterAdvMTaMapTosToCosEntry
   MAX-ACCESS  not-accessible
   STATUS      current
   DESCRIPTION
      ""
   INDEX      { er1645v2BaliAdvancedFilterAdvMTaMapTosToCosGlobalIx,
                er1645v2BaliAdvancedFilterTableIx,
                er1645v2BaliAdvancedFilterAdvMTaMapTosToCosTableIx }
   ::= {er1645v2BaliAdvancedFilterAdvMTaMapTosToCos 1}

Er1645v2BaliAdvancedFilterAdvMTaMapTosToCosEntry ::=
   SEQUENCE
      {
      er1645v2BaliAdvancedFilterAdvMTaMapTosToCosActions
         VariableLengthTableActions,
      er1645v2BaliAdvancedFilterAdvMTaMapTosToCosGlobalIx
         GlobalIndex,
      er1645v2BaliAdvancedFilterAdvMTaMapTosToCosTableIx
         TableIndex,
      er1645v2BaliAdvancedFilterAdvMTaMapTosToCosStartTos
         INTEGER,
      er1645v2BaliAdvancedFilterAdvMTaMapTosToCosEndTos
         INTEGER,
      er1645v2BaliAdvancedFilterAdvMTaMapTosToCosCos
         INTEGER,
      er1645v2BaliAdvancedFilterAdvMTaMapTosToCosDei
         INTEGER,
      er1645v2BaliAdvancedFilterAdvMTaMapTosToCosQueue
         INTEGER,
      er1645v2BaliAdvancedFilterAdvMTaMapTosToCosDropLevel
         INTEGER,
      er1645v2BaliAdvancedFilterAdvMTaMapTosToCosDeFlag
         INTEGER
      }

er1645v2BaliAdvancedFilterAdvMTaMapTosToCosActions OBJECT-TYPE
   SYNTAX      VariableLengthTableActions
   MAX-ACCESS  read-write
   STATUS      current
   DESCRIPTION
      "By way of this field, some manipulations
       on this table may be performed."
   ::= {er1645v2BaliAdvancedFilterAdvMTaMapTosToCosEntry 2}

er1645v2BaliAdvancedFilterAdvMTaMapTosToCosGlobalIx OBJECT-TYPE
   SYNTAX      GlobalIndex
   MAX-ACCESS  not-accessible
   STATUS      current
   DESCRIPTION
      "The value of the tlsCntTreeGlobalIndex of the MANAGED OBJECT."
   ::= {er1645v2BaliAdvancedFilterAdvMTaMapTosToCosEntry 10}

er1645v2BaliAdvancedFilterAdvMTaMapTosToCosTableIx OBJECT-TYPE
   SYNTAX      TableIndex
   MAX-ACCESS  not-accessible
   STATUS      current
   DESCRIPTION
      ""
   ::= {er1645v2BaliAdvancedFilterAdvMTaMapTosToCosEntry 11}

er1645v2BaliAdvancedFilterAdvMTaMapTosToCosStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.markTcpAck.mapTosToCos.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvMTaMapTosToCosEntry 16777216}

er1645v2BaliAdvancedFilterAdvMTaMapTosToCosEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: accessList.editConf.advancedFilter.advanced.markTcpAck.mapTosToCos.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BaliAdvancedFilterAdvMTaMapTosToCosEntry 33554432}

er1645v2BaliAdvancedFilterAdvMTaMapTosToCosCos OBJECT-TYPE
   SYNTAX      INTEGER
               {
               unchanged (8)
               }
   MAX-ACCESS  read-write
   STATUS      current
   DESCRIPTION
      "Path: accessList.editConf.advancedFilter.advanced.markTcpAck.mapTosToCos.cos

       Possibilities:
               unchanged   (8)"
   ::= {er1645v2BaliAdvancedFilterAdvMTaMapTosToCosEntry 50331648}

er1645v2BaliAdvancedFilterAdvMTaMapTosToCosDei OBJECT-TYPE
   SYNTAX      INTEGER
               {
               unchanged (255),
               clear (0),
               set (1)
               }
   MAX-ACCESS  read-write
   STATUS      current
   DESCRIPTION
      "Path: accessList.editConf.advancedFilter.advanced.markTcpAck.mapTosToCos.dei

       Possibilities:
               unchanged   (255)
               clear   (0)
               set   (1)"
   ::= {er1645v2BaliAdvancedFilterAdvMTaMapTosToCosEntry 100663296}

er1645v2BaliAdvancedFilterAdvMTaMapTosToCosQueue OBJECT-TYPE
   SYNTAX      INTEGER
               {
               queue1 (0),
               queue2 (1),
               queue3 (2),
               queue4 (3),
               queue5 (4),
               lowDelayQueue (5),
               lowDelay2Queue (6),
               systemQueue (7),
               drop (8)
               }
   MAX-ACCESS  read-write
   STATUS      current
   DESCRIPTION
      "Path: accessList.editConf.advancedFilter.advanced.markTcpAck.mapTosToCos.queue

       Possibilities:
               queue1   (0)
               queue2   (1)
               queue3   (2)
               queue4   (3)
               queue5   (4)
               lowDelayQueue   (5)
               lowDelay2Queue   (6)
               systemQueue   (7)
               drop   (8)"
   ::= {er1645v2BaliAdvancedFilterAdvMTaMapTosToCosEntry 67108864}

er1645v2BaliAdvancedFilterAdvMTaMapTosToCosDropLevel OBJECT-TYPE
   SYNTAX      INTEGER
               {
               dropOnQueue (0)
               }
   MAX-ACCESS  read-write
   STATUS      current
   DESCRIPTION
      "Path: accessList.editConf.advancedFilter.advanced.markTcpAck.mapTosToCos.dropLevel

       Possibilities:
               dropOnQueue   (0)"
   ::= {er1645v2BaliAdvancedFilterAdvMTaMapTosToCosEntry 83886080}

er1645v2BaliAdvancedFilterAdvMTaMapTosToCosDeFlag OBJECT-TYPE
   SYNTAX      INTEGER
               {
               unchanged (255),
               clear (0),
               set (1)
               }
   MAX-ACCESS  read-write
   STATUS      current
   DESCRIPTION
      "Path: accessList.editConf.advancedFilter.advanced.markTcpAck.mapTosToCos.deFlag

       Possibilities:
               unchanged   (255)
               clear   (0)
               set   (1)"
   ::= {er1645v2BaliAdvancedFilterAdvMTaMapTosToCosEntry 117440512}



sr1645v2Bali OBJECT IDENTIFIER ::= {r1645v2Bali 14}


sr1645v2BaliSnmpIndex OBJECT IDENTIFIER ::= {sr1645v2Bali 269}

sr1645v2BaliSnmpIndexTable OBJECT-TYPE
   SYNTAX      SEQUENCE OF Sr1645v2BaliSnmpIndexEntry
   MAX-ACCESS  not-accessible
   STATUS      current
   DESCRIPTION
      "SNMP index assigned to this object"
   ::= {sr1645v2BaliSnmpIndex 1}

sr1645v2BaliSnmpIndexEntry OBJECT-TYPE
   SYNTAX      Sr1645v2BaliSnmpIndexEntry
   MAX-ACCESS  not-accessible
   STATUS      current
   DESCRIPTION
      ""
   INDEX      { sr1645v2BaliSnmpIndexGlobalIx }
   ::= {sr1645v2BaliSnmpIndexTable 1}

Sr1645v2BaliSnmpIndexEntry ::=
   SEQUENCE
      {
      sr1645v2BaliSnmpIndexGlobalIx
         GlobalIndex,
      sr1645v2BaliSnmpIndexValue
         Integer32
      }

sr1645v2BaliSnmpIndexGlobalIx OBJECT-TYPE
   SYNTAX      GlobalIndex
   MAX-ACCESS  not-accessible
   STATUS      current
   DESCRIPTION
      "The value of the tlsCntTreeGlobalIndex of the MANAGED OBJECT."
   ::= {sr1645v2BaliSnmpIndexEntry 10}

sr1645v2BaliSnmpIndexValue OBJECT-TYPE
   SYNTAX      Integer32
   MAX-ACCESS  read-only
   STATUS      current
   DESCRIPTION
      "Path: accessList.status.snmpIndex"
   ::= {sr1645v2BaliSnmpIndexEntry 2147483648}



pr1645v2Bali OBJECT IDENTIFIER ::= {r1645v2Bali 12}


pr1645v2BaliBrAccLP OBJECT IDENTIFIER ::= {pr1645v2Bali 3}

pr1645v2BaliBrAccLPSSCTable OBJECT-TYPE
   SYNTAX      SEQUENCE OF Pr1645v2BaliBrAccLPEntry
   MAX-ACCESS  not-accessible
   STATUS      current
   DESCRIPTION
      "number of MAC address denials due to a bridge access list"
   ::= {pr1645v2BaliBrAccLP 1}

pr1645v2BaliBrAccLPEntry OBJECT-TYPE
   SYNTAX      Pr1645v2BaliBrAccLPEntry
   MAX-ACCESS  not-accessible
   STATUS      current
   DESCRIPTION
      ""
   INDEX      { pr1645v2BaliBrAccLPGlobalIx,
                pr1645v2BaliBrAccLPTableIx }
   ::= {pr1645v2BaliBrAccLPSSCTable 1}

Pr1645v2BaliBrAccLPEntry ::=
   SEQUENCE
      {
      pr1645v2BaliBrAccLPGlobalIx
         GlobalIndex,
      pr1645v2BaliBrAccLPTableIx
         TableIndex,
      pr1645v2BaliBrAccLPMacAddress
         OCTET STRING,
      pr1645v2BaliBrAccLPUses
         Counter32
      }

pr1645v2BaliBrAccLPGlobalIx OBJECT-TYPE
   SYNTAX      GlobalIndex
   MAX-ACCESS  not-accessible
   STATUS      current
   DESCRIPTION
      "The value of the tlsCntTreeGlobalIndex of the MANAGED OBJECT."
   ::= {pr1645v2BaliBrAccLPEntry 10}

pr1645v2BaliBrAccLPTableIx OBJECT-TYPE
   SYNTAX      TableIndex
   MAX-ACCESS  not-accessible
   STATUS      current
   DESCRIPTION
      ""
   ::= {pr1645v2BaliBrAccLPEntry 11}

pr1645v2BaliBrAccLPMacAddress OBJECT-TYPE
   SYNTAX      OCTET STRING
   MAX-ACCESS  read-only
   STATUS      current
   DESCRIPTION
      "Path: accessList.performance.bridgeAccessList.macAddress

       MAC address."
   ::= {pr1645v2BaliBrAccLPEntry 16777216}

pr1645v2BaliBrAccLPUses OBJECT-TYPE
   SYNTAX      Counter32
   MAX-ACCESS  read-only
   STATUS      current
   DESCRIPTION
      "Path: accessList.performance.bridgeAccessList.uses

       32 bit unsigned wrappable counter."
   ::= {pr1645v2BaliBrAccLPEntry 33554432}


pr1645v2BaliAdvancedFilter OBJECT IDENTIFIER ::= {pr1645v2Bali 5}

pr1645v2BaliAdvancedFilterSSCTable OBJECT-TYPE
   SYNTAX      SEQUENCE OF Pr1645v2BaliAdvancedFilterEntry
   MAX-ACCESS  not-accessible
   STATUS      current
   DESCRIPTION
      "MAC addresses to deny access"
   ::= {pr1645v2BaliAdvancedFilter 1}

pr1645v2BaliAdvancedFilterEntry OBJECT-TYPE
   SYNTAX      Pr1645v2BaliAdvancedFilterEntry
   MAX-ACCESS  not-accessible
   STATUS      current
   DESCRIPTION
      ""
   INDEX      { pr1645v2BaliAdvancedFilterGlobalIx,
                pr1645v2BaliAdvancedFilterTableIx }
   ::= {pr1645v2BaliAdvancedFilterSSCTable 1}

Pr1645v2BaliAdvancedFilterEntry ::=
   SEQUENCE
      {
      pr1645v2BaliAdvancedFilterGlobalIx
         GlobalIndex,
      pr1645v2BaliAdvancedFilterTableIx
         TableIndex,
      pr1645v2BaliAdvancedFilterName
         DisplayString,
      pr1645v2BaliAdvancedFilterMatched
         Gauge32,
      pr1645v2BaliAdvancedFilterChecked
         Gauge32,
      pr1645v2BaliAdvancedFilterSms
         OCTET STRING,
      pr1645v2BaliAdvancedFilterSme
         OCTET STRING,
      pr1645v2BaliAdvancedFilterDms
         OCTET STRING,
      pr1645v2BaliAdvancedFilterDme
         OCTET STRING,
      pr1645v2BaliAdvancedFilterVlanDepth
         INTEGER,
      pr1645v2BaliAdvancedFilterTpid
         INTEGER,
      pr1645v2BaliAdvancedFilterVlan
         INTEGER,
      pr1645v2BaliAdvancedFilterEndVlan
         INTEGER,
      pr1645v2BaliAdvancedFilterPriority
         INTEGER,
      pr1645v2BaliAdvancedFilterDei
         INTEGER,
      pr1645v2BaliAdvancedFilterPro
         INTEGER,
      pr1645v2BaliAdvancedFilterAct
         INTEGER,
      pr1645v2BaliAdvancedFilterAdvdr
         Gauge32,
      pr1645v2BaliAdvancedFilterAdv
         DisplayString
      }

pr1645v2BaliAdvancedFilterGlobalIx OBJECT-TYPE
   SYNTAX      GlobalIndex
   MAX-ACCESS  not-accessible
   STATUS      current
   DESCRIPTION
      "The value of the tlsCntTreeGlobalIndex of the MANAGED OBJECT."
   ::= {pr1645v2BaliAdvancedFilterEntry 10}

pr1645v2BaliAdvancedFilterTableIx OBJECT-TYPE
   SYNTAX      TableIndex
   MAX-ACCESS  not-accessible
   STATUS      current
   DESCRIPTION
      ""
   ::= {pr1645v2BaliAdvancedFilterEntry 11}

pr1645v2BaliAdvancedFilterName OBJECT-TYPE
   SYNTAX      DisplayString
   MAX-ACCESS  read-only
   STATUS      current
   DESCRIPTION
      "Path: accessList.performance.advancedFilter.name"
   ::= {pr1645v2BaliAdvancedFilterEntry 218103808}

pr1645v2BaliAdvancedFilterMatched OBJECT-TYPE
   SYNTAX      Gauge32
   MAX-ACCESS  read-only
   STATUS      current
   DESCRIPTION
      "Path: accessList.performance.advancedFilter.matched

       32 bit unsigned gauge value."
   ::= {pr1645v2BaliAdvancedFilterEntry 150994944}

pr1645v2BaliAdvancedFilterChecked OBJECT-TYPE
   SYNTAX      Gauge32
   MAX-ACCESS  read-only
   STATUS      current
   DESCRIPTION
      "Path: accessList.performance.advancedFilter.checked

       32 bit unsigned gauge value."
   ::= {pr1645v2BaliAdvancedFilterEntry 167772160}

pr1645v2BaliAdvancedFilterSms OBJECT-TYPE
   SYNTAX      OCTET STRING
   MAX-ACCESS  read-only
   STATUS      current
   DESCRIPTION
      "Path: accessList.performance.advancedFilter.sourceMacStart

       MAC address."
   ::= {pr1645v2BaliAdvancedFilterEntry 16777216}

pr1645v2BaliAdvancedFilterSme OBJECT-TYPE
   SYNTAX      OCTET STRING
   MAX-ACCESS  read-only
   STATUS      current
   DESCRIPTION
      "Path: accessList.performance.advancedFilter.sourceMacEnd

       MAC address."
   ::= {pr1645v2BaliAdvancedFilterEntry 33554432}

pr1645v2BaliAdvancedFilterDms OBJECT-TYPE
   SYNTAX      OCTET STRING
   MAX-ACCESS  read-only
   STATUS      current
   DESCRIPTION
      "Path: accessList.performance.advancedFilter.destinationMacStart

       MAC address."
   ::= {pr1645v2BaliAdvancedFilterEntry 50331648}

pr1645v2BaliAdvancedFilterDme OBJECT-TYPE
   SYNTAX      OCTET STRING
   MAX-ACCESS  read-only
   STATUS      current
   DESCRIPTION
      "Path: accessList.performance.advancedFilter.destinationMacEnd

       MAC address."
   ::= {pr1645v2BaliAdvancedFilterEntry 67108864}

pr1645v2BaliAdvancedFilterVlanDepth OBJECT-TYPE
   SYNTAX      INTEGER
               {
               unused (0)
               }
   MAX-ACCESS  read-only
   STATUS      current
   DESCRIPTION
      "Path: accessList.performance.advancedFilter.vlanDepth

       Possibilities:
               unused   (0)"
   ::= {pr1645v2BaliAdvancedFilterEntry 234881024}

pr1645v2BaliAdvancedFilterTpid OBJECT-TYPE
   SYNTAX      INTEGER
               {
               dot1q (33024),
               dot1ad (34984),
               s0x9100 (37120),
               s0x9200 (37376),
               s0x9300 (37632),
               dot1qOrDot1ad (65536),
               notUsed (65537)
               }
   MAX-ACCESS  read-only
   STATUS      current
   DESCRIPTION
      "Path: accessList.performance.advancedFilter.tpid

       Possibilities:
               dot1q   (33024)
               dot1ad   (34984)
               0x9100   (37120)
               0x9200   (37376)
               0x9300   (37632)
               dot1qOrDot1ad   (65536)
               notUsed   (65537)"
   ::= {pr1645v2BaliAdvancedFilterEntry 285212672}

pr1645v2BaliAdvancedFilterVlan OBJECT-TYPE
   SYNTAX      INTEGER
               {
               priorityTagged (0),
               untagged (4096),
               any (4097),
               anyVlan (4098)
               }
   MAX-ACCESS  read-only
   STATUS      current
   DESCRIPTION
      "Path: accessList.performance.advancedFilter.vlan

       Possibilities:
               priorityTagged   (0)
               untagged   (4096)
               any   (4097)
               anyVlan   (4098)"
   ::= {pr1645v2BaliAdvancedFilterEntry 184549376}

pr1645v2BaliAdvancedFilterEndVlan OBJECT-TYPE
   SYNTAX      INTEGER
               {
               notUsed (0)
               }
   MAX-ACCESS  read-only
   STATUS      current
   DESCRIPTION
      "Path: accessList.performance.advancedFilter.endVlan

       Possibilities:
               notUsed   (0)"
   ::= {pr1645v2BaliAdvancedFilterEntry 268435456}

pr1645v2BaliAdvancedFilterPriority OBJECT-TYPE
   SYNTAX      INTEGER
               {
               any (8)
               }
   MAX-ACCESS  read-only
   STATUS      current
   DESCRIPTION
      "Path: accessList.performance.advancedFilter.priority

       Possibilities:
               any   (8)"
   ::= {pr1645v2BaliAdvancedFilterEntry 201326592}

pr1645v2BaliAdvancedFilterDei OBJECT-TYPE
   SYNTAX      INTEGER
               {
               clear (0),
               set (1),
               any (2)
               }
   MAX-ACCESS  read-only
   STATUS      current
   DESCRIPTION
      "Path: accessList.performance.advancedFilter.dei

       Possibilities:
               clear   (0)
               set   (1)
               any   (2)"
   ::= {pr1645v2BaliAdvancedFilterEntry 301989888}

pr1645v2BaliAdvancedFilterPro OBJECT-TYPE
   SYNTAX      INTEGER
               {
               any (65536),
               ip (2048),
               arp (2054),
               rarp (32821),
               vlanTagged (33024),
               ipV6 (34525),
               slowProtocols (34825),
               mplsUnicast (34887),
               mplsMulticast (34888),
               pppoeControl (34915),
               pppoeData (34916),
               svlan802d1ad (34984),
               llcSnap (65537)
               }
   MAX-ACCESS  read-only
   STATUS      current
   DESCRIPTION
      "Path: accessList.performance.advancedFilter.protocol

       Possibilities:
               any   (65536)
               ip   (2048)
               arp   (2054)
               rarp   (32821)
               vlanTagged   (33024)
               ipV6   (34525)
               slowProtocols   (34825)
               mplsUnicast   (34887)
               mplsMulticast   (34888)
               pppoeControl   (34915)
               pppoeData   (34916)
               svlan802.1ad   (34984)
               llcSnap   (65537)"
   ::= {pr1645v2BaliAdvancedFilterEntry 83886080}

pr1645v2BaliAdvancedFilterAct OBJECT-TYPE
   SYNTAX      INTEGER
               {
               deny (0),
               permit (1),
               continue (2)
               }
   MAX-ACCESS  read-only
   STATUS      current
   DESCRIPTION
      "Path: accessList.performance.advancedFilter.action

       Possibilities:
               deny   (0)
               permit   (1)
               continue   (2)"
   ::= {pr1645v2BaliAdvancedFilterEntry 100663296}

pr1645v2BaliAdvancedFilterAdvdr OBJECT-TYPE
   SYNTAX      Gauge32
   MAX-ACCESS  read-only
   STATUS      current
   DESCRIPTION
      "Path: accessList.performance.advancedFilter.advancedDrops

       32 bit unsigned gauge value."
   ::= {pr1645v2BaliAdvancedFilterEntry 251658240}

pr1645v2BaliAdvancedFilterAdv OBJECT-TYPE
   SYNTAX      DisplayString
   MAX-ACCESS  read-only
   STATUS      current
   DESCRIPTION
      "Path: accessList.performance.advancedFilter.advanced"
   ::= {pr1645v2BaliAdvancedFilterEntry 134217728}



ar1645v2Bali OBJECT IDENTIFIER ::= {r1645v2Bali 16}


ar1645v2BaliClearCounters OBJECT IDENTIFIER ::= {ar1645v2Bali 263}

ar1645v2BaliClearCountersTable OBJECT-TYPE
   SYNTAX      SEQUENCE OF Ar1645v2BaliClearCountersEntry
   MAX-ACCESS  not-accessible
   STATUS      current
   DESCRIPTION
      "reset counters"
   ::= {ar1645v2BaliClearCounters 1}

ar1645v2BaliClearCountersEntry OBJECT-TYPE
   SYNTAX      Ar1645v2BaliClearCountersEntry
   MAX-ACCESS  not-accessible
   STATUS      current
   DESCRIPTION
      ""
   INDEX      { ar1645v2BaliClearCountersGlobalIx }
   ::= {ar1645v2BaliClearCountersTable 1}

Ar1645v2BaliClearCountersEntry ::=
   SEQUENCE
      {
      ar1645v2BaliClearCountersGlobalIx
         GlobalIndex,
      ar1645v2BaliClearCountersValue
         Integer32
      }

ar1645v2BaliClearCountersGlobalIx OBJECT-TYPE
   SYNTAX      GlobalIndex
   MAX-ACCESS  not-accessible
   STATUS      current
   DESCRIPTION
      "The value of the tlsCntTreeGlobalIndex of the MANAGED OBJECT."
   ::= {ar1645v2BaliClearCountersEntry 10}

ar1645v2BaliClearCountersValue OBJECT-TYPE
   SYNTAX      Integer32
   MAX-ACCESS  read-write
   STATUS      current
   DESCRIPTION
      "Path: accessList.actions.clearCounters"
   ::= {ar1645v2BaliClearCountersEntry 2147483648}



END
