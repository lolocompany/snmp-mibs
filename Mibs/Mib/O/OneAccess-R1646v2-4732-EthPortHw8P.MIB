OneAccess-R1646v2-4732-EthPortHw8P DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2EthPortHw8P OBJECT IDENTIFIER ::= {r1646Rootv2 4732}

r1646v2EthPortHw8PMOProp OBJECT-TYPE
   SYNTAX      SEQUENCE OF R1646v2EthPortHw8PMOPropEntry
   MAX-ACCESS  not-accessible
   STATUS      current
   DESCRIPTION
      ""
   ::= {r1646v2EthPortHw8P 1}

r1646v2EthPortHw8PMOPropEntry OBJECT-TYPE
   SYNTAX      R1646v2EthPortHw8PMOPropEntry
   MAX-ACCESS  not-accessible
   STATUS      current
   DESCRIPTION
      ""
   INDEX      { r1646v2EthPortHw8PMOPropGlobalIx }
   ::= {r1646v2EthPortHw8PMOProp 1}

R1646v2EthPortHw8PMOPropEntry ::=
   SEQUENCE
      {
      r1646v2EthPortHw8PMOPropPath
         ContainmentPath,
      r1646v2EthPortHw8PMOPropRev
         ObjectRevision,
      r1646v2EthPortHw8PMOPropGlobalIx
         GlobalIndex
      }

r1646v2EthPortHw8PMOPropPath OBJECT-TYPE
   SYNTAX      ContainmentPath
   MAX-ACCESS  read-only
   STATUS      current
   DESCRIPTION
      "Textual description of the containment tree from the instance of
       the root object down to the instance of the current object."
   ::= {r1646v2EthPortHw8PMOPropEntry 3}

r1646v2EthPortHw8PMOPropRev OBJECT-TYPE
   SYNTAX      ObjectRevision
   MAX-ACCESS  read-only
   STATUS      current
   DESCRIPTION
      "This value corresponds with the revision of the MANAGED OBJECT."
   ::= {r1646v2EthPortHw8PMOPropEntry 4}

r1646v2EthPortHw8PMOPropGlobalIx OBJECT-TYPE
   SYNTAX      GlobalIndex
   MAX-ACCESS  read-only
   STATUS      current
   DESCRIPTION
      "The value of the tlsCntTreeGlobalIndex of the MANAGED OBJECT."
   ::= {r1646v2EthPortHw8PMOPropEntry 10}



er1646v2EthPortHw8P OBJECT IDENTIFIER ::= {r1646v2EthPortHw8P 11}


er1646v2EthPortHw8PQos OBJECT IDENTIFIER ::= {er1646v2EthPortHw8P 31}

er1646v2EthPortHw8PQosSSCTable OBJECT-TYPE
   SYNTAX      SEQUENCE OF Er1646v2EthPortHw8PQosEntry
   MAX-ACCESS  not-accessible
   STATUS      current
   DESCRIPTION
      ""
   ::= {er1646v2EthPortHw8PQos 1}

er1646v2EthPortHw8PQosEntry OBJECT-TYPE
   SYNTAX      Er1646v2EthPortHw8PQosEntry
   MAX-ACCESS  not-accessible
   STATUS      current
   DESCRIPTION
      ""
   INDEX      { er1646v2EthPortHw8PQosGlobalIx }
   ::= {er1646v2EthPortHw8PQosSSCTable 1}

Er1646v2EthPortHw8PQosEntry ::=
   SEQUENCE
      {
      er1646v2EthPortHw8PQosGlobalIx
         GlobalIndex,
      er1646v2EthPortHw8PQosKeepCos
         OCTET STRING,
      er1646v2EthPortHw8PQosMapCosToCosP0
         INTEGER,
      er1646v2EthPortHw8PQosMapCosToCosP1
         INTEGER,
      er1646v2EthPortHw8PQosMapCosToCosP2
         INTEGER,
      er1646v2EthPortHw8PQosMapCosToCosP3
         INTEGER,
      er1646v2EthPortHw8PQosMapCosToCosP4
         INTEGER,
      er1646v2EthPortHw8PQosMapCosToCosP5
         INTEGER,
      er1646v2EthPortHw8PQosMapCosToCosP6
         INTEGER,
      er1646v2EthPortHw8PQosMapCosToCosP7
         INTEGER,
      er1646v2EthPortHw8PQosSetCos
         INTEGER,
      er1646v2EthPortHw8PQosUseDscp
         OCTET STRING
      }

er1646v2EthPortHw8PQosGlobalIx OBJECT-TYPE
   SYNTAX      GlobalIndex
   MAX-ACCESS  not-accessible
   STATUS      current
   DESCRIPTION
      "The value of the tlsCntTreeGlobalIndex of the MANAGED OBJECT."
   ::= {er1646v2EthPortHw8PQosEntry 10}

er1646v2EthPortHw8PQosKeepCos OBJECT-TYPE
   SYNTAX      OCTET STRING
   MAX-ACCESS  read-write
   STATUS      current
   DESCRIPTION
      "Path: hwPort.editConf.qos.keepCos"
   ::= {er1646v2EthPortHw8PQosEntry 536870912}

er1646v2EthPortHw8PQosMapCosToCosP0 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p0

       Possibilities:
               p0   (1)
               p1   (2)
               p2   (3)
               p3   (4)
               p4   (5)
               p5   (6)
               p6   (7)
               p7   (8)"
   ::= {er1646v2EthPortHw8PQosEntry 1075838976}

er1646v2EthPortHw8PQosMapCosToCosP1 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p1

       Possibilities:
               p0   (1)
               p1   (2)
               p2   (3)
               p3   (4)
               p4   (5)
               p5   (6)
               p6   (7)
               p7   (8)"
   ::= {er1646v2EthPortHw8PQosEntry 1077936128}

er1646v2EthPortHw8PQosMapCosToCosP2 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p2

       Possibilities:
               p0   (1)
               p1   (2)
               p2   (3)
               p3   (4)
               p4   (5)
               p5   (6)
               p6   (7)
               p7   (8)"
   ::= {er1646v2EthPortHw8PQosEntry 1080033280}

er1646v2EthPortHw8PQosMapCosToCosP3 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p3

       Possibilities:
               p0   (1)
               p1   (2)
               p2   (3)
               p3   (4)
               p4   (5)
               p5   (6)
               p6   (7)
               p7   (8)"
   ::= {er1646v2EthPortHw8PQosEntry 1082130432}

er1646v2EthPortHw8PQosMapCosToCosP4 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p4

       Possibilities:
               p0   (1)
               p1   (2)
               p2   (3)
               p3   (4)
               p4   (5)
               p5   (6)
               p6   (7)
               p7   (8)"
   ::= {er1646v2EthPortHw8PQosEntry 1084227584}

er1646v2EthPortHw8PQosMapCosToCosP5 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p5

       Possibilities:
               p0   (1)
               p1   (2)
               p2   (3)
               p3   (4)
               p4   (5)
               p5   (6)
               p6   (7)
               p7   (8)"
   ::= {er1646v2EthPortHw8PQosEntry 1086324736}

er1646v2EthPortHw8PQosMapCosToCosP6 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p6

       Possibilities:
               p0   (1)
               p1   (2)
               p2   (3)
               p3   (4)
               p4   (5)
               p5   (6)
               p6   (7)
               p7   (8)"
   ::= {er1646v2EthPortHw8PQosEntry 1088421888}

er1646v2EthPortHw8PQosMapCosToCosP7 OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.mapCosToCos.p7

       Possibilities:
               p0   (1)
               p1   (2)
               p2   (3)
               p3   (4)
               p4   (5)
               p5   (6)
               p6   (7)
               p7   (8)"
   ::= {er1646v2EthPortHw8PQosEntry 1090519040}

er1646v2EthPortHw8PQosSetCos OBJECT-TYPE
   SYNTAX      INTEGER
               {
               p0 (1),
               p1 (2),
               p2 (3),
               p3 (4),
               p4 (5),
               p5 (6),
               p6 (7),
               p7 (8)
               }
   MAX-ACCESS  read-write
   STATUS      current
   DESCRIPTION
      "Path: hwPort.editConf.qos.setCos

       Possibilities:
               p0   (1)
               p1   (2)
               p2   (3)
               p3   (4)
               p4   (5)
               p5   (6)
               p6   (7)
               p7   (8)"
   ::= {er1646v2EthPortHw8PQosEntry 1610612736}

er1646v2EthPortHw8PQosUseDscp OBJECT-TYPE
   SYNTAX      OCTET STRING
   MAX-ACCESS  read-write
   STATUS      current
   DESCRIPTION
      "Path: hwPort.editConf.qos.useDscp"
   ::= {er1646v2EthPortHw8PQosEntry 2147483648}


er1646v2EthPortHw8PPriorityAlgorithm OBJECT IDENTIFIER ::= {er1646v2EthPortHw8P 33}

er1646v2EthPortHw8PPriorityAlgorithmTable OBJECT-TYPE
   SYNTAX      SEQUENCE OF Er1646v2EthPortHw8PPriorityAlgorithmEntry
   MAX-ACCESS  not-accessible
   STATUS      current
   DESCRIPTION
      ""
   ::= {er1646v2EthPortHw8PPriorityAlgorithm 1}

er1646v2EthPortHw8PPriorityAlgorithmEntry OBJECT-TYPE
   SYNTAX      Er1646v2EthPortHw8PPriorityAlgorithmEntry
   MAX-ACCESS  not-accessible
   STATUS      current
   DESCRIPTION
      ""
   INDEX      { er1646v2EthPortHw8PPriorityAlgorithmGlobalIx }
   ::= {er1646v2EthPortHw8PPriorityAlgorithmTable 1}

Er1646v2EthPortHw8PPriorityAlgorithmEntry ::=
   SEQUENCE
      {
      er1646v2EthPortHw8PPriorityAlgorithmGlobalIx
         GlobalIndex,
      er1646v2EthPortHw8PPriorityAlgorithmValue
         INTEGER
      }

er1646v2EthPortHw8PPriorityAlgorithmGlobalIx OBJECT-TYPE
   SYNTAX      GlobalIndex
   MAX-ACCESS  not-accessible
   STATUS      current
   DESCRIPTION
      "The value of the tlsCntTreeGlobalIndex of the MANAGED OBJECT."
   ::= {er1646v2EthPortHw8PPriorityAlgorithmEntry 10}

er1646v2EthPortHw8PPriorityAlgorithmValue OBJECT-TYPE
   SYNTAX      INTEGER
               {
               absolutePriority (3),
               weightedFairQueueing (0),
               queue4WeightedFairQueueing (1),
               queue3WeightedFairQueueing (2)
               }
   MAX-ACCESS  read-write
   STATUS      current
   DESCRIPTION
      "Path: hwPort.editConf.priorityAlgorithm

       Possibilities:
               absolutePriority   (3)
               weightedFairQueueing   (0)
               queue4WeightedFairQueueing   (1)
               queue3WeightedFairQueueing   (2)"
   ::= {er1646v2EthPortHw8PPriorityAlgorithmEntry 2147483648}


er1646v2EthPortHw8PBandwidth OBJECT IDENTIFIER ::= {er1646v2EthPortHw8P 34}

er1646v2EthPortHw8PBandwidthSSCTable OBJECT-TYPE
   SYNTAX      SEQUENCE OF Er1646v2EthPortHw8PBandwidthEntry
   MAX-ACCESS  not-accessible
   STATUS      current
   DESCRIPTION
      ""
   ::= {er1646v2EthPortHw8PBandwidth 1}

er1646v2EthPortHw8PBandwidthEntry OBJECT-TYPE
   SYNTAX      Er1646v2EthPortHw8PBandwidthEntry
   MAX-ACCESS  not-accessible
   STATUS      current
   DESCRIPTION
      ""
   INDEX      { er1646v2EthPortHw8PBandwidthGlobalIx }
   ::= {er1646v2EthPortHw8PBandwidthSSCTable 1}

Er1646v2EthPortHw8PBandwidthEntry ::=
   SEQUENCE
      {
      er1646v2EthPortHw8PBandwidthGlobalIx
         GlobalIndex,
      er1646v2EthPortHw8PBandwidthCir
         Integer32,
      er1646v2EthPortHw8PBandwidthCountMode
         INTEGER
      }

er1646v2EthPortHw8PBandwidthGlobalIx OBJECT-TYPE
   SYNTAX      GlobalIndex
   MAX-ACCESS  not-accessible
   STATUS      current
   DESCRIPTION
      "The value of the tlsCntTreeGlobalIndex of the MANAGED OBJECT."
   ::= {er1646v2EthPortHw8PBandwidthEntry 10}

er1646v2EthPortHw8PBandwidthCir OBJECT-TYPE
   SYNTAX      Integer32
   MAX-ACCESS  read-write
   STATUS      current
   DESCRIPTION
      "Path: hwPort.editConf.bandwidth.cir"
   ::= {er1646v2EthPortHw8PBandwidthEntry 16777216}

er1646v2EthPortHw8PBandwidthCountMode OBJECT-TYPE
   SYNTAX      INTEGER
               {
               layer1 (1),
               layer2 (2)
               }
   MAX-ACCESS  read-write
   STATUS      current
   DESCRIPTION
      "Path: hwPort.editConf.bandwidth.countMode

       Possibilities:
               layer1   (1)
               layer2   (2)"
   ::= {er1646v2EthPortHw8PBandwidthEntry 33554432}


er1646v2EthPortHw8PDataHandling OBJECT IDENTIFIER ::= {er1646v2EthPortHw8P 27}

er1646v2EthPortHw8PDataHandlingSSCTable OBJECT-TYPE
   SYNTAX      SEQUENCE OF Er1646v2EthPortHw8PDataHandlingEntry
   MAX-ACCESS  not-accessible
   STATUS      current
   DESCRIPTION
      "vlan tagging config"
   ::= {er1646v2EthPortHw8PDataHandling 1}

er1646v2EthPortHw8PDataHandlingEntry OBJECT-TYPE
   SYNTAX      Er1646v2EthPortHw8PDataHandlingEntry
   MAX-ACCESS  not-accessible
   STATUS      current
   DESCRIPTION
      ""
   INDEX      { er1646v2EthPortHw8PDataHandlingGlobalIx }
   ::= {er1646v2EthPortHw8PDataHandlingSSCTable 1}

Er1646v2EthPortHw8PDataHandlingEntry ::=
   SEQUENCE
      {
      er1646v2EthPortHw8PDataHandlingGlobalIx
         GlobalIndex,
      er1646v2EthPortHw8PDataHandlingAuto
         OCTET STRING,
      er1646v2EthPortHw8PDataHandlingAssignAllVid
         Integer32,
      er1646v2EthPortHw8PDataHandlingClassUntaggedAction
         INTEGER,
      er1646v2EthPortHw8PDataHandlingClassUntaggedTagInfoVid
         Integer32,
      er1646v2EthPortHw8PDataHandlingClassUnknownsAction
         INTEGER
      }

er1646v2EthPortHw8PDataHandlingGlobalIx OBJECT-TYPE
   SYNTAX      GlobalIndex
   MAX-ACCESS  not-accessible
   STATUS      current
   DESCRIPTION
      "The value of the tlsCntTreeGlobalIndex of the MANAGED OBJECT."
   ::= {er1646v2EthPortHw8PDataHandlingEntry 10}

er1646v2EthPortHw8PDataHandlingAuto OBJECT-TYPE
   SYNTAX      OCTET STRING
   MAX-ACCESS  read-write
   STATUS      current
   DESCRIPTION
      "Path: hwPort.editConf.dataHandling.auto"
   ::= {er1646v2EthPortHw8PDataHandlingEntry 2147483648}

er1646v2EthPortHw8PDataHandlingAssignAllVid OBJECT-TYPE
   SYNTAX      Integer32
   MAX-ACCESS  read-write
   STATUS      current
   DESCRIPTION
      "Path: hwPort.editConf.dataHandling.assignAll.vid"
   ::= {er1646v2EthPortHw8PDataHandlingEntry 671088640}

er1646v2EthPortHw8PDataHandlingClassUntaggedAction OBJECT-TYPE
   SYNTAX      INTEGER
               {
               discard (0),
               tag (2)
               }
   MAX-ACCESS  read-write
   STATUS      current
   DESCRIPTION
      "Path: hwPort.editConf.dataHandling.classified.untagged.action

       Possibilities:
               discard   (0)
               tag   (2)"
   ::= {er1646v2EthPortHw8PDataHandlingEntry 1157627904}

er1646v2EthPortHw8PDataHandlingClassUntaggedTagInfoVid OBJECT-TYPE
   SYNTAX      Integer32
   MAX-ACCESS  read-write
   STATUS      current
   DESCRIPTION
      "Path: hwPort.editConf.dataHandling.classified.untagged.tagInfo.vid"
   ::= {er1646v2EthPortHw8PDataHandlingEntry 1168113664}

er1646v2EthPortHw8PDataHandlingClassUnknownsAction OBJECT-TYPE
   SYNTAX      INTEGER
               {
               discard (0),
               accept (1)
               }
   MAX-ACCESS  read-write
   STATUS      current
   DESCRIPTION
      "Path: hwPort.editConf.dataHandling.classified.unknownVlans.action

       Possibilities:
               discard   (0)
               accept   (1)"
   ::= {er1646v2EthPortHw8PDataHandlingEntry 1291845632}

er1646v2EthPortHw8PDataHandlingClassVlans OBJECT-TYPE
   SYNTAX      SEQUENCE OF Er1646v2EthPortHw8PDataHandlingClassVlansEntry
   MAX-ACCESS  not-accessible
   STATUS      current
   DESCRIPTION
      ""
   ::= {er1646v2EthPortHw8PDataHandling 1207959552}

er1646v2EthPortHw8PDataHandlingClassVlansEntry OBJECT-TYPE
   SYNTAX      Er1646v2EthPortHw8PDataHandlingClassVlansEntry
   MAX-ACCESS  not-accessible
   STATUS      current
   DESCRIPTION
      ""
   INDEX      { er1646v2EthPortHw8PDataHandlingClassVlansGlobalIx,
                er1646v2EthPortHw8PDataHandlingClassVlansTableIx }
   ::= {er1646v2EthPortHw8PDataHandlingClassVlans 1}

Er1646v2EthPortHw8PDataHandlingClassVlansEntry ::=
   SEQUENCE
      {
      er1646v2EthPortHw8PDataHandlingClassVlansActions
         VariableLengthTableActions,
      er1646v2EthPortHw8PDataHandlingClassVlansGlobalIx
         GlobalIndex,
      er1646v2EthPortHw8PDataHandlingClassVlansTableIx
         TableIndex,
      er1646v2EthPortHw8PDataHandlingClassVlansVid
         Integer32,
      er1646v2EthPortHw8PDataHandlingClassVlansEgressMode
         INTEGER
      }

er1646v2EthPortHw8PDataHandlingClassVlansActions OBJECT-TYPE
   SYNTAX      VariableLengthTableActions
   MAX-ACCESS  read-write
   STATUS      current
   DESCRIPTION
      "By way of this field, some manipulations
       on this table may be performed."
   ::= {er1646v2EthPortHw8PDataHandlingClassVlansEntry 2}

er1646v2EthPortHw8PDataHandlingClassVlansGlobalIx OBJECT-TYPE
   SYNTAX      GlobalIndex
   MAX-ACCESS  not-accessible
   STATUS      current
   DESCRIPTION
      "The value of the tlsCntTreeGlobalIndex of the MANAGED OBJECT."
   ::= {er1646v2EthPortHw8PDataHandlingClassVlansEntry 10}

er1646v2EthPortHw8PDataHandlingClassVlansTableIx OBJECT-TYPE
   SYNTAX      TableIndex
   MAX-ACCESS  not-accessible
   STATUS      current
   DESCRIPTION
      ""
   ::= {er1646v2EthPortHw8PDataHandlingClassVlansEntry 11}

er1646v2EthPortHw8PDataHandlingClassVlansVid OBJECT-TYPE
   SYNTAX      Integer32
   MAX-ACCESS  read-write
   STATUS      current
   DESCRIPTION
      "Path: hwPort.editConf.dataHandling.classified.vlans.vid"
   ::= {er1646v2EthPortHw8PDataHandlingClassVlansEntry 536870912}

er1646v2EthPortHw8PDataHandlingClassVlansEgressMode OBJECT-TYPE
   SYNTAX      INTEGER
               {
               unchanged (1),
               tagged (2),
               untagged (3)
               }
   MAX-ACCESS  read-write
   STATUS      current
   DESCRIPTION
      "Path: hwPort.editConf.dataHandling.classified.vlans.egressMode

       Possibilities:
               unchanged   (1)
               tagged   (2)
               untagged   (3)"
   ::= {er1646v2EthPortHw8PDataHandlingClassVlansEntry 1073741824}


er1646v2EthPortHw8PRemark OBJECT IDENTIFIER ::= {er1646v2EthPortHw8P 321}

er1646v2EthPortHw8PRemarkTable OBJECT-TYPE
   SYNTAX      SEQUENCE OF Er1646v2EthPortHw8PRemarkEntry
   MAX-ACCESS  not-accessible
   STATUS      current
   DESCRIPTION
      "intfRemark"
   ::= {er1646v2EthPortHw8PRemark 1}

er1646v2EthPortHw8PRemarkEntry OBJECT-TYPE
   SYNTAX      Er1646v2EthPortHw8PRemarkEntry
   MAX-ACCESS  not-accessible
   STATUS      current
   DESCRIPTION
      ""
   INDEX      { er1646v2EthPortHw8PRemarkGlobalIx }
   ::= {er1646v2EthPortHw8PRemarkTable 1}

Er1646v2EthPortHw8PRemarkEntry ::=
   SEQUENCE
      {
      er1646v2EthPortHw8PRemarkGlobalIx
         GlobalIndex,
      er1646v2EthPortHw8PRemarkValue
         DisplayString
      }

er1646v2EthPortHw8PRemarkGlobalIx OBJECT-TYPE
   SYNTAX      GlobalIndex
   MAX-ACCESS  not-accessible
   STATUS      current
   DESCRIPTION
      "The value of the tlsCntTreeGlobalIndex of the MANAGED OBJECT."
   ::= {er1646v2EthPortHw8PRemarkEntry 10}

er1646v2EthPortHw8PRemarkValue OBJECT-TYPE
   SYNTAX      DisplayString
   MAX-ACCESS  read-write
   STATUS      current
   DESCRIPTION
      "Path: hwPort.editConf.remark"
   ::= {er1646v2EthPortHw8PRemarkEntry 2147483648}


er1646v2EthPortHw8PAdminStatus OBJECT IDENTIFIER ::= {er1646v2EthPortHw8P 106}

er1646v2EthPortHw8PAdminStatusTable OBJECT-TYPE
   SYNTAX      SEQUENCE OF Er1646v2EthPortHw8PAdminStatusEntry
   MAX-ACCESS  not-accessible
   STATUS      current
   DESCRIPTION
      "ifAdminStatus"
   ::= {er1646v2EthPortHw8PAdminStatus 1}

er1646v2EthPortHw8PAdminStatusEntry OBJECT-TYPE
   SYNTAX      Er1646v2EthPortHw8PAdminStatusEntry
   MAX-ACCESS  not-accessible
   STATUS      current
   DESCRIPTION
      ""
   INDEX      { er1646v2EthPortHw8PAdminStatusGlobalIx }
   ::= {er1646v2EthPortHw8PAdminStatusTable 1}

Er1646v2EthPortHw8PAdminStatusEntry ::=
   SEQUENCE
      {
      er1646v2EthPortHw8PAdminStatusGlobalIx
         GlobalIndex,
      er1646v2EthPortHw8PAdminStatusValue
         INTEGER
      }

er1646v2EthPortHw8PAdminStatusGlobalIx OBJECT-TYPE
   SYNTAX      GlobalIndex
   MAX-ACCESS  not-accessible
   STATUS      current
   DESCRIPTION
      "The value of the tlsCntTreeGlobalIndex of the MANAGED OBJECT."
   ::= {er1646v2EthPortHw8PAdminStatusEntry 10}

er1646v2EthPortHw8PAdminStatusValue OBJECT-TYPE
   SYNTAX      INTEGER
               {
               up (1),
               down (2)
               }
   MAX-ACCESS  read-write
   STATUS      current
   DESCRIPTION
      "Path: hwPort.editConf.adminStatus

       Possibilities:
               up   (1)
               down   (2)"
   ::= {er1646v2EthPortHw8PAdminStatusEntry 2147483648}


er1646v2EthPortHw8POperation OBJECT IDENTIFIER ::= {er1646v2EthPortHw8P 8}

er1646v2EthPortHw8POperationSSCTable OBJECT-TYPE
   SYNTAX      SEQUENCE OF Er1646v2EthPortHw8POperationEntry
   MAX-ACCESS  not-accessible
   STATUS      current
   DESCRIPTION
      "Mirror port configuration for 88E6171 hw switch port"
   ::= {er1646v2EthPortHw8POperation 1}

er1646v2EthPortHw8POperationEntry OBJECT-TYPE
   SYNTAX      Er1646v2EthPortHw8POperationEntry
   MAX-ACCESS  not-accessible
   STATUS      current
   DESCRIPTION
      ""
   INDEX      { er1646v2EthPortHw8POperationGlobalIx }
   ::= {er1646v2EthPortHw8POperationSSCTable 1}

Er1646v2EthPortHw8POperationEntry ::=
   SEQUENCE
      {
      er1646v2EthPortHw8POperationGlobalIx
         GlobalIndex,
      er1646v2EthPortHw8POperationNormal
         DisplayString
      }

er1646v2EthPortHw8POperationGlobalIx OBJECT-TYPE
   SYNTAX      GlobalIndex
   MAX-ACCESS  not-accessible
   STATUS      current
   DESCRIPTION
      "The value of the tlsCntTreeGlobalIndex of the MANAGED OBJECT."
   ::= {er1646v2EthPortHw8POperationEntry 10}

er1646v2EthPortHw8POperationNormal OBJECT-TYPE
   SYNTAX      DisplayString
   MAX-ACCESS  read-write
   STATUS      current
   DESCRIPTION
      "Path: hwPort.editConf.operation.normal"
   ::= {er1646v2EthPortHw8POperationEntry 16777216}

er1646v2EthPortHw8POperationMirrorPorts OBJECT-TYPE
   SYNTAX      SEQUENCE OF Er1646v2EthPortHw8POperationMirrorPortsEntry
   MAX-ACCESS  not-accessible
   STATUS      current
   DESCRIPTION
      ""
   ::= {er1646v2EthPortHw8POperation 33685504}

er1646v2EthPortHw8POperationMirrorPortsEntry OBJECT-TYPE
   SYNTAX      Er1646v2EthPortHw8POperationMirrorPortsEntry
   MAX-ACCESS  not-accessible
   STATUS      current
   DESCRIPTION
      ""
   INDEX      { er1646v2EthPortHw8POperationMirrorPortsGlobalIx,
                er1646v2EthPortHw8POperationMirrorPortsTableIx }
   ::= {er1646v2EthPortHw8POperationMirrorPorts 1}

Er1646v2EthPortHw8POperationMirrorPortsEntry ::=
   SEQUENCE
      {
      er1646v2EthPortHw8POperationMirrorPortsActions
         VariableLengthTableActions,
      er1646v2EthPortHw8POperationMirrorPortsGlobalIx
         GlobalIndex,
      er1646v2EthPortHw8POperationMirrorPortsTableIx
         TableIndex,
      er1646v2EthPortHw8POperationMirrorPortsPort
         INTEGER,
      er1646v2EthPortHw8POperationMirrorPortsMode
         INTEGER
      }

er1646v2EthPortHw8POperationMirrorPortsActions OBJECT-TYPE
   SYNTAX      VariableLengthTableActions
   MAX-ACCESS  read-write
   STATUS      current
   DESCRIPTION
      "By way of this field, some manipulations
       on this table may be performed."
   ::= {er1646v2EthPortHw8POperationMirrorPortsEntry 2}

er1646v2EthPortHw8POperationMirrorPortsGlobalIx OBJECT-TYPE
   SYNTAX      GlobalIndex
   MAX-ACCESS  not-accessible
   STATUS      current
   DESCRIPTION
      "The value of the tlsCntTreeGlobalIndex of the MANAGED OBJECT."
   ::= {er1646v2EthPortHw8POperationMirrorPortsEntry 10}

er1646v2EthPortHw8POperationMirrorPortsTableIx OBJECT-TYPE
   SYNTAX      TableIndex
   MAX-ACCESS  not-accessible
   STATUS      current
   DESCRIPTION
      ""
   ::= {er1646v2EthPortHw8POperationMirrorPortsEntry 11}

er1646v2EthPortHw8POperationMirrorPortsPort OBJECT-TYPE
   SYNTAX      INTEGER
               {
               port1 (1),
               port2 (2),
               port3 (3),
               port4 (4),
               localPort (6)
               }
   MAX-ACCESS  read-write
   STATUS      current
   DESCRIPTION
      "Path: hwPort.editConf.operation.mirror.ports.port

       Possibilities:
               port1   (1)
               port2   (2)
               port3   (3)
               port4   (4)
               localPort   (6)"
   ::= {er1646v2EthPortHw8POperationMirrorPortsEntry 16777216}

er1646v2EthPortHw8POperationMirrorPortsMode OBJECT-TYPE
   SYNTAX      INTEGER
               {
               egress (1),
               ingress (2),
               ingressAndEgress (3)
               }
   MAX-ACCESS  read-write
   STATUS      current
   DESCRIPTION
      "Path: hwPort.editConf.operation.mirror.ports.mode

       Possibilities:
               egress   (1)
               ingress   (2)
               ingressAndEgress   (3)"
   ::= {er1646v2EthPortHw8POperationMirrorPortsEntry 33554432}


er1646v2EthPortHw8PCrossover OBJECT IDENTIFIER ::= {er1646v2EthPortHw8P 3}

er1646v2EthPortHw8PCrossoverTable OBJECT-TYPE
   SYNTAX      SEQUENCE OF Er1646v2EthPortHw8PCrossoverEntry
   MAX-ACCESS  not-accessible
   STATUS      current
   DESCRIPTION
      "LAN crossover"
   ::= {er1646v2EthPortHw8PCrossover 1}

er1646v2EthPortHw8PCrossoverEntry OBJECT-TYPE
   SYNTAX      Er1646v2EthPortHw8PCrossoverEntry
   MAX-ACCESS  not-accessible
   STATUS      current
   DESCRIPTION
      ""
   INDEX      { er1646v2EthPortHw8PCrossoverGlobalIx }
   ::= {er1646v2EthPortHw8PCrossoverTable 1}

Er1646v2EthPortHw8PCrossoverEntry ::=
   SEQUENCE
      {
      er1646v2EthPortHw8PCrossoverGlobalIx
         GlobalIndex,
      er1646v2EthPortHw8PCrossoverValue
         INTEGER
      }

er1646v2EthPortHw8PCrossoverGlobalIx OBJECT-TYPE
   SYNTAX      GlobalIndex
   MAX-ACCESS  not-accessible
   STATUS      current
   DESCRIPTION
      "The value of the tlsCntTreeGlobalIndex of the MANAGED OBJECT."
   ::= {er1646v2EthPortHw8PCrossoverEntry 10}

er1646v2EthPortHw8PCrossoverValue OBJECT-TYPE
   SYNTAX      INTEGER
               {
               auto (1),
               mdi (2),
               mdix (3)
               }
   MAX-ACCESS  read-write
   STATUS      current
   DESCRIPTION
      "Path: hwPort.editConf.crossover

       Possibilities:
               auto   (1)
               mdi   (2)
               mdix   (3)"
   ::= {er1646v2EthPortHw8PCrossoverEntry 2147483648}


er1646v2EthPortHw8PAlarmMask OBJECT IDENTIFIER ::= {er1646v2EthPortHw8P 135}

er1646v2EthPortHw8PAlarmMaskTable OBJECT-TYPE
   SYNTAX      SEQUENCE OF Er1646v2EthPortHw8PAlarmMaskEntry
   MAX-ACCESS  not-accessible
   STATUS      current
   DESCRIPTION
      "ifAlarmMask"
   ::= {er1646v2EthPortHw8PAlarmMask 1}

er1646v2EthPortHw8PAlarmMaskEntry OBJECT-TYPE
   SYNTAX      Er1646v2EthPortHw8PAlarmMaskEntry
   MAX-ACCESS  not-accessible
   STATUS      current
   DESCRIPTION
      ""
   INDEX      { er1646v2EthPortHw8PAlarmMaskGlobalIx }
   ::= {er1646v2EthPortHw8PAlarmMaskTable 1}

Er1646v2EthPortHw8PAlarmMaskEntry ::=
   SEQUENCE
      {
      er1646v2EthPortHw8PAlarmMaskGlobalIx
         GlobalIndex,
      er1646v2EthPortHw8PAlarmMaskValue
         Integer32
      }

er1646v2EthPortHw8PAlarmMaskGlobalIx OBJECT-TYPE
   SYNTAX      GlobalIndex
   MAX-ACCESS  not-accessible
   STATUS      current
   DESCRIPTION
      "The value of the tlsCntTreeGlobalIndex of the MANAGED OBJECT."
   ::= {er1646v2EthPortHw8PAlarmMaskEntry 10}

er1646v2EthPortHw8PAlarmMaskValue OBJECT-TYPE
   SYNTAX      Integer32
   MAX-ACCESS  read-write
   STATUS      current
   DESCRIPTION
      "Path: hwPort.editConf.alarmMask

       Bit meanings:
               bit 0 = linkDown"
   ::= {er1646v2EthPortHw8PAlarmMaskEntry 2147483648}


er1646v2EthPortHw8PAlarmLev OBJECT IDENTIFIER ::= {er1646v2EthPortHw8P 170}

er1646v2EthPortHw8PAlarmLevSSCTable OBJECT-TYPE
   SYNTAX      SEQUENCE OF Er1646v2EthPortHw8PAlarmLevEntry
   MAX-ACCESS  not-accessible
   STATUS      current
   DESCRIPTION
      "IfAlarmLevels"
   ::= {er1646v2EthPortHw8PAlarmLev 1}

er1646v2EthPortHw8PAlarmLevEntry OBJECT-TYPE
   SYNTAX      Er1646v2EthPortHw8PAlarmLevEntry
   MAX-ACCESS  not-accessible
   STATUS      current
   DESCRIPTION
      ""
   INDEX      { er1646v2EthPortHw8PAlarmLevGlobalIx }
   ::= {er1646v2EthPortHw8PAlarmLevSSCTable 1}

Er1646v2EthPortHw8PAlarmLevEntry ::=
   SEQUENCE
      {
      er1646v2EthPortHw8PAlarmLevGlobalIx
         GlobalIndex,
      er1646v2EthPortHw8PAlarmLevLinkDown
         Integer32
      }

er1646v2EthPortHw8PAlarmLevGlobalIx OBJECT-TYPE
   SYNTAX      GlobalIndex
   MAX-ACCESS  not-accessible
   STATUS      current
   DESCRIPTION
      "The value of the tlsCntTreeGlobalIndex of the MANAGED OBJECT."
   ::= {er1646v2EthPortHw8PAlarmLevEntry 10}

er1646v2EthPortHw8PAlarmLevLinkDown OBJECT-TYPE
   SYNTAX      Integer32
   MAX-ACCESS  read-write
   STATUS      current
   DESCRIPTION
      "Path: hwPort.editConf.alarmLevel.linkDown"
   ::= {er1646v2EthPortHw8PAlarmLevEntry 16777216}


er1646v2EthPortHw8PIbw OBJECT IDENTIFIER ::= {er1646v2EthPortHw8P 5}

er1646v2EthPortHw8PIbwSSCTable OBJECT-TYPE
   SYNTAX      SEQUENCE OF Er1646v2EthPortHw8PIbwEntry
   MAX-ACCESS  not-accessible
   STATUS      current
   DESCRIPTION
      ""
   ::= {er1646v2EthPortHw8PIbw 1}

er1646v2EthPortHw8PIbwEntry OBJECT-TYPE
   SYNTAX      Er1646v2EthPortHw8PIbwEntry
   MAX-ACCESS  not-accessible
   STATUS      current
   DESCRIPTION
      ""
   INDEX      { er1646v2EthPortHw8PIbwGlobalIx }
   ::= {er1646v2EthPortHw8PIbwSSCTable 1}

Er1646v2EthPortHw8PIbwEntry ::=
   SEQUENCE
      {
      er1646v2EthPortHw8PIbwGlobalIx
         GlobalIndex,
      er1646v2EthPortHw8PIbwCirRateLimit
         Integer32,
      er1646v2EthPortHw8PIbwCirTrafficLimitQueue1Type
         Integer32,
      er1646v2EthPortHw8PIbwCirTrafficLimitQueue1Cir
         Integer32,
      er1646v2EthPortHw8PIbwCirTrafficLimitQueue2Type
         Integer32,
      er1646v2EthPortHw8PIbwCirTrafficLimitQueue2Cir
         Integer32,
      er1646v2EthPortHw8PIbwCirQueueLimitQueue1Queues
         Integer32,
      er1646v2EthPortHw8PIbwCirQueueLimitQueue1Cir
         Integer32,
      er1646v2EthPortHw8PIbwCirQueueLimitQueue2Queues
         Integer32,
      er1646v2EthPortHw8PIbwCirQueueLimitQueue2Cir
         Integer32,
      er1646v2EthPortHw8PIbwCountMode
         INTEGER
      }

er1646v2EthPortHw8PIbwGlobalIx OBJECT-TYPE
   SYNTAX      GlobalIndex
   MAX-ACCESS  not-accessible
   STATUS      current
   DESCRIPTION
      "The value of the tlsCntTreeGlobalIndex of the MANAGED OBJECT."
   ::= {er1646v2EthPortHw8PIbwEntry 10}

er1646v2EthPortHw8PIbwCirRateLimit OBJECT-TYPE
   SYNTAX      Integer32
   MAX-ACCESS  read-write
   STATUS      current
   DESCRIPTION
      "Path: hwPort.editConf.inboundBandwidth.cir.rateLimit"
   ::= {er1646v2EthPortHw8PIbwEntry 16842752}

er1646v2EthPortHw8PIbwCirTrafficLimitQueue1Type OBJECT-TYPE
   SYNTAX      Integer32
   MAX-ACCESS  read-write
   STATUS      current
   DESCRIPTION
      "Path: hwPort.editConf.inboundBandwidth.cir.trafficLimit.queue1.type

       Bit meanings:
               bit 0 = unknownUnicasts,
               bit 1 = unknownMulticasts,
               bit 2 = broadcasts,
               bit 3 = multicasts,
               bit 4 = unicasts,
               bit 5 = mgmt,
               bit 7 = arp,
               bit 8 = tcpData,
               bit 9 = tcpCtrl,
               bit 10 = udp,
               bit 11 = nonTcpUdp"
   ::= {er1646v2EthPortHw8PIbwEntry 16908545}

er1646v2EthPortHw8PIbwCirTrafficLimitQueue1Cir OBJECT-TYPE
   SYNTAX      Integer32
   MAX-ACCESS  read-write
   STATUS      current
   DESCRIPTION
      "Path: hwPort.editConf.inboundBandwidth.cir.trafficLimit.queue1.cir"
   ::= {er1646v2EthPortHw8PIbwEntry 16908546}

er1646v2EthPortHw8PIbwCirTrafficLimitQueue2Type OBJECT-TYPE
   SYNTAX      Integer32
   MAX-ACCESS  read-write
   STATUS      current
   DESCRIPTION
      "Path: hwPort.editConf.inboundBandwidth.cir.trafficLimit.queue2.type

       Bit meanings:
               bit 0 = unknownUnicasts,
               bit 1 = unknownMulticasts,
               bit 2 = broadcasts,
               bit 3 = multicasts,
               bit 4 = unicasts,
               bit 5 = mgmt,
               bit 7 = arp,
               bit 8 = tcpData,
               bit 9 = tcpCtrl,
               bit 10 = udp,
               bit 11 = nonTcpUdp"
   ::= {er1646v2EthPortHw8PIbwEntry 16908801}

er1646v2EthPortHw8PIbwCirTrafficLimitQueue2Cir OBJECT-TYPE
   SYNTAX      Integer32
   MAX-ACCESS  read-write
   STATUS      current
   DESCRIPTION
      "Path: hwPort.editConf.inboundBandwidth.cir.trafficLimit.queue2.cir"
   ::= {er1646v2EthPortHw8PIbwEntry 16908802}

er1646v2EthPortHw8PIbwCirQueueLimitQueue1Queues OBJECT-TYPE
   SYNTAX      Integer32
   MAX-ACCESS  read-write
   STATUS      current
   DESCRIPTION
      "Path: hwPort.editConf.inboundBandwidth.cir.queueLimit.queue1.queues

       Bit meanings:
               bit 0 = queue1,
               bit 1 = queue2,
               bit 2 = queue3,
               bit 3 = queue4"
   ::= {er1646v2EthPortHw8PIbwEntry 16974081}

er1646v2EthPortHw8PIbwCirQueueLimitQueue1Cir OBJECT-TYPE
   SYNTAX      Integer32
   MAX-ACCESS  read-write
   STATUS      current
   DESCRIPTION
      "Path: hwPort.editConf.inboundBandwidth.cir.queueLimit.queue1.cir"
   ::= {er1646v2EthPortHw8PIbwEntry 16974082}

er1646v2EthPortHw8PIbwCirQueueLimitQueue2Queues OBJECT-TYPE
   SYNTAX      Integer32
   MAX-ACCESS  read-write
   STATUS      current
   DESCRIPTION
      "Path: hwPort.editConf.inboundBandwidth.cir.queueLimit.queue2.queues

       Bit meanings:
               bit 0 = queue1,
               bit 1 = queue2,
               bit 2 = queue3,
               bit 3 = queue4"
   ::= {er1646v2EthPortHw8PIbwEntry 16974337}

er1646v2EthPortHw8PIbwCirQueueLimitQueue2Cir OBJECT-TYPE
   SYNTAX      Integer32
   MAX-ACCESS  read-write
   STATUS      current
   DESCRIPTION
      "Path: hwPort.editConf.inboundBandwidth.cir.queueLimit.queue2.cir"
   ::= {er1646v2EthPortHw8PIbwEntry 16974338}

er1646v2EthPortHw8PIbwCountMode OBJECT-TYPE
   SYNTAX      INTEGER
               {
               layer1 (1),
               layer2 (2)
               }
   MAX-ACCESS  read-write
   STATUS      current
   DESCRIPTION
      "Path: hwPort.editConf.inboundBandwidth.countMode

       Possibilities:
               layer1   (1)
               layer2   (2)"
   ::= {er1646v2EthPortHw8PIbwEntry 33554432}


er1646v2EthPortHw8PSwPort OBJECT IDENTIFIER ::= {er1646v2EthPortHw8P 4}

er1646v2EthPortHw8PSwPortSSCTable OBJECT-TYPE
   SYNTAX      SEQUENCE OF Er1646v2EthPortHw8PSwPortEntry
   MAX-ACCESS  not-accessible
   STATUS      current
   DESCRIPTION
      ""
   ::= {er1646v2EthPortHw8PSwPort 1}

er1646v2EthPortHw8PSwPortEntry OBJECT-TYPE
   SYNTAX      Er1646v2EthPortHw8PSwPortEntry
   MAX-ACCESS  not-accessible
   STATUS      current
   DESCRIPTION
      ""
   INDEX      { er1646v2EthPortHw8PSwPortGlobalIx }
   ::= {er1646v2EthPortHw8PSwPortSSCTable 1}

Er1646v2EthPortHw8PSwPortEntry ::=
   SEQUENCE
      {
      er1646v2EthPortHw8PSwPortGlobalIx
         GlobalIndex,
      er1646v2EthPortHw8PSwPortInstance
         INTEGER
      }

er1646v2EthPortHw8PSwPortGlobalIx OBJECT-TYPE
   SYNTAX      GlobalIndex
   MAX-ACCESS  not-accessible
   STATUS      current
   DESCRIPTION
      "The value of the tlsCntTreeGlobalIndex of the MANAGED OBJECT."
   ::= {er1646v2EthPortHw8PSwPortEntry 10}

er1646v2EthPortHw8PSwPortInstance OBJECT-TYPE
   SYNTAX      INTEGER
               {
               auto (0)
               }
   MAX-ACCESS  read-write
   STATUS      current
   DESCRIPTION
      "Path: hwPort.editConf.swPort.instance

       Possibilities:
               auto   (0)"
   ::= {er1646v2EthPortHw8PSwPortEntry 16777216}


er1646v2EthPortHw8PAdapter OBJECT IDENTIFIER ::= {er1646v2EthPortHw8P 2}

er1646v2EthPortHw8PAdapterSSCTable OBJECT-TYPE
   SYNTAX      SEQUENCE OF Er1646v2EthPortHw8PAdapterEntry
   MAX-ACCESS  not-accessible
   STATUS      current
   DESCRIPTION
      "switch port adapter config"
   ::= {er1646v2EthPortHw8PAdapter 1}

er1646v2EthPortHw8PAdapterEntry OBJECT-TYPE
   SYNTAX      Er1646v2EthPortHw8PAdapterEntry
   MAX-ACCESS  not-accessible
   STATUS      current
   DESCRIPTION
      ""
   INDEX      { er1646v2EthPortHw8PAdapterGlobalIx }
   ::= {er1646v2EthPortHw8PAdapterSSCTable 1}

Er1646v2EthPortHw8PAdapterEntry ::=
   SEQUENCE
      {
      er1646v2EthPortHw8PAdapterGlobalIx
         GlobalIndex,
      er1646v2EthPortHw8PAdapterAN10HD
         INTEGER,
      er1646v2EthPortHw8PAdapterAN10FD
         INTEGER,
      er1646v2EthPortHw8PAdapterAN100HD
         INTEGER,
      er1646v2EthPortHw8PAdapterAN100FD
         INTEGER,
      er1646v2EthPortHw8PAdapterANFlCtrl
         INTEGER,
      er1646v2EthPortHw8PAdapterFix
         INTEGER
      }

er1646v2EthPortHw8PAdapterGlobalIx OBJECT-TYPE
   SYNTAX      GlobalIndex
   MAX-ACCESS  not-accessible
   STATUS      current
   DESCRIPTION
      "The value of the tlsCntTreeGlobalIndex of the MANAGED OBJECT."
   ::= {er1646v2EthPortHw8PAdapterEntry 10}

er1646v2EthPortHw8PAdapterAN10HD OBJECT-TYPE
   SYNTAX      INTEGER
               {
               disabled (0),
               enabled (1)
               }
   MAX-ACCESS  read-write
   STATUS      current
   DESCRIPTION
      "Path: hwPort.editConf.adapter.autoNegotiate.10Mb/halfDuplex

       Possibilities:
               disabled   (0)
               enabled   (1)"
   ::= {er1646v2EthPortHw8PAdapterEntry 16842752}

er1646v2EthPortHw8PAdapterAN10FD OBJECT-TYPE
   SYNTAX      INTEGER
               {
               disabled (0),
               enabled (1)
               }
   MAX-ACCESS  read-write
   STATUS      current
   DESCRIPTION
      "Path: hwPort.editConf.adapter.autoNegotiate.10Mb/fullDuplex

       Possibilities:
               disabled   (0)
               enabled   (1)"
   ::= {er1646v2EthPortHw8PAdapterEntry 16908288}

er1646v2EthPortHw8PAdapterAN100HD OBJECT-TYPE
   SYNTAX      INTEGER
               {
               disabled (0),
               enabled (1)
               }
   MAX-ACCESS  read-write
   STATUS      current
   DESCRIPTION
      "Path: hwPort.editConf.adapter.autoNegotiate.100Mb/halfDuplex

       Possibilities:
               disabled   (0)
               enabled   (1)"
   ::= {er1646v2EthPortHw8PAdapterEntry 16973824}

er1646v2EthPortHw8PAdapterAN100FD OBJECT-TYPE
   SYNTAX      INTEGER
               {
               disabled (0),
               enabled (1)
               }
   MAX-ACCESS  read-write
   STATUS      current
   DESCRIPTION
      "Path: hwPort.editConf.adapter.autoNegotiate.100Mb/fullDuplex

       Possibilities:
               disabled   (0)
               enabled   (1)"
   ::= {er1646v2EthPortHw8PAdapterEntry 17039360}

er1646v2EthPortHw8PAdapterANFlCtrl OBJECT-TYPE
   SYNTAX      INTEGER
               {
               disabled (0),
               enabled (1)
               }
   MAX-ACCESS  read-write
   STATUS      current
   DESCRIPTION
      "Path: hwPort.editConf.adapter.autoNegotiate.flowControl

       Possibilities:
               disabled   (0)
               enabled   (1)"
   ::= {er1646v2EthPortHw8PAdapterEntry 17104896}

er1646v2EthPortHw8PAdapterFix OBJECT-TYPE
   SYNTAX      INTEGER
               {
               s10MbhalfDuplex (1),
               s10MbfullDuplex (2),
               s100MbhalfDuplex (3),
               s100MbfullDuplex (4)
               }
   MAX-ACCESS  read-write
   STATUS      current
   DESCRIPTION
      "Path: hwPort.editConf.adapter.fixed

       Possibilities:
               10Mb/halfDuplex   (1)
               10Mb/fullDuplex   (2)
               100Mb/halfDuplex   (3)
               100Mb/fullDuplex   (4)"
   ::= {er1646v2EthPortHw8PAdapterEntry 33554432}


er1646v2EthPortHw8PPrivateHwPorts OBJECT IDENTIFIER ::= {er1646v2EthPortHw8P 29}

er1646v2EthPortHw8PPrivateHwPortsTable OBJECT-TYPE
   SYNTAX      SEQUENCE OF Er1646v2EthPortHw8PPrivateHwPortsEntry
   MAX-ACCESS  not-accessible
   STATUS      current
   DESCRIPTION
      ""
   ::= {er1646v2EthPortHw8PPrivateHwPorts 1}

er1646v2EthPortHw8PPrivateHwPortsEntry OBJECT-TYPE
   SYNTAX      Er1646v2EthPortHw8PPrivateHwPortsEntry
   MAX-ACCESS  not-accessible
   STATUS      current
   DESCRIPTION
      ""
   INDEX      { er1646v2EthPortHw8PPrivateHwPortsGlobalIx }
   ::= {er1646v2EthPortHw8PPrivateHwPortsTable 1}

Er1646v2EthPortHw8PPrivateHwPortsEntry ::=
   SEQUENCE
      {
      er1646v2EthPortHw8PPrivateHwPortsGlobalIx
         GlobalIndex,
      er1646v2EthPortHw8PPrivateHwPortsValue
         Integer32
      }

er1646v2EthPortHw8PPrivateHwPortsGlobalIx OBJECT-TYPE
   SYNTAX      GlobalIndex
   MAX-ACCESS  not-accessible
   STATUS      current
   DESCRIPTION
      "The value of the tlsCntTreeGlobalIndex of the MANAGED OBJECT."
   ::= {er1646v2EthPortHw8PPrivateHwPortsEntry 10}

er1646v2EthPortHw8PPrivateHwPortsValue OBJECT-TYPE
   SYNTAX      Integer32
   MAX-ACCESS  read-write
   STATUS      current
   DESCRIPTION
      "Path: hwPort.editConf.privateHwPorts

       Bit meanings:
               bit 0 = hwPort1,
               bit 1 = hwPort2,
               bit 2 = hwPort3,
               bit 3 = hwPort4,
               bit 4 = hwPort5,
               bit 5 = hwPort6,
               bit 6 = hwPort7,
               bit 7 = hwPort8"
   ::= {er1646v2EthPortHw8PPrivateHwPortsEntry 2147483648}



sr1646v2EthPortHw8P OBJECT IDENTIFIER ::= {r1646v2EthPortHw8P 14}


sr1646v2EthPortHw8PAdapter OBJECT IDENTIFIER ::= {sr1646v2EthPortHw8P 145}

sr1646v2EthPortHw8PAdapterSSCTable OBJECT-TYPE
   SYNTAX      SEQUENCE OF Sr1646v2EthPortHw8PAdapterEntry
   MAX-ACCESS  not-accessible
   STATUS      current
   DESCRIPTION
      ""
   ::= {sr1646v2EthPortHw8PAdapter 1}

sr1646v2EthPortHw8PAdapterEntry OBJECT-TYPE
   SYNTAX      Sr1646v2EthPortHw8PAdapterEntry
   MAX-ACCESS  not-accessible
   STATUS      current
   DESCRIPTION
      ""
   INDEX      { sr1646v2EthPortHw8PAdapterGlobalIx }
   ::= {sr1646v2EthPortHw8PAdapterSSCTable 1}

Sr1646v2EthPortHw8PAdapterEntry ::=
   SEQUENCE
      {
      sr1646v2EthPortHw8PAdapterGlobalIx
         GlobalIndex,
      sr1646v2EthPortHw8PAdapterSpeed
         INTEGER,
      sr1646v2EthPortHw8PAdapterDuplex
         INTEGER
      }

sr1646v2EthPortHw8PAdapterGlobalIx OBJECT-TYPE
   SYNTAX      GlobalIndex
   MAX-ACCESS  not-accessible
   STATUS      current
   DESCRIPTION
      "The value of the tlsCntTreeGlobalIndex of the MANAGED OBJECT."
   ::= {sr1646v2EthPortHw8PAdapterEntry 10}

sr1646v2EthPortHw8PAdapterSpeed OBJECT-TYPE
   SYNTAX      INTEGER
               {
               s10 (0),
               s100 (1),
               s1000 (2),
               s200 (3)
               }
   MAX-ACCESS  read-only
   STATUS      current
   DESCRIPTION
      "Path: hwPort.status.adapter.speed

       Possibilities:
               10   (0)
               100   (1)
               1000   (2)
               200   (3)"
   ::= {sr1646v2EthPortHw8PAdapterEntry 16777216}

sr1646v2EthPortHw8PAdapterDuplex OBJECT-TYPE
   SYNTAX      INTEGER
               {
               halfDuplex (0),
               fullDuplex (1)
               }
   MAX-ACCESS  read-only
   STATUS      current
   DESCRIPTION
      "Path: hwPort.status.adapter.duplex

       Possibilities:
               halfDuplex   (0)
               fullDuplex   (1)"
   ::= {sr1646v2EthPortHw8PAdapterEntry 33554432}


sr1646v2EthPortHw8PDescr OBJECT IDENTIFIER ::= {sr1646v2EthPortHw8P 101}

sr1646v2EthPortHw8PDescrTable OBJECT-TYPE
   SYNTAX      SEQUENCE OF Sr1646v2EthPortHw8PDescrEntry
   MAX-ACCESS  not-accessible
   STATUS      current
   DESCRIPTION
      "ifDescr"
   ::= {sr1646v2EthPortHw8PDescr 1}

sr1646v2EthPortHw8PDescrEntry OBJECT-TYPE
   SYNTAX      Sr1646v2EthPortHw8PDescrEntry
   MAX-ACCESS  not-accessible
   STATUS      current
   DESCRIPTION
      ""
   INDEX      { sr1646v2EthPortHw8PDescrGlobalIx }
   ::= {sr1646v2EthPortHw8PDescrTable 1}

Sr1646v2EthPortHw8PDescrEntry ::=
   SEQUENCE
      {
      sr1646v2EthPortHw8PDescrGlobalIx
         GlobalIndex,
      sr1646v2EthPortHw8PDescrValue
         DisplayString
      }

sr1646v2EthPortHw8PDescrGlobalIx OBJECT-TYPE
   SYNTAX      GlobalIndex
   MAX-ACCESS  not-accessible
   STATUS      current
   DESCRIPTION
      "The value of the tlsCntTreeGlobalIndex of the MANAGED OBJECT."
   ::= {sr1646v2EthPortHw8PDescrEntry 10}

sr1646v2EthPortHw8PDescrValue OBJECT-TYPE
   SYNTAX      DisplayString
   MAX-ACCESS  read-only
   STATUS      current
   DESCRIPTION
      "Path: hwPort.status.ifDescr"
   ::= {sr1646v2EthPortHw8PDescrEntry 2147483648}


sr1646v2EthPortHw8PType OBJECT IDENTIFIER ::= {sr1646v2EthPortHw8P 102}

sr1646v2EthPortHw8PTypeTable OBJECT-TYPE
   SYNTAX      SEQUENCE OF Sr1646v2EthPortHw8PTypeEntry
   MAX-ACCESS  not-accessible
   STATUS      current
   DESCRIPTION
      "ifType"
   ::= {sr1646v2EthPortHw8PType 1}

sr1646v2EthPortHw8PTypeEntry OBJECT-TYPE
   SYNTAX      Sr1646v2EthPortHw8PTypeEntry
   MAX-ACCESS  not-accessible
   STATUS      current
   DESCRIPTION
      ""
   INDEX      { sr1646v2EthPortHw8PTypeGlobalIx }
   ::= {sr1646v2EthPortHw8PTypeTable 1}

Sr1646v2EthPortHw8PTypeEntry ::=
   SEQUENCE
      {
      sr1646v2EthPortHw8PTypeGlobalIx
         GlobalIndex,
      sr1646v2EthPortHw8PTypeValue
         INTEGER
      }

sr1646v2EthPortHw8PTypeGlobalIx OBJECT-TYPE
   SYNTAX      GlobalIndex
   MAX-ACCESS  not-accessible
   STATUS      current
   DESCRIPTION
      "The value of the tlsCntTreeGlobalIndex of the MANAGED OBJECT."
   ::= {sr1646v2EthPortHw8PTypeEntry 10}

sr1646v2EthPortHw8PTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: hwPort.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2EthPortHw8PTypeEntry 2147483648}


sr1646v2EthPortHw8PMtu OBJECT IDENTIFIER ::= {sr1646v2EthPortHw8P 103}

sr1646v2EthPortHw8PMtuTable OBJECT-TYPE
   SYNTAX      SEQUENCE OF Sr1646v2EthPortHw8PMtuEntry
   MAX-ACCESS  not-accessible
   STATUS      current
   DESCRIPTION
      "ifMtu"
   ::= {sr1646v2EthPortHw8PMtu 1}

sr1646v2EthPortHw8PMtuEntry OBJECT-TYPE
   SYNTAX      Sr1646v2EthPortHw8PMtuEntry
   MAX-ACCESS  not-accessible
   STATUS      current
   DESCRIPTION
      ""
   INDEX      { sr1646v2EthPortHw8PMtuGlobalIx }
   ::= {sr1646v2EthPortHw8PMtuTable 1}

Sr1646v2EthPortHw8PMtuEntry ::=
   SEQUENCE
      {
      sr1646v2EthPortHw8PMtuGlobalIx
         GlobalIndex,
      sr1646v2EthPortHw8PMtuValue
         Integer32
      }

sr1646v2EthPortHw8PMtuGlobalIx OBJECT-TYPE
   SYNTAX      GlobalIndex
   MAX-ACCESS  not-accessible
   STATUS      current
   DESCRIPTION
      "The value of the tlsCntTreeGlobalIndex of the MANAGED OBJECT."
   ::= {sr1646v2EthPortHw8PMtuEntry 10}

sr1646v2EthPortHw8PMtuValue OBJECT-TYPE
   SYNTAX      Integer32
   MAX-ACCESS  read-only
   STATUS      current
   DESCRIPTION
      "Path: hwPort.status.ifMtu"
   ::= {sr1646v2EthPortHw8PMtuEntry 2147483648}


sr1646v2EthPortHw8POperStatus OBJECT IDENTIFIER ::= {sr1646v2EthPortHw8P 107}

sr1646v2EthPortHw8POperStatusTable OBJECT-TYPE
   SYNTAX      SEQUENCE OF Sr1646v2EthPortHw8POperStatusEntry
   MAX-ACCESS  not-accessible
   STATUS      current
   DESCRIPTION
      "ifOperStatus"
   ::= {sr1646v2EthPortHw8POperStatus 1}

sr1646v2EthPortHw8POperStatusEntry OBJECT-TYPE
   SYNTAX      Sr1646v2EthPortHw8POperStatusEntry
   MAX-ACCESS  not-accessible
   STATUS      current
   DESCRIPTION
      ""
   INDEX      { sr1646v2EthPortHw8POperStatusGlobalIx }
   ::= {sr1646v2EthPortHw8POperStatusTable 1}

Sr1646v2EthPortHw8POperStatusEntry ::=
   SEQUENCE
      {
      sr1646v2EthPortHw8POperStatusGlobalIx
         GlobalIndex,
      sr1646v2EthPortHw8POperStatusValue
         INTEGER
      }

sr1646v2EthPortHw8POperStatusGlobalIx OBJECT-TYPE
   SYNTAX      GlobalIndex
   MAX-ACCESS  not-accessible
   STATUS      current
   DESCRIPTION
      "The value of the tlsCntTreeGlobalIndex of the MANAGED OBJECT."
   ::= {sr1646v2EthPortHw8POperStatusEntry 10}

sr1646v2EthPortHw8POperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: hwPort.status.ifOperStatus

       Possibilities:
               up   (1)
               down   (2)
               testing   (3)
               unknown   (4)
               dormant   (5)
               notPresent   (6)
               lowerLayerDown   (7)"
   ::= {sr1646v2EthPortHw8POperStatusEntry 2147483648}


sr1646v2EthPortHw8PLastChange OBJECT IDENTIFIER ::= {sr1646v2EthPortHw8P 108}

sr1646v2EthPortHw8PLastChangeTable OBJECT-TYPE
   SYNTAX      SEQUENCE OF Sr1646v2EthPortHw8PLastChangeEntry
   MAX-ACCESS  not-accessible
   STATUS      current
   DESCRIPTION
      "ifLastChange"
   ::= {sr1646v2EthPortHw8PLastChange 1}

sr1646v2EthPortHw8PLastChangeEntry OBJECT-TYPE
   SYNTAX      Sr1646v2EthPortHw8PLastChangeEntry
   MAX-ACCESS  not-accessible
   STATUS      current
   DESCRIPTION
      ""
   INDEX      { sr1646v2EthPortHw8PLastChangeGlobalIx }
   ::= {sr1646v2EthPortHw8PLastChangeTable 1}

Sr1646v2EthPortHw8PLastChangeEntry ::=
   SEQUENCE
      {
      sr1646v2EthPortHw8PLastChangeGlobalIx
         GlobalIndex,
      sr1646v2EthPortHw8PLastChangeValue
         TimeTicks
      }

sr1646v2EthPortHw8PLastChangeGlobalIx OBJECT-TYPE
   SYNTAX      GlobalIndex
   MAX-ACCESS  not-accessible
   STATUS      current
   DESCRIPTION
      "The value of the tlsCntTreeGlobalIndex of the MANAGED OBJECT."
   ::= {sr1646v2EthPortHw8PLastChangeEntry 10}

sr1646v2EthPortHw8PLastChangeValue OBJECT-TYPE
   SYNTAX      TimeTicks
   MAX-ACCESS  read-only
   STATUS      current
   DESCRIPTION
      "Path: hwPort.status.ifLastChange

       Time in centi-second."
   ::= {sr1646v2EthPortHw8PLastChangeEntry 2147483648}


sr1646v2EthPortHw8PLastChangeD OBJECT IDENTIFIER ::= {sr1646v2EthPortHw8P 183}

sr1646v2EthPortHw8PLastChangeDTable OBJECT-TYPE
   SYNTAX      SEQUENCE OF Sr1646v2EthPortHw8PLastChangeDEntry
   MAX-ACCESS  not-accessible
   STATUS      current
   DESCRIPTION
      "ifLastChangeDate"
   ::= {sr1646v2EthPortHw8PLastChangeD 1}

sr1646v2EthPortHw8PLastChangeDEntry OBJECT-TYPE
   SYNTAX      Sr1646v2EthPortHw8PLastChangeDEntry
   MAX-ACCESS  not-accessible
   STATUS      current
   DESCRIPTION
      ""
   INDEX      { sr1646v2EthPortHw8PLastChangeDGlobalIx }
   ::= {sr1646v2EthPortHw8PLastChangeDTable 1}

Sr1646v2EthPortHw8PLastChangeDEntry ::=
   SEQUENCE
      {
      sr1646v2EthPortHw8PLastChangeDGlobalIx
         GlobalIndex,
      sr1646v2EthPortHw8PLastChangeDValue
         DisplayString
      }

sr1646v2EthPortHw8PLastChangeDGlobalIx OBJECT-TYPE
   SYNTAX      GlobalIndex
   MAX-ACCESS  not-accessible
   STATUS      current
   DESCRIPTION
      "The value of the tlsCntTreeGlobalIndex of the MANAGED OBJECT."
   ::= {sr1646v2EthPortHw8PLastChangeDEntry 10}

sr1646v2EthPortHw8PLastChangeDValue OBJECT-TYPE
   SYNTAX      DisplayString
   MAX-ACCESS  read-only
   STATUS      current
   DESCRIPTION
      "Path: hwPort.status.ifLastChangeDate"
   ::= {sr1646v2EthPortHw8PLastChangeDEntry 2147483648}


sr1646v2EthPortHw8PSpeed OBJECT IDENTIFIER ::= {sr1646v2EthPortHw8P 104}

sr1646v2EthPortHw8PSpeedTable OBJECT-TYPE
   SYNTAX      SEQUENCE OF Sr1646v2EthPortHw8PSpeedEntry
   MAX-ACCESS  not-accessible
   STATUS      current
   DESCRIPTION
      "ifSpeed"
   ::= {sr1646v2EthPortHw8PSpeed 1}

sr1646v2EthPortHw8PSpeedEntry OBJECT-TYPE
   SYNTAX      Sr1646v2EthPortHw8PSpeedEntry
   MAX-ACCESS  not-accessible
   STATUS      current
   DESCRIPTION
      ""
   INDEX      { sr1646v2EthPortHw8PSpeedGlobalIx }
   ::= {sr1646v2EthPortHw8PSpeedTable 1}

Sr1646v2EthPortHw8PSpeedEntry ::=
   SEQUENCE
      {
      sr1646v2EthPortHw8PSpeedGlobalIx
         GlobalIndex,
      sr1646v2EthPortHw8PSpeedValue
         Gauge32
      }

sr1646v2EthPortHw8PSpeedGlobalIx OBJECT-TYPE
   SYNTAX      GlobalIndex
   MAX-ACCESS  not-accessible
   STATUS      current
   DESCRIPTION
      "The value of the tlsCntTreeGlobalIndex of the MANAGED OBJECT."
   ::= {sr1646v2EthPortHw8PSpeedEntry 10}

sr1646v2EthPortHw8PSpeedValue OBJECT-TYPE
   SYNTAX      Gauge32
   MAX-ACCESS  read-only
   STATUS      current
   DESCRIPTION
      "Path: hwPort.status.ifSpeed

       32 bit unsigned gauge value."
   ::= {sr1646v2EthPortHw8PSpeedEntry 2147483648}


sr1646v2EthPortHw8PFlowControl OBJECT IDENTIFIER ::= {sr1646v2EthPortHw8P 850}

sr1646v2EthPortHw8PFlowControlSSCTable OBJECT-TYPE
   SYNTAX      SEQUENCE OF Sr1646v2EthPortHw8PFlowControlEntry
   MAX-ACCESS  not-accessible
   STATUS      current
   DESCRIPTION
      ""
   ::= {sr1646v2EthPortHw8PFlowControl 1}

sr1646v2EthPortHw8PFlowControlEntry OBJECT-TYPE
   SYNTAX      Sr1646v2EthPortHw8PFlowControlEntry
   MAX-ACCESS  not-accessible
   STATUS      current
   DESCRIPTION
      ""
   INDEX      { sr1646v2EthPortHw8PFlowControlGlobalIx }
   ::= {sr1646v2EthPortHw8PFlowControlSSCTable 1}

Sr1646v2EthPortHw8PFlowControlEntry ::=
   SEQUENCE
      {
      sr1646v2EthPortHw8PFlowControlGlobalIx
         GlobalIndex,
      sr1646v2EthPortHw8PFlowControlMode
         INTEGER,
      sr1646v2EthPortHw8PFlowControlNegotiated
         INTEGER
      }

sr1646v2EthPortHw8PFlowControlGlobalIx OBJECT-TYPE
   SYNTAX      GlobalIndex
   MAX-ACCESS  not-accessible
   STATUS      current
   DESCRIPTION
      "The value of the tlsCntTreeGlobalIndex of the MANAGED OBJECT."
   ::= {sr1646v2EthPortHw8PFlowControlEntry 10}

sr1646v2EthPortHw8PFlowControlMode OBJECT-TYPE
   SYNTAX      INTEGER
               {
               disabled (0),
               enabled (1)
               }
   MAX-ACCESS  read-only
   STATUS      current
   DESCRIPTION
      "Path: hwPort.status.flowControl.mode

       Possibilities:
               disabled   (0)
               enabled   (1)"
   ::= {sr1646v2EthPortHw8PFlowControlEntry 16777216}

sr1646v2EthPortHw8PFlowControlNegotiated OBJECT-TYPE
   SYNTAX      INTEGER
               {
               no (0),
               yes (1)
               }
   MAX-ACCESS  read-only
   STATUS      current
   DESCRIPTION
      "Path: hwPort.status.flowControl.negotiated

       Possibilities:
               no   (0)
               yes   (1)"
   ::= {sr1646v2EthPortHw8PFlowControlEntry 33554432}


sr1646v2EthPortHw8PSnmpIndex OBJECT IDENTIFIER ::= {sr1646v2EthPortHw8P 269}

sr1646v2EthPortHw8PSnmpIndexTable OBJECT-TYPE
   SYNTAX      SEQUENCE OF Sr1646v2EthPortHw8PSnmpIndexEntry
   MAX-ACCESS  not-accessible
   STATUS      current
   DESCRIPTION
      "SNMP index assigned to this object"
   ::= {sr1646v2EthPortHw8PSnmpIndex 1}

sr1646v2EthPortHw8PSnmpIndexEntry OBJECT-TYPE
   SYNTAX      Sr1646v2EthPortHw8PSnmpIndexEntry
   MAX-ACCESS  not-accessible
   STATUS      current
   DESCRIPTION
      ""
   INDEX      { sr1646v2EthPortHw8PSnmpIndexGlobalIx }
   ::= {sr1646v2EthPortHw8PSnmpIndexTable 1}

Sr1646v2EthPortHw8PSnmpIndexEntry ::=
   SEQUENCE
      {
      sr1646v2EthPortHw8PSnmpIndexGlobalIx
         GlobalIndex,
      sr1646v2EthPortHw8PSnmpIndexValue
         Integer32
      }

sr1646v2EthPortHw8PSnmpIndexGlobalIx OBJECT-TYPE
   SYNTAX      GlobalIndex
   MAX-ACCESS  not-accessible
   STATUS      current
   DESCRIPTION
      "The value of the tlsCntTreeGlobalIndex of the MANAGED OBJECT."
   ::= {sr1646v2EthPortHw8PSnmpIndexEntry 10}

sr1646v2EthPortHw8PSnmpIndexValue OBJECT-TYPE
   SYNTAX      Integer32
   MAX-ACCESS  read-only
   STATUS      current
   DESCRIPTION
      "Path: hwPort.status.snmpIndex"
   ::= {sr1646v2EthPortHw8PSnmpIndexEntry 2147483648}


sr1646v2EthPortHw8PAutoNegotiate OBJECT IDENTIFIER ::= {sr1646v2EthPortHw8P 148}

sr1646v2EthPortHw8PAutoNegotiateTable OBJECT-TYPE
   SYNTAX      SEQUENCE OF Sr1646v2EthPortHw8PAutoNegotiateEntry
   MAX-ACCESS  not-accessible
   STATUS      current
   DESCRIPTION
      ""
   ::= {sr1646v2EthPortHw8PAutoNegotiate 1}

sr1646v2EthPortHw8PAutoNegotiateEntry OBJECT-TYPE
   SYNTAX      Sr1646v2EthPortHw8PAutoNegotiateEntry
   MAX-ACCESS  not-accessible
   STATUS      current
   DESCRIPTION
      ""
   INDEX      { sr1646v2EthPortHw8PAutoNegotiateGlobalIx }
   ::= {sr1646v2EthPortHw8PAutoNegotiateTable 1}

Sr1646v2EthPortHw8PAutoNegotiateEntry ::=
   SEQUENCE
      {
      sr1646v2EthPortHw8PAutoNegotiateGlobalIx
         GlobalIndex,
      sr1646v2EthPortHw8PAutoNegotiateValue
         INTEGER
      }

sr1646v2EthPortHw8PAutoNegotiateGlobalIx OBJECT-TYPE
   SYNTAX      GlobalIndex
   MAX-ACCESS  not-accessible
   STATUS      current
   DESCRIPTION
      "The value of the tlsCntTreeGlobalIndex of the MANAGED OBJECT."
   ::= {sr1646v2EthPortHw8PAutoNegotiateEntry 10}

sr1646v2EthPortHw8PAutoNegotiateValue OBJECT-TYPE
   SYNTAX      INTEGER
               {
               disabled (0),
               done (1),
               notDone (2)
               }
   MAX-ACCESS  read-only
   STATUS      current
   DESCRIPTION
      "Path: hwPort.status.autoNegotiate

       Possibilities:
               disabled   (0)
               done   (1)
               notDone   (2)"
   ::= {sr1646v2EthPortHw8PAutoNegotiateEntry 2147483648}


sr1646v2EthPortHw8PPartnerCaps OBJECT IDENTIFIER ::= {sr1646v2EthPortHw8P 147}

sr1646v2EthPortHw8PPartnerCapsSSCTable OBJECT-TYPE
   SYNTAX      SEQUENCE OF Sr1646v2EthPortHw8PPartnerCapsEntry
   MAX-ACCESS  not-accessible
   STATUS      current
   DESCRIPTION
      ""
   ::= {sr1646v2EthPortHw8PPartnerCaps 1}

sr1646v2EthPortHw8PPartnerCapsEntry OBJECT-TYPE
   SYNTAX      Sr1646v2EthPortHw8PPartnerCapsEntry
   MAX-ACCESS  not-accessible
   STATUS      current
   DESCRIPTION
      ""
   INDEX      { sr1646v2EthPortHw8PPartnerCapsGlobalIx }
   ::= {sr1646v2EthPortHw8PPartnerCapsSSCTable 1}

Sr1646v2EthPortHw8PPartnerCapsEntry ::=
   SEQUENCE
      {
      sr1646v2EthPortHw8PPartnerCapsGlobalIx
         GlobalIndex,
      sr1646v2EthPortHw8PPartnerCapsFlowCtrl
         INTEGER,
      sr1646v2EthPortHw8PPartnerCapsHD10
         INTEGER,
      sr1646v2EthPortHw8PPartnerCapsFD10
         INTEGER,
      sr1646v2EthPortHw8PPartnerCapsHD100
         INTEGER,
      sr1646v2EthPortHw8PPartnerCapsFD100
         INTEGER,
      sr1646v2EthPortHw8PPartnerCapsFD1000
         INTEGER
      }

sr1646v2EthPortHw8PPartnerCapsGlobalIx OBJECT-TYPE
   SYNTAX      GlobalIndex
   MAX-ACCESS  not-accessible
   STATUS      current
   DESCRIPTION
      "The value of the tlsCntTreeGlobalIndex of the MANAGED OBJECT."
   ::= {sr1646v2EthPortHw8PPartnerCapsEntry 10}

sr1646v2EthPortHw8PPartnerCapsFlowCtrl OBJECT-TYPE
   SYNTAX      INTEGER
               {
               notCapable (0),
               capable (1),
               unknown (2)
               }
   MAX-ACCESS  read-only
   STATUS      current
   DESCRIPTION
      "Path: hwPort.status.linkPartnerCaps.flowControl

       Possibilities:
               notCapable   (0)
               capable   (1)
               unknown   (2)"
   ::= {sr1646v2EthPortHw8PPartnerCapsEntry 16777216}

sr1646v2EthPortHw8PPartnerCapsHD10 OBJECT-TYPE
   SYNTAX      INTEGER
               {
               notCapable (0),
               capable (1),
               unknown (2)
               }
   MAX-ACCESS  read-only
   STATUS      current
   DESCRIPTION
      "Path: hwPort.status.linkPartnerCaps.10Mb/halfDuplex

       Possibilities:
               notCapable   (0)
               capable   (1)
               unknown   (2)"
   ::= {sr1646v2EthPortHw8PPartnerCapsEntry 33554432}

sr1646v2EthPortHw8PPartnerCapsFD10 OBJECT-TYPE
   SYNTAX      INTEGER
               {
               notCapable (0),
               capable (1),
               unknown (2)
               }
   MAX-ACCESS  read-only
   STATUS      current
   DESCRIPTION
      "Path: hwPort.status.linkPartnerCaps.10Mb/fullDuplex

       Possibilities:
               notCapable   (0)
               capable   (1)
               unknown   (2)"
   ::= {sr1646v2EthPortHw8PPartnerCapsEntry 50331648}

sr1646v2EthPortHw8PPartnerCapsHD100 OBJECT-TYPE
   SYNTAX      INTEGER
               {
               notCapable (0),
               capable (1),
               unknown (2)
               }
   MAX-ACCESS  read-only
   STATUS      current
   DESCRIPTION
      "Path: hwPort.status.linkPartnerCaps.100Mb/halfDuplex

       Possibilities:
               notCapable   (0)
               capable   (1)
               unknown   (2)"
   ::= {sr1646v2EthPortHw8PPartnerCapsEntry 67108864}

sr1646v2EthPortHw8PPartnerCapsFD100 OBJECT-TYPE
   SYNTAX      INTEGER
               {
               notCapable (0),
               capable (1),
               unknown (2)
               }
   MAX-ACCESS  read-only
   STATUS      current
   DESCRIPTION
      "Path: hwPort.status.linkPartnerCaps.100Mb/fullDuplex

       Possibilities:
               notCapable   (0)
               capable   (1)
               unknown   (2)"
   ::= {sr1646v2EthPortHw8PPartnerCapsEntry 83886080}

sr1646v2EthPortHw8PPartnerCapsFD1000 OBJECT-TYPE
   SYNTAX      INTEGER
               {
               notCapable (0),
               capable (1),
               unknown (2)
               }
   MAX-ACCESS  read-only
   STATUS      current
   DESCRIPTION
      "Path: hwPort.status.linkPartnerCaps.1000Mb/fullDuplex

       Possibilities:
               notCapable   (0)
               capable   (1)
               unknown   (2)"
   ::= {sr1646v2EthPortHw8PPartnerCapsEntry 100663296}



pr1646v2EthPortHw8P OBJECT IDENTIFIER ::= {r1646v2EthPortHw8P 12}


pr1646v2EthPortHw8PInOctets OBJECT IDENTIFIER ::= {pr1646v2EthPortHw8P 109}

pr1646v2EthPortHw8PInOctetsTable OBJECT-TYPE
   SYNTAX      SEQUENCE OF Pr1646v2EthPortHw8PInOctetsEntry
   MAX-ACCESS  not-accessible
   STATUS      current
   DESCRIPTION
      "ifInOctets"
   ::= {pr1646v2EthPortHw8PInOctets 1}

pr1646v2EthPortHw8PInOctetsEntry OBJECT-TYPE
   SYNTAX      Pr1646v2EthPortHw8PInOctetsEntry
   MAX-ACCESS  not-accessible
   STATUS      current
   DESCRIPTION
      ""
   INDEX      { pr1646v2EthPortHw8PInOctetsGlobalIx }
   ::= {pr1646v2EthPortHw8PInOctetsTable 1}

Pr1646v2EthPortHw8PInOctetsEntry ::=
   SEQUENCE
      {
      pr1646v2EthPortHw8PInOctetsGlobalIx
         GlobalIndex,
      pr1646v2EthPortHw8PInOctetsValue
         Counter64
      }

pr1646v2EthPortHw8PInOctetsGlobalIx OBJECT-TYPE
   SYNTAX      GlobalIndex
   MAX-ACCESS  not-accessible
   STATUS      current
   DESCRIPTION
      "The value of the tlsCntTreeGlobalIndex of the MANAGED OBJECT."
   ::= {pr1646v2EthPortHw8PInOctetsEntry 10}

pr1646v2EthPortHw8PInOctetsValue OBJECT-TYPE
   SYNTAX      Counter64
   MAX-ACCESS  read-only
   STATUS      current
   DESCRIPTION
      "Path: hwPort.performance.ifInOctets

       64 bit unsigned wrappable counter."
   ::= {pr1646v2EthPortHw8PInOctetsEntry 2147483648}


pr1646v2EthPortHw8PInUcast OBJECT IDENTIFIER ::= {pr1646v2EthPortHw8P 110}

pr1646v2EthPortHw8PInUcastTable OBJECT-TYPE
   SYNTAX      SEQUENCE OF Pr1646v2EthPortHw8PInUcastEntry
   MAX-ACCESS  not-accessible
   STATUS      current
   DESCRIPTION
      "ifInUcastPkts"
   ::= {pr1646v2EthPortHw8PInUcast 1}

pr1646v2EthPortHw8PInUcastEntry OBJECT-TYPE
   SYNTAX      Pr1646v2EthPortHw8PInUcastEntry
   MAX-ACCESS  not-accessible
   STATUS      current
   DESCRIPTION
      ""
   INDEX      { pr1646v2EthPortHw8PInUcastGlobalIx }
   ::= {pr1646v2EthPortHw8PInUcastTable 1}

Pr1646v2EthPortHw8PInUcastEntry ::=
   SEQUENCE
      {
      pr1646v2EthPortHw8PInUcastGlobalIx
         GlobalIndex,
      pr1646v2EthPortHw8PInUcastValue
         Counter64
      }

pr1646v2EthPortHw8PInUcastGlobalIx OBJECT-TYPE
   SYNTAX      GlobalIndex
   MAX-ACCESS  not-accessible
   STATUS      current
   DESCRIPTION
      "The value of the tlsCntTreeGlobalIndex of the MANAGED OBJECT."
   ::= {pr1646v2EthPortHw8PInUcastEntry 10}

pr1646v2EthPortHw8PInUcastValue OBJECT-TYPE
   SYNTAX      Counter64
   MAX-ACCESS  read-only
   STATUS      current
   DESCRIPTION
      "Path: hwPort.performance.ifInUcastPkts

       64 bit unsigned wrappable counter."
   ::= {pr1646v2EthPortHw8PInUcastEntry 2147483648}


pr1646v2EthPortHw8PInNUcastPkts OBJECT IDENTIFIER ::= {pr1646v2EthPortHw8P 111}

pr1646v2EthPortHw8PInNUcastPktsTable OBJECT-TYPE
   SYNTAX      SEQUENCE OF Pr1646v2EthPortHw8PInNUcastPktsEntry
   MAX-ACCESS  not-accessible
   STATUS      current
   DESCRIPTION
      "ifInNUcastPkts"
   ::= {pr1646v2EthPortHw8PInNUcastPkts 1}

pr1646v2EthPortHw8PInNUcastPktsEntry OBJECT-TYPE
   SYNTAX      Pr1646v2EthPortHw8PInNUcastPktsEntry
   MAX-ACCESS  not-accessible
   STATUS      current
   DESCRIPTION
      ""
   INDEX      { pr1646v2EthPortHw8PInNUcastPktsGlobalIx }
   ::= {pr1646v2EthPortHw8PInNUcastPktsTable 1}

Pr1646v2EthPortHw8PInNUcastPktsEntry ::=
   SEQUENCE
      {
      pr1646v2EthPortHw8PInNUcastPktsGlobalIx
         GlobalIndex,
      pr1646v2EthPortHw8PInNUcastPktsValue
         Counter64
      }

pr1646v2EthPortHw8PInNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortHw8PInNUcastPktsEntry 10}

pr1646v2EthPortHw8PInNUcastPktsValue OBJECT-TYPE
   SYNTAX      Counter64
   MAX-ACCESS  read-only
   STATUS      current
   DESCRIPTION
      "Path: hwPort.performance.ifInNUcastPkts

       64 bit unsigned wrappable counter."
   ::= {pr1646v2EthPortHw8PInNUcastPktsEntry 2147483648}


pr1646v2EthPortHw8PInDiscards OBJECT IDENTIFIER ::= {pr1646v2EthPortHw8P 112}

pr1646v2EthPortHw8PInDiscardsTable OBJECT-TYPE
   SYNTAX      SEQUENCE OF Pr1646v2EthPortHw8PInDiscardsEntry
   MAX-ACCESS  not-accessible
   STATUS      current
   DESCRIPTION
      "ifInDiscards"
   ::= {pr1646v2EthPortHw8PInDiscards 1}

pr1646v2EthPortHw8PInDiscardsEntry OBJECT-TYPE
   SYNTAX      Pr1646v2EthPortHw8PInDiscardsEntry
   MAX-ACCESS  not-accessible
   STATUS      current
   DESCRIPTION
      ""
   INDEX      { pr1646v2EthPortHw8PInDiscardsGlobalIx }
   ::= {pr1646v2EthPortHw8PInDiscardsTable 1}

Pr1646v2EthPortHw8PInDiscardsEntry ::=
   SEQUENCE
      {
      pr1646v2EthPortHw8PInDiscardsGlobalIx
         GlobalIndex,
      pr1646v2EthPortHw8PInDiscardsValue
         Counter64
      }

pr1646v2EthPortHw8PInDiscardsGlobalIx OBJECT-TYPE
   SYNTAX      GlobalIndex
   MAX-ACCESS  not-accessible
   STATUS      current
   DESCRIPTION
      "The value of the tlsCntTreeGlobalIndex of the MANAGED OBJECT."
   ::= {pr1646v2EthPortHw8PInDiscardsEntry 10}

pr1646v2EthPortHw8PInDiscardsValue OBJECT-TYPE
   SYNTAX      Counter64
   MAX-ACCESS  read-only
   STATUS      current
   DESCRIPTION
      "Path: hwPort.performance.ifInDiscards

       64 bit unsigned wrappable counter."
   ::= {pr1646v2EthPortHw8PInDiscardsEntry 2147483648}


pr1646v2EthPortHw8PIfInPause OBJECT IDENTIFIER ::= {pr1646v2EthPortHw8P 250}

pr1646v2EthPortHw8PIfInPauseTable OBJECT-TYPE
   SYNTAX      SEQUENCE OF Pr1646v2EthPortHw8PIfInPauseEntry
   MAX-ACCESS  not-accessible
   STATUS      current
   DESCRIPTION
      "hwPortCounter"
   ::= {pr1646v2EthPortHw8PIfInPause 1}

pr1646v2EthPortHw8PIfInPauseEntry OBJECT-TYPE
   SYNTAX      Pr1646v2EthPortHw8PIfInPauseEntry
   MAX-ACCESS  not-accessible
   STATUS      current
   DESCRIPTION
      ""
   INDEX      { pr1646v2EthPortHw8PIfInPauseGlobalIx }
   ::= {pr1646v2EthPortHw8PIfInPauseTable 1}

Pr1646v2EthPortHw8PIfInPauseEntry ::=
   SEQUENCE
      {
      pr1646v2EthPortHw8PIfInPauseGlobalIx
         GlobalIndex,
      pr1646v2EthPortHw8PIfInPauseValue
         Counter64
      }

pr1646v2EthPortHw8PIfInPauseGlobalIx OBJECT-TYPE
   SYNTAX      GlobalIndex
   MAX-ACCESS  not-accessible
   STATUS      current
   DESCRIPTION
      "The value of the tlsCntTreeGlobalIndex of the MANAGED OBJECT."
   ::= {pr1646v2EthPortHw8PIfInPauseEntry 10}

pr1646v2EthPortHw8PIfInPauseValue OBJECT-TYPE
   SYNTAX      Counter64
   MAX-ACCESS  read-only
   STATUS      current
   DESCRIPTION
      "Path: hwPort.performance.ifInPause

       64 bit unsigned wrappable counter."
   ::= {pr1646v2EthPortHw8PIfInPauseEntry 2147483648}


pr1646v2EthPortHw8PIfInFiltered OBJECT IDENTIFIER ::= {pr1646v2EthPortHw8P 834}

pr1646v2EthPortHw8PIfInFilteredTable OBJECT-TYPE
   SYNTAX      SEQUENCE OF Pr1646v2EthPortHw8PIfInFilteredEntry
   MAX-ACCESS  not-accessible
   STATUS      current
   DESCRIPTION
      "hwPortCounter"
   ::= {pr1646v2EthPortHw8PIfInFiltered 1}

pr1646v2EthPortHw8PIfInFilteredEntry OBJECT-TYPE
   SYNTAX      Pr1646v2EthPortHw8PIfInFilteredEntry
   MAX-ACCESS  not-accessible
   STATUS      current
   DESCRIPTION
      ""
   INDEX      { pr1646v2EthPortHw8PIfInFilteredGlobalIx }
   ::= {pr1646v2EthPortHw8PIfInFilteredTable 1}

Pr1646v2EthPortHw8PIfInFilteredEntry ::=
   SEQUENCE
      {
      pr1646v2EthPortHw8PIfInFilteredGlobalIx
         GlobalIndex,
      pr1646v2EthPortHw8PIfInFilteredValue
         Counter64
      }

pr1646v2EthPortHw8PIfInFilteredGlobalIx OBJECT-TYPE
   SYNTAX      GlobalIndex
   MAX-ACCESS  not-accessible
   STATUS      current
   DESCRIPTION
      "The value of the tlsCntTreeGlobalIndex of the MANAGED OBJECT."
   ::= {pr1646v2EthPortHw8PIfInFilteredEntry 10}

pr1646v2EthPortHw8PIfInFilteredValue OBJECT-TYPE
   SYNTAX      Counter64
   MAX-ACCESS  read-only
   STATUS      current
   DESCRIPTION
      "Path: hwPort.performance.ifInFiltered

       64 bit unsigned wrappable counter."
   ::= {pr1646v2EthPortHw8PIfInFilteredEntry 2147483648}


pr1646v2EthPortHw8PInErrors OBJECT IDENTIFIER ::= {pr1646v2EthPortHw8P 113}

pr1646v2EthPortHw8PInErrorsTable OBJECT-TYPE
   SYNTAX      SEQUENCE OF Pr1646v2EthPortHw8PInErrorsEntry
   MAX-ACCESS  not-accessible
   STATUS      current
   DESCRIPTION
      "ifInErrors"
   ::= {pr1646v2EthPortHw8PInErrors 1}

pr1646v2EthPortHw8PInErrorsEntry OBJECT-TYPE
   SYNTAX      Pr1646v2EthPortHw8PInErrorsEntry
   MAX-ACCESS  not-accessible
   STATUS      current
   DESCRIPTION
      ""
   INDEX      { pr1646v2EthPortHw8PInErrorsGlobalIx }
   ::= {pr1646v2EthPortHw8PInErrorsTable 1}

Pr1646v2EthPortHw8PInErrorsEntry ::=
   SEQUENCE
      {
      pr1646v2EthPortHw8PInErrorsGlobalIx
         GlobalIndex,
      pr1646v2EthPortHw8PInErrorsValue
         Counter64
      }

pr1646v2EthPortHw8PInErrorsGlobalIx OBJECT-TYPE
   SYNTAX      GlobalIndex
   MAX-ACCESS  not-accessible
   STATUS      current
   DESCRIPTION
      "The value of the tlsCntTreeGlobalIndex of the MANAGED OBJECT."
   ::= {pr1646v2EthPortHw8PInErrorsEntry 10}

pr1646v2EthPortHw8PInErrorsValue OBJECT-TYPE
   SYNTAX      Counter64
   MAX-ACCESS  read-only
   STATUS      current
   DESCRIPTION
      "Path: hwPort.performance.ifInErrors

       64 bit unsigned wrappable counter."
   ::= {pr1646v2EthPortHw8PInErrorsEntry 2147483648}


pr1646v2EthPortHw8PInBandwidth OBJECT IDENTIFIER ::= {pr1646v2EthPortHw8P 181}

pr1646v2EthPortHw8PInBandwidthSSCTable OBJECT-TYPE
   SYNTAX      SEQUENCE OF Pr1646v2EthPortHw8PInBandwidthEntry
   MAX-ACCESS  not-accessible
   STATUS      current
   DESCRIPTION
      "bandwidth"
   ::= {pr1646v2EthPortHw8PInBandwidth 1}

pr1646v2EthPortHw8PInBandwidthEntry OBJECT-TYPE
   SYNTAX      Pr1646v2EthPortHw8PInBandwidthEntry
   MAX-ACCESS  not-accessible
   STATUS      current
   DESCRIPTION
      ""
   INDEX      { pr1646v2EthPortHw8PInBandwidthGlobalIx }
   ::= {pr1646v2EthPortHw8PInBandwidthSSCTable 1}

Pr1646v2EthPortHw8PInBandwidthEntry ::=
   SEQUENCE
      {
      pr1646v2EthPortHw8PInBandwidthGlobalIx
         GlobalIndex,
      pr1646v2EthPortHw8PInBandwidth15sec
         Integer32,
      pr1646v2EthPortHw8PInBandwidth30sec
         Integer32,
      pr1646v2EthPortHw8PInBandwidth1min
         Integer32,
      pr1646v2EthPortHw8PInBandwidth2min
         Integer32,
      pr1646v2EthPortHw8PInBandwidth5min
         Integer32
      }

pr1646v2EthPortHw8PInBandwidthGlobalIx OBJECT-TYPE
   SYNTAX      GlobalIndex
   MAX-ACCESS  not-accessible
   STATUS      current
   DESCRIPTION
      "The value of the tlsCntTreeGlobalIndex of the MANAGED OBJECT."
   ::= {pr1646v2EthPortHw8PInBandwidthEntry 10}

pr1646v2EthPortHw8PInBandwidth15sec OBJECT-TYPE
   SYNTAX      Integer32
   MAX-ACCESS  read-only
   STATUS      current
   DESCRIPTION
      "Path: hwPort.performance.ifInBandwidth.15sec

       unit name = bps
       formula = 8 * ; 8 /"
   ::= {pr1646v2EthPortHw8PInBandwidthEntry 83886080}

pr1646v2EthPortHw8PInBandwidth30sec OBJECT-TYPE
   SYNTAX      Integer32
   MAX-ACCESS  read-only
   STATUS      current
   DESCRIPTION
      "Path: hwPort.performance.ifInBandwidth.30sec

       unit name = bps
       formula = 8 * ; 8 /"
   ::= {pr1646v2EthPortHw8PInBandwidthEntry 167772160}

pr1646v2EthPortHw8PInBandwidth1min OBJECT-TYPE
   SYNTAX      Integer32
   MAX-ACCESS  read-only
   STATUS      current
   DESCRIPTION
      "Path: hwPort.performance.ifInBandwidth.1min

       unit name = bps
       formula = 8 * ; 8 /"
   ::= {pr1646v2EthPortHw8PInBandwidthEntry 335544320}

pr1646v2EthPortHw8PInBandwidth2min OBJECT-TYPE
   SYNTAX      Integer32
   MAX-ACCESS  read-only
   STATUS      current
   DESCRIPTION
      "Path: hwPort.performance.ifInBandwidth.2min

       unit name = bps
       formula = 8 * ; 8 /"
   ::= {pr1646v2EthPortHw8PInBandwidthEntry 671088640}

pr1646v2EthPortHw8PInBandwidth5min OBJECT-TYPE
   SYNTAX      Integer32
   MAX-ACCESS  read-only
   STATUS      current
   DESCRIPTION
      "Path: hwPort.performance.ifInBandwidth.5min

       unit name = bps
       formula = 8 * ; 8 /"
   ::= {pr1646v2EthPortHw8PInBandwidthEntry 1677721600}


pr1646v2EthPortHw8POutOctets OBJECT IDENTIFIER ::= {pr1646v2EthPortHw8P 115}

pr1646v2EthPortHw8POutOctetsTable OBJECT-TYPE
   SYNTAX      SEQUENCE OF Pr1646v2EthPortHw8POutOctetsEntry
   MAX-ACCESS  not-accessible
   STATUS      current
   DESCRIPTION
      "ifOutOctets"
   ::= {pr1646v2EthPortHw8POutOctets 1}

pr1646v2EthPortHw8POutOctetsEntry OBJECT-TYPE
   SYNTAX      Pr1646v2EthPortHw8POutOctetsEntry
   MAX-ACCESS  not-accessible
   STATUS      current
   DESCRIPTION
      ""
   INDEX      { pr1646v2EthPortHw8POutOctetsGlobalIx }
   ::= {pr1646v2EthPortHw8POutOctetsTable 1}

Pr1646v2EthPortHw8POutOctetsEntry ::=
   SEQUENCE
      {
      pr1646v2EthPortHw8POutOctetsGlobalIx
         GlobalIndex,
      pr1646v2EthPortHw8POutOctetsValue
         Counter64
      }

pr1646v2EthPortHw8POutOctetsGlobalIx OBJECT-TYPE
   SYNTAX      GlobalIndex
   MAX-ACCESS  not-accessible
   STATUS      current
   DESCRIPTION
      "The value of the tlsCntTreeGlobalIndex of the MANAGED OBJECT."
   ::= {pr1646v2EthPortHw8POutOctetsEntry 10}

pr1646v2EthPortHw8POutOctetsValue OBJECT-TYPE
   SYNTAX      Counter64
   MAX-ACCESS  read-only
   STATUS      current
   DESCRIPTION
      "Path: hwPort.performance.ifOutOctets

       64 bit unsigned wrappable counter."
   ::= {pr1646v2EthPortHw8POutOctetsEntry 2147483648}


pr1646v2EthPortHw8POutUcastPkts OBJECT IDENTIFIER ::= {pr1646v2EthPortHw8P 116}

pr1646v2EthPortHw8POutUcastPktsTable OBJECT-TYPE
   SYNTAX      SEQUENCE OF Pr1646v2EthPortHw8POutUcastPktsEntry
   MAX-ACCESS  not-accessible
   STATUS      current
   DESCRIPTION
      "ifOutUcastPkts"
   ::= {pr1646v2EthPortHw8POutUcastPkts 1}

pr1646v2EthPortHw8POutUcastPktsEntry OBJECT-TYPE
   SYNTAX      Pr1646v2EthPortHw8POutUcastPktsEntry
   MAX-ACCESS  not-accessible
   STATUS      current
   DESCRIPTION
      ""
   INDEX      { pr1646v2EthPortHw8POutUcastPktsGlobalIx }
   ::= {pr1646v2EthPortHw8POutUcastPktsTable 1}

Pr1646v2EthPortHw8POutUcastPktsEntry ::=
   SEQUENCE
      {
      pr1646v2EthPortHw8POutUcastPktsGlobalIx
         GlobalIndex,
      pr1646v2EthPortHw8POutUcastPktsValue
         Counter64
      }

pr1646v2EthPortHw8POutUcastPktsGlobalIx OBJECT-TYPE
   SYNTAX      GlobalIndex
   MAX-ACCESS  not-accessible
   STATUS      current
   DESCRIPTION
      "The value of the tlsCntTreeGlobalIndex of the MANAGED OBJECT."
   ::= {pr1646v2EthPortHw8POutUcastPktsEntry 10}

pr1646v2EthPortHw8POutUcastPktsValue OBJECT-TYPE
   SYNTAX      Counter64
   MAX-ACCESS  read-only
   STATUS      current
   DESCRIPTION
      "Path: hwPort.performance.ifOutUcastPkts

       64 bit unsigned wrappable counter."
   ::= {pr1646v2EthPortHw8POutUcastPktsEntry 2147483648}


pr1646v2EthPortHw8POutNUcastPkts OBJECT IDENTIFIER ::= {pr1646v2EthPortHw8P 117}

pr1646v2EthPortHw8POutNUcastPktsTable OBJECT-TYPE
   SYNTAX      SEQUENCE OF Pr1646v2EthPortHw8POutNUcastPktsEntry
   MAX-ACCESS  not-accessible
   STATUS      current
   DESCRIPTION
      "ifOutNUcastPkts"
   ::= {pr1646v2EthPortHw8POutNUcastPkts 1}

pr1646v2EthPortHw8POutNUcastPktsEntry OBJECT-TYPE
   SYNTAX      Pr1646v2EthPortHw8POutNUcastPktsEntry
   MAX-ACCESS  not-accessible
   STATUS      current
   DESCRIPTION
      ""
   INDEX      { pr1646v2EthPortHw8POutNUcastPktsGlobalIx }
   ::= {pr1646v2EthPortHw8POutNUcastPktsTable 1}

Pr1646v2EthPortHw8POutNUcastPktsEntry ::=
   SEQUENCE
      {
      pr1646v2EthPortHw8POutNUcastPktsGlobalIx
         GlobalIndex,
      pr1646v2EthPortHw8POutNUcastPktsValue
         Counter64
      }

pr1646v2EthPortHw8POutNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortHw8POutNUcastPktsEntry 10}

pr1646v2EthPortHw8POutNUcastPktsValue OBJECT-TYPE
   SYNTAX      Counter64
   MAX-ACCESS  read-only
   STATUS      current
   DESCRIPTION
      "Path: hwPort.performance.ifOutNUcastPkts

       64 bit unsigned wrappable counter."
   ::= {pr1646v2EthPortHw8POutNUcastPktsEntry 2147483648}


pr1646v2EthPortHw8POutDiscards OBJECT IDENTIFIER ::= {pr1646v2EthPortHw8P 118}

pr1646v2EthPortHw8POutDiscardsTable OBJECT-TYPE
   SYNTAX      SEQUENCE OF Pr1646v2EthPortHw8POutDiscardsEntry
   MAX-ACCESS  not-accessible
   STATUS      current
   DESCRIPTION
      "ifOutDiscards"
   ::= {pr1646v2EthPortHw8POutDiscards 1}

pr1646v2EthPortHw8POutDiscardsEntry OBJECT-TYPE
   SYNTAX      Pr1646v2EthPortHw8POutDiscardsEntry
   MAX-ACCESS  not-accessible
   STATUS      current
   DESCRIPTION
      ""
   INDEX      { pr1646v2EthPortHw8POutDiscardsGlobalIx }
   ::= {pr1646v2EthPortHw8POutDiscardsTable 1}

Pr1646v2EthPortHw8POutDiscardsEntry ::=
   SEQUENCE
      {
      pr1646v2EthPortHw8POutDiscardsGlobalIx
         GlobalIndex,
      pr1646v2EthPortHw8POutDiscardsValue
         Counter64
      }

pr1646v2EthPortHw8POutDiscardsGlobalIx OBJECT-TYPE
   SYNTAX      GlobalIndex
   MAX-ACCESS  not-accessible
   STATUS      current
   DESCRIPTION
      "The value of the tlsCntTreeGlobalIndex of the MANAGED OBJECT."
   ::= {pr1646v2EthPortHw8POutDiscardsEntry 10}

pr1646v2EthPortHw8POutDiscardsValue OBJECT-TYPE
   SYNTAX      Counter64
   MAX-ACCESS  read-only
   STATUS      current
   DESCRIPTION
      "Path: hwPort.performance.ifOutDiscards

       64 bit unsigned wrappable counter."
   ::= {pr1646v2EthPortHw8POutDiscardsEntry 2147483648}


pr1646v2EthPortHw8PIfOutPause OBJECT IDENTIFIER ::= {pr1646v2EthPortHw8P 251}

pr1646v2EthPortHw8PIfOutPauseTable OBJECT-TYPE
   SYNTAX      SEQUENCE OF Pr1646v2EthPortHw8PIfOutPauseEntry
   MAX-ACCESS  not-accessible
   STATUS      current
   DESCRIPTION
      "hwPortCounter"
   ::= {pr1646v2EthPortHw8PIfOutPause 1}

pr1646v2EthPortHw8PIfOutPauseEntry OBJECT-TYPE
   SYNTAX      Pr1646v2EthPortHw8PIfOutPauseEntry
   MAX-ACCESS  not-accessible
   STATUS      current
   DESCRIPTION
      ""
   INDEX      { pr1646v2EthPortHw8PIfOutPauseGlobalIx }
   ::= {pr1646v2EthPortHw8PIfOutPauseTable 1}

Pr1646v2EthPortHw8PIfOutPauseEntry ::=
   SEQUENCE
      {
      pr1646v2EthPortHw8PIfOutPauseGlobalIx
         GlobalIndex,
      pr1646v2EthPortHw8PIfOutPauseValue
         Counter64
      }

pr1646v2EthPortHw8PIfOutPauseGlobalIx OBJECT-TYPE
   SYNTAX      GlobalIndex
   MAX-ACCESS  not-accessible
   STATUS      current
   DESCRIPTION
      "The value of the tlsCntTreeGlobalIndex of the MANAGED OBJECT."
   ::= {pr1646v2EthPortHw8PIfOutPauseEntry 10}

pr1646v2EthPortHw8PIfOutPauseValue OBJECT-TYPE
   SYNTAX      Counter64
   MAX-ACCESS  read-only
   STATUS      current
   DESCRIPTION
      "Path: hwPort.performance.ifOutPause

       64 bit unsigned wrappable counter."
   ::= {pr1646v2EthPortHw8PIfOutPauseEntry 2147483648}


pr1646v2EthPortHw8POutErrors OBJECT IDENTIFIER ::= {pr1646v2EthPortHw8P 119}

pr1646v2EthPortHw8POutErrorsTable OBJECT-TYPE
   SYNTAX      SEQUENCE OF Pr1646v2EthPortHw8POutErrorsEntry
   MAX-ACCESS  not-accessible
   STATUS      current
   DESCRIPTION
      "ifOutErrors"
   ::= {pr1646v2EthPortHw8POutErrors 1}

pr1646v2EthPortHw8POutErrorsEntry OBJECT-TYPE
   SYNTAX      Pr1646v2EthPortHw8POutErrorsEntry
   MAX-ACCESS  not-accessible
   STATUS      current
   DESCRIPTION
      ""
   INDEX      { pr1646v2EthPortHw8POutErrorsGlobalIx }
   ::= {pr1646v2EthPortHw8POutErrorsTable 1}

Pr1646v2EthPortHw8POutErrorsEntry ::=
   SEQUENCE
      {
      pr1646v2EthPortHw8POutErrorsGlobalIx
         GlobalIndex,
      pr1646v2EthPortHw8POutErrorsValue
         Counter64
      }

pr1646v2EthPortHw8POutErrorsGlobalIx OBJECT-TYPE
   SYNTAX      GlobalIndex
   MAX-ACCESS  not-accessible
   STATUS      current
   DESCRIPTION
      "The value of the tlsCntTreeGlobalIndex of the MANAGED OBJECT."
   ::= {pr1646v2EthPortHw8POutErrorsEntry 10}

pr1646v2EthPortHw8POutErrorsValue OBJECT-TYPE
   SYNTAX      Counter64
   MAX-ACCESS  read-only
   STATUS      current
   DESCRIPTION
      "Path: hwPort.performance.ifOutErrors

       64 bit unsigned wrappable counter."
   ::= {pr1646v2EthPortHw8POutErrorsEntry 2147483648}


pr1646v2EthPortHw8POutBandwidth OBJECT IDENTIFIER ::= {pr1646v2EthPortHw8P 182}

pr1646v2EthPortHw8POutBandwidthSSCTable OBJECT-TYPE
   SYNTAX      SEQUENCE OF Pr1646v2EthPortHw8POutBandwidthEntry
   MAX-ACCESS  not-accessible
   STATUS      current
   DESCRIPTION
      "bandwidth"
   ::= {pr1646v2EthPortHw8POutBandwidth 1}

pr1646v2EthPortHw8POutBandwidthEntry OBJECT-TYPE
   SYNTAX      Pr1646v2EthPortHw8POutBandwidthEntry
   MAX-ACCESS  not-accessible
   STATUS      current
   DESCRIPTION
      ""
   INDEX      { pr1646v2EthPortHw8POutBandwidthGlobalIx }
   ::= {pr1646v2EthPortHw8POutBandwidthSSCTable 1}

Pr1646v2EthPortHw8POutBandwidthEntry ::=
   SEQUENCE
      {
      pr1646v2EthPortHw8POutBandwidthGlobalIx
         GlobalIndex,
      pr1646v2EthPortHw8POutBandwidth15sec
         Integer32,
      pr1646v2EthPortHw8POutBandwidth30sec
         Integer32,
      pr1646v2EthPortHw8POutBandwidth1min
         Integer32,
      pr1646v2EthPortHw8POutBandwidth2min
         Integer32,
      pr1646v2EthPortHw8POutBandwidth5min
         Integer32
      }

pr1646v2EthPortHw8POutBandwidthGlobalIx OBJECT-TYPE
   SYNTAX      GlobalIndex
   MAX-ACCESS  not-accessible
   STATUS      current
   DESCRIPTION
      "The value of the tlsCntTreeGlobalIndex of the MANAGED OBJECT."
   ::= {pr1646v2EthPortHw8POutBandwidthEntry 10}

pr1646v2EthPortHw8POutBandwidth15sec OBJECT-TYPE
   SYNTAX      Integer32
   MAX-ACCESS  read-only
   STATUS      current
   DESCRIPTION
      "Path: hwPort.performance.ifOutBandwidth.15sec

       unit name = bps
       formula = 8 * ; 8 /"
   ::= {pr1646v2EthPortHw8POutBandwidthEntry 83886080}

pr1646v2EthPortHw8POutBandwidth30sec OBJECT-TYPE
   SYNTAX      Integer32
   MAX-ACCESS  read-only
   STATUS      current
   DESCRIPTION
      "Path: hwPort.performance.ifOutBandwidth.30sec

       unit name = bps
       formula = 8 * ; 8 /"
   ::= {pr1646v2EthPortHw8POutBandwidthEntry 167772160}

pr1646v2EthPortHw8POutBandwidth1min OBJECT-TYPE
   SYNTAX      Integer32
   MAX-ACCESS  read-only
   STATUS      current
   DESCRIPTION
      "Path: hwPort.performance.ifOutBandwidth.1min

       unit name = bps
       formula = 8 * ; 8 /"
   ::= {pr1646v2EthPortHw8POutBandwidthEntry 335544320}

pr1646v2EthPortHw8POutBandwidth2min OBJECT-TYPE
   SYNTAX      Integer32
   MAX-ACCESS  read-only
   STATUS      current
   DESCRIPTION
      "Path: hwPort.performance.ifOutBandwidth.2min

       unit name = bps
       formula = 8 * ; 8 /"
   ::= {pr1646v2EthPortHw8POutBandwidthEntry 671088640}

pr1646v2EthPortHw8POutBandwidth5min OBJECT-TYPE
   SYNTAX      Integer32
   MAX-ACCESS  read-only
   STATUS      current
   DESCRIPTION
      "Path: hwPort.performance.ifOutBandwidth.5min

       unit name = bps
       formula = 8 * ; 8 /"
   ::= {pr1646v2EthPortHw8POutBandwidthEntry 1677721600}


pr1646v2EthPortHw8PInP OBJECT IDENTIFIER ::= {pr1646v2EthPortHw8P 307}

pr1646v2EthPortHw8PInPSSCTable OBJECT-TYPE
   SYNTAX      SEQUENCE OF Pr1646v2EthPortHw8PInPEntry
   MAX-ACCESS  not-accessible
   STATUS      current
   DESCRIPTION
      "h2IfInPerformance"
   ::= {pr1646v2EthPortHw8PInP 1}

pr1646v2EthPortHw8PInPEntry OBJECT-TYPE
   SYNTAX      Pr1646v2EthPortHw8PInPEntry
   MAX-ACCESS  not-accessible
   STATUS      current
   DESCRIPTION
      ""
   INDEX      { pr1646v2EthPortHw8PInPGlobalIx,
                pr1646v2EthPortHw8PInPTableIx }
   ::= {pr1646v2EthPortHw8PInPSSCTable 1}

Pr1646v2EthPortHw8PInPEntry ::=
   SEQUENCE
      {
      pr1646v2EthPortHw8PInPGlobalIx
         GlobalIndex,
      pr1646v2EthPortHw8PInPTableIx
         TableIndex,
      pr1646v2EthPortHw8PInPSysUpTime
         TimeTicks,
      pr1646v2EthPortHw8PInPIfUpTime
         TimeTicks,
      pr1646v2EthPortHw8PInPIfStatChanges
         Counter32,
      pr1646v2EthPortHw8PInPIfInOctets
         Counter64,
      pr1646v2EthPortHw8PInPIfInUCPkts
         Counter64,
      pr1646v2EthPortHw8PInPIfInNUCPkts
         Counter64,
      pr1646v2EthPortHw8PInPIfInBCPkts
         Counter64,
      pr1646v2EthPortHw8PInPIfInMCPkts
         Counter64,
      pr1646v2EthPortHw8PInPIfInDiscards
         Counter64,
      pr1646v2EthPortHw8PInPIfInErrors
         Counter64,
      pr1646v2EthPortHw8PInPIfInUnkwn
         Counter64,
      pr1646v2EthPortHw8PInPInDropEx
         Counter64,
      pr1646v2EthPortHw8PInPInDropNoMac
         Counter64,
      pr1646v2EthPortHw8PInPInDropNUCast
         Counter64,
      pr1646v2EthPortHw8PInPInDropFilter
         Counter64,
      pr1646v2EthPortHw8PInPIfInBandwidth
         Integer32,
      pr1646v2EthPortHw8PInPIfOutOctets
         Counter64,
      pr1646v2EthPortHw8PInPIfOutUCPkts
         Counter64,
      pr1646v2EthPortHw8PInPIfOutNUCPkts
         Counter64,
      pr1646v2EthPortHw8PInPIfOutBCPkts
         Counter64,
      pr1646v2EthPortHw8PInPIfOutMCPkts
         Counter64,
      pr1646v2EthPortHw8PInPIfOutDiscards
         Counter64,
      pr1646v2EthPortHw8PInPIfOutErrors
         Counter64,
      pr1646v2EthPortHw8PInPOutDropEx
         Counter64,
      pr1646v2EthPortHw8PInPOutDropNoArp
         Counter64,
      pr1646v2EthPortHw8PInPOutDropFilter
         Counter64,
      pr1646v2EthPortHw8PInPIfOutBandwidth
         Integer32,
      pr1646v2EthPortHw8PInPIfErrSec
         Counter32
      }

pr1646v2EthPortHw8PInPGlobalIx OBJECT-TYPE
   SYNTAX      GlobalIndex
   MAX-ACCESS  not-accessible
   STATUS      current
   DESCRIPTION
      "The value of the tlsCntTreeGlobalIndex of the MANAGED OBJECT."
   ::= {pr1646v2EthPortHw8PInPEntry 10}

pr1646v2EthPortHw8PInPTableIx OBJECT-TYPE
   SYNTAX      TableIndex
   MAX-ACCESS  not-accessible
   STATUS      current
   DESCRIPTION
      ""
   ::= {pr1646v2EthPortHw8PInPEntry 11}

pr1646v2EthPortHw8PInPSysUpTime OBJECT-TYPE
   SYNTAX      TimeTicks
   MAX-ACCESS  read-only
   STATUS      current
   DESCRIPTION
      "Path: hwPort.performance.h2Performance.sysUpTime

       Time in centi-second."
   ::= {pr1646v2EthPortHw8PInPEntry 16777216}

pr1646v2EthPortHw8PInPIfUpTime OBJECT-TYPE
   SYNTAX      TimeTicks
   MAX-ACCESS  read-only
   STATUS      current
   DESCRIPTION
      "Path: hwPort.performance.h2Performance.ifUpTime

       Time in centi-second."
   ::= {pr1646v2EthPortHw8PInPEntry 33554432}

pr1646v2EthPortHw8PInPIfStatChanges OBJECT-TYPE
   SYNTAX      Counter32
   MAX-ACCESS  read-only
   STATUS      current
   DESCRIPTION
      "Path: hwPort.performance.h2Performance.ifStatusChanges

       32 bit unsigned wrappable counter."
   ::= {pr1646v2EthPortHw8PInPEntry 50331648}

pr1646v2EthPortHw8PInPIfInOctets OBJECT-TYPE
   SYNTAX      Counter64
   MAX-ACCESS  read-only
   STATUS      current
   DESCRIPTION
      "Path: hwPort.performance.h2Performance.ifInOctets

       64 bit unsigned wrappable counter."
   ::= {pr1646v2EthPortHw8PInPEntry 67108864}

pr1646v2EthPortHw8PInPIfInUCPkts OBJECT-TYPE
   SYNTAX      Counter64
   MAX-ACCESS  read-only
   STATUS      current
   DESCRIPTION
      "Path: hwPort.performance.h2Performance.ifInUcastPkts

       64 bit unsigned wrappable counter."
   ::= {pr1646v2EthPortHw8PInPEntry 83886080}

pr1646v2EthPortHw8PInPIfInNUCPkts OBJECT-TYPE
   SYNTAX      Counter64
   MAX-ACCESS  read-only
   STATUS      current
   DESCRIPTION
      "Path: hwPort.performance.h2Performance.ifInNUcastPkts

       64 bit unsigned wrappable counter."
   ::= {pr1646v2EthPortHw8PInPEntry 100663296}

pr1646v2EthPortHw8PInPIfInBCPkts OBJECT-TYPE
   SYNTAX      Counter64
   MAX-ACCESS  read-only
   STATUS      current
   DESCRIPTION
      "Path: hwPort.performance.h2Performance.ifInBcastPkts

       64 bit unsigned wrappable counter."
   ::= {pr1646v2EthPortHw8PInPEntry 419430400}

pr1646v2EthPortHw8PInPIfInMCPkts OBJECT-TYPE
   SYNTAX      Counter64
   MAX-ACCESS  read-only
   STATUS      current
   DESCRIPTION
      "Path: hwPort.performance.h2Performance.ifInMcastPkts

       64 bit unsigned wrappable counter."
   ::= {pr1646v2EthPortHw8PInPEntry 436207616}

pr1646v2EthPortHw8PInPIfInDiscards OBJECT-TYPE
   SYNTAX      Counter64
   MAX-ACCESS  read-only
   STATUS      current
   DESCRIPTION
      "Path: hwPort.performance.h2Performance.ifInDiscards

       64 bit unsigned wrappable counter."
   ::= {pr1646v2EthPortHw8PInPEntry 117440512}

pr1646v2EthPortHw8PInPIfInErrors OBJECT-TYPE
   SYNTAX      Counter64
   MAX-ACCESS  read-only
   STATUS      current
   DESCRIPTION
      "Path: hwPort.performance.h2Performance.ifInErrors

       64 bit unsigned wrappable counter."
   ::= {pr1646v2EthPortHw8PInPEntry 134217728}

pr1646v2EthPortHw8PInPIfInUnkwn OBJECT-TYPE
   SYNTAX      Counter64
   MAX-ACCESS  read-only
   STATUS      current
   DESCRIPTION
      "Path: hwPort.performance.h2Performance.ifInUnknownProtos

       64 bit unsigned wrappable counter."
   ::= {pr1646v2EthPortHw8PInPEntry 150994944}

pr1646v2EthPortHw8PInPInDropEx OBJECT-TYPE
   SYNTAX      Counter64
   MAX-ACCESS  read-only
   STATUS      current
   DESCRIPTION
      "Path: hwPort.performance.h2Performance.ifInDropLevelExceeded

       64 bit unsigned wrappable counter."
   ::= {pr1646v2EthPortHw8PInPEntry 335544320}

pr1646v2EthPortHw8PInPInDropNoMac OBJECT-TYPE
   SYNTAX      Counter64
   MAX-ACCESS  read-only
   STATUS      current
   DESCRIPTION
      "Path: hwPort.performance.h2Performance.fInDiscardsNoMacFit

       64 bit unsigned wrappable counter."
   ::= {pr1646v2EthPortHw8PInPEntry 301989888}

pr1646v2EthPortHw8PInPInDropNUCast OBJECT-TYPE
   SYNTAX      Counter64
   MAX-ACCESS  read-only
   STATUS      current
   DESCRIPTION
      "Path: hwPort.performance.h2Performance.fInDiscardsNUCast

       64 bit unsigned wrappable counter."
   ::= {pr1646v2EthPortHw8PInPEntry 318767104}

pr1646v2EthPortHw8PInPInDropFilter OBJECT-TYPE
   SYNTAX      Counter64
   MAX-ACCESS  read-only
   STATUS      current
   DESCRIPTION
      "Path: hwPort.performance.h2Performance.fInDiscardsFilter

       64 bit unsigned wrappable counter."
   ::= {pr1646v2EthPortHw8PInPEntry 385875968}

pr1646v2EthPortHw8PInPIfInBandwidth OBJECT-TYPE
   SYNTAX      Integer32
   MAX-ACCESS  read-only
   STATUS      current
   DESCRIPTION
      "Path: hwPort.performance.h2Performance.ifInBandwidth

       unit name = bps
       formula = 8 * ; 8 /"
   ::= {pr1646v2EthPortHw8PInPEntry 268435456}

pr1646v2EthPortHw8PInPIfOutOctets OBJECT-TYPE
   SYNTAX      Counter64
   MAX-ACCESS  read-only
   STATUS      current
   DESCRIPTION
      "Path: hwPort.performance.h2Performance.ifOutOctets

       64 bit unsigned wrappable counter."
   ::= {pr1646v2EthPortHw8PInPEntry 167772160}

pr1646v2EthPortHw8PInPIfOutUCPkts OBJECT-TYPE
   SYNTAX      Counter64
   MAX-ACCESS  read-only
   STATUS      current
   DESCRIPTION
      "Path: hwPort.performance.h2Performance.ifOutUcastPkts

       64 bit unsigned wrappable counter."
   ::= {pr1646v2EthPortHw8PInPEntry 184549376}

pr1646v2EthPortHw8PInPIfOutNUCPkts OBJECT-TYPE
   SYNTAX      Counter64
   MAX-ACCESS  read-only
   STATUS      current
   DESCRIPTION
      "Path: hwPort.performance.h2Performance.ifOutNUcastPkts

       64 bit unsigned wrappable counter."
   ::= {pr1646v2EthPortHw8PInPEntry 201326592}

pr1646v2EthPortHw8PInPIfOutBCPkts OBJECT-TYPE
   SYNTAX      Counter64
   MAX-ACCESS  read-only
   STATUS      current
   DESCRIPTION
      "Path: hwPort.performance.h2Performance.ifOutBcastPkts

       64 bit unsigned wrappable counter."
   ::= {pr1646v2EthPortHw8PInPEntry 452984832}

pr1646v2EthPortHw8PInPIfOutMCPkts OBJECT-TYPE
   SYNTAX      Counter64
   MAX-ACCESS  read-only
   STATUS      current
   DESCRIPTION
      "Path: hwPort.performance.h2Performance.ifOutMcastPkts

       64 bit unsigned wrappable counter."
   ::= {pr1646v2EthPortHw8PInPEntry 469762048}

pr1646v2EthPortHw8PInPIfOutDiscards OBJECT-TYPE
   SYNTAX      Counter64
   MAX-ACCESS  read-only
   STATUS      current
   DESCRIPTION
      "Path: hwPort.performance.h2Performance.ifOutDiscards

       64 bit unsigned wrappable counter."
   ::= {pr1646v2EthPortHw8PInPEntry 218103808}

pr1646v2EthPortHw8PInPIfOutErrors OBJECT-TYPE
   SYNTAX      Counter64
   MAX-ACCESS  read-only
   STATUS      current
   DESCRIPTION
      "Path: hwPort.performance.h2Performance.ifOutErrors

       64 bit unsigned wrappable counter."
   ::= {pr1646v2EthPortHw8PInPEntry 234881024}

pr1646v2EthPortHw8PInPOutDropEx OBJECT-TYPE
   SYNTAX      Counter64
   MAX-ACCESS  read-only
   STATUS      current
   DESCRIPTION
      "Path: hwPort.performance.h2Performance.ifOutDropLevelExceeded

       64 bit unsigned wrappable counter."
   ::= {pr1646v2EthPortHw8PInPEntry 352321536}

pr1646v2EthPortHw8PInPOutDropNoArp OBJECT-TYPE
   SYNTAX      Counter64
   MAX-ACCESS  read-only
   STATUS      current
   DESCRIPTION
      "Path: hwPort.performance.h2Performance.ifOutDiscardsNoArp

       64 bit unsigned wrappable counter."
   ::= {pr1646v2EthPortHw8PInPEntry 369098752}

pr1646v2EthPortHw8PInPOutDropFilter OBJECT-TYPE
   SYNTAX      Counter64
   MAX-ACCESS  read-only
   STATUS      current
   DESCRIPTION
      "Path: hwPort.performance.h2Performance.ifOutDiscardsFilter

       64 bit unsigned wrappable counter."
   ::= {pr1646v2EthPortHw8PInPEntry 402653184}

pr1646v2EthPortHw8PInPIfOutBandwidth OBJECT-TYPE
   SYNTAX      Integer32
   MAX-ACCESS  read-only
   STATUS      current
   DESCRIPTION
      "Path: hwPort.performance.h2Performance.ifOutBandwidth

       unit name = bps
       formula = 8 * ; 8 /"
   ::= {pr1646v2EthPortHw8PInPEntry 285212672}

pr1646v2EthPortHw8PInPIfErrSec OBJECT-TYPE
   SYNTAX      Counter32
   MAX-ACCESS  read-only
   STATUS      current
   DESCRIPTION
      "Path: hwPort.performance.h2Performance.ifErrSec

       32 bit unsigned wrappable counter."
   ::= {pr1646v2EthPortHw8PInPEntry 251658240}


pr1646v2EthPortHw8PH24InP OBJECT IDENTIFIER ::= {pr1646v2EthPortHw8P 308}

pr1646v2EthPortHw8PH24InPSSCTable OBJECT-TYPE
   SYNTAX      SEQUENCE OF Pr1646v2EthPortHw8PH24InPEntry
   MAX-ACCESS  not-accessible
   STATUS      current
   DESCRIPTION
      "h24IfInPerformance"
   ::= {pr1646v2EthPortHw8PH24InP 1}

pr1646v2EthPortHw8PH24InPEntry OBJECT-TYPE
   SYNTAX      Pr1646v2EthPortHw8PH24InPEntry
   MAX-ACCESS  not-accessible
   STATUS      current
   DESCRIPTION
      ""
   INDEX      { pr1646v2EthPortHw8PH24InPGlobalIx,
                pr1646v2EthPortHw8PH24InPTableIx }
   ::= {pr1646v2EthPortHw8PH24InPSSCTable 1}

Pr1646v2EthPortHw8PH24InPEntry ::=
   SEQUENCE
      {
      pr1646v2EthPortHw8PH24InPGlobalIx
         GlobalIndex,
      pr1646v2EthPortHw8PH24InPTableIx
         TableIndex,
      pr1646v2EthPortHw8PH24InPSysUpTime
         TimeTicks,
      pr1646v2EthPortHw8PH24InPIfUpTime
         TimeTicks,
      pr1646v2EthPortHw8PH24InPIfStatChanges
         Counter32,
      pr1646v2EthPortHw8PH24InPIfInOctets
         Counter64,
      pr1646v2EthPortHw8PH24InPIfInUCPkts
         Counter64,
      pr1646v2EthPortHw8PH24InPIfInNUCPkts
         Counter64,
      pr1646v2EthPortHw8PH24InPIfInBCPkts
         Counter64,
      pr1646v2EthPortHw8PH24InPIfInMCPkts
         Counter64,
      pr1646v2EthPortHw8PH24InPIfInDiscards
         Counter64,
      pr1646v2EthPortHw8PH24InPIfInErrors
         Counter64,
      pr1646v2EthPortHw8PH24InPIfInUnkwn
         Counter64,
      pr1646v2EthPortHw8PH24InPInDropEx
         Counter64,
      pr1646v2EthPortHw8PH24InPInDropNoMac
         Counter64,
      pr1646v2EthPortHw8PH24InPInDropNUCast
         Counter64,
      pr1646v2EthPortHw8PH24InPInDropFilter
         Counter64,
      pr1646v2EthPortHw8PH24InPIfInBandwidth
         Integer32,
      pr1646v2EthPortHw8PH24InPIfOutOctets
         Counter64,
      pr1646v2EthPortHw8PH24InPIfOutUCPkts
         Counter64,
      pr1646v2EthPortHw8PH24InPIfOutNUCPkts
         Counter64,
      pr1646v2EthPortHw8PH24InPIfOutBCPkts
         Counter64,
      pr1646v2EthPortHw8PH24InPIfOutMCPkts
         Counter64,
      pr1646v2EthPortHw8PH24InPIfOutDiscards
         Counter64,
      pr1646v2EthPortHw8PH24InPIfOutErrors
         Counter64,
      pr1646v2EthPortHw8PH24InPOutDropEx
         Counter64,
      pr1646v2EthPortHw8PH24InPOutDropNoArp
         Counter64,
      pr1646v2EthPortHw8PH24InPOutDropFilter
         Counter64,
      pr1646v2EthPortHw8PH24InPIfOutBandwidth
         Integer32,
      pr1646v2EthPortHw8PH24InPIfErrSec
         Counter32
      }

pr1646v2EthPortHw8PH24InPGlobalIx OBJECT-TYPE
   SYNTAX      GlobalIndex
   MAX-ACCESS  not-accessible
   STATUS      current
   DESCRIPTION
      "The value of the tlsCntTreeGlobalIndex of the MANAGED OBJECT."
   ::= {pr1646v2EthPortHw8PH24InPEntry 10}

pr1646v2EthPortHw8PH24InPTableIx OBJECT-TYPE
   SYNTAX      TableIndex
   MAX-ACCESS  not-accessible
   STATUS      current
   DESCRIPTION
      ""
   ::= {pr1646v2EthPortHw8PH24InPEntry 11}

pr1646v2EthPortHw8PH24InPSysUpTime OBJECT-TYPE
   SYNTAX      TimeTicks
   MAX-ACCESS  read-only
   STATUS      current
   DESCRIPTION
      "Path: hwPort.performance.h24Performance.sysUpTime

       Time in centi-second."
   ::= {pr1646v2EthPortHw8PH24InPEntry 16777216}

pr1646v2EthPortHw8PH24InPIfUpTime OBJECT-TYPE
   SYNTAX      TimeTicks
   MAX-ACCESS  read-only
   STATUS      current
   DESCRIPTION
      "Path: hwPort.performance.h24Performance.ifUpTime

       Time in centi-second."
   ::= {pr1646v2EthPortHw8PH24InPEntry 33554432}

pr1646v2EthPortHw8PH24InPIfStatChanges OBJECT-TYPE
   SYNTAX      Counter32
   MAX-ACCESS  read-only
   STATUS      current
   DESCRIPTION
      "Path: hwPort.performance.h24Performance.ifStatusChanges

       32 bit unsigned wrappable counter."
   ::= {pr1646v2EthPortHw8PH24InPEntry 50331648}

pr1646v2EthPortHw8PH24InPIfInOctets OBJECT-TYPE
   SYNTAX      Counter64
   MAX-ACCESS  read-only
   STATUS      current
   DESCRIPTION
      "Path: hwPort.performance.h24Performance.ifInOctets

       64 bit unsigned wrappable counter."
   ::= {pr1646v2EthPortHw8PH24InPEntry 67108864}

pr1646v2EthPortHw8PH24InPIfInUCPkts OBJECT-TYPE
   SYNTAX      Counter64
   MAX-ACCESS  read-only
   STATUS      current
   DESCRIPTION
      "Path: hwPort.performance.h24Performance.ifInUcastPkts

       64 bit unsigned wrappable counter."
   ::= {pr1646v2EthPortHw8PH24InPEntry 83886080}

pr1646v2EthPortHw8PH24InPIfInNUCPkts OBJECT-TYPE
   SYNTAX      Counter64
   MAX-ACCESS  read-only
   STATUS      current
   DESCRIPTION
      "Path: hwPort.performance.h24Performance.ifInNUcastPkts

       64 bit unsigned wrappable counter."
   ::= {pr1646v2EthPortHw8PH24InPEntry 100663296}

pr1646v2EthPortHw8PH24InPIfInBCPkts OBJECT-TYPE
   SYNTAX      Counter64
   MAX-ACCESS  read-only
   STATUS      current
   DESCRIPTION
      "Path: hwPort.performance.h24Performance.ifInBcastPkts

       64 bit unsigned wrappable counter."
   ::= {pr1646v2EthPortHw8PH24InPEntry 419430400}

pr1646v2EthPortHw8PH24InPIfInMCPkts OBJECT-TYPE
   SYNTAX      Counter64
   MAX-ACCESS  read-only
   STATUS      current
   DESCRIPTION
      "Path: hwPort.performance.h24Performance.ifInMcastPkts

       64 bit unsigned wrappable counter."
   ::= {pr1646v2EthPortHw8PH24InPEntry 436207616}

pr1646v2EthPortHw8PH24InPIfInDiscards OBJECT-TYPE
   SYNTAX      Counter64
   MAX-ACCESS  read-only
   STATUS      current
   DESCRIPTION
      "Path: hwPort.performance.h24Performance.ifInDiscards

       64 bit unsigned wrappable counter."
   ::= {pr1646v2EthPortHw8PH24InPEntry 117440512}

pr1646v2EthPortHw8PH24InPIfInErrors OBJECT-TYPE
   SYNTAX      Counter64
   MAX-ACCESS  read-only
   STATUS      current
   DESCRIPTION
      "Path: hwPort.performance.h24Performance.ifInErrors

       64 bit unsigned wrappable counter."
   ::= {pr1646v2EthPortHw8PH24InPEntry 134217728}

pr1646v2EthPortHw8PH24InPIfInUnkwn OBJECT-TYPE
   SYNTAX      Counter64
   MAX-ACCESS  read-only
   STATUS      current
   DESCRIPTION
      "Path: hwPort.performance.h24Performance.ifInUnknownProtos

       64 bit unsigned wrappable counter."
   ::= {pr1646v2EthPortHw8PH24InPEntry 150994944}

pr1646v2EthPortHw8PH24InPInDropEx OBJECT-TYPE
   SYNTAX      Counter64
   MAX-ACCESS  read-only
   STATUS      current
   DESCRIPTION
      "Path: hwPort.performance.h24Performance.ifInDropLevelExceeded

       64 bit unsigned wrappable counter."
   ::= {pr1646v2EthPortHw8PH24InPEntry 335544320}

pr1646v2EthPortHw8PH24InPInDropNoMac OBJECT-TYPE
   SYNTAX      Counter64
   MAX-ACCESS  read-only
   STATUS      current
   DESCRIPTION
      "Path: hwPort.performance.h24Performance.fInDiscardsNoMacFit

       64 bit unsigned wrappable counter."
   ::= {pr1646v2EthPortHw8PH24InPEntry 301989888}

pr1646v2EthPortHw8PH24InPInDropNUCast OBJECT-TYPE
   SYNTAX      Counter64
   MAX-ACCESS  read-only
   STATUS      current
   DESCRIPTION
      "Path: hwPort.performance.h24Performance.fInDiscardsNUCast

       64 bit unsigned wrappable counter."
   ::= {pr1646v2EthPortHw8PH24InPEntry 318767104}

pr1646v2EthPortHw8PH24InPInDropFilter OBJECT-TYPE
   SYNTAX      Counter64
   MAX-ACCESS  read-only
   STATUS      current
   DESCRIPTION
      "Path: hwPort.performance.h24Performance.fInDiscardsFilter

       64 bit unsigned wrappable counter."
   ::= {pr1646v2EthPortHw8PH24InPEntry 385875968}

pr1646v2EthPortHw8PH24InPIfInBandwidth OBJECT-TYPE
   SYNTAX      Integer32
   MAX-ACCESS  read-only
   STATUS      current
   DESCRIPTION
      "Path: hwPort.performance.h24Performance.ifInBandwidth

       unit name = bps
       formula = 8 * ; 8 /"
   ::= {pr1646v2EthPortHw8PH24InPEntry 268435456}

pr1646v2EthPortHw8PH24InPIfOutOctets OBJECT-TYPE
   SYNTAX      Counter64
   MAX-ACCESS  read-only
   STATUS      current
   DESCRIPTION
      "Path: hwPort.performance.h24Performance.ifOutOctets

       64 bit unsigned wrappable counter."
   ::= {pr1646v2EthPortHw8PH24InPEntry 167772160}

pr1646v2EthPortHw8PH24InPIfOutUCPkts OBJECT-TYPE
   SYNTAX      Counter64
   MAX-ACCESS  read-only
   STATUS      current
   DESCRIPTION
      "Path: hwPort.performance.h24Performance.ifOutUcastPkts

       64 bit unsigned wrappable counter."
   ::= {pr1646v2EthPortHw8PH24InPEntry 184549376}

pr1646v2EthPortHw8PH24InPIfOutNUCPkts OBJECT-TYPE
   SYNTAX      Counter64
   MAX-ACCESS  read-only
   STATUS      current
   DESCRIPTION
      "Path: hwPort.performance.h24Performance.ifOutNUcastPkts

       64 bit unsigned wrappable counter."
   ::= {pr1646v2EthPortHw8PH24InPEntry 201326592}

pr1646v2EthPortHw8PH24InPIfOutBCPkts OBJECT-TYPE
   SYNTAX      Counter64
   MAX-ACCESS  read-only
   STATUS      current
   DESCRIPTION
      "Path: hwPort.performance.h24Performance.ifOutBcastPkts

       64 bit unsigned wrappable counter."
   ::= {pr1646v2EthPortHw8PH24InPEntry 452984832}

pr1646v2EthPortHw8PH24InPIfOutMCPkts OBJECT-TYPE
   SYNTAX      Counter64
   MAX-ACCESS  read-only
   STATUS      current
   DESCRIPTION
      "Path: hwPort.performance.h24Performance.ifOutMcastPkts

       64 bit unsigned wrappable counter."
   ::= {pr1646v2EthPortHw8PH24InPEntry 469762048}

pr1646v2EthPortHw8PH24InPIfOutDiscards OBJECT-TYPE
   SYNTAX      Counter64
   MAX-ACCESS  read-only
   STATUS      current
   DESCRIPTION
      "Path: hwPort.performance.h24Performance.ifOutDiscards

       64 bit unsigned wrappable counter."
   ::= {pr1646v2EthPortHw8PH24InPEntry 218103808}

pr1646v2EthPortHw8PH24InPIfOutErrors OBJECT-TYPE
   SYNTAX      Counter64
   MAX-ACCESS  read-only
   STATUS      current
   DESCRIPTION
      "Path: hwPort.performance.h24Performance.ifOutErrors

       64 bit unsigned wrappable counter."
   ::= {pr1646v2EthPortHw8PH24InPEntry 234881024}

pr1646v2EthPortHw8PH24InPOutDropEx OBJECT-TYPE
   SYNTAX      Counter64
   MAX-ACCESS  read-only
   STATUS      current
   DESCRIPTION
      "Path: hwPort.performance.h24Performance.ifOutDropLevelExceeded

       64 bit unsigned wrappable counter."
   ::= {pr1646v2EthPortHw8PH24InPEntry 352321536}

pr1646v2EthPortHw8PH24InPOutDropNoArp OBJECT-TYPE
   SYNTAX      Counter64
   MAX-ACCESS  read-only
   STATUS      current
   DESCRIPTION
      "Path: hwPort.performance.h24Performance.ifOutDiscardsNoArp

       64 bit unsigned wrappable counter."
   ::= {pr1646v2EthPortHw8PH24InPEntry 369098752}

pr1646v2EthPortHw8PH24InPOutDropFilter OBJECT-TYPE
   SYNTAX      Counter64
   MAX-ACCESS  read-only
   STATUS      current
   DESCRIPTION
      "Path: hwPort.performance.h24Performance.ifOutDiscardsFilter

       64 bit unsigned wrappable counter."
   ::= {pr1646v2EthPortHw8PH24InPEntry 402653184}

pr1646v2EthPortHw8PH24InPIfOutBandwidth OBJECT-TYPE
   SYNTAX      Integer32
   MAX-ACCESS  read-only
   STATUS      current
   DESCRIPTION
      "Path: hwPort.performance.h24Performance.ifOutBandwidth

       unit name = bps
       formula = 8 * ; 8 /"
   ::= {pr1646v2EthPortHw8PH24InPEntry 285212672}

pr1646v2EthPortHw8PH24InPIfErrSec OBJECT-TYPE
   SYNTAX      Counter32
   MAX-ACCESS  read-only
   STATUS      current
   DESCRIPTION
      "Path: hwPort.performance.h24Performance.ifErrSec

       32 bit unsigned wrappable counter."
   ::= {pr1646v2EthPortHw8PH24InPEntry 251658240}


pr1646v2EthPortHw8PD7InP OBJECT IDENTIFIER ::= {pr1646v2EthPortHw8P 309}

pr1646v2EthPortHw8PD7InPSSCTable OBJECT-TYPE
   SYNTAX      SEQUENCE OF Pr1646v2EthPortHw8PD7InPEntry
   MAX-ACCESS  not-accessible
   STATUS      current
   DESCRIPTION
      "d7IfInPerformance"
   ::= {pr1646v2EthPortHw8PD7InP 1}

pr1646v2EthPortHw8PD7InPEntry OBJECT-TYPE
   SYNTAX      Pr1646v2EthPortHw8PD7InPEntry
   MAX-ACCESS  not-accessible
   STATUS      current
   DESCRIPTION
      ""
   INDEX      { pr1646v2EthPortHw8PD7InPGlobalIx,
                pr1646v2EthPortHw8PD7InPTableIx }
   ::= {pr1646v2EthPortHw8PD7InPSSCTable 1}

Pr1646v2EthPortHw8PD7InPEntry ::=
   SEQUENCE
      {
      pr1646v2EthPortHw8PD7InPGlobalIx
         GlobalIndex,
      pr1646v2EthPortHw8PD7InPTableIx
         TableIndex,
      pr1646v2EthPortHw8PD7InPSysUpTime
         TimeTicks,
      pr1646v2EthPortHw8PD7InPIfUpTime
         TimeTicks,
      pr1646v2EthPortHw8PD7InPIfStatChanges
         Counter32,
      pr1646v2EthPortHw8PD7InPIfInOctets
         Counter64,
      pr1646v2EthPortHw8PD7InPIfInUCPkts
         Counter64,
      pr1646v2EthPortHw8PD7InPIfInNUCPkts
         Counter64,
      pr1646v2EthPortHw8PD7InPIfInBCPkts
         Counter64,
      pr1646v2EthPortHw8PD7InPIfInMCPkts
         Counter64,
      pr1646v2EthPortHw8PD7InPIfInDiscards
         Counter64,
      pr1646v2EthPortHw8PD7InPIfInErrors
         Counter64,
      pr1646v2EthPortHw8PD7InPIfInUnkwn
         Counter64,
      pr1646v2EthPortHw8PD7InPInDropEx
         Counter64,
      pr1646v2EthPortHw8PD7InPInDropNoMac
         Counter64,
      pr1646v2EthPortHw8PD7InPInDropNUCast
         Counter64,
      pr1646v2EthPortHw8PD7InPInDropFilter
         Counter64,
      pr1646v2EthPortHw8PD7InPIfInBandwidth
         Integer32,
      pr1646v2EthPortHw8PD7InPIfOutOctets
         Counter64,
      pr1646v2EthPortHw8PD7InPIfOutUCPkts
         Counter64,
      pr1646v2EthPortHw8PD7InPIfOutNUCPkts
         Counter64,
      pr1646v2EthPortHw8PD7InPIfOutBCPkts
         Counter64,
      pr1646v2EthPortHw8PD7InPIfOutMCPkts
         Counter64,
      pr1646v2EthPortHw8PD7InPIfOutDiscards
         Counter64,
      pr1646v2EthPortHw8PD7InPIfOutErrors
         Counter64,
      pr1646v2EthPortHw8PD7InPOutDropEx
         Counter64,
      pr1646v2EthPortHw8PD7InPOutDropNoArp
         Counter64,
      pr1646v2EthPortHw8PD7InPOutDropFilter
         Counter64,
      pr1646v2EthPortHw8PD7InPIfOutBandwidth
         Integer32,
      pr1646v2EthPortHw8PD7InPIfErrSec
         Counter32
      }

pr1646v2EthPortHw8PD7InPGlobalIx OBJECT-TYPE
   SYNTAX      GlobalIndex
   MAX-ACCESS  not-accessible
   STATUS      current
   DESCRIPTION
      "The value of the tlsCntTreeGlobalIndex of the MANAGED OBJECT."
   ::= {pr1646v2EthPortHw8PD7InPEntry 10}

pr1646v2EthPortHw8PD7InPTableIx OBJECT-TYPE
   SYNTAX      TableIndex
   MAX-ACCESS  not-accessible
   STATUS      current
   DESCRIPTION
      ""
   ::= {pr1646v2EthPortHw8PD7InPEntry 11}

pr1646v2EthPortHw8PD7InPSysUpTime OBJECT-TYPE
   SYNTAX      TimeTicks
   MAX-ACCESS  read-only
   STATUS      current
   DESCRIPTION
      "Path: hwPort.performance.d7Performance.sysUpTime

       Time in centi-second."
   ::= {pr1646v2EthPortHw8PD7InPEntry 16777216}

pr1646v2EthPortHw8PD7InPIfUpTime OBJECT-TYPE
   SYNTAX      TimeTicks
   MAX-ACCESS  read-only
   STATUS      current
   DESCRIPTION
      "Path: hwPort.performance.d7Performance.ifUpTime

       Time in centi-second."
   ::= {pr1646v2EthPortHw8PD7InPEntry 33554432}

pr1646v2EthPortHw8PD7InPIfStatChanges OBJECT-TYPE
   SYNTAX      Counter32
   MAX-ACCESS  read-only
   STATUS      current
   DESCRIPTION
      "Path: hwPort.performance.d7Performance.ifStatusChanges

       32 bit unsigned wrappable counter."
   ::= {pr1646v2EthPortHw8PD7InPEntry 50331648}

pr1646v2EthPortHw8PD7InPIfInOctets OBJECT-TYPE
   SYNTAX      Counter64
   MAX-ACCESS  read-only
   STATUS      current
   DESCRIPTION
      "Path: hwPort.performance.d7Performance.ifInOctets

       64 bit unsigned wrappable counter."
   ::= {pr1646v2EthPortHw8PD7InPEntry 67108864}

pr1646v2EthPortHw8PD7InPIfInUCPkts OBJECT-TYPE
   SYNTAX      Counter64
   MAX-ACCESS  read-only
   STATUS      current
   DESCRIPTION
      "Path: hwPort.performance.d7Performance.ifInUcastPkts

       64 bit unsigned wrappable counter."
   ::= {pr1646v2EthPortHw8PD7InPEntry 83886080}

pr1646v2EthPortHw8PD7InPIfInNUCPkts OBJECT-TYPE
   SYNTAX      Counter64
   MAX-ACCESS  read-only
   STATUS      current
   DESCRIPTION
      "Path: hwPort.performance.d7Performance.ifInNUcastPkts

       64 bit unsigned wrappable counter."
   ::= {pr1646v2EthPortHw8PD7InPEntry 100663296}

pr1646v2EthPortHw8PD7InPIfInBCPkts OBJECT-TYPE
   SYNTAX      Counter64
   MAX-ACCESS  read-only
   STATUS      current
   DESCRIPTION
      "Path: hwPort.performance.d7Performance.ifInBcastPkts

       64 bit unsigned wrappable counter."
   ::= {pr1646v2EthPortHw8PD7InPEntry 419430400}

pr1646v2EthPortHw8PD7InPIfInMCPkts OBJECT-TYPE
   SYNTAX      Counter64
   MAX-ACCESS  read-only
   STATUS      current
   DESCRIPTION
      "Path: hwPort.performance.d7Performance.ifInMcastPkts

       64 bit unsigned wrappable counter."
   ::= {pr1646v2EthPortHw8PD7InPEntry 436207616}

pr1646v2EthPortHw8PD7InPIfInDiscards OBJECT-TYPE
   SYNTAX      Counter64
   MAX-ACCESS  read-only
   STATUS      current
   DESCRIPTION
      "Path: hwPort.performance.d7Performance.ifInDiscards

       64 bit unsigned wrappable counter."
   ::= {pr1646v2EthPortHw8PD7InPEntry 117440512}

pr1646v2EthPortHw8PD7InPIfInErrors OBJECT-TYPE
   SYNTAX      Counter64
   MAX-ACCESS  read-only
   STATUS      current
   DESCRIPTION
      "Path: hwPort.performance.d7Performance.ifInErrors

       64 bit unsigned wrappable counter."
   ::= {pr1646v2EthPortHw8PD7InPEntry 134217728}

pr1646v2EthPortHw8PD7InPIfInUnkwn OBJECT-TYPE
   SYNTAX      Counter64
   MAX-ACCESS  read-only
   STATUS      current
   DESCRIPTION
      "Path: hwPort.performance.d7Performance.ifInUnknownProtos

       64 bit unsigned wrappable counter."
   ::= {pr1646v2EthPortHw8PD7InPEntry 150994944}

pr1646v2EthPortHw8PD7InPInDropEx OBJECT-TYPE
   SYNTAX      Counter64
   MAX-ACCESS  read-only
   STATUS      current
   DESCRIPTION
      "Path: hwPort.performance.d7Performance.ifInDropLevelExceeded

       64 bit unsigned wrappable counter."
   ::= {pr1646v2EthPortHw8PD7InPEntry 335544320}

pr1646v2EthPortHw8PD7InPInDropNoMac OBJECT-TYPE
   SYNTAX      Counter64
   MAX-ACCESS  read-only
   STATUS      current
   DESCRIPTION
      "Path: hwPort.performance.d7Performance.fInDiscardsNoMacFit

       64 bit unsigned wrappable counter."
   ::= {pr1646v2EthPortHw8PD7InPEntry 301989888}

pr1646v2EthPortHw8PD7InPInDropNUCast OBJECT-TYPE
   SYNTAX      Counter64
   MAX-ACCESS  read-only
   STATUS      current
   DESCRIPTION
      "Path: hwPort.performance.d7Performance.fInDiscardsNUCast

       64 bit unsigned wrappable counter."
   ::= {pr1646v2EthPortHw8PD7InPEntry 318767104}

pr1646v2EthPortHw8PD7InPInDropFilter OBJECT-TYPE
   SYNTAX      Counter64
   MAX-ACCESS  read-only
   STATUS      current
   DESCRIPTION
      "Path: hwPort.performance.d7Performance.fInDiscardsFilter

       64 bit unsigned wrappable counter."
   ::= {pr1646v2EthPortHw8PD7InPEntry 385875968}

pr1646v2EthPortHw8PD7InPIfInBandwidth OBJECT-TYPE
   SYNTAX      Integer32
   MAX-ACCESS  read-only
   STATUS      current
   DESCRIPTION
      "Path: hwPort.performance.d7Performance.ifInBandwidth

       unit name = bps
       formula = 8 * ; 8 /"
   ::= {pr1646v2EthPortHw8PD7InPEntry 268435456}

pr1646v2EthPortHw8PD7InPIfOutOctets OBJECT-TYPE
   SYNTAX      Counter64
   MAX-ACCESS  read-only
   STATUS      current
   DESCRIPTION
      "Path: hwPort.performance.d7Performance.ifOutOctets

       64 bit unsigned wrappable counter."
   ::= {pr1646v2EthPortHw8PD7InPEntry 167772160}

pr1646v2EthPortHw8PD7InPIfOutUCPkts OBJECT-TYPE
   SYNTAX      Counter64
   MAX-ACCESS  read-only
   STATUS      current
   DESCRIPTION
      "Path: hwPort.performance.d7Performance.ifOutUcastPkts

       64 bit unsigned wrappable counter."
   ::= {pr1646v2EthPortHw8PD7InPEntry 184549376}

pr1646v2EthPortHw8PD7InPIfOutNUCPkts OBJECT-TYPE
   SYNTAX      Counter64
   MAX-ACCESS  read-only
   STATUS      current
   DESCRIPTION
      "Path: hwPort.performance.d7Performance.ifOutNUcastPkts

       64 bit unsigned wrappable counter."
   ::= {pr1646v2EthPortHw8PD7InPEntry 201326592}

pr1646v2EthPortHw8PD7InPIfOutBCPkts OBJECT-TYPE
   SYNTAX      Counter64
   MAX-ACCESS  read-only
   STATUS      current
   DESCRIPTION
      "Path: hwPort.performance.d7Performance.ifOutBcastPkts

       64 bit unsigned wrappable counter."
   ::= {pr1646v2EthPortHw8PD7InPEntry 452984832}

pr1646v2EthPortHw8PD7InPIfOutMCPkts OBJECT-TYPE
   SYNTAX      Counter64
   MAX-ACCESS  read-only
   STATUS      current
   DESCRIPTION
      "Path: hwPort.performance.d7Performance.ifOutMcastPkts

       64 bit unsigned wrappable counter."
   ::= {pr1646v2EthPortHw8PD7InPEntry 469762048}

pr1646v2EthPortHw8PD7InPIfOutDiscards OBJECT-TYPE
   SYNTAX      Counter64
   MAX-ACCESS  read-only
   STATUS      current
   DESCRIPTION
      "Path: hwPort.performance.d7Performance.ifOutDiscards

       64 bit unsigned wrappable counter."
   ::= {pr1646v2EthPortHw8PD7InPEntry 218103808}

pr1646v2EthPortHw8PD7InPIfOutErrors OBJECT-TYPE
   SYNTAX      Counter64
   MAX-ACCESS  read-only
   STATUS      current
   DESCRIPTION
      "Path: hwPort.performance.d7Performance.ifOutErrors

       64 bit unsigned wrappable counter."
   ::= {pr1646v2EthPortHw8PD7InPEntry 234881024}

pr1646v2EthPortHw8PD7InPOutDropEx OBJECT-TYPE
   SYNTAX      Counter64
   MAX-ACCESS  read-only
   STATUS      current
   DESCRIPTION
      "Path: hwPort.performance.d7Performance.ifOutDropLevelExceeded

       64 bit unsigned wrappable counter."
   ::= {pr1646v2EthPortHw8PD7InPEntry 352321536}

pr1646v2EthPortHw8PD7InPOutDropNoArp OBJECT-TYPE
   SYNTAX      Counter64
   MAX-ACCESS  read-only
   STATUS      current
   DESCRIPTION
      "Path: hwPort.performance.d7Performance.ifOutDiscardsNoArp

       64 bit unsigned wrappable counter."
   ::= {pr1646v2EthPortHw8PD7InPEntry 369098752}

pr1646v2EthPortHw8PD7InPOutDropFilter OBJECT-TYPE
   SYNTAX      Counter64
   MAX-ACCESS  read-only
   STATUS      current
   DESCRIPTION
      "Path: hwPort.performance.d7Performance.ifOutDiscardsFilter

       64 bit unsigned wrappable counter."
   ::= {pr1646v2EthPortHw8PD7InPEntry 402653184}

pr1646v2EthPortHw8PD7InPIfOutBandwidth OBJECT-TYPE
   SYNTAX      Integer32
   MAX-ACCESS  read-only
   STATUS      current
   DESCRIPTION
      "Path: hwPort.performance.d7Performance.ifOutBandwidth

       unit name = bps
       formula = 8 * ; 8 /"
   ::= {pr1646v2EthPortHw8PD7InPEntry 285212672}

pr1646v2EthPortHw8PD7InPIfErrSec OBJECT-TYPE
   SYNTAX      Counter32
   MAX-ACCESS  read-only
   STATUS      current
   DESCRIPTION
      "Path: hwPort.performance.d7Performance.ifErrSec

       32 bit unsigned wrappable counter."
   ::= {pr1646v2EthPortHw8PD7InPEntry 251658240}



ar1646v2EthPortHw8P OBJECT IDENTIFIER ::= {r1646v2EthPortHw8P 16}


ar1646v2EthPortHw8PClearCounters OBJECT IDENTIFIER ::= {ar1646v2EthPortHw8P 263}

ar1646v2EthPortHw8PClearCountersTable OBJECT-TYPE
   SYNTAX      SEQUENCE OF Ar1646v2EthPortHw8PClearCountersEntry
   MAX-ACCESS  not-accessible
   STATUS      current
   DESCRIPTION
      "reset counters"
   ::= {ar1646v2EthPortHw8PClearCounters 1}

ar1646v2EthPortHw8PClearCountersEntry OBJECT-TYPE
   SYNTAX      Ar1646v2EthPortHw8PClearCountersEntry
   MAX-ACCESS  not-accessible
   STATUS      current
   DESCRIPTION
      ""
   INDEX      { ar1646v2EthPortHw8PClearCountersGlobalIx }
   ::= {ar1646v2EthPortHw8PClearCountersTable 1}

Ar1646v2EthPortHw8PClearCountersEntry ::=
   SEQUENCE
      {
      ar1646v2EthPortHw8PClearCountersGlobalIx
         GlobalIndex,
      ar1646v2EthPortHw8PClearCountersValue
         Integer32
      }

ar1646v2EthPortHw8PClearCountersGlobalIx OBJECT-TYPE
   SYNTAX      GlobalIndex
   MAX-ACCESS  not-accessible
   STATUS      current
   DESCRIPTION
      "The value of the tlsCntTreeGlobalIndex of the MANAGED OBJECT."
   ::= {ar1646v2EthPortHw8PClearCountersEntry 10}

ar1646v2EthPortHw8PClearCountersValue OBJECT-TYPE
   SYNTAX      Integer32
   MAX-ACCESS  read-write
   STATUS      current
   DESCRIPTION
      "Path: hwPort.actions.clearCounters"
   ::= {ar1646v2EthPortHw8PClearCountersEntry 2147483648}


ar1646v2EthPortHw8PForceLink OBJECT IDENTIFIER ::= {ar1646v2EthPortHw8P 904}

ar1646v2EthPortHw8PForceLinkTable OBJECT-TYPE
   SYNTAX      SEQUENCE OF Ar1646v2EthPortHw8PForceLinkEntry
   MAX-ACCESS  not-accessible
   STATUS      current
   DESCRIPTION
      "action in the debug group"
   ::= {ar1646v2EthPortHw8PForceLink 1}

ar1646v2EthPortHw8PForceLinkEntry OBJECT-TYPE
   SYNTAX      Ar1646v2EthPortHw8PForceLinkEntry
   MAX-ACCESS  not-accessible
   STATUS      current
   DESCRIPTION
      ""
   INDEX      { ar1646v2EthPortHw8PForceLinkGlobalIx }
   ::= {ar1646v2EthPortHw8PForceLinkTable 1}

Ar1646v2EthPortHw8PForceLinkEntry ::=
   SEQUENCE
      {
      ar1646v2EthPortHw8PForceLinkGlobalIx
         GlobalIndex,
      ar1646v2EthPortHw8PForceLinkValue
         Integer32
      }

ar1646v2EthPortHw8PForceLinkGlobalIx OBJECT-TYPE
   SYNTAX      GlobalIndex
   MAX-ACCESS  not-accessible
   STATUS      current
   DESCRIPTION
      "The value of the tlsCntTreeGlobalIndex of the MANAGED OBJECT."
   ::= {ar1646v2EthPortHw8PForceLinkEntry 10}

ar1646v2EthPortHw8PForceLinkValue OBJECT-TYPE
   SYNTAX      Integer32
   MAX-ACCESS  read-write
   STATUS      current
   DESCRIPTION
      "Path: hwPort.actions.forceLink"
   ::= {ar1646v2EthPortHw8PForceLinkEntry 2147483648}


ar1646v2EthPortHw8PForceLinkType OBJECT IDENTIFIER ::= {ar1646v2EthPortHw8P 905}

ar1646v2EthPortHw8PForceLinkTypeTable OBJECT-TYPE
   SYNTAX      SEQUENCE OF Ar1646v2EthPortHw8PForceLinkTypeEntry
   MAX-ACCESS  not-accessible
   STATUS      current
   DESCRIPTION
      "force link type"
   ::= {ar1646v2EthPortHw8PForceLinkType 1}

ar1646v2EthPortHw8PForceLinkTypeEntry OBJECT-TYPE
   SYNTAX      Ar1646v2EthPortHw8PForceLinkTypeEntry
   MAX-ACCESS  not-accessible
   STATUS      current
   DESCRIPTION
      ""
   INDEX      { ar1646v2EthPortHw8PForceLinkTypeGlobalIx }
   ::= {ar1646v2EthPortHw8PForceLinkTypeTable 1}

Ar1646v2EthPortHw8PForceLinkTypeEntry ::=
   SEQUENCE
      {
      ar1646v2EthPortHw8PForceLinkTypeGlobalIx
         GlobalIndex,
      ar1646v2EthPortHw8PForceLinkTypeValue
         INTEGER
      }

ar1646v2EthPortHw8PForceLinkTypeGlobalIx OBJECT-TYPE
   SYNTAX      GlobalIndex
   MAX-ACCESS  not-accessible
   STATUS      current
   DESCRIPTION
      "The value of the tlsCntTreeGlobalIndex of the MANAGED OBJECT."
   ::= {ar1646v2EthPortHw8PForceLinkTypeEntry 10}

ar1646v2EthPortHw8PForceLinkTypeValue OBJECT-TYPE
   SYNTAX      INTEGER
               {
               no (0),
               up (1),
               down (2)
               }
   MAX-ACCESS  read-write
   STATUS      current
   DESCRIPTION
      "Path: hwPort.actions.forceLinkType

       Possibilities:
               no   (0)
               up   (1)
               down   (2)"
   ::= {ar1646v2EthPortHw8PForceLinkTypeEntry 2147483648}


ar1646v2EthPortHw8PTestMode OBJECT IDENTIFIER ::= {ar1646v2EthPortHw8P 902}

ar1646v2EthPortHw8PTestModeTable OBJECT-TYPE
   SYNTAX      SEQUENCE OF Ar1646v2EthPortHw8PTestModeEntry
   MAX-ACCESS  not-accessible
   STATUS      current
   DESCRIPTION
      "action in the debug group"
   ::= {ar1646v2EthPortHw8PTestMode 1}

ar1646v2EthPortHw8PTestModeEntry OBJECT-TYPE
   SYNTAX      Ar1646v2EthPortHw8PTestModeEntry
   MAX-ACCESS  not-accessible
   STATUS      current
   DESCRIPTION
      ""
   INDEX      { ar1646v2EthPortHw8PTestModeGlobalIx }
   ::= {ar1646v2EthPortHw8PTestModeTable 1}

Ar1646v2EthPortHw8PTestModeEntry ::=
   SEQUENCE
      {
      ar1646v2EthPortHw8PTestModeGlobalIx
         GlobalIndex,
      ar1646v2EthPortHw8PTestModeValue
         Integer32
      }

ar1646v2EthPortHw8PTestModeGlobalIx OBJECT-TYPE
   SYNTAX      GlobalIndex
   MAX-ACCESS  not-accessible
   STATUS      current
   DESCRIPTION
      "The value of the tlsCntTreeGlobalIndex of the MANAGED OBJECT."
   ::= {ar1646v2EthPortHw8PTestModeEntry 10}

ar1646v2EthPortHw8PTestModeValue OBJECT-TYPE
   SYNTAX      Integer32
   MAX-ACCESS  read-write
   STATUS      current
   DESCRIPTION
      "Path: hwPort.actions.testMode"
   ::= {ar1646v2EthPortHw8PTestModeEntry 2147483648}


ar1646v2EthPortHw8PTestType OBJECT IDENTIFIER ::= {ar1646v2EthPortHw8P 903}

ar1646v2EthPortHw8PTestTypeTable OBJECT-TYPE
   SYNTAX      SEQUENCE OF Ar1646v2EthPortHw8PTestTypeEntry
   MAX-ACCESS  not-accessible
   STATUS      current
   DESCRIPTION
      "ethernet test type"
   ::= {ar1646v2EthPortHw8PTestType 1}

ar1646v2EthPortHw8PTestTypeEntry OBJECT-TYPE
   SYNTAX      Ar1646v2EthPortHw8PTestTypeEntry
   MAX-ACCESS  not-accessible
   STATUS      current
   DESCRIPTION
      ""
   INDEX      { ar1646v2EthPortHw8PTestTypeGlobalIx }
   ::= {ar1646v2EthPortHw8PTestTypeTable 1}

Ar1646v2EthPortHw8PTestTypeEntry ::=
   SEQUENCE
      {
      ar1646v2EthPortHw8PTestTypeGlobalIx
         GlobalIndex,
      ar1646v2EthPortHw8PTestTypeValue
         INTEGER
      }

ar1646v2EthPortHw8PTestTypeGlobalIx OBJECT-TYPE
   SYNTAX      GlobalIndex
   MAX-ACCESS  not-accessible
   STATUS      current
   DESCRIPTION
      "The value of the tlsCntTreeGlobalIndex of the MANAGED OBJECT."
   ::= {ar1646v2EthPortHw8PTestTypeEntry 10}

ar1646v2EthPortHw8PTestTypeValue OBJECT-TYPE
   SYNTAX      INTEGER
               {
               none (0),
               testMode1TxWaveform (1),
               testMode2TxJitterMaster (2),
               testMode3TxJitterSlave (3),
               testMode4TxDistortion (4),
               loopback10100 (5)
               }
   MAX-ACCESS  read-write
   STATUS      current
   DESCRIPTION
      "Path: hwPort.actions.testType

       Possibilities:
               none   (0)
               testMode1TxWaveform   (1)
               testMode2TxJitterMaster   (2)
               testMode3TxJitterSlave   (3)
               testMode4TxDistortion   (4)
               loopback10/100   (5)"
   ::= {ar1646v2EthPortHw8PTestTypeEntry 2147483648}



fr1646v2EthPortHw8P OBJECT IDENTIFIER ::= {r1646v2EthPortHw8P 13}


fr1646v2EthPortHw8PAlarm OBJECT IDENTIFIER ::= {fr1646v2EthPortHw8P 207}

fr1646v2EthPortHw8PAlarmSSCTable OBJECT-TYPE
   SYNTAX      SEQUENCE OF Fr1646v2EthPortHw8PAlarmEntry
   MAX-ACCESS  not-accessible
   STATUS      current
   DESCRIPTION
      "IfAlarmInfo"
   ::= {fr1646v2EthPortHw8PAlarm 1}

fr1646v2EthPortHw8PAlarmEntry OBJECT-TYPE
   SYNTAX      Fr1646v2EthPortHw8PAlarmEntry
   MAX-ACCESS  not-accessible
   STATUS      current
   DESCRIPTION
      ""
   INDEX      { fr1646v2EthPortHw8PAlarmGlobalIx }
   ::= {fr1646v2EthPortHw8PAlarmSSCTable 1}

Fr1646v2EthPortHw8PAlarmEntry ::=
   SEQUENCE
      {
      fr1646v2EthPortHw8PAlarmGlobalIx
         GlobalIndex,
      fr1646v2EthPortHw8PAlarmDiscriminator
         Integer32,
      fr1646v2EthPortHw8PAlarmCurrent
         Integer32,
      fr1646v2EthPortHw8PAlarmPrevious
         Integer32,
      fr1646v2EthPortHw8PAlarmMask
         Integer32,
      fr1646v2EthPortHw8PAlarmLevLinkDown
         Integer32
      }

fr1646v2EthPortHw8PAlarmGlobalIx OBJECT-TYPE
   SYNTAX      GlobalIndex
   MAX-ACCESS  not-accessible
   STATUS      current
   DESCRIPTION
      "The value of the tlsCntTreeGlobalIndex of the MANAGED OBJECT."
   ::= {fr1646v2EthPortHw8PAlarmEntry 10}

fr1646v2EthPortHw8PAlarmDiscriminator OBJECT-TYPE
   SYNTAX      Integer32
   MAX-ACCESS  read-only
   STATUS      current
   DESCRIPTION
      "Path: hwPort.alarms.alarmInfo.discriminator"
   ::= {fr1646v2EthPortHw8PAlarmEntry 16777216}

fr1646v2EthPortHw8PAlarmCurrent OBJECT-TYPE
   SYNTAX      Integer32
   MAX-ACCESS  read-only
   STATUS      current
   DESCRIPTION
      "Path: hwPort.alarms.alarmInfo.currentAlarms

       Bit meanings:
               bit 0 = linkDown"
   ::= {fr1646v2EthPortHw8PAlarmEntry 33554432}

fr1646v2EthPortHw8PAlarmPrevious OBJECT-TYPE
   SYNTAX      Integer32
   MAX-ACCESS  read-only
   STATUS      current
   DESCRIPTION
      "Path: hwPort.alarms.alarmInfo.previousAlarms

       Bit meanings:
               bit 0 = linkDown"
   ::= {fr1646v2EthPortHw8PAlarmEntry 50331648}

fr1646v2EthPortHw8PAlarmMask OBJECT-TYPE
   SYNTAX      Integer32
   MAX-ACCESS  read-only
   STATUS      current
   DESCRIPTION
      "Path: hwPort.alarms.alarmInfo.alarmMask

       Bit meanings:
               bit 0 = linkDown"
   ::= {fr1646v2EthPortHw8PAlarmEntry 67108864}

fr1646v2EthPortHw8PAlarmLevLinkDown OBJECT-TYPE
   SYNTAX      Integer32
   MAX-ACCESS  read-only
   STATUS      current
   DESCRIPTION
      "Path: hwPort.alarms.alarmInfo.alarmLevel.linkDown"
   ::= {fr1646v2EthPortHw8PAlarmEntry 83951616}


fr1646v2EthPortHw8PAlarmE2 OBJECT IDENTIFIER ::= {fr1646v2EthPortHw8PAlarm 2}

fr1646v2EthPortHw8PAlarmE2Entry OBJECT IDENTIFIER ::= {fr1646v2EthPortHw8PAlarmE2 1}

fr1646v2EthPortHw8PAlarmE2LinkDown OBJECT IDENTIFIER ::= {fr1646v2EthPortHw8PAlarmE2Entry 10}

fr1646v2EthPortHw8PAlarmE2LinkDownPfx OBJECT IDENTIFIER ::= {fr1646v2EthPortHw8PAlarmE2LinkDown 0}

fr1646v2EthPortHw8PAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortHw8P'
                (root='router1646') has changed from the ON to the OFF state."
   ::= {fr1646v2EthPortHw8PAlarmE2LinkDownPfx 1}

fr1646v2EthPortHw8PAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortHw8P'
                (root='router1646') has changed from the OFF to the ON state."
   ::= {fr1646v2EthPortHw8PAlarmE2LinkDownPfx 2}



END
