OneAccess-R1645v2-1841-CellUsrPr DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2CellUsrPr OBJECT IDENTIFIER ::= {r1645Rootv2 1841}

r1645v2CellUsrPrMOProp OBJECT-TYPE
   SYNTAX      SEQUENCE OF R1645v2CellUsrPrMOPropEntry
   MAX-ACCESS  not-accessible
   STATUS      current
   DESCRIPTION
      ""
   ::= {r1645v2CellUsrPr 1}

r1645v2CellUsrPrMOPropEntry OBJECT-TYPE
   SYNTAX      R1645v2CellUsrPrMOPropEntry
   MAX-ACCESS  not-accessible
   STATUS      current
   DESCRIPTION
      ""
   INDEX      { r1645v2CellUsrPrMOPropGlobalIx }
   ::= {r1645v2CellUsrPrMOProp 1}

R1645v2CellUsrPrMOPropEntry ::=
   SEQUENCE
      {
      r1645v2CellUsrPrMOPropPath
         ContainmentPath,
      r1645v2CellUsrPrMOPropRev
         ObjectRevision,
      r1645v2CellUsrPrMOPropGlobalIx
         GlobalIndex
      }

r1645v2CellUsrPrMOPropPath OBJECT-TYPE
   SYNTAX      ContainmentPath
   MAX-ACCESS  read-only
   STATUS      current
   DESCRIPTION
      "Textual description of the containment tree from the instance of
       the root object down to the instance of the current object."
   ::= {r1645v2CellUsrPrMOPropEntry 3}

r1645v2CellUsrPrMOPropRev OBJECT-TYPE
   SYNTAX      ObjectRevision
   MAX-ACCESS  read-only
   STATUS      current
   DESCRIPTION
      "This value corresponds with the revision of the MANAGED OBJECT."
   ::= {r1645v2CellUsrPrMOPropEntry 4}

r1645v2CellUsrPrMOPropGlobalIx OBJECT-TYPE
   SYNTAX      GlobalIndex
   MAX-ACCESS  read-only
   STATUS      current
   DESCRIPTION
      "The value of the tlsCntTreeGlobalIndex of the MANAGED OBJECT."
   ::= {r1645v2CellUsrPrMOPropEntry 10}



er1645v2CellUsrPr OBJECT IDENTIFIER ::= {r1645v2CellUsrPr 11}


er1645v2CellUsrPrDialPktBufSize OBJECT IDENTIFIER ::= {er1645v2CellUsrPr 4}

er1645v2CellUsrPrDialPktBufSizeTable OBJECT-TYPE
   SYNTAX      SEQUENCE OF Er1645v2CellUsrPrDialPktBufSizeEntry
   MAX-ACCESS  not-accessible
   STATUS      current
   DESCRIPTION
      "max number of outstanding packets"
   ::= {er1645v2CellUsrPrDialPktBufSize 1}

er1645v2CellUsrPrDialPktBufSizeEntry OBJECT-TYPE
   SYNTAX      Er1645v2CellUsrPrDialPktBufSizeEntry
   MAX-ACCESS  not-accessible
   STATUS      current
   DESCRIPTION
      ""
   INDEX      { er1645v2CellUsrPrDialPktBufSizeGlobalIx }
   ::= {er1645v2CellUsrPrDialPktBufSizeTable 1}

Er1645v2CellUsrPrDialPktBufSizeEntry ::=
   SEQUENCE
      {
      er1645v2CellUsrPrDialPktBufSizeGlobalIx
         GlobalIndex,
      er1645v2CellUsrPrDialPktBufSizeValue
         Integer32
      }

er1645v2CellUsrPrDialPktBufSizeGlobalIx OBJECT-TYPE
   SYNTAX      GlobalIndex
   MAX-ACCESS  not-accessible
   STATUS      current
   DESCRIPTION
      "The value of the tlsCntTreeGlobalIndex of the MANAGED OBJECT."
   ::= {er1645v2CellUsrPrDialPktBufSizeEntry 10}

er1645v2CellUsrPrDialPktBufSizeValue OBJECT-TYPE
   SYNTAX      Integer32
   MAX-ACCESS  read-write
   STATUS      current
   DESCRIPTION
      "Path: pdp.editConf.dialPktBufSize"
   ::= {er1645v2CellUsrPrDialPktBufSizeEntry 2147483648}


er1645v2CellUsrPrType OBJECT IDENTIFIER ::= {er1645v2CellUsrPr 50}

er1645v2CellUsrPrTypeTable OBJECT-TYPE
   SYNTAX      SEQUENCE OF Er1645v2CellUsrPrTypeEntry
   MAX-ACCESS  not-accessible
   STATUS      current
   DESCRIPTION
      "3G call type: OnDemand or LeasedLine"
   ::= {er1645v2CellUsrPrType 1}

er1645v2CellUsrPrTypeEntry OBJECT-TYPE
   SYNTAX      Er1645v2CellUsrPrTypeEntry
   MAX-ACCESS  not-accessible
   STATUS      current
   DESCRIPTION
      ""
   INDEX      { er1645v2CellUsrPrTypeGlobalIx }
   ::= {er1645v2CellUsrPrTypeTable 1}

Er1645v2CellUsrPrTypeEntry ::=
   SEQUENCE
      {
      er1645v2CellUsrPrTypeGlobalIx
         GlobalIndex,
      er1645v2CellUsrPrTypeValue
         INTEGER
      }

er1645v2CellUsrPrTypeGlobalIx OBJECT-TYPE
   SYNTAX      GlobalIndex
   MAX-ACCESS  not-accessible
   STATUS      current
   DESCRIPTION
      "The value of the tlsCntTreeGlobalIndex of the MANAGED OBJECT."
   ::= {er1645v2CellUsrPrTypeEntry 10}

er1645v2CellUsrPrTypeValue OBJECT-TYPE
   SYNTAX      INTEGER
               {
               outgoingDial (1),
               outgoingLeasedLine (2)
               }
   MAX-ACCESS  read-write
   STATUS      current
   DESCRIPTION
      "Path: pdp.editConf.type

       Possibilities:
               outgoingDial   (1)
               outgoingLeasedLine   (2)"
   ::= {er1645v2CellUsrPrTypeEntry 2147483648}


er1645v2CellUsrPrIdleTimeOut OBJECT IDENTIFIER ::= {er1645v2CellUsrPr 5}

er1645v2CellUsrPrIdleTimeOutTable OBJECT-TYPE
   SYNTAX      SEQUENCE OF Er1645v2CellUsrPrIdleTimeOutEntry
   MAX-ACCESS  not-accessible
   STATUS      current
   DESCRIPTION
      "idle timeout before disconnecting (only relevant when MobileCallType is OnDemand)"
   ::= {er1645v2CellUsrPrIdleTimeOut 1}

er1645v2CellUsrPrIdleTimeOutEntry OBJECT-TYPE
   SYNTAX      Er1645v2CellUsrPrIdleTimeOutEntry
   MAX-ACCESS  not-accessible
   STATUS      current
   DESCRIPTION
      ""
   INDEX      { er1645v2CellUsrPrIdleTimeOutGlobalIx }
   ::= {er1645v2CellUsrPrIdleTimeOutTable 1}

Er1645v2CellUsrPrIdleTimeOutEntry ::=
   SEQUENCE
      {
      er1645v2CellUsrPrIdleTimeOutGlobalIx
         GlobalIndex,
      er1645v2CellUsrPrIdleTimeOutValue
         TimeTicks
      }

er1645v2CellUsrPrIdleTimeOutGlobalIx OBJECT-TYPE
   SYNTAX      GlobalIndex
   MAX-ACCESS  not-accessible
   STATUS      current
   DESCRIPTION
      "The value of the tlsCntTreeGlobalIndex of the MANAGED OBJECT."
   ::= {er1645v2CellUsrPrIdleTimeOutEntry 10}

er1645v2CellUsrPrIdleTimeOutValue OBJECT-TYPE
   SYNTAX      TimeTicks
   MAX-ACCESS  read-write
   STATUS      current
   DESCRIPTION
      "Path: pdp.editConf.idleTimeOut

       Time in centi-second."
   ::= {er1645v2CellUsrPrIdleTimeOutEntry 2147483648}


er1645v2CellUsrPrCallInterval OBJECT IDENTIFIER ::= {er1645v2CellUsrPr 7}

er1645v2CellUsrPrCallIntervalTable OBJECT-TYPE
   SYNTAX      SEQUENCE OF Er1645v2CellUsrPrCallIntervalEntry
   MAX-ACCESS  not-accessible
   STATUS      current
   DESCRIPTION
      "minimum time between two calls"
   ::= {er1645v2CellUsrPrCallInterval 1}

er1645v2CellUsrPrCallIntervalEntry OBJECT-TYPE
   SYNTAX      Er1645v2CellUsrPrCallIntervalEntry
   MAX-ACCESS  not-accessible
   STATUS      current
   DESCRIPTION
      ""
   INDEX      { er1645v2CellUsrPrCallIntervalGlobalIx }
   ::= {er1645v2CellUsrPrCallIntervalTable 1}

Er1645v2CellUsrPrCallIntervalEntry ::=
   SEQUENCE
      {
      er1645v2CellUsrPrCallIntervalGlobalIx
         GlobalIndex,
      er1645v2CellUsrPrCallIntervalValue
         TimeTicks
      }

er1645v2CellUsrPrCallIntervalGlobalIx OBJECT-TYPE
   SYNTAX      GlobalIndex
   MAX-ACCESS  not-accessible
   STATUS      current
   DESCRIPTION
      "The value of the tlsCntTreeGlobalIndex of the MANAGED OBJECT."
   ::= {er1645v2CellUsrPrCallIntervalEntry 10}

er1645v2CellUsrPrCallIntervalValue OBJECT-TYPE
   SYNTAX      TimeTicks
   MAX-ACCESS  read-write
   STATUS      current
   DESCRIPTION
      "Path: pdp.editConf.callInterval

       Time in centi-second."
   ::= {er1645v2CellUsrPrCallIntervalEntry 2147483648}


er1645v2CellUsrPrStartDelay OBJECT IDENTIFIER ::= {er1645v2CellUsrPr 21}

er1645v2CellUsrPrStartDelayTable OBJECT-TYPE
   SYNTAX      SEQUENCE OF Er1645v2CellUsrPrStartDelayEntry
   MAX-ACCESS  not-accessible
   STATUS      current
   DESCRIPTION
      "delay before attempting connection setup"
   ::= {er1645v2CellUsrPrStartDelay 1}

er1645v2CellUsrPrStartDelayEntry OBJECT-TYPE
   SYNTAX      Er1645v2CellUsrPrStartDelayEntry
   MAX-ACCESS  not-accessible
   STATUS      current
   DESCRIPTION
      ""
   INDEX      { er1645v2CellUsrPrStartDelayGlobalIx }
   ::= {er1645v2CellUsrPrStartDelayTable 1}

Er1645v2CellUsrPrStartDelayEntry ::=
   SEQUENCE
      {
      er1645v2CellUsrPrStartDelayGlobalIx
         GlobalIndex,
      er1645v2CellUsrPrStartDelayValue
         TimeTicks
      }

er1645v2CellUsrPrStartDelayGlobalIx OBJECT-TYPE
   SYNTAX      GlobalIndex
   MAX-ACCESS  not-accessible
   STATUS      current
   DESCRIPTION
      "The value of the tlsCntTreeGlobalIndex of the MANAGED OBJECT."
   ::= {er1645v2CellUsrPrStartDelayEntry 10}

er1645v2CellUsrPrStartDelayValue OBJECT-TYPE
   SYNTAX      TimeTicks
   MAX-ACCESS  read-write
   STATUS      current
   DESCRIPTION
      "Path: pdp.editConf.startDelay

       Time in centi-second."
   ::= {er1645v2CellUsrPrStartDelayEntry 2147483648}


er1645v2CellUsrPr24hMaxCallTime OBJECT IDENTIFIER ::= {er1645v2CellUsrPr 9}

er1645v2CellUsrPr24hMaxCallTimeTable OBJECT-TYPE
   SYNTAX      SEQUENCE OF Er1645v2CellUsrPr24hMaxCallTimeEntry
   MAX-ACCESS  not-accessible
   STATUS      current
   DESCRIPTION
      "max time per 24 hours interval of dial-up connection"
   ::= {er1645v2CellUsrPr24hMaxCallTime 1}

er1645v2CellUsrPr24hMaxCallTimeEntry OBJECT-TYPE
   SYNTAX      Er1645v2CellUsrPr24hMaxCallTimeEntry
   MAX-ACCESS  not-accessible
   STATUS      current
   DESCRIPTION
      ""
   INDEX      { er1645v2CellUsrPr24hMaxCallTimeGlobalIx }
   ::= {er1645v2CellUsrPr24hMaxCallTimeTable 1}

Er1645v2CellUsrPr24hMaxCallTimeEntry ::=
   SEQUENCE
      {
      er1645v2CellUsrPr24hMaxCallTimeGlobalIx
         GlobalIndex,
      er1645v2CellUsrPr24hMaxCallTimeValue
         TimeTicks
      }

er1645v2CellUsrPr24hMaxCallTimeGlobalIx OBJECT-TYPE
   SYNTAX      GlobalIndex
   MAX-ACCESS  not-accessible
   STATUS      current
   DESCRIPTION
      "The value of the tlsCntTreeGlobalIndex of the MANAGED OBJECT."
   ::= {er1645v2CellUsrPr24hMaxCallTimeEntry 10}

er1645v2CellUsrPr24hMaxCallTimeValue OBJECT-TYPE
   SYNTAX      TimeTicks
   MAX-ACCESS  read-write
   STATUS      current
   DESCRIPTION
      "Path: pdp.editConf.24hMaxCallTime

       Time in centi-second."
   ::= {er1645v2CellUsrPr24hMaxCallTimeEntry 2147483648}


er1645v2CellUsrPrIdleDirection OBJECT IDENTIFIER ::= {er1645v2CellUsrPr 20}

er1645v2CellUsrPrIdleDirectionTable OBJECT-TYPE
   SYNTAX      SEQUENCE OF Er1645v2CellUsrPrIdleDirectionEntry
   MAX-ACCESS  not-accessible
   STATUS      current
   DESCRIPTION
      "direction of idle traffic verification"
   ::= {er1645v2CellUsrPrIdleDirection 1}

er1645v2CellUsrPrIdleDirectionEntry OBJECT-TYPE
   SYNTAX      Er1645v2CellUsrPrIdleDirectionEntry
   MAX-ACCESS  not-accessible
   STATUS      current
   DESCRIPTION
      ""
   INDEX      { er1645v2CellUsrPrIdleDirectionGlobalIx }
   ::= {er1645v2CellUsrPrIdleDirectionTable 1}

Er1645v2CellUsrPrIdleDirectionEntry ::=
   SEQUENCE
      {
      er1645v2CellUsrPrIdleDirectionGlobalIx
         GlobalIndex,
      er1645v2CellUsrPrIdleDirectionValue
         INTEGER
      }

er1645v2CellUsrPrIdleDirectionGlobalIx OBJECT-TYPE
   SYNTAX      GlobalIndex
   MAX-ACCESS  not-accessible
   STATUS      current
   DESCRIPTION
      "The value of the tlsCntTreeGlobalIndex of the MANAGED OBJECT."
   ::= {er1645v2CellUsrPrIdleDirectionEntry 10}

er1645v2CellUsrPrIdleDirectionValue OBJECT-TYPE
   SYNTAX      INTEGER
               {
               inbound (1),
               outbound (2),
               all (3)
               }
   MAX-ACCESS  read-write
   STATUS      current
   DESCRIPTION
      "Path: pdp.editConf.idleDirection

       Possibilities:
               inbound   (1)
               outbound   (2)
               all   (3)"
   ::= {er1645v2CellUsrPrIdleDirectionEntry 2147483648}


er1645v2CellUsrPrDialTm OBJECT IDENTIFIER ::= {er1645v2CellUsrPr 10}

er1645v2CellUsrPrDialTmSSCTable OBJECT-TYPE
   SYNTAX      SEQUENCE OF Er1645v2CellUsrPrDialTmEntry
   MAX-ACCESS  not-accessible
   STATUS      current
   DESCRIPTION
      "Table with months, days, dotw, hour and minutes for dialouts"
   ::= {er1645v2CellUsrPrDialTm 1}

er1645v2CellUsrPrDialTmEntry OBJECT-TYPE
   SYNTAX      Er1645v2CellUsrPrDialTmEntry
   MAX-ACCESS  not-accessible
   STATUS      current
   DESCRIPTION
      ""
   INDEX      { er1645v2CellUsrPrDialTmGlobalIx,
                er1645v2CellUsrPrDialTmTableIx }
   ::= {er1645v2CellUsrPrDialTmSSCTable 1}

Er1645v2CellUsrPrDialTmEntry ::=
   SEQUENCE
      {
      er1645v2CellUsrPrDialTmActions
         VariableLengthTableActions,
      er1645v2CellUsrPrDialTmGlobalIx
         GlobalIndex,
      er1645v2CellUsrPrDialTmTableIx
         TableIndex,
      er1645v2CellUsrPrDialTmStartMon
         INTEGER,
      er1645v2CellUsrPrDialTmStartDom
         INTEGER,
      er1645v2CellUsrPrDialTmStartDof
         INTEGER,
      er1645v2CellUsrPrDialTmStartHr
         INTEGER,
      er1645v2CellUsrPrDialTmStartMin
         INTEGER,
      er1645v2CellUsrPrDialTmEndMon
         INTEGER,
      er1645v2CellUsrPrDialTmEndDom
         INTEGER,
      er1645v2CellUsrPrDialTmEndDof
         INTEGER,
      er1645v2CellUsrPrDialTmEndHr
         INTEGER,
      er1645v2CellUsrPrDialTmEndMin
         INTEGER
      }

er1645v2CellUsrPrDialTmActions OBJECT-TYPE
   SYNTAX      VariableLengthTableActions
   MAX-ACCESS  read-write
   STATUS      current
   DESCRIPTION
      "By way of this field, some manipulations
       on this table may be performed."
   ::= {er1645v2CellUsrPrDialTmEntry 2}

er1645v2CellUsrPrDialTmGlobalIx OBJECT-TYPE
   SYNTAX      GlobalIndex
   MAX-ACCESS  not-accessible
   STATUS      current
   DESCRIPTION
      "The value of the tlsCntTreeGlobalIndex of the MANAGED OBJECT."
   ::= {er1645v2CellUsrPrDialTmEntry 10}

er1645v2CellUsrPrDialTmTableIx OBJECT-TYPE
   SYNTAX      TableIndex
   MAX-ACCESS  not-accessible
   STATUS      current
   DESCRIPTION
      ""
   ::= {er1645v2CellUsrPrDialTmEntry 11}

er1645v2CellUsrPrDialTmStartMon OBJECT-TYPE
   SYNTAX      INTEGER
               {
               jan (1),
               feb (2),
               mar (3),
               apr (4),
               may (5),
               jun (6),
               jul (7),
               aug (8),
               sep (9),
               oct (10),
               nov (11),
               dec (12),
               slOPTg (255)
               }
   MAX-ACCESS  read-write
   STATUS      current
   DESCRIPTION
      "Path: pdp.editConf.dialTimeTable.start.month

       Possibilities:
               jan   (1)
               feb   (2)
               mar   (3)
               apr   (4)
               may   (5)
               jun   (6)
               jul   (7)
               aug   (8)
               sep   (9)
               oct   (10)
               nov   (11)
               dec   (12)
               <OPT>   (255)"
   ::= {er1645v2CellUsrPrDialTmEntry 16842752}

er1645v2CellUsrPrDialTmStartDom OBJECT-TYPE
   SYNTAX      INTEGER
               {
               slOPTg (255)
               }
   MAX-ACCESS  read-write
   STATUS      current
   DESCRIPTION
      "Path: pdp.editConf.dialTimeTable.start.dayOfMonth

       Possibilities:
               <OPT>   (255)"
   ::= {er1645v2CellUsrPrDialTmEntry 16908288}

er1645v2CellUsrPrDialTmStartDof OBJECT-TYPE
   SYNTAX      INTEGER
               {
               sunday (1),
               monday (2),
               tuesday (3),
               wednesday (4),
               thursday (5),
               friday (6),
               saturday (7),
               slOPTg (255)
               }
   MAX-ACCESS  read-write
   STATUS      current
   DESCRIPTION
      "Path: pdp.editConf.dialTimeTable.start.dayOfWeek

       Possibilities:
               sunday   (1)
               monday   (2)
               tuesday   (3)
               wednesday   (4)
               thursday   (5)
               friday   (6)
               saturday   (7)
               <OPT>   (255)"
   ::= {er1645v2CellUsrPrDialTmEntry 16973824}

er1645v2CellUsrPrDialTmStartHr OBJECT-TYPE
   SYNTAX      INTEGER
               {
               slOPTg (255)
               }
   MAX-ACCESS  read-write
   STATUS      current
   DESCRIPTION
      "Path: pdp.editConf.dialTimeTable.start.hour

       Possibilities:
               <OPT>   (255)"
   ::= {er1645v2CellUsrPrDialTmEntry 17039360}

er1645v2CellUsrPrDialTmStartMin OBJECT-TYPE
   SYNTAX      INTEGER
               {
               slOPTg (255)
               }
   MAX-ACCESS  read-write
   STATUS      current
   DESCRIPTION
      "Path: pdp.editConf.dialTimeTable.start.minute

       Possibilities:
               <OPT>   (255)"
   ::= {er1645v2CellUsrPrDialTmEntry 17104896}

er1645v2CellUsrPrDialTmEndMon OBJECT-TYPE
   SYNTAX      INTEGER
               {
               jan (1),
               feb (2),
               mar (3),
               apr (4),
               may (5),
               jun (6),
               jul (7),
               aug (8),
               sep (9),
               oct (10),
               nov (11),
               dec (12),
               slOPTg (255)
               }
   MAX-ACCESS  read-write
   STATUS      current
   DESCRIPTION
      "Path: pdp.editConf.dialTimeTable.end.month

       Possibilities:
               jan   (1)
               feb   (2)
               mar   (3)
               apr   (4)
               may   (5)
               jun   (6)
               jul   (7)
               aug   (8)
               sep   (9)
               oct   (10)
               nov   (11)
               dec   (12)
               <OPT>   (255)"
   ::= {er1645v2CellUsrPrDialTmEntry 33619968}

er1645v2CellUsrPrDialTmEndDom OBJECT-TYPE
   SYNTAX      INTEGER
               {
               slOPTg (255)
               }
   MAX-ACCESS  read-write
   STATUS      current
   DESCRIPTION
      "Path: pdp.editConf.dialTimeTable.end.dayOfMonth

       Possibilities:
               <OPT>   (255)"
   ::= {er1645v2CellUsrPrDialTmEntry 33685504}

er1645v2CellUsrPrDialTmEndDof OBJECT-TYPE
   SYNTAX      INTEGER
               {
               sunday (1),
               monday (2),
               tuesday (3),
               wednesday (4),
               thursday (5),
               friday (6),
               saturday (7),
               slOPTg (255)
               }
   MAX-ACCESS  read-write
   STATUS      current
   DESCRIPTION
      "Path: pdp.editConf.dialTimeTable.end.dayOfWeek

       Possibilities:
               sunday   (1)
               monday   (2)
               tuesday   (3)
               wednesday   (4)
               thursday   (5)
               friday   (6)
               saturday   (7)
               <OPT>   (255)"
   ::= {er1645v2CellUsrPrDialTmEntry 33751040}

er1645v2CellUsrPrDialTmEndHr OBJECT-TYPE
   SYNTAX      INTEGER
               {
               slOPTg (255)
               }
   MAX-ACCESS  read-write
   STATUS      current
   DESCRIPTION
      "Path: pdp.editConf.dialTimeTable.end.hour

       Possibilities:
               <OPT>   (255)"
   ::= {er1645v2CellUsrPrDialTmEntry 33816576}

er1645v2CellUsrPrDialTmEndMin OBJECT-TYPE
   SYNTAX      INTEGER
               {
               slOPTg (255)
               }
   MAX-ACCESS  read-write
   STATUS      current
   DESCRIPTION
      "Path: pdp.editConf.dialTimeTable.end.minute

       Possibilities:
               <OPT>   (255)"
   ::= {er1645v2CellUsrPrDialTmEntry 33882112}


er1645v2CellUsrPrCallTimeOut OBJECT IDENTIFIER ::= {er1645v2CellUsrPr 8}

er1645v2CellUsrPrCallTimeOutTable OBJECT-TYPE
   SYNTAX      SEQUENCE OF Er1645v2CellUsrPrCallTimeOutEntry
   MAX-ACCESS  not-accessible
   STATUS      current
   DESCRIPTION
      "call set-up timeout"
   ::= {er1645v2CellUsrPrCallTimeOut 1}

er1645v2CellUsrPrCallTimeOutEntry OBJECT-TYPE
   SYNTAX      Er1645v2CellUsrPrCallTimeOutEntry
   MAX-ACCESS  not-accessible
   STATUS      current
   DESCRIPTION
      ""
   INDEX      { er1645v2CellUsrPrCallTimeOutGlobalIx }
   ::= {er1645v2CellUsrPrCallTimeOutTable 1}

Er1645v2CellUsrPrCallTimeOutEntry ::=
   SEQUENCE
      {
      er1645v2CellUsrPrCallTimeOutGlobalIx
         GlobalIndex,
      er1645v2CellUsrPrCallTimeOutValue
         TimeTicks
      }

er1645v2CellUsrPrCallTimeOutGlobalIx OBJECT-TYPE
   SYNTAX      GlobalIndex
   MAX-ACCESS  not-accessible
   STATUS      current
   DESCRIPTION
      "The value of the tlsCntTreeGlobalIndex of the MANAGED OBJECT."
   ::= {er1645v2CellUsrPrCallTimeOutEntry 10}

er1645v2CellUsrPrCallTimeOutValue OBJECT-TYPE
   SYNTAX      TimeTicks
   MAX-ACCESS  read-write
   STATUS      current
   DESCRIPTION
      "Path: pdp.editConf.callTimeOut

       Time in centi-second."
   ::= {er1645v2CellUsrPrCallTimeOutEntry 2147483648}


er1645v2CellUsrPrSnmpIndexOffset OBJECT IDENTIFIER ::= {er1645v2CellUsrPr 268}

er1645v2CellUsrPrSnmpIndexOffsetTable OBJECT-TYPE
   SYNTAX      SEQUENCE OF Er1645v2CellUsrPrSnmpIndexOffsetEntry
   MAX-ACCESS  not-accessible
   STATUS      current
   DESCRIPTION
      "Preferred offset in the range of SNMP indices for this SWinst, 0 means automatic"
   ::= {er1645v2CellUsrPrSnmpIndexOffset 1}

er1645v2CellUsrPrSnmpIndexOffsetEntry OBJECT-TYPE
   SYNTAX      Er1645v2CellUsrPrSnmpIndexOffsetEntry
   MAX-ACCESS  not-accessible
   STATUS      current
   DESCRIPTION
      ""
   INDEX      { er1645v2CellUsrPrSnmpIndexOffsetGlobalIx }
   ::= {er1645v2CellUsrPrSnmpIndexOffsetTable 1}

Er1645v2CellUsrPrSnmpIndexOffsetEntry ::=
   SEQUENCE
      {
      er1645v2CellUsrPrSnmpIndexOffsetGlobalIx
         GlobalIndex,
      er1645v2CellUsrPrSnmpIndexOffsetValue
         Integer32
      }

er1645v2CellUsrPrSnmpIndexOffsetGlobalIx OBJECT-TYPE
   SYNTAX      GlobalIndex
   MAX-ACCESS  not-accessible
   STATUS      current
   DESCRIPTION
      "The value of the tlsCntTreeGlobalIndex of the MANAGED OBJECT."
   ::= {er1645v2CellUsrPrSnmpIndexOffsetEntry 10}

er1645v2CellUsrPrSnmpIndexOffsetValue OBJECT-TYPE
   SYNTAX      Integer32
   MAX-ACCESS  read-write
   STATUS      current
   DESCRIPTION
      "Path: pdp.editConf.snmpIndexOffset"
   ::= {er1645v2CellUsrPrSnmpIndexOffsetEntry 2147483648}



sr1645v2CellUsrPr OBJECT IDENTIFIER ::= {r1645v2CellUsrPr 14}


sr1645v2CellUsrPrProfUsers OBJECT IDENTIFIER ::= {sr1645v2CellUsrPr 40}

sr1645v2CellUsrPrProfUsersSSCTable OBJECT-TYPE
   SYNTAX      SEQUENCE OF Sr1645v2CellUsrPrProfUsersEntry
   MAX-ACCESS  not-accessible
   STATUS      current
   DESCRIPTION
      "users of the different profiles"
   ::= {sr1645v2CellUsrPrProfUsers 1}

sr1645v2CellUsrPrProfUsersEntry OBJECT-TYPE
   SYNTAX      Sr1645v2CellUsrPrProfUsersEntry
   MAX-ACCESS  not-accessible
   STATUS      current
   DESCRIPTION
      ""
   INDEX      { sr1645v2CellUsrPrProfUsersGlobalIx,
                sr1645v2CellUsrPrProfUsersTableIx }
   ::= {sr1645v2CellUsrPrProfUsersSSCTable 1}

Sr1645v2CellUsrPrProfUsersEntry ::=
   SEQUENCE
      {
      sr1645v2CellUsrPrProfUsersGlobalIx
         GlobalIndex,
      sr1645v2CellUsrPrProfUsersTableIx
         TableIndex,
      sr1645v2CellUsrPrProfUsersType
         INTEGER,
      sr1645v2CellUsrPrProfUsersName
         DisplayString
      }

sr1645v2CellUsrPrProfUsersGlobalIx OBJECT-TYPE
   SYNTAX      GlobalIndex
   MAX-ACCESS  not-accessible
   STATUS      current
   DESCRIPTION
      "The value of the tlsCntTreeGlobalIndex of the MANAGED OBJECT."
   ::= {sr1645v2CellUsrPrProfUsersEntry 10}

sr1645v2CellUsrPrProfUsersTableIx OBJECT-TYPE
   SYNTAX      TableIndex
   MAX-ACCESS  not-accessible
   STATUS      current
   DESCRIPTION
      ""
   ::= {sr1645v2CellUsrPrProfUsersEntry 11}

sr1645v2CellUsrPrProfUsersType OBJECT-TYPE
   SYNTAX      INTEGER
               {
               dialmap (1)
               }
   MAX-ACCESS  read-only
   STATUS      current
   DESCRIPTION
      "Path: pdp.status.profileUsers.type

       Possibilities:
               dialmap   (1)"
   ::= {sr1645v2CellUsrPrProfUsersEntry 16777216}

sr1645v2CellUsrPrProfUsersName OBJECT-TYPE
   SYNTAX      DisplayString
   MAX-ACCESS  read-only
   STATUS      current
   DESCRIPTION
      "Path: pdp.status.profileUsers.name"
   ::= {sr1645v2CellUsrPrProfUsersEntry 33554432}


sr1645v2CellUsrPrSnmpIndex OBJECT IDENTIFIER ::= {sr1645v2CellUsrPr 269}

sr1645v2CellUsrPrSnmpIndexTable OBJECT-TYPE
   SYNTAX      SEQUENCE OF Sr1645v2CellUsrPrSnmpIndexEntry
   MAX-ACCESS  not-accessible
   STATUS      current
   DESCRIPTION
      "SNMP index assigned to this object"
   ::= {sr1645v2CellUsrPrSnmpIndex 1}

sr1645v2CellUsrPrSnmpIndexEntry OBJECT-TYPE
   SYNTAX      Sr1645v2CellUsrPrSnmpIndexEntry
   MAX-ACCESS  not-accessible
   STATUS      current
   DESCRIPTION
      ""
   INDEX      { sr1645v2CellUsrPrSnmpIndexGlobalIx }
   ::= {sr1645v2CellUsrPrSnmpIndexTable 1}

Sr1645v2CellUsrPrSnmpIndexEntry ::=
   SEQUENCE
      {
      sr1645v2CellUsrPrSnmpIndexGlobalIx
         GlobalIndex,
      sr1645v2CellUsrPrSnmpIndexValue
         Integer32
      }

sr1645v2CellUsrPrSnmpIndexGlobalIx OBJECT-TYPE
   SYNTAX      GlobalIndex
   MAX-ACCESS  not-accessible
   STATUS      current
   DESCRIPTION
      "The value of the tlsCntTreeGlobalIndex of the MANAGED OBJECT."
   ::= {sr1645v2CellUsrPrSnmpIndexEntry 10}

sr1645v2CellUsrPrSnmpIndexValue OBJECT-TYPE
   SYNTAX      Integer32
   MAX-ACCESS  read-only
   STATUS      current
   DESCRIPTION
      "Path: pdp.status.snmpIndex"
   ::= {sr1645v2CellUsrPrSnmpIndexEntry 2147483648}



END
