OneAccess-R1646v2-4822-PortSwMC DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2PortSwMC OBJECT IDENTIFIER ::= {r1646Rootv2 4822}

r1646v2PortSwMCMOProp OBJECT IDENTIFIER ::= {r1646v2PortSwMC 1}

r1646v2PortSwMCMOPropEntry OBJECT IDENTIFIER ::= {r1646v2PortSwMCMOProp 1}

r1646v2PortSwMCMOPropPath OBJECT-TYPE
   SYNTAX      ContainmentPath
   MAX-ACCESS  read-only
   STATUS      current
   DESCRIPTION
      "Textual description of the containment tree from the instance of
       the root object down to the instance of the current object."
   ::= {r1646v2PortSwMCMOPropEntry 3}

r1646v2PortSwMCMOPropRev OBJECT-TYPE
   SYNTAX      ObjectRevision
   MAX-ACCESS  read-only
   STATUS      current
   DESCRIPTION
      "This value corresponds with the revision of the MANAGED OBJECT."
   ::= {r1646v2PortSwMCMOPropEntry 4}



er1646v2PortSwMC OBJECT IDENTIFIER ::= {r1646v2PortSwMC 11}


er1646v2PortSwMCRemark OBJECT-TYPE
   SYNTAX      DisplayString
   MAX-ACCESS  read-write
   STATUS      current
   DESCRIPTION
      "Path: ethernet1.editConf.remark
       Info: intfRemark"
   ::= {er1646v2PortSwMC 321}


er1646v2PortSwMCAdminStatus OBJECT-TYPE
   SYNTAX      INTEGER
               {
               up (1),
               down (2)
               }
   MAX-ACCESS  read-write
   STATUS      current
   DESCRIPTION
      "Path: ethernet1.editConf.adminStatus
       Info: ifAdminStatus

       Possibilities:
               up   (1)
               down   (2)"
   ::= {er1646v2PortSwMC 106}


er1646v2PortSwMCAlarmMask OBJECT-TYPE
   SYNTAX      Integer32
   MAX-ACCESS  read-write
   STATUS      current
   DESCRIPTION
      "Path: ethernet1.editConf.alarmMask
       Info: ifAlarmMask

       Bit meanings:
               bit 0 = linkDown"
   ::= {er1646v2PortSwMC 135}


er1646v2PortSwMCAlarmLev OBJECT IDENTIFIER ::= {er1646v2PortSwMC 170}

er1646v2PortSwMCAlarmLevSSC OBJECT IDENTIFIER ::= {er1646v2PortSwMCAlarmLev 1}

er1646v2PortSwMCAlarmLevEntry OBJECT IDENTIFIER ::= {er1646v2PortSwMCAlarmLevSSC 1}

er1646v2PortSwMCAlarmLevLinkDown OBJECT-TYPE
   SYNTAX      Integer32
   MAX-ACCESS  read-write
   STATUS      current
   DESCRIPTION
      "Path: ethernet1.editConf.alarmLevel.linkDown"
   ::= {er1646v2PortSwMCAlarmLevEntry 16777216}


er1646v2PortSwMCBw OBJECT IDENTIFIER ::= {er1646v2PortSwMC 5}

er1646v2PortSwMCBwSSC OBJECT IDENTIFIER ::= {er1646v2PortSwMCBw 1}

er1646v2PortSwMCBwEntry OBJECT IDENTIFIER ::= {er1646v2PortSwMCBwSSC 1}

er1646v2PortSwMCBwMode OBJECT-TYPE
   SYNTAX      INTEGER
               {
               reshaping (1),
               policing (2),
               policingReshape (3)
               }
   MAX-ACCESS  read-write
   STATUS      current
   DESCRIPTION
      "Path: ethernet1.editConf.bandwidth.mode

       Possibilities:
               reshaping   (1)
               policing   (2)
               policingReshape   (3)"
   ::= {er1646v2PortSwMCBwEntry 3758096384}

er1646v2PortSwMCBwCir OBJECT-TYPE
   SYNTAX      Integer32
   MAX-ACCESS  read-write
   STATUS      current
   DESCRIPTION
      "Path: ethernet1.editConf.bandwidth.cir"
   ::= {er1646v2PortSwMCBwEntry 268435456}

er1646v2PortSwMCBwEir OBJECT-TYPE
   SYNTAX      Integer32
   MAX-ACCESS  read-write
   STATUS      current
   DESCRIPTION
      "Path: ethernet1.editConf.bandwidth.eir"
   ::= {er1646v2PortSwMCBwEntry 1879048192}

er1646v2PortSwMCBwUnit OBJECT-TYPE
   SYNTAX      INTEGER
               {
               bitssec (1),
               percent (2)
               }
   MAX-ACCESS  read-write
   STATUS      current
   DESCRIPTION
      "Path: ethernet1.editConf.bandwidth.unit

       Possibilities:
               bits/sec   (1)
               percent   (2)"
   ::= {er1646v2PortSwMCBwEntry 1342177280}

er1646v2PortSwMCBwTc OBJECT-TYPE
   SYNTAX      INTEGER
               {
               auto (0)
               }
   MAX-ACCESS  read-write
   STATUS      current
   DESCRIPTION
      "Path: ethernet1.editConf.bandwidth.tc

       Possibilities:
               auto   (0)"
   ::= {er1646v2PortSwMCBwEntry 1610612736}

er1646v2PortSwMCBwTcFactor OBJECT-TYPE
   SYNTAX      INTEGER
               {
               ms (10),
               s100us (1)
               }
   MAX-ACCESS  read-write
   STATUS      current
   DESCRIPTION
      "Path: ethernet1.editConf.bandwidth.tcFactor

       Possibilities:
               ms   (10)
               *100us   (1)"
   ::= {er1646v2PortSwMCBwEntry 2147483648}

er1646v2PortSwMCBwCorrType OBJECT-TYPE
   SYNTAX      INTEGER
               {
               noCorrection (0),
               predefined (1),
               manual (2)
               }
   MAX-ACCESS  read-write
   STATUS      current
   DESCRIPTION
      "Path: ethernet1.editConf.bandwidth.correction.type

       Possibilities:
               noCorrection   (0)
               predefined   (1)
               manual   (2)"
   ::= {er1646v2PortSwMCBwEntry 570425344}

er1646v2PortSwMCBwCorrPredefEncapsFrameRelay OBJECT-TYPE
   SYNTAX      DisplayString
   MAX-ACCESS  read-write
   STATUS      current
   DESCRIPTION
      "Path: ethernet1.editConf.bandwidth.correction.predefined.encapsulation.frameRelay"
   ::= {er1646v2PortSwMCBwEntry 608436224}

er1646v2PortSwMCBwCorrPredefEncapsPpp OBJECT-TYPE
   SYNTAX      DisplayString
   MAX-ACCESS  read-write
   STATUS      current
   DESCRIPTION
      "Path: ethernet1.editConf.bandwidth.correction.predefined.encapsulation.ppp"
   ::= {er1646v2PortSwMCBwEntry 608698368}

er1646v2PortSwMCBwCorrPredefEncapsAtmHl OBJECT-TYPE
   SYNTAX      INTEGER
               {
               rfc2684 (0),
               ppp (1),
               pppOverEthernet (2)
               }
   MAX-ACCESS  read-write
   STATUS      current
   DESCRIPTION
      "Path: ethernet1.editConf.bandwidth.correction.predefined.encapsulation.atm.higherLayer

       Possibilities:
               rfc2684   (0)
               ppp   (1)
               pppOverEthernet   (2)"
   ::= {er1646v2PortSwMCBwEntry 608993280}

er1646v2PortSwMCBwCorrPredefEncapsAtmMp OBJECT-TYPE
   SYNTAX      INTEGER
               {
               llcEncapsulation (0),
               vcMultiplexing (1)
               }
   MAX-ACCESS  read-write
   STATUS      current
   DESCRIPTION
      "Path: ethernet1.editConf.bandwidth.correction.predefined.encapsulation.atm.multiProtocol

       Possibilities:
               llcEncapsulation   (0)
               vcMultiplexing   (1)"
   ::= {er1646v2PortSwMCBwEntry 609026048}

er1646v2PortSwMCBwCorrPredefEncapsHdlc OBJECT-TYPE
   SYNTAX      DisplayString
   MAX-ACCESS  read-write
   STATUS      current
   DESCRIPTION
      "Path: ethernet1.editConf.bandwidth.correction.predefined.encapsulation.hdlc"
   ::= {er1646v2PortSwMCBwEntry 609222656}

er1646v2PortSwMCBwCorrPredefEncapsEfmFs OBJECT-TYPE
   SYNTAX      Integer32
   MAX-ACCESS  read-write
   STATUS      current
   DESCRIPTION
      "Path: ethernet1.editConf.bandwidth.correction.predefined.encapsulation.efm.fragmentSize"
   ::= {er1646v2PortSwMCBwEntry 609517568}

er1646v2PortSwMCBwCorrPredefEncapsEfmIb OBJECT-TYPE
   SYNTAX      Integer32
   MAX-ACCESS  read-write
   STATUS      current
   DESCRIPTION
      "Path: ethernet1.editConf.bandwidth.correction.predefined.encapsulation.efm.idleBytes"
   ::= {er1646v2PortSwMCBwEntry 609550336}

er1646v2PortSwMCBwCorrPredefMode OBJECT-TYPE
   SYNTAX      INTEGER
               {
               routing (0),
               bridging (1)
               }
   MAX-ACCESS  read-write
   STATUS      current
   DESCRIPTION
      "Path: ethernet1.editConf.bandwidth.correction.predefined.mode

       Possibilities:
               routing   (0)
               bridging   (1)"
   ::= {er1646v2PortSwMCBwEntry 612368384}

er1646v2PortSwMCBwCorrManualOverhead OBJECT-TYPE
   SYNTAX      Integer32
   MAX-ACCESS  read-write
   STATUS      current
   DESCRIPTION
      "Path: ethernet1.editConf.bandwidth.correction.manual.overhead"
   ::= {er1646v2PortSwMCBwEntry 637665280}

er1646v2PortSwMCBwCorrManualFrameData OBJECT-TYPE
   SYNTAX      Counter32
   MAX-ACCESS  read-write
   STATUS      current
   DESCRIPTION
      "Path: ethernet1.editConf.bandwidth.correction.manual.frameData

       32 bit unsigned wrappable counter."
   ::= {er1646v2PortSwMCBwEntry 637796352}

er1646v2PortSwMCBwCorrManualFrameHeader OBJECT-TYPE
   SYNTAX      Counter32
   MAX-ACCESS  read-write
   STATUS      current
   DESCRIPTION
      "Path: ethernet1.editConf.bandwidth.correction.manual.frameHeader

       32 bit unsigned wrappable counter."
   ::= {er1646v2PortSwMCBwEntry 637927424}

er1646v2PortSwMCBwMaxFifoQLen OBJECT-TYPE
   SYNTAX      Integer32
   MAX-ACCESS  read-write
   STATUS      current
   DESCRIPTION
      "Path: ethernet1.editConf.bandwidth.maxFifoQLen"
   ::= {er1646v2PortSwMCBwEntry 805306368}

er1646v2PortSwMCBwDeFlagCir OBJECT-TYPE
   SYNTAX      INTEGER
               {
               allowed (1),
               notAllowed (2)
               }
   MAX-ACCESS  read-write
   STATUS      current
   DESCRIPTION
      "Path: ethernet1.editConf.bandwidth.deFlag.cir

       Possibilities:
               allowed   (1)
               notAllowed   (2)"
   ::= {er1646v2PortSwMCBwEntry 3490709504}

er1646v2PortSwMCBwDeFlagEir OBJECT-TYPE
   SYNTAX      INTEGER
               {
               allowed (1),
               notAllowed (2)
               }
   MAX-ACCESS  read-write
   STATUS      current
   DESCRIPTION
      "Path: ethernet1.editConf.bandwidth.deFlag.eir

       Possibilities:
               allowed   (1)
               notAllowed   (2)"
   ::= {er1646v2PortSwMCBwEntry 3491758080}

er1646v2PortSwMCBwDeFlagViolate OBJECT-TYPE
   SYNTAX      INTEGER
               {
               allowed (1),
               notAllowed (2)
               }
   MAX-ACCESS  read-write
   STATUS      current
   DESCRIPTION
      "Path: ethernet1.editConf.bandwidth.deFlag.violate

       Possibilities:
               allowed   (1)
               notAllowed   (2)"
   ::= {er1646v2PortSwMCBwEntry 3492806656}

er1646v2PortSwMCBwActCirActNone OBJECT-TYPE
   SYNTAX      OCTET STRING
   MAX-ACCESS  read-write
   STATUS      current
   DESCRIPTION
      "Path: ethernet1.editConf.bandwidth.action.cirAction.none"
   ::= {er1646v2PortSwMCBwEntry 4062183424}

er1646v2PortSwMCBwActCirActEthCos1 OBJECT-TYPE
   SYNTAX      INTEGER
               {
               unchanged (256)
               }
   MAX-ACCESS  read-write
   STATUS      current
   DESCRIPTION
      "Path: ethernet1.editConf.bandwidth.action.cirAction.ethernet.cosDepth1

       Possibilities:
               unchanged   (256)"
   ::= {er1646v2PortSwMCBwEntry 4064346112}

er1646v2PortSwMCBwActCirActEthDei1 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth1

       Possibilities:
               unchanged   (255)
               clear   (0)
               set   (1)"
   ::= {er1646v2PortSwMCBwEntry 4065656832}

er1646v2PortSwMCBwActCirActEthCos2 OBJECT-TYPE
   SYNTAX      INTEGER
               {
               unchanged (256)
               }
   MAX-ACCESS  read-write
   STATUS      current
   DESCRIPTION
      "Path: ethernet1.editConf.bandwidth.action.cirAction.ethernet.cosDepth2

       Possibilities:
               unchanged   (256)"
   ::= {er1646v2PortSwMCBwEntry 4064411648}

er1646v2PortSwMCBwActCirActEthDei2 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth2

       Possibilities:
               unchanged   (255)
               clear   (0)
               set   (1)"
   ::= {er1646v2PortSwMCBwEntry 4065722368}

er1646v2PortSwMCBwActCirActEthCos3 OBJECT-TYPE
   SYNTAX      INTEGER
               {
               unchanged (256)
               }
   MAX-ACCESS  read-write
   STATUS      current
   DESCRIPTION
      "Path: ethernet1.editConf.bandwidth.action.cirAction.ethernet.cosDepth3

       Possibilities:
               unchanged   (256)"
   ::= {er1646v2PortSwMCBwEntry 4064477184}

er1646v2PortSwMCBwActCirActEthDei3 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth3

       Possibilities:
               unchanged   (255)
               clear   (0)
               set   (1)"
   ::= {er1646v2PortSwMCBwEntry 4065787904}

er1646v2PortSwMCBwActCirActEthCos4 OBJECT-TYPE
   SYNTAX      INTEGER
               {
               unchanged (256)
               }
   MAX-ACCESS  read-write
   STATUS      current
   DESCRIPTION
      "Path: ethernet1.editConf.bandwidth.action.cirAction.ethernet.cosDepth4

       Possibilities:
               unchanged   (256)"
   ::= {er1646v2PortSwMCBwEntry 4064542720}

er1646v2PortSwMCBwActCirActEthDei4 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth4

       Possibilities:
               unchanged   (255)
               clear   (0)
               set   (1)"
   ::= {er1646v2PortSwMCBwEntry 4065853440}

er1646v2PortSwMCBwActCirActEthCos5 OBJECT-TYPE
   SYNTAX      INTEGER
               {
               unchanged (256)
               }
   MAX-ACCESS  read-write
   STATUS      current
   DESCRIPTION
      "Path: ethernet1.editConf.bandwidth.action.cirAction.ethernet.cosDepth5

       Possibilities:
               unchanged   (256)"
   ::= {er1646v2PortSwMCBwEntry 4064608256}

er1646v2PortSwMCBwActCirActEthDei5 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth5

       Possibilities:
               unchanged   (255)
               clear   (0)
               set   (1)"
   ::= {er1646v2PortSwMCBwEntry 4065918976}

er1646v2PortSwMCBwActCirActEthCos6 OBJECT-TYPE
   SYNTAX      INTEGER
               {
               unchanged (256)
               }
   MAX-ACCESS  read-write
   STATUS      current
   DESCRIPTION
      "Path: ethernet1.editConf.bandwidth.action.cirAction.ethernet.cosDepth6

       Possibilities:
               unchanged   (256)"
   ::= {er1646v2PortSwMCBwEntry 4064673792}

er1646v2PortSwMCBwActCirActEthDei6 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth6

       Possibilities:
               unchanged   (255)
               clear   (0)
               set   (1)"
   ::= {er1646v2PortSwMCBwEntry 4065984512}

er1646v2PortSwMCBwActCirActEthCos7 OBJECT-TYPE
   SYNTAX      INTEGER
               {
               unchanged (256)
               }
   MAX-ACCESS  read-write
   STATUS      current
   DESCRIPTION
      "Path: ethernet1.editConf.bandwidth.action.cirAction.ethernet.cosDepth7

       Possibilities:
               unchanged   (256)"
   ::= {er1646v2PortSwMCBwEntry 4064739328}

er1646v2PortSwMCBwActCirActEthDei7 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth7

       Possibilities:
               unchanged   (255)
               clear   (0)
               set   (1)"
   ::= {er1646v2PortSwMCBwEntry 4066050048}

er1646v2PortSwMCBwActCirActEthCos8 OBJECT-TYPE
   SYNTAX      INTEGER
               {
               unchanged (256)
               }
   MAX-ACCESS  read-write
   STATUS      current
   DESCRIPTION
      "Path: ethernet1.editConf.bandwidth.action.cirAction.ethernet.cosDepth8

       Possibilities:
               unchanged   (256)"
   ::= {er1646v2PortSwMCBwEntry 4064804864}

er1646v2PortSwMCBwActCirActEthDei8 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth8

       Possibilities:
               unchanged   (255)
               clear   (0)
               set   (1)"
   ::= {er1646v2PortSwMCBwEntry 4066115584}

er1646v2PortSwMCBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4064870400}

er1646v2PortSwMCBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4064935936}

er1646v2PortSwMCBwActCirActEthDrpLev OBJECT-TYPE
   SYNTAX      INTEGER
               {
               unchanged (0)
               }
   MAX-ACCESS  read-write
   STATUS      current
   DESCRIPTION
      "Path: ethernet1.editConf.bandwidth.action.cirAction.ethernet.dropLevel

       Possibilities:
               unchanged   (0)"
   ::= {er1646v2PortSwMCBwEntry 4065001472}

er1646v2PortSwMCBwActCirActEthDeFlag OBJECT-TYPE
   SYNTAX      INTEGER
               {
               unchanged (255),
               clear (0),
               set (1)
               }
   MAX-ACCESS  read-write
   STATUS      current
   DESCRIPTION
      "Path: ethernet1.editConf.bandwidth.action.cirAction.ethernet.deFlag

       Possibilities:
               unchanged   (255)
               clear   (0)
               set   (1)"
   ::= {er1646v2PortSwMCBwEntry 4065198080}

er1646v2PortSwMCBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4071161856}

er1646v2PortSwMCBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4071227392}

er1646v2PortSwMCBwActCirActIpDrpLev OBJECT-TYPE
   SYNTAX      INTEGER
               {
               unchanged (0)
               }
   MAX-ACCESS  read-write
   STATUS      current
   DESCRIPTION
      "Path: ethernet1.editConf.bandwidth.action.cirAction.ip.dropLevel

       Possibilities:
               unchanged   (0)"
   ::= {er1646v2PortSwMCBwEntry 4071292928}

er1646v2PortSwMCBwActCirActIpDeFlag OBJECT-TYPE
   SYNTAX      INTEGER
               {
               unchanged (255),
               clear (0),
               set (1)
               }
   MAX-ACCESS  read-write
   STATUS      current
   DESCRIPTION
      "Path: ethernet1.editConf.bandwidth.action.cirAction.ip.deFlag

       Possibilities:
               unchanged   (255)
               clear   (0)
               set   (1)"
   ::= {er1646v2PortSwMCBwEntry 4071489536}

er1646v2PortSwMCBwActEirActNone OBJECT-TYPE
   SYNTAX      OCTET STRING
   MAX-ACCESS  read-write
   STATUS      current
   DESCRIPTION
      "Path: ethernet1.editConf.bandwidth.action.eirAction.none"
   ::= {er1646v2PortSwMCBwEntry 4095737856}

er1646v2PortSwMCBwActEirActEthCos1 OBJECT-TYPE
   SYNTAX      INTEGER
               {
               unchanged (256)
               }
   MAX-ACCESS  read-write
   STATUS      current
   DESCRIPTION
      "Path: ethernet1.editConf.bandwidth.action.eirAction.ethernet.cosDepth1

       Possibilities:
               unchanged   (256)"
   ::= {er1646v2PortSwMCBwEntry 4097900544}

er1646v2PortSwMCBwActEirActEthDei1 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth1

       Possibilities:
               unchanged   (255)
               clear   (0)
               set   (1)"
   ::= {er1646v2PortSwMCBwEntry 4099211264}

er1646v2PortSwMCBwActEirActEthCos2 OBJECT-TYPE
   SYNTAX      INTEGER
               {
               unchanged (256)
               }
   MAX-ACCESS  read-write
   STATUS      current
   DESCRIPTION
      "Path: ethernet1.editConf.bandwidth.action.eirAction.ethernet.cosDepth2

       Possibilities:
               unchanged   (256)"
   ::= {er1646v2PortSwMCBwEntry 4097966080}

er1646v2PortSwMCBwActEirActEthDei2 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth2

       Possibilities:
               unchanged   (255)
               clear   (0)
               set   (1)"
   ::= {er1646v2PortSwMCBwEntry 4099276800}

er1646v2PortSwMCBwActEirActEthCos3 OBJECT-TYPE
   SYNTAX      INTEGER
               {
               unchanged (256)
               }
   MAX-ACCESS  read-write
   STATUS      current
   DESCRIPTION
      "Path: ethernet1.editConf.bandwidth.action.eirAction.ethernet.cosDepth3

       Possibilities:
               unchanged   (256)"
   ::= {er1646v2PortSwMCBwEntry 4098031616}

er1646v2PortSwMCBwActEirActEthDei3 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth3

       Possibilities:
               unchanged   (255)
               clear   (0)
               set   (1)"
   ::= {er1646v2PortSwMCBwEntry 4099342336}

er1646v2PortSwMCBwActEirActEthCos4 OBJECT-TYPE
   SYNTAX      INTEGER
               {
               unchanged (256)
               }
   MAX-ACCESS  read-write
   STATUS      current
   DESCRIPTION
      "Path: ethernet1.editConf.bandwidth.action.eirAction.ethernet.cosDepth4

       Possibilities:
               unchanged   (256)"
   ::= {er1646v2PortSwMCBwEntry 4098097152}

er1646v2PortSwMCBwActEirActEthDei4 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth4

       Possibilities:
               unchanged   (255)
               clear   (0)
               set   (1)"
   ::= {er1646v2PortSwMCBwEntry 4099407872}

er1646v2PortSwMCBwActEirActEthCos5 OBJECT-TYPE
   SYNTAX      INTEGER
               {
               unchanged (256)
               }
   MAX-ACCESS  read-write
   STATUS      current
   DESCRIPTION
      "Path: ethernet1.editConf.bandwidth.action.eirAction.ethernet.cosDepth5

       Possibilities:
               unchanged   (256)"
   ::= {er1646v2PortSwMCBwEntry 4098162688}

er1646v2PortSwMCBwActEirActEthDei5 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth5

       Possibilities:
               unchanged   (255)
               clear   (0)
               set   (1)"
   ::= {er1646v2PortSwMCBwEntry 4099473408}

er1646v2PortSwMCBwActEirActEthCos6 OBJECT-TYPE
   SYNTAX      INTEGER
               {
               unchanged (256)
               }
   MAX-ACCESS  read-write
   STATUS      current
   DESCRIPTION
      "Path: ethernet1.editConf.bandwidth.action.eirAction.ethernet.cosDepth6

       Possibilities:
               unchanged   (256)"
   ::= {er1646v2PortSwMCBwEntry 4098228224}

er1646v2PortSwMCBwActEirActEthDei6 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth6

       Possibilities:
               unchanged   (255)
               clear   (0)
               set   (1)"
   ::= {er1646v2PortSwMCBwEntry 4099538944}

er1646v2PortSwMCBwActEirActEthCos7 OBJECT-TYPE
   SYNTAX      INTEGER
               {
               unchanged (256)
               }
   MAX-ACCESS  read-write
   STATUS      current
   DESCRIPTION
      "Path: ethernet1.editConf.bandwidth.action.eirAction.ethernet.cosDepth7

       Possibilities:
               unchanged   (256)"
   ::= {er1646v2PortSwMCBwEntry 4098293760}

er1646v2PortSwMCBwActEirActEthDei7 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth7

       Possibilities:
               unchanged   (255)
               clear   (0)
               set   (1)"
   ::= {er1646v2PortSwMCBwEntry 4099604480}

er1646v2PortSwMCBwActEirActEthCos8 OBJECT-TYPE
   SYNTAX      INTEGER
               {
               unchanged (256)
               }
   MAX-ACCESS  read-write
   STATUS      current
   DESCRIPTION
      "Path: ethernet1.editConf.bandwidth.action.eirAction.ethernet.cosDepth8

       Possibilities:
               unchanged   (256)"
   ::= {er1646v2PortSwMCBwEntry 4098359296}

er1646v2PortSwMCBwActEirActEthDei8 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth8

       Possibilities:
               unchanged   (255)
               clear   (0)
               set   (1)"
   ::= {er1646v2PortSwMCBwEntry 4099670016}

er1646v2PortSwMCBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4098424832}

er1646v2PortSwMCBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4098490368}

er1646v2PortSwMCBwActEirActEthDrpLev OBJECT-TYPE
   SYNTAX      INTEGER
               {
               unchanged (0)
               }
   MAX-ACCESS  read-write
   STATUS      current
   DESCRIPTION
      "Path: ethernet1.editConf.bandwidth.action.eirAction.ethernet.dropLevel

       Possibilities:
               unchanged   (0)"
   ::= {er1646v2PortSwMCBwEntry 4098555904}

er1646v2PortSwMCBwActEirActEthDeFlag OBJECT-TYPE
   SYNTAX      INTEGER
               {
               unchanged (255),
               clear (0),
               set (1)
               }
   MAX-ACCESS  read-write
   STATUS      current
   DESCRIPTION
      "Path: ethernet1.editConf.bandwidth.action.eirAction.ethernet.deFlag

       Possibilities:
               unchanged   (255)
               clear   (0)
               set   (1)"
   ::= {er1646v2PortSwMCBwEntry 4098752512}

er1646v2PortSwMCBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4104716288}

er1646v2PortSwMCBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4104781824}

er1646v2PortSwMCBwActEirActIpDrpLev OBJECT-TYPE
   SYNTAX      INTEGER
               {
               unchanged (0)
               }
   MAX-ACCESS  read-write
   STATUS      current
   DESCRIPTION
      "Path: ethernet1.editConf.bandwidth.action.eirAction.ip.dropLevel

       Possibilities:
               unchanged   (0)"
   ::= {er1646v2PortSwMCBwEntry 4104847360}

er1646v2PortSwMCBwActEirActIpDeFlag OBJECT-TYPE
   SYNTAX      INTEGER
               {
               unchanged (255),
               clear (0),
               set (1)
               }
   MAX-ACCESS  read-write
   STATUS      current
   DESCRIPTION
      "Path: ethernet1.editConf.bandwidth.action.eirAction.ip.deFlag

       Possibilities:
               unchanged   (255)
               clear   (0)
               set   (1)"
   ::= {er1646v2PortSwMCBwEntry 4105043968}

er1646v2PortSwMCBwActViolActNone OBJECT-TYPE
   SYNTAX      OCTET STRING
   MAX-ACCESS  read-write
   STATUS      current
   DESCRIPTION
      "Path: ethernet1.editConf.bandwidth.action.violateAction.none"
   ::= {er1646v2PortSwMCBwEntry 4129292288}

er1646v2PortSwMCBwActViolActDrop OBJECT-TYPE
   SYNTAX      OCTET STRING
   MAX-ACCESS  read-write
   STATUS      current
   DESCRIPTION
      "Path: ethernet1.editConf.bandwidth.action.violateAction.drop"
   ::= {er1646v2PortSwMCBwEntry 4133486592}

er1646v2PortSwMCBwActViolActEthCos1 OBJECT-TYPE
   SYNTAX      INTEGER
               {
               unchanged (256)
               }
   MAX-ACCESS  read-write
   STATUS      current
   DESCRIPTION
      "Path: ethernet1.editConf.bandwidth.action.violateAction.ethernet.cosDepth1

       Possibilities:
               unchanged   (256)"
   ::= {er1646v2PortSwMCBwEntry 4131454976}

er1646v2PortSwMCBwActViolActEthDei1 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth1

       Possibilities:
               unchanged   (255)
               clear   (0)
               set   (1)"
   ::= {er1646v2PortSwMCBwEntry 4132765696}

er1646v2PortSwMCBwActViolActEthCos2 OBJECT-TYPE
   SYNTAX      INTEGER
               {
               unchanged (256)
               }
   MAX-ACCESS  read-write
   STATUS      current
   DESCRIPTION
      "Path: ethernet1.editConf.bandwidth.action.violateAction.ethernet.cosDepth2

       Possibilities:
               unchanged   (256)"
   ::= {er1646v2PortSwMCBwEntry 4131520512}

er1646v2PortSwMCBwActViolActEthDei2 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth2

       Possibilities:
               unchanged   (255)
               clear   (0)
               set   (1)"
   ::= {er1646v2PortSwMCBwEntry 4132831232}

er1646v2PortSwMCBwActViolActEthCos3 OBJECT-TYPE
   SYNTAX      INTEGER
               {
               unchanged (256)
               }
   MAX-ACCESS  read-write
   STATUS      current
   DESCRIPTION
      "Path: ethernet1.editConf.bandwidth.action.violateAction.ethernet.cosDepth3

       Possibilities:
               unchanged   (256)"
   ::= {er1646v2PortSwMCBwEntry 4131586048}

er1646v2PortSwMCBwActViolActEthDei3 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth3

       Possibilities:
               unchanged   (255)
               clear   (0)
               set   (1)"
   ::= {er1646v2PortSwMCBwEntry 4132896768}

er1646v2PortSwMCBwActViolActEthCos4 OBJECT-TYPE
   SYNTAX      INTEGER
               {
               unchanged (256)
               }
   MAX-ACCESS  read-write
   STATUS      current
   DESCRIPTION
      "Path: ethernet1.editConf.bandwidth.action.violateAction.ethernet.cosDepth4

       Possibilities:
               unchanged   (256)"
   ::= {er1646v2PortSwMCBwEntry 4131651584}

er1646v2PortSwMCBwActViolActEthDei4 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth4

       Possibilities:
               unchanged   (255)
               clear   (0)
               set   (1)"
   ::= {er1646v2PortSwMCBwEntry 4132962304}

er1646v2PortSwMCBwActViolActEthCos5 OBJECT-TYPE
   SYNTAX      INTEGER
               {
               unchanged (256)
               }
   MAX-ACCESS  read-write
   STATUS      current
   DESCRIPTION
      "Path: ethernet1.editConf.bandwidth.action.violateAction.ethernet.cosDepth5

       Possibilities:
               unchanged   (256)"
   ::= {er1646v2PortSwMCBwEntry 4131717120}

er1646v2PortSwMCBwActViolActEthDei5 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth5

       Possibilities:
               unchanged   (255)
               clear   (0)
               set   (1)"
   ::= {er1646v2PortSwMCBwEntry 4133027840}

er1646v2PortSwMCBwActViolActEthCos6 OBJECT-TYPE
   SYNTAX      INTEGER
               {
               unchanged (256)
               }
   MAX-ACCESS  read-write
   STATUS      current
   DESCRIPTION
      "Path: ethernet1.editConf.bandwidth.action.violateAction.ethernet.cosDepth6

       Possibilities:
               unchanged   (256)"
   ::= {er1646v2PortSwMCBwEntry 4131782656}

er1646v2PortSwMCBwActViolActEthDei6 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth6

       Possibilities:
               unchanged   (255)
               clear   (0)
               set   (1)"
   ::= {er1646v2PortSwMCBwEntry 4133093376}

er1646v2PortSwMCBwActViolActEthCos7 OBJECT-TYPE
   SYNTAX      INTEGER
               {
               unchanged (256)
               }
   MAX-ACCESS  read-write
   STATUS      current
   DESCRIPTION
      "Path: ethernet1.editConf.bandwidth.action.violateAction.ethernet.cosDepth7

       Possibilities:
               unchanged   (256)"
   ::= {er1646v2PortSwMCBwEntry 4131848192}

er1646v2PortSwMCBwActViolActEthDei7 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth7

       Possibilities:
               unchanged   (255)
               clear   (0)
               set   (1)"
   ::= {er1646v2PortSwMCBwEntry 4133158912}

er1646v2PortSwMCBwActViolActEthCos8 OBJECT-TYPE
   SYNTAX      INTEGER
               {
               unchanged (256)
               }
   MAX-ACCESS  read-write
   STATUS      current
   DESCRIPTION
      "Path: ethernet1.editConf.bandwidth.action.violateAction.ethernet.cosDepth8

       Possibilities:
               unchanged   (256)"
   ::= {er1646v2PortSwMCBwEntry 4131913728}

er1646v2PortSwMCBwActViolActEthDei8 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth8

       Possibilities:
               unchanged   (255)
               clear   (0)
               set   (1)"
   ::= {er1646v2PortSwMCBwEntry 4133224448}

er1646v2PortSwMCBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4131979264}

er1646v2PortSwMCBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4132044800}

er1646v2PortSwMCBwActViolActEthDrpLev OBJECT-TYPE
   SYNTAX      INTEGER
               {
               unchanged (0)
               }
   MAX-ACCESS  read-write
   STATUS      current
   DESCRIPTION
      "Path: ethernet1.editConf.bandwidth.action.violateAction.ethernet.dropLevel

       Possibilities:
               unchanged   (0)"
   ::= {er1646v2PortSwMCBwEntry 4132110336}

er1646v2PortSwMCBwActViolActEthDeFlag OBJECT-TYPE
   SYNTAX      INTEGER
               {
               unchanged (255),
               clear (0),
               set (1)
               }
   MAX-ACCESS  read-write
   STATUS      current
   DESCRIPTION
      "Path: ethernet1.editConf.bandwidth.action.violateAction.ethernet.deFlag

       Possibilities:
               unchanged   (255)
               clear   (0)
               set   (1)"
   ::= {er1646v2PortSwMCBwEntry 4132306944}

er1646v2PortSwMCBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCBwEntry 4138270720}

er1646v2PortSwMCBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCBwEntry 4138336256}

er1646v2PortSwMCBwActViolActIpDrpLev OBJECT-TYPE
   SYNTAX      INTEGER
               {
               unchanged (0)
               }
   MAX-ACCESS  read-write
   STATUS      current
   DESCRIPTION
      "Path: ethernet1.editConf.bandwidth.action.violateAction.ip.dropLevel

       Possibilities:
               unchanged   (0)"
   ::= {er1646v2PortSwMCBwEntry 4138401792}

er1646v2PortSwMCBwActViolActIpDeFlag OBJECT-TYPE
   SYNTAX      INTEGER
               {
               unchanged (255),
               clear (0),
               set (1)
               }
   MAX-ACCESS  read-write
   STATUS      current
   DESCRIPTION
      "Path: ethernet1.editConf.bandwidth.action.violateAction.ip.deFlag

       Possibilities:
               unchanged   (255)
               clear   (0)
               set   (1)"
   ::= {er1646v2PortSwMCBwEntry 4138598400}


er1646v2PortSwMCPriorityPolicy OBJECT-TYPE
   SYNTAX      DisplayString
   MAX-ACCESS  read-write
   STATUS      current
   DESCRIPTION
      "Path: ethernet1.editConf.priorityPolicy
       Info: Preferred Policy"
   ::= {er1646v2PortSwMC 39}


er1646v2PortSwMCMru OBJECT-TYPE
   SYNTAX      Integer32
   MAX-ACCESS  read-write
   STATUS      current
   DESCRIPTION
      "Path: ethernet1.editConf.mru"
   ::= {er1646v2PortSwMC 43}


er1646v2PortSwMCDelayOptimisation OBJECT-TYPE
   SYNTAX      INTEGER
               {
               disabled (0),
               enabled (1)
               }
   MAX-ACCESS  read-write
   STATUS      current
   DESCRIPTION
      "Path: ethernet1.editConf.delayOptimisation
       Info: optimise delay

       Possibilities:
               disabled   (0)
               enabled   (1)"
   ::= {er1646v2PortSwMC 80}


er1646v2PortSwMCIbw OBJECT IDENTIFIER ::= {er1646v2PortSwMC 13}

er1646v2PortSwMCIbwSSC OBJECT IDENTIFIER ::= {er1646v2PortSwMCIbw 1}

er1646v2PortSwMCIbwEntry OBJECT IDENTIFIER ::= {er1646v2PortSwMCIbwSSC 1}

er1646v2PortSwMCIbwMode OBJECT-TYPE
   SYNTAX      INTEGER
               {
               reshaping (1),
               policing (2)
               }
   MAX-ACCESS  read-write
   STATUS      current
   DESCRIPTION
      "Path: ethernet1.editConf.inboundBandwidth.mode

       Possibilities:
               reshaping   (1)
               policing   (2)"
   ::= {er1646v2PortSwMCIbwEntry 3758096384}

er1646v2PortSwMCIbwCir OBJECT-TYPE
   SYNTAX      Integer32
   MAX-ACCESS  read-write
   STATUS      current
   DESCRIPTION
      "Path: ethernet1.editConf.inboundBandwidth.cir"
   ::= {er1646v2PortSwMCIbwEntry 268435456}

er1646v2PortSwMCIbwEir OBJECT-TYPE
   SYNTAX      Integer32
   MAX-ACCESS  read-write
   STATUS      current
   DESCRIPTION
      "Path: ethernet1.editConf.inboundBandwidth.eir"
   ::= {er1646v2PortSwMCIbwEntry 1879048192}

er1646v2PortSwMCIbwTc OBJECT-TYPE
   SYNTAX      INTEGER
               {
               auto (0)
               }
   MAX-ACCESS  read-write
   STATUS      current
   DESCRIPTION
      "Path: ethernet1.editConf.inboundBandwidth.tc

       Possibilities:
               auto   (0)"
   ::= {er1646v2PortSwMCIbwEntry 1610612736}

er1646v2PortSwMCIbwTcFactor OBJECT-TYPE
   SYNTAX      INTEGER
               {
               ms (10),
               s100us (1)
               }
   MAX-ACCESS  read-write
   STATUS      current
   DESCRIPTION
      "Path: ethernet1.editConf.inboundBandwidth.tcFactor

       Possibilities:
               ms   (10)
               *100us   (1)"
   ::= {er1646v2PortSwMCIbwEntry 2147483648}

er1646v2PortSwMCIbwCorrType OBJECT-TYPE
   SYNTAX      INTEGER
               {
               noCorrection (0),
               predefined (1),
               manual (2)
               }
   MAX-ACCESS  read-write
   STATUS      current
   DESCRIPTION
      "Path: ethernet1.editConf.inboundBandwidth.correction.type

       Possibilities:
               noCorrection   (0)
               predefined   (1)
               manual   (2)"
   ::= {er1646v2PortSwMCIbwEntry 570425344}

er1646v2PortSwMCIbwCorrPredefEncapsFrameRelay OBJECT-TYPE
   SYNTAX      DisplayString
   MAX-ACCESS  read-write
   STATUS      current
   DESCRIPTION
      "Path: ethernet1.editConf.inboundBandwidth.correction.predefined.encapsulation.frameRelay"
   ::= {er1646v2PortSwMCIbwEntry 608436224}

er1646v2PortSwMCIbwCorrPredefEncapsPpp OBJECT-TYPE
   SYNTAX      DisplayString
   MAX-ACCESS  read-write
   STATUS      current
   DESCRIPTION
      "Path: ethernet1.editConf.inboundBandwidth.correction.predefined.encapsulation.ppp"
   ::= {er1646v2PortSwMCIbwEntry 608698368}

er1646v2PortSwMCIbwCorrPredefEncapsAtmHl OBJECT-TYPE
   SYNTAX      INTEGER
               {
               rfc2684 (0),
               ppp (1),
               pppOverEthernet (2)
               }
   MAX-ACCESS  read-write
   STATUS      current
   DESCRIPTION
      "Path: ethernet1.editConf.inboundBandwidth.correction.predefined.encapsulation.atm.higherLayer

       Possibilities:
               rfc2684   (0)
               ppp   (1)
               pppOverEthernet   (2)"
   ::= {er1646v2PortSwMCIbwEntry 608993280}

er1646v2PortSwMCIbwCorrPredefEncapsAtmMp OBJECT-TYPE
   SYNTAX      INTEGER
               {
               llcEncapsulation (0),
               vcMultiplexing (1)
               }
   MAX-ACCESS  read-write
   STATUS      current
   DESCRIPTION
      "Path: ethernet1.editConf.inboundBandwidth.correction.predefined.encapsulation.atm.multiProtocol

       Possibilities:
               llcEncapsulation   (0)
               vcMultiplexing   (1)"
   ::= {er1646v2PortSwMCIbwEntry 609026048}

er1646v2PortSwMCIbwCorrPredefEncapsHdlc OBJECT-TYPE
   SYNTAX      DisplayString
   MAX-ACCESS  read-write
   STATUS      current
   DESCRIPTION
      "Path: ethernet1.editConf.inboundBandwidth.correction.predefined.encapsulation.hdlc"
   ::= {er1646v2PortSwMCIbwEntry 609222656}

er1646v2PortSwMCIbwCorrPredefEncapsEfmFs OBJECT-TYPE
   SYNTAX      Integer32
   MAX-ACCESS  read-write
   STATUS      current
   DESCRIPTION
      "Path: ethernet1.editConf.inboundBandwidth.correction.predefined.encapsulation.efm.fragmentSize"
   ::= {er1646v2PortSwMCIbwEntry 609517568}

er1646v2PortSwMCIbwCorrPredefEncapsEfmIb OBJECT-TYPE
   SYNTAX      Integer32
   MAX-ACCESS  read-write
   STATUS      current
   DESCRIPTION
      "Path: ethernet1.editConf.inboundBandwidth.correction.predefined.encapsulation.efm.idleBytes"
   ::= {er1646v2PortSwMCIbwEntry 609550336}

er1646v2PortSwMCIbwCorrPredefMode OBJECT-TYPE
   SYNTAX      INTEGER
               {
               routing (0),
               bridging (1)
               }
   MAX-ACCESS  read-write
   STATUS      current
   DESCRIPTION
      "Path: ethernet1.editConf.inboundBandwidth.correction.predefined.mode

       Possibilities:
               routing   (0)
               bridging   (1)"
   ::= {er1646v2PortSwMCIbwEntry 612368384}

er1646v2PortSwMCIbwCorrManualOverhead OBJECT-TYPE
   SYNTAX      Integer32
   MAX-ACCESS  read-write
   STATUS      current
   DESCRIPTION
      "Path: ethernet1.editConf.inboundBandwidth.correction.manual.overhead"
   ::= {er1646v2PortSwMCIbwEntry 637665280}

er1646v2PortSwMCIbwCorrManualFrameData OBJECT-TYPE
   SYNTAX      Counter32
   MAX-ACCESS  read-write
   STATUS      current
   DESCRIPTION
      "Path: ethernet1.editConf.inboundBandwidth.correction.manual.frameData

       32 bit unsigned wrappable counter."
   ::= {er1646v2PortSwMCIbwEntry 637796352}

er1646v2PortSwMCIbwCorrManualFrameHeader OBJECT-TYPE
   SYNTAX      Counter32
   MAX-ACCESS  read-write
   STATUS      current
   DESCRIPTION
      "Path: ethernet1.editConf.inboundBandwidth.correction.manual.frameHeader

       32 bit unsigned wrappable counter."
   ::= {er1646v2PortSwMCIbwEntry 637927424}

er1646v2PortSwMCIbwMaxFifoQLen OBJECT-TYPE
   SYNTAX      Integer32
   MAX-ACCESS  read-write
   STATUS      current
   DESCRIPTION
      "Path: ethernet1.editConf.inboundBandwidth.maxFifoQLen"
   ::= {er1646v2PortSwMCIbwEntry 805306368}

er1646v2PortSwMCIbwPriorityPolicy OBJECT-TYPE
   SYNTAX      DisplayString
   MAX-ACCESS  read-write
   STATUS      current
   DESCRIPTION
      "Path: ethernet1.editConf.inboundBandwidth.priorityPolicy"
   ::= {er1646v2PortSwMCIbwEntry 1073741824}

er1646v2PortSwMCIbwDeFlagCir OBJECT-TYPE
   SYNTAX      INTEGER
               {
               allowed (1),
               notAllowed (2)
               }
   MAX-ACCESS  read-write
   STATUS      current
   DESCRIPTION
      "Path: ethernet1.editConf.inboundBandwidth.deFlag.cir

       Possibilities:
               allowed   (1)
               notAllowed   (2)"
   ::= {er1646v2PortSwMCIbwEntry 3490709504}

er1646v2PortSwMCIbwDeFlagEir OBJECT-TYPE
   SYNTAX      INTEGER
               {
               allowed (1),
               notAllowed (2)
               }
   MAX-ACCESS  read-write
   STATUS      current
   DESCRIPTION
      "Path: ethernet1.editConf.inboundBandwidth.deFlag.eir

       Possibilities:
               allowed   (1)
               notAllowed   (2)"
   ::= {er1646v2PortSwMCIbwEntry 3491758080}

er1646v2PortSwMCIbwDeFlagViolate OBJECT-TYPE
   SYNTAX      INTEGER
               {
               allowed (1),
               notAllowed (2)
               }
   MAX-ACCESS  read-write
   STATUS      current
   DESCRIPTION
      "Path: ethernet1.editConf.inboundBandwidth.deFlag.violate

       Possibilities:
               allowed   (1)
               notAllowed   (2)"
   ::= {er1646v2PortSwMCIbwEntry 3492806656}

er1646v2PortSwMCIbwActCirActNone OBJECT-TYPE
   SYNTAX      OCTET STRING
   MAX-ACCESS  read-write
   STATUS      current
   DESCRIPTION
      "Path: ethernet1.editConf.inboundBandwidth.action.cirAction.none"
   ::= {er1646v2PortSwMCIbwEntry 4062183424}

er1646v2PortSwMCIbwActCirActEthCos1 OBJECT-TYPE
   SYNTAX      INTEGER
               {
               unchanged (256)
               }
   MAX-ACCESS  read-write
   STATUS      current
   DESCRIPTION
      "Path: ethernet1.editConf.inboundBandwidth.action.cirAction.ethernet.cosDepth1

       Possibilities:
               unchanged   (256)"
   ::= {er1646v2PortSwMCIbwEntry 4064346112}

er1646v2PortSwMCIbwActCirActEthDei1 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth1

       Possibilities:
               unchanged   (255)
               clear   (0)
               set   (1)"
   ::= {er1646v2PortSwMCIbwEntry 4065656832}

er1646v2PortSwMCIbwActCirActEthCos2 OBJECT-TYPE
   SYNTAX      INTEGER
               {
               unchanged (256)
               }
   MAX-ACCESS  read-write
   STATUS      current
   DESCRIPTION
      "Path: ethernet1.editConf.inboundBandwidth.action.cirAction.ethernet.cosDepth2

       Possibilities:
               unchanged   (256)"
   ::= {er1646v2PortSwMCIbwEntry 4064411648}

er1646v2PortSwMCIbwActCirActEthDei2 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth2

       Possibilities:
               unchanged   (255)
               clear   (0)
               set   (1)"
   ::= {er1646v2PortSwMCIbwEntry 4065722368}

er1646v2PortSwMCIbwActCirActEthCos3 OBJECT-TYPE
   SYNTAX      INTEGER
               {
               unchanged (256)
               }
   MAX-ACCESS  read-write
   STATUS      current
   DESCRIPTION
      "Path: ethernet1.editConf.inboundBandwidth.action.cirAction.ethernet.cosDepth3

       Possibilities:
               unchanged   (256)"
   ::= {er1646v2PortSwMCIbwEntry 4064477184}

er1646v2PortSwMCIbwActCirActEthDei3 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth3

       Possibilities:
               unchanged   (255)
               clear   (0)
               set   (1)"
   ::= {er1646v2PortSwMCIbwEntry 4065787904}

er1646v2PortSwMCIbwActCirActEthCos4 OBJECT-TYPE
   SYNTAX      INTEGER
               {
               unchanged (256)
               }
   MAX-ACCESS  read-write
   STATUS      current
   DESCRIPTION
      "Path: ethernet1.editConf.inboundBandwidth.action.cirAction.ethernet.cosDepth4

       Possibilities:
               unchanged   (256)"
   ::= {er1646v2PortSwMCIbwEntry 4064542720}

er1646v2PortSwMCIbwActCirActEthDei4 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth4

       Possibilities:
               unchanged   (255)
               clear   (0)
               set   (1)"
   ::= {er1646v2PortSwMCIbwEntry 4065853440}

er1646v2PortSwMCIbwActCirActEthCos5 OBJECT-TYPE
   SYNTAX      INTEGER
               {
               unchanged (256)
               }
   MAX-ACCESS  read-write
   STATUS      current
   DESCRIPTION
      "Path: ethernet1.editConf.inboundBandwidth.action.cirAction.ethernet.cosDepth5

       Possibilities:
               unchanged   (256)"
   ::= {er1646v2PortSwMCIbwEntry 4064608256}

er1646v2PortSwMCIbwActCirActEthDei5 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth5

       Possibilities:
               unchanged   (255)
               clear   (0)
               set   (1)"
   ::= {er1646v2PortSwMCIbwEntry 4065918976}

er1646v2PortSwMCIbwActCirActEthCos6 OBJECT-TYPE
   SYNTAX      INTEGER
               {
               unchanged (256)
               }
   MAX-ACCESS  read-write
   STATUS      current
   DESCRIPTION
      "Path: ethernet1.editConf.inboundBandwidth.action.cirAction.ethernet.cosDepth6

       Possibilities:
               unchanged   (256)"
   ::= {er1646v2PortSwMCIbwEntry 4064673792}

er1646v2PortSwMCIbwActCirActEthDei6 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth6

       Possibilities:
               unchanged   (255)
               clear   (0)
               set   (1)"
   ::= {er1646v2PortSwMCIbwEntry 4065984512}

er1646v2PortSwMCIbwActCirActEthCos7 OBJECT-TYPE
   SYNTAX      INTEGER
               {
               unchanged (256)
               }
   MAX-ACCESS  read-write
   STATUS      current
   DESCRIPTION
      "Path: ethernet1.editConf.inboundBandwidth.action.cirAction.ethernet.cosDepth7

       Possibilities:
               unchanged   (256)"
   ::= {er1646v2PortSwMCIbwEntry 4064739328}

er1646v2PortSwMCIbwActCirActEthDei7 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth7

       Possibilities:
               unchanged   (255)
               clear   (0)
               set   (1)"
   ::= {er1646v2PortSwMCIbwEntry 4066050048}

er1646v2PortSwMCIbwActCirActEthCos8 OBJECT-TYPE
   SYNTAX      INTEGER
               {
               unchanged (256)
               }
   MAX-ACCESS  read-write
   STATUS      current
   DESCRIPTION
      "Path: ethernet1.editConf.inboundBandwidth.action.cirAction.ethernet.cosDepth8

       Possibilities:
               unchanged   (256)"
   ::= {er1646v2PortSwMCIbwEntry 4064804864}

er1646v2PortSwMCIbwActCirActEthDei8 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth8

       Possibilities:
               unchanged   (255)
               clear   (0)
               set   (1)"
   ::= {er1646v2PortSwMCIbwEntry 4066115584}

er1646v2PortSwMCIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4064870400}

er1646v2PortSwMCIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4064935936}

er1646v2PortSwMCIbwActCirActEthDrpLev OBJECT-TYPE
   SYNTAX      INTEGER
               {
               unchanged (0)
               }
   MAX-ACCESS  read-write
   STATUS      current
   DESCRIPTION
      "Path: ethernet1.editConf.inboundBandwidth.action.cirAction.ethernet.dropLevel

       Possibilities:
               unchanged   (0)"
   ::= {er1646v2PortSwMCIbwEntry 4065001472}

er1646v2PortSwMCIbwActCirActEthDeFlag OBJECT-TYPE
   SYNTAX      INTEGER
               {
               unchanged (255),
               clear (0),
               set (1)
               }
   MAX-ACCESS  read-write
   STATUS      current
   DESCRIPTION
      "Path: ethernet1.editConf.inboundBandwidth.action.cirAction.ethernet.deFlag

       Possibilities:
               unchanged   (255)
               clear   (0)
               set   (1)"
   ::= {er1646v2PortSwMCIbwEntry 4065198080}

er1646v2PortSwMCIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4071161856}

er1646v2PortSwMCIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4071227392}

er1646v2PortSwMCIbwActCirActIpDrpLev OBJECT-TYPE
   SYNTAX      INTEGER
               {
               unchanged (0)
               }
   MAX-ACCESS  read-write
   STATUS      current
   DESCRIPTION
      "Path: ethernet1.editConf.inboundBandwidth.action.cirAction.ip.dropLevel

       Possibilities:
               unchanged   (0)"
   ::= {er1646v2PortSwMCIbwEntry 4071292928}

er1646v2PortSwMCIbwActCirActIpDeFlag OBJECT-TYPE
   SYNTAX      INTEGER
               {
               unchanged (255),
               clear (0),
               set (1)
               }
   MAX-ACCESS  read-write
   STATUS      current
   DESCRIPTION
      "Path: ethernet1.editConf.inboundBandwidth.action.cirAction.ip.deFlag

       Possibilities:
               unchanged   (255)
               clear   (0)
               set   (1)"
   ::= {er1646v2PortSwMCIbwEntry 4071489536}

er1646v2PortSwMCIbwActEirActNone OBJECT-TYPE
   SYNTAX      OCTET STRING
   MAX-ACCESS  read-write
   STATUS      current
   DESCRIPTION
      "Path: ethernet1.editConf.inboundBandwidth.action.eirAction.none"
   ::= {er1646v2PortSwMCIbwEntry 4095737856}

er1646v2PortSwMCIbwActEirActEthCos1 OBJECT-TYPE
   SYNTAX      INTEGER
               {
               unchanged (256)
               }
   MAX-ACCESS  read-write
   STATUS      current
   DESCRIPTION
      "Path: ethernet1.editConf.inboundBandwidth.action.eirAction.ethernet.cosDepth1

       Possibilities:
               unchanged   (256)"
   ::= {er1646v2PortSwMCIbwEntry 4097900544}

er1646v2PortSwMCIbwActEirActEthDei1 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth1

       Possibilities:
               unchanged   (255)
               clear   (0)
               set   (1)"
   ::= {er1646v2PortSwMCIbwEntry 4099211264}

er1646v2PortSwMCIbwActEirActEthCos2 OBJECT-TYPE
   SYNTAX      INTEGER
               {
               unchanged (256)
               }
   MAX-ACCESS  read-write
   STATUS      current
   DESCRIPTION
      "Path: ethernet1.editConf.inboundBandwidth.action.eirAction.ethernet.cosDepth2

       Possibilities:
               unchanged   (256)"
   ::= {er1646v2PortSwMCIbwEntry 4097966080}

er1646v2PortSwMCIbwActEirActEthDei2 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth2

       Possibilities:
               unchanged   (255)
               clear   (0)
               set   (1)"
   ::= {er1646v2PortSwMCIbwEntry 4099276800}

er1646v2PortSwMCIbwActEirActEthCos3 OBJECT-TYPE
   SYNTAX      INTEGER
               {
               unchanged (256)
               }
   MAX-ACCESS  read-write
   STATUS      current
   DESCRIPTION
      "Path: ethernet1.editConf.inboundBandwidth.action.eirAction.ethernet.cosDepth3

       Possibilities:
               unchanged   (256)"
   ::= {er1646v2PortSwMCIbwEntry 4098031616}

er1646v2PortSwMCIbwActEirActEthDei3 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth3

       Possibilities:
               unchanged   (255)
               clear   (0)
               set   (1)"
   ::= {er1646v2PortSwMCIbwEntry 4099342336}

er1646v2PortSwMCIbwActEirActEthCos4 OBJECT-TYPE
   SYNTAX      INTEGER
               {
               unchanged (256)
               }
   MAX-ACCESS  read-write
   STATUS      current
   DESCRIPTION
      "Path: ethernet1.editConf.inboundBandwidth.action.eirAction.ethernet.cosDepth4

       Possibilities:
               unchanged   (256)"
   ::= {er1646v2PortSwMCIbwEntry 4098097152}

er1646v2PortSwMCIbwActEirActEthDei4 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth4

       Possibilities:
               unchanged   (255)
               clear   (0)
               set   (1)"
   ::= {er1646v2PortSwMCIbwEntry 4099407872}

er1646v2PortSwMCIbwActEirActEthCos5 OBJECT-TYPE
   SYNTAX      INTEGER
               {
               unchanged (256)
               }
   MAX-ACCESS  read-write
   STATUS      current
   DESCRIPTION
      "Path: ethernet1.editConf.inboundBandwidth.action.eirAction.ethernet.cosDepth5

       Possibilities:
               unchanged   (256)"
   ::= {er1646v2PortSwMCIbwEntry 4098162688}

er1646v2PortSwMCIbwActEirActEthDei5 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth5

       Possibilities:
               unchanged   (255)
               clear   (0)
               set   (1)"
   ::= {er1646v2PortSwMCIbwEntry 4099473408}

er1646v2PortSwMCIbwActEirActEthCos6 OBJECT-TYPE
   SYNTAX      INTEGER
               {
               unchanged (256)
               }
   MAX-ACCESS  read-write
   STATUS      current
   DESCRIPTION
      "Path: ethernet1.editConf.inboundBandwidth.action.eirAction.ethernet.cosDepth6

       Possibilities:
               unchanged   (256)"
   ::= {er1646v2PortSwMCIbwEntry 4098228224}

er1646v2PortSwMCIbwActEirActEthDei6 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth6

       Possibilities:
               unchanged   (255)
               clear   (0)
               set   (1)"
   ::= {er1646v2PortSwMCIbwEntry 4099538944}

er1646v2PortSwMCIbwActEirActEthCos7 OBJECT-TYPE
   SYNTAX      INTEGER
               {
               unchanged (256)
               }
   MAX-ACCESS  read-write
   STATUS      current
   DESCRIPTION
      "Path: ethernet1.editConf.inboundBandwidth.action.eirAction.ethernet.cosDepth7

       Possibilities:
               unchanged   (256)"
   ::= {er1646v2PortSwMCIbwEntry 4098293760}

er1646v2PortSwMCIbwActEirActEthDei7 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth7

       Possibilities:
               unchanged   (255)
               clear   (0)
               set   (1)"
   ::= {er1646v2PortSwMCIbwEntry 4099604480}

er1646v2PortSwMCIbwActEirActEthCos8 OBJECT-TYPE
   SYNTAX      INTEGER
               {
               unchanged (256)
               }
   MAX-ACCESS  read-write
   STATUS      current
   DESCRIPTION
      "Path: ethernet1.editConf.inboundBandwidth.action.eirAction.ethernet.cosDepth8

       Possibilities:
               unchanged   (256)"
   ::= {er1646v2PortSwMCIbwEntry 4098359296}

er1646v2PortSwMCIbwActEirActEthDei8 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth8

       Possibilities:
               unchanged   (255)
               clear   (0)
               set   (1)"
   ::= {er1646v2PortSwMCIbwEntry 4099670016}

er1646v2PortSwMCIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4098424832}

er1646v2PortSwMCIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4098490368}

er1646v2PortSwMCIbwActEirActEthDrpLev OBJECT-TYPE
   SYNTAX      INTEGER
               {
               unchanged (0)
               }
   MAX-ACCESS  read-write
   STATUS      current
   DESCRIPTION
      "Path: ethernet1.editConf.inboundBandwidth.action.eirAction.ethernet.dropLevel

       Possibilities:
               unchanged   (0)"
   ::= {er1646v2PortSwMCIbwEntry 4098555904}

er1646v2PortSwMCIbwActEirActEthDeFlag OBJECT-TYPE
   SYNTAX      INTEGER
               {
               unchanged (255),
               clear (0),
               set (1)
               }
   MAX-ACCESS  read-write
   STATUS      current
   DESCRIPTION
      "Path: ethernet1.editConf.inboundBandwidth.action.eirAction.ethernet.deFlag

       Possibilities:
               unchanged   (255)
               clear   (0)
               set   (1)"
   ::= {er1646v2PortSwMCIbwEntry 4098752512}

er1646v2PortSwMCIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4104716288}

er1646v2PortSwMCIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4104781824}

er1646v2PortSwMCIbwActEirActIpDrpLev OBJECT-TYPE
   SYNTAX      INTEGER
               {
               unchanged (0)
               }
   MAX-ACCESS  read-write
   STATUS      current
   DESCRIPTION
      "Path: ethernet1.editConf.inboundBandwidth.action.eirAction.ip.dropLevel

       Possibilities:
               unchanged   (0)"
   ::= {er1646v2PortSwMCIbwEntry 4104847360}

er1646v2PortSwMCIbwActEirActIpDeFlag OBJECT-TYPE
   SYNTAX      INTEGER
               {
               unchanged (255),
               clear (0),
               set (1)
               }
   MAX-ACCESS  read-write
   STATUS      current
   DESCRIPTION
      "Path: ethernet1.editConf.inboundBandwidth.action.eirAction.ip.deFlag

       Possibilities:
               unchanged   (255)
               clear   (0)
               set   (1)"
   ::= {er1646v2PortSwMCIbwEntry 4105043968}

er1646v2PortSwMCIbwActViolActNone OBJECT-TYPE
   SYNTAX      OCTET STRING
   MAX-ACCESS  read-write
   STATUS      current
   DESCRIPTION
      "Path: ethernet1.editConf.inboundBandwidth.action.violateAction.none"
   ::= {er1646v2PortSwMCIbwEntry 4129292288}

er1646v2PortSwMCIbwActViolActDrop OBJECT-TYPE
   SYNTAX      OCTET STRING
   MAX-ACCESS  read-write
   STATUS      current
   DESCRIPTION
      "Path: ethernet1.editConf.inboundBandwidth.action.violateAction.drop"
   ::= {er1646v2PortSwMCIbwEntry 4133486592}

er1646v2PortSwMCIbwActViolActEthCos1 OBJECT-TYPE
   SYNTAX      INTEGER
               {
               unchanged (256)
               }
   MAX-ACCESS  read-write
   STATUS      current
   DESCRIPTION
      "Path: ethernet1.editConf.inboundBandwidth.action.violateAction.ethernet.cosDepth1

       Possibilities:
               unchanged   (256)"
   ::= {er1646v2PortSwMCIbwEntry 4131454976}

er1646v2PortSwMCIbwActViolActEthDei1 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth1

       Possibilities:
               unchanged   (255)
               clear   (0)
               set   (1)"
   ::= {er1646v2PortSwMCIbwEntry 4132765696}

er1646v2PortSwMCIbwActViolActEthCos2 OBJECT-TYPE
   SYNTAX      INTEGER
               {
               unchanged (256)
               }
   MAX-ACCESS  read-write
   STATUS      current
   DESCRIPTION
      "Path: ethernet1.editConf.inboundBandwidth.action.violateAction.ethernet.cosDepth2

       Possibilities:
               unchanged   (256)"
   ::= {er1646v2PortSwMCIbwEntry 4131520512}

er1646v2PortSwMCIbwActViolActEthDei2 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth2

       Possibilities:
               unchanged   (255)
               clear   (0)
               set   (1)"
   ::= {er1646v2PortSwMCIbwEntry 4132831232}

er1646v2PortSwMCIbwActViolActEthCos3 OBJECT-TYPE
   SYNTAX      INTEGER
               {
               unchanged (256)
               }
   MAX-ACCESS  read-write
   STATUS      current
   DESCRIPTION
      "Path: ethernet1.editConf.inboundBandwidth.action.violateAction.ethernet.cosDepth3

       Possibilities:
               unchanged   (256)"
   ::= {er1646v2PortSwMCIbwEntry 4131586048}

er1646v2PortSwMCIbwActViolActEthDei3 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth3

       Possibilities:
               unchanged   (255)
               clear   (0)
               set   (1)"
   ::= {er1646v2PortSwMCIbwEntry 4132896768}

er1646v2PortSwMCIbwActViolActEthCos4 OBJECT-TYPE
   SYNTAX      INTEGER
               {
               unchanged (256)
               }
   MAX-ACCESS  read-write
   STATUS      current
   DESCRIPTION
      "Path: ethernet1.editConf.inboundBandwidth.action.violateAction.ethernet.cosDepth4

       Possibilities:
               unchanged   (256)"
   ::= {er1646v2PortSwMCIbwEntry 4131651584}

er1646v2PortSwMCIbwActViolActEthDei4 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth4

       Possibilities:
               unchanged   (255)
               clear   (0)
               set   (1)"
   ::= {er1646v2PortSwMCIbwEntry 4132962304}

er1646v2PortSwMCIbwActViolActEthCos5 OBJECT-TYPE
   SYNTAX      INTEGER
               {
               unchanged (256)
               }
   MAX-ACCESS  read-write
   STATUS      current
   DESCRIPTION
      "Path: ethernet1.editConf.inboundBandwidth.action.violateAction.ethernet.cosDepth5

       Possibilities:
               unchanged   (256)"
   ::= {er1646v2PortSwMCIbwEntry 4131717120}

er1646v2PortSwMCIbwActViolActEthDei5 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth5

       Possibilities:
               unchanged   (255)
               clear   (0)
               set   (1)"
   ::= {er1646v2PortSwMCIbwEntry 4133027840}

er1646v2PortSwMCIbwActViolActEthCos6 OBJECT-TYPE
   SYNTAX      INTEGER
               {
               unchanged (256)
               }
   MAX-ACCESS  read-write
   STATUS      current
   DESCRIPTION
      "Path: ethernet1.editConf.inboundBandwidth.action.violateAction.ethernet.cosDepth6

       Possibilities:
               unchanged   (256)"
   ::= {er1646v2PortSwMCIbwEntry 4131782656}

er1646v2PortSwMCIbwActViolActEthDei6 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth6

       Possibilities:
               unchanged   (255)
               clear   (0)
               set   (1)"
   ::= {er1646v2PortSwMCIbwEntry 4133093376}

er1646v2PortSwMCIbwActViolActEthCos7 OBJECT-TYPE
   SYNTAX      INTEGER
               {
               unchanged (256)
               }
   MAX-ACCESS  read-write
   STATUS      current
   DESCRIPTION
      "Path: ethernet1.editConf.inboundBandwidth.action.violateAction.ethernet.cosDepth7

       Possibilities:
               unchanged   (256)"
   ::= {er1646v2PortSwMCIbwEntry 4131848192}

er1646v2PortSwMCIbwActViolActEthDei7 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth7

       Possibilities:
               unchanged   (255)
               clear   (0)
               set   (1)"
   ::= {er1646v2PortSwMCIbwEntry 4133158912}

er1646v2PortSwMCIbwActViolActEthCos8 OBJECT-TYPE
   SYNTAX      INTEGER
               {
               unchanged (256)
               }
   MAX-ACCESS  read-write
   STATUS      current
   DESCRIPTION
      "Path: ethernet1.editConf.inboundBandwidth.action.violateAction.ethernet.cosDepth8

       Possibilities:
               unchanged   (256)"
   ::= {er1646v2PortSwMCIbwEntry 4131913728}

er1646v2PortSwMCIbwActViolActEthDei8 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth8

       Possibilities:
               unchanged   (255)
               clear   (0)
               set   (1)"
   ::= {er1646v2PortSwMCIbwEntry 4133224448}

er1646v2PortSwMCIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4131979264}

er1646v2PortSwMCIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4132044800}

er1646v2PortSwMCIbwActViolActEthDrpLev OBJECT-TYPE
   SYNTAX      INTEGER
               {
               unchanged (0)
               }
   MAX-ACCESS  read-write
   STATUS      current
   DESCRIPTION
      "Path: ethernet1.editConf.inboundBandwidth.action.violateAction.ethernet.dropLevel

       Possibilities:
               unchanged   (0)"
   ::= {er1646v2PortSwMCIbwEntry 4132110336}

er1646v2PortSwMCIbwActViolActEthDeFlag OBJECT-TYPE
   SYNTAX      INTEGER
               {
               unchanged (255),
               clear (0),
               set (1)
               }
   MAX-ACCESS  read-write
   STATUS      current
   DESCRIPTION
      "Path: ethernet1.editConf.inboundBandwidth.action.violateAction.ethernet.deFlag

       Possibilities:
               unchanged   (255)
               clear   (0)
               set   (1)"
   ::= {er1646v2PortSwMCIbwEntry 4132306944}

er1646v2PortSwMCIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2PortSwMCIbwEntry 4138270720}

er1646v2PortSwMCIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2PortSwMCIbwEntry 4138336256}

er1646v2PortSwMCIbwActViolActIpDrpLev OBJECT-TYPE
   SYNTAX      INTEGER
               {
               unchanged (0)
               }
   MAX-ACCESS  read-write
   STATUS      current
   DESCRIPTION
      "Path: ethernet1.editConf.inboundBandwidth.action.violateAction.ip.dropLevel

       Possibilities:
               unchanged   (0)"
   ::= {er1646v2PortSwMCIbwEntry 4138401792}

er1646v2PortSwMCIbwActViolActIpDeFlag OBJECT-TYPE
   SYNTAX      INTEGER
               {
               unchanged (255),
               clear (0),
               set (1)
               }
   MAX-ACCESS  read-write
   STATUS      current
   DESCRIPTION
      "Path: ethernet1.editConf.inboundBandwidth.action.violateAction.ip.deFlag

       Possibilities:
               unchanged   (255)
               clear   (0)
               set   (1)"
   ::= {er1646v2PortSwMCIbwEntry 4138598400}

er1646v2PortSwMCIbwSubInterfacesExcluded OBJECT-TYPE
   SYNTAX      INTEGER
               {
               s (1)
               }
   MAX-ACCESS  read-write
   STATUS      current
   DESCRIPTION
      "Path: ethernet1.editConf.inboundBandwidth.subInterfaces.excluded

       Possibilities:
                  (1)"
   ::= {er1646v2PortSwMCIbwEntry 2416967680}

er1646v2PortSwMCIbwSubInterfacesIncludedInAccessList OBJECT-TYPE
   SYNTAX      DisplayString
   MAX-ACCESS  read-write
   STATUS      current
   DESCRIPTION
      "Path: ethernet1.editConf.inboundBandwidth.subInterfaces.included.inAccessList"
   ::= {er1646v2PortSwMCIbwEntry 2418020352}


er1646v2PortSwMCInboundNUcastPriority OBJECT IDENTIFIER ::= {er1646v2PortSwMC 230}

er1646v2PortSwMCInboundNUcastPrioritySSC OBJECT IDENTIFIER ::= {er1646v2PortSwMCInboundNUcastPriority 1}

er1646v2PortSwMCInboundNUcastPriorityEntry OBJECT IDENTIFIER ::= {er1646v2PortSwMCInboundNUcastPrioritySSC 1}

er1646v2PortSwMCInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundNUcastPriority.broadcast

       Possibilities:
               queue1   (0)
               queue2   (1)
               queue3   (2)
               queue4   (3)
               queue5   (4)
               lowDelayQueue   (5)
               lowDelay2Queue   (6)
               systemQueue   (7)"
   ::= {er1646v2PortSwMCInboundNUcastPriorityEntry 16777216}

er1646v2PortSwMCInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundNUcastPriority.multicast

       Possibilities:
               queue1   (0)
               queue2   (1)
               queue3   (2)
               queue4   (3)
               queue5   (4)
               lowDelayQueue   (5)
               lowDelay2Queue   (6)
               systemQueue   (7)"
   ::= {er1646v2PortSwMCInboundNUcastPriorityEntry 33554432}


er1646v2PortSwMCInboundHwPriority OBJECT IDENTIFIER ::= {er1646v2PortSwMC 231}

er1646v2PortSwMCInboundHwPrioritySSC OBJECT IDENTIFIER ::= {er1646v2PortSwMCInboundHwPriority 1}

er1646v2PortSwMCInboundHwPriorityEntry OBJECT IDENTIFIER ::= {er1646v2PortSwMCInboundHwPrioritySSC 1}

er1646v2PortSwMCInboundHwPriorityNone OBJECT-TYPE
   SYNTAX      OCTET STRING
   MAX-ACCESS  read-write
   STATUS      current
   DESCRIPTION
      "Path: ethernet1.editConf.inboundHwPriority.none"
   ::= {er1646v2PortSwMCInboundHwPriorityEntry 16777216}

er1646v2PortSwMCInboundHwPriorityMapCosToQueueP0 OBJECT-TYPE
   SYNTAX      INTEGER
               {
               queue1 (1),
               queue2 (2)
               }
   MAX-ACCESS  read-write
   STATUS      current
   DESCRIPTION
      "Path: ethernet1.editConf.inboundHwPriority.mapCosToQueue.p0

       Possibilities:
               queue1   (1)
               queue2   (2)"
   ::= {er1646v2PortSwMCInboundHwPriorityEntry 33619968}

er1646v2PortSwMCInboundHwPriorityMapCosToQueueP1 OBJECT-TYPE
   SYNTAX      INTEGER
               {
               queue1 (1),
               queue2 (2)
               }
   MAX-ACCESS  read-write
   STATUS      current
   DESCRIPTION
      "Path: ethernet1.editConf.inboundHwPriority.mapCosToQueue.p1

       Possibilities:
               queue1   (1)
               queue2   (2)"
   ::= {er1646v2PortSwMCInboundHwPriorityEntry 33685504}

er1646v2PortSwMCInboundHwPriorityMapCosToQueueP2 OBJECT-TYPE
   SYNTAX      INTEGER
               {
               queue1 (1),
               queue2 (2)
               }
   MAX-ACCESS  read-write
   STATUS      current
   DESCRIPTION
      "Path: ethernet1.editConf.inboundHwPriority.mapCosToQueue.p2

       Possibilities:
               queue1   (1)
               queue2   (2)"
   ::= {er1646v2PortSwMCInboundHwPriorityEntry 33751040}

er1646v2PortSwMCInboundHwPriorityMapCosToQueueP3 OBJECT-TYPE
   SYNTAX      INTEGER
               {
               queue1 (1),
               queue2 (2)
               }
   MAX-ACCESS  read-write
   STATUS      current
   DESCRIPTION
      "Path: ethernet1.editConf.inboundHwPriority.mapCosToQueue.p3

       Possibilities:
               queue1   (1)
               queue2   (2)"
   ::= {er1646v2PortSwMCInboundHwPriorityEntry 33816576}

er1646v2PortSwMCInboundHwPriorityMapCosToQueueP4 OBJECT-TYPE
   SYNTAX      INTEGER
               {
               queue1 (1),
               queue2 (2)
               }
   MAX-ACCESS  read-write
   STATUS      current
   DESCRIPTION
      "Path: ethernet1.editConf.inboundHwPriority.mapCosToQueue.p4

       Possibilities:
               queue1   (1)
               queue2   (2)"
   ::= {er1646v2PortSwMCInboundHwPriorityEntry 33882112}

er1646v2PortSwMCInboundHwPriorityMapCosToQueueP5 OBJECT-TYPE
   SYNTAX      INTEGER
               {
               queue1 (1),
               queue2 (2)
               }
   MAX-ACCESS  read-write
   STATUS      current
   DESCRIPTION
      "Path: ethernet1.editConf.inboundHwPriority.mapCosToQueue.p5

       Possibilities:
               queue1   (1)
               queue2   (2)"
   ::= {er1646v2PortSwMCInboundHwPriorityEntry 33947648}

er1646v2PortSwMCInboundHwPriorityMapCosToQueueP6 OBJECT-TYPE
   SYNTAX      INTEGER
               {
               queue1 (1),
               queue2 (2)
               }
   MAX-ACCESS  read-write
   STATUS      current
   DESCRIPTION
      "Path: ethernet1.editConf.inboundHwPriority.mapCosToQueue.p6

       Possibilities:
               queue1   (1)
               queue2   (2)"
   ::= {er1646v2PortSwMCInboundHwPriorityEntry 34013184}

er1646v2PortSwMCInboundHwPriorityMapCosToQueueP7 OBJECT-TYPE
   SYNTAX      INTEGER
               {
               queue1 (1),
               queue2 (2)
               }
   MAX-ACCESS  read-write
   STATUS      current
   DESCRIPTION
      "Path: ethernet1.editConf.inboundHwPriority.mapCosToQueue.p7

       Possibilities:
               queue1   (1)
               queue2   (2)"
   ::= {er1646v2PortSwMCInboundHwPriorityEntry 34078720}

er1646v2PortSwMCInboundHwPriorityMapDscpToQueue OBJECT-TYPE
   SYNTAX      SEQUENCE OF Er1646v2PortSwMCInboundHwPriorityMapDscpToQueueEntry
   MAX-ACCESS  not-accessible
   STATUS      current
   DESCRIPTION
      ""
   ::= {er1646v2PortSwMCInboundHwPriority 50331648}

er1646v2PortSwMCInboundHwPriorityMapDscpToQueueEntry OBJECT-TYPE
   SYNTAX      Er1646v2PortSwMCInboundHwPriorityMapDscpToQueueEntry
   MAX-ACCESS  not-accessible
   STATUS      current
   DESCRIPTION
      ""
   INDEX      { er1646v2PortSwMCInboundHwPriorityMapDscpToQueueTableIx }
   ::= {er1646v2PortSwMCInboundHwPriorityMapDscpToQueue 1}

Er1646v2PortSwMCInboundHwPriorityMapDscpToQueueEntry ::=
   SEQUENCE
      {
      er1646v2PortSwMCInboundHwPriorityMapDscpToQueueActions
         VariableLengthTableActions,
      er1646v2PortSwMCInboundHwPriorityMapDscpToQueueTableIx
         TableIndex,
      er1646v2PortSwMCInboundHwPriorityMapDscpToQueueStartDscp
         INTEGER,
      er1646v2PortSwMCInboundHwPriorityMapDscpToQueueEndDscp
         INTEGER,
      er1646v2PortSwMCInboundHwPriorityMapDscpToQueueQueue
         INTEGER
      }

er1646v2PortSwMCInboundHwPriorityMapDscpToQueueActions OBJECT-TYPE
   SYNTAX      VariableLengthTableActions
   MAX-ACCESS  read-write
   STATUS      current
   DESCRIPTION
      "By way of this field, some manipulations
       on this table may be performed."
   ::= {er1646v2PortSwMCInboundHwPriorityMapDscpToQueueEntry 2}

er1646v2PortSwMCInboundHwPriorityMapDscpToQueueTableIx OBJECT-TYPE
   SYNTAX      TableIndex
   MAX-ACCESS  not-accessible
   STATUS      current
   DESCRIPTION
      ""
   ::= {er1646v2PortSwMCInboundHwPriorityMapDscpToQueueEntry 11}

er1646v2PortSwMCInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet1.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1646v2PortSwMCInboundHwPriorityMapDscpToQueueEntry 16777216}

er1646v2PortSwMCInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet1.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1646v2PortSwMCInboundHwPriorityMapDscpToQueueEntry 33554432}

er1646v2PortSwMCInboundHwPriorityMapDscpToQueueQueue OBJECT-TYPE
   SYNTAX      INTEGER
               {
               queue1 (1),
               queue2 (2)
               }
   MAX-ACCESS  read-write
   STATUS      current
   DESCRIPTION
      "Path: ethernet1.editConf.inboundHwPriority.mapDscpToQueue.queue

       Possibilities:
               queue1   (1)
               queue2   (2)"
   ::= {er1646v2PortSwMCInboundHwPriorityMapDscpToQueueEntry 50331648}


er1646v2PortSwMCName OBJECT-TYPE
   SYNTAX      DisplayString
   MAX-ACCESS  read-write
   STATUS      current
   DESCRIPTION
      "Path: ethernet1.editConf.name
       Info: config interface name"
   ::= {er1646v2PortSwMC 2}


er1646v2PortSwMCInterfaceSide OBJECT-TYPE
   SYNTAX      INTEGER
               {
               user (1),
               network (2)
               }
   MAX-ACCESS  read-write
   STATUS      current
   DESCRIPTION
      "Path: ethernet1.editConf.interfaceSide

       Possibilities:
               user   (1)
               network   (2)"
   ::= {er1646v2PortSwMC 232}



sr1646v2PortSwMC OBJECT IDENTIFIER ::= {r1646v2PortSwMC 14}


sr1646v2PortSwMCDescr OBJECT-TYPE
   SYNTAX      DisplayString
   MAX-ACCESS  read-only
   STATUS      current
   DESCRIPTION
      "Path: ethernet1.status.ifDescr
       Info: ifDescr"
   ::= {sr1646v2PortSwMC 101}


sr1646v2PortSwMCType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet1.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2PortSwMC 102}


sr1646v2PortSwMCMtu OBJECT-TYPE
   SYNTAX      Integer32
   MAX-ACCESS  read-only
   STATUS      current
   DESCRIPTION
      "Path: ethernet1.status.ifMtu
       Info: ifMtu"
   ::= {sr1646v2PortSwMC 103}


sr1646v2PortSwMCOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet1.status.ifOperStatus
       Info: ifOperStatus

       Possibilities:
               up   (1)
               down   (2)
               testing   (3)
               unknown   (4)
               dormant   (5)
               notPresent   (6)
               lowerLayerDown   (7)"
   ::= {sr1646v2PortSwMC 107}


sr1646v2PortSwMCLastChange OBJECT-TYPE
   SYNTAX      TimeTicks
   MAX-ACCESS  read-only
   STATUS      current
   DESCRIPTION
      "Path: ethernet1.status.ifLastChange
       Info: ifLastChange

       Time in centi-second."
   ::= {sr1646v2PortSwMC 108}


sr1646v2PortSwMCLastChangeD OBJECT-TYPE
   SYNTAX      DisplayString
   MAX-ACCESS  read-only
   STATUS      current
   DESCRIPTION
      "Path: ethernet1.status.ifLastChangeDate
       Info: ifLastChangeDate"
   ::= {sr1646v2PortSwMC 183}


sr1646v2PortSwMCSpeed OBJECT-TYPE
   SYNTAX      Gauge32
   MAX-ACCESS  read-only
   STATUS      current
   DESCRIPTION
      "Path: ethernet1.status.ifSpeed
       Info: ifSpeed

       32 bit unsigned gauge value."
   ::= {sr1646v2PortSwMC 104}


sr1646v2PortSwMCSnmpIndex OBJECT-TYPE
   SYNTAX      Integer32
   MAX-ACCESS  read-only
   STATUS      current
   DESCRIPTION
      "Path: ethernet1.status.snmpIndex
       Info: SNMP index assigned to this object"
   ::= {sr1646v2PortSwMC 269}


sr1646v2PortSwMCPorts OBJECT IDENTIFIER ::= {sr1646v2PortSwMC 146}

sr1646v2PortSwMCPortsSSCTable OBJECT-TYPE
   SYNTAX      SEQUENCE OF Sr1646v2PortSwMCPortsEntry
   MAX-ACCESS  not-accessible
   STATUS      current
   DESCRIPTION
      "Ethernet Switch 4 Gigabit Ports Status without vlan"
   ::= {sr1646v2PortSwMCPorts 1}

sr1646v2PortSwMCPortsEntry OBJECT-TYPE
   SYNTAX      Sr1646v2PortSwMCPortsEntry
   MAX-ACCESS  not-accessible
   STATUS      current
   DESCRIPTION
      ""
   INDEX      { sr1646v2PortSwMCPortsTableIx }
   ::= {sr1646v2PortSwMCPortsSSCTable 1}

Sr1646v2PortSwMCPortsEntry ::=
   SEQUENCE
      {
      sr1646v2PortSwMCPortsTableIx
         TableIndex,
      sr1646v2PortSwMCPortsPortName
         INTEGER,
      sr1646v2PortSwMCPortsOperStatus
         INTEGER,
      sr1646v2PortSwMCPortsSpeed
         INTEGER,
      sr1646v2PortSwMCPortsDuplex
         INTEGER,
      sr1646v2PortSwMCPortsAutoNeg
         INTEGER,
      sr1646v2PortSwMCPortsPartnerCapsFlowCtrl
         INTEGER,
      sr1646v2PortSwMCPortsPartnerCapsHD10
         INTEGER,
      sr1646v2PortSwMCPortsPartnerCapsFD10
         INTEGER,
      sr1646v2PortSwMCPortsPartnerCapsHD100
         INTEGER,
      sr1646v2PortSwMCPortsPartnerCapsFD100
         INTEGER,
      sr1646v2PortSwMCPortsPartnerCapsFD1000
         INTEGER,
      sr1646v2PortSwMCPortsCir
         Integer32,
      sr1646v2PortSwMCPortsSwPort
         INTEGER
      }

sr1646v2PortSwMCPortsTableIx OBJECT-TYPE
   SYNTAX      TableIndex
   MAX-ACCESS  not-accessible
   STATUS      current
   DESCRIPTION
      ""
   ::= {sr1646v2PortSwMCPortsEntry 11}

sr1646v2PortSwMCPortsPortName OBJECT-TYPE
   SYNTAX      INTEGER
               {
               hwPortu1 (1),
               hwPortu2 (2),
               hwPortu3 (3),
               hwPortu4 (4),
               hwPortu5 (5),
               hwPortu6 (6),
               hwPortuLocalPort (255)
               }
   MAX-ACCESS  read-only
   STATUS      current
   DESCRIPTION
      "Path: ethernet1.status.ports.portName

       Possibilities:
               hwPort_1   (1)
               hwPort_2   (2)
               hwPort_3   (3)
               hwPort_4   (4)
               hwPort_5   (5)
               hwPort_6   (6)
               hwPort_LocalPort   (255)"
   ::= {sr1646v2PortSwMCPortsEntry 16777216}

sr1646v2PortSwMCPortsOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet1.status.ports.ifOperStatus

       Possibilities:
               up   (1)
               down   (2)
               testing   (3)
               unknown   (4)
               dormant   (5)
               notPresent   (6)
               lowerLayerDown   (7)"
   ::= {sr1646v2PortSwMCPortsEntry 33554432}

sr1646v2PortSwMCPortsSpeed OBJECT-TYPE
   SYNTAX      INTEGER
               {
               s10 (0),
               s100 (1),
               s1000 (2),
               s200 (3)
               }
   MAX-ACCESS  read-only
   STATUS      current
   DESCRIPTION
      "Path: ethernet1.status.ports.speed

       Possibilities:
               10   (0)
               100   (1)
               1000   (2)
               200   (3)"
   ::= {sr1646v2PortSwMCPortsEntry 50331648}

sr1646v2PortSwMCPortsDuplex OBJECT-TYPE
   SYNTAX      INTEGER
               {
               halfDuplex (0),
               fullDuplex (1)
               }
   MAX-ACCESS  read-only
   STATUS      current
   DESCRIPTION
      "Path: ethernet1.status.ports.duplex

       Possibilities:
               halfDuplex   (0)
               fullDuplex   (1)"
   ::= {sr1646v2PortSwMCPortsEntry 67108864}

sr1646v2PortSwMCPortsAutoNeg OBJECT-TYPE
   SYNTAX      INTEGER
               {
               disabled (0),
               done (1),
               notDone (2)
               }
   MAX-ACCESS  read-only
   STATUS      current
   DESCRIPTION
      "Path: ethernet1.status.ports.autoNegotiate

       Possibilities:
               disabled   (0)
               done   (1)
               notDone   (2)"
   ::= {sr1646v2PortSwMCPortsEntry 83886080}

sr1646v2PortSwMCPortsPartnerCapsFlowCtrl OBJECT-TYPE
   SYNTAX      INTEGER
               {
               notCapable (0),
               capable (1),
               unknown (2)
               }
   MAX-ACCESS  read-only
   STATUS      current
   DESCRIPTION
      "Path: ethernet1.status.ports.linkPartnerCaps.flowControl

       Possibilities:
               notCapable   (0)
               capable   (1)
               unknown   (2)"
   ::= {sr1646v2PortSwMCPortsEntry 100728832}

sr1646v2PortSwMCPortsPartnerCapsHD10 OBJECT-TYPE
   SYNTAX      INTEGER
               {
               notCapable (0),
               capable (1),
               unknown (2)
               }
   MAX-ACCESS  read-only
   STATUS      current
   DESCRIPTION
      "Path: ethernet1.status.ports.linkPartnerCaps.10Mb/halfDuplex

       Possibilities:
               notCapable   (0)
               capable   (1)
               unknown   (2)"
   ::= {sr1646v2PortSwMCPortsEntry 100794368}

sr1646v2PortSwMCPortsPartnerCapsFD10 OBJECT-TYPE
   SYNTAX      INTEGER
               {
               notCapable (0),
               capable (1),
               unknown (2)
               }
   MAX-ACCESS  read-only
   STATUS      current
   DESCRIPTION
      "Path: ethernet1.status.ports.linkPartnerCaps.10Mb/fullDuplex

       Possibilities:
               notCapable   (0)
               capable   (1)
               unknown   (2)"
   ::= {sr1646v2PortSwMCPortsEntry 100859904}

sr1646v2PortSwMCPortsPartnerCapsHD100 OBJECT-TYPE
   SYNTAX      INTEGER
               {
               notCapable (0),
               capable (1),
               unknown (2)
               }
   MAX-ACCESS  read-only
   STATUS      current
   DESCRIPTION
      "Path: ethernet1.status.ports.linkPartnerCaps.100Mb/halfDuplex

       Possibilities:
               notCapable   (0)
               capable   (1)
               unknown   (2)"
   ::= {sr1646v2PortSwMCPortsEntry 100925440}

sr1646v2PortSwMCPortsPartnerCapsFD100 OBJECT-TYPE
   SYNTAX      INTEGER
               {
               notCapable (0),
               capable (1),
               unknown (2)
               }
   MAX-ACCESS  read-only
   STATUS      current
   DESCRIPTION
      "Path: ethernet1.status.ports.linkPartnerCaps.100Mb/fullDuplex

       Possibilities:
               notCapable   (0)
               capable   (1)
               unknown   (2)"
   ::= {sr1646v2PortSwMCPortsEntry 100990976}

sr1646v2PortSwMCPortsPartnerCapsFD1000 OBJECT-TYPE
   SYNTAX      INTEGER
               {
               notCapable (0),
               capable (1),
               unknown (2)
               }
   MAX-ACCESS  read-only
   STATUS      current
   DESCRIPTION
      "Path: ethernet1.status.ports.linkPartnerCaps.1000Mb/fullDuplex

       Possibilities:
               notCapable   (0)
               capable   (1)
               unknown   (2)"
   ::= {sr1646v2PortSwMCPortsEntry 101056512}

sr1646v2PortSwMCPortsCir OBJECT-TYPE
   SYNTAX      Integer32
   MAX-ACCESS  read-only
   STATUS      current
   DESCRIPTION
      "Path: ethernet1.status.ports.cir"
   ::= {sr1646v2PortSwMCPortsEntry 134217728}

sr1646v2PortSwMCPortsSwPort OBJECT-TYPE
   SYNTAX      INTEGER
               {
               swPort1 (1),
               swPort2 (2),
               swPort3 (3),
               swPort4 (4),
               swPort5 (5),
               swPort6 (6),
               swPort7 (7),
               swPort8 (8),
               none (255),
               all (65535)
               }
   MAX-ACCESS  read-only
   STATUS      current
   DESCRIPTION
      "Path: ethernet1.status.ports.swPort

       Possibilities:
               swPort[1]   (1)
               swPort[2]   (2)
               swPort[3]   (3)
               swPort[4]   (4)
               swPort[5]   (5)
               swPort[6]   (6)
               swPort[7]   (7)
               swPort[8]   (8)
               none   (255)
               all   (65535)"
   ::= {sr1646v2PortSwMCPortsEntry 150994944}


sr1646v2PortSwMCSwitchCache OBJECT IDENTIFIER ::= {sr1646v2PortSwMC 10}

sr1646v2PortSwMCSwitchCacheSSCTable OBJECT-TYPE
   SYNTAX      SEQUENCE OF Sr1646v2PortSwMCSwitchCacheEntry
   MAX-ACCESS  not-accessible
   STATUS      current
   DESCRIPTION
      "switch MAC cache"
   ::= {sr1646v2PortSwMCSwitchCache 1}

sr1646v2PortSwMCSwitchCacheEntry OBJECT-TYPE
   SYNTAX      Sr1646v2PortSwMCSwitchCacheEntry
   MAX-ACCESS  not-accessible
   STATUS      current
   DESCRIPTION
      ""
   INDEX      { sr1646v2PortSwMCSwitchCacheTableIx }
   ::= {sr1646v2PortSwMCSwitchCacheSSCTable 1}

Sr1646v2PortSwMCSwitchCacheEntry ::=
   SEQUENCE
      {
      sr1646v2PortSwMCSwitchCacheTableIx
         TableIndex,
      sr1646v2PortSwMCSwitchCacheMacAddress
         OCTET STRING,
      sr1646v2PortSwMCSwitchCachePort
         INTEGER,
      sr1646v2PortSwMCSwitchCacheType
         INTEGER,
      sr1646v2PortSwMCSwitchCacheTimeout
         TimeTicks,
      sr1646v2PortSwMCSwitchCacheDbNum
         Integer32
      }

sr1646v2PortSwMCSwitchCacheTableIx OBJECT-TYPE
   SYNTAX      TableIndex
   MAX-ACCESS  not-accessible
   STATUS      current
   DESCRIPTION
      ""
   ::= {sr1646v2PortSwMCSwitchCacheEntry 11}

sr1646v2PortSwMCSwitchCacheMacAddress OBJECT-TYPE
   SYNTAX      OCTET STRING
   MAX-ACCESS  read-only
   STATUS      current
   DESCRIPTION
      "Path: ethernet1.status.switchCache.macAddress

       MAC address."
   ::= {sr1646v2PortSwMCSwitchCacheEntry 16777216}

sr1646v2PortSwMCSwitchCachePort OBJECT-TYPE
   SYNTAX      INTEGER
               {
               none (0),
               hwPortu1 (1),
               hwPortu2 (2),
               hwPortu3 (3),
               hwPortu4 (4),
               hwPortu5 (5),
               hwPortuLocalPort (6),
               hwPortuLocalPort2 (7)
               }
   MAX-ACCESS  read-only
   STATUS      current
   DESCRIPTION
      "Path: ethernet1.status.switchCache.port

       Possibilities:
               none   (0)
               hwPort_1   (1)
               hwPort_2   (2)
               hwPort_3   (3)
               hwPort_4   (4)
               hwPort_5   (5)
               hwPort_LocalPort   (6)
               hwPort_LocalPort2   (7)"
   ::= {sr1646v2PortSwMCSwitchCacheEntry 33554432}

sr1646v2PortSwMCSwitchCacheType OBJECT-TYPE
   SYNTAX      INTEGER
               {
               static (0),
               dynamic (1)
               }
   MAX-ACCESS  read-only
   STATUS      current
   DESCRIPTION
      "Path: ethernet1.status.switchCache.type

       Possibilities:
               static   (0)
               dynamic   (1)"
   ::= {sr1646v2PortSwMCSwitchCacheEntry 50331648}

sr1646v2PortSwMCSwitchCacheTimeout OBJECT-TYPE
   SYNTAX      TimeTicks
   MAX-ACCESS  read-only
   STATUS      current
   DESCRIPTION
      "Path: ethernet1.status.switchCache.timeout

       Time in centi-second."
   ::= {sr1646v2PortSwMCSwitchCacheEntry 67108864}

sr1646v2PortSwMCSwitchCacheDbNum OBJECT-TYPE
   SYNTAX      Integer32
   MAX-ACCESS  read-only
   STATUS      current
   DESCRIPTION
      "Path: ethernet1.status.switchCache.dbNum"
   ::= {sr1646v2PortSwMCSwitchCacheEntry 83886080}


sr1646v2PortSwMCVtuTable OBJECT IDENTIFIER ::= {sr1646v2PortSwMC 89}

sr1646v2PortSwMCVtuTableSSCTable OBJECT-TYPE
   SYNTAX      SEQUENCE OF Sr1646v2PortSwMCVtuTableEntry
   MAX-ACCESS  not-accessible
   STATUS      current
   DESCRIPTION
      "VTU table"
   ::= {sr1646v2PortSwMCVtuTable 1}

sr1646v2PortSwMCVtuTableEntry OBJECT-TYPE
   SYNTAX      Sr1646v2PortSwMCVtuTableEntry
   MAX-ACCESS  not-accessible
   STATUS      current
   DESCRIPTION
      ""
   INDEX      { sr1646v2PortSwMCVtuTableTableIx }
   ::= {sr1646v2PortSwMCVtuTableSSCTable 1}

Sr1646v2PortSwMCVtuTableEntry ::=
   SEQUENCE
      {
      sr1646v2PortSwMCVtuTableTableIx
         TableIndex,
      sr1646v2PortSwMCVtuTableVid
         INTEGER,
      sr1646v2PortSwMCVtuTableHwPort1
         INTEGER,
      sr1646v2PortSwMCVtuTableHwPort2
         INTEGER,
      sr1646v2PortSwMCVtuTableHwPort3
         INTEGER,
      sr1646v2PortSwMCVtuTableHwPort4
         INTEGER,
      sr1646v2PortSwMCVtuTableHwPortLocalPort
         INTEGER,
      sr1646v2PortSwMCVtuTableDbNum
         Integer32
      }

sr1646v2PortSwMCVtuTableTableIx OBJECT-TYPE
   SYNTAX      TableIndex
   MAX-ACCESS  not-accessible
   STATUS      current
   DESCRIPTION
      ""
   ::= {sr1646v2PortSwMCVtuTableEntry 11}

sr1646v2PortSwMCVtuTableVid OBJECT-TYPE
   SYNTAX      INTEGER
               {
               untagged (0)
               }
   MAX-ACCESS  read-only
   STATUS      current
   DESCRIPTION
      "Path: ethernet1.status.vtuTable.vid

       Possibilities:
               untagged   (0)"
   ::= {sr1646v2PortSwMCVtuTableEntry 16777216}

sr1646v2PortSwMCVtuTableHwPort1 OBJECT-TYPE
   SYNTAX      INTEGER
               {
               pass (0),
               untag (1),
               tag (2),
               smm (3)
               }
   MAX-ACCESS  read-only
   STATUS      current
   DESCRIPTION
      "Path: ethernet1.status.vtuTable.hwPort1

       Possibilities:
               pass   (0)
               untag   (1)
               tag   (2)
               --   (3)"
   ::= {sr1646v2PortSwMCVtuTableEntry 33554432}

sr1646v2PortSwMCVtuTableHwPort2 OBJECT-TYPE
   SYNTAX      INTEGER
               {
               pass (0),
               untag (1),
               tag (2),
               smm (3)
               }
   MAX-ACCESS  read-only
   STATUS      current
   DESCRIPTION
      "Path: ethernet1.status.vtuTable.hwPort2

       Possibilities:
               pass   (0)
               untag   (1)
               tag   (2)
               --   (3)"
   ::= {sr1646v2PortSwMCVtuTableEntry 50331648}

sr1646v2PortSwMCVtuTableHwPort3 OBJECT-TYPE
   SYNTAX      INTEGER
               {
               pass (0),
               untag (1),
               tag (2),
               smm (3)
               }
   MAX-ACCESS  read-only
   STATUS      current
   DESCRIPTION
      "Path: ethernet1.status.vtuTable.hwPort3

       Possibilities:
               pass   (0)
               untag   (1)
               tag   (2)
               --   (3)"
   ::= {sr1646v2PortSwMCVtuTableEntry 67108864}

sr1646v2PortSwMCVtuTableHwPort4 OBJECT-TYPE
   SYNTAX      INTEGER
               {
               pass (0),
               untag (1),
               tag (2),
               smm (3)
               }
   MAX-ACCESS  read-only
   STATUS      current
   DESCRIPTION
      "Path: ethernet1.status.vtuTable.hwPort4

       Possibilities:
               pass   (0)
               untag   (1)
               tag   (2)
               --   (3)"
   ::= {sr1646v2PortSwMCVtuTableEntry 83886080}

sr1646v2PortSwMCVtuTableHwPortLocalPort OBJECT-TYPE
   SYNTAX      INTEGER
               {
               pass (0),
               untag (1),
               tag (2),
               smm (3)
               }
   MAX-ACCESS  read-only
   STATUS      current
   DESCRIPTION
      "Path: ethernet1.status.vtuTable.hwPortLocalPort

       Possibilities:
               pass   (0)
               untag   (1)
               tag   (2)
               --   (3)"
   ::= {sr1646v2PortSwMCVtuTableEntry 117440512}

sr1646v2PortSwMCVtuTableDbNum OBJECT-TYPE
   SYNTAX      Integer32
   MAX-ACCESS  read-only
   STATUS      current
   DESCRIPTION
      "Path: ethernet1.status.vtuTable.dbNum"
   ::= {sr1646v2PortSwMCVtuTableEntry 134217728}



pr1646v2PortSwMC OBJECT IDENTIFIER ::= {r1646v2PortSwMC 12}


pr1646v2PortSwMCInOctets OBJECT-TYPE
   SYNTAX      Counter64
   MAX-ACCESS  read-only
   STATUS      current
   DESCRIPTION
      "Path: ethernet1.performance.ifInOctets
       Info: ifInOctets

       64 bit unsigned wrappable counter."
   ::= {pr1646v2PortSwMC 109}


pr1646v2PortSwMCInUcast OBJECT-TYPE
   SYNTAX      Counter64
   MAX-ACCESS  read-only
   STATUS      current
   DESCRIPTION
      "Path: ethernet1.performance.ifInUcastPkts
       Info: ifInUcastPkts

       64 bit unsigned wrappable counter."
   ::= {pr1646v2PortSwMC 110}


pr1646v2PortSwMCInNUcastPkts OBJECT-TYPE
   SYNTAX      Counter64
   MAX-ACCESS  read-only
   STATUS      current
   DESCRIPTION
      "Path: ethernet1.performance.ifInNUcastPkts
       Info: ifInNUcastPkts

       64 bit unsigned wrappable counter."
   ::= {pr1646v2PortSwMC 111}


pr1646v2PortSwMCInBcastPkts OBJECT-TYPE
   SYNTAX      Counter64
   MAX-ACCESS  read-only
   STATUS      current
   DESCRIPTION
      "Path: ethernet1.performance.ifInBcastPkts
       Info: ifInBcastPkts

       64 bit unsigned wrappable counter."
   ::= {pr1646v2PortSwMC 211}


pr1646v2PortSwMCInMcastPkts OBJECT-TYPE
   SYNTAX      Counter64
   MAX-ACCESS  read-only
   STATUS      current
   DESCRIPTION
      "Path: ethernet1.performance.ifInMcastPkts
       Info: ifInNUcastPkts

       64 bit unsigned wrappable counter."
   ::= {pr1646v2PortSwMC 221}


pr1646v2PortSwMCInDiscards OBJECT-TYPE
   SYNTAX      Counter64
   MAX-ACCESS  read-only
   STATUS      current
   DESCRIPTION
      "Path: ethernet1.performance.ifInDiscards
       Info: ifInDiscards

       64 bit unsigned wrappable counter."
   ::= {pr1646v2PortSwMC 112}


pr1646v2PortSwMCInErrors OBJECT-TYPE
   SYNTAX      Counter64
   MAX-ACCESS  read-only
   STATUS      current
   DESCRIPTION
      "Path: ethernet1.performance.ifInErrors
       Info: ifInErrors

       64 bit unsigned wrappable counter."
   ::= {pr1646v2PortSwMC 113}


pr1646v2PortSwMCInUnknownProtos OBJECT-TYPE
   SYNTAX      Counter64
   MAX-ACCESS  read-only
   STATUS      current
   DESCRIPTION
      "Path: ethernet1.performance.ifInUnknownProtos
       Info: ifInUnknownprotos

       64 bit unsigned wrappable counter."
   ::= {pr1646v2PortSwMC 114}


pr1646v2PortSwMCInQLen OBJECT-TYPE
   SYNTAX      Gauge32
   MAX-ACCESS  read-only
   STATUS      current
   DESCRIPTION
      "Path: ethernet1.performance.ifInQLen
       Info: ifInQLen

       32 bit unsigned gauge value."
   ::= {pr1646v2PortSwMC 128}


pr1646v2PortSwMCInDropEx OBJECT-TYPE
   SYNTAX      Counter64
   MAX-ACCESS  read-only
   STATUS      current
   DESCRIPTION
      "Path: ethernet1.performance.ifInDropLevelExceeded
       Info: ifInDiscards

       64 bit unsigned wrappable counter."
   ::= {pr1646v2PortSwMC 130}


pr1646v2PortSwMCInDropNoMac OBJECT-TYPE
   SYNTAX      Counter64
   MAX-ACCESS  read-only
   STATUS      current
   DESCRIPTION
      "Path: ethernet1.performance.ifInDiscardsNoMacFit
       Info: ifInDiscards

       64 bit unsigned wrappable counter."
   ::= {pr1646v2PortSwMC 133}


pr1646v2PortSwMCInDropNUCast OBJECT-TYPE
   SYNTAX      Counter64
   MAX-ACCESS  read-only
   STATUS      current
   DESCRIPTION
      "Path: ethernet1.performance.ifInDiscardsNUCast
       Info: ifInDiscards

       64 bit unsigned wrappable counter."
   ::= {pr1646v2PortSwMC 136}


pr1646v2PortSwMCInDropFilter OBJECT-TYPE
   SYNTAX      Counter64
   MAX-ACCESS  read-only
   STATUS      current
   DESCRIPTION
      "Path: ethernet1.performance.ifInDiscardsFilter
       Info: ifInDiscards

       64 bit unsigned wrappable counter."
   ::= {pr1646v2PortSwMC 137}


pr1646v2PortSwMCInBandwidth OBJECT IDENTIFIER ::= {pr1646v2PortSwMC 181}

pr1646v2PortSwMCInBandwidthSSC OBJECT IDENTIFIER ::= {pr1646v2PortSwMCInBandwidth 1}

pr1646v2PortSwMCInBandwidthEntry OBJECT IDENTIFIER ::= {pr1646v2PortSwMCInBandwidthSSC 1}

pr1646v2PortSwMCInBandwidth15sec OBJECT-TYPE
   SYNTAX      Integer32
   MAX-ACCESS  read-only
   STATUS      current
   DESCRIPTION
      "Path: ethernet1.performance.ifInBandwidth.15sec

       unit name = bps
       formula = 8 * ; 8 /"
   ::= {pr1646v2PortSwMCInBandwidthEntry 83886080}

pr1646v2PortSwMCInBandwidth30sec OBJECT-TYPE
   SYNTAX      Integer32
   MAX-ACCESS  read-only
   STATUS      current
   DESCRIPTION
      "Path: ethernet1.performance.ifInBandwidth.30sec

       unit name = bps
       formula = 8 * ; 8 /"
   ::= {pr1646v2PortSwMCInBandwidthEntry 167772160}

pr1646v2PortSwMCInBandwidth1min OBJECT-TYPE
   SYNTAX      Integer32
   MAX-ACCESS  read-only
   STATUS      current
   DESCRIPTION
      "Path: ethernet1.performance.ifInBandwidth.1min

       unit name = bps
       formula = 8 * ; 8 /"
   ::= {pr1646v2PortSwMCInBandwidthEntry 335544320}

pr1646v2PortSwMCInBandwidth2min OBJECT-TYPE
   SYNTAX      Integer32
   MAX-ACCESS  read-only
   STATUS      current
   DESCRIPTION
      "Path: ethernet1.performance.ifInBandwidth.2min

       unit name = bps
       formula = 8 * ; 8 /"
   ::= {pr1646v2PortSwMCInBandwidthEntry 671088640}

pr1646v2PortSwMCInBandwidth5min OBJECT-TYPE
   SYNTAX      Integer32
   MAX-ACCESS  read-only
   STATUS      current
   DESCRIPTION
      "Path: ethernet1.performance.ifInBandwidth.5min

       unit name = bps
       formula = 8 * ; 8 /"
   ::= {pr1646v2PortSwMCInBandwidthEntry 1677721600}


pr1646v2PortSwMCOutOctets OBJECT-TYPE
   SYNTAX      Counter64
   MAX-ACCESS  read-only
   STATUS      current
   DESCRIPTION
      "Path: ethernet1.performance.ifOutOctets
       Info: ifOutOctets

       64 bit unsigned wrappable counter."
   ::= {pr1646v2PortSwMC 115}


pr1646v2PortSwMCOutUcastPkts OBJECT-TYPE
   SYNTAX      Counter64
   MAX-ACCESS  read-only
   STATUS      current
   DESCRIPTION
      "Path: ethernet1.performance.ifOutUcastPkts
       Info: ifOutUcastPkts

       64 bit unsigned wrappable counter."
   ::= {pr1646v2PortSwMC 116}


pr1646v2PortSwMCOutNUcastPkts OBJECT-TYPE
   SYNTAX      Counter64
   MAX-ACCESS  read-only
   STATUS      current
   DESCRIPTION
      "Path: ethernet1.performance.ifOutNUcastPkts
       Info: ifOutNUcastPkts

       64 bit unsigned wrappable counter."
   ::= {pr1646v2PortSwMC 117}


pr1646v2PortSwMCOutBcastPkts OBJECT-TYPE
   SYNTAX      Counter64
   MAX-ACCESS  read-only
   STATUS      current
   DESCRIPTION
      "Path: ethernet1.performance.ifOutBcastPkts
       Info: ifOutBcastPkts

       64 bit unsigned wrappable counter."
   ::= {pr1646v2PortSwMC 217}


pr1646v2PortSwMCOutMcastPkts OBJECT-TYPE
   SYNTAX      Counter64
   MAX-ACCESS  read-only
   STATUS      current
   DESCRIPTION
      "Path: ethernet1.performance.ifOutMcastPkts
       Info: ifOutMcastPkts

       64 bit unsigned wrappable counter."
   ::= {pr1646v2PortSwMC 227}


pr1646v2PortSwMCOutDiscards OBJECT-TYPE
   SYNTAX      Counter64
   MAX-ACCESS  read-only
   STATUS      current
   DESCRIPTION
      "Path: ethernet1.performance.ifOutDiscards
       Info: ifOutDiscards

       64 bit unsigned wrappable counter."
   ::= {pr1646v2PortSwMC 118}


pr1646v2PortSwMCOutErrors OBJECT-TYPE
   SYNTAX      Counter64
   MAX-ACCESS  read-only
   STATUS      current
   DESCRIPTION
      "Path: ethernet1.performance.ifOutErrors
       Info: ifOutErrors

       64 bit unsigned wrappable counter."
   ::= {pr1646v2PortSwMC 119}


pr1646v2PortSwMCOutQLen OBJECT-TYPE
   SYNTAX      Gauge32
   MAX-ACCESS  read-only
   STATUS      current
   DESCRIPTION
      "Path: ethernet1.performance.ifOutQLen
       Info: ifOutQLen

       32 bit unsigned gauge value."
   ::= {pr1646v2PortSwMC 120}


pr1646v2PortSwMCOutDropEx OBJECT-TYPE
   SYNTAX      Counter64
   MAX-ACCESS  read-only
   STATUS      current
   DESCRIPTION
      "Path: ethernet1.performance.ifOutDropLevelExceeded
       Info: ifOutDiscards

       64 bit unsigned wrappable counter."
   ::= {pr1646v2PortSwMC 127}


pr1646v2PortSwMCOutDropNoArp OBJECT-TYPE
   SYNTAX      Counter64
   MAX-ACCESS  read-only
   STATUS      current
   DESCRIPTION
      "Path: ethernet1.performance.ifOutDiscardsNoArp
       Info: ifOutDiscards

       64 bit unsigned wrappable counter."
   ::= {pr1646v2PortSwMC 134}


pr1646v2PortSwMCOutDropFilter OBJECT-TYPE
   SYNTAX      Counter64
   MAX-ACCESS  read-only
   STATUS      current
   DESCRIPTION
      "Path: ethernet1.performance.ifOutDiscardsFilter
       Info: ifOutDiscards

       64 bit unsigned wrappable counter."
   ::= {pr1646v2PortSwMC 138}


pr1646v2PortSwMCOutQueues OBJECT IDENTIFIER ::= {pr1646v2PortSwMC 129}

pr1646v2PortSwMCOutQueuesSSCTable OBJECT-TYPE
   SYNTAX      SEQUENCE OF Pr1646v2PortSwMCOutQueuesEntry
   MAX-ACCESS  not-accessible
   STATUS      current
   DESCRIPTION
      "Queue Lengths"
   ::= {pr1646v2PortSwMCOutQueues 1}

pr1646v2PortSwMCOutQueuesEntry OBJECT-TYPE
   SYNTAX      Pr1646v2PortSwMCOutQueuesEntry
   MAX-ACCESS  not-accessible
   STATUS      current
   DESCRIPTION
      ""
   INDEX      { pr1646v2PortSwMCOutQueuesTableIx }
   ::= {pr1646v2PortSwMCOutQueuesSSCTable 1}

Pr1646v2PortSwMCOutQueuesEntry ::=
   SEQUENCE
      {
      pr1646v2PortSwMCOutQueuesTableIx
         TableIndex,
      pr1646v2PortSwMCOutQueuesName
         INTEGER,
      pr1646v2PortSwMCOutQueuesLength
         Integer32,
      pr1646v2PortSwMCOutQueuesOctetLength
         Integer32,
      pr1646v2PortSwMCOutQueuesRedLength
         Integer32,
      pr1646v2PortSwMCOutQueuesPacketsTotal
         Counter64,
      pr1646v2PortSwMCOutQueuesPacketsDirectTx
         Counter64,
      pr1646v2PortSwMCOutQueuesPacketsQueued
         Counter64,
      pr1646v2PortSwMCOutQueuesPacketsDropped
         Counter64,
      pr1646v2PortSwMCOutQueuesPacketsRedDropped
         Counter64,
      pr1646v2PortSwMCOutQueuesPacketsCirTx
         Counter64,
      pr1646v2PortSwMCOutQueuesPacketsEirTx
         Counter64,
      pr1646v2PortSwMCOutQueuesPacketsViolateTx
         Counter64,
      pr1646v2PortSwMCOutQueuesOctetsTotal
         Counter64,
      pr1646v2PortSwMCOutQueuesOctetsDirectTx
         Counter64,
      pr1646v2PortSwMCOutQueuesOctetsQueued
         Counter64,
      pr1646v2PortSwMCOutQueuesOctetsDropped
         Counter64,
      pr1646v2PortSwMCOutQueuesOctetsRedDropped
         Counter64,
      pr1646v2PortSwMCOutQueuesOctetsCirTx
         Counter64,
      pr1646v2PortSwMCOutQueuesOctetsEirTx
         Counter64,
      pr1646v2PortSwMCOutQueuesOctetsViolateTx
         Counter64,
      pr1646v2PortSwMCOutQueuesOctetsBandwidth15sec
         Integer32,
      pr1646v2PortSwMCOutQueuesOctetsBandwidth30sec
         Integer32,
      pr1646v2PortSwMCOutQueuesOctetsBandwidth1min
         Integer32,
      pr1646v2PortSwMCOutQueuesOctetsBandwidth2min
         Integer32,
      pr1646v2PortSwMCOutQueuesOctetsBandwidth5min
         Integer32
      }

pr1646v2PortSwMCOutQueuesTableIx OBJECT-TYPE
   SYNTAX      TableIndex
   MAX-ACCESS  not-accessible
   STATUS      current
   DESCRIPTION
      ""
   ::= {pr1646v2PortSwMCOutQueuesEntry 11}

pr1646v2PortSwMCOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2PortSwMCOutQueuesEntry 16777216}

pr1646v2PortSwMCOutQueuesLength OBJECT-TYPE
   SYNTAX      Integer32
   MAX-ACCESS  read-only
   STATUS      current
   DESCRIPTION
      "Path: ethernet1.performance.ifOutPriorityQueues.length"
   ::= {pr1646v2PortSwMCOutQueuesEntry 33554432}

pr1646v2PortSwMCOutQueuesOctetLength OBJECT-TYPE
   SYNTAX      Integer32
   MAX-ACCESS  read-only
   STATUS      current
   DESCRIPTION
      "Path: ethernet1.performance.ifOutPriorityQueues.octetLength"
   ::= {pr1646v2PortSwMCOutQueuesEntry 150994944}

pr1646v2PortSwMCOutQueuesRedLength OBJECT-TYPE
   SYNTAX      Integer32
   MAX-ACCESS  read-only
   STATUS      current
   DESCRIPTION
      "Path: ethernet1.performance.ifOutPriorityQueues.redLength"
   ::= {pr1646v2PortSwMCOutQueuesEntry 134217728}

pr1646v2PortSwMCOutQueuesPacketsTotal OBJECT-TYPE
   SYNTAX      Counter64
   MAX-ACCESS  read-only
   STATUS      current
   DESCRIPTION
      "Path: ethernet1.performance.ifOutPriorityQueues.packets.total

       64 bit unsigned wrappable counter."
   ::= {pr1646v2PortSwMCOutQueuesEntry 50790400}

pr1646v2PortSwMCOutQueuesPacketsDirectTx OBJECT-TYPE
   SYNTAX      Counter64
   MAX-ACCESS  read-only
   STATUS      current
   DESCRIPTION
      "Path: ethernet1.performance.ifOutPriorityQueues.packets.directTx

       64 bit unsigned wrappable counter."
   ::= {pr1646v2PortSwMCOutQueuesEntry 50397184}

pr1646v2PortSwMCOutQueuesPacketsQueued OBJECT-TYPE
   SYNTAX      Counter64
   MAX-ACCESS  read-only
   STATUS      current
   DESCRIPTION
      "Path: ethernet1.performance.ifOutPriorityQueues.packets.queued

       64 bit unsigned wrappable counter."
   ::= {pr1646v2PortSwMCOutQueuesEntry 50462720}

pr1646v2PortSwMCOutQueuesPacketsDropped OBJECT-TYPE
   SYNTAX      Counter64
   MAX-ACCESS  read-only
   STATUS      current
   DESCRIPTION
      "Path: ethernet1.performance.ifOutPriorityQueues.packets.dropped

       64 bit unsigned wrappable counter."
   ::= {pr1646v2PortSwMCOutQueuesEntry 50528256}

pr1646v2PortSwMCOutQueuesPacketsRedDropped OBJECT-TYPE
   SYNTAX      Counter64
   MAX-ACCESS  read-only
   STATUS      current
   DESCRIPTION
      "Path: ethernet1.performance.ifOutPriorityQueues.packets.redDropped

       64 bit unsigned wrappable counter."
   ::= {pr1646v2PortSwMCOutQueuesEntry 50724864}

pr1646v2PortSwMCOutQueuesPacketsCirTx OBJECT-TYPE
   SYNTAX      Counter64
   MAX-ACCESS  read-only
   STATUS      current
   DESCRIPTION
      "Path: ethernet1.performance.ifOutPriorityQueues.packets.cirTx

       64 bit unsigned wrappable counter."
   ::= {pr1646v2PortSwMCOutQueuesEntry 50593792}

pr1646v2PortSwMCOutQueuesPacketsEirTx OBJECT-TYPE
   SYNTAX      Counter64
   MAX-ACCESS  read-only
   STATUS      current
   DESCRIPTION
      "Path: ethernet1.performance.ifOutPriorityQueues.packets.eirTx

       64 bit unsigned wrappable counter."
   ::= {pr1646v2PortSwMCOutQueuesEntry 50659328}

pr1646v2PortSwMCOutQueuesPacketsViolateTx OBJECT-TYPE
   SYNTAX      Counter64
   MAX-ACCESS  read-only
   STATUS      current
   DESCRIPTION
      "Path: ethernet1.performance.ifOutPriorityQueues.packets.violateTx

       64 bit unsigned wrappable counter."
   ::= {pr1646v2PortSwMCOutQueuesEntry 50855936}

pr1646v2PortSwMCOutQueuesOctetsTotal OBJECT-TYPE
   SYNTAX      Counter64
   MAX-ACCESS  read-only
   STATUS      current
   DESCRIPTION
      "Path: ethernet1.performance.ifOutPriorityQueues.octets.total

       64 bit unsigned wrappable counter."
   ::= {pr1646v2PortSwMCOutQueuesEntry 67567616}

pr1646v2PortSwMCOutQueuesOctetsDirectTx OBJECT-TYPE
   SYNTAX      Counter64
   MAX-ACCESS  read-only
   STATUS      current
   DESCRIPTION
      "Path: ethernet1.performance.ifOutPriorityQueues.octets.directTx

       64 bit unsigned wrappable counter."
   ::= {pr1646v2PortSwMCOutQueuesEntry 67174400}

pr1646v2PortSwMCOutQueuesOctetsQueued OBJECT-TYPE
   SYNTAX      Counter64
   MAX-ACCESS  read-only
   STATUS      current
   DESCRIPTION
      "Path: ethernet1.performance.ifOutPriorityQueues.octets.queued

       64 bit unsigned wrappable counter."
   ::= {pr1646v2PortSwMCOutQueuesEntry 67239936}

pr1646v2PortSwMCOutQueuesOctetsDropped OBJECT-TYPE
   SYNTAX      Counter64
   MAX-ACCESS  read-only
   STATUS      current
   DESCRIPTION
      "Path: ethernet1.performance.ifOutPriorityQueues.octets.dropped

       64 bit unsigned wrappable counter."
   ::= {pr1646v2PortSwMCOutQueuesEntry 67305472}

pr1646v2PortSwMCOutQueuesOctetsRedDropped OBJECT-TYPE
   SYNTAX      Counter64
   MAX-ACCESS  read-only
   STATUS      current
   DESCRIPTION
      "Path: ethernet1.performance.ifOutPriorityQueues.octets.redDropped

       64 bit unsigned wrappable counter."
   ::= {pr1646v2PortSwMCOutQueuesEntry 67502080}

pr1646v2PortSwMCOutQueuesOctetsCirTx OBJECT-TYPE
   SYNTAX      Counter64
   MAX-ACCESS  read-only
   STATUS      current
   DESCRIPTION
      "Path: ethernet1.performance.ifOutPriorityQueues.octets.cirTx

       64 bit unsigned wrappable counter."
   ::= {pr1646v2PortSwMCOutQueuesEntry 67371008}

pr1646v2PortSwMCOutQueuesOctetsEirTx OBJECT-TYPE
   SYNTAX      Counter64
   MAX-ACCESS  read-only
   STATUS      current
   DESCRIPTION
      "Path: ethernet1.performance.ifOutPriorityQueues.octets.eirTx

       64 bit unsigned wrappable counter."
   ::= {pr1646v2PortSwMCOutQueuesEntry 67436544}

pr1646v2PortSwMCOutQueuesOctetsViolateTx OBJECT-TYPE
   SYNTAX      Counter64
   MAX-ACCESS  read-only
   STATUS      current
   DESCRIPTION
      "Path: ethernet1.performance.ifOutPriorityQueues.octets.violateTx

       64 bit unsigned wrappable counter."
   ::= {pr1646v2PortSwMCOutQueuesEntry 67633152}

pr1646v2PortSwMCOutQueuesOctetsBandwidth15sec OBJECT-TYPE
   SYNTAX      Integer32
   MAX-ACCESS  read-only
   STATUS      current
   DESCRIPTION
      "Path: ethernet1.performance.ifOutPriorityQueues.octets.bandwidth.15sec

       unit name = bps
       formula = 8 * ; 8 /"
   ::= {pr1646v2PortSwMCOutQueuesEntry 70386944}

pr1646v2PortSwMCOutQueuesOctetsBandwidth30sec OBJECT-TYPE
   SYNTAX      Integer32
   MAX-ACCESS  read-only
   STATUS      current
   DESCRIPTION
      "Path: ethernet1.performance.ifOutPriorityQueues.octets.bandwidth.30sec

       unit name = bps
       formula = 8 * ; 8 /"
   ::= {pr1646v2PortSwMCOutQueuesEntry 70388224}

pr1646v2PortSwMCOutQueuesOctetsBandwidth1min OBJECT-TYPE
   SYNTAX      Integer32
   MAX-ACCESS  read-only
   STATUS      current
   DESCRIPTION
      "Path: ethernet1.performance.ifOutPriorityQueues.octets.bandwidth.1min

       unit name = bps
       formula = 8 * ; 8 /"
   ::= {pr1646v2PortSwMCOutQueuesEntry 70390784}

pr1646v2PortSwMCOutQueuesOctetsBandwidth2min OBJECT-TYPE
   SYNTAX      Integer32
   MAX-ACCESS  read-only
   STATUS      current
   DESCRIPTION
      "Path: ethernet1.performance.ifOutPriorityQueues.octets.bandwidth.2min

       unit name = bps
       formula = 8 * ; 8 /"
   ::= {pr1646v2PortSwMCOutQueuesEntry 70395904}

pr1646v2PortSwMCOutQueuesOctetsBandwidth5min OBJECT-TYPE
   SYNTAX      Integer32
   MAX-ACCESS  read-only
   STATUS      current
   DESCRIPTION
      "Path: ethernet1.performance.ifOutPriorityQueues.octets.bandwidth.5min

       unit name = bps
       formula = 8 * ; 8 /"
   ::= {pr1646v2PortSwMCOutQueuesEntry 70411264}

pr1646v2PortSwMCOutQueuesH2Performance OBJECT-TYPE
   SYNTAX      SEQUENCE OF Pr1646v2PortSwMCOutQueuesH2PerformanceEntry
   MAX-ACCESS  not-accessible
   STATUS      current
   DESCRIPTION
      ""
   ::= {pr1646v2PortSwMCOutQueues 83886080}

pr1646v2PortSwMCOutQueuesH2PerformanceEntry OBJECT-TYPE
   SYNTAX      Pr1646v2PortSwMCOutQueuesH2PerformanceEntry
   MAX-ACCESS  not-accessible
   STATUS      current
   DESCRIPTION
      ""
   INDEX      { pr1646v2PortSwMCOutQueuesTableIx,
                pr1646v2PortSwMCOutQueuesH2PerformanceTableIx }
   ::= {pr1646v2PortSwMCOutQueuesH2Performance 1}

Pr1646v2PortSwMCOutQueuesH2PerformanceEntry ::=
   SEQUENCE
      {
      pr1646v2PortSwMCOutQueuesH2PerformanceTableIx
         TableIndex,
      pr1646v2PortSwMCOutQueuesH2PerformanceSysUpTime
         TimeTicks,
      pr1646v2PortSwMCOutQueuesH2PerformanceTotPkts
         Counter64,
      pr1646v2PortSwMCOutQueuesH2PerformanceDirTxPkts
         Counter64,
      pr1646v2PortSwMCOutQueuesH2PerformanceQdPkts
         Counter64,
      pr1646v2PortSwMCOutQueuesH2PerformanceDropPkts
         Counter64,
      pr1646v2PortSwMCOutQueuesH2PerformanceRDropPkts
         Counter64,
      pr1646v2PortSwMCOutQueuesH2PerformanceCirTxPkts
         Counter64,
      pr1646v2PortSwMCOutQueuesH2PerformanceEirTxPkts
         Counter64,
      pr1646v2PortSwMCOutQueuesH2PerformanceViolTxPkts
         Counter64,
      pr1646v2PortSwMCOutQueuesH2PerformanceTotOcts
         Counter64,
      pr1646v2PortSwMCOutQueuesH2PerformanceDirTxOcts
         Counter64,
      pr1646v2PortSwMCOutQueuesH2PerformanceQdOcts
         Counter64,
      pr1646v2PortSwMCOutQueuesH2PerformanceDropOcts
         Counter64,
      pr1646v2PortSwMCOutQueuesH2PerformanceRDropOcts
         Counter64,
      pr1646v2PortSwMCOutQueuesH2PerformanceCirTxOcts
         Counter64,
      pr1646v2PortSwMCOutQueuesH2PerformanceEirTxOcts
         Counter64,
      pr1646v2PortSwMCOutQueuesH2PerformanceViolTxOcts
         Counter64,
      pr1646v2PortSwMCOutQueuesH2PerformanceBandwidth
         Integer32
      }

pr1646v2PortSwMCOutQueuesH2PerformanceTableIx OBJECT-TYPE
   SYNTAX      TableIndex
   MAX-ACCESS  not-accessible
   STATUS      current
   DESCRIPTION
      ""
   ::= {pr1646v2PortSwMCOutQueuesH2PerformanceEntry 11}

pr1646v2PortSwMCOutQueuesH2PerformanceSysUpTime OBJECT-TYPE
   SYNTAX      TimeTicks
   MAX-ACCESS  read-only
   STATUS      current
   DESCRIPTION
      "Path: ethernet1.performance.ifOutPriorityQueues.h2Performance.sysUpTime

       Time in centi-second."
   ::= {pr1646v2PortSwMCOutQueuesH2PerformanceEntry 16777216}

pr1646v2PortSwMCOutQueuesH2PerformanceTotPkts OBJECT-TYPE
   SYNTAX      Counter64
   MAX-ACCESS  read-only
   STATUS      current
   DESCRIPTION
      "Path: ethernet1.performance.ifOutPriorityQueues.h2Performance.totalPkts

       64 bit unsigned wrappable counter."
   ::= {pr1646v2PortSwMCOutQueuesH2PerformanceEntry 234881024}

pr1646v2PortSwMCOutQueuesH2PerformanceDirTxPkts OBJECT-TYPE
   SYNTAX      Counter64
   MAX-ACCESS  read-only
   STATUS      current
   DESCRIPTION
      "Path: ethernet1.performance.ifOutPriorityQueues.h2Performance.directTxPkts

       64 bit unsigned wrappable counter."
   ::= {pr1646v2PortSwMCOutQueuesH2PerformanceEntry 33554432}

pr1646v2PortSwMCOutQueuesH2PerformanceQdPkts OBJECT-TYPE
   SYNTAX      Counter64
   MAX-ACCESS  read-only
   STATUS      current
   DESCRIPTION
      "Path: ethernet1.performance.ifOutPriorityQueues.h2Performance.queuedPkts

       64 bit unsigned wrappable counter."
   ::= {pr1646v2PortSwMCOutQueuesH2PerformanceEntry 50331648}

pr1646v2PortSwMCOutQueuesH2PerformanceDropPkts OBJECT-TYPE
   SYNTAX      Counter64
   MAX-ACCESS  read-only
   STATUS      current
   DESCRIPTION
      "Path: ethernet1.performance.ifOutPriorityQueues.h2Performance.droppedPkts

       64 bit unsigned wrappable counter."
   ::= {pr1646v2PortSwMCOutQueuesH2PerformanceEntry 67108864}

pr1646v2PortSwMCOutQueuesH2PerformanceRDropPkts OBJECT-TYPE
   SYNTAX      Counter64
   MAX-ACCESS  read-only
   STATUS      current
   DESCRIPTION
      "Path: ethernet1.performance.ifOutPriorityQueues.h2Performance.redDroppedPkts

       64 bit unsigned wrappable counter."
   ::= {pr1646v2PortSwMCOutQueuesH2PerformanceEntry 201326592}

pr1646v2PortSwMCOutQueuesH2PerformanceCirTxPkts OBJECT-TYPE
   SYNTAX      Counter64
   MAX-ACCESS  read-only
   STATUS      current
   DESCRIPTION
      "Path: ethernet1.performance.ifOutPriorityQueues.h2Performance.cirTxPkts

       64 bit unsigned wrappable counter."
   ::= {pr1646v2PortSwMCOutQueuesH2PerformanceEntry 83886080}

pr1646v2PortSwMCOutQueuesH2PerformanceEirTxPkts OBJECT-TYPE
   SYNTAX      Counter64
   MAX-ACCESS  read-only
   STATUS      current
   DESCRIPTION
      "Path: ethernet1.performance.ifOutPriorityQueues.h2Performance.eirTxPkts

       64 bit unsigned wrappable counter."
   ::= {pr1646v2PortSwMCOutQueuesH2PerformanceEntry 100663296}

pr1646v2PortSwMCOutQueuesH2PerformanceViolTxPkts OBJECT-TYPE
   SYNTAX      Counter64
   MAX-ACCESS  read-only
   STATUS      current
   DESCRIPTION
      "Path: ethernet1.performance.ifOutPriorityQueues.h2Performance.violateTxPkts

       64 bit unsigned wrappable counter."
   ::= {pr1646v2PortSwMCOutQueuesH2PerformanceEntry 301989888}

pr1646v2PortSwMCOutQueuesH2PerformanceTotOcts OBJECT-TYPE
   SYNTAX      Counter64
   MAX-ACCESS  read-only
   STATUS      current
   DESCRIPTION
      "Path: ethernet1.performance.ifOutPriorityQueues.h2Performance.totalOctets

       64 bit unsigned wrappable counter."
   ::= {pr1646v2PortSwMCOutQueuesH2PerformanceEntry 251658240}

pr1646v2PortSwMCOutQueuesH2PerformanceDirTxOcts OBJECT-TYPE
   SYNTAX      Counter64
   MAX-ACCESS  read-only
   STATUS      current
   DESCRIPTION
      "Path: ethernet1.performance.ifOutPriorityQueues.h2Performance.directTxOctets

       64 bit unsigned wrappable counter."
   ::= {pr1646v2PortSwMCOutQueuesH2PerformanceEntry 117440512}

pr1646v2PortSwMCOutQueuesH2PerformanceQdOcts OBJECT-TYPE
   SYNTAX      Counter64
   MAX-ACCESS  read-only
   STATUS      current
   DESCRIPTION
      "Path: ethernet1.performance.ifOutPriorityQueues.h2Performance.queuedOctets

       64 bit unsigned wrappable counter."
   ::= {pr1646v2PortSwMCOutQueuesH2PerformanceEntry 134217728}

pr1646v2PortSwMCOutQueuesH2PerformanceDropOcts OBJECT-TYPE
   SYNTAX      Counter64
   MAX-ACCESS  read-only
   STATUS      current
   DESCRIPTION
      "Path: ethernet1.performance.ifOutPriorityQueues.h2Performance.droppedOctets

       64 bit unsigned wrappable counter."
   ::= {pr1646v2PortSwMCOutQueuesH2PerformanceEntry 150994944}

pr1646v2PortSwMCOutQueuesH2PerformanceRDropOcts OBJECT-TYPE
   SYNTAX      Counter64
   MAX-ACCESS  read-only
   STATUS      current
   DESCRIPTION
      "Path: ethernet1.performance.ifOutPriorityQueues.h2Performance.redDroppedOctets

       64 bit unsigned wrappable counter."
   ::= {pr1646v2PortSwMCOutQueuesH2PerformanceEntry 218103808}

pr1646v2PortSwMCOutQueuesH2PerformanceCirTxOcts OBJECT-TYPE
   SYNTAX      Counter64
   MAX-ACCESS  read-only
   STATUS      current
   DESCRIPTION
      "Path: ethernet1.performance.ifOutPriorityQueues.h2Performance.cirTxOctets

       64 bit unsigned wrappable counter."
   ::= {pr1646v2PortSwMCOutQueuesH2PerformanceEntry 167772160}

pr1646v2PortSwMCOutQueuesH2PerformanceEirTxOcts OBJECT-TYPE
   SYNTAX      Counter64
   MAX-ACCESS  read-only
   STATUS      current
   DESCRIPTION
      "Path: ethernet1.performance.ifOutPriorityQueues.h2Performance.eirTxOctets

       64 bit unsigned wrappable counter."
   ::= {pr1646v2PortSwMCOutQueuesH2PerformanceEntry 184549376}

pr1646v2PortSwMCOutQueuesH2PerformanceViolTxOcts OBJECT-TYPE
   SYNTAX      Counter64
   MAX-ACCESS  read-only
   STATUS      current
   DESCRIPTION
      "Path: ethernet1.performance.ifOutPriorityQueues.h2Performance.violateTxOctets

       64 bit unsigned wrappable counter."
   ::= {pr1646v2PortSwMCOutQueuesH2PerformanceEntry 318767104}

pr1646v2PortSwMCOutQueuesH2PerformanceBandwidth OBJECT-TYPE
   SYNTAX      Integer32
   MAX-ACCESS  read-only
   STATUS      current
   DESCRIPTION
      "Path: ethernet1.performance.ifOutPriorityQueues.h2Performance.bandwidth

       unit name = bps
       formula = 8 * ; 8 /"
   ::= {pr1646v2PortSwMCOutQueuesH2PerformanceEntry 268435456}

pr1646v2PortSwMCOutQueuesH24Performance OBJECT-TYPE
   SYNTAX      SEQUENCE OF Pr1646v2PortSwMCOutQueuesH24PerformanceEntry
   MAX-ACCESS  not-accessible
   STATUS      current
   DESCRIPTION
      ""
   ::= {pr1646v2PortSwMCOutQueues 100663296}

pr1646v2PortSwMCOutQueuesH24PerformanceEntry OBJECT-TYPE
   SYNTAX      Pr1646v2PortSwMCOutQueuesH24PerformanceEntry
   MAX-ACCESS  not-accessible
   STATUS      current
   DESCRIPTION
      ""
   INDEX      { pr1646v2PortSwMCOutQueuesTableIx,
                pr1646v2PortSwMCOutQueuesH24PerformanceTableIx }
   ::= {pr1646v2PortSwMCOutQueuesH24Performance 1}

Pr1646v2PortSwMCOutQueuesH24PerformanceEntry ::=
   SEQUENCE
      {
      pr1646v2PortSwMCOutQueuesH24PerformanceTableIx
         TableIndex,
      pr1646v2PortSwMCOutQueuesH24PerformanceSysUpTime
         TimeTicks,
      pr1646v2PortSwMCOutQueuesH24PerformanceTotPkts
         Counter64,
      pr1646v2PortSwMCOutQueuesH24PerformanceDirTxPkts
         Counter64,
      pr1646v2PortSwMCOutQueuesH24PerformanceQdPkts
         Counter64,
      pr1646v2PortSwMCOutQueuesH24PerformanceDropPkts
         Counter64,
      pr1646v2PortSwMCOutQueuesH24PerformanceRDropPkts
         Counter64,
      pr1646v2PortSwMCOutQueuesH24PerformanceCirTxPkts
         Counter64,
      pr1646v2PortSwMCOutQueuesH24PerformanceEirTxPkts
         Counter64,
      pr1646v2PortSwMCOutQueuesH24PerformanceViolTxPkts
         Counter64,
      pr1646v2PortSwMCOutQueuesH24PerformanceTotOcts
         Counter64,
      pr1646v2PortSwMCOutQueuesH24PerformanceDirTxOcts
         Counter64,
      pr1646v2PortSwMCOutQueuesH24PerformanceQdOcts
         Counter64,
      pr1646v2PortSwMCOutQueuesH24PerformanceDropOcts
         Counter64,
      pr1646v2PortSwMCOutQueuesH24PerformanceRDropOcts
         Counter64,
      pr1646v2PortSwMCOutQueuesH24PerformanceCirTxOcts
         Counter64,
      pr1646v2PortSwMCOutQueuesH24PerformanceEirTxOcts
         Counter64,
      pr1646v2PortSwMCOutQueuesH24PerformanceViolTxOcts
         Counter64,
      pr1646v2PortSwMCOutQueuesH24PerformanceBandwidth
         Integer32
      }

pr1646v2PortSwMCOutQueuesH24PerformanceTableIx OBJECT-TYPE
   SYNTAX      TableIndex
   MAX-ACCESS  not-accessible
   STATUS      current
   DESCRIPTION
      ""
   ::= {pr1646v2PortSwMCOutQueuesH24PerformanceEntry 11}

pr1646v2PortSwMCOutQueuesH24PerformanceSysUpTime OBJECT-TYPE
   SYNTAX      TimeTicks
   MAX-ACCESS  read-only
   STATUS      current
   DESCRIPTION
      "Path: ethernet1.performance.ifOutPriorityQueues.h24Performance.sysUpTime

       Time in centi-second."
   ::= {pr1646v2PortSwMCOutQueuesH24PerformanceEntry 16777216}

pr1646v2PortSwMCOutQueuesH24PerformanceTotPkts OBJECT-TYPE
   SYNTAX      Counter64
   MAX-ACCESS  read-only
   STATUS      current
   DESCRIPTION
      "Path: ethernet1.performance.ifOutPriorityQueues.h24Performance.totalPkts

       64 bit unsigned wrappable counter."
   ::= {pr1646v2PortSwMCOutQueuesH24PerformanceEntry 234881024}

pr1646v2PortSwMCOutQueuesH24PerformanceDirTxPkts OBJECT-TYPE
   SYNTAX      Counter64
   MAX-ACCESS  read-only
   STATUS      current
   DESCRIPTION
      "Path: ethernet1.performance.ifOutPriorityQueues.h24Performance.directTxPkts

       64 bit unsigned wrappable counter."
   ::= {pr1646v2PortSwMCOutQueuesH24PerformanceEntry 33554432}

pr1646v2PortSwMCOutQueuesH24PerformanceQdPkts OBJECT-TYPE
   SYNTAX      Counter64
   MAX-ACCESS  read-only
   STATUS      current
   DESCRIPTION
      "Path: ethernet1.performance.ifOutPriorityQueues.h24Performance.queuedPkts

       64 bit unsigned wrappable counter."
   ::= {pr1646v2PortSwMCOutQueuesH24PerformanceEntry 50331648}

pr1646v2PortSwMCOutQueuesH24PerformanceDropPkts OBJECT-TYPE
   SYNTAX      Counter64
   MAX-ACCESS  read-only
   STATUS      current
   DESCRIPTION
      "Path: ethernet1.performance.ifOutPriorityQueues.h24Performance.droppedPkts

       64 bit unsigned wrappable counter."
   ::= {pr1646v2PortSwMCOutQueuesH24PerformanceEntry 67108864}

pr1646v2PortSwMCOutQueuesH24PerformanceRDropPkts OBJECT-TYPE
   SYNTAX      Counter64
   MAX-ACCESS  read-only
   STATUS      current
   DESCRIPTION
      "Path: ethernet1.performance.ifOutPriorityQueues.h24Performance.redDroppedPkts

       64 bit unsigned wrappable counter."
   ::= {pr1646v2PortSwMCOutQueuesH24PerformanceEntry 201326592}

pr1646v2PortSwMCOutQueuesH24PerformanceCirTxPkts OBJECT-TYPE
   SYNTAX      Counter64
   MAX-ACCESS  read-only
   STATUS      current
   DESCRIPTION
      "Path: ethernet1.performance.ifOutPriorityQueues.h24Performance.cirTxPkts

       64 bit unsigned wrappable counter."
   ::= {pr1646v2PortSwMCOutQueuesH24PerformanceEntry 83886080}

pr1646v2PortSwMCOutQueuesH24PerformanceEirTxPkts OBJECT-TYPE
   SYNTAX      Counter64
   MAX-ACCESS  read-only
   STATUS      current
   DESCRIPTION
      "Path: ethernet1.performance.ifOutPriorityQueues.h24Performance.eirTxPkts

       64 bit unsigned wrappable counter."
   ::= {pr1646v2PortSwMCOutQueuesH24PerformanceEntry 100663296}

pr1646v2PortSwMCOutQueuesH24PerformanceViolTxPkts OBJECT-TYPE
   SYNTAX      Counter64
   MAX-ACCESS  read-only
   STATUS      current
   DESCRIPTION
      "Path: ethernet1.performance.ifOutPriorityQueues.h24Performance.violateTxPkts

       64 bit unsigned wrappable counter."
   ::= {pr1646v2PortSwMCOutQueuesH24PerformanceEntry 301989888}

pr1646v2PortSwMCOutQueuesH24PerformanceTotOcts OBJECT-TYPE
   SYNTAX      Counter64
   MAX-ACCESS  read-only
   STATUS      current
   DESCRIPTION
      "Path: ethernet1.performance.ifOutPriorityQueues.h24Performance.totalOctets

       64 bit unsigned wrappable counter."
   ::= {pr1646v2PortSwMCOutQueuesH24PerformanceEntry 251658240}

pr1646v2PortSwMCOutQueuesH24PerformanceDirTxOcts OBJECT-TYPE
   SYNTAX      Counter64
   MAX-ACCESS  read-only
   STATUS      current
   DESCRIPTION
      "Path: ethernet1.performance.ifOutPriorityQueues.h24Performance.directTxOctets

       64 bit unsigned wrappable counter."
   ::= {pr1646v2PortSwMCOutQueuesH24PerformanceEntry 117440512}

pr1646v2PortSwMCOutQueuesH24PerformanceQdOcts OBJECT-TYPE
   SYNTAX      Counter64
   MAX-ACCESS  read-only
   STATUS      current
   DESCRIPTION
      "Path: ethernet1.performance.ifOutPriorityQueues.h24Performance.queuedOctets

       64 bit unsigned wrappable counter."
   ::= {pr1646v2PortSwMCOutQueuesH24PerformanceEntry 134217728}

pr1646v2PortSwMCOutQueuesH24PerformanceDropOcts OBJECT-TYPE
   SYNTAX      Counter64
   MAX-ACCESS  read-only
   STATUS      current
   DESCRIPTION
      "Path: ethernet1.performance.ifOutPriorityQueues.h24Performance.droppedOctets

       64 bit unsigned wrappable counter."
   ::= {pr1646v2PortSwMCOutQueuesH24PerformanceEntry 150994944}

pr1646v2PortSwMCOutQueuesH24PerformanceRDropOcts OBJECT-TYPE
   SYNTAX      Counter64
   MAX-ACCESS  read-only
   STATUS      current
   DESCRIPTION
      "Path: ethernet1.performance.ifOutPriorityQueues.h24Performance.redDroppedOctets

       64 bit unsigned wrappable counter."
   ::= {pr1646v2PortSwMCOutQueuesH24PerformanceEntry 218103808}

pr1646v2PortSwMCOutQueuesH24PerformanceCirTxOcts OBJECT-TYPE
   SYNTAX      Counter64
   MAX-ACCESS  read-only
   STATUS      current
   DESCRIPTION
      "Path: ethernet1.performance.ifOutPriorityQueues.h24Performance.cirTxOctets

       64 bit unsigned wrappable counter."
   ::= {pr1646v2PortSwMCOutQueuesH24PerformanceEntry 167772160}

pr1646v2PortSwMCOutQueuesH24PerformanceEirTxOcts OBJECT-TYPE
   SYNTAX      Counter64
   MAX-ACCESS  read-only
   STATUS      current
   DESCRIPTION
      "Path: ethernet1.performance.ifOutPriorityQueues.h24Performance.eirTxOctets

       64 bit unsigned wrappable counter."
   ::= {pr1646v2PortSwMCOutQueuesH24PerformanceEntry 184549376}

pr1646v2PortSwMCOutQueuesH24PerformanceViolTxOcts OBJECT-TYPE
   SYNTAX      Counter64
   MAX-ACCESS  read-only
   STATUS      current
   DESCRIPTION
      "Path: ethernet1.performance.ifOutPriorityQueues.h24Performance.violateTxOctets

       64 bit unsigned wrappable counter."
   ::= {pr1646v2PortSwMCOutQueuesH24PerformanceEntry 318767104}

pr1646v2PortSwMCOutQueuesH24PerformanceBandwidth OBJECT-TYPE
   SYNTAX      Integer32
   MAX-ACCESS  read-only
   STATUS      current
   DESCRIPTION
      "Path: ethernet1.performance.ifOutPriorityQueues.h24Performance.bandwidth

       unit name = bps
       formula = 8 * ; 8 /"
   ::= {pr1646v2PortSwMCOutQueuesH24PerformanceEntry 268435456}

pr1646v2PortSwMCOutQueuesD7Performance OBJECT-TYPE
   SYNTAX      SEQUENCE OF Pr1646v2PortSwMCOutQueuesD7PerformanceEntry
   MAX-ACCESS  not-accessible
   STATUS      current
   DESCRIPTION
      ""
   ::= {pr1646v2PortSwMCOutQueues 117440512}

pr1646v2PortSwMCOutQueuesD7PerformanceEntry OBJECT-TYPE
   SYNTAX      Pr1646v2PortSwMCOutQueuesD7PerformanceEntry
   MAX-ACCESS  not-accessible
   STATUS      current
   DESCRIPTION
      ""
   INDEX      { pr1646v2PortSwMCOutQueuesTableIx,
                pr1646v2PortSwMCOutQueuesD7PerformanceTableIx }
   ::= {pr1646v2PortSwMCOutQueuesD7Performance 1}

Pr1646v2PortSwMCOutQueuesD7PerformanceEntry ::=
   SEQUENCE
      {
      pr1646v2PortSwMCOutQueuesD7PerformanceTableIx
         TableIndex,
      pr1646v2PortSwMCOutQueuesD7PerformanceSysUpTime
         TimeTicks,
      pr1646v2PortSwMCOutQueuesD7PerformanceTotPkts
         Counter64,
      pr1646v2PortSwMCOutQueuesD7PerformanceDirTxPkts
         Counter64,
      pr1646v2PortSwMCOutQueuesD7PerformanceQdPkts
         Counter64,
      pr1646v2PortSwMCOutQueuesD7PerformanceDropPkts
         Counter64,
      pr1646v2PortSwMCOutQueuesD7PerformanceRDropPkts
         Counter64,
      pr1646v2PortSwMCOutQueuesD7PerformanceCirTxPkts
         Counter64,
      pr1646v2PortSwMCOutQueuesD7PerformanceEirTxPkts
         Counter64,
      pr1646v2PortSwMCOutQueuesD7PerformanceViolTxPkts
         Counter64,
      pr1646v2PortSwMCOutQueuesD7PerformanceTotOcts
         Counter64,
      pr1646v2PortSwMCOutQueuesD7PerformanceDirTxOcts
         Counter64,
      pr1646v2PortSwMCOutQueuesD7PerformanceQdOcts
         Counter64,
      pr1646v2PortSwMCOutQueuesD7PerformanceDropOcts
         Counter64,
      pr1646v2PortSwMCOutQueuesD7PerformanceRDropOcts
         Counter64,
      pr1646v2PortSwMCOutQueuesD7PerformanceCirTxOcts
         Counter64,
      pr1646v2PortSwMCOutQueuesD7PerformanceEirTxOcts
         Counter64,
      pr1646v2PortSwMCOutQueuesD7PerformanceViolTxOcts
         Counter64,
      pr1646v2PortSwMCOutQueuesD7PerformanceBandwidth
         Integer32
      }

pr1646v2PortSwMCOutQueuesD7PerformanceTableIx OBJECT-TYPE
   SYNTAX      TableIndex
   MAX-ACCESS  not-accessible
   STATUS      current
   DESCRIPTION
      ""
   ::= {pr1646v2PortSwMCOutQueuesD7PerformanceEntry 11}

pr1646v2PortSwMCOutQueuesD7PerformanceSysUpTime OBJECT-TYPE
   SYNTAX      TimeTicks
   MAX-ACCESS  read-only
   STATUS      current
   DESCRIPTION
      "Path: ethernet1.performance.ifOutPriorityQueues.d7Performance.sysUpTime

       Time in centi-second."
   ::= {pr1646v2PortSwMCOutQueuesD7PerformanceEntry 16777216}

pr1646v2PortSwMCOutQueuesD7PerformanceTotPkts OBJECT-TYPE
   SYNTAX      Counter64
   MAX-ACCESS  read-only
   STATUS      current
   DESCRIPTION
      "Path: ethernet1.performance.ifOutPriorityQueues.d7Performance.totalPkts

       64 bit unsigned wrappable counter."
   ::= {pr1646v2PortSwMCOutQueuesD7PerformanceEntry 234881024}

pr1646v2PortSwMCOutQueuesD7PerformanceDirTxPkts OBJECT-TYPE
   SYNTAX      Counter64
   MAX-ACCESS  read-only
   STATUS      current
   DESCRIPTION
      "Path: ethernet1.performance.ifOutPriorityQueues.d7Performance.directTxPkts

       64 bit unsigned wrappable counter."
   ::= {pr1646v2PortSwMCOutQueuesD7PerformanceEntry 33554432}

pr1646v2PortSwMCOutQueuesD7PerformanceQdPkts OBJECT-TYPE
   SYNTAX      Counter64
   MAX-ACCESS  read-only
   STATUS      current
   DESCRIPTION
      "Path: ethernet1.performance.ifOutPriorityQueues.d7Performance.queuedPkts

       64 bit unsigned wrappable counter."
   ::= {pr1646v2PortSwMCOutQueuesD7PerformanceEntry 50331648}

pr1646v2PortSwMCOutQueuesD7PerformanceDropPkts OBJECT-TYPE
   SYNTAX      Counter64
   MAX-ACCESS  read-only
   STATUS      current
   DESCRIPTION
      "Path: ethernet1.performance.ifOutPriorityQueues.d7Performance.droppedPkts

       64 bit unsigned wrappable counter."
   ::= {pr1646v2PortSwMCOutQueuesD7PerformanceEntry 67108864}

pr1646v2PortSwMCOutQueuesD7PerformanceRDropPkts OBJECT-TYPE
   SYNTAX      Counter64
   MAX-ACCESS  read-only
   STATUS      current
   DESCRIPTION
      "Path: ethernet1.performance.ifOutPriorityQueues.d7Performance.redDroppedPkts

       64 bit unsigned wrappable counter."
   ::= {pr1646v2PortSwMCOutQueuesD7PerformanceEntry 201326592}

pr1646v2PortSwMCOutQueuesD7PerformanceCirTxPkts OBJECT-TYPE
   SYNTAX      Counter64
   MAX-ACCESS  read-only
   STATUS      current
   DESCRIPTION
      "Path: ethernet1.performance.ifOutPriorityQueues.d7Performance.cirTxPkts

       64 bit unsigned wrappable counter."
   ::= {pr1646v2PortSwMCOutQueuesD7PerformanceEntry 83886080}

pr1646v2PortSwMCOutQueuesD7PerformanceEirTxPkts OBJECT-TYPE
   SYNTAX      Counter64
   MAX-ACCESS  read-only
   STATUS      current
   DESCRIPTION
      "Path: ethernet1.performance.ifOutPriorityQueues.d7Performance.eirTxPkts

       64 bit unsigned wrappable counter."
   ::= {pr1646v2PortSwMCOutQueuesD7PerformanceEntry 100663296}

pr1646v2PortSwMCOutQueuesD7PerformanceViolTxPkts OBJECT-TYPE
   SYNTAX      Counter64
   MAX-ACCESS  read-only
   STATUS      current
   DESCRIPTION
      "Path: ethernet1.performance.ifOutPriorityQueues.d7Performance.violateTxPkts

       64 bit unsigned wrappable counter."
   ::= {pr1646v2PortSwMCOutQueuesD7PerformanceEntry 301989888}

pr1646v2PortSwMCOutQueuesD7PerformanceTotOcts OBJECT-TYPE
   SYNTAX      Counter64
   MAX-ACCESS  read-only
   STATUS      current
   DESCRIPTION
      "Path: ethernet1.performance.ifOutPriorityQueues.d7Performance.totalOctets

       64 bit unsigned wrappable counter."
   ::= {pr1646v2PortSwMCOutQueuesD7PerformanceEntry 251658240}

pr1646v2PortSwMCOutQueuesD7PerformanceDirTxOcts OBJECT-TYPE
   SYNTAX      Counter64
   MAX-ACCESS  read-only
   STATUS      current
   DESCRIPTION
      "Path: ethernet1.performance.ifOutPriorityQueues.d7Performance.directTxOctets

       64 bit unsigned wrappable counter."
   ::= {pr1646v2PortSwMCOutQueuesD7PerformanceEntry 117440512}

pr1646v2PortSwMCOutQueuesD7PerformanceQdOcts OBJECT-TYPE
   SYNTAX      Counter64
   MAX-ACCESS  read-only
   STATUS      current
   DESCRIPTION
      "Path: ethernet1.performance.ifOutPriorityQueues.d7Performance.queuedOctets

       64 bit unsigned wrappable counter."
   ::= {pr1646v2PortSwMCOutQueuesD7PerformanceEntry 134217728}

pr1646v2PortSwMCOutQueuesD7PerformanceDropOcts OBJECT-TYPE
   SYNTAX      Counter64
   MAX-ACCESS  read-only
   STATUS      current
   DESCRIPTION
      "Path: ethernet1.performance.ifOutPriorityQueues.d7Performance.droppedOctets

       64 bit unsigned wrappable counter."
   ::= {pr1646v2PortSwMCOutQueuesD7PerformanceEntry 150994944}

pr1646v2PortSwMCOutQueuesD7PerformanceRDropOcts OBJECT-TYPE
   SYNTAX      Counter64
   MAX-ACCESS  read-only
   STATUS      current
   DESCRIPTION
      "Path: ethernet1.performance.ifOutPriorityQueues.d7Performance.redDroppedOctets

       64 bit unsigned wrappable counter."
   ::= {pr1646v2PortSwMCOutQueuesD7PerformanceEntry 218103808}

pr1646v2PortSwMCOutQueuesD7PerformanceCirTxOcts OBJECT-TYPE
   SYNTAX      Counter64
   MAX-ACCESS  read-only
   STATUS      current
   DESCRIPTION
      "Path: ethernet1.performance.ifOutPriorityQueues.d7Performance.cirTxOctets

       64 bit unsigned wrappable counter."
   ::= {pr1646v2PortSwMCOutQueuesD7PerformanceEntry 167772160}

pr1646v2PortSwMCOutQueuesD7PerformanceEirTxOcts OBJECT-TYPE
   SYNTAX      Counter64
   MAX-ACCESS  read-only
   STATUS      current
   DESCRIPTION
      "Path: ethernet1.performance.ifOutPriorityQueues.d7Performance.eirTxOctets

       64 bit unsigned wrappable counter."
   ::= {pr1646v2PortSwMCOutQueuesD7PerformanceEntry 184549376}

pr1646v2PortSwMCOutQueuesD7PerformanceViolTxOcts OBJECT-TYPE
   SYNTAX      Counter64
   MAX-ACCESS  read-only
   STATUS      current
   DESCRIPTION
      "Path: ethernet1.performance.ifOutPriorityQueues.d7Performance.violateTxOctets

       64 bit unsigned wrappable counter."
   ::= {pr1646v2PortSwMCOutQueuesD7PerformanceEntry 318767104}

pr1646v2PortSwMCOutQueuesD7PerformanceBandwidth OBJECT-TYPE
   SYNTAX      Integer32
   MAX-ACCESS  read-only
   STATUS      current
   DESCRIPTION
      "Path: ethernet1.performance.ifOutPriorityQueues.d7Performance.bandwidth

       unit name = bps
       formula = 8 * ; 8 /"
   ::= {pr1646v2PortSwMCOutQueuesD7PerformanceEntry 268435456}


pr1646v2PortSwMCOutBandwidth OBJECT IDENTIFIER ::= {pr1646v2PortSwMC 182}

pr1646v2PortSwMCOutBandwidthSSC OBJECT IDENTIFIER ::= {pr1646v2PortSwMCOutBandwidth 1}

pr1646v2PortSwMCOutBandwidthEntry OBJECT IDENTIFIER ::= {pr1646v2PortSwMCOutBandwidthSSC 1}

pr1646v2PortSwMCOutBandwidth15sec OBJECT-TYPE
   SYNTAX      Integer32
   MAX-ACCESS  read-only
   STATUS      current
   DESCRIPTION
      "Path: ethernet1.performance.ifOutBandwidth.15sec

       unit name = bps
       formula = 8 * ; 8 /"
   ::= {pr1646v2PortSwMCOutBandwidthEntry 83886080}

pr1646v2PortSwMCOutBandwidth30sec OBJECT-TYPE
   SYNTAX      Integer32
   MAX-ACCESS  read-only
   STATUS      current
   DESCRIPTION
      "Path: ethernet1.performance.ifOutBandwidth.30sec

       unit name = bps
       formula = 8 * ; 8 /"
   ::= {pr1646v2PortSwMCOutBandwidthEntry 167772160}

pr1646v2PortSwMCOutBandwidth1min OBJECT-TYPE
   SYNTAX      Integer32
   MAX-ACCESS  read-only
   STATUS      current
   DESCRIPTION
      "Path: ethernet1.performance.ifOutBandwidth.1min

       unit name = bps
       formula = 8 * ; 8 /"
   ::= {pr1646v2PortSwMCOutBandwidthEntry 335544320}

pr1646v2PortSwMCOutBandwidth2min OBJECT-TYPE
   SYNTAX      Integer32
   MAX-ACCESS  read-only
   STATUS      current
   DESCRIPTION
      "Path: ethernet1.performance.ifOutBandwidth.2min

       unit name = bps
       formula = 8 * ; 8 /"
   ::= {pr1646v2PortSwMCOutBandwidthEntry 671088640}

pr1646v2PortSwMCOutBandwidth5min OBJECT-TYPE
   SYNTAX      Integer32
   MAX-ACCESS  read-only
   STATUS      current
   DESCRIPTION
      "Path: ethernet1.performance.ifOutBandwidth.5min

       unit name = bps
       formula = 8 * ; 8 /"
   ::= {pr1646v2PortSwMCOutBandwidthEntry 1677721600}


pr1646v2PortSwMCInP OBJECT IDENTIFIER ::= {pr1646v2PortSwMC 307}

pr1646v2PortSwMCInPSSCTable OBJECT-TYPE
   SYNTAX      SEQUENCE OF Pr1646v2PortSwMCInPEntry
   MAX-ACCESS  not-accessible
   STATUS      current
   DESCRIPTION
      "h2IfInPerformance"
   ::= {pr1646v2PortSwMCInP 1}

pr1646v2PortSwMCInPEntry OBJECT-TYPE
   SYNTAX      Pr1646v2PortSwMCInPEntry
   MAX-ACCESS  not-accessible
   STATUS      current
   DESCRIPTION
      ""
   INDEX      { pr1646v2PortSwMCInPTableIx }
   ::= {pr1646v2PortSwMCInPSSCTable 1}

Pr1646v2PortSwMCInPEntry ::=
   SEQUENCE
      {
      pr1646v2PortSwMCInPTableIx
         TableIndex,
      pr1646v2PortSwMCInPSysUpTime
         TimeTicks,
      pr1646v2PortSwMCInPIfUpTime
         TimeTicks,
      pr1646v2PortSwMCInPIfStatChanges
         Counter32,
      pr1646v2PortSwMCInPIfInOctets
         Counter64,
      pr1646v2PortSwMCInPIfInUCPkts
         Counter64,
      pr1646v2PortSwMCInPIfInNUCPkts
         Counter64,
      pr1646v2PortSwMCInPIfInBCPkts
         Counter64,
      pr1646v2PortSwMCInPIfInMCPkts
         Counter64,
      pr1646v2PortSwMCInPIfInDiscards
         Counter64,
      pr1646v2PortSwMCInPIfInErrors
         Counter64,
      pr1646v2PortSwMCInPIfInUnkwn
         Counter64,
      pr1646v2PortSwMCInPInDropEx
         Counter64,
      pr1646v2PortSwMCInPInDropNoMac
         Counter64,
      pr1646v2PortSwMCInPInDropNUCast
         Counter64,
      pr1646v2PortSwMCInPInDropFilter
         Counter64,
      pr1646v2PortSwMCInPIfInBandwidth
         Integer32,
      pr1646v2PortSwMCInPIfOutOctets
         Counter64,
      pr1646v2PortSwMCInPIfOutUCPkts
         Counter64,
      pr1646v2PortSwMCInPIfOutNUCPkts
         Counter64,
      pr1646v2PortSwMCInPIfOutBCPkts
         Counter64,
      pr1646v2PortSwMCInPIfOutMCPkts
         Counter64,
      pr1646v2PortSwMCInPIfOutDiscards
         Counter64,
      pr1646v2PortSwMCInPIfOutErrors
         Counter64,
      pr1646v2PortSwMCInPOutDropEx
         Counter64,
      pr1646v2PortSwMCInPOutDropNoArp
         Counter64,
      pr1646v2PortSwMCInPOutDropFilter
         Counter64,
      pr1646v2PortSwMCInPIfOutBandwidth
         Integer32,
      pr1646v2PortSwMCInPIfErrSec
         Counter32
      }

pr1646v2PortSwMCInPTableIx OBJECT-TYPE
   SYNTAX      TableIndex
   MAX-ACCESS  not-accessible
   STATUS      current
   DESCRIPTION
      ""
   ::= {pr1646v2PortSwMCInPEntry 11}

pr1646v2PortSwMCInPSysUpTime OBJECT-TYPE
   SYNTAX      TimeTicks
   MAX-ACCESS  read-only
   STATUS      current
   DESCRIPTION
      "Path: ethernet1.performance.h2Performance.sysUpTime

       Time in centi-second."
   ::= {pr1646v2PortSwMCInPEntry 16777216}

pr1646v2PortSwMCInPIfUpTime OBJECT-TYPE
   SYNTAX      TimeTicks
   MAX-ACCESS  read-only
   STATUS      current
   DESCRIPTION
      "Path: ethernet1.performance.h2Performance.ifUpTime

       Time in centi-second."
   ::= {pr1646v2PortSwMCInPEntry 33554432}

pr1646v2PortSwMCInPIfStatChanges OBJECT-TYPE
   SYNTAX      Counter32
   MAX-ACCESS  read-only
   STATUS      current
   DESCRIPTION
      "Path: ethernet1.performance.h2Performance.ifStatusChanges

       32 bit unsigned wrappable counter."
   ::= {pr1646v2PortSwMCInPEntry 50331648}

pr1646v2PortSwMCInPIfInOctets OBJECT-TYPE
   SYNTAX      Counter64
   MAX-ACCESS  read-only
   STATUS      current
   DESCRIPTION
      "Path: ethernet1.performance.h2Performance.ifInOctets

       64 bit unsigned wrappable counter."
   ::= {pr1646v2PortSwMCInPEntry 67108864}

pr1646v2PortSwMCInPIfInUCPkts OBJECT-TYPE
   SYNTAX      Counter64
   MAX-ACCESS  read-only
   STATUS      current
   DESCRIPTION
      "Path: ethernet1.performance.h2Performance.ifInUcastPkts

       64 bit unsigned wrappable counter."
   ::= {pr1646v2PortSwMCInPEntry 83886080}

pr1646v2PortSwMCInPIfInNUCPkts OBJECT-TYPE
   SYNTAX      Counter64
   MAX-ACCESS  read-only
   STATUS      current
   DESCRIPTION
      "Path: ethernet1.performance.h2Performance.ifInNUcastPkts

       64 bit unsigned wrappable counter."
   ::= {pr1646v2PortSwMCInPEntry 100663296}

pr1646v2PortSwMCInPIfInBCPkts OBJECT-TYPE
   SYNTAX      Counter64
   MAX-ACCESS  read-only
   STATUS      current
   DESCRIPTION
      "Path: ethernet1.performance.h2Performance.ifInBcastPkts

       64 bit unsigned wrappable counter."
   ::= {pr1646v2PortSwMCInPEntry 419430400}

pr1646v2PortSwMCInPIfInMCPkts OBJECT-TYPE
   SYNTAX      Counter64
   MAX-ACCESS  read-only
   STATUS      current
   DESCRIPTION
      "Path: ethernet1.performance.h2Performance.ifInMcastPkts

       64 bit unsigned wrappable counter."
   ::= {pr1646v2PortSwMCInPEntry 436207616}

pr1646v2PortSwMCInPIfInDiscards OBJECT-TYPE
   SYNTAX      Counter64
   MAX-ACCESS  read-only
   STATUS      current
   DESCRIPTION
      "Path: ethernet1.performance.h2Performance.ifInDiscards

       64 bit unsigned wrappable counter."
   ::= {pr1646v2PortSwMCInPEntry 117440512}

pr1646v2PortSwMCInPIfInErrors OBJECT-TYPE
   SYNTAX      Counter64
   MAX-ACCESS  read-only
   STATUS      current
   DESCRIPTION
      "Path: ethernet1.performance.h2Performance.ifInErrors

       64 bit unsigned wrappable counter."
   ::= {pr1646v2PortSwMCInPEntry 134217728}

pr1646v2PortSwMCInPIfInUnkwn OBJECT-TYPE
   SYNTAX      Counter64
   MAX-ACCESS  read-only
   STATUS      current
   DESCRIPTION
      "Path: ethernet1.performance.h2Performance.ifInUnknownProtos

       64 bit unsigned wrappable counter."
   ::= {pr1646v2PortSwMCInPEntry 150994944}

pr1646v2PortSwMCInPInDropEx OBJECT-TYPE
   SYNTAX      Counter64
   MAX-ACCESS  read-only
   STATUS      current
   DESCRIPTION
      "Path: ethernet1.performance.h2Performance.ifInDropLevelExceeded

       64 bit unsigned wrappable counter."
   ::= {pr1646v2PortSwMCInPEntry 335544320}

pr1646v2PortSwMCInPInDropNoMac OBJECT-TYPE
   SYNTAX      Counter64
   MAX-ACCESS  read-only
   STATUS      current
   DESCRIPTION
      "Path: ethernet1.performance.h2Performance.fInDiscardsNoMacFit

       64 bit unsigned wrappable counter."
   ::= {pr1646v2PortSwMCInPEntry 301989888}

pr1646v2PortSwMCInPInDropNUCast OBJECT-TYPE
   SYNTAX      Counter64
   MAX-ACCESS  read-only
   STATUS      current
   DESCRIPTION
      "Path: ethernet1.performance.h2Performance.fInDiscardsNUCast

       64 bit unsigned wrappable counter."
   ::= {pr1646v2PortSwMCInPEntry 318767104}

pr1646v2PortSwMCInPInDropFilter OBJECT-TYPE
   SYNTAX      Counter64
   MAX-ACCESS  read-only
   STATUS      current
   DESCRIPTION
      "Path: ethernet1.performance.h2Performance.fInDiscardsFilter

       64 bit unsigned wrappable counter."
   ::= {pr1646v2PortSwMCInPEntry 385875968}

pr1646v2PortSwMCInPIfInBandwidth OBJECT-TYPE
   SYNTAX      Integer32
   MAX-ACCESS  read-only
   STATUS      current
   DESCRIPTION
      "Path: ethernet1.performance.h2Performance.ifInBandwidth

       unit name = bps
       formula = 8 * ; 8 /"
   ::= {pr1646v2PortSwMCInPEntry 268435456}

pr1646v2PortSwMCInPIfOutOctets OBJECT-TYPE
   SYNTAX      Counter64
   MAX-ACCESS  read-only
   STATUS      current
   DESCRIPTION
      "Path: ethernet1.performance.h2Performance.ifOutOctets

       64 bit unsigned wrappable counter."
   ::= {pr1646v2PortSwMCInPEntry 167772160}

pr1646v2PortSwMCInPIfOutUCPkts OBJECT-TYPE
   SYNTAX      Counter64
   MAX-ACCESS  read-only
   STATUS      current
   DESCRIPTION
      "Path: ethernet1.performance.h2Performance.ifOutUcastPkts

       64 bit unsigned wrappable counter."
   ::= {pr1646v2PortSwMCInPEntry 184549376}

pr1646v2PortSwMCInPIfOutNUCPkts OBJECT-TYPE
   SYNTAX      Counter64
   MAX-ACCESS  read-only
   STATUS      current
   DESCRIPTION
      "Path: ethernet1.performance.h2Performance.ifOutNUcastPkts

       64 bit unsigned wrappable counter."
   ::= {pr1646v2PortSwMCInPEntry 201326592}

pr1646v2PortSwMCInPIfOutBCPkts OBJECT-TYPE
   SYNTAX      Counter64
   MAX-ACCESS  read-only
   STATUS      current
   DESCRIPTION
      "Path: ethernet1.performance.h2Performance.ifOutBcastPkts

       64 bit unsigned wrappable counter."
   ::= {pr1646v2PortSwMCInPEntry 452984832}

pr1646v2PortSwMCInPIfOutMCPkts OBJECT-TYPE
   SYNTAX      Counter64
   MAX-ACCESS  read-only
   STATUS      current
   DESCRIPTION
      "Path: ethernet1.performance.h2Performance.ifOutMcastPkts

       64 bit unsigned wrappable counter."
   ::= {pr1646v2PortSwMCInPEntry 469762048}

pr1646v2PortSwMCInPIfOutDiscards OBJECT-TYPE
   SYNTAX      Counter64
   MAX-ACCESS  read-only
   STATUS      current
   DESCRIPTION
      "Path: ethernet1.performance.h2Performance.ifOutDiscards

       64 bit unsigned wrappable counter."
   ::= {pr1646v2PortSwMCInPEntry 218103808}

pr1646v2PortSwMCInPIfOutErrors OBJECT-TYPE
   SYNTAX      Counter64
   MAX-ACCESS  read-only
   STATUS      current
   DESCRIPTION
      "Path: ethernet1.performance.h2Performance.ifOutErrors

       64 bit unsigned wrappable counter."
   ::= {pr1646v2PortSwMCInPEntry 234881024}

pr1646v2PortSwMCInPOutDropEx OBJECT-TYPE
   SYNTAX      Counter64
   MAX-ACCESS  read-only
   STATUS      current
   DESCRIPTION
      "Path: ethernet1.performance.h2Performance.ifOutDropLevelExceeded

       64 bit unsigned wrappable counter."
   ::= {pr1646v2PortSwMCInPEntry 352321536}

pr1646v2PortSwMCInPOutDropNoArp OBJECT-TYPE
   SYNTAX      Counter64
   MAX-ACCESS  read-only
   STATUS      current
   DESCRIPTION
      "Path: ethernet1.performance.h2Performance.ifOutDiscardsNoArp

       64 bit unsigned wrappable counter."
   ::= {pr1646v2PortSwMCInPEntry 369098752}

pr1646v2PortSwMCInPOutDropFilter OBJECT-TYPE
   SYNTAX      Counter64
   MAX-ACCESS  read-only
   STATUS      current
   DESCRIPTION
      "Path: ethernet1.performance.h2Performance.ifOutDiscardsFilter

       64 bit unsigned wrappable counter."
   ::= {pr1646v2PortSwMCInPEntry 402653184}

pr1646v2PortSwMCInPIfOutBandwidth OBJECT-TYPE
   SYNTAX      Integer32
   MAX-ACCESS  read-only
   STATUS      current
   DESCRIPTION
      "Path: ethernet1.performance.h2Performance.ifOutBandwidth

       unit name = bps
       formula = 8 * ; 8 /"
   ::= {pr1646v2PortSwMCInPEntry 285212672}

pr1646v2PortSwMCInPIfErrSec OBJECT-TYPE
   SYNTAX      Counter32
   MAX-ACCESS  read-only
   STATUS      current
   DESCRIPTION
      "Path: ethernet1.performance.h2Performance.ifErrSec

       32 bit unsigned wrappable counter."
   ::= {pr1646v2PortSwMCInPEntry 251658240}


pr1646v2PortSwMCH24InP OBJECT IDENTIFIER ::= {pr1646v2PortSwMC 308}

pr1646v2PortSwMCH24InPSSCTable OBJECT-TYPE
   SYNTAX      SEQUENCE OF Pr1646v2PortSwMCH24InPEntry
   MAX-ACCESS  not-accessible
   STATUS      current
   DESCRIPTION
      "h24IfInPerformance"
   ::= {pr1646v2PortSwMCH24InP 1}

pr1646v2PortSwMCH24InPEntry OBJECT-TYPE
   SYNTAX      Pr1646v2PortSwMCH24InPEntry
   MAX-ACCESS  not-accessible
   STATUS      current
   DESCRIPTION
      ""
   INDEX      { pr1646v2PortSwMCH24InPTableIx }
   ::= {pr1646v2PortSwMCH24InPSSCTable 1}

Pr1646v2PortSwMCH24InPEntry ::=
   SEQUENCE
      {
      pr1646v2PortSwMCH24InPTableIx
         TableIndex,
      pr1646v2PortSwMCH24InPSysUpTime
         TimeTicks,
      pr1646v2PortSwMCH24InPIfUpTime
         TimeTicks,
      pr1646v2PortSwMCH24InPIfStatChanges
         Counter32,
      pr1646v2PortSwMCH24InPIfInOctets
         Counter64,
      pr1646v2PortSwMCH24InPIfInUCPkts
         Counter64,
      pr1646v2PortSwMCH24InPIfInNUCPkts
         Counter64,
      pr1646v2PortSwMCH24InPIfInBCPkts
         Counter64,
      pr1646v2PortSwMCH24InPIfInMCPkts
         Counter64,
      pr1646v2PortSwMCH24InPIfInDiscards
         Counter64,
      pr1646v2PortSwMCH24InPIfInErrors
         Counter64,
      pr1646v2PortSwMCH24InPIfInUnkwn
         Counter64,
      pr1646v2PortSwMCH24InPInDropEx
         Counter64,
      pr1646v2PortSwMCH24InPInDropNoMac
         Counter64,
      pr1646v2PortSwMCH24InPInDropNUCast
         Counter64,
      pr1646v2PortSwMCH24InPInDropFilter
         Counter64,
      pr1646v2PortSwMCH24InPIfInBandwidth
         Integer32,
      pr1646v2PortSwMCH24InPIfOutOctets
         Counter64,
      pr1646v2PortSwMCH24InPIfOutUCPkts
         Counter64,
      pr1646v2PortSwMCH24InPIfOutNUCPkts
         Counter64,
      pr1646v2PortSwMCH24InPIfOutBCPkts
         Counter64,
      pr1646v2PortSwMCH24InPIfOutMCPkts
         Counter64,
      pr1646v2PortSwMCH24InPIfOutDiscards
         Counter64,
      pr1646v2PortSwMCH24InPIfOutErrors
         Counter64,
      pr1646v2PortSwMCH24InPOutDropEx
         Counter64,
      pr1646v2PortSwMCH24InPOutDropNoArp
         Counter64,
      pr1646v2PortSwMCH24InPOutDropFilter
         Counter64,
      pr1646v2PortSwMCH24InPIfOutBandwidth
         Integer32,
      pr1646v2PortSwMCH24InPIfErrSec
         Counter32
      }

pr1646v2PortSwMCH24InPTableIx OBJECT-TYPE
   SYNTAX      TableIndex
   MAX-ACCESS  not-accessible
   STATUS      current
   DESCRIPTION
      ""
   ::= {pr1646v2PortSwMCH24InPEntry 11}

pr1646v2PortSwMCH24InPSysUpTime OBJECT-TYPE
   SYNTAX      TimeTicks
   MAX-ACCESS  read-only
   STATUS      current
   DESCRIPTION
      "Path: ethernet1.performance.h24Performance.sysUpTime

       Time in centi-second."
   ::= {pr1646v2PortSwMCH24InPEntry 16777216}

pr1646v2PortSwMCH24InPIfUpTime OBJECT-TYPE
   SYNTAX      TimeTicks
   MAX-ACCESS  read-only
   STATUS      current
   DESCRIPTION
      "Path: ethernet1.performance.h24Performance.ifUpTime

       Time in centi-second."
   ::= {pr1646v2PortSwMCH24InPEntry 33554432}

pr1646v2PortSwMCH24InPIfStatChanges OBJECT-TYPE
   SYNTAX      Counter32
   MAX-ACCESS  read-only
   STATUS      current
   DESCRIPTION
      "Path: ethernet1.performance.h24Performance.ifStatusChanges

       32 bit unsigned wrappable counter."
   ::= {pr1646v2PortSwMCH24InPEntry 50331648}

pr1646v2PortSwMCH24InPIfInOctets OBJECT-TYPE
   SYNTAX      Counter64
   MAX-ACCESS  read-only
   STATUS      current
   DESCRIPTION
      "Path: ethernet1.performance.h24Performance.ifInOctets

       64 bit unsigned wrappable counter."
   ::= {pr1646v2PortSwMCH24InPEntry 67108864}

pr1646v2PortSwMCH24InPIfInUCPkts OBJECT-TYPE
   SYNTAX      Counter64
   MAX-ACCESS  read-only
   STATUS      current
   DESCRIPTION
      "Path: ethernet1.performance.h24Performance.ifInUcastPkts

       64 bit unsigned wrappable counter."
   ::= {pr1646v2PortSwMCH24InPEntry 83886080}

pr1646v2PortSwMCH24InPIfInNUCPkts OBJECT-TYPE
   SYNTAX      Counter64
   MAX-ACCESS  read-only
   STATUS      current
   DESCRIPTION
      "Path: ethernet1.performance.h24Performance.ifInNUcastPkts

       64 bit unsigned wrappable counter."
   ::= {pr1646v2PortSwMCH24InPEntry 100663296}

pr1646v2PortSwMCH24InPIfInBCPkts OBJECT-TYPE
   SYNTAX      Counter64
   MAX-ACCESS  read-only
   STATUS      current
   DESCRIPTION
      "Path: ethernet1.performance.h24Performance.ifInBcastPkts

       64 bit unsigned wrappable counter."
   ::= {pr1646v2PortSwMCH24InPEntry 419430400}

pr1646v2PortSwMCH24InPIfInMCPkts OBJECT-TYPE
   SYNTAX      Counter64
   MAX-ACCESS  read-only
   STATUS      current
   DESCRIPTION
      "Path: ethernet1.performance.h24Performance.ifInMcastPkts

       64 bit unsigned wrappable counter."
   ::= {pr1646v2PortSwMCH24InPEntry 436207616}

pr1646v2PortSwMCH24InPIfInDiscards OBJECT-TYPE
   SYNTAX      Counter64
   MAX-ACCESS  read-only
   STATUS      current
   DESCRIPTION
      "Path: ethernet1.performance.h24Performance.ifInDiscards

       64 bit unsigned wrappable counter."
   ::= {pr1646v2PortSwMCH24InPEntry 117440512}

pr1646v2PortSwMCH24InPIfInErrors OBJECT-TYPE
   SYNTAX      Counter64
   MAX-ACCESS  read-only
   STATUS      current
   DESCRIPTION
      "Path: ethernet1.performance.h24Performance.ifInErrors

       64 bit unsigned wrappable counter."
   ::= {pr1646v2PortSwMCH24InPEntry 134217728}

pr1646v2PortSwMCH24InPIfInUnkwn OBJECT-TYPE
   SYNTAX      Counter64
   MAX-ACCESS  read-only
   STATUS      current
   DESCRIPTION
      "Path: ethernet1.performance.h24Performance.ifInUnknownProtos

       64 bit unsigned wrappable counter."
   ::= {pr1646v2PortSwMCH24InPEntry 150994944}

pr1646v2PortSwMCH24InPInDropEx OBJECT-TYPE
   SYNTAX      Counter64
   MAX-ACCESS  read-only
   STATUS      current
   DESCRIPTION
      "Path: ethernet1.performance.h24Performance.ifInDropLevelExceeded

       64 bit unsigned wrappable counter."
   ::= {pr1646v2PortSwMCH24InPEntry 335544320}

pr1646v2PortSwMCH24InPInDropNoMac OBJECT-TYPE
   SYNTAX      Counter64
   MAX-ACCESS  read-only
   STATUS      current
   DESCRIPTION
      "Path: ethernet1.performance.h24Performance.fInDiscardsNoMacFit

       64 bit unsigned wrappable counter."
   ::= {pr1646v2PortSwMCH24InPEntry 301989888}

pr1646v2PortSwMCH24InPInDropNUCast OBJECT-TYPE
   SYNTAX      Counter64
   MAX-ACCESS  read-only
   STATUS      current
   DESCRIPTION
      "Path: ethernet1.performance.h24Performance.fInDiscardsNUCast

       64 bit unsigned wrappable counter."
   ::= {pr1646v2PortSwMCH24InPEntry 318767104}

pr1646v2PortSwMCH24InPInDropFilter OBJECT-TYPE
   SYNTAX      Counter64
   MAX-ACCESS  read-only
   STATUS      current
   DESCRIPTION
      "Path: ethernet1.performance.h24Performance.fInDiscardsFilter

       64 bit unsigned wrappable counter."
   ::= {pr1646v2PortSwMCH24InPEntry 385875968}

pr1646v2PortSwMCH24InPIfInBandwidth OBJECT-TYPE
   SYNTAX      Integer32
   MAX-ACCESS  read-only
   STATUS      current
   DESCRIPTION
      "Path: ethernet1.performance.h24Performance.ifInBandwidth

       unit name = bps
       formula = 8 * ; 8 /"
   ::= {pr1646v2PortSwMCH24InPEntry 268435456}

pr1646v2PortSwMCH24InPIfOutOctets OBJECT-TYPE
   SYNTAX      Counter64
   MAX-ACCESS  read-only
   STATUS      current
   DESCRIPTION
      "Path: ethernet1.performance.h24Performance.ifOutOctets

       64 bit unsigned wrappable counter."
   ::= {pr1646v2PortSwMCH24InPEntry 167772160}

pr1646v2PortSwMCH24InPIfOutUCPkts OBJECT-TYPE
   SYNTAX      Counter64
   MAX-ACCESS  read-only
   STATUS      current
   DESCRIPTION
      "Path: ethernet1.performance.h24Performance.ifOutUcastPkts

       64 bit unsigned wrappable counter."
   ::= {pr1646v2PortSwMCH24InPEntry 184549376}

pr1646v2PortSwMCH24InPIfOutNUCPkts OBJECT-TYPE
   SYNTAX      Counter64
   MAX-ACCESS  read-only
   STATUS      current
   DESCRIPTION
      "Path: ethernet1.performance.h24Performance.ifOutNUcastPkts

       64 bit unsigned wrappable counter."
   ::= {pr1646v2PortSwMCH24InPEntry 201326592}

pr1646v2PortSwMCH24InPIfOutBCPkts OBJECT-TYPE
   SYNTAX      Counter64
   MAX-ACCESS  read-only
   STATUS      current
   DESCRIPTION
      "Path: ethernet1.performance.h24Performance.ifOutBcastPkts

       64 bit unsigned wrappable counter."
   ::= {pr1646v2PortSwMCH24InPEntry 452984832}

pr1646v2PortSwMCH24InPIfOutMCPkts OBJECT-TYPE
   SYNTAX      Counter64
   MAX-ACCESS  read-only
   STATUS      current
   DESCRIPTION
      "Path: ethernet1.performance.h24Performance.ifOutMcastPkts

       64 bit unsigned wrappable counter."
   ::= {pr1646v2PortSwMCH24InPEntry 469762048}

pr1646v2PortSwMCH24InPIfOutDiscards OBJECT-TYPE
   SYNTAX      Counter64
   MAX-ACCESS  read-only
   STATUS      current
   DESCRIPTION
      "Path: ethernet1.performance.h24Performance.ifOutDiscards

       64 bit unsigned wrappable counter."
   ::= {pr1646v2PortSwMCH24InPEntry 218103808}

pr1646v2PortSwMCH24InPIfOutErrors OBJECT-TYPE
   SYNTAX      Counter64
   MAX-ACCESS  read-only
   STATUS      current
   DESCRIPTION
      "Path: ethernet1.performance.h24Performance.ifOutErrors

       64 bit unsigned wrappable counter."
   ::= {pr1646v2PortSwMCH24InPEntry 234881024}

pr1646v2PortSwMCH24InPOutDropEx OBJECT-TYPE
   SYNTAX      Counter64
   MAX-ACCESS  read-only
   STATUS      current
   DESCRIPTION
      "Path: ethernet1.performance.h24Performance.ifOutDropLevelExceeded

       64 bit unsigned wrappable counter."
   ::= {pr1646v2PortSwMCH24InPEntry 352321536}

pr1646v2PortSwMCH24InPOutDropNoArp OBJECT-TYPE
   SYNTAX      Counter64
   MAX-ACCESS  read-only
   STATUS      current
   DESCRIPTION
      "Path: ethernet1.performance.h24Performance.ifOutDiscardsNoArp

       64 bit unsigned wrappable counter."
   ::= {pr1646v2PortSwMCH24InPEntry 369098752}

pr1646v2PortSwMCH24InPOutDropFilter OBJECT-TYPE
   SYNTAX      Counter64
   MAX-ACCESS  read-only
   STATUS      current
   DESCRIPTION
      "Path: ethernet1.performance.h24Performance.ifOutDiscardsFilter

       64 bit unsigned wrappable counter."
   ::= {pr1646v2PortSwMCH24InPEntry 402653184}

pr1646v2PortSwMCH24InPIfOutBandwidth OBJECT-TYPE
   SYNTAX      Integer32
   MAX-ACCESS  read-only
   STATUS      current
   DESCRIPTION
      "Path: ethernet1.performance.h24Performance.ifOutBandwidth

       unit name = bps
       formula = 8 * ; 8 /"
   ::= {pr1646v2PortSwMCH24InPEntry 285212672}

pr1646v2PortSwMCH24InPIfErrSec OBJECT-TYPE
   SYNTAX      Counter32
   MAX-ACCESS  read-only
   STATUS      current
   DESCRIPTION
      "Path: ethernet1.performance.h24Performance.ifErrSec

       32 bit unsigned wrappable counter."
   ::= {pr1646v2PortSwMCH24InPEntry 251658240}


pr1646v2PortSwMCD7InP OBJECT IDENTIFIER ::= {pr1646v2PortSwMC 309}

pr1646v2PortSwMCD7InPSSCTable OBJECT-TYPE
   SYNTAX      SEQUENCE OF Pr1646v2PortSwMCD7InPEntry
   MAX-ACCESS  not-accessible
   STATUS      current
   DESCRIPTION
      "d7IfInPerformance"
   ::= {pr1646v2PortSwMCD7InP 1}

pr1646v2PortSwMCD7InPEntry OBJECT-TYPE
   SYNTAX      Pr1646v2PortSwMCD7InPEntry
   MAX-ACCESS  not-accessible
   STATUS      current
   DESCRIPTION
      ""
   INDEX      { pr1646v2PortSwMCD7InPTableIx }
   ::= {pr1646v2PortSwMCD7InPSSCTable 1}

Pr1646v2PortSwMCD7InPEntry ::=
   SEQUENCE
      {
      pr1646v2PortSwMCD7InPTableIx
         TableIndex,
      pr1646v2PortSwMCD7InPSysUpTime
         TimeTicks,
      pr1646v2PortSwMCD7InPIfUpTime
         TimeTicks,
      pr1646v2PortSwMCD7InPIfStatChanges
         Counter32,
      pr1646v2PortSwMCD7InPIfInOctets
         Counter64,
      pr1646v2PortSwMCD7InPIfInUCPkts
         Counter64,
      pr1646v2PortSwMCD7InPIfInNUCPkts
         Counter64,
      pr1646v2PortSwMCD7InPIfInBCPkts
         Counter64,
      pr1646v2PortSwMCD7InPIfInMCPkts
         Counter64,
      pr1646v2PortSwMCD7InPIfInDiscards
         Counter64,
      pr1646v2PortSwMCD7InPIfInErrors
         Counter64,
      pr1646v2PortSwMCD7InPIfInUnkwn
         Counter64,
      pr1646v2PortSwMCD7InPInDropEx
         Counter64,
      pr1646v2PortSwMCD7InPInDropNoMac
         Counter64,
      pr1646v2PortSwMCD7InPInDropNUCast
         Counter64,
      pr1646v2PortSwMCD7InPInDropFilter
         Counter64,
      pr1646v2PortSwMCD7InPIfInBandwidth
         Integer32,
      pr1646v2PortSwMCD7InPIfOutOctets
         Counter64,
      pr1646v2PortSwMCD7InPIfOutUCPkts
         Counter64,
      pr1646v2PortSwMCD7InPIfOutNUCPkts
         Counter64,
      pr1646v2PortSwMCD7InPIfOutBCPkts
         Counter64,
      pr1646v2PortSwMCD7InPIfOutMCPkts
         Counter64,
      pr1646v2PortSwMCD7InPIfOutDiscards
         Counter64,
      pr1646v2PortSwMCD7InPIfOutErrors
         Counter64,
      pr1646v2PortSwMCD7InPOutDropEx
         Counter64,
      pr1646v2PortSwMCD7InPOutDropNoArp
         Counter64,
      pr1646v2PortSwMCD7InPOutDropFilter
         Counter64,
      pr1646v2PortSwMCD7InPIfOutBandwidth
         Integer32,
      pr1646v2PortSwMCD7InPIfErrSec
         Counter32
      }

pr1646v2PortSwMCD7InPTableIx OBJECT-TYPE
   SYNTAX      TableIndex
   MAX-ACCESS  not-accessible
   STATUS      current
   DESCRIPTION
      ""
   ::= {pr1646v2PortSwMCD7InPEntry 11}

pr1646v2PortSwMCD7InPSysUpTime OBJECT-TYPE
   SYNTAX      TimeTicks
   MAX-ACCESS  read-only
   STATUS      current
   DESCRIPTION
      "Path: ethernet1.performance.d7Performance.sysUpTime

       Time in centi-second."
   ::= {pr1646v2PortSwMCD7InPEntry 16777216}

pr1646v2PortSwMCD7InPIfUpTime OBJECT-TYPE
   SYNTAX      TimeTicks
   MAX-ACCESS  read-only
   STATUS      current
   DESCRIPTION
      "Path: ethernet1.performance.d7Performance.ifUpTime

       Time in centi-second."
   ::= {pr1646v2PortSwMCD7InPEntry 33554432}

pr1646v2PortSwMCD7InPIfStatChanges OBJECT-TYPE
   SYNTAX      Counter32
   MAX-ACCESS  read-only
   STATUS      current
   DESCRIPTION
      "Path: ethernet1.performance.d7Performance.ifStatusChanges

       32 bit unsigned wrappable counter."
   ::= {pr1646v2PortSwMCD7InPEntry 50331648}

pr1646v2PortSwMCD7InPIfInOctets OBJECT-TYPE
   SYNTAX      Counter64
   MAX-ACCESS  read-only
   STATUS      current
   DESCRIPTION
      "Path: ethernet1.performance.d7Performance.ifInOctets

       64 bit unsigned wrappable counter."
   ::= {pr1646v2PortSwMCD7InPEntry 67108864}

pr1646v2PortSwMCD7InPIfInUCPkts OBJECT-TYPE
   SYNTAX      Counter64
   MAX-ACCESS  read-only
   STATUS      current
   DESCRIPTION
      "Path: ethernet1.performance.d7Performance.ifInUcastPkts

       64 bit unsigned wrappable counter."
   ::= {pr1646v2PortSwMCD7InPEntry 83886080}

pr1646v2PortSwMCD7InPIfInNUCPkts OBJECT-TYPE
   SYNTAX      Counter64
   MAX-ACCESS  read-only
   STATUS      current
   DESCRIPTION
      "Path: ethernet1.performance.d7Performance.ifInNUcastPkts

       64 bit unsigned wrappable counter."
   ::= {pr1646v2PortSwMCD7InPEntry 100663296}

pr1646v2PortSwMCD7InPIfInBCPkts OBJECT-TYPE
   SYNTAX      Counter64
   MAX-ACCESS  read-only
   STATUS      current
   DESCRIPTION
      "Path: ethernet1.performance.d7Performance.ifInBcastPkts

       64 bit unsigned wrappable counter."
   ::= {pr1646v2PortSwMCD7InPEntry 419430400}

pr1646v2PortSwMCD7InPIfInMCPkts OBJECT-TYPE
   SYNTAX      Counter64
   MAX-ACCESS  read-only
   STATUS      current
   DESCRIPTION
      "Path: ethernet1.performance.d7Performance.ifInMcastPkts

       64 bit unsigned wrappable counter."
   ::= {pr1646v2PortSwMCD7InPEntry 436207616}

pr1646v2PortSwMCD7InPIfInDiscards OBJECT-TYPE
   SYNTAX      Counter64
   MAX-ACCESS  read-only
   STATUS      current
   DESCRIPTION
      "Path: ethernet1.performance.d7Performance.ifInDiscards

       64 bit unsigned wrappable counter."
   ::= {pr1646v2PortSwMCD7InPEntry 117440512}

pr1646v2PortSwMCD7InPIfInErrors OBJECT-TYPE
   SYNTAX      Counter64
   MAX-ACCESS  read-only
   STATUS      current
   DESCRIPTION
      "Path: ethernet1.performance.d7Performance.ifInErrors

       64 bit unsigned wrappable counter."
   ::= {pr1646v2PortSwMCD7InPEntry 134217728}

pr1646v2PortSwMCD7InPIfInUnkwn OBJECT-TYPE
   SYNTAX      Counter64
   MAX-ACCESS  read-only
   STATUS      current
   DESCRIPTION
      "Path: ethernet1.performance.d7Performance.ifInUnknownProtos

       64 bit unsigned wrappable counter."
   ::= {pr1646v2PortSwMCD7InPEntry 150994944}

pr1646v2PortSwMCD7InPInDropEx OBJECT-TYPE
   SYNTAX      Counter64
   MAX-ACCESS  read-only
   STATUS      current
   DESCRIPTION
      "Path: ethernet1.performance.d7Performance.ifInDropLevelExceeded

       64 bit unsigned wrappable counter."
   ::= {pr1646v2PortSwMCD7InPEntry 335544320}

pr1646v2PortSwMCD7InPInDropNoMac OBJECT-TYPE
   SYNTAX      Counter64
   MAX-ACCESS  read-only
   STATUS      current
   DESCRIPTION
      "Path: ethernet1.performance.d7Performance.fInDiscardsNoMacFit

       64 bit unsigned wrappable counter."
   ::= {pr1646v2PortSwMCD7InPEntry 301989888}

pr1646v2PortSwMCD7InPInDropNUCast OBJECT-TYPE
   SYNTAX      Counter64
   MAX-ACCESS  read-only
   STATUS      current
   DESCRIPTION
      "Path: ethernet1.performance.d7Performance.fInDiscardsNUCast

       64 bit unsigned wrappable counter."
   ::= {pr1646v2PortSwMCD7InPEntry 318767104}

pr1646v2PortSwMCD7InPInDropFilter OBJECT-TYPE
   SYNTAX      Counter64
   MAX-ACCESS  read-only
   STATUS      current
   DESCRIPTION
      "Path: ethernet1.performance.d7Performance.fInDiscardsFilter

       64 bit unsigned wrappable counter."
   ::= {pr1646v2PortSwMCD7InPEntry 385875968}

pr1646v2PortSwMCD7InPIfInBandwidth OBJECT-TYPE
   SYNTAX      Integer32
   MAX-ACCESS  read-only
   STATUS      current
   DESCRIPTION
      "Path: ethernet1.performance.d7Performance.ifInBandwidth

       unit name = bps
       formula = 8 * ; 8 /"
   ::= {pr1646v2PortSwMCD7InPEntry 268435456}

pr1646v2PortSwMCD7InPIfOutOctets OBJECT-TYPE
   SYNTAX      Counter64
   MAX-ACCESS  read-only
   STATUS      current
   DESCRIPTION
      "Path: ethernet1.performance.d7Performance.ifOutOctets

       64 bit unsigned wrappable counter."
   ::= {pr1646v2PortSwMCD7InPEntry 167772160}

pr1646v2PortSwMCD7InPIfOutUCPkts OBJECT-TYPE
   SYNTAX      Counter64
   MAX-ACCESS  read-only
   STATUS      current
   DESCRIPTION
      "Path: ethernet1.performance.d7Performance.ifOutUcastPkts

       64 bit unsigned wrappable counter."
   ::= {pr1646v2PortSwMCD7InPEntry 184549376}

pr1646v2PortSwMCD7InPIfOutNUCPkts OBJECT-TYPE
   SYNTAX      Counter64
   MAX-ACCESS  read-only
   STATUS      current
   DESCRIPTION
      "Path: ethernet1.performance.d7Performance.ifOutNUcastPkts

       64 bit unsigned wrappable counter."
   ::= {pr1646v2PortSwMCD7InPEntry 201326592}

pr1646v2PortSwMCD7InPIfOutBCPkts OBJECT-TYPE
   SYNTAX      Counter64
   MAX-ACCESS  read-only
   STATUS      current
   DESCRIPTION
      "Path: ethernet1.performance.d7Performance.ifOutBcastPkts

       64 bit unsigned wrappable counter."
   ::= {pr1646v2PortSwMCD7InPEntry 452984832}

pr1646v2PortSwMCD7InPIfOutMCPkts OBJECT-TYPE
   SYNTAX      Counter64
   MAX-ACCESS  read-only
   STATUS      current
   DESCRIPTION
      "Path: ethernet1.performance.d7Performance.ifOutMcastPkts

       64 bit unsigned wrappable counter."
   ::= {pr1646v2PortSwMCD7InPEntry 469762048}

pr1646v2PortSwMCD7InPIfOutDiscards OBJECT-TYPE
   SYNTAX      Counter64
   MAX-ACCESS  read-only
   STATUS      current
   DESCRIPTION
      "Path: ethernet1.performance.d7Performance.ifOutDiscards

       64 bit unsigned wrappable counter."
   ::= {pr1646v2PortSwMCD7InPEntry 218103808}

pr1646v2PortSwMCD7InPIfOutErrors OBJECT-TYPE
   SYNTAX      Counter64
   MAX-ACCESS  read-only
   STATUS      current
   DESCRIPTION
      "Path: ethernet1.performance.d7Performance.ifOutErrors

       64 bit unsigned wrappable counter."
   ::= {pr1646v2PortSwMCD7InPEntry 234881024}

pr1646v2PortSwMCD7InPOutDropEx OBJECT-TYPE
   SYNTAX      Counter64
   MAX-ACCESS  read-only
   STATUS      current
   DESCRIPTION
      "Path: ethernet1.performance.d7Performance.ifOutDropLevelExceeded

       64 bit unsigned wrappable counter."
   ::= {pr1646v2PortSwMCD7InPEntry 352321536}

pr1646v2PortSwMCD7InPOutDropNoArp OBJECT-TYPE
   SYNTAX      Counter64
   MAX-ACCESS  read-only
   STATUS      current
   DESCRIPTION
      "Path: ethernet1.performance.d7Performance.ifOutDiscardsNoArp

       64 bit unsigned wrappable counter."
   ::= {pr1646v2PortSwMCD7InPEntry 369098752}

pr1646v2PortSwMCD7InPOutDropFilter OBJECT-TYPE
   SYNTAX      Counter64
   MAX-ACCESS  read-only
   STATUS      current
   DESCRIPTION
      "Path: ethernet1.performance.d7Performance.ifOutDiscardsFilter

       64 bit unsigned wrappable counter."
   ::= {pr1646v2PortSwMCD7InPEntry 402653184}

pr1646v2PortSwMCD7InPIfOutBandwidth OBJECT-TYPE
   SYNTAX      Integer32
   MAX-ACCESS  read-only
   STATUS      current
   DESCRIPTION
      "Path: ethernet1.performance.d7Performance.ifOutBandwidth

       unit name = bps
       formula = 8 * ; 8 /"
   ::= {pr1646v2PortSwMCD7InPEntry 285212672}

pr1646v2PortSwMCD7InPIfErrSec OBJECT-TYPE
   SYNTAX      Counter32
   MAX-ACCESS  read-only
   STATUS      current
   DESCRIPTION
      "Path: ethernet1.performance.d7Performance.ifErrSec

       32 bit unsigned wrappable counter."
   ::= {pr1646v2PortSwMCD7InPEntry 251658240}


pr1646v2PortSwMCIfInPriorityQueues OBJECT IDENTIFIER ::= {pr1646v2PortSwMC 131}

pr1646v2PortSwMCIfInPriorityQueuesSSCTable OBJECT-TYPE
   SYNTAX      SEQUENCE OF Pr1646v2PortSwMCIfInPriorityQueuesEntry
   MAX-ACCESS  not-accessible
   STATUS      current
   DESCRIPTION
      "Queue Lengths"
   ::= {pr1646v2PortSwMCIfInPriorityQueues 1}

pr1646v2PortSwMCIfInPriorityQueuesEntry OBJECT-TYPE
   SYNTAX      Pr1646v2PortSwMCIfInPriorityQueuesEntry
   MAX-ACCESS  not-accessible
   STATUS      current
   DESCRIPTION
      ""
   INDEX      { pr1646v2PortSwMCIfInPriorityQueuesTableIx }
   ::= {pr1646v2PortSwMCIfInPriorityQueuesSSCTable 1}

Pr1646v2PortSwMCIfInPriorityQueuesEntry ::=
   SEQUENCE
      {
      pr1646v2PortSwMCIfInPriorityQueuesTableIx
         TableIndex,
      pr1646v2PortSwMCIfInPriorityQueuesName
         INTEGER,
      pr1646v2PortSwMCIfInPriorityQueuesLength
         Integer32,
      pr1646v2PortSwMCIfInPriorityQueuesOctetLength
         Integer32,
      pr1646v2PortSwMCIfInPriorityQueuesRedLength
         Integer32,
      pr1646v2PortSwMCIfInPriorityQueuesPacketsTotal
         Counter64,
      pr1646v2PortSwMCIfInPriorityQueuesPacketsDirectTx
         Counter64,
      pr1646v2PortSwMCIfInPriorityQueuesPacketsQueued
         Counter64,
      pr1646v2PortSwMCIfInPriorityQueuesPacketsDropped
         Counter64,
      pr1646v2PortSwMCIfInPriorityQueuesPacketsRedDropped
         Counter64,
      pr1646v2PortSwMCIfInPriorityQueuesPacketsCirTx
         Counter64,
      pr1646v2PortSwMCIfInPriorityQueuesPacketsEirTx
         Counter64,
      pr1646v2PortSwMCIfInPriorityQueuesPacketsViolateTx
         Counter64,
      pr1646v2PortSwMCIfInPriorityQueuesOctetsTotal
         Counter64,
      pr1646v2PortSwMCIfInPriorityQueuesOctetsDirectTx
         Counter64,
      pr1646v2PortSwMCIfInPriorityQueuesOctetsQueued
         Counter64,
      pr1646v2PortSwMCIfInPriorityQueuesOctetsDropped
         Counter64,
      pr1646v2PortSwMCIfInPriorityQueuesOctetsRedDropped
         Counter64,
      pr1646v2PortSwMCIfInPriorityQueuesOctetsCirTx
         Counter64,
      pr1646v2PortSwMCIfInPriorityQueuesOctetsEirTx
         Counter64,
      pr1646v2PortSwMCIfInPriorityQueuesOctetsViolateTx
         Counter64,
      pr1646v2PortSwMCIfInPriorityQueuesOctetsBandwidth15sec
         Integer32,
      pr1646v2PortSwMCIfInPriorityQueuesOctetsBandwidth30sec
         Integer32,
      pr1646v2PortSwMCIfInPriorityQueuesOctetsBandwidth1min
         Integer32,
      pr1646v2PortSwMCIfInPriorityQueuesOctetsBandwidth2min
         Integer32,
      pr1646v2PortSwMCIfInPriorityQueuesOctetsBandwidth5min
         Integer32
      }

pr1646v2PortSwMCIfInPriorityQueuesTableIx OBJECT-TYPE
   SYNTAX      TableIndex
   MAX-ACCESS  not-accessible
   STATUS      current
   DESCRIPTION
      ""
   ::= {pr1646v2PortSwMCIfInPriorityQueuesEntry 11}

pr1646v2PortSwMCIfInPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2PortSwMCIfInPriorityQueuesEntry 16777216}

pr1646v2PortSwMCIfInPriorityQueuesLength OBJECT-TYPE
   SYNTAX      Integer32
   MAX-ACCESS  read-only
   STATUS      current
   DESCRIPTION
      "Path: ethernet1.performance.ifInPriorityQueues.length"
   ::= {pr1646v2PortSwMCIfInPriorityQueuesEntry 33554432}

pr1646v2PortSwMCIfInPriorityQueuesOctetLength OBJECT-TYPE
   SYNTAX      Integer32
   MAX-ACCESS  read-only
   STATUS      current
   DESCRIPTION
      "Path: ethernet1.performance.ifInPriorityQueues.octetLength"
   ::= {pr1646v2PortSwMCIfInPriorityQueuesEntry 150994944}

pr1646v2PortSwMCIfInPriorityQueuesRedLength OBJECT-TYPE
   SYNTAX      Integer32
   MAX-ACCESS  read-only
   STATUS      current
   DESCRIPTION
      "Path: ethernet1.performance.ifInPriorityQueues.redLength"
   ::= {pr1646v2PortSwMCIfInPriorityQueuesEntry 134217728}

pr1646v2PortSwMCIfInPriorityQueuesPacketsTotal OBJECT-TYPE
   SYNTAX      Counter64
   MAX-ACCESS  read-only
   STATUS      current
   DESCRIPTION
      "Path: ethernet1.performance.ifInPriorityQueues.packets.total

       64 bit unsigned wrappable counter."
   ::= {pr1646v2PortSwMCIfInPriorityQueuesEntry 50790400}

pr1646v2PortSwMCIfInPriorityQueuesPacketsDirectTx OBJECT-TYPE
   SYNTAX      Counter64
   MAX-ACCESS  read-only
   STATUS      current
   DESCRIPTION
      "Path: ethernet1.performance.ifInPriorityQueues.packets.directTx

       64 bit unsigned wrappable counter."
   ::= {pr1646v2PortSwMCIfInPriorityQueuesEntry 50397184}

pr1646v2PortSwMCIfInPriorityQueuesPacketsQueued OBJECT-TYPE
   SYNTAX      Counter64
   MAX-ACCESS  read-only
   STATUS      current
   DESCRIPTION
      "Path: ethernet1.performance.ifInPriorityQueues.packets.queued

       64 bit unsigned wrappable counter."
   ::= {pr1646v2PortSwMCIfInPriorityQueuesEntry 50462720}

pr1646v2PortSwMCIfInPriorityQueuesPacketsDropped OBJECT-TYPE
   SYNTAX      Counter64
   MAX-ACCESS  read-only
   STATUS      current
   DESCRIPTION
      "Path: ethernet1.performance.ifInPriorityQueues.packets.dropped

       64 bit unsigned wrappable counter."
   ::= {pr1646v2PortSwMCIfInPriorityQueuesEntry 50528256}

pr1646v2PortSwMCIfInPriorityQueuesPacketsRedDropped OBJECT-TYPE
   SYNTAX      Counter64
   MAX-ACCESS  read-only
   STATUS      current
   DESCRIPTION
      "Path: ethernet1.performance.ifInPriorityQueues.packets.redDropped

       64 bit unsigned wrappable counter."
   ::= {pr1646v2PortSwMCIfInPriorityQueuesEntry 50724864}

pr1646v2PortSwMCIfInPriorityQueuesPacketsCirTx OBJECT-TYPE
   SYNTAX      Counter64
   MAX-ACCESS  read-only
   STATUS      current
   DESCRIPTION
      "Path: ethernet1.performance.ifInPriorityQueues.packets.cirTx

       64 bit unsigned wrappable counter."
   ::= {pr1646v2PortSwMCIfInPriorityQueuesEntry 50593792}

pr1646v2PortSwMCIfInPriorityQueuesPacketsEirTx OBJECT-TYPE
   SYNTAX      Counter64
   MAX-ACCESS  read-only
   STATUS      current
   DESCRIPTION
      "Path: ethernet1.performance.ifInPriorityQueues.packets.eirTx

       64 bit unsigned wrappable counter."
   ::= {pr1646v2PortSwMCIfInPriorityQueuesEntry 50659328}

pr1646v2PortSwMCIfInPriorityQueuesPacketsViolateTx OBJECT-TYPE
   SYNTAX      Counter64
   MAX-ACCESS  read-only
   STATUS      current
   DESCRIPTION
      "Path: ethernet1.performance.ifInPriorityQueues.packets.violateTx

       64 bit unsigned wrappable counter."
   ::= {pr1646v2PortSwMCIfInPriorityQueuesEntry 50855936}

pr1646v2PortSwMCIfInPriorityQueuesOctetsTotal OBJECT-TYPE
   SYNTAX      Counter64
   MAX-ACCESS  read-only
   STATUS      current
   DESCRIPTION
      "Path: ethernet1.performance.ifInPriorityQueues.octets.total

       64 bit unsigned wrappable counter."
   ::= {pr1646v2PortSwMCIfInPriorityQueuesEntry 67567616}

pr1646v2PortSwMCIfInPriorityQueuesOctetsDirectTx OBJECT-TYPE
   SYNTAX      Counter64
   MAX-ACCESS  read-only
   STATUS      current
   DESCRIPTION
      "Path: ethernet1.performance.ifInPriorityQueues.octets.directTx

       64 bit unsigned wrappable counter."
   ::= {pr1646v2PortSwMCIfInPriorityQueuesEntry 67174400}

pr1646v2PortSwMCIfInPriorityQueuesOctetsQueued OBJECT-TYPE
   SYNTAX      Counter64
   MAX-ACCESS  read-only
   STATUS      current
   DESCRIPTION
      "Path: ethernet1.performance.ifInPriorityQueues.octets.queued

       64 bit unsigned wrappable counter."
   ::= {pr1646v2PortSwMCIfInPriorityQueuesEntry 67239936}

pr1646v2PortSwMCIfInPriorityQueuesOctetsDropped OBJECT-TYPE
   SYNTAX      Counter64
   MAX-ACCESS  read-only
   STATUS      current
   DESCRIPTION
      "Path: ethernet1.performance.ifInPriorityQueues.octets.dropped

       64 bit unsigned wrappable counter."
   ::= {pr1646v2PortSwMCIfInPriorityQueuesEntry 67305472}

pr1646v2PortSwMCIfInPriorityQueuesOctetsRedDropped OBJECT-TYPE
   SYNTAX      Counter64
   MAX-ACCESS  read-only
   STATUS      current
   DESCRIPTION
      "Path: ethernet1.performance.ifInPriorityQueues.octets.redDropped

       64 bit unsigned wrappable counter."
   ::= {pr1646v2PortSwMCIfInPriorityQueuesEntry 67502080}

pr1646v2PortSwMCIfInPriorityQueuesOctetsCirTx OBJECT-TYPE
   SYNTAX      Counter64
   MAX-ACCESS  read-only
   STATUS      current
   DESCRIPTION
      "Path: ethernet1.performance.ifInPriorityQueues.octets.cirTx

       64 bit unsigned wrappable counter."
   ::= {pr1646v2PortSwMCIfInPriorityQueuesEntry 67371008}

pr1646v2PortSwMCIfInPriorityQueuesOctetsEirTx OBJECT-TYPE
   SYNTAX      Counter64
   MAX-ACCESS  read-only
   STATUS      current
   DESCRIPTION
      "Path: ethernet1.performance.ifInPriorityQueues.octets.eirTx

       64 bit unsigned wrappable counter."
   ::= {pr1646v2PortSwMCIfInPriorityQueuesEntry 67436544}

pr1646v2PortSwMCIfInPriorityQueuesOctetsViolateTx OBJECT-TYPE
   SYNTAX      Counter64
   MAX-ACCESS  read-only
   STATUS      current
   DESCRIPTION
      "Path: ethernet1.performance.ifInPriorityQueues.octets.violateTx

       64 bit unsigned wrappable counter."
   ::= {pr1646v2PortSwMCIfInPriorityQueuesEntry 67633152}

pr1646v2PortSwMCIfInPriorityQueuesOctetsBandwidth15sec OBJECT-TYPE
   SYNTAX      Integer32
   MAX-ACCESS  read-only
   STATUS      current
   DESCRIPTION
      "Path: ethernet1.performance.ifInPriorityQueues.octets.bandwidth.15sec

       unit name = bps
       formula = 8 * ; 8 /"
   ::= {pr1646v2PortSwMCIfInPriorityQueuesEntry 70386944}

pr1646v2PortSwMCIfInPriorityQueuesOctetsBandwidth30sec OBJECT-TYPE
   SYNTAX      Integer32
   MAX-ACCESS  read-only
   STATUS      current
   DESCRIPTION
      "Path: ethernet1.performance.ifInPriorityQueues.octets.bandwidth.30sec

       unit name = bps
       formula = 8 * ; 8 /"
   ::= {pr1646v2PortSwMCIfInPriorityQueuesEntry 70388224}

pr1646v2PortSwMCIfInPriorityQueuesOctetsBandwidth1min OBJECT-TYPE
   SYNTAX      Integer32
   MAX-ACCESS  read-only
   STATUS      current
   DESCRIPTION
      "Path: ethernet1.performance.ifInPriorityQueues.octets.bandwidth.1min

       unit name = bps
       formula = 8 * ; 8 /"
   ::= {pr1646v2PortSwMCIfInPriorityQueuesEntry 70390784}

pr1646v2PortSwMCIfInPriorityQueuesOctetsBandwidth2min OBJECT-TYPE
   SYNTAX      Integer32
   MAX-ACCESS  read-only
   STATUS      current
   DESCRIPTION
      "Path: ethernet1.performance.ifInPriorityQueues.octets.bandwidth.2min

       unit name = bps
       formula = 8 * ; 8 /"
   ::= {pr1646v2PortSwMCIfInPriorityQueuesEntry 70395904}

pr1646v2PortSwMCIfInPriorityQueuesOctetsBandwidth5min OBJECT-TYPE
   SYNTAX      Integer32
   MAX-ACCESS  read-only
   STATUS      current
   DESCRIPTION
      "Path: ethernet1.performance.ifInPriorityQueues.octets.bandwidth.5min

       unit name = bps
       formula = 8 * ; 8 /"
   ::= {pr1646v2PortSwMCIfInPriorityQueuesEntry 70411264}

pr1646v2PortSwMCIfInPriorityQueuesH2Performance OBJECT-TYPE
   SYNTAX      SEQUENCE OF Pr1646v2PortSwMCIfInPriorityQueuesH2PerformanceEntry
   MAX-ACCESS  not-accessible
   STATUS      current
   DESCRIPTION
      ""
   ::= {pr1646v2PortSwMCIfInPriorityQueues 83886080}

pr1646v2PortSwMCIfInPriorityQueuesH2PerformanceEntry OBJECT-TYPE
   SYNTAX      Pr1646v2PortSwMCIfInPriorityQueuesH2PerformanceEntry
   MAX-ACCESS  not-accessible
   STATUS      current
   DESCRIPTION
      ""
   INDEX      { pr1646v2PortSwMCIfInPriorityQueuesTableIx,
                pr1646v2PortSwMCIfInPriorityQueuesH2PerformanceTableIx }
   ::= {pr1646v2PortSwMCIfInPriorityQueuesH2Performance 1}

Pr1646v2PortSwMCIfInPriorityQueuesH2PerformanceEntry ::=
   SEQUENCE
      {
      pr1646v2PortSwMCIfInPriorityQueuesH2PerformanceTableIx
         TableIndex,
      pr1646v2PortSwMCIfInPriorityQueuesH2PerformanceSysUpTime
         TimeTicks,
      pr1646v2PortSwMCIfInPriorityQueuesH2PerformanceTotPkts
         Counter64,
      pr1646v2PortSwMCIfInPriorityQueuesH2PerformanceDirTxPkts
         Counter64,
      pr1646v2PortSwMCIfInPriorityQueuesH2PerformanceQdPkts
         Counter64,
      pr1646v2PortSwMCIfInPriorityQueuesH2PerformanceDropPkts
         Counter64,
      pr1646v2PortSwMCIfInPriorityQueuesH2PerformanceRDropPkts
         Counter64,
      pr1646v2PortSwMCIfInPriorityQueuesH2PerformanceCirTxPkts
         Counter64,
      pr1646v2PortSwMCIfInPriorityQueuesH2PerformanceEirTxPkts
         Counter64,
      pr1646v2PortSwMCIfInPriorityQueuesH2PerformanceViolTxPkts
         Counter64,
      pr1646v2PortSwMCIfInPriorityQueuesH2PerformanceTotOcts
         Counter64,
      pr1646v2PortSwMCIfInPriorityQueuesH2PerformanceDirTxOcts
         Counter64,
      pr1646v2PortSwMCIfInPriorityQueuesH2PerformanceQdOcts
         Counter64,
      pr1646v2PortSwMCIfInPriorityQueuesH2PerformanceDropOcts
         Counter64,
      pr1646v2PortSwMCIfInPriorityQueuesH2PerformanceRDropOcts
         Counter64,
      pr1646v2PortSwMCIfInPriorityQueuesH2PerformanceCirTxOcts
         Counter64,
      pr1646v2PortSwMCIfInPriorityQueuesH2PerformanceEirTxOcts
         Counter64,
      pr1646v2PortSwMCIfInPriorityQueuesH2PerformanceViolTxOcts
         Counter64,
      pr1646v2PortSwMCIfInPriorityQueuesH2PerformanceBandwidth
         Integer32
      }

pr1646v2PortSwMCIfInPriorityQueuesH2PerformanceTableIx OBJECT-TYPE
   SYNTAX      TableIndex
   MAX-ACCESS  not-accessible
   STATUS      current
   DESCRIPTION
      ""
   ::= {pr1646v2PortSwMCIfInPriorityQueuesH2PerformanceEntry 11}

pr1646v2PortSwMCIfInPriorityQueuesH2PerformanceSysUpTime OBJECT-TYPE
   SYNTAX      TimeTicks
   MAX-ACCESS  read-only
   STATUS      current
   DESCRIPTION
      "Path: ethernet1.performance.ifInPriorityQueues.h2Performance.sysUpTime

       Time in centi-second."
   ::= {pr1646v2PortSwMCIfInPriorityQueuesH2PerformanceEntry 16777216}

pr1646v2PortSwMCIfInPriorityQueuesH2PerformanceTotPkts OBJECT-TYPE
   SYNTAX      Counter64
   MAX-ACCESS  read-only
   STATUS      current
   DESCRIPTION
      "Path: ethernet1.performance.ifInPriorityQueues.h2Performance.totalPkts

       64 bit unsigned wrappable counter."
   ::= {pr1646v2PortSwMCIfInPriorityQueuesH2PerformanceEntry 234881024}

pr1646v2PortSwMCIfInPriorityQueuesH2PerformanceDirTxPkts OBJECT-TYPE
   SYNTAX      Counter64
   MAX-ACCESS  read-only
   STATUS      current
   DESCRIPTION
      "Path: ethernet1.performance.ifInPriorityQueues.h2Performance.directTxPkts

       64 bit unsigned wrappable counter."
   ::= {pr1646v2PortSwMCIfInPriorityQueuesH2PerformanceEntry 33554432}

pr1646v2PortSwMCIfInPriorityQueuesH2PerformanceQdPkts OBJECT-TYPE
   SYNTAX      Counter64
   MAX-ACCESS  read-only
   STATUS      current
   DESCRIPTION
      "Path: ethernet1.performance.ifInPriorityQueues.h2Performance.queuedPkts

       64 bit unsigned wrappable counter."
   ::= {pr1646v2PortSwMCIfInPriorityQueuesH2PerformanceEntry 50331648}

pr1646v2PortSwMCIfInPriorityQueuesH2PerformanceDropPkts OBJECT-TYPE
   SYNTAX      Counter64
   MAX-ACCESS  read-only
   STATUS      current
   DESCRIPTION
      "Path: ethernet1.performance.ifInPriorityQueues.h2Performance.droppedPkts

       64 bit unsigned wrappable counter."
   ::= {pr1646v2PortSwMCIfInPriorityQueuesH2PerformanceEntry 67108864}

pr1646v2PortSwMCIfInPriorityQueuesH2PerformanceRDropPkts OBJECT-TYPE
   SYNTAX      Counter64
   MAX-ACCESS  read-only
   STATUS      current
   DESCRIPTION
      "Path: ethernet1.performance.ifInPriorityQueues.h2Performance.redDroppedPkts

       64 bit unsigned wrappable counter."
   ::= {pr1646v2PortSwMCIfInPriorityQueuesH2PerformanceEntry 201326592}

pr1646v2PortSwMCIfInPriorityQueuesH2PerformanceCirTxPkts OBJECT-TYPE
   SYNTAX      Counter64
   MAX-ACCESS  read-only
   STATUS      current
   DESCRIPTION
      "Path: ethernet1.performance.ifInPriorityQueues.h2Performance.cirTxPkts

       64 bit unsigned wrappable counter."
   ::= {pr1646v2PortSwMCIfInPriorityQueuesH2PerformanceEntry 83886080}

pr1646v2PortSwMCIfInPriorityQueuesH2PerformanceEirTxPkts OBJECT-TYPE
   SYNTAX      Counter64
   MAX-ACCESS  read-only
   STATUS      current
   DESCRIPTION
      "Path: ethernet1.performance.ifInPriorityQueues.h2Performance.eirTxPkts

       64 bit unsigned wrappable counter."
   ::= {pr1646v2PortSwMCIfInPriorityQueuesH2PerformanceEntry 100663296}

pr1646v2PortSwMCIfInPriorityQueuesH2PerformanceViolTxPkts OBJECT-TYPE
   SYNTAX      Counter64
   MAX-ACCESS  read-only
   STATUS      current
   DESCRIPTION
      "Path: ethernet1.performance.ifInPriorityQueues.h2Performance.violateTxPkts

       64 bit unsigned wrappable counter."
   ::= {pr1646v2PortSwMCIfInPriorityQueuesH2PerformanceEntry 301989888}

pr1646v2PortSwMCIfInPriorityQueuesH2PerformanceTotOcts OBJECT-TYPE
   SYNTAX      Counter64
   MAX-ACCESS  read-only
   STATUS      current
   DESCRIPTION
      "Path: ethernet1.performance.ifInPriorityQueues.h2Performance.totalOctets

       64 bit unsigned wrappable counter."
   ::= {pr1646v2PortSwMCIfInPriorityQueuesH2PerformanceEntry 251658240}

pr1646v2PortSwMCIfInPriorityQueuesH2PerformanceDirTxOcts OBJECT-TYPE
   SYNTAX      Counter64
   MAX-ACCESS  read-only
   STATUS      current
   DESCRIPTION
      "Path: ethernet1.performance.ifInPriorityQueues.h2Performance.directTxOctets

       64 bit unsigned wrappable counter."
   ::= {pr1646v2PortSwMCIfInPriorityQueuesH2PerformanceEntry 117440512}

pr1646v2PortSwMCIfInPriorityQueuesH2PerformanceQdOcts OBJECT-TYPE
   SYNTAX      Counter64
   MAX-ACCESS  read-only
   STATUS      current
   DESCRIPTION
      "Path: ethernet1.performance.ifInPriorityQueues.h2Performance.queuedOctets

       64 bit unsigned wrappable counter."
   ::= {pr1646v2PortSwMCIfInPriorityQueuesH2PerformanceEntry 134217728}

pr1646v2PortSwMCIfInPriorityQueuesH2PerformanceDropOcts OBJECT-TYPE
   SYNTAX      Counter64
   MAX-ACCESS  read-only
   STATUS      current
   DESCRIPTION
      "Path: ethernet1.performance.ifInPriorityQueues.h2Performance.droppedOctets

       64 bit unsigned wrappable counter."
   ::= {pr1646v2PortSwMCIfInPriorityQueuesH2PerformanceEntry 150994944}

pr1646v2PortSwMCIfInPriorityQueuesH2PerformanceRDropOcts OBJECT-TYPE
   SYNTAX      Counter64
   MAX-ACCESS  read-only
   STATUS      current
   DESCRIPTION
      "Path: ethernet1.performance.ifInPriorityQueues.h2Performance.redDroppedOctets

       64 bit unsigned wrappable counter."
   ::= {pr1646v2PortSwMCIfInPriorityQueuesH2PerformanceEntry 218103808}

pr1646v2PortSwMCIfInPriorityQueuesH2PerformanceCirTxOcts OBJECT-TYPE
   SYNTAX      Counter64
   MAX-ACCESS  read-only
   STATUS      current
   DESCRIPTION
      "Path: ethernet1.performance.ifInPriorityQueues.h2Performance.cirTxOctets

       64 bit unsigned wrappable counter."
   ::= {pr1646v2PortSwMCIfInPriorityQueuesH2PerformanceEntry 167772160}

pr1646v2PortSwMCIfInPriorityQueuesH2PerformanceEirTxOcts OBJECT-TYPE
   SYNTAX      Counter64
   MAX-ACCESS  read-only
   STATUS      current
   DESCRIPTION
      "Path: ethernet1.performance.ifInPriorityQueues.h2Performance.eirTxOctets

       64 bit unsigned wrappable counter."
   ::= {pr1646v2PortSwMCIfInPriorityQueuesH2PerformanceEntry 184549376}

pr1646v2PortSwMCIfInPriorityQueuesH2PerformanceViolTxOcts OBJECT-TYPE
   SYNTAX      Counter64
   MAX-ACCESS  read-only
   STATUS      current
   DESCRIPTION
      "Path: ethernet1.performance.ifInPriorityQueues.h2Performance.violateTxOctets

       64 bit unsigned wrappable counter."
   ::= {pr1646v2PortSwMCIfInPriorityQueuesH2PerformanceEntry 318767104}

pr1646v2PortSwMCIfInPriorityQueuesH2PerformanceBandwidth OBJECT-TYPE
   SYNTAX      Integer32
   MAX-ACCESS  read-only
   STATUS      current
   DESCRIPTION
      "Path: ethernet1.performance.ifInPriorityQueues.h2Performance.bandwidth

       unit name = bps
       formula = 8 * ; 8 /"
   ::= {pr1646v2PortSwMCIfInPriorityQueuesH2PerformanceEntry 268435456}

pr1646v2PortSwMCIfInPriorityQueuesH24Performance OBJECT-TYPE
   SYNTAX      SEQUENCE OF Pr1646v2PortSwMCIfInPriorityQueuesH24PerformanceEntry
   MAX-ACCESS  not-accessible
   STATUS      current
   DESCRIPTION
      ""
   ::= {pr1646v2PortSwMCIfInPriorityQueues 100663296}

pr1646v2PortSwMCIfInPriorityQueuesH24PerformanceEntry OBJECT-TYPE
   SYNTAX      Pr1646v2PortSwMCIfInPriorityQueuesH24PerformanceEntry
   MAX-ACCESS  not-accessible
   STATUS      current
   DESCRIPTION
      ""
   INDEX      { pr1646v2PortSwMCIfInPriorityQueuesTableIx,
                pr1646v2PortSwMCIfInPriorityQueuesH24PerformanceTableIx }
   ::= {pr1646v2PortSwMCIfInPriorityQueuesH24Performance 1}

Pr1646v2PortSwMCIfInPriorityQueuesH24PerformanceEntry ::=
   SEQUENCE
      {
      pr1646v2PortSwMCIfInPriorityQueuesH24PerformanceTableIx
         TableIndex,
      pr1646v2PortSwMCIfInPriorityQueuesH24PerformanceSysUpTime
         TimeTicks,
      pr1646v2PortSwMCIfInPriorityQueuesH24PerformanceTotPkts
         Counter64,
      pr1646v2PortSwMCIfInPriorityQueuesH24PerformanceDirTxPkts
         Counter64,
      pr1646v2PortSwMCIfInPriorityQueuesH24PerformanceQdPkts
         Counter64,
      pr1646v2PortSwMCIfInPriorityQueuesH24PerformanceDropPkts
         Counter64,
      pr1646v2PortSwMCIfInPriorityQueuesH24PerformanceRDropPkts
         Counter64,
      pr1646v2PortSwMCIfInPriorityQueuesH24PerformanceCirTxPkts
         Counter64,
      pr1646v2PortSwMCIfInPriorityQueuesH24PerformanceEirTxPkts
         Counter64,
      pr1646v2PortSwMCIfInPriorityQueuesH24PerformanceViolTxPkts
         Counter64,
      pr1646v2PortSwMCIfInPriorityQueuesH24PerformanceTotOcts
         Counter64,
      pr1646v2PortSwMCIfInPriorityQueuesH24PerformanceDirTxOcts
         Counter64,
      pr1646v2PortSwMCIfInPriorityQueuesH24PerformanceQdOcts
         Counter64,
      pr1646v2PortSwMCIfInPriorityQueuesH24PerformanceDropOcts
         Counter64,
      pr1646v2PortSwMCIfInPriorityQueuesH24PerformanceRDropOcts
         Counter64,
      pr1646v2PortSwMCIfInPriorityQueuesH24PerformanceCirTxOcts
         Counter64,
      pr1646v2PortSwMCIfInPriorityQueuesH24PerformanceEirTxOcts
         Counter64,
      pr1646v2PortSwMCIfInPriorityQueuesH24PerformanceViolTxOcts
         Counter64,
      pr1646v2PortSwMCIfInPriorityQueuesH24PerformanceBandwidth
         Integer32
      }

pr1646v2PortSwMCIfInPriorityQueuesH24PerformanceTableIx OBJECT-TYPE
   SYNTAX      TableIndex
   MAX-ACCESS  not-accessible
   STATUS      current
   DESCRIPTION
      ""
   ::= {pr1646v2PortSwMCIfInPriorityQueuesH24PerformanceEntry 11}

pr1646v2PortSwMCIfInPriorityQueuesH24PerformanceSysUpTime OBJECT-TYPE
   SYNTAX      TimeTicks
   MAX-ACCESS  read-only
   STATUS      current
   DESCRIPTION
      "Path: ethernet1.performance.ifInPriorityQueues.h24Performance.sysUpTime

       Time in centi-second."
   ::= {pr1646v2PortSwMCIfInPriorityQueuesH24PerformanceEntry 16777216}

pr1646v2PortSwMCIfInPriorityQueuesH24PerformanceTotPkts OBJECT-TYPE
   SYNTAX      Counter64
   MAX-ACCESS  read-only
   STATUS      current
   DESCRIPTION
      "Path: ethernet1.performance.ifInPriorityQueues.h24Performance.totalPkts

       64 bit unsigned wrappable counter."
   ::= {pr1646v2PortSwMCIfInPriorityQueuesH24PerformanceEntry 234881024}

pr1646v2PortSwMCIfInPriorityQueuesH24PerformanceDirTxPkts OBJECT-TYPE
   SYNTAX      Counter64
   MAX-ACCESS  read-only
   STATUS      current
   DESCRIPTION
      "Path: ethernet1.performance.ifInPriorityQueues.h24Performance.directTxPkts

       64 bit unsigned wrappable counter."
   ::= {pr1646v2PortSwMCIfInPriorityQueuesH24PerformanceEntry 33554432}

pr1646v2PortSwMCIfInPriorityQueuesH24PerformanceQdPkts OBJECT-TYPE
   SYNTAX      Counter64
   MAX-ACCESS  read-only
   STATUS      current
   DESCRIPTION
      "Path: ethernet1.performance.ifInPriorityQueues.h24Performance.queuedPkts

       64 bit unsigned wrappable counter."
   ::= {pr1646v2PortSwMCIfInPriorityQueuesH24PerformanceEntry 50331648}

pr1646v2PortSwMCIfInPriorityQueuesH24PerformanceDropPkts OBJECT-TYPE
   SYNTAX      Counter64
   MAX-ACCESS  read-only
   STATUS      current
   DESCRIPTION
      "Path: ethernet1.performance.ifInPriorityQueues.h24Performance.droppedPkts

       64 bit unsigned wrappable counter."
   ::= {pr1646v2PortSwMCIfInPriorityQueuesH24PerformanceEntry 67108864}

pr1646v2PortSwMCIfInPriorityQueuesH24PerformanceRDropPkts OBJECT-TYPE
   SYNTAX      Counter64
   MAX-ACCESS  read-only
   STATUS      current
   DESCRIPTION
      "Path: ethernet1.performance.ifInPriorityQueues.h24Performance.redDroppedPkts

       64 bit unsigned wrappable counter."
   ::= {pr1646v2PortSwMCIfInPriorityQueuesH24PerformanceEntry 201326592}

pr1646v2PortSwMCIfInPriorityQueuesH24PerformanceCirTxPkts OBJECT-TYPE
   SYNTAX      Counter64
   MAX-ACCESS  read-only
   STATUS      current
   DESCRIPTION
      "Path: ethernet1.performance.ifInPriorityQueues.h24Performance.cirTxPkts

       64 bit unsigned wrappable counter."
   ::= {pr1646v2PortSwMCIfInPriorityQueuesH24PerformanceEntry 83886080}

pr1646v2PortSwMCIfInPriorityQueuesH24PerformanceEirTxPkts OBJECT-TYPE
   SYNTAX      Counter64
   MAX-ACCESS  read-only
   STATUS      current
   DESCRIPTION
      "Path: ethernet1.performance.ifInPriorityQueues.h24Performance.eirTxPkts

       64 bit unsigned wrappable counter."
   ::= {pr1646v2PortSwMCIfInPriorityQueuesH24PerformanceEntry 100663296}

pr1646v2PortSwMCIfInPriorityQueuesH24PerformanceViolTxPkts OBJECT-TYPE
   SYNTAX      Counter64
   MAX-ACCESS  read-only
   STATUS      current
   DESCRIPTION
      "Path: ethernet1.performance.ifInPriorityQueues.h24Performance.violateTxPkts

       64 bit unsigned wrappable counter."
   ::= {pr1646v2PortSwMCIfInPriorityQueuesH24PerformanceEntry 301989888}

pr1646v2PortSwMCIfInPriorityQueuesH24PerformanceTotOcts OBJECT-TYPE
   SYNTAX      Counter64
   MAX-ACCESS  read-only
   STATUS      current
   DESCRIPTION
      "Path: ethernet1.performance.ifInPriorityQueues.h24Performance.totalOctets

       64 bit unsigned wrappable counter."
   ::= {pr1646v2PortSwMCIfInPriorityQueuesH24PerformanceEntry 251658240}

pr1646v2PortSwMCIfInPriorityQueuesH24PerformanceDirTxOcts OBJECT-TYPE
   SYNTAX      Counter64
   MAX-ACCESS  read-only
   STATUS      current
   DESCRIPTION
      "Path: ethernet1.performance.ifInPriorityQueues.h24Performance.directTxOctets

       64 bit unsigned wrappable counter."
   ::= {pr1646v2PortSwMCIfInPriorityQueuesH24PerformanceEntry 117440512}

pr1646v2PortSwMCIfInPriorityQueuesH24PerformanceQdOcts OBJECT-TYPE
   SYNTAX      Counter64
   MAX-ACCESS  read-only
   STATUS      current
   DESCRIPTION
      "Path: ethernet1.performance.ifInPriorityQueues.h24Performance.queuedOctets

       64 bit unsigned wrappable counter."
   ::= {pr1646v2PortSwMCIfInPriorityQueuesH24PerformanceEntry 134217728}

pr1646v2PortSwMCIfInPriorityQueuesH24PerformanceDropOcts OBJECT-TYPE
   SYNTAX      Counter64
   MAX-ACCESS  read-only
   STATUS      current
   DESCRIPTION
      "Path: ethernet1.performance.ifInPriorityQueues.h24Performance.droppedOctets

       64 bit unsigned wrappable counter."
   ::= {pr1646v2PortSwMCIfInPriorityQueuesH24PerformanceEntry 150994944}

pr1646v2PortSwMCIfInPriorityQueuesH24PerformanceRDropOcts OBJECT-TYPE
   SYNTAX      Counter64
   MAX-ACCESS  read-only
   STATUS      current
   DESCRIPTION
      "Path: ethernet1.performance.ifInPriorityQueues.h24Performance.redDroppedOctets

       64 bit unsigned wrappable counter."
   ::= {pr1646v2PortSwMCIfInPriorityQueuesH24PerformanceEntry 218103808}

pr1646v2PortSwMCIfInPriorityQueuesH24PerformanceCirTxOcts OBJECT-TYPE
   SYNTAX      Counter64
   MAX-ACCESS  read-only
   STATUS      current
   DESCRIPTION
      "Path: ethernet1.performance.ifInPriorityQueues.h24Performance.cirTxOctets

       64 bit unsigned wrappable counter."
   ::= {pr1646v2PortSwMCIfInPriorityQueuesH24PerformanceEntry 167772160}

pr1646v2PortSwMCIfInPriorityQueuesH24PerformanceEirTxOcts OBJECT-TYPE
   SYNTAX      Counter64
   MAX-ACCESS  read-only
   STATUS      current
   DESCRIPTION
      "Path: ethernet1.performance.ifInPriorityQueues.h24Performance.eirTxOctets

       64 bit unsigned wrappable counter."
   ::= {pr1646v2PortSwMCIfInPriorityQueuesH24PerformanceEntry 184549376}

pr1646v2PortSwMCIfInPriorityQueuesH24PerformanceViolTxOcts OBJECT-TYPE
   SYNTAX      Counter64
   MAX-ACCESS  read-only
   STATUS      current
   DESCRIPTION
      "Path: ethernet1.performance.ifInPriorityQueues.h24Performance.violateTxOctets

       64 bit unsigned wrappable counter."
   ::= {pr1646v2PortSwMCIfInPriorityQueuesH24PerformanceEntry 318767104}

pr1646v2PortSwMCIfInPriorityQueuesH24PerformanceBandwidth OBJECT-TYPE
   SYNTAX      Integer32
   MAX-ACCESS  read-only
   STATUS      current
   DESCRIPTION
      "Path: ethernet1.performance.ifInPriorityQueues.h24Performance.bandwidth

       unit name = bps
       formula = 8 * ; 8 /"
   ::= {pr1646v2PortSwMCIfInPriorityQueuesH24PerformanceEntry 268435456}

pr1646v2PortSwMCIfInPriorityQueuesD7Performance OBJECT-TYPE
   SYNTAX      SEQUENCE OF Pr1646v2PortSwMCIfInPriorityQueuesD7PerformanceEntry
   MAX-ACCESS  not-accessible
   STATUS      current
   DESCRIPTION
      ""
   ::= {pr1646v2PortSwMCIfInPriorityQueues 117440512}

pr1646v2PortSwMCIfInPriorityQueuesD7PerformanceEntry OBJECT-TYPE
   SYNTAX      Pr1646v2PortSwMCIfInPriorityQueuesD7PerformanceEntry
   MAX-ACCESS  not-accessible
   STATUS      current
   DESCRIPTION
      ""
   INDEX      { pr1646v2PortSwMCIfInPriorityQueuesTableIx,
                pr1646v2PortSwMCIfInPriorityQueuesD7PerformanceTableIx }
   ::= {pr1646v2PortSwMCIfInPriorityQueuesD7Performance 1}

Pr1646v2PortSwMCIfInPriorityQueuesD7PerformanceEntry ::=
   SEQUENCE
      {
      pr1646v2PortSwMCIfInPriorityQueuesD7PerformanceTableIx
         TableIndex,
      pr1646v2PortSwMCIfInPriorityQueuesD7PerformanceSysUpTime
         TimeTicks,
      pr1646v2PortSwMCIfInPriorityQueuesD7PerformanceTotPkts
         Counter64,
      pr1646v2PortSwMCIfInPriorityQueuesD7PerformanceDirTxPkts
         Counter64,
      pr1646v2PortSwMCIfInPriorityQueuesD7PerformanceQdPkts
         Counter64,
      pr1646v2PortSwMCIfInPriorityQueuesD7PerformanceDropPkts
         Counter64,
      pr1646v2PortSwMCIfInPriorityQueuesD7PerformanceRDropPkts
         Counter64,
      pr1646v2PortSwMCIfInPriorityQueuesD7PerformanceCirTxPkts
         Counter64,
      pr1646v2PortSwMCIfInPriorityQueuesD7PerformanceEirTxPkts
         Counter64,
      pr1646v2PortSwMCIfInPriorityQueuesD7PerformanceViolTxPkts
         Counter64,
      pr1646v2PortSwMCIfInPriorityQueuesD7PerformanceTotOcts
         Counter64,
      pr1646v2PortSwMCIfInPriorityQueuesD7PerformanceDirTxOcts
         Counter64,
      pr1646v2PortSwMCIfInPriorityQueuesD7PerformanceQdOcts
         Counter64,
      pr1646v2PortSwMCIfInPriorityQueuesD7PerformanceDropOcts
         Counter64,
      pr1646v2PortSwMCIfInPriorityQueuesD7PerformanceRDropOcts
         Counter64,
      pr1646v2PortSwMCIfInPriorityQueuesD7PerformanceCirTxOcts
         Counter64,
      pr1646v2PortSwMCIfInPriorityQueuesD7PerformanceEirTxOcts
         Counter64,
      pr1646v2PortSwMCIfInPriorityQueuesD7PerformanceViolTxOcts
         Counter64,
      pr1646v2PortSwMCIfInPriorityQueuesD7PerformanceBandwidth
         Integer32
      }

pr1646v2PortSwMCIfInPriorityQueuesD7PerformanceTableIx OBJECT-TYPE
   SYNTAX      TableIndex
   MAX-ACCESS  not-accessible
   STATUS      current
   DESCRIPTION
      ""
   ::= {pr1646v2PortSwMCIfInPriorityQueuesD7PerformanceEntry 11}

pr1646v2PortSwMCIfInPriorityQueuesD7PerformanceSysUpTime OBJECT-TYPE
   SYNTAX      TimeTicks
   MAX-ACCESS  read-only
   STATUS      current
   DESCRIPTION
      "Path: ethernet1.performance.ifInPriorityQueues.d7Performance.sysUpTime

       Time in centi-second."
   ::= {pr1646v2PortSwMCIfInPriorityQueuesD7PerformanceEntry 16777216}

pr1646v2PortSwMCIfInPriorityQueuesD7PerformanceTotPkts OBJECT-TYPE
   SYNTAX      Counter64
   MAX-ACCESS  read-only
   STATUS      current
   DESCRIPTION
      "Path: ethernet1.performance.ifInPriorityQueues.d7Performance.totalPkts

       64 bit unsigned wrappable counter."
   ::= {pr1646v2PortSwMCIfInPriorityQueuesD7PerformanceEntry 234881024}

pr1646v2PortSwMCIfInPriorityQueuesD7PerformanceDirTxPkts OBJECT-TYPE
   SYNTAX      Counter64
   MAX-ACCESS  read-only
   STATUS      current
   DESCRIPTION
      "Path: ethernet1.performance.ifInPriorityQueues.d7Performance.directTxPkts

       64 bit unsigned wrappable counter."
   ::= {pr1646v2PortSwMCIfInPriorityQueuesD7PerformanceEntry 33554432}

pr1646v2PortSwMCIfInPriorityQueuesD7PerformanceQdPkts OBJECT-TYPE
   SYNTAX      Counter64
   MAX-ACCESS  read-only
   STATUS      current
   DESCRIPTION
      "Path: ethernet1.performance.ifInPriorityQueues.d7Performance.queuedPkts

       64 bit unsigned wrappable counter."
   ::= {pr1646v2PortSwMCIfInPriorityQueuesD7PerformanceEntry 50331648}

pr1646v2PortSwMCIfInPriorityQueuesD7PerformanceDropPkts OBJECT-TYPE
   SYNTAX      Counter64
   MAX-ACCESS  read-only
   STATUS      current
   DESCRIPTION
      "Path: ethernet1.performance.ifInPriorityQueues.d7Performance.droppedPkts

       64 bit unsigned wrappable counter."
   ::= {pr1646v2PortSwMCIfInPriorityQueuesD7PerformanceEntry 67108864}

pr1646v2PortSwMCIfInPriorityQueuesD7PerformanceRDropPkts OBJECT-TYPE
   SYNTAX      Counter64
   MAX-ACCESS  read-only
   STATUS      current
   DESCRIPTION
      "Path: ethernet1.performance.ifInPriorityQueues.d7Performance.redDroppedPkts

       64 bit unsigned wrappable counter."
   ::= {pr1646v2PortSwMCIfInPriorityQueuesD7PerformanceEntry 201326592}

pr1646v2PortSwMCIfInPriorityQueuesD7PerformanceCirTxPkts OBJECT-TYPE
   SYNTAX      Counter64
   MAX-ACCESS  read-only
   STATUS      current
   DESCRIPTION
      "Path: ethernet1.performance.ifInPriorityQueues.d7Performance.cirTxPkts

       64 bit unsigned wrappable counter."
   ::= {pr1646v2PortSwMCIfInPriorityQueuesD7PerformanceEntry 83886080}

pr1646v2PortSwMCIfInPriorityQueuesD7PerformanceEirTxPkts OBJECT-TYPE
   SYNTAX      Counter64
   MAX-ACCESS  read-only
   STATUS      current
   DESCRIPTION
      "Path: ethernet1.performance.ifInPriorityQueues.d7Performance.eirTxPkts

       64 bit unsigned wrappable counter."
   ::= {pr1646v2PortSwMCIfInPriorityQueuesD7PerformanceEntry 100663296}

pr1646v2PortSwMCIfInPriorityQueuesD7PerformanceViolTxPkts OBJECT-TYPE
   SYNTAX      Counter64
   MAX-ACCESS  read-only
   STATUS      current
   DESCRIPTION
      "Path: ethernet1.performance.ifInPriorityQueues.d7Performance.violateTxPkts

       64 bit unsigned wrappable counter."
   ::= {pr1646v2PortSwMCIfInPriorityQueuesD7PerformanceEntry 301989888}

pr1646v2PortSwMCIfInPriorityQueuesD7PerformanceTotOcts OBJECT-TYPE
   SYNTAX      Counter64
   MAX-ACCESS  read-only
   STATUS      current
   DESCRIPTION
      "Path: ethernet1.performance.ifInPriorityQueues.d7Performance.totalOctets

       64 bit unsigned wrappable counter."
   ::= {pr1646v2PortSwMCIfInPriorityQueuesD7PerformanceEntry 251658240}

pr1646v2PortSwMCIfInPriorityQueuesD7PerformanceDirTxOcts OBJECT-TYPE
   SYNTAX      Counter64
   MAX-ACCESS  read-only
   STATUS      current
   DESCRIPTION
      "Path: ethernet1.performance.ifInPriorityQueues.d7Performance.directTxOctets

       64 bit unsigned wrappable counter."
   ::= {pr1646v2PortSwMCIfInPriorityQueuesD7PerformanceEntry 117440512}

pr1646v2PortSwMCIfInPriorityQueuesD7PerformanceQdOcts OBJECT-TYPE
   SYNTAX      Counter64
   MAX-ACCESS  read-only
   STATUS      current
   DESCRIPTION
      "Path: ethernet1.performance.ifInPriorityQueues.d7Performance.queuedOctets

       64 bit unsigned wrappable counter."
   ::= {pr1646v2PortSwMCIfInPriorityQueuesD7PerformanceEntry 134217728}

pr1646v2PortSwMCIfInPriorityQueuesD7PerformanceDropOcts OBJECT-TYPE
   SYNTAX      Counter64
   MAX-ACCESS  read-only
   STATUS      current
   DESCRIPTION
      "Path: ethernet1.performance.ifInPriorityQueues.d7Performance.droppedOctets

       64 bit unsigned wrappable counter."
   ::= {pr1646v2PortSwMCIfInPriorityQueuesD7PerformanceEntry 150994944}

pr1646v2PortSwMCIfInPriorityQueuesD7PerformanceRDropOcts OBJECT-TYPE
   SYNTAX      Counter64
   MAX-ACCESS  read-only
   STATUS      current
   DESCRIPTION
      "Path: ethernet1.performance.ifInPriorityQueues.d7Performance.redDroppedOctets

       64 bit unsigned wrappable counter."
   ::= {pr1646v2PortSwMCIfInPriorityQueuesD7PerformanceEntry 218103808}

pr1646v2PortSwMCIfInPriorityQueuesD7PerformanceCirTxOcts OBJECT-TYPE
   SYNTAX      Counter64
   MAX-ACCESS  read-only
   STATUS      current
   DESCRIPTION
      "Path: ethernet1.performance.ifInPriorityQueues.d7Performance.cirTxOctets

       64 bit unsigned wrappable counter."
   ::= {pr1646v2PortSwMCIfInPriorityQueuesD7PerformanceEntry 167772160}

pr1646v2PortSwMCIfInPriorityQueuesD7PerformanceEirTxOcts OBJECT-TYPE
   SYNTAX      Counter64
   MAX-ACCESS  read-only
   STATUS      current
   DESCRIPTION
      "Path: ethernet1.performance.ifInPriorityQueues.d7Performance.eirTxOctets

       64 bit unsigned wrappable counter."
   ::= {pr1646v2PortSwMCIfInPriorityQueuesD7PerformanceEntry 184549376}

pr1646v2PortSwMCIfInPriorityQueuesD7PerformanceViolTxOcts OBJECT-TYPE
   SYNTAX      Counter64
   MAX-ACCESS  read-only
   STATUS      current
   DESCRIPTION
      "Path: ethernet1.performance.ifInPriorityQueues.d7Performance.violateTxOctets

       64 bit unsigned wrappable counter."
   ::= {pr1646v2PortSwMCIfInPriorityQueuesD7PerformanceEntry 318767104}

pr1646v2PortSwMCIfInPriorityQueuesD7PerformanceBandwidth OBJECT-TYPE
   SYNTAX      Integer32
   MAX-ACCESS  read-only
   STATUS      current
   DESCRIPTION
      "Path: ethernet1.performance.ifInPriorityQueues.d7Performance.bandwidth

       unit name = bps
       formula = 8 * ; 8 /"
   ::= {pr1646v2PortSwMCIfInPriorityQueuesD7PerformanceEntry 268435456}


pr1646v2PortSwMCIfInHwPriorityQueues OBJECT IDENTIFIER ::= {pr1646v2PortSwMC 132}

pr1646v2PortSwMCIfInHwPriorityQueuesSSCTable OBJECT-TYPE
   SYNTAX      SEQUENCE OF Pr1646v2PortSwMCIfInHwPriorityQueuesEntry
   MAX-ACCESS  not-accessible
   STATUS      current
   DESCRIPTION
      "hwPriorityQueues"
   ::= {pr1646v2PortSwMCIfInHwPriorityQueues 1}

pr1646v2PortSwMCIfInHwPriorityQueuesEntry OBJECT-TYPE
   SYNTAX      Pr1646v2PortSwMCIfInHwPriorityQueuesEntry
   MAX-ACCESS  not-accessible
   STATUS      current
   DESCRIPTION
      ""
   INDEX      { pr1646v2PortSwMCIfInHwPriorityQueuesTableIx }
   ::= {pr1646v2PortSwMCIfInHwPriorityQueuesSSCTable 1}

Pr1646v2PortSwMCIfInHwPriorityQueuesEntry ::=
   SEQUENCE
      {
      pr1646v2PortSwMCIfInHwPriorityQueuesTableIx
         TableIndex,
      pr1646v2PortSwMCIfInHwPriorityQueuesName
         INTEGER,
      pr1646v2PortSwMCIfInHwPriorityQueuesLength
         Integer32,
      pr1646v2PortSwMCIfInHwPriorityQueuesPacketsTotal
         Counter64,
      pr1646v2PortSwMCIfInHwPriorityQueuesOctetsTotal
         Counter64,
      pr1646v2PortSwMCIfInHwPriorityQueuesOctetsBandwidth15sec
         Integer32,
      pr1646v2PortSwMCIfInHwPriorityQueuesOctetsBandwidth30sec
         Integer32,
      pr1646v2PortSwMCIfInHwPriorityQueuesOctetsBandwidth1min
         Integer32,
      pr1646v2PortSwMCIfInHwPriorityQueuesOctetsBandwidth2min
         Integer32,
      pr1646v2PortSwMCIfInHwPriorityQueuesOctetsBandwidth5min
         Integer32
      }

pr1646v2PortSwMCIfInHwPriorityQueuesTableIx OBJECT-TYPE
   SYNTAX      TableIndex
   MAX-ACCESS  not-accessible
   STATUS      current
   DESCRIPTION
      ""
   ::= {pr1646v2PortSwMCIfInHwPriorityQueuesEntry 11}

pr1646v2PortSwMCIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2PortSwMCIfInHwPriorityQueuesEntry 16777216}

pr1646v2PortSwMCIfInHwPriorityQueuesLength OBJECT-TYPE
   SYNTAX      Integer32
   MAX-ACCESS  read-only
   STATUS      current
   DESCRIPTION
      "Path: ethernet1.performance.ifInHwPriorityQueues.length"
   ::= {pr1646v2PortSwMCIfInHwPriorityQueuesEntry 33554432}

pr1646v2PortSwMCIfInHwPriorityQueuesPacketsTotal OBJECT-TYPE
   SYNTAX      Counter64
   MAX-ACCESS  read-only
   STATUS      current
   DESCRIPTION
      "Path: ethernet1.performance.ifInHwPriorityQueues.packets.total

       64 bit unsigned wrappable counter."
   ::= {pr1646v2PortSwMCIfInHwPriorityQueuesEntry 50790400}

pr1646v2PortSwMCIfInHwPriorityQueuesOctetsTotal OBJECT-TYPE
   SYNTAX      Counter64
   MAX-ACCESS  read-only
   STATUS      current
   DESCRIPTION
      "Path: ethernet1.performance.ifInHwPriorityQueues.octets.total

       64 bit unsigned wrappable counter."
   ::= {pr1646v2PortSwMCIfInHwPriorityQueuesEntry 67567616}

pr1646v2PortSwMCIfInHwPriorityQueuesOctetsBandwidth15sec OBJECT-TYPE
   SYNTAX      Integer32
   MAX-ACCESS  read-only
   STATUS      current
   DESCRIPTION
      "Path: ethernet1.performance.ifInHwPriorityQueues.octets.bandwidth.15sec

       unit name = bps
       formula = 8 * ; 8 /"
   ::= {pr1646v2PortSwMCIfInHwPriorityQueuesEntry 70386944}

pr1646v2PortSwMCIfInHwPriorityQueuesOctetsBandwidth30sec OBJECT-TYPE
   SYNTAX      Integer32
   MAX-ACCESS  read-only
   STATUS      current
   DESCRIPTION
      "Path: ethernet1.performance.ifInHwPriorityQueues.octets.bandwidth.30sec

       unit name = bps
       formula = 8 * ; 8 /"
   ::= {pr1646v2PortSwMCIfInHwPriorityQueuesEntry 70388224}

pr1646v2PortSwMCIfInHwPriorityQueuesOctetsBandwidth1min OBJECT-TYPE
   SYNTAX      Integer32
   MAX-ACCESS  read-only
   STATUS      current
   DESCRIPTION
      "Path: ethernet1.performance.ifInHwPriorityQueues.octets.bandwidth.1min

       unit name = bps
       formula = 8 * ; 8 /"
   ::= {pr1646v2PortSwMCIfInHwPriorityQueuesEntry 70390784}

pr1646v2PortSwMCIfInHwPriorityQueuesOctetsBandwidth2min OBJECT-TYPE
   SYNTAX      Integer32
   MAX-ACCESS  read-only
   STATUS      current
   DESCRIPTION
      "Path: ethernet1.performance.ifInHwPriorityQueues.octets.bandwidth.2min

       unit name = bps
       formula = 8 * ; 8 /"
   ::= {pr1646v2PortSwMCIfInHwPriorityQueuesEntry 70395904}

pr1646v2PortSwMCIfInHwPriorityQueuesOctetsBandwidth5min OBJECT-TYPE
   SYNTAX      Integer32
   MAX-ACCESS  read-only
   STATUS      current
   DESCRIPTION
      "Path: ethernet1.performance.ifInHwPriorityQueues.octets.bandwidth.5min

       unit name = bps
       formula = 8 * ; 8 /"
   ::= {pr1646v2PortSwMCIfInHwPriorityQueuesEntry 70411264}

pr1646v2PortSwMCIfInHwPriorityQueuesH2Performance OBJECT-TYPE
   SYNTAX      SEQUENCE OF Pr1646v2PortSwMCIfInHwPriorityQueuesH2PerformanceEntry
   MAX-ACCESS  not-accessible
   STATUS      current
   DESCRIPTION
      ""
   ::= {pr1646v2PortSwMCIfInHwPriorityQueues 83886080}

pr1646v2PortSwMCIfInHwPriorityQueuesH2PerformanceEntry OBJECT-TYPE
   SYNTAX      Pr1646v2PortSwMCIfInHwPriorityQueuesH2PerformanceEntry
   MAX-ACCESS  not-accessible
   STATUS      current
   DESCRIPTION
      ""
   INDEX      { pr1646v2PortSwMCIfInHwPriorityQueuesTableIx,
                pr1646v2PortSwMCIfInHwPriorityQueuesH2PerformanceTableIx }
   ::= {pr1646v2PortSwMCIfInHwPriorityQueuesH2Performance 1}

Pr1646v2PortSwMCIfInHwPriorityQueuesH2PerformanceEntry ::=
   SEQUENCE
      {
      pr1646v2PortSwMCIfInHwPriorityQueuesH2PerformanceTableIx
         TableIndex,
      pr1646v2PortSwMCIfInHwPriorityQueuesH2PerformanceSysUpTime
         TimeTicks,
      pr1646v2PortSwMCIfInHwPriorityQueuesH2PerformanceTotPkts
         Counter64,
      pr1646v2PortSwMCIfInHwPriorityQueuesH2PerformanceTotOcts
         Counter64,
      pr1646v2PortSwMCIfInHwPriorityQueuesH2PerformanceBandwidth
         Integer32
      }

pr1646v2PortSwMCIfInHwPriorityQueuesH2PerformanceTableIx OBJECT-TYPE
   SYNTAX      TableIndex
   MAX-ACCESS  not-accessible
   STATUS      current
   DESCRIPTION
      ""
   ::= {pr1646v2PortSwMCIfInHwPriorityQueuesH2PerformanceEntry 11}

pr1646v2PortSwMCIfInHwPriorityQueuesH2PerformanceSysUpTime OBJECT-TYPE
   SYNTAX      TimeTicks
   MAX-ACCESS  read-only
   STATUS      current
   DESCRIPTION
      "Path: ethernet1.performance.ifInHwPriorityQueues.h2Performance.sysUpTime

       Time in centi-second."
   ::= {pr1646v2PortSwMCIfInHwPriorityQueuesH2PerformanceEntry 16777216}

pr1646v2PortSwMCIfInHwPriorityQueuesH2PerformanceTotPkts OBJECT-TYPE
   SYNTAX      Counter64
   MAX-ACCESS  read-only
   STATUS      current
   DESCRIPTION
      "Path: ethernet1.performance.ifInHwPriorityQueues.h2Performance.totalPkts

       64 bit unsigned wrappable counter."
   ::= {pr1646v2PortSwMCIfInHwPriorityQueuesH2PerformanceEntry 234881024}

pr1646v2PortSwMCIfInHwPriorityQueuesH2PerformanceTotOcts OBJECT-TYPE
   SYNTAX      Counter64
   MAX-ACCESS  read-only
   STATUS      current
   DESCRIPTION
      "Path: ethernet1.performance.ifInHwPriorityQueues.h2Performance.totalOctets

       64 bit unsigned wrappable counter."
   ::= {pr1646v2PortSwMCIfInHwPriorityQueuesH2PerformanceEntry 251658240}

pr1646v2PortSwMCIfInHwPriorityQueuesH2PerformanceBandwidth OBJECT-TYPE
   SYNTAX      Integer32
   MAX-ACCESS  read-only
   STATUS      current
   DESCRIPTION
      "Path: ethernet1.performance.ifInHwPriorityQueues.h2Performance.bandwidth

       unit name = bps
       formula = 8 * ; 8 /"
   ::= {pr1646v2PortSwMCIfInHwPriorityQueuesH2PerformanceEntry 268435456}

pr1646v2PortSwMCIfInHwPriorityQueuesH24Performance OBJECT-TYPE
   SYNTAX      SEQUENCE OF Pr1646v2PortSwMCIfInHwPriorityQueuesH24PerformanceEntry
   MAX-ACCESS  not-accessible
   STATUS      current
   DESCRIPTION
      ""
   ::= {pr1646v2PortSwMCIfInHwPriorityQueues 100663296}

pr1646v2PortSwMCIfInHwPriorityQueuesH24PerformanceEntry OBJECT-TYPE
   SYNTAX      Pr1646v2PortSwMCIfInHwPriorityQueuesH24PerformanceEntry
   MAX-ACCESS  not-accessible
   STATUS      current
   DESCRIPTION
      ""
   INDEX      { pr1646v2PortSwMCIfInHwPriorityQueuesTableIx,
                pr1646v2PortSwMCIfInHwPriorityQueuesH24PerformanceTableIx }
   ::= {pr1646v2PortSwMCIfInHwPriorityQueuesH24Performance 1}

Pr1646v2PortSwMCIfInHwPriorityQueuesH24PerformanceEntry ::=
   SEQUENCE
      {
      pr1646v2PortSwMCIfInHwPriorityQueuesH24PerformanceTableIx
         TableIndex,
      pr1646v2PortSwMCIfInHwPriorityQueuesH24PerformanceSysUpTime
         TimeTicks,
      pr1646v2PortSwMCIfInHwPriorityQueuesH24PerformanceTotPkts
         Counter64,
      pr1646v2PortSwMCIfInHwPriorityQueuesH24PerformanceTotOcts
         Counter64,
      pr1646v2PortSwMCIfInHwPriorityQueuesH24PerformanceBandwidth
         Integer32
      }

pr1646v2PortSwMCIfInHwPriorityQueuesH24PerformanceTableIx OBJECT-TYPE
   SYNTAX      TableIndex
   MAX-ACCESS  not-accessible
   STATUS      current
   DESCRIPTION
      ""
   ::= {pr1646v2PortSwMCIfInHwPriorityQueuesH24PerformanceEntry 11}

pr1646v2PortSwMCIfInHwPriorityQueuesH24PerformanceSysUpTime OBJECT-TYPE
   SYNTAX      TimeTicks
   MAX-ACCESS  read-only
   STATUS      current
   DESCRIPTION
      "Path: ethernet1.performance.ifInHwPriorityQueues.h24Performance.sysUpTime

       Time in centi-second."
   ::= {pr1646v2PortSwMCIfInHwPriorityQueuesH24PerformanceEntry 16777216}

pr1646v2PortSwMCIfInHwPriorityQueuesH24PerformanceTotPkts OBJECT-TYPE
   SYNTAX      Counter64
   MAX-ACCESS  read-only
   STATUS      current
   DESCRIPTION
      "Path: ethernet1.performance.ifInHwPriorityQueues.h24Performance.totalPkts

       64 bit unsigned wrappable counter."
   ::= {pr1646v2PortSwMCIfInHwPriorityQueuesH24PerformanceEntry 234881024}

pr1646v2PortSwMCIfInHwPriorityQueuesH24PerformanceTotOcts OBJECT-TYPE
   SYNTAX      Counter64
   MAX-ACCESS  read-only
   STATUS      current
   DESCRIPTION
      "Path: ethernet1.performance.ifInHwPriorityQueues.h24Performance.totalOctets

       64 bit unsigned wrappable counter."
   ::= {pr1646v2PortSwMCIfInHwPriorityQueuesH24PerformanceEntry 251658240}

pr1646v2PortSwMCIfInHwPriorityQueuesH24PerformanceBandwidth OBJECT-TYPE
   SYNTAX      Integer32
   MAX-ACCESS  read-only
   STATUS      current
   DESCRIPTION
      "Path: ethernet1.performance.ifInHwPriorityQueues.h24Performance.bandwidth

       unit name = bps
       formula = 8 * ; 8 /"
   ::= {pr1646v2PortSwMCIfInHwPriorityQueuesH24PerformanceEntry 268435456}

pr1646v2PortSwMCIfInHwPriorityQueuesD7Performance OBJECT-TYPE
   SYNTAX      SEQUENCE OF Pr1646v2PortSwMCIfInHwPriorityQueuesD7PerformanceEntry
   MAX-ACCESS  not-accessible
   STATUS      current
   DESCRIPTION
      ""
   ::= {pr1646v2PortSwMCIfInHwPriorityQueues 117440512}

pr1646v2PortSwMCIfInHwPriorityQueuesD7PerformanceEntry OBJECT-TYPE
   SYNTAX      Pr1646v2PortSwMCIfInHwPriorityQueuesD7PerformanceEntry
   MAX-ACCESS  not-accessible
   STATUS      current
   DESCRIPTION
      ""
   INDEX      { pr1646v2PortSwMCIfInHwPriorityQueuesTableIx,
                pr1646v2PortSwMCIfInHwPriorityQueuesD7PerformanceTableIx }
   ::= {pr1646v2PortSwMCIfInHwPriorityQueuesD7Performance 1}

Pr1646v2PortSwMCIfInHwPriorityQueuesD7PerformanceEntry ::=
   SEQUENCE
      {
      pr1646v2PortSwMCIfInHwPriorityQueuesD7PerformanceTableIx
         TableIndex,
      pr1646v2PortSwMCIfInHwPriorityQueuesD7PerformanceSysUpTime
         TimeTicks,
      pr1646v2PortSwMCIfInHwPriorityQueuesD7PerformanceTotPkts
         Counter64,
      pr1646v2PortSwMCIfInHwPriorityQueuesD7PerformanceTotOcts
         Counter64,
      pr1646v2PortSwMCIfInHwPriorityQueuesD7PerformanceBandwidth
         Integer32
      }

pr1646v2PortSwMCIfInHwPriorityQueuesD7PerformanceTableIx OBJECT-TYPE
   SYNTAX      TableIndex
   MAX-ACCESS  not-accessible
   STATUS      current
   DESCRIPTION
      ""
   ::= {pr1646v2PortSwMCIfInHwPriorityQueuesD7PerformanceEntry 11}

pr1646v2PortSwMCIfInHwPriorityQueuesD7PerformanceSysUpTime OBJECT-TYPE
   SYNTAX      TimeTicks
   MAX-ACCESS  read-only
   STATUS      current
   DESCRIPTION
      "Path: ethernet1.performance.ifInHwPriorityQueues.d7Performance.sysUpTime

       Time in centi-second."
   ::= {pr1646v2PortSwMCIfInHwPriorityQueuesD7PerformanceEntry 16777216}

pr1646v2PortSwMCIfInHwPriorityQueuesD7PerformanceTotPkts OBJECT-TYPE
   SYNTAX      Counter64
   MAX-ACCESS  read-only
   STATUS      current
   DESCRIPTION
      "Path: ethernet1.performance.ifInHwPriorityQueues.d7Performance.totalPkts

       64 bit unsigned wrappable counter."
   ::= {pr1646v2PortSwMCIfInHwPriorityQueuesD7PerformanceEntry 234881024}

pr1646v2PortSwMCIfInHwPriorityQueuesD7PerformanceTotOcts OBJECT-TYPE
   SYNTAX      Counter64
   MAX-ACCESS  read-only
   STATUS      current
   DESCRIPTION
      "Path: ethernet1.performance.ifInHwPriorityQueues.d7Performance.totalOctets

       64 bit unsigned wrappable counter."
   ::= {pr1646v2PortSwMCIfInHwPriorityQueuesD7PerformanceEntry 251658240}

pr1646v2PortSwMCIfInHwPriorityQueuesD7PerformanceBandwidth OBJECT-TYPE
   SYNTAX      Integer32
   MAX-ACCESS  read-only
   STATUS      current
   DESCRIPTION
      "Path: ethernet1.performance.ifInHwPriorityQueues.d7Performance.bandwidth

       unit name = bps
       formula = 8 * ; 8 /"
   ::= {pr1646v2PortSwMCIfInHwPriorityQueuesD7PerformanceEntry 268435456}


pr1646v2PortSwMCMibCntrs OBJECT IDENTIFIER ::= {pr1646v2PortSwMC 198}

pr1646v2PortSwMCMibCntrsSSCTable OBJECT-TYPE
   SYNTAX      SEQUENCE OF Pr1646v2PortSwMCMibCntrsEntry
   MAX-ACCESS  not-accessible
   STATUS      current
   DESCRIPTION
      "Ethernet Switch MIB Counters"
   ::= {pr1646v2PortSwMCMibCntrs 1}

pr1646v2PortSwMCMibCntrsEntry OBJECT-TYPE
   SYNTAX      Pr1646v2PortSwMCMibCntrsEntry
   MAX-ACCESS  not-accessible
   STATUS      current
   DESCRIPTION
      ""
   INDEX      { pr1646v2PortSwMCMibCntrsTableIx }
   ::= {pr1646v2PortSwMCMibCntrsSSCTable 1}

Pr1646v2PortSwMCMibCntrsEntry ::=
   SEQUENCE
      {
      pr1646v2PortSwMCMibCntrsTableIx
         TableIndex,
      pr1646v2PortSwMCMibCntrsPortName
         INTEGER,
      pr1646v2PortSwMCMibCntrsInOctets
         Counter64,
      pr1646v2PortSwMCMibCntrsInUcast
         Counter64,
      pr1646v2PortSwMCMibCntrsInNUcastPkts
         Counter64,
      pr1646v2PortSwMCMibCntrsInDiscards
         Counter64,
      pr1646v2PortSwMCMibCntrsInPause
         Counter64,
      pr1646v2PortSwMCMibCntrsInErrors
         Counter64,
      pr1646v2PortSwMCMibCntrsInBandwidth15sec
         Integer32,
      pr1646v2PortSwMCMibCntrsInBandwidth30sec
         Integer32,
      pr1646v2PortSwMCMibCntrsInBandwidth1min
         Integer32,
      pr1646v2PortSwMCMibCntrsInBandwidth2min
         Integer32,
      pr1646v2PortSwMCMibCntrsInBandwidth5min
         Integer32,
      pr1646v2PortSwMCMibCntrsOutOctets
         Counter64,
      pr1646v2PortSwMCMibCntrsOutUcastPkts
         Counter64,
      pr1646v2PortSwMCMibCntrsOutNUcastPkts
         Counter64,
      pr1646v2PortSwMCMibCntrsOutDiscards
         Counter64,
      pr1646v2PortSwMCMibCntrsOutPause
         Counter64,
      pr1646v2PortSwMCMibCntrsOutErrors
         Counter64,
      pr1646v2PortSwMCMibCntrsOutBandwidth15sec
         Integer32,
      pr1646v2PortSwMCMibCntrsOutBandwidth30sec
         Integer32,
      pr1646v2PortSwMCMibCntrsOutBandwidth1min
         Integer32,
      pr1646v2PortSwMCMibCntrsOutBandwidth2min
         Integer32,
      pr1646v2PortSwMCMibCntrsOutBandwidth5min
         Integer32
      }

pr1646v2PortSwMCMibCntrsTableIx OBJECT-TYPE
   SYNTAX      TableIndex
   MAX-ACCESS  not-accessible
   STATUS      current
   DESCRIPTION
      ""
   ::= {pr1646v2PortSwMCMibCntrsEntry 11}

pr1646v2PortSwMCMibCntrsPortName OBJECT-TYPE
   SYNTAX      INTEGER
               {
               hwPortu1 (1),
               hwPortu2 (2),
               hwPortu3 (3),
               hwPortu4 (4),
               hwPortu5 (5),
               hwPortu6 (6),
               hwPortuLocalPort (255)
               }
   MAX-ACCESS  read-only
   STATUS      current
   DESCRIPTION
      "Path: ethernet1.performance.mibCounters.portName

       Possibilities:
               hwPort_1   (1)
               hwPort_2   (2)
               hwPort_3   (3)
               hwPort_4   (4)
               hwPort_5   (5)
               hwPort_6   (6)
               hwPort_LocalPort   (255)"
   ::= {pr1646v2PortSwMCMibCntrsEntry 16777216}

pr1646v2PortSwMCMibCntrsInOctets OBJECT-TYPE
   SYNTAX      Counter64
   MAX-ACCESS  read-only
   STATUS      current
   DESCRIPTION
      "Path: ethernet1.performance.mibCounters.ifInOctets

       64 bit unsigned wrappable counter."
   ::= {pr1646v2PortSwMCMibCntrsEntry 1828716544}

pr1646v2PortSwMCMibCntrsInUcast OBJECT-TYPE
   SYNTAX      Counter64
   MAX-ACCESS  read-only
   STATUS      current
   DESCRIPTION
      "Path: ethernet1.performance.mibCounters.ifInUcastPkts

       64 bit unsigned wrappable counter."
   ::= {pr1646v2PortSwMCMibCntrsEntry 1845493760}

pr1646v2PortSwMCMibCntrsInNUcastPkts OBJECT-TYPE
   SYNTAX      Counter64
   MAX-ACCESS  read-only
   STATUS      current
   DESCRIPTION
      "Path: ethernet1.performance.mibCounters.ifInNUcastPkts

       64 bit unsigned wrappable counter."
   ::= {pr1646v2PortSwMCMibCntrsEntry 1862270976}

pr1646v2PortSwMCMibCntrsInDiscards OBJECT-TYPE
   SYNTAX      Counter64
   MAX-ACCESS  read-only
   STATUS      current
   DESCRIPTION
      "Path: ethernet1.performance.mibCounters.ifInDiscards

       64 bit unsigned wrappable counter."
   ::= {pr1646v2PortSwMCMibCntrsEntry 1879048192}

pr1646v2PortSwMCMibCntrsInPause OBJECT-TYPE
   SYNTAX      Counter64
   MAX-ACCESS  read-only
   STATUS      current
   DESCRIPTION
      "Path: ethernet1.performance.mibCounters.ifInPause

       64 bit unsigned wrappable counter."
   ::= {pr1646v2PortSwMCMibCntrsEntry 4194304000}

pr1646v2PortSwMCMibCntrsInErrors OBJECT-TYPE
   SYNTAX      Counter64
   MAX-ACCESS  read-only
   STATUS      current
   DESCRIPTION
      "Path: ethernet1.performance.mibCounters.ifInErrors

       64 bit unsigned wrappable counter."
   ::= {pr1646v2PortSwMCMibCntrsEntry 1895825408}

pr1646v2PortSwMCMibCntrsInBandwidth15sec OBJECT-TYPE
   SYNTAX      Integer32
   MAX-ACCESS  read-only
   STATUS      current
   DESCRIPTION
      "Path: ethernet1.performance.mibCounters.ifInBandwidth.15sec

       unit name = bps
       formula = 8 * ; 8 /"
   ::= {pr1646v2PortSwMCMibCntrsEntry 3037003776}

pr1646v2PortSwMCMibCntrsInBandwidth30sec OBJECT-TYPE
   SYNTAX      Integer32
   MAX-ACCESS  read-only
   STATUS      current
   DESCRIPTION
      "Path: ethernet1.performance.mibCounters.ifInBandwidth.30sec

       unit name = bps
       formula = 8 * ; 8 /"
   ::= {pr1646v2PortSwMCMibCntrsEntry 3037331456}

pr1646v2PortSwMCMibCntrsInBandwidth1min OBJECT-TYPE
   SYNTAX      Integer32
   MAX-ACCESS  read-only
   STATUS      current
   DESCRIPTION
      "Path: ethernet1.performance.mibCounters.ifInBandwidth.1min

       unit name = bps
       formula = 8 * ; 8 /"
   ::= {pr1646v2PortSwMCMibCntrsEntry 3037986816}

pr1646v2PortSwMCMibCntrsInBandwidth2min OBJECT-TYPE
   SYNTAX      Integer32
   MAX-ACCESS  read-only
   STATUS      current
   DESCRIPTION
      "Path: ethernet1.performance.mibCounters.ifInBandwidth.2min

       unit name = bps
       formula = 8 * ; 8 /"
   ::= {pr1646v2PortSwMCMibCntrsEntry 3039297536}

pr1646v2PortSwMCMibCntrsInBandwidth5min OBJECT-TYPE
   SYNTAX      Integer32
   MAX-ACCESS  read-only
   STATUS      current
   DESCRIPTION
      "Path: ethernet1.performance.mibCounters.ifInBandwidth.5min

       unit name = bps
       formula = 8 * ; 8 /"
   ::= {pr1646v2PortSwMCMibCntrsEntry 3043229696}

pr1646v2PortSwMCMibCntrsOutOctets OBJECT-TYPE
   SYNTAX      Counter64
   MAX-ACCESS  read-only
   STATUS      current
   DESCRIPTION
      "Path: ethernet1.performance.mibCounters.ifOutOctets

       64 bit unsigned wrappable counter."
   ::= {pr1646v2PortSwMCMibCntrsEntry 1929379840}

pr1646v2PortSwMCMibCntrsOutUcastPkts OBJECT-TYPE
   SYNTAX      Counter64
   MAX-ACCESS  read-only
   STATUS      current
   DESCRIPTION
      "Path: ethernet1.performance.mibCounters.ifOutUcastPkts

       64 bit unsigned wrappable counter."
   ::= {pr1646v2PortSwMCMibCntrsEntry 1946157056}

pr1646v2PortSwMCMibCntrsOutNUcastPkts OBJECT-TYPE
   SYNTAX      Counter64
   MAX-ACCESS  read-only
   STATUS      current
   DESCRIPTION
      "Path: ethernet1.performance.mibCounters.ifOutNUcastPkts

       64 bit unsigned wrappable counter."
   ::= {pr1646v2PortSwMCMibCntrsEntry 1962934272}

pr1646v2PortSwMCMibCntrsOutDiscards OBJECT-TYPE
   SYNTAX      Counter64
   MAX-ACCESS  read-only
   STATUS      current
   DESCRIPTION
      "Path: ethernet1.performance.mibCounters.ifOutDiscards

       64 bit unsigned wrappable counter."
   ::= {pr1646v2PortSwMCMibCntrsEntry 1979711488}

pr1646v2PortSwMCMibCntrsOutPause OBJECT-TYPE
   SYNTAX      Counter64
   MAX-ACCESS  read-only
   STATUS      current
   DESCRIPTION
      "Path: ethernet1.performance.mibCounters.ifOutPause

       64 bit unsigned wrappable counter."
   ::= {pr1646v2PortSwMCMibCntrsEntry 4211081216}

pr1646v2PortSwMCMibCntrsOutErrors OBJECT-TYPE
   SYNTAX      Counter64
   MAX-ACCESS  read-only
   STATUS      current
   DESCRIPTION
      "Path: ethernet1.performance.mibCounters.ifOutErrors

       64 bit unsigned wrappable counter."
   ::= {pr1646v2PortSwMCMibCntrsEntry 1996488704}

pr1646v2PortSwMCMibCntrsOutBandwidth15sec OBJECT-TYPE
   SYNTAX      Integer32
   MAX-ACCESS  read-only
   STATUS      current
   DESCRIPTION
      "Path: ethernet1.performance.mibCounters.ifOutBandwidth.15sec

       unit name = bps
       formula = 8 * ; 8 /"
   ::= {pr1646v2PortSwMCMibCntrsEntry 3053780992}

pr1646v2PortSwMCMibCntrsOutBandwidth30sec OBJECT-TYPE
   SYNTAX      Integer32
   MAX-ACCESS  read-only
   STATUS      current
   DESCRIPTION
      "Path: ethernet1.performance.mibCounters.ifOutBandwidth.30sec

       unit name = bps
       formula = 8 * ; 8 /"
   ::= {pr1646v2PortSwMCMibCntrsEntry 3054108672}

pr1646v2PortSwMCMibCntrsOutBandwidth1min OBJECT-TYPE
   SYNTAX      Integer32
   MAX-ACCESS  read-only
   STATUS      current
   DESCRIPTION
      "Path: ethernet1.performance.mibCounters.ifOutBandwidth.1min

       unit name = bps
       formula = 8 * ; 8 /"
   ::= {pr1646v2PortSwMCMibCntrsEntry 3054764032}

pr1646v2PortSwMCMibCntrsOutBandwidth2min OBJECT-TYPE
   SYNTAX      Integer32
   MAX-ACCESS  read-only
   STATUS      current
   DESCRIPTION
      "Path: ethernet1.performance.mibCounters.ifOutBandwidth.2min

       unit name = bps
       formula = 8 * ; 8 /"
   ::= {pr1646v2PortSwMCMibCntrsEntry 3056074752}

pr1646v2PortSwMCMibCntrsOutBandwidth5min OBJECT-TYPE
   SYNTAX      Integer32
   MAX-ACCESS  read-only
   STATUS      current
   DESCRIPTION
      "Path: ethernet1.performance.mibCounters.ifOutBandwidth.5min

       unit name = bps
       formula = 8 * ; 8 /"
   ::= {pr1646v2PortSwMCMibCntrsEntry 3060006912}

pr1646v2PortSwMCMibCntrsH2P OBJECT-TYPE
   SYNTAX      SEQUENCE OF Pr1646v2PortSwMCMibCntrsH2PEntry
   MAX-ACCESS  not-accessible
   STATUS      current
   DESCRIPTION
      ""
   ::= {pr1646v2PortSwMCMibCntrs 2046820352}

pr1646v2PortSwMCMibCntrsH2PEntry OBJECT-TYPE
   SYNTAX      Pr1646v2PortSwMCMibCntrsH2PEntry
   MAX-ACCESS  not-accessible
   STATUS      current
   DESCRIPTION
      ""
   INDEX      { pr1646v2PortSwMCMibCntrsTableIx,
                pr1646v2PortSwMCMibCntrsH2PTableIx }
   ::= {pr1646v2PortSwMCMibCntrsH2P 1}

Pr1646v2PortSwMCMibCntrsH2PEntry ::=
   SEQUENCE
      {
      pr1646v2PortSwMCMibCntrsH2PTableIx
         TableIndex,
      pr1646v2PortSwMCMibCntrsH2PSysUpTime
         TimeTicks,
      pr1646v2PortSwMCMibCntrsH2PIfUpTime
         TimeTicks,
      pr1646v2PortSwMCMibCntrsH2PIfStatChanges
         Counter32,
      pr1646v2PortSwMCMibCntrsH2PIfInOctets
         Counter64,
      pr1646v2PortSwMCMibCntrsH2PIfInUCPkts
         Counter64,
      pr1646v2PortSwMCMibCntrsH2PIfInNUCPkts
         Counter64,
      pr1646v2PortSwMCMibCntrsH2PIfInDiscards
         Counter64,
      pr1646v2PortSwMCMibCntrsH2PIfInErrors
         Counter64,
      pr1646v2PortSwMCMibCntrsH2PIfInBandwidth
         Integer32,
      pr1646v2PortSwMCMibCntrsH2PIfOutOctets
         Counter64,
      pr1646v2PortSwMCMibCntrsH2PIfOutUCPkts
         Counter64,
      pr1646v2PortSwMCMibCntrsH2PIfOutNUCPkts
         Counter64,
      pr1646v2PortSwMCMibCntrsH2PIfOutDiscards
         Counter64,
      pr1646v2PortSwMCMibCntrsH2PIfOutErrors
         Counter64,
      pr1646v2PortSwMCMibCntrsH2PIfOutBandwidth
         Integer32,
      pr1646v2PortSwMCMibCntrsH2PIfErrSec
         Counter32
      }

pr1646v2PortSwMCMibCntrsH2PTableIx OBJECT-TYPE
   SYNTAX      TableIndex
   MAX-ACCESS  not-accessible
   STATUS      current
   DESCRIPTION
      ""
   ::= {pr1646v2PortSwMCMibCntrsH2PEntry 11}

pr1646v2PortSwMCMibCntrsH2PSysUpTime OBJECT-TYPE
   SYNTAX      TimeTicks
   MAX-ACCESS  read-only
   STATUS      current
   DESCRIPTION
      "Path: ethernet1.performance.mibCounters.h2Performance.sysUpTime

       Time in centi-second."
   ::= {pr1646v2PortSwMCMibCntrsH2PEntry 16777216}

pr1646v2PortSwMCMibCntrsH2PIfUpTime OBJECT-TYPE
   SYNTAX      TimeTicks
   MAX-ACCESS  read-only
   STATUS      current
   DESCRIPTION
      "Path: ethernet1.performance.mibCounters.h2Performance.ifUpTime

       Time in centi-second."
   ::= {pr1646v2PortSwMCMibCntrsH2PEntry 33554432}

pr1646v2PortSwMCMibCntrsH2PIfStatChanges OBJECT-TYPE
   SYNTAX      Counter32
   MAX-ACCESS  read-only
   STATUS      current
   DESCRIPTION
      "Path: ethernet1.performance.mibCounters.h2Performance.ifStatusChanges

       32 bit unsigned wrappable counter."
   ::= {pr1646v2PortSwMCMibCntrsH2PEntry 50331648}

pr1646v2PortSwMCMibCntrsH2PIfInOctets OBJECT-TYPE
   SYNTAX      Counter64
   MAX-ACCESS  read-only
   STATUS      current
   DESCRIPTION
      "Path: ethernet1.performance.mibCounters.h2Performance.ifInOctets

       64 bit unsigned wrappable counter."
   ::= {pr1646v2PortSwMCMibCntrsH2PEntry 67108864}

pr1646v2PortSwMCMibCntrsH2PIfInUCPkts OBJECT-TYPE
   SYNTAX      Counter64
   MAX-ACCESS  read-only
   STATUS      current
   DESCRIPTION
      "Path: ethernet1.performance.mibCounters.h2Performance.ifInUcastPkts

       64 bit unsigned wrappable counter."
   ::= {pr1646v2PortSwMCMibCntrsH2PEntry 83886080}

pr1646v2PortSwMCMibCntrsH2PIfInNUCPkts OBJECT-TYPE
   SYNTAX      Counter64
   MAX-ACCESS  read-only
   STATUS      current
   DESCRIPTION
      "Path: ethernet1.performance.mibCounters.h2Performance.ifInNUcastPkts

       64 bit unsigned wrappable counter."
   ::= {pr1646v2PortSwMCMibCntrsH2PEntry 100663296}

pr1646v2PortSwMCMibCntrsH2PIfInDiscards OBJECT-TYPE
   SYNTAX      Counter64
   MAX-ACCESS  read-only
   STATUS      current
   DESCRIPTION
      "Path: ethernet1.performance.mibCounters.h2Performance.ifInDiscards

       64 bit unsigned wrappable counter."
   ::= {pr1646v2PortSwMCMibCntrsH2PEntry 117440512}

pr1646v2PortSwMCMibCntrsH2PIfInErrors OBJECT-TYPE
   SYNTAX      Counter64
   MAX-ACCESS  read-only
   STATUS      current
   DESCRIPTION
      "Path: ethernet1.performance.mibCounters.h2Performance.ifInErrors

       64 bit unsigned wrappable counter."
   ::= {pr1646v2PortSwMCMibCntrsH2PEntry 134217728}

pr1646v2PortSwMCMibCntrsH2PIfInBandwidth OBJECT-TYPE
   SYNTAX      Integer32
   MAX-ACCESS  read-only
   STATUS      current
   DESCRIPTION
      "Path: ethernet1.performance.mibCounters.h2Performance.ifInBandwidth

       unit name = bps
       formula = 8 * ; 8 /"
   ::= {pr1646v2PortSwMCMibCntrsH2PEntry 268435456}

pr1646v2PortSwMCMibCntrsH2PIfOutOctets OBJECT-TYPE
   SYNTAX      Counter64
   MAX-ACCESS  read-only
   STATUS      current
   DESCRIPTION
      "Path: ethernet1.performance.mibCounters.h2Performance.ifOutOctets

       64 bit unsigned wrappable counter."
   ::= {pr1646v2PortSwMCMibCntrsH2PEntry 167772160}

pr1646v2PortSwMCMibCntrsH2PIfOutUCPkts OBJECT-TYPE
   SYNTAX      Counter64
   MAX-ACCESS  read-only
   STATUS      current
   DESCRIPTION
      "Path: ethernet1.performance.mibCounters.h2Performance.ifOutUcastPkts

       64 bit unsigned wrappable counter."
   ::= {pr1646v2PortSwMCMibCntrsH2PEntry 184549376}

pr1646v2PortSwMCMibCntrsH2PIfOutNUCPkts OBJECT-TYPE
   SYNTAX      Counter64
   MAX-ACCESS  read-only
   STATUS      current
   DESCRIPTION
      "Path: ethernet1.performance.mibCounters.h2Performance.ifOutNUcastPkts

       64 bit unsigned wrappable counter."
   ::= {pr1646v2PortSwMCMibCntrsH2PEntry 201326592}

pr1646v2PortSwMCMibCntrsH2PIfOutDiscards OBJECT-TYPE
   SYNTAX      Counter64
   MAX-ACCESS  read-only
   STATUS      current
   DESCRIPTION
      "Path: ethernet1.performance.mibCounters.h2Performance.ifOutDiscards

       64 bit unsigned wrappable counter."
   ::= {pr1646v2PortSwMCMibCntrsH2PEntry 218103808}

pr1646v2PortSwMCMibCntrsH2PIfOutErrors OBJECT-TYPE
   SYNTAX      Counter64
   MAX-ACCESS  read-only
   STATUS      current
   DESCRIPTION
      "Path: ethernet1.performance.mibCounters.h2Performance.ifOutErrors

       64 bit unsigned wrappable counter."
   ::= {pr1646v2PortSwMCMibCntrsH2PEntry 234881024}

pr1646v2PortSwMCMibCntrsH2PIfOutBandwidth OBJECT-TYPE
   SYNTAX      Integer32
   MAX-ACCESS  read-only
   STATUS      current
   DESCRIPTION
      "Path: ethernet1.performance.mibCounters.h2Performance.ifOutBandwidth

       unit name = bps
       formula = 8 * ; 8 /"
   ::= {pr1646v2PortSwMCMibCntrsH2PEntry 285212672}

pr1646v2PortSwMCMibCntrsH2PIfErrSec OBJECT-TYPE
   SYNTAX      Counter32
   MAX-ACCESS  read-only
   STATUS      current
   DESCRIPTION
      "Path: ethernet1.performance.mibCounters.h2Performance.ifErrSec

       32 bit unsigned wrappable counter."
   ::= {pr1646v2PortSwMCMibCntrsH2PEntry 251658240}

pr1646v2PortSwMCMibCntrsH24P OBJECT-TYPE
   SYNTAX      SEQUENCE OF Pr1646v2PortSwMCMibCntrsH24PEntry
   MAX-ACCESS  not-accessible
   STATUS      current
   DESCRIPTION
      ""
   ::= {pr1646v2PortSwMCMibCntrs 2063597568}

pr1646v2PortSwMCMibCntrsH24PEntry OBJECT-TYPE
   SYNTAX      Pr1646v2PortSwMCMibCntrsH24PEntry
   MAX-ACCESS  not-accessible
   STATUS      current
   DESCRIPTION
      ""
   INDEX      { pr1646v2PortSwMCMibCntrsTableIx,
                pr1646v2PortSwMCMibCntrsH24PTableIx }
   ::= {pr1646v2PortSwMCMibCntrsH24P 1}

Pr1646v2PortSwMCMibCntrsH24PEntry ::=
   SEQUENCE
      {
      pr1646v2PortSwMCMibCntrsH24PTableIx
         TableIndex,
      pr1646v2PortSwMCMibCntrsH24PSysUpTime
         TimeTicks,
      pr1646v2PortSwMCMibCntrsH24PIfUpTime
         TimeTicks,
      pr1646v2PortSwMCMibCntrsH24PIfStatChanges
         Counter32,
      pr1646v2PortSwMCMibCntrsH24PIfInOctets
         Counter64,
      pr1646v2PortSwMCMibCntrsH24PIfInUCPkts
         Counter64,
      pr1646v2PortSwMCMibCntrsH24PIfInNUCPkts
         Counter64,
      pr1646v2PortSwMCMibCntrsH24PIfInDiscards
         Counter64,
      pr1646v2PortSwMCMibCntrsH24PIfInErrors
         Counter64,
      pr1646v2PortSwMCMibCntrsH24PIfInBandwidth
         Integer32,
      pr1646v2PortSwMCMibCntrsH24PIfOutOctets
         Counter64,
      pr1646v2PortSwMCMibCntrsH24PIfOutUCPkts
         Counter64,
      pr1646v2PortSwMCMibCntrsH24PIfOutNUCPkts
         Counter64,
      pr1646v2PortSwMCMibCntrsH24PIfOutDiscards
         Counter64,
      pr1646v2PortSwMCMibCntrsH24PIfOutErrors
         Counter64,
      pr1646v2PortSwMCMibCntrsH24PIfOutBandwidth
         Integer32,
      pr1646v2PortSwMCMibCntrsH24PIfErrSec
         Counter32
      }

pr1646v2PortSwMCMibCntrsH24PTableIx OBJECT-TYPE
   SYNTAX      TableIndex
   MAX-ACCESS  not-accessible
   STATUS      current
   DESCRIPTION
      ""
   ::= {pr1646v2PortSwMCMibCntrsH24PEntry 11}

pr1646v2PortSwMCMibCntrsH24PSysUpTime OBJECT-TYPE
   SYNTAX      TimeTicks
   MAX-ACCESS  read-only
   STATUS      current
   DESCRIPTION
      "Path: ethernet1.performance.mibCounters.h24Performance.sysUpTime

       Time in centi-second."
   ::= {pr1646v2PortSwMCMibCntrsH24PEntry 16777216}

pr1646v2PortSwMCMibCntrsH24PIfUpTime OBJECT-TYPE
   SYNTAX      TimeTicks
   MAX-ACCESS  read-only
   STATUS      current
   DESCRIPTION
      "Path: ethernet1.performance.mibCounters.h24Performance.ifUpTime

       Time in centi-second."
   ::= {pr1646v2PortSwMCMibCntrsH24PEntry 33554432}

pr1646v2PortSwMCMibCntrsH24PIfStatChanges OBJECT-TYPE
   SYNTAX      Counter32
   MAX-ACCESS  read-only
   STATUS      current
   DESCRIPTION
      "Path: ethernet1.performance.mibCounters.h24Performance.ifStatusChanges

       32 bit unsigned wrappable counter."
   ::= {pr1646v2PortSwMCMibCntrsH24PEntry 50331648}

pr1646v2PortSwMCMibCntrsH24PIfInOctets OBJECT-TYPE
   SYNTAX      Counter64
   MAX-ACCESS  read-only
   STATUS      current
   DESCRIPTION
      "Path: ethernet1.performance.mibCounters.h24Performance.ifInOctets

       64 bit unsigned wrappable counter."
   ::= {pr1646v2PortSwMCMibCntrsH24PEntry 67108864}

pr1646v2PortSwMCMibCntrsH24PIfInUCPkts OBJECT-TYPE
   SYNTAX      Counter64
   MAX-ACCESS  read-only
   STATUS      current
   DESCRIPTION
      "Path: ethernet1.performance.mibCounters.h24Performance.ifInUcastPkts

       64 bit unsigned wrappable counter."
   ::= {pr1646v2PortSwMCMibCntrsH24PEntry 83886080}

pr1646v2PortSwMCMibCntrsH24PIfInNUCPkts OBJECT-TYPE
   SYNTAX      Counter64
   MAX-ACCESS  read-only
   STATUS      current
   DESCRIPTION
      "Path: ethernet1.performance.mibCounters.h24Performance.ifInNUcastPkts

       64 bit unsigned wrappable counter."
   ::= {pr1646v2PortSwMCMibCntrsH24PEntry 100663296}

pr1646v2PortSwMCMibCntrsH24PIfInDiscards OBJECT-TYPE
   SYNTAX      Counter64
   MAX-ACCESS  read-only
   STATUS      current
   DESCRIPTION
      "Path: ethernet1.performance.mibCounters.h24Performance.ifInDiscards

       64 bit unsigned wrappable counter."
   ::= {pr1646v2PortSwMCMibCntrsH24PEntry 117440512}

pr1646v2PortSwMCMibCntrsH24PIfInErrors OBJECT-TYPE
   SYNTAX      Counter64
   MAX-ACCESS  read-only
   STATUS      current
   DESCRIPTION
      "Path: ethernet1.performance.mibCounters.h24Performance.ifInErrors

       64 bit unsigned wrappable counter."
   ::= {pr1646v2PortSwMCMibCntrsH24PEntry 134217728}

pr1646v2PortSwMCMibCntrsH24PIfInBandwidth OBJECT-TYPE
   SYNTAX      Integer32
   MAX-ACCESS  read-only
   STATUS      current
   DESCRIPTION
      "Path: ethernet1.performance.mibCounters.h24Performance.ifInBandwidth

       unit name = bps
       formula = 8 * ; 8 /"
   ::= {pr1646v2PortSwMCMibCntrsH24PEntry 268435456}

pr1646v2PortSwMCMibCntrsH24PIfOutOctets OBJECT-TYPE
   SYNTAX      Counter64
   MAX-ACCESS  read-only
   STATUS      current
   DESCRIPTION
      "Path: ethernet1.performance.mibCounters.h24Performance.ifOutOctets

       64 bit unsigned wrappable counter."
   ::= {pr1646v2PortSwMCMibCntrsH24PEntry 167772160}

pr1646v2PortSwMCMibCntrsH24PIfOutUCPkts OBJECT-TYPE
   SYNTAX      Counter64
   MAX-ACCESS  read-only
   STATUS      current
   DESCRIPTION
      "Path: ethernet1.performance.mibCounters.h24Performance.ifOutUcastPkts

       64 bit unsigned wrappable counter."
   ::= {pr1646v2PortSwMCMibCntrsH24PEntry 184549376}

pr1646v2PortSwMCMibCntrsH24PIfOutNUCPkts OBJECT-TYPE
   SYNTAX      Counter64
   MAX-ACCESS  read-only
   STATUS      current
   DESCRIPTION
      "Path: ethernet1.performance.mibCounters.h24Performance.ifOutNUcastPkts

       64 bit unsigned wrappable counter."
   ::= {pr1646v2PortSwMCMibCntrsH24PEntry 201326592}

pr1646v2PortSwMCMibCntrsH24PIfOutDiscards OBJECT-TYPE
   SYNTAX      Counter64
   MAX-ACCESS  read-only
   STATUS      current
   DESCRIPTION
      "Path: ethernet1.performance.mibCounters.h24Performance.ifOutDiscards

       64 bit unsigned wrappable counter."
   ::= {pr1646v2PortSwMCMibCntrsH24PEntry 218103808}

pr1646v2PortSwMCMibCntrsH24PIfOutErrors OBJECT-TYPE
   SYNTAX      Counter64
   MAX-ACCESS  read-only
   STATUS      current
   DESCRIPTION
      "Path: ethernet1.performance.mibCounters.h24Performance.ifOutErrors

       64 bit unsigned wrappable counter."
   ::= {pr1646v2PortSwMCMibCntrsH24PEntry 234881024}

pr1646v2PortSwMCMibCntrsH24PIfOutBandwidth OBJECT-TYPE
   SYNTAX      Integer32
   MAX-ACCESS  read-only
   STATUS      current
   DESCRIPTION
      "Path: ethernet1.performance.mibCounters.h24Performance.ifOutBandwidth

       unit name = bps
       formula = 8 * ; 8 /"
   ::= {pr1646v2PortSwMCMibCntrsH24PEntry 285212672}

pr1646v2PortSwMCMibCntrsH24PIfErrSec OBJECT-TYPE
   SYNTAX      Counter32
   MAX-ACCESS  read-only
   STATUS      current
   DESCRIPTION
      "Path: ethernet1.performance.mibCounters.h24Performance.ifErrSec

       32 bit unsigned wrappable counter."
   ::= {pr1646v2PortSwMCMibCntrsH24PEntry 251658240}

pr1646v2PortSwMCMibCntrsD7P OBJECT-TYPE
   SYNTAX      SEQUENCE OF Pr1646v2PortSwMCMibCntrsD7PEntry
   MAX-ACCESS  not-accessible
   STATUS      current
   DESCRIPTION
      ""
   ::= {pr1646v2PortSwMCMibCntrs 2080374784}

pr1646v2PortSwMCMibCntrsD7PEntry OBJECT-TYPE
   SYNTAX      Pr1646v2PortSwMCMibCntrsD7PEntry
   MAX-ACCESS  not-accessible
   STATUS      current
   DESCRIPTION
      ""
   INDEX      { pr1646v2PortSwMCMibCntrsTableIx,
                pr1646v2PortSwMCMibCntrsD7PTableIx }
   ::= {pr1646v2PortSwMCMibCntrsD7P 1}

Pr1646v2PortSwMCMibCntrsD7PEntry ::=
   SEQUENCE
      {
      pr1646v2PortSwMCMibCntrsD7PTableIx
         TableIndex,
      pr1646v2PortSwMCMibCntrsD7PSysUpTime
         TimeTicks,
      pr1646v2PortSwMCMibCntrsD7PIfUpTime
         TimeTicks,
      pr1646v2PortSwMCMibCntrsD7PIfStatChanges
         Counter32,
      pr1646v2PortSwMCMibCntrsD7PIfInOctets
         Counter64,
      pr1646v2PortSwMCMibCntrsD7PIfInUCPkts
         Counter64,
      pr1646v2PortSwMCMibCntrsD7PIfInNUCPkts
         Counter64,
      pr1646v2PortSwMCMibCntrsD7PIfInDiscards
         Counter64,
      pr1646v2PortSwMCMibCntrsD7PIfInErrors
         Counter64,
      pr1646v2PortSwMCMibCntrsD7PIfInBandwidth
         Integer32,
      pr1646v2PortSwMCMibCntrsD7PIfOutOctets
         Counter64,
      pr1646v2PortSwMCMibCntrsD7PIfOutUCPkts
         Counter64,
      pr1646v2PortSwMCMibCntrsD7PIfOutNUCPkts
         Counter64,
      pr1646v2PortSwMCMibCntrsD7PIfOutDiscards
         Counter64,
      pr1646v2PortSwMCMibCntrsD7PIfOutErrors
         Counter64,
      pr1646v2PortSwMCMibCntrsD7PIfOutBandwidth
         Integer32,
      pr1646v2PortSwMCMibCntrsD7PIfErrSec
         Counter32
      }

pr1646v2PortSwMCMibCntrsD7PTableIx OBJECT-TYPE
   SYNTAX      TableIndex
   MAX-ACCESS  not-accessible
   STATUS      current
   DESCRIPTION
      ""
   ::= {pr1646v2PortSwMCMibCntrsD7PEntry 11}

pr1646v2PortSwMCMibCntrsD7PSysUpTime OBJECT-TYPE
   SYNTAX      TimeTicks
   MAX-ACCESS  read-only
   STATUS      current
   DESCRIPTION
      "Path: ethernet1.performance.mibCounters.d7Performance.sysUpTime

       Time in centi-second."
   ::= {pr1646v2PortSwMCMibCntrsD7PEntry 16777216}

pr1646v2PortSwMCMibCntrsD7PIfUpTime OBJECT-TYPE
   SYNTAX      TimeTicks
   MAX-ACCESS  read-only
   STATUS      current
   DESCRIPTION
      "Path: ethernet1.performance.mibCounters.d7Performance.ifUpTime

       Time in centi-second."
   ::= {pr1646v2PortSwMCMibCntrsD7PEntry 33554432}

pr1646v2PortSwMCMibCntrsD7PIfStatChanges OBJECT-TYPE
   SYNTAX      Counter32
   MAX-ACCESS  read-only
   STATUS      current
   DESCRIPTION
      "Path: ethernet1.performance.mibCounters.d7Performance.ifStatusChanges

       32 bit unsigned wrappable counter."
   ::= {pr1646v2PortSwMCMibCntrsD7PEntry 50331648}

pr1646v2PortSwMCMibCntrsD7PIfInOctets OBJECT-TYPE
   SYNTAX      Counter64
   MAX-ACCESS  read-only
   STATUS      current
   DESCRIPTION
      "Path: ethernet1.performance.mibCounters.d7Performance.ifInOctets

       64 bit unsigned wrappable counter."
   ::= {pr1646v2PortSwMCMibCntrsD7PEntry 67108864}

pr1646v2PortSwMCMibCntrsD7PIfInUCPkts OBJECT-TYPE
   SYNTAX      Counter64
   MAX-ACCESS  read-only
   STATUS      current
   DESCRIPTION
      "Path: ethernet1.performance.mibCounters.d7Performance.ifInUcastPkts

       64 bit unsigned wrappable counter."
   ::= {pr1646v2PortSwMCMibCntrsD7PEntry 83886080}

pr1646v2PortSwMCMibCntrsD7PIfInNUCPkts OBJECT-TYPE
   SYNTAX      Counter64
   MAX-ACCESS  read-only
   STATUS      current
   DESCRIPTION
      "Path: ethernet1.performance.mibCounters.d7Performance.ifInNUcastPkts

       64 bit unsigned wrappable counter."
   ::= {pr1646v2PortSwMCMibCntrsD7PEntry 100663296}

pr1646v2PortSwMCMibCntrsD7PIfInDiscards OBJECT-TYPE
   SYNTAX      Counter64
   MAX-ACCESS  read-only
   STATUS      current
   DESCRIPTION
      "Path: ethernet1.performance.mibCounters.d7Performance.ifInDiscards

       64 bit unsigned wrappable counter."
   ::= {pr1646v2PortSwMCMibCntrsD7PEntry 117440512}

pr1646v2PortSwMCMibCntrsD7PIfInErrors OBJECT-TYPE
   SYNTAX      Counter64
   MAX-ACCESS  read-only
   STATUS      current
   DESCRIPTION
      "Path: ethernet1.performance.mibCounters.d7Performance.ifInErrors

       64 bit unsigned wrappable counter."
   ::= {pr1646v2PortSwMCMibCntrsD7PEntry 134217728}

pr1646v2PortSwMCMibCntrsD7PIfInBandwidth OBJECT-TYPE
   SYNTAX      Integer32
   MAX-ACCESS  read-only
   STATUS      current
   DESCRIPTION
      "Path: ethernet1.performance.mibCounters.d7Performance.ifInBandwidth

       unit name = bps
       formula = 8 * ; 8 /"
   ::= {pr1646v2PortSwMCMibCntrsD7PEntry 268435456}

pr1646v2PortSwMCMibCntrsD7PIfOutOctets OBJECT-TYPE
   SYNTAX      Counter64
   MAX-ACCESS  read-only
   STATUS      current
   DESCRIPTION
      "Path: ethernet1.performance.mibCounters.d7Performance.ifOutOctets

       64 bit unsigned wrappable counter."
   ::= {pr1646v2PortSwMCMibCntrsD7PEntry 167772160}

pr1646v2PortSwMCMibCntrsD7PIfOutUCPkts OBJECT-TYPE
   SYNTAX      Counter64
   MAX-ACCESS  read-only
   STATUS      current
   DESCRIPTION
      "Path: ethernet1.performance.mibCounters.d7Performance.ifOutUcastPkts

       64 bit unsigned wrappable counter."
   ::= {pr1646v2PortSwMCMibCntrsD7PEntry 184549376}

pr1646v2PortSwMCMibCntrsD7PIfOutNUCPkts OBJECT-TYPE
   SYNTAX      Counter64
   MAX-ACCESS  read-only
   STATUS      current
   DESCRIPTION
      "Path: ethernet1.performance.mibCounters.d7Performance.ifOutNUcastPkts

       64 bit unsigned wrappable counter."
   ::= {pr1646v2PortSwMCMibCntrsD7PEntry 201326592}

pr1646v2PortSwMCMibCntrsD7PIfOutDiscards OBJECT-TYPE
   SYNTAX      Counter64
   MAX-ACCESS  read-only
   STATUS      current
   DESCRIPTION
      "Path: ethernet1.performance.mibCounters.d7Performance.ifOutDiscards

       64 bit unsigned wrappable counter."
   ::= {pr1646v2PortSwMCMibCntrsD7PEntry 218103808}

pr1646v2PortSwMCMibCntrsD7PIfOutErrors OBJECT-TYPE
   SYNTAX      Counter64
   MAX-ACCESS  read-only
   STATUS      current
   DESCRIPTION
      "Path: ethernet1.performance.mibCounters.d7Performance.ifOutErrors

       64 bit unsigned wrappable counter."
   ::= {pr1646v2PortSwMCMibCntrsD7PEntry 234881024}

pr1646v2PortSwMCMibCntrsD7PIfOutBandwidth OBJECT-TYPE
   SYNTAX      Integer32
   MAX-ACCESS  read-only
   STATUS      current
   DESCRIPTION
      "Path: ethernet1.performance.mibCounters.d7Performance.ifOutBandwidth

       unit name = bps
       formula = 8 * ; 8 /"
   ::= {pr1646v2PortSwMCMibCntrsD7PEntry 285212672}

pr1646v2PortSwMCMibCntrsD7PIfErrSec OBJECT-TYPE
   SYNTAX      Counter32
   MAX-ACCESS  read-only
   STATUS      current
   DESCRIPTION
      "Path: ethernet1.performance.mibCounters.d7Performance.ifErrSec

       32 bit unsigned wrappable counter."
   ::= {pr1646v2PortSwMCMibCntrsD7PEntry 251658240}



fr1646v2PortSwMC OBJECT IDENTIFIER ::= {r1646v2PortSwMC 13}


fr1646v2PortSwMCAlarm OBJECT IDENTIFIER ::= {fr1646v2PortSwMC 207}

fr1646v2PortSwMCAlarmSSC OBJECT IDENTIFIER ::= {fr1646v2PortSwMCAlarm 1}

fr1646v2PortSwMCAlarmEntry OBJECT IDENTIFIER ::= {fr1646v2PortSwMCAlarmSSC 1}

fr1646v2PortSwMCAlarmDiscriminator OBJECT-TYPE
   SYNTAX      Integer32
   MAX-ACCESS  read-only
   STATUS      current
   DESCRIPTION
      "Path: ethernet1.alarms.alarmInfo.discriminator"
   ::= {fr1646v2PortSwMCAlarmEntry 16777216}

fr1646v2PortSwMCAlarmCurrent OBJECT-TYPE
   SYNTAX      Integer32
   MAX-ACCESS  read-only
   STATUS      current
   DESCRIPTION
      "Path: ethernet1.alarms.alarmInfo.currentAlarms

       Bit meanings:
               bit 0 = linkDown"
   ::= {fr1646v2PortSwMCAlarmEntry 33554432}

fr1646v2PortSwMCAlarmPrevious OBJECT-TYPE
   SYNTAX      Integer32
   MAX-ACCESS  read-only
   STATUS      current
   DESCRIPTION
      "Path: ethernet1.alarms.alarmInfo.previousAlarms

       Bit meanings:
               bit 0 = linkDown"
   ::= {fr1646v2PortSwMCAlarmEntry 50331648}

fr1646v2PortSwMCAlarmMask OBJECT-TYPE
   SYNTAX      Integer32
   MAX-ACCESS  read-only
   STATUS      current
   DESCRIPTION
      "Path: ethernet1.alarms.alarmInfo.alarmMask

       Bit meanings:
               bit 0 = linkDown"
   ::= {fr1646v2PortSwMCAlarmEntry 67108864}

fr1646v2PortSwMCAlarmLevLinkDown OBJECT-TYPE
   SYNTAX      Integer32
   MAX-ACCESS  read-only
   STATUS      current
   DESCRIPTION
      "Path: ethernet1.alarms.alarmInfo.alarmLevel.linkDown"
   ::= {fr1646v2PortSwMCAlarmEntry 83951616}


fr1646v2PortSwMCAlarmE2 OBJECT IDENTIFIER ::= {fr1646v2PortSwMCAlarm 2}

fr1646v2PortSwMCAlarmE2Entry OBJECT IDENTIFIER ::= {fr1646v2PortSwMCAlarmE2 1}

fr1646v2PortSwMCAlarmE2LinkDown OBJECT IDENTIFIER ::= {fr1646v2PortSwMCAlarmE2Entry 10}

fr1646v2PortSwMCAlarmE2LinkDownPfx OBJECT IDENTIFIER ::= {fr1646v2PortSwMCAlarmE2LinkDown 0}

fr1646v2PortSwMCAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitchMC'
                (root='router1646') has changed from the ON to the OFF state."
   ::= {fr1646v2PortSwMCAlarmE2LinkDownPfx 1}

fr1646v2PortSwMCAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitchMC'
                (root='router1646') has changed from the OFF to the ON state."
   ::= {fr1646v2PortSwMCAlarmE2LinkDownPfx 2}



ar1646v2PortSwMC OBJECT IDENTIFIER ::= {r1646v2PortSwMC 16}


ar1646v2PortSwMCClearCounters OBJECT-TYPE
   SYNTAX      Integer32
   MAX-ACCESS  read-write
   STATUS      current
   DESCRIPTION
      "Path: ethernet1.actions.clearCounters
       Info: reset counters"
   ::= {ar1646v2PortSwMC 263}


ar1646v2PortSwMCSalAction OBJECT-TYPE
   SYNTAX      Integer32
   MAX-ACCESS  read-write
   STATUS      current
   DESCRIPTION
      "Path: ethernet1.actions.salAction
       Info: action in the debug group"
   ::= {ar1646v2PortSwMC 97}


ar1646v2PortSwMCRegAction OBJECT-TYPE
   SYNTAX      Integer32
   MAX-ACCESS  read-write
   STATUS      current
   DESCRIPTION
      "Path: ethernet1.actions.regAction
       Info: action in the debug group"
   ::= {ar1646v2PortSwMC 95}


ar1646v2PortSwMCMeasTemp OBJECT-TYPE
   SYNTAX      Integer32
   MAX-ACCESS  read-write
   STATUS      current
   DESCRIPTION
      "Path: ethernet1.actions.measTemp
       Info: action in the debug group"
   ::= {ar1646v2PortSwMC 85}


ar1646v2PortSwMCClearAction OBJECT-TYPE
   SYNTAX      Integer32
   MAX-ACCESS  read-write
   STATUS      current
   DESCRIPTION
      "Path: ethernet1.actions.clearAction
       Info: action in the debug group"
   ::= {ar1646v2PortSwMC 84}


ar1646v2PortSwMCClearSwitchCache OBJECT-TYPE
   SYNTAX      Integer32
   MAX-ACCESS  read-write
   STATUS      current
   DESCRIPTION
      "Path: ethernet1.actions.clearSwitchCache
       Info: Clear the dnamic entries in the swith MAC cache"
   ::= {ar1646v2PortSwMC 81}


ar1646v2PortSwMCEnableRds OBJECT-TYPE
   SYNTAX      Integer32
   MAX-ACCESS  read-write
   STATUS      current
   DESCRIPTION
      "Path: ethernet1.actions.enableRds
       Info: action in the debug group"
   ::= {ar1646v2PortSwMC 367}


ar1646v2PortSwMCDisableRds OBJECT-TYPE
   SYNTAX      Integer32
   MAX-ACCESS  read-write
   STATUS      current
   DESCRIPTION
      "Path: ethernet1.actions.disableRds
       Info: action in the debug group"
   ::= {ar1646v2PortSwMC 366}


ar1646v2PortSwMCEnableTds OBJECT-TYPE
   SYNTAX      Integer32
   MAX-ACCESS  read-write
   STATUS      current
   DESCRIPTION
      "Path: ethernet1.actions.enableTds
       Info: action in the debug group"
   ::= {ar1646v2PortSwMC 365}


ar1646v2PortSwMCDisableTds OBJECT-TYPE
   SYNTAX      Integer32
   MAX-ACCESS  read-write
   STATUS      current
   DESCRIPTION
      "Path: ethernet1.actions.disableTds
       Info: action in the debug group"
   ::= {ar1646v2PortSwMC 364}


ar1646v2PortSwMCClearTsecStats OBJECT-TYPE
   SYNTAX      Integer32
   MAX-ACCESS  read-write
   STATUS      current
   DESCRIPTION
      "Path: ethernet1.actions.clearTsecStats
       Info: action in the debug group"
   ::= {ar1646v2PortSwMC 363}


ar1646v2PortSwMCStopTsecStats OBJECT-TYPE
   SYNTAX      Integer32
   MAX-ACCESS  read-write
   STATUS      current
   DESCRIPTION
      "Path: ethernet1.actions.stopTsecStats
       Info: action in the debug group"
   ::= {ar1646v2PortSwMC 362}


ar1646v2PortSwMCStartTsecStats OBJECT-TYPE
   SYNTAX      Integer32
   MAX-ACCESS  read-write
   STATUS      current
   DESCRIPTION
      "Path: ethernet1.actions.startTsecStats
       Info: action in the debug group"
   ::= {ar1646v2PortSwMC 361}


ar1646v2PortSwMCClearDebugCounters OBJECT-TYPE
   SYNTAX      Integer32
   MAX-ACCESS  read-write
   STATUS      current
   DESCRIPTION
      "Path: ethernet1.actions.clearDebugCounters
       Info: action in the debug group"
   ::= {ar1646v2PortSwMC 76}



END
