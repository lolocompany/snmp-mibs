OneAccess-R1645v2-4652-EthPortSwI DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2EthPortSwI OBJECT IDENTIFIER ::= {r1645Rootv2 4652}

r1645v2EthPortSwIMOProp OBJECT-TYPE
   SYNTAX      SEQUENCE OF R1645v2EthPortSwIMOPropEntry
   MAX-ACCESS  not-accessible
   STATUS      current
   DESCRIPTION
      ""
   ::= {r1645v2EthPortSwI 1}

r1645v2EthPortSwIMOPropEntry OBJECT-TYPE
   SYNTAX      R1645v2EthPortSwIMOPropEntry
   MAX-ACCESS  not-accessible
   STATUS      current
   DESCRIPTION
      ""
   INDEX      { r1645v2EthPortSwIMOPropGlobalIx }
   ::= {r1645v2EthPortSwIMOProp 1}

R1645v2EthPortSwIMOPropEntry ::=
   SEQUENCE
      {
      r1645v2EthPortSwIMOPropPath
         ContainmentPath,
      r1645v2EthPortSwIMOPropRev
         ObjectRevision,
      r1645v2EthPortSwIMOPropGlobalIx
         GlobalIndex
      }

r1645v2EthPortSwIMOPropPath OBJECT-TYPE
   SYNTAX      ContainmentPath
   MAX-ACCESS  read-only
   STATUS      current
   DESCRIPTION
      "Textual description of the containment tree from the instance of
       the root object down to the instance of the current object."
   ::= {r1645v2EthPortSwIMOPropEntry 3}

r1645v2EthPortSwIMOPropRev OBJECT-TYPE
   SYNTAX      ObjectRevision
   MAX-ACCESS  read-only
   STATUS      current
   DESCRIPTION
      "This value corresponds with the revision of the MANAGED OBJECT."
   ::= {r1645v2EthPortSwIMOPropEntry 4}

r1645v2EthPortSwIMOPropGlobalIx OBJECT-TYPE
   SYNTAX      GlobalIndex
   MAX-ACCESS  read-only
   STATUS      current
   DESCRIPTION
      "The value of the tlsCntTreeGlobalIndex of the MANAGED OBJECT."
   ::= {r1645v2EthPortSwIMOPropEntry 10}



er1645v2EthPortSwI OBJECT IDENTIFIER ::= {r1645v2EthPortSwI 11}


er1645v2EthPortSwIRemark OBJECT IDENTIFIER ::= {er1645v2EthPortSwI 321}

er1645v2EthPortSwIRemarkTable OBJECT-TYPE
   SYNTAX      SEQUENCE OF Er1645v2EthPortSwIRemarkEntry
   MAX-ACCESS  not-accessible
   STATUS      current
   DESCRIPTION
      "intfRemark"
   ::= {er1645v2EthPortSwIRemark 1}

er1645v2EthPortSwIRemarkEntry OBJECT-TYPE
   SYNTAX      Er1645v2EthPortSwIRemarkEntry
   MAX-ACCESS  not-accessible
   STATUS      current
   DESCRIPTION
      ""
   INDEX      { er1645v2EthPortSwIRemarkGlobalIx }
   ::= {er1645v2EthPortSwIRemarkTable 1}

Er1645v2EthPortSwIRemarkEntry ::=
   SEQUENCE
      {
      er1645v2EthPortSwIRemarkGlobalIx
         GlobalIndex,
      er1645v2EthPortSwIRemarkValue
         DisplayString
      }

er1645v2EthPortSwIRemarkGlobalIx OBJECT-TYPE
   SYNTAX      GlobalIndex
   MAX-ACCESS  not-accessible
   STATUS      current
   DESCRIPTION
      "The value of the tlsCntTreeGlobalIndex of the MANAGED OBJECT."
   ::= {er1645v2EthPortSwIRemarkEntry 10}

er1645v2EthPortSwIRemarkValue OBJECT-TYPE
   SYNTAX      DisplayString
   MAX-ACCESS  read-write
   STATUS      current
   DESCRIPTION
      "Path: swPort.editConf.remark"
   ::= {er1645v2EthPortSwIRemarkEntry 2147483648}


er1645v2EthPortSwIArp OBJECT IDENTIFIER ::= {er1645v2EthPortSwI 19}

er1645v2EthPortSwIArpSSCTable OBJECT-TYPE
   SYNTAX      SEQUENCE OF Er1645v2EthPortSwIArpEntry
   MAX-ACCESS  not-accessible
   STATUS      current
   DESCRIPTION
      "ethernet related config parameters"
   ::= {er1645v2EthPortSwIArp 1}

er1645v2EthPortSwIArpEntry OBJECT-TYPE
   SYNTAX      Er1645v2EthPortSwIArpEntry
   MAX-ACCESS  not-accessible
   STATUS      current
   DESCRIPTION
      ""
   INDEX      { er1645v2EthPortSwIArpGlobalIx }
   ::= {er1645v2EthPortSwIArpSSCTable 1}

Er1645v2EthPortSwIArpEntry ::=
   SEQUENCE
      {
      er1645v2EthPortSwIArpGlobalIx
         GlobalIndex,
      er1645v2EthPortSwIArpTimeOut
         TimeTicks,
      er1645v2EthPortSwIArpProxyArp
         INTEGER
      }

er1645v2EthPortSwIArpGlobalIx OBJECT-TYPE
   SYNTAX      GlobalIndex
   MAX-ACCESS  not-accessible
   STATUS      current
   DESCRIPTION
      "The value of the tlsCntTreeGlobalIndex of the MANAGED OBJECT."
   ::= {er1645v2EthPortSwIArpEntry 10}

er1645v2EthPortSwIArpTimeOut OBJECT-TYPE
   SYNTAX      TimeTicks
   MAX-ACCESS  read-write
   STATUS      current
   DESCRIPTION
      "Path: swPort.editConf.arp.timeOut

       Time in centi-second."
   ::= {er1645v2EthPortSwIArpEntry 201326592}

er1645v2EthPortSwIArpProxyArp OBJECT-TYPE
   SYNTAX      INTEGER
               {
               disabled (0),
               enabled (1)
               }
   MAX-ACCESS  read-write
   STATUS      current
   DESCRIPTION
      "Path: swPort.editConf.arp.proxyArp

       Possibilities:
               disabled   (0)
               enabled   (1)"
   ::= {er1645v2EthPortSwIArpEntry 838860800}

er1645v2EthPortSwIArpStaticArp OBJECT-TYPE
   SYNTAX      SEQUENCE OF Er1645v2EthPortSwIArpStaticArpEntry
   MAX-ACCESS  not-accessible
   STATUS      current
   DESCRIPTION
      ""
   ::= {er1645v2EthPortSwIArp 50331648}

er1645v2EthPortSwIArpStaticArpEntry OBJECT-TYPE
   SYNTAX      Er1645v2EthPortSwIArpStaticArpEntry
   MAX-ACCESS  not-accessible
   STATUS      current
   DESCRIPTION
      ""
   INDEX      { er1645v2EthPortSwIArpStaticArpGlobalIx,
                er1645v2EthPortSwIArpStaticArpTableIx }
   ::= {er1645v2EthPortSwIArpStaticArp 1}

Er1645v2EthPortSwIArpStaticArpEntry ::=
   SEQUENCE
      {
      er1645v2EthPortSwIArpStaticArpActions
         VariableLengthTableActions,
      er1645v2EthPortSwIArpStaticArpGlobalIx
         GlobalIndex,
      er1645v2EthPortSwIArpStaticArpTableIx
         TableIndex,
      er1645v2EthPortSwIArpStaticArpMacAddress
         OCTET STRING,
      er1645v2EthPortSwIArpStaticArpIpAddress
         IpAddress
      }

er1645v2EthPortSwIArpStaticArpActions OBJECT-TYPE
   SYNTAX      VariableLengthTableActions
   MAX-ACCESS  read-write
   STATUS      current
   DESCRIPTION
      "By way of this field, some manipulations
       on this table may be performed."
   ::= {er1645v2EthPortSwIArpStaticArpEntry 2}

er1645v2EthPortSwIArpStaticArpGlobalIx OBJECT-TYPE
   SYNTAX      GlobalIndex
   MAX-ACCESS  not-accessible
   STATUS      current
   DESCRIPTION
      "The value of the tlsCntTreeGlobalIndex of the MANAGED OBJECT."
   ::= {er1645v2EthPortSwIArpStaticArpEntry 10}

er1645v2EthPortSwIArpStaticArpTableIx OBJECT-TYPE
   SYNTAX      TableIndex
   MAX-ACCESS  not-accessible
   STATUS      current
   DESCRIPTION
      ""
   ::= {er1645v2EthPortSwIArpStaticArpEntry 11}

er1645v2EthPortSwIArpStaticArpMacAddress OBJECT-TYPE
   SYNTAX      OCTET STRING
   MAX-ACCESS  read-write
   STATUS      current
   DESCRIPTION
      "Path: swPort.editConf.arp.staticArp.macAddress

       MAC address."
   ::= {er1645v2EthPortSwIArpStaticArpEntry 16777216}

er1645v2EthPortSwIArpStaticArpIpAddress OBJECT-TYPE
   SYNTAX      IpAddress
   MAX-ACCESS  read-write
   STATUS      current
   DESCRIPTION
      "Path: swPort.editConf.arp.staticArp.ipAddress"
   ::= {er1645v2EthPortSwIArpStaticArpEntry 33554432}


er1645v2EthPortSwIBrC OBJECT IDENTIFIER ::= {er1645v2EthPortSwI 27}

er1645v2EthPortSwIBrCSSCTable OBJECT-TYPE
   SYNTAX      SEQUENCE OF Er1645v2EthPortSwIBrCEntry
   MAX-ACCESS  not-accessible
   STATUS      current
   DESCRIPTION
      "Set bridging parameters"
   ::= {er1645v2EthPortSwIBrC 1}

er1645v2EthPortSwIBrCEntry OBJECT-TYPE
   SYNTAX      Er1645v2EthPortSwIBrCEntry
   MAX-ACCESS  not-accessible
   STATUS      current
   DESCRIPTION
      ""
   INDEX      { er1645v2EthPortSwIBrCGlobalIx }
   ::= {er1645v2EthPortSwIBrCSSCTable 1}

Er1645v2EthPortSwIBrCEntry ::=
   SEQUENCE
      {
      er1645v2EthPortSwIBrCGlobalIx
         GlobalIndex,
      er1645v2EthPortSwIBrCAccessList
         DisplayString,
      er1645v2EthPortSwIBrCInAccessList
         DisplayString,
      er1645v2EthPortSwIBrCTp
         DisplayString,
      er1645v2EthPortSwIBrCBridgeGroup
         DisplayString,
      er1645v2EthPortSwIBrCLimBC
         INTEGER,
      er1645v2EthPortSwIBrCPrivateMode
         INTEGER,
      er1645v2EthPortSwIBrCLearning
         INTEGER,
      er1645v2EthPortSwIBrCMaxCacheSize
         INTEGER,
      er1645v2EthPortSwIBrCRelearnDropOnRelearn
         INTEGER,
      er1645v2EthPortSwIBrCRelearnShutdownThreshold
         Integer32,
      er1645v2EthPortSwIBrCRelearnShutdownTime
         TimeTicks,
      er1645v2EthPortSwIBrCRelearnLoopDetection
         INTEGER,
      er1645v2EthPortSwIBrCRelearnLoopDetectionInterval
         TimeTicks,
      er1645v2EthPortSwIBrCVlanMemberShip
         INTEGER,
      er1645v2EthPortSwIBrCDot1adType
         INTEGER,
      er1645v2EthPortSwIBrCPriority
         Integer32,
      er1645v2EthPortSwIBrCPathCost
         Integer32,
      er1645v2EthPortSwIBrCInternalPathCost
         Integer32,
      er1645v2EthPortSwIBrCTCD
         INTEGER,
      er1645v2EthPortSwIBrCRestrictedRole
         INTEGER,
      er1645v2EthPortSwIBrCAdminEdge
         INTEGER,
      er1645v2EthPortSwIBrCMgmtInline
         INTEGER,
      er1645v2EthPortSwIBrCL2ptMode
         INTEGER,
      er1645v2EthPortSwIBrCL2ptProtocols
         Integer32,
      er1645v2EthPortSwIBrCL2ptDestMac
         OCTET STRING,
      er1645v2EthPortSwIBrCL2ptCos
         INTEGER,
      er1645v2EthPortSwIBrCL2ptDropThrStp
         INTEGER,
      er1645v2EthPortSwIBrCL2ptDropThrLldp
         INTEGER,
      er1645v2EthPortSwIBrCL2ptDropThrOam
         INTEGER,
      er1645v2EthPortSwIBrCL2ptDropThrCdp
         INTEGER,
      er1645v2EthPortSwIBrCL2ptDropThrVtp
         INTEGER,
      er1645v2EthPortSwIBrCL2ptDropThrLacp
         INTEGER,
      er1645v2EthPortSwIBrCL2ptDropThrEfmOam
         INTEGER,
      er1645v2EthPortSwIBrCL2ptDropThrPvst
         INTEGER,
      er1645v2EthPortSwIBrCL2ptDropThrMmrp
         INTEGER,
      er1645v2EthPortSwIBrCL2ptDropThrMvrp
         INTEGER,
      er1645v2EthPortSwIBrCL2ptDropThrGvrp
         INTEGER,
      er1645v2EthPortSwIBrCL2ptDropThrGmrp
         INTEGER,
      er1645v2EthPortSwIBrCL2ptDropThrDtp
         INTEGER,
      er1645v2EthPortSwIBrCL2ptDropThrPagp
         INTEGER,
      er1645v2EthPortSwIBrCL2ptDropThrUdld
         INTEGER
      }

er1645v2EthPortSwIBrCGlobalIx OBJECT-TYPE
   SYNTAX      GlobalIndex
   MAX-ACCESS  not-accessible
   STATUS      current
   DESCRIPTION
      "The value of the tlsCntTreeGlobalIndex of the MANAGED OBJECT."
   ::= {er1645v2EthPortSwIBrCEntry 10}

er1645v2EthPortSwIBrCAccessList OBJECT-TYPE
   SYNTAX      DisplayString
   MAX-ACCESS  read-write
   STATUS      current
   DESCRIPTION
      "Path: swPort.editConf.bridging.accessList"
   ::= {er1645v2EthPortSwIBrCEntry 83886080}

er1645v2EthPortSwIBrCInAccessList OBJECT-TYPE
   SYNTAX      DisplayString
   MAX-ACCESS  read-write
   STATUS      current
   DESCRIPTION
      "Path: swPort.editConf.bridging.inAccessList"
   ::= {er1645v2EthPortSwIBrCEntry 251658240}

er1645v2EthPortSwIBrCTp OBJECT-TYPE
   SYNTAX      DisplayString
   MAX-ACCESS  read-write
   STATUS      current
   DESCRIPTION
      "Path: swPort.editConf.bridging.trafficPolicy"
   ::= {er1645v2EthPortSwIBrCEntry 100663296}

er1645v2EthPortSwIBrCBridgeGroup OBJECT-TYPE
   SYNTAX      DisplayString
   MAX-ACCESS  read-write
   STATUS      current
   DESCRIPTION
      "Path: swPort.editConf.bridging.bridgeGroup"
   ::= {er1645v2EthPortSwIBrCEntry 117440512}

er1645v2EthPortSwIBrCLimBC OBJECT-TYPE
   SYNTAX      INTEGER
               {
               disabled (0),
               enabled (1)
               }
   MAX-ACCESS  read-write
   STATUS      current
   DESCRIPTION
      "Path: swPort.editConf.bridging.limitBroadcasts

       Possibilities:
               disabled   (0)
               enabled   (1)"
   ::= {er1645v2EthPortSwIBrCEntry 134217728}

er1645v2EthPortSwIBrCPrivateMode OBJECT-TYPE
   SYNTAX      INTEGER
               {
               disabled (0),
               enabled (1)
               }
   MAX-ACCESS  read-write
   STATUS      current
   DESCRIPTION
      "Path: swPort.editConf.bridging.privateMode

       Possibilities:
               disabled   (0)
               enabled   (1)"
   ::= {er1645v2EthPortSwIBrCEntry 419430400}

er1645v2EthPortSwIBrCLearning OBJECT-TYPE
   SYNTAX      INTEGER
               {
               disabled (0),
               enabled (1)
               }
   MAX-ACCESS  read-write
   STATUS      current
   DESCRIPTION
      "Path: swPort.editConf.bridging.learning

       Possibilities:
               disabled   (0)
               enabled   (1)"
   ::= {er1645v2EthPortSwIBrCEntry 201326592}

er1645v2EthPortSwIBrCMaxCacheSize OBJECT-TYPE
   SYNTAX      INTEGER
               {
               unlimited (0)
               }
   MAX-ACCESS  read-write
   STATUS      current
   DESCRIPTION
      "Path: swPort.editConf.bridging.maxCacheSize

       Possibilities:
               unlimited   (0)"
   ::= {er1645v2EthPortSwIBrCEntry 218103808}

er1645v2EthPortSwIBrCRelearnDropOnRelearn OBJECT-TYPE
   SYNTAX      INTEGER
               {
               disabled (0),
               enabled (1)
               }
   MAX-ACCESS  read-write
   STATUS      current
   DESCRIPTION
      "Path: swPort.editConf.bridging.relearn.dropOnRelearn

       Possibilities:
               disabled   (0)
               enabled   (1)"
   ::= {er1645v2EthPortSwIBrCEntry 234946560}

er1645v2EthPortSwIBrCRelearnShutdownThreshold OBJECT-TYPE
   SYNTAX      Integer32
   MAX-ACCESS  read-write
   STATUS      current
   DESCRIPTION
      "Path: swPort.editConf.bridging.relearn.shutdownThreshold"
   ::= {er1645v2EthPortSwIBrCEntry 235012096}

er1645v2EthPortSwIBrCRelearnShutdownTime OBJECT-TYPE
   SYNTAX      TimeTicks
   MAX-ACCESS  read-write
   STATUS      current
   DESCRIPTION
      "Path: swPort.editConf.bridging.relearn.shutdownTime

       Time in centi-second."
   ::= {er1645v2EthPortSwIBrCEntry 235077632}

er1645v2EthPortSwIBrCRelearnLoopDetection OBJECT-TYPE
   SYNTAX      INTEGER
               {
               disabled (0),
               passive (1),
               active (2)
               }
   MAX-ACCESS  read-write
   STATUS      current
   DESCRIPTION
      "Path: swPort.editConf.bridging.relearn.loopDetection

       Possibilities:
               disabled   (0)
               passive   (1)
               active   (2)"
   ::= {er1645v2EthPortSwIBrCEntry 235143168}

er1645v2EthPortSwIBrCRelearnLoopDetectionInterval OBJECT-TYPE
   SYNTAX      TimeTicks
   MAX-ACCESS  read-write
   STATUS      current
   DESCRIPTION
      "Path: swPort.editConf.bridging.relearn.loopDetectionInterval

       Time in centi-second."
   ::= {er1645v2EthPortSwIBrCEntry 235208704}

er1645v2EthPortSwIBrCVlanMemberShip OBJECT-TYPE
   SYNTAX      INTEGER
               {
               all (0),
               none (1),
               grouped (2)
               }
   MAX-ACCESS  read-write
   STATUS      current
   DESCRIPTION
      "Path: swPort.editConf.bridging.vlanMemberShip

       Possibilities:
               all   (0)
               none   (1)
               grouped   (2)"
   ::= {er1645v2EthPortSwIBrCEntry 318767104}

er1645v2EthPortSwIBrCDot1adType OBJECT-TYPE
   SYNTAX      INTEGER
               {
               slOPTg (0),
               cPort (4),
               sPort (1),
               nni (2)
               }
   MAX-ACCESS  read-write
   STATUS      current
   DESCRIPTION
      "Path: swPort.editConf.bridging.dot1ad.type

       Possibilities:
               <OPT>   (0)
               cPort   (4)
               sPort   (1)
               nni   (2)"
   ::= {er1645v2EthPortSwIBrCEntry 503382016}

er1645v2EthPortSwIBrCPriority OBJECT-TYPE
   SYNTAX      Integer32
   MAX-ACCESS  read-write
   STATUS      current
   DESCRIPTION
      "Path: swPort.editConf.bridging.priority"
   ::= {er1645v2EthPortSwIBrCEntry 33554432}

er1645v2EthPortSwIBrCPathCost OBJECT-TYPE
   SYNTAX      Integer32
   MAX-ACCESS  read-write
   STATUS      current
   DESCRIPTION
      "Path: swPort.editConf.bridging.pathCost"
   ::= {er1645v2EthPortSwIBrCEntry 50331648}

er1645v2EthPortSwIBrCInternalPathCost OBJECT-TYPE
   SYNTAX      Integer32
   MAX-ACCESS  read-write
   STATUS      current
   DESCRIPTION
      "Path: swPort.editConf.bridging.internalPathCost"
   ::= {er1645v2EthPortSwIBrCEntry 301989888}

er1645v2EthPortSwIBrCTCD OBJECT-TYPE
   SYNTAX      INTEGER
               {
               disabled (0),
               enabled (1)
               }
   MAX-ACCESS  read-write
   STATUS      current
   DESCRIPTION
      "Path: swPort.editConf.bridging.topologyChangeDetection

       Possibilities:
               disabled   (0)
               enabled   (1)"
   ::= {er1645v2EthPortSwIBrCEntry 67108864}

er1645v2EthPortSwIBrCRestrictedRole OBJECT-TYPE
   SYNTAX      INTEGER
               {
               disabled (0),
               enabled (1)
               }
   MAX-ACCESS  read-write
   STATUS      current
   DESCRIPTION
      "Path: swPort.editConf.bridging.restrictedRole

       Possibilities:
               disabled   (0)
               enabled   (1)"
   ::= {er1645v2EthPortSwIBrCEntry 335544320}

er1645v2EthPortSwIBrCAdminEdge OBJECT-TYPE
   SYNTAX      INTEGER
               {
               disabled (0),
               enabled (1)
               }
   MAX-ACCESS  read-write
   STATUS      current
   DESCRIPTION
      "Path: swPort.editConf.bridging.adminEdge

       Possibilities:
               disabled   (0)
               enabled   (1)"
   ::= {er1645v2EthPortSwIBrCEntry 268435456}

er1645v2EthPortSwIBrCMgmtInline OBJECT-TYPE
   SYNTAX      INTEGER
               {
               disabled (0),
               enabled (1)
               }
   MAX-ACCESS  read-write
   STATUS      current
   DESCRIPTION
      "Path: swPort.editConf.bridging.mgmtInline

       Possibilities:
               disabled   (0)
               enabled   (1)"
   ::= {er1645v2EthPortSwIBrCEntry 369098752}

er1645v2EthPortSwIBrCL2ptMode OBJECT-TYPE
   SYNTAX      INTEGER
               {
               disabled (0),
               enabled (1)
               }
   MAX-ACCESS  read-write
   STATUS      current
   DESCRIPTION
      "Path: swPort.editConf.bridging.l2ProtTunnel.mode

       Possibilities:
               disabled   (0)
               enabled   (1)"
   ::= {er1645v2EthPortSwIBrCEntry 403701760}

er1645v2EthPortSwIBrCL2ptProtocols OBJECT-TYPE
   SYNTAX      Integer32
   MAX-ACCESS  read-write
   STATUS      current
   DESCRIPTION
      "Path: swPort.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2EthPortSwIBrCEntry 404750336}

er1645v2EthPortSwIBrCL2ptDestMac OBJECT-TYPE
   SYNTAX      OCTET STRING
   MAX-ACCESS  read-write
   STATUS      current
   DESCRIPTION
      "Path: swPort.editConf.bridging.l2ProtTunnel.destinationMac

       MAC address."
   ::= {er1645v2EthPortSwIBrCEntry 405798912}

er1645v2EthPortSwIBrCL2ptCos OBJECT-TYPE
   SYNTAX      INTEGER
               {
               unchanged (255)
               }
   MAX-ACCESS  read-write
   STATUS      current
   DESCRIPTION
      "Path: swPort.editConf.bridging.l2ProtTunnel.cos

       Possibilities:
               unchanged   (255)"
   ::= {er1645v2EthPortSwIBrCEntry 406847488}

er1645v2EthPortSwIBrCL2ptDropThrStp OBJECT-TYPE
   SYNTAX      INTEGER
               {
               unlimited (0)
               }
   UNITS       "packets/sec"
   MAX-ACCESS  read-write
   STATUS      current
   DESCRIPTION
      "Path: swPort.editConf.bridging.l2ProtTunnel.dropThresholds.stp

       unit name = packets/sec

       Possibilities:
               unlimited   (0)"
   ::= {er1645v2EthPortSwIBrCEntry 407900160}

er1645v2EthPortSwIBrCL2ptDropThrLldp OBJECT-TYPE
   SYNTAX      INTEGER
               {
               unlimited (0)
               }
   UNITS       "packets/sec"
   MAX-ACCESS  read-write
   STATUS      current
   DESCRIPTION
      "Path: swPort.editConf.bridging.l2ProtTunnel.dropThresholds.lldp

       unit name = packets/sec

       Possibilities:
               unlimited   (0)"
   ::= {er1645v2EthPortSwIBrCEntry 407904256}

er1645v2EthPortSwIBrCL2ptDropThrOam OBJECT-TYPE
   SYNTAX      INTEGER
               {
               unlimited (0)
               }
   UNITS       "packets/sec"
   MAX-ACCESS  read-write
   STATUS      current
   DESCRIPTION
      "Path: swPort.editConf.bridging.l2ProtTunnel.dropThresholds.oam

       unit name = packets/sec

       Possibilities:
               unlimited   (0)"
   ::= {er1645v2EthPortSwIBrCEntry 407908352}

er1645v2EthPortSwIBrCL2ptDropThrCdp OBJECT-TYPE
   SYNTAX      INTEGER
               {
               unlimited (0)
               }
   UNITS       "packets/sec"
   MAX-ACCESS  read-write
   STATUS      current
   DESCRIPTION
      "Path: swPort.editConf.bridging.l2ProtTunnel.dropThresholds.cdp

       unit name = packets/sec

       Possibilities:
               unlimited   (0)"
   ::= {er1645v2EthPortSwIBrCEntry 407912448}

er1645v2EthPortSwIBrCL2ptDropThrVtp OBJECT-TYPE
   SYNTAX      INTEGER
               {
               unlimited (0)
               }
   UNITS       "packets/sec"
   MAX-ACCESS  read-write
   STATUS      current
   DESCRIPTION
      "Path: swPort.editConf.bridging.l2ProtTunnel.dropThresholds.vtp

       unit name = packets/sec

       Possibilities:
               unlimited   (0)"
   ::= {er1645v2EthPortSwIBrCEntry 407916544}

er1645v2EthPortSwIBrCL2ptDropThrLacp OBJECT-TYPE
   SYNTAX      INTEGER
               {
               unlimited (0)
               }
   UNITS       "packets/sec"
   MAX-ACCESS  read-write
   STATUS      current
   DESCRIPTION
      "Path: swPort.editConf.bridging.l2ProtTunnel.dropThresholds.lacp

       unit name = packets/sec

       Possibilities:
               unlimited   (0)"
   ::= {er1645v2EthPortSwIBrCEntry 407920640}

er1645v2EthPortSwIBrCL2ptDropThrEfmOam OBJECT-TYPE
   SYNTAX      INTEGER
               {
               unlimited (0)
               }
   UNITS       "packets/sec"
   MAX-ACCESS  read-write
   STATUS      current
   DESCRIPTION
      "Path: swPort.editConf.bridging.l2ProtTunnel.dropThresholds.efmOam

       unit name = packets/sec

       Possibilities:
               unlimited   (0)"
   ::= {er1645v2EthPortSwIBrCEntry 407924736}

er1645v2EthPortSwIBrCL2ptDropThrPvst OBJECT-TYPE
   SYNTAX      INTEGER
               {
               unlimited (0)
               }
   UNITS       "packets/sec"
   MAX-ACCESS  read-write
   STATUS      current
   DESCRIPTION
      "Path: swPort.editConf.bridging.l2ProtTunnel.dropThresholds.pvst

       unit name = packets/sec

       Possibilities:
               unlimited   (0)"
   ::= {er1645v2EthPortSwIBrCEntry 407928832}

er1645v2EthPortSwIBrCL2ptDropThrMmrp OBJECT-TYPE
   SYNTAX      INTEGER
               {
               unlimited (0)
               }
   UNITS       "packets/sec"
   MAX-ACCESS  read-write
   STATUS      current
   DESCRIPTION
      "Path: swPort.editConf.bridging.l2ProtTunnel.dropThresholds.mmrp

       unit name = packets/sec

       Possibilities:
               unlimited   (0)"
   ::= {er1645v2EthPortSwIBrCEntry 407932928}

er1645v2EthPortSwIBrCL2ptDropThrMvrp OBJECT-TYPE
   SYNTAX      INTEGER
               {
               unlimited (0)
               }
   UNITS       "packets/sec"
   MAX-ACCESS  read-write
   STATUS      current
   DESCRIPTION
      "Path: swPort.editConf.bridging.l2ProtTunnel.dropThresholds.mvrp

       unit name = packets/sec

       Possibilities:
               unlimited   (0)"
   ::= {er1645v2EthPortSwIBrCEntry 407937024}

er1645v2EthPortSwIBrCL2ptDropThrGvrp OBJECT-TYPE
   SYNTAX      INTEGER
               {
               unlimited (0)
               }
   UNITS       "packets/sec"
   MAX-ACCESS  read-write
   STATUS      current
   DESCRIPTION
      "Path: swPort.editConf.bridging.l2ProtTunnel.dropThresholds.gvrp

       unit name = packets/sec

       Possibilities:
               unlimited   (0)"
   ::= {er1645v2EthPortSwIBrCEntry 407941120}

er1645v2EthPortSwIBrCL2ptDropThrGmrp OBJECT-TYPE
   SYNTAX      INTEGER
               {
               unlimited (0)
               }
   UNITS       "packets/sec"
   MAX-ACCESS  read-write
   STATUS      current
   DESCRIPTION
      "Path: swPort.editConf.bridging.l2ProtTunnel.dropThresholds.gmrp

       unit name = packets/sec

       Possibilities:
               unlimited   (0)"
   ::= {er1645v2EthPortSwIBrCEntry 407945216}

er1645v2EthPortSwIBrCL2ptDropThrDtp OBJECT-TYPE
   SYNTAX      INTEGER
               {
               unlimited (0)
               }
   UNITS       "packets/sec"
   MAX-ACCESS  read-write
   STATUS      current
   DESCRIPTION
      "Path: swPort.editConf.bridging.l2ProtTunnel.dropThresholds.dtp

       unit name = packets/sec

       Possibilities:
               unlimited   (0)"
   ::= {er1645v2EthPortSwIBrCEntry 407949312}

er1645v2EthPortSwIBrCL2ptDropThrPagp OBJECT-TYPE
   SYNTAX      INTEGER
               {
               unlimited (0)
               }
   UNITS       "packets/sec"
   MAX-ACCESS  read-write
   STATUS      current
   DESCRIPTION
      "Path: swPort.editConf.bridging.l2ProtTunnel.dropThresholds.pagp

       unit name = packets/sec

       Possibilities:
               unlimited   (0)"
   ::= {er1645v2EthPortSwIBrCEntry 407953408}

er1645v2EthPortSwIBrCL2ptDropThrUdld OBJECT-TYPE
   SYNTAX      INTEGER
               {
               unlimited (0)
               }
   UNITS       "packets/sec"
   MAX-ACCESS  read-write
   STATUS      current
   DESCRIPTION
      "Path: swPort.editConf.bridging.l2ProtTunnel.dropThresholds.udld

       unit name = packets/sec

       Possibilities:
               unlimited   (0)"
   ::= {er1645v2EthPortSwIBrCEntry 407957504}


er1645v2EthPortSwIVlanTagging OBJECT IDENTIFIER ::= {er1645v2EthPortSwI 14}

er1645v2EthPortSwIVlanTaggingSSCTable OBJECT-TYPE
   SYNTAX      SEQUENCE OF Er1645v2EthPortSwIVlanTaggingEntry
   MAX-ACCESS  not-accessible
   STATUS      current
   DESCRIPTION
      "vlan tagging config"
   ::= {er1645v2EthPortSwIVlanTagging 1}

er1645v2EthPortSwIVlanTaggingEntry OBJECT-TYPE
   SYNTAX      Er1645v2EthPortSwIVlanTaggingEntry
   MAX-ACCESS  not-accessible
   STATUS      current
   DESCRIPTION
      ""
   INDEX      { er1645v2EthPortSwIVlanTaggingGlobalIx }
   ::= {er1645v2EthPortSwIVlanTaggingSSCTable 1}

Er1645v2EthPortSwIVlanTaggingEntry ::=
   SEQUENCE
      {
      er1645v2EthPortSwIVlanTaggingGlobalIx
         GlobalIndex,
      er1645v2EthPortSwIVlanTaggingUntaggedAction
         INTEGER,
      er1645v2EthPortSwIVlanTaggingUntaggedTagInfoTpid
         INTEGER,
      er1645v2EthPortSwIVlanTaggingUntaggedTagInfoVid
         Integer32,
      er1645v2EthPortSwIVlanTaggingUnknownVlansAction
         INTEGER,
      er1645v2EthPortSwIVlanTaggingUnknownVlansTagInfoTpid
         INTEGER,
      er1645v2EthPortSwIVlanTaggingUnknownVlansTagInfoVid
         Integer32
      }

er1645v2EthPortSwIVlanTaggingGlobalIx OBJECT-TYPE
   SYNTAX      GlobalIndex
   MAX-ACCESS  not-accessible
   STATUS      current
   DESCRIPTION
      "The value of the tlsCntTreeGlobalIndex of the MANAGED OBJECT."
   ::= {er1645v2EthPortSwIVlanTaggingEntry 10}

er1645v2EthPortSwIVlanTaggingUntaggedAction OBJECT-TYPE
   SYNTAX      INTEGER
               {
               discard (0),
               accept (1),
               tag (2)
               }
   MAX-ACCESS  read-write
   STATUS      current
   DESCRIPTION
      "Path: swPort.editConf.vlanTagging.untagged.action

       Possibilities:
               discard   (0)
               accept   (1)
               tag   (2)"
   ::= {er1645v2EthPortSwIVlanTaggingEntry 671088640}

er1645v2EthPortSwIVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.untagged.tagInfo.tpid

       Possibilities:
               dot1Q   (33024)
               dot1ad   (34984)
               0x9100   (37120)
               0x9200   (37376)
               0x9300   (37632)"
   ::= {er1645v2EthPortSwIVlanTaggingEntry 746586112}

er1645v2EthPortSwIVlanTaggingUntaggedTagInfoVid OBJECT-TYPE
   SYNTAX      Integer32
   MAX-ACCESS  read-write
   STATUS      current
   DESCRIPTION
      "Path: swPort.editConf.vlanTagging.untagged.tagInfo.vid"
   ::= {er1645v2EthPortSwIVlanTaggingEntry 754974720}

er1645v2EthPortSwIVlanTaggingUnknownVlansAction OBJECT-TYPE
   SYNTAX      INTEGER
               {
               discard (0),
               accept (1),
               tag (2)
               }
   MAX-ACCESS  read-write
   STATUS      current
   DESCRIPTION
      "Path: swPort.editConf.vlanTagging.unknownVlans.action

       Possibilities:
               discard   (0)
               accept   (1)
               tag   (2)"
   ::= {er1645v2EthPortSwIVlanTaggingEntry 1744830464}

er1645v2EthPortSwIVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.unknownVlans.tagInfo.tpid

       Possibilities:
               dot1Q   (33024)
               dot1ad   (34984)
               0x9100   (37120)
               0x9200   (37376)
               0x9300   (37632)"
   ::= {er1645v2EthPortSwIVlanTaggingEntry 1820327936}

er1645v2EthPortSwIVlanTaggingUnknownVlansTagInfoVid OBJECT-TYPE
   SYNTAX      Integer32
   MAX-ACCESS  read-write
   STATUS      current
   DESCRIPTION
      "Path: swPort.editConf.vlanTagging.unknownVlans.tagInfo.vid"
   ::= {er1645v2EthPortSwIVlanTaggingEntry 1828716544}

er1645v2EthPortSwIVlanTaggingVlans OBJECT-TYPE
   SYNTAX      SEQUENCE OF Er1645v2EthPortSwIVlanTaggingVlansEntry
   MAX-ACCESS  not-accessible
   STATUS      current
   DESCRIPTION
      ""
   ::= {er1645v2EthPortSwIVlanTagging 1073741824}

er1645v2EthPortSwIVlanTaggingVlansEntry OBJECT-TYPE
   SYNTAX      Er1645v2EthPortSwIVlanTaggingVlansEntry
   MAX-ACCESS  not-accessible
   STATUS      current
   DESCRIPTION
      ""
   INDEX      { er1645v2EthPortSwIVlanTaggingVlansGlobalIx,
                er1645v2EthPortSwIVlanTaggingVlansTableIx }
   ::= {er1645v2EthPortSwIVlanTaggingVlans 1}

Er1645v2EthPortSwIVlanTaggingVlansEntry ::=
   SEQUENCE
      {
      er1645v2EthPortSwIVlanTaggingVlansActions
         VariableLengthTableActions,
      er1645v2EthPortSwIVlanTaggingVlansGlobalIx
         GlobalIndex,
      er1645v2EthPortSwIVlanTaggingVlansTableIx
         TableIndex,
      er1645v2EthPortSwIVlanTaggingVlansVid
         Integer32,
      er1645v2EthPortSwIVlanTaggingVlansEndVid
         Integer32,
      er1645v2EthPortSwIVlanTaggingVlansAction
         INTEGER,
      er1645v2EthPortSwIVlanTaggingVlansTagInfoTpid
         INTEGER,
      er1645v2EthPortSwIVlanTaggingVlansTagInfoVid
         Integer32
      }

er1645v2EthPortSwIVlanTaggingVlansActions OBJECT-TYPE
   SYNTAX      VariableLengthTableActions
   MAX-ACCESS  read-write
   STATUS      current
   DESCRIPTION
      "By way of this field, some manipulations
       on this table may be performed."
   ::= {er1645v2EthPortSwIVlanTaggingVlansEntry 2}

er1645v2EthPortSwIVlanTaggingVlansGlobalIx OBJECT-TYPE
   SYNTAX      GlobalIndex
   MAX-ACCESS  not-accessible
   STATUS      current
   DESCRIPTION
      "The value of the tlsCntTreeGlobalIndex of the MANAGED OBJECT."
   ::= {er1645v2EthPortSwIVlanTaggingVlansEntry 10}

er1645v2EthPortSwIVlanTaggingVlansTableIx OBJECT-TYPE
   SYNTAX      TableIndex
   MAX-ACCESS  not-accessible
   STATUS      current
   DESCRIPTION
      ""
   ::= {er1645v2EthPortSwIVlanTaggingVlansEntry 11}

er1645v2EthPortSwIVlanTaggingVlansVid OBJECT-TYPE
   SYNTAX      Integer32
   MAX-ACCESS  read-write
   STATUS      current
   DESCRIPTION
      "Path: swPort.editConf.vlanTagging.vlans.vid"
   ::= {er1645v2EthPortSwIVlanTaggingVlansEntry 536870912}

er1645v2EthPortSwIVlanTaggingVlansEndVid OBJECT-TYPE
   SYNTAX      Integer32
   MAX-ACCESS  read-write
   STATUS      current
   DESCRIPTION
      "Path: swPort.editConf.vlanTagging.vlans.endVid"
   ::= {er1645v2EthPortSwIVlanTaggingVlansEntry 2147483648}

er1645v2EthPortSwIVlanTaggingVlansAction OBJECT-TYPE
   SYNTAX      INTEGER
               {
               discard (0),
               accept (1),
               tag (2)
               }
   MAX-ACCESS  read-write
   STATUS      current
   DESCRIPTION
      "Path: swPort.editConf.vlanTagging.vlans.action

       Possibilities:
               discard   (0)
               accept   (1)
               tag   (2)"
   ::= {er1645v2EthPortSwIVlanTaggingVlansEntry 1073741824}

er1645v2EthPortSwIVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.vlans.tagInfo.tpid

       Possibilities:
               dot1Q   (33024)
               dot1ad   (34984)
               0x9100   (37120)
               0x9200   (37376)
               0x9300   (37632)"
   ::= {er1645v2EthPortSwIVlanTaggingVlansEntry 1677721600}

er1645v2EthPortSwIVlanTaggingVlansTagInfoVid OBJECT-TYPE
   SYNTAX      Integer32
   MAX-ACCESS  read-write
   STATUS      current
   DESCRIPTION
      "Path: swPort.editConf.vlanTagging.vlans.tagInfo.vid"
   ::= {er1645v2EthPortSwIVlanTaggingVlansEntry 1744830464}


er1645v2EthPortSwIOam OBJECT IDENTIFIER ::= {er1645v2EthPortSwI 900}

er1645v2EthPortSwIOamSSCTable OBJECT-TYPE
   SYNTAX      SEQUENCE OF Er1645v2EthPortSwIOamEntry
   MAX-ACCESS  not-accessible
   STATUS      current
   DESCRIPTION
      "OAM mode"
   ::= {er1645v2EthPortSwIOam 1}

er1645v2EthPortSwIOamEntry OBJECT-TYPE
   SYNTAX      Er1645v2EthPortSwIOamEntry
   MAX-ACCESS  not-accessible
   STATUS      current
   DESCRIPTION
      ""
   INDEX      { er1645v2EthPortSwIOamGlobalIx }
   ::= {er1645v2EthPortSwIOamSSCTable 1}

Er1645v2EthPortSwIOamEntry ::=
   SEQUENCE
      {
      er1645v2EthPortSwIOamGlobalIx
         GlobalIndex,
      er1645v2EthPortSwIOamMode
         INTEGER,
      er1645v2EthPortSwIOamLpbkLocalParAction
         INTEGER,
      er1645v2EthPortSwIOamLpbkSwapMacAddr
         INTEGER,
      er1645v2EthPortSwIOamLoopbackIgnoreRx
         INTEGER,
      er1645v2EthPortSwIOamEventsErroredSymbolEnabled
         INTEGER,
      er1645v2EthPortSwIOamEventsErroredSymbolWindowHi
         INTEGER,
      er1645v2EthPortSwIOamEventsErroredSymbolWindowLo
         INTEGER,
      er1645v2EthPortSwIOamEventsErroredSymbolThresholdHi
         Integer32,
      er1645v2EthPortSwIOamEventsErroredSymbolThresholdLo
         Integer32,
      er1645v2EthPortSwIOamEventsErroredFramePeriodEnabled
         INTEGER,
      er1645v2EthPortSwIOamEventsErroredFramePeriodWindow
         INTEGER,
      er1645v2EthPortSwIOamEventsErroredFramePeriodThreshold
         Integer32,
      er1645v2EthPortSwIOamEventsErroredFrameEnabled
         INTEGER,
      er1645v2EthPortSwIOamEventsErroredFrameWindow
         Integer32,
      er1645v2EthPortSwIOamEventsErroredFrameThreshold
         Integer32,
      er1645v2EthPortSwIOamEventsErroredFrameSecondsEnabled
         INTEGER,
      er1645v2EthPortSwIOamEventsErroredFrameSecondsWindow
         Integer32,
      er1645v2EthPortSwIOamEventsErroredFrameSecondsThreshold
         Integer32,
      er1645v2EthPortSwIOamEventsDyingGasp
         INTEGER,
      er1645v2EthPortSwIOamEventsCriticalEvent
         INTEGER
      }

er1645v2EthPortSwIOamGlobalIx OBJECT-TYPE
   SYNTAX      GlobalIndex
   MAX-ACCESS  not-accessible
   STATUS      current
   DESCRIPTION
      "The value of the tlsCntTreeGlobalIndex of the MANAGED OBJECT."
   ::= {er1645v2EthPortSwIOamEntry 10}

er1645v2EthPortSwIOamMode OBJECT-TYPE
   SYNTAX      INTEGER
               {
               disabled (0),
               passive (3),
               active (2)
               }
   MAX-ACCESS  read-write
   STATUS      current
   DESCRIPTION
      "Path: swPort.editConf.oam.mode

       Possibilities:
               disabled   (0)
               passive   (3)
               active   (2)"
   ::= {er1645v2EthPortSwIOamEntry 16777216}

er1645v2EthPortSwIOamLpbkLocalParAction OBJECT-TYPE
   SYNTAX      INTEGER
               {
               discard (0),
               forward (1)
               }
   MAX-ACCESS  read-write
   STATUS      current
   DESCRIPTION
      "Path: swPort.editConf.oam.loopbackLocalParserAction

       Possibilities:
               discard   (0)
               forward   (1)"
   ::= {er1645v2EthPortSwIOamEntry 33554432}

er1645v2EthPortSwIOamLpbkSwapMacAddr OBJECT-TYPE
   SYNTAX      INTEGER
               {
               disabled (0),
               enabled (1)
               }
   MAX-ACCESS  read-write
   STATUS      current
   DESCRIPTION
      "Path: swPort.editConf.oam.loopbackSwapMacAddresses

       Possibilities:
               disabled   (0)
               enabled   (1)"
   ::= {er1645v2EthPortSwIOamEntry 50331648}

er1645v2EthPortSwIOamLoopbackIgnoreRx OBJECT-TYPE
   SYNTAX      INTEGER
               {
               no (0),
               yes (1)
               }
   MAX-ACCESS  read-write
   STATUS      current
   DESCRIPTION
      "Path: swPort.editConf.oam.loopbackIgnoreRx

       Possibilities:
               no   (0)
               yes   (1)"
   ::= {er1645v2EthPortSwIOamEntry 67108864}

er1645v2EthPortSwIOamEventsErroredSymbolEnabled OBJECT-TYPE
   SYNTAX      INTEGER
               {
               no (0),
               yes (1)
               }
   MAX-ACCESS  read-write
   STATUS      current
   DESCRIPTION
      "Path: swPort.editConf.oam.events.erroredSymbol.enabled

       Possibilities:
               no   (0)
               yes   (1)"
   ::= {er1645v2EthPortSwIOamEntry 83951872}

er1645v2EthPortSwIOamEventsErroredSymbolWindowHi OBJECT-TYPE
   SYNTAX      INTEGER
               {
               default (0)
               }
   UNITS       "symbols"
   MAX-ACCESS  read-write
   STATUS      current
   DESCRIPTION
      "Path: swPort.editConf.oam.events.erroredSymbol.windowHi

       unit name = symbols

       Possibilities:
               default   (0)"
   ::= {er1645v2EthPortSwIOamEntry 83952128}

er1645v2EthPortSwIOamEventsErroredSymbolWindowLo OBJECT-TYPE
   SYNTAX      INTEGER
               {
               default (0)
               }
   UNITS       "symbols"
   MAX-ACCESS  read-write
   STATUS      current
   DESCRIPTION
      "Path: swPort.editConf.oam.events.erroredSymbol.windowLo

       unit name = symbols

       Possibilities:
               default   (0)"
   ::= {er1645v2EthPortSwIOamEntry 83952384}

er1645v2EthPortSwIOamEventsErroredSymbolThresholdHi OBJECT-TYPE
   SYNTAX      Integer32
   UNITS       "symbols"
   MAX-ACCESS  read-write
   STATUS      current
   DESCRIPTION
      "Path: swPort.editConf.oam.events.erroredSymbol.thresholdHi

       unit name = symbols"
   ::= {er1645v2EthPortSwIOamEntry 83952640}

er1645v2EthPortSwIOamEventsErroredSymbolThresholdLo OBJECT-TYPE
   SYNTAX      Integer32
   UNITS       "symbols"
   MAX-ACCESS  read-write
   STATUS      current
   DESCRIPTION
      "Path: swPort.editConf.oam.events.erroredSymbol.thresholdLo

       unit name = symbols"
   ::= {er1645v2EthPortSwIOamEntry 83952896}

er1645v2EthPortSwIOamEventsErroredFramePeriodEnabled OBJECT-TYPE
   SYNTAX      INTEGER
               {
               no (0),
               yes (1)
               }
   MAX-ACCESS  read-write
   STATUS      current
   DESCRIPTION
      "Path: swPort.editConf.oam.events.erroredFramePeriod.enabled

       Possibilities:
               no   (0)
               yes   (1)"
   ::= {er1645v2EthPortSwIOamEntry 84017408}

er1645v2EthPortSwIOamEventsErroredFramePeriodWindow OBJECT-TYPE
   SYNTAX      INTEGER
               {
               default (0)
               }
   UNITS       "frames"
   MAX-ACCESS  read-write
   STATUS      current
   DESCRIPTION
      "Path: swPort.editConf.oam.events.erroredFramePeriod.window

       unit name = frames

       Possibilities:
               default   (0)"
   ::= {er1645v2EthPortSwIOamEntry 84017664}

er1645v2EthPortSwIOamEventsErroredFramePeriodThreshold OBJECT-TYPE
   SYNTAX      Integer32
   UNITS       "frames"
   MAX-ACCESS  read-write
   STATUS      current
   DESCRIPTION
      "Path: swPort.editConf.oam.events.erroredFramePeriod.threshold

       unit name = frames"
   ::= {er1645v2EthPortSwIOamEntry 84017920}

er1645v2EthPortSwIOamEventsErroredFrameEnabled OBJECT-TYPE
   SYNTAX      INTEGER
               {
               no (0),
               yes (1)
               }
   MAX-ACCESS  read-write
   STATUS      current
   DESCRIPTION
      "Path: swPort.editConf.oam.events.erroredFrame.enabled

       Possibilities:
               no   (0)
               yes   (1)"
   ::= {er1645v2EthPortSwIOamEntry 84082944}

er1645v2EthPortSwIOamEventsErroredFrameWindow OBJECT-TYPE
   SYNTAX      Integer32
   UNITS       "100msec"
   MAX-ACCESS  read-write
   STATUS      current
   DESCRIPTION
      "Path: swPort.editConf.oam.events.erroredFrame.window

       unit name = 100msec"
   ::= {er1645v2EthPortSwIOamEntry 84083200}

er1645v2EthPortSwIOamEventsErroredFrameThreshold OBJECT-TYPE
   SYNTAX      Integer32
   UNITS       "frames"
   MAX-ACCESS  read-write
   STATUS      current
   DESCRIPTION
      "Path: swPort.editConf.oam.events.erroredFrame.threshold

       unit name = frames"
   ::= {er1645v2EthPortSwIOamEntry 84083456}

er1645v2EthPortSwIOamEventsErroredFrameSecondsEnabled OBJECT-TYPE
   SYNTAX      INTEGER
               {
               no (0),
               yes (1)
               }
   MAX-ACCESS  read-write
   STATUS      current
   DESCRIPTION
      "Path: swPort.editConf.oam.events.erroredFrameSeconds.enabled

       Possibilities:
               no   (0)
               yes   (1)"
   ::= {er1645v2EthPortSwIOamEntry 84148480}

er1645v2EthPortSwIOamEventsErroredFrameSecondsWindow OBJECT-TYPE
   SYNTAX      Integer32
   UNITS       "100msec"
   MAX-ACCESS  read-write
   STATUS      current
   DESCRIPTION
      "Path: swPort.editConf.oam.events.erroredFrameSeconds.window

       unit name = 100msec"
   ::= {er1645v2EthPortSwIOamEntry 84148736}

er1645v2EthPortSwIOamEventsErroredFrameSecondsThreshold OBJECT-TYPE
   SYNTAX      Integer32
   UNITS       "frames"
   MAX-ACCESS  read-write
   STATUS      current
   DESCRIPTION
      "Path: swPort.editConf.oam.events.erroredFrameSeconds.threshold

       unit name = frames"
   ::= {er1645v2EthPortSwIOamEntry 84148992}

er1645v2EthPortSwIOamEventsDyingGasp OBJECT-TYPE
   SYNTAX      INTEGER
               {
               disabled (0),
               enabled (1)
               }
   MAX-ACCESS  read-write
   STATUS      current
   DESCRIPTION
      "Path: swPort.editConf.oam.events.dyingGasp

       Possibilities:
               disabled   (0)
               enabled   (1)"
   ::= {er1645v2EthPortSwIOamEntry 84213760}

er1645v2EthPortSwIOamEventsCriticalEvent OBJECT-TYPE
   SYNTAX      INTEGER
               {
               disabled (0),
               enabled (1)
               }
   MAX-ACCESS  read-write
   STATUS      current
   DESCRIPTION
      "Path: swPort.editConf.oam.events.criticalEvent

       Possibilities:
               disabled   (0)
               enabled   (1)"
   ::= {er1645v2EthPortSwIOamEntry 84279296}


er1645v2EthPortSwIDot1x OBJECT IDENTIFIER ::= {er1645v2EthPortSwI 191}

er1645v2EthPortSwIDot1xSSCTable OBJECT-TYPE
   SYNTAX      SEQUENCE OF Er1645v2EthPortSwIDot1xEntry
   MAX-ACCESS  not-accessible
   STATUS      current
   DESCRIPTION
      "ppp server name on interface"
   ::= {er1645v2EthPortSwIDot1x 1}

er1645v2EthPortSwIDot1xEntry OBJECT-TYPE
   SYNTAX      Er1645v2EthPortSwIDot1xEntry
   MAX-ACCESS  not-accessible
   STATUS      current
   DESCRIPTION
      ""
   INDEX      { er1645v2EthPortSwIDot1xGlobalIx }
   ::= {er1645v2EthPortSwIDot1xSSCTable 1}

Er1645v2EthPortSwIDot1xEntry ::=
   SEQUENCE
      {
      er1645v2EthPortSwIDot1xGlobalIx
         GlobalIndex,
      er1645v2EthPortSwIDot1xMode
         INTEGER,
      er1645v2EthPortSwIDot1xMaxHosts
         Integer32,
      er1645v2EthPortSwIDot1xReAuthentication
         INTEGER,
      er1645v2EthPortSwIDot1xReAuthPeriod
         TimeTicks,
      er1645v2EthPortSwIDot1xQuietPeriod
         TimeTicks,
      er1645v2EthPortSwIDot1xSupplTimeout
         TimeTicks,
      er1645v2EthPortSwIDot1xServerTimeout
         TimeTicks,
      er1645v2EthPortSwIDot1xMaxReqCount
         Integer32
      }

er1645v2EthPortSwIDot1xGlobalIx OBJECT-TYPE
   SYNTAX      GlobalIndex
   MAX-ACCESS  not-accessible
   STATUS      current
   DESCRIPTION
      "The value of the tlsCntTreeGlobalIndex of the MANAGED OBJECT."
   ::= {er1645v2EthPortSwIDot1xEntry 10}

er1645v2EthPortSwIDot1xMode OBJECT-TYPE
   SYNTAX      INTEGER
               {
               inactive (0),
               auto (1)
               }
   MAX-ACCESS  read-write
   STATUS      current
   DESCRIPTION
      "Path: swPort.editConf.dot1x.mode

       Possibilities:
               inactive   (0)
               auto   (1)"
   ::= {er1645v2EthPortSwIDot1xEntry 16777216}

er1645v2EthPortSwIDot1xMaxHosts OBJECT-TYPE
   SYNTAX      Integer32
   MAX-ACCESS  read-write
   STATUS      current
   DESCRIPTION
      "Path: swPort.editConf.dot1x.maxHosts"
   ::= {er1645v2EthPortSwIDot1xEntry 33554432}

er1645v2EthPortSwIDot1xReAuthentication OBJECT-TYPE
   SYNTAX      INTEGER
               {
               disabled (0),
               enabled (1)
               }
   MAX-ACCESS  read-write
   STATUS      current
   DESCRIPTION
      "Path: swPort.editConf.dot1x.reAuthentication

       Possibilities:
               disabled   (0)
               enabled   (1)"
   ::= {er1645v2EthPortSwIDot1xEntry 50331648}

er1645v2EthPortSwIDot1xReAuthPeriod OBJECT-TYPE
   SYNTAX      TimeTicks
   MAX-ACCESS  read-write
   STATUS      current
   DESCRIPTION
      "Path: swPort.editConf.dot1x.reAuthPeriod

       Time in centi-second."
   ::= {er1645v2EthPortSwIDot1xEntry 67108864}

er1645v2EthPortSwIDot1xQuietPeriod OBJECT-TYPE
   SYNTAX      TimeTicks
   MAX-ACCESS  read-write
   STATUS      current
   DESCRIPTION
      "Path: swPort.editConf.dot1x.quietPeriod

       Time in centi-second."
   ::= {er1645v2EthPortSwIDot1xEntry 83886080}

er1645v2EthPortSwIDot1xSupplTimeout OBJECT-TYPE
   SYNTAX      TimeTicks
   MAX-ACCESS  read-write
   STATUS      current
   DESCRIPTION
      "Path: swPort.editConf.dot1x.supplTimeout

       Time in centi-second."
   ::= {er1645v2EthPortSwIDot1xEntry 100663296}

er1645v2EthPortSwIDot1xServerTimeout OBJECT-TYPE
   SYNTAX      TimeTicks
   MAX-ACCESS  read-write
   STATUS      current
   DESCRIPTION
      "Path: swPort.editConf.dot1x.serverTimeout

       Time in centi-second."
   ::= {er1645v2EthPortSwIDot1xEntry 117440512}

er1645v2EthPortSwIDot1xMaxReqCount OBJECT-TYPE
   SYNTAX      Integer32
   MAX-ACCESS  read-write
   STATUS      current
   DESCRIPTION
      "Path: swPort.editConf.dot1x.maxReqCount"
   ::= {er1645v2EthPortSwIDot1xEntry 134217728}


er1645v2EthPortSwIIpV6 OBJECT IDENTIFIER ::= {er1645v2EthPortSwI 15}

er1645v2EthPortSwIIpV6SSCTable OBJECT-TYPE
   SYNTAX      SEQUENCE OF Er1645v2EthPortSwIIpV6Entry
   MAX-ACCESS  not-accessible
   STATUS      current
   DESCRIPTION
      "IPv6 interface config parameters"
   ::= {er1645v2EthPortSwIIpV6 1}

er1645v2EthPortSwIIpV6Entry OBJECT-TYPE
   SYNTAX      Er1645v2EthPortSwIIpV6Entry
   MAX-ACCESS  not-accessible
   STATUS      current
   DESCRIPTION
      ""
   INDEX      { er1645v2EthPortSwIIpV6GlobalIx }
   ::= {er1645v2EthPortSwIIpV6SSCTable 1}

Er1645v2EthPortSwIIpV6Entry ::=
   SEQUENCE
      {
      er1645v2EthPortSwIIpV6GlobalIx
         GlobalIndex,
      er1645v2EthPortSwIIpV6VrfRouter
         DisplayString,
      er1645v2EthPortSwIIpV6AddrAutoConfigNrDupAddrDetects
         Integer32,
      er1645v2EthPortSwIIpV6AddrAutoConfigAcceptRa
         INTEGER,
      er1645v2EthPortSwIIpV6AddrAutoConfigAcceptRaRdnss
         INTEGER,
      er1645v2EthPortSwIIpV6AddrAutoConfigAcceptRaDnssl
         INTEGER,
      er1645v2EthPortSwIIpV6DefaultRoute
         INTEGER,
      er1645v2EthPortSwIIpV6RaSend
         INTEGER,
      er1645v2EthPortSwIIpV6RaMinInterval
         TimeTicks,
      er1645v2EthPortSwIIpV6RaMaxInterval
         TimeTicks,
      er1645v2EthPortSwIIpV6RaManagedFlag
         INTEGER,
      er1645v2EthPortSwIIpV6RaOtherConfFlag
         INTEGER,
      er1645v2EthPortSwIIpV6RaLinkMtu
         Integer32,
      er1645v2EthPortSwIIpV6RaReachableTime
         TimeTicks,
      er1645v2EthPortSwIIpV6RaRetransmitTime
         TimeTicks,
      er1645v2EthPortSwIIpV6RaHopLimit
         Integer32,
      er1645v2EthPortSwIIpV6RaDefaultLifeTime
         TimeTicks,
      er1645v2EthPortSwIIpV6RaDnsOptionsRdnssLifeTime
         TimeTicks,
      er1645v2EthPortSwIIpV6RaDnsOptionsRdnssImportServers
         INTEGER,
      er1645v2EthPortSwIIpV6RaDnsOptionsDnsslLifeTime
         TimeTicks,
      er1645v2EthPortSwIIpV6RaDnsOptionsDnsslImportDomains
         INTEGER,
      er1645v2EthPortSwIIpV6RsSend
         INTEGER,
      er1645v2EthPortSwIIpV6RsMaxRandomDelay
         TimeTicks,
      er1645v2EthPortSwIIpV6RsInterval
         TimeTicks,
      er1645v2EthPortSwIIpV6RsMaxSolicitations
         Integer32,
      er1645v2EthPortSwIIpV6TrafficPolicyInbound
         DisplayString,
      er1645v2EthPortSwIIpV6TrafficPolicyOutbound
         DisplayString,
      er1645v2EthPortSwIIpV6FirewallZone
         DisplayString,
      er1645v2EthPortSwIIpV6DhcpClientAddrAC
         INTEGER,
      er1645v2EthPortSwIIpV6DhcpClientPrDelMode
         INTEGER,
      er1645v2EthPortSwIIpV6DhcpClientPrDelPool
         DisplayString,
      er1645v2EthPortSwIIpV6DhcpClientPrDelPdExclOpt
         INTEGER,
      er1645v2EthPortSwIIpV6DhcpClientDnsServerPref
         Integer32,
      er1645v2EthPortSwIIpV6DhcpClientRapidCommit
         INTEGER,
      er1645v2EthPortSwIIpV6DhcpClientTimersSolTimeOut
         TimeTicks,
      er1645v2EthPortSwIIpV6DhcpClientTimersSolMaxRt
         TimeTicks,
      er1645v2EthPortSwIIpV6DhcpClientTimersInfoRefresh
         TimeTicks,
      er1645v2EthPortSwIIpV6DhcpServerMode
         INTEGER,
      er1645v2EthPortSwIIpV6DhcpServerPreference
         Integer32,
      er1645v2EthPortSwIIpV6DhcpServerPool
         DisplayString,
      er1645v2EthPortSwIIpV6DhcpServerRapidCommit
         INTEGER,
      er1645v2EthPortSwIIpV6DhcpServerTimersInfoRefresh
         TimeTicks,
      er1645v2EthPortSwIIpV6DhcpRelayMode
         INTEGER,
      er1645v2EthPortSwIIpV6SendRedirect
         INTEGER,
      er1645v2EthPortSwIIpV6LinkMtu
         Integer32,
      er1645v2EthPortSwIIpV6InterfaceId
         OCTET STRING,
      er1645v2EthPortSwIIpV6MF
         Integer32,
      er1645v2EthPortSwIIpV6IcmpMessagesNoRoute
         INTEGER,
      er1645v2EthPortSwIIpV6IcmpMessagesBeyondScope
         INTEGER,
      er1645v2EthPortSwIIpV6IcmpMessagesAddressUnreachable
         INTEGER,
      er1645v2EthPortSwIIpV6IcmpMessagesPortUnreachable
         INTEGER,
      er1645v2EthPortSwIIpV6IcmpMessagesPacketTooBig
         INTEGER,
      er1645v2EthPortSwIIpV6IcmpMessagesHopLimitExceeded
         INTEGER,
      er1645v2EthPortSwIIpV6IcmpMessagesFragTimeExceeded
         INTEGER,
      er1645v2EthPortSwIIpV6IcmpMessagesHeaderFieldErr
         INTEGER,
      er1645v2EthPortSwIIpV6IcmpMessagesOptionUnrecognized
         INTEGER,
      er1645v2EthPortSwIIpV6IcmpMessagesRedirect
         INTEGER
      }

er1645v2EthPortSwIIpV6GlobalIx OBJECT-TYPE
   SYNTAX      GlobalIndex
   MAX-ACCESS  not-accessible
   STATUS      current
   DESCRIPTION
      "The value of the tlsCntTreeGlobalIndex of the MANAGED OBJECT."
   ::= {er1645v2EthPortSwIIpV6Entry 10}

er1645v2EthPortSwIIpV6VrfRouter OBJECT-TYPE
   SYNTAX      DisplayString
   MAX-ACCESS  read-write
   STATUS      current
   DESCRIPTION
      "Path: swPort.editConf.ipV6.vrfRouter"
   ::= {er1645v2EthPortSwIIpV6Entry 16777216}

er1645v2EthPortSwIIpV6AddrAutoConfigNrDupAddrDetects OBJECT-TYPE
   SYNTAX      Integer32
   MAX-ACCESS  read-write
   STATUS      current
   DESCRIPTION
      "Path: swPort.editConf.ipV6.addrAutoConfig.nrDupAddrDetects"
   ::= {er1645v2EthPortSwIIpV6Entry 67174400}

er1645v2EthPortSwIIpV6AddrAutoConfigAcceptRa OBJECT-TYPE
   SYNTAX      INTEGER
               {
               disabled (0),
               enabled (1)
               }
   MAX-ACCESS  read-write
   STATUS      current
   DESCRIPTION
      "Path: swPort.editConf.ipV6.addrAutoConfig.acceptRa

       Possibilities:
               disabled   (0)
               enabled   (1)"
   ::= {er1645v2EthPortSwIIpV6Entry 67239936}

er1645v2EthPortSwIIpV6AddrAutoConfigAcceptRaRdnss OBJECT-TYPE
   SYNTAX      INTEGER
               {
               disabled (0),
               enabled (1)
               }
   MAX-ACCESS  read-write
   STATUS      current
   DESCRIPTION
      "Path: swPort.editConf.ipV6.addrAutoConfig.acceptRaRdnss

       Possibilities:
               disabled   (0)
               enabled   (1)"
   ::= {er1645v2EthPortSwIIpV6Entry 67305472}

er1645v2EthPortSwIIpV6AddrAutoConfigAcceptRaDnssl OBJECT-TYPE
   SYNTAX      INTEGER
               {
               disabled (0),
               enabled (1)
               }
   MAX-ACCESS  read-write
   STATUS      current
   DESCRIPTION
      "Path: swPort.editConf.ipV6.addrAutoConfig.acceptRaDnssl

       Possibilities:
               disabled   (0)
               enabled   (1)"
   ::= {er1645v2EthPortSwIIpV6Entry 67371008}

er1645v2EthPortSwIIpV6DefaultRoute OBJECT-TYPE
   SYNTAX      INTEGER
               {
               disabled (0),
               enabled (1)
               }
   MAX-ACCESS  read-write
   STATUS      current
   DESCRIPTION
      "Path: swPort.editConf.ipV6.defaultRoute

       Possibilities:
               disabled   (0)
               enabled   (1)"
   ::= {er1645v2EthPortSwIIpV6Entry 83886080}

er1645v2EthPortSwIIpV6RaSend OBJECT-TYPE
   SYNTAX      INTEGER
               {
               disabled (0),
               enabled (1)
               }
   MAX-ACCESS  read-write
   STATUS      current
   DESCRIPTION
      "Path: swPort.editConf.ipV6.ra.send

       Possibilities:
               disabled   (0)
               enabled   (1)"
   ::= {er1645v2EthPortSwIIpV6Entry 100728832}

er1645v2EthPortSwIIpV6RaMinInterval OBJECT-TYPE
   SYNTAX      TimeTicks
   MAX-ACCESS  read-write
   STATUS      current
   DESCRIPTION
      "Path: swPort.editConf.ipV6.ra.minInterval

       Time in centi-second."
   ::= {er1645v2EthPortSwIIpV6Entry 100794368}

er1645v2EthPortSwIIpV6RaMaxInterval OBJECT-TYPE
   SYNTAX      TimeTicks
   MAX-ACCESS  read-write
   STATUS      current
   DESCRIPTION
      "Path: swPort.editConf.ipV6.ra.maxInterval

       Time in centi-second."
   ::= {er1645v2EthPortSwIIpV6Entry 100859904}

er1645v2EthPortSwIIpV6RaManagedFlag OBJECT-TYPE
   SYNTAX      INTEGER
               {
               disabled (0),
               enabled (1)
               }
   MAX-ACCESS  read-write
   STATUS      current
   DESCRIPTION
      "Path: swPort.editConf.ipV6.ra.managedFlag

       Possibilities:
               disabled   (0)
               enabled   (1)"
   ::= {er1645v2EthPortSwIIpV6Entry 100925440}

er1645v2EthPortSwIIpV6RaOtherConfFlag OBJECT-TYPE
   SYNTAX      INTEGER
               {
               disabled (0),
               enabled (1)
               }
   MAX-ACCESS  read-write
   STATUS      current
   DESCRIPTION
      "Path: swPort.editConf.ipV6.ra.otherConfFlag

       Possibilities:
               disabled   (0)
               enabled   (1)"
   ::= {er1645v2EthPortSwIIpV6Entry 100990976}

er1645v2EthPortSwIIpV6RaLinkMtu OBJECT-TYPE
   SYNTAX      Integer32
   MAX-ACCESS  read-write
   STATUS      current
   DESCRIPTION
      "Path: swPort.editConf.ipV6.ra.linkMtu"
   ::= {er1645v2EthPortSwIIpV6Entry 101056512}

er1645v2EthPortSwIIpV6RaReachableTime OBJECT-TYPE
   SYNTAX      TimeTicks
   MAX-ACCESS  read-write
   STATUS      current
   DESCRIPTION
      "Path: swPort.editConf.ipV6.ra.reachableTime

       Time in centi-second."
   ::= {er1645v2EthPortSwIIpV6Entry 101122048}

er1645v2EthPortSwIIpV6RaRetransmitTime OBJECT-TYPE
   SYNTAX      TimeTicks
   MAX-ACCESS  read-write
   STATUS      current
   DESCRIPTION
      "Path: swPort.editConf.ipV6.ra.retransmitTime

       Time in centi-second."
   ::= {er1645v2EthPortSwIIpV6Entry 101187584}

er1645v2EthPortSwIIpV6RaHopLimit OBJECT-TYPE
   SYNTAX      Integer32
   MAX-ACCESS  read-write
   STATUS      current
   DESCRIPTION
      "Path: swPort.editConf.ipV6.ra.hopLimit"
   ::= {er1645v2EthPortSwIIpV6Entry 101253120}

er1645v2EthPortSwIIpV6RaDefaultLifeTime OBJECT-TYPE
   SYNTAX      TimeTicks
   MAX-ACCESS  read-write
   STATUS      current
   DESCRIPTION
      "Path: swPort.editConf.ipV6.ra.defaultLifeTime

       Time in centi-second."
   ::= {er1645v2EthPortSwIIpV6Entry 101318656}

er1645v2EthPortSwIIpV6RaDnsOptionsRdnssLifeTime OBJECT-TYPE
   SYNTAX      TimeTicks
   MAX-ACCESS  read-write
   STATUS      current
   DESCRIPTION
      "Path: swPort.editConf.ipV6.ra.dnsOptions.rdnss.lifeTime

       Time in centi-second."
   ::= {er1645v2EthPortSwIIpV6Entry 101393408}

er1645v2EthPortSwIIpV6RaDnsOptionsRdnssImportServers OBJECT-TYPE
   SYNTAX      INTEGER
               {
               disabled (0),
               enabled (1)
               }
   MAX-ACCESS  read-write
   STATUS      current
   DESCRIPTION
      "Path: swPort.editConf.ipV6.ra.dnsOptions.rdnss.importServers

       Possibilities:
               disabled   (0)
               enabled   (1)"
   ::= {er1645v2EthPortSwIIpV6Entry 101395456}

er1645v2EthPortSwIIpV6RaDnsOptionsDnsslLifeTime OBJECT-TYPE
   SYNTAX      TimeTicks
   MAX-ACCESS  read-write
   STATUS      current
   DESCRIPTION
      "Path: swPort.editConf.ipV6.ra.dnsOptions.dnssl.lifeTime

       Time in centi-second."
   ::= {er1645v2EthPortSwIIpV6Entry 101401600}

er1645v2EthPortSwIIpV6RaDnsOptionsDnsslImportDomains OBJECT-TYPE
   SYNTAX      INTEGER
               {
               disabled (0),
               enabled (1)
               }
   MAX-ACCESS  read-write
   STATUS      current
   DESCRIPTION
      "Path: swPort.editConf.ipV6.ra.dnsOptions.dnssl.importDomains

       Possibilities:
               disabled   (0)
               enabled   (1)"
   ::= {er1645v2EthPortSwIIpV6Entry 101403648}

er1645v2EthPortSwIIpV6RsSend OBJECT-TYPE
   SYNTAX      INTEGER
               {
               disabled (0),
               enabled (1)
               }
   MAX-ACCESS  read-write
   STATUS      current
   DESCRIPTION
      "Path: swPort.editConf.ipV6.rs.send

       Possibilities:
               disabled   (0)
               enabled   (1)"
   ::= {er1645v2EthPortSwIIpV6Entry 335609856}

er1645v2EthPortSwIIpV6RsMaxRandomDelay OBJECT-TYPE
   SYNTAX      TimeTicks
   MAX-ACCESS  read-write
   STATUS      current
   DESCRIPTION
      "Path: swPort.editConf.ipV6.rs.maxRandomDelay

       Time in centi-second."
   ::= {er1645v2EthPortSwIIpV6Entry 335675392}

er1645v2EthPortSwIIpV6RsInterval OBJECT-TYPE
   SYNTAX      TimeTicks
   MAX-ACCESS  read-write
   STATUS      current
   DESCRIPTION
      "Path: swPort.editConf.ipV6.rs.interval

       Time in centi-second."
   ::= {er1645v2EthPortSwIIpV6Entry 335740928}

er1645v2EthPortSwIIpV6RsMaxSolicitations OBJECT-TYPE
   SYNTAX      Integer32
   MAX-ACCESS  read-write
   STATUS      current
   DESCRIPTION
      "Path: swPort.editConf.ipV6.rs.maxSolicitations"
   ::= {er1645v2EthPortSwIIpV6Entry 335806464}

er1645v2EthPortSwIIpV6TrafficPolicyInbound OBJECT-TYPE
   SYNTAX      DisplayString
   MAX-ACCESS  read-write
   STATUS      current
   DESCRIPTION
      "Path: swPort.editConf.ipV6.trafficPolicy.inbound"
   ::= {er1645v2EthPortSwIIpV6Entry 184614912}

er1645v2EthPortSwIIpV6TrafficPolicyOutbound OBJECT-TYPE
   SYNTAX      DisplayString
   MAX-ACCESS  read-write
   STATUS      current
   DESCRIPTION
      "Path: swPort.editConf.ipV6.trafficPolicy.outbound"
   ::= {er1645v2EthPortSwIIpV6Entry 184680448}

er1645v2EthPortSwIIpV6FirewallZone OBJECT-TYPE
   SYNTAX      DisplayString
   MAX-ACCESS  read-write
   STATUS      current
   DESCRIPTION
      "Path: swPort.editConf.ipV6.firewall.zone"
   ::= {er1645v2EthPortSwIIpV6Entry 201392128}

er1645v2EthPortSwIIpV6DhcpClientAddrAC OBJECT-TYPE
   SYNTAX      INTEGER
               {
               disabled (0),
               enabled (1)
               }
   MAX-ACCESS  read-write
   STATUS      current
   DESCRIPTION
      "Path: swPort.editConf.ipV6.dhcp.client.addrAutoConfig

       Possibilities:
               disabled   (0)
               enabled   (1)"
   ::= {er1645v2EthPortSwIIpV6Entry 170131456}

er1645v2EthPortSwIIpV6DhcpClientPrDelMode OBJECT-TYPE
   SYNTAX      INTEGER
               {
               disabled (0),
               enabled (1)
               }
   MAX-ACCESS  read-write
   STATUS      current
   DESCRIPTION
      "Path: swPort.editConf.ipV6.dhcp.client.pd.mode

       Possibilities:
               disabled   (0)
               enabled   (1)"
   ::= {er1645v2EthPortSwIIpV6Entry 170394624}

er1645v2EthPortSwIIpV6DhcpClientPrDelPool OBJECT-TYPE
   SYNTAX      DisplayString
   MAX-ACCESS  read-write
   STATUS      current
   DESCRIPTION
      "Path: swPort.editConf.ipV6.dhcp.client.pd.pool"
   ::= {er1645v2EthPortSwIIpV6Entry 170395648}

er1645v2EthPortSwIIpV6DhcpClientPrDelPdExclOpt OBJECT-TYPE
   SYNTAX      INTEGER
               {
               disabled (0),
               enabled (1)
               }
   MAX-ACCESS  read-write
   STATUS      current
   DESCRIPTION
      "Path: swPort.editConf.ipV6.dhcp.client.pd.pdExclOpt

       Possibilities:
               disabled   (0)
               enabled   (1)"
   ::= {er1645v2EthPortSwIIpV6Entry 170396672}

er1645v2EthPortSwIIpV6DhcpClientDnsServerPref OBJECT-TYPE
   SYNTAX      Integer32
   MAX-ACCESS  read-write
   STATUS      current
   DESCRIPTION
      "Path: swPort.editConf.ipV6.dhcp.client.dns.serverPref"
   ::= {er1645v2EthPortSwIIpV6Entry 170918912}

er1645v2EthPortSwIIpV6DhcpClientRapidCommit OBJECT-TYPE
   SYNTAX      INTEGER
               {
               disabled (0),
               enabled (1)
               }
   MAX-ACCESS  read-write
   STATUS      current
   DESCRIPTION
      "Path: swPort.editConf.ipV6.dhcp.client.rapidCommit

       Possibilities:
               disabled   (0)
               enabled   (1)"
   ::= {er1645v2EthPortSwIIpV6Entry 170655744}

er1645v2EthPortSwIIpV6DhcpClientTimersSolTimeOut OBJECT-TYPE
   SYNTAX      TimeTicks
   MAX-ACCESS  read-write
   STATUS      current
   DESCRIPTION
      "Path: swPort.editConf.ipV6.dhcp.client.timers.solTimeOut

       Time in centi-second."
   ::= {er1645v2EthPortSwIIpV6Entry 171181056}

er1645v2EthPortSwIIpV6DhcpClientTimersSolMaxRt OBJECT-TYPE
   SYNTAX      TimeTicks
   MAX-ACCESS  read-write
   STATUS      current
   DESCRIPTION
      "Path: swPort.editConf.ipV6.dhcp.client.timers.solMaxRt

       Time in centi-second."
   ::= {er1645v2EthPortSwIIpV6Entry 171182080}

er1645v2EthPortSwIIpV6DhcpClientTimersInfoRefresh OBJECT-TYPE
   SYNTAX      TimeTicks
   MAX-ACCESS  read-write
   STATUS      current
   DESCRIPTION
      "Path: swPort.editConf.ipV6.dhcp.client.timers.infoRefresh

       Time in centi-second."
   ::= {er1645v2EthPortSwIIpV6Entry 171183104}

er1645v2EthPortSwIIpV6DhcpServerMode OBJECT-TYPE
   SYNTAX      INTEGER
               {
               disabled (0),
               enabled (1)
               }
   MAX-ACCESS  read-write
   STATUS      current
   DESCRIPTION
      "Path: swPort.editConf.ipV6.dhcp.server.mode

       Possibilities:
               disabled   (0)
               enabled   (1)"
   ::= {er1645v2EthPortSwIIpV6Entry 172228608}

er1645v2EthPortSwIIpV6DhcpServerPreference OBJECT-TYPE
   SYNTAX      Integer32
   MAX-ACCESS  read-write
   STATUS      current
   DESCRIPTION
      "Path: swPort.editConf.ipV6.dhcp.server.preference"
   ::= {er1645v2EthPortSwIIpV6Entry 172490752}

er1645v2EthPortSwIIpV6DhcpServerPool OBJECT-TYPE
   SYNTAX      DisplayString
   MAX-ACCESS  read-write
   STATUS      current
   DESCRIPTION
      "Path: swPort.editConf.ipV6.dhcp.server.pool"
   ::= {er1645v2EthPortSwIIpV6Entry 172752896}

er1645v2EthPortSwIIpV6DhcpServerRapidCommit OBJECT-TYPE
   SYNTAX      INTEGER
               {
               disabled (0),
               enabled (1)
               }
   MAX-ACCESS  read-write
   STATUS      current
   DESCRIPTION
      "Path: swPort.editConf.ipV6.dhcp.server.rapidCommit

       Possibilities:
               disabled   (0)
               enabled   (1)"
   ::= {er1645v2EthPortSwIIpV6Entry 173015040}

er1645v2EthPortSwIIpV6DhcpServerTimersInfoRefresh OBJECT-TYPE
   SYNTAX      TimeTicks
   MAX-ACCESS  read-write
   STATUS      current
   DESCRIPTION
      "Path: swPort.editConf.ipV6.dhcp.server.timers.infoRefresh

       Time in centi-second."
   ::= {er1645v2EthPortSwIIpV6Entry 173278208}

er1645v2EthPortSwIIpV6DhcpRelayMode OBJECT-TYPE
   SYNTAX      INTEGER
               {
               disabled (0),
               enabled (1)
               }
   MAX-ACCESS  read-write
   STATUS      current
   DESCRIPTION
      "Path: swPort.editConf.ipV6.dhcp.relay.mode

       Possibilities:
               disabled   (0)
               enabled   (1)"
   ::= {er1645v2EthPortSwIIpV6Entry 174071808}

er1645v2EthPortSwIIpV6SendRedirect OBJECT-TYPE
   SYNTAX      INTEGER
               {
               disabled (0),
               enabled (1)
               }
   MAX-ACCESS  read-write
   STATUS      current
   DESCRIPTION
      "Path: swPort.editConf.ipV6.sendRedirect

       Possibilities:
               disabled   (0)
               enabled   (1)"
   ::= {er1645v2EthPortSwIIpV6Entry 117440512}

er1645v2EthPortSwIIpV6LinkMtu OBJECT-TYPE
   SYNTAX      Integer32
   MAX-ACCESS  read-write
   STATUS      current
   DESCRIPTION
      "Path: swPort.editConf.ipV6.linkMtu"
   ::= {er1645v2EthPortSwIIpV6Entry 134217728}

er1645v2EthPortSwIIpV6InterfaceId OBJECT-TYPE
   SYNTAX      OCTET STRING
   MAX-ACCESS  read-write
   STATUS      current
   DESCRIPTION
      "Path: swPort.editConf.ipV6.interfaceId"
   ::= {er1645v2EthPortSwIIpV6Entry 150994944}

er1645v2EthPortSwIIpV6MF OBJECT-TYPE
   SYNTAX      Integer32
   MAX-ACCESS  read-write
   STATUS      current
   DESCRIPTION
      "Path: swPort.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPortSwIIpV6Entry 285212672}

er1645v2EthPortSwIIpV6IcmpMessagesNoRoute OBJECT-TYPE
   SYNTAX      INTEGER
               {
               disabled (0),
               enabled (1)
               }
   MAX-ACCESS  read-write
   STATUS      current
   DESCRIPTION
      "Path: swPort.editConf.ipV6.icmpMessages.noRoute

       Possibilities:
               disabled   (0)
               enabled   (1)"
   ::= {er1645v2EthPortSwIIpV6Entry 302055424}

er1645v2EthPortSwIIpV6IcmpMessagesBeyondScope OBJECT-TYPE
   SYNTAX      INTEGER
               {
               disabled (0),
               enabled (1)
               }
   MAX-ACCESS  read-write
   STATUS      current
   DESCRIPTION
      "Path: swPort.editConf.ipV6.icmpMessages.beyondScope

       Possibilities:
               disabled   (0)
               enabled   (1)"
   ::= {er1645v2EthPortSwIIpV6Entry 302186496}

er1645v2EthPortSwIIpV6IcmpMessagesAddressUnreachable OBJECT-TYPE
   SYNTAX      INTEGER
               {
               disabled (0),
               enabled (1)
               }
   MAX-ACCESS  read-write
   STATUS      current
   DESCRIPTION
      "Path: swPort.editConf.ipV6.icmpMessages.addressUnreachable

       Possibilities:
               disabled   (0)
               enabled   (1)"
   ::= {er1645v2EthPortSwIIpV6Entry 302252032}

er1645v2EthPortSwIIpV6IcmpMessagesPortUnreachable OBJECT-TYPE
   SYNTAX      INTEGER
               {
               disabled (0),
               enabled (1)
               }
   MAX-ACCESS  read-write
   STATUS      current
   DESCRIPTION
      "Path: swPort.editConf.ipV6.icmpMessages.portUnreachable

       Possibilities:
               disabled   (0)
               enabled   (1)"
   ::= {er1645v2EthPortSwIIpV6Entry 302317568}

er1645v2EthPortSwIIpV6IcmpMessagesPacketTooBig OBJECT-TYPE
   SYNTAX      INTEGER
               {
               disabled (0),
               enabled (1)
               }
   MAX-ACCESS  read-write
   STATUS      current
   DESCRIPTION
      "Path: swPort.editConf.ipV6.icmpMessages.packetTooBig

       Possibilities:
               disabled   (0)
               enabled   (1)"
   ::= {er1645v2EthPortSwIIpV6Entry 302645248}

er1645v2EthPortSwIIpV6IcmpMessagesHopLimitExceeded OBJECT-TYPE
   SYNTAX      INTEGER
               {
               disabled (0),
               enabled (1)
               }
   MAX-ACCESS  read-write
   STATUS      current
   DESCRIPTION
      "Path: swPort.editConf.ipV6.icmpMessages.hopLimitExceeded

       Possibilities:
               disabled   (0)
               enabled   (1)"
   ::= {er1645v2EthPortSwIIpV6Entry 303300608}

er1645v2EthPortSwIIpV6IcmpMessagesFragTimeExceeded OBJECT-TYPE
   SYNTAX      INTEGER
               {
               disabled (0),
               enabled (1)
               }
   MAX-ACCESS  read-write
   STATUS      current
   DESCRIPTION
      "Path: swPort.editConf.ipV6.icmpMessages.fragTimeExceeded

       Possibilities:
               disabled   (0)
               enabled   (1)"
   ::= {er1645v2EthPortSwIIpV6Entry 303366144}

er1645v2EthPortSwIIpV6IcmpMessagesHeaderFieldErr OBJECT-TYPE
   SYNTAX      INTEGER
               {
               disabled (0),
               enabled (1)
               }
   MAX-ACCESS  read-write
   STATUS      current
   DESCRIPTION
      "Path: swPort.editConf.ipV6.icmpMessages.headerFieldErr

       Possibilities:
               disabled   (0)
               enabled   (1)"
   ::= {er1645v2EthPortSwIIpV6Entry 303955968}

er1645v2EthPortSwIIpV6IcmpMessagesOptionUnrecognized OBJECT-TYPE
   SYNTAX      INTEGER
               {
               disabled (0),
               enabled (1)
               }
   MAX-ACCESS  read-write
   STATUS      current
   DESCRIPTION
      "Path: swPort.editConf.ipV6.icmpMessages.optionUnrecognized

       Possibilities:
               disabled   (0)
               enabled   (1)"
   ::= {er1645v2EthPortSwIIpV6Entry 304087040}

er1645v2EthPortSwIIpV6IcmpMessagesRedirect OBJECT-TYPE
   SYNTAX      INTEGER
               {
               disabled (0),
               enabled (1)
               }
   MAX-ACCESS  read-write
   STATUS      current
   DESCRIPTION
      "Path: swPort.editConf.ipV6.icmpMessages.redirect

       Possibilities:
               disabled   (0)
               enabled   (1)"
   ::= {er1645v2EthPortSwIIpV6Entry 304611328}

er1645v2EthPortSwIIpV6Addresses OBJECT-TYPE
   SYNTAX      SEQUENCE OF Er1645v2EthPortSwIIpV6AddressesEntry
   MAX-ACCESS  not-accessible
   STATUS      current
   DESCRIPTION
      ""
   ::= {er1645v2EthPortSwIIpV6 50331648}

er1645v2EthPortSwIIpV6AddressesEntry OBJECT-TYPE
   SYNTAX      Er1645v2EthPortSwIIpV6AddressesEntry
   MAX-ACCESS  not-accessible
   STATUS      current
   DESCRIPTION
      ""
   INDEX      { er1645v2EthPortSwIIpV6AddressesGlobalIx,
                er1645v2EthPortSwIIpV6AddressesTableIx }
   ::= {er1645v2EthPortSwIIpV6Addresses 1}

Er1645v2EthPortSwIIpV6AddressesEntry ::=
   SEQUENCE
      {
      er1645v2EthPortSwIIpV6AddressesActions
         VariableLengthTableActions,
      er1645v2EthPortSwIIpV6AddressesGlobalIx
         GlobalIndex,
      er1645v2EthPortSwIIpV6AddressesTableIx
         TableIndex,
      er1645v2EthPortSwIIpV6AddressesType
         INTEGER,
      er1645v2EthPortSwIIpV6AddressesAddress
         Ipv6Address,
      er1645v2EthPortSwIIpV6AddressesPrefixLength
         Integer32,
      er1645v2EthPortSwIIpV6AddressesGeneralPrefix
         DisplayString,
      er1645v2EthPortSwIIpV6AddressesRaSend
         INTEGER,
      er1645v2EthPortSwIIpV6AddressesRaOnLinkFlag
         INTEGER,
      er1645v2EthPortSwIIpV6AddressesRaAutoFlag
         INTEGER,
      er1645v2EthPortSwIIpV6AddressesRaValidLifeTime
         TimeTicks,
      er1645v2EthPortSwIIpV6AddressesRaValidLTMode
         INTEGER,
      er1645v2EthPortSwIIpV6AddressesRaPrefLifeTime
         TimeTicks,
      er1645v2EthPortSwIIpV6AddressesRaPrefLTMode
         INTEGER
      }

er1645v2EthPortSwIIpV6AddressesActions OBJECT-TYPE
   SYNTAX      VariableLengthTableActions
   MAX-ACCESS  read-write
   STATUS      current
   DESCRIPTION
      "By way of this field, some manipulations
       on this table may be performed."
   ::= {er1645v2EthPortSwIIpV6AddressesEntry 2}

er1645v2EthPortSwIIpV6AddressesGlobalIx OBJECT-TYPE
   SYNTAX      GlobalIndex
   MAX-ACCESS  not-accessible
   STATUS      current
   DESCRIPTION
      "The value of the tlsCntTreeGlobalIndex of the MANAGED OBJECT."
   ::= {er1645v2EthPortSwIIpV6AddressesEntry 10}

er1645v2EthPortSwIIpV6AddressesTableIx OBJECT-TYPE
   SYNTAX      TableIndex
   MAX-ACCESS  not-accessible
   STATUS      current
   DESCRIPTION
      ""
   ::= {er1645v2EthPortSwIIpV6AddressesEntry 11}

er1645v2EthPortSwIIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.ipV6.addresses.type

       Possibilities:
               unicast   (0)
               eui64   (1)
               anycast   (2)
               linkLocal   (3)
               generalPrefix   (4)"
   ::= {er1645v2EthPortSwIIpV6AddressesEntry 50331648}

er1645v2EthPortSwIIpV6AddressesAddress OBJECT-TYPE
   SYNTAX      Ipv6Address
   MAX-ACCESS  read-write
   STATUS      current
   DESCRIPTION
      "Path: swPort.editConf.ipV6.addresses.address

       ipv6 address"
   ::= {er1645v2EthPortSwIIpV6AddressesEntry 16777216}

er1645v2EthPortSwIIpV6AddressesPrefixLength OBJECT-TYPE
   SYNTAX      Integer32
   MAX-ACCESS  read-write
   STATUS      current
   DESCRIPTION
      "Path: swPort.editConf.ipV6.addresses.prefixLength"
   ::= {er1645v2EthPortSwIIpV6AddressesEntry 33554432}

er1645v2EthPortSwIIpV6AddressesGeneralPrefix OBJECT-TYPE
   SYNTAX      DisplayString
   MAX-ACCESS  read-write
   STATUS      current
   DESCRIPTION
      "Path: swPort.editConf.ipV6.addresses.generalPrefix"
   ::= {er1645v2EthPortSwIIpV6AddressesEntry 83886080}

er1645v2EthPortSwIIpV6AddressesRaSend OBJECT-TYPE
   SYNTAX      INTEGER
               {
               disabled (0),
               enabled (1)
               }
   MAX-ACCESS  read-write
   STATUS      current
   DESCRIPTION
      "Path: swPort.editConf.ipV6.addresses.ra.send

       Possibilities:
               disabled   (0)
               enabled   (1)"
   ::= {er1645v2EthPortSwIIpV6AddressesEntry 67174400}

er1645v2EthPortSwIIpV6AddressesRaOnLinkFlag OBJECT-TYPE
   SYNTAX      INTEGER
               {
               disabled (0),
               enabled (1)
               }
   MAX-ACCESS  read-write
   STATUS      current
   DESCRIPTION
      "Path: swPort.editConf.ipV6.addresses.ra.onLinkFlag

       Possibilities:
               disabled   (0)
               enabled   (1)"
   ::= {er1645v2EthPortSwIIpV6AddressesEntry 67371008}

er1645v2EthPortSwIIpV6AddressesRaAutoFlag OBJECT-TYPE
   SYNTAX      INTEGER
               {
               disabled (0),
               enabled (1)
               }
   MAX-ACCESS  read-write
   STATUS      current
   DESCRIPTION
      "Path: swPort.editConf.ipV6.addresses.ra.autonomousFlag

       Possibilities:
               disabled   (0)
               enabled   (1)"
   ::= {er1645v2EthPortSwIIpV6AddressesEntry 67567616}

er1645v2EthPortSwIIpV6AddressesRaValidLifeTime OBJECT-TYPE
   SYNTAX      TimeTicks
   MAX-ACCESS  read-write
   STATUS      current
   DESCRIPTION
      "Path: swPort.editConf.ipV6.addresses.ra.validLifeTime

       Time in centi-second."
   ::= {er1645v2EthPortSwIIpV6AddressesEntry 67239936}

er1645v2EthPortSwIIpV6AddressesRaValidLTMode OBJECT-TYPE
   SYNTAX      INTEGER
               {
               fixed (0),
               infinite (2)
               }
   MAX-ACCESS  read-write
   STATUS      current
   DESCRIPTION
      "Path: swPort.editConf.ipV6.addresses.ra.validLifeTimeMode

       Possibilities:
               fixed   (0)
               infinite   (2)"
   ::= {er1645v2EthPortSwIIpV6AddressesEntry 67305472}

er1645v2EthPortSwIIpV6AddressesRaPrefLifeTime OBJECT-TYPE
   SYNTAX      TimeTicks
   MAX-ACCESS  read-write
   STATUS      current
   DESCRIPTION
      "Path: swPort.editConf.ipV6.addresses.ra.prefLifeTime

       Time in centi-second."
   ::= {er1645v2EthPortSwIIpV6AddressesEntry 67436544}

er1645v2EthPortSwIIpV6AddressesRaPrefLTMode OBJECT-TYPE
   SYNTAX      INTEGER
               {
               fixed (0),
               infinite (2)
               }
   MAX-ACCESS  read-write
   STATUS      current
   DESCRIPTION
      "Path: swPort.editConf.ipV6.addresses.ra.prefLifeTimeMode

       Possibilities:
               fixed   (0)
               infinite   (2)"
   ::= {er1645v2EthPortSwIIpV6AddressesEntry 67502080}

er1645v2EthPortSwIIpV6RaDnsOptionsRdnssServers OBJECT-TYPE
   SYNTAX      SEQUENCE OF Er1645v2EthPortSwIIpV6RaDnsOptionsRdnssServersEntry
   MAX-ACCESS  not-accessible
   STATUS      current
   DESCRIPTION
      ""
   ::= {er1645v2EthPortSwIIpV6 101394432}

er1645v2EthPortSwIIpV6RaDnsOptionsRdnssServersEntry OBJECT-TYPE
   SYNTAX      Er1645v2EthPortSwIIpV6RaDnsOptionsRdnssServersEntry
   MAX-ACCESS  not-accessible
   STATUS      current
   DESCRIPTION
      ""
   INDEX      { er1645v2EthPortSwIIpV6RaDnsOptionsRdnssServersGlobalIx,
                er1645v2EthPortSwIIpV6RaDnsOptionsRdnssServersTableIx }
   ::= {er1645v2EthPortSwIIpV6RaDnsOptionsRdnssServers 1}

Er1645v2EthPortSwIIpV6RaDnsOptionsRdnssServersEntry ::=
   SEQUENCE
      {
      er1645v2EthPortSwIIpV6RaDnsOptionsRdnssServersActions
         VariableLengthTableActions,
      er1645v2EthPortSwIIpV6RaDnsOptionsRdnssServersGlobalIx
         GlobalIndex,
      er1645v2EthPortSwIIpV6RaDnsOptionsRdnssServersTableIx
         TableIndex,
      er1645v2EthPortSwIIpV6RaDnsOptionsRdnssServersAddress
         Ipv6Address
      }

er1645v2EthPortSwIIpV6RaDnsOptionsRdnssServersActions OBJECT-TYPE
   SYNTAX      VariableLengthTableActions
   MAX-ACCESS  read-write
   STATUS      current
   DESCRIPTION
      "By way of this field, some manipulations
       on this table may be performed."
   ::= {er1645v2EthPortSwIIpV6RaDnsOptionsRdnssServersEntry 2}

er1645v2EthPortSwIIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPortSwIIpV6RaDnsOptionsRdnssServersEntry 10}

er1645v2EthPortSwIIpV6RaDnsOptionsRdnssServersTableIx OBJECT-TYPE
   SYNTAX      TableIndex
   MAX-ACCESS  not-accessible
   STATUS      current
   DESCRIPTION
      ""
   ::= {er1645v2EthPortSwIIpV6RaDnsOptionsRdnssServersEntry 11}

er1645v2EthPortSwIIpV6RaDnsOptionsRdnssServersAddress OBJECT-TYPE
   SYNTAX      Ipv6Address
   MAX-ACCESS  read-write
   STATUS      current
   DESCRIPTION
      "Path: swPort.editConf.ipV6.ra.dnsOptions.rdnss.servers.address

       ipv6 address"
   ::= {er1645v2EthPortSwIIpV6RaDnsOptionsRdnssServersEntry 16777216}

er1645v2EthPortSwIIpV6RaDnsOptionsDnsslDomains OBJECT-TYPE
   SYNTAX      SEQUENCE OF Er1645v2EthPortSwIIpV6RaDnsOptionsDnsslDomainsEntry
   MAX-ACCESS  not-accessible
   STATUS      current
   DESCRIPTION
      ""
   ::= {er1645v2EthPortSwIIpV6 101402624}

er1645v2EthPortSwIIpV6RaDnsOptionsDnsslDomainsEntry OBJECT-TYPE
   SYNTAX      Er1645v2EthPortSwIIpV6RaDnsOptionsDnsslDomainsEntry
   MAX-ACCESS  not-accessible
   STATUS      current
   DESCRIPTION
      ""
   INDEX      { er1645v2EthPortSwIIpV6RaDnsOptionsDnsslDomainsGlobalIx,
                er1645v2EthPortSwIIpV6RaDnsOptionsDnsslDomainsTableIx }
   ::= {er1645v2EthPortSwIIpV6RaDnsOptionsDnsslDomains 1}

Er1645v2EthPortSwIIpV6RaDnsOptionsDnsslDomainsEntry ::=
   SEQUENCE
      {
      er1645v2EthPortSwIIpV6RaDnsOptionsDnsslDomainsActions
         VariableLengthTableActions,
      er1645v2EthPortSwIIpV6RaDnsOptionsDnsslDomainsGlobalIx
         GlobalIndex,
      er1645v2EthPortSwIIpV6RaDnsOptionsDnsslDomainsTableIx
         TableIndex,
      er1645v2EthPortSwIIpV6RaDnsOptionsDnsslDomainsName
         DisplayString
      }

er1645v2EthPortSwIIpV6RaDnsOptionsDnsslDomainsActions OBJECT-TYPE
   SYNTAX      VariableLengthTableActions
   MAX-ACCESS  read-write
   STATUS      current
   DESCRIPTION
      "By way of this field, some manipulations
       on this table may be performed."
   ::= {er1645v2EthPortSwIIpV6RaDnsOptionsDnsslDomainsEntry 2}

er1645v2EthPortSwIIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPortSwIIpV6RaDnsOptionsDnsslDomainsEntry 10}

er1645v2EthPortSwIIpV6RaDnsOptionsDnsslDomainsTableIx OBJECT-TYPE
   SYNTAX      TableIndex
   MAX-ACCESS  not-accessible
   STATUS      current
   DESCRIPTION
      ""
   ::= {er1645v2EthPortSwIIpV6RaDnsOptionsDnsslDomainsEntry 11}

er1645v2EthPortSwIIpV6RaDnsOptionsDnsslDomainsName OBJECT-TYPE
   SYNTAX      DisplayString
   MAX-ACCESS  read-write
   STATUS      current
   DESCRIPTION
      "Path: swPort.editConf.ipV6.ra.dnsOptions.dnssl.domains.name"
   ::= {er1645v2EthPortSwIIpV6RaDnsOptionsDnsslDomainsEntry 16777216}

er1645v2EthPortSwIIpV6DhcpClientUserClassOpt OBJECT-TYPE
   SYNTAX      SEQUENCE OF Er1645v2EthPortSwIIpV6DhcpClientUserClassOptEntry
   MAX-ACCESS  not-accessible
   STATUS      current
   DESCRIPTION
      ""
   ::= {er1645v2EthPortSwIIpV6 171442176}

er1645v2EthPortSwIIpV6DhcpClientUserClassOptEntry OBJECT-TYPE
   SYNTAX      Er1645v2EthPortSwIIpV6DhcpClientUserClassOptEntry
   MAX-ACCESS  not-accessible
   STATUS      current
   DESCRIPTION
      ""
   INDEX      { er1645v2EthPortSwIIpV6DhcpClientUserClassOptGlobalIx,
                er1645v2EthPortSwIIpV6DhcpClientUserClassOptTableIx }
   ::= {er1645v2EthPortSwIIpV6DhcpClientUserClassOpt 1}

Er1645v2EthPortSwIIpV6DhcpClientUserClassOptEntry ::=
   SEQUENCE
      {
      er1645v2EthPortSwIIpV6DhcpClientUserClassOptActions
         VariableLengthTableActions,
      er1645v2EthPortSwIIpV6DhcpClientUserClassOptGlobalIx
         GlobalIndex,
      er1645v2EthPortSwIIpV6DhcpClientUserClassOptTableIx
         TableIndex,
      er1645v2EthPortSwIIpV6DhcpClientUserClassOptValueAscii
         DisplayString,
      er1645v2EthPortSwIIpV6DhcpClientUserClassOptValueDecimal
         Integer32,
      er1645v2EthPortSwIIpV6DhcpClientUserClassOptValueHexData
         OCTET STRING
      }

er1645v2EthPortSwIIpV6DhcpClientUserClassOptActions OBJECT-TYPE
   SYNTAX      VariableLengthTableActions
   MAX-ACCESS  read-write
   STATUS      current
   DESCRIPTION
      "By way of this field, some manipulations
       on this table may be performed."
   ::= {er1645v2EthPortSwIIpV6DhcpClientUserClassOptEntry 2}

er1645v2EthPortSwIIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPortSwIIpV6DhcpClientUserClassOptEntry 10}

er1645v2EthPortSwIIpV6DhcpClientUserClassOptTableIx OBJECT-TYPE
   SYNTAX      TableIndex
   MAX-ACCESS  not-accessible
   STATUS      current
   DESCRIPTION
      ""
   ::= {er1645v2EthPortSwIIpV6DhcpClientUserClassOptEntry 11}

er1645v2EthPortSwIIpV6DhcpClientUserClassOptValueAscii OBJECT-TYPE
   SYNTAX      DisplayString
   MAX-ACCESS  read-write
   STATUS      current
   DESCRIPTION
      "Path: swPort.editConf.ipV6.dhcp.client.userClassOpt.value.ascii"
   ::= {er1645v2EthPortSwIIpV6DhcpClientUserClassOptEntry 16842752}

er1645v2EthPortSwIIpV6DhcpClientUserClassOptValueDecimal OBJECT-TYPE
   SYNTAX      Integer32
   MAX-ACCESS  read-write
   STATUS      current
   DESCRIPTION
      "Path: swPort.editConf.ipV6.dhcp.client.userClassOpt.value.decimal"
   ::= {er1645v2EthPortSwIIpV6DhcpClientUserClassOptEntry 16908288}

er1645v2EthPortSwIIpV6DhcpClientUserClassOptValueHexData OBJECT-TYPE
   SYNTAX      OCTET STRING
   MAX-ACCESS  read-write
   STATUS      current
   DESCRIPTION
      "Path: swPort.editConf.ipV6.dhcp.client.userClassOpt.value.hexData"
   ::= {er1645v2EthPortSwIIpV6DhcpClientUserClassOptEntry 16973824}

er1645v2EthPortSwIIpV6DhcpClientVendorCl OBJECT-TYPE
   SYNTAX      SEQUENCE OF Er1645v2EthPortSwIIpV6DhcpClientVendorClEntry
   MAX-ACCESS  not-accessible
   STATUS      current
   DESCRIPTION
      ""
   ::= {er1645v2EthPortSwIIpV6 171704320}

er1645v2EthPortSwIIpV6DhcpClientVendorClEntry OBJECT-TYPE
   SYNTAX      Er1645v2EthPortSwIIpV6DhcpClientVendorClEntry
   MAX-ACCESS  not-accessible
   STATUS      current
   DESCRIPTION
      ""
   INDEX      { er1645v2EthPortSwIIpV6DhcpClientVendorClGlobalIx,
                er1645v2EthPortSwIIpV6DhcpClientVendorClTableIx }
   ::= {er1645v2EthPortSwIIpV6DhcpClientVendorCl 1}

Er1645v2EthPortSwIIpV6DhcpClientVendorClEntry ::=
   SEQUENCE
      {
      er1645v2EthPortSwIIpV6DhcpClientVendorClActions
         VariableLengthTableActions,
      er1645v2EthPortSwIIpV6DhcpClientVendorClGlobalIx
         GlobalIndex,
      er1645v2EthPortSwIIpV6DhcpClientVendorClTableIx
         TableIndex,
      er1645v2EthPortSwIIpV6DhcpClientVendorClValueAscii
         DisplayString,
      er1645v2EthPortSwIIpV6DhcpClientVendorClValueDecimal
         Integer32,
      er1645v2EthPortSwIIpV6DhcpClientVendorClValueHexData
         OCTET STRING
      }

er1645v2EthPortSwIIpV6DhcpClientVendorClActions OBJECT-TYPE
   SYNTAX      VariableLengthTableActions
   MAX-ACCESS  read-write
   STATUS      current
   DESCRIPTION
      "By way of this field, some manipulations
       on this table may be performed."
   ::= {er1645v2EthPortSwIIpV6DhcpClientVendorClEntry 2}

er1645v2EthPortSwIIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPortSwIIpV6DhcpClientVendorClEntry 10}

er1645v2EthPortSwIIpV6DhcpClientVendorClTableIx OBJECT-TYPE
   SYNTAX      TableIndex
   MAX-ACCESS  not-accessible
   STATUS      current
   DESCRIPTION
      ""
   ::= {er1645v2EthPortSwIIpV6DhcpClientVendorClEntry 11}

er1645v2EthPortSwIIpV6DhcpClientVendorClValueAscii OBJECT-TYPE
   SYNTAX      DisplayString
   MAX-ACCESS  read-write
   STATUS      current
   DESCRIPTION
      "Path: swPort.editConf.ipV6.dhcp.client.vendorClassOpt.value.ascii"
   ::= {er1645v2EthPortSwIIpV6DhcpClientVendorClEntry 16842752}

er1645v2EthPortSwIIpV6DhcpClientVendorClValueDecimal OBJECT-TYPE
   SYNTAX      Integer32
   MAX-ACCESS  read-write
   STATUS      current
   DESCRIPTION
      "Path: swPort.editConf.ipV6.dhcp.client.vendorClassOpt.value.decimal"
   ::= {er1645v2EthPortSwIIpV6DhcpClientVendorClEntry 16908288}

er1645v2EthPortSwIIpV6DhcpClientVendorClValueHexData OBJECT-TYPE
   SYNTAX      OCTET STRING
   MAX-ACCESS  read-write
   STATUS      current
   DESCRIPTION
      "Path: swPort.editConf.ipV6.dhcp.client.vendorClassOpt.value.hexData"
   ::= {er1645v2EthPortSwIIpV6DhcpClientVendorClEntry 16973824}

er1645v2EthPortSwIIpV6DhcpRelayDestinations OBJECT-TYPE
   SYNTAX      SEQUENCE OF Er1645v2EthPortSwIIpV6DhcpRelayDestinationsEntry
   MAX-ACCESS  not-accessible
   STATUS      current
   DESCRIPTION
      ""
   ::= {er1645v2EthPortSwIIpV6 174080000}

er1645v2EthPortSwIIpV6DhcpRelayDestinationsEntry OBJECT-TYPE
   SYNTAX      Er1645v2EthPortSwIIpV6DhcpRelayDestinationsEntry
   MAX-ACCESS  not-accessible
   STATUS      current
   DESCRIPTION
      ""
   INDEX      { er1645v2EthPortSwIIpV6DhcpRelayDestinationsGlobalIx,
                er1645v2EthPortSwIIpV6DhcpRelayDestinationsTableIx }
   ::= {er1645v2EthPortSwIIpV6DhcpRelayDestinations 1}

Er1645v2EthPortSwIIpV6DhcpRelayDestinationsEntry ::=
   SEQUENCE
      {
      er1645v2EthPortSwIIpV6DhcpRelayDestinationsActions
         VariableLengthTableActions,
      er1645v2EthPortSwIIpV6DhcpRelayDestinationsGlobalIx
         GlobalIndex,
      er1645v2EthPortSwIIpV6DhcpRelayDestinationsTableIx
         TableIndex,
      er1645v2EthPortSwIIpV6DhcpRelayDestinationsAddress
         Ipv6Address,
      er1645v2EthPortSwIIpV6DhcpRelayDestinationsInterface
         DisplayString
      }

er1645v2EthPortSwIIpV6DhcpRelayDestinationsActions OBJECT-TYPE
   SYNTAX      VariableLengthTableActions
   MAX-ACCESS  read-write
   STATUS      current
   DESCRIPTION
      "By way of this field, some manipulations
       on this table may be performed."
   ::= {er1645v2EthPortSwIIpV6DhcpRelayDestinationsEntry 2}

er1645v2EthPortSwIIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPortSwIIpV6DhcpRelayDestinationsEntry 10}

er1645v2EthPortSwIIpV6DhcpRelayDestinationsTableIx OBJECT-TYPE
   SYNTAX      TableIndex
   MAX-ACCESS  not-accessible
   STATUS      current
   DESCRIPTION
      ""
   ::= {er1645v2EthPortSwIIpV6DhcpRelayDestinationsEntry 11}

er1645v2EthPortSwIIpV6DhcpRelayDestinationsAddress OBJECT-TYPE
   SYNTAX      Ipv6Address
   MAX-ACCESS  read-write
   STATUS      current
   DESCRIPTION
      "Path: swPort.editConf.ipV6.dhcp.relay.destinations.address

       ipv6 address"
   ::= {er1645v2EthPortSwIIpV6DhcpRelayDestinationsEntry 16777216}

er1645v2EthPortSwIIpV6DhcpRelayDestinationsInterface OBJECT-TYPE
   SYNTAX      DisplayString
   MAX-ACCESS  read-write
   STATUS      current
   DESCRIPTION
      "Path: swPort.editConf.ipV6.dhcp.relay.destinations.interface"
   ::= {er1645v2EthPortSwIIpV6DhcpRelayDestinationsEntry 33554432}


er1645v2EthPortSwIMode OBJECT IDENTIFIER ::= {er1645v2EthPortSwI 29}

er1645v2EthPortSwIModeTable OBJECT-TYPE
   SYNTAX      SEQUENCE OF Er1645v2EthPortSwIModeEntry
   MAX-ACCESS  not-accessible
   STATUS      current
   DESCRIPTION
      "routing and/or bridging or ipV6 or multilink selection"
   ::= {er1645v2EthPortSwIMode 1}

er1645v2EthPortSwIModeEntry OBJECT-TYPE
   SYNTAX      Er1645v2EthPortSwIModeEntry
   MAX-ACCESS  not-accessible
   STATUS      current
   DESCRIPTION
      ""
   INDEX      { er1645v2EthPortSwIModeGlobalIx }
   ::= {er1645v2EthPortSwIModeTable 1}

Er1645v2EthPortSwIModeEntry ::=
   SEQUENCE
      {
      er1645v2EthPortSwIModeGlobalIx
         GlobalIndex,
      er1645v2EthPortSwIModeValue
         INTEGER
      }

er1645v2EthPortSwIModeGlobalIx OBJECT-TYPE
   SYNTAX      GlobalIndex
   MAX-ACCESS  not-accessible
   STATUS      current
   DESCRIPTION
      "The value of the tlsCntTreeGlobalIndex of the MANAGED OBJECT."
   ::= {er1645v2EthPortSwIModeEntry 10}

er1645v2EthPortSwIModeValue OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: swPort.editConf.mode

       Possibilities:
               bridging   (0)
               routing   (1)
               routingAndBridging   (2)
               ipV6   (3)
               ipV6/ipV4   (4)
               multilink   (5)"
   ::= {er1645v2EthPortSwIModeEntry 2147483648}


er1645v2EthPortSwIIp OBJECT IDENTIFIER ::= {er1645v2EthPortSwI 1}

er1645v2EthPortSwIIpSSCTable OBJECT-TYPE
   SYNTAX      SEQUENCE OF Er1645v2EthPortSwIIpEntry
   MAX-ACCESS  not-accessible
   STATUS      current
   DESCRIPTION
      "ip interface config parameters"
   ::= {er1645v2EthPortSwIIp 1}

er1645v2EthPortSwIIpEntry OBJECT-TYPE
   SYNTAX      Er1645v2EthPortSwIIpEntry
   MAX-ACCESS  not-accessible
   STATUS      current
   DESCRIPTION
      ""
   INDEX      { er1645v2EthPortSwIIpGlobalIx }
   ::= {er1645v2EthPortSwIIpSSCTable 1}

Er1645v2EthPortSwIIpEntry ::=
   SEQUENCE
      {
      er1645v2EthPortSwIIpGlobalIx
         GlobalIndex,
      er1645v2EthPortSwIIpVrfRouter
         DisplayString,
      er1645v2EthPortSwIIpAdr
         IpAddress,
      er1645v2EthPortSwIIpNetm
         IpAddress,
      er1645v2EthPortSwIIpSNetName
         INTEGER,
      er1645v2EthPortSwIIpSNetCust
         DisplayString,
      er1645v2EthPortSwIIpDhcpC
         INTEGER,
      er1645v2EthPortSwIIpDhcpGatewayPreference
         Integer32,
      er1645v2EthPortSwIIpDhcpRoutePreference
         Integer32,
      er1645v2EthPortSwIIpDhcpDnsPreference
         Integer32,
      er1645v2EthPortSwIIpMtu
         Integer32,
      er1645v2EthPortSwIIpMssAdjust
         INTEGER,
      er1645v2EthPortSwIIpRipMetric
         Integer32,
      er1645v2EthPortSwIIpRipMetricOut
         Integer32,
      er1645v2EthPortSwIIpRipMode
         INTEGER,
      er1645v2EthPortSwIIpRipTxVer
         INTEGER,
      er1645v2EthPortSwIIpRipRxVer
         INTEGER,
      er1645v2EthPortSwIIpRipSplitH
         INTEGER,
      er1645v2EthPortSwIIpRipAuth
         INTEGER,
      er1645v2EthPortSwIIpRipFilter
         DisplayString,
      er1645v2EthPortSwIIpRipFilterIn
         DisplayString,
      er1645v2EthPortSwIIpRipClearNextHop
         INTEGER,
      er1645v2EthPortSwIIpAccPol
         DisplayString,
      er1645v2EthPortSwIIpAB
         DisplayString,
      er1645v2EthPortSwIIpMA
         INTEGER,
      er1645v2EthPortSwIIpMF
         Integer32,
      er1645v2EthPortSwIIpDB
         INTEGER,
      er1645v2EthPortSwIIpIR
         INTEGER,
      er1645v2EthPortSwIIpIgmp
         INTEGER,
      er1645v2EthPortSwIIpNN
         DisplayString,
      er1645v2EthPortSwIIpVrrp
         INTEGER,
      er1645v2EthPortSwIIpPimMode
         INTEGER,
      er1645v2EthPortSwIIpPimDrPriority
         Counter32,
      er1645v2EthPortSwIIpPimHelloTime
         TimeTicks,
      er1645v2EthPortSwIIpPimPropagationDelay
         TimeTicks,
      er1645v2EthPortSwIIpPimOverrideInterval
         TimeTicks,
      er1645v2EthPortSwIIpPimBsrBorder
         INTEGER,
      er1645v2EthPortSwIIpPimTtlThreshold
         Integer32,
      er1645v2EthPortSwIIpIMNetworkUnreachable
         INTEGER,
      er1645v2EthPortSwIIpIMHostUnreachable
         INTEGER,
      er1645v2EthPortSwIIpIMProtocolUnreachable
         INTEGER,
      er1645v2EthPortSwIIpIMPortUnreachable
         INTEGER,
      er1645v2EthPortSwIIpIMMtuExceeded
         INTEGER,
      er1645v2EthPortSwIIpIMAdminProhibited
         INTEGER,
      er1645v2EthPortSwIIpIMTtlExceeded
         INTEGER,
      er1645v2EthPortSwIIpIMRedirect
         INTEGER
      }

er1645v2EthPortSwIIpGlobalIx OBJECT-TYPE
   SYNTAX      GlobalIndex
   MAX-ACCESS  not-accessible
   STATUS      current
   DESCRIPTION
      "The value of the tlsCntTreeGlobalIndex of the MANAGED OBJECT."
   ::= {er1645v2EthPortSwIIpEntry 10}

er1645v2EthPortSwIIpVrfRouter OBJECT-TYPE
   SYNTAX      DisplayString
   MAX-ACCESS  read-write
   STATUS      current
   DESCRIPTION
      "Path: swPort.editConf.ip.vrfRouter"
   ::= {er1645v2EthPortSwIIpEntry 738197504}

er1645v2EthPortSwIIpAdr OBJECT-TYPE
   SYNTAX      IpAddress
   MAX-ACCESS  read-write
   STATUS      current
   DESCRIPTION
      "Path: swPort.editConf.ip.address"
   ::= {er1645v2EthPortSwIIpEntry 2030043136}

er1645v2EthPortSwIIpNetm OBJECT-TYPE
   SYNTAX      IpAddress
   MAX-ACCESS  read-write
   STATUS      current
   DESCRIPTION
      "Path: swPort.editConf.ip.netMask"
   ::= {er1645v2EthPortSwIIpEntry 2063597568}

er1645v2EthPortSwIIpSNetName OBJECT-TYPE
   SYNTAX      INTEGER
               {
               slOPTg (0),
               corp (2),
               dmz (3),
               internet (1)
               }
   MAX-ACCESS  read-write
   STATUS      current
   DESCRIPTION
      "Path: swPort.editConf.ip.sNet.name

       Possibilities:
               <OPT>   (0)
               corp   (2)
               dmz   (3)
               internet   (1)"
   ::= {er1645v2EthPortSwIIpEntry 855703552}

er1645v2EthPortSwIIpSNetCust OBJECT-TYPE
   SYNTAX      DisplayString
   MAX-ACCESS  read-write
   STATUS      current
   DESCRIPTION
      "Path: swPort.editConf.ip.sNet.custom"
   ::= {er1645v2EthPortSwIIpEntry 855769088}

er1645v2EthPortSwIIpDhcpC OBJECT-TYPE
   SYNTAX      INTEGER
               {
               disabled (0),
               enabled (1)
               }
   MAX-ACCESS  read-write
   STATUS      current
   DESCRIPTION
      "Path: swPort.editConf.ip.dhcpClient

       Possibilities:
               disabled   (0)
               enabled   (1)"
   ::= {er1645v2EthPortSwIIpEntry 838860800}

er1645v2EthPortSwIIpDhcpGatewayPreference OBJECT-TYPE
   SYNTAX      Integer32
   MAX-ACCESS  read-write
   STATUS      current
   DESCRIPTION
      "Path: swPort.editConf.ip.dhcp.gatewayPreference"
   ::= {er1645v2EthPortSwIIpEntry 872480768}

er1645v2EthPortSwIIpDhcpRoutePreference OBJECT-TYPE
   SYNTAX      Integer32
   MAX-ACCESS  read-write
   STATUS      current
   DESCRIPTION
      "Path: swPort.editConf.ip.dhcp.routePreference"
   ::= {er1645v2EthPortSwIIpEntry 872546304}

er1645v2EthPortSwIIpDhcpDnsPreference OBJECT-TYPE
   SYNTAX      Integer32
   MAX-ACCESS  read-write
   STATUS      current
   DESCRIPTION
      "Path: swPort.editConf.ip.dhcp.dnsPreference"
   ::= {er1645v2EthPortSwIIpEntry 872611840}

er1645v2EthPortSwIIpMtu OBJECT-TYPE
   SYNTAX      Integer32
   MAX-ACCESS  read-write
   STATUS      current
   DESCRIPTION
      "Path: swPort.editConf.ip.mtu"
   ::= {er1645v2EthPortSwIIpEntry 671088640}

er1645v2EthPortSwIIpMssAdjust OBJECT-TYPE
   SYNTAX      INTEGER
               {
               disabled (0),
               auto (65536)
               }
   MAX-ACCESS  read-write
   STATUS      current
   DESCRIPTION
      "Path: swPort.editConf.ip.mssAdjust

       Possibilities:
               disabled   (0)
               auto   (65536)"
   ::= {er1645v2EthPortSwIIpEntry 754974720}

er1645v2EthPortSwIIpRipMetric OBJECT-TYPE
   SYNTAX      Integer32
   MAX-ACCESS  read-write
   STATUS      current
   DESCRIPTION
      "Path: swPort.editConf.ip.rip.metric"
   ::= {er1645v2EthPortSwIIpEntry 353566720}

er1645v2EthPortSwIIpRipMetricOut OBJECT-TYPE
   SYNTAX      Integer32
   MAX-ACCESS  read-write
   STATUS      current
   DESCRIPTION
      "Path: swPort.editConf.ip.rip.metricOut"
   ::= {er1645v2EthPortSwIIpEntry 353632256}

er1645v2EthPortSwIIpRipMode OBJECT-TYPE
   SYNTAX      INTEGER
               {
               disabled (0),
               passive (1),
               active (2)
               }
   MAX-ACCESS  read-write
   STATUS      current
   DESCRIPTION
      "Path: swPort.editConf.ip.rip.mode

       Possibilities:
               disabled   (0)
               passive   (1)
               active   (2)"
   ::= {er1645v2EthPortSwIIpEntry 353697792}

er1645v2EthPortSwIIpRipTxVer OBJECT-TYPE
   SYNTAX      INTEGER
               {
               rip1 (0),
               rip2 (1),
               rip1mcompatible (2)
               }
   MAX-ACCESS  read-write
   STATUS      current
   DESCRIPTION
      "Path: swPort.editConf.ip.rip.txVersion

       Possibilities:
               rip1   (0)
               rip2   (1)
               rip1-compatible   (2)"
   ::= {er1645v2EthPortSwIIpEntry 354615296}

er1645v2EthPortSwIIpRipRxVer OBJECT-TYPE
   SYNTAX      INTEGER
               {
               rip1only (0),
               rip2only (1),
               rip12 (2)
               }
   MAX-ACCESS  read-write
   STATUS      current
   DESCRIPTION
      "Path: swPort.editConf.ip.rip.rxVersion

       Possibilities:
               rip1only   (0)
               rip2only   (1)
               rip1&2   (2)"
   ::= {er1645v2EthPortSwIIpEntry 354680832}

er1645v2EthPortSwIIpRipSplitH OBJECT-TYPE
   SYNTAX      INTEGER
               {
               disabled (0),
               enabled (1),
               poisonedReverse (2)
               }
   MAX-ACCESS  read-write
   STATUS      current
   DESCRIPTION
      "Path: swPort.editConf.ip.rip.splitHorizon

       Possibilities:
               disabled   (0)
               enabled   (1)
               poisonedReverse   (2)"
   ::= {er1645v2EthPortSwIIpEntry 353828864}

er1645v2EthPortSwIIpRipAuth OBJECT-TYPE
   SYNTAX      INTEGER
               {
               disabled (0),
               texts (1),
               md5 (2)
               }
   MAX-ACCESS  read-write
   STATUS      current
   DESCRIPTION
      "Path: swPort.editConf.ip.rip.authentication

       Possibilities:
               disabled   (0)
               text    (1)
               md5   (2)"
   ::= {er1645v2EthPortSwIIpEntry 353501184}

er1645v2EthPortSwIIpRipFilter OBJECT-TYPE
   SYNTAX      DisplayString
   MAX-ACCESS  read-write
   STATUS      current
   DESCRIPTION
      "Path: swPort.editConf.ip.rip.filter"
   ::= {er1645v2EthPortSwIIpEntry 354418688}

er1645v2EthPortSwIIpRipFilterIn OBJECT-TYPE
   SYNTAX      DisplayString
   MAX-ACCESS  read-write
   STATUS      current
   DESCRIPTION
      "Path: swPort.editConf.ip.rip.filterIn"
   ::= {er1645v2EthPortSwIIpEntry 354484224}

er1645v2EthPortSwIIpRipClearNextHop OBJECT-TYPE
   SYNTAX      INTEGER
               {
               disabled (0),
               enabled (1)
               }
   MAX-ACCESS  read-write
   STATUS      current
   DESCRIPTION
      "Path: swPort.editConf.ip.rip.clearNextHop

       Possibilities:
               disabled   (0)
               enabled   (1)"
   ::= {er1645v2EthPortSwIIpEntry 352452608}

er1645v2EthPortSwIIpAccPol OBJECT-TYPE
   SYNTAX      DisplayString
   MAX-ACCESS  read-write
   STATUS      current
   DESCRIPTION
      "Path: swPort.editConf.ip.accessPolicy"
   ::= {er1645v2EthPortSwIIpEntry 704643072}

er1645v2EthPortSwIIpAB OBJECT-TYPE
   SYNTAX      DisplayString
   MAX-ACCESS  read-write
   STATUS      current
   DESCRIPTION
      "Path: swPort.editConf.ip.trafficPolicy"
   ::= {er1645v2EthPortSwIIpEntry 234881024}

er1645v2EthPortSwIIpMA OBJECT-TYPE
   SYNTAX      INTEGER
               {
               disabled (0),
               enabled (1)
               }
   MAX-ACCESS  read-write
   STATUS      current
   DESCRIPTION
      "Path: swPort.editConf.ip.mgmtAccess

       Possibilities:
               disabled   (0)
               enabled   (1)"
   ::= {er1645v2EthPortSwIIpEntry 268435456}

er1645v2EthPortSwIIpMF OBJECT-TYPE
   SYNTAX      Integer32
   MAX-ACCESS  read-write
   STATUS      current
   DESCRIPTION
      "Path: swPort.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPortSwIIpEntry 285212672}

er1645v2EthPortSwIIpDB OBJECT-TYPE
   SYNTAX      INTEGER
               {
               disabled (0),
               enabled (1)
               }
   MAX-ACCESS  read-write
   STATUS      current
   DESCRIPTION
      "Path: swPort.editConf.ip.directedBroadcasts

       Possibilities:
               disabled   (0)
               enabled   (1)"
   ::= {er1645v2EthPortSwIIpEntry 369098752}

er1645v2EthPortSwIIpIR OBJECT-TYPE
   SYNTAX      INTEGER
               {
               disabled (0),
               enabled (1)
               }
   MAX-ACCESS  read-write
   STATUS      current
   DESCRIPTION
      "Path: swPort.editConf.ip.icmpRedirects

       Possibilities:
               disabled   (0)
               enabled   (1)"
   ::= {er1645v2EthPortSwIIpEntry 436207616}

er1645v2EthPortSwIIpIgmp OBJECT-TYPE
   SYNTAX      INTEGER
               {
               disabled (0),
               proxy (1),
               router (2),
               v3Router (5)
               }
   MAX-ACCESS  read-write
   STATUS      current
   DESCRIPTION
      "Path: swPort.editConf.ip.igmp

       Possibilities:
               disabled   (0)
               proxy   (1)
               router   (2)
               v3Router   (5)"
   ::= {er1645v2EthPortSwIIpEntry 536870912}

er1645v2EthPortSwIIpNN OBJECT-TYPE
   SYNTAX      DisplayString
   MAX-ACCESS  read-write
   STATUS      current
   DESCRIPTION
      "Path: swPort.editConf.ip.nat"
   ::= {er1645v2EthPortSwIIpEntry 452984832}

er1645v2EthPortSwIIpVrrp OBJECT-TYPE
   SYNTAX      INTEGER
               {
               disabled (0),
               enabled (1)
               }
   MAX-ACCESS  read-write
   STATUS      current
   DESCRIPTION
      "Path: swPort.editConf.ip.vrrp

       Possibilities:
               disabled   (0)
               enabled   (1)"
   ::= {er1645v2EthPortSwIIpEntry 721420288}

er1645v2EthPortSwIIpPimMode OBJECT-TYPE
   SYNTAX      INTEGER
               {
               disabled (0),
               sparse (1),
               passive (2)
               }
   MAX-ACCESS  read-write
   STATUS      current
   DESCRIPTION
      "Path: swPort.editConf.ip.pim.mode

       Possibilities:
               disabled   (0)
               sparse   (1)
               passive   (2)"
   ::= {er1645v2EthPortSwIIpEntry 771817472}

er1645v2EthPortSwIIpPimDrPriority OBJECT-TYPE
   SYNTAX      Counter32
   MAX-ACCESS  read-write
   STATUS      current
   DESCRIPTION
      "Path: swPort.editConf.ip.pim.drPriority

       32 bit unsigned wrappable counter."
   ::= {er1645v2EthPortSwIIpEntry 771883008}

er1645v2EthPortSwIIpPimHelloTime OBJECT-TYPE
   SYNTAX      TimeTicks
   MAX-ACCESS  read-write
   STATUS      current
   DESCRIPTION
      "Path: swPort.editConf.ip.pim.helloTime

       Time in centi-second."
   ::= {er1645v2EthPortSwIIpEntry 771948544}

er1645v2EthPortSwIIpPimPropagationDelay OBJECT-TYPE
   SYNTAX      TimeTicks
   MAX-ACCESS  read-write
   STATUS      current
   DESCRIPTION
      "Path: swPort.editConf.ip.pim.propagationDelay

       Time in centi-second."
   ::= {er1645v2EthPortSwIIpEntry 772014080}

er1645v2EthPortSwIIpPimOverrideInterval OBJECT-TYPE
   SYNTAX      TimeTicks
   MAX-ACCESS  read-write
   STATUS      current
   DESCRIPTION
      "Path: swPort.editConf.ip.pim.overrideInterval

       Time in centi-second."
   ::= {er1645v2EthPortSwIIpEntry 772079616}

er1645v2EthPortSwIIpPimBsrBorder OBJECT-TYPE
   SYNTAX      INTEGER
               {
               disabled (0),
               enabled (1)
               }
   MAX-ACCESS  read-write
   STATUS      current
   DESCRIPTION
      "Path: swPort.editConf.ip.pim.bsrBorder

       Possibilities:
               disabled   (0)
               enabled   (1)"
   ::= {er1645v2EthPortSwIIpEntry 772145152}

er1645v2EthPortSwIIpPimTtlThreshold OBJECT-TYPE
   SYNTAX      Integer32
   MAX-ACCESS  read-write
   STATUS      current
   DESCRIPTION
      "Path: swPort.editConf.ip.pim.ttlThreshold"
   ::= {er1645v2EthPortSwIIpEntry 772210688}

er1645v2EthPortSwIIpIMNetworkUnreachable OBJECT-TYPE
   SYNTAX      INTEGER
               {
               disabled (0),
               enabled (1)
               }
   MAX-ACCESS  read-write
   STATUS      current
   DESCRIPTION
      "Path: swPort.editConf.ip.icmpMessages.networkUnreachable

       Possibilities:
               disabled   (0)
               enabled   (1)"
   ::= {er1645v2EthPortSwIIpEntry 788594688}

er1645v2EthPortSwIIpIMHostUnreachable OBJECT-TYPE
   SYNTAX      INTEGER
               {
               disabled (0),
               enabled (1)
               }
   MAX-ACCESS  read-write
   STATUS      current
   DESCRIPTION
      "Path: swPort.editConf.ip.icmpMessages.hostUnreachable

       Possibilities:
               disabled   (0)
               enabled   (1)"
   ::= {er1645v2EthPortSwIIpEntry 788660224}

er1645v2EthPortSwIIpIMProtocolUnreachable OBJECT-TYPE
   SYNTAX      INTEGER
               {
               disabled (0),
               enabled (1)
               }
   MAX-ACCESS  read-write
   STATUS      current
   DESCRIPTION
      "Path: swPort.editConf.ip.icmpMessages.protocolUnreachable

       Possibilities:
               disabled   (0)
               enabled   (1)"
   ::= {er1645v2EthPortSwIIpEntry 788725760}

er1645v2EthPortSwIIpIMPortUnreachable OBJECT-TYPE
   SYNTAX      INTEGER
               {
               disabled (0),
               enabled (1)
               }
   MAX-ACCESS  read-write
   STATUS      current
   DESCRIPTION
      "Path: swPort.editConf.ip.icmpMessages.portUnreachable

       Possibilities:
               disabled   (0)
               enabled   (1)"
   ::= {er1645v2EthPortSwIIpEntry 788791296}

er1645v2EthPortSwIIpIMMtuExceeded OBJECT-TYPE
   SYNTAX      INTEGER
               {
               disabled (0),
               enabled (1)
               }
   MAX-ACCESS  read-write
   STATUS      current
   DESCRIPTION
      "Path: swPort.editConf.ip.icmpMessages.mtuExceeded

       Possibilities:
               disabled   (0)
               enabled   (1)"
   ::= {er1645v2EthPortSwIIpEntry 788856832}

er1645v2EthPortSwIIpIMAdminProhibited OBJECT-TYPE
   SYNTAX      INTEGER
               {
               disabled (0),
               enabled (1)
               }
   MAX-ACCESS  read-write
   STATUS      current
   DESCRIPTION
      "Path: swPort.editConf.ip.icmpMessages.adminProhibited

       Possibilities:
               disabled   (0)
               enabled   (1)"
   ::= {er1645v2EthPortSwIIpEntry 788922368}

er1645v2EthPortSwIIpIMTtlExceeded OBJECT-TYPE
   SYNTAX      INTEGER
               {
               disabled (0),
               enabled (1)
               }
   MAX-ACCESS  read-write
   STATUS      current
   DESCRIPTION
      "Path: swPort.editConf.ip.icmpMessages.ttlExceeded

       Possibilities:
               disabled   (0)
               enabled   (1)"
   ::= {er1645v2EthPortSwIIpEntry 788987904}

er1645v2EthPortSwIIpIMRedirect OBJECT-TYPE
   SYNTAX      INTEGER
               {
               disabled (0),
               enabled (1)
               }
   MAX-ACCESS  read-write
   STATUS      current
   DESCRIPTION
      "Path: swPort.editConf.ip.icmpMessages.redirect

       Possibilities:
               disabled   (0)
               enabled   (1)"
   ::= {er1645v2EthPortSwIIpEntry 789053440}

er1645v2EthPortSwIIpSaddr OBJECT-TYPE
   SYNTAX      SEQUENCE OF Er1645v2EthPortSwIIpSaddrEntry
   MAX-ACCESS  not-accessible
   STATUS      current
   DESCRIPTION
      ""
   ::= {er1645v2EthPortSwIIp 385875968}

er1645v2EthPortSwIIpSaddrEntry OBJECT-TYPE
   SYNTAX      Er1645v2EthPortSwIIpSaddrEntry
   MAX-ACCESS  not-accessible
   STATUS      current
   DESCRIPTION
      ""
   INDEX      { er1645v2EthPortSwIIpSaddrGlobalIx,
                er1645v2EthPortSwIIpSaddrTableIx }
   ::= {er1645v2EthPortSwIIpSaddr 1}

Er1645v2EthPortSwIIpSaddrEntry ::=
   SEQUENCE
      {
      er1645v2EthPortSwIIpSaddrActions
         VariableLengthTableActions,
      er1645v2EthPortSwIIpSaddrGlobalIx
         GlobalIndex,
      er1645v2EthPortSwIIpSaddrTableIx
         TableIndex,
      er1645v2EthPortSwIIpSaddrAddress
         IpAddress,
      er1645v2EthPortSwIIpSaddrNetMask
         IpAddress
      }

er1645v2EthPortSwIIpSaddrActions OBJECT-TYPE
   SYNTAX      VariableLengthTableActions
   MAX-ACCESS  read-write
   STATUS      current
   DESCRIPTION
      "By way of this field, some manipulations
       on this table may be performed."
   ::= {er1645v2EthPortSwIIpSaddrEntry 2}

er1645v2EthPortSwIIpSaddrGlobalIx OBJECT-TYPE
   SYNTAX      GlobalIndex
   MAX-ACCESS  not-accessible
   STATUS      current
   DESCRIPTION
      "The value of the tlsCntTreeGlobalIndex of the MANAGED OBJECT."
   ::= {er1645v2EthPortSwIIpSaddrEntry 10}

er1645v2EthPortSwIIpSaddrTableIx OBJECT-TYPE
   SYNTAX      TableIndex
   MAX-ACCESS  not-accessible
   STATUS      current
   DESCRIPTION
      ""
   ::= {er1645v2EthPortSwIIpSaddrEntry 11}

er1645v2EthPortSwIIpSaddrAddress OBJECT-TYPE
   SYNTAX      IpAddress
   MAX-ACCESS  read-write
   STATUS      current
   DESCRIPTION
      "Path: swPort.editConf.ip.secondaryIp.address"
   ::= {er1645v2EthPortSwIIpSaddrEntry 2030043136}

er1645v2EthPortSwIIpSaddrNetMask OBJECT-TYPE
   SYNTAX      IpAddress
   MAX-ACCESS  read-write
   STATUS      current
   DESCRIPTION
      "Path: swPort.editConf.ip.secondaryIp.netMask"
   ::= {er1645v2EthPortSwIIpSaddrEntry 2063597568}

er1645v2EthPortSwIIpH OBJECT-TYPE
   SYNTAX      SEQUENCE OF Er1645v2EthPortSwIIpHEntry
   MAX-ACCESS  not-accessible
   STATUS      current
   DESCRIPTION
      ""
   ::= {er1645v2EthPortSwIIp 251658240}

er1645v2EthPortSwIIpHEntry OBJECT-TYPE
   SYNTAX      Er1645v2EthPortSwIIpHEntry
   MAX-ACCESS  not-accessible
   STATUS      current
   DESCRIPTION
      ""
   INDEX      { er1645v2EthPortSwIIpHGlobalIx,
                er1645v2EthPortSwIIpHTableIx }
   ::= {er1645v2EthPortSwIIpH 1}

Er1645v2EthPortSwIIpHEntry ::=
   SEQUENCE
      {
      er1645v2EthPortSwIIpHActions
         VariableLengthTableActions,
      er1645v2EthPortSwIIpHGlobalIx
         GlobalIndex,
      er1645v2EthPortSwIIpHTableIx
         TableIndex,
      er1645v2EthPortSwIIpHAddress
         IpAddress,
      er1645v2EthPortSwIIpHDhcpRelayOptionSubscriberId
         DisplayString
      }

er1645v2EthPortSwIIpHActions OBJECT-TYPE
   SYNTAX      VariableLengthTableActions
   MAX-ACCESS  read-write
   STATUS      current
   DESCRIPTION
      "By way of this field, some manipulations
       on this table may be performed."
   ::= {er1645v2EthPortSwIIpHEntry 2}

er1645v2EthPortSwIIpHGlobalIx OBJECT-TYPE
   SYNTAX      GlobalIndex
   MAX-ACCESS  not-accessible
   STATUS      current
   DESCRIPTION
      "The value of the tlsCntTreeGlobalIndex of the MANAGED OBJECT."
   ::= {er1645v2EthPortSwIIpHEntry 10}

er1645v2EthPortSwIIpHTableIx OBJECT-TYPE
   SYNTAX      TableIndex
   MAX-ACCESS  not-accessible
   STATUS      current
   DESCRIPTION
      ""
   ::= {er1645v2EthPortSwIIpHEntry 11}

er1645v2EthPortSwIIpHAddress OBJECT-TYPE
   SYNTAX      IpAddress
   MAX-ACCESS  read-write
   STATUS      current
   DESCRIPTION
      "Path: swPort.editConf.ip.helpers.address"
   ::= {er1645v2EthPortSwIIpHEntry 16777216}

er1645v2EthPortSwIIpHDhcpRelayOptionSubscriberId OBJECT-TYPE
   SYNTAX      DisplayString
   MAX-ACCESS  read-write
   STATUS      current
   DESCRIPTION
      "Path: swPort.editConf.ip.helpers.dhcpRelayOption.subscriberId"
   ::= {er1645v2EthPortSwIIpHEntry 33947648}


er1645v2EthPortSwIName OBJECT IDENTIFIER ::= {er1645v2EthPortSwI 2}

er1645v2EthPortSwINameTable OBJECT-TYPE
   SYNTAX      SEQUENCE OF Er1645v2EthPortSwINameEntry
   MAX-ACCESS  not-accessible
   STATUS      current
   DESCRIPTION
      "config interface name"
   ::= {er1645v2EthPortSwIName 1}

er1645v2EthPortSwINameEntry OBJECT-TYPE
   SYNTAX      Er1645v2EthPortSwINameEntry
   MAX-ACCESS  not-accessible
   STATUS      current
   DESCRIPTION
      ""
   INDEX      { er1645v2EthPortSwINameGlobalIx }
   ::= {er1645v2EthPortSwINameTable 1}

Er1645v2EthPortSwINameEntry ::=
   SEQUENCE
      {
      er1645v2EthPortSwINameGlobalIx
         GlobalIndex,
      er1645v2EthPortSwINameValue
         DisplayString
      }

er1645v2EthPortSwINameGlobalIx OBJECT-TYPE
   SYNTAX      GlobalIndex
   MAX-ACCESS  not-accessible
   STATUS      current
   DESCRIPTION
      "The value of the tlsCntTreeGlobalIndex of the MANAGED OBJECT."
   ::= {er1645v2EthPortSwINameEntry 10}

er1645v2EthPortSwINameValue OBJECT-TYPE
   SYNTAX      DisplayString
   MAX-ACCESS  read-write
   STATUS      current
   DESCRIPTION
      "Path: swPort.editConf.name"
   ::= {er1645v2EthPortSwINameEntry 2147483648}


er1645v2EthPortSwIBw OBJECT IDENTIFIER ::= {er1645v2EthPortSwI 5}

er1645v2EthPortSwIBwSSCTable OBJECT-TYPE
   SYNTAX      SEQUENCE OF Er1645v2EthPortSwIBwEntry
   MAX-ACCESS  not-accessible
   STATUS      current
   DESCRIPTION
      ""
   ::= {er1645v2EthPortSwIBw 1}

er1645v2EthPortSwIBwEntry OBJECT-TYPE
   SYNTAX      Er1645v2EthPortSwIBwEntry
   MAX-ACCESS  not-accessible
   STATUS      current
   DESCRIPTION
      ""
   INDEX      { er1645v2EthPortSwIBwGlobalIx }
   ::= {er1645v2EthPortSwIBwSSCTable 1}

Er1645v2EthPortSwIBwEntry ::=
   SEQUENCE
      {
      er1645v2EthPortSwIBwGlobalIx
         GlobalIndex,
      er1645v2EthPortSwIBwMode
         INTEGER,
      er1645v2EthPortSwIBwCir
         Integer32,
      er1645v2EthPortSwIBwEir
         Integer32,
      er1645v2EthPortSwIBwUnit
         INTEGER,
      er1645v2EthPortSwIBwTc
         INTEGER,
      er1645v2EthPortSwIBwTcFactor
         INTEGER,
      er1645v2EthPortSwIBwCorrType
         INTEGER,
      er1645v2EthPortSwIBwCorrPredefEncapsFrameRelay
         DisplayString,
      er1645v2EthPortSwIBwCorrPredefEncapsPpp
         DisplayString,
      er1645v2EthPortSwIBwCorrPredefEncapsAtmHl
         INTEGER,
      er1645v2EthPortSwIBwCorrPredefEncapsAtmMp
         INTEGER,
      er1645v2EthPortSwIBwCorrPredefEncapsHdlc
         DisplayString,
      er1645v2EthPortSwIBwCorrPredefEncapsEfmFs
         Integer32,
      er1645v2EthPortSwIBwCorrPredefEncapsEfmIb
         Integer32,
      er1645v2EthPortSwIBwCorrPredefMode
         INTEGER,
      er1645v2EthPortSwIBwCorrManualOverhead
         Integer32,
      er1645v2EthPortSwIBwCorrManualFrameData
         Counter32,
      er1645v2EthPortSwIBwCorrManualFrameHeader
         Counter32,
      er1645v2EthPortSwIBwMaxFifoQLen
         Integer32,
      er1645v2EthPortSwIBwDeFlagCir
         INTEGER,
      er1645v2EthPortSwIBwDeFlagEir
         INTEGER,
      er1645v2EthPortSwIBwDeFlagViolate
         INTEGER,
      er1645v2EthPortSwIBwActCirActNone
         OCTET STRING,
      er1645v2EthPortSwIBwActCirActEthCos1
         INTEGER,
      er1645v2EthPortSwIBwActCirActEthDei1
         INTEGER,
      er1645v2EthPortSwIBwActCirActEthCos2
         INTEGER,
      er1645v2EthPortSwIBwActCirActEthDei2
         INTEGER,
      er1645v2EthPortSwIBwActCirActEthCos3
         INTEGER,
      er1645v2EthPortSwIBwActCirActEthDei3
         INTEGER,
      er1645v2EthPortSwIBwActCirActEthCos4
         INTEGER,
      er1645v2EthPortSwIBwActCirActEthDei4
         INTEGER,
      er1645v2EthPortSwIBwActCirActEthCos5
         INTEGER,
      er1645v2EthPortSwIBwActCirActEthDei5
         INTEGER,
      er1645v2EthPortSwIBwActCirActEthCos6
         INTEGER,
      er1645v2EthPortSwIBwActCirActEthDei6
         INTEGER,
      er1645v2EthPortSwIBwActCirActEthCos7
         INTEGER,
      er1645v2EthPortSwIBwActCirActEthDei7
         INTEGER,
      er1645v2EthPortSwIBwActCirActEthCos8
         INTEGER,
      er1645v2EthPortSwIBwActCirActEthDei8
         INTEGER,
      er1645v2EthPortSwIBwActCirActEthTos
         INTEGER,
      er1645v2EthPortSwIBwActCirActEthQueue
         INTEGER,
      er1645v2EthPortSwIBwActCirActEthDrpLev
         INTEGER,
      er1645v2EthPortSwIBwActCirActEthDeFlag
         INTEGER,
      er1645v2EthPortSwIBwActCirActIpTos
         INTEGER,
      er1645v2EthPortSwIBwActCirActIpQueue
         INTEGER,
      er1645v2EthPortSwIBwActCirActIpDrpLev
         INTEGER,
      er1645v2EthPortSwIBwActCirActIpDeFlag
         INTEGER,
      er1645v2EthPortSwIBwActEirActNone
         OCTET STRING,
      er1645v2EthPortSwIBwActEirActEthCos1
         INTEGER,
      er1645v2EthPortSwIBwActEirActEthDei1
         INTEGER,
      er1645v2EthPortSwIBwActEirActEthCos2
         INTEGER,
      er1645v2EthPortSwIBwActEirActEthDei2
         INTEGER,
      er1645v2EthPortSwIBwActEirActEthCos3
         INTEGER,
      er1645v2EthPortSwIBwActEirActEthDei3
         INTEGER,
      er1645v2EthPortSwIBwActEirActEthCos4
         INTEGER,
      er1645v2EthPortSwIBwActEirActEthDei4
         INTEGER,
      er1645v2EthPortSwIBwActEirActEthCos5
         INTEGER,
      er1645v2EthPortSwIBwActEirActEthDei5
         INTEGER,
      er1645v2EthPortSwIBwActEirActEthCos6
         INTEGER,
      er1645v2EthPortSwIBwActEirActEthDei6
         INTEGER,
      er1645v2EthPortSwIBwActEirActEthCos7
         INTEGER,
      er1645v2EthPortSwIBwActEirActEthDei7
         INTEGER,
      er1645v2EthPortSwIBwActEirActEthCos8
         INTEGER,
      er1645v2EthPortSwIBwActEirActEthDei8
         INTEGER,
      er1645v2EthPortSwIBwActEirActEthTos
         INTEGER,
      er1645v2EthPortSwIBwActEirActEthQueue
         INTEGER,
      er1645v2EthPortSwIBwActEirActEthDrpLev
         INTEGER,
      er1645v2EthPortSwIBwActEirActEthDeFlag
         INTEGER,
      er1645v2EthPortSwIBwActEirActIpTos
         INTEGER,
      er1645v2EthPortSwIBwActEirActIpQueue
         INTEGER,
      er1645v2EthPortSwIBwActEirActIpDrpLev
         INTEGER,
      er1645v2EthPortSwIBwActEirActIpDeFlag
         INTEGER,
      er1645v2EthPortSwIBwActViolActNone
         OCTET STRING,
      er1645v2EthPortSwIBwActViolActDrop
         OCTET STRING,
      er1645v2EthPortSwIBwActViolActEthCos1
         INTEGER,
      er1645v2EthPortSwIBwActViolActEthDei1
         INTEGER,
      er1645v2EthPortSwIBwActViolActEthCos2
         INTEGER,
      er1645v2EthPortSwIBwActViolActEthDei2
         INTEGER,
      er1645v2EthPortSwIBwActViolActEthCos3
         INTEGER,
      er1645v2EthPortSwIBwActViolActEthDei3
         INTEGER,
      er1645v2EthPortSwIBwActViolActEthCos4
         INTEGER,
      er1645v2EthPortSwIBwActViolActEthDei4
         INTEGER,
      er1645v2EthPortSwIBwActViolActEthCos5
         INTEGER,
      er1645v2EthPortSwIBwActViolActEthDei5
         INTEGER,
      er1645v2EthPortSwIBwActViolActEthCos6
         INTEGER,
      er1645v2EthPortSwIBwActViolActEthDei6
         INTEGER,
      er1645v2EthPortSwIBwActViolActEthCos7
         INTEGER,
      er1645v2EthPortSwIBwActViolActEthDei7
         INTEGER,
      er1645v2EthPortSwIBwActViolActEthCos8
         INTEGER,
      er1645v2EthPortSwIBwActViolActEthDei8
         INTEGER,
      er1645v2EthPortSwIBwActViolActEthTos
         INTEGER,
      er1645v2EthPortSwIBwActViolActEthQueue
         INTEGER,
      er1645v2EthPortSwIBwActViolActEthDrpLev
         INTEGER,
      er1645v2EthPortSwIBwActViolActEthDeFlag
         INTEGER,
      er1645v2EthPortSwIBwActViolActIpTos
         INTEGER,
      er1645v2EthPortSwIBwActViolActIpQueue
         INTEGER,
      er1645v2EthPortSwIBwActViolActIpDrpLev
         INTEGER,
      er1645v2EthPortSwIBwActViolActIpDeFlag
         INTEGER
      }

er1645v2EthPortSwIBwGlobalIx OBJECT-TYPE
   SYNTAX      GlobalIndex
   MAX-ACCESS  not-accessible
   STATUS      current
   DESCRIPTION
      "The value of the tlsCntTreeGlobalIndex of the MANAGED OBJECT."
   ::= {er1645v2EthPortSwIBwEntry 10}

er1645v2EthPortSwIBwMode OBJECT-TYPE
   SYNTAX      INTEGER
               {
               reshaping (1),
               policing (2),
               policingReshape (3)
               }
   MAX-ACCESS  read-write
   STATUS      current
   DESCRIPTION
      "Path: swPort.editConf.bandwidth.mode

       Possibilities:
               reshaping   (1)
               policing   (2)
               policingReshape   (3)"
   ::= {er1645v2EthPortSwIBwEntry 3758096384}

er1645v2EthPortSwIBwCir OBJECT-TYPE
   SYNTAX      Integer32
   MAX-ACCESS  read-write
   STATUS      current
   DESCRIPTION
      "Path: swPort.editConf.bandwidth.cir"
   ::= {er1645v2EthPortSwIBwEntry 268435456}

er1645v2EthPortSwIBwEir OBJECT-TYPE
   SYNTAX      Integer32
   MAX-ACCESS  read-write
   STATUS      current
   DESCRIPTION
      "Path: swPort.editConf.bandwidth.eir"
   ::= {er1645v2EthPortSwIBwEntry 1879048192}

er1645v2EthPortSwIBwUnit OBJECT-TYPE
   SYNTAX      INTEGER
               {
               bitssec (1),
               percent (2)
               }
   MAX-ACCESS  read-write
   STATUS      current
   DESCRIPTION
      "Path: swPort.editConf.bandwidth.unit

       Possibilities:
               bits/sec   (1)
               percent   (2)"
   ::= {er1645v2EthPortSwIBwEntry 1342177280}

er1645v2EthPortSwIBwTc OBJECT-TYPE
   SYNTAX      INTEGER
               {
               auto (0)
               }
   MAX-ACCESS  read-write
   STATUS      current
   DESCRIPTION
      "Path: swPort.editConf.bandwidth.tc

       Possibilities:
               auto   (0)"
   ::= {er1645v2EthPortSwIBwEntry 1610612736}

er1645v2EthPortSwIBwTcFactor OBJECT-TYPE
   SYNTAX      INTEGER
               {
               ms (10),
               s100us (1)
               }
   MAX-ACCESS  read-write
   STATUS      current
   DESCRIPTION
      "Path: swPort.editConf.bandwidth.tcFactor

       Possibilities:
               ms   (10)
               *100us   (1)"
   ::= {er1645v2EthPortSwIBwEntry 2147483648}

er1645v2EthPortSwIBwCorrType OBJECT-TYPE
   SYNTAX      INTEGER
               {
               noCorrection (0),
               predefined (1),
               manual (2)
               }
   MAX-ACCESS  read-write
   STATUS      current
   DESCRIPTION
      "Path: swPort.editConf.bandwidth.correction.type

       Possibilities:
               noCorrection   (0)
               predefined   (1)
               manual   (2)"
   ::= {er1645v2EthPortSwIBwEntry 570425344}

er1645v2EthPortSwIBwCorrPredefEncapsFrameRelay OBJECT-TYPE
   SYNTAX      DisplayString
   MAX-ACCESS  read-write
   STATUS      current
   DESCRIPTION
      "Path: swPort.editConf.bandwidth.correction.predefined.encapsulation.frameRelay"
   ::= {er1645v2EthPortSwIBwEntry 608436224}

er1645v2EthPortSwIBwCorrPredefEncapsPpp OBJECT-TYPE
   SYNTAX      DisplayString
   MAX-ACCESS  read-write
   STATUS      current
   DESCRIPTION
      "Path: swPort.editConf.bandwidth.correction.predefined.encapsulation.ppp"
   ::= {er1645v2EthPortSwIBwEntry 608698368}

er1645v2EthPortSwIBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.bandwidth.correction.predefined.encapsulation.atm.higherLayer

       Possibilities:
               rfc2684   (0)
               ppp   (1)
               pppOverEthernet   (2)"
   ::= {er1645v2EthPortSwIBwEntry 608993280}

er1645v2EthPortSwIBwCorrPredefEncapsAtmMp OBJECT-TYPE
   SYNTAX      INTEGER
               {
               llcEncapsulation (0),
               vcMultiplexing (1)
               }
   MAX-ACCESS  read-write
   STATUS      current
   DESCRIPTION
      "Path: swPort.editConf.bandwidth.correction.predefined.encapsulation.atm.multiProtocol

       Possibilities:
               llcEncapsulation   (0)
               vcMultiplexing   (1)"
   ::= {er1645v2EthPortSwIBwEntry 609026048}

er1645v2EthPortSwIBwCorrPredefEncapsHdlc OBJECT-TYPE
   SYNTAX      DisplayString
   MAX-ACCESS  read-write
   STATUS      current
   DESCRIPTION
      "Path: swPort.editConf.bandwidth.correction.predefined.encapsulation.hdlc"
   ::= {er1645v2EthPortSwIBwEntry 609222656}

er1645v2EthPortSwIBwCorrPredefEncapsEfmFs OBJECT-TYPE
   SYNTAX      Integer32
   MAX-ACCESS  read-write
   STATUS      current
   DESCRIPTION
      "Path: swPort.editConf.bandwidth.correction.predefined.encapsulation.efm.fragmentSize"
   ::= {er1645v2EthPortSwIBwEntry 609517568}

er1645v2EthPortSwIBwCorrPredefEncapsEfmIb OBJECT-TYPE
   SYNTAX      Integer32
   MAX-ACCESS  read-write
   STATUS      current
   DESCRIPTION
      "Path: swPort.editConf.bandwidth.correction.predefined.encapsulation.efm.idleBytes"
   ::= {er1645v2EthPortSwIBwEntry 609550336}

er1645v2EthPortSwIBwCorrPredefMode OBJECT-TYPE
   SYNTAX      INTEGER
               {
               routing (0),
               bridging (1)
               }
   MAX-ACCESS  read-write
   STATUS      current
   DESCRIPTION
      "Path: swPort.editConf.bandwidth.correction.predefined.mode

       Possibilities:
               routing   (0)
               bridging   (1)"
   ::= {er1645v2EthPortSwIBwEntry 612368384}

er1645v2EthPortSwIBwCorrManualOverhead OBJECT-TYPE
   SYNTAX      Integer32
   MAX-ACCESS  read-write
   STATUS      current
   DESCRIPTION
      "Path: swPort.editConf.bandwidth.correction.manual.overhead"
   ::= {er1645v2EthPortSwIBwEntry 637665280}

er1645v2EthPortSwIBwCorrManualFrameData OBJECT-TYPE
   SYNTAX      Counter32
   MAX-ACCESS  read-write
   STATUS      current
   DESCRIPTION
      "Path: swPort.editConf.bandwidth.correction.manual.frameData

       32 bit unsigned wrappable counter."
   ::= {er1645v2EthPortSwIBwEntry 637796352}

er1645v2EthPortSwIBwCorrManualFrameHeader OBJECT-TYPE
   SYNTAX      Counter32
   MAX-ACCESS  read-write
   STATUS      current
   DESCRIPTION
      "Path: swPort.editConf.bandwidth.correction.manual.frameHeader

       32 bit unsigned wrappable counter."
   ::= {er1645v2EthPortSwIBwEntry 637927424}

er1645v2EthPortSwIBwMaxFifoQLen OBJECT-TYPE
   SYNTAX      Integer32
   MAX-ACCESS  read-write
   STATUS      current
   DESCRIPTION
      "Path: swPort.editConf.bandwidth.maxFifoQLen"
   ::= {er1645v2EthPortSwIBwEntry 805306368}

er1645v2EthPortSwIBwDeFlagCir OBJECT-TYPE
   SYNTAX      INTEGER
               {
               allowed (1),
               notAllowed (2)
               }
   MAX-ACCESS  read-write
   STATUS      current
   DESCRIPTION
      "Path: swPort.editConf.bandwidth.deFlag.cir

       Possibilities:
               allowed   (1)
               notAllowed   (2)"
   ::= {er1645v2EthPortSwIBwEntry 3490709504}

er1645v2EthPortSwIBwDeFlagEir OBJECT-TYPE
   SYNTAX      INTEGER
               {
               allowed (1),
               notAllowed (2)
               }
   MAX-ACCESS  read-write
   STATUS      current
   DESCRIPTION
      "Path: swPort.editConf.bandwidth.deFlag.eir

       Possibilities:
               allowed   (1)
               notAllowed   (2)"
   ::= {er1645v2EthPortSwIBwEntry 3491758080}

er1645v2EthPortSwIBwDeFlagViolate OBJECT-TYPE
   SYNTAX      INTEGER
               {
               allowed (1),
               notAllowed (2)
               }
   MAX-ACCESS  read-write
   STATUS      current
   DESCRIPTION
      "Path: swPort.editConf.bandwidth.deFlag.violate

       Possibilities:
               allowed   (1)
               notAllowed   (2)"
   ::= {er1645v2EthPortSwIBwEntry 3492806656}

er1645v2EthPortSwIBwActCirActNone OBJECT-TYPE
   SYNTAX      OCTET STRING
   MAX-ACCESS  read-write
   STATUS      current
   DESCRIPTION
      "Path: swPort.editConf.bandwidth.action.cirAction.none"
   ::= {er1645v2EthPortSwIBwEntry 4062183424}

er1645v2EthPortSwIBwActCirActEthCos1 OBJECT-TYPE
   SYNTAX      INTEGER
               {
               unchanged (256)
               }
   MAX-ACCESS  read-write
   STATUS      current
   DESCRIPTION
      "Path: swPort.editConf.bandwidth.action.cirAction.ethernet.cosDepth1

       Possibilities:
               unchanged   (256)"
   ::= {er1645v2EthPortSwIBwEntry 4064346112}

er1645v2EthPortSwIBwActCirActEthDei1 OBJECT-TYPE
   SYNTAX      INTEGER
               {
               unchanged (255),
               clear (0),
               set (1)
               }
   MAX-ACCESS  read-write
   STATUS      current
   DESCRIPTION
      "Path: swPort.editConf.bandwidth.action.cirAction.ethernet.deiDepth1

       Possibilities:
               unchanged   (255)
               clear   (0)
               set   (1)"
   ::= {er1645v2EthPortSwIBwEntry 4065656832}

er1645v2EthPortSwIBwActCirActEthCos2 OBJECT-TYPE
   SYNTAX      INTEGER
               {
               unchanged (256)
               }
   MAX-ACCESS  read-write
   STATUS      current
   DESCRIPTION
      "Path: swPort.editConf.bandwidth.action.cirAction.ethernet.cosDepth2

       Possibilities:
               unchanged   (256)"
   ::= {er1645v2EthPortSwIBwEntry 4064411648}

er1645v2EthPortSwIBwActCirActEthDei2 OBJECT-TYPE
   SYNTAX      INTEGER
               {
               unchanged (255),
               clear (0),
               set (1)
               }
   MAX-ACCESS  read-write
   STATUS      current
   DESCRIPTION
      "Path: swPort.editConf.bandwidth.action.cirAction.ethernet.deiDepth2

       Possibilities:
               unchanged   (255)
               clear   (0)
               set   (1)"
   ::= {er1645v2EthPortSwIBwEntry 4065722368}

er1645v2EthPortSwIBwActCirActEthCos3 OBJECT-TYPE
   SYNTAX      INTEGER
               {
               unchanged (256)
               }
   MAX-ACCESS  read-write
   STATUS      current
   DESCRIPTION
      "Path: swPort.editConf.bandwidth.action.cirAction.ethernet.cosDepth3

       Possibilities:
               unchanged   (256)"
   ::= {er1645v2EthPortSwIBwEntry 4064477184}

er1645v2EthPortSwIBwActCirActEthDei3 OBJECT-TYPE
   SYNTAX      INTEGER
               {
               unchanged (255),
               clear (0),
               set (1)
               }
   MAX-ACCESS  read-write
   STATUS      current
   DESCRIPTION
      "Path: swPort.editConf.bandwidth.action.cirAction.ethernet.deiDepth3

       Possibilities:
               unchanged   (255)
               clear   (0)
               set   (1)"
   ::= {er1645v2EthPortSwIBwEntry 4065787904}

er1645v2EthPortSwIBwActCirActEthCos4 OBJECT-TYPE
   SYNTAX      INTEGER
               {
               unchanged (256)
               }
   MAX-ACCESS  read-write
   STATUS      current
   DESCRIPTION
      "Path: swPort.editConf.bandwidth.action.cirAction.ethernet.cosDepth4

       Possibilities:
               unchanged   (256)"
   ::= {er1645v2EthPortSwIBwEntry 4064542720}

er1645v2EthPortSwIBwActCirActEthDei4 OBJECT-TYPE
   SYNTAX      INTEGER
               {
               unchanged (255),
               clear (0),
               set (1)
               }
   MAX-ACCESS  read-write
   STATUS      current
   DESCRIPTION
      "Path: swPort.editConf.bandwidth.action.cirAction.ethernet.deiDepth4

       Possibilities:
               unchanged   (255)
               clear   (0)
               set   (1)"
   ::= {er1645v2EthPortSwIBwEntry 4065853440}

er1645v2EthPortSwIBwActCirActEthCos5 OBJECT-TYPE
   SYNTAX      INTEGER
               {
               unchanged (256)
               }
   MAX-ACCESS  read-write
   STATUS      current
   DESCRIPTION
      "Path: swPort.editConf.bandwidth.action.cirAction.ethernet.cosDepth5

       Possibilities:
               unchanged   (256)"
   ::= {er1645v2EthPortSwIBwEntry 4064608256}

er1645v2EthPortSwIBwActCirActEthDei5 OBJECT-TYPE
   SYNTAX      INTEGER
               {
               unchanged (255),
               clear (0),
               set (1)
               }
   MAX-ACCESS  read-write
   STATUS      current
   DESCRIPTION
      "Path: swPort.editConf.bandwidth.action.cirAction.ethernet.deiDepth5

       Possibilities:
               unchanged   (255)
               clear   (0)
               set   (1)"
   ::= {er1645v2EthPortSwIBwEntry 4065918976}

er1645v2EthPortSwIBwActCirActEthCos6 OBJECT-TYPE
   SYNTAX      INTEGER
               {
               unchanged (256)
               }
   MAX-ACCESS  read-write
   STATUS      current
   DESCRIPTION
      "Path: swPort.editConf.bandwidth.action.cirAction.ethernet.cosDepth6

       Possibilities:
               unchanged   (256)"
   ::= {er1645v2EthPortSwIBwEntry 4064673792}

er1645v2EthPortSwIBwActCirActEthDei6 OBJECT-TYPE
   SYNTAX      INTEGER
               {
               unchanged (255),
               clear (0),
               set (1)
               }
   MAX-ACCESS  read-write
   STATUS      current
   DESCRIPTION
      "Path: swPort.editConf.bandwidth.action.cirAction.ethernet.deiDepth6

       Possibilities:
               unchanged   (255)
               clear   (0)
               set   (1)"
   ::= {er1645v2EthPortSwIBwEntry 4065984512}

er1645v2EthPortSwIBwActCirActEthCos7 OBJECT-TYPE
   SYNTAX      INTEGER
               {
               unchanged (256)
               }
   MAX-ACCESS  read-write
   STATUS      current
   DESCRIPTION
      "Path: swPort.editConf.bandwidth.action.cirAction.ethernet.cosDepth7

       Possibilities:
               unchanged   (256)"
   ::= {er1645v2EthPortSwIBwEntry 4064739328}

er1645v2EthPortSwIBwActCirActEthDei7 OBJECT-TYPE
   SYNTAX      INTEGER
               {
               unchanged (255),
               clear (0),
               set (1)
               }
   MAX-ACCESS  read-write
   STATUS      current
   DESCRIPTION
      "Path: swPort.editConf.bandwidth.action.cirAction.ethernet.deiDepth7

       Possibilities:
               unchanged   (255)
               clear   (0)
               set   (1)"
   ::= {er1645v2EthPortSwIBwEntry 4066050048}

er1645v2EthPortSwIBwActCirActEthCos8 OBJECT-TYPE
   SYNTAX      INTEGER
               {
               unchanged (256)
               }
   MAX-ACCESS  read-write
   STATUS      current
   DESCRIPTION
      "Path: swPort.editConf.bandwidth.action.cirAction.ethernet.cosDepth8

       Possibilities:
               unchanged   (256)"
   ::= {er1645v2EthPortSwIBwEntry 4064804864}

er1645v2EthPortSwIBwActCirActEthDei8 OBJECT-TYPE
   SYNTAX      INTEGER
               {
               unchanged (255),
               clear (0),
               set (1)
               }
   MAX-ACCESS  read-write
   STATUS      current
   DESCRIPTION
      "Path: swPort.editConf.bandwidth.action.cirAction.ethernet.deiDepth8

       Possibilities:
               unchanged   (255)
               clear   (0)
               set   (1)"
   ::= {er1645v2EthPortSwIBwEntry 4066115584}

er1645v2EthPortSwIBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4064870400}

er1645v2EthPortSwIBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4064935936}

er1645v2EthPortSwIBwActCirActEthDrpLev OBJECT-TYPE
   SYNTAX      INTEGER
               {
               unchanged (0)
               }
   MAX-ACCESS  read-write
   STATUS      current
   DESCRIPTION
      "Path: swPort.editConf.bandwidth.action.cirAction.ethernet.dropLevel

       Possibilities:
               unchanged   (0)"
   ::= {er1645v2EthPortSwIBwEntry 4065001472}

er1645v2EthPortSwIBwActCirActEthDeFlag OBJECT-TYPE
   SYNTAX      INTEGER
               {
               unchanged (255),
               clear (0),
               set (1)
               }
   MAX-ACCESS  read-write
   STATUS      current
   DESCRIPTION
      "Path: swPort.editConf.bandwidth.action.cirAction.ethernet.deFlag

       Possibilities:
               unchanged   (255)
               clear   (0)
               set   (1)"
   ::= {er1645v2EthPortSwIBwEntry 4065198080}

er1645v2EthPortSwIBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4071161856}

er1645v2EthPortSwIBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4071227392}

er1645v2EthPortSwIBwActCirActIpDrpLev OBJECT-TYPE
   SYNTAX      INTEGER
               {
               unchanged (0)
               }
   MAX-ACCESS  read-write
   STATUS      current
   DESCRIPTION
      "Path: swPort.editConf.bandwidth.action.cirAction.ip.dropLevel

       Possibilities:
               unchanged   (0)"
   ::= {er1645v2EthPortSwIBwEntry 4071292928}

er1645v2EthPortSwIBwActCirActIpDeFlag OBJECT-TYPE
   SYNTAX      INTEGER
               {
               unchanged (255),
               clear (0),
               set (1)
               }
   MAX-ACCESS  read-write
   STATUS      current
   DESCRIPTION
      "Path: swPort.editConf.bandwidth.action.cirAction.ip.deFlag

       Possibilities:
               unchanged   (255)
               clear   (0)
               set   (1)"
   ::= {er1645v2EthPortSwIBwEntry 4071489536}

er1645v2EthPortSwIBwActEirActNone OBJECT-TYPE
   SYNTAX      OCTET STRING
   MAX-ACCESS  read-write
   STATUS      current
   DESCRIPTION
      "Path: swPort.editConf.bandwidth.action.eirAction.none"
   ::= {er1645v2EthPortSwIBwEntry 4095737856}

er1645v2EthPortSwIBwActEirActEthCos1 OBJECT-TYPE
   SYNTAX      INTEGER
               {
               unchanged (256)
               }
   MAX-ACCESS  read-write
   STATUS      current
   DESCRIPTION
      "Path: swPort.editConf.bandwidth.action.eirAction.ethernet.cosDepth1

       Possibilities:
               unchanged   (256)"
   ::= {er1645v2EthPortSwIBwEntry 4097900544}

er1645v2EthPortSwIBwActEirActEthDei1 OBJECT-TYPE
   SYNTAX      INTEGER
               {
               unchanged (255),
               clear (0),
               set (1)
               }
   MAX-ACCESS  read-write
   STATUS      current
   DESCRIPTION
      "Path: swPort.editConf.bandwidth.action.eirAction.ethernet.deiDepth1

       Possibilities:
               unchanged   (255)
               clear   (0)
               set   (1)"
   ::= {er1645v2EthPortSwIBwEntry 4099211264}

er1645v2EthPortSwIBwActEirActEthCos2 OBJECT-TYPE
   SYNTAX      INTEGER
               {
               unchanged (256)
               }
   MAX-ACCESS  read-write
   STATUS      current
   DESCRIPTION
      "Path: swPort.editConf.bandwidth.action.eirAction.ethernet.cosDepth2

       Possibilities:
               unchanged   (256)"
   ::= {er1645v2EthPortSwIBwEntry 4097966080}

er1645v2EthPortSwIBwActEirActEthDei2 OBJECT-TYPE
   SYNTAX      INTEGER
               {
               unchanged (255),
               clear (0),
               set (1)
               }
   MAX-ACCESS  read-write
   STATUS      current
   DESCRIPTION
      "Path: swPort.editConf.bandwidth.action.eirAction.ethernet.deiDepth2

       Possibilities:
               unchanged   (255)
               clear   (0)
               set   (1)"
   ::= {er1645v2EthPortSwIBwEntry 4099276800}

er1645v2EthPortSwIBwActEirActEthCos3 OBJECT-TYPE
   SYNTAX      INTEGER
               {
               unchanged (256)
               }
   MAX-ACCESS  read-write
   STATUS      current
   DESCRIPTION
      "Path: swPort.editConf.bandwidth.action.eirAction.ethernet.cosDepth3

       Possibilities:
               unchanged   (256)"
   ::= {er1645v2EthPortSwIBwEntry 4098031616}

er1645v2EthPortSwIBwActEirActEthDei3 OBJECT-TYPE
   SYNTAX      INTEGER
               {
               unchanged (255),
               clear (0),
               set (1)
               }
   MAX-ACCESS  read-write
   STATUS      current
   DESCRIPTION
      "Path: swPort.editConf.bandwidth.action.eirAction.ethernet.deiDepth3

       Possibilities:
               unchanged   (255)
               clear   (0)
               set   (1)"
   ::= {er1645v2EthPortSwIBwEntry 4099342336}

er1645v2EthPortSwIBwActEirActEthCos4 OBJECT-TYPE
   SYNTAX      INTEGER
               {
               unchanged (256)
               }
   MAX-ACCESS  read-write
   STATUS      current
   DESCRIPTION
      "Path: swPort.editConf.bandwidth.action.eirAction.ethernet.cosDepth4

       Possibilities:
               unchanged   (256)"
   ::= {er1645v2EthPortSwIBwEntry 4098097152}

er1645v2EthPortSwIBwActEirActEthDei4 OBJECT-TYPE
   SYNTAX      INTEGER
               {
               unchanged (255),
               clear (0),
               set (1)
               }
   MAX-ACCESS  read-write
   STATUS      current
   DESCRIPTION
      "Path: swPort.editConf.bandwidth.action.eirAction.ethernet.deiDepth4

       Possibilities:
               unchanged   (255)
               clear   (0)
               set   (1)"
   ::= {er1645v2EthPortSwIBwEntry 4099407872}

er1645v2EthPortSwIBwActEirActEthCos5 OBJECT-TYPE
   SYNTAX      INTEGER
               {
               unchanged (256)
               }
   MAX-ACCESS  read-write
   STATUS      current
   DESCRIPTION
      "Path: swPort.editConf.bandwidth.action.eirAction.ethernet.cosDepth5

       Possibilities:
               unchanged   (256)"
   ::= {er1645v2EthPortSwIBwEntry 4098162688}

er1645v2EthPortSwIBwActEirActEthDei5 OBJECT-TYPE
   SYNTAX      INTEGER
               {
               unchanged (255),
               clear (0),
               set (1)
               }
   MAX-ACCESS  read-write
   STATUS      current
   DESCRIPTION
      "Path: swPort.editConf.bandwidth.action.eirAction.ethernet.deiDepth5

       Possibilities:
               unchanged   (255)
               clear   (0)
               set   (1)"
   ::= {er1645v2EthPortSwIBwEntry 4099473408}

er1645v2EthPortSwIBwActEirActEthCos6 OBJECT-TYPE
   SYNTAX      INTEGER
               {
               unchanged (256)
               }
   MAX-ACCESS  read-write
   STATUS      current
   DESCRIPTION
      "Path: swPort.editConf.bandwidth.action.eirAction.ethernet.cosDepth6

       Possibilities:
               unchanged   (256)"
   ::= {er1645v2EthPortSwIBwEntry 4098228224}

er1645v2EthPortSwIBwActEirActEthDei6 OBJECT-TYPE
   SYNTAX      INTEGER
               {
               unchanged (255),
               clear (0),
               set (1)
               }
   MAX-ACCESS  read-write
   STATUS      current
   DESCRIPTION
      "Path: swPort.editConf.bandwidth.action.eirAction.ethernet.deiDepth6

       Possibilities:
               unchanged   (255)
               clear   (0)
               set   (1)"
   ::= {er1645v2EthPortSwIBwEntry 4099538944}

er1645v2EthPortSwIBwActEirActEthCos7 OBJECT-TYPE
   SYNTAX      INTEGER
               {
               unchanged (256)
               }
   MAX-ACCESS  read-write
   STATUS      current
   DESCRIPTION
      "Path: swPort.editConf.bandwidth.action.eirAction.ethernet.cosDepth7

       Possibilities:
               unchanged   (256)"
   ::= {er1645v2EthPortSwIBwEntry 4098293760}

er1645v2EthPortSwIBwActEirActEthDei7 OBJECT-TYPE
   SYNTAX      INTEGER
               {
               unchanged (255),
               clear (0),
               set (1)
               }
   MAX-ACCESS  read-write
   STATUS      current
   DESCRIPTION
      "Path: swPort.editConf.bandwidth.action.eirAction.ethernet.deiDepth7

       Possibilities:
               unchanged   (255)
               clear   (0)
               set   (1)"
   ::= {er1645v2EthPortSwIBwEntry 4099604480}

er1645v2EthPortSwIBwActEirActEthCos8 OBJECT-TYPE
   SYNTAX      INTEGER
               {
               unchanged (256)
               }
   MAX-ACCESS  read-write
   STATUS      current
   DESCRIPTION
      "Path: swPort.editConf.bandwidth.action.eirAction.ethernet.cosDepth8

       Possibilities:
               unchanged   (256)"
   ::= {er1645v2EthPortSwIBwEntry 4098359296}

er1645v2EthPortSwIBwActEirActEthDei8 OBJECT-TYPE
   SYNTAX      INTEGER
               {
               unchanged (255),
               clear (0),
               set (1)
               }
   MAX-ACCESS  read-write
   STATUS      current
   DESCRIPTION
      "Path: swPort.editConf.bandwidth.action.eirAction.ethernet.deiDepth8

       Possibilities:
               unchanged   (255)
               clear   (0)
               set   (1)"
   ::= {er1645v2EthPortSwIBwEntry 4099670016}

er1645v2EthPortSwIBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4098424832}

er1645v2EthPortSwIBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4098490368}

er1645v2EthPortSwIBwActEirActEthDrpLev OBJECT-TYPE
   SYNTAX      INTEGER
               {
               unchanged (0)
               }
   MAX-ACCESS  read-write
   STATUS      current
   DESCRIPTION
      "Path: swPort.editConf.bandwidth.action.eirAction.ethernet.dropLevel

       Possibilities:
               unchanged   (0)"
   ::= {er1645v2EthPortSwIBwEntry 4098555904}

er1645v2EthPortSwIBwActEirActEthDeFlag OBJECT-TYPE
   SYNTAX      INTEGER
               {
               unchanged (255),
               clear (0),
               set (1)
               }
   MAX-ACCESS  read-write
   STATUS      current
   DESCRIPTION
      "Path: swPort.editConf.bandwidth.action.eirAction.ethernet.deFlag

       Possibilities:
               unchanged   (255)
               clear   (0)
               set   (1)"
   ::= {er1645v2EthPortSwIBwEntry 4098752512}

er1645v2EthPortSwIBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4104716288}

er1645v2EthPortSwIBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4104781824}

er1645v2EthPortSwIBwActEirActIpDrpLev OBJECT-TYPE
   SYNTAX      INTEGER
               {
               unchanged (0)
               }
   MAX-ACCESS  read-write
   STATUS      current
   DESCRIPTION
      "Path: swPort.editConf.bandwidth.action.eirAction.ip.dropLevel

       Possibilities:
               unchanged   (0)"
   ::= {er1645v2EthPortSwIBwEntry 4104847360}

er1645v2EthPortSwIBwActEirActIpDeFlag OBJECT-TYPE
   SYNTAX      INTEGER
               {
               unchanged (255),
               clear (0),
               set (1)
               }
   MAX-ACCESS  read-write
   STATUS      current
   DESCRIPTION
      "Path: swPort.editConf.bandwidth.action.eirAction.ip.deFlag

       Possibilities:
               unchanged   (255)
               clear   (0)
               set   (1)"
   ::= {er1645v2EthPortSwIBwEntry 4105043968}

er1645v2EthPortSwIBwActViolActNone OBJECT-TYPE
   SYNTAX      OCTET STRING
   MAX-ACCESS  read-write
   STATUS      current
   DESCRIPTION
      "Path: swPort.editConf.bandwidth.action.violateAction.none"
   ::= {er1645v2EthPortSwIBwEntry 4129292288}

er1645v2EthPortSwIBwActViolActDrop OBJECT-TYPE
   SYNTAX      OCTET STRING
   MAX-ACCESS  read-write
   STATUS      current
   DESCRIPTION
      "Path: swPort.editConf.bandwidth.action.violateAction.drop"
   ::= {er1645v2EthPortSwIBwEntry 4133486592}

er1645v2EthPortSwIBwActViolActEthCos1 OBJECT-TYPE
   SYNTAX      INTEGER
               {
               unchanged (256)
               }
   MAX-ACCESS  read-write
   STATUS      current
   DESCRIPTION
      "Path: swPort.editConf.bandwidth.action.violateAction.ethernet.cosDepth1

       Possibilities:
               unchanged   (256)"
   ::= {er1645v2EthPortSwIBwEntry 4131454976}

er1645v2EthPortSwIBwActViolActEthDei1 OBJECT-TYPE
   SYNTAX      INTEGER
               {
               unchanged (255),
               clear (0),
               set (1)
               }
   MAX-ACCESS  read-write
   STATUS      current
   DESCRIPTION
      "Path: swPort.editConf.bandwidth.action.violateAction.ethernet.deiDepth1

       Possibilities:
               unchanged   (255)
               clear   (0)
               set   (1)"
   ::= {er1645v2EthPortSwIBwEntry 4132765696}

er1645v2EthPortSwIBwActViolActEthCos2 OBJECT-TYPE
   SYNTAX      INTEGER
               {
               unchanged (256)
               }
   MAX-ACCESS  read-write
   STATUS      current
   DESCRIPTION
      "Path: swPort.editConf.bandwidth.action.violateAction.ethernet.cosDepth2

       Possibilities:
               unchanged   (256)"
   ::= {er1645v2EthPortSwIBwEntry 4131520512}

er1645v2EthPortSwIBwActViolActEthDei2 OBJECT-TYPE
   SYNTAX      INTEGER
               {
               unchanged (255),
               clear (0),
               set (1)
               }
   MAX-ACCESS  read-write
   STATUS      current
   DESCRIPTION
      "Path: swPort.editConf.bandwidth.action.violateAction.ethernet.deiDepth2

       Possibilities:
               unchanged   (255)
               clear   (0)
               set   (1)"
   ::= {er1645v2EthPortSwIBwEntry 4132831232}

er1645v2EthPortSwIBwActViolActEthCos3 OBJECT-TYPE
   SYNTAX      INTEGER
               {
               unchanged (256)
               }
   MAX-ACCESS  read-write
   STATUS      current
   DESCRIPTION
      "Path: swPort.editConf.bandwidth.action.violateAction.ethernet.cosDepth3

       Possibilities:
               unchanged   (256)"
   ::= {er1645v2EthPortSwIBwEntry 4131586048}

er1645v2EthPortSwIBwActViolActEthDei3 OBJECT-TYPE
   SYNTAX      INTEGER
               {
               unchanged (255),
               clear (0),
               set (1)
               }
   MAX-ACCESS  read-write
   STATUS      current
   DESCRIPTION
      "Path: swPort.editConf.bandwidth.action.violateAction.ethernet.deiDepth3

       Possibilities:
               unchanged   (255)
               clear   (0)
               set   (1)"
   ::= {er1645v2EthPortSwIBwEntry 4132896768}

er1645v2EthPortSwIBwActViolActEthCos4 OBJECT-TYPE
   SYNTAX      INTEGER
               {
               unchanged (256)
               }
   MAX-ACCESS  read-write
   STATUS      current
   DESCRIPTION
      "Path: swPort.editConf.bandwidth.action.violateAction.ethernet.cosDepth4

       Possibilities:
               unchanged   (256)"
   ::= {er1645v2EthPortSwIBwEntry 4131651584}

er1645v2EthPortSwIBwActViolActEthDei4 OBJECT-TYPE
   SYNTAX      INTEGER
               {
               unchanged (255),
               clear (0),
               set (1)
               }
   MAX-ACCESS  read-write
   STATUS      current
   DESCRIPTION
      "Path: swPort.editConf.bandwidth.action.violateAction.ethernet.deiDepth4

       Possibilities:
               unchanged   (255)
               clear   (0)
               set   (1)"
   ::= {er1645v2EthPortSwIBwEntry 4132962304}

er1645v2EthPortSwIBwActViolActEthCos5 OBJECT-TYPE
   SYNTAX      INTEGER
               {
               unchanged (256)
               }
   MAX-ACCESS  read-write
   STATUS      current
   DESCRIPTION
      "Path: swPort.editConf.bandwidth.action.violateAction.ethernet.cosDepth5

       Possibilities:
               unchanged   (256)"
   ::= {er1645v2EthPortSwIBwEntry 4131717120}

er1645v2EthPortSwIBwActViolActEthDei5 OBJECT-TYPE
   SYNTAX      INTEGER
               {
               unchanged (255),
               clear (0),
               set (1)
               }
   MAX-ACCESS  read-write
   STATUS      current
   DESCRIPTION
      "Path: swPort.editConf.bandwidth.action.violateAction.ethernet.deiDepth5

       Possibilities:
               unchanged   (255)
               clear   (0)
               set   (1)"
   ::= {er1645v2EthPortSwIBwEntry 4133027840}

er1645v2EthPortSwIBwActViolActEthCos6 OBJECT-TYPE
   SYNTAX      INTEGER
               {
               unchanged (256)
               }
   MAX-ACCESS  read-write
   STATUS      current
   DESCRIPTION
      "Path: swPort.editConf.bandwidth.action.violateAction.ethernet.cosDepth6

       Possibilities:
               unchanged   (256)"
   ::= {er1645v2EthPortSwIBwEntry 4131782656}

er1645v2EthPortSwIBwActViolActEthDei6 OBJECT-TYPE
   SYNTAX      INTEGER
               {
               unchanged (255),
               clear (0),
               set (1)
               }
   MAX-ACCESS  read-write
   STATUS      current
   DESCRIPTION
      "Path: swPort.editConf.bandwidth.action.violateAction.ethernet.deiDepth6

       Possibilities:
               unchanged   (255)
               clear   (0)
               set   (1)"
   ::= {er1645v2EthPortSwIBwEntry 4133093376}

er1645v2EthPortSwIBwActViolActEthCos7 OBJECT-TYPE
   SYNTAX      INTEGER
               {
               unchanged (256)
               }
   MAX-ACCESS  read-write
   STATUS      current
   DESCRIPTION
      "Path: swPort.editConf.bandwidth.action.violateAction.ethernet.cosDepth7

       Possibilities:
               unchanged   (256)"
   ::= {er1645v2EthPortSwIBwEntry 4131848192}

er1645v2EthPortSwIBwActViolActEthDei7 OBJECT-TYPE
   SYNTAX      INTEGER
               {
               unchanged (255),
               clear (0),
               set (1)
               }
   MAX-ACCESS  read-write
   STATUS      current
   DESCRIPTION
      "Path: swPort.editConf.bandwidth.action.violateAction.ethernet.deiDepth7

       Possibilities:
               unchanged   (255)
               clear   (0)
               set   (1)"
   ::= {er1645v2EthPortSwIBwEntry 4133158912}

er1645v2EthPortSwIBwActViolActEthCos8 OBJECT-TYPE
   SYNTAX      INTEGER
               {
               unchanged (256)
               }
   MAX-ACCESS  read-write
   STATUS      current
   DESCRIPTION
      "Path: swPort.editConf.bandwidth.action.violateAction.ethernet.cosDepth8

       Possibilities:
               unchanged   (256)"
   ::= {er1645v2EthPortSwIBwEntry 4131913728}

er1645v2EthPortSwIBwActViolActEthDei8 OBJECT-TYPE
   SYNTAX      INTEGER
               {
               unchanged (255),
               clear (0),
               set (1)
               }
   MAX-ACCESS  read-write
   STATUS      current
   DESCRIPTION
      "Path: swPort.editConf.bandwidth.action.violateAction.ethernet.deiDepth8

       Possibilities:
               unchanged   (255)
               clear   (0)
               set   (1)"
   ::= {er1645v2EthPortSwIBwEntry 4133224448}

er1645v2EthPortSwIBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4131979264}

er1645v2EthPortSwIBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4132044800}

er1645v2EthPortSwIBwActViolActEthDrpLev OBJECT-TYPE
   SYNTAX      INTEGER
               {
               unchanged (0)
               }
   MAX-ACCESS  read-write
   STATUS      current
   DESCRIPTION
      "Path: swPort.editConf.bandwidth.action.violateAction.ethernet.dropLevel

       Possibilities:
               unchanged   (0)"
   ::= {er1645v2EthPortSwIBwEntry 4132110336}

er1645v2EthPortSwIBwActViolActEthDeFlag OBJECT-TYPE
   SYNTAX      INTEGER
               {
               unchanged (255),
               clear (0),
               set (1)
               }
   MAX-ACCESS  read-write
   STATUS      current
   DESCRIPTION
      "Path: swPort.editConf.bandwidth.action.violateAction.ethernet.deFlag

       Possibilities:
               unchanged   (255)
               clear   (0)
               set   (1)"
   ::= {er1645v2EthPortSwIBwEntry 4132306944}

er1645v2EthPortSwIBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIBwEntry 4138270720}

er1645v2EthPortSwIBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIBwEntry 4138336256}

er1645v2EthPortSwIBwActViolActIpDrpLev OBJECT-TYPE
   SYNTAX      INTEGER
               {
               unchanged (0)
               }
   MAX-ACCESS  read-write
   STATUS      current
   DESCRIPTION
      "Path: swPort.editConf.bandwidth.action.violateAction.ip.dropLevel

       Possibilities:
               unchanged   (0)"
   ::= {er1645v2EthPortSwIBwEntry 4138401792}

er1645v2EthPortSwIBwActViolActIpDeFlag OBJECT-TYPE
   SYNTAX      INTEGER
               {
               unchanged (255),
               clear (0),
               set (1)
               }
   MAX-ACCESS  read-write
   STATUS      current
   DESCRIPTION
      "Path: swPort.editConf.bandwidth.action.violateAction.ip.deFlag

       Possibilities:
               unchanged   (255)
               clear   (0)
               set   (1)"
   ::= {er1645v2EthPortSwIBwEntry 4138598400}


er1645v2EthPortSwIIbw OBJECT IDENTIFIER ::= {er1645v2EthPortSwI 13}

er1645v2EthPortSwIIbwSSCTable OBJECT-TYPE
   SYNTAX      SEQUENCE OF Er1645v2EthPortSwIIbwEntry
   MAX-ACCESS  not-accessible
   STATUS      current
   DESCRIPTION
      ""
   ::= {er1645v2EthPortSwIIbw 1}

er1645v2EthPortSwIIbwEntry OBJECT-TYPE
   SYNTAX      Er1645v2EthPortSwIIbwEntry
   MAX-ACCESS  not-accessible
   STATUS      current
   DESCRIPTION
      ""
   INDEX      { er1645v2EthPortSwIIbwGlobalIx }
   ::= {er1645v2EthPortSwIIbwSSCTable 1}

Er1645v2EthPortSwIIbwEntry ::=
   SEQUENCE
      {
      er1645v2EthPortSwIIbwGlobalIx
         GlobalIndex,
      er1645v2EthPortSwIIbwMode
         INTEGER,
      er1645v2EthPortSwIIbwCir
         Integer32,
      er1645v2EthPortSwIIbwEir
         Integer32,
      er1645v2EthPortSwIIbwUnit
         INTEGER,
      er1645v2EthPortSwIIbwTc
         INTEGER,
      er1645v2EthPortSwIIbwTcFactor
         INTEGER,
      er1645v2EthPortSwIIbwCorrType
         INTEGER,
      er1645v2EthPortSwIIbwCorrPredefEncapsFrameRelay
         DisplayString,
      er1645v2EthPortSwIIbwCorrPredefEncapsPpp
         DisplayString,
      er1645v2EthPortSwIIbwCorrPredefEncapsAtmHl
         INTEGER,
      er1645v2EthPortSwIIbwCorrPredefEncapsAtmMp
         INTEGER,
      er1645v2EthPortSwIIbwCorrPredefEncapsHdlc
         DisplayString,
      er1645v2EthPortSwIIbwCorrPredefEncapsEfmFs
         Integer32,
      er1645v2EthPortSwIIbwCorrPredefEncapsEfmIb
         Integer32,
      er1645v2EthPortSwIIbwCorrPredefMode
         INTEGER,
      er1645v2EthPortSwIIbwCorrManualOverhead
         Integer32,
      er1645v2EthPortSwIIbwCorrManualFrameData
         Counter32,
      er1645v2EthPortSwIIbwCorrManualFrameHeader
         Counter32,
      er1645v2EthPortSwIIbwMaxFifoQLen
         Integer32,
      er1645v2EthPortSwIIbwPriorityPolicy
         DisplayString,
      er1645v2EthPortSwIIbwDeFlagCir
         INTEGER,
      er1645v2EthPortSwIIbwDeFlagEir
         INTEGER,
      er1645v2EthPortSwIIbwDeFlagViolate
         INTEGER,
      er1645v2EthPortSwIIbwActCirActNone
         OCTET STRING,
      er1645v2EthPortSwIIbwActCirActEthCos1
         INTEGER,
      er1645v2EthPortSwIIbwActCirActEthDei1
         INTEGER,
      er1645v2EthPortSwIIbwActCirActEthCos2
         INTEGER,
      er1645v2EthPortSwIIbwActCirActEthDei2
         INTEGER,
      er1645v2EthPortSwIIbwActCirActEthCos3
         INTEGER,
      er1645v2EthPortSwIIbwActCirActEthDei3
         INTEGER,
      er1645v2EthPortSwIIbwActCirActEthCos4
         INTEGER,
      er1645v2EthPortSwIIbwActCirActEthDei4
         INTEGER,
      er1645v2EthPortSwIIbwActCirActEthCos5
         INTEGER,
      er1645v2EthPortSwIIbwActCirActEthDei5
         INTEGER,
      er1645v2EthPortSwIIbwActCirActEthCos6
         INTEGER,
      er1645v2EthPortSwIIbwActCirActEthDei6
         INTEGER,
      er1645v2EthPortSwIIbwActCirActEthCos7
         INTEGER,
      er1645v2EthPortSwIIbwActCirActEthDei7
         INTEGER,
      er1645v2EthPortSwIIbwActCirActEthCos8
         INTEGER,
      er1645v2EthPortSwIIbwActCirActEthDei8
         INTEGER,
      er1645v2EthPortSwIIbwActCirActEthTos
         INTEGER,
      er1645v2EthPortSwIIbwActCirActEthQueue
         INTEGER,
      er1645v2EthPortSwIIbwActCirActEthDrpLev
         INTEGER,
      er1645v2EthPortSwIIbwActCirActEthDeFlag
         INTEGER,
      er1645v2EthPortSwIIbwActCirActIpTos
         INTEGER,
      er1645v2EthPortSwIIbwActCirActIpQueue
         INTEGER,
      er1645v2EthPortSwIIbwActCirActIpDrpLev
         INTEGER,
      er1645v2EthPortSwIIbwActCirActIpDeFlag
         INTEGER,
      er1645v2EthPortSwIIbwActEirActNone
         OCTET STRING,
      er1645v2EthPortSwIIbwActEirActEthCos1
         INTEGER,
      er1645v2EthPortSwIIbwActEirActEthDei1
         INTEGER,
      er1645v2EthPortSwIIbwActEirActEthCos2
         INTEGER,
      er1645v2EthPortSwIIbwActEirActEthDei2
         INTEGER,
      er1645v2EthPortSwIIbwActEirActEthCos3
         INTEGER,
      er1645v2EthPortSwIIbwActEirActEthDei3
         INTEGER,
      er1645v2EthPortSwIIbwActEirActEthCos4
         INTEGER,
      er1645v2EthPortSwIIbwActEirActEthDei4
         INTEGER,
      er1645v2EthPortSwIIbwActEirActEthCos5
         INTEGER,
      er1645v2EthPortSwIIbwActEirActEthDei5
         INTEGER,
      er1645v2EthPortSwIIbwActEirActEthCos6
         INTEGER,
      er1645v2EthPortSwIIbwActEirActEthDei6
         INTEGER,
      er1645v2EthPortSwIIbwActEirActEthCos7
         INTEGER,
      er1645v2EthPortSwIIbwActEirActEthDei7
         INTEGER,
      er1645v2EthPortSwIIbwActEirActEthCos8
         INTEGER,
      er1645v2EthPortSwIIbwActEirActEthDei8
         INTEGER,
      er1645v2EthPortSwIIbwActEirActEthTos
         INTEGER,
      er1645v2EthPortSwIIbwActEirActEthQueue
         INTEGER,
      er1645v2EthPortSwIIbwActEirActEthDrpLev
         INTEGER,
      er1645v2EthPortSwIIbwActEirActEthDeFlag
         INTEGER,
      er1645v2EthPortSwIIbwActEirActIpTos
         INTEGER,
      er1645v2EthPortSwIIbwActEirActIpQueue
         INTEGER,
      er1645v2EthPortSwIIbwActEirActIpDrpLev
         INTEGER,
      er1645v2EthPortSwIIbwActEirActIpDeFlag
         INTEGER,
      er1645v2EthPortSwIIbwActViolActNone
         OCTET STRING,
      er1645v2EthPortSwIIbwActViolActDrop
         OCTET STRING,
      er1645v2EthPortSwIIbwActViolActEthCos1
         INTEGER,
      er1645v2EthPortSwIIbwActViolActEthDei1
         INTEGER,
      er1645v2EthPortSwIIbwActViolActEthCos2
         INTEGER,
      er1645v2EthPortSwIIbwActViolActEthDei2
         INTEGER,
      er1645v2EthPortSwIIbwActViolActEthCos3
         INTEGER,
      er1645v2EthPortSwIIbwActViolActEthDei3
         INTEGER,
      er1645v2EthPortSwIIbwActViolActEthCos4
         INTEGER,
      er1645v2EthPortSwIIbwActViolActEthDei4
         INTEGER,
      er1645v2EthPortSwIIbwActViolActEthCos5
         INTEGER,
      er1645v2EthPortSwIIbwActViolActEthDei5
         INTEGER,
      er1645v2EthPortSwIIbwActViolActEthCos6
         INTEGER,
      er1645v2EthPortSwIIbwActViolActEthDei6
         INTEGER,
      er1645v2EthPortSwIIbwActViolActEthCos7
         INTEGER,
      er1645v2EthPortSwIIbwActViolActEthDei7
         INTEGER,
      er1645v2EthPortSwIIbwActViolActEthCos8
         INTEGER,
      er1645v2EthPortSwIIbwActViolActEthDei8
         INTEGER,
      er1645v2EthPortSwIIbwActViolActEthTos
         INTEGER,
      er1645v2EthPortSwIIbwActViolActEthQueue
         INTEGER,
      er1645v2EthPortSwIIbwActViolActEthDrpLev
         INTEGER,
      er1645v2EthPortSwIIbwActViolActEthDeFlag
         INTEGER,
      er1645v2EthPortSwIIbwActViolActIpTos
         INTEGER,
      er1645v2EthPortSwIIbwActViolActIpQueue
         INTEGER,
      er1645v2EthPortSwIIbwActViolActIpDrpLev
         INTEGER,
      er1645v2EthPortSwIIbwActViolActIpDeFlag
         INTEGER,
      er1645v2EthPortSwIIbwSubInterfacesExcluded
         INTEGER,
      er1645v2EthPortSwIIbwSubInterfacesIncludedInAccessList
         DisplayString
      }

er1645v2EthPortSwIIbwGlobalIx OBJECT-TYPE
   SYNTAX      GlobalIndex
   MAX-ACCESS  not-accessible
   STATUS      current
   DESCRIPTION
      "The value of the tlsCntTreeGlobalIndex of the MANAGED OBJECT."
   ::= {er1645v2EthPortSwIIbwEntry 10}

er1645v2EthPortSwIIbwMode OBJECT-TYPE
   SYNTAX      INTEGER
               {
               reshaping (1),
               policing (2)
               }
   MAX-ACCESS  read-write
   STATUS      current
   DESCRIPTION
      "Path: swPort.editConf.inboundBandwidth.mode

       Possibilities:
               reshaping   (1)
               policing   (2)"
   ::= {er1645v2EthPortSwIIbwEntry 3758096384}

er1645v2EthPortSwIIbwCir OBJECT-TYPE
   SYNTAX      Integer32
   MAX-ACCESS  read-write
   STATUS      current
   DESCRIPTION
      "Path: swPort.editConf.inboundBandwidth.cir"
   ::= {er1645v2EthPortSwIIbwEntry 268435456}

er1645v2EthPortSwIIbwEir OBJECT-TYPE
   SYNTAX      Integer32
   MAX-ACCESS  read-write
   STATUS      current
   DESCRIPTION
      "Path: swPort.editConf.inboundBandwidth.eir"
   ::= {er1645v2EthPortSwIIbwEntry 1879048192}

er1645v2EthPortSwIIbwUnit OBJECT-TYPE
   SYNTAX      INTEGER
               {
               bitssec (1),
               percent (2)
               }
   MAX-ACCESS  read-write
   STATUS      current
   DESCRIPTION
      "Path: swPort.editConf.inboundBandwidth.unit

       Possibilities:
               bits/sec   (1)
               percent   (2)"
   ::= {er1645v2EthPortSwIIbwEntry 1342177280}

er1645v2EthPortSwIIbwTc OBJECT-TYPE
   SYNTAX      INTEGER
               {
               auto (0)
               }
   MAX-ACCESS  read-write
   STATUS      current
   DESCRIPTION
      "Path: swPort.editConf.inboundBandwidth.tc

       Possibilities:
               auto   (0)"
   ::= {er1645v2EthPortSwIIbwEntry 1610612736}

er1645v2EthPortSwIIbwTcFactor OBJECT-TYPE
   SYNTAX      INTEGER
               {
               ms (10),
               s100us (1)
               }
   MAX-ACCESS  read-write
   STATUS      current
   DESCRIPTION
      "Path: swPort.editConf.inboundBandwidth.tcFactor

       Possibilities:
               ms   (10)
               *100us   (1)"
   ::= {er1645v2EthPortSwIIbwEntry 2147483648}

er1645v2EthPortSwIIbwCorrType OBJECT-TYPE
   SYNTAX      INTEGER
               {
               noCorrection (0),
               predefined (1),
               manual (2)
               }
   MAX-ACCESS  read-write
   STATUS      current
   DESCRIPTION
      "Path: swPort.editConf.inboundBandwidth.correction.type

       Possibilities:
               noCorrection   (0)
               predefined   (1)
               manual   (2)"
   ::= {er1645v2EthPortSwIIbwEntry 570425344}

er1645v2EthPortSwIIbwCorrPredefEncapsFrameRelay OBJECT-TYPE
   SYNTAX      DisplayString
   MAX-ACCESS  read-write
   STATUS      current
   DESCRIPTION
      "Path: swPort.editConf.inboundBandwidth.correction.predefined.encapsulation.frameRelay"
   ::= {er1645v2EthPortSwIIbwEntry 608436224}

er1645v2EthPortSwIIbwCorrPredefEncapsPpp OBJECT-TYPE
   SYNTAX      DisplayString
   MAX-ACCESS  read-write
   STATUS      current
   DESCRIPTION
      "Path: swPort.editConf.inboundBandwidth.correction.predefined.encapsulation.ppp"
   ::= {er1645v2EthPortSwIIbwEntry 608698368}

er1645v2EthPortSwIIbwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.inboundBandwidth.correction.predefined.encapsulation.atm.higherLayer

       Possibilities:
               rfc2684   (0)
               ppp   (1)
               pppOverEthernet   (2)"
   ::= {er1645v2EthPortSwIIbwEntry 608993280}

er1645v2EthPortSwIIbwCorrPredefEncapsAtmMp OBJECT-TYPE
   SYNTAX      INTEGER
               {
               llcEncapsulation (0),
               vcMultiplexing (1)
               }
   MAX-ACCESS  read-write
   STATUS      current
   DESCRIPTION
      "Path: swPort.editConf.inboundBandwidth.correction.predefined.encapsulation.atm.multiProtocol

       Possibilities:
               llcEncapsulation   (0)
               vcMultiplexing   (1)"
   ::= {er1645v2EthPortSwIIbwEntry 609026048}

er1645v2EthPortSwIIbwCorrPredefEncapsHdlc OBJECT-TYPE
   SYNTAX      DisplayString
   MAX-ACCESS  read-write
   STATUS      current
   DESCRIPTION
      "Path: swPort.editConf.inboundBandwidth.correction.predefined.encapsulation.hdlc"
   ::= {er1645v2EthPortSwIIbwEntry 609222656}

er1645v2EthPortSwIIbwCorrPredefEncapsEfmFs OBJECT-TYPE
   SYNTAX      Integer32
   MAX-ACCESS  read-write
   STATUS      current
   DESCRIPTION
      "Path: swPort.editConf.inboundBandwidth.correction.predefined.encapsulation.efm.fragmentSize"
   ::= {er1645v2EthPortSwIIbwEntry 609517568}

er1645v2EthPortSwIIbwCorrPredefEncapsEfmIb OBJECT-TYPE
   SYNTAX      Integer32
   MAX-ACCESS  read-write
   STATUS      current
   DESCRIPTION
      "Path: swPort.editConf.inboundBandwidth.correction.predefined.encapsulation.efm.idleBytes"
   ::= {er1645v2EthPortSwIIbwEntry 609550336}

er1645v2EthPortSwIIbwCorrPredefMode OBJECT-TYPE
   SYNTAX      INTEGER
               {
               routing (0),
               bridging (1)
               }
   MAX-ACCESS  read-write
   STATUS      current
   DESCRIPTION
      "Path: swPort.editConf.inboundBandwidth.correction.predefined.mode

       Possibilities:
               routing   (0)
               bridging   (1)"
   ::= {er1645v2EthPortSwIIbwEntry 612368384}

er1645v2EthPortSwIIbwCorrManualOverhead OBJECT-TYPE
   SYNTAX      Integer32
   MAX-ACCESS  read-write
   STATUS      current
   DESCRIPTION
      "Path: swPort.editConf.inboundBandwidth.correction.manual.overhead"
   ::= {er1645v2EthPortSwIIbwEntry 637665280}

er1645v2EthPortSwIIbwCorrManualFrameData OBJECT-TYPE
   SYNTAX      Counter32
   MAX-ACCESS  read-write
   STATUS      current
   DESCRIPTION
      "Path: swPort.editConf.inboundBandwidth.correction.manual.frameData

       32 bit unsigned wrappable counter."
   ::= {er1645v2EthPortSwIIbwEntry 637796352}

er1645v2EthPortSwIIbwCorrManualFrameHeader OBJECT-TYPE
   SYNTAX      Counter32
   MAX-ACCESS  read-write
   STATUS      current
   DESCRIPTION
      "Path: swPort.editConf.inboundBandwidth.correction.manual.frameHeader

       32 bit unsigned wrappable counter."
   ::= {er1645v2EthPortSwIIbwEntry 637927424}

er1645v2EthPortSwIIbwMaxFifoQLen OBJECT-TYPE
   SYNTAX      Integer32
   MAX-ACCESS  read-write
   STATUS      current
   DESCRIPTION
      "Path: swPort.editConf.inboundBandwidth.maxFifoQLen"
   ::= {er1645v2EthPortSwIIbwEntry 805306368}

er1645v2EthPortSwIIbwPriorityPolicy OBJECT-TYPE
   SYNTAX      DisplayString
   MAX-ACCESS  read-write
   STATUS      current
   DESCRIPTION
      "Path: swPort.editConf.inboundBandwidth.priorityPolicy"
   ::= {er1645v2EthPortSwIIbwEntry 1073741824}

er1645v2EthPortSwIIbwDeFlagCir OBJECT-TYPE
   SYNTAX      INTEGER
               {
               allowed (1),
               notAllowed (2)
               }
   MAX-ACCESS  read-write
   STATUS      current
   DESCRIPTION
      "Path: swPort.editConf.inboundBandwidth.deFlag.cir

       Possibilities:
               allowed   (1)
               notAllowed   (2)"
   ::= {er1645v2EthPortSwIIbwEntry 3490709504}

er1645v2EthPortSwIIbwDeFlagEir OBJECT-TYPE
   SYNTAX      INTEGER
               {
               allowed (1),
               notAllowed (2)
               }
   MAX-ACCESS  read-write
   STATUS      current
   DESCRIPTION
      "Path: swPort.editConf.inboundBandwidth.deFlag.eir

       Possibilities:
               allowed   (1)
               notAllowed   (2)"
   ::= {er1645v2EthPortSwIIbwEntry 3491758080}

er1645v2EthPortSwIIbwDeFlagViolate OBJECT-TYPE
   SYNTAX      INTEGER
               {
               allowed (1),
               notAllowed (2)
               }
   MAX-ACCESS  read-write
   STATUS      current
   DESCRIPTION
      "Path: swPort.editConf.inboundBandwidth.deFlag.violate

       Possibilities:
               allowed   (1)
               notAllowed   (2)"
   ::= {er1645v2EthPortSwIIbwEntry 3492806656}

er1645v2EthPortSwIIbwActCirActNone OBJECT-TYPE
   SYNTAX      OCTET STRING
   MAX-ACCESS  read-write
   STATUS      current
   DESCRIPTION
      "Path: swPort.editConf.inboundBandwidth.action.cirAction.none"
   ::= {er1645v2EthPortSwIIbwEntry 4062183424}

er1645v2EthPortSwIIbwActCirActEthCos1 OBJECT-TYPE
   SYNTAX      INTEGER
               {
               unchanged (256)
               }
   MAX-ACCESS  read-write
   STATUS      current
   DESCRIPTION
      "Path: swPort.editConf.inboundBandwidth.action.cirAction.ethernet.cosDepth1

       Possibilities:
               unchanged   (256)"
   ::= {er1645v2EthPortSwIIbwEntry 4064346112}

er1645v2EthPortSwIIbwActCirActEthDei1 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth1

       Possibilities:
               unchanged   (255)
               clear   (0)
               set   (1)"
   ::= {er1645v2EthPortSwIIbwEntry 4065656832}

er1645v2EthPortSwIIbwActCirActEthCos2 OBJECT-TYPE
   SYNTAX      INTEGER
               {
               unchanged (256)
               }
   MAX-ACCESS  read-write
   STATUS      current
   DESCRIPTION
      "Path: swPort.editConf.inboundBandwidth.action.cirAction.ethernet.cosDepth2

       Possibilities:
               unchanged   (256)"
   ::= {er1645v2EthPortSwIIbwEntry 4064411648}

er1645v2EthPortSwIIbwActCirActEthDei2 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth2

       Possibilities:
               unchanged   (255)
               clear   (0)
               set   (1)"
   ::= {er1645v2EthPortSwIIbwEntry 4065722368}

er1645v2EthPortSwIIbwActCirActEthCos3 OBJECT-TYPE
   SYNTAX      INTEGER
               {
               unchanged (256)
               }
   MAX-ACCESS  read-write
   STATUS      current
   DESCRIPTION
      "Path: swPort.editConf.inboundBandwidth.action.cirAction.ethernet.cosDepth3

       Possibilities:
               unchanged   (256)"
   ::= {er1645v2EthPortSwIIbwEntry 4064477184}

er1645v2EthPortSwIIbwActCirActEthDei3 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth3

       Possibilities:
               unchanged   (255)
               clear   (0)
               set   (1)"
   ::= {er1645v2EthPortSwIIbwEntry 4065787904}

er1645v2EthPortSwIIbwActCirActEthCos4 OBJECT-TYPE
   SYNTAX      INTEGER
               {
               unchanged (256)
               }
   MAX-ACCESS  read-write
   STATUS      current
   DESCRIPTION
      "Path: swPort.editConf.inboundBandwidth.action.cirAction.ethernet.cosDepth4

       Possibilities:
               unchanged   (256)"
   ::= {er1645v2EthPortSwIIbwEntry 4064542720}

er1645v2EthPortSwIIbwActCirActEthDei4 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth4

       Possibilities:
               unchanged   (255)
               clear   (0)
               set   (1)"
   ::= {er1645v2EthPortSwIIbwEntry 4065853440}

er1645v2EthPortSwIIbwActCirActEthCos5 OBJECT-TYPE
   SYNTAX      INTEGER
               {
               unchanged (256)
               }
   MAX-ACCESS  read-write
   STATUS      current
   DESCRIPTION
      "Path: swPort.editConf.inboundBandwidth.action.cirAction.ethernet.cosDepth5

       Possibilities:
               unchanged   (256)"
   ::= {er1645v2EthPortSwIIbwEntry 4064608256}

er1645v2EthPortSwIIbwActCirActEthDei5 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth5

       Possibilities:
               unchanged   (255)
               clear   (0)
               set   (1)"
   ::= {er1645v2EthPortSwIIbwEntry 4065918976}

er1645v2EthPortSwIIbwActCirActEthCos6 OBJECT-TYPE
   SYNTAX      INTEGER
               {
               unchanged (256)
               }
   MAX-ACCESS  read-write
   STATUS      current
   DESCRIPTION
      "Path: swPort.editConf.inboundBandwidth.action.cirAction.ethernet.cosDepth6

       Possibilities:
               unchanged   (256)"
   ::= {er1645v2EthPortSwIIbwEntry 4064673792}

er1645v2EthPortSwIIbwActCirActEthDei6 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth6

       Possibilities:
               unchanged   (255)
               clear   (0)
               set   (1)"
   ::= {er1645v2EthPortSwIIbwEntry 4065984512}

er1645v2EthPortSwIIbwActCirActEthCos7 OBJECT-TYPE
   SYNTAX      INTEGER
               {
               unchanged (256)
               }
   MAX-ACCESS  read-write
   STATUS      current
   DESCRIPTION
      "Path: swPort.editConf.inboundBandwidth.action.cirAction.ethernet.cosDepth7

       Possibilities:
               unchanged   (256)"
   ::= {er1645v2EthPortSwIIbwEntry 4064739328}

er1645v2EthPortSwIIbwActCirActEthDei7 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth7

       Possibilities:
               unchanged   (255)
               clear   (0)
               set   (1)"
   ::= {er1645v2EthPortSwIIbwEntry 4066050048}

er1645v2EthPortSwIIbwActCirActEthCos8 OBJECT-TYPE
   SYNTAX      INTEGER
               {
               unchanged (256)
               }
   MAX-ACCESS  read-write
   STATUS      current
   DESCRIPTION
      "Path: swPort.editConf.inboundBandwidth.action.cirAction.ethernet.cosDepth8

       Possibilities:
               unchanged   (256)"
   ::= {er1645v2EthPortSwIIbwEntry 4064804864}

er1645v2EthPortSwIIbwActCirActEthDei8 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth8

       Possibilities:
               unchanged   (255)
               clear   (0)
               set   (1)"
   ::= {er1645v2EthPortSwIIbwEntry 4066115584}

er1645v2EthPortSwIIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4064870400}

er1645v2EthPortSwIIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4064935936}

er1645v2EthPortSwIIbwActCirActEthDrpLev OBJECT-TYPE
   SYNTAX      INTEGER
               {
               unchanged (0)
               }
   MAX-ACCESS  read-write
   STATUS      current
   DESCRIPTION
      "Path: swPort.editConf.inboundBandwidth.action.cirAction.ethernet.dropLevel

       Possibilities:
               unchanged   (0)"
   ::= {er1645v2EthPortSwIIbwEntry 4065001472}

er1645v2EthPortSwIIbwActCirActEthDeFlag OBJECT-TYPE
   SYNTAX      INTEGER
               {
               unchanged (255),
               clear (0),
               set (1)
               }
   MAX-ACCESS  read-write
   STATUS      current
   DESCRIPTION
      "Path: swPort.editConf.inboundBandwidth.action.cirAction.ethernet.deFlag

       Possibilities:
               unchanged   (255)
               clear   (0)
               set   (1)"
   ::= {er1645v2EthPortSwIIbwEntry 4065198080}

er1645v2EthPortSwIIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4071161856}

er1645v2EthPortSwIIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4071227392}

er1645v2EthPortSwIIbwActCirActIpDrpLev OBJECT-TYPE
   SYNTAX      INTEGER
               {
               unchanged (0)
               }
   MAX-ACCESS  read-write
   STATUS      current
   DESCRIPTION
      "Path: swPort.editConf.inboundBandwidth.action.cirAction.ip.dropLevel

       Possibilities:
               unchanged   (0)"
   ::= {er1645v2EthPortSwIIbwEntry 4071292928}

er1645v2EthPortSwIIbwActCirActIpDeFlag OBJECT-TYPE
   SYNTAX      INTEGER
               {
               unchanged (255),
               clear (0),
               set (1)
               }
   MAX-ACCESS  read-write
   STATUS      current
   DESCRIPTION
      "Path: swPort.editConf.inboundBandwidth.action.cirAction.ip.deFlag

       Possibilities:
               unchanged   (255)
               clear   (0)
               set   (1)"
   ::= {er1645v2EthPortSwIIbwEntry 4071489536}

er1645v2EthPortSwIIbwActEirActNone OBJECT-TYPE
   SYNTAX      OCTET STRING
   MAX-ACCESS  read-write
   STATUS      current
   DESCRIPTION
      "Path: swPort.editConf.inboundBandwidth.action.eirAction.none"
   ::= {er1645v2EthPortSwIIbwEntry 4095737856}

er1645v2EthPortSwIIbwActEirActEthCos1 OBJECT-TYPE
   SYNTAX      INTEGER
               {
               unchanged (256)
               }
   MAX-ACCESS  read-write
   STATUS      current
   DESCRIPTION
      "Path: swPort.editConf.inboundBandwidth.action.eirAction.ethernet.cosDepth1

       Possibilities:
               unchanged   (256)"
   ::= {er1645v2EthPortSwIIbwEntry 4097900544}

er1645v2EthPortSwIIbwActEirActEthDei1 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth1

       Possibilities:
               unchanged   (255)
               clear   (0)
               set   (1)"
   ::= {er1645v2EthPortSwIIbwEntry 4099211264}

er1645v2EthPortSwIIbwActEirActEthCos2 OBJECT-TYPE
   SYNTAX      INTEGER
               {
               unchanged (256)
               }
   MAX-ACCESS  read-write
   STATUS      current
   DESCRIPTION
      "Path: swPort.editConf.inboundBandwidth.action.eirAction.ethernet.cosDepth2

       Possibilities:
               unchanged   (256)"
   ::= {er1645v2EthPortSwIIbwEntry 4097966080}

er1645v2EthPortSwIIbwActEirActEthDei2 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth2

       Possibilities:
               unchanged   (255)
               clear   (0)
               set   (1)"
   ::= {er1645v2EthPortSwIIbwEntry 4099276800}

er1645v2EthPortSwIIbwActEirActEthCos3 OBJECT-TYPE
   SYNTAX      INTEGER
               {
               unchanged (256)
               }
   MAX-ACCESS  read-write
   STATUS      current
   DESCRIPTION
      "Path: swPort.editConf.inboundBandwidth.action.eirAction.ethernet.cosDepth3

       Possibilities:
               unchanged   (256)"
   ::= {er1645v2EthPortSwIIbwEntry 4098031616}

er1645v2EthPortSwIIbwActEirActEthDei3 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth3

       Possibilities:
               unchanged   (255)
               clear   (0)
               set   (1)"
   ::= {er1645v2EthPortSwIIbwEntry 4099342336}

er1645v2EthPortSwIIbwActEirActEthCos4 OBJECT-TYPE
   SYNTAX      INTEGER
               {
               unchanged (256)
               }
   MAX-ACCESS  read-write
   STATUS      current
   DESCRIPTION
      "Path: swPort.editConf.inboundBandwidth.action.eirAction.ethernet.cosDepth4

       Possibilities:
               unchanged   (256)"
   ::= {er1645v2EthPortSwIIbwEntry 4098097152}

er1645v2EthPortSwIIbwActEirActEthDei4 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth4

       Possibilities:
               unchanged   (255)
               clear   (0)
               set   (1)"
   ::= {er1645v2EthPortSwIIbwEntry 4099407872}

er1645v2EthPortSwIIbwActEirActEthCos5 OBJECT-TYPE
   SYNTAX      INTEGER
               {
               unchanged (256)
               }
   MAX-ACCESS  read-write
   STATUS      current
   DESCRIPTION
      "Path: swPort.editConf.inboundBandwidth.action.eirAction.ethernet.cosDepth5

       Possibilities:
               unchanged   (256)"
   ::= {er1645v2EthPortSwIIbwEntry 4098162688}

er1645v2EthPortSwIIbwActEirActEthDei5 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth5

       Possibilities:
               unchanged   (255)
               clear   (0)
               set   (1)"
   ::= {er1645v2EthPortSwIIbwEntry 4099473408}

er1645v2EthPortSwIIbwActEirActEthCos6 OBJECT-TYPE
   SYNTAX      INTEGER
               {
               unchanged (256)
               }
   MAX-ACCESS  read-write
   STATUS      current
   DESCRIPTION
      "Path: swPort.editConf.inboundBandwidth.action.eirAction.ethernet.cosDepth6

       Possibilities:
               unchanged   (256)"
   ::= {er1645v2EthPortSwIIbwEntry 4098228224}

er1645v2EthPortSwIIbwActEirActEthDei6 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth6

       Possibilities:
               unchanged   (255)
               clear   (0)
               set   (1)"
   ::= {er1645v2EthPortSwIIbwEntry 4099538944}

er1645v2EthPortSwIIbwActEirActEthCos7 OBJECT-TYPE
   SYNTAX      INTEGER
               {
               unchanged (256)
               }
   MAX-ACCESS  read-write
   STATUS      current
   DESCRIPTION
      "Path: swPort.editConf.inboundBandwidth.action.eirAction.ethernet.cosDepth7

       Possibilities:
               unchanged   (256)"
   ::= {er1645v2EthPortSwIIbwEntry 4098293760}

er1645v2EthPortSwIIbwActEirActEthDei7 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth7

       Possibilities:
               unchanged   (255)
               clear   (0)
               set   (1)"
   ::= {er1645v2EthPortSwIIbwEntry 4099604480}

er1645v2EthPortSwIIbwActEirActEthCos8 OBJECT-TYPE
   SYNTAX      INTEGER
               {
               unchanged (256)
               }
   MAX-ACCESS  read-write
   STATUS      current
   DESCRIPTION
      "Path: swPort.editConf.inboundBandwidth.action.eirAction.ethernet.cosDepth8

       Possibilities:
               unchanged   (256)"
   ::= {er1645v2EthPortSwIIbwEntry 4098359296}

er1645v2EthPortSwIIbwActEirActEthDei8 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth8

       Possibilities:
               unchanged   (255)
               clear   (0)
               set   (1)"
   ::= {er1645v2EthPortSwIIbwEntry 4099670016}

er1645v2EthPortSwIIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4098424832}

er1645v2EthPortSwIIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4098490368}

er1645v2EthPortSwIIbwActEirActEthDrpLev OBJECT-TYPE
   SYNTAX      INTEGER
               {
               unchanged (0)
               }
   MAX-ACCESS  read-write
   STATUS      current
   DESCRIPTION
      "Path: swPort.editConf.inboundBandwidth.action.eirAction.ethernet.dropLevel

       Possibilities:
               unchanged   (0)"
   ::= {er1645v2EthPortSwIIbwEntry 4098555904}

er1645v2EthPortSwIIbwActEirActEthDeFlag OBJECT-TYPE
   SYNTAX      INTEGER
               {
               unchanged (255),
               clear (0),
               set (1)
               }
   MAX-ACCESS  read-write
   STATUS      current
   DESCRIPTION
      "Path: swPort.editConf.inboundBandwidth.action.eirAction.ethernet.deFlag

       Possibilities:
               unchanged   (255)
               clear   (0)
               set   (1)"
   ::= {er1645v2EthPortSwIIbwEntry 4098752512}

er1645v2EthPortSwIIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4104716288}

er1645v2EthPortSwIIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4104781824}

er1645v2EthPortSwIIbwActEirActIpDrpLev OBJECT-TYPE
   SYNTAX      INTEGER
               {
               unchanged (0)
               }
   MAX-ACCESS  read-write
   STATUS      current
   DESCRIPTION
      "Path: swPort.editConf.inboundBandwidth.action.eirAction.ip.dropLevel

       Possibilities:
               unchanged   (0)"
   ::= {er1645v2EthPortSwIIbwEntry 4104847360}

er1645v2EthPortSwIIbwActEirActIpDeFlag OBJECT-TYPE
   SYNTAX      INTEGER
               {
               unchanged (255),
               clear (0),
               set (1)
               }
   MAX-ACCESS  read-write
   STATUS      current
   DESCRIPTION
      "Path: swPort.editConf.inboundBandwidth.action.eirAction.ip.deFlag

       Possibilities:
               unchanged   (255)
               clear   (0)
               set   (1)"
   ::= {er1645v2EthPortSwIIbwEntry 4105043968}

er1645v2EthPortSwIIbwActViolActNone OBJECT-TYPE
   SYNTAX      OCTET STRING
   MAX-ACCESS  read-write
   STATUS      current
   DESCRIPTION
      "Path: swPort.editConf.inboundBandwidth.action.violateAction.none"
   ::= {er1645v2EthPortSwIIbwEntry 4129292288}

er1645v2EthPortSwIIbwActViolActDrop OBJECT-TYPE
   SYNTAX      OCTET STRING
   MAX-ACCESS  read-write
   STATUS      current
   DESCRIPTION
      "Path: swPort.editConf.inboundBandwidth.action.violateAction.drop"
   ::= {er1645v2EthPortSwIIbwEntry 4133486592}

er1645v2EthPortSwIIbwActViolActEthCos1 OBJECT-TYPE
   SYNTAX      INTEGER
               {
               unchanged (256)
               }
   MAX-ACCESS  read-write
   STATUS      current
   DESCRIPTION
      "Path: swPort.editConf.inboundBandwidth.action.violateAction.ethernet.cosDepth1

       Possibilities:
               unchanged   (256)"
   ::= {er1645v2EthPortSwIIbwEntry 4131454976}

er1645v2EthPortSwIIbwActViolActEthDei1 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth1

       Possibilities:
               unchanged   (255)
               clear   (0)
               set   (1)"
   ::= {er1645v2EthPortSwIIbwEntry 4132765696}

er1645v2EthPortSwIIbwActViolActEthCos2 OBJECT-TYPE
   SYNTAX      INTEGER
               {
               unchanged (256)
               }
   MAX-ACCESS  read-write
   STATUS      current
   DESCRIPTION
      "Path: swPort.editConf.inboundBandwidth.action.violateAction.ethernet.cosDepth2

       Possibilities:
               unchanged   (256)"
   ::= {er1645v2EthPortSwIIbwEntry 4131520512}

er1645v2EthPortSwIIbwActViolActEthDei2 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth2

       Possibilities:
               unchanged   (255)
               clear   (0)
               set   (1)"
   ::= {er1645v2EthPortSwIIbwEntry 4132831232}

er1645v2EthPortSwIIbwActViolActEthCos3 OBJECT-TYPE
   SYNTAX      INTEGER
               {
               unchanged (256)
               }
   MAX-ACCESS  read-write
   STATUS      current
   DESCRIPTION
      "Path: swPort.editConf.inboundBandwidth.action.violateAction.ethernet.cosDepth3

       Possibilities:
               unchanged   (256)"
   ::= {er1645v2EthPortSwIIbwEntry 4131586048}

er1645v2EthPortSwIIbwActViolActEthDei3 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth3

       Possibilities:
               unchanged   (255)
               clear   (0)
               set   (1)"
   ::= {er1645v2EthPortSwIIbwEntry 4132896768}

er1645v2EthPortSwIIbwActViolActEthCos4 OBJECT-TYPE
   SYNTAX      INTEGER
               {
               unchanged (256)
               }
   MAX-ACCESS  read-write
   STATUS      current
   DESCRIPTION
      "Path: swPort.editConf.inboundBandwidth.action.violateAction.ethernet.cosDepth4

       Possibilities:
               unchanged   (256)"
   ::= {er1645v2EthPortSwIIbwEntry 4131651584}

er1645v2EthPortSwIIbwActViolActEthDei4 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth4

       Possibilities:
               unchanged   (255)
               clear   (0)
               set   (1)"
   ::= {er1645v2EthPortSwIIbwEntry 4132962304}

er1645v2EthPortSwIIbwActViolActEthCos5 OBJECT-TYPE
   SYNTAX      INTEGER
               {
               unchanged (256)
               }
   MAX-ACCESS  read-write
   STATUS      current
   DESCRIPTION
      "Path: swPort.editConf.inboundBandwidth.action.violateAction.ethernet.cosDepth5

       Possibilities:
               unchanged   (256)"
   ::= {er1645v2EthPortSwIIbwEntry 4131717120}

er1645v2EthPortSwIIbwActViolActEthDei5 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth5

       Possibilities:
               unchanged   (255)
               clear   (0)
               set   (1)"
   ::= {er1645v2EthPortSwIIbwEntry 4133027840}

er1645v2EthPortSwIIbwActViolActEthCos6 OBJECT-TYPE
   SYNTAX      INTEGER
               {
               unchanged (256)
               }
   MAX-ACCESS  read-write
   STATUS      current
   DESCRIPTION
      "Path: swPort.editConf.inboundBandwidth.action.violateAction.ethernet.cosDepth6

       Possibilities:
               unchanged   (256)"
   ::= {er1645v2EthPortSwIIbwEntry 4131782656}

er1645v2EthPortSwIIbwActViolActEthDei6 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth6

       Possibilities:
               unchanged   (255)
               clear   (0)
               set   (1)"
   ::= {er1645v2EthPortSwIIbwEntry 4133093376}

er1645v2EthPortSwIIbwActViolActEthCos7 OBJECT-TYPE
   SYNTAX      INTEGER
               {
               unchanged (256)
               }
   MAX-ACCESS  read-write
   STATUS      current
   DESCRIPTION
      "Path: swPort.editConf.inboundBandwidth.action.violateAction.ethernet.cosDepth7

       Possibilities:
               unchanged   (256)"
   ::= {er1645v2EthPortSwIIbwEntry 4131848192}

er1645v2EthPortSwIIbwActViolActEthDei7 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth7

       Possibilities:
               unchanged   (255)
               clear   (0)
               set   (1)"
   ::= {er1645v2EthPortSwIIbwEntry 4133158912}

er1645v2EthPortSwIIbwActViolActEthCos8 OBJECT-TYPE
   SYNTAX      INTEGER
               {
               unchanged (256)
               }
   MAX-ACCESS  read-write
   STATUS      current
   DESCRIPTION
      "Path: swPort.editConf.inboundBandwidth.action.violateAction.ethernet.cosDepth8

       Possibilities:
               unchanged   (256)"
   ::= {er1645v2EthPortSwIIbwEntry 4131913728}

er1645v2EthPortSwIIbwActViolActEthDei8 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth8

       Possibilities:
               unchanged   (255)
               clear   (0)
               set   (1)"
   ::= {er1645v2EthPortSwIIbwEntry 4133224448}

er1645v2EthPortSwIIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4131979264}

er1645v2EthPortSwIIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4132044800}

er1645v2EthPortSwIIbwActViolActEthDrpLev OBJECT-TYPE
   SYNTAX      INTEGER
               {
               unchanged (0)
               }
   MAX-ACCESS  read-write
   STATUS      current
   DESCRIPTION
      "Path: swPort.editConf.inboundBandwidth.action.violateAction.ethernet.dropLevel

       Possibilities:
               unchanged   (0)"
   ::= {er1645v2EthPortSwIIbwEntry 4132110336}

er1645v2EthPortSwIIbwActViolActEthDeFlag OBJECT-TYPE
   SYNTAX      INTEGER
               {
               unchanged (255),
               clear (0),
               set (1)
               }
   MAX-ACCESS  read-write
   STATUS      current
   DESCRIPTION
      "Path: swPort.editConf.inboundBandwidth.action.violateAction.ethernet.deFlag

       Possibilities:
               unchanged   (255)
               clear   (0)
               set   (1)"
   ::= {er1645v2EthPortSwIIbwEntry 4132306944}

er1645v2EthPortSwIIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIIbwEntry 4138270720}

er1645v2EthPortSwIIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIIbwEntry 4138336256}

er1645v2EthPortSwIIbwActViolActIpDrpLev OBJECT-TYPE
   SYNTAX      INTEGER
               {
               unchanged (0)
               }
   MAX-ACCESS  read-write
   STATUS      current
   DESCRIPTION
      "Path: swPort.editConf.inboundBandwidth.action.violateAction.ip.dropLevel

       Possibilities:
               unchanged   (0)"
   ::= {er1645v2EthPortSwIIbwEntry 4138401792}

er1645v2EthPortSwIIbwActViolActIpDeFlag OBJECT-TYPE
   SYNTAX      INTEGER
               {
               unchanged (255),
               clear (0),
               set (1)
               }
   MAX-ACCESS  read-write
   STATUS      current
   DESCRIPTION
      "Path: swPort.editConf.inboundBandwidth.action.violateAction.ip.deFlag

       Possibilities:
               unchanged   (255)
               clear   (0)
               set   (1)"
   ::= {er1645v2EthPortSwIIbwEntry 4138598400}

er1645v2EthPortSwIIbwSubInterfacesExcluded OBJECT-TYPE
   SYNTAX      INTEGER
               {
               s (1)
               }
   MAX-ACCESS  read-write
   STATUS      current
   DESCRIPTION
      "Path: swPort.editConf.inboundBandwidth.subInterfaces.excluded

       Possibilities:
                  (1)"
   ::= {er1645v2EthPortSwIIbwEntry 2416967680}

er1645v2EthPortSwIIbwSubInterfacesIncludedInAccessList OBJECT-TYPE
   SYNTAX      DisplayString
   MAX-ACCESS  read-write
   STATUS      current
   DESCRIPTION
      "Path: swPort.editConf.inboundBandwidth.subInterfaces.included.inAccessList"
   ::= {er1645v2EthPortSwIIbwEntry 2418020352}


er1645v2EthPortSwIVlan OBJECT IDENTIFIER ::= {er1645v2EthPortSwI 33}

er1645v2EthPortSwIVlanSSCTable OBJECT-TYPE
   SYNTAX      SEQUENCE OF Er1645v2EthPortSwIVlanEntry
   MAX-ACCESS  not-accessible
   STATUS      current
   DESCRIPTION
      ""
   ::= {er1645v2EthPortSwIVlan 1}

er1645v2EthPortSwIVlanEntry OBJECT-TYPE
   SYNTAX      Er1645v2EthPortSwIVlanEntry
   MAX-ACCESS  not-accessible
   STATUS      current
   DESCRIPTION
      ""
   INDEX      { er1645v2EthPortSwIVlanGlobalIx,
                er1645v2EthPortSwIVlanTableIx }
   ::= {er1645v2EthPortSwIVlanSSCTable 1}

Er1645v2EthPortSwIVlanEntry ::=
   SEQUENCE
      {
      er1645v2EthPortSwIVlanActions
         VariableLengthTableActions,
      er1645v2EthPortSwIVlanGlobalIx
         GlobalIndex,
      er1645v2EthPortSwIVlanTableIx
         TableIndex,
      er1645v2EthPortSwIVlanName
         DisplayString,
      er1645v2EthPortSwIVlanRemark
         DisplayString,
      er1645v2EthPortSwIVlanAdminStatus
         INTEGER,
      er1645v2EthPortSwIVlanMode
         INTEGER,
      er1645v2EthPortSwIVlanPriorityPolicy
         DisplayString,
      er1645v2EthPortSwIVlanIpVrfRouter
         DisplayString,
      er1645v2EthPortSwIVlanIpAdr
         IpAddress,
      er1645v2EthPortSwIVlanIpNetm
         IpAddress,
      er1645v2EthPortSwIVlanIpSNetName
         INTEGER,
      er1645v2EthPortSwIVlanIpSNetCust
         DisplayString,
      er1645v2EthPortSwIVlanIpDhcpC
         INTEGER,
      er1645v2EthPortSwIVlanIpDhcpGatewayPreference
         Integer32,
      er1645v2EthPortSwIVlanIpDhcpRoutePreference
         Integer32,
      er1645v2EthPortSwIVlanIpDhcpDnsPreference
         Integer32,
      er1645v2EthPortSwIVlanIpMtu
         Integer32,
      er1645v2EthPortSwIVlanIpMssAdjust
         INTEGER,
      er1645v2EthPortSwIVlanIpRipMetric
         Integer32,
      er1645v2EthPortSwIVlanIpRipMetricOut
         Integer32,
      er1645v2EthPortSwIVlanIpRipMode
         INTEGER,
      er1645v2EthPortSwIVlanIpRipTxVer
         INTEGER,
      er1645v2EthPortSwIVlanIpRipRxVer
         INTEGER,
      er1645v2EthPortSwIVlanIpRipSplitH
         INTEGER,
      er1645v2EthPortSwIVlanIpRipAuth
         INTEGER,
      er1645v2EthPortSwIVlanIpRipFilter
         DisplayString,
      er1645v2EthPortSwIVlanIpRipFilterIn
         DisplayString,
      er1645v2EthPortSwIVlanIpRipClearNextHop
         INTEGER,
      er1645v2EthPortSwIVlanIpAccPol
         DisplayString,
      er1645v2EthPortSwIVlanIpAB
         DisplayString,
      er1645v2EthPortSwIVlanIpMA
         INTEGER,
      er1645v2EthPortSwIVlanIpMF
         Integer32,
      er1645v2EthPortSwIVlanIpDB
         INTEGER,
      er1645v2EthPortSwIVlanIpIR
         INTEGER,
      er1645v2EthPortSwIVlanIpIgmp
         INTEGER,
      er1645v2EthPortSwIVlanIpNN
         DisplayString,
      er1645v2EthPortSwIVlanIpVrrp
         INTEGER,
      er1645v2EthPortSwIVlanIpPimMode
         INTEGER,
      er1645v2EthPortSwIVlanIpPimDrPriority
         Counter32,
      er1645v2EthPortSwIVlanIpPimHelloTime
         TimeTicks,
      er1645v2EthPortSwIVlanIpPimPropagationDelay
         TimeTicks,
      er1645v2EthPortSwIVlanIpPimOverrideInterval
         TimeTicks,
      er1645v2EthPortSwIVlanIpPimBsrBorder
         INTEGER,
      er1645v2EthPortSwIVlanIpPimTtlThreshold
         Integer32,
      er1645v2EthPortSwIVlanIpIMNetworkUnreachable
         INTEGER,
      er1645v2EthPortSwIVlanIpIMHostUnreachable
         INTEGER,
      er1645v2EthPortSwIVlanIpIMProtocolUnreachable
         INTEGER,
      er1645v2EthPortSwIVlanIpIMPortUnreachable
         INTEGER,
      er1645v2EthPortSwIVlanIpIMMtuExceeded
         INTEGER,
      er1645v2EthPortSwIVlanIpIMAdminProhibited
         INTEGER,
      er1645v2EthPortSwIVlanIpIMTtlExceeded
         INTEGER,
      er1645v2EthPortSwIVlanIpIMRedirect
         INTEGER,
      er1645v2EthPortSwIVlanIpV6VrfRouter
         DisplayString,
      er1645v2EthPortSwIVlanIpV6AddrAutoConfigNrDupAddrDetects
         Integer32,
      er1645v2EthPortSwIVlanIpV6AddrAutoConfigAcceptRa
         INTEGER,
      er1645v2EthPortSwIVlanIpV6AddrAutoConfigAcceptRaRdnss
         INTEGER,
      er1645v2EthPortSwIVlanIpV6AddrAutoConfigAcceptRaDnssl
         INTEGER,
      er1645v2EthPortSwIVlanIpV6DefaultRoute
         INTEGER,
      er1645v2EthPortSwIVlanIpV6RaSend
         INTEGER,
      er1645v2EthPortSwIVlanIpV6RaMinInterval
         TimeTicks,
      er1645v2EthPortSwIVlanIpV6RaMaxInterval
         TimeTicks,
      er1645v2EthPortSwIVlanIpV6RaManagedFlag
         INTEGER,
      er1645v2EthPortSwIVlanIpV6RaOtherConfFlag
         INTEGER,
      er1645v2EthPortSwIVlanIpV6RaLinkMtu
         Integer32,
      er1645v2EthPortSwIVlanIpV6RaReachableTime
         TimeTicks,
      er1645v2EthPortSwIVlanIpV6RaRetransmitTime
         TimeTicks,
      er1645v2EthPortSwIVlanIpV6RaHopLimit
         Integer32,
      er1645v2EthPortSwIVlanIpV6RaDefaultLifeTime
         TimeTicks,
      er1645v2EthPortSwIVlanIpV6RaDnsOptionsRdnssLifeTime
         TimeTicks,
      er1645v2EthPortSwIVlanIpV6RaDnsOptionsRdnssImportServers
         INTEGER,
      er1645v2EthPortSwIVlanIpV6RaDnsOptionsDnsslLifeTime
         TimeTicks,
      er1645v2EthPortSwIVlanIpV6RaDnsOptionsDnsslImportDomains
         INTEGER,
      er1645v2EthPortSwIVlanIpV6RsSend
         INTEGER,
      er1645v2EthPortSwIVlanIpV6RsMaxRandomDelay
         TimeTicks,
      er1645v2EthPortSwIVlanIpV6RsInterval
         TimeTicks,
      er1645v2EthPortSwIVlanIpV6RsMaxSolicitations
         Integer32,
      er1645v2EthPortSwIVlanIpV6TrafficPolicyInbound
         DisplayString,
      er1645v2EthPortSwIVlanIpV6TrafficPolicyOutbound
         DisplayString,
      er1645v2EthPortSwIVlanIpV6FirewallZone
         DisplayString,
      er1645v2EthPortSwIVlanIpV6DhcpClientAddrAC
         INTEGER,
      er1645v2EthPortSwIVlanIpV6DhcpClientPrDelMode
         INTEGER,
      er1645v2EthPortSwIVlanIpV6DhcpClientPrDelPool
         DisplayString,
      er1645v2EthPortSwIVlanIpV6DhcpClientPrDelPdExclOpt
         INTEGER,
      er1645v2EthPortSwIVlanIpV6DhcpClientDnsServerPref
         Integer32,
      er1645v2EthPortSwIVlanIpV6DhcpClientRapidCommit
         INTEGER,
      er1645v2EthPortSwIVlanIpV6DhcpClientTimersSolTimeOut
         TimeTicks,
      er1645v2EthPortSwIVlanIpV6DhcpClientTimersSolMaxRt
         TimeTicks,
      er1645v2EthPortSwIVlanIpV6DhcpClientTimersInfoRefresh
         TimeTicks,
      er1645v2EthPortSwIVlanIpV6DhcpServerMode
         INTEGER,
      er1645v2EthPortSwIVlanIpV6DhcpServerPreference
         Integer32,
      er1645v2EthPortSwIVlanIpV6DhcpServerPool
         DisplayString,
      er1645v2EthPortSwIVlanIpV6DhcpServerRapidCommit
         INTEGER,
      er1645v2EthPortSwIVlanIpV6DhcpServerTimersInfoRefresh
         TimeTicks,
      er1645v2EthPortSwIVlanIpV6DhcpRelayMode
         INTEGER,
      er1645v2EthPortSwIVlanIpV6SendRedirect
         INTEGER,
      er1645v2EthPortSwIVlanIpV6LinkMtu
         Integer32,
      er1645v2EthPortSwIVlanIpV6InterfaceId
         OCTET STRING,
      er1645v2EthPortSwIVlanIpV6MF
         Integer32,
      er1645v2EthPortSwIVlanIpV6IcmpMessagesNoRoute
         INTEGER,
      er1645v2EthPortSwIVlanIpV6IcmpMessagesBeyondScope
         INTEGER,
      er1645v2EthPortSwIVlanIpV6IcmpMessagesAddressUnreachable
         INTEGER,
      er1645v2EthPortSwIVlanIpV6IcmpMessagesPortUnreachable
         INTEGER,
      er1645v2EthPortSwIVlanIpV6IcmpMessagesPacketTooBig
         INTEGER,
      er1645v2EthPortSwIVlanIpV6IcmpMessagesHopLimitExceeded
         INTEGER,
      er1645v2EthPortSwIVlanIpV6IcmpMessagesFragTimeExceeded
         INTEGER,
      er1645v2EthPortSwIVlanIpV6IcmpMessagesHeaderFieldErr
         INTEGER,
      er1645v2EthPortSwIVlanIpV6IcmpMessagesOptionUnrecognized
         INTEGER,
      er1645v2EthPortSwIVlanIpV6IcmpMessagesRedirect
         INTEGER,
      er1645v2EthPortSwIVlanBridgingAccList
         DisplayString,
      er1645v2EthPortSwIVlanBridgingInACL
         DisplayString,
      er1645v2EthPortSwIVlanBridgingTp
         DisplayString,
      er1645v2EthPortSwIVlanBridgingBrGrp
         DisplayString,
      er1645v2EthPortSwIVlanBridgingLimBC
         INTEGER,
      er1645v2EthPortSwIVlanBridgingPrivateMode
         INTEGER,
      er1645v2EthPortSwIVlanBridgingLearning
         INTEGER,
      er1645v2EthPortSwIVlanBridgingMaxCacheSize
         INTEGER,
      er1645v2EthPortSwIVlanBridgingRelearnDropOnRelearn
         INTEGER,
      er1645v2EthPortSwIVlanBridgingRelearnShutdownThreshold
         Integer32,
      er1645v2EthPortSwIVlanBridgingRelearnShutdownTime
         TimeTicks,
      er1645v2EthPortSwIVlanBridgingRelearnLoopDetection
         INTEGER,
      er1645v2EthPortSwIVlanBridgingRelearnLoopDetectionInterval
         TimeTicks,
      er1645v2EthPortSwIVlanBridgingVlanMemberShip
         INTEGER,
      er1645v2EthPortSwIVlanBridgingVlTUntaggedAction
         INTEGER,
      er1645v2EthPortSwIVlanBridgingVlTUntaggedTagInfoTpid
         INTEGER,
      er1645v2EthPortSwIVlanBridgingVlTUntaggedTagInfoVid
         Integer32,
      er1645v2EthPortSwIVlanBridgingVlTUnknownVlansAction
         INTEGER,
      er1645v2EthPortSwIVlanBridgingVlTUnknownVlansTagInfoTpid
         INTEGER,
      er1645v2EthPortSwIVlanBridgingVlTUnknownVlansTagInfoVid
         Integer32,
      er1645v2EthPortSwIVlanBridgingDot1adType
         INTEGER,
      er1645v2EthPortSwIVlanBridgingPriority
         Integer32,
      er1645v2EthPortSwIVlanBridgingPathCost
         Integer32,
      er1645v2EthPortSwIVlanBridgingInternalPathCost
         Integer32,
      er1645v2EthPortSwIVlanBridgingTCD
         INTEGER,
      er1645v2EthPortSwIVlanBridgingRestrictedRole
         INTEGER,
      er1645v2EthPortSwIVlanBridgingAdminEdge
         INTEGER,
      er1645v2EthPortSwIVlanBridgingOamMacDeviceMac
         DisplayString,
      er1645v2EthPortSwIVlanBridgingOamMacUserMac
         OCTET STRING,
      er1645v2EthPortSwIVlanBridgingOamMacBridgeMac
         DisplayString,
      er1645v2EthPortSwIVlanBridgingMgmtInline
         INTEGER,
      er1645v2EthPortSwIVlanBridgingL2ptMode
         INTEGER,
      er1645v2EthPortSwIVlanBridgingL2ptProtocols
         Integer32,
      er1645v2EthPortSwIVlanBridgingL2ptDestMac
         OCTET STRING,
      er1645v2EthPortSwIVlanBridgingL2ptCos
         INTEGER,
      er1645v2EthPortSwIVlanBridgingL2ptDropThrStp
         INTEGER,
      er1645v2EthPortSwIVlanBridgingL2ptDropThrLldp
         INTEGER,
      er1645v2EthPortSwIVlanBridgingL2ptDropThrOam
         INTEGER,
      er1645v2EthPortSwIVlanBridgingL2ptDropThrCdp
         INTEGER,
      er1645v2EthPortSwIVlanBridgingL2ptDropThrVtp
         INTEGER,
      er1645v2EthPortSwIVlanBridgingL2ptDropThrLacp
         INTEGER,
      er1645v2EthPortSwIVlanBridgingL2ptDropThrEfmOam
         INTEGER,
      er1645v2EthPortSwIVlanBridgingL2ptDropThrPvst
         INTEGER,
      er1645v2EthPortSwIVlanBridgingL2ptDropThrMmrp
         INTEGER,
      er1645v2EthPortSwIVlanBridgingL2ptDropThrMvrp
         INTEGER,
      er1645v2EthPortSwIVlanBridgingL2ptDropThrGvrp
         INTEGER,
      er1645v2EthPortSwIVlanBridgingL2ptDropThrGmrp
         INTEGER,
      er1645v2EthPortSwIVlanBridgingL2ptDropThrDtp
         INTEGER,
      er1645v2EthPortSwIVlanBridgingL2ptDropThrPagp
         INTEGER,
      er1645v2EthPortSwIVlanBridgingL2ptDropThrUdld
         INTEGER,
      er1645v2EthPortSwIVlanVlanVid
         INTEGER,
      er1645v2EthPortSwIVlanVlanVidExtensionSingle
         OCTET STRING,
      er1645v2EthPortSwIVlanVlanVidExtensionEndVid
         Integer32,
      er1645v2EthPortSwIVlanVlanTpid
         INTEGER,
      er1645v2EthPortSwIVlanVlanTagSign
         INTEGER,
      er1645v2EthPortSwIVlanVlanChTos
         INTEGER,
      er1645v2EthPortSwIVlanVlanCTMapP0
         INTEGER,
      er1645v2EthPortSwIVlanVlanCTMapP1
         INTEGER,
      er1645v2EthPortSwIVlanVlanCTMapP2
         INTEGER,
      er1645v2EthPortSwIVlanVlanCTMapP3
         INTEGER,
      er1645v2EthPortSwIVlanVlanCTMapP4
         INTEGER,
      er1645v2EthPortSwIVlanVlanCTMapP5
         INTEGER,
      er1645v2EthPortSwIVlanVlanCTMapP6
         INTEGER,
      er1645v2EthPortSwIVlanVlanCTMapP7
         INTEGER,
      er1645v2EthPortSwIVlanVlanTxCos
         INTEGER,
      er1645v2EthPortSwIVlanVlanCCMapP0
         Integer32,
      er1645v2EthPortSwIVlanVlanCCMapP1
         Integer32,
      er1645v2EthPortSwIVlanVlanCCMapP2
         Integer32,
      er1645v2EthPortSwIVlanVlanCCMapP3
         Integer32,
      er1645v2EthPortSwIVlanVlanCCMapP4
         Integer32,
      er1645v2EthPortSwIVlanVlanCCMapP5
         Integer32,
      er1645v2EthPortSwIVlanVlanCCMapP6
         Integer32,
      er1645v2EthPortSwIVlanVlanCCMapP7
         Integer32,
      er1645v2EthPortSwIVlanVlanQCMapQueue1
         Integer32,
      er1645v2EthPortSwIVlanVlanQCMapQueue2
         Integer32,
      er1645v2EthPortSwIVlanVlanQCMapQueue3
         Integer32,
      er1645v2EthPortSwIVlanVlanQCMapQueue4
         Integer32,
      er1645v2EthPortSwIVlanVlanQCMapQueue5
         Integer32,
      er1645v2EthPortSwIVlanVlanQCMapLowDelayQueue
         Integer32,
      er1645v2EthPortSwIVlanVlanQCMapLowDelay2Queue
         Integer32,
      er1645v2EthPortSwIVlanVlanQCMapSystemQueue
         Integer32,
      er1645v2EthPortSwIVlanVlanQinQSVid
         Integer32,
      er1645v2EthPortSwIVlanVlanQinQSTpid
         INTEGER,
      er1645v2EthPortSwIVlanVlanArpTimeOut
         TimeTicks,
      er1645v2EthPortSwIVlanVlanArpProxyArp
         INTEGER,
      er1645v2EthPortSwIVlanBandwidthMode
         INTEGER,
      er1645v2EthPortSwIVlanBandwidthCir
         Integer32,
      er1645v2EthPortSwIVlanBandwidthEir
         Integer32,
      er1645v2EthPortSwIVlanBandwidthUnit
         INTEGER,
      er1645v2EthPortSwIVlanBandwidthTc
         INTEGER,
      er1645v2EthPortSwIVlanBandwidthTcFactor
         INTEGER,
      er1645v2EthPortSwIVlanBandwidthCorrType
         INTEGER,
      er1645v2EthPortSwIVlanBandwidthCorrPredefEncapsFrameRelay
         DisplayString,
      er1645v2EthPortSwIVlanBandwidthCorrPredefEncapsPpp
         DisplayString,
      er1645v2EthPortSwIVlanBandwidthCorrPredefEncapsAtmHl
         INTEGER,
      er1645v2EthPortSwIVlanBandwidthCorrPredefEncapsAtmMp
         INTEGER,
      er1645v2EthPortSwIVlanBandwidthCorrPredefEncapsHdlc
         DisplayString,
      er1645v2EthPortSwIVlanBandwidthCorrPredefEncapsEfmFs
         Integer32,
      er1645v2EthPortSwIVlanBandwidthCorrPredefEncapsEfmIb
         Integer32,
      er1645v2EthPortSwIVlanBandwidthCorrPredefMode
         INTEGER,
      er1645v2EthPortSwIVlanBandwidthCorrManualOverhead
         Integer32,
      er1645v2EthPortSwIVlanBandwidthCorrManualFrameData
         Counter32,
      er1645v2EthPortSwIVlanBandwidthCorrManualFrameHeader
         Counter32,
      er1645v2EthPortSwIVlanBandwidthMaxFifoQLen
         Integer32,
      er1645v2EthPortSwIVlanBandwidthDeFlagCir
         INTEGER,
      er1645v2EthPortSwIVlanBandwidthDeFlagEir
         INTEGER,
      er1645v2EthPortSwIVlanBandwidthDeFlagViolate
         INTEGER,
      er1645v2EthPortSwIVlanBandwidthActCirActNone
         OCTET STRING,
      er1645v2EthPortSwIVlanBandwidthActCirActEthCos1
         INTEGER,
      er1645v2EthPortSwIVlanBandwidthActCirActEthDei1
         INTEGER,
      er1645v2EthPortSwIVlanBandwidthActCirActEthCos2
         INTEGER,
      er1645v2EthPortSwIVlanBandwidthActCirActEthDei2
         INTEGER,
      er1645v2EthPortSwIVlanBandwidthActCirActEthCos3
         INTEGER,
      er1645v2EthPortSwIVlanBandwidthActCirActEthDei3
         INTEGER,
      er1645v2EthPortSwIVlanBandwidthActCirActEthCos4
         INTEGER,
      er1645v2EthPortSwIVlanBandwidthActCirActEthDei4
         INTEGER,
      er1645v2EthPortSwIVlanBandwidthActCirActEthCos5
         INTEGER,
      er1645v2EthPortSwIVlanBandwidthActCirActEthDei5
         INTEGER,
      er1645v2EthPortSwIVlanBandwidthActCirActEthCos6
         INTEGER,
      er1645v2EthPortSwIVlanBandwidthActCirActEthDei6
         INTEGER,
      er1645v2EthPortSwIVlanBandwidthActCirActEthCos7
         INTEGER,
      er1645v2EthPortSwIVlanBandwidthActCirActEthDei7
         INTEGER,
      er1645v2EthPortSwIVlanBandwidthActCirActEthCos8
         INTEGER,
      er1645v2EthPortSwIVlanBandwidthActCirActEthDei8
         INTEGER,
      er1645v2EthPortSwIVlanBandwidthActCirActEthTos
         INTEGER,
      er1645v2EthPortSwIVlanBandwidthActCirActEthQueue
         INTEGER,
      er1645v2EthPortSwIVlanBandwidthActCirActEthDrpLev
         INTEGER,
      er1645v2EthPortSwIVlanBandwidthActCirActEthDeFlag
         INTEGER,
      er1645v2EthPortSwIVlanBandwidthActCirActIpTos
         INTEGER,
      er1645v2EthPortSwIVlanBandwidthActCirActIpQueue
         INTEGER,
      er1645v2EthPortSwIVlanBandwidthActCirActIpDrpLev
         INTEGER,
      er1645v2EthPortSwIVlanBandwidthActCirActIpDeFlag
         INTEGER,
      er1645v2EthPortSwIVlanBandwidthActEirActNone
         OCTET STRING,
      er1645v2EthPortSwIVlanBandwidthActEirActEthCos1
         INTEGER,
      er1645v2EthPortSwIVlanBandwidthActEirActEthDei1
         INTEGER,
      er1645v2EthPortSwIVlanBandwidthActEirActEthCos2
         INTEGER,
      er1645v2EthPortSwIVlanBandwidthActEirActEthDei2
         INTEGER,
      er1645v2EthPortSwIVlanBandwidthActEirActEthCos3
         INTEGER,
      er1645v2EthPortSwIVlanBandwidthActEirActEthDei3
         INTEGER,
      er1645v2EthPortSwIVlanBandwidthActEirActEthCos4
         INTEGER,
      er1645v2EthPortSwIVlanBandwidthActEirActEthDei4
         INTEGER,
      er1645v2EthPortSwIVlanBandwidthActEirActEthCos5
         INTEGER,
      er1645v2EthPortSwIVlanBandwidthActEirActEthDei5
         INTEGER,
      er1645v2EthPortSwIVlanBandwidthActEirActEthCos6
         INTEGER,
      er1645v2EthPortSwIVlanBandwidthActEirActEthDei6
         INTEGER,
      er1645v2EthPortSwIVlanBandwidthActEirActEthCos7
         INTEGER,
      er1645v2EthPortSwIVlanBandwidthActEirActEthDei7
         INTEGER,
      er1645v2EthPortSwIVlanBandwidthActEirActEthCos8
         INTEGER,
      er1645v2EthPortSwIVlanBandwidthActEirActEthDei8
         INTEGER,
      er1645v2EthPortSwIVlanBandwidthActEirActEthTos
         INTEGER,
      er1645v2EthPortSwIVlanBandwidthActEirActEthQueue
         INTEGER,
      er1645v2EthPortSwIVlanBandwidthActEirActEthDrpLev
         INTEGER,
      er1645v2EthPortSwIVlanBandwidthActEirActEthDeFlag
         INTEGER,
      er1645v2EthPortSwIVlanBandwidthActEirActIpTos
         INTEGER,
      er1645v2EthPortSwIVlanBandwidthActEirActIpQueue
         INTEGER,
      er1645v2EthPortSwIVlanBandwidthActEirActIpDrpLev
         INTEGER,
      er1645v2EthPortSwIVlanBandwidthActEirActIpDeFlag
         INTEGER,
      er1645v2EthPortSwIVlanBandwidthActViolActNone
         OCTET STRING,
      er1645v2EthPortSwIVlanBandwidthActViolActDrop
         OCTET STRING,
      er1645v2EthPortSwIVlanBandwidthActViolActEthCos1
         INTEGER,
      er1645v2EthPortSwIVlanBandwidthActViolActEthDei1
         INTEGER,
      er1645v2EthPortSwIVlanBandwidthActViolActEthCos2
         INTEGER,
      er1645v2EthPortSwIVlanBandwidthActViolActEthDei2
         INTEGER,
      er1645v2EthPortSwIVlanBandwidthActViolActEthCos3
         INTEGER,
      er1645v2EthPortSwIVlanBandwidthActViolActEthDei3
         INTEGER,
      er1645v2EthPortSwIVlanBandwidthActViolActEthCos4
         INTEGER,
      er1645v2EthPortSwIVlanBandwidthActViolActEthDei4
         INTEGER,
      er1645v2EthPortSwIVlanBandwidthActViolActEthCos5
         INTEGER,
      er1645v2EthPortSwIVlanBandwidthActViolActEthDei5
         INTEGER,
      er1645v2EthPortSwIVlanBandwidthActViolActEthCos6
         INTEGER,
      er1645v2EthPortSwIVlanBandwidthActViolActEthDei6
         INTEGER,
      er1645v2EthPortSwIVlanBandwidthActViolActEthCos7
         INTEGER,
      er1645v2EthPortSwIVlanBandwidthActViolActEthDei7
         INTEGER,
      er1645v2EthPortSwIVlanBandwidthActViolActEthCos8
         INTEGER,
      er1645v2EthPortSwIVlanBandwidthActViolActEthDei8
         INTEGER,
      er1645v2EthPortSwIVlanBandwidthActViolActEthTos
         INTEGER,
      er1645v2EthPortSwIVlanBandwidthActViolActEthQueue
         INTEGER,
      er1645v2EthPortSwIVlanBandwidthActViolActEthDrpLev
         INTEGER,
      er1645v2EthPortSwIVlanBandwidthActViolActEthDeFlag
         INTEGER,
      er1645v2EthPortSwIVlanBandwidthActViolActIpTos
         INTEGER,
      er1645v2EthPortSwIVlanBandwidthActViolActIpQueue
         INTEGER,
      er1645v2EthPortSwIVlanBandwidthActViolActIpDrpLev
         INTEGER,
      er1645v2EthPortSwIVlanBandwidthActViolActIpDeFlag
         INTEGER,
      er1645v2EthPortSwIVlanInbBwMode
         INTEGER,
      er1645v2EthPortSwIVlanInbBwCir
         Integer32,
      er1645v2EthPortSwIVlanInbBwEir
         Integer32,
      er1645v2EthPortSwIVlanInbBwUnit
         INTEGER,
      er1645v2EthPortSwIVlanInbBwTc
         INTEGER,
      er1645v2EthPortSwIVlanInbBwTcFactor
         INTEGER,
      er1645v2EthPortSwIVlanInbBwCorrType
         INTEGER,
      er1645v2EthPortSwIVlanInbBwCorrPredefEncapsFrameRelay
         DisplayString,
      er1645v2EthPortSwIVlanInbBwCorrPredefEncapsPpp
         DisplayString,
      er1645v2EthPortSwIVlanInbBwCorrPredefEncapsAtmHl
         INTEGER,
      er1645v2EthPortSwIVlanInbBwCorrPredefEncapsAtmMp
         INTEGER,
      er1645v2EthPortSwIVlanInbBwCorrPredefEncapsHdlc
         DisplayString,
      er1645v2EthPortSwIVlanInbBwCorrPredefEncapsEfmFs
         Integer32,
      er1645v2EthPortSwIVlanInbBwCorrPredefEncapsEfmIb
         Integer32,
      er1645v2EthPortSwIVlanInbBwCorrPredefMode
         INTEGER,
      er1645v2EthPortSwIVlanInbBwCorrManualOverhead
         Integer32,
      er1645v2EthPortSwIVlanInbBwCorrManualFrameData
         Counter32,
      er1645v2EthPortSwIVlanInbBwCorrManualFrameHeader
         Counter32,
      er1645v2EthPortSwIVlanInbBwMaxFifoQLen
         Integer32,
      er1645v2EthPortSwIVlanInbBwPriorityPolicy
         DisplayString,
      er1645v2EthPortSwIVlanInbBwDeFlagCir
         INTEGER,
      er1645v2EthPortSwIVlanInbBwDeFlagEir
         INTEGER,
      er1645v2EthPortSwIVlanInbBwDeFlagViolate
         INTEGER,
      er1645v2EthPortSwIVlanInbBwActCirActNone
         OCTET STRING,
      er1645v2EthPortSwIVlanInbBwActCirActEthCos1
         INTEGER,
      er1645v2EthPortSwIVlanInbBwActCirActEthDei1
         INTEGER,
      er1645v2EthPortSwIVlanInbBwActCirActEthCos2
         INTEGER,
      er1645v2EthPortSwIVlanInbBwActCirActEthDei2
         INTEGER,
      er1645v2EthPortSwIVlanInbBwActCirActEthCos3
         INTEGER,
      er1645v2EthPortSwIVlanInbBwActCirActEthDei3
         INTEGER,
      er1645v2EthPortSwIVlanInbBwActCirActEthCos4
         INTEGER,
      er1645v2EthPortSwIVlanInbBwActCirActEthDei4
         INTEGER,
      er1645v2EthPortSwIVlanInbBwActCirActEthCos5
         INTEGER,
      er1645v2EthPortSwIVlanInbBwActCirActEthDei5
         INTEGER,
      er1645v2EthPortSwIVlanInbBwActCirActEthCos6
         INTEGER,
      er1645v2EthPortSwIVlanInbBwActCirActEthDei6
         INTEGER,
      er1645v2EthPortSwIVlanInbBwActCirActEthCos7
         INTEGER,
      er1645v2EthPortSwIVlanInbBwActCirActEthDei7
         INTEGER,
      er1645v2EthPortSwIVlanInbBwActCirActEthCos8
         INTEGER,
      er1645v2EthPortSwIVlanInbBwActCirActEthDei8
         INTEGER,
      er1645v2EthPortSwIVlanInbBwActCirActEthTos
         INTEGER,
      er1645v2EthPortSwIVlanInbBwActCirActEthQueue
         INTEGER,
      er1645v2EthPortSwIVlanInbBwActCirActEthDrpLev
         INTEGER,
      er1645v2EthPortSwIVlanInbBwActCirActEthDeFlag
         INTEGER,
      er1645v2EthPortSwIVlanInbBwActCirActIpTos
         INTEGER,
      er1645v2EthPortSwIVlanInbBwActCirActIpQueue
         INTEGER,
      er1645v2EthPortSwIVlanInbBwActCirActIpDrpLev
         INTEGER,
      er1645v2EthPortSwIVlanInbBwActCirActIpDeFlag
         INTEGER,
      er1645v2EthPortSwIVlanInbBwActEirActNone
         OCTET STRING,
      er1645v2EthPortSwIVlanInbBwActEirActEthCos1
         INTEGER,
      er1645v2EthPortSwIVlanInbBwActEirActEthDei1
         INTEGER,
      er1645v2EthPortSwIVlanInbBwActEirActEthCos2
         INTEGER,
      er1645v2EthPortSwIVlanInbBwActEirActEthDei2
         INTEGER,
      er1645v2EthPortSwIVlanInbBwActEirActEthCos3
         INTEGER,
      er1645v2EthPortSwIVlanInbBwActEirActEthDei3
         INTEGER,
      er1645v2EthPortSwIVlanInbBwActEirActEthCos4
         INTEGER,
      er1645v2EthPortSwIVlanInbBwActEirActEthDei4
         INTEGER,
      er1645v2EthPortSwIVlanInbBwActEirActEthCos5
         INTEGER,
      er1645v2EthPortSwIVlanInbBwActEirActEthDei5
         INTEGER,
      er1645v2EthPortSwIVlanInbBwActEirActEthCos6
         INTEGER,
      er1645v2EthPortSwIVlanInbBwActEirActEthDei6
         INTEGER,
      er1645v2EthPortSwIVlanInbBwActEirActEthCos7
         INTEGER,
      er1645v2EthPortSwIVlanInbBwActEirActEthDei7
         INTEGER,
      er1645v2EthPortSwIVlanInbBwActEirActEthCos8
         INTEGER,
      er1645v2EthPortSwIVlanInbBwActEirActEthDei8
         INTEGER,
      er1645v2EthPortSwIVlanInbBwActEirActEthTos
         INTEGER,
      er1645v2EthPortSwIVlanInbBwActEirActEthQueue
         INTEGER,
      er1645v2EthPortSwIVlanInbBwActEirActEthDrpLev
         INTEGER,
      er1645v2EthPortSwIVlanInbBwActEirActEthDeFlag
         INTEGER,
      er1645v2EthPortSwIVlanInbBwActEirActIpTos
         INTEGER,
      er1645v2EthPortSwIVlanInbBwActEirActIpQueue
         INTEGER,
      er1645v2EthPortSwIVlanInbBwActEirActIpDrpLev
         INTEGER,
      er1645v2EthPortSwIVlanInbBwActEirActIpDeFlag
         INTEGER,
      er1645v2EthPortSwIVlanInbBwActViolActNone
         OCTET STRING,
      er1645v2EthPortSwIVlanInbBwActViolActDrop
         OCTET STRING,
      er1645v2EthPortSwIVlanInbBwActViolActEthCos1
         INTEGER,
      er1645v2EthPortSwIVlanInbBwActViolActEthDei1
         INTEGER,
      er1645v2EthPortSwIVlanInbBwActViolActEthCos2
         INTEGER,
      er1645v2EthPortSwIVlanInbBwActViolActEthDei2
         INTEGER,
      er1645v2EthPortSwIVlanInbBwActViolActEthCos3
         INTEGER,
      er1645v2EthPortSwIVlanInbBwActViolActEthDei3
         INTEGER,
      er1645v2EthPortSwIVlanInbBwActViolActEthCos4
         INTEGER,
      er1645v2EthPortSwIVlanInbBwActViolActEthDei4
         INTEGER,
      er1645v2EthPortSwIVlanInbBwActViolActEthCos5
         INTEGER,
      er1645v2EthPortSwIVlanInbBwActViolActEthDei5
         INTEGER,
      er1645v2EthPortSwIVlanInbBwActViolActEthCos6
         INTEGER,
      er1645v2EthPortSwIVlanInbBwActViolActEthDei6
         INTEGER,
      er1645v2EthPortSwIVlanInbBwActViolActEthCos7
         INTEGER,
      er1645v2EthPortSwIVlanInbBwActViolActEthDei7
         INTEGER,
      er1645v2EthPortSwIVlanInbBwActViolActEthCos8
         INTEGER,
      er1645v2EthPortSwIVlanInbBwActViolActEthDei8
         INTEGER,
      er1645v2EthPortSwIVlanInbBwActViolActEthTos
         INTEGER,
      er1645v2EthPortSwIVlanInbBwActViolActEthQueue
         INTEGER,
      er1645v2EthPortSwIVlanInbBwActViolActEthDrpLev
         INTEGER,
      er1645v2EthPortSwIVlanInbBwActViolActEthDeFlag
         INTEGER,
      er1645v2EthPortSwIVlanInbBwActViolActIpTos
         INTEGER,
      er1645v2EthPortSwIVlanInbBwActViolActIpQueue
         INTEGER,
      er1645v2EthPortSwIVlanInbBwActViolActIpDrpLev
         INTEGER,
      er1645v2EthPortSwIVlanInbBwActViolActIpDeFlag
         INTEGER,
      er1645v2EthPortSwIVlanPppoE
         INTEGER,
      er1645v2EthPortSwIVlanPppLnkMOperation
         INTEGER,
      er1645v2EthPortSwIVlanPppLnkMInterval
         TimeTicks,
      er1645v2EthPortSwIVlanPppLnkMRepTimeOut
         TimeTicks,
      er1645v2EthPortSwIVlanPppLnkMFailsPrmt
         Integer32,
      er1645v2EthPortSwIVlanPppAuthentication
         INTEGER,
      er1645v2EthPortSwIVlanPppAuthenPeriod
         TimeTicks,
      er1645v2EthPortSwIVlanPppSessionName
         DisplayString,
      er1645v2EthPortSwIVlanPppSessionSecret
         DisplayString,
      er1645v2EthPortSwIVlanPppEncModeSessionSecret
         INTEGER,
      er1645v2EthPortSwIVlanPppEncSessionSecret
         DisplayString,
      er1645v2EthPortSwIVlanPppServiceName
         DisplayString,
      er1645v2EthPortSwIVlanPbbMode
         INTEGER,
      er1645v2EthPortSwIVlanPbbTxCos
         Integer32,
      er1645v2EthPortSwIVlanPbbIsid
         Integer32,
      er1645v2EthPortSwIVlanPbbDestMac
         OCTET STRING,
      er1645v2EthPortSwIVlanPbbCustomGroupMac
         OCTET STRING
      }

er1645v2EthPortSwIVlanActions OBJECT-TYPE
   SYNTAX      VariableLengthTableActions
   MAX-ACCESS  read-write
   STATUS      current
   DESCRIPTION
      "By way of this field, some manipulations
       on this table may be performed."
   ::= {er1645v2EthPortSwIVlanEntry 2}

er1645v2EthPortSwIVlanGlobalIx OBJECT-TYPE
   SYNTAX      GlobalIndex
   MAX-ACCESS  not-accessible
   STATUS      current
   DESCRIPTION
      "The value of the tlsCntTreeGlobalIndex of the MANAGED OBJECT."
   ::= {er1645v2EthPortSwIVlanEntry 10}

er1645v2EthPortSwIVlanTableIx OBJECT-TYPE
   SYNTAX      TableIndex
   MAX-ACCESS  not-accessible
   STATUS      current
   DESCRIPTION
      ""
   ::= {er1645v2EthPortSwIVlanEntry 11}

er1645v2EthPortSwIVlanName OBJECT-TYPE
   SYNTAX      DisplayString
   MAX-ACCESS  read-write
   STATUS      current
   DESCRIPTION
      "Path: swPort.editConf.vlan.name"
   ::= {er1645v2EthPortSwIVlanEntry 16777216}

er1645v2EthPortSwIVlanRemark OBJECT-TYPE
   SYNTAX      DisplayString
   MAX-ACCESS  read-write
   STATUS      current
   DESCRIPTION
      "Path: swPort.editConf.vlan.remark"
   ::= {er1645v2EthPortSwIVlanEntry 1157627904}

er1645v2EthPortSwIVlanAdminStatus OBJECT-TYPE
   SYNTAX      INTEGER
               {
               up (1),
               down (2)
               }
   MAX-ACCESS  read-write
   STATUS      current
   DESCRIPTION
      "Path: swPort.editConf.vlan.adminStatus

       Possibilities:
               up   (1)
               down   (2)"
   ::= {er1645v2EthPortSwIVlanEntry 33554432}

er1645v2EthPortSwIVlanMode OBJECT-TYPE
   SYNTAX      INTEGER
               {
               routing (1),
               bridging (2),
               ipV6 (16),
               ipV6ipV4 (17),
               multilink (8)
               }
   MAX-ACCESS  read-write
   STATUS      current
   DESCRIPTION
      "Path: swPort.editConf.vlan.mode

       Possibilities:
               routing   (1)
               bridging   (2)
               ipV6   (16)
               ipV6/ipV4   (17)
               multilink   (8)"
   ::= {er1645v2EthPortSwIVlanEntry 67108864}

er1645v2EthPortSwIVlanPriorityPolicy OBJECT-TYPE
   SYNTAX      DisplayString
   MAX-ACCESS  read-write
   STATUS      current
   DESCRIPTION
      "Path: swPort.editConf.vlan.priorityPolicy"
   ::= {er1645v2EthPortSwIVlanEntry 83886080}

er1645v2EthPortSwIVlanIpVrfRouter OBJECT-TYPE
   SYNTAX      DisplayString
   MAX-ACCESS  read-write
   STATUS      current
   DESCRIPTION
      "Path: swPort.editConf.vlan.ip.vrfRouter"
   ::= {er1645v2EthPortSwIVlanEntry 53215232}

er1645v2EthPortSwIVlanIpAdr OBJECT-TYPE
   SYNTAX      IpAddress
   MAX-ACCESS  read-write
   STATUS      current
   DESCRIPTION
      "Path: swPort.editConf.vlan.ip.address"
   ::= {er1645v2EthPortSwIVlanEntry 58261504}

er1645v2EthPortSwIVlanIpNetm OBJECT-TYPE
   SYNTAX      IpAddress
   MAX-ACCESS  read-write
   STATUS      current
   DESCRIPTION
      "Path: swPort.editConf.vlan.ip.netMask"
   ::= {er1645v2EthPortSwIVlanEntry 58392576}

er1645v2EthPortSwIVlanIpSNetName OBJECT-TYPE
   SYNTAX      INTEGER
               {
               slOPTg (0),
               corp (2),
               dmz (3),
               internet (1)
               }
   MAX-ACCESS  read-write
   STATUS      current
   DESCRIPTION
      "Path: swPort.editConf.vlan.ip.sNet.name

       Possibilities:
               <OPT>   (0)
               corp   (2)
               dmz   (3)
               internet   (1)"
   ::= {er1645v2EthPortSwIVlanEntry 53674240}

er1645v2EthPortSwIVlanIpSNetCust OBJECT-TYPE
   SYNTAX      DisplayString
   MAX-ACCESS  read-write
   STATUS      current
   DESCRIPTION
      "Path: swPort.editConf.vlan.ip.sNet.custom"
   ::= {er1645v2EthPortSwIVlanEntry 53674496}

er1645v2EthPortSwIVlanIpDhcpC OBJECT-TYPE
   SYNTAX      INTEGER
               {
               disabled (0),
               enabled (1)
               }
   MAX-ACCESS  read-write
   STATUS      current
   DESCRIPTION
      "Path: swPort.editConf.vlan.ip.dhcpClient

       Possibilities:
               disabled   (0)
               enabled   (1)"
   ::= {er1645v2EthPortSwIVlanEntry 53608448}

er1645v2EthPortSwIVlanIpDhcpGatewayPreference OBJECT-TYPE
   SYNTAX      Integer32
   MAX-ACCESS  read-write
   STATUS      current
   DESCRIPTION
      "Path: swPort.editConf.vlan.ip.dhcp.gatewayPreference"
   ::= {er1645v2EthPortSwIVlanEntry 53739776}

er1645v2EthPortSwIVlanIpDhcpRoutePreference OBJECT-TYPE
   SYNTAX      Integer32
   MAX-ACCESS  read-write
   STATUS      current
   DESCRIPTION
      "Path: swPort.editConf.vlan.ip.dhcp.routePreference"
   ::= {er1645v2EthPortSwIVlanEntry 53740032}

er1645v2EthPortSwIVlanIpDhcpDnsPreference OBJECT-TYPE
   SYNTAX      Integer32
   MAX-ACCESS  read-write
   STATUS      current
   DESCRIPTION
      "Path: swPort.editConf.vlan.ip.dhcp.dnsPreference"
   ::= {er1645v2EthPortSwIVlanEntry 53740288}

er1645v2EthPortSwIVlanIpMtu OBJECT-TYPE
   SYNTAX      Integer32
   MAX-ACCESS  read-write
   STATUS      current
   DESCRIPTION
      "Path: swPort.editConf.vlan.ip.mtu"
   ::= {er1645v2EthPortSwIVlanEntry 52953088}

er1645v2EthPortSwIVlanIpMssAdjust OBJECT-TYPE
   SYNTAX      INTEGER
               {
               disabled (0),
               auto (65536)
               }
   MAX-ACCESS  read-write
   STATUS      current
   DESCRIPTION
      "Path: swPort.editConf.vlan.ip.mssAdjust

       Possibilities:
               disabled   (0)
               auto   (65536)"
   ::= {er1645v2EthPortSwIVlanEntry 53280768}

er1645v2EthPortSwIVlanIpRipMetric OBJECT-TYPE
   SYNTAX      Integer32
   MAX-ACCESS  read-write
   STATUS      current
   DESCRIPTION
      "Path: swPort.editConf.vlan.ip.rip.metric"
   ::= {er1645v2EthPortSwIVlanEntry 51712768}

er1645v2EthPortSwIVlanIpRipMetricOut OBJECT-TYPE
   SYNTAX      Integer32
   MAX-ACCESS  read-write
   STATUS      current
   DESCRIPTION
      "Path: swPort.editConf.vlan.ip.rip.metricOut"
   ::= {er1645v2EthPortSwIVlanEntry 51713024}

er1645v2EthPortSwIVlanIpRipMode OBJECT-TYPE
   SYNTAX      INTEGER
               {
               disabled (0),
               passive (1),
               active (2)
               }
   MAX-ACCESS  read-write
   STATUS      current
   DESCRIPTION
      "Path: swPort.editConf.vlan.ip.rip.mode

       Possibilities:
               disabled   (0)
               passive   (1)
               active   (2)"
   ::= {er1645v2EthPortSwIVlanEntry 51713280}

er1645v2EthPortSwIVlanIpRipTxVer OBJECT-TYPE
   SYNTAX      INTEGER
               {
               rip1 (0),
               rip2 (1),
               rip1mcompatible (2)
               }
   MAX-ACCESS  read-write
   STATUS      current
   DESCRIPTION
      "Path: swPort.editConf.vlan.ip.rip.txVersion

       Possibilities:
               rip1   (0)
               rip2   (1)
               rip1-compatible   (2)"
   ::= {er1645v2EthPortSwIVlanEntry 51716864}

er1645v2EthPortSwIVlanIpRipRxVer OBJECT-TYPE
   SYNTAX      INTEGER
               {
               rip1only (0),
               rip2only (1),
               rip12 (2)
               }
   MAX-ACCESS  read-write
   STATUS      current
   DESCRIPTION
      "Path: swPort.editConf.vlan.ip.rip.rxVersion

       Possibilities:
               rip1only   (0)
               rip2only   (1)
               rip1&2   (2)"
   ::= {er1645v2EthPortSwIVlanEntry 51717120}

er1645v2EthPortSwIVlanIpRipSplitH OBJECT-TYPE
   SYNTAX      INTEGER
               {
               disabled (0),
               enabled (1),
               poisonedReverse (2)
               }
   MAX-ACCESS  read-write
   STATUS      current
   DESCRIPTION
      "Path: swPort.editConf.vlan.ip.rip.splitHorizon

       Possibilities:
               disabled   (0)
               enabled   (1)
               poisonedReverse   (2)"
   ::= {er1645v2EthPortSwIVlanEntry 51713792}

er1645v2EthPortSwIVlanIpRipAuth OBJECT-TYPE
   SYNTAX      INTEGER
               {
               disabled (0),
               texts (1),
               md5 (2)
               }
   MAX-ACCESS  read-write
   STATUS      current
   DESCRIPTION
      "Path: swPort.editConf.vlan.ip.rip.authentication

       Possibilities:
               disabled   (0)
               text    (1)
               md5   (2)"
   ::= {er1645v2EthPortSwIVlanEntry 51712512}

er1645v2EthPortSwIVlanIpRipFilter OBJECT-TYPE
   SYNTAX      DisplayString
   MAX-ACCESS  read-write
   STATUS      current
   DESCRIPTION
      "Path: swPort.editConf.vlan.ip.rip.filter"
   ::= {er1645v2EthPortSwIVlanEntry 51716096}

er1645v2EthPortSwIVlanIpRipFilterIn OBJECT-TYPE
   SYNTAX      DisplayString
   MAX-ACCESS  read-write
   STATUS      current
   DESCRIPTION
      "Path: swPort.editConf.vlan.ip.rip.filterIn"
   ::= {er1645v2EthPortSwIVlanEntry 51716352}

er1645v2EthPortSwIVlanIpRipClearNextHop OBJECT-TYPE
   SYNTAX      INTEGER
               {
               disabled (0),
               enabled (1)
               }
   MAX-ACCESS  read-write
   STATUS      current
   DESCRIPTION
      "Path: swPort.editConf.vlan.ip.rip.clearNextHop

       Possibilities:
               disabled   (0)
               enabled   (1)"
   ::= {er1645v2EthPortSwIVlanEntry 51708416}

er1645v2EthPortSwIVlanIpAccPol OBJECT-TYPE
   SYNTAX      DisplayString
   MAX-ACCESS  read-write
   STATUS      current
   DESCRIPTION
      "Path: swPort.editConf.vlan.ip.accessPolicy"
   ::= {er1645v2EthPortSwIVlanEntry 53084160}

er1645v2EthPortSwIVlanIpAB OBJECT-TYPE
   SYNTAX      DisplayString
   MAX-ACCESS  read-write
   STATUS      current
   DESCRIPTION
      "Path: swPort.editConf.vlan.ip.trafficPolicy"
   ::= {er1645v2EthPortSwIVlanEntry 51249152}

er1645v2EthPortSwIVlanIpMA OBJECT-TYPE
   SYNTAX      INTEGER
               {
               disabled (0),
               enabled (1)
               }
   MAX-ACCESS  read-write
   STATUS      current
   DESCRIPTION
      "Path: swPort.editConf.vlan.ip.mgmtAccess

       Possibilities:
               disabled   (0)
               enabled   (1)"
   ::= {er1645v2EthPortSwIVlanEntry 51380224}

er1645v2EthPortSwIVlanIpMF OBJECT-TYPE
   SYNTAX      Integer32
   MAX-ACCESS  read-write
   STATUS      current
   DESCRIPTION
      "Path: swPort.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPortSwIVlanEntry 51445760}

er1645v2EthPortSwIVlanIpDB OBJECT-TYPE
   SYNTAX      INTEGER
               {
               disabled (0),
               enabled (1)
               }
   MAX-ACCESS  read-write
   STATUS      current
   DESCRIPTION
      "Path: swPort.editConf.vlan.ip.directedBroadcasts

       Possibilities:
               disabled   (0)
               enabled   (1)"
   ::= {er1645v2EthPortSwIVlanEntry 51773440}

er1645v2EthPortSwIVlanIpIR OBJECT-TYPE
   SYNTAX      INTEGER
               {
               disabled (0),
               enabled (1)
               }
   MAX-ACCESS  read-write
   STATUS      current
   DESCRIPTION
      "Path: swPort.editConf.vlan.ip.icmpRedirects

       Possibilities:
               disabled   (0)
               enabled   (1)"
   ::= {er1645v2EthPortSwIVlanEntry 52035584}

er1645v2EthPortSwIVlanIpIgmp OBJECT-TYPE
   SYNTAX      INTEGER
               {
               disabled (0),
               proxy (1),
               router (2),
               v3Router (5)
               }
   MAX-ACCESS  read-write
   STATUS      current
   DESCRIPTION
      "Path: swPort.editConf.vlan.ip.igmp

       Possibilities:
               disabled   (0)
               proxy   (1)
               router   (2)
               v3Router   (5)"
   ::= {er1645v2EthPortSwIVlanEntry 52428800}

er1645v2EthPortSwIVlanIpNN OBJECT-TYPE
   SYNTAX      DisplayString
   MAX-ACCESS  read-write
   STATUS      current
   DESCRIPTION
      "Path: swPort.editConf.vlan.ip.nat"
   ::= {er1645v2EthPortSwIVlanEntry 52101120}

er1645v2EthPortSwIVlanIpVrrp OBJECT-TYPE
   SYNTAX      INTEGER
               {
               disabled (0),
               enabled (1)
               }
   MAX-ACCESS  read-write
   STATUS      current
   DESCRIPTION
      "Path: swPort.editConf.vlan.ip.vrrp

       Possibilities:
               disabled   (0)
               enabled   (1)"
   ::= {er1645v2EthPortSwIVlanEntry 53149696}

er1645v2EthPortSwIVlanIpPimMode OBJECT-TYPE
   SYNTAX      INTEGER
               {
               disabled (0),
               sparse (1),
               passive (2)
               }
   MAX-ACCESS  read-write
   STATUS      current
   DESCRIPTION
      "Path: swPort.editConf.vlan.ip.pim.mode

       Possibilities:
               disabled   (0)
               sparse   (1)
               passive   (2)"
   ::= {er1645v2EthPortSwIVlanEntry 53346560}

er1645v2EthPortSwIVlanIpPimDrPriority OBJECT-TYPE
   SYNTAX      Counter32
   MAX-ACCESS  read-write
   STATUS      current
   DESCRIPTION
      "Path: swPort.editConf.vlan.ip.pim.drPriority

       32 bit unsigned wrappable counter."
   ::= {er1645v2EthPortSwIVlanEntry 53346816}

er1645v2EthPortSwIVlanIpPimHelloTime OBJECT-TYPE
   SYNTAX      TimeTicks
   MAX-ACCESS  read-write
   STATUS      current
   DESCRIPTION
      "Path: swPort.editConf.vlan.ip.pim.helloTime

       Time in centi-second."
   ::= {er1645v2EthPortSwIVlanEntry 53347072}

er1645v2EthPortSwIVlanIpPimPropagationDelay OBJECT-TYPE
   SYNTAX      TimeTicks
   MAX-ACCESS  read-write
   STATUS      current
   DESCRIPTION
      "Path: swPort.editConf.vlan.ip.pim.propagationDelay

       Time in centi-second."
   ::= {er1645v2EthPortSwIVlanEntry 53347328}

er1645v2EthPortSwIVlanIpPimOverrideInterval OBJECT-TYPE
   SYNTAX      TimeTicks
   MAX-ACCESS  read-write
   STATUS      current
   DESCRIPTION
      "Path: swPort.editConf.vlan.ip.pim.overrideInterval

       Time in centi-second."
   ::= {er1645v2EthPortSwIVlanEntry 53347584}

er1645v2EthPortSwIVlanIpPimBsrBorder OBJECT-TYPE
   SYNTAX      INTEGER
               {
               disabled (0),
               enabled (1)
               }
   MAX-ACCESS  read-write
   STATUS      current
   DESCRIPTION
      "Path: swPort.editConf.vlan.ip.pim.bsrBorder

       Possibilities:
               disabled   (0)
               enabled   (1)"
   ::= {er1645v2EthPortSwIVlanEntry 53347840}

er1645v2EthPortSwIVlanIpPimTtlThreshold OBJECT-TYPE
   SYNTAX      Integer32
   MAX-ACCESS  read-write
   STATUS      current
   DESCRIPTION
      "Path: swPort.editConf.vlan.ip.pim.ttlThreshold"
   ::= {er1645v2EthPortSwIVlanEntry 53348096}

er1645v2EthPortSwIVlanIpIMNetworkUnreachable OBJECT-TYPE
   SYNTAX      INTEGER
               {
               disabled (0),
               enabled (1)
               }
   MAX-ACCESS  read-write
   STATUS      current
   DESCRIPTION
      "Path: swPort.editConf.vlan.ip.icmpMessages.networkUnreachable

       Possibilities:
               disabled   (0)
               enabled   (1)"
   ::= {er1645v2EthPortSwIVlanEntry 53412096}

er1645v2EthPortSwIVlanIpIMHostUnreachable OBJECT-TYPE
   SYNTAX      INTEGER
               {
               disabled (0),
               enabled (1)
               }
   MAX-ACCESS  read-write
   STATUS      current
   DESCRIPTION
      "Path: swPort.editConf.vlan.ip.icmpMessages.hostUnreachable

       Possibilities:
               disabled   (0)
               enabled   (1)"
   ::= {er1645v2EthPortSwIVlanEntry 53412352}

er1645v2EthPortSwIVlanIpIMProtocolUnreachable OBJECT-TYPE
   SYNTAX      INTEGER
               {
               disabled (0),
               enabled (1)
               }
   MAX-ACCESS  read-write
   STATUS      current
   DESCRIPTION
      "Path: swPort.editConf.vlan.ip.icmpMessages.protocolUnreachable

       Possibilities:
               disabled   (0)
               enabled   (1)"
   ::= {er1645v2EthPortSwIVlanEntry 53412608}

er1645v2EthPortSwIVlanIpIMPortUnreachable OBJECT-TYPE
   SYNTAX      INTEGER
               {
               disabled (0),
               enabled (1)
               }
   MAX-ACCESS  read-write
   STATUS      current
   DESCRIPTION
      "Path: swPort.editConf.vlan.ip.icmpMessages.portUnreachable

       Possibilities:
               disabled   (0)
               enabled   (1)"
   ::= {er1645v2EthPortSwIVlanEntry 53412864}

er1645v2EthPortSwIVlanIpIMMtuExceeded OBJECT-TYPE
   SYNTAX      INTEGER
               {
               disabled (0),
               enabled (1)
               }
   MAX-ACCESS  read-write
   STATUS      current
   DESCRIPTION
      "Path: swPort.editConf.vlan.ip.icmpMessages.mtuExceeded

       Possibilities:
               disabled   (0)
               enabled   (1)"
   ::= {er1645v2EthPortSwIVlanEntry 53413120}

er1645v2EthPortSwIVlanIpIMAdminProhibited OBJECT-TYPE
   SYNTAX      INTEGER
               {
               disabled (0),
               enabled (1)
               }
   MAX-ACCESS  read-write
   STATUS      current
   DESCRIPTION
      "Path: swPort.editConf.vlan.ip.icmpMessages.adminProhibited

       Possibilities:
               disabled   (0)
               enabled   (1)"
   ::= {er1645v2EthPortSwIVlanEntry 53413376}

er1645v2EthPortSwIVlanIpIMTtlExceeded OBJECT-TYPE
   SYNTAX      INTEGER
               {
               disabled (0),
               enabled (1)
               }
   MAX-ACCESS  read-write
   STATUS      current
   DESCRIPTION
      "Path: swPort.editConf.vlan.ip.icmpMessages.ttlExceeded

       Possibilities:
               disabled   (0)
               enabled   (1)"
   ::= {er1645v2EthPortSwIVlanEntry 53413632}

er1645v2EthPortSwIVlanIpIMRedirect OBJECT-TYPE
   SYNTAX      INTEGER
               {
               disabled (0),
               enabled (1)
               }
   MAX-ACCESS  read-write
   STATUS      current
   DESCRIPTION
      "Path: swPort.editConf.vlan.ip.icmpMessages.redirect

       Possibilities:
               disabled   (0)
               enabled   (1)"
   ::= {er1645v2EthPortSwIVlanEntry 53413888}

er1645v2EthPortSwIVlanIpV6VrfRouter OBJECT-TYPE
   SYNTAX      DisplayString
   MAX-ACCESS  read-write
   STATUS      current
   DESCRIPTION
      "Path: swPort.editConf.vlan.ipV6.vrfRouter"
   ::= {er1645v2EthPortSwIVlanEntry 704708608}

er1645v2EthPortSwIVlanIpV6AddrAutoConfigNrDupAddrDetects OBJECT-TYPE
   SYNTAX      Integer32
   MAX-ACCESS  read-write
   STATUS      current
   DESCRIPTION
      "Path: swPort.editConf.vlan.ipV6.addrAutoConfig.nrDupAddrDetects"
   ::= {er1645v2EthPortSwIVlanEntry 704905472}

er1645v2EthPortSwIVlanIpV6AddrAutoConfigAcceptRa OBJECT-TYPE
   SYNTAX      INTEGER
               {
               disabled (0),
               enabled (1)
               }
   MAX-ACCESS  read-write
   STATUS      current
   DESCRIPTION
      "Path: swPort.editConf.vlan.ipV6.addrAutoConfig.acceptRa

       Possibilities:
               disabled   (0)
               enabled   (1)"
   ::= {er1645v2EthPortSwIVlanEntry 704905728}

er1645v2EthPortSwIVlanIpV6AddrAutoConfigAcceptRaRdnss OBJECT-TYPE
   SYNTAX      INTEGER
               {
               disabled (0),
               enabled (1)
               }
   MAX-ACCESS  read-write
   STATUS      current
   DESCRIPTION
      "Path: swPort.editConf.vlan.ipV6.addrAutoConfig.acceptRaRdnss

       Possibilities:
               disabled   (0)
               enabled   (1)"
   ::= {er1645v2EthPortSwIVlanEntry 704905984}

er1645v2EthPortSwIVlanIpV6AddrAutoConfigAcceptRaDnssl OBJECT-TYPE
   SYNTAX      INTEGER
               {
               disabled (0),
               enabled (1)
               }
   MAX-ACCESS  read-write
   STATUS      current
   DESCRIPTION
      "Path: swPort.editConf.vlan.ipV6.addrAutoConfig.acceptRaDnssl

       Possibilities:
               disabled   (0)
               enabled   (1)"
   ::= {er1645v2EthPortSwIVlanEntry 704906240}

er1645v2EthPortSwIVlanIpV6DefaultRoute OBJECT-TYPE
   SYNTAX      INTEGER
               {
               disabled (0),
               enabled (1)
               }
   MAX-ACCESS  read-write
   STATUS      current
   DESCRIPTION
      "Path: swPort.editConf.vlan.ipV6.defaultRoute

       Possibilities:
               disabled   (0)
               enabled   (1)"
   ::= {er1645v2EthPortSwIVlanEntry 704970752}

er1645v2EthPortSwIVlanIpV6RaSend OBJECT-TYPE
   SYNTAX      INTEGER
               {
               disabled (0),
               enabled (1)
               }
   MAX-ACCESS  read-write
   STATUS      current
   DESCRIPTION
      "Path: swPort.editConf.vlan.ipV6.ra.send

       Possibilities:
               disabled   (0)
               enabled   (1)"
   ::= {er1645v2EthPortSwIVlanEntry 705036544}

er1645v2EthPortSwIVlanIpV6RaMinInterval OBJECT-TYPE
   SYNTAX      TimeTicks
   MAX-ACCESS  read-write
   STATUS      current
   DESCRIPTION
      "Path: swPort.editConf.vlan.ipV6.ra.minInterval

       Time in centi-second."
   ::= {er1645v2EthPortSwIVlanEntry 705036800}

er1645v2EthPortSwIVlanIpV6RaMaxInterval OBJECT-TYPE
   SYNTAX      TimeTicks
   MAX-ACCESS  read-write
   STATUS      current
   DESCRIPTION
      "Path: swPort.editConf.vlan.ipV6.ra.maxInterval

       Time in centi-second."
   ::= {er1645v2EthPortSwIVlanEntry 705037056}

er1645v2EthPortSwIVlanIpV6RaManagedFlag OBJECT-TYPE
   SYNTAX      INTEGER
               {
               disabled (0),
               enabled (1)
               }
   MAX-ACCESS  read-write
   STATUS      current
   DESCRIPTION
      "Path: swPort.editConf.vlan.ipV6.ra.managedFlag

       Possibilities:
               disabled   (0)
               enabled   (1)"
   ::= {er1645v2EthPortSwIVlanEntry 705037312}

er1645v2EthPortSwIVlanIpV6RaOtherConfFlag OBJECT-TYPE
   SYNTAX      INTEGER
               {
               disabled (0),
               enabled (1)
               }
   MAX-ACCESS  read-write
   STATUS      current
   DESCRIPTION
      "Path: swPort.editConf.vlan.ipV6.ra.otherConfFlag

       Possibilities:
               disabled   (0)
               enabled   (1)"
   ::= {er1645v2EthPortSwIVlanEntry 705037568}

er1645v2EthPortSwIVlanIpV6RaLinkMtu OBJECT-TYPE
   SYNTAX      Integer32
   MAX-ACCESS  read-write
   STATUS      current
   DESCRIPTION
      "Path: swPort.editConf.vlan.ipV6.ra.linkMtu"
   ::= {er1645v2EthPortSwIVlanEntry 705037824}

er1645v2EthPortSwIVlanIpV6RaReachableTime OBJECT-TYPE
   SYNTAX      TimeTicks
   MAX-ACCESS  read-write
   STATUS      current
   DESCRIPTION
      "Path: swPort.editConf.vlan.ipV6.ra.reachableTime

       Time in centi-second."
   ::= {er1645v2EthPortSwIVlanEntry 705038080}

er1645v2EthPortSwIVlanIpV6RaRetransmitTime OBJECT-TYPE
   SYNTAX      TimeTicks
   MAX-ACCESS  read-write
   STATUS      current
   DESCRIPTION
      "Path: swPort.editConf.vlan.ipV6.ra.retransmitTime

       Time in centi-second."
   ::= {er1645v2EthPortSwIVlanEntry 705038336}

er1645v2EthPortSwIVlanIpV6RaHopLimit OBJECT-TYPE
   SYNTAX      Integer32
   MAX-ACCESS  read-write
   STATUS      current
   DESCRIPTION
      "Path: swPort.editConf.vlan.ipV6.ra.hopLimit"
   ::= {er1645v2EthPortSwIVlanEntry 705038592}

er1645v2EthPortSwIVlanIpV6RaDefaultLifeTime OBJECT-TYPE
   SYNTAX      TimeTicks
   MAX-ACCESS  read-write
   STATUS      current
   DESCRIPTION
      "Path: swPort.editConf.vlan.ipV6.ra.defaultLifeTime

       Time in centi-second."
   ::= {er1645v2EthPortSwIVlanEntry 705038848}

er1645v2EthPortSwIVlanIpV6RaDnsOptionsRdnssLifeTime OBJECT-TYPE
   SYNTAX      TimeTicks
   MAX-ACCESS  read-write
   STATUS      current
   DESCRIPTION
      "Path: swPort.editConf.vlan.ipV6.ra.dnsOptions.rdnss.lifeTime

       Time in centi-second."
   ::= {er1645v2EthPortSwIVlanEntry 705039140}

er1645v2EthPortSwIVlanIpV6RaDnsOptionsRdnssImportServers OBJECT-TYPE
   SYNTAX      INTEGER
               {
               disabled (0),
               enabled (1)
               }
   MAX-ACCESS  read-write
   STATUS      current
   DESCRIPTION
      "Path: swPort.editConf.vlan.ipV6.ra.dnsOptions.rdnss.importServers

       Possibilities:
               disabled   (0)
               enabled   (1)"
   ::= {er1645v2EthPortSwIVlanEntry 705039148}

er1645v2EthPortSwIVlanIpV6RaDnsOptionsDnsslLifeTime OBJECT-TYPE
   SYNTAX      TimeTicks
   MAX-ACCESS  read-write
   STATUS      current
   DESCRIPTION
      "Path: swPort.editConf.vlan.ipV6.ra.dnsOptions.dnssl.lifeTime

       Time in centi-second."
   ::= {er1645v2EthPortSwIVlanEntry 705039172}

er1645v2EthPortSwIVlanIpV6RaDnsOptionsDnsslImportDomains OBJECT-TYPE
   SYNTAX      INTEGER
               {
               disabled (0),
               enabled (1)
               }
   MAX-ACCESS  read-write
   STATUS      current
   DESCRIPTION
      "Path: swPort.editConf.vlan.ipV6.ra.dnsOptions.dnssl.importDomains

       Possibilities:
               disabled   (0)
               enabled   (1)"
   ::= {er1645v2EthPortSwIVlanEntry 705039180}

er1645v2EthPortSwIVlanIpV6RsSend OBJECT-TYPE
   SYNTAX      INTEGER
               {
               disabled (0),
               enabled (1)
               }
   MAX-ACCESS  read-write
   STATUS      current
   DESCRIPTION
      "Path: swPort.editConf.vlan.ipV6.rs.send

       Possibilities:
               disabled   (0)
               enabled   (1)"
   ::= {er1645v2EthPortSwIVlanEntry 705954048}

er1645v2EthPortSwIVlanIpV6RsMaxRandomDelay OBJECT-TYPE
   SYNTAX      TimeTicks
   MAX-ACCESS  read-write
   STATUS      current
   DESCRIPTION
      "Path: swPort.editConf.vlan.ipV6.rs.maxRandomDelay

       Time in centi-second."
   ::= {er1645v2EthPortSwIVlanEntry 705954304}

er1645v2EthPortSwIVlanIpV6RsInterval OBJECT-TYPE
   SYNTAX      TimeTicks
   MAX-ACCESS  read-write
   STATUS      current
   DESCRIPTION
      "Path: swPort.editConf.vlan.ipV6.rs.interval

       Time in centi-second."
   ::= {er1645v2EthPortSwIVlanEntry 705954560}

er1645v2EthPortSwIVlanIpV6RsMaxSolicitations OBJECT-TYPE
   SYNTAX      Integer32
   MAX-ACCESS  read-write
   STATUS      current
   DESCRIPTION
      "Path: swPort.editConf.vlan.ipV6.rs.maxSolicitations"
   ::= {er1645v2EthPortSwIVlanEntry 705954816}

er1645v2EthPortSwIVlanIpV6TrafficPolicyInbound OBJECT-TYPE
   SYNTAX      DisplayString
   MAX-ACCESS  read-write
   STATUS      current
   DESCRIPTION
      "Path: swPort.editConf.vlan.ipV6.trafficPolicy.inbound"
   ::= {er1645v2EthPortSwIVlanEntry 705364224}

er1645v2EthPortSwIVlanIpV6TrafficPolicyOutbound OBJECT-TYPE
   SYNTAX      DisplayString
   MAX-ACCESS  read-write
   STATUS      current
   DESCRIPTION
      "Path: swPort.editConf.vlan.ipV6.trafficPolicy.outbound"
   ::= {er1645v2EthPortSwIVlanEntry 705364480}

er1645v2EthPortSwIVlanIpV6FirewallZone OBJECT-TYPE
   SYNTAX      DisplayString
   MAX-ACCESS  read-write
   STATUS      current
   DESCRIPTION
      "Path: swPort.editConf.vlan.ipV6.firewall.zone"
   ::= {er1645v2EthPortSwIVlanEntry 705429760}

er1645v2EthPortSwIVlanIpV6DhcpClientAddrAC OBJECT-TYPE
   SYNTAX      INTEGER
               {
               disabled (0),
               enabled (1)
               }
   MAX-ACCESS  read-write
   STATUS      current
   DESCRIPTION
      "Path: swPort.editConf.vlan.ipV6.dhcp.client.addrAutoConfig

       Possibilities:
               disabled   (0)
               enabled   (1)"
   ::= {er1645v2EthPortSwIVlanEntry 705307648}

er1645v2EthPortSwIVlanIpV6DhcpClientPrDelMode OBJECT-TYPE
   SYNTAX      INTEGER
               {
               disabled (0),
               enabled (1)
               }
   MAX-ACCESS  read-write
   STATUS      current
   DESCRIPTION
      "Path: swPort.editConf.vlan.ipV6.dhcp.client.pd.mode

       Possibilities:
               disabled   (0)
               enabled   (1)"
   ::= {er1645v2EthPortSwIVlanEntry 705308676}

er1645v2EthPortSwIVlanIpV6DhcpClientPrDelPool OBJECT-TYPE
   SYNTAX      DisplayString
   MAX-ACCESS  read-write
   STATUS      current
   DESCRIPTION
      "Path: swPort.editConf.vlan.ipV6.dhcp.client.pd.pool"
   ::= {er1645v2EthPortSwIVlanEntry 705308680}

er1645v2EthPortSwIVlanIpV6DhcpClientPrDelPdExclOpt OBJECT-TYPE
   SYNTAX      INTEGER
               {
               disabled (0),
               enabled (1)
               }
   MAX-ACCESS  read-write
   STATUS      current
   DESCRIPTION
      "Path: swPort.editConf.vlan.ipV6.dhcp.client.pd.pdExclOpt

       Possibilities:
               disabled   (0)
               enabled   (1)"
   ::= {er1645v2EthPortSwIVlanEntry 705308684}

er1645v2EthPortSwIVlanIpV6DhcpClientDnsServerPref OBJECT-TYPE
   SYNTAX      Integer32
   MAX-ACCESS  read-write
   STATUS      current
   DESCRIPTION
      "Path: swPort.editConf.vlan.ipV6.dhcp.client.dns.serverPref"
   ::= {er1645v2EthPortSwIVlanEntry 705310724}

er1645v2EthPortSwIVlanIpV6DhcpClientRapidCommit OBJECT-TYPE
   SYNTAX      INTEGER
               {
               disabled (0),
               enabled (1)
               }
   MAX-ACCESS  read-write
   STATUS      current
   DESCRIPTION
      "Path: swPort.editConf.vlan.ipV6.dhcp.client.rapidCommit

       Possibilities:
               disabled   (0)
               enabled   (1)"
   ::= {er1645v2EthPortSwIVlanEntry 705309696}

er1645v2EthPortSwIVlanIpV6DhcpClientTimersSolTimeOut OBJECT-TYPE
   SYNTAX      TimeTicks
   MAX-ACCESS  read-write
   STATUS      current
   DESCRIPTION
      "Path: swPort.editConf.vlan.ipV6.dhcp.client.timers.solTimeOut

       Time in centi-second."
   ::= {er1645v2EthPortSwIVlanEntry 705311748}

er1645v2EthPortSwIVlanIpV6DhcpClientTimersSolMaxRt OBJECT-TYPE
   SYNTAX      TimeTicks
   MAX-ACCESS  read-write
   STATUS      current
   DESCRIPTION
      "Path: swPort.editConf.vlan.ipV6.dhcp.client.timers.solMaxRt

       Time in centi-second."
   ::= {er1645v2EthPortSwIVlanEntry 705311752}

er1645v2EthPortSwIVlanIpV6DhcpClientTimersInfoRefresh OBJECT-TYPE
   SYNTAX      TimeTicks
   MAX-ACCESS  read-write
   STATUS      current
   DESCRIPTION
      "Path: swPort.editConf.vlan.ipV6.dhcp.client.timers.infoRefresh

       Time in centi-second."
   ::= {er1645v2EthPortSwIVlanEntry 705311756}

er1645v2EthPortSwIVlanIpV6DhcpServerMode OBJECT-TYPE
   SYNTAX      INTEGER
               {
               disabled (0),
               enabled (1)
               }
   MAX-ACCESS  read-write
   STATUS      current
   DESCRIPTION
      "Path: swPort.editConf.vlan.ipV6.dhcp.server.mode

       Possibilities:
               disabled   (0)
               enabled   (1)"
   ::= {er1645v2EthPortSwIVlanEntry 705315840}

er1645v2EthPortSwIVlanIpV6DhcpServerPreference OBJECT-TYPE
   SYNTAX      Integer32
   MAX-ACCESS  read-write
   STATUS      current
   DESCRIPTION
      "Path: swPort.editConf.vlan.ipV6.dhcp.server.preference"
   ::= {er1645v2EthPortSwIVlanEntry 705316864}

er1645v2EthPortSwIVlanIpV6DhcpServerPool OBJECT-TYPE
   SYNTAX      DisplayString
   MAX-ACCESS  read-write
   STATUS      current
   DESCRIPTION
      "Path: swPort.editConf.vlan.ipV6.dhcp.server.pool"
   ::= {er1645v2EthPortSwIVlanEntry 705317888}

er1645v2EthPortSwIVlanIpV6DhcpServerRapidCommit OBJECT-TYPE
   SYNTAX      INTEGER
               {
               disabled (0),
               enabled (1)
               }
   MAX-ACCESS  read-write
   STATUS      current
   DESCRIPTION
      "Path: swPort.editConf.vlan.ipV6.dhcp.server.rapidCommit

       Possibilities:
               disabled   (0)
               enabled   (1)"
   ::= {er1645v2EthPortSwIVlanEntry 705318912}

er1645v2EthPortSwIVlanIpV6DhcpServerTimersInfoRefresh OBJECT-TYPE
   SYNTAX      TimeTicks
   MAX-ACCESS  read-write
   STATUS      current
   DESCRIPTION
      "Path: swPort.editConf.vlan.ipV6.dhcp.server.timers.infoRefresh

       Time in centi-second."
   ::= {er1645v2EthPortSwIVlanEntry 705319940}

er1645v2EthPortSwIVlanIpV6DhcpRelayMode OBJECT-TYPE
   SYNTAX      INTEGER
               {
               disabled (0),
               enabled (1)
               }
   MAX-ACCESS  read-write
   STATUS      current
   DESCRIPTION
      "Path: swPort.editConf.vlan.ipV6.dhcp.relay.mode

       Possibilities:
               disabled   (0)
               enabled   (1)"
   ::= {er1645v2EthPortSwIVlanEntry 705323040}

er1645v2EthPortSwIVlanIpV6SendRedirect OBJECT-TYPE
   SYNTAX      INTEGER
               {
               disabled (0),
               enabled (1)
               }
   MAX-ACCESS  read-write
   STATUS      current
   DESCRIPTION
      "Path: swPort.editConf.vlan.ipV6.sendRedirect

       Possibilities:
               disabled   (0)
               enabled   (1)"
   ::= {er1645v2EthPortSwIVlanEntry 705101824}

er1645v2EthPortSwIVlanIpV6LinkMtu OBJECT-TYPE
   SYNTAX      Integer32
   MAX-ACCESS  read-write
   STATUS      current
   DESCRIPTION
      "Path: swPort.editConf.vlan.ipV6.linkMtu"
   ::= {er1645v2EthPortSwIVlanEntry 705167360}

er1645v2EthPortSwIVlanIpV6InterfaceId OBJECT-TYPE
   SYNTAX      OCTET STRING
   MAX-ACCESS  read-write
   STATUS      current
   DESCRIPTION
      "Path: swPort.editConf.vlan.ipV6.interfaceId"
   ::= {er1645v2EthPortSwIVlanEntry 705232896}

er1645v2EthPortSwIVlanIpV6MF OBJECT-TYPE
   SYNTAX      Integer32
   MAX-ACCESS  read-write
   STATUS      current
   DESCRIPTION
      "Path: swPort.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPortSwIVlanEntry 705757184}

er1645v2EthPortSwIVlanIpV6IcmpMessagesNoRoute OBJECT-TYPE
   SYNTAX      INTEGER
               {
               disabled (0),
               enabled (1)
               }
   MAX-ACCESS  read-write
   STATUS      current
   DESCRIPTION
      "Path: swPort.editConf.vlan.ipV6.icmpMessages.noRoute

       Possibilities:
               disabled   (0)
               enabled   (1)"
   ::= {er1645v2EthPortSwIVlanEntry 705822976}

er1645v2EthPortSwIVlanIpV6IcmpMessagesBeyondScope OBJECT-TYPE
   SYNTAX      INTEGER
               {
               disabled (0),
               enabled (1)
               }
   MAX-ACCESS  read-write
   STATUS      current
   DESCRIPTION
      "Path: swPort.editConf.vlan.ipV6.icmpMessages.beyondScope

       Possibilities:
               disabled   (0)
               enabled   (1)"
   ::= {er1645v2EthPortSwIVlanEntry 705823488}

er1645v2EthPortSwIVlanIpV6IcmpMessagesAddressUnreachable OBJECT-TYPE
   SYNTAX      INTEGER
               {
               disabled (0),
               enabled (1)
               }
   MAX-ACCESS  read-write
   STATUS      current
   DESCRIPTION
      "Path: swPort.editConf.vlan.ipV6.icmpMessages.addressUnreachable

       Possibilities:
               disabled   (0)
               enabled   (1)"
   ::= {er1645v2EthPortSwIVlanEntry 705823744}

er1645v2EthPortSwIVlanIpV6IcmpMessagesPortUnreachable OBJECT-TYPE
   SYNTAX      INTEGER
               {
               disabled (0),
               enabled (1)
               }
   MAX-ACCESS  read-write
   STATUS      current
   DESCRIPTION
      "Path: swPort.editConf.vlan.ipV6.icmpMessages.portUnreachable

       Possibilities:
               disabled   (0)
               enabled   (1)"
   ::= {er1645v2EthPortSwIVlanEntry 705824000}

er1645v2EthPortSwIVlanIpV6IcmpMessagesPacketTooBig OBJECT-TYPE
   SYNTAX      INTEGER
               {
               disabled (0),
               enabled (1)
               }
   MAX-ACCESS  read-write
   STATUS      current
   DESCRIPTION
      "Path: swPort.editConf.vlan.ipV6.icmpMessages.packetTooBig

       Possibilities:
               disabled   (0)
               enabled   (1)"
   ::= {er1645v2EthPortSwIVlanEntry 705825280}

er1645v2EthPortSwIVlanIpV6IcmpMessagesHopLimitExceeded OBJECT-TYPE
   SYNTAX      INTEGER
               {
               disabled (0),
               enabled (1)
               }
   MAX-ACCESS  read-write
   STATUS      current
   DESCRIPTION
      "Path: swPort.editConf.vlan.ipV6.icmpMessages.hopLimitExceeded

       Possibilities:
               disabled   (0)
               enabled   (1)"
   ::= {er1645v2EthPortSwIVlanEntry 705827840}

er1645v2EthPortSwIVlanIpV6IcmpMessagesFragTimeExceeded OBJECT-TYPE
   SYNTAX      INTEGER
               {
               disabled (0),
               enabled (1)
               }
   MAX-ACCESS  read-write
   STATUS      current
   DESCRIPTION
      "Path: swPort.editConf.vlan.ipV6.icmpMessages.fragTimeExceeded

       Possibilities:
               disabled   (0)
               enabled   (1)"
   ::= {er1645v2EthPortSwIVlanEntry 705828096}

er1645v2EthPortSwIVlanIpV6IcmpMessagesHeaderFieldErr OBJECT-TYPE
   SYNTAX      INTEGER
               {
               disabled (0),
               enabled (1)
               }
   MAX-ACCESS  read-write
   STATUS      current
   DESCRIPTION
      "Path: swPort.editConf.vlan.ipV6.icmpMessages.headerFieldErr

       Possibilities:
               disabled   (0)
               enabled   (1)"
   ::= {er1645v2EthPortSwIVlanEntry 705830400}

er1645v2EthPortSwIVlanIpV6IcmpMessagesOptionUnrecognized OBJECT-TYPE
   SYNTAX      INTEGER
               {
               disabled (0),
               enabled (1)
               }
   MAX-ACCESS  read-write
   STATUS      current
   DESCRIPTION
      "Path: swPort.editConf.vlan.ipV6.icmpMessages.optionUnrecognized

       Possibilities:
               disabled   (0)
               enabled   (1)"
   ::= {er1645v2EthPortSwIVlanEntry 705830912}

er1645v2EthPortSwIVlanIpV6IcmpMessagesRedirect OBJECT-TYPE
   SYNTAX      INTEGER
               {
               disabled (0),
               enabled (1)
               }
   MAX-ACCESS  read-write
   STATUS      current
   DESCRIPTION
      "Path: swPort.editConf.vlan.ipV6.icmpMessages.redirect

       Possibilities:
               disabled   (0)
               enabled   (1)"
   ::= {er1645v2EthPortSwIVlanEntry 705832960}

er1645v2EthPortSwIVlanBridgingAccList OBJECT-TYPE
   SYNTAX      DisplayString
   MAX-ACCESS  read-write
   STATUS      current
   DESCRIPTION
      "Path: swPort.editConf.vlan.bridging.accessList"
   ::= {er1645v2EthPortSwIVlanEntry 453246976}

er1645v2EthPortSwIVlanBridgingInACL OBJECT-TYPE
   SYNTAX      DisplayString
   MAX-ACCESS  read-write
   STATUS      current
   DESCRIPTION
      "Path: swPort.editConf.vlan.bridging.inAccessList"
   ::= {er1645v2EthPortSwIVlanEntry 456916992}

er1645v2EthPortSwIVlanBridgingTp OBJECT-TYPE
   SYNTAX      DisplayString
   MAX-ACCESS  read-write
   STATUS      current
   DESCRIPTION
      "Path: swPort.editConf.vlan.bridging.trafficPolicy"
   ::= {er1645v2EthPortSwIVlanEntry 454295552}

er1645v2EthPortSwIVlanBridgingBrGrp OBJECT-TYPE
   SYNTAX      DisplayString
   MAX-ACCESS  read-write
   STATUS      current
   DESCRIPTION
      "Path: swPort.editConf.vlan.bridging.bridgeGroup"
   ::= {er1645v2EthPortSwIVlanEntry 454819840}

er1645v2EthPortSwIVlanBridgingLimBC OBJECT-TYPE
   SYNTAX      INTEGER
               {
               disabled (0),
               enabled (1)
               }
   MAX-ACCESS  read-write
   STATUS      current
   DESCRIPTION
      "Path: swPort.editConf.vlan.bridging.limitBroadcasts

       Possibilities:
               disabled   (0)
               enabled   (1)"
   ::= {er1645v2EthPortSwIVlanEntry 455081984}

er1645v2EthPortSwIVlanBridgingPrivateMode OBJECT-TYPE
   SYNTAX      INTEGER
               {
               disabled (0),
               enabled (1)
               }
   MAX-ACCESS  read-write
   STATUS      current
   DESCRIPTION
      "Path: swPort.editConf.vlan.bridging.privateMode

       Possibilities:
               disabled   (0)
               enabled   (1)"
   ::= {er1645v2EthPortSwIVlanEntry 459538432}

er1645v2EthPortSwIVlanBridgingLearning OBJECT-TYPE
   SYNTAX      INTEGER
               {
               disabled (0),
               enabled (1)
               }
   MAX-ACCESS  read-write
   STATUS      current
   DESCRIPTION
      "Path: swPort.editConf.vlan.bridging.learning

       Possibilities:
               disabled   (0)
               enabled   (1)"
   ::= {er1645v2EthPortSwIVlanEntry 456130560}

er1645v2EthPortSwIVlanBridgingMaxCacheSize OBJECT-TYPE
   SYNTAX      INTEGER
               {
               unlimited (0)
               }
   MAX-ACCESS  read-write
   STATUS      current
   DESCRIPTION
      "Path: swPort.editConf.vlan.bridging.maxCacheSize

       Possibilities:
               unlimited   (0)"
   ::= {er1645v2EthPortSwIVlanEntry 456392704}

er1645v2EthPortSwIVlanBridgingRelearnDropOnRelearn OBJECT-TYPE
   SYNTAX      INTEGER
               {
               disabled (0),
               enabled (1)
               }
   MAX-ACCESS  read-write
   STATUS      current
   DESCRIPTION
      "Path: swPort.editConf.vlan.bridging.relearn.dropOnRelearn

       Possibilities:
               disabled   (0)
               enabled   (1)"
   ::= {er1645v2EthPortSwIVlanEntry 456655872}

er1645v2EthPortSwIVlanBridgingRelearnShutdownThreshold OBJECT-TYPE
   SYNTAX      Integer32
   MAX-ACCESS  read-write
   STATUS      current
   DESCRIPTION
      "Path: swPort.editConf.vlan.bridging.relearn.shutdownThreshold"
   ::= {er1645v2EthPortSwIVlanEntry 456656896}

er1645v2EthPortSwIVlanBridgingRelearnShutdownTime OBJECT-TYPE
   SYNTAX      TimeTicks
   MAX-ACCESS  read-write
   STATUS      current
   DESCRIPTION
      "Path: swPort.editConf.vlan.bridging.relearn.shutdownTime

       Time in centi-second."
   ::= {er1645v2EthPortSwIVlanEntry 456657920}

er1645v2EthPortSwIVlanBridgingRelearnLoopDetection OBJECT-TYPE
   SYNTAX      INTEGER
               {
               disabled (0),
               passive (1),
               active (2)
               }
   MAX-ACCESS  read-write
   STATUS      current
   DESCRIPTION
      "Path: swPort.editConf.vlan.bridging.relearn.loopDetection

       Possibilities:
               disabled   (0)
               passive   (1)
               active   (2)"
   ::= {er1645v2EthPortSwIVlanEntry 456658944}

er1645v2EthPortSwIVlanBridgingRelearnLoopDetectionInterval OBJECT-TYPE
   SYNTAX      TimeTicks
   MAX-ACCESS  read-write
   STATUS      current
   DESCRIPTION
      "Path: swPort.editConf.vlan.bridging.relearn.loopDetectionInterval

       Time in centi-second."
   ::= {er1645v2EthPortSwIVlanEntry 456659968}

er1645v2EthPortSwIVlanBridgingVlanMemberShip OBJECT-TYPE
   SYNTAX      INTEGER
               {
               all (0),
               none (1),
               grouped (2)
               }
   MAX-ACCESS  read-write
   STATUS      current
   DESCRIPTION
      "Path: swPort.editConf.vlan.bridging.vlanMemberShip

       Possibilities:
               all   (0)
               none   (1)
               grouped   (2)"
   ::= {er1645v2EthPortSwIVlanEntry 457965568}

er1645v2EthPortSwIVlanBridgingVlTUntaggedAction OBJECT-TYPE
   SYNTAX      INTEGER
               {
               discard (0),
               accept (1),
               tag (2)
               }
   MAX-ACCESS  read-write
   STATUS      current
   DESCRIPTION
      "Path: swPort.editConf.vlan.bridging.vlanTagging.untagged.action

       Possibilities:
               discard   (0)
               accept   (1)
               tag   (2)"
   ::= {er1645v2EthPortSwIVlanEntry 459055104}

er1645v2EthPortSwIVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.untagged.tagInfo.tpid

       Possibilities:
               dot1Q   (33024)
               dot1ad   (34984)
               0x9100   (37120)
               0x9200   (37376)
               0x9300   (37632)"
   ::= {er1645v2EthPortSwIVlanEntry 459059712}

er1645v2EthPortSwIVlanBridgingVlTUntaggedTagInfoVid OBJECT-TYPE
   SYNTAX      Integer32
   MAX-ACCESS  read-write
   STATUS      current
   DESCRIPTION
      "Path: swPort.editConf.vlan.bridging.vlanTagging.untagged.tagInfo.vid"
   ::= {er1645v2EthPortSwIVlanEntry 459060224}

er1645v2EthPortSwIVlanBridgingVlTUnknownVlansAction OBJECT-TYPE
   SYNTAX      INTEGER
               {
               discard (0),
               accept (1),
               tag (2)
               }
   MAX-ACCESS  read-write
   STATUS      current
   DESCRIPTION
      "Path: swPort.editConf.vlan.bridging.vlanTagging.unknownVlans.action

       Possibilities:
               discard   (0)
               accept   (1)
               tag   (2)"
   ::= {er1645v2EthPortSwIVlanEntry 459120640}

er1645v2EthPortSwIVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.unknownVlans.tagInfo.tpid

       Possibilities:
               dot1Q   (33024)
               dot1ad   (34984)
               0x9100   (37120)
               0x9200   (37376)
               0x9300   (37632)"
   ::= {er1645v2EthPortSwIVlanEntry 459125248}

er1645v2EthPortSwIVlanBridgingVlTUnknownVlansTagInfoVid OBJECT-TYPE
   SYNTAX      Integer32
   MAX-ACCESS  read-write
   STATUS      current
   DESCRIPTION
      "Path: swPort.editConf.vlan.bridging.vlanTagging.unknownVlans.tagInfo.vid"
   ::= {er1645v2EthPortSwIVlanEntry 459125760}

er1645v2EthPortSwIVlanBridgingDot1adType OBJECT-TYPE
   SYNTAX      INTEGER
               {
               slOPTg (0),
               cPort (4),
               sPort (1),
               nni (2)
               }
   MAX-ACCESS  read-write
   STATUS      current
   DESCRIPTION
      "Path: swPort.editConf.vlan.bridging.dot1ad.type

       Possibilities:
               <OPT>   (0)
               cPort   (4)
               sPort   (1)
               nni   (2)"
   ::= {er1645v2EthPortSwIVlanEntry 460850176}

er1645v2EthPortSwIVlanBridgingPriority OBJECT-TYPE
   SYNTAX      Integer32
   MAX-ACCESS  read-write
   STATUS      current
   DESCRIPTION
      "Path: swPort.editConf.vlan.bridging.priority"
   ::= {er1645v2EthPortSwIVlanEntry 453509120}

er1645v2EthPortSwIVlanBridgingPathCost OBJECT-TYPE
   SYNTAX      Integer32
   MAX-ACCESS  read-write
   STATUS      current
   DESCRIPTION
      "Path: swPort.editConf.vlan.bridging.pathCost"
   ::= {er1645v2EthPortSwIVlanEntry 453771264}

er1645v2EthPortSwIVlanBridgingInternalPathCost OBJECT-TYPE
   SYNTAX      Integer32
   MAX-ACCESS  read-write
   STATUS      current
   DESCRIPTION
      "Path: swPort.editConf.vlan.bridging.internalPathCost"
   ::= {er1645v2EthPortSwIVlanEntry 457703424}

er1645v2EthPortSwIVlanBridgingTCD OBJECT-TYPE
   SYNTAX      INTEGER
               {
               disabled (0),
               enabled (1)
               }
   MAX-ACCESS  read-write
   STATUS      current
   DESCRIPTION
      "Path: swPort.editConf.vlan.bridging.topologyChangeDetection

       Possibilities:
               disabled   (0)
               enabled   (1)"
   ::= {er1645v2EthPortSwIVlanEntry 454033408}

er1645v2EthPortSwIVlanBridgingRestrictedRole OBJECT-TYPE
   SYNTAX      INTEGER
               {
               disabled (0),
               enabled (1)
               }
   MAX-ACCESS  read-write
   STATUS      current
   DESCRIPTION
      "Path: swPort.editConf.vlan.bridging.restrictedRole

       Possibilities:
               disabled   (0)
               enabled   (1)"
   ::= {er1645v2EthPortSwIVlanEntry 458227712}

er1645v2EthPortSwIVlanBridgingAdminEdge OBJECT-TYPE
   SYNTAX      INTEGER
               {
               disabled (0),
               enabled (1)
               }
   MAX-ACCESS  read-write
   STATUS      current
   DESCRIPTION
      "Path: swPort.editConf.vlan.bridging.adminEdge

       Possibilities:
               disabled   (0)
               enabled   (1)"
   ::= {er1645v2EthPortSwIVlanEntry 457179136}

er1645v2EthPortSwIVlanBridgingOamMacDeviceMac OBJECT-TYPE
   SYNTAX      DisplayString
   MAX-ACCESS  read-write
   STATUS      current
   DESCRIPTION
      "Path: swPort.editConf.vlan.bridging.ethOam.macAddress.deviceMac"
   ::= {er1645v2EthPortSwIVlanEntry 458506496}

er1645v2EthPortSwIVlanBridgingOamMacUserMac OBJECT-TYPE
   SYNTAX      OCTET STRING
   MAX-ACCESS  read-write
   STATUS      current
   DESCRIPTION
      "Path: swPort.editConf.vlan.bridging.ethOam.macAddress.userMac

       MAC address."
   ::= {er1645v2EthPortSwIVlanEntry 458506368}

er1645v2EthPortSwIVlanBridgingOamMacBridgeMac OBJECT-TYPE
   SYNTAX      DisplayString
   MAX-ACCESS  read-write
   STATUS      current
   DESCRIPTION
      "Path: swPort.editConf.vlan.bridging.ethOam.macAddress.bridgeMac"
   ::= {er1645v2EthPortSwIVlanEntry 458506432}

er1645v2EthPortSwIVlanBridgingMgmtInline OBJECT-TYPE
   SYNTAX      INTEGER
               {
               disabled (0),
               enabled (1)
               }
   MAX-ACCESS  read-write
   STATUS      current
   DESCRIPTION
      "Path: swPort.editConf.vlan.bridging.mgmtInline

       Possibilities:
               disabled   (0)
               enabled   (1)"
   ::= {er1645v2EthPortSwIVlanEntry 458752000}

er1645v2EthPortSwIVlanBridgingL2ptMode OBJECT-TYPE
   SYNTAX      INTEGER
               {
               disabled (0),
               enabled (1)
               }
   MAX-ACCESS  read-write
   STATUS      current
   DESCRIPTION
      "Path: swPort.editConf.vlan.bridging.l2ProtTunnel.mode

       Possibilities:
               disabled   (0)
               enabled   (1)"
   ::= {er1645v2EthPortSwIVlanEntry 459292672}

er1645v2EthPortSwIVlanBridgingL2ptProtocols OBJECT-TYPE
   SYNTAX      Integer32
   MAX-ACCESS  read-write
   STATUS      current
   DESCRIPTION
      "Path: swPort.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2EthPortSwIVlanEntry 459309056}

er1645v2EthPortSwIVlanBridgingL2ptDestMac OBJECT-TYPE
   SYNTAX      OCTET STRING
   MAX-ACCESS  read-write
   STATUS      current
   DESCRIPTION
      "Path: swPort.editConf.vlan.bridging.l2ProtTunnel.destinationMac

       MAC address."
   ::= {er1645v2EthPortSwIVlanEntry 459325440}

er1645v2EthPortSwIVlanBridgingL2ptCos OBJECT-TYPE
   SYNTAX      INTEGER
               {
               unchanged (255)
               }
   MAX-ACCESS  read-write
   STATUS      current
   DESCRIPTION
      "Path: swPort.editConf.vlan.bridging.l2ProtTunnel.cos

       Possibilities:
               unchanged   (255)"
   ::= {er1645v2EthPortSwIVlanEntry 459341824}

er1645v2EthPortSwIVlanBridgingL2ptDropThrStp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.stp

       unit name = packets/sec

       Possibilities:
               unlimited   (0)"
   ::= {er1645v2EthPortSwIVlanEntry 459358272}

er1645v2EthPortSwIVlanBridgingL2ptDropThrLldp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lldp

       unit name = packets/sec

       Possibilities:
               unlimited   (0)"
   ::= {er1645v2EthPortSwIVlanEntry 459358336}

er1645v2EthPortSwIVlanBridgingL2ptDropThrOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.oam

       unit name = packets/sec

       Possibilities:
               unlimited   (0)"
   ::= {er1645v2EthPortSwIVlanEntry 459358400}

er1645v2EthPortSwIVlanBridgingL2ptDropThrCdp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.cdp

       unit name = packets/sec

       Possibilities:
               unlimited   (0)"
   ::= {er1645v2EthPortSwIVlanEntry 459358464}

er1645v2EthPortSwIVlanBridgingL2ptDropThrVtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.vtp

       unit name = packets/sec

       Possibilities:
               unlimited   (0)"
   ::= {er1645v2EthPortSwIVlanEntry 459358528}

er1645v2EthPortSwIVlanBridgingL2ptDropThrLacp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lacp

       unit name = packets/sec

       Possibilities:
               unlimited   (0)"
   ::= {er1645v2EthPortSwIVlanEntry 459358592}

er1645v2EthPortSwIVlanBridgingL2ptDropThrEfmOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.efmOam

       unit name = packets/sec

       Possibilities:
               unlimited   (0)"
   ::= {er1645v2EthPortSwIVlanEntry 459358656}

er1645v2EthPortSwIVlanBridgingL2ptDropThrPvst OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pvst

       unit name = packets/sec

       Possibilities:
               unlimited   (0)"
   ::= {er1645v2EthPortSwIVlanEntry 459358720}

er1645v2EthPortSwIVlanBridgingL2ptDropThrMmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mmrp

       unit name = packets/sec

       Possibilities:
               unlimited   (0)"
   ::= {er1645v2EthPortSwIVlanEntry 459358784}

er1645v2EthPortSwIVlanBridgingL2ptDropThrMvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mvrp

       unit name = packets/sec

       Possibilities:
               unlimited   (0)"
   ::= {er1645v2EthPortSwIVlanEntry 459358848}

er1645v2EthPortSwIVlanBridgingL2ptDropThrGvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gvrp

       unit name = packets/sec

       Possibilities:
               unlimited   (0)"
   ::= {er1645v2EthPortSwIVlanEntry 459358912}

er1645v2EthPortSwIVlanBridgingL2ptDropThrGmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gmrp

       unit name = packets/sec

       Possibilities:
               unlimited   (0)"
   ::= {er1645v2EthPortSwIVlanEntry 459358976}

er1645v2EthPortSwIVlanBridgingL2ptDropThrDtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.dtp

       unit name = packets/sec

       Possibilities:
               unlimited   (0)"
   ::= {er1645v2EthPortSwIVlanEntry 459359040}

er1645v2EthPortSwIVlanBridgingL2ptDropThrPagp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pagp

       unit name = packets/sec

       Possibilities:
               unlimited   (0)"
   ::= {er1645v2EthPortSwIVlanEntry 459359104}

er1645v2EthPortSwIVlanBridgingL2ptDropThrUdld OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.udld

       unit name = packets/sec

       Possibilities:
               unlimited   (0)"
   ::= {er1645v2EthPortSwIVlanEntry 459359168}

er1645v2EthPortSwIVlanVlanVid OBJECT-TYPE
   SYNTAX      INTEGER
               {
               untagged (0),
               prioTagged (4096),
               notUsed (4097)
               }
   MAX-ACCESS  read-write
   STATUS      current
   DESCRIPTION
      "Path: swPort.editConf.vlan.vlan.vid

       Possibilities:
               untagged   (0)
               prioTagged   (4096)
               notUsed   (4097)"
   ::= {er1645v2EthPortSwIVlanEntry 234946560}

er1645v2EthPortSwIVlanVlanVidExtensionSingle OBJECT-TYPE
   SYNTAX      OCTET STRING
   MAX-ACCESS  read-write
   STATUS      current
   DESCRIPTION
      "Path: swPort.editConf.vlan.vlan.vidExtension.single"
   ::= {er1645v2EthPortSwIVlanEntry 235340032}

er1645v2EthPortSwIVlanVlanVidExtensionEndVid OBJECT-TYPE
   SYNTAX      Integer32
   MAX-ACCESS  read-write
   STATUS      current
   DESCRIPTION
      "Path: swPort.editConf.vlan.vlan.vidExtension.endVid"
   ::= {er1645v2EthPortSwIVlanEntry 235340288}

er1645v2EthPortSwIVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tpid

       Possibilities:
               dot1Q   (33024)
               dot1ad   (34984)
               0x9100   (37120)
               0x9200   (37376)
               0x9300   (37632)"
   ::= {er1645v2EthPortSwIVlanEntry 241238016}

er1645v2EthPortSwIVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: swPort.editConf.vlan.vlan.tagSignificance

       Possibilities:
               global   (0)
               local   (1)
               sVlan   (2)
               sVlanGlobal   (6)
               cVlan   (3)
               scVlan   (5)
               cVlanLocal   (4)"
   ::= {er1645v2EthPortSwIVlanEntry 235012096}

er1645v2EthPortSwIVlanVlanChTos OBJECT-TYPE
   SYNTAX      INTEGER
               {
               disabled (0),
               enabled (1)
               }
   MAX-ACCESS  read-write
   STATUS      current
   DESCRIPTION
      "Path: swPort.editConf.vlan.vlan.changeTos

       Possibilities:
               disabled   (0)
               enabled   (1)"
   ::= {er1645v2EthPortSwIVlanEntry 235208704}

er1645v2EthPortSwIVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235143424}

er1645v2EthPortSwIVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235143680}

er1645v2EthPortSwIVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235143936}

er1645v2EthPortSwIVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235144192}

er1645v2EthPortSwIVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235144448}

er1645v2EthPortSwIVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235144704}

er1645v2EthPortSwIVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235144960}

er1645v2EthPortSwIVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPortSwIVlanEntry 235145216}

er1645v2EthPortSwIVlanVlanTxCos OBJECT-TYPE
   SYNTAX      INTEGER
               {
               tosCosMap (8),
               queueCosMap (16)
               }
   MAX-ACCESS  read-write
   STATUS      current
   DESCRIPTION
      "Path: swPort.editConf.vlan.vlan.txCos

       Possibilities:
               tosCosMap   (8)
               queueCosMap   (16)"
   ::= {er1645v2EthPortSwIVlanEntry 235077632}

er1645v2EthPortSwIVlanVlanCCMapP0 OBJECT-TYPE
   SYNTAX      Integer32
   MAX-ACCESS  read-write
   STATUS      current
   DESCRIPTION
      "Path: swPort.editConf.vlan.vlan.cosCosMap.p0"
   ::= {er1645v2EthPortSwIVlanEntry 241303808}

er1645v2EthPortSwIVlanVlanCCMapP1 OBJECT-TYPE
   SYNTAX      Integer32
   MAX-ACCESS  read-write
   STATUS      current
   DESCRIPTION
      "Path: swPort.editConf.vlan.vlan.cosCosMap.p1"
   ::= {er1645v2EthPortSwIVlanEntry 241304064}

er1645v2EthPortSwIVlanVlanCCMapP2 OBJECT-TYPE
   SYNTAX      Integer32
   MAX-ACCESS  read-write
   STATUS      current
   DESCRIPTION
      "Path: swPort.editConf.vlan.vlan.cosCosMap.p2"
   ::= {er1645v2EthPortSwIVlanEntry 241304320}

er1645v2EthPortSwIVlanVlanCCMapP3 OBJECT-TYPE
   SYNTAX      Integer32
   MAX-ACCESS  read-write
   STATUS      current
   DESCRIPTION
      "Path: swPort.editConf.vlan.vlan.cosCosMap.p3"
   ::= {er1645v2EthPortSwIVlanEntry 241304576}

er1645v2EthPortSwIVlanVlanCCMapP4 OBJECT-TYPE
   SYNTAX      Integer32
   MAX-ACCESS  read-write
   STATUS      current
   DESCRIPTION
      "Path: swPort.editConf.vlan.vlan.cosCosMap.p4"
   ::= {er1645v2EthPortSwIVlanEntry 241304832}

er1645v2EthPortSwIVlanVlanCCMapP5 OBJECT-TYPE
   SYNTAX      Integer32
   MAX-ACCESS  read-write
   STATUS      current
   DESCRIPTION
      "Path: swPort.editConf.vlan.vlan.cosCosMap.p5"
   ::= {er1645v2EthPortSwIVlanEntry 241305088}

er1645v2EthPortSwIVlanVlanCCMapP6 OBJECT-TYPE
   SYNTAX      Integer32
   MAX-ACCESS  read-write
   STATUS      current
   DESCRIPTION
      "Path: swPort.editConf.vlan.vlan.cosCosMap.p6"
   ::= {er1645v2EthPortSwIVlanEntry 241305344}

er1645v2EthPortSwIVlanVlanCCMapP7 OBJECT-TYPE
   SYNTAX      Integer32
   MAX-ACCESS  read-write
   STATUS      current
   DESCRIPTION
      "Path: swPort.editConf.vlan.vlan.cosCosMap.p7"
   ::= {er1645v2EthPortSwIVlanEntry 241305600}

er1645v2EthPortSwIVlanVlanQCMapQueue1 OBJECT-TYPE
   SYNTAX      Integer32
   MAX-ACCESS  read-write
   STATUS      current
   DESCRIPTION
      "Path: swPort.editConf.vlan.vlan.queueCosMap.queue1"
   ::= {er1645v2EthPortSwIVlanEntry 241434880}

er1645v2EthPortSwIVlanVlanQCMapQueue2 OBJECT-TYPE
   SYNTAX      Integer32
   MAX-ACCESS  read-write
   STATUS      current
   DESCRIPTION
      "Path: swPort.editConf.vlan.vlan.queueCosMap.queue2"
   ::= {er1645v2EthPortSwIVlanEntry 241435136}

er1645v2EthPortSwIVlanVlanQCMapQueue3 OBJECT-TYPE
   SYNTAX      Integer32
   MAX-ACCESS  read-write
   STATUS      current
   DESCRIPTION
      "Path: swPort.editConf.vlan.vlan.queueCosMap.queue3"
   ::= {er1645v2EthPortSwIVlanEntry 241435392}

er1645v2EthPortSwIVlanVlanQCMapQueue4 OBJECT-TYPE
   SYNTAX      Integer32
   MAX-ACCESS  read-write
   STATUS      current
   DESCRIPTION
      "Path: swPort.editConf.vlan.vlan.queueCosMap.queue4"
   ::= {er1645v2EthPortSwIVlanEntry 241435648}

er1645v2EthPortSwIVlanVlanQCMapQueue5 OBJECT-TYPE
   SYNTAX      Integer32
   MAX-ACCESS  read-write
   STATUS      current
   DESCRIPTION
      "Path: swPort.editConf.vlan.vlan.queueCosMap.queue5"
   ::= {er1645v2EthPortSwIVlanEntry 241435904}

er1645v2EthPortSwIVlanVlanQCMapLowDelayQueue OBJECT-TYPE
   SYNTAX      Integer32
   MAX-ACCESS  read-write
   STATUS      current
   DESCRIPTION
      "Path: swPort.editConf.vlan.vlan.queueCosMap.lowDelayQueue"
   ::= {er1645v2EthPortSwIVlanEntry 241436160}

er1645v2EthPortSwIVlanVlanQCMapLowDelay2Queue OBJECT-TYPE
   SYNTAX      Integer32
   MAX-ACCESS  read-write
   STATUS      current
   DESCRIPTION
      "Path: swPort.editConf.vlan.vlan.queueCosMap.lowDelay2Queue"
   ::= {er1645v2EthPortSwIVlanEntry 241436416}

er1645v2EthPortSwIVlanVlanQCMapSystemQueue OBJECT-TYPE
   SYNTAX      Integer32
   MAX-ACCESS  read-write
   STATUS      current
   DESCRIPTION
      "Path: swPort.editConf.vlan.vlan.queueCosMap.systemQueue"
   ::= {er1645v2EthPortSwIVlanEntry 241436672}

er1645v2EthPortSwIVlanVlanQinQSVid OBJECT-TYPE
   SYNTAX      Integer32
   MAX-ACCESS  read-write
   STATUS      current
   DESCRIPTION
      "Path: swPort.editConf.vlan.vlan.tunnel.sVid"
   ::= {er1645v2EthPortSwIVlanEntry 241172736}

er1645v2EthPortSwIVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tunnel.sTpid

       Possibilities:
               dot1Q   (33024)
               dot1ad   (34984)
               0x9100   (37120)
               0x9200   (37376)
               0x9300   (37632)"
   ::= {er1645v2EthPortSwIVlanEntry 241172992}

er1645v2EthPortSwIVlanVlanArpTimeOut OBJECT-TYPE
   SYNTAX      TimeTicks
   MAX-ACCESS  read-write
   STATUS      current
   DESCRIPTION
      "Path: swPort.editConf.vlan.vlan.arp.timeOut

       Time in centi-second."
   ::= {er1645v2EthPortSwIVlanEntry 235277312}

er1645v2EthPortSwIVlanVlanArpProxyArp OBJECT-TYPE
   SYNTAX      INTEGER
               {
               disabled (0),
               enabled (1)
               }
   MAX-ACCESS  read-write
   STATUS      current
   DESCRIPTION
      "Path: swPort.editConf.vlan.vlan.arp.proxyArp

       Possibilities:
               disabled   (0)
               enabled   (1)"
   ::= {er1645v2EthPortSwIVlanEntry 235287040}

er1645v2EthPortSwIVlanBandwidthMode OBJECT-TYPE
   SYNTAX      INTEGER
               {
               reshaping (1),
               policing (2),
               policingReshape (3)
               }
   MAX-ACCESS  read-write
   STATUS      current
   DESCRIPTION
      "Path: swPort.editConf.vlan.bandwidth.mode

       Possibilities:
               reshaping   (1)
               policing   (2)
               policingReshape   (3)"
   ::= {er1645v2EthPortSwIVlanEntry 148897792}

er1645v2EthPortSwIVlanBandwidthCir OBJECT-TYPE
   SYNTAX      Integer32
   MAX-ACCESS  read-write
   STATUS      current
   DESCRIPTION
      "Path: swPort.editConf.vlan.bandwidth.cir"
   ::= {er1645v2EthPortSwIVlanEntry 135266304}

er1645v2EthPortSwIVlanBandwidthEir OBJECT-TYPE
   SYNTAX      Integer32
   MAX-ACCESS  read-write
   STATUS      current
   DESCRIPTION
      "Path: swPort.editConf.vlan.bandwidth.eir"
   ::= {er1645v2EthPortSwIVlanEntry 141557760}

er1645v2EthPortSwIVlanBandwidthUnit OBJECT-TYPE
   SYNTAX      INTEGER
               {
               bitssec (1),
               percent (2)
               }
   MAX-ACCESS  read-write
   STATUS      current
   DESCRIPTION
      "Path: swPort.editConf.vlan.bandwidth.unit

       Possibilities:
               bits/sec   (1)
               percent   (2)"
   ::= {er1645v2EthPortSwIVlanEntry 139460608}

er1645v2EthPortSwIVlanBandwidthTc OBJECT-TYPE
   SYNTAX      INTEGER
               {
               auto (0)
               }
   MAX-ACCESS  read-write
   STATUS      current
   DESCRIPTION
      "Path: swPort.editConf.vlan.bandwidth.tc

       Possibilities:
               auto   (0)"
   ::= {er1645v2EthPortSwIVlanEntry 140509184}

er1645v2EthPortSwIVlanBandwidthTcFactor OBJECT-TYPE
   SYNTAX      INTEGER
               {
               ms (10),
               s100us (1)
               }
   MAX-ACCESS  read-write
   STATUS      current
   DESCRIPTION
      "Path: swPort.editConf.vlan.bandwidth.tcFactor

       Possibilities:
               ms   (10)
               *100us   (1)"
   ::= {er1645v2EthPortSwIVlanEntry 142606336}

er1645v2EthPortSwIVlanBandwidthCorrType OBJECT-TYPE
   SYNTAX      INTEGER
               {
               noCorrection (0),
               predefined (1),
               manual (2)
               }
   MAX-ACCESS  read-write
   STATUS      current
   DESCRIPTION
      "Path: swPort.editConf.vlan.bandwidth.correction.type

       Possibilities:
               noCorrection   (0)
               predefined   (1)
               manual   (2)"
   ::= {er1645v2EthPortSwIVlanEntry 136445952}

er1645v2EthPortSwIVlanBandwidthCorrPredefEncapsFrameRelay OBJECT-TYPE
   SYNTAX      DisplayString
   MAX-ACCESS  read-write
   STATUS      current
   DESCRIPTION
      "Path: swPort.editConf.vlan.bandwidth.correction.predefined.encapsulation.frameRelay"
   ::= {er1645v2EthPortSwIVlanEntry 136594432}

er1645v2EthPortSwIVlanBandwidthCorrPredefEncapsPpp OBJECT-TYPE
   SYNTAX      DisplayString
   MAX-ACCESS  read-write
   STATUS      current
   DESCRIPTION
      "Path: swPort.editConf.vlan.bandwidth.correction.predefined.encapsulation.ppp"
   ::= {er1645v2EthPortSwIVlanEntry 136595456}

er1645v2EthPortSwIVlanBandwidthCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.bandwidth.correction.predefined.encapsulation.atm.higherLayer

       Possibilities:
               rfc2684   (0)
               ppp   (1)
               pppOverEthernet   (2)"
   ::= {er1645v2EthPortSwIVlanEntry 136596608}

er1645v2EthPortSwIVlanBandwidthCorrPredefEncapsAtmMp OBJECT-TYPE
   SYNTAX      INTEGER
               {
               llcEncapsulation (0),
               vcMultiplexing (1)
               }
   MAX-ACCESS  read-write
   STATUS      current
   DESCRIPTION
      "Path: swPort.editConf.vlan.bandwidth.correction.predefined.encapsulation.atm.multiProtocol

       Possibilities:
               llcEncapsulation   (0)
               vcMultiplexing   (1)"
   ::= {er1645v2EthPortSwIVlanEntry 136596736}

er1645v2EthPortSwIVlanBandwidthCorrPredefEncapsHdlc OBJECT-TYPE
   SYNTAX      DisplayString
   MAX-ACCESS  read-write
   STATUS      current
   DESCRIPTION
      "Path: swPort.editConf.vlan.bandwidth.correction.predefined.encapsulation.hdlc"
   ::= {er1645v2EthPortSwIVlanEntry 136597504}

er1645v2EthPortSwIVlanBandwidthCorrPredefEncapsEfmFs OBJECT-TYPE
   SYNTAX      Integer32
   MAX-ACCESS  read-write
   STATUS      current
   DESCRIPTION
      "Path: swPort.editConf.vlan.bandwidth.correction.predefined.encapsulation.efm.fragmentSize"
   ::= {er1645v2EthPortSwIVlanEntry 136598656}

er1645v2EthPortSwIVlanBandwidthCorrPredefEncapsEfmIb OBJECT-TYPE
   SYNTAX      Integer32
   MAX-ACCESS  read-write
   STATUS      current
   DESCRIPTION
      "Path: swPort.editConf.vlan.bandwidth.correction.predefined.encapsulation.efm.idleBytes"
   ::= {er1645v2EthPortSwIVlanEntry 136598784}

er1645v2EthPortSwIVlanBandwidthCorrPredefMode OBJECT-TYPE
   SYNTAX      INTEGER
               {
               routing (0),
               bridging (1)
               }
   MAX-ACCESS  read-write
   STATUS      current
   DESCRIPTION
      "Path: swPort.editConf.vlan.bandwidth.correction.predefined.mode

       Possibilities:
               routing   (0)
               bridging   (1)"
   ::= {er1645v2EthPortSwIVlanEntry 136609792}

er1645v2EthPortSwIVlanBandwidthCorrManualOverhead OBJECT-TYPE
   SYNTAX      Integer32
   MAX-ACCESS  read-write
   STATUS      current
   DESCRIPTION
      "Path: swPort.editConf.vlan.bandwidth.correction.manual.overhead"
   ::= {er1645v2EthPortSwIVlanEntry 136708608}

er1645v2EthPortSwIVlanBandwidthCorrManualFrameData OBJECT-TYPE
   SYNTAX      Counter32
   MAX-ACCESS  read-write
   STATUS      current
   DESCRIPTION
      "Path: swPort.editConf.vlan.bandwidth.correction.manual.frameData

       32 bit unsigned wrappable counter."
   ::= {er1645v2EthPortSwIVlanEntry 136709120}

er1645v2EthPortSwIVlanBandwidthCorrManualFrameHeader OBJECT-TYPE
   SYNTAX      Counter32
   MAX-ACCESS  read-write
   STATUS      current
   DESCRIPTION
      "Path: swPort.editConf.vlan.bandwidth.correction.manual.frameHeader

       32 bit unsigned wrappable counter."
   ::= {er1645v2EthPortSwIVlanEntry 136709632}

er1645v2EthPortSwIVlanBandwidthMaxFifoQLen OBJECT-TYPE
   SYNTAX      Integer32
   MAX-ACCESS  read-write
   STATUS      current
   DESCRIPTION
      "Path: swPort.editConf.vlan.bandwidth.maxFifoQLen"
   ::= {er1645v2EthPortSwIVlanEntry 137363456}

er1645v2EthPortSwIVlanBandwidthDeFlagCir OBJECT-TYPE
   SYNTAX      INTEGER
               {
               allowed (1),
               notAllowed (2)
               }
   MAX-ACCESS  read-write
   STATUS      current
   DESCRIPTION
      "Path: swPort.editConf.vlan.bandwidth.deFlag.cir

       Possibilities:
               allowed   (1)
               notAllowed   (2)"
   ::= {er1645v2EthPortSwIVlanEntry 147853312}

er1645v2EthPortSwIVlanBandwidthDeFlagEir OBJECT-TYPE
   SYNTAX      INTEGER
               {
               allowed (1),
               notAllowed (2)
               }
   MAX-ACCESS  read-write
   STATUS      current
   DESCRIPTION
      "Path: swPort.editConf.vlan.bandwidth.deFlag.eir

       Possibilities:
               allowed   (1)
               notAllowed   (2)"
   ::= {er1645v2EthPortSwIVlanEntry 147857408}

er1645v2EthPortSwIVlanBandwidthDeFlagViolate OBJECT-TYPE
   SYNTAX      INTEGER
               {
               allowed (1),
               notAllowed (2)
               }
   MAX-ACCESS  read-write
   STATUS      current
   DESCRIPTION
      "Path: swPort.editConf.vlan.bandwidth.deFlag.violate

       Possibilities:
               allowed   (1)
               notAllowed   (2)"
   ::= {er1645v2EthPortSwIVlanEntry 147861504}

er1645v2EthPortSwIVlanBandwidthActCirActNone OBJECT-TYPE
   SYNTAX      OCTET STRING
   MAX-ACCESS  read-write
   STATUS      current
   DESCRIPTION
      "Path: swPort.editConf.vlan.bandwidth.action.cirAction.none"
   ::= {er1645v2EthPortSwIVlanEntry 150085632}

er1645v2EthPortSwIVlanBandwidthActCirActEthCos1 OBJECT-TYPE
   SYNTAX      INTEGER
               {
               unchanged (256)
               }
   MAX-ACCESS  read-write
   STATUS      current
   DESCRIPTION
      "Path: swPort.editConf.vlan.bandwidth.action.cirAction.ethernet.cosDepth1

       Possibilities:
               unchanged   (256)"
   ::= {er1645v2EthPortSwIVlanEntry 150094080}

er1645v2EthPortSwIVlanBandwidthActCirActEthDei1 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth1

       Possibilities:
               unchanged   (255)
               clear   (0)
               set   (1)"
   ::= {er1645v2EthPortSwIVlanEntry 150099200}

er1645v2EthPortSwIVlanBandwidthActCirActEthCos2 OBJECT-TYPE
   SYNTAX      INTEGER
               {
               unchanged (256)
               }
   MAX-ACCESS  read-write
   STATUS      current
   DESCRIPTION
      "Path: swPort.editConf.vlan.bandwidth.action.cirAction.ethernet.cosDepth2

       Possibilities:
               unchanged   (256)"
   ::= {er1645v2EthPortSwIVlanEntry 150094336}

er1645v2EthPortSwIVlanBandwidthActCirActEthDei2 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth2

       Possibilities:
               unchanged   (255)
               clear   (0)
               set   (1)"
   ::= {er1645v2EthPortSwIVlanEntry 150099456}

er1645v2EthPortSwIVlanBandwidthActCirActEthCos3 OBJECT-TYPE
   SYNTAX      INTEGER
               {
               unchanged (256)
               }
   MAX-ACCESS  read-write
   STATUS      current
   DESCRIPTION
      "Path: swPort.editConf.vlan.bandwidth.action.cirAction.ethernet.cosDepth3

       Possibilities:
               unchanged   (256)"
   ::= {er1645v2EthPortSwIVlanEntry 150094592}

er1645v2EthPortSwIVlanBandwidthActCirActEthDei3 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth3

       Possibilities:
               unchanged   (255)
               clear   (0)
               set   (1)"
   ::= {er1645v2EthPortSwIVlanEntry 150099712}

er1645v2EthPortSwIVlanBandwidthActCirActEthCos4 OBJECT-TYPE
   SYNTAX      INTEGER
               {
               unchanged (256)
               }
   MAX-ACCESS  read-write
   STATUS      current
   DESCRIPTION
      "Path: swPort.editConf.vlan.bandwidth.action.cirAction.ethernet.cosDepth4

       Possibilities:
               unchanged   (256)"
   ::= {er1645v2EthPortSwIVlanEntry 150094848}

er1645v2EthPortSwIVlanBandwidthActCirActEthDei4 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth4

       Possibilities:
               unchanged   (255)
               clear   (0)
               set   (1)"
   ::= {er1645v2EthPortSwIVlanEntry 150099968}

er1645v2EthPortSwIVlanBandwidthActCirActEthCos5 OBJECT-TYPE
   SYNTAX      INTEGER
               {
               unchanged (256)
               }
   MAX-ACCESS  read-write
   STATUS      current
   DESCRIPTION
      "Path: swPort.editConf.vlan.bandwidth.action.cirAction.ethernet.cosDepth5

       Possibilities:
               unchanged   (256)"
   ::= {er1645v2EthPortSwIVlanEntry 150095104}

er1645v2EthPortSwIVlanBandwidthActCirActEthDei5 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth5

       Possibilities:
               unchanged   (255)
               clear   (0)
               set   (1)"
   ::= {er1645v2EthPortSwIVlanEntry 150100224}

er1645v2EthPortSwIVlanBandwidthActCirActEthCos6 OBJECT-TYPE
   SYNTAX      INTEGER
               {
               unchanged (256)
               }
   MAX-ACCESS  read-write
   STATUS      current
   DESCRIPTION
      "Path: swPort.editConf.vlan.bandwidth.action.cirAction.ethernet.cosDepth6

       Possibilities:
               unchanged   (256)"
   ::= {er1645v2EthPortSwIVlanEntry 150095360}

er1645v2EthPortSwIVlanBandwidthActCirActEthDei6 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth6

       Possibilities:
               unchanged   (255)
               clear   (0)
               set   (1)"
   ::= {er1645v2EthPortSwIVlanEntry 150100480}

er1645v2EthPortSwIVlanBandwidthActCirActEthCos7 OBJECT-TYPE
   SYNTAX      INTEGER
               {
               unchanged (256)
               }
   MAX-ACCESS  read-write
   STATUS      current
   DESCRIPTION
      "Path: swPort.editConf.vlan.bandwidth.action.cirAction.ethernet.cosDepth7

       Possibilities:
               unchanged   (256)"
   ::= {er1645v2EthPortSwIVlanEntry 150095616}

er1645v2EthPortSwIVlanBandwidthActCirActEthDei7 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth7

       Possibilities:
               unchanged   (255)
               clear   (0)
               set   (1)"
   ::= {er1645v2EthPortSwIVlanEntry 150100736}

er1645v2EthPortSwIVlanBandwidthActCirActEthCos8 OBJECT-TYPE
   SYNTAX      INTEGER
               {
               unchanged (256)
               }
   MAX-ACCESS  read-write
   STATUS      current
   DESCRIPTION
      "Path: swPort.editConf.vlan.bandwidth.action.cirAction.ethernet.cosDepth8

       Possibilities:
               unchanged   (256)"
   ::= {er1645v2EthPortSwIVlanEntry 150095872}

er1645v2EthPortSwIVlanBandwidthActCirActEthDei8 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth8

       Possibilities:
               unchanged   (255)
               clear   (0)
               set   (1)"
   ::= {er1645v2EthPortSwIVlanEntry 150100992}

er1645v2EthPortSwIVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150096128}

er1645v2EthPortSwIVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150096384}

er1645v2EthPortSwIVlanBandwidthActCirActEthDrpLev OBJECT-TYPE
   SYNTAX      INTEGER
               {
               unchanged (0)
               }
   MAX-ACCESS  read-write
   STATUS      current
   DESCRIPTION
      "Path: swPort.editConf.vlan.bandwidth.action.cirAction.ethernet.dropLevel

       Possibilities:
               unchanged   (0)"
   ::= {er1645v2EthPortSwIVlanEntry 150096640}

er1645v2EthPortSwIVlanBandwidthActCirActEthDeFlag OBJECT-TYPE
   SYNTAX      INTEGER
               {
               unchanged (255),
               clear (0),
               set (1)
               }
   MAX-ACCESS  read-write
   STATUS      current
   DESCRIPTION
      "Path: swPort.editConf.vlan.bandwidth.action.cirAction.ethernet.deFlag

       Possibilities:
               unchanged   (255)
               clear   (0)
               set   (1)"
   ::= {er1645v2EthPortSwIVlanEntry 150097408}

er1645v2EthPortSwIVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150120704}

er1645v2EthPortSwIVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150120960}

er1645v2EthPortSwIVlanBandwidthActCirActIpDrpLev OBJECT-TYPE
   SYNTAX      INTEGER
               {
               unchanged (0)
               }
   MAX-ACCESS  read-write
   STATUS      current
   DESCRIPTION
      "Path: swPort.editConf.vlan.bandwidth.action.cirAction.ip.dropLevel

       Possibilities:
               unchanged   (0)"
   ::= {er1645v2EthPortSwIVlanEntry 150121216}

er1645v2EthPortSwIVlanBandwidthActCirActIpDeFlag OBJECT-TYPE
   SYNTAX      INTEGER
               {
               unchanged (255),
               clear (0),
               set (1)
               }
   MAX-ACCESS  read-write
   STATUS      current
   DESCRIPTION
      "Path: swPort.editConf.vlan.bandwidth.action.cirAction.ip.deFlag

       Possibilities:
               unchanged   (255)
               clear   (0)
               set   (1)"
   ::= {er1645v2EthPortSwIVlanEntry 150121984}

er1645v2EthPortSwIVlanBandwidthActEirActNone OBJECT-TYPE
   SYNTAX      OCTET STRING
   MAX-ACCESS  read-write
   STATUS      current
   DESCRIPTION
      "Path: swPort.editConf.vlan.bandwidth.action.eirAction.none"
   ::= {er1645v2EthPortSwIVlanEntry 150216704}

er1645v2EthPortSwIVlanBandwidthActEirActEthCos1 OBJECT-TYPE
   SYNTAX      INTEGER
               {
               unchanged (256)
               }
   MAX-ACCESS  read-write
   STATUS      current
   DESCRIPTION
      "Path: swPort.editConf.vlan.bandwidth.action.eirAction.ethernet.cosDepth1

       Possibilities:
               unchanged   (256)"
   ::= {er1645v2EthPortSwIVlanEntry 150225152}

er1645v2EthPortSwIVlanBandwidthActEirActEthDei1 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth1

       Possibilities:
               unchanged   (255)
               clear   (0)
               set   (1)"
   ::= {er1645v2EthPortSwIVlanEntry 150230272}

er1645v2EthPortSwIVlanBandwidthActEirActEthCos2 OBJECT-TYPE
   SYNTAX      INTEGER
               {
               unchanged (256)
               }
   MAX-ACCESS  read-write
   STATUS      current
   DESCRIPTION
      "Path: swPort.editConf.vlan.bandwidth.action.eirAction.ethernet.cosDepth2

       Possibilities:
               unchanged   (256)"
   ::= {er1645v2EthPortSwIVlanEntry 150225408}

er1645v2EthPortSwIVlanBandwidthActEirActEthDei2 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth2

       Possibilities:
               unchanged   (255)
               clear   (0)
               set   (1)"
   ::= {er1645v2EthPortSwIVlanEntry 150230528}

er1645v2EthPortSwIVlanBandwidthActEirActEthCos3 OBJECT-TYPE
   SYNTAX      INTEGER
               {
               unchanged (256)
               }
   MAX-ACCESS  read-write
   STATUS      current
   DESCRIPTION
      "Path: swPort.editConf.vlan.bandwidth.action.eirAction.ethernet.cosDepth3

       Possibilities:
               unchanged   (256)"
   ::= {er1645v2EthPortSwIVlanEntry 150225664}

er1645v2EthPortSwIVlanBandwidthActEirActEthDei3 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth3

       Possibilities:
               unchanged   (255)
               clear   (0)
               set   (1)"
   ::= {er1645v2EthPortSwIVlanEntry 150230784}

er1645v2EthPortSwIVlanBandwidthActEirActEthCos4 OBJECT-TYPE
   SYNTAX      INTEGER
               {
               unchanged (256)
               }
   MAX-ACCESS  read-write
   STATUS      current
   DESCRIPTION
      "Path: swPort.editConf.vlan.bandwidth.action.eirAction.ethernet.cosDepth4

       Possibilities:
               unchanged   (256)"
   ::= {er1645v2EthPortSwIVlanEntry 150225920}

er1645v2EthPortSwIVlanBandwidthActEirActEthDei4 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth4

       Possibilities:
               unchanged   (255)
               clear   (0)
               set   (1)"
   ::= {er1645v2EthPortSwIVlanEntry 150231040}

er1645v2EthPortSwIVlanBandwidthActEirActEthCos5 OBJECT-TYPE
   SYNTAX      INTEGER
               {
               unchanged (256)
               }
   MAX-ACCESS  read-write
   STATUS      current
   DESCRIPTION
      "Path: swPort.editConf.vlan.bandwidth.action.eirAction.ethernet.cosDepth5

       Possibilities:
               unchanged   (256)"
   ::= {er1645v2EthPortSwIVlanEntry 150226176}

er1645v2EthPortSwIVlanBandwidthActEirActEthDei5 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth5

       Possibilities:
               unchanged   (255)
               clear   (0)
               set   (1)"
   ::= {er1645v2EthPortSwIVlanEntry 150231296}

er1645v2EthPortSwIVlanBandwidthActEirActEthCos6 OBJECT-TYPE
   SYNTAX      INTEGER
               {
               unchanged (256)
               }
   MAX-ACCESS  read-write
   STATUS      current
   DESCRIPTION
      "Path: swPort.editConf.vlan.bandwidth.action.eirAction.ethernet.cosDepth6

       Possibilities:
               unchanged   (256)"
   ::= {er1645v2EthPortSwIVlanEntry 150226432}

er1645v2EthPortSwIVlanBandwidthActEirActEthDei6 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth6

       Possibilities:
               unchanged   (255)
               clear   (0)
               set   (1)"
   ::= {er1645v2EthPortSwIVlanEntry 150231552}

er1645v2EthPortSwIVlanBandwidthActEirActEthCos7 OBJECT-TYPE
   SYNTAX      INTEGER
               {
               unchanged (256)
               }
   MAX-ACCESS  read-write
   STATUS      current
   DESCRIPTION
      "Path: swPort.editConf.vlan.bandwidth.action.eirAction.ethernet.cosDepth7

       Possibilities:
               unchanged   (256)"
   ::= {er1645v2EthPortSwIVlanEntry 150226688}

er1645v2EthPortSwIVlanBandwidthActEirActEthDei7 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth7

       Possibilities:
               unchanged   (255)
               clear   (0)
               set   (1)"
   ::= {er1645v2EthPortSwIVlanEntry 150231808}

er1645v2EthPortSwIVlanBandwidthActEirActEthCos8 OBJECT-TYPE
   SYNTAX      INTEGER
               {
               unchanged (256)
               }
   MAX-ACCESS  read-write
   STATUS      current
   DESCRIPTION
      "Path: swPort.editConf.vlan.bandwidth.action.eirAction.ethernet.cosDepth8

       Possibilities:
               unchanged   (256)"
   ::= {er1645v2EthPortSwIVlanEntry 150226944}

er1645v2EthPortSwIVlanBandwidthActEirActEthDei8 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth8

       Possibilities:
               unchanged   (255)
               clear   (0)
               set   (1)"
   ::= {er1645v2EthPortSwIVlanEntry 150232064}

er1645v2EthPortSwIVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150227200}

er1645v2EthPortSwIVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150227456}

er1645v2EthPortSwIVlanBandwidthActEirActEthDrpLev OBJECT-TYPE
   SYNTAX      INTEGER
               {
               unchanged (0)
               }
   MAX-ACCESS  read-write
   STATUS      current
   DESCRIPTION
      "Path: swPort.editConf.vlan.bandwidth.action.eirAction.ethernet.dropLevel

       Possibilities:
               unchanged   (0)"
   ::= {er1645v2EthPortSwIVlanEntry 150227712}

er1645v2EthPortSwIVlanBandwidthActEirActEthDeFlag OBJECT-TYPE
   SYNTAX      INTEGER
               {
               unchanged (255),
               clear (0),
               set (1)
               }
   MAX-ACCESS  read-write
   STATUS      current
   DESCRIPTION
      "Path: swPort.editConf.vlan.bandwidth.action.eirAction.ethernet.deFlag

       Possibilities:
               unchanged   (255)
               clear   (0)
               set   (1)"
   ::= {er1645v2EthPortSwIVlanEntry 150228480}

er1645v2EthPortSwIVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150251776}

er1645v2EthPortSwIVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150252032}

er1645v2EthPortSwIVlanBandwidthActEirActIpDrpLev OBJECT-TYPE
   SYNTAX      INTEGER
               {
               unchanged (0)
               }
   MAX-ACCESS  read-write
   STATUS      current
   DESCRIPTION
      "Path: swPort.editConf.vlan.bandwidth.action.eirAction.ip.dropLevel

       Possibilities:
               unchanged   (0)"
   ::= {er1645v2EthPortSwIVlanEntry 150252288}

er1645v2EthPortSwIVlanBandwidthActEirActIpDeFlag OBJECT-TYPE
   SYNTAX      INTEGER
               {
               unchanged (255),
               clear (0),
               set (1)
               }
   MAX-ACCESS  read-write
   STATUS      current
   DESCRIPTION
      "Path: swPort.editConf.vlan.bandwidth.action.eirAction.ip.deFlag

       Possibilities:
               unchanged   (255)
               clear   (0)
               set   (1)"
   ::= {er1645v2EthPortSwIVlanEntry 150253056}

er1645v2EthPortSwIVlanBandwidthActViolActNone OBJECT-TYPE
   SYNTAX      OCTET STRING
   MAX-ACCESS  read-write
   STATUS      current
   DESCRIPTION
      "Path: swPort.editConf.vlan.bandwidth.action.violateAction.none"
   ::= {er1645v2EthPortSwIVlanEntry 150347776}

er1645v2EthPortSwIVlanBandwidthActViolActDrop OBJECT-TYPE
   SYNTAX      OCTET STRING
   MAX-ACCESS  read-write
   STATUS      current
   DESCRIPTION
      "Path: swPort.editConf.vlan.bandwidth.action.violateAction.drop"
   ::= {er1645v2EthPortSwIVlanEntry 150364160}

er1645v2EthPortSwIVlanBandwidthActViolActEthCos1 OBJECT-TYPE
   SYNTAX      INTEGER
               {
               unchanged (256)
               }
   MAX-ACCESS  read-write
   STATUS      current
   DESCRIPTION
      "Path: swPort.editConf.vlan.bandwidth.action.violateAction.ethernet.cosDepth1

       Possibilities:
               unchanged   (256)"
   ::= {er1645v2EthPortSwIVlanEntry 150356224}

er1645v2EthPortSwIVlanBandwidthActViolActEthDei1 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth1

       Possibilities:
               unchanged   (255)
               clear   (0)
               set   (1)"
   ::= {er1645v2EthPortSwIVlanEntry 150361344}

er1645v2EthPortSwIVlanBandwidthActViolActEthCos2 OBJECT-TYPE
   SYNTAX      INTEGER
               {
               unchanged (256)
               }
   MAX-ACCESS  read-write
   STATUS      current
   DESCRIPTION
      "Path: swPort.editConf.vlan.bandwidth.action.violateAction.ethernet.cosDepth2

       Possibilities:
               unchanged   (256)"
   ::= {er1645v2EthPortSwIVlanEntry 150356480}

er1645v2EthPortSwIVlanBandwidthActViolActEthDei2 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth2

       Possibilities:
               unchanged   (255)
               clear   (0)
               set   (1)"
   ::= {er1645v2EthPortSwIVlanEntry 150361600}

er1645v2EthPortSwIVlanBandwidthActViolActEthCos3 OBJECT-TYPE
   SYNTAX      INTEGER
               {
               unchanged (256)
               }
   MAX-ACCESS  read-write
   STATUS      current
   DESCRIPTION
      "Path: swPort.editConf.vlan.bandwidth.action.violateAction.ethernet.cosDepth3

       Possibilities:
               unchanged   (256)"
   ::= {er1645v2EthPortSwIVlanEntry 150356736}

er1645v2EthPortSwIVlanBandwidthActViolActEthDei3 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth3

       Possibilities:
               unchanged   (255)
               clear   (0)
               set   (1)"
   ::= {er1645v2EthPortSwIVlanEntry 150361856}

er1645v2EthPortSwIVlanBandwidthActViolActEthCos4 OBJECT-TYPE
   SYNTAX      INTEGER
               {
               unchanged (256)
               }
   MAX-ACCESS  read-write
   STATUS      current
   DESCRIPTION
      "Path: swPort.editConf.vlan.bandwidth.action.violateAction.ethernet.cosDepth4

       Possibilities:
               unchanged   (256)"
   ::= {er1645v2EthPortSwIVlanEntry 150356992}

er1645v2EthPortSwIVlanBandwidthActViolActEthDei4 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth4

       Possibilities:
               unchanged   (255)
               clear   (0)
               set   (1)"
   ::= {er1645v2EthPortSwIVlanEntry 150362112}

er1645v2EthPortSwIVlanBandwidthActViolActEthCos5 OBJECT-TYPE
   SYNTAX      INTEGER
               {
               unchanged (256)
               }
   MAX-ACCESS  read-write
   STATUS      current
   DESCRIPTION
      "Path: swPort.editConf.vlan.bandwidth.action.violateAction.ethernet.cosDepth5

       Possibilities:
               unchanged   (256)"
   ::= {er1645v2EthPortSwIVlanEntry 150357248}

er1645v2EthPortSwIVlanBandwidthActViolActEthDei5 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth5

       Possibilities:
               unchanged   (255)
               clear   (0)
               set   (1)"
   ::= {er1645v2EthPortSwIVlanEntry 150362368}

er1645v2EthPortSwIVlanBandwidthActViolActEthCos6 OBJECT-TYPE
   SYNTAX      INTEGER
               {
               unchanged (256)
               }
   MAX-ACCESS  read-write
   STATUS      current
   DESCRIPTION
      "Path: swPort.editConf.vlan.bandwidth.action.violateAction.ethernet.cosDepth6

       Possibilities:
               unchanged   (256)"
   ::= {er1645v2EthPortSwIVlanEntry 150357504}

er1645v2EthPortSwIVlanBandwidthActViolActEthDei6 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth6

       Possibilities:
               unchanged   (255)
               clear   (0)
               set   (1)"
   ::= {er1645v2EthPortSwIVlanEntry 150362624}

er1645v2EthPortSwIVlanBandwidthActViolActEthCos7 OBJECT-TYPE
   SYNTAX      INTEGER
               {
               unchanged (256)
               }
   MAX-ACCESS  read-write
   STATUS      current
   DESCRIPTION
      "Path: swPort.editConf.vlan.bandwidth.action.violateAction.ethernet.cosDepth7

       Possibilities:
               unchanged   (256)"
   ::= {er1645v2EthPortSwIVlanEntry 150357760}

er1645v2EthPortSwIVlanBandwidthActViolActEthDei7 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth7

       Possibilities:
               unchanged   (255)
               clear   (0)
               set   (1)"
   ::= {er1645v2EthPortSwIVlanEntry 150362880}

er1645v2EthPortSwIVlanBandwidthActViolActEthCos8 OBJECT-TYPE
   SYNTAX      INTEGER
               {
               unchanged (256)
               }
   MAX-ACCESS  read-write
   STATUS      current
   DESCRIPTION
      "Path: swPort.editConf.vlan.bandwidth.action.violateAction.ethernet.cosDepth8

       Possibilities:
               unchanged   (256)"
   ::= {er1645v2EthPortSwIVlanEntry 150358016}

er1645v2EthPortSwIVlanBandwidthActViolActEthDei8 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth8

       Possibilities:
               unchanged   (255)
               clear   (0)
               set   (1)"
   ::= {er1645v2EthPortSwIVlanEntry 150363136}

er1645v2EthPortSwIVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150358272}

er1645v2EthPortSwIVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150358528}

er1645v2EthPortSwIVlanBandwidthActViolActEthDrpLev OBJECT-TYPE
   SYNTAX      INTEGER
               {
               unchanged (0)
               }
   MAX-ACCESS  read-write
   STATUS      current
   DESCRIPTION
      "Path: swPort.editConf.vlan.bandwidth.action.violateAction.ethernet.dropLevel

       Possibilities:
               unchanged   (0)"
   ::= {er1645v2EthPortSwIVlanEntry 150358784}

er1645v2EthPortSwIVlanBandwidthActViolActEthDeFlag OBJECT-TYPE
   SYNTAX      INTEGER
               {
               unchanged (255),
               clear (0),
               set (1)
               }
   MAX-ACCESS  read-write
   STATUS      current
   DESCRIPTION
      "Path: swPort.editConf.vlan.bandwidth.action.violateAction.ethernet.deFlag

       Possibilities:
               unchanged   (255)
               clear   (0)
               set   (1)"
   ::= {er1645v2EthPortSwIVlanEntry 150359552}

er1645v2EthPortSwIVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 150382848}

er1645v2EthPortSwIVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 150383104}

er1645v2EthPortSwIVlanBandwidthActViolActIpDrpLev OBJECT-TYPE
   SYNTAX      INTEGER
               {
               unchanged (0)
               }
   MAX-ACCESS  read-write
   STATUS      current
   DESCRIPTION
      "Path: swPort.editConf.vlan.bandwidth.action.violateAction.ip.dropLevel

       Possibilities:
               unchanged   (0)"
   ::= {er1645v2EthPortSwIVlanEntry 150383360}

er1645v2EthPortSwIVlanBandwidthActViolActIpDeFlag OBJECT-TYPE
   SYNTAX      INTEGER
               {
               unchanged (255),
               clear (0),
               set (1)
               }
   MAX-ACCESS  read-write
   STATUS      current
   DESCRIPTION
      "Path: swPort.editConf.vlan.bandwidth.action.violateAction.ip.deFlag

       Possibilities:
               unchanged   (255)
               clear   (0)
               set   (1)"
   ::= {er1645v2EthPortSwIVlanEntry 150384128}

er1645v2EthPortSwIVlanInbBwMode OBJECT-TYPE
   SYNTAX      INTEGER
               {
               reshaping (1),
               policing (2)
               }
   MAX-ACCESS  read-write
   STATUS      current
   DESCRIPTION
      "Path: swPort.editConf.vlan.inboundBandwidth.mode

       Possibilities:
               reshaping   (1)
               policing   (2)"
   ::= {er1645v2EthPortSwIVlanEntry 132120576}

er1645v2EthPortSwIVlanInbBwCir OBJECT-TYPE
   SYNTAX      Integer32
   MAX-ACCESS  read-write
   STATUS      current
   DESCRIPTION
      "Path: swPort.editConf.vlan.inboundBandwidth.cir"
   ::= {er1645v2EthPortSwIVlanEntry 118489088}

er1645v2EthPortSwIVlanInbBwEir OBJECT-TYPE
   SYNTAX      Integer32
   MAX-ACCESS  read-write
   STATUS      current
   DESCRIPTION
      "Path: swPort.editConf.vlan.inboundBandwidth.eir"
   ::= {er1645v2EthPortSwIVlanEntry 124780544}

er1645v2EthPortSwIVlanInbBwUnit OBJECT-TYPE
   SYNTAX      INTEGER
               {
               bitssec (1),
               percent (2)
               }
   MAX-ACCESS  read-write
   STATUS      current
   DESCRIPTION
      "Path: swPort.editConf.vlan.inboundBandwidth.unit

       Possibilities:
               bits/sec   (1)
               percent   (2)"
   ::= {er1645v2EthPortSwIVlanEntry 122683392}

er1645v2EthPortSwIVlanInbBwTc OBJECT-TYPE
   SYNTAX      INTEGER
               {
               auto (0)
               }
   MAX-ACCESS  read-write
   STATUS      current
   DESCRIPTION
      "Path: swPort.editConf.vlan.inboundBandwidth.tc

       Possibilities:
               auto   (0)"
   ::= {er1645v2EthPortSwIVlanEntry 123731968}

er1645v2EthPortSwIVlanInbBwTcFactor OBJECT-TYPE
   SYNTAX      INTEGER
               {
               ms (10),
               s100us (1)
               }
   MAX-ACCESS  read-write
   STATUS      current
   DESCRIPTION
      "Path: swPort.editConf.vlan.inboundBandwidth.tcFactor

       Possibilities:
               ms   (10)
               *100us   (1)"
   ::= {er1645v2EthPortSwIVlanEntry 125829120}

er1645v2EthPortSwIVlanInbBwCorrType OBJECT-TYPE
   SYNTAX      INTEGER
               {
               noCorrection (0),
               predefined (1),
               manual (2)
               }
   MAX-ACCESS  read-write
   STATUS      current
   DESCRIPTION
      "Path: swPort.editConf.vlan.inboundBandwidth.correction.type

       Possibilities:
               noCorrection   (0)
               predefined   (1)
               manual   (2)"
   ::= {er1645v2EthPortSwIVlanEntry 119668736}

er1645v2EthPortSwIVlanInbBwCorrPredefEncapsFrameRelay OBJECT-TYPE
   SYNTAX      DisplayString
   MAX-ACCESS  read-write
   STATUS      current
   DESCRIPTION
      "Path: swPort.editConf.vlan.inboundBandwidth.correction.predefined.encapsulation.frameRelay"
   ::= {er1645v2EthPortSwIVlanEntry 119817216}

er1645v2EthPortSwIVlanInbBwCorrPredefEncapsPpp OBJECT-TYPE
   SYNTAX      DisplayString
   MAX-ACCESS  read-write
   STATUS      current
   DESCRIPTION
      "Path: swPort.editConf.vlan.inboundBandwidth.correction.predefined.encapsulation.ppp"
   ::= {er1645v2EthPortSwIVlanEntry 119818240}

er1645v2EthPortSwIVlanInbBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.inboundBandwidth.correction.predefined.encapsulation.atm.higherLayer

       Possibilities:
               rfc2684   (0)
               ppp   (1)
               pppOverEthernet   (2)"
   ::= {er1645v2EthPortSwIVlanEntry 119819392}

er1645v2EthPortSwIVlanInbBwCorrPredefEncapsAtmMp OBJECT-TYPE
   SYNTAX      INTEGER
               {
               llcEncapsulation (0),
               vcMultiplexing (1)
               }
   MAX-ACCESS  read-write
   STATUS      current
   DESCRIPTION
      "Path: swPort.editConf.vlan.inboundBandwidth.correction.predefined.encapsulation.atm.multiProtocol

       Possibilities:
               llcEncapsulation   (0)
               vcMultiplexing   (1)"
   ::= {er1645v2EthPortSwIVlanEntry 119819520}

er1645v2EthPortSwIVlanInbBwCorrPredefEncapsHdlc OBJECT-TYPE
   SYNTAX      DisplayString
   MAX-ACCESS  read-write
   STATUS      current
   DESCRIPTION
      "Path: swPort.editConf.vlan.inboundBandwidth.correction.predefined.encapsulation.hdlc"
   ::= {er1645v2EthPortSwIVlanEntry 119820288}

er1645v2EthPortSwIVlanInbBwCorrPredefEncapsEfmFs OBJECT-TYPE
   SYNTAX      Integer32
   MAX-ACCESS  read-write
   STATUS      current
   DESCRIPTION
      "Path: swPort.editConf.vlan.inboundBandwidth.correction.predefined.encapsulation.efm.fragmentSize"
   ::= {er1645v2EthPortSwIVlanEntry 119821440}

er1645v2EthPortSwIVlanInbBwCorrPredefEncapsEfmIb OBJECT-TYPE
   SYNTAX      Integer32
   MAX-ACCESS  read-write
   STATUS      current
   DESCRIPTION
      "Path: swPort.editConf.vlan.inboundBandwidth.correction.predefined.encapsulation.efm.idleBytes"
   ::= {er1645v2EthPortSwIVlanEntry 119821568}

er1645v2EthPortSwIVlanInbBwCorrPredefMode OBJECT-TYPE
   SYNTAX      INTEGER
               {
               routing (0),
               bridging (1)
               }
   MAX-ACCESS  read-write
   STATUS      current
   DESCRIPTION
      "Path: swPort.editConf.vlan.inboundBandwidth.correction.predefined.mode

       Possibilities:
               routing   (0)
               bridging   (1)"
   ::= {er1645v2EthPortSwIVlanEntry 119832576}

er1645v2EthPortSwIVlanInbBwCorrManualOverhead OBJECT-TYPE
   SYNTAX      Integer32
   MAX-ACCESS  read-write
   STATUS      current
   DESCRIPTION
      "Path: swPort.editConf.vlan.inboundBandwidth.correction.manual.overhead"
   ::= {er1645v2EthPortSwIVlanEntry 119931392}

er1645v2EthPortSwIVlanInbBwCorrManualFrameData OBJECT-TYPE
   SYNTAX      Counter32
   MAX-ACCESS  read-write
   STATUS      current
   DESCRIPTION
      "Path: swPort.editConf.vlan.inboundBandwidth.correction.manual.frameData

       32 bit unsigned wrappable counter."
   ::= {er1645v2EthPortSwIVlanEntry 119931904}

er1645v2EthPortSwIVlanInbBwCorrManualFrameHeader OBJECT-TYPE
   SYNTAX      Counter32
   MAX-ACCESS  read-write
   STATUS      current
   DESCRIPTION
      "Path: swPort.editConf.vlan.inboundBandwidth.correction.manual.frameHeader

       32 bit unsigned wrappable counter."
   ::= {er1645v2EthPortSwIVlanEntry 119932416}

er1645v2EthPortSwIVlanInbBwMaxFifoQLen OBJECT-TYPE
   SYNTAX      Integer32
   MAX-ACCESS  read-write
   STATUS      current
   DESCRIPTION
      "Path: swPort.editConf.vlan.inboundBandwidth.maxFifoQLen"
   ::= {er1645v2EthPortSwIVlanEntry 120586240}

er1645v2EthPortSwIVlanInbBwPriorityPolicy OBJECT-TYPE
   SYNTAX      DisplayString
   MAX-ACCESS  read-write
   STATUS      current
   DESCRIPTION
      "Path: swPort.editConf.vlan.inboundBandwidth.priorityPolicy"
   ::= {er1645v2EthPortSwIVlanEntry 121634816}

er1645v2EthPortSwIVlanInbBwDeFlagCir OBJECT-TYPE
   SYNTAX      INTEGER
               {
               allowed (1),
               notAllowed (2)
               }
   MAX-ACCESS  read-write
   STATUS      current
   DESCRIPTION
      "Path: swPort.editConf.vlan.inboundBandwidth.deFlag.cir

       Possibilities:
               allowed   (1)
               notAllowed   (2)"
   ::= {er1645v2EthPortSwIVlanEntry 131076096}

er1645v2EthPortSwIVlanInbBwDeFlagEir OBJECT-TYPE
   SYNTAX      INTEGER
               {
               allowed (1),
               notAllowed (2)
               }
   MAX-ACCESS  read-write
   STATUS      current
   DESCRIPTION
      "Path: swPort.editConf.vlan.inboundBandwidth.deFlag.eir

       Possibilities:
               allowed   (1)
               notAllowed   (2)"
   ::= {er1645v2EthPortSwIVlanEntry 131080192}

er1645v2EthPortSwIVlanInbBwDeFlagViolate OBJECT-TYPE
   SYNTAX      INTEGER
               {
               allowed (1),
               notAllowed (2)
               }
   MAX-ACCESS  read-write
   STATUS      current
   DESCRIPTION
      "Path: swPort.editConf.vlan.inboundBandwidth.deFlag.violate

       Possibilities:
               allowed   (1)
               notAllowed   (2)"
   ::= {er1645v2EthPortSwIVlanEntry 131084288}

er1645v2EthPortSwIVlanInbBwActCirActNone OBJECT-TYPE
   SYNTAX      OCTET STRING
   MAX-ACCESS  read-write
   STATUS      current
   DESCRIPTION
      "Path: swPort.editConf.vlan.inboundBandwidth.action.cirAction.none"
   ::= {er1645v2EthPortSwIVlanEntry 133308416}

er1645v2EthPortSwIVlanInbBwActCirActEthCos1 OBJECT-TYPE
   SYNTAX      INTEGER
               {
               unchanged (256)
               }
   MAX-ACCESS  read-write
   STATUS      current
   DESCRIPTION
      "Path: swPort.editConf.vlan.inboundBandwidth.action.cirAction.ethernet.cosDepth1

       Possibilities:
               unchanged   (256)"
   ::= {er1645v2EthPortSwIVlanEntry 133316864}

er1645v2EthPortSwIVlanInbBwActCirActEthDei1 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth1

       Possibilities:
               unchanged   (255)
               clear   (0)
               set   (1)"
   ::= {er1645v2EthPortSwIVlanEntry 133321984}

er1645v2EthPortSwIVlanInbBwActCirActEthCos2 OBJECT-TYPE
   SYNTAX      INTEGER
               {
               unchanged (256)
               }
   MAX-ACCESS  read-write
   STATUS      current
   DESCRIPTION
      "Path: swPort.editConf.vlan.inboundBandwidth.action.cirAction.ethernet.cosDepth2

       Possibilities:
               unchanged   (256)"
   ::= {er1645v2EthPortSwIVlanEntry 133317120}

er1645v2EthPortSwIVlanInbBwActCirActEthDei2 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth2

       Possibilities:
               unchanged   (255)
               clear   (0)
               set   (1)"
   ::= {er1645v2EthPortSwIVlanEntry 133322240}

er1645v2EthPortSwIVlanInbBwActCirActEthCos3 OBJECT-TYPE
   SYNTAX      INTEGER
               {
               unchanged (256)
               }
   MAX-ACCESS  read-write
   STATUS      current
   DESCRIPTION
      "Path: swPort.editConf.vlan.inboundBandwidth.action.cirAction.ethernet.cosDepth3

       Possibilities:
               unchanged   (256)"
   ::= {er1645v2EthPortSwIVlanEntry 133317376}

er1645v2EthPortSwIVlanInbBwActCirActEthDei3 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth3

       Possibilities:
               unchanged   (255)
               clear   (0)
               set   (1)"
   ::= {er1645v2EthPortSwIVlanEntry 133322496}

er1645v2EthPortSwIVlanInbBwActCirActEthCos4 OBJECT-TYPE
   SYNTAX      INTEGER
               {
               unchanged (256)
               }
   MAX-ACCESS  read-write
   STATUS      current
   DESCRIPTION
      "Path: swPort.editConf.vlan.inboundBandwidth.action.cirAction.ethernet.cosDepth4

       Possibilities:
               unchanged   (256)"
   ::= {er1645v2EthPortSwIVlanEntry 133317632}

er1645v2EthPortSwIVlanInbBwActCirActEthDei4 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth4

       Possibilities:
               unchanged   (255)
               clear   (0)
               set   (1)"
   ::= {er1645v2EthPortSwIVlanEntry 133322752}

er1645v2EthPortSwIVlanInbBwActCirActEthCos5 OBJECT-TYPE
   SYNTAX      INTEGER
               {
               unchanged (256)
               }
   MAX-ACCESS  read-write
   STATUS      current
   DESCRIPTION
      "Path: swPort.editConf.vlan.inboundBandwidth.action.cirAction.ethernet.cosDepth5

       Possibilities:
               unchanged   (256)"
   ::= {er1645v2EthPortSwIVlanEntry 133317888}

er1645v2EthPortSwIVlanInbBwActCirActEthDei5 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth5

       Possibilities:
               unchanged   (255)
               clear   (0)
               set   (1)"
   ::= {er1645v2EthPortSwIVlanEntry 133323008}

er1645v2EthPortSwIVlanInbBwActCirActEthCos6 OBJECT-TYPE
   SYNTAX      INTEGER
               {
               unchanged (256)
               }
   MAX-ACCESS  read-write
   STATUS      current
   DESCRIPTION
      "Path: swPort.editConf.vlan.inboundBandwidth.action.cirAction.ethernet.cosDepth6

       Possibilities:
               unchanged   (256)"
   ::= {er1645v2EthPortSwIVlanEntry 133318144}

er1645v2EthPortSwIVlanInbBwActCirActEthDei6 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth6

       Possibilities:
               unchanged   (255)
               clear   (0)
               set   (1)"
   ::= {er1645v2EthPortSwIVlanEntry 133323264}

er1645v2EthPortSwIVlanInbBwActCirActEthCos7 OBJECT-TYPE
   SYNTAX      INTEGER
               {
               unchanged (256)
               }
   MAX-ACCESS  read-write
   STATUS      current
   DESCRIPTION
      "Path: swPort.editConf.vlan.inboundBandwidth.action.cirAction.ethernet.cosDepth7

       Possibilities:
               unchanged   (256)"
   ::= {er1645v2EthPortSwIVlanEntry 133318400}

er1645v2EthPortSwIVlanInbBwActCirActEthDei7 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth7

       Possibilities:
               unchanged   (255)
               clear   (0)
               set   (1)"
   ::= {er1645v2EthPortSwIVlanEntry 133323520}

er1645v2EthPortSwIVlanInbBwActCirActEthCos8 OBJECT-TYPE
   SYNTAX      INTEGER
               {
               unchanged (256)
               }
   MAX-ACCESS  read-write
   STATUS      current
   DESCRIPTION
      "Path: swPort.editConf.vlan.inboundBandwidth.action.cirAction.ethernet.cosDepth8

       Possibilities:
               unchanged   (256)"
   ::= {er1645v2EthPortSwIVlanEntry 133318656}

er1645v2EthPortSwIVlanInbBwActCirActEthDei8 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth8

       Possibilities:
               unchanged   (255)
               clear   (0)
               set   (1)"
   ::= {er1645v2EthPortSwIVlanEntry 133323776}

er1645v2EthPortSwIVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133318912}

er1645v2EthPortSwIVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133319168}

er1645v2EthPortSwIVlanInbBwActCirActEthDrpLev OBJECT-TYPE
   SYNTAX      INTEGER
               {
               unchanged (0)
               }
   MAX-ACCESS  read-write
   STATUS      current
   DESCRIPTION
      "Path: swPort.editConf.vlan.inboundBandwidth.action.cirAction.ethernet.dropLevel

       Possibilities:
               unchanged   (0)"
   ::= {er1645v2EthPortSwIVlanEntry 133319424}

er1645v2EthPortSwIVlanInbBwActCirActEthDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deFlag

       Possibilities:
               unchanged   (255)
               clear   (0)
               set   (1)"
   ::= {er1645v2EthPortSwIVlanEntry 133320192}

er1645v2EthPortSwIVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133343488}

er1645v2EthPortSwIVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133343744}

er1645v2EthPortSwIVlanInbBwActCirActIpDrpLev OBJECT-TYPE
   SYNTAX      INTEGER
               {
               unchanged (0)
               }
   MAX-ACCESS  read-write
   STATUS      current
   DESCRIPTION
      "Path: swPort.editConf.vlan.inboundBandwidth.action.cirAction.ip.dropLevel

       Possibilities:
               unchanged   (0)"
   ::= {er1645v2EthPortSwIVlanEntry 133344000}

er1645v2EthPortSwIVlanInbBwActCirActIpDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ip.deFlag

       Possibilities:
               unchanged   (255)
               clear   (0)
               set   (1)"
   ::= {er1645v2EthPortSwIVlanEntry 133344768}

er1645v2EthPortSwIVlanInbBwActEirActNone OBJECT-TYPE
   SYNTAX      OCTET STRING
   MAX-ACCESS  read-write
   STATUS      current
   DESCRIPTION
      "Path: swPort.editConf.vlan.inboundBandwidth.action.eirAction.none"
   ::= {er1645v2EthPortSwIVlanEntry 133439488}

er1645v2EthPortSwIVlanInbBwActEirActEthCos1 OBJECT-TYPE
   SYNTAX      INTEGER
               {
               unchanged (256)
               }
   MAX-ACCESS  read-write
   STATUS      current
   DESCRIPTION
      "Path: swPort.editConf.vlan.inboundBandwidth.action.eirAction.ethernet.cosDepth1

       Possibilities:
               unchanged   (256)"
   ::= {er1645v2EthPortSwIVlanEntry 133447936}

er1645v2EthPortSwIVlanInbBwActEirActEthDei1 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth1

       Possibilities:
               unchanged   (255)
               clear   (0)
               set   (1)"
   ::= {er1645v2EthPortSwIVlanEntry 133453056}

er1645v2EthPortSwIVlanInbBwActEirActEthCos2 OBJECT-TYPE
   SYNTAX      INTEGER
               {
               unchanged (256)
               }
   MAX-ACCESS  read-write
   STATUS      current
   DESCRIPTION
      "Path: swPort.editConf.vlan.inboundBandwidth.action.eirAction.ethernet.cosDepth2

       Possibilities:
               unchanged   (256)"
   ::= {er1645v2EthPortSwIVlanEntry 133448192}

er1645v2EthPortSwIVlanInbBwActEirActEthDei2 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth2

       Possibilities:
               unchanged   (255)
               clear   (0)
               set   (1)"
   ::= {er1645v2EthPortSwIVlanEntry 133453312}

er1645v2EthPortSwIVlanInbBwActEirActEthCos3 OBJECT-TYPE
   SYNTAX      INTEGER
               {
               unchanged (256)
               }
   MAX-ACCESS  read-write
   STATUS      current
   DESCRIPTION
      "Path: swPort.editConf.vlan.inboundBandwidth.action.eirAction.ethernet.cosDepth3

       Possibilities:
               unchanged   (256)"
   ::= {er1645v2EthPortSwIVlanEntry 133448448}

er1645v2EthPortSwIVlanInbBwActEirActEthDei3 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth3

       Possibilities:
               unchanged   (255)
               clear   (0)
               set   (1)"
   ::= {er1645v2EthPortSwIVlanEntry 133453568}

er1645v2EthPortSwIVlanInbBwActEirActEthCos4 OBJECT-TYPE
   SYNTAX      INTEGER
               {
               unchanged (256)
               }
   MAX-ACCESS  read-write
   STATUS      current
   DESCRIPTION
      "Path: swPort.editConf.vlan.inboundBandwidth.action.eirAction.ethernet.cosDepth4

       Possibilities:
               unchanged   (256)"
   ::= {er1645v2EthPortSwIVlanEntry 133448704}

er1645v2EthPortSwIVlanInbBwActEirActEthDei4 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth4

       Possibilities:
               unchanged   (255)
               clear   (0)
               set   (1)"
   ::= {er1645v2EthPortSwIVlanEntry 133453824}

er1645v2EthPortSwIVlanInbBwActEirActEthCos5 OBJECT-TYPE
   SYNTAX      INTEGER
               {
               unchanged (256)
               }
   MAX-ACCESS  read-write
   STATUS      current
   DESCRIPTION
      "Path: swPort.editConf.vlan.inboundBandwidth.action.eirAction.ethernet.cosDepth5

       Possibilities:
               unchanged   (256)"
   ::= {er1645v2EthPortSwIVlanEntry 133448960}

er1645v2EthPortSwIVlanInbBwActEirActEthDei5 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth5

       Possibilities:
               unchanged   (255)
               clear   (0)
               set   (1)"
   ::= {er1645v2EthPortSwIVlanEntry 133454080}

er1645v2EthPortSwIVlanInbBwActEirActEthCos6 OBJECT-TYPE
   SYNTAX      INTEGER
               {
               unchanged (256)
               }
   MAX-ACCESS  read-write
   STATUS      current
   DESCRIPTION
      "Path: swPort.editConf.vlan.inboundBandwidth.action.eirAction.ethernet.cosDepth6

       Possibilities:
               unchanged   (256)"
   ::= {er1645v2EthPortSwIVlanEntry 133449216}

er1645v2EthPortSwIVlanInbBwActEirActEthDei6 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth6

       Possibilities:
               unchanged   (255)
               clear   (0)
               set   (1)"
   ::= {er1645v2EthPortSwIVlanEntry 133454336}

er1645v2EthPortSwIVlanInbBwActEirActEthCos7 OBJECT-TYPE
   SYNTAX      INTEGER
               {
               unchanged (256)
               }
   MAX-ACCESS  read-write
   STATUS      current
   DESCRIPTION
      "Path: swPort.editConf.vlan.inboundBandwidth.action.eirAction.ethernet.cosDepth7

       Possibilities:
               unchanged   (256)"
   ::= {er1645v2EthPortSwIVlanEntry 133449472}

er1645v2EthPortSwIVlanInbBwActEirActEthDei7 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth7

       Possibilities:
               unchanged   (255)
               clear   (0)
               set   (1)"
   ::= {er1645v2EthPortSwIVlanEntry 133454592}

er1645v2EthPortSwIVlanInbBwActEirActEthCos8 OBJECT-TYPE
   SYNTAX      INTEGER
               {
               unchanged (256)
               }
   MAX-ACCESS  read-write
   STATUS      current
   DESCRIPTION
      "Path: swPort.editConf.vlan.inboundBandwidth.action.eirAction.ethernet.cosDepth8

       Possibilities:
               unchanged   (256)"
   ::= {er1645v2EthPortSwIVlanEntry 133449728}

er1645v2EthPortSwIVlanInbBwActEirActEthDei8 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth8

       Possibilities:
               unchanged   (255)
               clear   (0)
               set   (1)"
   ::= {er1645v2EthPortSwIVlanEntry 133454848}

er1645v2EthPortSwIVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133449984}

er1645v2EthPortSwIVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133450240}

er1645v2EthPortSwIVlanInbBwActEirActEthDrpLev OBJECT-TYPE
   SYNTAX      INTEGER
               {
               unchanged (0)
               }
   MAX-ACCESS  read-write
   STATUS      current
   DESCRIPTION
      "Path: swPort.editConf.vlan.inboundBandwidth.action.eirAction.ethernet.dropLevel

       Possibilities:
               unchanged   (0)"
   ::= {er1645v2EthPortSwIVlanEntry 133450496}

er1645v2EthPortSwIVlanInbBwActEirActEthDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deFlag

       Possibilities:
               unchanged   (255)
               clear   (0)
               set   (1)"
   ::= {er1645v2EthPortSwIVlanEntry 133451264}

er1645v2EthPortSwIVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133474560}

er1645v2EthPortSwIVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133474816}

er1645v2EthPortSwIVlanInbBwActEirActIpDrpLev OBJECT-TYPE
   SYNTAX      INTEGER
               {
               unchanged (0)
               }
   MAX-ACCESS  read-write
   STATUS      current
   DESCRIPTION
      "Path: swPort.editConf.vlan.inboundBandwidth.action.eirAction.ip.dropLevel

       Possibilities:
               unchanged   (0)"
   ::= {er1645v2EthPortSwIVlanEntry 133475072}

er1645v2EthPortSwIVlanInbBwActEirActIpDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ip.deFlag

       Possibilities:
               unchanged   (255)
               clear   (0)
               set   (1)"
   ::= {er1645v2EthPortSwIVlanEntry 133475840}

er1645v2EthPortSwIVlanInbBwActViolActNone OBJECT-TYPE
   SYNTAX      OCTET STRING
   MAX-ACCESS  read-write
   STATUS      current
   DESCRIPTION
      "Path: swPort.editConf.vlan.inboundBandwidth.action.violateAction.none"
   ::= {er1645v2EthPortSwIVlanEntry 133570560}

er1645v2EthPortSwIVlanInbBwActViolActDrop OBJECT-TYPE
   SYNTAX      OCTET STRING
   MAX-ACCESS  read-write
   STATUS      current
   DESCRIPTION
      "Path: swPort.editConf.vlan.inboundBandwidth.action.violateAction.drop"
   ::= {er1645v2EthPortSwIVlanEntry 133586944}

er1645v2EthPortSwIVlanInbBwActViolActEthCos1 OBJECT-TYPE
   SYNTAX      INTEGER
               {
               unchanged (256)
               }
   MAX-ACCESS  read-write
   STATUS      current
   DESCRIPTION
      "Path: swPort.editConf.vlan.inboundBandwidth.action.violateAction.ethernet.cosDepth1

       Possibilities:
               unchanged   (256)"
   ::= {er1645v2EthPortSwIVlanEntry 133579008}

er1645v2EthPortSwIVlanInbBwActViolActEthDei1 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth1

       Possibilities:
               unchanged   (255)
               clear   (0)
               set   (1)"
   ::= {er1645v2EthPortSwIVlanEntry 133584128}

er1645v2EthPortSwIVlanInbBwActViolActEthCos2 OBJECT-TYPE
   SYNTAX      INTEGER
               {
               unchanged (256)
               }
   MAX-ACCESS  read-write
   STATUS      current
   DESCRIPTION
      "Path: swPort.editConf.vlan.inboundBandwidth.action.violateAction.ethernet.cosDepth2

       Possibilities:
               unchanged   (256)"
   ::= {er1645v2EthPortSwIVlanEntry 133579264}

er1645v2EthPortSwIVlanInbBwActViolActEthDei2 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth2

       Possibilities:
               unchanged   (255)
               clear   (0)
               set   (1)"
   ::= {er1645v2EthPortSwIVlanEntry 133584384}

er1645v2EthPortSwIVlanInbBwActViolActEthCos3 OBJECT-TYPE
   SYNTAX      INTEGER
               {
               unchanged (256)
               }
   MAX-ACCESS  read-write
   STATUS      current
   DESCRIPTION
      "Path: swPort.editConf.vlan.inboundBandwidth.action.violateAction.ethernet.cosDepth3

       Possibilities:
               unchanged   (256)"
   ::= {er1645v2EthPortSwIVlanEntry 133579520}

er1645v2EthPortSwIVlanInbBwActViolActEthDei3 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth3

       Possibilities:
               unchanged   (255)
               clear   (0)
               set   (1)"
   ::= {er1645v2EthPortSwIVlanEntry 133584640}

er1645v2EthPortSwIVlanInbBwActViolActEthCos4 OBJECT-TYPE
   SYNTAX      INTEGER
               {
               unchanged (256)
               }
   MAX-ACCESS  read-write
   STATUS      current
   DESCRIPTION
      "Path: swPort.editConf.vlan.inboundBandwidth.action.violateAction.ethernet.cosDepth4

       Possibilities:
               unchanged   (256)"
   ::= {er1645v2EthPortSwIVlanEntry 133579776}

er1645v2EthPortSwIVlanInbBwActViolActEthDei4 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth4

       Possibilities:
               unchanged   (255)
               clear   (0)
               set   (1)"
   ::= {er1645v2EthPortSwIVlanEntry 133584896}

er1645v2EthPortSwIVlanInbBwActViolActEthCos5 OBJECT-TYPE
   SYNTAX      INTEGER
               {
               unchanged (256)
               }
   MAX-ACCESS  read-write
   STATUS      current
   DESCRIPTION
      "Path: swPort.editConf.vlan.inboundBandwidth.action.violateAction.ethernet.cosDepth5

       Possibilities:
               unchanged   (256)"
   ::= {er1645v2EthPortSwIVlanEntry 133580032}

er1645v2EthPortSwIVlanInbBwActViolActEthDei5 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth5

       Possibilities:
               unchanged   (255)
               clear   (0)
               set   (1)"
   ::= {er1645v2EthPortSwIVlanEntry 133585152}

er1645v2EthPortSwIVlanInbBwActViolActEthCos6 OBJECT-TYPE
   SYNTAX      INTEGER
               {
               unchanged (256)
               }
   MAX-ACCESS  read-write
   STATUS      current
   DESCRIPTION
      "Path: swPort.editConf.vlan.inboundBandwidth.action.violateAction.ethernet.cosDepth6

       Possibilities:
               unchanged   (256)"
   ::= {er1645v2EthPortSwIVlanEntry 133580288}

er1645v2EthPortSwIVlanInbBwActViolActEthDei6 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth6

       Possibilities:
               unchanged   (255)
               clear   (0)
               set   (1)"
   ::= {er1645v2EthPortSwIVlanEntry 133585408}

er1645v2EthPortSwIVlanInbBwActViolActEthCos7 OBJECT-TYPE
   SYNTAX      INTEGER
               {
               unchanged (256)
               }
   MAX-ACCESS  read-write
   STATUS      current
   DESCRIPTION
      "Path: swPort.editConf.vlan.inboundBandwidth.action.violateAction.ethernet.cosDepth7

       Possibilities:
               unchanged   (256)"
   ::= {er1645v2EthPortSwIVlanEntry 133580544}

er1645v2EthPortSwIVlanInbBwActViolActEthDei7 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth7

       Possibilities:
               unchanged   (255)
               clear   (0)
               set   (1)"
   ::= {er1645v2EthPortSwIVlanEntry 133585664}

er1645v2EthPortSwIVlanInbBwActViolActEthCos8 OBJECT-TYPE
   SYNTAX      INTEGER
               {
               unchanged (256)
               }
   MAX-ACCESS  read-write
   STATUS      current
   DESCRIPTION
      "Path: swPort.editConf.vlan.inboundBandwidth.action.violateAction.ethernet.cosDepth8

       Possibilities:
               unchanged   (256)"
   ::= {er1645v2EthPortSwIVlanEntry 133580800}

er1645v2EthPortSwIVlanInbBwActViolActEthDei8 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth8

       Possibilities:
               unchanged   (255)
               clear   (0)
               set   (1)"
   ::= {er1645v2EthPortSwIVlanEntry 133585920}

er1645v2EthPortSwIVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133581056}

er1645v2EthPortSwIVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133581312}

er1645v2EthPortSwIVlanInbBwActViolActEthDrpLev OBJECT-TYPE
   SYNTAX      INTEGER
               {
               unchanged (0)
               }
   MAX-ACCESS  read-write
   STATUS      current
   DESCRIPTION
      "Path: swPort.editConf.vlan.inboundBandwidth.action.violateAction.ethernet.dropLevel

       Possibilities:
               unchanged   (0)"
   ::= {er1645v2EthPortSwIVlanEntry 133581568}

er1645v2EthPortSwIVlanInbBwActViolActEthDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deFlag

       Possibilities:
               unchanged   (255)
               clear   (0)
               set   (1)"
   ::= {er1645v2EthPortSwIVlanEntry 133582336}

er1645v2EthPortSwIVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanEntry 133605632}

er1645v2EthPortSwIVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanEntry 133605888}

er1645v2EthPortSwIVlanInbBwActViolActIpDrpLev OBJECT-TYPE
   SYNTAX      INTEGER
               {
               unchanged (0)
               }
   MAX-ACCESS  read-write
   STATUS      current
   DESCRIPTION
      "Path: swPort.editConf.vlan.inboundBandwidth.action.violateAction.ip.dropLevel

       Possibilities:
               unchanged   (0)"
   ::= {er1645v2EthPortSwIVlanEntry 133606144}

er1645v2EthPortSwIVlanInbBwActViolActIpDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ip.deFlag

       Possibilities:
               unchanged   (255)
               clear   (0)
               set   (1)"
   ::= {er1645v2EthPortSwIVlanEntry 133606912}

er1645v2EthPortSwIVlanPppoE OBJECT-TYPE
   SYNTAX      INTEGER
               {
               disabled (0),
               enabled (1)
               }
   MAX-ACCESS  read-write
   STATUS      current
   DESCRIPTION
      "Path: swPort.editConf.vlan.pppoE

       Possibilities:
               disabled   (0)
               enabled   (1)"
   ::= {er1645v2EthPortSwIVlanEntry 838860800}

er1645v2EthPortSwIVlanPppLnkMOperation OBJECT-TYPE
   SYNTAX      INTEGER
               {
               disabled (0),
               enabled (1)
               }
   MAX-ACCESS  read-write
   STATUS      current
   DESCRIPTION
      "Path: swPort.editConf.vlan.ppp.linkMonitoring.operation

       Possibilities:
               disabled   (0)
               enabled   (1)"
   ::= {er1645v2EthPortSwIVlanEntry 251724032}

er1645v2EthPortSwIVlanPppLnkMInterval OBJECT-TYPE
   SYNTAX      TimeTicks
   MAX-ACCESS  read-write
   STATUS      current
   DESCRIPTION
      "Path: swPort.editConf.vlan.ppp.linkMonitoring.interval

       Time in centi-second."
   ::= {er1645v2EthPortSwIVlanEntry 251724288}

er1645v2EthPortSwIVlanPppLnkMRepTimeOut OBJECT-TYPE
   SYNTAX      TimeTicks
   MAX-ACCESS  read-write
   STATUS      current
   DESCRIPTION
      "Path: swPort.editConf.vlan.ppp.linkMonitoring.replyTimeOut

       Time in centi-second."
   ::= {er1645v2EthPortSwIVlanEntry 251724544}

er1645v2EthPortSwIVlanPppLnkMFailsPrmt OBJECT-TYPE
   SYNTAX      Integer32
   MAX-ACCESS  read-write
   STATUS      current
   DESCRIPTION
      "Path: swPort.editConf.vlan.ppp.linkMonitoring.failsPermitted"
   ::= {er1645v2EthPortSwIVlanEntry 251724800}

er1645v2EthPortSwIVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.vlan.ppp.authentication

       Possibilities:
               disabled   (0)
               chap   (1)
               pap   (2)
               chapOrPap   (3)
               msChap   (4)
               msChapV2   (5)"
   ::= {er1645v2EthPortSwIVlanEntry 251789312}

er1645v2EthPortSwIVlanPppAuthenPeriod OBJECT-TYPE
   SYNTAX      TimeTicks
   MAX-ACCESS  read-write
   STATUS      current
   DESCRIPTION
      "Path: swPort.editConf.vlan.ppp.authenPeriod

       Time in centi-second."
   ::= {er1645v2EthPortSwIVlanEntry 251854848}

er1645v2EthPortSwIVlanPppSessionName OBJECT-TYPE
   SYNTAX      DisplayString
   MAX-ACCESS  read-write
   STATUS      current
   DESCRIPTION
      "Path: swPort.editConf.vlan.ppp.sessionName"
   ::= {er1645v2EthPortSwIVlanEntry 251985920}

er1645v2EthPortSwIVlanPppSessionSecret OBJECT-TYPE
   SYNTAX      DisplayString
   MAX-ACCESS  read-write
   STATUS      current
   DESCRIPTION
      "Path: swPort.editConf.vlan.ppp.sessionSecret"
   ::= {er1645v2EthPortSwIVlanEntry 252051456}

er1645v2EthPortSwIVlanPppEncModeSessionSecret OBJECT-TYPE
   SYNTAX      INTEGER
               {
               none (1),
               encrypt (2),
               encType1 (3),
               invalid (128)
               }
   MAX-ACCESS  read-write
   STATUS      current
   DESCRIPTION
      "Path: swPort.editConf.vlan.ppp.encModeSessionSecret

       Possibilities:
               none   (1)
               encrypt   (2)
               encType1   (3)
               invalid   (128)"
   ::= {er1645v2EthPortSwIVlanEntry 252182528}

er1645v2EthPortSwIVlanPppEncSessionSecret OBJECT-TYPE
   SYNTAX      DisplayString
   MAX-ACCESS  read-write
   STATUS      current
   DESCRIPTION
      "Path: swPort.editConf.vlan.ppp.encSessionSecret"
   ::= {er1645v2EthPortSwIVlanEntry 252248064}

er1645v2EthPortSwIVlanPppServiceName OBJECT-TYPE
   SYNTAX      DisplayString
   MAX-ACCESS  read-write
   STATUS      current
   DESCRIPTION
      "Path: swPort.editConf.vlan.ppp.serviceName"
   ::= {er1645v2EthPortSwIVlanEntry 252116992}

er1645v2EthPortSwIVlanPbbMode OBJECT-TYPE
   SYNTAX      INTEGER
               {
               disabled (0),
               static (1),
               dynamicPtp (2),
               dynamicPtmp (3)
               }
   MAX-ACCESS  read-write
   STATUS      current
   DESCRIPTION
      "Path: swPort.editConf.vlan.pbb.mode

       Possibilities:
               disabled   (0)
               static   (1)
               dynamicPtp   (2)
               dynamicPtmp   (3)"
   ::= {er1645v2EthPortSwIVlanEntry 1174667264}

er1645v2EthPortSwIVlanPbbTxCos OBJECT-TYPE
   SYNTAX      Integer32
   MAX-ACCESS  read-write
   STATUS      current
   DESCRIPTION
      "Path: swPort.editConf.vlan.pbb.txCos"
   ::= {er1645v2EthPortSwIVlanEntry 1175191552}

er1645v2EthPortSwIVlanPbbIsid OBJECT-TYPE
   SYNTAX      Integer32
   MAX-ACCESS  read-write
   STATUS      current
   DESCRIPTION
      "Path: swPort.editConf.vlan.pbb.isid"
   ::= {er1645v2EthPortSwIVlanEntry 1175453696}

er1645v2EthPortSwIVlanPbbDestMac OBJECT-TYPE
   SYNTAX      OCTET STRING
   MAX-ACCESS  read-write
   STATUS      current
   DESCRIPTION
      "Path: swPort.editConf.vlan.pbb.destMac

       MAC address."
   ::= {er1645v2EthPortSwIVlanEntry 1175715840}

er1645v2EthPortSwIVlanPbbCustomGroupMac OBJECT-TYPE
   SYNTAX      OCTET STRING
   MAX-ACCESS  read-write
   STATUS      current
   DESCRIPTION
      "Path: swPort.editConf.vlan.pbb.customGroupMac

       MAC address."
   ::= {er1645v2EthPortSwIVlanEntry 1175977984}

er1645v2EthPortSwIVlanIpSaddr OBJECT-TYPE
   SYNTAX      SEQUENCE OF Er1645v2EthPortSwIVlanIpSaddrEntry
   MAX-ACCESS  not-accessible
   STATUS      current
   DESCRIPTION
      ""
   ::= {er1645v2EthPortSwIVlan 51838976}

er1645v2EthPortSwIVlanIpSaddrEntry OBJECT-TYPE
   SYNTAX      Er1645v2EthPortSwIVlanIpSaddrEntry
   MAX-ACCESS  not-accessible
   STATUS      current
   DESCRIPTION
      ""
   INDEX      { er1645v2EthPortSwIVlanIpSaddrGlobalIx,
                er1645v2EthPortSwIVlanTableIx,
                er1645v2EthPortSwIVlanIpSaddrTableIx }
   ::= {er1645v2EthPortSwIVlanIpSaddr 1}

Er1645v2EthPortSwIVlanIpSaddrEntry ::=
   SEQUENCE
      {
      er1645v2EthPortSwIVlanIpSaddrActions
         VariableLengthTableActions,
      er1645v2EthPortSwIVlanIpSaddrGlobalIx
         GlobalIndex,
      er1645v2EthPortSwIVlanIpSaddrTableIx
         TableIndex,
      er1645v2EthPortSwIVlanIpSaddrAddress
         IpAddress,
      er1645v2EthPortSwIVlanIpSaddrNetMask
         IpAddress
      }

er1645v2EthPortSwIVlanIpSaddrActions OBJECT-TYPE
   SYNTAX      VariableLengthTableActions
   MAX-ACCESS  read-write
   STATUS      current
   DESCRIPTION
      "By way of this field, some manipulations
       on this table may be performed."
   ::= {er1645v2EthPortSwIVlanIpSaddrEntry 2}

er1645v2EthPortSwIVlanIpSaddrGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpSaddrEntry 10}

er1645v2EthPortSwIVlanIpSaddrTableIx OBJECT-TYPE
   SYNTAX      TableIndex
   MAX-ACCESS  not-accessible
   STATUS      current
   DESCRIPTION
      ""
   ::= {er1645v2EthPortSwIVlanIpSaddrEntry 11}

er1645v2EthPortSwIVlanIpSaddrAddress OBJECT-TYPE
   SYNTAX      IpAddress
   MAX-ACCESS  read-write
   STATUS      current
   DESCRIPTION
      "Path: swPort.editConf.vlan.ip.secondaryIp.address"
   ::= {er1645v2EthPortSwIVlanIpSaddrEntry 2030043136}

er1645v2EthPortSwIVlanIpSaddrNetMask OBJECT-TYPE
   SYNTAX      IpAddress
   MAX-ACCESS  read-write
   STATUS      current
   DESCRIPTION
      "Path: swPort.editConf.vlan.ip.secondaryIp.netMask"
   ::= {er1645v2EthPortSwIVlanIpSaddrEntry 2063597568}

er1645v2EthPortSwIVlanIpH OBJECT-TYPE
   SYNTAX      SEQUENCE OF Er1645v2EthPortSwIVlanIpHEntry
   MAX-ACCESS  not-accessible
   STATUS      current
   DESCRIPTION
      ""
   ::= {er1645v2EthPortSwIVlan 51314688}

er1645v2EthPortSwIVlanIpHEntry OBJECT-TYPE
   SYNTAX      Er1645v2EthPortSwIVlanIpHEntry
   MAX-ACCESS  not-accessible
   STATUS      current
   DESCRIPTION
      ""
   INDEX      { er1645v2EthPortSwIVlanIpHGlobalIx,
                er1645v2EthPortSwIVlanTableIx,
                er1645v2EthPortSwIVlanIpHTableIx }
   ::= {er1645v2EthPortSwIVlanIpH 1}

Er1645v2EthPortSwIVlanIpHEntry ::=
   SEQUENCE
      {
      er1645v2EthPortSwIVlanIpHActions
         VariableLengthTableActions,
      er1645v2EthPortSwIVlanIpHGlobalIx
         GlobalIndex,
      er1645v2EthPortSwIVlanIpHTableIx
         TableIndex,
      er1645v2EthPortSwIVlanIpHAddress
         IpAddress,
      er1645v2EthPortSwIVlanIpHDhcpRelayOptionSubscriberId
         DisplayString
      }

er1645v2EthPortSwIVlanIpHActions OBJECT-TYPE
   SYNTAX      VariableLengthTableActions
   MAX-ACCESS  read-write
   STATUS      current
   DESCRIPTION
      "By way of this field, some manipulations
       on this table may be performed."
   ::= {er1645v2EthPortSwIVlanIpHEntry 2}

er1645v2EthPortSwIVlanIpHGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpHEntry 10}

er1645v2EthPortSwIVlanIpHTableIx OBJECT-TYPE
   SYNTAX      TableIndex
   MAX-ACCESS  not-accessible
   STATUS      current
   DESCRIPTION
      ""
   ::= {er1645v2EthPortSwIVlanIpHEntry 11}

er1645v2EthPortSwIVlanIpHAddress OBJECT-TYPE
   SYNTAX      IpAddress
   MAX-ACCESS  read-write
   STATUS      current
   DESCRIPTION
      "Path: swPort.editConf.vlan.ip.helpers.address"
   ::= {er1645v2EthPortSwIVlanIpHEntry 16777216}

er1645v2EthPortSwIVlanIpHDhcpRelayOptionSubscriberId OBJECT-TYPE
   SYNTAX      DisplayString
   MAX-ACCESS  read-write
   STATUS      current
   DESCRIPTION
      "Path: swPort.editConf.vlan.ip.helpers.dhcpRelayOption.subscriberId"
   ::= {er1645v2EthPortSwIVlanIpHEntry 33947648}

er1645v2EthPortSwIVlanIpV6Addresses OBJECT-TYPE
   SYNTAX      SEQUENCE OF Er1645v2EthPortSwIVlanIpV6AddressesEntry
   MAX-ACCESS  not-accessible
   STATUS      current
   DESCRIPTION
      ""
   ::= {er1645v2EthPortSwIVlan 704839680}

er1645v2EthPortSwIVlanIpV6AddressesEntry OBJECT-TYPE
   SYNTAX      Er1645v2EthPortSwIVlanIpV6AddressesEntry
   MAX-ACCESS  not-accessible
   STATUS      current
   DESCRIPTION
      ""
   INDEX      { er1645v2EthPortSwIVlanIpV6AddressesGlobalIx,
                er1645v2EthPortSwIVlanTableIx,
                er1645v2EthPortSwIVlanIpV6AddressesTableIx }
   ::= {er1645v2EthPortSwIVlanIpV6Addresses 1}

Er1645v2EthPortSwIVlanIpV6AddressesEntry ::=
   SEQUENCE
      {
      er1645v2EthPortSwIVlanIpV6AddressesActions
         VariableLengthTableActions,
      er1645v2EthPortSwIVlanIpV6AddressesGlobalIx
         GlobalIndex,
      er1645v2EthPortSwIVlanIpV6AddressesTableIx
         TableIndex,
      er1645v2EthPortSwIVlanIpV6AddressesType
         INTEGER,
      er1645v2EthPortSwIVlanIpV6AddressesAddress
         Ipv6Address,
      er1645v2EthPortSwIVlanIpV6AddressesPrefixLength
         Integer32,
      er1645v2EthPortSwIVlanIpV6AddressesGeneralPrefix
         DisplayString,
      er1645v2EthPortSwIVlanIpV6AddressesRaSend
         INTEGER,
      er1645v2EthPortSwIVlanIpV6AddressesRaOnLinkFlag
         INTEGER,
      er1645v2EthPortSwIVlanIpV6AddressesRaAutoFlag
         INTEGER,
      er1645v2EthPortSwIVlanIpV6AddressesRaValidLifeTime
         TimeTicks,
      er1645v2EthPortSwIVlanIpV6AddressesRaValidLTMode
         INTEGER,
      er1645v2EthPortSwIVlanIpV6AddressesRaPrefLifeTime
         TimeTicks,
      er1645v2EthPortSwIVlanIpV6AddressesRaPrefLTMode
         INTEGER
      }

er1645v2EthPortSwIVlanIpV6AddressesActions OBJECT-TYPE
   SYNTAX      VariableLengthTableActions
   MAX-ACCESS  read-write
   STATUS      current
   DESCRIPTION
      "By way of this field, some manipulations
       on this table may be performed."
   ::= {er1645v2EthPortSwIVlanIpV6AddressesEntry 2}

er1645v2EthPortSwIVlanIpV6AddressesGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6AddressesEntry 10}

er1645v2EthPortSwIVlanIpV6AddressesTableIx OBJECT-TYPE
   SYNTAX      TableIndex
   MAX-ACCESS  not-accessible
   STATUS      current
   DESCRIPTION
      ""
   ::= {er1645v2EthPortSwIVlanIpV6AddressesEntry 11}

er1645v2EthPortSwIVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.vlan.ipV6.addresses.type

       Possibilities:
               unicast   (0)
               eui64   (1)
               anycast   (2)
               linkLocal   (3)
               generalPrefix   (4)"
   ::= {er1645v2EthPortSwIVlanIpV6AddressesEntry 50331648}

er1645v2EthPortSwIVlanIpV6AddressesAddress OBJECT-TYPE
   SYNTAX      Ipv6Address
   MAX-ACCESS  read-write
   STATUS      current
   DESCRIPTION
      "Path: swPort.editConf.vlan.ipV6.addresses.address

       ipv6 address"
   ::= {er1645v2EthPortSwIVlanIpV6AddressesEntry 16777216}

er1645v2EthPortSwIVlanIpV6AddressesPrefixLength OBJECT-TYPE
   SYNTAX      Integer32
   MAX-ACCESS  read-write
   STATUS      current
   DESCRIPTION
      "Path: swPort.editConf.vlan.ipV6.addresses.prefixLength"
   ::= {er1645v2EthPortSwIVlanIpV6AddressesEntry 33554432}

er1645v2EthPortSwIVlanIpV6AddressesGeneralPrefix OBJECT-TYPE
   SYNTAX      DisplayString
   MAX-ACCESS  read-write
   STATUS      current
   DESCRIPTION
      "Path: swPort.editConf.vlan.ipV6.addresses.generalPrefix"
   ::= {er1645v2EthPortSwIVlanIpV6AddressesEntry 83886080}

er1645v2EthPortSwIVlanIpV6AddressesRaSend OBJECT-TYPE
   SYNTAX      INTEGER
               {
               disabled (0),
               enabled (1)
               }
   MAX-ACCESS  read-write
   STATUS      current
   DESCRIPTION
      "Path: swPort.editConf.vlan.ipV6.addresses.ra.send

       Possibilities:
               disabled   (0)
               enabled   (1)"
   ::= {er1645v2EthPortSwIVlanIpV6AddressesEntry 67174400}

er1645v2EthPortSwIVlanIpV6AddressesRaOnLinkFlag OBJECT-TYPE
   SYNTAX      INTEGER
               {
               disabled (0),
               enabled (1)
               }
   MAX-ACCESS  read-write
   STATUS      current
   DESCRIPTION
      "Path: swPort.editConf.vlan.ipV6.addresses.ra.onLinkFlag

       Possibilities:
               disabled   (0)
               enabled   (1)"
   ::= {er1645v2EthPortSwIVlanIpV6AddressesEntry 67371008}

er1645v2EthPortSwIVlanIpV6AddressesRaAutoFlag OBJECT-TYPE
   SYNTAX      INTEGER
               {
               disabled (0),
               enabled (1)
               }
   MAX-ACCESS  read-write
   STATUS      current
   DESCRIPTION
      "Path: swPort.editConf.vlan.ipV6.addresses.ra.autonomousFlag

       Possibilities:
               disabled   (0)
               enabled   (1)"
   ::= {er1645v2EthPortSwIVlanIpV6AddressesEntry 67567616}

er1645v2EthPortSwIVlanIpV6AddressesRaValidLifeTime OBJECT-TYPE
   SYNTAX      TimeTicks
   MAX-ACCESS  read-write
   STATUS      current
   DESCRIPTION
      "Path: swPort.editConf.vlan.ipV6.addresses.ra.validLifeTime

       Time in centi-second."
   ::= {er1645v2EthPortSwIVlanIpV6AddressesEntry 67239936}

er1645v2EthPortSwIVlanIpV6AddressesRaValidLTMode OBJECT-TYPE
   SYNTAX      INTEGER
               {
               fixed (0),
               infinite (2)
               }
   MAX-ACCESS  read-write
   STATUS      current
   DESCRIPTION
      "Path: swPort.editConf.vlan.ipV6.addresses.ra.validLifeTimeMode

       Possibilities:
               fixed   (0)
               infinite   (2)"
   ::= {er1645v2EthPortSwIVlanIpV6AddressesEntry 67305472}

er1645v2EthPortSwIVlanIpV6AddressesRaPrefLifeTime OBJECT-TYPE
   SYNTAX      TimeTicks
   MAX-ACCESS  read-write
   STATUS      current
   DESCRIPTION
      "Path: swPort.editConf.vlan.ipV6.addresses.ra.prefLifeTime

       Time in centi-second."
   ::= {er1645v2EthPortSwIVlanIpV6AddressesEntry 67436544}

er1645v2EthPortSwIVlanIpV6AddressesRaPrefLTMode OBJECT-TYPE
   SYNTAX      INTEGER
               {
               fixed (0),
               infinite (2)
               }
   MAX-ACCESS  read-write
   STATUS      current
   DESCRIPTION
      "Path: swPort.editConf.vlan.ipV6.addresses.ra.prefLifeTimeMode

       Possibilities:
               fixed   (0)
               infinite   (2)"
   ::= {er1645v2EthPortSwIVlanIpV6AddressesEntry 67502080}

er1645v2EthPortSwIVlanIpV6RaDnsOptionsRdnssServers OBJECT-TYPE
   SYNTAX      SEQUENCE OF Er1645v2EthPortSwIVlanIpV6RaDnsOptionsRdnssServersEntry
   MAX-ACCESS  not-accessible
   STATUS      current
   DESCRIPTION
      ""
   ::= {er1645v2EthPortSwIVlan 705039144}

er1645v2EthPortSwIVlanIpV6RaDnsOptionsRdnssServersEntry OBJECT-TYPE
   SYNTAX      Er1645v2EthPortSwIVlanIpV6RaDnsOptionsRdnssServersEntry
   MAX-ACCESS  not-accessible
   STATUS      current
   DESCRIPTION
      ""
   INDEX      { er1645v2EthPortSwIVlanIpV6RaDnsOptionsRdnssServersGlobalIx,
                er1645v2EthPortSwIVlanTableIx,
                er1645v2EthPortSwIVlanIpV6RaDnsOptionsRdnssServersTableIx }
   ::= {er1645v2EthPortSwIVlanIpV6RaDnsOptionsRdnssServers 1}

Er1645v2EthPortSwIVlanIpV6RaDnsOptionsRdnssServersEntry ::=
   SEQUENCE
      {
      er1645v2EthPortSwIVlanIpV6RaDnsOptionsRdnssServersActions
         VariableLengthTableActions,
      er1645v2EthPortSwIVlanIpV6RaDnsOptionsRdnssServersGlobalIx
         GlobalIndex,
      er1645v2EthPortSwIVlanIpV6RaDnsOptionsRdnssServersTableIx
         TableIndex,
      er1645v2EthPortSwIVlanIpV6RaDnsOptionsRdnssServersAddress
         Ipv6Address
      }

er1645v2EthPortSwIVlanIpV6RaDnsOptionsRdnssServersActions OBJECT-TYPE
   SYNTAX      VariableLengthTableActions
   MAX-ACCESS  read-write
   STATUS      current
   DESCRIPTION
      "By way of this field, some manipulations
       on this table may be performed."
   ::= {er1645v2EthPortSwIVlanIpV6RaDnsOptionsRdnssServersEntry 2}

er1645v2EthPortSwIVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6RaDnsOptionsRdnssServersEntry 10}

er1645v2EthPortSwIVlanIpV6RaDnsOptionsRdnssServersTableIx OBJECT-TYPE
   SYNTAX      TableIndex
   MAX-ACCESS  not-accessible
   STATUS      current
   DESCRIPTION
      ""
   ::= {er1645v2EthPortSwIVlanIpV6RaDnsOptionsRdnssServersEntry 11}

er1645v2EthPortSwIVlanIpV6RaDnsOptionsRdnssServersAddress OBJECT-TYPE
   SYNTAX      Ipv6Address
   MAX-ACCESS  read-write
   STATUS      current
   DESCRIPTION
      "Path: swPort.editConf.vlan.ipV6.ra.dnsOptions.rdnss.servers.address

       ipv6 address"
   ::= {er1645v2EthPortSwIVlanIpV6RaDnsOptionsRdnssServersEntry 16777216}

er1645v2EthPortSwIVlanIpV6RaDnsOptionsDnsslDomains OBJECT-TYPE
   SYNTAX      SEQUENCE OF Er1645v2EthPortSwIVlanIpV6RaDnsOptionsDnsslDomainsEntry
   MAX-ACCESS  not-accessible
   STATUS      current
   DESCRIPTION
      ""
   ::= {er1645v2EthPortSwIVlan 705039176}

er1645v2EthPortSwIVlanIpV6RaDnsOptionsDnsslDomainsEntry OBJECT-TYPE
   SYNTAX      Er1645v2EthPortSwIVlanIpV6RaDnsOptionsDnsslDomainsEntry
   MAX-ACCESS  not-accessible
   STATUS      current
   DESCRIPTION
      ""
   INDEX      { er1645v2EthPortSwIVlanIpV6RaDnsOptionsDnsslDomainsGlobalIx,
                er1645v2EthPortSwIVlanTableIx,
                er1645v2EthPortSwIVlanIpV6RaDnsOptionsDnsslDomainsTableIx }
   ::= {er1645v2EthPortSwIVlanIpV6RaDnsOptionsDnsslDomains 1}

Er1645v2EthPortSwIVlanIpV6RaDnsOptionsDnsslDomainsEntry ::=
   SEQUENCE
      {
      er1645v2EthPortSwIVlanIpV6RaDnsOptionsDnsslDomainsActions
         VariableLengthTableActions,
      er1645v2EthPortSwIVlanIpV6RaDnsOptionsDnsslDomainsGlobalIx
         GlobalIndex,
      er1645v2EthPortSwIVlanIpV6RaDnsOptionsDnsslDomainsTableIx
         TableIndex,
      er1645v2EthPortSwIVlanIpV6RaDnsOptionsDnsslDomainsName
         DisplayString
      }

er1645v2EthPortSwIVlanIpV6RaDnsOptionsDnsslDomainsActions OBJECT-TYPE
   SYNTAX      VariableLengthTableActions
   MAX-ACCESS  read-write
   STATUS      current
   DESCRIPTION
      "By way of this field, some manipulations
       on this table may be performed."
   ::= {er1645v2EthPortSwIVlanIpV6RaDnsOptionsDnsslDomainsEntry 2}

er1645v2EthPortSwIVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6RaDnsOptionsDnsslDomainsEntry 10}

er1645v2EthPortSwIVlanIpV6RaDnsOptionsDnsslDomainsTableIx OBJECT-TYPE
   SYNTAX      TableIndex
   MAX-ACCESS  not-accessible
   STATUS      current
   DESCRIPTION
      ""
   ::= {er1645v2EthPortSwIVlanIpV6RaDnsOptionsDnsslDomainsEntry 11}

er1645v2EthPortSwIVlanIpV6RaDnsOptionsDnsslDomainsName OBJECT-TYPE
   SYNTAX      DisplayString
   MAX-ACCESS  read-write
   STATUS      current
   DESCRIPTION
      "Path: swPort.editConf.vlan.ipV6.ra.dnsOptions.dnssl.domains.name"
   ::= {er1645v2EthPortSwIVlanIpV6RaDnsOptionsDnsslDomainsEntry 16777216}

er1645v2EthPortSwIVlanIpV6DhcpClientUserClassOpt OBJECT-TYPE
   SYNTAX      SEQUENCE OF Er1645v2EthPortSwIVlanIpV6DhcpClientUserClassOptEntry
   MAX-ACCESS  not-accessible
   STATUS      current
   DESCRIPTION
      ""
   ::= {er1645v2EthPortSwIVlan 705312768}

er1645v2EthPortSwIVlanIpV6DhcpClientUserClassOptEntry OBJECT-TYPE
   SYNTAX      Er1645v2EthPortSwIVlanIpV6DhcpClientUserClassOptEntry
   MAX-ACCESS  not-accessible
   STATUS      current
   DESCRIPTION
      ""
   INDEX      { er1645v2EthPortSwIVlanIpV6DhcpClientUserClassOptGlobalIx,
                er1645v2EthPortSwIVlanTableIx,
                er1645v2EthPortSwIVlanIpV6DhcpClientUserClassOptTableIx }
   ::= {er1645v2EthPortSwIVlanIpV6DhcpClientUserClassOpt 1}

Er1645v2EthPortSwIVlanIpV6DhcpClientUserClassOptEntry ::=
   SEQUENCE
      {
      er1645v2EthPortSwIVlanIpV6DhcpClientUserClassOptActions
         VariableLengthTableActions,
      er1645v2EthPortSwIVlanIpV6DhcpClientUserClassOptGlobalIx
         GlobalIndex,
      er1645v2EthPortSwIVlanIpV6DhcpClientUserClassOptTableIx
         TableIndex,
      er1645v2EthPortSwIVlanIpV6DhcpClientUserClassOptValueAscii
         DisplayString,
      er1645v2EthPortSwIVlanIpV6DhcpClientUserClassOptValueDecimal
         Integer32,
      er1645v2EthPortSwIVlanIpV6DhcpClientUserClassOptValueHexData
         OCTET STRING
      }

er1645v2EthPortSwIVlanIpV6DhcpClientUserClassOptActions OBJECT-TYPE
   SYNTAX      VariableLengthTableActions
   MAX-ACCESS  read-write
   STATUS      current
   DESCRIPTION
      "By way of this field, some manipulations
       on this table may be performed."
   ::= {er1645v2EthPortSwIVlanIpV6DhcpClientUserClassOptEntry 2}

er1645v2EthPortSwIVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6DhcpClientUserClassOptEntry 10}

er1645v2EthPortSwIVlanIpV6DhcpClientUserClassOptTableIx OBJECT-TYPE
   SYNTAX      TableIndex
   MAX-ACCESS  not-accessible
   STATUS      current
   DESCRIPTION
      ""
   ::= {er1645v2EthPortSwIVlanIpV6DhcpClientUserClassOptEntry 11}

er1645v2EthPortSwIVlanIpV6DhcpClientUserClassOptValueAscii OBJECT-TYPE
   SYNTAX      DisplayString
   MAX-ACCESS  read-write
   STATUS      current
   DESCRIPTION
      "Path: swPort.editConf.vlan.ipV6.dhcp.client.userClassOpt.value.ascii"
   ::= {er1645v2EthPortSwIVlanIpV6DhcpClientUserClassOptEntry 16842752}

er1645v2EthPortSwIVlanIpV6DhcpClientUserClassOptValueDecimal OBJECT-TYPE
   SYNTAX      Integer32
   MAX-ACCESS  read-write
   STATUS      current
   DESCRIPTION
      "Path: swPort.editConf.vlan.ipV6.dhcp.client.userClassOpt.value.decimal"
   ::= {er1645v2EthPortSwIVlanIpV6DhcpClientUserClassOptEntry 16908288}

er1645v2EthPortSwIVlanIpV6DhcpClientUserClassOptValueHexData OBJECT-TYPE
   SYNTAX      OCTET STRING
   MAX-ACCESS  read-write
   STATUS      current
   DESCRIPTION
      "Path: swPort.editConf.vlan.ipV6.dhcp.client.userClassOpt.value.hexData"
   ::= {er1645v2EthPortSwIVlanIpV6DhcpClientUserClassOptEntry 16973824}

er1645v2EthPortSwIVlanIpV6DhcpClientVendorCl OBJECT-TYPE
   SYNTAX      SEQUENCE OF Er1645v2EthPortSwIVlanIpV6DhcpClientVendorClEntry
   MAX-ACCESS  not-accessible
   STATUS      current
   DESCRIPTION
      ""
   ::= {er1645v2EthPortSwIVlan 705313792}

er1645v2EthPortSwIVlanIpV6DhcpClientVendorClEntry OBJECT-TYPE
   SYNTAX      Er1645v2EthPortSwIVlanIpV6DhcpClientVendorClEntry
   MAX-ACCESS  not-accessible
   STATUS      current
   DESCRIPTION
      ""
   INDEX      { er1645v2EthPortSwIVlanIpV6DhcpClientVendorClGlobalIx,
                er1645v2EthPortSwIVlanTableIx,
                er1645v2EthPortSwIVlanIpV6DhcpClientVendorClTableIx }
   ::= {er1645v2EthPortSwIVlanIpV6DhcpClientVendorCl 1}

Er1645v2EthPortSwIVlanIpV6DhcpClientVendorClEntry ::=
   SEQUENCE
      {
      er1645v2EthPortSwIVlanIpV6DhcpClientVendorClActions
         VariableLengthTableActions,
      er1645v2EthPortSwIVlanIpV6DhcpClientVendorClGlobalIx
         GlobalIndex,
      er1645v2EthPortSwIVlanIpV6DhcpClientVendorClTableIx
         TableIndex,
      er1645v2EthPortSwIVlanIpV6DhcpClientVendorClValueAscii
         DisplayString,
      er1645v2EthPortSwIVlanIpV6DhcpClientVendorClValueDecimal
         Integer32,
      er1645v2EthPortSwIVlanIpV6DhcpClientVendorClValueHexData
         OCTET STRING
      }

er1645v2EthPortSwIVlanIpV6DhcpClientVendorClActions OBJECT-TYPE
   SYNTAX      VariableLengthTableActions
   MAX-ACCESS  read-write
   STATUS      current
   DESCRIPTION
      "By way of this field, some manipulations
       on this table may be performed."
   ::= {er1645v2EthPortSwIVlanIpV6DhcpClientVendorClEntry 2}

er1645v2EthPortSwIVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6DhcpClientVendorClEntry 10}

er1645v2EthPortSwIVlanIpV6DhcpClientVendorClTableIx OBJECT-TYPE
   SYNTAX      TableIndex
   MAX-ACCESS  not-accessible
   STATUS      current
   DESCRIPTION
      ""
   ::= {er1645v2EthPortSwIVlanIpV6DhcpClientVendorClEntry 11}

er1645v2EthPortSwIVlanIpV6DhcpClientVendorClValueAscii OBJECT-TYPE
   SYNTAX      DisplayString
   MAX-ACCESS  read-write
   STATUS      current
   DESCRIPTION
      "Path: swPort.editConf.vlan.ipV6.dhcp.client.vendorClassOpt.value.ascii"
   ::= {er1645v2EthPortSwIVlanIpV6DhcpClientVendorClEntry 16842752}

er1645v2EthPortSwIVlanIpV6DhcpClientVendorClValueDecimal OBJECT-TYPE
   SYNTAX      Integer32
   MAX-ACCESS  read-write
   STATUS      current
   DESCRIPTION
      "Path: swPort.editConf.vlan.ipV6.dhcp.client.vendorClassOpt.value.decimal"
   ::= {er1645v2EthPortSwIVlanIpV6DhcpClientVendorClEntry 16908288}

er1645v2EthPortSwIVlanIpV6DhcpClientVendorClValueHexData OBJECT-TYPE
   SYNTAX      OCTET STRING
   MAX-ACCESS  read-write
   STATUS      current
   DESCRIPTION
      "Path: swPort.editConf.vlan.ipV6.dhcp.client.vendorClassOpt.value.hexData"
   ::= {er1645v2EthPortSwIVlanIpV6DhcpClientVendorClEntry 16973824}

er1645v2EthPortSwIVlanIpV6DhcpRelayDestinations OBJECT-TYPE
   SYNTAX      SEQUENCE OF Er1645v2EthPortSwIVlanIpV6DhcpRelayDestinationsEntry
   MAX-ACCESS  not-accessible
   STATUS      current
   DESCRIPTION
      ""
   ::= {er1645v2EthPortSwIVlan 705323072}

er1645v2EthPortSwIVlanIpV6DhcpRelayDestinationsEntry OBJECT-TYPE
   SYNTAX      Er1645v2EthPortSwIVlanIpV6DhcpRelayDestinationsEntry
   MAX-ACCESS  not-accessible
   STATUS      current
   DESCRIPTION
      ""
   INDEX      { er1645v2EthPortSwIVlanIpV6DhcpRelayDestinationsGlobalIx,
                er1645v2EthPortSwIVlanTableIx,
                er1645v2EthPortSwIVlanIpV6DhcpRelayDestinationsTableIx }
   ::= {er1645v2EthPortSwIVlanIpV6DhcpRelayDestinations 1}

Er1645v2EthPortSwIVlanIpV6DhcpRelayDestinationsEntry ::=
   SEQUENCE
      {
      er1645v2EthPortSwIVlanIpV6DhcpRelayDestinationsActions
         VariableLengthTableActions,
      er1645v2EthPortSwIVlanIpV6DhcpRelayDestinationsGlobalIx
         GlobalIndex,
      er1645v2EthPortSwIVlanIpV6DhcpRelayDestinationsTableIx
         TableIndex,
      er1645v2EthPortSwIVlanIpV6DhcpRelayDestinationsAddress
         Ipv6Address,
      er1645v2EthPortSwIVlanIpV6DhcpRelayDestinationsInterface
         DisplayString
      }

er1645v2EthPortSwIVlanIpV6DhcpRelayDestinationsActions OBJECT-TYPE
   SYNTAX      VariableLengthTableActions
   MAX-ACCESS  read-write
   STATUS      current
   DESCRIPTION
      "By way of this field, some manipulations
       on this table may be performed."
   ::= {er1645v2EthPortSwIVlanIpV6DhcpRelayDestinationsEntry 2}

er1645v2EthPortSwIVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPortSwIVlanIpV6DhcpRelayDestinationsEntry 10}

er1645v2EthPortSwIVlanIpV6DhcpRelayDestinationsTableIx OBJECT-TYPE
   SYNTAX      TableIndex
   MAX-ACCESS  not-accessible
   STATUS      current
   DESCRIPTION
      ""
   ::= {er1645v2EthPortSwIVlanIpV6DhcpRelayDestinationsEntry 11}

er1645v2EthPortSwIVlanIpV6DhcpRelayDestinationsAddress OBJECT-TYPE
   SYNTAX      Ipv6Address
   MAX-ACCESS  read-write
   STATUS      current
   DESCRIPTION
      "Path: swPort.editConf.vlan.ipV6.dhcp.relay.destinations.address

       ipv6 address"
   ::= {er1645v2EthPortSwIVlanIpV6DhcpRelayDestinationsEntry 16777216}

er1645v2EthPortSwIVlanIpV6DhcpRelayDestinationsInterface OBJECT-TYPE
   SYNTAX      DisplayString
   MAX-ACCESS  read-write
   STATUS      current
   DESCRIPTION
      "Path: swPort.editConf.vlan.ipV6.dhcp.relay.destinations.interface"
   ::= {er1645v2EthPortSwIVlanIpV6DhcpRelayDestinationsEntry 33554432}

er1645v2EthPortSwIVlanBridgingVlTVlans OBJECT-TYPE
   SYNTAX      SEQUENCE OF Er1645v2EthPortSwIVlanBridgingVlTVlansEntry
   MAX-ACCESS  not-accessible
   STATUS      current
   DESCRIPTION
      ""
   ::= {er1645v2EthPortSwIVlan 459079680}

er1645v2EthPortSwIVlanBridgingVlTVlansEntry OBJECT-TYPE
   SYNTAX      Er1645v2EthPortSwIVlanBridgingVlTVlansEntry
   MAX-ACCESS  not-accessible
   STATUS      current
   DESCRIPTION
      ""
   INDEX      { er1645v2EthPortSwIVlanBridgingVlTVlansGlobalIx,
                er1645v2EthPortSwIVlanTableIx,
                er1645v2EthPortSwIVlanBridgingVlTVlansTableIx }
   ::= {er1645v2EthPortSwIVlanBridgingVlTVlans 1}

Er1645v2EthPortSwIVlanBridgingVlTVlansEntry ::=
   SEQUENCE
      {
      er1645v2EthPortSwIVlanBridgingVlTVlansActions
         VariableLengthTableActions,
      er1645v2EthPortSwIVlanBridgingVlTVlansGlobalIx
         GlobalIndex,
      er1645v2EthPortSwIVlanBridgingVlTVlansTableIx
         TableIndex,
      er1645v2EthPortSwIVlanBridgingVlTVlansVid
         Integer32,
      er1645v2EthPortSwIVlanBridgingVlTVlansEndVid
         Integer32,
      er1645v2EthPortSwIVlanBridgingVlTVlansAction
         INTEGER,
      er1645v2EthPortSwIVlanBridgingVlTVlansTagInfoTpid
         INTEGER,
      er1645v2EthPortSwIVlanBridgingVlTVlansTagInfoVid
         Integer32
      }

er1645v2EthPortSwIVlanBridgingVlTVlansActions OBJECT-TYPE
   SYNTAX      VariableLengthTableActions
   MAX-ACCESS  read-write
   STATUS      current
   DESCRIPTION
      "By way of this field, some manipulations
       on this table may be performed."
   ::= {er1645v2EthPortSwIVlanBridgingVlTVlansEntry 2}

er1645v2EthPortSwIVlanBridgingVlTVlansGlobalIx OBJECT-TYPE
   SYNTAX      GlobalIndex
   MAX-ACCESS  not-accessible
   STATUS      current
   DESCRIPTION
      "The value of the tlsCntTreeGlobalIndex of the MANAGED OBJECT."
   ::= {er1645v2EthPortSwIVlanBridgingVlTVlansEntry 10}

er1645v2EthPortSwIVlanBridgingVlTVlansTableIx OBJECT-TYPE
   SYNTAX      TableIndex
   MAX-ACCESS  not-accessible
   STATUS      current
   DESCRIPTION
      ""
   ::= {er1645v2EthPortSwIVlanBridgingVlTVlansEntry 11}

er1645v2EthPortSwIVlanBridgingVlTVlansVid OBJECT-TYPE
   SYNTAX      Integer32
   MAX-ACCESS  read-write
   STATUS      current
   DESCRIPTION
      "Path: swPort.editConf.vlan.bridging.vlanTagging.vlans.vid"
   ::= {er1645v2EthPortSwIVlanBridgingVlTVlansEntry 536870912}

er1645v2EthPortSwIVlanBridgingVlTVlansEndVid OBJECT-TYPE
   SYNTAX      Integer32
   MAX-ACCESS  read-write
   STATUS      current
   DESCRIPTION
      "Path: swPort.editConf.vlan.bridging.vlanTagging.vlans.endVid"
   ::= {er1645v2EthPortSwIVlanBridgingVlTVlansEntry 2147483648}

er1645v2EthPortSwIVlanBridgingVlTVlansAction OBJECT-TYPE
   SYNTAX      INTEGER
               {
               discard (0),
               accept (1),
               tag (2)
               }
   MAX-ACCESS  read-write
   STATUS      current
   DESCRIPTION
      "Path: swPort.editConf.vlan.bridging.vlanTagging.vlans.action

       Possibilities:
               discard   (0)
               accept   (1)
               tag   (2)"
   ::= {er1645v2EthPortSwIVlanBridgingVlTVlansEntry 1073741824}

er1645v2EthPortSwIVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.vlans.tagInfo.tpid

       Possibilities:
               dot1Q   (33024)
               dot1ad   (34984)
               0x9100   (37120)
               0x9200   (37376)
               0x9300   (37632)"
   ::= {er1645v2EthPortSwIVlanBridgingVlTVlansEntry 1677721600}

er1645v2EthPortSwIVlanBridgingVlTVlansTagInfoVid OBJECT-TYPE
   SYNTAX      Integer32
   MAX-ACCESS  read-write
   STATUS      current
   DESCRIPTION
      "Path: swPort.editConf.vlan.bridging.vlanTagging.vlans.tagInfo.vid"
   ::= {er1645v2EthPortSwIVlanBridgingVlTVlansEntry 1744830464}

er1645v2EthPortSwIVlanVlanVidExtensionTable OBJECT-TYPE
   SYNTAX      SEQUENCE OF Er1645v2EthPortSwIVlanVlanVidExtensionTableEntry
   MAX-ACCESS  not-accessible
   STATUS      current
   DESCRIPTION
      ""
   ::= {er1645v2EthPortSwIVlan 235340544}

er1645v2EthPortSwIVlanVlanVidExtensionTableEntry OBJECT-TYPE
   SYNTAX      Er1645v2EthPortSwIVlanVlanVidExtensionTableEntry
   MAX-ACCESS  not-accessible
   STATUS      current
   DESCRIPTION
      ""
   INDEX      { er1645v2EthPortSwIVlanVlanVidExtensionTableGlobalIx,
                er1645v2EthPortSwIVlanTableIx,
                er1645v2EthPortSwIVlanVlanVidExtensionTableTableIx }
   ::= {er1645v2EthPortSwIVlanVlanVidExtensionTable 1}

Er1645v2EthPortSwIVlanVlanVidExtensionTableEntry ::=
   SEQUENCE
      {
      er1645v2EthPortSwIVlanVlanVidExtensionTableActions
         VariableLengthTableActions,
      er1645v2EthPortSwIVlanVlanVidExtensionTableGlobalIx
         GlobalIndex,
      er1645v2EthPortSwIVlanVlanVidExtensionTableTableIx
         TableIndex,
      er1645v2EthPortSwIVlanVlanVidExtensionTableTpid
         INTEGER,
      er1645v2EthPortSwIVlanVlanVidExtensionTableVid
         Integer32,
      er1645v2EthPortSwIVlanVlanVidExtensionTableEndVid
         Integer32
      }

er1645v2EthPortSwIVlanVlanVidExtensionTableActions OBJECT-TYPE
   SYNTAX      VariableLengthTableActions
   MAX-ACCESS  read-write
   STATUS      current
   DESCRIPTION
      "By way of this field, some manipulations
       on this table may be performed."
   ::= {er1645v2EthPortSwIVlanVlanVidExtensionTableEntry 2}

er1645v2EthPortSwIVlanVlanVidExtensionTableGlobalIx OBJECT-TYPE
   SYNTAX      GlobalIndex
   MAX-ACCESS  not-accessible
   STATUS      current
   DESCRIPTION
      "The value of the tlsCntTreeGlobalIndex of the MANAGED OBJECT."
   ::= {er1645v2EthPortSwIVlanVlanVidExtensionTableEntry 10}

er1645v2EthPortSwIVlanVlanVidExtensionTableTableIx OBJECT-TYPE
   SYNTAX      TableIndex
   MAX-ACCESS  not-accessible
   STATUS      current
   DESCRIPTION
      ""
   ::= {er1645v2EthPortSwIVlanVlanVidExtensionTableEntry 11}

er1645v2EthPortSwIVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.vidExtension.table.tpid

       Possibilities:
               dot1Q   (33024)
               dot1ad   (34984)
               0x9100   (37120)
               0x9200   (37376)
               0x9300   (37632)"
   ::= {er1645v2EthPortSwIVlanVlanVidExtensionTableEntry 16777216}

er1645v2EthPortSwIVlanVlanVidExtensionTableVid OBJECT-TYPE
   SYNTAX      Integer32
   MAX-ACCESS  read-write
   STATUS      current
   DESCRIPTION
      "Path: swPort.editConf.vlan.vlan.vidExtension.table.vid"
   ::= {er1645v2EthPortSwIVlanVlanVidExtensionTableEntry 33554432}

er1645v2EthPortSwIVlanVlanVidExtensionTableEndVid OBJECT-TYPE
   SYNTAX      Integer32
   MAX-ACCESS  read-write
   STATUS      current
   DESCRIPTION
      "Path: swPort.editConf.vlan.vlan.vidExtension.table.endVid"
   ::= {er1645v2EthPortSwIVlanVlanVidExtensionTableEntry 50331648}

er1645v2EthPortSwIVlanVlanCSMap OBJECT-TYPE
   SYNTAX      SEQUENCE OF Er1645v2EthPortSwIVlanVlanCSMapEntry
   MAX-ACCESS  not-accessible
   STATUS      current
   DESCRIPTION
      ""
   ::= {er1645v2EthPortSwIVlan 235405312}

er1645v2EthPortSwIVlanVlanCSMapEntry OBJECT-TYPE
   SYNTAX      Er1645v2EthPortSwIVlanVlanCSMapEntry
   MAX-ACCESS  not-accessible
   STATUS      current
   DESCRIPTION
      ""
   INDEX      { er1645v2EthPortSwIVlanVlanCSMapGlobalIx,
                er1645v2EthPortSwIVlanTableIx,
                er1645v2EthPortSwIVlanVlanCSMapTableIx }
   ::= {er1645v2EthPortSwIVlanVlanCSMap 1}

Er1645v2EthPortSwIVlanVlanCSMapEntry ::=
   SEQUENCE
      {
      er1645v2EthPortSwIVlanVlanCSMapActions
         VariableLengthTableActions,
      er1645v2EthPortSwIVlanVlanCSMapGlobalIx
         GlobalIndex,
      er1645v2EthPortSwIVlanVlanCSMapTableIx
         TableIndex,
      er1645v2EthPortSwIVlanVlanCSMapCos
         INTEGER,
      er1645v2EthPortSwIVlanVlanCSMapDei
         INTEGER,
      er1645v2EthPortSwIVlanVlanCSMapTos
         INTEGER,
      er1645v2EthPortSwIVlanVlanCSMapQueue
         INTEGER,
      er1645v2EthPortSwIVlanVlanCSMapDropLevel
         INTEGER,
      er1645v2EthPortSwIVlanVlanCSMapDeFlag
         INTEGER
      }

er1645v2EthPortSwIVlanVlanCSMapActions OBJECT-TYPE
   SYNTAX      VariableLengthTableActions
   MAX-ACCESS  read-write
   STATUS      current
   DESCRIPTION
      "By way of this field, some manipulations
       on this table may be performed."
   ::= {er1645v2EthPortSwIVlanVlanCSMapEntry 2}

er1645v2EthPortSwIVlanVlanCSMapGlobalIx OBJECT-TYPE
   SYNTAX      GlobalIndex
   MAX-ACCESS  not-accessible
   STATUS      current
   DESCRIPTION
      "The value of the tlsCntTreeGlobalIndex of the MANAGED OBJECT."
   ::= {er1645v2EthPortSwIVlanVlanCSMapEntry 10}

er1645v2EthPortSwIVlanVlanCSMapTableIx OBJECT-TYPE
   SYNTAX      TableIndex
   MAX-ACCESS  not-accessible
   STATUS      current
   DESCRIPTION
      ""
   ::= {er1645v2EthPortSwIVlanVlanCSMapEntry 11}

er1645v2EthPortSwIVlanVlanCSMapCos OBJECT-TYPE
   SYNTAX      INTEGER
               {
               any (8)
               }
   MAX-ACCESS  read-write
   STATUS      current
   DESCRIPTION
      "Path: swPort.editConf.vlan.vlan.cosMap.cos

       Possibilities:
               any   (8)"
   ::= {er1645v2EthPortSwIVlanVlanCSMapEntry 16777216}

er1645v2EthPortSwIVlanVlanCSMapDei OBJECT-TYPE
   SYNTAX      INTEGER
               {
               clear (0),
               set (1),
               any (2)
               }
   MAX-ACCESS  read-write
   STATUS      current
   DESCRIPTION
      "Path: swPort.editConf.vlan.vlan.cosMap.dei

       Possibilities:
               clear   (0)
               set   (1)
               any   (2)"
   ::= {er1645v2EthPortSwIVlanVlanCSMapEntry 33554432}

er1645v2EthPortSwIVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPortSwIVlanVlanCSMapEntry 50331648}

er1645v2EthPortSwIVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2EthPortSwIVlanVlanCSMapEntry 67108864}

er1645v2EthPortSwIVlanVlanCSMapDropLevel OBJECT-TYPE
   SYNTAX      INTEGER
               {
               unchanged (-1),
               dropOnQueue (0)
               }
   MAX-ACCESS  read-write
   STATUS      current
   DESCRIPTION
      "Path: swPort.editConf.vlan.vlan.cosMap.dropLevel

       Possibilities:
               unchanged   (-1)
               dropOnQueue   (0)"
   ::= {er1645v2EthPortSwIVlanVlanCSMapEntry 83886080}

er1645v2EthPortSwIVlanVlanCSMapDeFlag OBJECT-TYPE
   SYNTAX      INTEGER
               {
               unchanged (255),
               clear (0),
               set (1)
               }
   MAX-ACCESS  read-write
   STATUS      current
   DESCRIPTION
      "Path: swPort.editConf.vlan.vlan.cosMap.deFlag

       Possibilities:
               unchanged   (255)
               clear   (0)
               set   (1)"
   ::= {er1645v2EthPortSwIVlanVlanCSMapEntry 117440512}

er1645v2EthPortSwIVlanVlanTCMap OBJECT-TYPE
   SYNTAX      SEQUENCE OF Er1645v2EthPortSwIVlanVlanTCMapEntry
   MAX-ACCESS  not-accessible
   STATUS      current
   DESCRIPTION
      ""
   ::= {er1645v2EthPortSwIVlan 241369088}

er1645v2EthPortSwIVlanVlanTCMapEntry OBJECT-TYPE
   SYNTAX      Er1645v2EthPortSwIVlanVlanTCMapEntry
   MAX-ACCESS  not-accessible
   STATUS      current
   DESCRIPTION
      ""
   INDEX      { er1645v2EthPortSwIVlanVlanTCMapGlobalIx,
                er1645v2EthPortSwIVlanTableIx,
                er1645v2EthPortSwIVlanVlanTCMapTableIx }
   ::= {er1645v2EthPortSwIVlanVlanTCMap 1}

Er1645v2EthPortSwIVlanVlanTCMapEntry ::=
   SEQUENCE
      {
      er1645v2EthPortSwIVlanVlanTCMapActions
         VariableLengthTableActions,
      er1645v2EthPortSwIVlanVlanTCMapGlobalIx
         GlobalIndex,
      er1645v2EthPortSwIVlanVlanTCMapTableIx
         TableIndex,
      er1645v2EthPortSwIVlanVlanTCMapStartTos
         INTEGER,
      er1645v2EthPortSwIVlanVlanTCMapEndTos
         INTEGER,
      er1645v2EthPortSwIVlanVlanTCMapCos
         INTEGER
      }

er1645v2EthPortSwIVlanVlanTCMapActions OBJECT-TYPE
   SYNTAX      VariableLengthTableActions
   MAX-ACCESS  read-write
   STATUS      current
   DESCRIPTION
      "By way of this field, some manipulations
       on this table may be performed."
   ::= {er1645v2EthPortSwIVlanVlanTCMapEntry 2}

er1645v2EthPortSwIVlanVlanTCMapGlobalIx OBJECT-TYPE
   SYNTAX      GlobalIndex
   MAX-ACCESS  not-accessible
   STATUS      current
   DESCRIPTION
      "The value of the tlsCntTreeGlobalIndex of the MANAGED OBJECT."
   ::= {er1645v2EthPortSwIVlanVlanTCMapEntry 10}

er1645v2EthPortSwIVlanVlanTCMapTableIx OBJECT-TYPE
   SYNTAX      TableIndex
   MAX-ACCESS  not-accessible
   STATUS      current
   DESCRIPTION
      ""
   ::= {er1645v2EthPortSwIVlanVlanTCMapEntry 11}

er1645v2EthPortSwIVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2EthPortSwIVlanVlanTCMapEntry 16777216}

er1645v2EthPortSwIVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2EthPortSwIVlanVlanTCMapEntry 33554432}

er1645v2EthPortSwIVlanVlanTCMapCos OBJECT-TYPE
   SYNTAX      INTEGER
               {
               queueCosMap (8)
               }
   MAX-ACCESS  read-write
   STATUS      current
   DESCRIPTION
      "Path: swPort.editConf.vlan.vlan.tosCosMap.cos

       Possibilities:
               queueCosMap   (8)"
   ::= {er1645v2EthPortSwIVlanVlanTCMapEntry 50331648}

er1645v2EthPortSwIVlanVlanArpStaticArp OBJECT-TYPE
   SYNTAX      SEQUENCE OF Er1645v2EthPortSwIVlanVlanArpStaticArpEntry
   MAX-ACCESS  not-accessible
   STATUS      current
   DESCRIPTION
      ""
   ::= {er1645v2EthPortSwIVlan 235275008}

er1645v2EthPortSwIVlanVlanArpStaticArpEntry OBJECT-TYPE
   SYNTAX      Er1645v2EthPortSwIVlanVlanArpStaticArpEntry
   MAX-ACCESS  not-accessible
   STATUS      current
   DESCRIPTION
      ""
   INDEX      { er1645v2EthPortSwIVlanVlanArpStaticArpGlobalIx,
                er1645v2EthPortSwIVlanTableIx,
                er1645v2EthPortSwIVlanVlanArpStaticArpTableIx }
   ::= {er1645v2EthPortSwIVlanVlanArpStaticArp 1}

Er1645v2EthPortSwIVlanVlanArpStaticArpEntry ::=
   SEQUENCE
      {
      er1645v2EthPortSwIVlanVlanArpStaticArpActions
         VariableLengthTableActions,
      er1645v2EthPortSwIVlanVlanArpStaticArpGlobalIx
         GlobalIndex,
      er1645v2EthPortSwIVlanVlanArpStaticArpTableIx
         TableIndex,
      er1645v2EthPortSwIVlanVlanArpStaticArpMacAddress
         OCTET STRING,
      er1645v2EthPortSwIVlanVlanArpStaticArpIpAddress
         IpAddress
      }

er1645v2EthPortSwIVlanVlanArpStaticArpActions OBJECT-TYPE
   SYNTAX      VariableLengthTableActions
   MAX-ACCESS  read-write
   STATUS      current
   DESCRIPTION
      "By way of this field, some manipulations
       on this table may be performed."
   ::= {er1645v2EthPortSwIVlanVlanArpStaticArpEntry 2}

er1645v2EthPortSwIVlanVlanArpStaticArpGlobalIx OBJECT-TYPE
   SYNTAX      GlobalIndex
   MAX-ACCESS  not-accessible
   STATUS      current
   DESCRIPTION
      "The value of the tlsCntTreeGlobalIndex of the MANAGED OBJECT."
   ::= {er1645v2EthPortSwIVlanVlanArpStaticArpEntry 10}

er1645v2EthPortSwIVlanVlanArpStaticArpTableIx OBJECT-TYPE
   SYNTAX      TableIndex
   MAX-ACCESS  not-accessible
   STATUS      current
   DESCRIPTION
      ""
   ::= {er1645v2EthPortSwIVlanVlanArpStaticArpEntry 11}

er1645v2EthPortSwIVlanVlanArpStaticArpMacAddress OBJECT-TYPE
   SYNTAX      OCTET STRING
   MAX-ACCESS  read-write
   STATUS      current
   DESCRIPTION
      "Path: swPort.editConf.vlan.vlan.arp.staticArp.macAddress

       MAC address."
   ::= {er1645v2EthPortSwIVlanVlanArpStaticArpEntry 16777216}

er1645v2EthPortSwIVlanVlanArpStaticArpIpAddress OBJECT-TYPE
   SYNTAX      IpAddress
   MAX-ACCESS  read-write
   STATUS      current
   DESCRIPTION
      "Path: swPort.editConf.vlan.vlan.arp.staticArp.ipAddress"
   ::= {er1645v2EthPortSwIVlanVlanArpStaticArpEntry 33554432}


er1645v2EthPortSwIPppOE OBJECT IDENTIFIER ::= {er1645v2EthPortSwI 35}

er1645v2EthPortSwIPppOESSCTable OBJECT-TYPE
   SYNTAX      SEQUENCE OF Er1645v2EthPortSwIPppOEEntry
   MAX-ACCESS  not-accessible
   STATUS      current
   DESCRIPTION
      ""
   ::= {er1645v2EthPortSwIPppOE 1}

er1645v2EthPortSwIPppOEEntry OBJECT-TYPE
   SYNTAX      Er1645v2EthPortSwIPppOEEntry
   MAX-ACCESS  not-accessible
   STATUS      current
   DESCRIPTION
      ""
   INDEX      { er1645v2EthPortSwIPppOEGlobalIx,
                er1645v2EthPortSwIPppOETableIx }
   ::= {er1645v2EthPortSwIPppOESSCTable 1}

Er1645v2EthPortSwIPppOEEntry ::=
   SEQUENCE
      {
      er1645v2EthPortSwIPppOEActions
         VariableLengthTableActions,
      er1645v2EthPortSwIPppOEGlobalIx
         GlobalIndex,
      er1645v2EthPortSwIPppOETableIx
         TableIndex,
      er1645v2EthPortSwIPppOEName
         DisplayString,
      er1645v2EthPortSwIPppOERemark
         DisplayString,
      er1645v2EthPortSwIPppOEAdminStatus
         INTEGER,
      er1645v2EthPortSwIPppOEMode
         INTEGER,
      er1645v2EthPortSwIPppOEIpVrfRouter
         DisplayString,
      er1645v2EthPortSwIPppOEIpAdr
         IpAddress,
      er1645v2EthPortSwIPppOEIpNetm
         IpAddress,
      er1645v2EthPortSwIPppOEIpSNetName
         INTEGER,
      er1645v2EthPortSwIPppOEIpSNetCust
         DisplayString,
      er1645v2EthPortSwIPppOEIpRem
         IpAddress,
      er1645v2EthPortSwIPppOEIpUnnumbered
         DisplayString,
      er1645v2EthPortSwIPppOEIpGwPref
         Integer32,
      er1645v2EthPortSwIPppOEIpRsn
         INTEGER,
      er1645v2EthPortSwIPppOEIpMtu
         Integer32,
      er1645v2EthPortSwIPppOEIpMssAdjust
         INTEGER,
      er1645v2EthPortSwIPppOEIpRipMetric
         Integer32,
      er1645v2EthPortSwIPppOEIpRipMetricOut
         Integer32,
      er1645v2EthPortSwIPppOEIpRipMode
         INTEGER,
      er1645v2EthPortSwIPppOEIpRipTxVer
         INTEGER,
      er1645v2EthPortSwIPppOEIpRipRxVer
         INTEGER,
      er1645v2EthPortSwIPppOEIpRipSplitH
         INTEGER,
      er1645v2EthPortSwIPppOEIpRipAuth
         INTEGER,
      er1645v2EthPortSwIPppOEIpRipFilter
         DisplayString,
      er1645v2EthPortSwIPppOEIpRipFilterIn
         DisplayString,
      er1645v2EthPortSwIPppOEIpRipClearNextHop
         INTEGER,
      er1645v2EthPortSwIPppOEIpAccPol
         DisplayString,
      er1645v2EthPortSwIPppOEIpAB
         DisplayString,
      er1645v2EthPortSwIPppOEIpMA
         INTEGER,
      er1645v2EthPortSwIPppOEIpMF
         Integer32,
      er1645v2EthPortSwIPppOEIpDB
         INTEGER,
      er1645v2EthPortSwIPppOEIpIR
         INTEGER,
      er1645v2EthPortSwIPppOEIpIgmp
         INTEGER,
      er1645v2EthPortSwIPppOEIpNN
         DisplayString,
      er1645v2EthPortSwIPppOEIpPimMode
         INTEGER,
      er1645v2EthPortSwIPppOEIpPimDrPriority
         Counter32,
      er1645v2EthPortSwIPppOEIpPimHelloTime
         TimeTicks,
      er1645v2EthPortSwIPppOEIpPimPropagationDelay
         TimeTicks,
      er1645v2EthPortSwIPppOEIpPimOverrideInterval
         TimeTicks,
      er1645v2EthPortSwIPppOEIpPimBsrBorder
         INTEGER,
      er1645v2EthPortSwIPppOEIpPimTtlThreshold
         Integer32,
      er1645v2EthPortSwIPppOEIpIMNetworkUnreachable
         INTEGER,
      er1645v2EthPortSwIPppOEIpIMHostUnreachable
         INTEGER,
      er1645v2EthPortSwIPppOEIpIMProtocolUnreachable
         INTEGER,
      er1645v2EthPortSwIPppOEIpIMPortUnreachable
         INTEGER,
      er1645v2EthPortSwIPppOEIpIMMtuExceeded
         INTEGER,
      er1645v2EthPortSwIPppOEIpIMAdminProhibited
         INTEGER,
      er1645v2EthPortSwIPppOEIpIMTtlExceeded
         INTEGER,
      er1645v2EthPortSwIPppOEIpIMRedirect
         INTEGER,
      er1645v2EthPortSwIPppOEIpV6VrfRouter
         DisplayString,
      er1645v2EthPortSwIPppOEIpV6AddrAutoConfigNrDupAddrDetects
         Integer32,
      er1645v2EthPortSwIPppOEIpV6AddrAutoConfigAcceptRa
         INTEGER,
      er1645v2EthPortSwIPppOEIpV6AddrAutoConfigAcceptRaRdnss
         INTEGER,
      er1645v2EthPortSwIPppOEIpV6AddrAutoConfigAcceptRaDnssl
         INTEGER,
      er1645v2EthPortSwIPppOEIpV6DefaultRoute
         INTEGER,
      er1645v2EthPortSwIPppOEIpV6RaSend
         INTEGER,
      er1645v2EthPortSwIPppOEIpV6RaMinInterval
         TimeTicks,
      er1645v2EthPortSwIPppOEIpV6RaMaxInterval
         TimeTicks,
      er1645v2EthPortSwIPppOEIpV6RaManagedFlag
         INTEGER,
      er1645v2EthPortSwIPppOEIpV6RaOtherConfFlag
         INTEGER,
      er1645v2EthPortSwIPppOEIpV6RaLinkMtu
         Integer32,
      er1645v2EthPortSwIPppOEIpV6RaReachableTime
         TimeTicks,
      er1645v2EthPortSwIPppOEIpV6RaRetransmitTime
         TimeTicks,
      er1645v2EthPortSwIPppOEIpV6RaHopLimit
         Integer32,
      er1645v2EthPortSwIPppOEIpV6RaDefaultLifeTime
         TimeTicks,
      er1645v2EthPortSwIPppOEIpV6RaDnsOptionsRdnssLifeTime
         TimeTicks,
      er1645v2EthPortSwIPppOEIpV6RaDnsOptionsRdnssImportServers
         INTEGER,
      er1645v2EthPortSwIPppOEIpV6RaDnsOptionsDnsslLifeTime
         TimeTicks,
      er1645v2EthPortSwIPppOEIpV6RaDnsOptionsDnsslImportDomains
         INTEGER,
      er1645v2EthPortSwIPppOEIpV6RsSend
         INTEGER,
      er1645v2EthPortSwIPppOEIpV6RsMaxRandomDelay
         TimeTicks,
      er1645v2EthPortSwIPppOEIpV6RsInterval
         TimeTicks,
      er1645v2EthPortSwIPppOEIpV6RsMaxSolicitations
         Integer32,
      er1645v2EthPortSwIPppOEIpV6TrafficPolicyInbound
         DisplayString,
      er1645v2EthPortSwIPppOEIpV6TrafficPolicyOutbound
         DisplayString,
      er1645v2EthPortSwIPppOEIpV6FirewallZone
         DisplayString,
      er1645v2EthPortSwIPppOEIpV6DhcpClientAddrAC
         INTEGER,
      er1645v2EthPortSwIPppOEIpV6DhcpClientPrDelMode
         INTEGER,
      er1645v2EthPortSwIPppOEIpV6DhcpClientPrDelPool
         DisplayString,
      er1645v2EthPortSwIPppOEIpV6DhcpClientPrDelPdExclOpt
         INTEGER,
      er1645v2EthPortSwIPppOEIpV6DhcpClientDnsServerPref
         Integer32,
      er1645v2EthPortSwIPppOEIpV6DhcpClientRapidCommit
         INTEGER,
      er1645v2EthPortSwIPppOEIpV6DhcpClientTimersSolTimeOut
         TimeTicks,
      er1645v2EthPortSwIPppOEIpV6DhcpClientTimersSolMaxRt
         TimeTicks,
      er1645v2EthPortSwIPppOEIpV6DhcpClientTimersInfoRefresh
         TimeTicks,
      er1645v2EthPortSwIPppOEIpV6DhcpServerMode
         INTEGER,
      er1645v2EthPortSwIPppOEIpV6DhcpServerPreference
         Integer32,
      er1645v2EthPortSwIPppOEIpV6DhcpServerPool
         DisplayString,
      er1645v2EthPortSwIPppOEIpV6DhcpServerRapidCommit
         INTEGER,
      er1645v2EthPortSwIPppOEIpV6DhcpServerTimersInfoRefresh
         TimeTicks,
      er1645v2EthPortSwIPppOEIpV6DhcpRelayMode
         INTEGER,
      er1645v2EthPortSwIPppOEIpV6SendRedirect
         INTEGER,
      er1645v2EthPortSwIPppOEIpV6LinkMtu
         Integer32,
      er1645v2EthPortSwIPppOEIpV6InterfaceId
         OCTET STRING,
      er1645v2EthPortSwIPppOEIpV6MF
         Integer32,
      er1645v2EthPortSwIPppOEIpV6IcmpMessagesNoRoute
         INTEGER,
      er1645v2EthPortSwIPppOEIpV6IcmpMessagesBeyondScope
         INTEGER,
      er1645v2EthPortSwIPppOEIpV6IcmpMessagesAddressUnreachable
         INTEGER,
      er1645v2EthPortSwIPppOEIpV6IcmpMessagesPortUnreachable
         INTEGER,
      er1645v2EthPortSwIPppOEIpV6IcmpMessagesPacketTooBig
         INTEGER,
      er1645v2EthPortSwIPppOEIpV6IcmpMessagesHopLimitExceeded
         INTEGER,
      er1645v2EthPortSwIPppOEIpV6IcmpMessagesFragTimeExceeded
         INTEGER,
      er1645v2EthPortSwIPppOEIpV6IcmpMessagesHeaderFieldErr
         INTEGER,
      er1645v2EthPortSwIPppOEIpV6IcmpMessagesOptionUnrecognized
         INTEGER,
      er1645v2EthPortSwIPppOEIpV6IcmpMessagesRedirect
         INTEGER,
      er1645v2EthPortSwIPppOEPppLnkMOperation
         INTEGER,
      er1645v2EthPortSwIPppOEPppLnkMInterval
         TimeTicks,
      er1645v2EthPortSwIPppOEPppLnkMRepTimeOut
         TimeTicks,
      er1645v2EthPortSwIPppOEPppLnkMFailsPrmt
         Integer32,
      er1645v2EthPortSwIPppOEPppAuthentication
         INTEGER,
      er1645v2EthPortSwIPppOEPppAuthenPeriod
         TimeTicks,
      er1645v2EthPortSwIPppOEPppSessionName
         DisplayString,
      er1645v2EthPortSwIPppOEPppSessionSecret
         DisplayString,
      er1645v2EthPortSwIPppOEPppEncModeSessionSecret
         INTEGER,
      er1645v2EthPortSwIPppOEPppEncSessionSecret
         DisplayString,
      er1645v2EthPortSwIPppOEPppServiceName
         DisplayString
      }

er1645v2EthPortSwIPppOEActions OBJECT-TYPE
   SYNTAX      VariableLengthTableActions
   MAX-ACCESS  read-write
   STATUS      current
   DESCRIPTION
      "By way of this field, some manipulations
       on this table may be performed."
   ::= {er1645v2EthPortSwIPppOEEntry 2}

er1645v2EthPortSwIPppOEGlobalIx OBJECT-TYPE
   SYNTAX      GlobalIndex
   MAX-ACCESS  not-accessible
   STATUS      current
   DESCRIPTION
      "The value of the tlsCntTreeGlobalIndex of the MANAGED OBJECT."
   ::= {er1645v2EthPortSwIPppOEEntry 10}

er1645v2EthPortSwIPppOETableIx OBJECT-TYPE
   SYNTAX      TableIndex
   MAX-ACCESS  not-accessible
   STATUS      current
   DESCRIPTION
      ""
   ::= {er1645v2EthPortSwIPppOEEntry 11}

er1645v2EthPortSwIPppOEName OBJECT-TYPE
   SYNTAX      DisplayString
   MAX-ACCESS  read-write
   STATUS      current
   DESCRIPTION
      "Path: swPort.editConf.pppoEClient.name"
   ::= {er1645v2EthPortSwIPppOEEntry 16777216}

er1645v2EthPortSwIPppOERemark OBJECT-TYPE
   SYNTAX      DisplayString
   MAX-ACCESS  read-write
   STATUS      current
   DESCRIPTION
      "Path: swPort.editConf.pppoEClient.remark"
   ::= {er1645v2EthPortSwIPppOEEntry 1157627904}

er1645v2EthPortSwIPppOEAdminStatus OBJECT-TYPE
   SYNTAX      INTEGER
               {
               up (1),
               down (2)
               }
   MAX-ACCESS  read-write
   STATUS      current
   DESCRIPTION
      "Path: swPort.editConf.pppoEClient.adminStatus

       Possibilities:
               up   (1)
               down   (2)"
   ::= {er1645v2EthPortSwIPppOEEntry 33554432}

er1645v2EthPortSwIPppOEMode OBJECT-TYPE
   SYNTAX      INTEGER
               {
               routing (1),
               multilink (8),
               ipV6 (16),
               ipV6ipV4 (17)
               }
   MAX-ACCESS  read-write
   STATUS      current
   DESCRIPTION
      "Path: swPort.editConf.pppoEClient.mode

       Possibilities:
               routing   (1)
               multilink   (8)
               ipV6   (16)
               ipV6/ipV4   (17)"
   ::= {er1645v2EthPortSwIPppOEEntry 67108864}

er1645v2EthPortSwIPppOEIpVrfRouter OBJECT-TYPE
   SYNTAX      DisplayString
   MAX-ACCESS  read-write
   STATUS      current
   DESCRIPTION
      "Path: swPort.editConf.pppoEClient.ip.vrfRouter"
   ::= {er1645v2EthPortSwIPppOEEntry 53215232}

er1645v2EthPortSwIPppOEIpAdr OBJECT-TYPE
   SYNTAX      IpAddress
   MAX-ACCESS  read-write
   STATUS      current
   DESCRIPTION
      "Path: swPort.editConf.pppoEClient.ip.address"
   ::= {er1645v2EthPortSwIPppOEEntry 58261504}

er1645v2EthPortSwIPppOEIpNetm OBJECT-TYPE
   SYNTAX      IpAddress
   MAX-ACCESS  read-write
   STATUS      current
   DESCRIPTION
      "Path: swPort.editConf.pppoEClient.ip.netMask"
   ::= {er1645v2EthPortSwIPppOEEntry 58392576}

er1645v2EthPortSwIPppOEIpSNetName OBJECT-TYPE
   SYNTAX      INTEGER
               {
               slOPTg (0),
               corp (2),
               dmz (3),
               internet (1)
               }
   MAX-ACCESS  read-write
   STATUS      current
   DESCRIPTION
      "Path: swPort.editConf.pppoEClient.ip.sNet.name

       Possibilities:
               <OPT>   (0)
               corp   (2)
               dmz   (3)
               internet   (1)"
   ::= {er1645v2EthPortSwIPppOEEntry 53674240}

er1645v2EthPortSwIPppOEIpSNetCust OBJECT-TYPE
   SYNTAX      DisplayString
   MAX-ACCESS  read-write
   STATUS      current
   DESCRIPTION
      "Path: swPort.editConf.pppoEClient.ip.sNet.custom"
   ::= {er1645v2EthPortSwIPppOEEntry 53674496}

er1645v2EthPortSwIPppOEIpRem OBJECT-TYPE
   SYNTAX      IpAddress
   MAX-ACCESS  read-write
   STATUS      current
   DESCRIPTION
      "Path: swPort.editConf.pppoEClient.ip.remote"
   ::= {er1645v2EthPortSwIPppOEEntry 58458112}

er1645v2EthPortSwIPppOEIpUnnumbered OBJECT-TYPE
   SYNTAX      DisplayString
   MAX-ACCESS  read-write
   STATUS      current
   DESCRIPTION
      "Path: swPort.editConf.pppoEClient.ip.unnumbered"
   ::= {er1645v2EthPortSwIPppOEEntry 52625408}

er1645v2EthPortSwIPppOEIpGwPref OBJECT-TYPE
   SYNTAX      Integer32
   MAX-ACCESS  read-write
   STATUS      current
   DESCRIPTION
      "Path: swPort.editConf.pppoEClient.ip.gatewayPreference"
   ::= {er1645v2EthPortSwIPppOEEntry 52690944}

er1645v2EthPortSwIPppOEIpRsn OBJECT-TYPE
   SYNTAX      INTEGER
               {
               disabled (0),
               enabled (1)
               }
   MAX-ACCESS  read-write
   STATUS      current
   DESCRIPTION
      "Path: swPort.editConf.pppoEClient.ip.requestSubnet

       Possibilities:
               disabled   (0)
               enabled   (1)"
   ::= {er1645v2EthPortSwIPppOEEntry 56688640}

er1645v2EthPortSwIPppOEIpMtu OBJECT-TYPE
   SYNTAX      Integer32
   MAX-ACCESS  read-write
   STATUS      current
   DESCRIPTION
      "Path: swPort.editConf.pppoEClient.ip.mtu"
   ::= {er1645v2EthPortSwIPppOEEntry 52953088}

er1645v2EthPortSwIPppOEIpMssAdjust OBJECT-TYPE
   SYNTAX      INTEGER
               {
               disabled (0),
               auto (65536)
               }
   MAX-ACCESS  read-write
   STATUS      current
   DESCRIPTION
      "Path: swPort.editConf.pppoEClient.ip.mssAdjust

       Possibilities:
               disabled   (0)
               auto   (65536)"
   ::= {er1645v2EthPortSwIPppOEEntry 53280768}

er1645v2EthPortSwIPppOEIpRipMetric OBJECT-TYPE
   SYNTAX      Integer32
   MAX-ACCESS  read-write
   STATUS      current
   DESCRIPTION
      "Path: swPort.editConf.pppoEClient.ip.rip.metric"
   ::= {er1645v2EthPortSwIPppOEEntry 51712768}

er1645v2EthPortSwIPppOEIpRipMetricOut OBJECT-TYPE
   SYNTAX      Integer32
   MAX-ACCESS  read-write
   STATUS      current
   DESCRIPTION
      "Path: swPort.editConf.pppoEClient.ip.rip.metricOut"
   ::= {er1645v2EthPortSwIPppOEEntry 51713024}

er1645v2EthPortSwIPppOEIpRipMode OBJECT-TYPE
   SYNTAX      INTEGER
               {
               disabled (0),
               passive (1),
               active (2)
               }
   MAX-ACCESS  read-write
   STATUS      current
   DESCRIPTION
      "Path: swPort.editConf.pppoEClient.ip.rip.mode

       Possibilities:
               disabled   (0)
               passive   (1)
               active   (2)"
   ::= {er1645v2EthPortSwIPppOEEntry 51713280}

er1645v2EthPortSwIPppOEIpRipTxVer OBJECT-TYPE
   SYNTAX      INTEGER
               {
               rip1 (0),
               rip2 (1),
               rip1mcompatible (2)
               }
   MAX-ACCESS  read-write
   STATUS      current
   DESCRIPTION
      "Path: swPort.editConf.pppoEClient.ip.rip.txVersion

       Possibilities:
               rip1   (0)
               rip2   (1)
               rip1-compatible   (2)"
   ::= {er1645v2EthPortSwIPppOEEntry 51716864}

er1645v2EthPortSwIPppOEIpRipRxVer OBJECT-TYPE
   SYNTAX      INTEGER
               {
               rip1only (0),
               rip2only (1),
               rip12 (2)
               }
   MAX-ACCESS  read-write
   STATUS      current
   DESCRIPTION
      "Path: swPort.editConf.pppoEClient.ip.rip.rxVersion

       Possibilities:
               rip1only   (0)
               rip2only   (1)
               rip1&2   (2)"
   ::= {er1645v2EthPortSwIPppOEEntry 51717120}

er1645v2EthPortSwIPppOEIpRipSplitH OBJECT-TYPE
   SYNTAX      INTEGER
               {
               disabled (0),
               enabled (1),
               poisonedReverse (2)
               }
   MAX-ACCESS  read-write
   STATUS      current
   DESCRIPTION
      "Path: swPort.editConf.pppoEClient.ip.rip.splitHorizon

       Possibilities:
               disabled   (0)
               enabled   (1)
               poisonedReverse   (2)"
   ::= {er1645v2EthPortSwIPppOEEntry 51713792}

er1645v2EthPortSwIPppOEIpRipAuth OBJECT-TYPE
   SYNTAX      INTEGER
               {
               disabled (0),
               texts (1),
               md5 (2)
               }
   MAX-ACCESS  read-write
   STATUS      current
   DESCRIPTION
      "Path: swPort.editConf.pppoEClient.ip.rip.authentication

       Possibilities:
               disabled   (0)
               text    (1)
               md5   (2)"
   ::= {er1645v2EthPortSwIPppOEEntry 51712512}

er1645v2EthPortSwIPppOEIpRipFilter OBJECT-TYPE
   SYNTAX      DisplayString
   MAX-ACCESS  read-write
   STATUS      current
   DESCRIPTION
      "Path: swPort.editConf.pppoEClient.ip.rip.filter"
   ::= {er1645v2EthPortSwIPppOEEntry 51716096}

er1645v2EthPortSwIPppOEIpRipFilterIn OBJECT-TYPE
   SYNTAX      DisplayString
   MAX-ACCESS  read-write
   STATUS      current
   DESCRIPTION
      "Path: swPort.editConf.pppoEClient.ip.rip.filterIn"
   ::= {er1645v2EthPortSwIPppOEEntry 51716352}

er1645v2EthPortSwIPppOEIpRipClearNextHop OBJECT-TYPE
   SYNTAX      INTEGER
               {
               disabled (0),
               enabled (1)
               }
   MAX-ACCESS  read-write
   STATUS      current
   DESCRIPTION
      "Path: swPort.editConf.pppoEClient.ip.rip.clearNextHop

       Possibilities:
               disabled   (0)
               enabled   (1)"
   ::= {er1645v2EthPortSwIPppOEEntry 51708416}

er1645v2EthPortSwIPppOEIpAccPol OBJECT-TYPE
   SYNTAX      DisplayString
   MAX-ACCESS  read-write
   STATUS      current
   DESCRIPTION
      "Path: swPort.editConf.pppoEClient.ip.accessPolicy"
   ::= {er1645v2EthPortSwIPppOEEntry 53084160}

er1645v2EthPortSwIPppOEIpAB OBJECT-TYPE
   SYNTAX      DisplayString
   MAX-ACCESS  read-write
   STATUS      current
   DESCRIPTION
      "Path: swPort.editConf.pppoEClient.ip.trafficPolicy"
   ::= {er1645v2EthPortSwIPppOEEntry 51249152}

er1645v2EthPortSwIPppOEIpMA OBJECT-TYPE
   SYNTAX      INTEGER
               {
               disabled (0),
               enabled (1)
               }
   MAX-ACCESS  read-write
   STATUS      current
   DESCRIPTION
      "Path: swPort.editConf.pppoEClient.ip.mgmtAccess

       Possibilities:
               disabled   (0)
               enabled   (1)"
   ::= {er1645v2EthPortSwIPppOEEntry 51380224}

er1645v2EthPortSwIPppOEIpMF OBJECT-TYPE
   SYNTAX      Integer32
   MAX-ACCESS  read-write
   STATUS      current
   DESCRIPTION
      "Path: swPort.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPortSwIPppOEEntry 51445760}

er1645v2EthPortSwIPppOEIpDB OBJECT-TYPE
   SYNTAX      INTEGER
               {
               disabled (0),
               enabled (1)
               }
   MAX-ACCESS  read-write
   STATUS      current
   DESCRIPTION
      "Path: swPort.editConf.pppoEClient.ip.directedBroadcasts

       Possibilities:
               disabled   (0)
               enabled   (1)"
   ::= {er1645v2EthPortSwIPppOEEntry 51773440}

er1645v2EthPortSwIPppOEIpIR OBJECT-TYPE
   SYNTAX      INTEGER
               {
               disabled (0),
               enabled (1)
               }
   MAX-ACCESS  read-write
   STATUS      current
   DESCRIPTION
      "Path: swPort.editConf.pppoEClient.ip.icmpRedirects

       Possibilities:
               disabled   (0)
               enabled   (1)"
   ::= {er1645v2EthPortSwIPppOEEntry 52035584}

er1645v2EthPortSwIPppOEIpIgmp OBJECT-TYPE
   SYNTAX      INTEGER
               {
               disabled (0),
               proxy (1),
               router (2),
               v3Router (5)
               }
   MAX-ACCESS  read-write
   STATUS      current
   DESCRIPTION
      "Path: swPort.editConf.pppoEClient.ip.igmp

       Possibilities:
               disabled   (0)
               proxy   (1)
               router   (2)
               v3Router   (5)"
   ::= {er1645v2EthPortSwIPppOEEntry 52428800}

er1645v2EthPortSwIPppOEIpNN OBJECT-TYPE
   SYNTAX      DisplayString
   MAX-ACCESS  read-write
   STATUS      current
   DESCRIPTION
      "Path: swPort.editConf.pppoEClient.ip.nat"
   ::= {er1645v2EthPortSwIPppOEEntry 52101120}

er1645v2EthPortSwIPppOEIpPimMode OBJECT-TYPE
   SYNTAX      INTEGER
               {
               disabled (0),
               sparse (1),
               passive (2)
               }
   MAX-ACCESS  read-write
   STATUS      current
   DESCRIPTION
      "Path: swPort.editConf.pppoEClient.ip.pim.mode

       Possibilities:
               disabled   (0)
               sparse   (1)
               passive   (2)"
   ::= {er1645v2EthPortSwIPppOEEntry 53346560}

er1645v2EthPortSwIPppOEIpPimDrPriority OBJECT-TYPE
   SYNTAX      Counter32
   MAX-ACCESS  read-write
   STATUS      current
   DESCRIPTION
      "Path: swPort.editConf.pppoEClient.ip.pim.drPriority

       32 bit unsigned wrappable counter."
   ::= {er1645v2EthPortSwIPppOEEntry 53346816}

er1645v2EthPortSwIPppOEIpPimHelloTime OBJECT-TYPE
   SYNTAX      TimeTicks
   MAX-ACCESS  read-write
   STATUS      current
   DESCRIPTION
      "Path: swPort.editConf.pppoEClient.ip.pim.helloTime

       Time in centi-second."
   ::= {er1645v2EthPortSwIPppOEEntry 53347072}

er1645v2EthPortSwIPppOEIpPimPropagationDelay OBJECT-TYPE
   SYNTAX      TimeTicks
   MAX-ACCESS  read-write
   STATUS      current
   DESCRIPTION
      "Path: swPort.editConf.pppoEClient.ip.pim.propagationDelay

       Time in centi-second."
   ::= {er1645v2EthPortSwIPppOEEntry 53347328}

er1645v2EthPortSwIPppOEIpPimOverrideInterval OBJECT-TYPE
   SYNTAX      TimeTicks
   MAX-ACCESS  read-write
   STATUS      current
   DESCRIPTION
      "Path: swPort.editConf.pppoEClient.ip.pim.overrideInterval

       Time in centi-second."
   ::= {er1645v2EthPortSwIPppOEEntry 53347584}

er1645v2EthPortSwIPppOEIpPimBsrBorder OBJECT-TYPE
   SYNTAX      INTEGER
               {
               disabled (0),
               enabled (1)
               }
   MAX-ACCESS  read-write
   STATUS      current
   DESCRIPTION
      "Path: swPort.editConf.pppoEClient.ip.pim.bsrBorder

       Possibilities:
               disabled   (0)
               enabled   (1)"
   ::= {er1645v2EthPortSwIPppOEEntry 53347840}

er1645v2EthPortSwIPppOEIpPimTtlThreshold OBJECT-TYPE
   SYNTAX      Integer32
   MAX-ACCESS  read-write
   STATUS      current
   DESCRIPTION
      "Path: swPort.editConf.pppoEClient.ip.pim.ttlThreshold"
   ::= {er1645v2EthPortSwIPppOEEntry 53348096}

er1645v2EthPortSwIPppOEIpIMNetworkUnreachable OBJECT-TYPE
   SYNTAX      INTEGER
               {
               disabled (0),
               enabled (1)
               }
   MAX-ACCESS  read-write
   STATUS      current
   DESCRIPTION
      "Path: swPort.editConf.pppoEClient.ip.icmpMessages.networkUnreachable

       Possibilities:
               disabled   (0)
               enabled   (1)"
   ::= {er1645v2EthPortSwIPppOEEntry 53412096}

er1645v2EthPortSwIPppOEIpIMHostUnreachable OBJECT-TYPE
   SYNTAX      INTEGER
               {
               disabled (0),
               enabled (1)
               }
   MAX-ACCESS  read-write
   STATUS      current
   DESCRIPTION
      "Path: swPort.editConf.pppoEClient.ip.icmpMessages.hostUnreachable

       Possibilities:
               disabled   (0)
               enabled   (1)"
   ::= {er1645v2EthPortSwIPppOEEntry 53412352}

er1645v2EthPortSwIPppOEIpIMProtocolUnreachable OBJECT-TYPE
   SYNTAX      INTEGER
               {
               disabled (0),
               enabled (1)
               }
   MAX-ACCESS  read-write
   STATUS      current
   DESCRIPTION
      "Path: swPort.editConf.pppoEClient.ip.icmpMessages.protocolUnreachable

       Possibilities:
               disabled   (0)
               enabled   (1)"
   ::= {er1645v2EthPortSwIPppOEEntry 53412608}

er1645v2EthPortSwIPppOEIpIMPortUnreachable OBJECT-TYPE
   SYNTAX      INTEGER
               {
               disabled (0),
               enabled (1)
               }
   MAX-ACCESS  read-write
   STATUS      current
   DESCRIPTION
      "Path: swPort.editConf.pppoEClient.ip.icmpMessages.portUnreachable

       Possibilities:
               disabled   (0)
               enabled   (1)"
   ::= {er1645v2EthPortSwIPppOEEntry 53412864}

er1645v2EthPortSwIPppOEIpIMMtuExceeded OBJECT-TYPE
   SYNTAX      INTEGER
               {
               disabled (0),
               enabled (1)
               }
   MAX-ACCESS  read-write
   STATUS      current
   DESCRIPTION
      "Path: swPort.editConf.pppoEClient.ip.icmpMessages.mtuExceeded

       Possibilities:
               disabled   (0)
               enabled   (1)"
   ::= {er1645v2EthPortSwIPppOEEntry 53413120}

er1645v2EthPortSwIPppOEIpIMAdminProhibited OBJECT-TYPE
   SYNTAX      INTEGER
               {
               disabled (0),
               enabled (1)
               }
   MAX-ACCESS  read-write
   STATUS      current
   DESCRIPTION
      "Path: swPort.editConf.pppoEClient.ip.icmpMessages.adminProhibited

       Possibilities:
               disabled   (0)
               enabled   (1)"
   ::= {er1645v2EthPortSwIPppOEEntry 53413376}

er1645v2EthPortSwIPppOEIpIMTtlExceeded OBJECT-TYPE
   SYNTAX      INTEGER
               {
               disabled (0),
               enabled (1)
               }
   MAX-ACCESS  read-write
   STATUS      current
   DESCRIPTION
      "Path: swPort.editConf.pppoEClient.ip.icmpMessages.ttlExceeded

       Possibilities:
               disabled   (0)
               enabled   (1)"
   ::= {er1645v2EthPortSwIPppOEEntry 53413632}

er1645v2EthPortSwIPppOEIpIMRedirect OBJECT-TYPE
   SYNTAX      INTEGER
               {
               disabled (0),
               enabled (1)
               }
   MAX-ACCESS  read-write
   STATUS      current
   DESCRIPTION
      "Path: swPort.editConf.pppoEClient.ip.icmpMessages.redirect

       Possibilities:
               disabled   (0)
               enabled   (1)"
   ::= {er1645v2EthPortSwIPppOEEntry 53413888}

er1645v2EthPortSwIPppOEIpV6VrfRouter OBJECT-TYPE
   SYNTAX      DisplayString
   MAX-ACCESS  read-write
   STATUS      current
   DESCRIPTION
      "Path: swPort.editConf.pppoEClient.ipV6.vrfRouter"
   ::= {er1645v2EthPortSwIPppOEEntry 704708608}

er1645v2EthPortSwIPppOEIpV6AddrAutoConfigNrDupAddrDetects OBJECT-TYPE
   SYNTAX      Integer32
   MAX-ACCESS  read-write
   STATUS      current
   DESCRIPTION
      "Path: swPort.editConf.pppoEClient.ipV6.addrAutoConfig.nrDupAddrDetects"
   ::= {er1645v2EthPortSwIPppOEEntry 704905472}

er1645v2EthPortSwIPppOEIpV6AddrAutoConfigAcceptRa OBJECT-TYPE
   SYNTAX      INTEGER
               {
               disabled (0),
               enabled (1)
               }
   MAX-ACCESS  read-write
   STATUS      current
   DESCRIPTION
      "Path: swPort.editConf.pppoEClient.ipV6.addrAutoConfig.acceptRa

       Possibilities:
               disabled   (0)
               enabled   (1)"
   ::= {er1645v2EthPortSwIPppOEEntry 704905728}

er1645v2EthPortSwIPppOEIpV6AddrAutoConfigAcceptRaRdnss OBJECT-TYPE
   SYNTAX      INTEGER
               {
               disabled (0),
               enabled (1)
               }
   MAX-ACCESS  read-write
   STATUS      current
   DESCRIPTION
      "Path: swPort.editConf.pppoEClient.ipV6.addrAutoConfig.acceptRaRdnss

       Possibilities:
               disabled   (0)
               enabled   (1)"
   ::= {er1645v2EthPortSwIPppOEEntry 704905984}

er1645v2EthPortSwIPppOEIpV6AddrAutoConfigAcceptRaDnssl OBJECT-TYPE
   SYNTAX      INTEGER
               {
               disabled (0),
               enabled (1)
               }
   MAX-ACCESS  read-write
   STATUS      current
   DESCRIPTION
      "Path: swPort.editConf.pppoEClient.ipV6.addrAutoConfig.acceptRaDnssl

       Possibilities:
               disabled   (0)
               enabled   (1)"
   ::= {er1645v2EthPortSwIPppOEEntry 704906240}

er1645v2EthPortSwIPppOEIpV6DefaultRoute OBJECT-TYPE
   SYNTAX      INTEGER
               {
               disabled (0),
               enabled (1)
               }
   MAX-ACCESS  read-write
   STATUS      current
   DESCRIPTION
      "Path: swPort.editConf.pppoEClient.ipV6.defaultRoute

       Possibilities:
               disabled   (0)
               enabled   (1)"
   ::= {er1645v2EthPortSwIPppOEEntry 704970752}

er1645v2EthPortSwIPppOEIpV6RaSend OBJECT-TYPE
   SYNTAX      INTEGER
               {
               disabled (0),
               enabled (1)
               }
   MAX-ACCESS  read-write
   STATUS      current
   DESCRIPTION
      "Path: swPort.editConf.pppoEClient.ipV6.ra.send

       Possibilities:
               disabled   (0)
               enabled   (1)"
   ::= {er1645v2EthPortSwIPppOEEntry 705036544}

er1645v2EthPortSwIPppOEIpV6RaMinInterval OBJECT-TYPE
   SYNTAX      TimeTicks
   MAX-ACCESS  read-write
   STATUS      current
   DESCRIPTION
      "Path: swPort.editConf.pppoEClient.ipV6.ra.minInterval

       Time in centi-second."
   ::= {er1645v2EthPortSwIPppOEEntry 705036800}

er1645v2EthPortSwIPppOEIpV6RaMaxInterval OBJECT-TYPE
   SYNTAX      TimeTicks
   MAX-ACCESS  read-write
   STATUS      current
   DESCRIPTION
      "Path: swPort.editConf.pppoEClient.ipV6.ra.maxInterval

       Time in centi-second."
   ::= {er1645v2EthPortSwIPppOEEntry 705037056}

er1645v2EthPortSwIPppOEIpV6RaManagedFlag OBJECT-TYPE
   SYNTAX      INTEGER
               {
               disabled (0),
               enabled (1)
               }
   MAX-ACCESS  read-write
   STATUS      current
   DESCRIPTION
      "Path: swPort.editConf.pppoEClient.ipV6.ra.managedFlag

       Possibilities:
               disabled   (0)
               enabled   (1)"
   ::= {er1645v2EthPortSwIPppOEEntry 705037312}

er1645v2EthPortSwIPppOEIpV6RaOtherConfFlag OBJECT-TYPE
   SYNTAX      INTEGER
               {
               disabled (0),
               enabled (1)
               }
   MAX-ACCESS  read-write
   STATUS      current
   DESCRIPTION
      "Path: swPort.editConf.pppoEClient.ipV6.ra.otherConfFlag

       Possibilities:
               disabled   (0)
               enabled   (1)"
   ::= {er1645v2EthPortSwIPppOEEntry 705037568}

er1645v2EthPortSwIPppOEIpV6RaLinkMtu OBJECT-TYPE
   SYNTAX      Integer32
   MAX-ACCESS  read-write
   STATUS      current
   DESCRIPTION
      "Path: swPort.editConf.pppoEClient.ipV6.ra.linkMtu"
   ::= {er1645v2EthPortSwIPppOEEntry 705037824}

er1645v2EthPortSwIPppOEIpV6RaReachableTime OBJECT-TYPE
   SYNTAX      TimeTicks
   MAX-ACCESS  read-write
   STATUS      current
   DESCRIPTION
      "Path: swPort.editConf.pppoEClient.ipV6.ra.reachableTime

       Time in centi-second."
   ::= {er1645v2EthPortSwIPppOEEntry 705038080}

er1645v2EthPortSwIPppOEIpV6RaRetransmitTime OBJECT-TYPE
   SYNTAX      TimeTicks
   MAX-ACCESS  read-write
   STATUS      current
   DESCRIPTION
      "Path: swPort.editConf.pppoEClient.ipV6.ra.retransmitTime

       Time in centi-second."
   ::= {er1645v2EthPortSwIPppOEEntry 705038336}

er1645v2EthPortSwIPppOEIpV6RaHopLimit OBJECT-TYPE
   SYNTAX      Integer32
   MAX-ACCESS  read-write
   STATUS      current
   DESCRIPTION
      "Path: swPort.editConf.pppoEClient.ipV6.ra.hopLimit"
   ::= {er1645v2EthPortSwIPppOEEntry 705038592}

er1645v2EthPortSwIPppOEIpV6RaDefaultLifeTime OBJECT-TYPE
   SYNTAX      TimeTicks
   MAX-ACCESS  read-write
   STATUS      current
   DESCRIPTION
      "Path: swPort.editConf.pppoEClient.ipV6.ra.defaultLifeTime

       Time in centi-second."
   ::= {er1645v2EthPortSwIPppOEEntry 705038848}

er1645v2EthPortSwIPppOEIpV6RaDnsOptionsRdnssLifeTime OBJECT-TYPE
   SYNTAX      TimeTicks
   MAX-ACCESS  read-write
   STATUS      current
   DESCRIPTION
      "Path: swPort.editConf.pppoEClient.ipV6.ra.dnsOptions.rdnss.lifeTime

       Time in centi-second."
   ::= {er1645v2EthPortSwIPppOEEntry 705039140}

er1645v2EthPortSwIPppOEIpV6RaDnsOptionsRdnssImportServers OBJECT-TYPE
   SYNTAX      INTEGER
               {
               disabled (0),
               enabled (1)
               }
   MAX-ACCESS  read-write
   STATUS      current
   DESCRIPTION
      "Path: swPort.editConf.pppoEClient.ipV6.ra.dnsOptions.rdnss.importServers

       Possibilities:
               disabled   (0)
               enabled   (1)"
   ::= {er1645v2EthPortSwIPppOEEntry 705039148}

er1645v2EthPortSwIPppOEIpV6RaDnsOptionsDnsslLifeTime OBJECT-TYPE
   SYNTAX      TimeTicks
   MAX-ACCESS  read-write
   STATUS      current
   DESCRIPTION
      "Path: swPort.editConf.pppoEClient.ipV6.ra.dnsOptions.dnssl.lifeTime

       Time in centi-second."
   ::= {er1645v2EthPortSwIPppOEEntry 705039172}

er1645v2EthPortSwIPppOEIpV6RaDnsOptionsDnsslImportDomains OBJECT-TYPE
   SYNTAX      INTEGER
               {
               disabled (0),
               enabled (1)
               }
   MAX-ACCESS  read-write
   STATUS      current
   DESCRIPTION
      "Path: swPort.editConf.pppoEClient.ipV6.ra.dnsOptions.dnssl.importDomains

       Possibilities:
               disabled   (0)
               enabled   (1)"
   ::= {er1645v2EthPortSwIPppOEEntry 705039180}

er1645v2EthPortSwIPppOEIpV6RsSend OBJECT-TYPE
   SYNTAX      INTEGER
               {
               disabled (0),
               enabled (1)
               }
   MAX-ACCESS  read-write
   STATUS      current
   DESCRIPTION
      "Path: swPort.editConf.pppoEClient.ipV6.rs.send

       Possibilities:
               disabled   (0)
               enabled   (1)"
   ::= {er1645v2EthPortSwIPppOEEntry 705954048}

er1645v2EthPortSwIPppOEIpV6RsMaxRandomDelay OBJECT-TYPE
   SYNTAX      TimeTicks
   MAX-ACCESS  read-write
   STATUS      current
   DESCRIPTION
      "Path: swPort.editConf.pppoEClient.ipV6.rs.maxRandomDelay

       Time in centi-second."
   ::= {er1645v2EthPortSwIPppOEEntry 705954304}

er1645v2EthPortSwIPppOEIpV6RsInterval OBJECT-TYPE
   SYNTAX      TimeTicks
   MAX-ACCESS  read-write
   STATUS      current
   DESCRIPTION
      "Path: swPort.editConf.pppoEClient.ipV6.rs.interval

       Time in centi-second."
   ::= {er1645v2EthPortSwIPppOEEntry 705954560}

er1645v2EthPortSwIPppOEIpV6RsMaxSolicitations OBJECT-TYPE
   SYNTAX      Integer32
   MAX-ACCESS  read-write
   STATUS      current
   DESCRIPTION
      "Path: swPort.editConf.pppoEClient.ipV6.rs.maxSolicitations"
   ::= {er1645v2EthPortSwIPppOEEntry 705954816}

er1645v2EthPortSwIPppOEIpV6TrafficPolicyInbound OBJECT-TYPE
   SYNTAX      DisplayString
   MAX-ACCESS  read-write
   STATUS      current
   DESCRIPTION
      "Path: swPort.editConf.pppoEClient.ipV6.trafficPolicy.inbound"
   ::= {er1645v2EthPortSwIPppOEEntry 705364224}

er1645v2EthPortSwIPppOEIpV6TrafficPolicyOutbound OBJECT-TYPE
   SYNTAX      DisplayString
   MAX-ACCESS  read-write
   STATUS      current
   DESCRIPTION
      "Path: swPort.editConf.pppoEClient.ipV6.trafficPolicy.outbound"
   ::= {er1645v2EthPortSwIPppOEEntry 705364480}

er1645v2EthPortSwIPppOEIpV6FirewallZone OBJECT-TYPE
   SYNTAX      DisplayString
   MAX-ACCESS  read-write
   STATUS      current
   DESCRIPTION
      "Path: swPort.editConf.pppoEClient.ipV6.firewall.zone"
   ::= {er1645v2EthPortSwIPppOEEntry 705429760}

er1645v2EthPortSwIPppOEIpV6DhcpClientAddrAC OBJECT-TYPE
   SYNTAX      INTEGER
               {
               disabled (0),
               enabled (1)
               }
   MAX-ACCESS  read-write
   STATUS      current
   DESCRIPTION
      "Path: swPort.editConf.pppoEClient.ipV6.dhcp.client.addrAutoConfig

       Possibilities:
               disabled   (0)
               enabled   (1)"
   ::= {er1645v2EthPortSwIPppOEEntry 705307648}

er1645v2EthPortSwIPppOEIpV6DhcpClientPrDelMode OBJECT-TYPE
   SYNTAX      INTEGER
               {
               disabled (0),
               enabled (1)
               }
   MAX-ACCESS  read-write
   STATUS      current
   DESCRIPTION
      "Path: swPort.editConf.pppoEClient.ipV6.dhcp.client.pd.mode

       Possibilities:
               disabled   (0)
               enabled   (1)"
   ::= {er1645v2EthPortSwIPppOEEntry 705308676}

er1645v2EthPortSwIPppOEIpV6DhcpClientPrDelPool OBJECT-TYPE
   SYNTAX      DisplayString
   MAX-ACCESS  read-write
   STATUS      current
   DESCRIPTION
      "Path: swPort.editConf.pppoEClient.ipV6.dhcp.client.pd.pool"
   ::= {er1645v2EthPortSwIPppOEEntry 705308680}

er1645v2EthPortSwIPppOEIpV6DhcpClientPrDelPdExclOpt OBJECT-TYPE
   SYNTAX      INTEGER
               {
               disabled (0),
               enabled (1)
               }
   MAX-ACCESS  read-write
   STATUS      current
   DESCRIPTION
      "Path: swPort.editConf.pppoEClient.ipV6.dhcp.client.pd.pdExclOpt

       Possibilities:
               disabled   (0)
               enabled   (1)"
   ::= {er1645v2EthPortSwIPppOEEntry 705308684}

er1645v2EthPortSwIPppOEIpV6DhcpClientDnsServerPref OBJECT-TYPE
   SYNTAX      Integer32
   MAX-ACCESS  read-write
   STATUS      current
   DESCRIPTION
      "Path: swPort.editConf.pppoEClient.ipV6.dhcp.client.dns.serverPref"
   ::= {er1645v2EthPortSwIPppOEEntry 705310724}

er1645v2EthPortSwIPppOEIpV6DhcpClientRapidCommit OBJECT-TYPE
   SYNTAX      INTEGER
               {
               disabled (0),
               enabled (1)
               }
   MAX-ACCESS  read-write
   STATUS      current
   DESCRIPTION
      "Path: swPort.editConf.pppoEClient.ipV6.dhcp.client.rapidCommit

       Possibilities:
               disabled   (0)
               enabled   (1)"
   ::= {er1645v2EthPortSwIPppOEEntry 705309696}

er1645v2EthPortSwIPppOEIpV6DhcpClientTimersSolTimeOut OBJECT-TYPE
   SYNTAX      TimeTicks
   MAX-ACCESS  read-write
   STATUS      current
   DESCRIPTION
      "Path: swPort.editConf.pppoEClient.ipV6.dhcp.client.timers.solTimeOut

       Time in centi-second."
   ::= {er1645v2EthPortSwIPppOEEntry 705311748}

er1645v2EthPortSwIPppOEIpV6DhcpClientTimersSolMaxRt OBJECT-TYPE
   SYNTAX      TimeTicks
   MAX-ACCESS  read-write
   STATUS      current
   DESCRIPTION
      "Path: swPort.editConf.pppoEClient.ipV6.dhcp.client.timers.solMaxRt

       Time in centi-second."
   ::= {er1645v2EthPortSwIPppOEEntry 705311752}

er1645v2EthPortSwIPppOEIpV6DhcpClientTimersInfoRefresh OBJECT-TYPE
   SYNTAX      TimeTicks
   MAX-ACCESS  read-write
   STATUS      current
   DESCRIPTION
      "Path: swPort.editConf.pppoEClient.ipV6.dhcp.client.timers.infoRefresh

       Time in centi-second."
   ::= {er1645v2EthPortSwIPppOEEntry 705311756}

er1645v2EthPortSwIPppOEIpV6DhcpServerMode OBJECT-TYPE
   SYNTAX      INTEGER
               {
               disabled (0),
               enabled (1)
               }
   MAX-ACCESS  read-write
   STATUS      current
   DESCRIPTION
      "Path: swPort.editConf.pppoEClient.ipV6.dhcp.server.mode

       Possibilities:
               disabled   (0)
               enabled   (1)"
   ::= {er1645v2EthPortSwIPppOEEntry 705315840}

er1645v2EthPortSwIPppOEIpV6DhcpServerPreference OBJECT-TYPE
   SYNTAX      Integer32
   MAX-ACCESS  read-write
   STATUS      current
   DESCRIPTION
      "Path: swPort.editConf.pppoEClient.ipV6.dhcp.server.preference"
   ::= {er1645v2EthPortSwIPppOEEntry 705316864}

er1645v2EthPortSwIPppOEIpV6DhcpServerPool OBJECT-TYPE
   SYNTAX      DisplayString
   MAX-ACCESS  read-write
   STATUS      current
   DESCRIPTION
      "Path: swPort.editConf.pppoEClient.ipV6.dhcp.server.pool"
   ::= {er1645v2EthPortSwIPppOEEntry 705317888}

er1645v2EthPortSwIPppOEIpV6DhcpServerRapidCommit OBJECT-TYPE
   SYNTAX      INTEGER
               {
               disabled (0),
               enabled (1)
               }
   MAX-ACCESS  read-write
   STATUS      current
   DESCRIPTION
      "Path: swPort.editConf.pppoEClient.ipV6.dhcp.server.rapidCommit

       Possibilities:
               disabled   (0)
               enabled   (1)"
   ::= {er1645v2EthPortSwIPppOEEntry 705318912}

er1645v2EthPortSwIPppOEIpV6DhcpServerTimersInfoRefresh OBJECT-TYPE
   SYNTAX      TimeTicks
   MAX-ACCESS  read-write
   STATUS      current
   DESCRIPTION
      "Path: swPort.editConf.pppoEClient.ipV6.dhcp.server.timers.infoRefresh

       Time in centi-second."
   ::= {er1645v2EthPortSwIPppOEEntry 705319940}

er1645v2EthPortSwIPppOEIpV6DhcpRelayMode OBJECT-TYPE
   SYNTAX      INTEGER
               {
               disabled (0),
               enabled (1)
               }
   MAX-ACCESS  read-write
   STATUS      current
   DESCRIPTION
      "Path: swPort.editConf.pppoEClient.ipV6.dhcp.relay.mode

       Possibilities:
               disabled   (0)
               enabled   (1)"
   ::= {er1645v2EthPortSwIPppOEEntry 705323040}

er1645v2EthPortSwIPppOEIpV6SendRedirect OBJECT-TYPE
   SYNTAX      INTEGER
               {
               disabled (0),
               enabled (1)
               }
   MAX-ACCESS  read-write
   STATUS      current
   DESCRIPTION
      "Path: swPort.editConf.pppoEClient.ipV6.sendRedirect

       Possibilities:
               disabled   (0)
               enabled   (1)"
   ::= {er1645v2EthPortSwIPppOEEntry 705101824}

er1645v2EthPortSwIPppOEIpV6LinkMtu OBJECT-TYPE
   SYNTAX      Integer32
   MAX-ACCESS  read-write
   STATUS      current
   DESCRIPTION
      "Path: swPort.editConf.pppoEClient.ipV6.linkMtu"
   ::= {er1645v2EthPortSwIPppOEEntry 705167360}

er1645v2EthPortSwIPppOEIpV6InterfaceId OBJECT-TYPE
   SYNTAX      OCTET STRING
   MAX-ACCESS  read-write
   STATUS      current
   DESCRIPTION
      "Path: swPort.editConf.pppoEClient.ipV6.interfaceId"
   ::= {er1645v2EthPortSwIPppOEEntry 705232896}

er1645v2EthPortSwIPppOEIpV6MF OBJECT-TYPE
   SYNTAX      Integer32
   MAX-ACCESS  read-write
   STATUS      current
   DESCRIPTION
      "Path: swPort.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPortSwIPppOEEntry 705757184}

er1645v2EthPortSwIPppOEIpV6IcmpMessagesNoRoute OBJECT-TYPE
   SYNTAX      INTEGER
               {
               disabled (0),
               enabled (1)
               }
   MAX-ACCESS  read-write
   STATUS      current
   DESCRIPTION
      "Path: swPort.editConf.pppoEClient.ipV6.icmpMessages.noRoute

       Possibilities:
               disabled   (0)
               enabled   (1)"
   ::= {er1645v2EthPortSwIPppOEEntry 705822976}

er1645v2EthPortSwIPppOEIpV6IcmpMessagesBeyondScope OBJECT-TYPE
   SYNTAX      INTEGER
               {
               disabled (0),
               enabled (1)
               }
   MAX-ACCESS  read-write
   STATUS      current
   DESCRIPTION
      "Path: swPort.editConf.pppoEClient.ipV6.icmpMessages.beyondScope

       Possibilities:
               disabled   (0)
               enabled   (1)"
   ::= {er1645v2EthPortSwIPppOEEntry 705823488}

er1645v2EthPortSwIPppOEIpV6IcmpMessagesAddressUnreachable OBJECT-TYPE
   SYNTAX      INTEGER
               {
               disabled (0),
               enabled (1)
               }
   MAX-ACCESS  read-write
   STATUS      current
   DESCRIPTION
      "Path: swPort.editConf.pppoEClient.ipV6.icmpMessages.addressUnreachable

       Possibilities:
               disabled   (0)
               enabled   (1)"
   ::= {er1645v2EthPortSwIPppOEEntry 705823744}

er1645v2EthPortSwIPppOEIpV6IcmpMessagesPortUnreachable OBJECT-TYPE
   SYNTAX      INTEGER
               {
               disabled (0),
               enabled (1)
               }
   MAX-ACCESS  read-write
   STATUS      current
   DESCRIPTION
      "Path: swPort.editConf.pppoEClient.ipV6.icmpMessages.portUnreachable

       Possibilities:
               disabled   (0)
               enabled   (1)"
   ::= {er1645v2EthPortSwIPppOEEntry 705824000}

er1645v2EthPortSwIPppOEIpV6IcmpMessagesPacketTooBig OBJECT-TYPE
   SYNTAX      INTEGER
               {
               disabled (0),
               enabled (1)
               }
   MAX-ACCESS  read-write
   STATUS      current
   DESCRIPTION
      "Path: swPort.editConf.pppoEClient.ipV6.icmpMessages.packetTooBig

       Possibilities:
               disabled   (0)
               enabled   (1)"
   ::= {er1645v2EthPortSwIPppOEEntry 705825280}

er1645v2EthPortSwIPppOEIpV6IcmpMessagesHopLimitExceeded OBJECT-TYPE
   SYNTAX      INTEGER
               {
               disabled (0),
               enabled (1)
               }
   MAX-ACCESS  read-write
   STATUS      current
   DESCRIPTION
      "Path: swPort.editConf.pppoEClient.ipV6.icmpMessages.hopLimitExceeded

       Possibilities:
               disabled   (0)
               enabled   (1)"
   ::= {er1645v2EthPortSwIPppOEEntry 705827840}

er1645v2EthPortSwIPppOEIpV6IcmpMessagesFragTimeExceeded OBJECT-TYPE
   SYNTAX      INTEGER
               {
               disabled (0),
               enabled (1)
               }
   MAX-ACCESS  read-write
   STATUS      current
   DESCRIPTION
      "Path: swPort.editConf.pppoEClient.ipV6.icmpMessages.fragTimeExceeded

       Possibilities:
               disabled   (0)
               enabled   (1)"
   ::= {er1645v2EthPortSwIPppOEEntry 705828096}

er1645v2EthPortSwIPppOEIpV6IcmpMessagesHeaderFieldErr OBJECT-TYPE
   SYNTAX      INTEGER
               {
               disabled (0),
               enabled (1)
               }
   MAX-ACCESS  read-write
   STATUS      current
   DESCRIPTION
      "Path: swPort.editConf.pppoEClient.ipV6.icmpMessages.headerFieldErr

       Possibilities:
               disabled   (0)
               enabled   (1)"
   ::= {er1645v2EthPortSwIPppOEEntry 705830400}

er1645v2EthPortSwIPppOEIpV6IcmpMessagesOptionUnrecognized OBJECT-TYPE
   SYNTAX      INTEGER
               {
               disabled (0),
               enabled (1)
               }
   MAX-ACCESS  read-write
   STATUS      current
   DESCRIPTION
      "Path: swPort.editConf.pppoEClient.ipV6.icmpMessages.optionUnrecognized

       Possibilities:
               disabled   (0)
               enabled   (1)"
   ::= {er1645v2EthPortSwIPppOEEntry 705830912}

er1645v2EthPortSwIPppOEIpV6IcmpMessagesRedirect OBJECT-TYPE
   SYNTAX      INTEGER
               {
               disabled (0),
               enabled (1)
               }
   MAX-ACCESS  read-write
   STATUS      current
   DESCRIPTION
      "Path: swPort.editConf.pppoEClient.ipV6.icmpMessages.redirect

       Possibilities:
               disabled   (0)
               enabled   (1)"
   ::= {er1645v2EthPortSwIPppOEEntry 705832960}

er1645v2EthPortSwIPppOEPppLnkMOperation OBJECT-TYPE
   SYNTAX      INTEGER
               {
               disabled (0),
               enabled (1)
               }
   MAX-ACCESS  read-write
   STATUS      current
   DESCRIPTION
      "Path: swPort.editConf.pppoEClient.ppp.linkMonitoring.operation

       Possibilities:
               disabled   (0)
               enabled   (1)"
   ::= {er1645v2EthPortSwIPppOEEntry 251724032}

er1645v2EthPortSwIPppOEPppLnkMInterval OBJECT-TYPE
   SYNTAX      TimeTicks
   MAX-ACCESS  read-write
   STATUS      current
   DESCRIPTION
      "Path: swPort.editConf.pppoEClient.ppp.linkMonitoring.interval

       Time in centi-second."
   ::= {er1645v2EthPortSwIPppOEEntry 251724288}

er1645v2EthPortSwIPppOEPppLnkMRepTimeOut OBJECT-TYPE
   SYNTAX      TimeTicks
   MAX-ACCESS  read-write
   STATUS      current
   DESCRIPTION
      "Path: swPort.editConf.pppoEClient.ppp.linkMonitoring.replyTimeOut

       Time in centi-second."
   ::= {er1645v2EthPortSwIPppOEEntry 251724544}

er1645v2EthPortSwIPppOEPppLnkMFailsPrmt OBJECT-TYPE
   SYNTAX      Integer32
   MAX-ACCESS  read-write
   STATUS      current
   DESCRIPTION
      "Path: swPort.editConf.pppoEClient.ppp.linkMonitoring.failsPermitted"
   ::= {er1645v2EthPortSwIPppOEEntry 251724800}

er1645v2EthPortSwIPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.pppoEClient.ppp.authentication

       Possibilities:
               disabled   (0)
               chap   (1)
               pap   (2)
               chapOrPap   (3)
               msChap   (4)
               msChapV2   (5)"
   ::= {er1645v2EthPortSwIPppOEEntry 251789312}

er1645v2EthPortSwIPppOEPppAuthenPeriod OBJECT-TYPE
   SYNTAX      TimeTicks
   MAX-ACCESS  read-write
   STATUS      current
   DESCRIPTION
      "Path: swPort.editConf.pppoEClient.ppp.authenPeriod

       Time in centi-second."
   ::= {er1645v2EthPortSwIPppOEEntry 251854848}

er1645v2EthPortSwIPppOEPppSessionName OBJECT-TYPE
   SYNTAX      DisplayString
   MAX-ACCESS  read-write
   STATUS      current
   DESCRIPTION
      "Path: swPort.editConf.pppoEClient.ppp.sessionName"
   ::= {er1645v2EthPortSwIPppOEEntry 251985920}

er1645v2EthPortSwIPppOEPppSessionSecret OBJECT-TYPE
   SYNTAX      DisplayString
   MAX-ACCESS  read-write
   STATUS      current
   DESCRIPTION
      "Path: swPort.editConf.pppoEClient.ppp.sessionSecret"
   ::= {er1645v2EthPortSwIPppOEEntry 252051456}

er1645v2EthPortSwIPppOEPppEncModeSessionSecret OBJECT-TYPE
   SYNTAX      INTEGER
               {
               none (1),
               encrypt (2),
               encType1 (3),
               invalid (128)
               }
   MAX-ACCESS  read-write
   STATUS      current
   DESCRIPTION
      "Path: swPort.editConf.pppoEClient.ppp.encModeSessionSecret

       Possibilities:
               none   (1)
               encrypt   (2)
               encType1   (3)
               invalid   (128)"
   ::= {er1645v2EthPortSwIPppOEEntry 252182528}

er1645v2EthPortSwIPppOEPppEncSessionSecret OBJECT-TYPE
   SYNTAX      DisplayString
   MAX-ACCESS  read-write
   STATUS      current
   DESCRIPTION
      "Path: swPort.editConf.pppoEClient.ppp.encSessionSecret"
   ::= {er1645v2EthPortSwIPppOEEntry 252248064}

er1645v2EthPortSwIPppOEPppServiceName OBJECT-TYPE
   SYNTAX      DisplayString
   MAX-ACCESS  read-write
   STATUS      current
   DESCRIPTION
      "Path: swPort.editConf.pppoEClient.ppp.serviceName"
   ::= {er1645v2EthPortSwIPppOEEntry 252116992}

er1645v2EthPortSwIPppOEIpH OBJECT-TYPE
   SYNTAX      SEQUENCE OF Er1645v2EthPortSwIPppOEIpHEntry
   MAX-ACCESS  not-accessible
   STATUS      current
   DESCRIPTION
      ""
   ::= {er1645v2EthPortSwIPppOE 51314688}

er1645v2EthPortSwIPppOEIpHEntry OBJECT-TYPE
   SYNTAX      Er1645v2EthPortSwIPppOEIpHEntry
   MAX-ACCESS  not-accessible
   STATUS      current
   DESCRIPTION
      ""
   INDEX      { er1645v2EthPortSwIPppOEIpHGlobalIx,
                er1645v2EthPortSwIPppOETableIx,
                er1645v2EthPortSwIPppOEIpHTableIx }
   ::= {er1645v2EthPortSwIPppOEIpH 1}

Er1645v2EthPortSwIPppOEIpHEntry ::=
   SEQUENCE
      {
      er1645v2EthPortSwIPppOEIpHActions
         VariableLengthTableActions,
      er1645v2EthPortSwIPppOEIpHGlobalIx
         GlobalIndex,
      er1645v2EthPortSwIPppOEIpHTableIx
         TableIndex,
      er1645v2EthPortSwIPppOEIpHAddress
         IpAddress,
      er1645v2EthPortSwIPppOEIpHDhcpRelayOptionSubscriberId
         DisplayString
      }

er1645v2EthPortSwIPppOEIpHActions OBJECT-TYPE
   SYNTAX      VariableLengthTableActions
   MAX-ACCESS  read-write
   STATUS      current
   DESCRIPTION
      "By way of this field, some manipulations
       on this table may be performed."
   ::= {er1645v2EthPortSwIPppOEIpHEntry 2}

er1645v2EthPortSwIPppOEIpHGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpHEntry 10}

er1645v2EthPortSwIPppOEIpHTableIx OBJECT-TYPE
   SYNTAX      TableIndex
   MAX-ACCESS  not-accessible
   STATUS      current
   DESCRIPTION
      ""
   ::= {er1645v2EthPortSwIPppOEIpHEntry 11}

er1645v2EthPortSwIPppOEIpHAddress OBJECT-TYPE
   SYNTAX      IpAddress
   MAX-ACCESS  read-write
   STATUS      current
   DESCRIPTION
      "Path: swPort.editConf.pppoEClient.ip.helpers.address"
   ::= {er1645v2EthPortSwIPppOEIpHEntry 16777216}

er1645v2EthPortSwIPppOEIpHDhcpRelayOptionSubscriberId OBJECT-TYPE
   SYNTAX      DisplayString
   MAX-ACCESS  read-write
   STATUS      current
   DESCRIPTION
      "Path: swPort.editConf.pppoEClient.ip.helpers.dhcpRelayOption.subscriberId"
   ::= {er1645v2EthPortSwIPppOEIpHEntry 33947648}

er1645v2EthPortSwIPppOEIpV6Addresses OBJECT-TYPE
   SYNTAX      SEQUENCE OF Er1645v2EthPortSwIPppOEIpV6AddressesEntry
   MAX-ACCESS  not-accessible
   STATUS      current
   DESCRIPTION
      ""
   ::= {er1645v2EthPortSwIPppOE 704839680}

er1645v2EthPortSwIPppOEIpV6AddressesEntry OBJECT-TYPE
   SYNTAX      Er1645v2EthPortSwIPppOEIpV6AddressesEntry
   MAX-ACCESS  not-accessible
   STATUS      current
   DESCRIPTION
      ""
   INDEX      { er1645v2EthPortSwIPppOEIpV6AddressesGlobalIx,
                er1645v2EthPortSwIPppOETableIx,
                er1645v2EthPortSwIPppOEIpV6AddressesTableIx }
   ::= {er1645v2EthPortSwIPppOEIpV6Addresses 1}

Er1645v2EthPortSwIPppOEIpV6AddressesEntry ::=
   SEQUENCE
      {
      er1645v2EthPortSwIPppOEIpV6AddressesActions
         VariableLengthTableActions,
      er1645v2EthPortSwIPppOEIpV6AddressesGlobalIx
         GlobalIndex,
      er1645v2EthPortSwIPppOEIpV6AddressesTableIx
         TableIndex,
      er1645v2EthPortSwIPppOEIpV6AddressesType
         INTEGER,
      er1645v2EthPortSwIPppOEIpV6AddressesAddress
         Ipv6Address,
      er1645v2EthPortSwIPppOEIpV6AddressesPrefixLength
         Integer32,
      er1645v2EthPortSwIPppOEIpV6AddressesGeneralPrefix
         DisplayString,
      er1645v2EthPortSwIPppOEIpV6AddressesRaSend
         INTEGER,
      er1645v2EthPortSwIPppOEIpV6AddressesRaOnLinkFlag
         INTEGER,
      er1645v2EthPortSwIPppOEIpV6AddressesRaAutoFlag
         INTEGER,
      er1645v2EthPortSwIPppOEIpV6AddressesRaValidLifeTime
         TimeTicks,
      er1645v2EthPortSwIPppOEIpV6AddressesRaValidLTMode
         INTEGER,
      er1645v2EthPortSwIPppOEIpV6AddressesRaPrefLifeTime
         TimeTicks,
      er1645v2EthPortSwIPppOEIpV6AddressesRaPrefLTMode
         INTEGER
      }

er1645v2EthPortSwIPppOEIpV6AddressesActions OBJECT-TYPE
   SYNTAX      VariableLengthTableActions
   MAX-ACCESS  read-write
   STATUS      current
   DESCRIPTION
      "By way of this field, some manipulations
       on this table may be performed."
   ::= {er1645v2EthPortSwIPppOEIpV6AddressesEntry 2}

er1645v2EthPortSwIPppOEIpV6AddressesGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6AddressesEntry 10}

er1645v2EthPortSwIPppOEIpV6AddressesTableIx OBJECT-TYPE
   SYNTAX      TableIndex
   MAX-ACCESS  not-accessible
   STATUS      current
   DESCRIPTION
      ""
   ::= {er1645v2EthPortSwIPppOEIpV6AddressesEntry 11}

er1645v2EthPortSwIPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.pppoEClient.ipV6.addresses.type

       Possibilities:
               unicast   (0)
               eui64   (1)
               anycast   (2)
               linkLocal   (3)
               generalPrefix   (4)"
   ::= {er1645v2EthPortSwIPppOEIpV6AddressesEntry 50331648}

er1645v2EthPortSwIPppOEIpV6AddressesAddress OBJECT-TYPE
   SYNTAX      Ipv6Address
   MAX-ACCESS  read-write
   STATUS      current
   DESCRIPTION
      "Path: swPort.editConf.pppoEClient.ipV6.addresses.address

       ipv6 address"
   ::= {er1645v2EthPortSwIPppOEIpV6AddressesEntry 16777216}

er1645v2EthPortSwIPppOEIpV6AddressesPrefixLength OBJECT-TYPE
   SYNTAX      Integer32
   MAX-ACCESS  read-write
   STATUS      current
   DESCRIPTION
      "Path: swPort.editConf.pppoEClient.ipV6.addresses.prefixLength"
   ::= {er1645v2EthPortSwIPppOEIpV6AddressesEntry 33554432}

er1645v2EthPortSwIPppOEIpV6AddressesGeneralPrefix OBJECT-TYPE
   SYNTAX      DisplayString
   MAX-ACCESS  read-write
   STATUS      current
   DESCRIPTION
      "Path: swPort.editConf.pppoEClient.ipV6.addresses.generalPrefix"
   ::= {er1645v2EthPortSwIPppOEIpV6AddressesEntry 83886080}

er1645v2EthPortSwIPppOEIpV6AddressesRaSend OBJECT-TYPE
   SYNTAX      INTEGER
               {
               disabled (0),
               enabled (1)
               }
   MAX-ACCESS  read-write
   STATUS      current
   DESCRIPTION
      "Path: swPort.editConf.pppoEClient.ipV6.addresses.ra.send

       Possibilities:
               disabled   (0)
               enabled   (1)"
   ::= {er1645v2EthPortSwIPppOEIpV6AddressesEntry 67174400}

er1645v2EthPortSwIPppOEIpV6AddressesRaOnLinkFlag OBJECT-TYPE
   SYNTAX      INTEGER
               {
               disabled (0),
               enabled (1)
               }
   MAX-ACCESS  read-write
   STATUS      current
   DESCRIPTION
      "Path: swPort.editConf.pppoEClient.ipV6.addresses.ra.onLinkFlag

       Possibilities:
               disabled   (0)
               enabled   (1)"
   ::= {er1645v2EthPortSwIPppOEIpV6AddressesEntry 67371008}

er1645v2EthPortSwIPppOEIpV6AddressesRaAutoFlag OBJECT-TYPE
   SYNTAX      INTEGER
               {
               disabled (0),
               enabled (1)
               }
   MAX-ACCESS  read-write
   STATUS      current
   DESCRIPTION
      "Path: swPort.editConf.pppoEClient.ipV6.addresses.ra.autonomousFlag

       Possibilities:
               disabled   (0)
               enabled   (1)"
   ::= {er1645v2EthPortSwIPppOEIpV6AddressesEntry 67567616}

er1645v2EthPortSwIPppOEIpV6AddressesRaValidLifeTime OBJECT-TYPE
   SYNTAX      TimeTicks
   MAX-ACCESS  read-write
   STATUS      current
   DESCRIPTION
      "Path: swPort.editConf.pppoEClient.ipV6.addresses.ra.validLifeTime

       Time in centi-second."
   ::= {er1645v2EthPortSwIPppOEIpV6AddressesEntry 67239936}

er1645v2EthPortSwIPppOEIpV6AddressesRaValidLTMode OBJECT-TYPE
   SYNTAX      INTEGER
               {
               fixed (0),
               infinite (2)
               }
   MAX-ACCESS  read-write
   STATUS      current
   DESCRIPTION
      "Path: swPort.editConf.pppoEClient.ipV6.addresses.ra.validLifeTimeMode

       Possibilities:
               fixed   (0)
               infinite   (2)"
   ::= {er1645v2EthPortSwIPppOEIpV6AddressesEntry 67305472}

er1645v2EthPortSwIPppOEIpV6AddressesRaPrefLifeTime OBJECT-TYPE
   SYNTAX      TimeTicks
   MAX-ACCESS  read-write
   STATUS      current
   DESCRIPTION
      "Path: swPort.editConf.pppoEClient.ipV6.addresses.ra.prefLifeTime

       Time in centi-second."
   ::= {er1645v2EthPortSwIPppOEIpV6AddressesEntry 67436544}

er1645v2EthPortSwIPppOEIpV6AddressesRaPrefLTMode OBJECT-TYPE
   SYNTAX      INTEGER
               {
               fixed (0),
               infinite (2)
               }
   MAX-ACCESS  read-write
   STATUS      current
   DESCRIPTION
      "Path: swPort.editConf.pppoEClient.ipV6.addresses.ra.prefLifeTimeMode

       Possibilities:
               fixed   (0)
               infinite   (2)"
   ::= {er1645v2EthPortSwIPppOEIpV6AddressesEntry 67502080}

er1645v2EthPortSwIPppOEIpV6RaDnsOptionsRdnssServers OBJECT-TYPE
   SYNTAX      SEQUENCE OF Er1645v2EthPortSwIPppOEIpV6RaDnsOptionsRdnssServersEntry
   MAX-ACCESS  not-accessible
   STATUS      current
   DESCRIPTION
      ""
   ::= {er1645v2EthPortSwIPppOE 705039144}

er1645v2EthPortSwIPppOEIpV6RaDnsOptionsRdnssServersEntry OBJECT-TYPE
   SYNTAX      Er1645v2EthPortSwIPppOEIpV6RaDnsOptionsRdnssServersEntry
   MAX-ACCESS  not-accessible
   STATUS      current
   DESCRIPTION
      ""
   INDEX      { er1645v2EthPortSwIPppOEIpV6RaDnsOptionsRdnssServersGlobalIx,
                er1645v2EthPortSwIPppOETableIx,
                er1645v2EthPortSwIPppOEIpV6RaDnsOptionsRdnssServersTableIx }
   ::= {er1645v2EthPortSwIPppOEIpV6RaDnsOptionsRdnssServers 1}

Er1645v2EthPortSwIPppOEIpV6RaDnsOptionsRdnssServersEntry ::=
   SEQUENCE
      {
      er1645v2EthPortSwIPppOEIpV6RaDnsOptionsRdnssServersActions
         VariableLengthTableActions,
      er1645v2EthPortSwIPppOEIpV6RaDnsOptionsRdnssServersGlobalIx
         GlobalIndex,
      er1645v2EthPortSwIPppOEIpV6RaDnsOptionsRdnssServersTableIx
         TableIndex,
      er1645v2EthPortSwIPppOEIpV6RaDnsOptionsRdnssServersAddress
         Ipv6Address
      }

er1645v2EthPortSwIPppOEIpV6RaDnsOptionsRdnssServersActions OBJECT-TYPE
   SYNTAX      VariableLengthTableActions
   MAX-ACCESS  read-write
   STATUS      current
   DESCRIPTION
      "By way of this field, some manipulations
       on this table may be performed."
   ::= {er1645v2EthPortSwIPppOEIpV6RaDnsOptionsRdnssServersEntry 2}

er1645v2EthPortSwIPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6RaDnsOptionsRdnssServersEntry 10}

er1645v2EthPortSwIPppOEIpV6RaDnsOptionsRdnssServersTableIx OBJECT-TYPE
   SYNTAX      TableIndex
   MAX-ACCESS  not-accessible
   STATUS      current
   DESCRIPTION
      ""
   ::= {er1645v2EthPortSwIPppOEIpV6RaDnsOptionsRdnssServersEntry 11}

er1645v2EthPortSwIPppOEIpV6RaDnsOptionsRdnssServersAddress OBJECT-TYPE
   SYNTAX      Ipv6Address
   MAX-ACCESS  read-write
   STATUS      current
   DESCRIPTION
      "Path: swPort.editConf.pppoEClient.ipV6.ra.dnsOptions.rdnss.servers.address

       ipv6 address"
   ::= {er1645v2EthPortSwIPppOEIpV6RaDnsOptionsRdnssServersEntry 16777216}

er1645v2EthPortSwIPppOEIpV6RaDnsOptionsDnsslDomains OBJECT-TYPE
   SYNTAX      SEQUENCE OF Er1645v2EthPortSwIPppOEIpV6RaDnsOptionsDnsslDomainsEntry
   MAX-ACCESS  not-accessible
   STATUS      current
   DESCRIPTION
      ""
   ::= {er1645v2EthPortSwIPppOE 705039176}

er1645v2EthPortSwIPppOEIpV6RaDnsOptionsDnsslDomainsEntry OBJECT-TYPE
   SYNTAX      Er1645v2EthPortSwIPppOEIpV6RaDnsOptionsDnsslDomainsEntry
   MAX-ACCESS  not-accessible
   STATUS      current
   DESCRIPTION
      ""
   INDEX      { er1645v2EthPortSwIPppOEIpV6RaDnsOptionsDnsslDomainsGlobalIx,
                er1645v2EthPortSwIPppOETableIx,
                er1645v2EthPortSwIPppOEIpV6RaDnsOptionsDnsslDomainsTableIx }
   ::= {er1645v2EthPortSwIPppOEIpV6RaDnsOptionsDnsslDomains 1}

Er1645v2EthPortSwIPppOEIpV6RaDnsOptionsDnsslDomainsEntry ::=
   SEQUENCE
      {
      er1645v2EthPortSwIPppOEIpV6RaDnsOptionsDnsslDomainsActions
         VariableLengthTableActions,
      er1645v2EthPortSwIPppOEIpV6RaDnsOptionsDnsslDomainsGlobalIx
         GlobalIndex,
      er1645v2EthPortSwIPppOEIpV6RaDnsOptionsDnsslDomainsTableIx
         TableIndex,
      er1645v2EthPortSwIPppOEIpV6RaDnsOptionsDnsslDomainsName
         DisplayString
      }

er1645v2EthPortSwIPppOEIpV6RaDnsOptionsDnsslDomainsActions OBJECT-TYPE
   SYNTAX      VariableLengthTableActions
   MAX-ACCESS  read-write
   STATUS      current
   DESCRIPTION
      "By way of this field, some manipulations
       on this table may be performed."
   ::= {er1645v2EthPortSwIPppOEIpV6RaDnsOptionsDnsslDomainsEntry 2}

er1645v2EthPortSwIPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6RaDnsOptionsDnsslDomainsEntry 10}

er1645v2EthPortSwIPppOEIpV6RaDnsOptionsDnsslDomainsTableIx OBJECT-TYPE
   SYNTAX      TableIndex
   MAX-ACCESS  not-accessible
   STATUS      current
   DESCRIPTION
      ""
   ::= {er1645v2EthPortSwIPppOEIpV6RaDnsOptionsDnsslDomainsEntry 11}

er1645v2EthPortSwIPppOEIpV6RaDnsOptionsDnsslDomainsName OBJECT-TYPE
   SYNTAX      DisplayString
   MAX-ACCESS  read-write
   STATUS      current
   DESCRIPTION
      "Path: swPort.editConf.pppoEClient.ipV6.ra.dnsOptions.dnssl.domains.name"
   ::= {er1645v2EthPortSwIPppOEIpV6RaDnsOptionsDnsslDomainsEntry 16777216}

er1645v2EthPortSwIPppOEIpV6DhcpClientUserClassOpt OBJECT-TYPE
   SYNTAX      SEQUENCE OF Er1645v2EthPortSwIPppOEIpV6DhcpClientUserClassOptEntry
   MAX-ACCESS  not-accessible
   STATUS      current
   DESCRIPTION
      ""
   ::= {er1645v2EthPortSwIPppOE 705312768}

er1645v2EthPortSwIPppOEIpV6DhcpClientUserClassOptEntry OBJECT-TYPE
   SYNTAX      Er1645v2EthPortSwIPppOEIpV6DhcpClientUserClassOptEntry
   MAX-ACCESS  not-accessible
   STATUS      current
   DESCRIPTION
      ""
   INDEX      { er1645v2EthPortSwIPppOEIpV6DhcpClientUserClassOptGlobalIx,
                er1645v2EthPortSwIPppOETableIx,
                er1645v2EthPortSwIPppOEIpV6DhcpClientUserClassOptTableIx }
   ::= {er1645v2EthPortSwIPppOEIpV6DhcpClientUserClassOpt 1}

Er1645v2EthPortSwIPppOEIpV6DhcpClientUserClassOptEntry ::=
   SEQUENCE
      {
      er1645v2EthPortSwIPppOEIpV6DhcpClientUserClassOptActions
         VariableLengthTableActions,
      er1645v2EthPortSwIPppOEIpV6DhcpClientUserClassOptGlobalIx
         GlobalIndex,
      er1645v2EthPortSwIPppOEIpV6DhcpClientUserClassOptTableIx
         TableIndex,
      er1645v2EthPortSwIPppOEIpV6DhcpClientUserClassOptValueAscii
         DisplayString,
      er1645v2EthPortSwIPppOEIpV6DhcpClientUserClassOptValueDecimal
         Integer32,
      er1645v2EthPortSwIPppOEIpV6DhcpClientUserClassOptValueHexData
         OCTET STRING
      }

er1645v2EthPortSwIPppOEIpV6DhcpClientUserClassOptActions OBJECT-TYPE
   SYNTAX      VariableLengthTableActions
   MAX-ACCESS  read-write
   STATUS      current
   DESCRIPTION
      "By way of this field, some manipulations
       on this table may be performed."
   ::= {er1645v2EthPortSwIPppOEIpV6DhcpClientUserClassOptEntry 2}

er1645v2EthPortSwIPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6DhcpClientUserClassOptEntry 10}

er1645v2EthPortSwIPppOEIpV6DhcpClientUserClassOptTableIx OBJECT-TYPE
   SYNTAX      TableIndex
   MAX-ACCESS  not-accessible
   STATUS      current
   DESCRIPTION
      ""
   ::= {er1645v2EthPortSwIPppOEIpV6DhcpClientUserClassOptEntry 11}

er1645v2EthPortSwIPppOEIpV6DhcpClientUserClassOptValueAscii OBJECT-TYPE
   SYNTAX      DisplayString
   MAX-ACCESS  read-write
   STATUS      current
   DESCRIPTION
      "Path: swPort.editConf.pppoEClient.ipV6.dhcp.client.userClassOpt.value.ascii"
   ::= {er1645v2EthPortSwIPppOEIpV6DhcpClientUserClassOptEntry 16842752}

er1645v2EthPortSwIPppOEIpV6DhcpClientUserClassOptValueDecimal OBJECT-TYPE
   SYNTAX      Integer32
   MAX-ACCESS  read-write
   STATUS      current
   DESCRIPTION
      "Path: swPort.editConf.pppoEClient.ipV6.dhcp.client.userClassOpt.value.decimal"
   ::= {er1645v2EthPortSwIPppOEIpV6DhcpClientUserClassOptEntry 16908288}

er1645v2EthPortSwIPppOEIpV6DhcpClientUserClassOptValueHexData OBJECT-TYPE
   SYNTAX      OCTET STRING
   MAX-ACCESS  read-write
   STATUS      current
   DESCRIPTION
      "Path: swPort.editConf.pppoEClient.ipV6.dhcp.client.userClassOpt.value.hexData"
   ::= {er1645v2EthPortSwIPppOEIpV6DhcpClientUserClassOptEntry 16973824}

er1645v2EthPortSwIPppOEIpV6DhcpClientVendorCl OBJECT-TYPE
   SYNTAX      SEQUENCE OF Er1645v2EthPortSwIPppOEIpV6DhcpClientVendorClEntry
   MAX-ACCESS  not-accessible
   STATUS      current
   DESCRIPTION
      ""
   ::= {er1645v2EthPortSwIPppOE 705313792}

er1645v2EthPortSwIPppOEIpV6DhcpClientVendorClEntry OBJECT-TYPE
   SYNTAX      Er1645v2EthPortSwIPppOEIpV6DhcpClientVendorClEntry
   MAX-ACCESS  not-accessible
   STATUS      current
   DESCRIPTION
      ""
   INDEX      { er1645v2EthPortSwIPppOEIpV6DhcpClientVendorClGlobalIx,
                er1645v2EthPortSwIPppOETableIx,
                er1645v2EthPortSwIPppOEIpV6DhcpClientVendorClTableIx }
   ::= {er1645v2EthPortSwIPppOEIpV6DhcpClientVendorCl 1}

Er1645v2EthPortSwIPppOEIpV6DhcpClientVendorClEntry ::=
   SEQUENCE
      {
      er1645v2EthPortSwIPppOEIpV6DhcpClientVendorClActions
         VariableLengthTableActions,
      er1645v2EthPortSwIPppOEIpV6DhcpClientVendorClGlobalIx
         GlobalIndex,
      er1645v2EthPortSwIPppOEIpV6DhcpClientVendorClTableIx
         TableIndex,
      er1645v2EthPortSwIPppOEIpV6DhcpClientVendorClValueAscii
         DisplayString,
      er1645v2EthPortSwIPppOEIpV6DhcpClientVendorClValueDecimal
         Integer32,
      er1645v2EthPortSwIPppOEIpV6DhcpClientVendorClValueHexData
         OCTET STRING
      }

er1645v2EthPortSwIPppOEIpV6DhcpClientVendorClActions OBJECT-TYPE
   SYNTAX      VariableLengthTableActions
   MAX-ACCESS  read-write
   STATUS      current
   DESCRIPTION
      "By way of this field, some manipulations
       on this table may be performed."
   ::= {er1645v2EthPortSwIPppOEIpV6DhcpClientVendorClEntry 2}

er1645v2EthPortSwIPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6DhcpClientVendorClEntry 10}

er1645v2EthPortSwIPppOEIpV6DhcpClientVendorClTableIx OBJECT-TYPE
   SYNTAX      TableIndex
   MAX-ACCESS  not-accessible
   STATUS      current
   DESCRIPTION
      ""
   ::= {er1645v2EthPortSwIPppOEIpV6DhcpClientVendorClEntry 11}

er1645v2EthPortSwIPppOEIpV6DhcpClientVendorClValueAscii OBJECT-TYPE
   SYNTAX      DisplayString
   MAX-ACCESS  read-write
   STATUS      current
   DESCRIPTION
      "Path: swPort.editConf.pppoEClient.ipV6.dhcp.client.vendorClassOpt.value.ascii"
   ::= {er1645v2EthPortSwIPppOEIpV6DhcpClientVendorClEntry 16842752}

er1645v2EthPortSwIPppOEIpV6DhcpClientVendorClValueDecimal OBJECT-TYPE
   SYNTAX      Integer32
   MAX-ACCESS  read-write
   STATUS      current
   DESCRIPTION
      "Path: swPort.editConf.pppoEClient.ipV6.dhcp.client.vendorClassOpt.value.decimal"
   ::= {er1645v2EthPortSwIPppOEIpV6DhcpClientVendorClEntry 16908288}

er1645v2EthPortSwIPppOEIpV6DhcpClientVendorClValueHexData OBJECT-TYPE
   SYNTAX      OCTET STRING
   MAX-ACCESS  read-write
   STATUS      current
   DESCRIPTION
      "Path: swPort.editConf.pppoEClient.ipV6.dhcp.client.vendorClassOpt.value.hexData"
   ::= {er1645v2EthPortSwIPppOEIpV6DhcpClientVendorClEntry 16973824}

er1645v2EthPortSwIPppOEIpV6DhcpRelayDestinations OBJECT-TYPE
   SYNTAX      SEQUENCE OF Er1645v2EthPortSwIPppOEIpV6DhcpRelayDestinationsEntry
   MAX-ACCESS  not-accessible
   STATUS      current
   DESCRIPTION
      ""
   ::= {er1645v2EthPortSwIPppOE 705323072}

er1645v2EthPortSwIPppOEIpV6DhcpRelayDestinationsEntry OBJECT-TYPE
   SYNTAX      Er1645v2EthPortSwIPppOEIpV6DhcpRelayDestinationsEntry
   MAX-ACCESS  not-accessible
   STATUS      current
   DESCRIPTION
      ""
   INDEX      { er1645v2EthPortSwIPppOEIpV6DhcpRelayDestinationsGlobalIx,
                er1645v2EthPortSwIPppOETableIx,
                er1645v2EthPortSwIPppOEIpV6DhcpRelayDestinationsTableIx }
   ::= {er1645v2EthPortSwIPppOEIpV6DhcpRelayDestinations 1}

Er1645v2EthPortSwIPppOEIpV6DhcpRelayDestinationsEntry ::=
   SEQUENCE
      {
      er1645v2EthPortSwIPppOEIpV6DhcpRelayDestinationsActions
         VariableLengthTableActions,
      er1645v2EthPortSwIPppOEIpV6DhcpRelayDestinationsGlobalIx
         GlobalIndex,
      er1645v2EthPortSwIPppOEIpV6DhcpRelayDestinationsTableIx
         TableIndex,
      er1645v2EthPortSwIPppOEIpV6DhcpRelayDestinationsAddress
         Ipv6Address,
      er1645v2EthPortSwIPppOEIpV6DhcpRelayDestinationsInterface
         DisplayString
      }

er1645v2EthPortSwIPppOEIpV6DhcpRelayDestinationsActions OBJECT-TYPE
   SYNTAX      VariableLengthTableActions
   MAX-ACCESS  read-write
   STATUS      current
   DESCRIPTION
      "By way of this field, some manipulations
       on this table may be performed."
   ::= {er1645v2EthPortSwIPppOEIpV6DhcpRelayDestinationsEntry 2}

er1645v2EthPortSwIPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPortSwIPppOEIpV6DhcpRelayDestinationsEntry 10}

er1645v2EthPortSwIPppOEIpV6DhcpRelayDestinationsTableIx OBJECT-TYPE
   SYNTAX      TableIndex
   MAX-ACCESS  not-accessible
   STATUS      current
   DESCRIPTION
      ""
   ::= {er1645v2EthPortSwIPppOEIpV6DhcpRelayDestinationsEntry 11}

er1645v2EthPortSwIPppOEIpV6DhcpRelayDestinationsAddress OBJECT-TYPE
   SYNTAX      Ipv6Address
   MAX-ACCESS  read-write
   STATUS      current
   DESCRIPTION
      "Path: swPort.editConf.pppoEClient.ipV6.dhcp.relay.destinations.address

       ipv6 address"
   ::= {er1645v2EthPortSwIPppOEIpV6DhcpRelayDestinationsEntry 16777216}

er1645v2EthPortSwIPppOEIpV6DhcpRelayDestinationsInterface OBJECT-TYPE
   SYNTAX      DisplayString
   MAX-ACCESS  read-write
   STATUS      current
   DESCRIPTION
      "Path: swPort.editConf.pppoEClient.ipV6.dhcp.relay.destinations.interface"
   ::= {er1645v2EthPortSwIPppOEIpV6DhcpRelayDestinationsEntry 33554432}


er1645v2EthPortSwIPppOES OBJECT IDENTIFIER ::= {er1645v2EthPortSwI 37}

er1645v2EthPortSwIPppOESTable OBJECT-TYPE
   SYNTAX      SEQUENCE OF Er1645v2EthPortSwIPppOESEntry
   MAX-ACCESS  not-accessible
   STATUS      current
   DESCRIPTION
      "ppp server name on interface"
   ::= {er1645v2EthPortSwIPppOES 1}

er1645v2EthPortSwIPppOESEntry OBJECT-TYPE
   SYNTAX      Er1645v2EthPortSwIPppOESEntry
   MAX-ACCESS  not-accessible
   STATUS      current
   DESCRIPTION
      ""
   INDEX      { er1645v2EthPortSwIPppOESGlobalIx }
   ::= {er1645v2EthPortSwIPppOESTable 1}

Er1645v2EthPortSwIPppOESEntry ::=
   SEQUENCE
      {
      er1645v2EthPortSwIPppOESGlobalIx
         GlobalIndex,
      er1645v2EthPortSwIPppOESValue
         DisplayString
      }

er1645v2EthPortSwIPppOESGlobalIx OBJECT-TYPE
   SYNTAX      GlobalIndex
   MAX-ACCESS  not-accessible
   STATUS      current
   DESCRIPTION
      "The value of the tlsCntTreeGlobalIndex of the MANAGED OBJECT."
   ::= {er1645v2EthPortSwIPppOESEntry 10}

er1645v2EthPortSwIPppOESValue OBJECT-TYPE
   SYNTAX      DisplayString
   MAX-ACCESS  read-write
   STATUS      current
   DESCRIPTION
      "Path: swPort.editConf.pppoEServer"
   ::= {er1645v2EthPortSwIPppOESEntry 2147483648}


er1645v2EthPortSwIAdminStatus OBJECT IDENTIFIER ::= {er1645v2EthPortSwI 106}

er1645v2EthPortSwIAdminStatusTable OBJECT-TYPE
   SYNTAX      SEQUENCE OF Er1645v2EthPortSwIAdminStatusEntry
   MAX-ACCESS  not-accessible
   STATUS      current
   DESCRIPTION
      "ifAdminStatus"
   ::= {er1645v2EthPortSwIAdminStatus 1}

er1645v2EthPortSwIAdminStatusEntry OBJECT-TYPE
   SYNTAX      Er1645v2EthPortSwIAdminStatusEntry
   MAX-ACCESS  not-accessible
   STATUS      current
   DESCRIPTION
      ""
   INDEX      { er1645v2EthPortSwIAdminStatusGlobalIx }
   ::= {er1645v2EthPortSwIAdminStatusTable 1}

Er1645v2EthPortSwIAdminStatusEntry ::=
   SEQUENCE
      {
      er1645v2EthPortSwIAdminStatusGlobalIx
         GlobalIndex,
      er1645v2EthPortSwIAdminStatusValue
         INTEGER
      }

er1645v2EthPortSwIAdminStatusGlobalIx OBJECT-TYPE
   SYNTAX      GlobalIndex
   MAX-ACCESS  not-accessible
   STATUS      current
   DESCRIPTION
      "The value of the tlsCntTreeGlobalIndex of the MANAGED OBJECT."
   ::= {er1645v2EthPortSwIAdminStatusEntry 10}

er1645v2EthPortSwIAdminStatusValue OBJECT-TYPE
   SYNTAX      INTEGER
               {
               up (1),
               down (2)
               }
   MAX-ACCESS  read-write
   STATUS      current
   DESCRIPTION
      "Path: swPort.editConf.adminStatus

       Possibilities:
               up   (1)
               down   (2)"
   ::= {er1645v2EthPortSwIAdminStatusEntry 2147483648}


er1645v2EthPortSwIAlarmMask OBJECT IDENTIFIER ::= {er1645v2EthPortSwI 135}

er1645v2EthPortSwIAlarmMaskTable OBJECT-TYPE
   SYNTAX      SEQUENCE OF Er1645v2EthPortSwIAlarmMaskEntry
   MAX-ACCESS  not-accessible
   STATUS      current
   DESCRIPTION
      "ifAlarmMask"
   ::= {er1645v2EthPortSwIAlarmMask 1}

er1645v2EthPortSwIAlarmMaskEntry OBJECT-TYPE
   SYNTAX      Er1645v2EthPortSwIAlarmMaskEntry
   MAX-ACCESS  not-accessible
   STATUS      current
   DESCRIPTION
      ""
   INDEX      { er1645v2EthPortSwIAlarmMaskGlobalIx }
   ::= {er1645v2EthPortSwIAlarmMaskTable 1}

Er1645v2EthPortSwIAlarmMaskEntry ::=
   SEQUENCE
      {
      er1645v2EthPortSwIAlarmMaskGlobalIx
         GlobalIndex,
      er1645v2EthPortSwIAlarmMaskValue
         Integer32
      }

er1645v2EthPortSwIAlarmMaskGlobalIx OBJECT-TYPE
   SYNTAX      GlobalIndex
   MAX-ACCESS  not-accessible
   STATUS      current
   DESCRIPTION
      "The value of the tlsCntTreeGlobalIndex of the MANAGED OBJECT."
   ::= {er1645v2EthPortSwIAlarmMaskEntry 10}

er1645v2EthPortSwIAlarmMaskValue OBJECT-TYPE
   SYNTAX      Integer32
   MAX-ACCESS  read-write
   STATUS      current
   DESCRIPTION
      "Path: swPort.editConf.alarmMask

       Bit meanings:
               bit 0 = linkDown,
               bit 9 = pppoEDown"
   ::= {er1645v2EthPortSwIAlarmMaskEntry 2147483648}


er1645v2EthPortSwIAlarmLev OBJECT IDENTIFIER ::= {er1645v2EthPortSwI 170}

er1645v2EthPortSwIAlarmLevSSCTable OBJECT-TYPE
   SYNTAX      SEQUENCE OF Er1645v2EthPortSwIAlarmLevEntry
   MAX-ACCESS  not-accessible
   STATUS      current
   DESCRIPTION
      "IfAlarmLevels"
   ::= {er1645v2EthPortSwIAlarmLev 1}

er1645v2EthPortSwIAlarmLevEntry OBJECT-TYPE
   SYNTAX      Er1645v2EthPortSwIAlarmLevEntry
   MAX-ACCESS  not-accessible
   STATUS      current
   DESCRIPTION
      ""
   INDEX      { er1645v2EthPortSwIAlarmLevGlobalIx }
   ::= {er1645v2EthPortSwIAlarmLevSSCTable 1}

Er1645v2EthPortSwIAlarmLevEntry ::=
   SEQUENCE
      {
      er1645v2EthPortSwIAlarmLevGlobalIx
         GlobalIndex,
      er1645v2EthPortSwIAlarmLevLinkDown
         Integer32,
      er1645v2EthPortSwIAlarmLevPppoEDown
         Integer32
      }

er1645v2EthPortSwIAlarmLevGlobalIx OBJECT-TYPE
   SYNTAX      GlobalIndex
   MAX-ACCESS  not-accessible
   STATUS      current
   DESCRIPTION
      "The value of the tlsCntTreeGlobalIndex of the MANAGED OBJECT."
   ::= {er1645v2EthPortSwIAlarmLevEntry 10}

er1645v2EthPortSwIAlarmLevLinkDown OBJECT-TYPE
   SYNTAX      Integer32
   MAX-ACCESS  read-write
   STATUS      current
   DESCRIPTION
      "Path: swPort.editConf.alarmLevel.linkDown"
   ::= {er1645v2EthPortSwIAlarmLevEntry 16777216}

er1645v2EthPortSwIAlarmLevPppoEDown OBJECT-TYPE
   SYNTAX      Integer32
   MAX-ACCESS  read-write
   STATUS      current
   DESCRIPTION
      "Path: swPort.editConf.alarmLevel.pppoEDown"
   ::= {er1645v2EthPortSwIAlarmLevEntry 167772160}


er1645v2EthPortSwIPriorityPolicy OBJECT IDENTIFIER ::= {er1645v2EthPortSwI 39}

er1645v2EthPortSwIPriorityPolicyTable OBJECT-TYPE
   SYNTAX      SEQUENCE OF Er1645v2EthPortSwIPriorityPolicyEntry
   MAX-ACCESS  not-accessible
   STATUS      current
   DESCRIPTION
      "Preferred Policy"
   ::= {er1645v2EthPortSwIPriorityPolicy 1}

er1645v2EthPortSwIPriorityPolicyEntry OBJECT-TYPE
   SYNTAX      Er1645v2EthPortSwIPriorityPolicyEntry
   MAX-ACCESS  not-accessible
   STATUS      current
   DESCRIPTION
      ""
   INDEX      { er1645v2EthPortSwIPriorityPolicyGlobalIx }
   ::= {er1645v2EthPortSwIPriorityPolicyTable 1}

Er1645v2EthPortSwIPriorityPolicyEntry ::=
   SEQUENCE
      {
      er1645v2EthPortSwIPriorityPolicyGlobalIx
         GlobalIndex,
      er1645v2EthPortSwIPriorityPolicyValue
         DisplayString
      }

er1645v2EthPortSwIPriorityPolicyGlobalIx OBJECT-TYPE
   SYNTAX      GlobalIndex
   MAX-ACCESS  not-accessible
   STATUS      current
   DESCRIPTION
      "The value of the tlsCntTreeGlobalIndex of the MANAGED OBJECT."
   ::= {er1645v2EthPortSwIPriorityPolicyEntry 10}

er1645v2EthPortSwIPriorityPolicyValue OBJECT-TYPE
   SYNTAX      DisplayString
   MAX-ACCESS  read-write
   STATUS      current
   DESCRIPTION
      "Path: swPort.editConf.priorityPolicy"
   ::= {er1645v2EthPortSwIPriorityPolicyEntry 2147483648}


er1645v2EthPortSwILst OBJECT IDENTIFIER ::= {er1645v2EthPortSwI 12}

er1645v2EthPortSwILstSSCTable OBJECT-TYPE
   SYNTAX      SEQUENCE OF Er1645v2EthPortSwILstEntry
   MAX-ACCESS  not-accessible
   STATUS      current
   DESCRIPTION
      ""
   ::= {er1645v2EthPortSwILst 1}

er1645v2EthPortSwILstEntry OBJECT-TYPE
   SYNTAX      Er1645v2EthPortSwILstEntry
   MAX-ACCESS  not-accessible
   STATUS      current
   DESCRIPTION
      ""
   INDEX      { er1645v2EthPortSwILstGlobalIx }
   ::= {er1645v2EthPortSwILstSSCTable 1}

Er1645v2EthPortSwILstEntry ::=
   SEQUENCE
      {
      er1645v2EthPortSwILstGlobalIx
         GlobalIndex,
      er1645v2EthPortSwILstTrackedInterface
         DisplayString
      }

er1645v2EthPortSwILstGlobalIx OBJECT-TYPE
   SYNTAX      GlobalIndex
   MAX-ACCESS  not-accessible
   STATUS      current
   DESCRIPTION
      "The value of the tlsCntTreeGlobalIndex of the MANAGED OBJECT."
   ::= {er1645v2EthPortSwILstEntry 10}

er1645v2EthPortSwILstTrackedInterface OBJECT-TYPE
   SYNTAX      DisplayString
   MAX-ACCESS  read-write
   STATUS      current
   DESCRIPTION
      "Path: swPort.editConf.linkStateTracking.trackedInterface"
   ::= {er1645v2EthPortSwILstEntry 16777216}


er1645v2EthPortSwISnmpIndexOffset OBJECT IDENTIFIER ::= {er1645v2EthPortSwI 268}

er1645v2EthPortSwISnmpIndexOffsetTable OBJECT-TYPE
   SYNTAX      SEQUENCE OF Er1645v2EthPortSwISnmpIndexOffsetEntry
   MAX-ACCESS  not-accessible
   STATUS      current
   DESCRIPTION
      "Preferred offset in the range of SNMP indices for this SWinst, 0 means automatic"
   ::= {er1645v2EthPortSwISnmpIndexOffset 1}

er1645v2EthPortSwISnmpIndexOffsetEntry OBJECT-TYPE
   SYNTAX      Er1645v2EthPortSwISnmpIndexOffsetEntry
   MAX-ACCESS  not-accessible
   STATUS      current
   DESCRIPTION
      ""
   INDEX      { er1645v2EthPortSwISnmpIndexOffsetGlobalIx }
   ::= {er1645v2EthPortSwISnmpIndexOffsetTable 1}

Er1645v2EthPortSwISnmpIndexOffsetEntry ::=
   SEQUENCE
      {
      er1645v2EthPortSwISnmpIndexOffsetGlobalIx
         GlobalIndex,
      er1645v2EthPortSwISnmpIndexOffsetValue
         Integer32
      }

er1645v2EthPortSwISnmpIndexOffsetGlobalIx OBJECT-TYPE
   SYNTAX      GlobalIndex
   MAX-ACCESS  not-accessible
   STATUS      current
   DESCRIPTION
      "The value of the tlsCntTreeGlobalIndex of the MANAGED OBJECT."
   ::= {er1645v2EthPortSwISnmpIndexOffsetEntry 10}

er1645v2EthPortSwISnmpIndexOffsetValue OBJECT-TYPE
   SYNTAX      Integer32
   MAX-ACCESS  read-write
   STATUS      current
   DESCRIPTION
      "Path: swPort.editConf.snmpIndexOffset"
   ::= {er1645v2EthPortSwISnmpIndexOffsetEntry 2147483648}



sr1645v2EthPortSwI OBJECT IDENTIFIER ::= {r1645v2EthPortSwI 14}


sr1645v2EthPortSwIDescr OBJECT IDENTIFIER ::= {sr1645v2EthPortSwI 101}

sr1645v2EthPortSwIDescrTable OBJECT-TYPE
   SYNTAX      SEQUENCE OF Sr1645v2EthPortSwIDescrEntry
   MAX-ACCESS  not-accessible
   STATUS      current
   DESCRIPTION
      "ifDescr"
   ::= {sr1645v2EthPortSwIDescr 1}

sr1645v2EthPortSwIDescrEntry OBJECT-TYPE
   SYNTAX      Sr1645v2EthPortSwIDescrEntry
   MAX-ACCESS  not-accessible
   STATUS      current
   DESCRIPTION
      ""
   INDEX      { sr1645v2EthPortSwIDescrGlobalIx }
   ::= {sr1645v2EthPortSwIDescrTable 1}

Sr1645v2EthPortSwIDescrEntry ::=
   SEQUENCE
      {
      sr1645v2EthPortSwIDescrGlobalIx
         GlobalIndex,
      sr1645v2EthPortSwIDescrValue
         DisplayString
      }

sr1645v2EthPortSwIDescrGlobalIx OBJECT-TYPE
   SYNTAX      GlobalIndex
   MAX-ACCESS  not-accessible
   STATUS      current
   DESCRIPTION
      "The value of the tlsCntTreeGlobalIndex of the MANAGED OBJECT."
   ::= {sr1645v2EthPortSwIDescrEntry 10}

sr1645v2EthPortSwIDescrValue OBJECT-TYPE
   SYNTAX      DisplayString
   MAX-ACCESS  read-only
   STATUS      current
   DESCRIPTION
      "Path: swPort.status.ifDescr"
   ::= {sr1645v2EthPortSwIDescrEntry 2147483648}


sr1645v2EthPortSwIType OBJECT IDENTIFIER ::= {sr1645v2EthPortSwI 102}

sr1645v2EthPortSwITypeTable OBJECT-TYPE
   SYNTAX      SEQUENCE OF Sr1645v2EthPortSwITypeEntry
   MAX-ACCESS  not-accessible
   STATUS      current
   DESCRIPTION
      "ifType"
   ::= {sr1645v2EthPortSwIType 1}

sr1645v2EthPortSwITypeEntry OBJECT-TYPE
   SYNTAX      Sr1645v2EthPortSwITypeEntry
   MAX-ACCESS  not-accessible
   STATUS      current
   DESCRIPTION
      ""
   INDEX      { sr1645v2EthPortSwITypeGlobalIx }
   ::= {sr1645v2EthPortSwITypeTable 1}

Sr1645v2EthPortSwITypeEntry ::=
   SEQUENCE
      {
      sr1645v2EthPortSwITypeGlobalIx
         GlobalIndex,
      sr1645v2EthPortSwITypeValue
         INTEGER
      }

sr1645v2EthPortSwITypeGlobalIx OBJECT-TYPE
   SYNTAX      GlobalIndex
   MAX-ACCESS  not-accessible
   STATUS      current
   DESCRIPTION
      "The value of the tlsCntTreeGlobalIndex of the MANAGED OBJECT."
   ::= {sr1645v2EthPortSwITypeEntry 10}

sr1645v2EthPortSwITypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: swPort.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2EthPortSwITypeEntry 2147483648}


sr1645v2EthPortSwIMtu OBJECT IDENTIFIER ::= {sr1645v2EthPortSwI 103}

sr1645v2EthPortSwIMtuTable OBJECT-TYPE
   SYNTAX      SEQUENCE OF Sr1645v2EthPortSwIMtuEntry
   MAX-ACCESS  not-accessible
   STATUS      current
   DESCRIPTION
      "ifMtu"
   ::= {sr1645v2EthPortSwIMtu 1}

sr1645v2EthPortSwIMtuEntry OBJECT-TYPE
   SYNTAX      Sr1645v2EthPortSwIMtuEntry
   MAX-ACCESS  not-accessible
   STATUS      current
   DESCRIPTION
      ""
   INDEX      { sr1645v2EthPortSwIMtuGlobalIx }
   ::= {sr1645v2EthPortSwIMtuTable 1}

Sr1645v2EthPortSwIMtuEntry ::=
   SEQUENCE
      {
      sr1645v2EthPortSwIMtuGlobalIx
         GlobalIndex,
      sr1645v2EthPortSwIMtuValue
         Integer32
      }

sr1645v2EthPortSwIMtuGlobalIx OBJECT-TYPE
   SYNTAX      GlobalIndex
   MAX-ACCESS  not-accessible
   STATUS      current
   DESCRIPTION
      "The value of the tlsCntTreeGlobalIndex of the MANAGED OBJECT."
   ::= {sr1645v2EthPortSwIMtuEntry 10}

sr1645v2EthPortSwIMtuValue OBJECT-TYPE
   SYNTAX      Integer32
   MAX-ACCESS  read-only
   STATUS      current
   DESCRIPTION
      "Path: swPort.status.ifMtu"
   ::= {sr1645v2EthPortSwIMtuEntry 2147483648}


sr1645v2EthPortSwIOperStatus OBJECT IDENTIFIER ::= {sr1645v2EthPortSwI 107}

sr1645v2EthPortSwIOperStatusTable OBJECT-TYPE
   SYNTAX      SEQUENCE OF Sr1645v2EthPortSwIOperStatusEntry
   MAX-ACCESS  not-accessible
   STATUS      current
   DESCRIPTION
      "ifOperStatus"
   ::= {sr1645v2EthPortSwIOperStatus 1}

sr1645v2EthPortSwIOperStatusEntry OBJECT-TYPE
   SYNTAX      Sr1645v2EthPortSwIOperStatusEntry
   MAX-ACCESS  not-accessible
   STATUS      current
   DESCRIPTION
      ""
   INDEX      { sr1645v2EthPortSwIOperStatusGlobalIx }
   ::= {sr1645v2EthPortSwIOperStatusTable 1}

Sr1645v2EthPortSwIOperStatusEntry ::=
   SEQUENCE
      {
      sr1645v2EthPortSwIOperStatusGlobalIx
         GlobalIndex,
      sr1645v2EthPortSwIOperStatusValue
         INTEGER
      }

sr1645v2EthPortSwIOperStatusGlobalIx OBJECT-TYPE
   SYNTAX      GlobalIndex
   MAX-ACCESS  not-accessible
   STATUS      current
   DESCRIPTION
      "The value of the tlsCntTreeGlobalIndex of the MANAGED OBJECT."
   ::= {sr1645v2EthPortSwIOperStatusEntry 10}

sr1645v2EthPortSwIOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ifOperStatus

       Possibilities:
               up   (1)
               down   (2)
               testing   (3)
               unknown   (4)
               dormant   (5)
               notPresent   (6)
               lowerLayerDown   (7)"
   ::= {sr1645v2EthPortSwIOperStatusEntry 2147483648}


sr1645v2EthPortSwILastChange OBJECT IDENTIFIER ::= {sr1645v2EthPortSwI 108}

sr1645v2EthPortSwILastChangeTable OBJECT-TYPE
   SYNTAX      SEQUENCE OF Sr1645v2EthPortSwILastChangeEntry
   MAX-ACCESS  not-accessible
   STATUS      current
   DESCRIPTION
      "ifLastChange"
   ::= {sr1645v2EthPortSwILastChange 1}

sr1645v2EthPortSwILastChangeEntry OBJECT-TYPE
   SYNTAX      Sr1645v2EthPortSwILastChangeEntry
   MAX-ACCESS  not-accessible
   STATUS      current
   DESCRIPTION
      ""
   INDEX      { sr1645v2EthPortSwILastChangeGlobalIx }
   ::= {sr1645v2EthPortSwILastChangeTable 1}

Sr1645v2EthPortSwILastChangeEntry ::=
   SEQUENCE
      {
      sr1645v2EthPortSwILastChangeGlobalIx
         GlobalIndex,
      sr1645v2EthPortSwILastChangeValue
         TimeTicks
      }

sr1645v2EthPortSwILastChangeGlobalIx OBJECT-TYPE
   SYNTAX      GlobalIndex
   MAX-ACCESS  not-accessible
   STATUS      current
   DESCRIPTION
      "The value of the tlsCntTreeGlobalIndex of the MANAGED OBJECT."
   ::= {sr1645v2EthPortSwILastChangeEntry 10}

sr1645v2EthPortSwILastChangeValue OBJECT-TYPE
   SYNTAX      TimeTicks
   MAX-ACCESS  read-only
   STATUS      current
   DESCRIPTION
      "Path: swPort.status.ifLastChange

       Time in centi-second."
   ::= {sr1645v2EthPortSwILastChangeEntry 2147483648}


sr1645v2EthPortSwILastChangeD OBJECT IDENTIFIER ::= {sr1645v2EthPortSwI 183}

sr1645v2EthPortSwILastChangeDTable OBJECT-TYPE
   SYNTAX      SEQUENCE OF Sr1645v2EthPortSwILastChangeDEntry
   MAX-ACCESS  not-accessible
   STATUS      current
   DESCRIPTION
      "ifLastChangeDate"
   ::= {sr1645v2EthPortSwILastChangeD 1}

sr1645v2EthPortSwILastChangeDEntry OBJECT-TYPE
   SYNTAX      Sr1645v2EthPortSwILastChangeDEntry
   MAX-ACCESS  not-accessible
   STATUS      current
   DESCRIPTION
      ""
   INDEX      { sr1645v2EthPortSwILastChangeDGlobalIx }
   ::= {sr1645v2EthPortSwILastChangeDTable 1}

Sr1645v2EthPortSwILastChangeDEntry ::=
   SEQUENCE
      {
      sr1645v2EthPortSwILastChangeDGlobalIx
         GlobalIndex,
      sr1645v2EthPortSwILastChangeDValue
         DisplayString
      }

sr1645v2EthPortSwILastChangeDGlobalIx OBJECT-TYPE
   SYNTAX      GlobalIndex
   MAX-ACCESS  not-accessible
   STATUS      current
   DESCRIPTION
      "The value of the tlsCntTreeGlobalIndex of the MANAGED OBJECT."
   ::= {sr1645v2EthPortSwILastChangeDEntry 10}

sr1645v2EthPortSwILastChangeDValue OBJECT-TYPE
   SYNTAX      DisplayString
   MAX-ACCESS  read-only
   STATUS      current
   DESCRIPTION
      "Path: swPort.status.ifLastChangeDate"
   ::= {sr1645v2EthPortSwILastChangeDEntry 2147483648}


sr1645v2EthPortSwISpeed OBJECT IDENTIFIER ::= {sr1645v2EthPortSwI 104}

sr1645v2EthPortSwISpeedTable OBJECT-TYPE
   SYNTAX      SEQUENCE OF Sr1645v2EthPortSwISpeedEntry
   MAX-ACCESS  not-accessible
   STATUS      current
   DESCRIPTION
      "ifSpeed"
   ::= {sr1645v2EthPortSwISpeed 1}

sr1645v2EthPortSwISpeedEntry OBJECT-TYPE
   SYNTAX      Sr1645v2EthPortSwISpeedEntry
   MAX-ACCESS  not-accessible
   STATUS      current
   DESCRIPTION
      ""
   INDEX      { sr1645v2EthPortSwISpeedGlobalIx }
   ::= {sr1645v2EthPortSwISpeedTable 1}

Sr1645v2EthPortSwISpeedEntry ::=
   SEQUENCE
      {
      sr1645v2EthPortSwISpeedGlobalIx
         GlobalIndex,
      sr1645v2EthPortSwISpeedValue
         Gauge32
      }

sr1645v2EthPortSwISpeedGlobalIx OBJECT-TYPE
   SYNTAX      GlobalIndex
   MAX-ACCESS  not-accessible
   STATUS      current
   DESCRIPTION
      "The value of the tlsCntTreeGlobalIndex of the MANAGED OBJECT."
   ::= {sr1645v2EthPortSwISpeedEntry 10}

sr1645v2EthPortSwISpeedValue OBJECT-TYPE
   SYNTAX      Gauge32
   MAX-ACCESS  read-only
   STATUS      current
   DESCRIPTION
      "Path: swPort.status.ifSpeed

       32 bit unsigned gauge value."
   ::= {sr1645v2EthPortSwISpeedEntry 2147483648}


sr1645v2EthPortSwIIp OBJECT IDENTIFIER ::= {sr1645v2EthPortSwI 16}

sr1645v2EthPortSwIIpSSCTable OBJECT-TYPE
   SYNTAX      SEQUENCE OF Sr1645v2EthPortSwIIpEntry
   MAX-ACCESS  not-accessible
   STATUS      current
   DESCRIPTION
      "ip interface status parameters"
   ::= {sr1645v2EthPortSwIIp 1}

sr1645v2EthPortSwIIpEntry OBJECT-TYPE
   SYNTAX      Sr1645v2EthPortSwIIpEntry
   MAX-ACCESS  not-accessible
   STATUS      current
   DESCRIPTION
      ""
   INDEX      { sr1645v2EthPortSwIIpGlobalIx }
   ::= {sr1645v2EthPortSwIIpSSCTable 1}

Sr1645v2EthPortSwIIpEntry ::=
   SEQUENCE
      {
      sr1645v2EthPortSwIIpGlobalIx
         GlobalIndex,
      sr1645v2EthPortSwIIpStatus
         INTEGER,
      sr1645v2EthPortSwIIpAddress
         IpAddress,
      sr1645v2EthPortSwIIpNetMask
         IpAddress,
      sr1645v2EthPortSwIIpDhcpStatus
         INTEGER,
      sr1645v2EthPortSwIIpDhcpLeaseTime
         TimeTicks
      }

sr1645v2EthPortSwIIpGlobalIx OBJECT-TYPE
   SYNTAX      GlobalIndex
   MAX-ACCESS  not-accessible
   STATUS      current
   DESCRIPTION
      "The value of the tlsCntTreeGlobalIndex of the MANAGED OBJECT."
   ::= {sr1645v2EthPortSwIIpEntry 10}

sr1645v2EthPortSwIIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ip.status

       Possibilities:
               up   (1)
               down   (2)
               testing   (3)
               unknown   (4)
               dormant   (5)
               notPresent   (6)
               lowerLayerDown   (7)"
   ::= {sr1645v2EthPortSwIIpEntry 1795162112}

sr1645v2EthPortSwIIpAddress OBJECT-TYPE
   SYNTAX      IpAddress
   MAX-ACCESS  read-only
   STATUS      current
   DESCRIPTION
      "Path: swPort.status.ip.address"
   ::= {sr1645v2EthPortSwIIpEntry 2030043136}

sr1645v2EthPortSwIIpNetMask OBJECT-TYPE
   SYNTAX      IpAddress
   MAX-ACCESS  read-only
   STATUS      current
   DESCRIPTION
      "Path: swPort.status.ip.netMask"
   ::= {sr1645v2EthPortSwIIpEntry 2063597568}

sr1645v2EthPortSwIIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.ip.dhcp.status

       Possibilities:
               none   (0)
               selecting   (1)
               requesting   (2)
               rebinding   (3)
               bound   (4)
               renewing   (5)
               rebooting   (6)
               initreboot   (7)"
   ::= {sr1645v2EthPortSwIIpEntry 402718720}

sr1645v2EthPortSwIIpDhcpLeaseTime OBJECT-TYPE
   SYNTAX      TimeTicks
   MAX-ACCESS  read-only
   STATUS      current
   DESCRIPTION
      "Path: swPort.status.ip.dhcp.leaseTime

       Time in centi-second."
   ::= {sr1645v2EthPortSwIIpEntry 402784256}

sr1645v2EthPortSwIIpSecondaryIp OBJECT-TYPE
   SYNTAX      SEQUENCE OF Sr1645v2EthPortSwIIpSecondaryIpEntry
   MAX-ACCESS  not-accessible
   STATUS      current
   DESCRIPTION
      ""
   ::= {sr1645v2EthPortSwIIp 385875968}

sr1645v2EthPortSwIIpSecondaryIpEntry OBJECT-TYPE
   SYNTAX      Sr1645v2EthPortSwIIpSecondaryIpEntry
   MAX-ACCESS  not-accessible
   STATUS      current
   DESCRIPTION
      ""
   INDEX      { sr1645v2EthPortSwIIpSecondaryIpGlobalIx,
                sr1645v2EthPortSwIIpSecondaryIpTableIx }
   ::= {sr1645v2EthPortSwIIpSecondaryIp 1}

Sr1645v2EthPortSwIIpSecondaryIpEntry ::=
   SEQUENCE
      {
      sr1645v2EthPortSwIIpSecondaryIpGlobalIx
         GlobalIndex,
      sr1645v2EthPortSwIIpSecondaryIpTableIx
         TableIndex,
      sr1645v2EthPortSwIIpSecondaryIpAddress
         IpAddress,
      sr1645v2EthPortSwIIpSecondaryIpNetMask
         IpAddress
      }

sr1645v2EthPortSwIIpSecondaryIpGlobalIx OBJECT-TYPE
   SYNTAX      GlobalIndex
   MAX-ACCESS  not-accessible
   STATUS      current
   DESCRIPTION
      "The value of the tlsCntTreeGlobalIndex of the MANAGED OBJECT."
   ::= {sr1645v2EthPortSwIIpSecondaryIpEntry 10}

sr1645v2EthPortSwIIpSecondaryIpTableIx OBJECT-TYPE
   SYNTAX      TableIndex
   MAX-ACCESS  not-accessible
   STATUS      current
   DESCRIPTION
      ""
   ::= {sr1645v2EthPortSwIIpSecondaryIpEntry 11}

sr1645v2EthPortSwIIpSecondaryIpAddress OBJECT-TYPE
   SYNTAX      IpAddress
   MAX-ACCESS  read-only
   STATUS      current
   DESCRIPTION
      "Path: swPort.status.ip.secondaryIp.address"
   ::= {sr1645v2EthPortSwIIpSecondaryIpEntry 2030043136}

sr1645v2EthPortSwIIpSecondaryIpNetMask OBJECT-TYPE
   SYNTAX      IpAddress
   MAX-ACCESS  read-only
   STATUS      current
   DESCRIPTION
      "Path: swPort.status.ip.secondaryIp.netMask"
   ::= {sr1645v2EthPortSwIIpSecondaryIpEntry 2063597568}


sr1645v2EthPortSwIArpCache OBJECT IDENTIFIER ::= {sr1645v2EthPortSwI 11}

sr1645v2EthPortSwIArpCacheSSCTable OBJECT-TYPE
   SYNTAX      SEQUENCE OF Sr1645v2EthPortSwIArpCacheEntry
   MAX-ACCESS  not-accessible
   STATUS      current
   DESCRIPTION
      "arp cache of ethernet interface"
   ::= {sr1645v2EthPortSwIArpCache 1}

sr1645v2EthPortSwIArpCacheEntry OBJECT-TYPE
   SYNTAX      Sr1645v2EthPortSwIArpCacheEntry
   MAX-ACCESS  not-accessible
   STATUS      current
   DESCRIPTION
      ""
   INDEX      { sr1645v2EthPortSwIArpCacheGlobalIx,
                sr1645v2EthPortSwIArpCacheTableIx }
   ::= {sr1645v2EthPortSwIArpCacheSSCTable 1}

Sr1645v2EthPortSwIArpCacheEntry ::=
   SEQUENCE
      {
      sr1645v2EthPortSwIArpCacheGlobalIx
         GlobalIndex,
      sr1645v2EthPortSwIArpCacheTableIx
         TableIndex,
      sr1645v2EthPortSwIArpCacheMacAddress
         OCTET STRING,
      sr1645v2EthPortSwIArpCacheIpAddress
         IpAddress,
      sr1645v2EthPortSwIArpCacheType
         INTEGER,
      sr1645v2EthPortSwIArpCacheTimeOut
         TimeTicks
      }

sr1645v2EthPortSwIArpCacheGlobalIx OBJECT-TYPE
   SYNTAX      GlobalIndex
   MAX-ACCESS  not-accessible
   STATUS      current
   DESCRIPTION
      "The value of the tlsCntTreeGlobalIndex of the MANAGED OBJECT."
   ::= {sr1645v2EthPortSwIArpCacheEntry 10}

sr1645v2EthPortSwIArpCacheTableIx OBJECT-TYPE
   SYNTAX      TableIndex
   MAX-ACCESS  not-accessible
   STATUS      current
   DESCRIPTION
      ""
   ::= {sr1645v2EthPortSwIArpCacheEntry 11}

sr1645v2EthPortSwIArpCacheMacAddress OBJECT-TYPE
   SYNTAX      OCTET STRING
   MAX-ACCESS  read-only
   STATUS      current
   DESCRIPTION
      "Path: swPort.status.arpCache.macAddress

       MAC address."
   ::= {sr1645v2EthPortSwIArpCacheEntry 16777216}

sr1645v2EthPortSwIArpCacheIpAddress OBJECT-TYPE
   SYNTAX      IpAddress
   MAX-ACCESS  read-only
   STATUS      current
   DESCRIPTION
      "Path: swPort.status.arpCache.ipAddress"
   ::= {sr1645v2EthPortSwIArpCacheEntry 33554432}

sr1645v2EthPortSwIArpCacheType OBJECT-TYPE
   SYNTAX      INTEGER
               {
               static (0),
               dynamic (1)
               }
   MAX-ACCESS  read-only
   STATUS      current
   DESCRIPTION
      "Path: swPort.status.arpCache.type

       Possibilities:
               static   (0)
               dynamic   (1)"
   ::= {sr1645v2EthPortSwIArpCacheEntry 50331648}

sr1645v2EthPortSwIArpCacheTimeOut OBJECT-TYPE
   SYNTAX      TimeTicks
   MAX-ACCESS  read-only
   STATUS      current
   DESCRIPTION
      "Path: swPort.status.arpCache.timeOut

       Time in centi-second."
   ::= {sr1645v2EthPortSwIArpCacheEntry 67108864}


sr1645v2EthPortSwIBrS OBJECT IDENTIFIER ::= {sr1645v2EthPortSwI 28}

sr1645v2EthPortSwIBrSSSCTable OBJECT-TYPE
   SYNTAX      SEQUENCE OF Sr1645v2EthPortSwIBrSEntry
   MAX-ACCESS  not-accessible
   STATUS      current
   DESCRIPTION
      "spanning tree status ethernet interface"
   ::= {sr1645v2EthPortSwIBrS 1}

sr1645v2EthPortSwIBrSEntry OBJECT-TYPE
   SYNTAX      Sr1645v2EthPortSwIBrSEntry
   MAX-ACCESS  not-accessible
   STATUS      current
   DESCRIPTION
      ""
   INDEX      { sr1645v2EthPortSwIBrSGlobalIx }
   ::= {sr1645v2EthPortSwIBrSSSCTable 1}

Sr1645v2EthPortSwIBrSEntry ::=
   SEQUENCE
      {
      sr1645v2EthPortSwIBrSGlobalIx
         GlobalIndex,
      sr1645v2EthPortSwIBrSStatus
         INTEGER,
      sr1645v2EthPortSwIBrSStPortRole
         INTEGER,
      sr1645v2EthPortSwIBrSStPortId
         Integer32,
      sr1645v2EthPortSwIBrSStPpCostExtPathCost
         Integer32,
      sr1645v2EthPortSwIBrSStPpCostIntPathCost
         Integer32,
      sr1645v2EthPortSwIBrSStExtRpCost
         Integer32,
      sr1645v2EthPortSwIBrSStIntRpCost
         Integer32,
      sr1645v2EthPortSwIBrSStDesBrIdPriority
         Integer32,
      sr1645v2EthPortSwIBrSStDesBrIdMacAddress
         OCTET STRING,
      sr1645v2EthPortSwIBrSStDesPrtId
         Integer32,
      sr1645v2EthPortSwIBrSStDesInt
         INTEGER,
      sr1645v2EthPortSwIBrSStEdgeDetection
         INTEGER
      }

sr1645v2EthPortSwIBrSGlobalIx OBJECT-TYPE
   SYNTAX      GlobalIndex
   MAX-ACCESS  not-accessible
   STATUS      current
   DESCRIPTION
      "The value of the tlsCntTreeGlobalIndex of the MANAGED OBJECT."
   ::= {sr1645v2EthPortSwIBrSEntry 10}

sr1645v2EthPortSwIBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.bridging.status

       Possibilities:
               disabled   (0)
               discarding   (1)
               learning   (2)
               forwarding   (3)
               backupBlockedIntfDown   (256)
               backupBlockedIntfUp   (259)
               shutdown   (255)"
   ::= {sr1645v2EthPortSwIBrSEntry 16777216}

sr1645v2EthPortSwIBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.bridging.spanningTree.portRole

       Possibilities:
               none   (0)
               root   (1)
               designated   (2)
               alternate   (3)
               backup   (4)
               disabled   (5)
               master   (6)"
   ::= {sr1645v2EthPortSwIBrSEntry 33619968}

sr1645v2EthPortSwIBrSStPortId OBJECT-TYPE
   SYNTAX      Integer32
   MAX-ACCESS  read-only
   STATUS      current
   DESCRIPTION
      "Path: swPort.status.bridging.spanningTree.portId"
   ::= {sr1645v2EthPortSwIBrSEntry 33685504}

sr1645v2EthPortSwIBrSStPpCostExtPathCost OBJECT-TYPE
   SYNTAX      Integer32
   MAX-ACCESS  read-only
   STATUS      current
   DESCRIPTION
      "Path: swPort.status.bridging.spanningTree.portPathCosts.extPathCost"
   ::= {sr1645v2EthPortSwIBrSEntry 33751296}

sr1645v2EthPortSwIBrSStPpCostIntPathCost OBJECT-TYPE
   SYNTAX      Integer32
   MAX-ACCESS  read-only
   STATUS      current
   DESCRIPTION
      "Path: swPort.status.bridging.spanningTree.portPathCosts.intPathCost"
   ::= {sr1645v2EthPortSwIBrSEntry 33751552}

sr1645v2EthPortSwIBrSStExtRpCost OBJECT-TYPE
   SYNTAX      Integer32
   MAX-ACCESS  read-only
   STATUS      current
   DESCRIPTION
      "Path: swPort.status.bridging.spanningTree.extRootPathCost"
   ::= {sr1645v2EthPortSwIBrSEntry 33816576}

sr1645v2EthPortSwIBrSStIntRpCost OBJECT-TYPE
   SYNTAX      Integer32
   MAX-ACCESS  read-only
   STATUS      current
   DESCRIPTION
      "Path: swPort.status.bridging.spanningTree.intRootPathCost"
   ::= {sr1645v2EthPortSwIBrSEntry 33882112}

sr1645v2EthPortSwIBrSStDesBrIdPriority OBJECT-TYPE
   SYNTAX      Integer32
   MAX-ACCESS  read-only
   STATUS      current
   DESCRIPTION
      "Path: swPort.status.bridging.spanningTree.designatedBridgeId.priority"
   ::= {sr1645v2EthPortSwIBrSEntry 33947904}

sr1645v2EthPortSwIBrSStDesBrIdMacAddress OBJECT-TYPE
   SYNTAX      OCTET STRING
   MAX-ACCESS  read-only
   STATUS      current
   DESCRIPTION
      "Path: swPort.status.bridging.spanningTree.designatedBridgeId.macAddress

       MAC address."
   ::= {sr1645v2EthPortSwIBrSEntry 33948160}

sr1645v2EthPortSwIBrSStDesPrtId OBJECT-TYPE
   SYNTAX      Integer32
   MAX-ACCESS  read-only
   STATUS      current
   DESCRIPTION
      "Path: swPort.status.bridging.spanningTree.designatedPortId"
   ::= {sr1645v2EthPortSwIBrSEntry 34013184}

sr1645v2EthPortSwIBrSStDesInt OBJECT-TYPE
   SYNTAX      INTEGER
               {
               no (0),
               yes (1)
               }
   MAX-ACCESS  read-only
   STATUS      current
   DESCRIPTION
      "Path: swPort.status.bridging.spanningTree.designatedOrInternal

       Possibilities:
               no   (0)
               yes   (1)"
   ::= {sr1645v2EthPortSwIBrSEntry 34078720}

sr1645v2EthPortSwIBrSStEdgeDetection OBJECT-TYPE
   SYNTAX      INTEGER
               {
               none (0),
               edge (1),
               notEdge (2)
               }
   MAX-ACCESS  read-only
   STATUS      current
   DESCRIPTION
      "Path: swPort.status.bridging.spanningTree.edgeDetection

       Possibilities:
               none   (0)
               edge   (1)
               notEdge   (2)"
   ::= {sr1645v2EthPortSwIBrSEntry 34144256}


sr1645v2EthPortSwIMacAddress OBJECT IDENTIFIER ::= {sr1645v2EthPortSwI 105}

sr1645v2EthPortSwIMacAddressTable OBJECT-TYPE
   SYNTAX      SEQUENCE OF Sr1645v2EthPortSwIMacAddressEntry
   MAX-ACCESS  not-accessible
   STATUS      current
   DESCRIPTION
      "ifPhysAddress"
   ::= {sr1645v2EthPortSwIMacAddress 1}

sr1645v2EthPortSwIMacAddressEntry OBJECT-TYPE
   SYNTAX      Sr1645v2EthPortSwIMacAddressEntry
   MAX-ACCESS  not-accessible
   STATUS      current
   DESCRIPTION
      ""
   INDEX      { sr1645v2EthPortSwIMacAddressGlobalIx }
   ::= {sr1645v2EthPortSwIMacAddressTable 1}

Sr1645v2EthPortSwIMacAddressEntry ::=
   SEQUENCE
      {
      sr1645v2EthPortSwIMacAddressGlobalIx
         GlobalIndex,
      sr1645v2EthPortSwIMacAddressValue
         OCTET STRING
      }

sr1645v2EthPortSwIMacAddressGlobalIx OBJECT-TYPE
   SYNTAX      GlobalIndex
   MAX-ACCESS  not-accessible
   STATUS      current
   DESCRIPTION
      "The value of the tlsCntTreeGlobalIndex of the MANAGED OBJECT."
   ::= {sr1645v2EthPortSwIMacAddressEntry 10}

sr1645v2EthPortSwIMacAddressValue OBJECT-TYPE
   SYNTAX      OCTET STRING
   MAX-ACCESS  read-only
   STATUS      current
   DESCRIPTION
      "Path: swPort.status.macAddress

       MAC address."
   ::= {sr1645v2EthPortSwIMacAddressEntry 2147483648}


sr1645v2EthPortSwIIpAdEntBcastAddr OBJECT IDENTIFIER ::= {sr1645v2EthPortSwI 124}

sr1645v2EthPortSwIIpAdEntBcastAddrTable OBJECT-TYPE
   SYNTAX      SEQUENCE OF Sr1645v2EthPortSwIIpAdEntBcastAddrEntry
   MAX-ACCESS  not-accessible
   STATUS      current
   DESCRIPTION
      "ipAdEntBcastAddr"
   ::= {sr1645v2EthPortSwIIpAdEntBcastAddr 1}

sr1645v2EthPortSwIIpAdEntBcastAddrEntry OBJECT-TYPE
   SYNTAX      Sr1645v2EthPortSwIIpAdEntBcastAddrEntry
   MAX-ACCESS  not-accessible
   STATUS      current
   DESCRIPTION
      ""
   INDEX      { sr1645v2EthPortSwIIpAdEntBcastAddrGlobalIx }
   ::= {sr1645v2EthPortSwIIpAdEntBcastAddrTable 1}

Sr1645v2EthPortSwIIpAdEntBcastAddrEntry ::=
   SEQUENCE
      {
      sr1645v2EthPortSwIIpAdEntBcastAddrGlobalIx
         GlobalIndex,
      sr1645v2EthPortSwIIpAdEntBcastAddrValue
         Integer32
      }

sr1645v2EthPortSwIIpAdEntBcastAddrGlobalIx OBJECT-TYPE
   SYNTAX      GlobalIndex
   MAX-ACCESS  not-accessible
   STATUS      current
   DESCRIPTION
      "The value of the tlsCntTreeGlobalIndex of the MANAGED OBJECT."
   ::= {sr1645v2EthPortSwIIpAdEntBcastAddrEntry 10}

sr1645v2EthPortSwIIpAdEntBcastAddrValue OBJECT-TYPE
   SYNTAX      Integer32
   MAX-ACCESS  read-only
   STATUS      current
   DESCRIPTION
      "Path: swPort.status.ipAdEntBcastAddr"
   ::= {sr1645v2EthPortSwIIpAdEntBcastAddrEntry 2147483648}


sr1645v2EthPortSwIIpAdEntReasmMaxSize OBJECT IDENTIFIER ::= {sr1645v2EthPortSwI 125}

sr1645v2EthPortSwIIpAdEntReasmMaxSizeTable OBJECT-TYPE
   SYNTAX      SEQUENCE OF Sr1645v2EthPortSwIIpAdEntReasmMaxSizeEntry
   MAX-ACCESS  not-accessible
   STATUS      current
   DESCRIPTION
      "ipAdEntReasmMaxSize"
   ::= {sr1645v2EthPortSwIIpAdEntReasmMaxSize 1}

sr1645v2EthPortSwIIpAdEntReasmMaxSizeEntry OBJECT-TYPE
   SYNTAX      Sr1645v2EthPortSwIIpAdEntReasmMaxSizeEntry
   MAX-ACCESS  not-accessible
   STATUS      current
   DESCRIPTION
      ""
   INDEX      { sr1645v2EthPortSwIIpAdEntReasmMaxSizeGlobalIx }
   ::= {sr1645v2EthPortSwIIpAdEntReasmMaxSizeTable 1}

Sr1645v2EthPortSwIIpAdEntReasmMaxSizeEntry ::=
   SEQUENCE
      {
      sr1645v2EthPortSwIIpAdEntReasmMaxSizeGlobalIx
         GlobalIndex,
      sr1645v2EthPortSwIIpAdEntReasmMaxSizeValue
         Integer32
      }

sr1645v2EthPortSwIIpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1645v2EthPortSwIIpAdEntReasmMaxSizeEntry 10}

sr1645v2EthPortSwIIpAdEntReasmMaxSizeValue OBJECT-TYPE
   SYNTAX      Integer32
   MAX-ACCESS  read-only
   STATUS      current
   DESCRIPTION
      "Path: swPort.status.ipAdEntReasmMaxSize"
   ::= {sr1645v2EthPortSwIIpAdEntReasmMaxSizeEntry 2147483648}


sr1645v2EthPortSwIOam OBJECT IDENTIFIER ::= {sr1645v2EthPortSwI 901}

sr1645v2EthPortSwIOamSSCTable OBJECT-TYPE
   SYNTAX      SEQUENCE OF Sr1645v2EthPortSwIOamEntry
   MAX-ACCESS  not-accessible
   STATUS      current
   DESCRIPTION
      "OAM discovery state"
   ::= {sr1645v2EthPortSwIOam 1}

sr1645v2EthPortSwIOamEntry OBJECT-TYPE
   SYNTAX      Sr1645v2EthPortSwIOamEntry
   MAX-ACCESS  not-accessible
   STATUS      current
   DESCRIPTION
      ""
   INDEX      { sr1645v2EthPortSwIOamGlobalIx }
   ::= {sr1645v2EthPortSwIOamSSCTable 1}

Sr1645v2EthPortSwIOamEntry ::=
   SEQUENCE
      {
      sr1645v2EthPortSwIOamGlobalIx
         GlobalIndex,
      sr1645v2EthPortSwIOamDiscovery
         INTEGER,
      sr1645v2EthPortSwIOamLoopback
         INTEGER,
      sr1645v2EthPortSwIOamLocalInfoVersion
         Integer32,
      sr1645v2EthPortSwIOamLocalInfoRevision
         Integer32,
      sr1645v2EthPortSwIOamLocalInfoStateMuxAction
         INTEGER,
      sr1645v2EthPortSwIOamLocalInfoStateParserAction
         INTEGER,
      sr1645v2EthPortSwIOamLocalInfoOui
         OCTET STRING,
      sr1645v2EthPortSwIOamLocalInfoVendorInfo
         OCTET STRING,
      sr1645v2EthPortSwIOamLocalInfoVarRetrieval
         INTEGER,
      sr1645v2EthPortSwIOamLocalInfoLinkEvents
         INTEGER,
      sr1645v2EthPortSwIOamLocalInfoLoopback
         INTEGER,
      sr1645v2EthPortSwIOamLocalInfoUnidirectional
         INTEGER,
      sr1645v2EthPortSwIOamLocalInfoMode
         INTEGER,
      sr1645v2EthPortSwIOamLocalInfoMaxPduSize
         Integer32,
      sr1645v2EthPortSwIOamRemoteInfoVersion
         Integer32,
      sr1645v2EthPortSwIOamRemoteInfoRevision
         Integer32,
      sr1645v2EthPortSwIOamRemoteInfoStateMuxAction
         INTEGER,
      sr1645v2EthPortSwIOamRemoteInfoStateParserAction
         INTEGER,
      sr1645v2EthPortSwIOamRemoteInfoOui
         OCTET STRING,
      sr1645v2EthPortSwIOamRemoteInfoVendorInfo
         OCTET STRING,
      sr1645v2EthPortSwIOamRemoteInfoVarRetrieval
         INTEGER,
      sr1645v2EthPortSwIOamRemoteInfoLinkEvents
         INTEGER,
      sr1645v2EthPortSwIOamRemoteInfoLoopback
         INTEGER,
      sr1645v2EthPortSwIOamRemoteInfoUnidirectional
         INTEGER,
      sr1645v2EthPortSwIOamRemoteInfoMode
         INTEGER,
      sr1645v2EthPortSwIOamRemoteInfoMaxPduSize
         Integer32,
      sr1645v2EthPortSwIOamEventsErroredSymbolWindow
         Integer32,
      sr1645v2EthPortSwIOamEventsErroredSymbolThreshold
         OCTET STRING,
      sr1645v2EthPortSwIOamEventsErroredFramePeriodWindow
         INTEGER,
      sr1645v2EthPortSwIOamEventsErroredFramePeriodThreshold
         Integer32,
      sr1645v2EthPortSwIOamEventsErroredFrameWindow
         Integer32,
      sr1645v2EthPortSwIOamEventsErroredFrameThreshold
         Integer32,
      sr1645v2EthPortSwIOamEventsErroredFrameSecondsWindow
         Integer32,
      sr1645v2EthPortSwIOamEventsErroredFrameSecondsThreshold
         Integer32
      }

sr1645v2EthPortSwIOamGlobalIx OBJECT-TYPE
   SYNTAX      GlobalIndex
   MAX-ACCESS  not-accessible
   STATUS      current
   DESCRIPTION
      "The value of the tlsCntTreeGlobalIndex of the MANAGED OBJECT."
   ::= {sr1645v2EthPortSwIOamEntry 10}

sr1645v2EthPortSwIOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: swPort.status.oam.discovery

       Possibilities:
               fault   (0)
               sendLocal   (1)
               passiveWait   (2)
               sendLocalRemote   (3)
               sendLocalRemoteOk   (4)
               sendAny   (5)"
   ::= {sr1645v2EthPortSwIOamEntry 16777216}

sr1645v2EthPortSwIOamLoopback OBJECT-TYPE
   SYNTAX      INTEGER
               {
               idle (0),
               waiting (1),
               localRunning (2),
               remoteRunning (3)
               }
   MAX-ACCESS  read-only
   STATUS      current
   DESCRIPTION
      "Path: swPort.status.oam.loopback

       Possibilities:
               idle   (0)
               waiting   (1)
               localRunning   (2)
               remoteRunning   (3)"
   ::= {sr1645v2EthPortSwIOamEntry 33554432}

sr1645v2EthPortSwIOamLocalInfoVersion OBJECT-TYPE
   SYNTAX      Integer32
   MAX-ACCESS  read-only
   STATUS      current
   DESCRIPTION
      "Path: swPort.status.oam.localInfo.version"
   ::= {sr1645v2EthPortSwIOamEntry 50397184}

sr1645v2EthPortSwIOamLocalInfoRevision OBJECT-TYPE
   SYNTAX      Integer32
   MAX-ACCESS  read-only
   STATUS      current
   DESCRIPTION
      "Path: swPort.status.oam.localInfo.revision"
   ::= {sr1645v2EthPortSwIOamEntry 50462720}

sr1645v2EthPortSwIOamLocalInfoStateMuxAction OBJECT-TYPE
   SYNTAX      INTEGER
               {
               forwarding (0),
               discarding (1)
               }
   MAX-ACCESS  read-only
   STATUS      current
   DESCRIPTION
      "Path: swPort.status.oam.localInfo.state.muxAction

       Possibilities:
               forwarding   (0)
               discarding   (1)"
   ::= {sr1645v2EthPortSwIOamEntry 50528512}

sr1645v2EthPortSwIOamLocalInfoStateParserAction OBJECT-TYPE
   SYNTAX      INTEGER
               {
               forwarding (0),
               loopback (1),
               discarding (2),
               reserved (3)
               }
   MAX-ACCESS  read-only
   STATUS      current
   DESCRIPTION
      "Path: swPort.status.oam.localInfo.state.parserAction

       Possibilities:
               forwarding   (0)
               loopback   (1)
               discarding   (2)
               reserved   (3)"
   ::= {sr1645v2EthPortSwIOamEntry 50528768}

sr1645v2EthPortSwIOamLocalInfoOui OBJECT-TYPE
   SYNTAX      OCTET STRING
   MAX-ACCESS  read-only
   STATUS      current
   DESCRIPTION
      "Path: swPort.status.oam.localInfo.oui"
   ::= {sr1645v2EthPortSwIOamEntry 50593792}

sr1645v2EthPortSwIOamLocalInfoVendorInfo OBJECT-TYPE
   SYNTAX      OCTET STRING
   MAX-ACCESS  read-only
   STATUS      current
   DESCRIPTION
      "Path: swPort.status.oam.localInfo.vendorInfo"
   ::= {sr1645v2EthPortSwIOamEntry 50659328}

sr1645v2EthPortSwIOamLocalInfoVarRetrieval OBJECT-TYPE
   SYNTAX      INTEGER
               {
               notSupported (0),
               supported (1)
               }
   MAX-ACCESS  read-only
   STATUS      current
   DESCRIPTION
      "Path: swPort.status.oam.localInfo.varRetrieval

       Possibilities:
               notSupported   (0)
               supported   (1)"
   ::= {sr1645v2EthPortSwIOamEntry 50724864}

sr1645v2EthPortSwIOamLocalInfoLinkEvents OBJECT-TYPE
   SYNTAX      INTEGER
               {
               ignored (0),
               interpreted (1)
               }
   MAX-ACCESS  read-only
   STATUS      current
   DESCRIPTION
      "Path: swPort.status.oam.localInfo.linkEvents

       Possibilities:
               ignored   (0)
               interpreted   (1)"
   ::= {sr1645v2EthPortSwIOamEntry 50790400}

sr1645v2EthPortSwIOamLocalInfoLoopback OBJECT-TYPE
   SYNTAX      INTEGER
               {
               notSupported (0),
               supported (1)
               }
   MAX-ACCESS  read-only
   STATUS      current
   DESCRIPTION
      "Path: swPort.status.oam.localInfo.loopback

       Possibilities:
               notSupported   (0)
               supported   (1)"
   ::= {sr1645v2EthPortSwIOamEntry 50855936}

sr1645v2EthPortSwIOamLocalInfoUnidirectional OBJECT-TYPE
   SYNTAX      INTEGER
               {
               notSupported (0),
               supported (1)
               }
   MAX-ACCESS  read-only
   STATUS      current
   DESCRIPTION
      "Path: swPort.status.oam.localInfo.unidirectional

       Possibilities:
               notSupported   (0)
               supported   (1)"
   ::= {sr1645v2EthPortSwIOamEntry 50921472}

sr1645v2EthPortSwIOamLocalInfoMode OBJECT-TYPE
   SYNTAX      INTEGER
               {
               passive (0),
               active (1)
               }
   MAX-ACCESS  read-only
   STATUS      current
   DESCRIPTION
      "Path: swPort.status.oam.localInfo.mode

       Possibilities:
               passive   (0)
               active   (1)"
   ::= {sr1645v2EthPortSwIOamEntry 50987008}

sr1645v2EthPortSwIOamLocalInfoMaxPduSize OBJECT-TYPE
   SYNTAX      Integer32
   MAX-ACCESS  read-only
   STATUS      current
   DESCRIPTION
      "Path: swPort.status.oam.localInfo.maxPduSize"
   ::= {sr1645v2EthPortSwIOamEntry 51052544}

sr1645v2EthPortSwIOamRemoteInfoVersion OBJECT-TYPE
   SYNTAX      Integer32
   MAX-ACCESS  read-only
   STATUS      current
   DESCRIPTION
      "Path: swPort.status.oam.remoteInfo.version"
   ::= {sr1645v2EthPortSwIOamEntry 67174400}

sr1645v2EthPortSwIOamRemoteInfoRevision OBJECT-TYPE
   SYNTAX      Integer32
   MAX-ACCESS  read-only
   STATUS      current
   DESCRIPTION
      "Path: swPort.status.oam.remoteInfo.revision"
   ::= {sr1645v2EthPortSwIOamEntry 67239936}

sr1645v2EthPortSwIOamRemoteInfoStateMuxAction OBJECT-TYPE
   SYNTAX      INTEGER
               {
               forwarding (0),
               discarding (1)
               }
   MAX-ACCESS  read-only
   STATUS      current
   DESCRIPTION
      "Path: swPort.status.oam.remoteInfo.state.muxAction

       Possibilities:
               forwarding   (0)
               discarding   (1)"
   ::= {sr1645v2EthPortSwIOamEntry 67305728}

sr1645v2EthPortSwIOamRemoteInfoStateParserAction OBJECT-TYPE
   SYNTAX      INTEGER
               {
               forwarding (0),
               loopback (1),
               discarding (2),
               reserved (3)
               }
   MAX-ACCESS  read-only
   STATUS      current
   DESCRIPTION
      "Path: swPort.status.oam.remoteInfo.state.parserAction

       Possibilities:
               forwarding   (0)
               loopback   (1)
               discarding   (2)
               reserved   (3)"
   ::= {sr1645v2EthPortSwIOamEntry 67305984}

sr1645v2EthPortSwIOamRemoteInfoOui OBJECT-TYPE
   SYNTAX      OCTET STRING
   MAX-ACCESS  read-only
   STATUS      current
   DESCRIPTION
      "Path: swPort.status.oam.remoteInfo.oui"
   ::= {sr1645v2EthPortSwIOamEntry 67371008}

sr1645v2EthPortSwIOamRemoteInfoVendorInfo OBJECT-TYPE
   SYNTAX      OCTET STRING
   MAX-ACCESS  read-only
   STATUS      current
   DESCRIPTION
      "Path: swPort.status.oam.remoteInfo.vendorInfo"
   ::= {sr1645v2EthPortSwIOamEntry 67436544}

sr1645v2EthPortSwIOamRemoteInfoVarRetrieval OBJECT-TYPE
   SYNTAX      INTEGER
               {
               notSupported (0),
               supported (1)
               }
   MAX-ACCESS  read-only
   STATUS      current
   DESCRIPTION
      "Path: swPort.status.oam.remoteInfo.varRetrieval

       Possibilities:
               notSupported   (0)
               supported   (1)"
   ::= {sr1645v2EthPortSwIOamEntry 67502080}

sr1645v2EthPortSwIOamRemoteInfoLinkEvents OBJECT-TYPE
   SYNTAX      INTEGER
               {
               ignored (0),
               interpreted (1)
               }
   MAX-ACCESS  read-only
   STATUS      current
   DESCRIPTION
      "Path: swPort.status.oam.remoteInfo.linkEvents

       Possibilities:
               ignored   (0)
               interpreted   (1)"
   ::= {sr1645v2EthPortSwIOamEntry 67567616}

sr1645v2EthPortSwIOamRemoteInfoLoopback OBJECT-TYPE
   SYNTAX      INTEGER
               {
               notSupported (0),
               supported (1)
               }
   MAX-ACCESS  read-only
   STATUS      current
   DESCRIPTION
      "Path: swPort.status.oam.remoteInfo.loopback

       Possibilities:
               notSupported   (0)
               supported   (1)"
   ::= {sr1645v2EthPortSwIOamEntry 67633152}

sr1645v2EthPortSwIOamRemoteInfoUnidirectional OBJECT-TYPE
   SYNTAX      INTEGER
               {
               notSupported (0),
               supported (1)
               }
   MAX-ACCESS  read-only
   STATUS      current
   DESCRIPTION
      "Path: swPort.status.oam.remoteInfo.unidirectional

       Possibilities:
               notSupported   (0)
               supported   (1)"
   ::= {sr1645v2EthPortSwIOamEntry 67698688}

sr1645v2EthPortSwIOamRemoteInfoMode OBJECT-TYPE
   SYNTAX      INTEGER
               {
               passive (0),
               active (1)
               }
   MAX-ACCESS  read-only
   STATUS      current
   DESCRIPTION
      "Path: swPort.status.oam.remoteInfo.mode

       Possibilities:
               passive   (0)
               active   (1)"
   ::= {sr1645v2EthPortSwIOamEntry 67764224}

sr1645v2EthPortSwIOamRemoteInfoMaxPduSize OBJECT-TYPE
   SYNTAX      Integer32
   MAX-ACCESS  read-only
   STATUS      current
   DESCRIPTION
      "Path: swPort.status.oam.remoteInfo.maxPduSize"
   ::= {sr1645v2EthPortSwIOamEntry 67829760}

sr1645v2EthPortSwIOamEventsErroredSymbolWindow OBJECT-TYPE
   SYNTAX      Integer32
   UNITS       "symbols"
   MAX-ACCESS  read-only
   STATUS      current
   DESCRIPTION
      "Path: swPort.status.oam.events.erroredSymbol.window

       unit name = symbols"
   ::= {sr1645v2EthPortSwIOamEntry 83951872}

sr1645v2EthPortSwIOamEventsErroredSymbolThreshold OBJECT-TYPE
   SYNTAX      OCTET STRING
   UNITS       "symbols"
   MAX-ACCESS  read-only
   STATUS      current
   DESCRIPTION
      "Path: swPort.status.oam.events.erroredSymbol.threshold

       unit name = symbols"
   ::= {sr1645v2EthPortSwIOamEntry 83952128}

sr1645v2EthPortSwIOamEventsErroredFramePeriodWindow OBJECT-TYPE
   SYNTAX      INTEGER
               {
               default (0)
               }
   UNITS       "frames"
   MAX-ACCESS  read-only
   STATUS      current
   DESCRIPTION
      "Path: swPort.status.oam.events.erroredFramePeriod.window

       unit name = frames

       Possibilities:
               default   (0)"
   ::= {sr1645v2EthPortSwIOamEntry 84017408}

sr1645v2EthPortSwIOamEventsErroredFramePeriodThreshold OBJECT-TYPE
   SYNTAX      Integer32
   UNITS       "frames"
   MAX-ACCESS  read-only
   STATUS      current
   DESCRIPTION
      "Path: swPort.status.oam.events.erroredFramePeriod.threshold

       unit name = frames"
   ::= {sr1645v2EthPortSwIOamEntry 84017664}

sr1645v2EthPortSwIOamEventsErroredFrameWindow OBJECT-TYPE
   SYNTAX      Integer32
   UNITS       "100msec"
   MAX-ACCESS  read-only
   STATUS      current
   DESCRIPTION
      "Path: swPort.status.oam.events.erroredFrame.window

       unit name = 100msec"
   ::= {sr1645v2EthPortSwIOamEntry 84082944}

sr1645v2EthPortSwIOamEventsErroredFrameThreshold OBJECT-TYPE
   SYNTAX      Integer32
   UNITS       "frames"
   MAX-ACCESS  read-only
   STATUS      current
   DESCRIPTION
      "Path: swPort.status.oam.events.erroredFrame.threshold

       unit name = frames"
   ::= {sr1645v2EthPortSwIOamEntry 84083200}

sr1645v2EthPortSwIOamEventsErroredFrameSecondsWindow OBJECT-TYPE
   SYNTAX      Integer32
   UNITS       "100msec"
   MAX-ACCESS  read-only
   STATUS      current
   DESCRIPTION
      "Path: swPort.status.oam.events.erroredFrameSeconds.window

       unit name = 100msec"
   ::= {sr1645v2EthPortSwIOamEntry 84148480}

sr1645v2EthPortSwIOamEventsErroredFrameSecondsThreshold OBJECT-TYPE
   SYNTAX      Integer32
   UNITS       "frames"
   MAX-ACCESS  read-only
   STATUS      current
   DESCRIPTION
      "Path: swPort.status.oam.events.erroredFrameSeconds.threshold

       unit name = frames"
   ::= {sr1645v2EthPortSwIOamEntry 84148736}


sr1645v2EthPortSwIOamEventLog OBJECT IDENTIFIER ::= {sr1645v2EthPortSwI 911}

sr1645v2EthPortSwIOamEventLogSSCTable OBJECT-TYPE
   SYNTAX      SEQUENCE OF Sr1645v2EthPortSwIOamEventLogEntry
   MAX-ACCESS  not-accessible
   STATUS      current
   DESCRIPTION
      "OAM event log"
   ::= {sr1645v2EthPortSwIOamEventLog 1}

sr1645v2EthPortSwIOamEventLogEntry OBJECT-TYPE
   SYNTAX      Sr1645v2EthPortSwIOamEventLogEntry
   MAX-ACCESS  not-accessible
   STATUS      current
   DESCRIPTION
      ""
   INDEX      { sr1645v2EthPortSwIOamEventLogGlobalIx,
                sr1645v2EthPortSwIOamEventLogTableIx }
   ::= {sr1645v2EthPortSwIOamEventLogSSCTable 1}

Sr1645v2EthPortSwIOamEventLogEntry ::=
   SEQUENCE
      {
      sr1645v2EthPortSwIOamEventLogGlobalIx
         GlobalIndex,
      sr1645v2EthPortSwIOamEventLogTableIx
         TableIndex,
      sr1645v2EthPortSwIOamEventLogSysUpTime
         TimeTicks,
      sr1645v2EthPortSwIOamEventLogLocation
         INTEGER,
      sr1645v2EthPortSwIOamEventLogType
         INTEGER,
      sr1645v2EthPortSwIOamEventLogOui
         OCTET STRING,
      sr1645v2EthPortSwIOamEventLogWindow
         Counter64,
      sr1645v2EthPortSwIOamEventLogThreshold
         Counter64,
      sr1645v2EthPortSwIOamEventLogTotal
         Counter32,
      sr1645v2EthPortSwIOamEventLogValue
         Counter64,
      sr1645v2EthPortSwIOamEventLogRunningTotal
         Counter64
      }

sr1645v2EthPortSwIOamEventLogGlobalIx OBJECT-TYPE
   SYNTAX      GlobalIndex
   MAX-ACCESS  not-accessible
   STATUS      current
   DESCRIPTION
      "The value of the tlsCntTreeGlobalIndex of the MANAGED OBJECT."
   ::= {sr1645v2EthPortSwIOamEventLogEntry 10}

sr1645v2EthPortSwIOamEventLogTableIx OBJECT-TYPE
   SYNTAX      TableIndex
   MAX-ACCESS  not-accessible
   STATUS      current
   DESCRIPTION
      ""
   ::= {sr1645v2EthPortSwIOamEventLogEntry 11}

sr1645v2EthPortSwIOamEventLogSysUpTime OBJECT-TYPE
   SYNTAX      TimeTicks
   MAX-ACCESS  read-only
   STATUS      current
   DESCRIPTION
      "Path: swPort.status.oamEventLog.sysUpTime

       Time in centi-second."
   ::= {sr1645v2EthPortSwIOamEventLogEntry 16777216}

sr1645v2EthPortSwIOamEventLogLocation OBJECT-TYPE
   SYNTAX      INTEGER
               {
               local (1),
               remote (2)
               }
   MAX-ACCESS  read-only
   STATUS      current
   DESCRIPTION
      "Path: swPort.status.oamEventLog.location

       Possibilities:
               local   (1)
               remote   (2)"
   ::= {sr1645v2EthPortSwIOamEventLogEntry 33554432}

sr1645v2EthPortSwIOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: swPort.status.oamEventLog.type

       Possibilities:
               erroredSymbols   (1)
               erroredFramePeriod   (2)
               erroredFrame   (3)
               erroredFrameSeconds   (4)
               linkFault   (256)
               dyingGasp   (257)
               criticalLink   (258)"
   ::= {sr1645v2EthPortSwIOamEventLogEntry 50331648}

sr1645v2EthPortSwIOamEventLogOui OBJECT-TYPE
   SYNTAX      OCTET STRING
   MAX-ACCESS  read-only
   STATUS      current
   DESCRIPTION
      "Path: swPort.status.oamEventLog.oui"
   ::= {sr1645v2EthPortSwIOamEventLogEntry 67108864}

sr1645v2EthPortSwIOamEventLogWindow OBJECT-TYPE
   SYNTAX      Counter64
   MAX-ACCESS  read-only
   STATUS      current
   DESCRIPTION
      "Path: swPort.status.oamEventLog.window

       64 bit unsigned wrappable counter."
   ::= {sr1645v2EthPortSwIOamEventLogEntry 83886080}

sr1645v2EthPortSwIOamEventLogThreshold OBJECT-TYPE
   SYNTAX      Counter64
   MAX-ACCESS  read-only
   STATUS      current
   DESCRIPTION
      "Path: swPort.status.oamEventLog.threshold

       64 bit unsigned wrappable counter."
   ::= {sr1645v2EthPortSwIOamEventLogEntry 100663296}

sr1645v2EthPortSwIOamEventLogTotal OBJECT-TYPE
   SYNTAX      Counter32
   MAX-ACCESS  read-only
   STATUS      current
   DESCRIPTION
      "Path: swPort.status.oamEventLog.total

       32 bit unsigned wrappable counter."
   ::= {sr1645v2EthPortSwIOamEventLogEntry 117440512}

sr1645v2EthPortSwIOamEventLogValue OBJECT-TYPE
   SYNTAX      Counter64
   MAX-ACCESS  read-only
   STATUS      current
   DESCRIPTION
      "Path: swPort.status.oamEventLog.value

       64 bit unsigned wrappable counter."
   ::= {sr1645v2EthPortSwIOamEventLogEntry 134217728}

sr1645v2EthPortSwIOamEventLogRunningTotal OBJECT-TYPE
   SYNTAX      Counter64
   MAX-ACCESS  read-only
   STATUS      current
   DESCRIPTION
      "Path: swPort.status.oamEventLog.runningTotal

       64 bit unsigned wrappable counter."
   ::= {sr1645v2EthPortSwIOamEventLogEntry 150994944}


sr1645v2EthPortSwIVlan OBJECT IDENTIFIER ::= {sr1645v2EthPortSwI 34}

sr1645v2EthPortSwIVlanSSCTable OBJECT-TYPE
   SYNTAX      SEQUENCE OF Sr1645v2EthPortSwIVlanEntry
   MAX-ACCESS  not-accessible
   STATUS      current
   DESCRIPTION
      ""
   ::= {sr1645v2EthPortSwIVlan 1}

sr1645v2EthPortSwIVlanEntry OBJECT-TYPE
   SYNTAX      Sr1645v2EthPortSwIVlanEntry
   MAX-ACCESS  not-accessible
   STATUS      current
   DESCRIPTION
      ""
   INDEX      { sr1645v2EthPortSwIVlanGlobalIx,
                sr1645v2EthPortSwIVlanTableIx }
   ::= {sr1645v2EthPortSwIVlanSSCTable 1}

Sr1645v2EthPortSwIVlanEntry ::=
   SEQUENCE
      {
      sr1645v2EthPortSwIVlanGlobalIx
         GlobalIndex,
      sr1645v2EthPortSwIVlanTableIx
         TableIndex,
      sr1645v2EthPortSwIVlanName
         DisplayString,
      sr1645v2EthPortSwIVlanMode
         INTEGER,
      sr1645v2EthPortSwIVlanIfOperStatus
         INTEGER,
      sr1645v2EthPortSwIVlanIfLastChange
         TimeTicks,
      sr1645v2EthPortSwIVlanIfLastChangeDate
         DisplayString,
      sr1645v2EthPortSwIVlanIpAddress
         IpAddress,
      sr1645v2EthPortSwIVlanIpNetMask
         IpAddress,
      sr1645v2EthPortSwIVlanIpRemote
         IpAddress,
      sr1645v2EthPortSwIVlanIpDhcpStatus
         INTEGER,
      sr1645v2EthPortSwIVlanIpDhcpLeaseTime
         TimeTicks,
      sr1645v2EthPortSwIVlanIpV6State
         INTEGER,
      sr1645v2EthPortSwIVlanIpV6InterfaceId
         OCTET STRING,
      sr1645v2EthPortSwIVlanIpV6LinkMtu
         Integer32,
      sr1645v2EthPortSwIVlanIpV6HopLimit
         Integer32,
      sr1645v2EthPortSwIVlanIpV6DhcpIaid
         Counter32,
      sr1645v2EthPortSwIVlanIpV6RaRcvOption
         Integer32,
      sr1645v2EthPortSwIVlanBridgingStatus
         INTEGER,
      sr1645v2EthPortSwIVlanBridgingSpanningTreePortRole
         INTEGER,
      sr1645v2EthPortSwIVlanBridgingSpanningTreePortId
         Integer32,
      sr1645v2EthPortSwIVlanBridgingSpanningTreePpCostExtPathCost
         Integer32,
      sr1645v2EthPortSwIVlanBridgingSpanningTreePpCostIntPathCost
         Integer32,
      sr1645v2EthPortSwIVlanBridgingSpanningTreeExtRpCost
         Integer32,
      sr1645v2EthPortSwIVlanBridgingSpanningTreeIntRpCost
         Integer32,
      sr1645v2EthPortSwIVlanBridgingSpanningTreeDesBrIdPriority
         Integer32,
      sr1645v2EthPortSwIVlanBridgingSpanningTreeDesBrIdMacAddress
         OCTET STRING,
      sr1645v2EthPortSwIVlanBridgingSpanningTreeDesPrtId
         Integer32,
      sr1645v2EthPortSwIVlanBridgingSpanningTreeDesInt
         INTEGER,
      sr1645v2EthPortSwIVlanBridgingSpanningTreeEdgeDetection
         INTEGER,
      sr1645v2EthPortSwIVlanVlanVid
         Integer32,
      sr1645v2EthPortSwIVlanPppOEthDiscState
         INTEGER,
      sr1645v2EthPortSwIVlanPppOEthPeerMac
         OCTET STRING,
      sr1645v2EthPortSwIVlanPppOEthServiceName
         DisplayString,
      sr1645v2EthPortSwIVlanPppLcpState
         INTEGER,
      sr1645v2EthPortSwIVlanPppIpcpState
         INTEGER,
      sr1645v2EthPortSwIVlanPppIp6cpState
         INTEGER,
      sr1645v2EthPortSwIVlanPppMyAutSt
         INTEGER,
      sr1645v2EthPortSwIVlanPppHisAutSt
         INTEGER,
      sr1645v2EthPortSwIVlanPppMru
         Integer32
      }

sr1645v2EthPortSwIVlanGlobalIx OBJECT-TYPE
   SYNTAX      GlobalIndex
   MAX-ACCESS  not-accessible
   STATUS      current
   DESCRIPTION
      "The value of the tlsCntTreeGlobalIndex of the MANAGED OBJECT."
   ::= {sr1645v2EthPortSwIVlanEntry 10}

sr1645v2EthPortSwIVlanTableIx OBJECT-TYPE
   SYNTAX      TableIndex
   MAX-ACCESS  not-accessible
   STATUS      current
   DESCRIPTION
      ""
   ::= {sr1645v2EthPortSwIVlanEntry 11}

sr1645v2EthPortSwIVlanName OBJECT-TYPE
   SYNTAX      DisplayString
   MAX-ACCESS  read-only
   STATUS      current
   DESCRIPTION
      "Path: swPort.status.vlan.name"
   ::= {sr1645v2EthPortSwIVlanEntry 16777216}

sr1645v2EthPortSwIVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2EthPortSwIVlanEntry 335544320}

sr1645v2EthPortSwIVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.vlan.ifOperStatus

       Possibilities:
               up   (1)
               down   (2)
               testing   (3)
               unknown   (4)
               dormant   (5)
               notPresent   (6)
               lowerLayerDown   (7)"
   ::= {sr1645v2EthPortSwIVlanEntry 1795162112}

sr1645v2EthPortSwIVlanIfLastChange OBJECT-TYPE
   SYNTAX      TimeTicks
   MAX-ACCESS  read-only
   STATUS      current
   DESCRIPTION
      "Path: swPort.status.vlan.ifLastChange

       Time in centi-second."
   ::= {sr1645v2EthPortSwIVlanEntry 1811939328}

sr1645v2EthPortSwIVlanIfLastChangeDate OBJECT-TYPE
   SYNTAX      DisplayString
   MAX-ACCESS  read-only
   STATUS      current
   DESCRIPTION
      "Path: swPort.status.vlan.ifLastChangeDate"
   ::= {sr1645v2EthPortSwIVlanEntry 3070230528}

sr1645v2EthPortSwIVlanIpAddress OBJECT-TYPE
   SYNTAX      IpAddress
   MAX-ACCESS  read-only
   STATUS      current
   DESCRIPTION
      "Path: swPort.status.vlan.ip.address"
   ::= {sr1645v2EthPortSwIVlanEntry 51380224}

sr1645v2EthPortSwIVlanIpNetMask OBJECT-TYPE
   SYNTAX      IpAddress
   MAX-ACCESS  read-only
   STATUS      current
   DESCRIPTION
      "Path: swPort.status.vlan.ip.netMask"
   ::= {sr1645v2EthPortSwIVlanEntry 51445760}

sr1645v2EthPortSwIVlanIpRemote OBJECT-TYPE
   SYNTAX      IpAddress
   MAX-ACCESS  read-only
   STATUS      current
   DESCRIPTION
      "Path: swPort.status.vlan.ip.remote"
   ::= {sr1645v2EthPortSwIVlanEntry 51511296}

sr1645v2EthPortSwIVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.vlan.ip.dhcp.status

       Possibilities:
               none   (0)
               selecting   (1)
               requesting   (2)
               rebinding   (3)
               bound   (4)
               renewing   (5)
               rebooting   (6)
               initreboot   (7)"
   ::= {sr1645v2EthPortSwIVlanEntry 51904768}

sr1645v2EthPortSwIVlanIpDhcpLeaseTime OBJECT-TYPE
   SYNTAX      TimeTicks
   MAX-ACCESS  read-only
   STATUS      current
   DESCRIPTION
      "Path: swPort.status.vlan.ip.dhcp.leaseTime

       Time in centi-second."
   ::= {sr1645v2EthPortSwIVlanEntry 51905024}

sr1645v2EthPortSwIVlanIpV6State OBJECT-TYPE
   SYNTAX      INTEGER
               {
               disabled (0),
               enabled (1)
               }
   MAX-ACCESS  read-only
   STATUS      current
   DESCRIPTION
      "Path: swPort.status.vlan.ipV6.state

       Possibilities:
               disabled   (0)
               enabled   (1)"
   ::= {sr1645v2EthPortSwIVlanEntry 100728832}

sr1645v2EthPortSwIVlanIpV6InterfaceId OBJECT-TYPE
   SYNTAX      OCTET STRING
   MAX-ACCESS  read-only
   STATUS      current
   DESCRIPTION
      "Path: swPort.status.vlan.ipV6.interfaceId"
   ::= {sr1645v2EthPortSwIVlanEntry 100794368}

sr1645v2EthPortSwIVlanIpV6LinkMtu OBJECT-TYPE
   SYNTAX      Integer32
   MAX-ACCESS  read-only
   STATUS      current
   DESCRIPTION
      "Path: swPort.status.vlan.ipV6.linkMtu"
   ::= {sr1645v2EthPortSwIVlanEntry 100925440}

sr1645v2EthPortSwIVlanIpV6HopLimit OBJECT-TYPE
   SYNTAX      Integer32
   MAX-ACCESS  read-only
   STATUS      current
   DESCRIPTION
      "Path: swPort.status.vlan.ipV6.hopLimit"
   ::= {sr1645v2EthPortSwIVlanEntry 100990976}

sr1645v2EthPortSwIVlanIpV6DhcpIaid OBJECT-TYPE
   SYNTAX      Counter32
   MAX-ACCESS  read-only
   STATUS      current
   DESCRIPTION
      "Path: swPort.status.vlan.ipV6.dhcp.iaid

       32 bit unsigned wrappable counter."
   ::= {sr1645v2EthPortSwIVlanEntry 101056768}

sr1645v2EthPortSwIVlanIpV6RaRcvOption OBJECT-TYPE
   SYNTAX      Integer32
   MAX-ACCESS  read-only
   STATUS      current
   DESCRIPTION
      "Path: swPort.status.vlan.ipV6.raRcvOption

       Bit meanings:
               bit 0 = linkMtu,
               bit 1 = srcLinkLayer,
               bit 2 = prefixInfo,
               bit 3 = rdnss,
               bit 4 = dnssl"
   ::= {sr1645v2EthPortSwIVlanEntry 101122048}

sr1645v2EthPortSwIVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.vlan.bridging.status

       Possibilities:
               disabled   (0)
               discarding   (1)
               learning   (2)
               forwarding   (3)
               backupBlockedIntfDown   (256)
               backupBlockedIntfUp   (259)
               shutdown   (255)"
   ::= {sr1645v2EthPortSwIVlanEntry 453050368}

sr1645v2EthPortSwIVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.vlan.bridging.spanningTree.portRole

       Possibilities:
               none   (0)
               root   (1)
               designated   (2)
               alternate   (3)
               backup   (4)
               disabled   (5)
               master   (6)"
   ::= {sr1645v2EthPortSwIVlanEntry 453116160}

sr1645v2EthPortSwIVlanBridgingSpanningTreePortId OBJECT-TYPE
   SYNTAX      Integer32
   MAX-ACCESS  read-only
   STATUS      current
   DESCRIPTION
      "Path: swPort.status.vlan.bridging.spanningTree.portId"
   ::= {sr1645v2EthPortSwIVlanEntry 453116416}

sr1645v2EthPortSwIVlanBridgingSpanningTreePpCostExtPathCost OBJECT-TYPE
   SYNTAX      Integer32
   MAX-ACCESS  read-only
   STATUS      current
   DESCRIPTION
      "Path: swPort.status.vlan.bridging.spanningTree.portPathCosts.extPathCost"
   ::= {sr1645v2EthPortSwIVlanEntry 453116673}

sr1645v2EthPortSwIVlanBridgingSpanningTreePpCostIntPathCost OBJECT-TYPE
   SYNTAX      Integer32
   MAX-ACCESS  read-only
   STATUS      current
   DESCRIPTION
      "Path: swPort.status.vlan.bridging.spanningTree.portPathCosts.intPathCost"
   ::= {sr1645v2EthPortSwIVlanEntry 453116674}

sr1645v2EthPortSwIVlanBridgingSpanningTreeExtRpCost OBJECT-TYPE
   SYNTAX      Integer32
   MAX-ACCESS  read-only
   STATUS      current
   DESCRIPTION
      "Path: swPort.status.vlan.bridging.spanningTree.extRootPathCost"
   ::= {sr1645v2EthPortSwIVlanEntry 453116928}

sr1645v2EthPortSwIVlanBridgingSpanningTreeIntRpCost OBJECT-TYPE
   SYNTAX      Integer32
   MAX-ACCESS  read-only
   STATUS      current
   DESCRIPTION
      "Path: swPort.status.vlan.bridging.spanningTree.intRootPathCost"
   ::= {sr1645v2EthPortSwIVlanEntry 453117184}

sr1645v2EthPortSwIVlanBridgingSpanningTreeDesBrIdPriority OBJECT-TYPE
   SYNTAX      Integer32
   MAX-ACCESS  read-only
   STATUS      current
   DESCRIPTION
      "Path: swPort.status.vlan.bridging.spanningTree.designatedBridgeId.priority"
   ::= {sr1645v2EthPortSwIVlanEntry 453117441}

sr1645v2EthPortSwIVlanBridgingSpanningTreeDesBrIdMacAddress OBJECT-TYPE
   SYNTAX      OCTET STRING
   MAX-ACCESS  read-only
   STATUS      current
   DESCRIPTION
      "Path: swPort.status.vlan.bridging.spanningTree.designatedBridgeId.macAddress

       MAC address."
   ::= {sr1645v2EthPortSwIVlanEntry 453117442}

sr1645v2EthPortSwIVlanBridgingSpanningTreeDesPrtId OBJECT-TYPE
   SYNTAX      Integer32
   MAX-ACCESS  read-only
   STATUS      current
   DESCRIPTION
      "Path: swPort.status.vlan.bridging.spanningTree.designatedPortId"
   ::= {sr1645v2EthPortSwIVlanEntry 453117696}

sr1645v2EthPortSwIVlanBridgingSpanningTreeDesInt OBJECT-TYPE
   SYNTAX      INTEGER
               {
               no (0),
               yes (1)
               }
   MAX-ACCESS  read-only
   STATUS      current
   DESCRIPTION
      "Path: swPort.status.vlan.bridging.spanningTree.designatedOrInternal

       Possibilities:
               no   (0)
               yes   (1)"
   ::= {sr1645v2EthPortSwIVlanEntry 453117952}

sr1645v2EthPortSwIVlanBridgingSpanningTreeEdgeDetection OBJECT-TYPE
   SYNTAX      INTEGER
               {
               none (0),
               edge (1),
               notEdge (2)
               }
   MAX-ACCESS  read-only
   STATUS      current
   DESCRIPTION
      "Path: swPort.status.vlan.bridging.spanningTree.edgeDetection

       Possibilities:
               none   (0)
               edge   (1)
               notEdge   (2)"
   ::= {sr1645v2EthPortSwIVlanEntry 453118208}

sr1645v2EthPortSwIVlanVlanVid OBJECT-TYPE
   SYNTAX      Integer32
   MAX-ACCESS  read-only
   STATUS      current
   DESCRIPTION
      "Path: swPort.status.vlan.vlan.vid"
   ::= {sr1645v2EthPortSwIVlanEntry 234946560}

sr1645v2EthPortSwIVlanPppOEthDiscState OBJECT-TYPE
   SYNTAX      INTEGER
               {
               idle (0),
               waitForPADO (1),
               waitForPADS (2),
               established (3)
               }
   MAX-ACCESS  read-only
   STATUS      current
   DESCRIPTION
      "Path: swPort.status.vlan.pppOverEth.discState

       Possibilities:
               idle   (0)
               waitForPADO   (1)
               waitForPADS   (2)
               established   (3)"
   ::= {sr1645v2EthPortSwIVlanEntry 67174400}

sr1645v2EthPortSwIVlanPppOEthPeerMac OBJECT-TYPE
   SYNTAX      OCTET STRING
   MAX-ACCESS  read-only
   STATUS      current
   DESCRIPTION
      "Path: swPort.status.vlan.pppOverEth.remoteMacAddress

       MAC address."
   ::= {sr1645v2EthPortSwIVlanEntry 67239936}

sr1645v2EthPortSwIVlanPppOEthServiceName OBJECT-TYPE
   SYNTAX      DisplayString
   MAX-ACCESS  read-only
   STATUS      current
   DESCRIPTION
      "Path: swPort.status.vlan.pppOverEth.serviceName"
   ::= {sr1645v2EthPortSwIVlanEntry 67305472}

sr1645v2EthPortSwIVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIVlanEntry 83951616}

sr1645v2EthPortSwIVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIVlanEntry 84017152}

sr1645v2EthPortSwIVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIVlanEntry 84869120}

sr1645v2EthPortSwIVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2EthPortSwIVlanEntry 84541440}

sr1645v2EthPortSwIVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2EthPortSwIVlanEntry 84606976}

sr1645v2EthPortSwIVlanPppMru OBJECT-TYPE
   SYNTAX      Integer32
   MAX-ACCESS  read-only
   STATUS      current
   DESCRIPTION
      "Path: swPort.status.vlan.ppp.mru"
   ::= {sr1645v2EthPortSwIVlanEntry 84934656}

sr1645v2EthPortSwIVlanIpSecondaryIp OBJECT-TYPE
   SYNTAX      SEQUENCE OF Sr1645v2EthPortSwIVlanIpSecondaryIpEntry
   MAX-ACCESS  not-accessible
   STATUS      current
   DESCRIPTION
      ""
   ::= {sr1645v2EthPortSwIVlan 51838976}

sr1645v2EthPortSwIVlanIpSecondaryIpEntry OBJECT-TYPE
   SYNTAX      Sr1645v2EthPortSwIVlanIpSecondaryIpEntry
   MAX-ACCESS  not-accessible
   STATUS      current
   DESCRIPTION
      ""
   INDEX      { sr1645v2EthPortSwIVlanIpSecondaryIpGlobalIx,
                sr1645v2EthPortSwIVlanTableIx,
                sr1645v2EthPortSwIVlanIpSecondaryIpTableIx }
   ::= {sr1645v2EthPortSwIVlanIpSecondaryIp 1}

Sr1645v2EthPortSwIVlanIpSecondaryIpEntry ::=
   SEQUENCE
      {
      sr1645v2EthPortSwIVlanIpSecondaryIpGlobalIx
         GlobalIndex,
      sr1645v2EthPortSwIVlanIpSecondaryIpTableIx
         TableIndex,
      sr1645v2EthPortSwIVlanIpSecondaryIpAddress
         IpAddress,
      sr1645v2EthPortSwIVlanIpSecondaryIpNetMask
         IpAddress
      }

sr1645v2EthPortSwIVlanIpSecondaryIpGlobalIx OBJECT-TYPE
   SYNTAX      GlobalIndex
   MAX-ACCESS  not-accessible
   STATUS      current
   DESCRIPTION
      "The value of the tlsCntTreeGlobalIndex of the MANAGED OBJECT."
   ::= {sr1645v2EthPortSwIVlanIpSecondaryIpEntry 10}

sr1645v2EthPortSwIVlanIpSecondaryIpTableIx OBJECT-TYPE
   SYNTAX      TableIndex
   MAX-ACCESS  not-accessible
   STATUS      current
   DESCRIPTION
      ""
   ::= {sr1645v2EthPortSwIVlanIpSecondaryIpEntry 11}

sr1645v2EthPortSwIVlanIpSecondaryIpAddress OBJECT-TYPE
   SYNTAX      IpAddress
   MAX-ACCESS  read-only
   STATUS      current
   DESCRIPTION
      "Path: swPort.status.vlan.ip.secondaryIp.address"
   ::= {sr1645v2EthPortSwIVlanIpSecondaryIpEntry 2030043136}

sr1645v2EthPortSwIVlanIpSecondaryIpNetMask OBJECT-TYPE
   SYNTAX      IpAddress
   MAX-ACCESS  read-only
   STATUS      current
   DESCRIPTION
      "Path: swPort.status.vlan.ip.secondaryIp.netMask"
   ::= {sr1645v2EthPortSwIVlanIpSecondaryIpEntry 2063597568}

sr1645v2EthPortSwIVlanIpV6Addresses OBJECT-TYPE
   SYNTAX      SEQUENCE OF Sr1645v2EthPortSwIVlanIpV6AddressesEntry
   MAX-ACCESS  not-accessible
   STATUS      current
   DESCRIPTION
      ""
   ::= {sr1645v2EthPortSwIVlan 100859904}

sr1645v2EthPortSwIVlanIpV6AddressesEntry OBJECT-TYPE
   SYNTAX      Sr1645v2EthPortSwIVlanIpV6AddressesEntry
   MAX-ACCESS  not-accessible
   STATUS      current
   DESCRIPTION
      ""
   INDEX      { sr1645v2EthPortSwIVlanIpV6AddressesGlobalIx,
                sr1645v2EthPortSwIVlanTableIx,
                sr1645v2EthPortSwIVlanIpV6AddressesTableIx }
   ::= {sr1645v2EthPortSwIVlanIpV6Addresses 1}

Sr1645v2EthPortSwIVlanIpV6AddressesEntry ::=
   SEQUENCE
      {
      sr1645v2EthPortSwIVlanIpV6AddressesGlobalIx
         GlobalIndex,
      sr1645v2EthPortSwIVlanIpV6AddressesTableIx
         TableIndex,
      sr1645v2EthPortSwIVlanIpV6AddressesAddress
         Ipv6Address,
      sr1645v2EthPortSwIVlanIpV6AddressesPrefixLength
         Integer32,
      sr1645v2EthPortSwIVlanIpV6AddressesStatus
         INTEGER,
      sr1645v2EthPortSwIVlanIpV6AddressesOrigin
         INTEGER,
      sr1645v2EthPortSwIVlanIpV6AddressesFlagsInterfaceId
         INTEGER,
      sr1645v2EthPortSwIVlanIpV6AddressesFlagsAnycast
         INTEGER,
      sr1645v2EthPortSwIVlanIpV6AddressesTimersValidLifeTime
         TimeTicks,
      sr1645v2EthPortSwIVlanIpV6AddressesTimersPrefLifeTime
         TimeTicks
      }

sr1645v2EthPortSwIVlanIpV6AddressesGlobalIx OBJECT-TYPE
   SYNTAX      GlobalIndex
   MAX-ACCESS  not-accessible
   STATUS      current
   DESCRIPTION
      "The value of the tlsCntTreeGlobalIndex of the MANAGED OBJECT."
   ::= {sr1645v2EthPortSwIVlanIpV6AddressesEntry 10}

sr1645v2EthPortSwIVlanIpV6AddressesTableIx OBJECT-TYPE
   SYNTAX      TableIndex
   MAX-ACCESS  not-accessible
   STATUS      current
   DESCRIPTION
      ""
   ::= {sr1645v2EthPortSwIVlanIpV6AddressesEntry 11}

sr1645v2EthPortSwIVlanIpV6AddressesAddress OBJECT-TYPE
   SYNTAX      Ipv6Address
   MAX-ACCESS  read-only
   STATUS      current
   DESCRIPTION
      "Path: swPort.status.vlan.ipV6.addresses.address

       ipv6 address"
   ::= {sr1645v2EthPortSwIVlanIpV6AddressesEntry 16777216}

sr1645v2EthPortSwIVlanIpV6AddressesPrefixLength OBJECT-TYPE
   SYNTAX      Integer32
   MAX-ACCESS  read-only
   STATUS      current
   DESCRIPTION
      "Path: swPort.status.vlan.ipV6.addresses.prefixLength"
   ::= {sr1645v2EthPortSwIVlanIpV6AddressesEntry 33554432}

sr1645v2EthPortSwIVlanIpV6AddressesStatus OBJECT-TYPE
   SYNTAX      INTEGER
               {
               invalid (0),
               tentative (1),
               deprecated (2),
               preferred (3)
               }
   MAX-ACCESS  read-only
   STATUS      current
   DESCRIPTION
      "Path: swPort.status.vlan.ipV6.addresses.status

       Possibilities:
               invalid   (0)
               tentative   (1)
               deprecated   (2)
               preferred   (3)"
   ::= {sr1645v2EthPortSwIVlanIpV6AddressesEntry 50331648}

sr1645v2EthPortSwIVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.vlan.ipV6.addresses.origin

       Possibilities:
               unknown   (0)
               manual   (1)
               generalPrefix   (2)
               statelessAuto   (3)
               statefullAuto   (4)"
   ::= {sr1645v2EthPortSwIVlanIpV6AddressesEntry 67108864}

sr1645v2EthPortSwIVlanIpV6AddressesFlagsInterfaceId OBJECT-TYPE
   SYNTAX      INTEGER
               {
               no (0),
               yes (1)
               }
   MAX-ACCESS  read-only
   STATUS      current
   DESCRIPTION
      "Path: swPort.status.vlan.ipV6.addresses.flags.interfaceId

       Possibilities:
               no   (0)
               yes   (1)"
   ::= {sr1645v2EthPortSwIVlanIpV6AddressesEntry 83951616}

sr1645v2EthPortSwIVlanIpV6AddressesFlagsAnycast OBJECT-TYPE
   SYNTAX      INTEGER
               {
               no (0),
               yes (1)
               }
   MAX-ACCESS  read-only
   STATUS      current
   DESCRIPTION
      "Path: swPort.status.vlan.ipV6.addresses.flags.anycast

       Possibilities:
               no   (0)
               yes   (1)"
   ::= {sr1645v2EthPortSwIVlanIpV6AddressesEntry 84017152}

sr1645v2EthPortSwIVlanIpV6AddressesTimersValidLifeTime OBJECT-TYPE
   SYNTAX      TimeTicks
   MAX-ACCESS  read-only
   STATUS      current
   DESCRIPTION
      "Path: swPort.status.vlan.ipV6.addresses.timers.validLifeTime

       Time in centi-second."
   ::= {sr1645v2EthPortSwIVlanIpV6AddressesEntry 100794368}

sr1645v2EthPortSwIVlanIpV6AddressesTimersPrefLifeTime OBJECT-TYPE
   SYNTAX      TimeTicks
   MAX-ACCESS  read-only
   STATUS      current
   DESCRIPTION
      "Path: swPort.status.vlan.ipV6.addresses.timers.prefLifeTime

       Time in centi-second."
   ::= {sr1645v2EthPortSwIVlanIpV6AddressesEntry 100728832}

sr1645v2EthPortSwIVlanVlanArpCache OBJECT-TYPE
   SYNTAX      SEQUENCE OF Sr1645v2EthPortSwIVlanVlanArpCacheEntry
   MAX-ACCESS  not-accessible
   STATUS      current
   DESCRIPTION
      ""
   ::= {sr1645v2EthPortSwIVlan 235601920}

sr1645v2EthPortSwIVlanVlanArpCacheEntry OBJECT-TYPE
   SYNTAX      Sr1645v2EthPortSwIVlanVlanArpCacheEntry
   MAX-ACCESS  not-accessible
   STATUS      current
   DESCRIPTION
      ""
   INDEX      { sr1645v2EthPortSwIVlanVlanArpCacheGlobalIx,
                sr1645v2EthPortSwIVlanTableIx,
                sr1645v2EthPortSwIVlanVlanArpCacheTableIx }
   ::= {sr1645v2EthPortSwIVlanVlanArpCache 1}

Sr1645v2EthPortSwIVlanVlanArpCacheEntry ::=
   SEQUENCE
      {
      sr1645v2EthPortSwIVlanVlanArpCacheGlobalIx
         GlobalIndex,
      sr1645v2EthPortSwIVlanVlanArpCacheTableIx
         TableIndex,
      sr1645v2EthPortSwIVlanVlanArpCacheMacAddress
         OCTET STRING,
      sr1645v2EthPortSwIVlanVlanArpCacheIpAddress
         IpAddress,
      sr1645v2EthPortSwIVlanVlanArpCacheType
         INTEGER,
      sr1645v2EthPortSwIVlanVlanArpCacheTimeOut
         TimeTicks
      }

sr1645v2EthPortSwIVlanVlanArpCacheGlobalIx OBJECT-TYPE
   SYNTAX      GlobalIndex
   MAX-ACCESS  not-accessible
   STATUS      current
   DESCRIPTION
      "The value of the tlsCntTreeGlobalIndex of the MANAGED OBJECT."
   ::= {sr1645v2EthPortSwIVlanVlanArpCacheEntry 10}

sr1645v2EthPortSwIVlanVlanArpCacheTableIx OBJECT-TYPE
   SYNTAX      TableIndex
   MAX-ACCESS  not-accessible
   STATUS      current
   DESCRIPTION
      ""
   ::= {sr1645v2EthPortSwIVlanVlanArpCacheEntry 11}

sr1645v2EthPortSwIVlanVlanArpCacheMacAddress OBJECT-TYPE
   SYNTAX      OCTET STRING
   MAX-ACCESS  read-only
   STATUS      current
   DESCRIPTION
      "Path: swPort.status.vlan.vlan.arpCache.macAddress

       MAC address."
   ::= {sr1645v2EthPortSwIVlanVlanArpCacheEntry 16777216}

sr1645v2EthPortSwIVlanVlanArpCacheIpAddress OBJECT-TYPE
   SYNTAX      IpAddress
   MAX-ACCESS  read-only
   STATUS      current
   DESCRIPTION
      "Path: swPort.status.vlan.vlan.arpCache.ipAddress"
   ::= {sr1645v2EthPortSwIVlanVlanArpCacheEntry 33554432}

sr1645v2EthPortSwIVlanVlanArpCacheType OBJECT-TYPE
   SYNTAX      INTEGER
               {
               static (0),
               dynamic (1)
               }
   MAX-ACCESS  read-only
   STATUS      current
   DESCRIPTION
      "Path: swPort.status.vlan.vlan.arpCache.type

       Possibilities:
               static   (0)
               dynamic   (1)"
   ::= {sr1645v2EthPortSwIVlanVlanArpCacheEntry 50331648}

sr1645v2EthPortSwIVlanVlanArpCacheTimeOut OBJECT-TYPE
   SYNTAX      TimeTicks
   MAX-ACCESS  read-only
   STATUS      current
   DESCRIPTION
      "Path: swPort.status.vlan.vlan.arpCache.timeOut

       Time in centi-second."
   ::= {sr1645v2EthPortSwIVlanVlanArpCacheEntry 67108864}


sr1645v2EthPortSwIPppOE OBJECT IDENTIFIER ::= {sr1645v2EthPortSwI 36}

sr1645v2EthPortSwIPppOESSCTable OBJECT-TYPE
   SYNTAX      SEQUENCE OF Sr1645v2EthPortSwIPppOEEntry
   MAX-ACCESS  not-accessible
   STATUS      current
   DESCRIPTION
      ""
   ::= {sr1645v2EthPortSwIPppOE 1}

sr1645v2EthPortSwIPppOEEntry OBJECT-TYPE
   SYNTAX      Sr1645v2EthPortSwIPppOEEntry
   MAX-ACCESS  not-accessible
   STATUS      current
   DESCRIPTION
      ""
   INDEX      { sr1645v2EthPortSwIPppOEGlobalIx,
                sr1645v2EthPortSwIPppOETableIx }
   ::= {sr1645v2EthPortSwIPppOESSCTable 1}

Sr1645v2EthPortSwIPppOEEntry ::=
   SEQUENCE
      {
      sr1645v2EthPortSwIPppOEGlobalIx
         GlobalIndex,
      sr1645v2EthPortSwIPppOETableIx
         TableIndex,
      sr1645v2EthPortSwIPppOEName
         DisplayString,
      sr1645v2EthPortSwIPppOEMode
         INTEGER,
      sr1645v2EthPortSwIPppOEIfOperStatus
         INTEGER,
      sr1645v2EthPortSwIPppOEIfLastChange
         TimeTicks,
      sr1645v2EthPortSwIPppOEIfLastChangeDate
         DisplayString,
      sr1645v2EthPortSwIPppOEIpAddress
         IpAddress,
      sr1645v2EthPortSwIPppOEIpNetMask
         IpAddress,
      sr1645v2EthPortSwIPppOEIpRemote
         IpAddress,
      sr1645v2EthPortSwIPppOEPppOEthDiscState
         INTEGER,
      sr1645v2EthPortSwIPppOEPppOEthPeerMac
         OCTET STRING,
      sr1645v2EthPortSwIPppOEPppOEthServiceName
         DisplayString,
      sr1645v2EthPortSwIPppOEPppLcpState
         INTEGER,
      sr1645v2EthPortSwIPppOEPppIpcpState
         INTEGER,
      sr1645v2EthPortSwIPppOEPppIp6cpState
         INTEGER,
      sr1645v2EthPortSwIPppOEPppMyAutSt
         INTEGER,
      sr1645v2EthPortSwIPppOEPppHisAutSt
         INTEGER,
      sr1645v2EthPortSwIPppOEPppMru
         Integer32,
      sr1645v2EthPortSwIPppOEIpV6State
         INTEGER,
      sr1645v2EthPortSwIPppOEIpV6InterfaceId
         OCTET STRING,
      sr1645v2EthPortSwIPppOEIpV6LinkMtu
         Integer32,
      sr1645v2EthPortSwIPppOEIpV6HopLimit
         Integer32,
      sr1645v2EthPortSwIPppOEIpV6DhcpIaid
         Counter32,
      sr1645v2EthPortSwIPppOEIpV6RaRcvOption
         Integer32
      }

sr1645v2EthPortSwIPppOEGlobalIx OBJECT-TYPE
   SYNTAX      GlobalIndex
   MAX-ACCESS  not-accessible
   STATUS      current
   DESCRIPTION
      "The value of the tlsCntTreeGlobalIndex of the MANAGED OBJECT."
   ::= {sr1645v2EthPortSwIPppOEEntry 10}

sr1645v2EthPortSwIPppOETableIx OBJECT-TYPE
   SYNTAX      TableIndex
   MAX-ACCESS  not-accessible
   STATUS      current
   DESCRIPTION
      ""
   ::= {sr1645v2EthPortSwIPppOEEntry 11}

sr1645v2EthPortSwIPppOEName OBJECT-TYPE
   SYNTAX      DisplayString
   MAX-ACCESS  read-only
   STATUS      current
   DESCRIPTION
      "Path: swPort.status.pppoEClient.name"
   ::= {sr1645v2EthPortSwIPppOEEntry 16777216}

sr1645v2EthPortSwIPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2EthPortSwIPppOEEntry 335544320}

sr1645v2EthPortSwIPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.pppoEClient.ifOperStatus

       Possibilities:
               up   (1)
               down   (2)
               testing   (3)
               unknown   (4)
               dormant   (5)
               notPresent   (6)
               lowerLayerDown   (7)"
   ::= {sr1645v2EthPortSwIPppOEEntry 1795162112}

sr1645v2EthPortSwIPppOEIfLastChange OBJECT-TYPE
   SYNTAX      TimeTicks
   MAX-ACCESS  read-only
   STATUS      current
   DESCRIPTION
      "Path: swPort.status.pppoEClient.ifLastChange

       Time in centi-second."
   ::= {sr1645v2EthPortSwIPppOEEntry 1811939328}

sr1645v2EthPortSwIPppOEIfLastChangeDate OBJECT-TYPE
   SYNTAX      DisplayString
   MAX-ACCESS  read-only
   STATUS      current
   DESCRIPTION
      "Path: swPort.status.pppoEClient.ifLastChangeDate"
   ::= {sr1645v2EthPortSwIPppOEEntry 3070230528}

sr1645v2EthPortSwIPppOEIpAddress OBJECT-TYPE
   SYNTAX      IpAddress
   MAX-ACCESS  read-only
   STATUS      current
   DESCRIPTION
      "Path: swPort.status.pppoEClient.ip.address"
   ::= {sr1645v2EthPortSwIPppOEEntry 51380224}

sr1645v2EthPortSwIPppOEIpNetMask OBJECT-TYPE
   SYNTAX      IpAddress
   MAX-ACCESS  read-only
   STATUS      current
   DESCRIPTION
      "Path: swPort.status.pppoEClient.ip.netMask"
   ::= {sr1645v2EthPortSwIPppOEEntry 51445760}

sr1645v2EthPortSwIPppOEIpRemote OBJECT-TYPE
   SYNTAX      IpAddress
   MAX-ACCESS  read-only
   STATUS      current
   DESCRIPTION
      "Path: swPort.status.pppoEClient.ip.remote"
   ::= {sr1645v2EthPortSwIPppOEEntry 51511296}

sr1645v2EthPortSwIPppOEPppOEthDiscState OBJECT-TYPE
   SYNTAX      INTEGER
               {
               idle (0),
               waitForPADO (1),
               waitForPADS (2),
               established (3)
               }
   MAX-ACCESS  read-only
   STATUS      current
   DESCRIPTION
      "Path: swPort.status.pppoEClient.pppOverEth.discState

       Possibilities:
               idle   (0)
               waitForPADO   (1)
               waitForPADS   (2)
               established   (3)"
   ::= {sr1645v2EthPortSwIPppOEEntry 67174400}

sr1645v2EthPortSwIPppOEPppOEthPeerMac OBJECT-TYPE
   SYNTAX      OCTET STRING
   MAX-ACCESS  read-only
   STATUS      current
   DESCRIPTION
      "Path: swPort.status.pppoEClient.pppOverEth.remoteMacAddress

       MAC address."
   ::= {sr1645v2EthPortSwIPppOEEntry 67239936}

sr1645v2EthPortSwIPppOEPppOEthServiceName OBJECT-TYPE
   SYNTAX      DisplayString
   MAX-ACCESS  read-only
   STATUS      current
   DESCRIPTION
      "Path: swPort.status.pppoEClient.pppOverEth.serviceName"
   ::= {sr1645v2EthPortSwIPppOEEntry 67305472}

sr1645v2EthPortSwIPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIPppOEEntry 83951616}

sr1645v2EthPortSwIPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIPppOEEntry 84017152}

sr1645v2EthPortSwIPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPortSwIPppOEEntry 84869120}

sr1645v2EthPortSwIPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2EthPortSwIPppOEEntry 84541440}

sr1645v2EthPortSwIPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2EthPortSwIPppOEEntry 84606976}

sr1645v2EthPortSwIPppOEPppMru OBJECT-TYPE
   SYNTAX      Integer32
   MAX-ACCESS  read-only
   STATUS      current
   DESCRIPTION
      "Path: swPort.status.pppoEClient.ppp.mru"
   ::= {sr1645v2EthPortSwIPppOEEntry 84934656}

sr1645v2EthPortSwIPppOEIpV6State OBJECT-TYPE
   SYNTAX      INTEGER
               {
               disabled (0),
               enabled (1)
               }
   MAX-ACCESS  read-only
   STATUS      current
   DESCRIPTION
      "Path: swPort.status.pppoEClient.ipV6.state

       Possibilities:
               disabled   (0)
               enabled   (1)"
   ::= {sr1645v2EthPortSwIPppOEEntry 100728832}

sr1645v2EthPortSwIPppOEIpV6InterfaceId OBJECT-TYPE
   SYNTAX      OCTET STRING
   MAX-ACCESS  read-only
   STATUS      current
   DESCRIPTION
      "Path: swPort.status.pppoEClient.ipV6.interfaceId"
   ::= {sr1645v2EthPortSwIPppOEEntry 100794368}

sr1645v2EthPortSwIPppOEIpV6LinkMtu OBJECT-TYPE
   SYNTAX      Integer32
   MAX-ACCESS  read-only
   STATUS      current
   DESCRIPTION
      "Path: swPort.status.pppoEClient.ipV6.linkMtu"
   ::= {sr1645v2EthPortSwIPppOEEntry 100925440}

sr1645v2EthPortSwIPppOEIpV6HopLimit OBJECT-TYPE
   SYNTAX      Integer32
   MAX-ACCESS  read-only
   STATUS      current
   DESCRIPTION
      "Path: swPort.status.pppoEClient.ipV6.hopLimit"
   ::= {sr1645v2EthPortSwIPppOEEntry 100990976}

sr1645v2EthPortSwIPppOEIpV6DhcpIaid OBJECT-TYPE
   SYNTAX      Counter32
   MAX-ACCESS  read-only
   STATUS      current
   DESCRIPTION
      "Path: swPort.status.pppoEClient.ipV6.dhcp.iaid

       32 bit unsigned wrappable counter."
   ::= {sr1645v2EthPortSwIPppOEEntry 101056768}

sr1645v2EthPortSwIPppOEIpV6RaRcvOption OBJECT-TYPE
   SYNTAX      Integer32
   MAX-ACCESS  read-only
   STATUS      current
   DESCRIPTION
      "Path: swPort.status.pppoEClient.ipV6.raRcvOption

       Bit meanings:
               bit 0 = linkMtu,
               bit 1 = srcLinkLayer,
               bit 2 = prefixInfo,
               bit 3 = rdnss,
               bit 4 = dnssl"
   ::= {sr1645v2EthPortSwIPppOEEntry 101122048}

sr1645v2EthPortSwIPppOEIpV6Addresses OBJECT-TYPE
   SYNTAX      SEQUENCE OF Sr1645v2EthPortSwIPppOEIpV6AddressesEntry
   MAX-ACCESS  not-accessible
   STATUS      current
   DESCRIPTION
      ""
   ::= {sr1645v2EthPortSwIPppOE 100859904}

sr1645v2EthPortSwIPppOEIpV6AddressesEntry OBJECT-TYPE
   SYNTAX      Sr1645v2EthPortSwIPppOEIpV6AddressesEntry
   MAX-ACCESS  not-accessible
   STATUS      current
   DESCRIPTION
      ""
   INDEX      { sr1645v2EthPortSwIPppOEIpV6AddressesGlobalIx,
                sr1645v2EthPortSwIPppOETableIx,
                sr1645v2EthPortSwIPppOEIpV6AddressesTableIx }
   ::= {sr1645v2EthPortSwIPppOEIpV6Addresses 1}

Sr1645v2EthPortSwIPppOEIpV6AddressesEntry ::=
   SEQUENCE
      {
      sr1645v2EthPortSwIPppOEIpV6AddressesGlobalIx
         GlobalIndex,
      sr1645v2EthPortSwIPppOEIpV6AddressesTableIx
         TableIndex,
      sr1645v2EthPortSwIPppOEIpV6AddressesAddress
         Ipv6Address,
      sr1645v2EthPortSwIPppOEIpV6AddressesPrefixLength
         Integer32,
      sr1645v2EthPortSwIPppOEIpV6AddressesStatus
         INTEGER,
      sr1645v2EthPortSwIPppOEIpV6AddressesOrigin
         INTEGER,
      sr1645v2EthPortSwIPppOEIpV6AddressesFlagsInterfaceId
         INTEGER,
      sr1645v2EthPortSwIPppOEIpV6AddressesFlagsAnycast
         INTEGER,
      sr1645v2EthPortSwIPppOEIpV6AddressesTimersValidLifeTime
         TimeTicks,
      sr1645v2EthPortSwIPppOEIpV6AddressesTimersPrefLifeTime
         TimeTicks
      }

sr1645v2EthPortSwIPppOEIpV6AddressesGlobalIx OBJECT-TYPE
   SYNTAX      GlobalIndex
   MAX-ACCESS  not-accessible
   STATUS      current
   DESCRIPTION
      "The value of the tlsCntTreeGlobalIndex of the MANAGED OBJECT."
   ::= {sr1645v2EthPortSwIPppOEIpV6AddressesEntry 10}

sr1645v2EthPortSwIPppOEIpV6AddressesTableIx OBJECT-TYPE
   SYNTAX      TableIndex
   MAX-ACCESS  not-accessible
   STATUS      current
   DESCRIPTION
      ""
   ::= {sr1645v2EthPortSwIPppOEIpV6AddressesEntry 11}

sr1645v2EthPortSwIPppOEIpV6AddressesAddress OBJECT-TYPE
   SYNTAX      Ipv6Address
   MAX-ACCESS  read-only
   STATUS      current
   DESCRIPTION
      "Path: swPort.status.pppoEClient.ipV6.addresses.address

       ipv6 address"
   ::= {sr1645v2EthPortSwIPppOEIpV6AddressesEntry 16777216}

sr1645v2EthPortSwIPppOEIpV6AddressesPrefixLength OBJECT-TYPE
   SYNTAX      Integer32
   MAX-ACCESS  read-only
   STATUS      current
   DESCRIPTION
      "Path: swPort.status.pppoEClient.ipV6.addresses.prefixLength"
   ::= {sr1645v2EthPortSwIPppOEIpV6AddressesEntry 33554432}

sr1645v2EthPortSwIPppOEIpV6AddressesStatus OBJECT-TYPE
   SYNTAX      INTEGER
               {
               invalid (0),
               tentative (1),
               deprecated (2),
               preferred (3)
               }
   MAX-ACCESS  read-only
   STATUS      current
   DESCRIPTION
      "Path: swPort.status.pppoEClient.ipV6.addresses.status

       Possibilities:
               invalid   (0)
               tentative   (1)
               deprecated   (2)
               preferred   (3)"
   ::= {sr1645v2EthPortSwIPppOEIpV6AddressesEntry 50331648}

sr1645v2EthPortSwIPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.pppoEClient.ipV6.addresses.origin

       Possibilities:
               unknown   (0)
               manual   (1)
               generalPrefix   (2)
               statelessAuto   (3)
               statefullAuto   (4)"
   ::= {sr1645v2EthPortSwIPppOEIpV6AddressesEntry 67108864}

sr1645v2EthPortSwIPppOEIpV6AddressesFlagsInterfaceId OBJECT-TYPE
   SYNTAX      INTEGER
               {
               no (0),
               yes (1)
               }
   MAX-ACCESS  read-only
   STATUS      current
   DESCRIPTION
      "Path: swPort.status.pppoEClient.ipV6.addresses.flags.interfaceId

       Possibilities:
               no   (0)
               yes   (1)"
   ::= {sr1645v2EthPortSwIPppOEIpV6AddressesEntry 83951616}

sr1645v2EthPortSwIPppOEIpV6AddressesFlagsAnycast OBJECT-TYPE
   SYNTAX      INTEGER
               {
               no (0),
               yes (1)
               }
   MAX-ACCESS  read-only
   STATUS      current
   DESCRIPTION
      "Path: swPort.status.pppoEClient.ipV6.addresses.flags.anycast

       Possibilities:
               no   (0)
               yes   (1)"
   ::= {sr1645v2EthPortSwIPppOEIpV6AddressesEntry 84017152}

sr1645v2EthPortSwIPppOEIpV6AddressesTimersValidLifeTime OBJECT-TYPE
   SYNTAX      TimeTicks
   MAX-ACCESS  read-only
   STATUS      current
   DESCRIPTION
      "Path: swPort.status.pppoEClient.ipV6.addresses.timers.validLifeTime

       Time in centi-second."
   ::= {sr1645v2EthPortSwIPppOEIpV6AddressesEntry 100794368}

sr1645v2EthPortSwIPppOEIpV6AddressesTimersPrefLifeTime OBJECT-TYPE
   SYNTAX      TimeTicks
   MAX-ACCESS  read-only
   STATUS      current
   DESCRIPTION
      "Path: swPort.status.pppoEClient.ipV6.addresses.timers.prefLifeTime

       Time in centi-second."
   ::= {sr1645v2EthPortSwIPppOEIpV6AddressesEntry 100728832}


sr1645v2EthPortSwIDot1x OBJECT IDENTIFIER ::= {sr1645v2EthPortSwI 190}

sr1645v2EthPortSwIDot1xSSCTable OBJECT-TYPE
   SYNTAX      SEQUENCE OF Sr1645v2EthPortSwIDot1xEntry
   MAX-ACCESS  not-accessible
   STATUS      current
   DESCRIPTION
      "Ethernet Switch VLAN Table"
   ::= {sr1645v2EthPortSwIDot1x 1}

sr1645v2EthPortSwIDot1xEntry OBJECT-TYPE
   SYNTAX      Sr1645v2EthPortSwIDot1xEntry
   MAX-ACCESS  not-accessible
   STATUS      current
   DESCRIPTION
      ""
   INDEX      { sr1645v2EthPortSwIDot1xGlobalIx,
                sr1645v2EthPortSwIDot1xTableIx }
   ::= {sr1645v2EthPortSwIDot1xSSCTable 1}

Sr1645v2EthPortSwIDot1xEntry ::=
   SEQUENCE
      {
      sr1645v2EthPortSwIDot1xGlobalIx
         GlobalIndex,
      sr1645v2EthPortSwIDot1xTableIx
         TableIndex,
      sr1645v2EthPortSwIDot1xRemote
         OCTET STRING,
      sr1645v2EthPortSwIDot1xAuthorized
         INTEGER,
      sr1645v2EthPortSwIDot1xAuthenticator
         INTEGER,
      sr1645v2EthPortSwIDot1xBackEnd
         INTEGER,
      sr1645v2EthPortSwIDot1xRetries
         Integer32,
      sr1645v2EthPortSwIDot1xReAuthTime
         TimeTicks,
      sr1645v2EthPortSwIDot1xHoldTime
         TimeTicks
      }

sr1645v2EthPortSwIDot1xGlobalIx OBJECT-TYPE
   SYNTAX      GlobalIndex
   MAX-ACCESS  not-accessible
   STATUS      current
   DESCRIPTION
      "The value of the tlsCntTreeGlobalIndex of the MANAGED OBJECT."
   ::= {sr1645v2EthPortSwIDot1xEntry 10}

sr1645v2EthPortSwIDot1xTableIx OBJECT-TYPE
   SYNTAX      TableIndex
   MAX-ACCESS  not-accessible
   STATUS      current
   DESCRIPTION
      ""
   ::= {sr1645v2EthPortSwIDot1xEntry 11}

sr1645v2EthPortSwIDot1xRemote OBJECT-TYPE
   SYNTAX      OCTET STRING
   MAX-ACCESS  read-only
   STATUS      current
   DESCRIPTION
      "Path: swPort.status.dot1x.remote

       MAC address."
   ::= {sr1645v2EthPortSwIDot1xEntry 16777216}

sr1645v2EthPortSwIDot1xAuthorized OBJECT-TYPE
   SYNTAX      INTEGER
               {
               no (0),
               yes (1)
               }
   MAX-ACCESS  read-only
   STATUS      current
   DESCRIPTION
      "Path: swPort.status.dot1x.authorized

       Possibilities:
               no   (0)
               yes   (1)"
   ::= {sr1645v2EthPortSwIDot1xEntry 33554432}

sr1645v2EthPortSwIDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: swPort.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2EthPortSwIDot1xEntry 50331648}

sr1645v2EthPortSwIDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: swPort.status.dot1x.backEnd

       Possibilities:
               preInit   (0)
               initialize   (1)
               idle   (2)
               request   (3)
               response   (4)
               success   (5)
               failure   (6)
               radiusTimeout   (7)
               timeout   (8)"
   ::= {sr1645v2EthPortSwIDot1xEntry 67108864}

sr1645v2EthPortSwIDot1xRetries OBJECT-TYPE
   SYNTAX      Integer32
   MAX-ACCESS  read-only
   STATUS      current
   DESCRIPTION
      "Path: swPort.status.dot1x.retries"
   ::= {sr1645v2EthPortSwIDot1xEntry 83886080}

sr1645v2EthPortSwIDot1xReAuthTime OBJECT-TYPE
   SYNTAX      TimeTicks
   MAX-ACCESS  read-only
   STATUS      current
   DESCRIPTION
      "Path: swPort.status.dot1x.reAuthTime

       Time in centi-second."
   ::= {sr1645v2EthPortSwIDot1xEntry 100663296}

sr1645v2EthPortSwIDot1xHoldTime OBJECT-TYPE
   SYNTAX      TimeTicks
   MAX-ACCESS  read-only
   STATUS      current
   DESCRIPTION
      "Path: swPort.status.dot1x.holdTime

       Time in centi-second."
   ::= {sr1645v2EthPortSwIDot1xEntry 117440512}


sr1645v2EthPortSwIIpV6 OBJECT IDENTIFIER ::= {sr1645v2EthPortSwI 17}

sr1645v2EthPortSwIIpV6SSCTable OBJECT-TYPE
   SYNTAX      SEQUENCE OF Sr1645v2EthPortSwIIpV6Entry
   MAX-ACCESS  not-accessible
   STATUS      current
   DESCRIPTION
      "IPv6 interface config parameters"
   ::= {sr1645v2EthPortSwIIpV6 1}

sr1645v2EthPortSwIIpV6Entry OBJECT-TYPE
   SYNTAX      Sr1645v2EthPortSwIIpV6Entry
   MAX-ACCESS  not-accessible
   STATUS      current
   DESCRIPTION
      ""
   INDEX      { sr1645v2EthPortSwIIpV6GlobalIx }
   ::= {sr1645v2EthPortSwIIpV6SSCTable 1}

Sr1645v2EthPortSwIIpV6Entry ::=
   SEQUENCE
      {
      sr1645v2EthPortSwIIpV6GlobalIx
         GlobalIndex,
      sr1645v2EthPortSwIIpV6State
         INTEGER,
      sr1645v2EthPortSwIIpV6InterfaceId
         OCTET STRING,
      sr1645v2EthPortSwIIpV6LinkMtu
         Integer32,
      sr1645v2EthPortSwIIpV6HopLimit
         Integer32,
      sr1645v2EthPortSwIIpV6DhcpIaid
         Counter32,
      sr1645v2EthPortSwIIpV6RaRcvOption
         Integer32
      }

sr1645v2EthPortSwIIpV6GlobalIx OBJECT-TYPE
   SYNTAX      GlobalIndex
   MAX-ACCESS  not-accessible
   STATUS      current
   DESCRIPTION
      "The value of the tlsCntTreeGlobalIndex of the MANAGED OBJECT."
   ::= {sr1645v2EthPortSwIIpV6Entry 10}

sr1645v2EthPortSwIIpV6State OBJECT-TYPE
   SYNTAX      INTEGER
               {
               disabled (0),
               enabled (1)
               }
   MAX-ACCESS  read-only
   STATUS      current
   DESCRIPTION
      "Path: swPort.status.ipV6.state

       Possibilities:
               disabled   (0)
               enabled   (1)"
   ::= {sr1645v2EthPortSwIIpV6Entry 16777216}

sr1645v2EthPortSwIIpV6InterfaceId OBJECT-TYPE
   SYNTAX      OCTET STRING
   MAX-ACCESS  read-only
   STATUS      current
   DESCRIPTION
      "Path: swPort.status.ipV6.interfaceId"
   ::= {sr1645v2EthPortSwIIpV6Entry 33554432}

sr1645v2EthPortSwIIpV6LinkMtu OBJECT-TYPE
   SYNTAX      Integer32
   MAX-ACCESS  read-only
   STATUS      current
   DESCRIPTION
      "Path: swPort.status.ipV6.linkMtu"
   ::= {sr1645v2EthPortSwIIpV6Entry 67108864}

sr1645v2EthPortSwIIpV6HopLimit OBJECT-TYPE
   SYNTAX      Integer32
   MAX-ACCESS  read-only
   STATUS      current
   DESCRIPTION
      "Path: swPort.status.ipV6.hopLimit"
   ::= {sr1645v2EthPortSwIIpV6Entry 83886080}

sr1645v2EthPortSwIIpV6DhcpIaid OBJECT-TYPE
   SYNTAX      Counter32
   MAX-ACCESS  read-only
   STATUS      current
   DESCRIPTION
      "Path: swPort.status.ipV6.dhcp.iaid

       32 bit unsigned wrappable counter."
   ::= {sr1645v2EthPortSwIIpV6Entry 100728832}

sr1645v2EthPortSwIIpV6RaRcvOption OBJECT-TYPE
   SYNTAX      Integer32
   MAX-ACCESS  read-only
   STATUS      current
   DESCRIPTION
      "Path: swPort.status.ipV6.raRcvOption

       Bit meanings:
               bit 0 = linkMtu,
               bit 1 = srcLinkLayer,
               bit 2 = prefixInfo,
               bit 3 = rdnss,
               bit 4 = dnssl"
   ::= {sr1645v2EthPortSwIIpV6Entry 117440512}

sr1645v2EthPortSwIIpV6Addresses OBJECT-TYPE
   SYNTAX      SEQUENCE OF Sr1645v2EthPortSwIIpV6AddressesEntry
   MAX-ACCESS  not-accessible
   STATUS      current
   DESCRIPTION
      ""
   ::= {sr1645v2EthPortSwIIpV6 50331648}

sr1645v2EthPortSwIIpV6AddressesEntry OBJECT-TYPE
   SYNTAX      Sr1645v2EthPortSwIIpV6AddressesEntry
   MAX-ACCESS  not-accessible
   STATUS      current
   DESCRIPTION
      ""
   INDEX      { sr1645v2EthPortSwIIpV6AddressesGlobalIx,
                sr1645v2EthPortSwIIpV6AddressesTableIx }
   ::= {sr1645v2EthPortSwIIpV6Addresses 1}

Sr1645v2EthPortSwIIpV6AddressesEntry ::=
   SEQUENCE
      {
      sr1645v2EthPortSwIIpV6AddressesGlobalIx
         GlobalIndex,
      sr1645v2EthPortSwIIpV6AddressesTableIx
         TableIndex,
      sr1645v2EthPortSwIIpV6AddressesAddress
         Ipv6Address,
      sr1645v2EthPortSwIIpV6AddressesPrefixLength
         Integer32,
      sr1645v2EthPortSwIIpV6AddressesStatus
         INTEGER,
      sr1645v2EthPortSwIIpV6AddressesOrigin
         INTEGER,
      sr1645v2EthPortSwIIpV6AddressesFlagsInterfaceId
         INTEGER,
      sr1645v2EthPortSwIIpV6AddressesFlagsAnycast
         INTEGER,
      sr1645v2EthPortSwIIpV6AddressesTimersValidLifeTime
         TimeTicks,
      sr1645v2EthPortSwIIpV6AddressesTimersPrefLifeTime
         TimeTicks
      }

sr1645v2EthPortSwIIpV6AddressesGlobalIx OBJECT-TYPE
   SYNTAX      GlobalIndex
   MAX-ACCESS  not-accessible
   STATUS      current
   DESCRIPTION
      "The value of the tlsCntTreeGlobalIndex of the MANAGED OBJECT."
   ::= {sr1645v2EthPortSwIIpV6AddressesEntry 10}

sr1645v2EthPortSwIIpV6AddressesTableIx OBJECT-TYPE
   SYNTAX      TableIndex
   MAX-ACCESS  not-accessible
   STATUS      current
   DESCRIPTION
      ""
   ::= {sr1645v2EthPortSwIIpV6AddressesEntry 11}

sr1645v2EthPortSwIIpV6AddressesAddress OBJECT-TYPE
   SYNTAX      Ipv6Address
   MAX-ACCESS  read-only
   STATUS      current
   DESCRIPTION
      "Path: swPort.status.ipV6.addresses.address

       ipv6 address"
   ::= {sr1645v2EthPortSwIIpV6AddressesEntry 16777216}

sr1645v2EthPortSwIIpV6AddressesPrefixLength OBJECT-TYPE
   SYNTAX      Integer32
   MAX-ACCESS  read-only
   STATUS      current
   DESCRIPTION
      "Path: swPort.status.ipV6.addresses.prefixLength"
   ::= {sr1645v2EthPortSwIIpV6AddressesEntry 33554432}

sr1645v2EthPortSwIIpV6AddressesStatus OBJECT-TYPE
   SYNTAX      INTEGER
               {
               invalid (0),
               tentative (1),
               deprecated (2),
               preferred (3)
               }
   MAX-ACCESS  read-only
   STATUS      current
   DESCRIPTION
      "Path: swPort.status.ipV6.addresses.status

       Possibilities:
               invalid   (0)
               tentative   (1)
               deprecated   (2)
               preferred   (3)"
   ::= {sr1645v2EthPortSwIIpV6AddressesEntry 50331648}

sr1645v2EthPortSwIIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.ipV6.addresses.origin

       Possibilities:
               unknown   (0)
               manual   (1)
               generalPrefix   (2)
               statelessAuto   (3)
               statefullAuto   (4)"
   ::= {sr1645v2EthPortSwIIpV6AddressesEntry 67108864}

sr1645v2EthPortSwIIpV6AddressesFlagsInterfaceId OBJECT-TYPE
   SYNTAX      INTEGER
               {
               no (0),
               yes (1)
               }
   MAX-ACCESS  read-only
   STATUS      current
   DESCRIPTION
      "Path: swPort.status.ipV6.addresses.flags.interfaceId

       Possibilities:
               no   (0)
               yes   (1)"
   ::= {sr1645v2EthPortSwIIpV6AddressesEntry 83951616}

sr1645v2EthPortSwIIpV6AddressesFlagsAnycast OBJECT-TYPE
   SYNTAX      INTEGER
               {
               no (0),
               yes (1)
               }
   MAX-ACCESS  read-only
   STATUS      current
   DESCRIPTION
      "Path: swPort.status.ipV6.addresses.flags.anycast

       Possibilities:
               no   (0)
               yes   (1)"
   ::= {sr1645v2EthPortSwIIpV6AddressesEntry 84017152}

sr1645v2EthPortSwIIpV6AddressesTimersValidLifeTime OBJECT-TYPE
   SYNTAX      TimeTicks
   MAX-ACCESS  read-only
   STATUS      current
   DESCRIPTION
      "Path: swPort.status.ipV6.addresses.timers.validLifeTime

       Time in centi-second."
   ::= {sr1645v2EthPortSwIIpV6AddressesEntry 100794368}

sr1645v2EthPortSwIIpV6AddressesTimersPrefLifeTime OBJECT-TYPE
   SYNTAX      TimeTicks
   MAX-ACCESS  read-only
   STATUS      current
   DESCRIPTION
      "Path: swPort.status.ipV6.addresses.timers.prefLifeTime

       Time in centi-second."
   ::= {sr1645v2EthPortSwIIpV6AddressesEntry 100728832}


sr1645v2EthPortSwISnmpIndex OBJECT IDENTIFIER ::= {sr1645v2EthPortSwI 269}

sr1645v2EthPortSwISnmpIndexTable OBJECT-TYPE
   SYNTAX      SEQUENCE OF Sr1645v2EthPortSwISnmpIndexEntry
   MAX-ACCESS  not-accessible
   STATUS      current
   DESCRIPTION
      "SNMP index assigned to this object"
   ::= {sr1645v2EthPortSwISnmpIndex 1}

sr1645v2EthPortSwISnmpIndexEntry OBJECT-TYPE
   SYNTAX      Sr1645v2EthPortSwISnmpIndexEntry
   MAX-ACCESS  not-accessible
   STATUS      current
   DESCRIPTION
      ""
   INDEX      { sr1645v2EthPortSwISnmpIndexGlobalIx }
   ::= {sr1645v2EthPortSwISnmpIndexTable 1}

Sr1645v2EthPortSwISnmpIndexEntry ::=
   SEQUENCE
      {
      sr1645v2EthPortSwISnmpIndexGlobalIx
         GlobalIndex,
      sr1645v2EthPortSwISnmpIndexValue
         Integer32
      }

sr1645v2EthPortSwISnmpIndexGlobalIx OBJECT-TYPE
   SYNTAX      GlobalIndex
   MAX-ACCESS  not-accessible
   STATUS      current
   DESCRIPTION
      "The value of the tlsCntTreeGlobalIndex of the MANAGED OBJECT."
   ::= {sr1645v2EthPortSwISnmpIndexEntry 10}

sr1645v2EthPortSwISnmpIndexValue OBJECT-TYPE
   SYNTAX      Integer32
   MAX-ACCESS  read-only
   STATUS      current
   DESCRIPTION
      "Path: swPort.status.snmpIndex"
   ::= {sr1645v2EthPortSwISnmpIndexEntry 2147483648}


sr1645v2EthPortSwILst OBJECT IDENTIFIER ::= {sr1645v2EthPortSwI 18}

sr1645v2EthPortSwILstSSCTable OBJECT-TYPE
   SYNTAX      SEQUENCE OF Sr1645v2EthPortSwILstEntry
   MAX-ACCESS  not-accessible
   STATUS      current
   DESCRIPTION
      ""
   ::= {sr1645v2EthPortSwILst 1}

sr1645v2EthPortSwILstEntry OBJECT-TYPE
   SYNTAX      Sr1645v2EthPortSwILstEntry
   MAX-ACCESS  not-accessible
   STATUS      current
   DESCRIPTION
      ""
   INDEX      { sr1645v2EthPortSwILstGlobalIx }
   ::= {sr1645v2EthPortSwILstSSCTable 1}

Sr1645v2EthPortSwILstEntry ::=
   SEQUENCE
      {
      sr1645v2EthPortSwILstGlobalIx
         GlobalIndex,
      sr1645v2EthPortSwILstTrackedInterface
         DisplayString,
      sr1645v2EthPortSwILstIfOperStatus
         INTEGER
      }

sr1645v2EthPortSwILstGlobalIx OBJECT-TYPE
   SYNTAX      GlobalIndex
   MAX-ACCESS  not-accessible
   STATUS      current
   DESCRIPTION
      "The value of the tlsCntTreeGlobalIndex of the MANAGED OBJECT."
   ::= {sr1645v2EthPortSwILstEntry 10}

sr1645v2EthPortSwILstTrackedInterface OBJECT-TYPE
   SYNTAX      DisplayString
   MAX-ACCESS  read-only
   STATUS      current
   DESCRIPTION
      "Path: swPort.status.linkStateTracking.trackedInterface"
   ::= {sr1645v2EthPortSwILstEntry 16777216}

sr1645v2EthPortSwILstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: swPort.status.linkStateTracking.ifOperStatus

       Possibilities:
               up   (1)
               down   (2)
               testing   (3)
               unknown   (4)
               dormant   (5)
               notPresent   (6)
               lowerLayerDown   (7)
                  (255)"
   ::= {sr1645v2EthPortSwILstEntry 50331648}


sr1645v2EthPortSwIHwPorts OBJECT IDENTIFIER ::= {sr1645v2EthPortSwI 270}

sr1645v2EthPortSwIHwPortsSSCTable OBJECT-TYPE
   SYNTAX      SEQUENCE OF Sr1645v2EthPortSwIHwPortsEntry
   MAX-ACCESS  not-accessible
   STATUS      current
   DESCRIPTION
      ""
   ::= {sr1645v2EthPortSwIHwPorts 1}

sr1645v2EthPortSwIHwPortsEntry OBJECT-TYPE
   SYNTAX      Sr1645v2EthPortSwIHwPortsEntry
   MAX-ACCESS  not-accessible
   STATUS      current
   DESCRIPTION
      ""
   INDEX      { sr1645v2EthPortSwIHwPortsGlobalIx,
                sr1645v2EthPortSwIHwPortsTableIx }
   ::= {sr1645v2EthPortSwIHwPortsSSCTable 1}

Sr1645v2EthPortSwIHwPortsEntry ::=
   SEQUENCE
      {
      sr1645v2EthPortSwIHwPortsGlobalIx
         GlobalIndex,
      sr1645v2EthPortSwIHwPortsTableIx
         TableIndex,
      sr1645v2EthPortSwIHwPortsHwPort
         INTEGER,
      sr1645v2EthPortSwIHwPortsStatus
         INTEGER
      }

sr1645v2EthPortSwIHwPortsGlobalIx OBJECT-TYPE
   SYNTAX      GlobalIndex
   MAX-ACCESS  not-accessible
   STATUS      current
   DESCRIPTION
      "The value of the tlsCntTreeGlobalIndex of the MANAGED OBJECT."
   ::= {sr1645v2EthPortSwIHwPortsEntry 10}

sr1645v2EthPortSwIHwPortsTableIx OBJECT-TYPE
   SYNTAX      TableIndex
   MAX-ACCESS  not-accessible
   STATUS      current
   DESCRIPTION
      ""
   ::= {sr1645v2EthPortSwIHwPortsEntry 11}

sr1645v2EthPortSwIHwPortsHwPort OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (65535)
               }
   MAX-ACCESS  read-only
   STATUS      current
   DESCRIPTION
      "Path: swPort.status.hwPorts.hwPort

       Possibilities:
               hwPort_1   (1)
               hwPort_2   (2)
               hwPort_3   (3)
               hwPort_4   (4)
               hwPort_5   (5)
               hwPort_6   (6)
               hwPort_7   (7)
               hwPort_8   (8)
               hwPort_LocalPort   (65535)"
   ::= {sr1645v2EthPortSwIHwPortsEntry 16777216}

sr1645v2EthPortSwIHwPortsStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.hwPorts.status

       Possibilities:
               up   (1)
               down   (2)
               testing   (3)
               unknown   (4)
               dormant   (5)
               notPresent   (6)
               lowerLayerDown   (7)"
   ::= {sr1645v2EthPortSwIHwPortsEntry 33554432}



pr1645v2EthPortSwI OBJECT IDENTIFIER ::= {r1645v2EthPortSwI 12}


pr1645v2EthPortSwIInOctets OBJECT IDENTIFIER ::= {pr1645v2EthPortSwI 109}

pr1645v2EthPortSwIInOctetsTable OBJECT-TYPE
   SYNTAX      SEQUENCE OF Pr1645v2EthPortSwIInOctetsEntry
   MAX-ACCESS  not-accessible
   STATUS      current
   DESCRIPTION
      "ifInOctets"
   ::= {pr1645v2EthPortSwIInOctets 1}

pr1645v2EthPortSwIInOctetsEntry OBJECT-TYPE
   SYNTAX      Pr1645v2EthPortSwIInOctetsEntry
   MAX-ACCESS  not-accessible
   STATUS      current
   DESCRIPTION
      ""
   INDEX      { pr1645v2EthPortSwIInOctetsGlobalIx }
   ::= {pr1645v2EthPortSwIInOctetsTable 1}

Pr1645v2EthPortSwIInOctetsEntry ::=
   SEQUENCE
      {
      pr1645v2EthPortSwIInOctetsGlobalIx
         GlobalIndex,
      pr1645v2EthPortSwIInOctetsValue
         Counter64
      }

pr1645v2EthPortSwIInOctetsGlobalIx OBJECT-TYPE
   SYNTAX      GlobalIndex
   MAX-ACCESS  not-accessible
   STATUS      current
   DESCRIPTION
      "The value of the tlsCntTreeGlobalIndex of the MANAGED OBJECT."
   ::= {pr1645v2EthPortSwIInOctetsEntry 10}

pr1645v2EthPortSwIInOctetsValue OBJECT-TYPE
   SYNTAX      Counter64
   MAX-ACCESS  read-only
   STATUS      current
   DESCRIPTION
      "Path: swPort.performance.ifInOctets

       64 bit unsigned wrappable counter."
   ::= {pr1645v2EthPortSwIInOctetsEntry 2147483648}


pr1645v2EthPortSwIInUcast OBJECT IDENTIFIER ::= {pr1645v2EthPortSwI 110}

pr1645v2EthPortSwIInUcastTable OBJECT-TYPE
   SYNTAX      SEQUENCE OF Pr1645v2EthPortSwIInUcastEntry
   MAX-ACCESS  not-accessible
   STATUS      current
   DESCRIPTION
      "ifInUcastPkts"
   ::= {pr1645v2EthPortSwIInUcast 1}

pr1645v2EthPortSwIInUcastEntry OBJECT-TYPE
   SYNTAX      Pr1645v2EthPortSwIInUcastEntry
   MAX-ACCESS  not-accessible
   STATUS      current
   DESCRIPTION
      ""
   INDEX      { pr1645v2EthPortSwIInUcastGlobalIx }
   ::= {pr1645v2EthPortSwIInUcastTable 1}

Pr1645v2EthPortSwIInUcastEntry ::=
   SEQUENCE
      {
      pr1645v2EthPortSwIInUcastGlobalIx
         GlobalIndex,
      pr1645v2EthPortSwIInUcastValue
         Counter64
      }

pr1645v2EthPortSwIInUcastGlobalIx OBJECT-TYPE
   SYNTAX      GlobalIndex
   MAX-ACCESS  not-accessible
   STATUS      current
   DESCRIPTION
      "The value of the tlsCntTreeGlobalIndex of the MANAGED OBJECT."
   ::= {pr1645v2EthPortSwIInUcastEntry 10}

pr1645v2EthPortSwIInUcastValue OBJECT-TYPE
   SYNTAX      Counter64
   MAX-ACCESS  read-only
   STATUS      current
   DESCRIPTION
      "Path: swPort.performance.ifInUcastPkts

       64 bit unsigned wrappable counter."
   ::= {pr1645v2EthPortSwIInUcastEntry 2147483648}


pr1645v2EthPortSwIInNUcastPkts OBJECT IDENTIFIER ::= {pr1645v2EthPortSwI 111}

pr1645v2EthPortSwIInNUcastPktsTable OBJECT-TYPE
   SYNTAX      SEQUENCE OF Pr1645v2EthPortSwIInNUcastPktsEntry
   MAX-ACCESS  not-accessible
   STATUS      current
   DESCRIPTION
      "ifInNUcastPkts"
   ::= {pr1645v2EthPortSwIInNUcastPkts 1}

pr1645v2EthPortSwIInNUcastPktsEntry OBJECT-TYPE
   SYNTAX      Pr1645v2EthPortSwIInNUcastPktsEntry
   MAX-ACCESS  not-accessible
   STATUS      current
   DESCRIPTION
      ""
   INDEX      { pr1645v2EthPortSwIInNUcastPktsGlobalIx }
   ::= {pr1645v2EthPortSwIInNUcastPktsTable 1}

Pr1645v2EthPortSwIInNUcastPktsEntry ::=
   SEQUENCE
      {
      pr1645v2EthPortSwIInNUcastPktsGlobalIx
         GlobalIndex,
      pr1645v2EthPortSwIInNUcastPktsValue
         Counter64
      }

pr1645v2EthPortSwIInNUcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIInNUcastPktsEntry 10}

pr1645v2EthPortSwIInNUcastPktsValue OBJECT-TYPE
   SYNTAX      Counter64
   MAX-ACCESS  read-only
   STATUS      current
   DESCRIPTION
      "Path: swPort.performance.ifInNUcastPkts

       64 bit unsigned wrappable counter."
   ::= {pr1645v2EthPortSwIInNUcastPktsEntry 2147483648}


pr1645v2EthPortSwIInBcastPkts OBJECT IDENTIFIER ::= {pr1645v2EthPortSwI 211}

pr1645v2EthPortSwIInBcastPktsTable OBJECT-TYPE
   SYNTAX      SEQUENCE OF Pr1645v2EthPortSwIInBcastPktsEntry
   MAX-ACCESS  not-accessible
   STATUS      current
   DESCRIPTION
      "ifInBcastPkts"
   ::= {pr1645v2EthPortSwIInBcastPkts 1}

pr1645v2EthPortSwIInBcastPktsEntry OBJECT-TYPE
   SYNTAX      Pr1645v2EthPortSwIInBcastPktsEntry
   MAX-ACCESS  not-accessible
   STATUS      current
   DESCRIPTION
      ""
   INDEX      { pr1645v2EthPortSwIInBcastPktsGlobalIx }
   ::= {pr1645v2EthPortSwIInBcastPktsTable 1}

Pr1645v2EthPortSwIInBcastPktsEntry ::=
   SEQUENCE
      {
      pr1645v2EthPortSwIInBcastPktsGlobalIx
         GlobalIndex,
      pr1645v2EthPortSwIInBcastPktsValue
         Counter64
      }

pr1645v2EthPortSwIInBcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIInBcastPktsEntry 10}

pr1645v2EthPortSwIInBcastPktsValue OBJECT-TYPE
   SYNTAX      Counter64
   MAX-ACCESS  read-only
   STATUS      current
   DESCRIPTION
      "Path: swPort.performance.ifInBcastPkts

       64 bit unsigned wrappable counter."
   ::= {pr1645v2EthPortSwIInBcastPktsEntry 2147483648}


pr1645v2EthPortSwIInMcastPkts OBJECT IDENTIFIER ::= {pr1645v2EthPortSwI 221}

pr1645v2EthPortSwIInMcastPktsTable OBJECT-TYPE
   SYNTAX      SEQUENCE OF Pr1645v2EthPortSwIInMcastPktsEntry
   MAX-ACCESS  not-accessible
   STATUS      current
   DESCRIPTION
      "ifInNUcastPkts"
   ::= {pr1645v2EthPortSwIInMcastPkts 1}

pr1645v2EthPortSwIInMcastPktsEntry OBJECT-TYPE
   SYNTAX      Pr1645v2EthPortSwIInMcastPktsEntry
   MAX-ACCESS  not-accessible
   STATUS      current
   DESCRIPTION
      ""
   INDEX      { pr1645v2EthPortSwIInMcastPktsGlobalIx }
   ::= {pr1645v2EthPortSwIInMcastPktsTable 1}

Pr1645v2EthPortSwIInMcastPktsEntry ::=
   SEQUENCE
      {
      pr1645v2EthPortSwIInMcastPktsGlobalIx
         GlobalIndex,
      pr1645v2EthPortSwIInMcastPktsValue
         Counter64
      }

pr1645v2EthPortSwIInMcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIInMcastPktsEntry 10}

pr1645v2EthPortSwIInMcastPktsValue OBJECT-TYPE
   SYNTAX      Counter64
   MAX-ACCESS  read-only
   STATUS      current
   DESCRIPTION
      "Path: swPort.performance.ifInMcastPkts

       64 bit unsigned wrappable counter."
   ::= {pr1645v2EthPortSwIInMcastPktsEntry 2147483648}


pr1645v2EthPortSwIInDiscards OBJECT IDENTIFIER ::= {pr1645v2EthPortSwI 112}

pr1645v2EthPortSwIInDiscardsTable OBJECT-TYPE
   SYNTAX      SEQUENCE OF Pr1645v2EthPortSwIInDiscardsEntry
   MAX-ACCESS  not-accessible
   STATUS      current
   DESCRIPTION
      "ifInDiscards"
   ::= {pr1645v2EthPortSwIInDiscards 1}

pr1645v2EthPortSwIInDiscardsEntry OBJECT-TYPE
   SYNTAX      Pr1645v2EthPortSwIInDiscardsEntry
   MAX-ACCESS  not-accessible
   STATUS      current
   DESCRIPTION
      ""
   INDEX      { pr1645v2EthPortSwIInDiscardsGlobalIx }
   ::= {pr1645v2EthPortSwIInDiscardsTable 1}

Pr1645v2EthPortSwIInDiscardsEntry ::=
   SEQUENCE
      {
      pr1645v2EthPortSwIInDiscardsGlobalIx
         GlobalIndex,
      pr1645v2EthPortSwIInDiscardsValue
         Counter64
      }

pr1645v2EthPortSwIInDiscardsGlobalIx OBJECT-TYPE
   SYNTAX      GlobalIndex
   MAX-ACCESS  not-accessible
   STATUS      current
   DESCRIPTION
      "The value of the tlsCntTreeGlobalIndex of the MANAGED OBJECT."
   ::= {pr1645v2EthPortSwIInDiscardsEntry 10}

pr1645v2EthPortSwIInDiscardsValue OBJECT-TYPE
   SYNTAX      Counter64
   MAX-ACCESS  read-only
   STATUS      current
   DESCRIPTION
      "Path: swPort.performance.ifInDiscards

       64 bit unsigned wrappable counter."
   ::= {pr1645v2EthPortSwIInDiscardsEntry 2147483648}


pr1645v2EthPortSwIInErrors OBJECT IDENTIFIER ::= {pr1645v2EthPortSwI 113}

pr1645v2EthPortSwIInErrorsTable OBJECT-TYPE
   SYNTAX      SEQUENCE OF Pr1645v2EthPortSwIInErrorsEntry
   MAX-ACCESS  not-accessible
   STATUS      current
   DESCRIPTION
      "ifInErrors"
   ::= {pr1645v2EthPortSwIInErrors 1}

pr1645v2EthPortSwIInErrorsEntry OBJECT-TYPE
   SYNTAX      Pr1645v2EthPortSwIInErrorsEntry
   MAX-ACCESS  not-accessible
   STATUS      current
   DESCRIPTION
      ""
   INDEX      { pr1645v2EthPortSwIInErrorsGlobalIx }
   ::= {pr1645v2EthPortSwIInErrorsTable 1}

Pr1645v2EthPortSwIInErrorsEntry ::=
   SEQUENCE
      {
      pr1645v2EthPortSwIInErrorsGlobalIx
         GlobalIndex,
      pr1645v2EthPortSwIInErrorsValue
         Counter64
      }

pr1645v2EthPortSwIInErrorsGlobalIx OBJECT-TYPE
   SYNTAX      GlobalIndex
   MAX-ACCESS  not-accessible
   STATUS      current
   DESCRIPTION
      "The value of the tlsCntTreeGlobalIndex of the MANAGED OBJECT."
   ::= {pr1645v2EthPortSwIInErrorsEntry 10}

pr1645v2EthPortSwIInErrorsValue OBJECT-TYPE
   SYNTAX      Counter64
   MAX-ACCESS  read-only
   STATUS      current
   DESCRIPTION
      "Path: swPort.performance.ifInErrors

       64 bit unsigned wrappable counter."
   ::= {pr1645v2EthPortSwIInErrorsEntry 2147483648}


pr1645v2EthPortSwIInUnknownProtos OBJECT IDENTIFIER ::= {pr1645v2EthPortSwI 114}

pr1645v2EthPortSwIInUnknownProtosTable OBJECT-TYPE
   SYNTAX      SEQUENCE OF Pr1645v2EthPortSwIInUnknownProtosEntry
   MAX-ACCESS  not-accessible
   STATUS      current
   DESCRIPTION
      "ifInUnknownprotos"
   ::= {pr1645v2EthPortSwIInUnknownProtos 1}

pr1645v2EthPortSwIInUnknownProtosEntry OBJECT-TYPE
   SYNTAX      Pr1645v2EthPortSwIInUnknownProtosEntry
   MAX-ACCESS  not-accessible
   STATUS      current
   DESCRIPTION
      ""
   INDEX      { pr1645v2EthPortSwIInUnknownProtosGlobalIx }
   ::= {pr1645v2EthPortSwIInUnknownProtosTable 1}

Pr1645v2EthPortSwIInUnknownProtosEntry ::=
   SEQUENCE
      {
      pr1645v2EthPortSwIInUnknownProtosGlobalIx
         GlobalIndex,
      pr1645v2EthPortSwIInUnknownProtosValue
         Counter64
      }

pr1645v2EthPortSwIInUnknownProtosGlobalIx OBJECT-TYPE
   SYNTAX      GlobalIndex
   MAX-ACCESS  not-accessible
   STATUS      current
   DESCRIPTION
      "The value of the tlsCntTreeGlobalIndex of the MANAGED OBJECT."
   ::= {pr1645v2EthPortSwIInUnknownProtosEntry 10}

pr1645v2EthPortSwIInUnknownProtosValue OBJECT-TYPE
   SYNTAX      Counter64
   MAX-ACCESS  read-only
   STATUS      current
   DESCRIPTION
      "Path: swPort.performance.ifInUnknownProtos

       64 bit unsigned wrappable counter."
   ::= {pr1645v2EthPortSwIInUnknownProtosEntry 2147483648}


pr1645v2EthPortSwIInDropEx OBJECT IDENTIFIER ::= {pr1645v2EthPortSwI 130}

pr1645v2EthPortSwIInDropExTable OBJECT-TYPE
   SYNTAX      SEQUENCE OF Pr1645v2EthPortSwIInDropExEntry
   MAX-ACCESS  not-accessible
   STATUS      current
   DESCRIPTION
      "ifInDiscards"
   ::= {pr1645v2EthPortSwIInDropEx 1}

pr1645v2EthPortSwIInDropExEntry OBJECT-TYPE
   SYNTAX      Pr1645v2EthPortSwIInDropExEntry
   MAX-ACCESS  not-accessible
   STATUS      current
   DESCRIPTION
      ""
   INDEX      { pr1645v2EthPortSwIInDropExGlobalIx }
   ::= {pr1645v2EthPortSwIInDropExTable 1}

Pr1645v2EthPortSwIInDropExEntry ::=
   SEQUENCE
      {
      pr1645v2EthPortSwIInDropExGlobalIx
         GlobalIndex,
      pr1645v2EthPortSwIInDropExValue
         Counter64
      }

pr1645v2EthPortSwIInDropExGlobalIx OBJECT-TYPE
   SYNTAX      GlobalIndex
   MAX-ACCESS  not-accessible
   STATUS      current
   DESCRIPTION
      "The value of the tlsCntTreeGlobalIndex of the MANAGED OBJECT."
   ::= {pr1645v2EthPortSwIInDropExEntry 10}

pr1645v2EthPortSwIInDropExValue OBJECT-TYPE
   SYNTAX      Counter64
   MAX-ACCESS  read-only
   STATUS      current
   DESCRIPTION
      "Path: swPort.performance.ifInDropLevelExceeded

       64 bit unsigned wrappable counter."
   ::= {pr1645v2EthPortSwIInDropExEntry 2147483648}


pr1645v2EthPortSwIInDropNoMac OBJECT IDENTIFIER ::= {pr1645v2EthPortSwI 133}

pr1645v2EthPortSwIInDropNoMacTable OBJECT-TYPE
   SYNTAX      SEQUENCE OF Pr1645v2EthPortSwIInDropNoMacEntry
   MAX-ACCESS  not-accessible
   STATUS      current
   DESCRIPTION
      "ifInDiscards"
   ::= {pr1645v2EthPortSwIInDropNoMac 1}

pr1645v2EthPortSwIInDropNoMacEntry OBJECT-TYPE
   SYNTAX      Pr1645v2EthPortSwIInDropNoMacEntry
   MAX-ACCESS  not-accessible
   STATUS      current
   DESCRIPTION
      ""
   INDEX      { pr1645v2EthPortSwIInDropNoMacGlobalIx }
   ::= {pr1645v2EthPortSwIInDropNoMacTable 1}

Pr1645v2EthPortSwIInDropNoMacEntry ::=
   SEQUENCE
      {
      pr1645v2EthPortSwIInDropNoMacGlobalIx
         GlobalIndex,
      pr1645v2EthPortSwIInDropNoMacValue
         Counter64
      }

pr1645v2EthPortSwIInDropNoMacGlobalIx OBJECT-TYPE
   SYNTAX      GlobalIndex
   MAX-ACCESS  not-accessible
   STATUS      current
   DESCRIPTION
      "The value of the tlsCntTreeGlobalIndex of the MANAGED OBJECT."
   ::= {pr1645v2EthPortSwIInDropNoMacEntry 10}

pr1645v2EthPortSwIInDropNoMacValue OBJECT-TYPE
   SYNTAX      Counter64
   MAX-ACCESS  read-only
   STATUS      current
   DESCRIPTION
      "Path: swPort.performance.ifInDiscardsNoMacFit

       64 bit unsigned wrappable counter."
   ::= {pr1645v2EthPortSwIInDropNoMacEntry 2147483648}


pr1645v2EthPortSwIInDropNUCast OBJECT IDENTIFIER ::= {pr1645v2EthPortSwI 136}

pr1645v2EthPortSwIInDropNUCastTable OBJECT-TYPE
   SYNTAX      SEQUENCE OF Pr1645v2EthPortSwIInDropNUCastEntry
   MAX-ACCESS  not-accessible
   STATUS      current
   DESCRIPTION
      "ifInDiscards"
   ::= {pr1645v2EthPortSwIInDropNUCast 1}

pr1645v2EthPortSwIInDropNUCastEntry OBJECT-TYPE
   SYNTAX      Pr1645v2EthPortSwIInDropNUCastEntry
   MAX-ACCESS  not-accessible
   STATUS      current
   DESCRIPTION
      ""
   INDEX      { pr1645v2EthPortSwIInDropNUCastGlobalIx }
   ::= {pr1645v2EthPortSwIInDropNUCastTable 1}

Pr1645v2EthPortSwIInDropNUCastEntry ::=
   SEQUENCE
      {
      pr1645v2EthPortSwIInDropNUCastGlobalIx
         GlobalIndex,
      pr1645v2EthPortSwIInDropNUCastValue
         Counter64
      }

pr1645v2EthPortSwIInDropNUCastGlobalIx OBJECT-TYPE
   SYNTAX      GlobalIndex
   MAX-ACCESS  not-accessible
   STATUS      current
   DESCRIPTION
      "The value of the tlsCntTreeGlobalIndex of the MANAGED OBJECT."
   ::= {pr1645v2EthPortSwIInDropNUCastEntry 10}

pr1645v2EthPortSwIInDropNUCastValue OBJECT-TYPE
   SYNTAX      Counter64
   MAX-ACCESS  read-only
   STATUS      current
   DESCRIPTION
      "Path: swPort.performance.ifInDiscardsNUCast

       64 bit unsigned wrappable counter."
   ::= {pr1645v2EthPortSwIInDropNUCastEntry 2147483648}


pr1645v2EthPortSwIInDropFilter OBJECT IDENTIFIER ::= {pr1645v2EthPortSwI 137}

pr1645v2EthPortSwIInDropFilterTable OBJECT-TYPE
   SYNTAX      SEQUENCE OF Pr1645v2EthPortSwIInDropFilterEntry
   MAX-ACCESS  not-accessible
   STATUS      current
   DESCRIPTION
      "ifInDiscards"
   ::= {pr1645v2EthPortSwIInDropFilter 1}

pr1645v2EthPortSwIInDropFilterEntry OBJECT-TYPE
   SYNTAX      Pr1645v2EthPortSwIInDropFilterEntry
   MAX-ACCESS  not-accessible
   STATUS      current
   DESCRIPTION
      ""
   INDEX      { pr1645v2EthPortSwIInDropFilterGlobalIx }
   ::= {pr1645v2EthPortSwIInDropFilterTable 1}

Pr1645v2EthPortSwIInDropFilterEntry ::=
   SEQUENCE
      {
      pr1645v2EthPortSwIInDropFilterGlobalIx
         GlobalIndex,
      pr1645v2EthPortSwIInDropFilterValue
         Counter64
      }

pr1645v2EthPortSwIInDropFilterGlobalIx OBJECT-TYPE
   SYNTAX      GlobalIndex
   MAX-ACCESS  not-accessible
   STATUS      current
   DESCRIPTION
      "The value of the tlsCntTreeGlobalIndex of the MANAGED OBJECT."
   ::= {pr1645v2EthPortSwIInDropFilterEntry 10}

pr1645v2EthPortSwIInDropFilterValue OBJECT-TYPE
   SYNTAX      Counter64
   MAX-ACCESS  read-only
   STATUS      current
   DESCRIPTION
      "Path: swPort.performance.ifInDiscardsFilter

       64 bit unsigned wrappable counter."
   ::= {pr1645v2EthPortSwIInDropFilterEntry 2147483648}


pr1645v2EthPortSwIInQueues OBJECT IDENTIFIER ::= {pr1645v2EthPortSwI 131}

pr1645v2EthPortSwIInQueuesSSCTable OBJECT-TYPE
   SYNTAX      SEQUENCE OF Pr1645v2EthPortSwIInQueuesEntry
   MAX-ACCESS  not-accessible
   STATUS      current
   DESCRIPTION
      "Queue Lengths"
   ::= {pr1645v2EthPortSwIInQueues 1}

pr1645v2EthPortSwIInQueuesEntry OBJECT-TYPE
   SYNTAX      Pr1645v2EthPortSwIInQueuesEntry
   MAX-ACCESS  not-accessible
   STATUS      current
   DESCRIPTION
      ""
   INDEX      { pr1645v2EthPortSwIInQueuesGlobalIx,
                pr1645v2EthPortSwIInQueuesTableIx }
   ::= {pr1645v2EthPortSwIInQueuesSSCTable 1}

Pr1645v2EthPortSwIInQueuesEntry ::=
   SEQUENCE
      {
      pr1645v2EthPortSwIInQueuesGlobalIx
         GlobalIndex,
      pr1645v2EthPortSwIInQueuesTableIx
         TableIndex,
      pr1645v2EthPortSwIInQueuesName
         INTEGER,
      pr1645v2EthPortSwIInQueuesLength
         Integer32,
      pr1645v2EthPortSwIInQueuesOctetLength
         Integer32,
      pr1645v2EthPortSwIInQueuesRedLength
         Integer32,
      pr1645v2EthPortSwIInQueuesPacketsTotal
         Counter64,
      pr1645v2EthPortSwIInQueuesPacketsDirectTx
         Counter64,
      pr1645v2EthPortSwIInQueuesPacketsQueued
         Counter64,
      pr1645v2EthPortSwIInQueuesPacketsDropped
         Counter64,
      pr1645v2EthPortSwIInQueuesPacketsRedDropped
         Counter64,
      pr1645v2EthPortSwIInQueuesPacketsCirTx
         Counter64,
      pr1645v2EthPortSwIInQueuesPacketsEirTx
         Counter64,
      pr1645v2EthPortSwIInQueuesPacketsViolateTx
         Counter64,
      pr1645v2EthPortSwIInQueuesOctetsTotal
         Counter64,
      pr1645v2EthPortSwIInQueuesOctetsDirectTx
         Counter64,
      pr1645v2EthPortSwIInQueuesOctetsQueued
         Counter64,
      pr1645v2EthPortSwIInQueuesOctetsDropped
         Counter64,
      pr1645v2EthPortSwIInQueuesOctetsRedDropped
         Counter64,
      pr1645v2EthPortSwIInQueuesOctetsCirTx
         Counter64,
      pr1645v2EthPortSwIInQueuesOctetsEirTx
         Counter64,
      pr1645v2EthPortSwIInQueuesOctetsViolateTx
         Counter64,
      pr1645v2EthPortSwIInQueuesOctetsBandwidth15sec
         Integer32,
      pr1645v2EthPortSwIInQueuesOctetsBandwidth30sec
         Integer32,
      pr1645v2EthPortSwIInQueuesOctetsBandwidth1min
         Integer32,
      pr1645v2EthPortSwIInQueuesOctetsBandwidth2min
         Integer32,
      pr1645v2EthPortSwIInQueuesOctetsBandwidth5min
         Integer32
      }

pr1645v2EthPortSwIInQueuesGlobalIx OBJECT-TYPE
   SYNTAX      GlobalIndex
   MAX-ACCESS  not-accessible
   STATUS      current
   DESCRIPTION
      "The value of the tlsCntTreeGlobalIndex of the MANAGED OBJECT."
   ::= {pr1645v2EthPortSwIInQueuesEntry 10}

pr1645v2EthPortSwIInQueuesTableIx OBJECT-TYPE
   SYNTAX      TableIndex
   MAX-ACCESS  not-accessible
   STATUS      current
   DESCRIPTION
      ""
   ::= {pr1645v2EthPortSwIInQueuesEntry 11}

pr1645v2EthPortSwIInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPortSwIInQueuesEntry 16777216}

pr1645v2EthPortSwIInQueuesLength OBJECT-TYPE
   SYNTAX      Integer32
   MAX-ACCESS  read-only
   STATUS      current
   DESCRIPTION
      "Path: swPort.performance.ifInPriorityQueues.length"
   ::= {pr1645v2EthPortSwIInQueuesEntry 33554432}

pr1645v2EthPortSwIInQueuesOctetLength OBJECT-TYPE
   SYNTAX      Integer32
   MAX-ACCESS  read-only
   STATUS      current
   DESCRIPTION
      "Path: swPort.performance.ifInPriorityQueues.octetLength"
   ::= {pr1645v2EthPortSwIInQueuesEntry 150994944}

pr1645v2EthPortSwIInQueuesRedLength OBJECT-TYPE
   SYNTAX      Integer32
   MAX-ACCESS  read-only
   STATUS      current
   DESCRIPTION
      "Path: swPort.performance.ifInPriorityQueues.redLength"
   ::= {pr1645v2EthPortSwIInQueuesEntry 134217728}

pr1645v2EthPortSwIInQueuesPacketsTotal OBJECT-TYPE
   SYNTAX      Counter64
   MAX-ACCESS  read-only
   STATUS      current
   DESCRIPTION
      "Path: swPort.performance.ifInPriorityQueues.packets.total

       64 bit unsigned wrappable counter."
   ::= {pr1645v2EthPortSwIInQueuesEntry 50790400}

pr1645v2EthPortSwIInQueuesPacketsDirectTx OBJECT-TYPE
   SYNTAX      Counter64
   MAX-ACCESS  read-only
   STATUS      current
   DESCRIPTION
      "Path: swPort.performance.ifInPriorityQueues.packets.directTx

       64 bit unsigned wrappable counter."
   ::= {pr1645v2EthPortSwIInQueuesEntry 50397184}

pr1645v2EthPortSwIInQueuesPacketsQueued OBJECT-TYPE
   SYNTAX      Counter64
   MAX-ACCESS  read-only
   STATUS      current
   DESCRIPTION
      "Path: swPort.performance.ifInPriorityQueues.packets.queued

       64 bit unsigned wrappable counter."
   ::= {pr1645v2EthPortSwIInQueuesEntry 50462720}

pr1645v2EthPortSwIInQueuesPacketsDropped OBJECT-TYPE
   SYNTAX      Counter64
   MAX-ACCESS  read-only
   STATUS      current
   DESCRIPTION
      "Path: swPort.performance.ifInPriorityQueues.packets.dropped

       64 bit unsigned wrappable counter."
   ::= {pr1645v2EthPortSwIInQueuesEntry 50528256}

pr1645v2EthPortSwIInQueuesPacketsRedDropped OBJECT-TYPE
   SYNTAX      Counter64
   MAX-ACCESS  read-only
   STATUS      current
   DESCRIPTION
      "Path: swPort.performance.ifInPriorityQueues.packets.redDropped

       64 bit unsigned wrappable counter."
   ::= {pr1645v2EthPortSwIInQueuesEntry 50724864}

pr1645v2EthPortSwIInQueuesPacketsCirTx OBJECT-TYPE
   SYNTAX      Counter64
   MAX-ACCESS  read-only
   STATUS      current
   DESCRIPTION
      "Path: swPort.performance.ifInPriorityQueues.packets.cirTx

       64 bit unsigned wrappable counter."
   ::= {pr1645v2EthPortSwIInQueuesEntry 50593792}

pr1645v2EthPortSwIInQueuesPacketsEirTx OBJECT-TYPE
   SYNTAX      Counter64
   MAX-ACCESS  read-only
   STATUS      current
   DESCRIPTION
      "Path: swPort.performance.ifInPriorityQueues.packets.eirTx

       64 bit unsigned wrappable counter."
   ::= {pr1645v2EthPortSwIInQueuesEntry 50659328}

pr1645v2EthPortSwIInQueuesPacketsViolateTx OBJECT-TYPE
   SYNTAX      Counter64
   MAX-ACCESS  read-only
   STATUS      current
   DESCRIPTION
      "Path: swPort.performance.ifInPriorityQueues.packets.violateTx

       64 bit unsigned wrappable counter."
   ::= {pr1645v2EthPortSwIInQueuesEntry 50855936}

pr1645v2EthPortSwIInQueuesOctetsTotal OBJECT-TYPE
   SYNTAX      Counter64
   MAX-ACCESS  read-only
   STATUS      current
   DESCRIPTION
      "Path: swPort.performance.ifInPriorityQueues.octets.total

       64 bit unsigned wrappable counter."
   ::= {pr1645v2EthPortSwIInQueuesEntry 67567616}

pr1645v2EthPortSwIInQueuesOctetsDirectTx OBJECT-TYPE
   SYNTAX      Counter64
   MAX-ACCESS  read-only
   STATUS      current
   DESCRIPTION
      "Path: swPort.performance.ifInPriorityQueues.octets.directTx

       64 bit unsigned wrappable counter."
   ::= {pr1645v2EthPortSwIInQueuesEntry 67174400}

pr1645v2EthPortSwIInQueuesOctetsQueued OBJECT-TYPE
   SYNTAX      Counter64
   MAX-ACCESS  read-only
   STATUS      current
   DESCRIPTION
      "Path: swPort.performance.ifInPriorityQueues.octets.queued

       64 bit unsigned wrappable counter."
   ::= {pr1645v2EthPortSwIInQueuesEntry 67239936}

pr1645v2EthPortSwIInQueuesOctetsDropped OBJECT-TYPE
   SYNTAX      Counter64
   MAX-ACCESS  read-only
   STATUS      current
   DESCRIPTION
      "Path: swPort.performance.ifInPriorityQueues.octets.dropped

       64 bit unsigned wrappable counter."
   ::= {pr1645v2EthPortSwIInQueuesEntry 67305472}

pr1645v2EthPortSwIInQueuesOctetsRedDropped OBJECT-TYPE
   SYNTAX      Counter64
   MAX-ACCESS  read-only
   STATUS      current
   DESCRIPTION
      "Path: swPort.performance.ifInPriorityQueues.octets.redDropped

       64 bit unsigned wrappable counter."
   ::= {pr1645v2EthPortSwIInQueuesEntry 67502080}

pr1645v2EthPortSwIInQueuesOctetsCirTx OBJECT-TYPE
   SYNTAX      Counter64
   MAX-ACCESS  read-only
   STATUS      current
   DESCRIPTION
      "Path: swPort.performance.ifInPriorityQueues.octets.cirTx

       64 bit unsigned wrappable counter."
   ::= {pr1645v2EthPortSwIInQueuesEntry 67371008}

pr1645v2EthPortSwIInQueuesOctetsEirTx OBJECT-TYPE
   SYNTAX      Counter64
   MAX-ACCESS  read-only
   STATUS      current
   DESCRIPTION
      "Path: swPort.performance.ifInPriorityQueues.octets.eirTx

       64 bit unsigned wrappable counter."
   ::= {pr1645v2EthPortSwIInQueuesEntry 67436544}

pr1645v2EthPortSwIInQueuesOctetsViolateTx OBJECT-TYPE
   SYNTAX      Counter64
   MAX-ACCESS  read-only
   STATUS      current
   DESCRIPTION
      "Path: swPort.performance.ifInPriorityQueues.octets.violateTx

       64 bit unsigned wrappable counter."
   ::= {pr1645v2EthPortSwIInQueuesEntry 67633152}

pr1645v2EthPortSwIInQueuesOctetsBandwidth15sec OBJECT-TYPE
   SYNTAX      Integer32
   MAX-ACCESS  read-only
   STATUS      current
   DESCRIPTION
      "Path: swPort.performance.ifInPriorityQueues.octets.bandwidth.15sec

       unit name = bps
       formula = 8 * ; 8 /"
   ::= {pr1645v2EthPortSwIInQueuesEntry 70386944}

pr1645v2EthPortSwIInQueuesOctetsBandwidth30sec OBJECT-TYPE
   SYNTAX      Integer32
   MAX-ACCESS  read-only
   STATUS      current
   DESCRIPTION
      "Path: swPort.performance.ifInPriorityQueues.octets.bandwidth.30sec

       unit name = bps
       formula = 8 * ; 8 /"
   ::= {pr1645v2EthPortSwIInQueuesEntry 70388224}

pr1645v2EthPortSwIInQueuesOctetsBandwidth1min OBJECT-TYPE
   SYNTAX      Integer32
   MAX-ACCESS  read-only
   STATUS      current
   DESCRIPTION
      "Path: swPort.performance.ifInPriorityQueues.octets.bandwidth.1min

       unit name = bps
       formula = 8 * ; 8 /"
   ::= {pr1645v2EthPortSwIInQueuesEntry 70390784}

pr1645v2EthPortSwIInQueuesOctetsBandwidth2min OBJECT-TYPE
   SYNTAX      Integer32
   MAX-ACCESS  read-only
   STATUS      current
   DESCRIPTION
      "Path: swPort.performance.ifInPriorityQueues.octets.bandwidth.2min

       unit name = bps
       formula = 8 * ; 8 /"
   ::= {pr1645v2EthPortSwIInQueuesEntry 70395904}

pr1645v2EthPortSwIInQueuesOctetsBandwidth5min OBJECT-TYPE
   SYNTAX      Integer32
   MAX-ACCESS  read-only
   STATUS      current
   DESCRIPTION
      "Path: swPort.performance.ifInPriorityQueues.octets.bandwidth.5min

       unit name = bps
       formula = 8 * ; 8 /"
   ::= {pr1645v2EthPortSwIInQueuesEntry 70411264}

pr1645v2EthPortSwIInQueuesH2Performance OBJECT-TYPE
   SYNTAX      SEQUENCE OF Pr1645v2EthPortSwIInQueuesH2PerformanceEntry
   MAX-ACCESS  not-accessible
   STATUS      current
   DESCRIPTION
      ""
   ::= {pr1645v2EthPortSwIInQueues 83886080}

pr1645v2EthPortSwIInQueuesH2PerformanceEntry OBJECT-TYPE
   SYNTAX      Pr1645v2EthPortSwIInQueuesH2PerformanceEntry
   MAX-ACCESS  not-accessible
   STATUS      current
   DESCRIPTION
      ""
   INDEX      { pr1645v2EthPortSwIInQueuesH2PerformanceGlobalIx,
                pr1645v2EthPortSwIInQueuesTableIx,
                pr1645v2EthPortSwIInQueuesH2PerformanceTableIx }
   ::= {pr1645v2EthPortSwIInQueuesH2Performance 1}

Pr1645v2EthPortSwIInQueuesH2PerformanceEntry ::=
   SEQUENCE
      {
      pr1645v2EthPortSwIInQueuesH2PerformanceGlobalIx
         GlobalIndex,
      pr1645v2EthPortSwIInQueuesH2PerformanceTableIx
         TableIndex,
      pr1645v2EthPortSwIInQueuesH2PerformanceSysUpTime
         TimeTicks,
      pr1645v2EthPortSwIInQueuesH2PerformanceTotPkts
         Counter64,
      pr1645v2EthPortSwIInQueuesH2PerformanceDirTxPkts
         Counter64,
      pr1645v2EthPortSwIInQueuesH2PerformanceQdPkts
         Counter64,
      pr1645v2EthPortSwIInQueuesH2PerformanceDropPkts
         Counter64,
      pr1645v2EthPortSwIInQueuesH2PerformanceRDropPkts
         Counter64,
      pr1645v2EthPortSwIInQueuesH2PerformanceCirTxPkts
         Counter64,
      pr1645v2EthPortSwIInQueuesH2PerformanceEirTxPkts
         Counter64,
      pr1645v2EthPortSwIInQueuesH2PerformanceViolTxPkts
         Counter64,
      pr1645v2EthPortSwIInQueuesH2PerformanceTotOcts
         Counter64,
      pr1645v2EthPortSwIInQueuesH2PerformanceDirTxOcts
         Counter64,
      pr1645v2EthPortSwIInQueuesH2PerformanceQdOcts
         Counter64,
      pr1645v2EthPortSwIInQueuesH2PerformanceDropOcts
         Counter64,
      pr1645v2EthPortSwIInQueuesH2PerformanceRDropOcts
         Counter64,
      pr1645v2EthPortSwIInQueuesH2PerformanceCirTxOcts
         Counter64,
      pr1645v2EthPortSwIInQueuesH2PerformanceEirTxOcts
         Counter64,
      pr1645v2EthPortSwIInQueuesH2PerformanceViolTxOcts
         Counter64,
      pr1645v2EthPortSwIInQueuesH2PerformanceBandwidth
         Integer32
      }

pr1645v2EthPortSwIInQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIInQueuesH2PerformanceEntry 10}

pr1645v2EthPortSwIInQueuesH2PerformanceTableIx OBJECT-TYPE
   SYNTAX      TableIndex
   MAX-ACCESS  not-accessible
   STATUS      current
   DESCRIPTION
      ""
   ::= {pr1645v2EthPortSwIInQueuesH2PerformanceEntry 11}

pr1645v2EthPortSwIInQueuesH2PerformanceSysUpTime OBJECT-TYPE
   SYNTAX      TimeTicks
   MAX-ACCESS  read-only
   STATUS      current
   DESCRIPTION
      "Path: swPort.performance.ifInPriorityQueues.h2Performance.sysUpTime

       Time in centi-second."
   ::= {pr1645v2EthPortSwIInQueuesH2PerformanceEntry 16777216}

pr1645v2EthPortSwIInQueuesH2PerformanceTotPkts OBJECT-TYPE
   SYNTAX      Counter64
   MAX-ACCESS  read-only
   STATUS      current
   DESCRIPTION
      "Path: swPort.performance.ifInPriorityQueues.h2Performance.totalPkts

       64 bit unsigned wrappable counter."
   ::= {pr1645v2EthPortSwIInQueuesH2PerformanceEntry 234881024}

pr1645v2EthPortSwIInQueuesH2PerformanceDirTxPkts OBJECT-TYPE
   SYNTAX      Counter64
   MAX-ACCESS  read-only
   STATUS      current
   DESCRIPTION
      "Path: swPort.performance.ifInPriorityQueues.h2Performance.directTxPkts

       64 bit unsigned wrappable counter."
   ::= {pr1645v2EthPortSwIInQueuesH2PerformanceEntry 33554432}

pr1645v2EthPortSwIInQueuesH2PerformanceQdPkts OBJECT-TYPE
   SYNTAX      Counter64
   MAX-ACCESS  read-only
   STATUS      current
   DESCRIPTION
      "Path: swPort.performance.ifInPriorityQueues.h2Performance.queuedPkts

       64 bit unsigned wrappable counter."
   ::= {pr1645v2EthPortSwIInQueuesH2PerformanceEntry 50331648}

pr1645v2EthPortSwIInQueuesH2PerformanceDropPkts OBJECT-TYPE
   SYNTAX      Counter64
   MAX-ACCESS  read-only
   STATUS      current
   DESCRIPTION
      "Path: swPort.performance.ifInPriorityQueues.h2Performance.droppedPkts

       64 bit unsigned wrappable counter."
   ::= {pr1645v2EthPortSwIInQueuesH2PerformanceEntry 67108864}

pr1645v2EthPortSwIInQueuesH2PerformanceRDropPkts OBJECT-TYPE
   SYNTAX      Counter64
   MAX-ACCESS  read-only
   STATUS      current
   DESCRIPTION
      "Path: swPort.performance.ifInPriorityQueues.h2Performance.redDroppedPkts

       64 bit unsigned wrappable counter."
   ::= {pr1645v2EthPortSwIInQueuesH2PerformanceEntry 201326592}

pr1645v2EthPortSwIInQueuesH2PerformanceCirTxPkts OBJECT-TYPE
   SYNTAX      Counter64
   MAX-ACCESS  read-only
   STATUS      current
   DESCRIPTION
      "Path: swPort.performance.ifInPriorityQueues.h2Performance.cirTxPkts

       64 bit unsigned wrappable counter."
   ::= {pr1645v2EthPortSwIInQueuesH2PerformanceEntry 83886080}

pr1645v2EthPortSwIInQueuesH2PerformanceEirTxPkts OBJECT-TYPE
   SYNTAX      Counter64
   MAX-ACCESS  read-only
   STATUS      current
   DESCRIPTION
      "Path: swPort.performance.ifInPriorityQueues.h2Performance.eirTxPkts

       64 bit unsigned wrappable counter."
   ::= {pr1645v2EthPortSwIInQueuesH2PerformanceEntry 100663296}

pr1645v2EthPortSwIInQueuesH2PerformanceViolTxPkts OBJECT-TYPE
   SYNTAX      Counter64
   MAX-ACCESS  read-only
   STATUS      current
   DESCRIPTION
      "Path: swPort.performance.ifInPriorityQueues.h2Performance.violateTxPkts

       64 bit unsigned wrappable counter."
   ::= {pr1645v2EthPortSwIInQueuesH2PerformanceEntry 301989888}

pr1645v2EthPortSwIInQueuesH2PerformanceTotOcts OBJECT-TYPE
   SYNTAX      Counter64
   MAX-ACCESS  read-only
   STATUS      current
   DESCRIPTION
      "Path: swPort.performance.ifInPriorityQueues.h2Performance.totalOctets

       64 bit unsigned wrappable counter."
   ::= {pr1645v2EthPortSwIInQueuesH2PerformanceEntry 251658240}

pr1645v2EthPortSwIInQueuesH2PerformanceDirTxOcts OBJECT-TYPE
   SYNTAX      Counter64
   MAX-ACCESS  read-only
   STATUS      current
   DESCRIPTION
      "Path: swPort.performance.ifInPriorityQueues.h2Performance.directTxOctets

       64 bit unsigned wrappable counter."
   ::= {pr1645v2EthPortSwIInQueuesH2PerformanceEntry 117440512}

pr1645v2EthPortSwIInQueuesH2PerformanceQdOcts OBJECT-TYPE
   SYNTAX      Counter64
   MAX-ACCESS  read-only
   STATUS      current
   DESCRIPTION
      "Path: swPort.performance.ifInPriorityQueues.h2Performance.queuedOctets

       64 bit unsigned wrappable counter."
   ::= {pr1645v2EthPortSwIInQueuesH2PerformanceEntry 134217728}

pr1645v2EthPortSwIInQueuesH2PerformanceDropOcts OBJECT-TYPE
   SYNTAX      Counter64
   MAX-ACCESS  read-only
   STATUS      current
   DESCRIPTION
      "Path: swPort.performance.ifInPriorityQueues.h2Performance.droppedOctets

       64 bit unsigned wrappable counter."
   ::= {pr1645v2EthPortSwIInQueuesH2PerformanceEntry 150994944}

pr1645v2EthPortSwIInQueuesH2PerformanceRDropOcts OBJECT-TYPE
   SYNTAX      Counter64
   MAX-ACCESS  read-only
   STATUS      current
   DESCRIPTION
      "Path: swPort.performance.ifInPriorityQueues.h2Performance.redDroppedOctets

       64 bit unsigned wrappable counter."
   ::= {pr1645v2EthPortSwIInQueuesH2PerformanceEntry 218103808}

pr1645v2EthPortSwIInQueuesH2PerformanceCirTxOcts OBJECT-TYPE
   SYNTAX      Counter64
   MAX-ACCESS  read-only
   STATUS      current
   DESCRIPTION
      "Path: swPort.performance.ifInPriorityQueues.h2Performance.cirTxOctets

       64 bit unsigned wrappable counter."
   ::= {pr1645v2EthPortSwIInQueuesH2PerformanceEntry 167772160}

pr1645v2EthPortSwIInQueuesH2PerformanceEirTxOcts OBJECT-TYPE
   SYNTAX      Counter64
   MAX-ACCESS  read-only
   STATUS      current
   DESCRIPTION
      "Path: swPort.performance.ifInPriorityQueues.h2Performance.eirTxOctets

       64 bit unsigned wrappable counter."
   ::= {pr1645v2EthPortSwIInQueuesH2PerformanceEntry 184549376}

pr1645v2EthPortSwIInQueuesH2PerformanceViolTxOcts OBJECT-TYPE
   SYNTAX      Counter64
   MAX-ACCESS  read-only
   STATUS      current
   DESCRIPTION
      "Path: swPort.performance.ifInPriorityQueues.h2Performance.violateTxOctets

       64 bit unsigned wrappable counter."
   ::= {pr1645v2EthPortSwIInQueuesH2PerformanceEntry 318767104}

pr1645v2EthPortSwIInQueuesH2PerformanceBandwidth OBJECT-TYPE
   SYNTAX      Integer32
   MAX-ACCESS  read-only
   STATUS      current
   DESCRIPTION
      "Path: swPort.performance.ifInPriorityQueues.h2Performance.bandwidth

       unit name = bps
       formula = 8 * ; 8 /"
   ::= {pr1645v2EthPortSwIInQueuesH2PerformanceEntry 268435456}

pr1645v2EthPortSwIInQueuesH24Performance OBJECT-TYPE
   SYNTAX      SEQUENCE OF Pr1645v2EthPortSwIInQueuesH24PerformanceEntry
   MAX-ACCESS  not-accessible
   STATUS      current
   DESCRIPTION
      ""
   ::= {pr1645v2EthPortSwIInQueues 100663296}

pr1645v2EthPortSwIInQueuesH24PerformanceEntry OBJECT-TYPE
   SYNTAX      Pr1645v2EthPortSwIInQueuesH24PerformanceEntry
   MAX-ACCESS  not-accessible
   STATUS      current
   DESCRIPTION
      ""
   INDEX      { pr1645v2EthPortSwIInQueuesH24PerformanceGlobalIx,
                pr1645v2EthPortSwIInQueuesTableIx,
                pr1645v2EthPortSwIInQueuesH24PerformanceTableIx }
   ::= {pr1645v2EthPortSwIInQueuesH24Performance 1}

Pr1645v2EthPortSwIInQueuesH24PerformanceEntry ::=
   SEQUENCE
      {
      pr1645v2EthPortSwIInQueuesH24PerformanceGlobalIx
         GlobalIndex,
      pr1645v2EthPortSwIInQueuesH24PerformanceTableIx
         TableIndex,
      pr1645v2EthPortSwIInQueuesH24PerformanceSysUpTime
         TimeTicks,
      pr1645v2EthPortSwIInQueuesH24PerformanceTotPkts
         Counter64,
      pr1645v2EthPortSwIInQueuesH24PerformanceDirTxPkts
         Counter64,
      pr1645v2EthPortSwIInQueuesH24PerformanceQdPkts
         Counter64,
      pr1645v2EthPortSwIInQueuesH24PerformanceDropPkts
         Counter64,
      pr1645v2EthPortSwIInQueuesH24PerformanceRDropPkts
         Counter64,
      pr1645v2EthPortSwIInQueuesH24PerformanceCirTxPkts
         Counter64,
      pr1645v2EthPortSwIInQueuesH24PerformanceEirTxPkts
         Counter64,
      pr1645v2EthPortSwIInQueuesH24PerformanceViolTxPkts
         Counter64,
      pr1645v2EthPortSwIInQueuesH24PerformanceTotOcts
         Counter64,
      pr1645v2EthPortSwIInQueuesH24PerformanceDirTxOcts
         Counter64,
      pr1645v2EthPortSwIInQueuesH24PerformanceQdOcts
         Counter64,
      pr1645v2EthPortSwIInQueuesH24PerformanceDropOcts
         Counter64,
      pr1645v2EthPortSwIInQueuesH24PerformanceRDropOcts
         Counter64,
      pr1645v2EthPortSwIInQueuesH24PerformanceCirTxOcts
         Counter64,
      pr1645v2EthPortSwIInQueuesH24PerformanceEirTxOcts
         Counter64,
      pr1645v2EthPortSwIInQueuesH24PerformanceViolTxOcts
         Counter64,
      pr1645v2EthPortSwIInQueuesH24PerformanceBandwidth
         Integer32
      }

pr1645v2EthPortSwIInQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIInQueuesH24PerformanceEntry 10}

pr1645v2EthPortSwIInQueuesH24PerformanceTableIx OBJECT-TYPE
   SYNTAX      TableIndex
   MAX-ACCESS  not-accessible
   STATUS      current
   DESCRIPTION
      ""
   ::= {pr1645v2EthPortSwIInQueuesH24PerformanceEntry 11}

pr1645v2EthPortSwIInQueuesH24PerformanceSysUpTime OBJECT-TYPE
   SYNTAX      TimeTicks
   MAX-ACCESS  read-only
   STATUS      current
   DESCRIPTION
      "Path: swPort.performance.ifInPriorityQueues.h24Performance.sysUpTime

       Time in centi-second."
   ::= {pr1645v2EthPortSwIInQueuesH24PerformanceEntry 16777216}

pr1645v2EthPortSwIInQueuesH24PerformanceTotPkts OBJECT-TYPE
   SYNTAX      Counter64
   MAX-ACCESS  read-only
   STATUS      current
   DESCRIPTION
      "Path: swPort.performance.ifInPriorityQueues.h24Performance.totalPkts

       64 bit unsigned wrappable counter."
   ::= {pr1645v2EthPortSwIInQueuesH24PerformanceEntry 234881024}

pr1645v2EthPortSwIInQueuesH24PerformanceDirTxPkts OBJECT-TYPE
   SYNTAX      Counter64
   MAX-ACCESS  read-only
   STATUS      current
   DESCRIPTION
      "Path: swPort.performance.ifInPriorityQueues.h24Performance.directTxPkts

       64 bit unsigned wrappable counter."
   ::= {pr1645v2EthPortSwIInQueuesH24PerformanceEntry 33554432}

pr1645v2EthPortSwIInQueuesH24PerformanceQdPkts OBJECT-TYPE
   SYNTAX      Counter64
   MAX-ACCESS  read-only
   STATUS      current
   DESCRIPTION
      "Path: swPort.performance.ifInPriorityQueues.h24Performance.queuedPkts

       64 bit unsigned wrappable counter."
   ::= {pr1645v2EthPortSwIInQueuesH24PerformanceEntry 50331648}

pr1645v2EthPortSwIInQueuesH24PerformanceDropPkts OBJECT-TYPE
   SYNTAX      Counter64
   MAX-ACCESS  read-only
   STATUS      current
   DESCRIPTION
      "Path: swPort.performance.ifInPriorityQueues.h24Performance.droppedPkts

       64 bit unsigned wrappable counter."
   ::= {pr1645v2EthPortSwIInQueuesH24PerformanceEntry 67108864}

pr1645v2EthPortSwIInQueuesH24PerformanceRDropPkts OBJECT-TYPE
   SYNTAX      Counter64
   MAX-ACCESS  read-only
   STATUS      current
   DESCRIPTION
      "Path: swPort.performance.ifInPriorityQueues.h24Performance.redDroppedPkts

       64 bit unsigned wrappable counter."
   ::= {pr1645v2EthPortSwIInQueuesH24PerformanceEntry 201326592}

pr1645v2EthPortSwIInQueuesH24PerformanceCirTxPkts OBJECT-TYPE
   SYNTAX      Counter64
   MAX-ACCESS  read-only
   STATUS      current
   DESCRIPTION
      "Path: swPort.performance.ifInPriorityQueues.h24Performance.cirTxPkts

       64 bit unsigned wrappable counter."
   ::= {pr1645v2EthPortSwIInQueuesH24PerformanceEntry 83886080}

pr1645v2EthPortSwIInQueuesH24PerformanceEirTxPkts OBJECT-TYPE
   SYNTAX      Counter64
   MAX-ACCESS  read-only
   STATUS      current
   DESCRIPTION
      "Path: swPort.performance.ifInPriorityQueues.h24Performance.eirTxPkts

       64 bit unsigned wrappable counter."
   ::= {pr1645v2EthPortSwIInQueuesH24PerformanceEntry 100663296}

pr1645v2EthPortSwIInQueuesH24PerformanceViolTxPkts OBJECT-TYPE
   SYNTAX      Counter64
   MAX-ACCESS  read-only
   STATUS      current
   DESCRIPTION
      "Path: swPort.performance.ifInPriorityQueues.h24Performance.violateTxPkts

       64 bit unsigned wrappable counter."
   ::= {pr1645v2EthPortSwIInQueuesH24PerformanceEntry 301989888}

pr1645v2EthPortSwIInQueuesH24PerformanceTotOcts OBJECT-TYPE
   SYNTAX      Counter64
   MAX-ACCESS  read-only
   STATUS      current
   DESCRIPTION
      "Path: swPort.performance.ifInPriorityQueues.h24Performance.totalOctets

       64 bit unsigned wrappable counter."
   ::= {pr1645v2EthPortSwIInQueuesH24PerformanceEntry 251658240}

pr1645v2EthPortSwIInQueuesH24PerformanceDirTxOcts OBJECT-TYPE
   SYNTAX      Counter64
   MAX-ACCESS  read-only
   STATUS      current
   DESCRIPTION
      "Path: swPort.performance.ifInPriorityQueues.h24Performance.directTxOctets

       64 bit unsigned wrappable counter."
   ::= {pr1645v2EthPortSwIInQueuesH24PerformanceEntry 117440512}

pr1645v2EthPortSwIInQueuesH24PerformanceQdOcts OBJECT-TYPE
   SYNTAX      Counter64
   MAX-ACCESS  read-only
   STATUS      current
   DESCRIPTION
      "Path: swPort.performance.ifInPriorityQueues.h24Performance.queuedOctets

       64 bit unsigned wrappable counter."
   ::= {pr1645v2EthPortSwIInQueuesH24PerformanceEntry 134217728}

pr1645v2EthPortSwIInQueuesH24PerformanceDropOcts OBJECT-TYPE
   SYNTAX      Counter64
   MAX-ACCESS  read-only
   STATUS      current
   DESCRIPTION
      "Path: swPort.performance.ifInPriorityQueues.h24Performance.droppedOctets

       64 bit unsigned wrappable counter."
   ::= {pr1645v2EthPortSwIInQueuesH24PerformanceEntry 150994944}

pr1645v2EthPortSwIInQueuesH24PerformanceRDropOcts OBJECT-TYPE
   SYNTAX      Counter64
   MAX-ACCESS  read-only
   STATUS      current
   DESCRIPTION
      "Path: swPort.performance.ifInPriorityQueues.h24Performance.redDroppedOctets

       64 bit unsigned wrappable counter."
   ::= {pr1645v2EthPortSwIInQueuesH24PerformanceEntry 218103808}

pr1645v2EthPortSwIInQueuesH24PerformanceCirTxOcts OBJECT-TYPE
   SYNTAX      Counter64
   MAX-ACCESS  read-only
   STATUS      current
   DESCRIPTION
      "Path: swPort.performance.ifInPriorityQueues.h24Performance.cirTxOctets

       64 bit unsigned wrappable counter."
   ::= {pr1645v2EthPortSwIInQueuesH24PerformanceEntry 167772160}

pr1645v2EthPortSwIInQueuesH24PerformanceEirTxOcts OBJECT-TYPE
   SYNTAX      Counter64
   MAX-ACCESS  read-only
   STATUS      current
   DESCRIPTION
      "Path: swPort.performance.ifInPriorityQueues.h24Performance.eirTxOctets

       64 bit unsigned wrappable counter."
   ::= {pr1645v2EthPortSwIInQueuesH24PerformanceEntry 184549376}

pr1645v2EthPortSwIInQueuesH24PerformanceViolTxOcts OBJECT-TYPE
   SYNTAX      Counter64
   MAX-ACCESS  read-only
   STATUS      current
   DESCRIPTION
      "Path: swPort.performance.ifInPriorityQueues.h24Performance.violateTxOctets

       64 bit unsigned wrappable counter."
   ::= {pr1645v2EthPortSwIInQueuesH24PerformanceEntry 318767104}

pr1645v2EthPortSwIInQueuesH24PerformanceBandwidth OBJECT-TYPE
   SYNTAX      Integer32
   MAX-ACCESS  read-only
   STATUS      current
   DESCRIPTION
      "Path: swPort.performance.ifInPriorityQueues.h24Performance.bandwidth

       unit name = bps
       formula = 8 * ; 8 /"
   ::= {pr1645v2EthPortSwIInQueuesH24PerformanceEntry 268435456}

pr1645v2EthPortSwIInQueuesD7Performance OBJECT-TYPE
   SYNTAX      SEQUENCE OF Pr1645v2EthPortSwIInQueuesD7PerformanceEntry
   MAX-ACCESS  not-accessible
   STATUS      current
   DESCRIPTION
      ""
   ::= {pr1645v2EthPortSwIInQueues 117440512}

pr1645v2EthPortSwIInQueuesD7PerformanceEntry OBJECT-TYPE
   SYNTAX      Pr1645v2EthPortSwIInQueuesD7PerformanceEntry
   MAX-ACCESS  not-accessible
   STATUS      current
   DESCRIPTION
      ""
   INDEX      { pr1645v2EthPortSwIInQueuesD7PerformanceGlobalIx,
                pr1645v2EthPortSwIInQueuesTableIx,
                pr1645v2EthPortSwIInQueuesD7PerformanceTableIx }
   ::= {pr1645v2EthPortSwIInQueuesD7Performance 1}

Pr1645v2EthPortSwIInQueuesD7PerformanceEntry ::=
   SEQUENCE
      {
      pr1645v2EthPortSwIInQueuesD7PerformanceGlobalIx
         GlobalIndex,
      pr1645v2EthPortSwIInQueuesD7PerformanceTableIx
         TableIndex,
      pr1645v2EthPortSwIInQueuesD7PerformanceSysUpTime
         TimeTicks,
      pr1645v2EthPortSwIInQueuesD7PerformanceTotPkts
         Counter64,
      pr1645v2EthPortSwIInQueuesD7PerformanceDirTxPkts
         Counter64,
      pr1645v2EthPortSwIInQueuesD7PerformanceQdPkts
         Counter64,
      pr1645v2EthPortSwIInQueuesD7PerformanceDropPkts
         Counter64,
      pr1645v2EthPortSwIInQueuesD7PerformanceRDropPkts
         Counter64,
      pr1645v2EthPortSwIInQueuesD7PerformanceCirTxPkts
         Counter64,
      pr1645v2EthPortSwIInQueuesD7PerformanceEirTxPkts
         Counter64,
      pr1645v2EthPortSwIInQueuesD7PerformanceViolTxPkts
         Counter64,
      pr1645v2EthPortSwIInQueuesD7PerformanceTotOcts
         Counter64,
      pr1645v2EthPortSwIInQueuesD7PerformanceDirTxOcts
         Counter64,
      pr1645v2EthPortSwIInQueuesD7PerformanceQdOcts
         Counter64,
      pr1645v2EthPortSwIInQueuesD7PerformanceDropOcts
         Counter64,
      pr1645v2EthPortSwIInQueuesD7PerformanceRDropOcts
         Counter64,
      pr1645v2EthPortSwIInQueuesD7PerformanceCirTxOcts
         Counter64,
      pr1645v2EthPortSwIInQueuesD7PerformanceEirTxOcts
         Counter64,
      pr1645v2EthPortSwIInQueuesD7PerformanceViolTxOcts
         Counter64,
      pr1645v2EthPortSwIInQueuesD7PerformanceBandwidth
         Integer32
      }

pr1645v2EthPortSwIInQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIInQueuesD7PerformanceEntry 10}

pr1645v2EthPortSwIInQueuesD7PerformanceTableIx OBJECT-TYPE
   SYNTAX      TableIndex
   MAX-ACCESS  not-accessible
   STATUS      current
   DESCRIPTION
      ""
   ::= {pr1645v2EthPortSwIInQueuesD7PerformanceEntry 11}

pr1645v2EthPortSwIInQueuesD7PerformanceSysUpTime OBJECT-TYPE
   SYNTAX      TimeTicks
   MAX-ACCESS  read-only
   STATUS      current
   DESCRIPTION
      "Path: swPort.performance.ifInPriorityQueues.d7Performance.sysUpTime

       Time in centi-second."
   ::= {pr1645v2EthPortSwIInQueuesD7PerformanceEntry 16777216}

pr1645v2EthPortSwIInQueuesD7PerformanceTotPkts OBJECT-TYPE
   SYNTAX      Counter64
   MAX-ACCESS  read-only
   STATUS      current
   DESCRIPTION
      "Path: swPort.performance.ifInPriorityQueues.d7Performance.totalPkts

       64 bit unsigned wrappable counter."
   ::= {pr1645v2EthPortSwIInQueuesD7PerformanceEntry 234881024}

pr1645v2EthPortSwIInQueuesD7PerformanceDirTxPkts OBJECT-TYPE
   SYNTAX      Counter64
   MAX-ACCESS  read-only
   STATUS      current
   DESCRIPTION
      "Path: swPort.performance.ifInPriorityQueues.d7Performance.directTxPkts

       64 bit unsigned wrappable counter."
   ::= {pr1645v2EthPortSwIInQueuesD7PerformanceEntry 33554432}

pr1645v2EthPortSwIInQueuesD7PerformanceQdPkts OBJECT-TYPE
   SYNTAX      Counter64
   MAX-ACCESS  read-only
   STATUS      current
   DESCRIPTION
      "Path: swPort.performance.ifInPriorityQueues.d7Performance.queuedPkts

       64 bit unsigned wrappable counter."
   ::= {pr1645v2EthPortSwIInQueuesD7PerformanceEntry 50331648}

pr1645v2EthPortSwIInQueuesD7PerformanceDropPkts OBJECT-TYPE
   SYNTAX      Counter64
   MAX-ACCESS  read-only
   STATUS      current
   DESCRIPTION
      "Path: swPort.performance.ifInPriorityQueues.d7Performance.droppedPkts

       64 bit unsigned wrappable counter."
   ::= {pr1645v2EthPortSwIInQueuesD7PerformanceEntry 67108864}

pr1645v2EthPortSwIInQueuesD7PerformanceRDropPkts OBJECT-TYPE
   SYNTAX      Counter64
   MAX-ACCESS  read-only
   STATUS      current
   DESCRIPTION
      "Path: swPort.performance.ifInPriorityQueues.d7Performance.redDroppedPkts

       64 bit unsigned wrappable counter."
   ::= {pr1645v2EthPortSwIInQueuesD7PerformanceEntry 201326592}

pr1645v2EthPortSwIInQueuesD7PerformanceCirTxPkts OBJECT-TYPE
   SYNTAX      Counter64
   MAX-ACCESS  read-only
   STATUS      current
   DESCRIPTION
      "Path: swPort.performance.ifInPriorityQueues.d7Performance.cirTxPkts

       64 bit unsigned wrappable counter."
   ::= {pr1645v2EthPortSwIInQueuesD7PerformanceEntry 83886080}

pr1645v2EthPortSwIInQueuesD7PerformanceEirTxPkts OBJECT-TYPE
   SYNTAX      Counter64
   MAX-ACCESS  read-only
   STATUS      current
   DESCRIPTION
      "Path: swPort.performance.ifInPriorityQueues.d7Performance.eirTxPkts

       64 bit unsigned wrappable counter."
   ::= {pr1645v2EthPortSwIInQueuesD7PerformanceEntry 100663296}

pr1645v2EthPortSwIInQueuesD7PerformanceViolTxPkts OBJECT-TYPE
   SYNTAX      Counter64
   MAX-ACCESS  read-only
   STATUS      current
   DESCRIPTION
      "Path: swPort.performance.ifInPriorityQueues.d7Performance.violateTxPkts

       64 bit unsigned wrappable counter."
   ::= {pr1645v2EthPortSwIInQueuesD7PerformanceEntry 301989888}

pr1645v2EthPortSwIInQueuesD7PerformanceTotOcts OBJECT-TYPE
   SYNTAX      Counter64
   MAX-ACCESS  read-only
   STATUS      current
   DESCRIPTION
      "Path: swPort.performance.ifInPriorityQueues.d7Performance.totalOctets

       64 bit unsigned wrappable counter."
   ::= {pr1645v2EthPortSwIInQueuesD7PerformanceEntry 251658240}

pr1645v2EthPortSwIInQueuesD7PerformanceDirTxOcts OBJECT-TYPE
   SYNTAX      Counter64
   MAX-ACCESS  read-only
   STATUS      current
   DESCRIPTION
      "Path: swPort.performance.ifInPriorityQueues.d7Performance.directTxOctets

       64 bit unsigned wrappable counter."
   ::= {pr1645v2EthPortSwIInQueuesD7PerformanceEntry 117440512}

pr1645v2EthPortSwIInQueuesD7PerformanceQdOcts OBJECT-TYPE
   SYNTAX      Counter64
   MAX-ACCESS  read-only
   STATUS      current
   DESCRIPTION
      "Path: swPort.performance.ifInPriorityQueues.d7Performance.queuedOctets

       64 bit unsigned wrappable counter."
   ::= {pr1645v2EthPortSwIInQueuesD7PerformanceEntry 134217728}

pr1645v2EthPortSwIInQueuesD7PerformanceDropOcts OBJECT-TYPE
   SYNTAX      Counter64
   MAX-ACCESS  read-only
   STATUS      current
   DESCRIPTION
      "Path: swPort.performance.ifInPriorityQueues.d7Performance.droppedOctets

       64 bit unsigned wrappable counter."
   ::= {pr1645v2EthPortSwIInQueuesD7PerformanceEntry 150994944}

pr1645v2EthPortSwIInQueuesD7PerformanceRDropOcts OBJECT-TYPE
   SYNTAX      Counter64
   MAX-ACCESS  read-only
   STATUS      current
   DESCRIPTION
      "Path: swPort.performance.ifInPriorityQueues.d7Performance.redDroppedOctets

       64 bit unsigned wrappable counter."
   ::= {pr1645v2EthPortSwIInQueuesD7PerformanceEntry 218103808}

pr1645v2EthPortSwIInQueuesD7PerformanceCirTxOcts OBJECT-TYPE
   SYNTAX      Counter64
   MAX-ACCESS  read-only
   STATUS      current
   DESCRIPTION
      "Path: swPort.performance.ifInPriorityQueues.d7Performance.cirTxOctets

       64 bit unsigned wrappable counter."
   ::= {pr1645v2EthPortSwIInQueuesD7PerformanceEntry 167772160}

pr1645v2EthPortSwIInQueuesD7PerformanceEirTxOcts OBJECT-TYPE
   SYNTAX      Counter64
   MAX-ACCESS  read-only
   STATUS      current
   DESCRIPTION
      "Path: swPort.performance.ifInPriorityQueues.d7Performance.eirTxOctets

       64 bit unsigned wrappable counter."
   ::= {pr1645v2EthPortSwIInQueuesD7PerformanceEntry 184549376}

pr1645v2EthPortSwIInQueuesD7PerformanceViolTxOcts OBJECT-TYPE
   SYNTAX      Counter64
   MAX-ACCESS  read-only
   STATUS      current
   DESCRIPTION
      "Path: swPort.performance.ifInPriorityQueues.d7Performance.violateTxOctets

       64 bit unsigned wrappable counter."
   ::= {pr1645v2EthPortSwIInQueuesD7PerformanceEntry 318767104}

pr1645v2EthPortSwIInQueuesD7PerformanceBandwidth OBJECT-TYPE
   SYNTAX      Integer32
   MAX-ACCESS  read-only
   STATUS      current
   DESCRIPTION
      "Path: swPort.performance.ifInPriorityQueues.d7Performance.bandwidth

       unit name = bps
       formula = 8 * ; 8 /"
   ::= {pr1645v2EthPortSwIInQueuesD7PerformanceEntry 268435456}


pr1645v2EthPortSwIInBandwidth OBJECT IDENTIFIER ::= {pr1645v2EthPortSwI 181}

pr1645v2EthPortSwIInBandwidthSSCTable OBJECT-TYPE
   SYNTAX      SEQUENCE OF Pr1645v2EthPortSwIInBandwidthEntry
   MAX-ACCESS  not-accessible
   STATUS      current
   DESCRIPTION
      "bandwidth"
   ::= {pr1645v2EthPortSwIInBandwidth 1}

pr1645v2EthPortSwIInBandwidthEntry OBJECT-TYPE
   SYNTAX      Pr1645v2EthPortSwIInBandwidthEntry
   MAX-ACCESS  not-accessible
   STATUS      current
   DESCRIPTION
      ""
   INDEX      { pr1645v2EthPortSwIInBandwidthGlobalIx }
   ::= {pr1645v2EthPortSwIInBandwidthSSCTable 1}

Pr1645v2EthPortSwIInBandwidthEntry ::=
   SEQUENCE
      {
      pr1645v2EthPortSwIInBandwidthGlobalIx
         GlobalIndex,
      pr1645v2EthPortSwIInBandwidth15sec
         Integer32,
      pr1645v2EthPortSwIInBandwidth30sec
         Integer32,
      pr1645v2EthPortSwIInBandwidth1min
         Integer32,
      pr1645v2EthPortSwIInBandwidth2min
         Integer32,
      pr1645v2EthPortSwIInBandwidth5min
         Integer32
      }

pr1645v2EthPortSwIInBandwidthGlobalIx OBJECT-TYPE
   SYNTAX      GlobalIndex
   MAX-ACCESS  not-accessible
   STATUS      current
   DESCRIPTION
      "The value of the tlsCntTreeGlobalIndex of the MANAGED OBJECT."
   ::= {pr1645v2EthPortSwIInBandwidthEntry 10}

pr1645v2EthPortSwIInBandwidth15sec OBJECT-TYPE
   SYNTAX      Integer32
   MAX-ACCESS  read-only
   STATUS      current
   DESCRIPTION
      "Path: swPort.performance.ifInBandwidth.15sec

       unit name = bps
       formula = 8 * ; 8 /"
   ::= {pr1645v2EthPortSwIInBandwidthEntry 83886080}

pr1645v2EthPortSwIInBandwidth30sec OBJECT-TYPE
   SYNTAX      Integer32
   MAX-ACCESS  read-only
   STATUS      current
   DESCRIPTION
      "Path: swPort.performance.ifInBandwidth.30sec

       unit name = bps
       formula = 8 * ; 8 /"
   ::= {pr1645v2EthPortSwIInBandwidthEntry 167772160}

pr1645v2EthPortSwIInBandwidth1min OBJECT-TYPE
   SYNTAX      Integer32
   MAX-ACCESS  read-only
   STATUS      current
   DESCRIPTION
      "Path: swPort.performance.ifInBandwidth.1min

       unit name = bps
       formula = 8 * ; 8 /"
   ::= {pr1645v2EthPortSwIInBandwidthEntry 335544320}

pr1645v2EthPortSwIInBandwidth2min OBJECT-TYPE
   SYNTAX      Integer32
   MAX-ACCESS  read-only
   STATUS      current
   DESCRIPTION
      "Path: swPort.performance.ifInBandwidth.2min

       unit name = bps
       formula = 8 * ; 8 /"
   ::= {pr1645v2EthPortSwIInBandwidthEntry 671088640}

pr1645v2EthPortSwIInBandwidth5min OBJECT-TYPE
   SYNTAX      Integer32
   MAX-ACCESS  read-only
   STATUS      current
   DESCRIPTION
      "Path: swPort.performance.ifInBandwidth.5min

       unit name = bps
       formula = 8 * ; 8 /"
   ::= {pr1645v2EthPortSwIInBandwidthEntry 1677721600}


pr1645v2EthPortSwIOutOctets OBJECT IDENTIFIER ::= {pr1645v2EthPortSwI 115}

pr1645v2EthPortSwIOutOctetsTable OBJECT-TYPE
   SYNTAX      SEQUENCE OF Pr1645v2EthPortSwIOutOctetsEntry
   MAX-ACCESS  not-accessible
   STATUS      current
   DESCRIPTION
      "ifOutOctets"
   ::= {pr1645v2EthPortSwIOutOctets 1}

pr1645v2EthPortSwIOutOctetsEntry OBJECT-TYPE
   SYNTAX      Pr1645v2EthPortSwIOutOctetsEntry
   MAX-ACCESS  not-accessible
   STATUS      current
   DESCRIPTION
      ""
   INDEX      { pr1645v2EthPortSwIOutOctetsGlobalIx }
   ::= {pr1645v2EthPortSwIOutOctetsTable 1}

Pr1645v2EthPortSwIOutOctetsEntry ::=
   SEQUENCE
      {
      pr1645v2EthPortSwIOutOctetsGlobalIx
         GlobalIndex,
      pr1645v2EthPortSwIOutOctetsValue
         Counter64
      }

pr1645v2EthPortSwIOutOctetsGlobalIx OBJECT-TYPE
   SYNTAX      GlobalIndex
   MAX-ACCESS  not-accessible
   STATUS      current
   DESCRIPTION
      "The value of the tlsCntTreeGlobalIndex of the MANAGED OBJECT."
   ::= {pr1645v2EthPortSwIOutOctetsEntry 10}

pr1645v2EthPortSwIOutOctetsValue OBJECT-TYPE
   SYNTAX      Counter64
   MAX-ACCESS  read-only
   STATUS      current
   DESCRIPTION
      "Path: swPort.performance.ifOutOctets

       64 bit unsigned wrappable counter."
   ::= {pr1645v2EthPortSwIOutOctetsEntry 2147483648}


pr1645v2EthPortSwIOutUcastPkts OBJECT IDENTIFIER ::= {pr1645v2EthPortSwI 116}

pr1645v2EthPortSwIOutUcastPktsTable OBJECT-TYPE
   SYNTAX      SEQUENCE OF Pr1645v2EthPortSwIOutUcastPktsEntry
   MAX-ACCESS  not-accessible
   STATUS      current
   DESCRIPTION
      "ifOutUcastPkts"
   ::= {pr1645v2EthPortSwIOutUcastPkts 1}

pr1645v2EthPortSwIOutUcastPktsEntry OBJECT-TYPE
   SYNTAX      Pr1645v2EthPortSwIOutUcastPktsEntry
   MAX-ACCESS  not-accessible
   STATUS      current
   DESCRIPTION
      ""
   INDEX      { pr1645v2EthPortSwIOutUcastPktsGlobalIx }
   ::= {pr1645v2EthPortSwIOutUcastPktsTable 1}

Pr1645v2EthPortSwIOutUcastPktsEntry ::=
   SEQUENCE
      {
      pr1645v2EthPortSwIOutUcastPktsGlobalIx
         GlobalIndex,
      pr1645v2EthPortSwIOutUcastPktsValue
         Counter64
      }

pr1645v2EthPortSwIOutUcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIOutUcastPktsEntry 10}

pr1645v2EthPortSwIOutUcastPktsValue OBJECT-TYPE
   SYNTAX      Counter64
   MAX-ACCESS  read-only
   STATUS      current
   DESCRIPTION
      "Path: swPort.performance.ifOutUcastPkts

       64 bit unsigned wrappable counter."
   ::= {pr1645v2EthPortSwIOutUcastPktsEntry 2147483648}


pr1645v2EthPortSwIOutNUcastPkts OBJECT IDENTIFIER ::= {pr1645v2EthPortSwI 117}

pr1645v2EthPortSwIOutNUcastPktsTable OBJECT-TYPE
   SYNTAX      SEQUENCE OF Pr1645v2EthPortSwIOutNUcastPktsEntry
   MAX-ACCESS  not-accessible
   STATUS      current
   DESCRIPTION
      "ifOutNUcastPkts"
   ::= {pr1645v2EthPortSwIOutNUcastPkts 1}

pr1645v2EthPortSwIOutNUcastPktsEntry OBJECT-TYPE
   SYNTAX      Pr1645v2EthPortSwIOutNUcastPktsEntry
   MAX-ACCESS  not-accessible
   STATUS      current
   DESCRIPTION
      ""
   INDEX      { pr1645v2EthPortSwIOutNUcastPktsGlobalIx }
   ::= {pr1645v2EthPortSwIOutNUcastPktsTable 1}

Pr1645v2EthPortSwIOutNUcastPktsEntry ::=
   SEQUENCE
      {
      pr1645v2EthPortSwIOutNUcastPktsGlobalIx
         GlobalIndex,
      pr1645v2EthPortSwIOutNUcastPktsValue
         Counter64
      }

pr1645v2EthPortSwIOutNUcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIOutNUcastPktsEntry 10}

pr1645v2EthPortSwIOutNUcastPktsValue OBJECT-TYPE
   SYNTAX      Counter64
   MAX-ACCESS  read-only
   STATUS      current
   DESCRIPTION
      "Path: swPort.performance.ifOutNUcastPkts

       64 bit unsigned wrappable counter."
   ::= {pr1645v2EthPortSwIOutNUcastPktsEntry 2147483648}


pr1645v2EthPortSwIOutBcastPkts OBJECT IDENTIFIER ::= {pr1645v2EthPortSwI 217}

pr1645v2EthPortSwIOutBcastPktsTable OBJECT-TYPE
   SYNTAX      SEQUENCE OF Pr1645v2EthPortSwIOutBcastPktsEntry
   MAX-ACCESS  not-accessible
   STATUS      current
   DESCRIPTION
      "ifOutBcastPkts"
   ::= {pr1645v2EthPortSwIOutBcastPkts 1}

pr1645v2EthPortSwIOutBcastPktsEntry OBJECT-TYPE
   SYNTAX      Pr1645v2EthPortSwIOutBcastPktsEntry
   MAX-ACCESS  not-accessible
   STATUS      current
   DESCRIPTION
      ""
   INDEX      { pr1645v2EthPortSwIOutBcastPktsGlobalIx }
   ::= {pr1645v2EthPortSwIOutBcastPktsTable 1}

Pr1645v2EthPortSwIOutBcastPktsEntry ::=
   SEQUENCE
      {
      pr1645v2EthPortSwIOutBcastPktsGlobalIx
         GlobalIndex,
      pr1645v2EthPortSwIOutBcastPktsValue
         Counter64
      }

pr1645v2EthPortSwIOutBcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIOutBcastPktsEntry 10}

pr1645v2EthPortSwIOutBcastPktsValue OBJECT-TYPE
   SYNTAX      Counter64
   MAX-ACCESS  read-only
   STATUS      current
   DESCRIPTION
      "Path: swPort.performance.ifOutBcastPkts

       64 bit unsigned wrappable counter."
   ::= {pr1645v2EthPortSwIOutBcastPktsEntry 2147483648}


pr1645v2EthPortSwIOutMcastPkts OBJECT IDENTIFIER ::= {pr1645v2EthPortSwI 227}

pr1645v2EthPortSwIOutMcastPktsTable OBJECT-TYPE
   SYNTAX      SEQUENCE OF Pr1645v2EthPortSwIOutMcastPktsEntry
   MAX-ACCESS  not-accessible
   STATUS      current
   DESCRIPTION
      "ifOutMcastPkts"
   ::= {pr1645v2EthPortSwIOutMcastPkts 1}

pr1645v2EthPortSwIOutMcastPktsEntry OBJECT-TYPE
   SYNTAX      Pr1645v2EthPortSwIOutMcastPktsEntry
   MAX-ACCESS  not-accessible
   STATUS      current
   DESCRIPTION
      ""
   INDEX      { pr1645v2EthPortSwIOutMcastPktsGlobalIx }
   ::= {pr1645v2EthPortSwIOutMcastPktsTable 1}

Pr1645v2EthPortSwIOutMcastPktsEntry ::=
   SEQUENCE
      {
      pr1645v2EthPortSwIOutMcastPktsGlobalIx
         GlobalIndex,
      pr1645v2EthPortSwIOutMcastPktsValue
         Counter64
      }

pr1645v2EthPortSwIOutMcastPktsGlobalIx OBJECT-TYPE
   SYNTAX      GlobalIndex
   MAX-ACCESS  not-accessible
   STATUS      current
   DESCRIPTION
      "The value of the tlsCntTreeGlobalIndex of the MANAGED OBJECT."
   ::= {pr1645v2EthPortSwIOutMcastPktsEntry 10}

pr1645v2EthPortSwIOutMcastPktsValue OBJECT-TYPE
   SYNTAX      Counter64
   MAX-ACCESS  read-only
   STATUS      current
   DESCRIPTION
      "Path: swPort.performance.ifOutMcastPkts

       64 bit unsigned wrappable counter."
   ::= {pr1645v2EthPortSwIOutMcastPktsEntry 2147483648}


pr1645v2EthPortSwIOutDiscards OBJECT IDENTIFIER ::= {pr1645v2EthPortSwI 118}

pr1645v2EthPortSwIOutDiscardsTable OBJECT-TYPE
   SYNTAX      SEQUENCE OF Pr1645v2EthPortSwIOutDiscardsEntry
   MAX-ACCESS  not-accessible
   STATUS      current
   DESCRIPTION
      "ifOutDiscards"
   ::= {pr1645v2EthPortSwIOutDiscards 1}

pr1645v2EthPortSwIOutDiscardsEntry OBJECT-TYPE
   SYNTAX      Pr1645v2EthPortSwIOutDiscardsEntry
   MAX-ACCESS  not-accessible
   STATUS      current
   DESCRIPTION
      ""
   INDEX      { pr1645v2EthPortSwIOutDiscardsGlobalIx }
   ::= {pr1645v2EthPortSwIOutDiscardsTable 1}

Pr1645v2EthPortSwIOutDiscardsEntry ::=
   SEQUENCE
      {
      pr1645v2EthPortSwIOutDiscardsGlobalIx
         GlobalIndex,
      pr1645v2EthPortSwIOutDiscardsValue
         Counter64
      }

pr1645v2EthPortSwIOutDiscardsGlobalIx OBJECT-TYPE
   SYNTAX      GlobalIndex
   MAX-ACCESS  not-accessible
   STATUS      current
   DESCRIPTION
      "The value of the tlsCntTreeGlobalIndex of the MANAGED OBJECT."
   ::= {pr1645v2EthPortSwIOutDiscardsEntry 10}

pr1645v2EthPortSwIOutDiscardsValue OBJECT-TYPE
   SYNTAX      Counter64
   MAX-ACCESS  read-only
   STATUS      current
   DESCRIPTION
      "Path: swPort.performance.ifOutDiscards

       64 bit unsigned wrappable counter."
   ::= {pr1645v2EthPortSwIOutDiscardsEntry 2147483648}


pr1645v2EthPortSwIOutErrors OBJECT IDENTIFIER ::= {pr1645v2EthPortSwI 119}

pr1645v2EthPortSwIOutErrorsTable OBJECT-TYPE
   SYNTAX      SEQUENCE OF Pr1645v2EthPortSwIOutErrorsEntry
   MAX-ACCESS  not-accessible
   STATUS      current
   DESCRIPTION
      "ifOutErrors"
   ::= {pr1645v2EthPortSwIOutErrors 1}

pr1645v2EthPortSwIOutErrorsEntry OBJECT-TYPE
   SYNTAX      Pr1645v2EthPortSwIOutErrorsEntry
   MAX-ACCESS  not-accessible
   STATUS      current
   DESCRIPTION
      ""
   INDEX      { pr1645v2EthPortSwIOutErrorsGlobalIx }
   ::= {pr1645v2EthPortSwIOutErrorsTable 1}

Pr1645v2EthPortSwIOutErrorsEntry ::=
   SEQUENCE
      {
      pr1645v2EthPortSwIOutErrorsGlobalIx
         GlobalIndex,
      pr1645v2EthPortSwIOutErrorsValue
         Counter64
      }

pr1645v2EthPortSwIOutErrorsGlobalIx OBJECT-TYPE
   SYNTAX      GlobalIndex
   MAX-ACCESS  not-accessible
   STATUS      current
   DESCRIPTION
      "The value of the tlsCntTreeGlobalIndex of the MANAGED OBJECT."
   ::= {pr1645v2EthPortSwIOutErrorsEntry 10}

pr1645v2EthPortSwIOutErrorsValue OBJECT-TYPE
   SYNTAX      Counter64
   MAX-ACCESS  read-only
   STATUS      current
   DESCRIPTION
      "Path: swPort.performance.ifOutErrors

       64 bit unsigned wrappable counter."
   ::= {pr1645v2EthPortSwIOutErrorsEntry 2147483648}


pr1645v2EthPortSwIOutQLen OBJECT IDENTIFIER ::= {pr1645v2EthPortSwI 120}

pr1645v2EthPortSwIOutQLenTable OBJECT-TYPE
   SYNTAX      SEQUENCE OF Pr1645v2EthPortSwIOutQLenEntry
   MAX-ACCESS  not-accessible
   STATUS      current
   DESCRIPTION
      "ifOutQLen"
   ::= {pr1645v2EthPortSwIOutQLen 1}

pr1645v2EthPortSwIOutQLenEntry OBJECT-TYPE
   SYNTAX      Pr1645v2EthPortSwIOutQLenEntry
   MAX-ACCESS  not-accessible
   STATUS      current
   DESCRIPTION
      ""
   INDEX      { pr1645v2EthPortSwIOutQLenGlobalIx }
   ::= {pr1645v2EthPortSwIOutQLenTable 1}

Pr1645v2EthPortSwIOutQLenEntry ::=
   SEQUENCE
      {
      pr1645v2EthPortSwIOutQLenGlobalIx
         GlobalIndex,
      pr1645v2EthPortSwIOutQLenValue
         Gauge32
      }

pr1645v2EthPortSwIOutQLenGlobalIx OBJECT-TYPE
   SYNTAX      GlobalIndex
   MAX-ACCESS  not-accessible
   STATUS      current
   DESCRIPTION
      "The value of the tlsCntTreeGlobalIndex of the MANAGED OBJECT."
   ::= {pr1645v2EthPortSwIOutQLenEntry 10}

pr1645v2EthPortSwIOutQLenValue OBJECT-TYPE
   SYNTAX      Gauge32
   MAX-ACCESS  read-only
   STATUS      current
   DESCRIPTION
      "Path: swPort.performance.ifOutQLen

       32 bit unsigned gauge value."
   ::= {pr1645v2EthPortSwIOutQLenEntry 2147483648}


pr1645v2EthPortSwIOutDropEx OBJECT IDENTIFIER ::= {pr1645v2EthPortSwI 127}

pr1645v2EthPortSwIOutDropExTable OBJECT-TYPE
   SYNTAX      SEQUENCE OF Pr1645v2EthPortSwIOutDropExEntry
   MAX-ACCESS  not-accessible
   STATUS      current
   DESCRIPTION
      "ifOutDiscards"
   ::= {pr1645v2EthPortSwIOutDropEx 1}

pr1645v2EthPortSwIOutDropExEntry OBJECT-TYPE
   SYNTAX      Pr1645v2EthPortSwIOutDropExEntry
   MAX-ACCESS  not-accessible
   STATUS      current
   DESCRIPTION
      ""
   INDEX      { pr1645v2EthPortSwIOutDropExGlobalIx }
   ::= {pr1645v2EthPortSwIOutDropExTable 1}

Pr1645v2EthPortSwIOutDropExEntry ::=
   SEQUENCE
      {
      pr1645v2EthPortSwIOutDropExGlobalIx
         GlobalIndex,
      pr1645v2EthPortSwIOutDropExValue
         Counter64
      }

pr1645v2EthPortSwIOutDropExGlobalIx OBJECT-TYPE
   SYNTAX      GlobalIndex
   MAX-ACCESS  not-accessible
   STATUS      current
   DESCRIPTION
      "The value of the tlsCntTreeGlobalIndex of the MANAGED OBJECT."
   ::= {pr1645v2EthPortSwIOutDropExEntry 10}

pr1645v2EthPortSwIOutDropExValue OBJECT-TYPE
   SYNTAX      Counter64
   MAX-ACCESS  read-only
   STATUS      current
   DESCRIPTION
      "Path: swPort.performance.ifOutDropLevelExceeded

       64 bit unsigned wrappable counter."
   ::= {pr1645v2EthPortSwIOutDropExEntry 2147483648}


pr1645v2EthPortSwIOutDropNoArp OBJECT IDENTIFIER ::= {pr1645v2EthPortSwI 134}

pr1645v2EthPortSwIOutDropNoArpTable OBJECT-TYPE
   SYNTAX      SEQUENCE OF Pr1645v2EthPortSwIOutDropNoArpEntry
   MAX-ACCESS  not-accessible
   STATUS      current
   DESCRIPTION
      "ifOutDiscards"
   ::= {pr1645v2EthPortSwIOutDropNoArp 1}

pr1645v2EthPortSwIOutDropNoArpEntry OBJECT-TYPE
   SYNTAX      Pr1645v2EthPortSwIOutDropNoArpEntry
   MAX-ACCESS  not-accessible
   STATUS      current
   DESCRIPTION
      ""
   INDEX      { pr1645v2EthPortSwIOutDropNoArpGlobalIx }
   ::= {pr1645v2EthPortSwIOutDropNoArpTable 1}

Pr1645v2EthPortSwIOutDropNoArpEntry ::=
   SEQUENCE
      {
      pr1645v2EthPortSwIOutDropNoArpGlobalIx
         GlobalIndex,
      pr1645v2EthPortSwIOutDropNoArpValue
         Counter64
      }

pr1645v2EthPortSwIOutDropNoArpGlobalIx OBJECT-TYPE
   SYNTAX      GlobalIndex
   MAX-ACCESS  not-accessible
   STATUS      current
   DESCRIPTION
      "The value of the tlsCntTreeGlobalIndex of the MANAGED OBJECT."
   ::= {pr1645v2EthPortSwIOutDropNoArpEntry 10}

pr1645v2EthPortSwIOutDropNoArpValue OBJECT-TYPE
   SYNTAX      Counter64
   MAX-ACCESS  read-only
   STATUS      current
   DESCRIPTION
      "Path: swPort.performance.ifOutDiscardsNoArp

       64 bit unsigned wrappable counter."
   ::= {pr1645v2EthPortSwIOutDropNoArpEntry 2147483648}


pr1645v2EthPortSwIOutDropFilter OBJECT IDENTIFIER ::= {pr1645v2EthPortSwI 138}

pr1645v2EthPortSwIOutDropFilterTable OBJECT-TYPE
   SYNTAX      SEQUENCE OF Pr1645v2EthPortSwIOutDropFilterEntry
   MAX-ACCESS  not-accessible
   STATUS      current
   DESCRIPTION
      "ifOutDiscards"
   ::= {pr1645v2EthPortSwIOutDropFilter 1}

pr1645v2EthPortSwIOutDropFilterEntry OBJECT-TYPE
   SYNTAX      Pr1645v2EthPortSwIOutDropFilterEntry
   MAX-ACCESS  not-accessible
   STATUS      current
   DESCRIPTION
      ""
   INDEX      { pr1645v2EthPortSwIOutDropFilterGlobalIx }
   ::= {pr1645v2EthPortSwIOutDropFilterTable 1}

Pr1645v2EthPortSwIOutDropFilterEntry ::=
   SEQUENCE
      {
      pr1645v2EthPortSwIOutDropFilterGlobalIx
         GlobalIndex,
      pr1645v2EthPortSwIOutDropFilterValue
         Counter64
      }

pr1645v2EthPortSwIOutDropFilterGlobalIx OBJECT-TYPE
   SYNTAX      GlobalIndex
   MAX-ACCESS  not-accessible
   STATUS      current
   DESCRIPTION
      "The value of the tlsCntTreeGlobalIndex of the MANAGED OBJECT."
   ::= {pr1645v2EthPortSwIOutDropFilterEntry 10}

pr1645v2EthPortSwIOutDropFilterValue OBJECT-TYPE
   SYNTAX      Counter64
   MAX-ACCESS  read-only
   STATUS      current
   DESCRIPTION
      "Path: swPort.performance.ifOutDiscardsFilter

       64 bit unsigned wrappable counter."
   ::= {pr1645v2EthPortSwIOutDropFilterEntry 2147483648}


pr1645v2EthPortSwIOutQueues OBJECT IDENTIFIER ::= {pr1645v2EthPortSwI 129}

pr1645v2EthPortSwIOutQueuesSSCTable OBJECT-TYPE
   SYNTAX      SEQUENCE OF Pr1645v2EthPortSwIOutQueuesEntry
   MAX-ACCESS  not-accessible
   STATUS      current
   DESCRIPTION
      "Queue Lengths"
   ::= {pr1645v2EthPortSwIOutQueues 1}

pr1645v2EthPortSwIOutQueuesEntry OBJECT-TYPE
   SYNTAX      Pr1645v2EthPortSwIOutQueuesEntry
   MAX-ACCESS  not-accessible
   STATUS      current
   DESCRIPTION
      ""
   INDEX      { pr1645v2EthPortSwIOutQueuesGlobalIx,
                pr1645v2EthPortSwIOutQueuesTableIx }
   ::= {pr1645v2EthPortSwIOutQueuesSSCTable 1}

Pr1645v2EthPortSwIOutQueuesEntry ::=
   SEQUENCE
      {
      pr1645v2EthPortSwIOutQueuesGlobalIx
         GlobalIndex,
      pr1645v2EthPortSwIOutQueuesTableIx
         TableIndex,
      pr1645v2EthPortSwIOutQueuesName
         INTEGER,
      pr1645v2EthPortSwIOutQueuesLength
         Integer32,
      pr1645v2EthPortSwIOutQueuesOctetLength
         Integer32,
      pr1645v2EthPortSwIOutQueuesRedLength
         Integer32,
      pr1645v2EthPortSwIOutQueuesPacketsTotal
         Counter64,
      pr1645v2EthPortSwIOutQueuesPacketsDirectTx
         Counter64,
      pr1645v2EthPortSwIOutQueuesPacketsQueued
         Counter64,
      pr1645v2EthPortSwIOutQueuesPacketsDropped
         Counter64,
      pr1645v2EthPortSwIOutQueuesPacketsRedDropped
         Counter64,
      pr1645v2EthPortSwIOutQueuesPacketsCirTx
         Counter64,
      pr1645v2EthPortSwIOutQueuesPacketsEirTx
         Counter64,
      pr1645v2EthPortSwIOutQueuesPacketsViolateTx
         Counter64,
      pr1645v2EthPortSwIOutQueuesOctetsTotal
         Counter64,
      pr1645v2EthPortSwIOutQueuesOctetsDirectTx
         Counter64,
      pr1645v2EthPortSwIOutQueuesOctetsQueued
         Counter64,
      pr1645v2EthPortSwIOutQueuesOctetsDropped
         Counter64,
      pr1645v2EthPortSwIOutQueuesOctetsRedDropped
         Counter64,
      pr1645v2EthPortSwIOutQueuesOctetsCirTx
         Counter64,
      pr1645v2EthPortSwIOutQueuesOctetsEirTx
         Counter64,
      pr1645v2EthPortSwIOutQueuesOctetsViolateTx
         Counter64,
      pr1645v2EthPortSwIOutQueuesOctetsBandwidth15sec
         Integer32,
      pr1645v2EthPortSwIOutQueuesOctetsBandwidth30sec
         Integer32,
      pr1645v2EthPortSwIOutQueuesOctetsBandwidth1min
         Integer32,
      pr1645v2EthPortSwIOutQueuesOctetsBandwidth2min
         Integer32,
      pr1645v2EthPortSwIOutQueuesOctetsBandwidth5min
         Integer32
      }

pr1645v2EthPortSwIOutQueuesGlobalIx OBJECT-TYPE
   SYNTAX      GlobalIndex
   MAX-ACCESS  not-accessible
   STATUS      current
   DESCRIPTION
      "The value of the tlsCntTreeGlobalIndex of the MANAGED OBJECT."
   ::= {pr1645v2EthPortSwIOutQueuesEntry 10}

pr1645v2EthPortSwIOutQueuesTableIx OBJECT-TYPE
   SYNTAX      TableIndex
   MAX-ACCESS  not-accessible
   STATUS      current
   DESCRIPTION
      ""
   ::= {pr1645v2EthPortSwIOutQueuesEntry 11}

pr1645v2EthPortSwIOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPortSwIOutQueuesEntry 16777216}

pr1645v2EthPortSwIOutQueuesLength OBJECT-TYPE
   SYNTAX      Integer32
   MAX-ACCESS  read-only
   STATUS      current
   DESCRIPTION
      "Path: swPort.performance.ifOutPriorityQueues.length"
   ::= {pr1645v2EthPortSwIOutQueuesEntry 33554432}

pr1645v2EthPortSwIOutQueuesOctetLength OBJECT-TYPE
   SYNTAX      Integer32
   MAX-ACCESS  read-only
   STATUS      current
   DESCRIPTION
      "Path: swPort.performance.ifOutPriorityQueues.octetLength"
   ::= {pr1645v2EthPortSwIOutQueuesEntry 150994944}

pr1645v2EthPortSwIOutQueuesRedLength OBJECT-TYPE
   SYNTAX      Integer32
   MAX-ACCESS  read-only
   STATUS      current
   DESCRIPTION
      "Path: swPort.performance.ifOutPriorityQueues.redLength"
   ::= {pr1645v2EthPortSwIOutQueuesEntry 134217728}

pr1645v2EthPortSwIOutQueuesPacketsTotal OBJECT-TYPE
   SYNTAX      Counter64
   MAX-ACCESS  read-only
   STATUS      current
   DESCRIPTION
      "Path: swPort.performance.ifOutPriorityQueues.packets.total

       64 bit unsigned wrappable counter."
   ::= {pr1645v2EthPortSwIOutQueuesEntry 50790400}

pr1645v2EthPortSwIOutQueuesPacketsDirectTx OBJECT-TYPE
   SYNTAX      Counter64
   MAX-ACCESS  read-only
   STATUS      current
   DESCRIPTION
      "Path: swPort.performance.ifOutPriorityQueues.packets.directTx

       64 bit unsigned wrappable counter."
   ::= {pr1645v2EthPortSwIOutQueuesEntry 50397184}

pr1645v2EthPortSwIOutQueuesPacketsQueued OBJECT-TYPE
   SYNTAX      Counter64
   MAX-ACCESS  read-only
   STATUS      current
   DESCRIPTION
      "Path: swPort.performance.ifOutPriorityQueues.packets.queued

       64 bit unsigned wrappable counter."
   ::= {pr1645v2EthPortSwIOutQueuesEntry 50462720}

pr1645v2EthPortSwIOutQueuesPacketsDropped OBJECT-TYPE
   SYNTAX      Counter64
   MAX-ACCESS  read-only
   STATUS      current
   DESCRIPTION
      "Path: swPort.performance.ifOutPriorityQueues.packets.dropped

       64 bit unsigned wrappable counter."
   ::= {pr1645v2EthPortSwIOutQueuesEntry 50528256}

pr1645v2EthPortSwIOutQueuesPacketsRedDropped OBJECT-TYPE
   SYNTAX      Counter64
   MAX-ACCESS  read-only
   STATUS      current
   DESCRIPTION
      "Path: swPort.performance.ifOutPriorityQueues.packets.redDropped

       64 bit unsigned wrappable counter."
   ::= {pr1645v2EthPortSwIOutQueuesEntry 50724864}

pr1645v2EthPortSwIOutQueuesPacketsCirTx OBJECT-TYPE
   SYNTAX      Counter64
   MAX-ACCESS  read-only
   STATUS      current
   DESCRIPTION
      "Path: swPort.performance.ifOutPriorityQueues.packets.cirTx

       64 bit unsigned wrappable counter."
   ::= {pr1645v2EthPortSwIOutQueuesEntry 50593792}

pr1645v2EthPortSwIOutQueuesPacketsEirTx OBJECT-TYPE
   SYNTAX      Counter64
   MAX-ACCESS  read-only
   STATUS      current
   DESCRIPTION
      "Path: swPort.performance.ifOutPriorityQueues.packets.eirTx

       64 bit unsigned wrappable counter."
   ::= {pr1645v2EthPortSwIOutQueuesEntry 50659328}

pr1645v2EthPortSwIOutQueuesPacketsViolateTx OBJECT-TYPE
   SYNTAX      Counter64
   MAX-ACCESS  read-only
   STATUS      current
   DESCRIPTION
      "Path: swPort.performance.ifOutPriorityQueues.packets.violateTx

       64 bit unsigned wrappable counter."
   ::= {pr1645v2EthPortSwIOutQueuesEntry 50855936}

pr1645v2EthPortSwIOutQueuesOctetsTotal OBJECT-TYPE
   SYNTAX      Counter64
   MAX-ACCESS  read-only
   STATUS      current
   DESCRIPTION
      "Path: swPort.performance.ifOutPriorityQueues.octets.total

       64 bit unsigned wrappable counter."
   ::= {pr1645v2EthPortSwIOutQueuesEntry 67567616}

pr1645v2EthPortSwIOutQueuesOctetsDirectTx OBJECT-TYPE
   SYNTAX      Counter64
   MAX-ACCESS  read-only
   STATUS      current
   DESCRIPTION
      "Path: swPort.performance.ifOutPriorityQueues.octets.directTx

       64 bit unsigned wrappable counter."
   ::= {pr1645v2EthPortSwIOutQueuesEntry 67174400}

pr1645v2EthPortSwIOutQueuesOctetsQueued OBJECT-TYPE
   SYNTAX      Counter64
   MAX-ACCESS  read-only
   STATUS      current
   DESCRIPTION
      "Path: swPort.performance.ifOutPriorityQueues.octets.queued

       64 bit unsigned wrappable counter."
   ::= {pr1645v2EthPortSwIOutQueuesEntry 67239936}

pr1645v2EthPortSwIOutQueuesOctetsDropped OBJECT-TYPE
   SYNTAX      Counter64
   MAX-ACCESS  read-only
   STATUS      current
   DESCRIPTION
      "Path: swPort.performance.ifOutPriorityQueues.octets.dropped

       64 bit unsigned wrappable counter."
   ::= {pr1645v2EthPortSwIOutQueuesEntry 67305472}

pr1645v2EthPortSwIOutQueuesOctetsRedDropped OBJECT-TYPE
   SYNTAX      Counter64
   MAX-ACCESS  read-only
   STATUS      current
   DESCRIPTION
      "Path: swPort.performance.ifOutPriorityQueues.octets.redDropped

       64 bit unsigned wrappable counter."
   ::= {pr1645v2EthPortSwIOutQueuesEntry 67502080}

pr1645v2EthPortSwIOutQueuesOctetsCirTx OBJECT-TYPE
   SYNTAX      Counter64
   MAX-ACCESS  read-only
   STATUS      current
   DESCRIPTION
      "Path: swPort.performance.ifOutPriorityQueues.octets.cirTx

       64 bit unsigned wrappable counter."
   ::= {pr1645v2EthPortSwIOutQueuesEntry 67371008}

pr1645v2EthPortSwIOutQueuesOctetsEirTx OBJECT-TYPE
   SYNTAX      Counter64
   MAX-ACCESS  read-only
   STATUS      current
   DESCRIPTION
      "Path: swPort.performance.ifOutPriorityQueues.octets.eirTx

       64 bit unsigned wrappable counter."
   ::= {pr1645v2EthPortSwIOutQueuesEntry 67436544}

pr1645v2EthPortSwIOutQueuesOctetsViolateTx OBJECT-TYPE
   SYNTAX      Counter64
   MAX-ACCESS  read-only
   STATUS      current
   DESCRIPTION
      "Path: swPort.performance.ifOutPriorityQueues.octets.violateTx

       64 bit unsigned wrappable counter."
   ::= {pr1645v2EthPortSwIOutQueuesEntry 67633152}

pr1645v2EthPortSwIOutQueuesOctetsBandwidth15sec OBJECT-TYPE
   SYNTAX      Integer32
   MAX-ACCESS  read-only
   STATUS      current
   DESCRIPTION
      "Path: swPort.performance.ifOutPriorityQueues.octets.bandwidth.15sec

       unit name = bps
       formula = 8 * ; 8 /"
   ::= {pr1645v2EthPortSwIOutQueuesEntry 70386944}

pr1645v2EthPortSwIOutQueuesOctetsBandwidth30sec OBJECT-TYPE
   SYNTAX      Integer32
   MAX-ACCESS  read-only
   STATUS      current
   DESCRIPTION
      "Path: swPort.performance.ifOutPriorityQueues.octets.bandwidth.30sec

       unit name = bps
       formula = 8 * ; 8 /"
   ::= {pr1645v2EthPortSwIOutQueuesEntry 70388224}

pr1645v2EthPortSwIOutQueuesOctetsBandwidth1min OBJECT-TYPE
   SYNTAX      Integer32
   MAX-ACCESS  read-only
   STATUS      current
   DESCRIPTION
      "Path: swPort.performance.ifOutPriorityQueues.octets.bandwidth.1min

       unit name = bps
       formula = 8 * ; 8 /"
   ::= {pr1645v2EthPortSwIOutQueuesEntry 70390784}

pr1645v2EthPortSwIOutQueuesOctetsBandwidth2min OBJECT-TYPE
   SYNTAX      Integer32
   MAX-ACCESS  read-only
   STATUS      current
   DESCRIPTION
      "Path: swPort.performance.ifOutPriorityQueues.octets.bandwidth.2min

       unit name = bps
       formula = 8 * ; 8 /"
   ::= {pr1645v2EthPortSwIOutQueuesEntry 70395904}

pr1645v2EthPortSwIOutQueuesOctetsBandwidth5min OBJECT-TYPE
   SYNTAX      Integer32
   MAX-ACCESS  read-only
   STATUS      current
   DESCRIPTION
      "Path: swPort.performance.ifOutPriorityQueues.octets.bandwidth.5min

       unit name = bps
       formula = 8 * ; 8 /"
   ::= {pr1645v2EthPortSwIOutQueuesEntry 70411264}

pr1645v2EthPortSwIOutQueuesH2Performance OBJECT-TYPE
   SYNTAX      SEQUENCE OF Pr1645v2EthPortSwIOutQueuesH2PerformanceEntry
   MAX-ACCESS  not-accessible
   STATUS      current
   DESCRIPTION
      ""
   ::= {pr1645v2EthPortSwIOutQueues 83886080}

pr1645v2EthPortSwIOutQueuesH2PerformanceEntry OBJECT-TYPE
   SYNTAX      Pr1645v2EthPortSwIOutQueuesH2PerformanceEntry
   MAX-ACCESS  not-accessible
   STATUS      current
   DESCRIPTION
      ""
   INDEX      { pr1645v2EthPortSwIOutQueuesH2PerformanceGlobalIx,
                pr1645v2EthPortSwIOutQueuesTableIx,
                pr1645v2EthPortSwIOutQueuesH2PerformanceTableIx }
   ::= {pr1645v2EthPortSwIOutQueuesH2Performance 1}

Pr1645v2EthPortSwIOutQueuesH2PerformanceEntry ::=
   SEQUENCE
      {
      pr1645v2EthPortSwIOutQueuesH2PerformanceGlobalIx
         GlobalIndex,
      pr1645v2EthPortSwIOutQueuesH2PerformanceTableIx
         TableIndex,
      pr1645v2EthPortSwIOutQueuesH2PerformanceSysUpTime
         TimeTicks,
      pr1645v2EthPortSwIOutQueuesH2PerformanceTotPkts
         Counter64,
      pr1645v2EthPortSwIOutQueuesH2PerformanceDirTxPkts
         Counter64,
      pr1645v2EthPortSwIOutQueuesH2PerformanceQdPkts
         Counter64,
      pr1645v2EthPortSwIOutQueuesH2PerformanceDropPkts
         Counter64,
      pr1645v2EthPortSwIOutQueuesH2PerformanceRDropPkts
         Counter64,
      pr1645v2EthPortSwIOutQueuesH2PerformanceCirTxPkts
         Counter64,
      pr1645v2EthPortSwIOutQueuesH2PerformanceEirTxPkts
         Counter64,
      pr1645v2EthPortSwIOutQueuesH2PerformanceViolTxPkts
         Counter64,
      pr1645v2EthPortSwIOutQueuesH2PerformanceTotOcts
         Counter64,
      pr1645v2EthPortSwIOutQueuesH2PerformanceDirTxOcts
         Counter64,
      pr1645v2EthPortSwIOutQueuesH2PerformanceQdOcts
         Counter64,
      pr1645v2EthPortSwIOutQueuesH2PerformanceDropOcts
         Counter64,
      pr1645v2EthPortSwIOutQueuesH2PerformanceRDropOcts
         Counter64,
      pr1645v2EthPortSwIOutQueuesH2PerformanceCirTxOcts
         Counter64,
      pr1645v2EthPortSwIOutQueuesH2PerformanceEirTxOcts
         Counter64,
      pr1645v2EthPortSwIOutQueuesH2PerformanceViolTxOcts
         Counter64,
      pr1645v2EthPortSwIOutQueuesH2PerformanceBandwidth
         Integer32
      }

pr1645v2EthPortSwIOutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIOutQueuesH2PerformanceEntry 10}

pr1645v2EthPortSwIOutQueuesH2PerformanceTableIx OBJECT-TYPE
   SYNTAX      TableIndex
   MAX-ACCESS  not-accessible
   STATUS      current
   DESCRIPTION
      ""
   ::= {pr1645v2EthPortSwIOutQueuesH2PerformanceEntry 11}

pr1645v2EthPortSwIOutQueuesH2PerformanceSysUpTime OBJECT-TYPE
   SYNTAX      TimeTicks
   MAX-ACCESS  read-only
   STATUS      current
   DESCRIPTION
      "Path: swPort.performance.ifOutPriorityQueues.h2Performance.sysUpTime

       Time in centi-second."
   ::= {pr1645v2EthPortSwIOutQueuesH2PerformanceEntry 16777216}

pr1645v2EthPortSwIOutQueuesH2PerformanceTotPkts OBJECT-TYPE
   SYNTAX      Counter64
   MAX-ACCESS  read-only
   STATUS      current
   DESCRIPTION
      "Path: swPort.performance.ifOutPriorityQueues.h2Performance.totalPkts

       64 bit unsigned wrappable counter."
   ::= {pr1645v2EthPortSwIOutQueuesH2PerformanceEntry 234881024}

pr1645v2EthPortSwIOutQueuesH2PerformanceDirTxPkts OBJECT-TYPE
   SYNTAX      Counter64
   MAX-ACCESS  read-only
   STATUS      current
   DESCRIPTION
      "Path: swPort.performance.ifOutPriorityQueues.h2Performance.directTxPkts

       64 bit unsigned wrappable counter."
   ::= {pr1645v2EthPortSwIOutQueuesH2PerformanceEntry 33554432}

pr1645v2EthPortSwIOutQueuesH2PerformanceQdPkts OBJECT-TYPE
   SYNTAX      Counter64
   MAX-ACCESS  read-only
   STATUS      current
   DESCRIPTION
      "Path: swPort.performance.ifOutPriorityQueues.h2Performance.queuedPkts

       64 bit unsigned wrappable counter."
   ::= {pr1645v2EthPortSwIOutQueuesH2PerformanceEntry 50331648}

pr1645v2EthPortSwIOutQueuesH2PerformanceDropPkts OBJECT-TYPE
   SYNTAX      Counter64
   MAX-ACCESS  read-only
   STATUS      current
   DESCRIPTION
      "Path: swPort.performance.ifOutPriorityQueues.h2Performance.droppedPkts

       64 bit unsigned wrappable counter."
   ::= {pr1645v2EthPortSwIOutQueuesH2PerformanceEntry 67108864}

pr1645v2EthPortSwIOutQueuesH2PerformanceRDropPkts OBJECT-TYPE
   SYNTAX      Counter64
   MAX-ACCESS  read-only
   STATUS      current
   DESCRIPTION
      "Path: swPort.performance.ifOutPriorityQueues.h2Performance.redDroppedPkts

       64 bit unsigned wrappable counter."
   ::= {pr1645v2EthPortSwIOutQueuesH2PerformanceEntry 201326592}

pr1645v2EthPortSwIOutQueuesH2PerformanceCirTxPkts OBJECT-TYPE
   SYNTAX      Counter64
   MAX-ACCESS  read-only
   STATUS      current
   DESCRIPTION
      "Path: swPort.performance.ifOutPriorityQueues.h2Performance.cirTxPkts

       64 bit unsigned wrappable counter."
   ::= {pr1645v2EthPortSwIOutQueuesH2PerformanceEntry 83886080}

pr1645v2EthPortSwIOutQueuesH2PerformanceEirTxPkts OBJECT-TYPE
   SYNTAX      Counter64
   MAX-ACCESS  read-only
   STATUS      current
   DESCRIPTION
      "Path: swPort.performance.ifOutPriorityQueues.h2Performance.eirTxPkts

       64 bit unsigned wrappable counter."
   ::= {pr1645v2EthPortSwIOutQueuesH2PerformanceEntry 100663296}

pr1645v2EthPortSwIOutQueuesH2PerformanceViolTxPkts OBJECT-TYPE
   SYNTAX      Counter64
   MAX-ACCESS  read-only
   STATUS      current
   DESCRIPTION
      "Path: swPort.performance.ifOutPriorityQueues.h2Performance.violateTxPkts

       64 bit unsigned wrappable counter."
   ::= {pr1645v2EthPortSwIOutQueuesH2PerformanceEntry 301989888}

pr1645v2EthPortSwIOutQueuesH2PerformanceTotOcts OBJECT-TYPE
   SYNTAX      Counter64
   MAX-ACCESS  read-only
   STATUS      current
   DESCRIPTION
      "Path: swPort.performance.ifOutPriorityQueues.h2Performance.totalOctets

       64 bit unsigned wrappable counter."
   ::= {pr1645v2EthPortSwIOutQueuesH2PerformanceEntry 251658240}

pr1645v2EthPortSwIOutQueuesH2PerformanceDirTxOcts OBJECT-TYPE
   SYNTAX      Counter64
   MAX-ACCESS  read-only
   STATUS      current
   DESCRIPTION
      "Path: swPort.performance.ifOutPriorityQueues.h2Performance.directTxOctets

       64 bit unsigned wrappable counter."
   ::= {pr1645v2EthPortSwIOutQueuesH2PerformanceEntry 117440512}

pr1645v2EthPortSwIOutQueuesH2PerformanceQdOcts OBJECT-TYPE
   SYNTAX      Counter64
   MAX-ACCESS  read-only
   STATUS      current
   DESCRIPTION
      "Path: swPort.performance.ifOutPriorityQueues.h2Performance.queuedOctets

       64 bit unsigned wrappable counter."
   ::= {pr1645v2EthPortSwIOutQueuesH2PerformanceEntry 134217728}

pr1645v2EthPortSwIOutQueuesH2PerformanceDropOcts OBJECT-TYPE
   SYNTAX      Counter64
   MAX-ACCESS  read-only
   STATUS      current
   DESCRIPTION
      "Path: swPort.performance.ifOutPriorityQueues.h2Performance.droppedOctets

       64 bit unsigned wrappable counter."
   ::= {pr1645v2EthPortSwIOutQueuesH2PerformanceEntry 150994944}

pr1645v2EthPortSwIOutQueuesH2PerformanceRDropOcts OBJECT-TYPE
   SYNTAX      Counter64
   MAX-ACCESS  read-only
   STATUS      current
   DESCRIPTION
      "Path: swPort.performance.ifOutPriorityQueues.h2Performance.redDroppedOctets

       64 bit unsigned wrappable counter."
   ::= {pr1645v2EthPortSwIOutQueuesH2PerformanceEntry 218103808}

pr1645v2EthPortSwIOutQueuesH2PerformanceCirTxOcts OBJECT-TYPE
   SYNTAX      Counter64
   MAX-ACCESS  read-only
   STATUS      current
   DESCRIPTION
      "Path: swPort.performance.ifOutPriorityQueues.h2Performance.cirTxOctets

       64 bit unsigned wrappable counter."
   ::= {pr1645v2EthPortSwIOutQueuesH2PerformanceEntry 167772160}

pr1645v2EthPortSwIOutQueuesH2PerformanceEirTxOcts OBJECT-TYPE
   SYNTAX      Counter64
   MAX-ACCESS  read-only
   STATUS      current
   DESCRIPTION
      "Path: swPort.performance.ifOutPriorityQueues.h2Performance.eirTxOctets

       64 bit unsigned wrappable counter."
   ::= {pr1645v2EthPortSwIOutQueuesH2PerformanceEntry 184549376}

pr1645v2EthPortSwIOutQueuesH2PerformanceViolTxOcts OBJECT-TYPE
   SYNTAX      Counter64
   MAX-ACCESS  read-only
   STATUS      current
   DESCRIPTION
      "Path: swPort.performance.ifOutPriorityQueues.h2Performance.violateTxOctets

       64 bit unsigned wrappable counter."
   ::= {pr1645v2EthPortSwIOutQueuesH2PerformanceEntry 318767104}

pr1645v2EthPortSwIOutQueuesH2PerformanceBandwidth OBJECT-TYPE
   SYNTAX      Integer32
   MAX-ACCESS  read-only
   STATUS      current
   DESCRIPTION
      "Path: swPort.performance.ifOutPriorityQueues.h2Performance.bandwidth

       unit name = bps
       formula = 8 * ; 8 /"
   ::= {pr1645v2EthPortSwIOutQueuesH2PerformanceEntry 268435456}

pr1645v2EthPortSwIOutQueuesH24Performance OBJECT-TYPE
   SYNTAX      SEQUENCE OF Pr1645v2EthPortSwIOutQueuesH24PerformanceEntry
   MAX-ACCESS  not-accessible
   STATUS      current
   DESCRIPTION
      ""
   ::= {pr1645v2EthPortSwIOutQueues 100663296}

pr1645v2EthPortSwIOutQueuesH24PerformanceEntry OBJECT-TYPE
   SYNTAX      Pr1645v2EthPortSwIOutQueuesH24PerformanceEntry
   MAX-ACCESS  not-accessible
   STATUS      current
   DESCRIPTION
      ""
   INDEX      { pr1645v2EthPortSwIOutQueuesH24PerformanceGlobalIx,
                pr1645v2EthPortSwIOutQueuesTableIx,
                pr1645v2EthPortSwIOutQueuesH24PerformanceTableIx }
   ::= {pr1645v2EthPortSwIOutQueuesH24Performance 1}

Pr1645v2EthPortSwIOutQueuesH24PerformanceEntry ::=
   SEQUENCE
      {
      pr1645v2EthPortSwIOutQueuesH24PerformanceGlobalIx
         GlobalIndex,
      pr1645v2EthPortSwIOutQueuesH24PerformanceTableIx
         TableIndex,
      pr1645v2EthPortSwIOutQueuesH24PerformanceSysUpTime
         TimeTicks,
      pr1645v2EthPortSwIOutQueuesH24PerformanceTotPkts
         Counter64,
      pr1645v2EthPortSwIOutQueuesH24PerformanceDirTxPkts
         Counter64,
      pr1645v2EthPortSwIOutQueuesH24PerformanceQdPkts
         Counter64,
      pr1645v2EthPortSwIOutQueuesH24PerformanceDropPkts
         Counter64,
      pr1645v2EthPortSwIOutQueuesH24PerformanceRDropPkts
         Counter64,
      pr1645v2EthPortSwIOutQueuesH24PerformanceCirTxPkts
         Counter64,
      pr1645v2EthPortSwIOutQueuesH24PerformanceEirTxPkts
         Counter64,
      pr1645v2EthPortSwIOutQueuesH24PerformanceViolTxPkts
         Counter64,
      pr1645v2EthPortSwIOutQueuesH24PerformanceTotOcts
         Counter64,
      pr1645v2EthPortSwIOutQueuesH24PerformanceDirTxOcts
         Counter64,
      pr1645v2EthPortSwIOutQueuesH24PerformanceQdOcts
         Counter64,
      pr1645v2EthPortSwIOutQueuesH24PerformanceDropOcts
         Counter64,
      pr1645v2EthPortSwIOutQueuesH24PerformanceRDropOcts
         Counter64,
      pr1645v2EthPortSwIOutQueuesH24PerformanceCirTxOcts
         Counter64,
      pr1645v2EthPortSwIOutQueuesH24PerformanceEirTxOcts
         Counter64,
      pr1645v2EthPortSwIOutQueuesH24PerformanceViolTxOcts
         Counter64,
      pr1645v2EthPortSwIOutQueuesH24PerformanceBandwidth
         Integer32
      }

pr1645v2EthPortSwIOutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIOutQueuesH24PerformanceEntry 10}

pr1645v2EthPortSwIOutQueuesH24PerformanceTableIx OBJECT-TYPE
   SYNTAX      TableIndex
   MAX-ACCESS  not-accessible
   STATUS      current
   DESCRIPTION
      ""
   ::= {pr1645v2EthPortSwIOutQueuesH24PerformanceEntry 11}

pr1645v2EthPortSwIOutQueuesH24PerformanceSysUpTime OBJECT-TYPE
   SYNTAX      TimeTicks
   MAX-ACCESS  read-only
   STATUS      current
   DESCRIPTION
      "Path: swPort.performance.ifOutPriorityQueues.h24Performance.sysUpTime

       Time in centi-second."
   ::= {pr1645v2EthPortSwIOutQueuesH24PerformanceEntry 16777216}

pr1645v2EthPortSwIOutQueuesH24PerformanceTotPkts OBJECT-TYPE
   SYNTAX      Counter64
   MAX-ACCESS  read-only
   STATUS      current
   DESCRIPTION
      "Path: swPort.performance.ifOutPriorityQueues.h24Performance.totalPkts

       64 bit unsigned wrappable counter."
   ::= {pr1645v2EthPortSwIOutQueuesH24PerformanceEntry 234881024}

pr1645v2EthPortSwIOutQueuesH24PerformanceDirTxPkts OBJECT-TYPE
   SYNTAX      Counter64
   MAX-ACCESS  read-only
   STATUS      current
   DESCRIPTION
      "Path: swPort.performance.ifOutPriorityQueues.h24Performance.directTxPkts

       64 bit unsigned wrappable counter."
   ::= {pr1645v2EthPortSwIOutQueuesH24PerformanceEntry 33554432}

pr1645v2EthPortSwIOutQueuesH24PerformanceQdPkts OBJECT-TYPE
   SYNTAX      Counter64
   MAX-ACCESS  read-only
   STATUS      current
   DESCRIPTION
      "Path: swPort.performance.ifOutPriorityQueues.h24Performance.queuedPkts

       64 bit unsigned wrappable counter."
   ::= {pr1645v2EthPortSwIOutQueuesH24PerformanceEntry 50331648}

pr1645v2EthPortSwIOutQueuesH24PerformanceDropPkts OBJECT-TYPE
   SYNTAX      Counter64
   MAX-ACCESS  read-only
   STATUS      current
   DESCRIPTION
      "Path: swPort.performance.ifOutPriorityQueues.h24Performance.droppedPkts

       64 bit unsigned wrappable counter."
   ::= {pr1645v2EthPortSwIOutQueuesH24PerformanceEntry 67108864}

pr1645v2EthPortSwIOutQueuesH24PerformanceRDropPkts OBJECT-TYPE
   SYNTAX      Counter64
   MAX-ACCESS  read-only
   STATUS      current
   DESCRIPTION
      "Path: swPort.performance.ifOutPriorityQueues.h24Performance.redDroppedPkts

       64 bit unsigned wrappable counter."
   ::= {pr1645v2EthPortSwIOutQueuesH24PerformanceEntry 201326592}

pr1645v2EthPortSwIOutQueuesH24PerformanceCirTxPkts OBJECT-TYPE
   SYNTAX      Counter64
   MAX-ACCESS  read-only
   STATUS      current
   DESCRIPTION
      "Path: swPort.performance.ifOutPriorityQueues.h24Performance.cirTxPkts

       64 bit unsigned wrappable counter."
   ::= {pr1645v2EthPortSwIOutQueuesH24PerformanceEntry 83886080}

pr1645v2EthPortSwIOutQueuesH24PerformanceEirTxPkts OBJECT-TYPE
   SYNTAX      Counter64
   MAX-ACCESS  read-only
   STATUS      current
   DESCRIPTION
      "Path: swPort.performance.ifOutPriorityQueues.h24Performance.eirTxPkts

       64 bit unsigned wrappable counter."
   ::= {pr1645v2EthPortSwIOutQueuesH24PerformanceEntry 100663296}

pr1645v2EthPortSwIOutQueuesH24PerformanceViolTxPkts OBJECT-TYPE
   SYNTAX      Counter64
   MAX-ACCESS  read-only
   STATUS      current
   DESCRIPTION
      "Path: swPort.performance.ifOutPriorityQueues.h24Performance.violateTxPkts

       64 bit unsigned wrappable counter."
   ::= {pr1645v2EthPortSwIOutQueuesH24PerformanceEntry 301989888}

pr1645v2EthPortSwIOutQueuesH24PerformanceTotOcts OBJECT-TYPE
   SYNTAX      Counter64
   MAX-ACCESS  read-only
   STATUS      current
   DESCRIPTION
      "Path: swPort.performance.ifOutPriorityQueues.h24Performance.totalOctets

       64 bit unsigned wrappable counter."
   ::= {pr1645v2EthPortSwIOutQueuesH24PerformanceEntry 251658240}

pr1645v2EthPortSwIOutQueuesH24PerformanceDirTxOcts OBJECT-TYPE
   SYNTAX      Counter64
   MAX-ACCESS  read-only
   STATUS      current
   DESCRIPTION
      "Path: swPort.performance.ifOutPriorityQueues.h24Performance.directTxOctets

       64 bit unsigned wrappable counter."
   ::= {pr1645v2EthPortSwIOutQueuesH24PerformanceEntry 117440512}

pr1645v2EthPortSwIOutQueuesH24PerformanceQdOcts OBJECT-TYPE
   SYNTAX      Counter64
   MAX-ACCESS  read-only
   STATUS      current
   DESCRIPTION
      "Path: swPort.performance.ifOutPriorityQueues.h24Performance.queuedOctets

       64 bit unsigned wrappable counter."
   ::= {pr1645v2EthPortSwIOutQueuesH24PerformanceEntry 134217728}

pr1645v2EthPortSwIOutQueuesH24PerformanceDropOcts OBJECT-TYPE
   SYNTAX      Counter64
   MAX-ACCESS  read-only
   STATUS      current
   DESCRIPTION
      "Path: swPort.performance.ifOutPriorityQueues.h24Performance.droppedOctets

       64 bit unsigned wrappable counter."
   ::= {pr1645v2EthPortSwIOutQueuesH24PerformanceEntry 150994944}

pr1645v2EthPortSwIOutQueuesH24PerformanceRDropOcts OBJECT-TYPE
   SYNTAX      Counter64
   MAX-ACCESS  read-only
   STATUS      current
   DESCRIPTION
      "Path: swPort.performance.ifOutPriorityQueues.h24Performance.redDroppedOctets

       64 bit unsigned wrappable counter."
   ::= {pr1645v2EthPortSwIOutQueuesH24PerformanceEntry 218103808}

pr1645v2EthPortSwIOutQueuesH24PerformanceCirTxOcts OBJECT-TYPE
   SYNTAX      Counter64
   MAX-ACCESS  read-only
   STATUS      current
   DESCRIPTION
      "Path: swPort.performance.ifOutPriorityQueues.h24Performance.cirTxOctets

       64 bit unsigned wrappable counter."
   ::= {pr1645v2EthPortSwIOutQueuesH24PerformanceEntry 167772160}

pr1645v2EthPortSwIOutQueuesH24PerformanceEirTxOcts OBJECT-TYPE
   SYNTAX      Counter64
   MAX-ACCESS  read-only
   STATUS      current
   DESCRIPTION
      "Path: swPort.performance.ifOutPriorityQueues.h24Performance.eirTxOctets

       64 bit unsigned wrappable counter."
   ::= {pr1645v2EthPortSwIOutQueuesH24PerformanceEntry 184549376}

pr1645v2EthPortSwIOutQueuesH24PerformanceViolTxOcts OBJECT-TYPE
   SYNTAX      Counter64
   MAX-ACCESS  read-only
   STATUS      current
   DESCRIPTION
      "Path: swPort.performance.ifOutPriorityQueues.h24Performance.violateTxOctets

       64 bit unsigned wrappable counter."
   ::= {pr1645v2EthPortSwIOutQueuesH24PerformanceEntry 318767104}

pr1645v2EthPortSwIOutQueuesH24PerformanceBandwidth OBJECT-TYPE
   SYNTAX      Integer32
   MAX-ACCESS  read-only
   STATUS      current
   DESCRIPTION
      "Path: swPort.performance.ifOutPriorityQueues.h24Performance.bandwidth

       unit name = bps
       formula = 8 * ; 8 /"
   ::= {pr1645v2EthPortSwIOutQueuesH24PerformanceEntry 268435456}

pr1645v2EthPortSwIOutQueuesD7Performance OBJECT-TYPE
   SYNTAX      SEQUENCE OF Pr1645v2EthPortSwIOutQueuesD7PerformanceEntry
   MAX-ACCESS  not-accessible
   STATUS      current
   DESCRIPTION
      ""
   ::= {pr1645v2EthPortSwIOutQueues 117440512}

pr1645v2EthPortSwIOutQueuesD7PerformanceEntry OBJECT-TYPE
   SYNTAX      Pr1645v2EthPortSwIOutQueuesD7PerformanceEntry
   MAX-ACCESS  not-accessible
   STATUS      current
   DESCRIPTION
      ""
   INDEX      { pr1645v2EthPortSwIOutQueuesD7PerformanceGlobalIx,
                pr1645v2EthPortSwIOutQueuesTableIx,
                pr1645v2EthPortSwIOutQueuesD7PerformanceTableIx }
   ::= {pr1645v2EthPortSwIOutQueuesD7Performance 1}

Pr1645v2EthPortSwIOutQueuesD7PerformanceEntry ::=
   SEQUENCE
      {
      pr1645v2EthPortSwIOutQueuesD7PerformanceGlobalIx
         GlobalIndex,
      pr1645v2EthPortSwIOutQueuesD7PerformanceTableIx
         TableIndex,
      pr1645v2EthPortSwIOutQueuesD7PerformanceSysUpTime
         TimeTicks,
      pr1645v2EthPortSwIOutQueuesD7PerformanceTotPkts
         Counter64,
      pr1645v2EthPortSwIOutQueuesD7PerformanceDirTxPkts
         Counter64,
      pr1645v2EthPortSwIOutQueuesD7PerformanceQdPkts
         Counter64,
      pr1645v2EthPortSwIOutQueuesD7PerformanceDropPkts
         Counter64,
      pr1645v2EthPortSwIOutQueuesD7PerformanceRDropPkts
         Counter64,
      pr1645v2EthPortSwIOutQueuesD7PerformanceCirTxPkts
         Counter64,
      pr1645v2EthPortSwIOutQueuesD7PerformanceEirTxPkts
         Counter64,
      pr1645v2EthPortSwIOutQueuesD7PerformanceViolTxPkts
         Counter64,
      pr1645v2EthPortSwIOutQueuesD7PerformanceTotOcts
         Counter64,
      pr1645v2EthPortSwIOutQueuesD7PerformanceDirTxOcts
         Counter64,
      pr1645v2EthPortSwIOutQueuesD7PerformanceQdOcts
         Counter64,
      pr1645v2EthPortSwIOutQueuesD7PerformanceDropOcts
         Counter64,
      pr1645v2EthPortSwIOutQueuesD7PerformanceRDropOcts
         Counter64,
      pr1645v2EthPortSwIOutQueuesD7PerformanceCirTxOcts
         Counter64,
      pr1645v2EthPortSwIOutQueuesD7PerformanceEirTxOcts
         Counter64,
      pr1645v2EthPortSwIOutQueuesD7PerformanceViolTxOcts
         Counter64,
      pr1645v2EthPortSwIOutQueuesD7PerformanceBandwidth
         Integer32
      }

pr1645v2EthPortSwIOutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIOutQueuesD7PerformanceEntry 10}

pr1645v2EthPortSwIOutQueuesD7PerformanceTableIx OBJECT-TYPE
   SYNTAX      TableIndex
   MAX-ACCESS  not-accessible
   STATUS      current
   DESCRIPTION
      ""
   ::= {pr1645v2EthPortSwIOutQueuesD7PerformanceEntry 11}

pr1645v2EthPortSwIOutQueuesD7PerformanceSysUpTime OBJECT-TYPE
   SYNTAX      TimeTicks
   MAX-ACCESS  read-only
   STATUS      current
   DESCRIPTION
      "Path: swPort.performance.ifOutPriorityQueues.d7Performance.sysUpTime

       Time in centi-second."
   ::= {pr1645v2EthPortSwIOutQueuesD7PerformanceEntry 16777216}

pr1645v2EthPortSwIOutQueuesD7PerformanceTotPkts OBJECT-TYPE
   SYNTAX      Counter64
   MAX-ACCESS  read-only
   STATUS      current
   DESCRIPTION
      "Path: swPort.performance.ifOutPriorityQueues.d7Performance.totalPkts

       64 bit unsigned wrappable counter."
   ::= {pr1645v2EthPortSwIOutQueuesD7PerformanceEntry 234881024}

pr1645v2EthPortSwIOutQueuesD7PerformanceDirTxPkts OBJECT-TYPE
   SYNTAX      Counter64
   MAX-ACCESS  read-only
   STATUS      current
   DESCRIPTION
      "Path: swPort.performance.ifOutPriorityQueues.d7Performance.directTxPkts

       64 bit unsigned wrappable counter."
   ::= {pr1645v2EthPortSwIOutQueuesD7PerformanceEntry 33554432}

pr1645v2EthPortSwIOutQueuesD7PerformanceQdPkts OBJECT-TYPE
   SYNTAX      Counter64
   MAX-ACCESS  read-only
   STATUS      current
   DESCRIPTION
      "Path: swPort.performance.ifOutPriorityQueues.d7Performance.queuedPkts

       64 bit unsigned wrappable counter."
   ::= {pr1645v2EthPortSwIOutQueuesD7PerformanceEntry 50331648}

pr1645v2EthPortSwIOutQueuesD7PerformanceDropPkts OBJECT-TYPE
   SYNTAX      Counter64
   MAX-ACCESS  read-only
   STATUS      current
   DESCRIPTION
      "Path: swPort.performance.ifOutPriorityQueues.d7Performance.droppedPkts

       64 bit unsigned wrappable counter."
   ::= {pr1645v2EthPortSwIOutQueuesD7PerformanceEntry 67108864}

pr1645v2EthPortSwIOutQueuesD7PerformanceRDropPkts OBJECT-TYPE
   SYNTAX      Counter64
   MAX-ACCESS  read-only
   STATUS      current
   DESCRIPTION
      "Path: swPort.performance.ifOutPriorityQueues.d7Performance.redDroppedPkts

       64 bit unsigned wrappable counter."
   ::= {pr1645v2EthPortSwIOutQueuesD7PerformanceEntry 201326592}

pr1645v2EthPortSwIOutQueuesD7PerformanceCirTxPkts OBJECT-TYPE
   SYNTAX      Counter64
   MAX-ACCESS  read-only
   STATUS      current
   DESCRIPTION
      "Path: swPort.performance.ifOutPriorityQueues.d7Performance.cirTxPkts

       64 bit unsigned wrappable counter."
   ::= {pr1645v2EthPortSwIOutQueuesD7PerformanceEntry 83886080}

pr1645v2EthPortSwIOutQueuesD7PerformanceEirTxPkts OBJECT-TYPE
   SYNTAX      Counter64
   MAX-ACCESS  read-only
   STATUS      current
   DESCRIPTION
      "Path: swPort.performance.ifOutPriorityQueues.d7Performance.eirTxPkts

       64 bit unsigned wrappable counter."
   ::= {pr1645v2EthPortSwIOutQueuesD7PerformanceEntry 100663296}

pr1645v2EthPortSwIOutQueuesD7PerformanceViolTxPkts OBJECT-TYPE
   SYNTAX      Counter64
   MAX-ACCESS  read-only
   STATUS      current
   DESCRIPTION
      "Path: swPort.performance.ifOutPriorityQueues.d7Performance.violateTxPkts

       64 bit unsigned wrappable counter."
   ::= {pr1645v2EthPortSwIOutQueuesD7PerformanceEntry 301989888}

pr1645v2EthPortSwIOutQueuesD7PerformanceTotOcts OBJECT-TYPE
   SYNTAX      Counter64
   MAX-ACCESS  read-only
   STATUS      current
   DESCRIPTION
      "Path: swPort.performance.ifOutPriorityQueues.d7Performance.totalOctets

       64 bit unsigned wrappable counter."
   ::= {pr1645v2EthPortSwIOutQueuesD7PerformanceEntry 251658240}

pr1645v2EthPortSwIOutQueuesD7PerformanceDirTxOcts OBJECT-TYPE
   SYNTAX      Counter64
   MAX-ACCESS  read-only
   STATUS      current
   DESCRIPTION
      "Path: swPort.performance.ifOutPriorityQueues.d7Performance.directTxOctets

       64 bit unsigned wrappable counter."
   ::= {pr1645v2EthPortSwIOutQueuesD7PerformanceEntry 117440512}

pr1645v2EthPortSwIOutQueuesD7PerformanceQdOcts OBJECT-TYPE
   SYNTAX      Counter64
   MAX-ACCESS  read-only
   STATUS      current
   DESCRIPTION
      "Path: swPort.performance.ifOutPriorityQueues.d7Performance.queuedOctets

       64 bit unsigned wrappable counter."
   ::= {pr1645v2EthPortSwIOutQueuesD7PerformanceEntry 134217728}

pr1645v2EthPortSwIOutQueuesD7PerformanceDropOcts OBJECT-TYPE
   SYNTAX      Counter64
   MAX-ACCESS  read-only
   STATUS      current
   DESCRIPTION
      "Path: swPort.performance.ifOutPriorityQueues.d7Performance.droppedOctets

       64 bit unsigned wrappable counter."
   ::= {pr1645v2EthPortSwIOutQueuesD7PerformanceEntry 150994944}

pr1645v2EthPortSwIOutQueuesD7PerformanceRDropOcts OBJECT-TYPE
   SYNTAX      Counter64
   MAX-ACCESS  read-only
   STATUS      current
   DESCRIPTION
      "Path: swPort.performance.ifOutPriorityQueues.d7Performance.redDroppedOctets

       64 bit unsigned wrappable counter."
   ::= {pr1645v2EthPortSwIOutQueuesD7PerformanceEntry 218103808}

pr1645v2EthPortSwIOutQueuesD7PerformanceCirTxOcts OBJECT-TYPE
   SYNTAX      Counter64
   MAX-ACCESS  read-only
   STATUS      current
   DESCRIPTION
      "Path: swPort.performance.ifOutPriorityQueues.d7Performance.cirTxOctets

       64 bit unsigned wrappable counter."
   ::= {pr1645v2EthPortSwIOutQueuesD7PerformanceEntry 167772160}

pr1645v2EthPortSwIOutQueuesD7PerformanceEirTxOcts OBJECT-TYPE
   SYNTAX      Counter64
   MAX-ACCESS  read-only
   STATUS      current
   DESCRIPTION
      "Path: swPort.performance.ifOutPriorityQueues.d7Performance.eirTxOctets

       64 bit unsigned wrappable counter."
   ::= {pr1645v2EthPortSwIOutQueuesD7PerformanceEntry 184549376}

pr1645v2EthPortSwIOutQueuesD7PerformanceViolTxOcts OBJECT-TYPE
   SYNTAX      Counter64
   MAX-ACCESS  read-only
   STATUS      current
   DESCRIPTION
      "Path: swPort.performance.ifOutPriorityQueues.d7Performance.violateTxOctets

       64 bit unsigned wrappable counter."
   ::= {pr1645v2EthPortSwIOutQueuesD7PerformanceEntry 318767104}

pr1645v2EthPortSwIOutQueuesD7PerformanceBandwidth OBJECT-TYPE
   SYNTAX      Integer32
   MAX-ACCESS  read-only
   STATUS      current
   DESCRIPTION
      "Path: swPort.performance.ifOutPriorityQueues.d7Performance.bandwidth

       unit name = bps
       formula = 8 * ; 8 /"
   ::= {pr1645v2EthPortSwIOutQueuesD7PerformanceEntry 268435456}


pr1645v2EthPortSwIOutBandwidth OBJECT IDENTIFIER ::= {pr1645v2EthPortSwI 182}

pr1645v2EthPortSwIOutBandwidthSSCTable OBJECT-TYPE
   SYNTAX      SEQUENCE OF Pr1645v2EthPortSwIOutBandwidthEntry
   MAX-ACCESS  not-accessible
   STATUS      current
   DESCRIPTION
      "bandwidth"
   ::= {pr1645v2EthPortSwIOutBandwidth 1}

pr1645v2EthPortSwIOutBandwidthEntry OBJECT-TYPE
   SYNTAX      Pr1645v2EthPortSwIOutBandwidthEntry
   MAX-ACCESS  not-accessible
   STATUS      current
   DESCRIPTION
      ""
   INDEX      { pr1645v2EthPortSwIOutBandwidthGlobalIx }
   ::= {pr1645v2EthPortSwIOutBandwidthSSCTable 1}

Pr1645v2EthPortSwIOutBandwidthEntry ::=
   SEQUENCE
      {
      pr1645v2EthPortSwIOutBandwidthGlobalIx
         GlobalIndex,
      pr1645v2EthPortSwIOutBandwidth15sec
         Integer32,
      pr1645v2EthPortSwIOutBandwidth30sec
         Integer32,
      pr1645v2EthPortSwIOutBandwidth1min
         Integer32,
      pr1645v2EthPortSwIOutBandwidth2min
         Integer32,
      pr1645v2EthPortSwIOutBandwidth5min
         Integer32
      }

pr1645v2EthPortSwIOutBandwidthGlobalIx OBJECT-TYPE
   SYNTAX      GlobalIndex
   MAX-ACCESS  not-accessible
   STATUS      current
   DESCRIPTION
      "The value of the tlsCntTreeGlobalIndex of the MANAGED OBJECT."
   ::= {pr1645v2EthPortSwIOutBandwidthEntry 10}

pr1645v2EthPortSwIOutBandwidth15sec OBJECT-TYPE
   SYNTAX      Integer32
   MAX-ACCESS  read-only
   STATUS      current
   DESCRIPTION
      "Path: swPort.performance.ifOutBandwidth.15sec

       unit name = bps
       formula = 8 * ; 8 /"
   ::= {pr1645v2EthPortSwIOutBandwidthEntry 83886080}

pr1645v2EthPortSwIOutBandwidth30sec OBJECT-TYPE
   SYNTAX      Integer32
   MAX-ACCESS  read-only
   STATUS      current
   DESCRIPTION
      "Path: swPort.performance.ifOutBandwidth.30sec

       unit name = bps
       formula = 8 * ; 8 /"
   ::= {pr1645v2EthPortSwIOutBandwidthEntry 167772160}

pr1645v2EthPortSwIOutBandwidth1min OBJECT-TYPE
   SYNTAX      Integer32
   MAX-ACCESS  read-only
   STATUS      current
   DESCRIPTION
      "Path: swPort.performance.ifOutBandwidth.1min

       unit name = bps
       formula = 8 * ; 8 /"
   ::= {pr1645v2EthPortSwIOutBandwidthEntry 335544320}

pr1645v2EthPortSwIOutBandwidth2min OBJECT-TYPE
   SYNTAX      Integer32
   MAX-ACCESS  read-only
   STATUS      current
   DESCRIPTION
      "Path: swPort.performance.ifOutBandwidth.2min

       unit name = bps
       formula = 8 * ; 8 /"
   ::= {pr1645v2EthPortSwIOutBandwidthEntry 671088640}

pr1645v2EthPortSwIOutBandwidth5min OBJECT-TYPE
   SYNTAX      Integer32
   MAX-ACCESS  read-only
   STATUS      current
   DESCRIPTION
      "Path: swPort.performance.ifOutBandwidth.5min

       unit name = bps
       formula = 8 * ; 8 /"
   ::= {pr1645v2EthPortSwIOutBandwidthEntry 1677721600}


pr1645v2EthPortSwIInP OBJECT IDENTIFIER ::= {pr1645v2EthPortSwI 307}

pr1645v2EthPortSwIInPSSCTable OBJECT-TYPE
   SYNTAX      SEQUENCE OF Pr1645v2EthPortSwIInPEntry
   MAX-ACCESS  not-accessible
   STATUS      current
   DESCRIPTION
      "h2IfInPerformance"
   ::= {pr1645v2EthPortSwIInP 1}

pr1645v2EthPortSwIInPEntry OBJECT-TYPE
   SYNTAX      Pr1645v2EthPortSwIInPEntry
   MAX-ACCESS  not-accessible
   STATUS      current
   DESCRIPTION
      ""
   INDEX      { pr1645v2EthPortSwIInPGlobalIx,
                pr1645v2EthPortSwIInPTableIx }
   ::= {pr1645v2EthPortSwIInPSSCTable 1}

Pr1645v2EthPortSwIInPEntry ::=
   SEQUENCE
      {
      pr1645v2EthPortSwIInPGlobalIx
         GlobalIndex,
      pr1645v2EthPortSwIInPTableIx
         TableIndex,
      pr1645v2EthPortSwIInPSysUpTime
         TimeTicks,
      pr1645v2EthPortSwIInPIfUpTime
         TimeTicks,
      pr1645v2EthPortSwIInPIfStatChanges
         Counter32,
      pr1645v2EthPortSwIInPIfInOctets
         Counter64,
      pr1645v2EthPortSwIInPIfInUCPkts
         Counter64,
      pr1645v2EthPortSwIInPIfInNUCPkts
         Counter64,
      pr1645v2EthPortSwIInPIfInBCPkts
         Counter64,
      pr1645v2EthPortSwIInPIfInMCPkts
         Counter64,
      pr1645v2EthPortSwIInPIfInDiscards
         Counter64,
      pr1645v2EthPortSwIInPIfInErrors
         Counter64,
      pr1645v2EthPortSwIInPIfInUnkwn
         Counter64,
      pr1645v2EthPortSwIInPInDropEx
         Counter64,
      pr1645v2EthPortSwIInPInDropNoMac
         Counter64,
      pr1645v2EthPortSwIInPInDropNUCast
         Counter64,
      pr1645v2EthPortSwIInPInDropFilter
         Counter64,
      pr1645v2EthPortSwIInPIfInBandwidth
         Integer32,
      pr1645v2EthPortSwIInPIfOutOctets
         Counter64,
      pr1645v2EthPortSwIInPIfOutUCPkts
         Counter64,
      pr1645v2EthPortSwIInPIfOutNUCPkts
         Counter64,
      pr1645v2EthPortSwIInPIfOutBCPkts
         Counter64,
      pr1645v2EthPortSwIInPIfOutMCPkts
         Counter64,
      pr1645v2EthPortSwIInPIfOutDiscards
         Counter64,
      pr1645v2EthPortSwIInPIfOutErrors
         Counter64,
      pr1645v2EthPortSwIInPOutDropEx
         Counter64,
      pr1645v2EthPortSwIInPOutDropNoArp
         Counter64,
      pr1645v2EthPortSwIInPOutDropFilter
         Counter64,
      pr1645v2EthPortSwIInPIfOutBandwidth
         Integer32,
      pr1645v2EthPortSwIInPIfErrSec
         Counter32
      }

pr1645v2EthPortSwIInPGlobalIx OBJECT-TYPE
   SYNTAX      GlobalIndex
   MAX-ACCESS  not-accessible
   STATUS      current
   DESCRIPTION
      "The value of the tlsCntTreeGlobalIndex of the MANAGED OBJECT."
   ::= {pr1645v2EthPortSwIInPEntry 10}

pr1645v2EthPortSwIInPTableIx OBJECT-TYPE
   SYNTAX      TableIndex
   MAX-ACCESS  not-accessible
   STATUS      current
   DESCRIPTION
      ""
   ::= {pr1645v2EthPortSwIInPEntry 11}

pr1645v2EthPortSwIInPSysUpTime OBJECT-TYPE
   SYNTAX      TimeTicks
   MAX-ACCESS  read-only
   STATUS      current
   DESCRIPTION
      "Path: swPort.performance.h2Performance.sysUpTime

       Time in centi-second."
   ::= {pr1645v2EthPortSwIInPEntry 16777216}

pr1645v2EthPortSwIInPIfUpTime OBJECT-TYPE
   SYNTAX      TimeTicks
   MAX-ACCESS  read-only
   STATUS      current
   DESCRIPTION
      "Path: swPort.performance.h2Performance.ifUpTime

       Time in centi-second."
   ::= {pr1645v2EthPortSwIInPEntry 33554432}

pr1645v2EthPortSwIInPIfStatChanges OBJECT-TYPE
   SYNTAX      Counter32
   MAX-ACCESS  read-only
   STATUS      current
   DESCRIPTION
      "Path: swPort.performance.h2Performance.ifStatusChanges

       32 bit unsigned wrappable counter."
   ::= {pr1645v2EthPortSwIInPEntry 50331648}

pr1645v2EthPortSwIInPIfInOctets OBJECT-TYPE
   SYNTAX      Counter64
   MAX-ACCESS  read-only
   STATUS      current
   DESCRIPTION
      "Path: swPort.performance.h2Performance.ifInOctets

       64 bit unsigned wrappable counter."
   ::= {pr1645v2EthPortSwIInPEntry 67108864}

pr1645v2EthPortSwIInPIfInUCPkts OBJECT-TYPE
   SYNTAX      Counter64
   MAX-ACCESS  read-only
   STATUS      current
   DESCRIPTION
      "Path: swPort.performance.h2Performance.ifInUcastPkts

       64 bit unsigned wrappable counter."
   ::= {pr1645v2EthPortSwIInPEntry 83886080}

pr1645v2EthPortSwIInPIfInNUCPkts OBJECT-TYPE
   SYNTAX      Counter64
   MAX-ACCESS  read-only
   STATUS      current
   DESCRIPTION
      "Path: swPort.performance.h2Performance.ifInNUcastPkts

       64 bit unsigned wrappable counter."
   ::= {pr1645v2EthPortSwIInPEntry 100663296}

pr1645v2EthPortSwIInPIfInBCPkts OBJECT-TYPE
   SYNTAX      Counter64
   MAX-ACCESS  read-only
   STATUS      current
   DESCRIPTION
      "Path: swPort.performance.h2Performance.ifInBcastPkts

       64 bit unsigned wrappable counter."
   ::= {pr1645v2EthPortSwIInPEntry 419430400}

pr1645v2EthPortSwIInPIfInMCPkts OBJECT-TYPE
   SYNTAX      Counter64
   MAX-ACCESS  read-only
   STATUS      current
   DESCRIPTION
      "Path: swPort.performance.h2Performance.ifInMcastPkts

       64 bit unsigned wrappable counter."
   ::= {pr1645v2EthPortSwIInPEntry 436207616}

pr1645v2EthPortSwIInPIfInDiscards OBJECT-TYPE
   SYNTAX      Counter64
   MAX-ACCESS  read-only
   STATUS      current
   DESCRIPTION
      "Path: swPort.performance.h2Performance.ifInDiscards

       64 bit unsigned wrappable counter."
   ::= {pr1645v2EthPortSwIInPEntry 117440512}

pr1645v2EthPortSwIInPIfInErrors OBJECT-TYPE
   SYNTAX      Counter64
   MAX-ACCESS  read-only
   STATUS      current
   DESCRIPTION
      "Path: swPort.performance.h2Performance.ifInErrors

       64 bit unsigned wrappable counter."
   ::= {pr1645v2EthPortSwIInPEntry 134217728}

pr1645v2EthPortSwIInPIfInUnkwn OBJECT-TYPE
   SYNTAX      Counter64
   MAX-ACCESS  read-only
   STATUS      current
   DESCRIPTION
      "Path: swPort.performance.h2Performance.ifInUnknownProtos

       64 bit unsigned wrappable counter."
   ::= {pr1645v2EthPortSwIInPEntry 150994944}

pr1645v2EthPortSwIInPInDropEx OBJECT-TYPE
   SYNTAX      Counter64
   MAX-ACCESS  read-only
   STATUS      current
   DESCRIPTION
      "Path: swPort.performance.h2Performance.ifInDropLevelExceeded

       64 bit unsigned wrappable counter."
   ::= {pr1645v2EthPortSwIInPEntry 335544320}

pr1645v2EthPortSwIInPInDropNoMac OBJECT-TYPE
   SYNTAX      Counter64
   MAX-ACCESS  read-only
   STATUS      current
   DESCRIPTION
      "Path: swPort.performance.h2Performance.fInDiscardsNoMacFit

       64 bit unsigned wrappable counter."
   ::= {pr1645v2EthPortSwIInPEntry 301989888}

pr1645v2EthPortSwIInPInDropNUCast OBJECT-TYPE
   SYNTAX      Counter64
   MAX-ACCESS  read-only
   STATUS      current
   DESCRIPTION
      "Path: swPort.performance.h2Performance.fInDiscardsNUCast

       64 bit unsigned wrappable counter."
   ::= {pr1645v2EthPortSwIInPEntry 318767104}

pr1645v2EthPortSwIInPInDropFilter OBJECT-TYPE
   SYNTAX      Counter64
   MAX-ACCESS  read-only
   STATUS      current
   DESCRIPTION
      "Path: swPort.performance.h2Performance.fInDiscardsFilter

       64 bit unsigned wrappable counter."
   ::= {pr1645v2EthPortSwIInPEntry 385875968}

pr1645v2EthPortSwIInPIfInBandwidth OBJECT-TYPE
   SYNTAX      Integer32
   MAX-ACCESS  read-only
   STATUS      current
   DESCRIPTION
      "Path: swPort.performance.h2Performance.ifInBandwidth

       unit name = bps
       formula = 8 * ; 8 /"
   ::= {pr1645v2EthPortSwIInPEntry 268435456}

pr1645v2EthPortSwIInPIfOutOctets OBJECT-TYPE
   SYNTAX      Counter64
   MAX-ACCESS  read-only
   STATUS      current
   DESCRIPTION
      "Path: swPort.performance.h2Performance.ifOutOctets

       64 bit unsigned wrappable counter."
   ::= {pr1645v2EthPortSwIInPEntry 167772160}

pr1645v2EthPortSwIInPIfOutUCPkts OBJECT-TYPE
   SYNTAX      Counter64
   MAX-ACCESS  read-only
   STATUS      current
   DESCRIPTION
      "Path: swPort.performance.h2Performance.ifOutUcastPkts

       64 bit unsigned wrappable counter."
   ::= {pr1645v2EthPortSwIInPEntry 184549376}

pr1645v2EthPortSwIInPIfOutNUCPkts OBJECT-TYPE
   SYNTAX      Counter64
   MAX-ACCESS  read-only
   STATUS      current
   DESCRIPTION
      "Path: swPort.performance.h2Performance.ifOutNUcastPkts

       64 bit unsigned wrappable counter."
   ::= {pr1645v2EthPortSwIInPEntry 201326592}

pr1645v2EthPortSwIInPIfOutBCPkts OBJECT-TYPE
   SYNTAX      Counter64
   MAX-ACCESS  read-only
   STATUS      current
   DESCRIPTION
      "Path: swPort.performance.h2Performance.ifOutBcastPkts

       64 bit unsigned wrappable counter."
   ::= {pr1645v2EthPortSwIInPEntry 452984832}

pr1645v2EthPortSwIInPIfOutMCPkts OBJECT-TYPE
   SYNTAX      Counter64
   MAX-ACCESS  read-only
   STATUS      current
   DESCRIPTION
      "Path: swPort.performance.h2Performance.ifOutMcastPkts

       64 bit unsigned wrappable counter."
   ::= {pr1645v2EthPortSwIInPEntry 469762048}

pr1645v2EthPortSwIInPIfOutDiscards OBJECT-TYPE
   SYNTAX      Counter64
   MAX-ACCESS  read-only
   STATUS      current
   DESCRIPTION
      "Path: swPort.performance.h2Performance.ifOutDiscards

       64 bit unsigned wrappable counter."
   ::= {pr1645v2EthPortSwIInPEntry 218103808}

pr1645v2EthPortSwIInPIfOutErrors OBJECT-TYPE
   SYNTAX      Counter64
   MAX-ACCESS  read-only
   STATUS      current
   DESCRIPTION
      "Path: swPort.performance.h2Performance.ifOutErrors

       64 bit unsigned wrappable counter."
   ::= {pr1645v2EthPortSwIInPEntry 234881024}

pr1645v2EthPortSwIInPOutDropEx OBJECT-TYPE
   SYNTAX      Counter64
   MAX-ACCESS  read-only
   STATUS      current
   DESCRIPTION
      "Path: swPort.performance.h2Performance.ifOutDropLevelExceeded

       64 bit unsigned wrappable counter."
   ::= {pr1645v2EthPortSwIInPEntry 352321536}

pr1645v2EthPortSwIInPOutDropNoArp OBJECT-TYPE
   SYNTAX      Counter64
   MAX-ACCESS  read-only
   STATUS      current
   DESCRIPTION
      "Path: swPort.performance.h2Performance.ifOutDiscardsNoArp

       64 bit unsigned wrappable counter."
   ::= {pr1645v2EthPortSwIInPEntry 369098752}

pr1645v2EthPortSwIInPOutDropFilter OBJECT-TYPE
   SYNTAX      Counter64
   MAX-ACCESS  read-only
   STATUS      current
   DESCRIPTION
      "Path: swPort.performance.h2Performance.ifOutDiscardsFilter

       64 bit unsigned wrappable counter."
   ::= {pr1645v2EthPortSwIInPEntry 402653184}

pr1645v2EthPortSwIInPIfOutBandwidth OBJECT-TYPE
   SYNTAX      Integer32
   MAX-ACCESS  read-only
   STATUS      current
   DESCRIPTION
      "Path: swPort.performance.h2Performance.ifOutBandwidth

       unit name = bps
       formula = 8 * ; 8 /"
   ::= {pr1645v2EthPortSwIInPEntry 285212672}

pr1645v2EthPortSwIInPIfErrSec OBJECT-TYPE
   SYNTAX      Counter32
   MAX-ACCESS  read-only
   STATUS      current
   DESCRIPTION
      "Path: swPort.performance.h2Performance.ifErrSec

       32 bit unsigned wrappable counter."
   ::= {pr1645v2EthPortSwIInPEntry 251658240}


pr1645v2EthPortSwIH24InP OBJECT IDENTIFIER ::= {pr1645v2EthPortSwI 308}

pr1645v2EthPortSwIH24InPSSCTable OBJECT-TYPE
   SYNTAX      SEQUENCE OF Pr1645v2EthPortSwIH24InPEntry
   MAX-ACCESS  not-accessible
   STATUS      current
   DESCRIPTION
      "h24IfInPerformance"
   ::= {pr1645v2EthPortSwIH24InP 1}

pr1645v2EthPortSwIH24InPEntry OBJECT-TYPE
   SYNTAX      Pr1645v2EthPortSwIH24InPEntry
   MAX-ACCESS  not-accessible
   STATUS      current
   DESCRIPTION
      ""
   INDEX      { pr1645v2EthPortSwIH24InPGlobalIx,
                pr1645v2EthPortSwIH24InPTableIx }
   ::= {pr1645v2EthPortSwIH24InPSSCTable 1}

Pr1645v2EthPortSwIH24InPEntry ::=
   SEQUENCE
      {
      pr1645v2EthPortSwIH24InPGlobalIx
         GlobalIndex,
      pr1645v2EthPortSwIH24InPTableIx
         TableIndex,
      pr1645v2EthPortSwIH24InPSysUpTime
         TimeTicks,
      pr1645v2EthPortSwIH24InPIfUpTime
         TimeTicks,
      pr1645v2EthPortSwIH24InPIfStatChanges
         Counter32,
      pr1645v2EthPortSwIH24InPIfInOctets
         Counter64,
      pr1645v2EthPortSwIH24InPIfInUCPkts
         Counter64,
      pr1645v2EthPortSwIH24InPIfInNUCPkts
         Counter64,
      pr1645v2EthPortSwIH24InPIfInBCPkts
         Counter64,
      pr1645v2EthPortSwIH24InPIfInMCPkts
         Counter64,
      pr1645v2EthPortSwIH24InPIfInDiscards
         Counter64,
      pr1645v2EthPortSwIH24InPIfInErrors
         Counter64,
      pr1645v2EthPortSwIH24InPIfInUnkwn
         Counter64,
      pr1645v2EthPortSwIH24InPInDropEx
         Counter64,
      pr1645v2EthPortSwIH24InPInDropNoMac
         Counter64,
      pr1645v2EthPortSwIH24InPInDropNUCast
         Counter64,
      pr1645v2EthPortSwIH24InPInDropFilter
         Counter64,
      pr1645v2EthPortSwIH24InPIfInBandwidth
         Integer32,
      pr1645v2EthPortSwIH24InPIfOutOctets
         Counter64,
      pr1645v2EthPortSwIH24InPIfOutUCPkts
         Counter64,
      pr1645v2EthPortSwIH24InPIfOutNUCPkts
         Counter64,
      pr1645v2EthPortSwIH24InPIfOutBCPkts
         Counter64,
      pr1645v2EthPortSwIH24InPIfOutMCPkts
         Counter64,
      pr1645v2EthPortSwIH24InPIfOutDiscards
         Counter64,
      pr1645v2EthPortSwIH24InPIfOutErrors
         Counter64,
      pr1645v2EthPortSwIH24InPOutDropEx
         Counter64,
      pr1645v2EthPortSwIH24InPOutDropNoArp
         Counter64,
      pr1645v2EthPortSwIH24InPOutDropFilter
         Counter64,
      pr1645v2EthPortSwIH24InPIfOutBandwidth
         Integer32,
      pr1645v2EthPortSwIH24InPIfErrSec
         Counter32
      }

pr1645v2EthPortSwIH24InPGlobalIx OBJECT-TYPE
   SYNTAX      GlobalIndex
   MAX-ACCESS  not-accessible
   STATUS      current
   DESCRIPTION
      "The value of the tlsCntTreeGlobalIndex of the MANAGED OBJECT."
   ::= {pr1645v2EthPortSwIH24InPEntry 10}

pr1645v2EthPortSwIH24InPTableIx OBJECT-TYPE
   SYNTAX      TableIndex
   MAX-ACCESS  not-accessible
   STATUS      current
   DESCRIPTION
      ""
   ::= {pr1645v2EthPortSwIH24InPEntry 11}

pr1645v2EthPortSwIH24InPSysUpTime OBJECT-TYPE
   SYNTAX      TimeTicks
   MAX-ACCESS  read-only
   STATUS      current
   DESCRIPTION
      "Path: swPort.performance.h24Performance.sysUpTime

       Time in centi-second."
   ::= {pr1645v2EthPortSwIH24InPEntry 16777216}

pr1645v2EthPortSwIH24InPIfUpTime OBJECT-TYPE
   SYNTAX      TimeTicks
   MAX-ACCESS  read-only
   STATUS      current
   DESCRIPTION
      "Path: swPort.performance.h24Performance.ifUpTime

       Time in centi-second."
   ::= {pr1645v2EthPortSwIH24InPEntry 33554432}

pr1645v2EthPortSwIH24InPIfStatChanges OBJECT-TYPE
   SYNTAX      Counter32
   MAX-ACCESS  read-only
   STATUS      current
   DESCRIPTION
      "Path: swPort.performance.h24Performance.ifStatusChanges

       32 bit unsigned wrappable counter."
   ::= {pr1645v2EthPortSwIH24InPEntry 50331648}

pr1645v2EthPortSwIH24InPIfInOctets OBJECT-TYPE
   SYNTAX      Counter64
   MAX-ACCESS  read-only
   STATUS      current
   DESCRIPTION
      "Path: swPort.performance.h24Performance.ifInOctets

       64 bit unsigned wrappable counter."
   ::= {pr1645v2EthPortSwIH24InPEntry 67108864}

pr1645v2EthPortSwIH24InPIfInUCPkts OBJECT-TYPE
   SYNTAX      Counter64
   MAX-ACCESS  read-only
   STATUS      current
   DESCRIPTION
      "Path: swPort.performance.h24Performance.ifInUcastPkts

       64 bit unsigned wrappable counter."
   ::= {pr1645v2EthPortSwIH24InPEntry 83886080}

pr1645v2EthPortSwIH24InPIfInNUCPkts OBJECT-TYPE
   SYNTAX      Counter64
   MAX-ACCESS  read-only
   STATUS      current
   DESCRIPTION
      "Path: swPort.performance.h24Performance.ifInNUcastPkts

       64 bit unsigned wrappable counter."
   ::= {pr1645v2EthPortSwIH24InPEntry 100663296}

pr1645v2EthPortSwIH24InPIfInBCPkts OBJECT-TYPE
   SYNTAX      Counter64
   MAX-ACCESS  read-only
   STATUS      current
   DESCRIPTION
      "Path: swPort.performance.h24Performance.ifInBcastPkts

       64 bit unsigned wrappable counter."
   ::= {pr1645v2EthPortSwIH24InPEntry 419430400}

pr1645v2EthPortSwIH24InPIfInMCPkts OBJECT-TYPE
   SYNTAX      Counter64
   MAX-ACCESS  read-only
   STATUS      current
   DESCRIPTION
      "Path: swPort.performance.h24Performance.ifInMcastPkts

       64 bit unsigned wrappable counter."
   ::= {pr1645v2EthPortSwIH24InPEntry 436207616}

pr1645v2EthPortSwIH24InPIfInDiscards OBJECT-TYPE
   SYNTAX      Counter64
   MAX-ACCESS  read-only
   STATUS      current
   DESCRIPTION
      "Path: swPort.performance.h24Performance.ifInDiscards

       64 bit unsigned wrappable counter."
   ::= {pr1645v2EthPortSwIH24InPEntry 117440512}

pr1645v2EthPortSwIH24InPIfInErrors OBJECT-TYPE
   SYNTAX      Counter64
   MAX-ACCESS  read-only
   STATUS      current
   DESCRIPTION
      "Path: swPort.performance.h24Performance.ifInErrors

       64 bit unsigned wrappable counter."
   ::= {pr1645v2EthPortSwIH24InPEntry 134217728}

pr1645v2EthPortSwIH24InPIfInUnkwn OBJECT-TYPE
   SYNTAX      Counter64
   MAX-ACCESS  read-only
   STATUS      current
   DESCRIPTION
      "Path: swPort.performance.h24Performance.ifInUnknownProtos

       64 bit unsigned wrappable counter."
   ::= {pr1645v2EthPortSwIH24InPEntry 150994944}

pr1645v2EthPortSwIH24InPInDropEx OBJECT-TYPE
   SYNTAX      Counter64
   MAX-ACCESS  read-only
   STATUS      current
   DESCRIPTION
      "Path: swPort.performance.h24Performance.ifInDropLevelExceeded

       64 bit unsigned wrappable counter."
   ::= {pr1645v2EthPortSwIH24InPEntry 335544320}

pr1645v2EthPortSwIH24InPInDropNoMac OBJECT-TYPE
   SYNTAX      Counter64
   MAX-ACCESS  read-only
   STATUS      current
   DESCRIPTION
      "Path: swPort.performance.h24Performance.fInDiscardsNoMacFit

       64 bit unsigned wrappable counter."
   ::= {pr1645v2EthPortSwIH24InPEntry 301989888}

pr1645v2EthPortSwIH24InPInDropNUCast OBJECT-TYPE
   SYNTAX      Counter64
   MAX-ACCESS  read-only
   STATUS      current
   DESCRIPTION
      "Path: swPort.performance.h24Performance.fInDiscardsNUCast

       64 bit unsigned wrappable counter."
   ::= {pr1645v2EthPortSwIH24InPEntry 318767104}

pr1645v2EthPortSwIH24InPInDropFilter OBJECT-TYPE
   SYNTAX      Counter64
   MAX-ACCESS  read-only
   STATUS      current
   DESCRIPTION
      "Path: swPort.performance.h24Performance.fInDiscardsFilter

       64 bit unsigned wrappable counter."
   ::= {pr1645v2EthPortSwIH24InPEntry 385875968}

pr1645v2EthPortSwIH24InPIfInBandwidth OBJECT-TYPE
   SYNTAX      Integer32
   MAX-ACCESS  read-only
   STATUS      current
   DESCRIPTION
      "Path: swPort.performance.h24Performance.ifInBandwidth

       unit name = bps
       formula = 8 * ; 8 /"
   ::= {pr1645v2EthPortSwIH24InPEntry 268435456}

pr1645v2EthPortSwIH24InPIfOutOctets OBJECT-TYPE
   SYNTAX      Counter64
   MAX-ACCESS  read-only
   STATUS      current
   DESCRIPTION
      "Path: swPort.performance.h24Performance.ifOutOctets

       64 bit unsigned wrappable counter."
   ::= {pr1645v2EthPortSwIH24InPEntry 167772160}

pr1645v2EthPortSwIH24InPIfOutUCPkts OBJECT-TYPE
   SYNTAX      Counter64
   MAX-ACCESS  read-only
   STATUS      current
   DESCRIPTION
      "Path: swPort.performance.h24Performance.ifOutUcastPkts

       64 bit unsigned wrappable counter."
   ::= {pr1645v2EthPortSwIH24InPEntry 184549376}

pr1645v2EthPortSwIH24InPIfOutNUCPkts OBJECT-TYPE
   SYNTAX      Counter64
   MAX-ACCESS  read-only
   STATUS      current
   DESCRIPTION
      "Path: swPort.performance.h24Performance.ifOutNUcastPkts

       64 bit unsigned wrappable counter."
   ::= {pr1645v2EthPortSwIH24InPEntry 201326592}

pr1645v2EthPortSwIH24InPIfOutBCPkts OBJECT-TYPE
   SYNTAX      Counter64
   MAX-ACCESS  read-only
   STATUS      current
   DESCRIPTION
      "Path: swPort.performance.h24Performance.ifOutBcastPkts

       64 bit unsigned wrappable counter."
   ::= {pr1645v2EthPortSwIH24InPEntry 452984832}

pr1645v2EthPortSwIH24InPIfOutMCPkts OBJECT-TYPE
   SYNTAX      Counter64
   MAX-ACCESS  read-only
   STATUS      current
   DESCRIPTION
      "Path: swPort.performance.h24Performance.ifOutMcastPkts

       64 bit unsigned wrappable counter."
   ::= {pr1645v2EthPortSwIH24InPEntry 469762048}

pr1645v2EthPortSwIH24InPIfOutDiscards OBJECT-TYPE
   SYNTAX      Counter64
   MAX-ACCESS  read-only
   STATUS      current
   DESCRIPTION
      "Path: swPort.performance.h24Performance.ifOutDiscards

       64 bit unsigned wrappable counter."
   ::= {pr1645v2EthPortSwIH24InPEntry 218103808}

pr1645v2EthPortSwIH24InPIfOutErrors OBJECT-TYPE
   SYNTAX      Counter64
   MAX-ACCESS  read-only
   STATUS      current
   DESCRIPTION
      "Path: swPort.performance.h24Performance.ifOutErrors

       64 bit unsigned wrappable counter."
   ::= {pr1645v2EthPortSwIH24InPEntry 234881024}

pr1645v2EthPortSwIH24InPOutDropEx OBJECT-TYPE
   SYNTAX      Counter64
   MAX-ACCESS  read-only
   STATUS      current
   DESCRIPTION
      "Path: swPort.performance.h24Performance.ifOutDropLevelExceeded

       64 bit unsigned wrappable counter."
   ::= {pr1645v2EthPortSwIH24InPEntry 352321536}

pr1645v2EthPortSwIH24InPOutDropNoArp OBJECT-TYPE
   SYNTAX      Counter64
   MAX-ACCESS  read-only
   STATUS      current
   DESCRIPTION
      "Path: swPort.performance.h24Performance.ifOutDiscardsNoArp

       64 bit unsigned wrappable counter."
   ::= {pr1645v2EthPortSwIH24InPEntry 369098752}

pr1645v2EthPortSwIH24InPOutDropFilter OBJECT-TYPE
   SYNTAX      Counter64
   MAX-ACCESS  read-only
   STATUS      current
   DESCRIPTION
      "Path: swPort.performance.h24Performance.ifOutDiscardsFilter

       64 bit unsigned wrappable counter."
   ::= {pr1645v2EthPortSwIH24InPEntry 402653184}

pr1645v2EthPortSwIH24InPIfOutBandwidth OBJECT-TYPE
   SYNTAX      Integer32
   MAX-ACCESS  read-only
   STATUS      current
   DESCRIPTION
      "Path: swPort.performance.h24Performance.ifOutBandwidth

       unit name = bps
       formula = 8 * ; 8 /"
   ::= {pr1645v2EthPortSwIH24InPEntry 285212672}

pr1645v2EthPortSwIH24InPIfErrSec OBJECT-TYPE
   SYNTAX      Counter32
   MAX-ACCESS  read-only
   STATUS      current
   DESCRIPTION
      "Path: swPort.performance.h24Performance.ifErrSec

       32 bit unsigned wrappable counter."
   ::= {pr1645v2EthPortSwIH24InPEntry 251658240}


pr1645v2EthPortSwID7InP OBJECT IDENTIFIER ::= {pr1645v2EthPortSwI 309}

pr1645v2EthPortSwID7InPSSCTable OBJECT-TYPE
   SYNTAX      SEQUENCE OF Pr1645v2EthPortSwID7InPEntry
   MAX-ACCESS  not-accessible
   STATUS      current
   DESCRIPTION
      "d7IfInPerformance"
   ::= {pr1645v2EthPortSwID7InP 1}

pr1645v2EthPortSwID7InPEntry OBJECT-TYPE
   SYNTAX      Pr1645v2EthPortSwID7InPEntry
   MAX-ACCESS  not-accessible
   STATUS      current
   DESCRIPTION
      ""
   INDEX      { pr1645v2EthPortSwID7InPGlobalIx,
                pr1645v2EthPortSwID7InPTableIx }
   ::= {pr1645v2EthPortSwID7InPSSCTable 1}

Pr1645v2EthPortSwID7InPEntry ::=
   SEQUENCE
      {
      pr1645v2EthPortSwID7InPGlobalIx
         GlobalIndex,
      pr1645v2EthPortSwID7InPTableIx
         TableIndex,
      pr1645v2EthPortSwID7InPSysUpTime
         TimeTicks,
      pr1645v2EthPortSwID7InPIfUpTime
         TimeTicks,
      pr1645v2EthPortSwID7InPIfStatChanges
         Counter32,
      pr1645v2EthPortSwID7InPIfInOctets
         Counter64,
      pr1645v2EthPortSwID7InPIfInUCPkts
         Counter64,
      pr1645v2EthPortSwID7InPIfInNUCPkts
         Counter64,
      pr1645v2EthPortSwID7InPIfInBCPkts
         Counter64,
      pr1645v2EthPortSwID7InPIfInMCPkts
         Counter64,
      pr1645v2EthPortSwID7InPIfInDiscards
         Counter64,
      pr1645v2EthPortSwID7InPIfInErrors
         Counter64,
      pr1645v2EthPortSwID7InPIfInUnkwn
         Counter64,
      pr1645v2EthPortSwID7InPInDropEx
         Counter64,
      pr1645v2EthPortSwID7InPInDropNoMac
         Counter64,
      pr1645v2EthPortSwID7InPInDropNUCast
         Counter64,
      pr1645v2EthPortSwID7InPInDropFilter
         Counter64,
      pr1645v2EthPortSwID7InPIfInBandwidth
         Integer32,
      pr1645v2EthPortSwID7InPIfOutOctets
         Counter64,
      pr1645v2EthPortSwID7InPIfOutUCPkts
         Counter64,
      pr1645v2EthPortSwID7InPIfOutNUCPkts
         Counter64,
      pr1645v2EthPortSwID7InPIfOutBCPkts
         Counter64,
      pr1645v2EthPortSwID7InPIfOutMCPkts
         Counter64,
      pr1645v2EthPortSwID7InPIfOutDiscards
         Counter64,
      pr1645v2EthPortSwID7InPIfOutErrors
         Counter64,
      pr1645v2EthPortSwID7InPOutDropEx
         Counter64,
      pr1645v2EthPortSwID7InPOutDropNoArp
         Counter64,
      pr1645v2EthPortSwID7InPOutDropFilter
         Counter64,
      pr1645v2EthPortSwID7InPIfOutBandwidth
         Integer32,
      pr1645v2EthPortSwID7InPIfErrSec
         Counter32
      }

pr1645v2EthPortSwID7InPGlobalIx OBJECT-TYPE
   SYNTAX      GlobalIndex
   MAX-ACCESS  not-accessible
   STATUS      current
   DESCRIPTION
      "The value of the tlsCntTreeGlobalIndex of the MANAGED OBJECT."
   ::= {pr1645v2EthPortSwID7InPEntry 10}

pr1645v2EthPortSwID7InPTableIx OBJECT-TYPE
   SYNTAX      TableIndex
   MAX-ACCESS  not-accessible
   STATUS      current
   DESCRIPTION
      ""
   ::= {pr1645v2EthPortSwID7InPEntry 11}

pr1645v2EthPortSwID7InPSysUpTime OBJECT-TYPE
   SYNTAX      TimeTicks
   MAX-ACCESS  read-only
   STATUS      current
   DESCRIPTION
      "Path: swPort.performance.d7Performance.sysUpTime

       Time in centi-second."
   ::= {pr1645v2EthPortSwID7InPEntry 16777216}

pr1645v2EthPortSwID7InPIfUpTime OBJECT-TYPE
   SYNTAX      TimeTicks
   MAX-ACCESS  read-only
   STATUS      current
   DESCRIPTION
      "Path: swPort.performance.d7Performance.ifUpTime

       Time in centi-second."
   ::= {pr1645v2EthPortSwID7InPEntry 33554432}

pr1645v2EthPortSwID7InPIfStatChanges OBJECT-TYPE
   SYNTAX      Counter32
   MAX-ACCESS  read-only
   STATUS      current
   DESCRIPTION
      "Path: swPort.performance.d7Performance.ifStatusChanges

       32 bit unsigned wrappable counter."
   ::= {pr1645v2EthPortSwID7InPEntry 50331648}

pr1645v2EthPortSwID7InPIfInOctets OBJECT-TYPE
   SYNTAX      Counter64
   MAX-ACCESS  read-only
   STATUS      current
   DESCRIPTION
      "Path: swPort.performance.d7Performance.ifInOctets

       64 bit unsigned wrappable counter."
   ::= {pr1645v2EthPortSwID7InPEntry 67108864}

pr1645v2EthPortSwID7InPIfInUCPkts OBJECT-TYPE
   SYNTAX      Counter64
   MAX-ACCESS  read-only
   STATUS      current
   DESCRIPTION
      "Path: swPort.performance.d7Performance.ifInUcastPkts

       64 bit unsigned wrappable counter."
   ::= {pr1645v2EthPortSwID7InPEntry 83886080}

pr1645v2EthPortSwID7InPIfInNUCPkts OBJECT-TYPE
   SYNTAX      Counter64
   MAX-ACCESS  read-only
   STATUS      current
   DESCRIPTION
      "Path: swPort.performance.d7Performance.ifInNUcastPkts

       64 bit unsigned wrappable counter."
   ::= {pr1645v2EthPortSwID7InPEntry 100663296}

pr1645v2EthPortSwID7InPIfInBCPkts OBJECT-TYPE
   SYNTAX      Counter64
   MAX-ACCESS  read-only
   STATUS      current
   DESCRIPTION
      "Path: swPort.performance.d7Performance.ifInBcastPkts

       64 bit unsigned wrappable counter."
   ::= {pr1645v2EthPortSwID7InPEntry 419430400}

pr1645v2EthPortSwID7InPIfInMCPkts OBJECT-TYPE
   SYNTAX      Counter64
   MAX-ACCESS  read-only
   STATUS      current
   DESCRIPTION
      "Path: swPort.performance.d7Performance.ifInMcastPkts

       64 bit unsigned wrappable counter."
   ::= {pr1645v2EthPortSwID7InPEntry 436207616}

pr1645v2EthPortSwID7InPIfInDiscards OBJECT-TYPE
   SYNTAX      Counter64
   MAX-ACCESS  read-only
   STATUS      current
   DESCRIPTION
      "Path: swPort.performance.d7Performance.ifInDiscards

       64 bit unsigned wrappable counter."
   ::= {pr1645v2EthPortSwID7InPEntry 117440512}

pr1645v2EthPortSwID7InPIfInErrors OBJECT-TYPE
   SYNTAX      Counter64
   MAX-ACCESS  read-only
   STATUS      current
   DESCRIPTION
      "Path: swPort.performance.d7Performance.ifInErrors

       64 bit unsigned wrappable counter."
   ::= {pr1645v2EthPortSwID7InPEntry 134217728}

pr1645v2EthPortSwID7InPIfInUnkwn OBJECT-TYPE
   SYNTAX      Counter64
   MAX-ACCESS  read-only
   STATUS      current
   DESCRIPTION
      "Path: swPort.performance.d7Performance.ifInUnknownProtos

       64 bit unsigned wrappable counter."
   ::= {pr1645v2EthPortSwID7InPEntry 150994944}

pr1645v2EthPortSwID7InPInDropEx OBJECT-TYPE
   SYNTAX      Counter64
   MAX-ACCESS  read-only
   STATUS      current
   DESCRIPTION
      "Path: swPort.performance.d7Performance.ifInDropLevelExceeded

       64 bit unsigned wrappable counter."
   ::= {pr1645v2EthPortSwID7InPEntry 335544320}

pr1645v2EthPortSwID7InPInDropNoMac OBJECT-TYPE
   SYNTAX      Counter64
   MAX-ACCESS  read-only
   STATUS      current
   DESCRIPTION
      "Path: swPort.performance.d7Performance.fInDiscardsNoMacFit

       64 bit unsigned wrappable counter."
   ::= {pr1645v2EthPortSwID7InPEntry 301989888}

pr1645v2EthPortSwID7InPInDropNUCast OBJECT-TYPE
   SYNTAX      Counter64
   MAX-ACCESS  read-only
   STATUS      current
   DESCRIPTION
      "Path: swPort.performance.d7Performance.fInDiscardsNUCast

       64 bit unsigned wrappable counter."
   ::= {pr1645v2EthPortSwID7InPEntry 318767104}

pr1645v2EthPortSwID7InPInDropFilter OBJECT-TYPE
   SYNTAX      Counter64
   MAX-ACCESS  read-only
   STATUS      current
   DESCRIPTION
      "Path: swPort.performance.d7Performance.fInDiscardsFilter

       64 bit unsigned wrappable counter."
   ::= {pr1645v2EthPortSwID7InPEntry 385875968}

pr1645v2EthPortSwID7InPIfInBandwidth OBJECT-TYPE
   SYNTAX      Integer32
   MAX-ACCESS  read-only
   STATUS      current
   DESCRIPTION
      "Path: swPort.performance.d7Performance.ifInBandwidth

       unit name = bps
       formula = 8 * ; 8 /"
   ::= {pr1645v2EthPortSwID7InPEntry 268435456}

pr1645v2EthPortSwID7InPIfOutOctets OBJECT-TYPE
   SYNTAX      Counter64
   MAX-ACCESS  read-only
   STATUS      current
   DESCRIPTION
      "Path: swPort.performance.d7Performance.ifOutOctets

       64 bit unsigned wrappable counter."
   ::= {pr1645v2EthPortSwID7InPEntry 167772160}

pr1645v2EthPortSwID7InPIfOutUCPkts OBJECT-TYPE
   SYNTAX      Counter64
   MAX-ACCESS  read-only
   STATUS      current
   DESCRIPTION
      "Path: swPort.performance.d7Performance.ifOutUcastPkts

       64 bit unsigned wrappable counter."
   ::= {pr1645v2EthPortSwID7InPEntry 184549376}

pr1645v2EthPortSwID7InPIfOutNUCPkts OBJECT-TYPE
   SYNTAX      Counter64
   MAX-ACCESS  read-only
   STATUS      current
   DESCRIPTION
      "Path: swPort.performance.d7Performance.ifOutNUcastPkts

       64 bit unsigned wrappable counter."
   ::= {pr1645v2EthPortSwID7InPEntry 201326592}

pr1645v2EthPortSwID7InPIfOutBCPkts OBJECT-TYPE
   SYNTAX      Counter64
   MAX-ACCESS  read-only
   STATUS      current
   DESCRIPTION
      "Path: swPort.performance.d7Performance.ifOutBcastPkts

       64 bit unsigned wrappable counter."
   ::= {pr1645v2EthPortSwID7InPEntry 452984832}

pr1645v2EthPortSwID7InPIfOutMCPkts OBJECT-TYPE
   SYNTAX      Counter64
   MAX-ACCESS  read-only
   STATUS      current
   DESCRIPTION
      "Path: swPort.performance.d7Performance.ifOutMcastPkts

       64 bit unsigned wrappable counter."
   ::= {pr1645v2EthPortSwID7InPEntry 469762048}

pr1645v2EthPortSwID7InPIfOutDiscards OBJECT-TYPE
   SYNTAX      Counter64
   MAX-ACCESS  read-only
   STATUS      current
   DESCRIPTION
      "Path: swPort.performance.d7Performance.ifOutDiscards

       64 bit unsigned wrappable counter."
   ::= {pr1645v2EthPortSwID7InPEntry 218103808}

pr1645v2EthPortSwID7InPIfOutErrors OBJECT-TYPE
   SYNTAX      Counter64
   MAX-ACCESS  read-only
   STATUS      current
   DESCRIPTION
      "Path: swPort.performance.d7Performance.ifOutErrors

       64 bit unsigned wrappable counter."
   ::= {pr1645v2EthPortSwID7InPEntry 234881024}

pr1645v2EthPortSwID7InPOutDropEx OBJECT-TYPE
   SYNTAX      Counter64
   MAX-ACCESS  read-only
   STATUS      current
   DESCRIPTION
      "Path: swPort.performance.d7Performance.ifOutDropLevelExceeded

       64 bit unsigned wrappable counter."
   ::= {pr1645v2EthPortSwID7InPEntry 352321536}

pr1645v2EthPortSwID7InPOutDropNoArp OBJECT-TYPE
   SYNTAX      Counter64
   MAX-ACCESS  read-only
   STATUS      current
   DESCRIPTION
      "Path: swPort.performance.d7Performance.ifOutDiscardsNoArp

       64 bit unsigned wrappable counter."
   ::= {pr1645v2EthPortSwID7InPEntry 369098752}

pr1645v2EthPortSwID7InPOutDropFilter OBJECT-TYPE
   SYNTAX      Counter64
   MAX-ACCESS  read-only
   STATUS      current
   DESCRIPTION
      "Path: swPort.performance.d7Performance.ifOutDiscardsFilter

       64 bit unsigned wrappable counter."
   ::= {pr1645v2EthPortSwID7InPEntry 402653184}

pr1645v2EthPortSwID7InPIfOutBandwidth OBJECT-TYPE
   SYNTAX      Integer32
   MAX-ACCESS  read-only
   STATUS      current
   DESCRIPTION
      "Path: swPort.performance.d7Performance.ifOutBandwidth

       unit name = bps
       formula = 8 * ; 8 /"
   ::= {pr1645v2EthPortSwID7InPEntry 285212672}

pr1645v2EthPortSwID7InPIfErrSec OBJECT-TYPE
   SYNTAX      Counter32
   MAX-ACCESS  read-only
   STATUS      current
   DESCRIPTION
      "Path: swPort.performance.d7Performance.ifErrSec

       32 bit unsigned wrappable counter."
   ::= {pr1645v2EthPortSwID7InPEntry 251658240}


pr1645v2EthPortSwIOam OBJECT IDENTIFIER ::= {pr1645v2EthPortSwI 910}

pr1645v2EthPortSwIOamSSCTable OBJECT-TYPE
   SYNTAX      SEQUENCE OF Pr1645v2EthPortSwIOamEntry
   MAX-ACCESS  not-accessible
   STATUS      current
   DESCRIPTION
      "OAM statistics"
   ::= {pr1645v2EthPortSwIOam 1}

pr1645v2EthPortSwIOamEntry OBJECT-TYPE
   SYNTAX      Pr1645v2EthPortSwIOamEntry
   MAX-ACCESS  not-accessible
   STATUS      current
   DESCRIPTION
      ""
   INDEX      { pr1645v2EthPortSwIOamGlobalIx }
   ::= {pr1645v2EthPortSwIOamSSCTable 1}

Pr1645v2EthPortSwIOamEntry ::=
   SEQUENCE
      {
      pr1645v2EthPortSwIOamGlobalIx
         GlobalIndex,
      pr1645v2EthPortSwIOamInformationTx
         Counter32,
      pr1645v2EthPortSwIOamInformationRx
         Counter32,
      pr1645v2EthPortSwIOamUniqueEventNotifTx
         Counter32,
      pr1645v2EthPortSwIOamUniqueEventNotifRx
         Counter32,
      pr1645v2EthPortSwIOamLoopbackCtrlTx
         Counter32,
      pr1645v2EthPortSwIOamLoopbackCtrlRx
         Counter32,
      pr1645v2EthPortSwIOamVarReqTx
         Counter32,
      pr1645v2EthPortSwIOamVarReqRx
         Counter32,
      pr1645v2EthPortSwIOamVarRespTx
         Counter32,
      pr1645v2EthPortSwIOamVarRespRx
         Counter32,
      pr1645v2EthPortSwIOamOrgSpecificTx
         Counter32,
      pr1645v2EthPortSwIOamOrgSpecificRx
         Counter32,
      pr1645v2EthPortSwIOamUnsupportedCodesTx
         Counter32,
      pr1645v2EthPortSwIOamUnsupportedCodesRx
         Counter32,
      pr1645v2EthPortSwIOamPduDiscardRx
         Counter32,
      pr1645v2EthPortSwIOamDataDiscardTx
         Counter32,
      pr1645v2EthPortSwIOamDataDiscardRx
         Counter32
      }

pr1645v2EthPortSwIOamGlobalIx OBJECT-TYPE
   SYNTAX      GlobalIndex
   MAX-ACCESS  not-accessible
   STATUS      current
   DESCRIPTION
      "The value of the tlsCntTreeGlobalIndex of the MANAGED OBJECT."
   ::= {pr1645v2EthPortSwIOamEntry 10}

pr1645v2EthPortSwIOamInformationTx OBJECT-TYPE
   SYNTAX      Counter32
   MAX-ACCESS  read-only
   STATUS      current
   DESCRIPTION
      "Path: swPort.performance.oam.informationTx

       32 bit unsigned wrappable counter."
   ::= {pr1645v2EthPortSwIOamEntry 16777216}

pr1645v2EthPortSwIOamInformationRx OBJECT-TYPE
   SYNTAX      Counter32
   MAX-ACCESS  read-only
   STATUS      current
   DESCRIPTION
      "Path: swPort.performance.oam.informationRx

       32 bit unsigned wrappable counter."
   ::= {pr1645v2EthPortSwIOamEntry 33554432}

pr1645v2EthPortSwIOamUniqueEventNotifTx OBJECT-TYPE
   SYNTAX      Counter32
   MAX-ACCESS  read-only
   STATUS      current
   DESCRIPTION
      "Path: swPort.performance.oam.uniqueEventNotifTx

       32 bit unsigned wrappable counter."
   ::= {pr1645v2EthPortSwIOamEntry 50331648}

pr1645v2EthPortSwIOamUniqueEventNotifRx OBJECT-TYPE
   SYNTAX      Counter32
   MAX-ACCESS  read-only
   STATUS      current
   DESCRIPTION
      "Path: swPort.performance.oam.uniqueEventNotifRx

       32 bit unsigned wrappable counter."
   ::= {pr1645v2EthPortSwIOamEntry 67108864}

pr1645v2EthPortSwIOamLoopbackCtrlTx OBJECT-TYPE
   SYNTAX      Counter32
   MAX-ACCESS  read-only
   STATUS      current
   DESCRIPTION
      "Path: swPort.performance.oam.loopbackCtrlTx

       32 bit unsigned wrappable counter."
   ::= {pr1645v2EthPortSwIOamEntry 117440512}

pr1645v2EthPortSwIOamLoopbackCtrlRx OBJECT-TYPE
   SYNTAX      Counter32
   MAX-ACCESS  read-only
   STATUS      current
   DESCRIPTION
      "Path: swPort.performance.oam.loopbackCtrlRx

       32 bit unsigned wrappable counter."
   ::= {pr1645v2EthPortSwIOamEntry 134217728}

pr1645v2EthPortSwIOamVarReqTx OBJECT-TYPE
   SYNTAX      Counter32
   MAX-ACCESS  read-only
   STATUS      current
   DESCRIPTION
      "Path: swPort.performance.oam.varReqTx

       32 bit unsigned wrappable counter."
   ::= {pr1645v2EthPortSwIOamEntry 150994944}

pr1645v2EthPortSwIOamVarReqRx OBJECT-TYPE
   SYNTAX      Counter32
   MAX-ACCESS  read-only
   STATUS      current
   DESCRIPTION
      "Path: swPort.performance.oam.varReqRx

       32 bit unsigned wrappable counter."
   ::= {pr1645v2EthPortSwIOamEntry 167772160}

pr1645v2EthPortSwIOamVarRespTx OBJECT-TYPE
   SYNTAX      Counter32
   MAX-ACCESS  read-only
   STATUS      current
   DESCRIPTION
      "Path: swPort.performance.oam.varRespTx

       32 bit unsigned wrappable counter."
   ::= {pr1645v2EthPortSwIOamEntry 184549376}

pr1645v2EthPortSwIOamVarRespRx OBJECT-TYPE
   SYNTAX      Counter32
   MAX-ACCESS  read-only
   STATUS      current
   DESCRIPTION
      "Path: swPort.performance.oam.varRespRx

       32 bit unsigned wrappable counter."
   ::= {pr1645v2EthPortSwIOamEntry 201326592}

pr1645v2EthPortSwIOamOrgSpecificTx OBJECT-TYPE
   SYNTAX      Counter32
   MAX-ACCESS  read-only
   STATUS      current
   DESCRIPTION
      "Path: swPort.performance.oam.orgSpecificTx

       32 bit unsigned wrappable counter."
   ::= {pr1645v2EthPortSwIOamEntry 218103808}

pr1645v2EthPortSwIOamOrgSpecificRx OBJECT-TYPE
   SYNTAX      Counter32
   MAX-ACCESS  read-only
   STATUS      current
   DESCRIPTION
      "Path: swPort.performance.oam.orgSpecificRx

       32 bit unsigned wrappable counter."
   ::= {pr1645v2EthPortSwIOamEntry 234881024}

pr1645v2EthPortSwIOamUnsupportedCodesTx OBJECT-TYPE
   SYNTAX      Counter32
   MAX-ACCESS  read-only
   STATUS      current
   DESCRIPTION
      "Path: swPort.performance.oam.unsupportedCodesTx

       32 bit unsigned wrappable counter."
   ::= {pr1645v2EthPortSwIOamEntry 251658240}

pr1645v2EthPortSwIOamUnsupportedCodesRx OBJECT-TYPE
   SYNTAX      Counter32
   MAX-ACCESS  read-only
   STATUS      current
   DESCRIPTION
      "Path: swPort.performance.oam.unsupportedCodesRx

       32 bit unsigned wrappable counter."
   ::= {pr1645v2EthPortSwIOamEntry 268435456}

pr1645v2EthPortSwIOamPduDiscardRx OBJECT-TYPE
   SYNTAX      Counter32
   MAX-ACCESS  read-only
   STATUS      current
   DESCRIPTION
      "Path: swPort.performance.oam.pduDiscardRx

       32 bit unsigned wrappable counter."
   ::= {pr1645v2EthPortSwIOamEntry 1694498816}

pr1645v2EthPortSwIOamDataDiscardTx OBJECT-TYPE
   SYNTAX      Counter32
   MAX-ACCESS  read-only
   STATUS      current
   DESCRIPTION
      "Path: swPort.performance.oam.dataDiscardTx

       32 bit unsigned wrappable counter."
   ::= {pr1645v2EthPortSwIOamEntry 1711276032}

pr1645v2EthPortSwIOamDataDiscardRx OBJECT-TYPE
   SYNTAX      Counter32
   MAX-ACCESS  read-only
   STATUS      current
   DESCRIPTION
      "Path: swPort.performance.oam.dataDiscardRx

       32 bit unsigned wrappable counter."
   ::= {pr1645v2EthPortSwIOamEntry 1728053248}


pr1645v2EthPortSwIVlan OBJECT IDENTIFIER ::= {pr1645v2EthPortSwI 310}

pr1645v2EthPortSwIVlanSSCTable OBJECT-TYPE
   SYNTAX      SEQUENCE OF Pr1645v2EthPortSwIVlanEntry
   MAX-ACCESS  not-accessible
   STATUS      current
   DESCRIPTION
      ""
   ::= {pr1645v2EthPortSwIVlan 1}

pr1645v2EthPortSwIVlanEntry OBJECT-TYPE
   SYNTAX      Pr1645v2EthPortSwIVlanEntry
   MAX-ACCESS  not-accessible
   STATUS      current
   DESCRIPTION
      ""
   INDEX      { pr1645v2EthPortSwIVlanGlobalIx,
                pr1645v2EthPortSwIVlanTableIx }
   ::= {pr1645v2EthPortSwIVlanSSCTable 1}

Pr1645v2EthPortSwIVlanEntry ::=
   SEQUENCE
      {
      pr1645v2EthPortSwIVlanGlobalIx
         GlobalIndex,
      pr1645v2EthPortSwIVlanTableIx
         TableIndex,
      pr1645v2EthPortSwIVlanName
         DisplayString,
      pr1645v2EthPortSwIVlanMCInOctets
         Counter64,
      pr1645v2EthPortSwIVlanMCInUcast
         Counter64,
      pr1645v2EthPortSwIVlanMCInNUcastPkts
         Counter64,
      pr1645v2EthPortSwIVlanMCInBcastPkts
         Counter64,
      pr1645v2EthPortSwIVlanMCInMcastPkts
         Counter64,
      pr1645v2EthPortSwIVlanMCInDiscards
         Counter64,
      pr1645v2EthPortSwIVlanMCInErrors
         Counter64,
      pr1645v2EthPortSwIVlanMCInUnknownProtos
         Counter64,
      pr1645v2EthPortSwIVlanMCInDropEx
         Counter64,
      pr1645v2EthPortSwIVlanMCInDropNoMac
         Counter64,
      pr1645v2EthPortSwIVlanMCInDropNUCast
         Counter64,
      pr1645v2EthPortSwIVlanMCInDropFilter
         Counter64,
      pr1645v2EthPortSwIVlanMCInBandwidth15sec
         Integer32,
      pr1645v2EthPortSwIVlanMCInBandwidth30sec
         Integer32,
      pr1645v2EthPortSwIVlanMCInBandwidth1min
         Integer32,
      pr1645v2EthPortSwIVlanMCInBandwidth2min
         Integer32,
      pr1645v2EthPortSwIVlanMCInBandwidth5min
         Integer32,
      pr1645v2EthPortSwIVlanMCOutOctets
         Counter64,
      pr1645v2EthPortSwIVlanMCOutUcastPkts
         Counter64,
      pr1645v2EthPortSwIVlanMCOutNUcastPkts
         Counter64,
      pr1645v2EthPortSwIVlanMCOutBcastPkts
         Counter64,
      pr1645v2EthPortSwIVlanMCOutMcastPkts
         Counter64,
      pr1645v2EthPortSwIVlanMCOutDiscards
         Counter64,
      pr1645v2EthPortSwIVlanMCOutErrors
         Counter64,
      pr1645v2EthPortSwIVlanMCOutQLen
         Counter32,
      pr1645v2EthPortSwIVlanMCOutDropEx
         Counter64,
      pr1645v2EthPortSwIVlanMCOutDropNoArp
         Counter64,
      pr1645v2EthPortSwIVlanMCOutDropFilter
         Counter64,
      pr1645v2EthPortSwIVlanMCOutBandwidth15sec
         Integer32,
      pr1645v2EthPortSwIVlanMCOutBandwidth30sec
         Integer32,
      pr1645v2EthPortSwIVlanMCOutBandwidth1min
         Integer32,
      pr1645v2EthPortSwIVlanMCOutBandwidth2min
         Integer32,
      pr1645v2EthPortSwIVlanMCOutBandwidth5min
         Integer32,
      pr1645v2EthPortSwIVlanVlanVid
         Integer32,
      pr1645v2EthPortSwIVlanPppLinkMonitoringRequestsSent
         Gauge32,
      pr1645v2EthPortSwIVlanPppLinkMonitoringRepliesRcvd
         Gauge32,
      pr1645v2EthPortSwIVlanPppLinkMonitoringRequestsRcvd
         Gauge32,
      pr1645v2EthPortSwIVlanPppLinkMonitoringRepliesSent
         Gauge32
      }

pr1645v2EthPortSwIVlanGlobalIx OBJECT-TYPE
   SYNTAX      GlobalIndex
   MAX-ACCESS  not-accessible
   STATUS      current
   DESCRIPTION
      "The value of the tlsCntTreeGlobalIndex of the MANAGED OBJECT."
   ::= {pr1645v2EthPortSwIVlanEntry 10}

pr1645v2EthPortSwIVlanTableIx OBJECT-TYPE
   SYNTAX      TableIndex
   MAX-ACCESS  not-accessible
   STATUS      current
   DESCRIPTION
      ""
   ::= {pr1645v2EthPortSwIVlanEntry 11}

pr1645v2EthPortSwIVlanName OBJECT-TYPE
   SYNTAX      DisplayString
   MAX-ACCESS  read-only
   STATUS      current
   DESCRIPTION
      "Path: swPort.performance.vlan.name"
   ::= {pr1645v2EthPortSwIVlanEntry 16777216}

pr1645v2EthPortSwIVlanMCInOctets OBJECT-TYPE
   SYNTAX      Counter64
   MAX-ACCESS  read-only
   STATUS      current
   DESCRIPTION
      "Path: swPort.performance.vlan.mibCounters.ifInOctets

       64 bit unsigned wrappable counter."
   ::= {pr1645v2EthPortSwIVlanEntry 40697856}

pr1645v2EthPortSwIVlanMCInUcast OBJECT-TYPE
   SYNTAX      Counter64
   MAX-ACCESS  read-only
   STATUS      current
   DESCRIPTION
      "Path: swPort.performance.vlan.mibCounters.ifInUcastPkts

       64 bit unsigned wrappable counter."
   ::= {pr1645v2EthPortSwIVlanEntry 40763392}

pr1645v2EthPortSwIVlanMCInNUcastPkts OBJECT-TYPE
   SYNTAX      Counter64
   MAX-ACCESS  read-only
   STATUS      current
   DESCRIPTION
      "Path: swPort.performance.vlan.mibCounters.ifInNUcastPkts

       64 bit unsigned wrappable counter."
   ::= {pr1645v2EthPortSwIVlanEntry 40828928}

pr1645v2EthPortSwIVlanMCInBcastPkts OBJECT-TYPE
   SYNTAX      Counter64
   MAX-ACCESS  read-only
   STATUS      current
   DESCRIPTION
      "Path: swPort.performance.vlan.mibCounters.ifInBcastPkts

       64 bit unsigned wrappable counter."
   ::= {pr1645v2EthPortSwIVlanEntry 47382528}

pr1645v2EthPortSwIVlanMCInMcastPkts OBJECT-TYPE
   SYNTAX      Counter64
   MAX-ACCESS  read-only
   STATUS      current
   DESCRIPTION
      "Path: swPort.performance.vlan.mibCounters.ifInMcastPkts

       64 bit unsigned wrappable counter."
   ::= {pr1645v2EthPortSwIVlanEntry 48037888}

pr1645v2EthPortSwIVlanMCInDiscards OBJECT-TYPE
   SYNTAX      Counter64
   MAX-ACCESS  read-only
   STATUS      current
   DESCRIPTION
      "Path: swPort.performance.vlan.mibCounters.ifInDiscards

       64 bit unsigned wrappable counter."
   ::= {pr1645v2EthPortSwIVlanEntry 40894464}

pr1645v2EthPortSwIVlanMCInErrors OBJECT-TYPE
   SYNTAX      Counter64
   MAX-ACCESS  read-only
   STATUS      current
   DESCRIPTION
      "Path: swPort.performance.vlan.mibCounters.ifInErrors

       64 bit unsigned wrappable counter."
   ::= {pr1645v2EthPortSwIVlanEntry 40960000}

pr1645v2EthPortSwIVlanMCInUnknownProtos OBJECT-TYPE
   SYNTAX      Counter64
   MAX-ACCESS  read-only
   STATUS      current
   DESCRIPTION
      "Path: swPort.performance.vlan.mibCounters.ifInUnknownProtos

       64 bit unsigned wrappable counter."
   ::= {pr1645v2EthPortSwIVlanEntry 41025536}

pr1645v2EthPortSwIVlanMCInDropEx OBJECT-TYPE
   SYNTAX      Counter64
   MAX-ACCESS  read-only
   STATUS      current
   DESCRIPTION
      "Path: swPort.performance.vlan.mibCounters.ifInDropLevelExceeded

       64 bit unsigned wrappable counter."
   ::= {pr1645v2EthPortSwIVlanEntry 42074112}

pr1645v2EthPortSwIVlanMCInDropNoMac OBJECT-TYPE
   SYNTAX      Counter64
   MAX-ACCESS  read-only
   STATUS      current
   DESCRIPTION
      "Path: swPort.performance.vlan.mibCounters.ifInDiscardsNoMacFit

       64 bit unsigned wrappable counter."
   ::= {pr1645v2EthPortSwIVlanEntry 42270720}

pr1645v2EthPortSwIVlanMCInDropNUCast OBJECT-TYPE
   SYNTAX      Counter64
   MAX-ACCESS  read-only
   STATUS      current
   DESCRIPTION
      "Path: swPort.performance.vlan.mibCounters.ifInDiscardsNUCast

       64 bit unsigned wrappable counter."
   ::= {pr1645v2EthPortSwIVlanEntry 42467328}

pr1645v2EthPortSwIVlanMCInDropFilter OBJECT-TYPE
   SYNTAX      Counter64
   MAX-ACCESS  read-only
   STATUS      current
   DESCRIPTION
      "Path: swPort.performance.vlan.mibCounters.ifInDiscardsFilter

       64 bit unsigned wrappable counter."
   ::= {pr1645v2EthPortSwIVlanEntry 42532864}

pr1645v2EthPortSwIVlanMCInBandwidth15sec OBJECT-TYPE
   SYNTAX      Integer32
   MAX-ACCESS  read-only
   STATUS      current
   DESCRIPTION
      "Path: swPort.performance.vlan.mibCounters.ifInBandwidth.15sec

       unit name = bps
       formula = 8 * ; 8 /"
   ::= {pr1645v2EthPortSwIVlanEntry 45417728}

pr1645v2EthPortSwIVlanMCInBandwidth30sec OBJECT-TYPE
   SYNTAX      Integer32
   MAX-ACCESS  read-only
   STATUS      current
   DESCRIPTION
      "Path: swPort.performance.vlan.mibCounters.ifInBandwidth.30sec

       unit name = bps
       formula = 8 * ; 8 /"
   ::= {pr1645v2EthPortSwIVlanEntry 45419008}

pr1645v2EthPortSwIVlanMCInBandwidth1min OBJECT-TYPE
   SYNTAX      Integer32
   MAX-ACCESS  read-only
   STATUS      current
   DESCRIPTION
      "Path: swPort.performance.vlan.mibCounters.ifInBandwidth.1min

       unit name = bps
       formula = 8 * ; 8 /"
   ::= {pr1645v2EthPortSwIVlanEntry 45421568}

pr1645v2EthPortSwIVlanMCInBandwidth2min OBJECT-TYPE
   SYNTAX      Integer32
   MAX-ACCESS  read-only
   STATUS      current
   DESCRIPTION
      "Path: swPort.performance.vlan.mibCounters.ifInBandwidth.2min

       unit name = bps
       formula = 8 * ; 8 /"
   ::= {pr1645v2EthPortSwIVlanEntry 45426688}

pr1645v2EthPortSwIVlanMCInBandwidth5min OBJECT-TYPE
   SYNTAX      Integer32
   MAX-ACCESS  read-only
   STATUS      current
   DESCRIPTION
      "Path: swPort.performance.vlan.mibCounters.ifInBandwidth.5min

       unit name = bps
       formula = 8 * ; 8 /"
   ::= {pr1645v2EthPortSwIVlanEntry 45442048}

pr1645v2EthPortSwIVlanMCOutOctets OBJECT-TYPE
   SYNTAX      Counter64
   MAX-ACCESS  read-only
   STATUS      current
   DESCRIPTION
      "Path: swPort.performance.vlan.mibCounters.ifOutOctets

       64 bit unsigned wrappable counter."
   ::= {pr1645v2EthPortSwIVlanEntry 41091072}

pr1645v2EthPortSwIVlanMCOutUcastPkts OBJECT-TYPE
   SYNTAX      Counter64
   MAX-ACCESS  read-only
   STATUS      current
   DESCRIPTION
      "Path: swPort.performance.vlan.mibCounters.ifOutUcastPkts

       64 bit unsigned wrappable counter."
   ::= {pr1645v2EthPortSwIVlanEntry 41156608}

pr1645v2EthPortSwIVlanMCOutNUcastPkts OBJECT-TYPE
   SYNTAX      Counter64
   MAX-ACCESS  read-only
   STATUS      current
   DESCRIPTION
      "Path: swPort.performance.vlan.mibCounters.ifOutNUcastPkts

       64 bit unsigned wrappable counter."
   ::= {pr1645v2EthPortSwIVlanEntry 41222144}

pr1645v2EthPortSwIVlanMCOutBcastPkts OBJECT-TYPE
   SYNTAX      Counter64
   MAX-ACCESS  read-only
   STATUS      current
   DESCRIPTION
      "Path: swPort.performance.vlan.mibCounters.ifOutBcastPkts

       64 bit unsigned wrappable counter."
   ::= {pr1645v2EthPortSwIVlanEntry 47775744}

pr1645v2EthPortSwIVlanMCOutMcastPkts OBJECT-TYPE
   SYNTAX      Counter64
   MAX-ACCESS  read-only
   STATUS      current
   DESCRIPTION
      "Path: swPort.performance.vlan.mibCounters.ifOutMcastPkts

       64 bit unsigned wrappable counter."
   ::= {pr1645v2EthPortSwIVlanEntry 48431104}

pr1645v2EthPortSwIVlanMCOutDiscards OBJECT-TYPE
   SYNTAX      Counter64
   MAX-ACCESS  read-only
   STATUS      current
   DESCRIPTION
      "Path: swPort.performance.vlan.mibCounters.ifOutDiscards

       64 bit unsigned wrappable counter."
   ::= {pr1645v2EthPortSwIVlanEntry 41287680}

pr1645v2EthPortSwIVlanMCOutErrors OBJECT-TYPE
   SYNTAX      Counter64
   MAX-ACCESS  read-only
   STATUS      current
   DESCRIPTION
      "Path: swPort.performance.vlan.mibCounters.ifOutErrors

       64 bit unsigned wrappable counter."
   ::= {pr1645v2EthPortSwIVlanEntry 41353216}

pr1645v2EthPortSwIVlanMCOutQLen OBJECT-TYPE
   SYNTAX      Counter32
   MAX-ACCESS  read-only
   STATUS      current
   DESCRIPTION
      "Path: swPort.performance.vlan.mibCounters.ifOutQLen

       32 bit unsigned wrappable counter."
   ::= {pr1645v2EthPortSwIVlanEntry 41418752}

pr1645v2EthPortSwIVlanMCOutDropEx OBJECT-TYPE
   SYNTAX      Counter64
   MAX-ACCESS  read-only
   STATUS      current
   DESCRIPTION
      "Path: swPort.performance.vlan.mibCounters.ifOutDropLevelExceeded

       64 bit unsigned wrappable counter."
   ::= {pr1645v2EthPortSwIVlanEntry 41484288}

pr1645v2EthPortSwIVlanMCOutDropNoArp OBJECT-TYPE
   SYNTAX      Counter64
   MAX-ACCESS  read-only
   STATUS      current
   DESCRIPTION
      "Path: swPort.performance.vlan.mibCounters.ifOutDiscardsNoArp

       64 bit unsigned wrappable counter."
   ::= {pr1645v2EthPortSwIVlanEntry 42336256}

pr1645v2EthPortSwIVlanMCOutDropFilter OBJECT-TYPE
   SYNTAX      Counter64
   MAX-ACCESS  read-only
   STATUS      current
   DESCRIPTION
      "Path: swPort.performance.vlan.mibCounters.ifOutDiscardsFilter

       64 bit unsigned wrappable counter."
   ::= {pr1645v2EthPortSwIVlanEntry 42598400}

pr1645v2EthPortSwIVlanMCOutBandwidth15sec OBJECT-TYPE
   SYNTAX      Integer32
   MAX-ACCESS  read-only
   STATUS      current
   DESCRIPTION
      "Path: swPort.performance.vlan.mibCounters.ifOutBandwidth.15sec

       unit name = bps
       formula = 8 * ; 8 /"
   ::= {pr1645v2EthPortSwIVlanEntry 45483264}

pr1645v2EthPortSwIVlanMCOutBandwidth30sec OBJECT-TYPE
   SYNTAX      Integer32
   MAX-ACCESS  read-only
   STATUS      current
   DESCRIPTION
      "Path: swPort.performance.vlan.mibCounters.ifOutBandwidth.30sec

       unit name = bps
       formula = 8 * ; 8 /"
   ::= {pr1645v2EthPortSwIVlanEntry 45484544}

pr1645v2EthPortSwIVlanMCOutBandwidth1min OBJECT-TYPE
   SYNTAX      Integer32
   MAX-ACCESS  read-only
   STATUS      current
   DESCRIPTION
      "Path: swPort.performance.vlan.mibCounters.ifOutBandwidth.1min

       unit name = bps
       formula = 8 * ; 8 /"
   ::= {pr1645v2EthPortSwIVlanEntry 45487104}

pr1645v2EthPortSwIVlanMCOutBandwidth2min OBJECT-TYPE
   SYNTAX      Integer32
   MAX-ACCESS  read-only
   STATUS      current
   DESCRIPTION
      "Path: swPort.performance.vlan.mibCounters.ifOutBandwidth.2min

       unit name = bps
       formula = 8 * ; 8 /"
   ::= {pr1645v2EthPortSwIVlanEntry 45492224}

pr1645v2EthPortSwIVlanMCOutBandwidth5min OBJECT-TYPE
   SYNTAX      Integer32
   MAX-ACCESS  read-only
   STATUS      current
   DESCRIPTION
      "Path: swPort.performance.vlan.mibCounters.ifOutBandwidth.5min

       unit name = bps
       formula = 8 * ; 8 /"
   ::= {pr1645v2EthPortSwIVlanEntry 45507584}

pr1645v2EthPortSwIVlanVlanVid OBJECT-TYPE
   SYNTAX      Integer32
   MAX-ACCESS  read-only
   STATUS      current
   DESCRIPTION
      "Path: swPort.performance.vlan.vlan.vid"
   ::= {pr1645v2EthPortSwIVlanEntry 234946560}

pr1645v2EthPortSwIVlanPppLinkMonitoringRequestsSent OBJECT-TYPE
   SYNTAX      Gauge32
   MAX-ACCESS  read-only
   STATUS      current
   DESCRIPTION
      "Path: swPort.performance.vlan.ppp.linkMonitoring.requestsSent

       32 bit unsigned gauge value."
   ::= {pr1645v2EthPortSwIVlanEntry 50397440}

pr1645v2EthPortSwIVlanPppLinkMonitoringRepliesRcvd OBJECT-TYPE
   SYNTAX      Gauge32
   MAX-ACCESS  read-only
   STATUS      current
   DESCRIPTION
      "Path: swPort.performance.vlan.ppp.linkMonitoring.repliesRcvd

       32 bit unsigned gauge value."
   ::= {pr1645v2EthPortSwIVlanEntry 50397696}

pr1645v2EthPortSwIVlanPppLinkMonitoringRequestsRcvd OBJECT-TYPE
   SYNTAX      Gauge32
   MAX-ACCESS  read-only
   STATUS      current
   DESCRIPTION
      "Path: swPort.performance.vlan.ppp.linkMonitoring.requestsRcvd

       32 bit unsigned gauge value."
   ::= {pr1645v2EthPortSwIVlanEntry 50397952}

pr1645v2EthPortSwIVlanPppLinkMonitoringRepliesSent OBJECT-TYPE
   SYNTAX      Gauge32
   MAX-ACCESS  read-only
   STATUS      current
   DESCRIPTION
      "Path: swPort.performance.vlan.ppp.linkMonitoring.repliesSent

       32 bit unsigned gauge value."
   ::= {pr1645v2EthPortSwIVlanEntry 50398208}

pr1645v2EthPortSwIVlanMCH2P OBJECT-TYPE
   SYNTAX      SEQUENCE OF Pr1645v2EthPortSwIVlanMCH2PEntry
   MAX-ACCESS  not-accessible
   STATUS      current
   DESCRIPTION
      ""
   ::= {pr1645v2EthPortSwIVlan 41549824}

pr1645v2EthPortSwIVlanMCH2PEntry OBJECT-TYPE
   SYNTAX      Pr1645v2EthPortSwIVlanMCH2PEntry
   MAX-ACCESS  not-accessible
   STATUS      current
   DESCRIPTION
      ""
   INDEX      { pr1645v2EthPortSwIVlanMCH2PGlobalIx,
                pr1645v2EthPortSwIVlanTableIx,
                pr1645v2EthPortSwIVlanMCH2PTableIx }
   ::= {pr1645v2EthPortSwIVlanMCH2P 1}

Pr1645v2EthPortSwIVlanMCH2PEntry ::=
   SEQUENCE
      {
      pr1645v2EthPortSwIVlanMCH2PGlobalIx
         GlobalIndex,
      pr1645v2EthPortSwIVlanMCH2PTableIx
         TableIndex,
      pr1645v2EthPortSwIVlanMCH2PSysUpTime
         TimeTicks,
      pr1645v2EthPortSwIVlanMCH2PIfUpTime
         TimeTicks,
      pr1645v2EthPortSwIVlanMCH2PIfStatChanges
         Counter32,
      pr1645v2EthPortSwIVlanMCH2PIfInOctets
         Counter64,
      pr1645v2EthPortSwIVlanMCH2PIfInUCPkts
         Counter64,
      pr1645v2EthPortSwIVlanMCH2PIfInNUCPkts
         Counter64,
      pr1645v2EthPortSwIVlanMCH2PIfInBCPkts
         Counter64,
      pr1645v2EthPortSwIVlanMCH2PIfInMCPkts
         Counter64,
      pr1645v2EthPortSwIVlanMCH2PIfInDiscards
         Counter64,
      pr1645v2EthPortSwIVlanMCH2PIfInErrors
         Counter64,
      pr1645v2EthPortSwIVlanMCH2PIfInUnkwn
         Counter64,
      pr1645v2EthPortSwIVlanMCH2PInDropEx
         Counter64,
      pr1645v2EthPortSwIVlanMCH2PInDropNoMac
         Counter64,
      pr1645v2EthPortSwIVlanMCH2PInDropNUCast
         Counter64,
      pr1645v2EthPortSwIVlanMCH2PInDropFilter
         Counter64,
      pr1645v2EthPortSwIVlanMCH2PIfInBandwidth
         Integer32,
      pr1645v2EthPortSwIVlanMCH2PIfOutOctets
         Counter64,
      pr1645v2EthPortSwIVlanMCH2PIfOutUCPkts
         Counter64,
      pr1645v2EthPortSwIVlanMCH2PIfOutNUCPkts
         Counter64,
      pr1645v2EthPortSwIVlanMCH2PIfOutBCPkts
         Counter64,
      pr1645v2EthPortSwIVlanMCH2PIfOutMCPkts
         Counter64,
      pr1645v2EthPortSwIVlanMCH2PIfOutDiscards
         Counter64,
      pr1645v2EthPortSwIVlanMCH2PIfOutErrors
         Counter64,
      pr1645v2EthPortSwIVlanMCH2POutDropEx
         Counter64,
      pr1645v2EthPortSwIVlanMCH2POutDropNoArp
         Counter64,
      pr1645v2EthPortSwIVlanMCH2POutDropFilter
         Counter64,
      pr1645v2EthPortSwIVlanMCH2PIfOutBandwidth
         Integer32,
      pr1645v2EthPortSwIVlanMCH2PIfErrSec
         Counter32
      }

pr1645v2EthPortSwIVlanMCH2PGlobalIx OBJECT-TYPE
   SYNTAX      GlobalIndex
   MAX-ACCESS  not-accessible
   STATUS      current
   DESCRIPTION
      "The value of the tlsCntTreeGlobalIndex of the MANAGED OBJECT."
   ::= {pr1645v2EthPortSwIVlanMCH2PEntry 10}

pr1645v2EthPortSwIVlanMCH2PTableIx OBJECT-TYPE
   SYNTAX      TableIndex
   MAX-ACCESS  not-accessible
   STATUS      current
   DESCRIPTION
      ""
   ::= {pr1645v2EthPortSwIVlanMCH2PEntry 11}

pr1645v2EthPortSwIVlanMCH2PSysUpTime OBJECT-TYPE
   SYNTAX      TimeTicks
   MAX-ACCESS  read-only
   STATUS      current
   DESCRIPTION
      "Path: swPort.performance.vlan.mibCounters.h2Performance.sysUpTime

       Time in centi-second."
   ::= {pr1645v2EthPortSwIVlanMCH2PEntry 16777216}

pr1645v2EthPortSwIVlanMCH2PIfUpTime OBJECT-TYPE
   SYNTAX      TimeTicks
   MAX-ACCESS  read-only
   STATUS      current
   DESCRIPTION
      "Path: swPort.performance.vlan.mibCounters.h2Performance.ifUpTime

       Time in centi-second."
   ::= {pr1645v2EthPortSwIVlanMCH2PEntry 33554432}

pr1645v2EthPortSwIVlanMCH2PIfStatChanges OBJECT-TYPE
   SYNTAX      Counter32
   MAX-ACCESS  read-only
   STATUS      current
   DESCRIPTION
      "Path: swPort.performance.vlan.mibCounters.h2Performance.ifStatusChanges

       32 bit unsigned wrappable counter."
   ::= {pr1645v2EthPortSwIVlanMCH2PEntry 50331648}

pr1645v2EthPortSwIVlanMCH2PIfInOctets OBJECT-TYPE
   SYNTAX      Counter64
   MAX-ACCESS  read-only
   STATUS      current
   DESCRIPTION
      "Path: swPort.performance.vlan.mibCounters.h2Performance.ifInOctets

       64 bit unsigned wrappable counter."
   ::= {pr1645v2EthPortSwIVlanMCH2PEntry 67108864}

pr1645v2EthPortSwIVlanMCH2PIfInUCPkts OBJECT-TYPE
   SYNTAX      Counter64
   MAX-ACCESS  read-only
   STATUS      current
   DESCRIPTION
      "Path: swPort.performance.vlan.mibCounters.h2Performance.ifInUcastPkts

       64 bit unsigned wrappable counter."
   ::= {pr1645v2EthPortSwIVlanMCH2PEntry 83886080}

pr1645v2EthPortSwIVlanMCH2PIfInNUCPkts OBJECT-TYPE
   SYNTAX      Counter64
   MAX-ACCESS  read-only
   STATUS      current
   DESCRIPTION
      "Path: swPort.performance.vlan.mibCounters.h2Performance.ifInNUcastPkts

       64 bit unsigned wrappable counter."
   ::= {pr1645v2EthPortSwIVlanMCH2PEntry 100663296}

pr1645v2EthPortSwIVlanMCH2PIfInBCPkts OBJECT-TYPE
   SYNTAX      Counter64
   MAX-ACCESS  read-only
   STATUS      current
   DESCRIPTION
      "Path: swPort.performance.vlan.mibCounters.h2Performance.ifInBcastPkts

       64 bit unsigned wrappable counter."
   ::= {pr1645v2EthPortSwIVlanMCH2PEntry 419430400}

pr1645v2EthPortSwIVlanMCH2PIfInMCPkts OBJECT-TYPE
   SYNTAX      Counter64
   MAX-ACCESS  read-only
   STATUS      current
   DESCRIPTION
      "Path: swPort.performance.vlan.mibCounters.h2Performance.ifInMcastPkts

       64 bit unsigned wrappable counter."
   ::= {pr1645v2EthPortSwIVlanMCH2PEntry 436207616}

pr1645v2EthPortSwIVlanMCH2PIfInDiscards OBJECT-TYPE
   SYNTAX      Counter64
   MAX-ACCESS  read-only
   STATUS      current
   DESCRIPTION
      "Path: swPort.performance.vlan.mibCounters.h2Performance.ifInDiscards

       64 bit unsigned wrappable counter."
   ::= {pr1645v2EthPortSwIVlanMCH2PEntry 117440512}

pr1645v2EthPortSwIVlanMCH2PIfInErrors OBJECT-TYPE
   SYNTAX      Counter64
   MAX-ACCESS  read-only
   STATUS      current
   DESCRIPTION
      "Path: swPort.performance.vlan.mibCounters.h2Performance.ifInErrors

       64 bit unsigned wrappable counter."
   ::= {pr1645v2EthPortSwIVlanMCH2PEntry 134217728}

pr1645v2EthPortSwIVlanMCH2PIfInUnkwn OBJECT-TYPE
   SYNTAX      Counter64
   MAX-ACCESS  read-only
   STATUS      current
   DESCRIPTION
      "Path: swPort.performance.vlan.mibCounters.h2Performance.ifInUnknownProtos

       64 bit unsigned wrappable counter."
   ::= {pr1645v2EthPortSwIVlanMCH2PEntry 150994944}

pr1645v2EthPortSwIVlanMCH2PInDropEx OBJECT-TYPE
   SYNTAX      Counter64
   MAX-ACCESS  read-only
   STATUS      current
   DESCRIPTION
      "Path: swPort.performance.vlan.mibCounters.h2Performance.ifInDropLevelExceeded

       64 bit unsigned wrappable counter."
   ::= {pr1645v2EthPortSwIVlanMCH2PEntry 335544320}

pr1645v2EthPortSwIVlanMCH2PInDropNoMac OBJECT-TYPE
   SYNTAX      Counter64
   MAX-ACCESS  read-only
   STATUS      current
   DESCRIPTION
      "Path: swPort.performance.vlan.mibCounters.h2Performance.fInDiscardsNoMacFit

       64 bit unsigned wrappable counter."
   ::= {pr1645v2EthPortSwIVlanMCH2PEntry 301989888}

pr1645v2EthPortSwIVlanMCH2PInDropNUCast OBJECT-TYPE
   SYNTAX      Counter64
   MAX-ACCESS  read-only
   STATUS      current
   DESCRIPTION
      "Path: swPort.performance.vlan.mibCounters.h2Performance.fInDiscardsNUCast

       64 bit unsigned wrappable counter."
   ::= {pr1645v2EthPortSwIVlanMCH2PEntry 318767104}

pr1645v2EthPortSwIVlanMCH2PInDropFilter OBJECT-TYPE
   SYNTAX      Counter64
   MAX-ACCESS  read-only
   STATUS      current
   DESCRIPTION
      "Path: swPort.performance.vlan.mibCounters.h2Performance.fInDiscardsFilter

       64 bit unsigned wrappable counter."
   ::= {pr1645v2EthPortSwIVlanMCH2PEntry 385875968}

pr1645v2EthPortSwIVlanMCH2PIfInBandwidth OBJECT-TYPE
   SYNTAX      Integer32
   MAX-ACCESS  read-only
   STATUS      current
   DESCRIPTION
      "Path: swPort.performance.vlan.mibCounters.h2Performance.ifInBandwidth

       unit name = bps
       formula = 8 * ; 8 /"
   ::= {pr1645v2EthPortSwIVlanMCH2PEntry 268435456}

pr1645v2EthPortSwIVlanMCH2PIfOutOctets OBJECT-TYPE
   SYNTAX      Counter64
   MAX-ACCESS  read-only
   STATUS      current
   DESCRIPTION
      "Path: swPort.performance.vlan.mibCounters.h2Performance.ifOutOctets

       64 bit unsigned wrappable counter."
   ::= {pr1645v2EthPortSwIVlanMCH2PEntry 167772160}

pr1645v2EthPortSwIVlanMCH2PIfOutUCPkts OBJECT-TYPE
   SYNTAX      Counter64
   MAX-ACCESS  read-only
   STATUS      current
   DESCRIPTION
      "Path: swPort.performance.vlan.mibCounters.h2Performance.ifOutUcastPkts

       64 bit unsigned wrappable counter."
   ::= {pr1645v2EthPortSwIVlanMCH2PEntry 184549376}

pr1645v2EthPortSwIVlanMCH2PIfOutNUCPkts OBJECT-TYPE
   SYNTAX      Counter64
   MAX-ACCESS  read-only
   STATUS      current
   DESCRIPTION
      "Path: swPort.performance.vlan.mibCounters.h2Performance.ifOutNUcastPkts

       64 bit unsigned wrappable counter."
   ::= {pr1645v2EthPortSwIVlanMCH2PEntry 201326592}

pr1645v2EthPortSwIVlanMCH2PIfOutBCPkts OBJECT-TYPE
   SYNTAX      Counter64
   MAX-ACCESS  read-only
   STATUS      current
   DESCRIPTION
      "Path: swPort.performance.vlan.mibCounters.h2Performance.ifOutBcastPkts

       64 bit unsigned wrappable counter."
   ::= {pr1645v2EthPortSwIVlanMCH2PEntry 452984832}

pr1645v2EthPortSwIVlanMCH2PIfOutMCPkts OBJECT-TYPE
   SYNTAX      Counter64
   MAX-ACCESS  read-only
   STATUS      current
   DESCRIPTION
      "Path: swPort.performance.vlan.mibCounters.h2Performance.ifOutMcastPkts

       64 bit unsigned wrappable counter."
   ::= {pr1645v2EthPortSwIVlanMCH2PEntry 469762048}

pr1645v2EthPortSwIVlanMCH2PIfOutDiscards OBJECT-TYPE
   SYNTAX      Counter64
   MAX-ACCESS  read-only
   STATUS      current
   DESCRIPTION
      "Path: swPort.performance.vlan.mibCounters.h2Performance.ifOutDiscards

       64 bit unsigned wrappable counter."
   ::= {pr1645v2EthPortSwIVlanMCH2PEntry 218103808}

pr1645v2EthPortSwIVlanMCH2PIfOutErrors OBJECT-TYPE
   SYNTAX      Counter64
   MAX-ACCESS  read-only
   STATUS      current
   DESCRIPTION
      "Path: swPort.performance.vlan.mibCounters.h2Performance.ifOutErrors

       64 bit unsigned wrappable counter."
   ::= {pr1645v2EthPortSwIVlanMCH2PEntry 234881024}

pr1645v2EthPortSwIVlanMCH2POutDropEx OBJECT-TYPE
   SYNTAX      Counter64
   MAX-ACCESS  read-only
   STATUS      current
   DESCRIPTION
      "Path: swPort.performance.vlan.mibCounters.h2Performance.ifOutDropLevelExceeded

       64 bit unsigned wrappable counter."
   ::= {pr1645v2EthPortSwIVlanMCH2PEntry 352321536}

pr1645v2EthPortSwIVlanMCH2POutDropNoArp OBJECT-TYPE
   SYNTAX      Counter64
   MAX-ACCESS  read-only
   STATUS      current
   DESCRIPTION
      "Path: swPort.performance.vlan.mibCounters.h2Performance.ifOutDiscardsNoArp

       64 bit unsigned wrappable counter."
   ::= {pr1645v2EthPortSwIVlanMCH2PEntry 369098752}

pr1645v2EthPortSwIVlanMCH2POutDropFilter OBJECT-TYPE
   SYNTAX      Counter64
   MAX-ACCESS  read-only
   STATUS      current
   DESCRIPTION
      "Path: swPort.performance.vlan.mibCounters.h2Performance.ifOutDiscardsFilter

       64 bit unsigned wrappable counter."
   ::= {pr1645v2EthPortSwIVlanMCH2PEntry 402653184}

pr1645v2EthPortSwIVlanMCH2PIfOutBandwidth OBJECT-TYPE
   SYNTAX      Integer32
   MAX-ACCESS  read-only
   STATUS      current
   DESCRIPTION
      "Path: swPort.performance.vlan.mibCounters.h2Performance.ifOutBandwidth

       unit name = bps
       formula = 8 * ; 8 /"
   ::= {pr1645v2EthPortSwIVlanMCH2PEntry 285212672}

pr1645v2EthPortSwIVlanMCH2PIfErrSec OBJECT-TYPE
   SYNTAX      Counter32
   MAX-ACCESS  read-only
   STATUS      current
   DESCRIPTION
      "Path: swPort.performance.vlan.mibCounters.h2Performance.ifErrSec

       32 bit unsigned wrappable counter."
   ::= {pr1645v2EthPortSwIVlanMCH2PEntry 251658240}

pr1645v2EthPortSwIVlanMCH24P OBJECT-TYPE
   SYNTAX      SEQUENCE OF Pr1645v2EthPortSwIVlanMCH24PEntry
   MAX-ACCESS  not-accessible
   STATUS      current
   DESCRIPTION
      ""
   ::= {pr1645v2EthPortSwIVlan 41615360}

pr1645v2EthPortSwIVlanMCH24PEntry OBJECT-TYPE
   SYNTAX      Pr1645v2EthPortSwIVlanMCH24PEntry
   MAX-ACCESS  not-accessible
   STATUS      current
   DESCRIPTION
      ""
   INDEX      { pr1645v2EthPortSwIVlanMCH24PGlobalIx,
                pr1645v2EthPortSwIVlanTableIx,
                pr1645v2EthPortSwIVlanMCH24PTableIx }
   ::= {pr1645v2EthPortSwIVlanMCH24P 1}

Pr1645v2EthPortSwIVlanMCH24PEntry ::=
   SEQUENCE
      {
      pr1645v2EthPortSwIVlanMCH24PGlobalIx
         GlobalIndex,
      pr1645v2EthPortSwIVlanMCH24PTableIx
         TableIndex,
      pr1645v2EthPortSwIVlanMCH24PSysUpTime
         TimeTicks,
      pr1645v2EthPortSwIVlanMCH24PIfUpTime
         TimeTicks,
      pr1645v2EthPortSwIVlanMCH24PIfStatChanges
         Counter32,
      pr1645v2EthPortSwIVlanMCH24PIfInOctets
         Counter64,
      pr1645v2EthPortSwIVlanMCH24PIfInUCPkts
         Counter64,
      pr1645v2EthPortSwIVlanMCH24PIfInNUCPkts
         Counter64,
      pr1645v2EthPortSwIVlanMCH24PIfInBCPkts
         Counter64,
      pr1645v2EthPortSwIVlanMCH24PIfInMCPkts
         Counter64,
      pr1645v2EthPortSwIVlanMCH24PIfInDiscards
         Counter64,
      pr1645v2EthPortSwIVlanMCH24PIfInErrors
         Counter64,
      pr1645v2EthPortSwIVlanMCH24PIfInUnkwn
         Counter64,
      pr1645v2EthPortSwIVlanMCH24PInDropEx
         Counter64,
      pr1645v2EthPortSwIVlanMCH24PInDropNoMac
         Counter64,
      pr1645v2EthPortSwIVlanMCH24PInDropNUCast
         Counter64,
      pr1645v2EthPortSwIVlanMCH24PInDropFilter
         Counter64,
      pr1645v2EthPortSwIVlanMCH24PIfInBandwidth
         Integer32,
      pr1645v2EthPortSwIVlanMCH24PIfOutOctets
         Counter64,
      pr1645v2EthPortSwIVlanMCH24PIfOutUCPkts
         Counter64,
      pr1645v2EthPortSwIVlanMCH24PIfOutNUCPkts
         Counter64,
      pr1645v2EthPortSwIVlanMCH24PIfOutBCPkts
         Counter64,
      pr1645v2EthPortSwIVlanMCH24PIfOutMCPkts
         Counter64,
      pr1645v2EthPortSwIVlanMCH24PIfOutDiscards
         Counter64,
      pr1645v2EthPortSwIVlanMCH24PIfOutErrors
         Counter64,
      pr1645v2EthPortSwIVlanMCH24POutDropEx
         Counter64,
      pr1645v2EthPortSwIVlanMCH24POutDropNoArp
         Counter64,
      pr1645v2EthPortSwIVlanMCH24POutDropFilter
         Counter64,
      pr1645v2EthPortSwIVlanMCH24PIfOutBandwidth
         Integer32,
      pr1645v2EthPortSwIVlanMCH24PIfErrSec
         Counter32
      }

pr1645v2EthPortSwIVlanMCH24PGlobalIx OBJECT-TYPE
   SYNTAX      GlobalIndex
   MAX-ACCESS  not-accessible
   STATUS      current
   DESCRIPTION
      "The value of the tlsCntTreeGlobalIndex of the MANAGED OBJECT."
   ::= {pr1645v2EthPortSwIVlanMCH24PEntry 10}

pr1645v2EthPortSwIVlanMCH24PTableIx OBJECT-TYPE
   SYNTAX      TableIndex
   MAX-ACCESS  not-accessible
   STATUS      current
   DESCRIPTION
      ""
   ::= {pr1645v2EthPortSwIVlanMCH24PEntry 11}

pr1645v2EthPortSwIVlanMCH24PSysUpTime OBJECT-TYPE
   SYNTAX      TimeTicks
   MAX-ACCESS  read-only
   STATUS      current
   DESCRIPTION
      "Path: swPort.performance.vlan.mibCounters.h24Performance.sysUpTime

       Time in centi-second."
   ::= {pr1645v2EthPortSwIVlanMCH24PEntry 16777216}

pr1645v2EthPortSwIVlanMCH24PIfUpTime OBJECT-TYPE
   SYNTAX      TimeTicks
   MAX-ACCESS  read-only
   STATUS      current
   DESCRIPTION
      "Path: swPort.performance.vlan.mibCounters.h24Performance.ifUpTime

       Time in centi-second."
   ::= {pr1645v2EthPortSwIVlanMCH24PEntry 33554432}

pr1645v2EthPortSwIVlanMCH24PIfStatChanges OBJECT-TYPE
   SYNTAX      Counter32
   MAX-ACCESS  read-only
   STATUS      current
   DESCRIPTION
      "Path: swPort.performance.vlan.mibCounters.h24Performance.ifStatusChanges

       32 bit unsigned wrappable counter."
   ::= {pr1645v2EthPortSwIVlanMCH24PEntry 50331648}

pr1645v2EthPortSwIVlanMCH24PIfInOctets OBJECT-TYPE
   SYNTAX      Counter64
   MAX-ACCESS  read-only
   STATUS      current
   DESCRIPTION
      "Path: swPort.performance.vlan.mibCounters.h24Performance.ifInOctets

       64 bit unsigned wrappable counter."
   ::= {pr1645v2EthPortSwIVlanMCH24PEntry 67108864}

pr1645v2EthPortSwIVlanMCH24PIfInUCPkts OBJECT-TYPE
   SYNTAX      Counter64
   MAX-ACCESS  read-only
   STATUS      current
   DESCRIPTION
      "Path: swPort.performance.vlan.mibCounters.h24Performance.ifInUcastPkts

       64 bit unsigned wrappable counter."
   ::= {pr1645v2EthPortSwIVlanMCH24PEntry 83886080}

pr1645v2EthPortSwIVlanMCH24PIfInNUCPkts OBJECT-TYPE
   SYNTAX      Counter64
   MAX-ACCESS  read-only
   STATUS      current
   DESCRIPTION
      "Path: swPort.performance.vlan.mibCounters.h24Performance.ifInNUcastPkts

       64 bit unsigned wrappable counter."
   ::= {pr1645v2EthPortSwIVlanMCH24PEntry 100663296}

pr1645v2EthPortSwIVlanMCH24PIfInBCPkts OBJECT-TYPE
   SYNTAX      Counter64
   MAX-ACCESS  read-only
   STATUS      current
   DESCRIPTION
      "Path: swPort.performance.vlan.mibCounters.h24Performance.ifInBcastPkts

       64 bit unsigned wrappable counter."
   ::= {pr1645v2EthPortSwIVlanMCH24PEntry 419430400}

pr1645v2EthPortSwIVlanMCH24PIfInMCPkts OBJECT-TYPE
   SYNTAX      Counter64
   MAX-ACCESS  read-only
   STATUS      current
   DESCRIPTION
      "Path: swPort.performance.vlan.mibCounters.h24Performance.ifInMcastPkts

       64 bit unsigned wrappable counter."
   ::= {pr1645v2EthPortSwIVlanMCH24PEntry 436207616}

pr1645v2EthPortSwIVlanMCH24PIfInDiscards OBJECT-TYPE
   SYNTAX      Counter64
   MAX-ACCESS  read-only
   STATUS      current
   DESCRIPTION
      "Path: swPort.performance.vlan.mibCounters.h24Performance.ifInDiscards

       64 bit unsigned wrappable counter."
   ::= {pr1645v2EthPortSwIVlanMCH24PEntry 117440512}

pr1645v2EthPortSwIVlanMCH24PIfInErrors OBJECT-TYPE
   SYNTAX      Counter64
   MAX-ACCESS  read-only
   STATUS      current
   DESCRIPTION
      "Path: swPort.performance.vlan.mibCounters.h24Performance.ifInErrors

       64 bit unsigned wrappable counter."
   ::= {pr1645v2EthPortSwIVlanMCH24PEntry 134217728}

pr1645v2EthPortSwIVlanMCH24PIfInUnkwn OBJECT-TYPE
   SYNTAX      Counter64
   MAX-ACCESS  read-only
   STATUS      current
   DESCRIPTION
      "Path: swPort.performance.vlan.mibCounters.h24Performance.ifInUnknownProtos

       64 bit unsigned wrappable counter."
   ::= {pr1645v2EthPortSwIVlanMCH24PEntry 150994944}

pr1645v2EthPortSwIVlanMCH24PInDropEx OBJECT-TYPE
   SYNTAX      Counter64
   MAX-ACCESS  read-only
   STATUS      current
   DESCRIPTION
      "Path: swPort.performance.vlan.mibCounters.h24Performance.ifInDropLevelExceeded

       64 bit unsigned wrappable counter."
   ::= {pr1645v2EthPortSwIVlanMCH24PEntry 335544320}

pr1645v2EthPortSwIVlanMCH24PInDropNoMac OBJECT-TYPE
   SYNTAX      Counter64
   MAX-ACCESS  read-only
   STATUS      current
   DESCRIPTION
      "Path: swPort.performance.vlan.mibCounters.h24Performance.fInDiscardsNoMacFit

       64 bit unsigned wrappable counter."
   ::= {pr1645v2EthPortSwIVlanMCH24PEntry 301989888}

pr1645v2EthPortSwIVlanMCH24PInDropNUCast OBJECT-TYPE
   SYNTAX      Counter64
   MAX-ACCESS  read-only
   STATUS      current
   DESCRIPTION
      "Path: swPort.performance.vlan.mibCounters.h24Performance.fInDiscardsNUCast

       64 bit unsigned wrappable counter."
   ::= {pr1645v2EthPortSwIVlanMCH24PEntry 318767104}

pr1645v2EthPortSwIVlanMCH24PInDropFilter OBJECT-TYPE
   SYNTAX      Counter64
   MAX-ACCESS  read-only
   STATUS      current
   DESCRIPTION
      "Path: swPort.performance.vlan.mibCounters.h24Performance.fInDiscardsFilter

       64 bit unsigned wrappable counter."
   ::= {pr1645v2EthPortSwIVlanMCH24PEntry 385875968}

pr1645v2EthPortSwIVlanMCH24PIfInBandwidth OBJECT-TYPE
   SYNTAX      Integer32
   MAX-ACCESS  read-only
   STATUS      current
   DESCRIPTION
      "Path: swPort.performance.vlan.mibCounters.h24Performance.ifInBandwidth

       unit name = bps
       formula = 8 * ; 8 /"
   ::= {pr1645v2EthPortSwIVlanMCH24PEntry 268435456}

pr1645v2EthPortSwIVlanMCH24PIfOutOctets OBJECT-TYPE
   SYNTAX      Counter64
   MAX-ACCESS  read-only
   STATUS      current
   DESCRIPTION
      "Path: swPort.performance.vlan.mibCounters.h24Performance.ifOutOctets

       64 bit unsigned wrappable counter."
   ::= {pr1645v2EthPortSwIVlanMCH24PEntry 167772160}

pr1645v2EthPortSwIVlanMCH24PIfOutUCPkts OBJECT-TYPE
   SYNTAX      Counter64
   MAX-ACCESS  read-only
   STATUS      current
   DESCRIPTION
      "Path: swPort.performance.vlan.mibCounters.h24Performance.ifOutUcastPkts

       64 bit unsigned wrappable counter."
   ::= {pr1645v2EthPortSwIVlanMCH24PEntry 184549376}

pr1645v2EthPortSwIVlanMCH24PIfOutNUCPkts OBJECT-TYPE
   SYNTAX      Counter64
   MAX-ACCESS  read-only
   STATUS      current
   DESCRIPTION
      "Path: swPort.performance.vlan.mibCounters.h24Performance.ifOutNUcastPkts

       64 bit unsigned wrappable counter."
   ::= {pr1645v2EthPortSwIVlanMCH24PEntry 201326592}

pr1645v2EthPortSwIVlanMCH24PIfOutBCPkts OBJECT-TYPE
   SYNTAX      Counter64
   MAX-ACCESS  read-only
   STATUS      current
   DESCRIPTION
      "Path: swPort.performance.vlan.mibCounters.h24Performance.ifOutBcastPkts

       64 bit unsigned wrappable counter."
   ::= {pr1645v2EthPortSwIVlanMCH24PEntry 452984832}

pr1645v2EthPortSwIVlanMCH24PIfOutMCPkts OBJECT-TYPE
   SYNTAX      Counter64
   MAX-ACCESS  read-only
   STATUS      current
   DESCRIPTION
      "Path: swPort.performance.vlan.mibCounters.h24Performance.ifOutMcastPkts

       64 bit unsigned wrappable counter."
   ::= {pr1645v2EthPortSwIVlanMCH24PEntry 469762048}

pr1645v2EthPortSwIVlanMCH24PIfOutDiscards OBJECT-TYPE
   SYNTAX      Counter64
   MAX-ACCESS  read-only
   STATUS      current
   DESCRIPTION
      "Path: swPort.performance.vlan.mibCounters.h24Performance.ifOutDiscards

       64 bit unsigned wrappable counter."
   ::= {pr1645v2EthPortSwIVlanMCH24PEntry 218103808}

pr1645v2EthPortSwIVlanMCH24PIfOutErrors OBJECT-TYPE
   SYNTAX      Counter64
   MAX-ACCESS  read-only
   STATUS      current
   DESCRIPTION
      "Path: swPort.performance.vlan.mibCounters.h24Performance.ifOutErrors

       64 bit unsigned wrappable counter."
   ::= {pr1645v2EthPortSwIVlanMCH24PEntry 234881024}

pr1645v2EthPortSwIVlanMCH24POutDropEx OBJECT-TYPE
   SYNTAX      Counter64
   MAX-ACCESS  read-only
   STATUS      current
   DESCRIPTION
      "Path: swPort.performance.vlan.mibCounters.h24Performance.ifOutDropLevelExceeded

       64 bit unsigned wrappable counter."
   ::= {pr1645v2EthPortSwIVlanMCH24PEntry 352321536}

pr1645v2EthPortSwIVlanMCH24POutDropNoArp OBJECT-TYPE
   SYNTAX      Counter64
   MAX-ACCESS  read-only
   STATUS      current
   DESCRIPTION
      "Path: swPort.performance.vlan.mibCounters.h24Performance.ifOutDiscardsNoArp

       64 bit unsigned wrappable counter."
   ::= {pr1645v2EthPortSwIVlanMCH24PEntry 369098752}

pr1645v2EthPortSwIVlanMCH24POutDropFilter OBJECT-TYPE
   SYNTAX      Counter64
   MAX-ACCESS  read-only
   STATUS      current
   DESCRIPTION
      "Path: swPort.performance.vlan.mibCounters.h24Performance.ifOutDiscardsFilter

       64 bit unsigned wrappable counter."
   ::= {pr1645v2EthPortSwIVlanMCH24PEntry 402653184}

pr1645v2EthPortSwIVlanMCH24PIfOutBandwidth OBJECT-TYPE
   SYNTAX      Integer32
   MAX-ACCESS  read-only
   STATUS      current
   DESCRIPTION
      "Path: swPort.performance.vlan.mibCounters.h24Performance.ifOutBandwidth

       unit name = bps
       formula = 8 * ; 8 /"
   ::= {pr1645v2EthPortSwIVlanMCH24PEntry 285212672}

pr1645v2EthPortSwIVlanMCH24PIfErrSec OBJECT-TYPE
   SYNTAX      Counter32
   MAX-ACCESS  read-only
   STATUS      current
   DESCRIPTION
      "Path: swPort.performance.vlan.mibCounters.h24Performance.ifErrSec

       32 bit unsigned wrappable counter."
   ::= {pr1645v2EthPortSwIVlanMCH24PEntry 251658240}

pr1645v2EthPortSwIVlanMCD7P OBJECT-TYPE
   SYNTAX      SEQUENCE OF Pr1645v2EthPortSwIVlanMCD7PEntry
   MAX-ACCESS  not-accessible
   STATUS      current
   DESCRIPTION
      ""
   ::= {pr1645v2EthPortSwIVlan 41680896}

pr1645v2EthPortSwIVlanMCD7PEntry OBJECT-TYPE
   SYNTAX      Pr1645v2EthPortSwIVlanMCD7PEntry
   MAX-ACCESS  not-accessible
   STATUS      current
   DESCRIPTION
      ""
   INDEX      { pr1645v2EthPortSwIVlanMCD7PGlobalIx,
                pr1645v2EthPortSwIVlanTableIx,
                pr1645v2EthPortSwIVlanMCD7PTableIx }
   ::= {pr1645v2EthPortSwIVlanMCD7P 1}

Pr1645v2EthPortSwIVlanMCD7PEntry ::=
   SEQUENCE
      {
      pr1645v2EthPortSwIVlanMCD7PGlobalIx
         GlobalIndex,
      pr1645v2EthPortSwIVlanMCD7PTableIx
         TableIndex,
      pr1645v2EthPortSwIVlanMCD7PSysUpTime
         TimeTicks,
      pr1645v2EthPortSwIVlanMCD7PIfUpTime
         TimeTicks,
      pr1645v2EthPortSwIVlanMCD7PIfStatChanges
         Counter32,
      pr1645v2EthPortSwIVlanMCD7PIfInOctets
         Counter64,
      pr1645v2EthPortSwIVlanMCD7PIfInUCPkts
         Counter64,
      pr1645v2EthPortSwIVlanMCD7PIfInNUCPkts
         Counter64,
      pr1645v2EthPortSwIVlanMCD7PIfInBCPkts
         Counter64,
      pr1645v2EthPortSwIVlanMCD7PIfInMCPkts
         Counter64,
      pr1645v2EthPortSwIVlanMCD7PIfInDiscards
         Counter64,
      pr1645v2EthPortSwIVlanMCD7PIfInErrors
         Counter64,
      pr1645v2EthPortSwIVlanMCD7PIfInUnkwn
         Counter64,
      pr1645v2EthPortSwIVlanMCD7PInDropEx
         Counter64,
      pr1645v2EthPortSwIVlanMCD7PInDropNoMac
         Counter64,
      pr1645v2EthPortSwIVlanMCD7PInDropNUCast
         Counter64,
      pr1645v2EthPortSwIVlanMCD7PInDropFilter
         Counter64,
      pr1645v2EthPortSwIVlanMCD7PIfInBandwidth
         Integer32,
      pr1645v2EthPortSwIVlanMCD7PIfOutOctets
         Counter64,
      pr1645v2EthPortSwIVlanMCD7PIfOutUCPkts
         Counter64,
      pr1645v2EthPortSwIVlanMCD7PIfOutNUCPkts
         Counter64,
      pr1645v2EthPortSwIVlanMCD7PIfOutBCPkts
         Counter64,
      pr1645v2EthPortSwIVlanMCD7PIfOutMCPkts
         Counter64,
      pr1645v2EthPortSwIVlanMCD7PIfOutDiscards
         Counter64,
      pr1645v2EthPortSwIVlanMCD7PIfOutErrors
         Counter64,
      pr1645v2EthPortSwIVlanMCD7POutDropEx
         Counter64,
      pr1645v2EthPortSwIVlanMCD7POutDropNoArp
         Counter64,
      pr1645v2EthPortSwIVlanMCD7POutDropFilter
         Counter64,
      pr1645v2EthPortSwIVlanMCD7PIfOutBandwidth
         Integer32,
      pr1645v2EthPortSwIVlanMCD7PIfErrSec
         Counter32
      }

pr1645v2EthPortSwIVlanMCD7PGlobalIx OBJECT-TYPE
   SYNTAX      GlobalIndex
   MAX-ACCESS  not-accessible
   STATUS      current
   DESCRIPTION
      "The value of the tlsCntTreeGlobalIndex of the MANAGED OBJECT."
   ::= {pr1645v2EthPortSwIVlanMCD7PEntry 10}

pr1645v2EthPortSwIVlanMCD7PTableIx OBJECT-TYPE
   SYNTAX      TableIndex
   MAX-ACCESS  not-accessible
   STATUS      current
   DESCRIPTION
      ""
   ::= {pr1645v2EthPortSwIVlanMCD7PEntry 11}

pr1645v2EthPortSwIVlanMCD7PSysUpTime OBJECT-TYPE
   SYNTAX      TimeTicks
   MAX-ACCESS  read-only
   STATUS      current
   DESCRIPTION
      "Path: swPort.performance.vlan.mibCounters.d7Performance.sysUpTime

       Time in centi-second."
   ::= {pr1645v2EthPortSwIVlanMCD7PEntry 16777216}

pr1645v2EthPortSwIVlanMCD7PIfUpTime OBJECT-TYPE
   SYNTAX      TimeTicks
   MAX-ACCESS  read-only
   STATUS      current
   DESCRIPTION
      "Path: swPort.performance.vlan.mibCounters.d7Performance.ifUpTime

       Time in centi-second."
   ::= {pr1645v2EthPortSwIVlanMCD7PEntry 33554432}

pr1645v2EthPortSwIVlanMCD7PIfStatChanges OBJECT-TYPE
   SYNTAX      Counter32
   MAX-ACCESS  read-only
   STATUS      current
   DESCRIPTION
      "Path: swPort.performance.vlan.mibCounters.d7Performance.ifStatusChanges

       32 bit unsigned wrappable counter."
   ::= {pr1645v2EthPortSwIVlanMCD7PEntry 50331648}

pr1645v2EthPortSwIVlanMCD7PIfInOctets OBJECT-TYPE
   SYNTAX      Counter64
   MAX-ACCESS  read-only
   STATUS      current
   DESCRIPTION
      "Path: swPort.performance.vlan.mibCounters.d7Performance.ifInOctets

       64 bit unsigned wrappable counter."
   ::= {pr1645v2EthPortSwIVlanMCD7PEntry 67108864}

pr1645v2EthPortSwIVlanMCD7PIfInUCPkts OBJECT-TYPE
   SYNTAX      Counter64
   MAX-ACCESS  read-only
   STATUS      current
   DESCRIPTION
      "Path: swPort.performance.vlan.mibCounters.d7Performance.ifInUcastPkts

       64 bit unsigned wrappable counter."
   ::= {pr1645v2EthPortSwIVlanMCD7PEntry 83886080}

pr1645v2EthPortSwIVlanMCD7PIfInNUCPkts OBJECT-TYPE
   SYNTAX      Counter64
   MAX-ACCESS  read-only
   STATUS      current
   DESCRIPTION
      "Path: swPort.performance.vlan.mibCounters.d7Performance.ifInNUcastPkts

       64 bit unsigned wrappable counter."
   ::= {pr1645v2EthPortSwIVlanMCD7PEntry 100663296}

pr1645v2EthPortSwIVlanMCD7PIfInBCPkts OBJECT-TYPE
   SYNTAX      Counter64
   MAX-ACCESS  read-only
   STATUS      current
   DESCRIPTION
      "Path: swPort.performance.vlan.mibCounters.d7Performance.ifInBcastPkts

       64 bit unsigned wrappable counter."
   ::= {pr1645v2EthPortSwIVlanMCD7PEntry 419430400}

pr1645v2EthPortSwIVlanMCD7PIfInMCPkts OBJECT-TYPE
   SYNTAX      Counter64
   MAX-ACCESS  read-only
   STATUS      current
   DESCRIPTION
      "Path: swPort.performance.vlan.mibCounters.d7Performance.ifInMcastPkts

       64 bit unsigned wrappable counter."
   ::= {pr1645v2EthPortSwIVlanMCD7PEntry 436207616}

pr1645v2EthPortSwIVlanMCD7PIfInDiscards OBJECT-TYPE
   SYNTAX      Counter64
   MAX-ACCESS  read-only
   STATUS      current
   DESCRIPTION
      "Path: swPort.performance.vlan.mibCounters.d7Performance.ifInDiscards

       64 bit unsigned wrappable counter."
   ::= {pr1645v2EthPortSwIVlanMCD7PEntry 117440512}

pr1645v2EthPortSwIVlanMCD7PIfInErrors OBJECT-TYPE
   SYNTAX      Counter64
   MAX-ACCESS  read-only
   STATUS      current
   DESCRIPTION
      "Path: swPort.performance.vlan.mibCounters.d7Performance.ifInErrors

       64 bit unsigned wrappable counter."
   ::= {pr1645v2EthPortSwIVlanMCD7PEntry 134217728}

pr1645v2EthPortSwIVlanMCD7PIfInUnkwn OBJECT-TYPE
   SYNTAX      Counter64
   MAX-ACCESS  read-only
   STATUS      current
   DESCRIPTION
      "Path: swPort.performance.vlan.mibCounters.d7Performance.ifInUnknownProtos

       64 bit unsigned wrappable counter."
   ::= {pr1645v2EthPortSwIVlanMCD7PEntry 150994944}

pr1645v2EthPortSwIVlanMCD7PInDropEx OBJECT-TYPE
   SYNTAX      Counter64
   MAX-ACCESS  read-only
   STATUS      current
   DESCRIPTION
      "Path: swPort.performance.vlan.mibCounters.d7Performance.ifInDropLevelExceeded

       64 bit unsigned wrappable counter."
   ::= {pr1645v2EthPortSwIVlanMCD7PEntry 335544320}

pr1645v2EthPortSwIVlanMCD7PInDropNoMac OBJECT-TYPE
   SYNTAX      Counter64
   MAX-ACCESS  read-only
   STATUS      current
   DESCRIPTION
      "Path: swPort.performance.vlan.mibCounters.d7Performance.fInDiscardsNoMacFit

       64 bit unsigned wrappable counter."
   ::= {pr1645v2EthPortSwIVlanMCD7PEntry 301989888}

pr1645v2EthPortSwIVlanMCD7PInDropNUCast OBJECT-TYPE
   SYNTAX      Counter64
   MAX-ACCESS  read-only
   STATUS      current
   DESCRIPTION
      "Path: swPort.performance.vlan.mibCounters.d7Performance.fInDiscardsNUCast

       64 bit unsigned wrappable counter."
   ::= {pr1645v2EthPortSwIVlanMCD7PEntry 318767104}

pr1645v2EthPortSwIVlanMCD7PInDropFilter OBJECT-TYPE
   SYNTAX      Counter64
   MAX-ACCESS  read-only
   STATUS      current
   DESCRIPTION
      "Path: swPort.performance.vlan.mibCounters.d7Performance.fInDiscardsFilter

       64 bit unsigned wrappable counter."
   ::= {pr1645v2EthPortSwIVlanMCD7PEntry 385875968}

pr1645v2EthPortSwIVlanMCD7PIfInBandwidth OBJECT-TYPE
   SYNTAX      Integer32
   MAX-ACCESS  read-only
   STATUS      current
   DESCRIPTION
      "Path: swPort.performance.vlan.mibCounters.d7Performance.ifInBandwidth

       unit name = bps
       formula = 8 * ; 8 /"
   ::= {pr1645v2EthPortSwIVlanMCD7PEntry 268435456}

pr1645v2EthPortSwIVlanMCD7PIfOutOctets OBJECT-TYPE
   SYNTAX      Counter64
   MAX-ACCESS  read-only
   STATUS      current
   DESCRIPTION
      "Path: swPort.performance.vlan.mibCounters.d7Performance.ifOutOctets

       64 bit unsigned wrappable counter."
   ::= {pr1645v2EthPortSwIVlanMCD7PEntry 167772160}

pr1645v2EthPortSwIVlanMCD7PIfOutUCPkts OBJECT-TYPE
   SYNTAX      Counter64
   MAX-ACCESS  read-only
   STATUS      current
   DESCRIPTION
      "Path: swPort.performance.vlan.mibCounters.d7Performance.ifOutUcastPkts

       64 bit unsigned wrappable counter."
   ::= {pr1645v2EthPortSwIVlanMCD7PEntry 184549376}

pr1645v2EthPortSwIVlanMCD7PIfOutNUCPkts OBJECT-TYPE
   SYNTAX      Counter64
   MAX-ACCESS  read-only
   STATUS      current
   DESCRIPTION
      "Path: swPort.performance.vlan.mibCounters.d7Performance.ifOutNUcastPkts

       64 bit unsigned wrappable counter."
   ::= {pr1645v2EthPortSwIVlanMCD7PEntry 201326592}

pr1645v2EthPortSwIVlanMCD7PIfOutBCPkts OBJECT-TYPE
   SYNTAX      Counter64
   MAX-ACCESS  read-only
   STATUS      current
   DESCRIPTION
      "Path: swPort.performance.vlan.mibCounters.d7Performance.ifOutBcastPkts

       64 bit unsigned wrappable counter."
   ::= {pr1645v2EthPortSwIVlanMCD7PEntry 452984832}

pr1645v2EthPortSwIVlanMCD7PIfOutMCPkts OBJECT-TYPE
   SYNTAX      Counter64
   MAX-ACCESS  read-only
   STATUS      current
   DESCRIPTION
      "Path: swPort.performance.vlan.mibCounters.d7Performance.ifOutMcastPkts

       64 bit unsigned wrappable counter."
   ::= {pr1645v2EthPortSwIVlanMCD7PEntry 469762048}

pr1645v2EthPortSwIVlanMCD7PIfOutDiscards OBJECT-TYPE
   SYNTAX      Counter64
   MAX-ACCESS  read-only
   STATUS      current
   DESCRIPTION
      "Path: swPort.performance.vlan.mibCounters.d7Performance.ifOutDiscards

       64 bit unsigned wrappable counter."
   ::= {pr1645v2EthPortSwIVlanMCD7PEntry 218103808}

pr1645v2EthPortSwIVlanMCD7PIfOutErrors OBJECT-TYPE
   SYNTAX      Counter64
   MAX-ACCESS  read-only
   STATUS      current
   DESCRIPTION
      "Path: swPort.performance.vlan.mibCounters.d7Performance.ifOutErrors

       64 bit unsigned wrappable counter."
   ::= {pr1645v2EthPortSwIVlanMCD7PEntry 234881024}

pr1645v2EthPortSwIVlanMCD7POutDropEx OBJECT-TYPE
   SYNTAX      Counter64
   MAX-ACCESS  read-only
   STATUS      current
   DESCRIPTION
      "Path: swPort.performance.vlan.mibCounters.d7Performance.ifOutDropLevelExceeded

       64 bit unsigned wrappable counter."
   ::= {pr1645v2EthPortSwIVlanMCD7PEntry 352321536}

pr1645v2EthPortSwIVlanMCD7POutDropNoArp OBJECT-TYPE
   SYNTAX      Counter64
   MAX-ACCESS  read-only
   STATUS      current
   DESCRIPTION
      "Path: swPort.performance.vlan.mibCounters.d7Performance.ifOutDiscardsNoArp

       64 bit unsigned wrappable counter."
   ::= {pr1645v2EthPortSwIVlanMCD7PEntry 369098752}

pr1645v2EthPortSwIVlanMCD7POutDropFilter OBJECT-TYPE
   SYNTAX      Counter64
   MAX-ACCESS  read-only
   STATUS      current
   DESCRIPTION
      "Path: swPort.performance.vlan.mibCounters.d7Performance.ifOutDiscardsFilter

       64 bit unsigned wrappable counter."
   ::= {pr1645v2EthPortSwIVlanMCD7PEntry 402653184}

pr1645v2EthPortSwIVlanMCD7PIfOutBandwidth OBJECT-TYPE
   SYNTAX      Integer32
   MAX-ACCESS  read-only
   STATUS      current
   DESCRIPTION
      "Path: swPort.performance.vlan.mibCounters.d7Performance.ifOutBandwidth

       unit name = bps
       formula = 8 * ; 8 /"
   ::= {pr1645v2EthPortSwIVlanMCD7PEntry 285212672}

pr1645v2EthPortSwIVlanMCD7PIfErrSec OBJECT-TYPE
   SYNTAX      Counter32
   MAX-ACCESS  read-only
   STATUS      current
   DESCRIPTION
      "Path: swPort.performance.vlan.mibCounters.d7Performance.ifErrSec

       32 bit unsigned wrappable counter."
   ::= {pr1645v2EthPortSwIVlanMCD7PEntry 251658240}

pr1645v2EthPortSwIVlanInPQs OBJECT-TYPE
   SYNTAX      SEQUENCE OF Pr1645v2EthPortSwIVlanInPQsEntry
   MAX-ACCESS  not-accessible
   STATUS      current
   DESCRIPTION
      ""
   ::= {pr1645v2EthPortSwIVlan 100663296}

pr1645v2EthPortSwIVlanInPQsEntry OBJECT-TYPE
   SYNTAX      Pr1645v2EthPortSwIVlanInPQsEntry
   MAX-ACCESS  not-accessible
   STATUS      current
   DESCRIPTION
      ""
   INDEX      { pr1645v2EthPortSwIVlanInPQsGlobalIx,
                pr1645v2EthPortSwIVlanTableIx,
                pr1645v2EthPortSwIVlanInPQsTableIx }
   ::= {pr1645v2EthPortSwIVlanInPQs 1}

Pr1645v2EthPortSwIVlanInPQsEntry ::=
   SEQUENCE
      {
      pr1645v2EthPortSwIVlanInPQsGlobalIx
         GlobalIndex,
      pr1645v2EthPortSwIVlanInPQsTableIx
         TableIndex,
      pr1645v2EthPortSwIVlanInPQsName
         INTEGER,
      pr1645v2EthPortSwIVlanInPQsLength
         Integer32,
      pr1645v2EthPortSwIVlanInPQsOctetLength
         Integer32,
      pr1645v2EthPortSwIVlanInPQsRedLength
         Integer32,
      pr1645v2EthPortSwIVlanInPQsPacketsTotal
         Counter64,
      pr1645v2EthPortSwIVlanInPQsPacketsDirectTx
         Counter64,
      pr1645v2EthPortSwIVlanInPQsPacketsQueued
         Counter64,
      pr1645v2EthPortSwIVlanInPQsPacketsDropped
         Counter64,
      pr1645v2EthPortSwIVlanInPQsPacketsRedDropped
         Counter64,
      pr1645v2EthPortSwIVlanInPQsPacketsCirTx
         Counter64,
      pr1645v2EthPortSwIVlanInPQsPacketsEirTx
         Counter64,
      pr1645v2EthPortSwIVlanInPQsPacketsViolateTx
         Counter64,
      pr1645v2EthPortSwIVlanInPQsOctetsTotal
         Counter64,
      pr1645v2EthPortSwIVlanInPQsOctetsDirectTx
         Counter64,
      pr1645v2EthPortSwIVlanInPQsOctetsQueued
         Counter64,
      pr1645v2EthPortSwIVlanInPQsOctetsDropped
         Counter64,
      pr1645v2EthPortSwIVlanInPQsOctetsRedDropped
         Counter64,
      pr1645v2EthPortSwIVlanInPQsOctetsCirTx
         Counter64,
      pr1645v2EthPortSwIVlanInPQsOctetsEirTx
         Counter64,
      pr1645v2EthPortSwIVlanInPQsOctetsViolateTx
         Counter64,
      pr1645v2EthPortSwIVlanInPQsOctetsBandwidth15sec
         Integer32,
      pr1645v2EthPortSwIVlanInPQsOctetsBandwidth30sec
         Integer32,
      pr1645v2EthPortSwIVlanInPQsOctetsBandwidth1min
         Integer32,
      pr1645v2EthPortSwIVlanInPQsOctetsBandwidth2min
         Integer32,
      pr1645v2EthPortSwIVlanInPQsOctetsBandwidth5min
         Integer32
      }

pr1645v2EthPortSwIVlanInPQsGlobalIx OBJECT-TYPE
   SYNTAX      GlobalIndex
   MAX-ACCESS  not-accessible
   STATUS      current
   DESCRIPTION
      "The value of the tlsCntTreeGlobalIndex of the MANAGED OBJECT."
   ::= {pr1645v2EthPortSwIVlanInPQsEntry 10}

pr1645v2EthPortSwIVlanInPQsTableIx OBJECT-TYPE
   SYNTAX      TableIndex
   MAX-ACCESS  not-accessible
   STATUS      current
   DESCRIPTION
      ""
   ::= {pr1645v2EthPortSwIVlanInPQsEntry 11}

pr1645v2EthPortSwIVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPortSwIVlanInPQsEntry 16777216}

pr1645v2EthPortSwIVlanInPQsLength OBJECT-TYPE
   SYNTAX      Integer32
   MAX-ACCESS  read-only
   STATUS      current
   DESCRIPTION
      "Path: swPort.performance.vlan.inPriorityQueues.length"
   ::= {pr1645v2EthPortSwIVlanInPQsEntry 33554432}

pr1645v2EthPortSwIVlanInPQsOctetLength OBJECT-TYPE
   SYNTAX      Integer32
   MAX-ACCESS  read-only
   STATUS      current
   DESCRIPTION
      "Path: swPort.performance.vlan.inPriorityQueues.octetLength"
   ::= {pr1645v2EthPortSwIVlanInPQsEntry 150994944}

pr1645v2EthPortSwIVlanInPQsRedLength OBJECT-TYPE
   SYNTAX      Integer32
   MAX-ACCESS  read-only
   STATUS      current
   DESCRIPTION
      "Path: swPort.performance.vlan.inPriorityQueues.redLength"
   ::= {pr1645v2EthPortSwIVlanInPQsEntry 134217728}

pr1645v2EthPortSwIVlanInPQsPacketsTotal OBJECT-TYPE
   SYNTAX      Counter64
   MAX-ACCESS  read-only
   STATUS      current
   DESCRIPTION
      "Path: swPort.performance.vlan.inPriorityQueues.packets.total

       64 bit unsigned wrappable counter."
   ::= {pr1645v2EthPortSwIVlanInPQsEntry 50790400}

pr1645v2EthPortSwIVlanInPQsPacketsDirectTx OBJECT-TYPE
   SYNTAX      Counter64
   MAX-ACCESS  read-only
   STATUS      current
   DESCRIPTION
      "Path: swPort.performance.vlan.inPriorityQueues.packets.directTx

       64 bit unsigned wrappable counter."
   ::= {pr1645v2EthPortSwIVlanInPQsEntry 50397184}

pr1645v2EthPortSwIVlanInPQsPacketsQueued OBJECT-TYPE
   SYNTAX      Counter64
   MAX-ACCESS  read-only
   STATUS      current
   DESCRIPTION
      "Path: swPort.performance.vlan.inPriorityQueues.packets.queued

       64 bit unsigned wrappable counter."
   ::= {pr1645v2EthPortSwIVlanInPQsEntry 50462720}

pr1645v2EthPortSwIVlanInPQsPacketsDropped OBJECT-TYPE
   SYNTAX      Counter64
   MAX-ACCESS  read-only
   STATUS      current
   DESCRIPTION
      "Path: swPort.performance.vlan.inPriorityQueues.packets.dropped

       64 bit unsigned wrappable counter."
   ::= {pr1645v2EthPortSwIVlanInPQsEntry 50528256}

pr1645v2EthPortSwIVlanInPQsPacketsRedDropped OBJECT-TYPE
   SYNTAX      Counter64
   MAX-ACCESS  read-only
   STATUS      current
   DESCRIPTION
      "Path: swPort.performance.vlan.inPriorityQueues.packets.redDropped

       64 bit unsigned wrappable counter."
   ::= {pr1645v2EthPortSwIVlanInPQsEntry 50724864}

pr1645v2EthPortSwIVlanInPQsPacketsCirTx OBJECT-TYPE
   SYNTAX      Counter64
   MAX-ACCESS  read-only
   STATUS      current
   DESCRIPTION
      "Path: swPort.performance.vlan.inPriorityQueues.packets.cirTx

       64 bit unsigned wrappable counter."
   ::= {pr1645v2EthPortSwIVlanInPQsEntry 50593792}

pr1645v2EthPortSwIVlanInPQsPacketsEirTx OBJECT-TYPE
   SYNTAX      Counter64
   MAX-ACCESS  read-only
   STATUS      current
   DESCRIPTION
      "Path: swPort.performance.vlan.inPriorityQueues.packets.eirTx

       64 bit unsigned wrappable counter."
   ::= {pr1645v2EthPortSwIVlanInPQsEntry 50659328}

pr1645v2EthPortSwIVlanInPQsPacketsViolateTx OBJECT-TYPE
   SYNTAX      Counter64
   MAX-ACCESS  read-only
   STATUS      current
   DESCRIPTION
      "Path: swPort.performance.vlan.inPriorityQueues.packets.violateTx

       64 bit unsigned wrappable counter."
   ::= {pr1645v2EthPortSwIVlanInPQsEntry 50855936}

pr1645v2EthPortSwIVlanInPQsOctetsTotal OBJECT-TYPE
   SYNTAX      Counter64
   MAX-ACCESS  read-only
   STATUS      current
   DESCRIPTION
      "Path: swPort.performance.vlan.inPriorityQueues.octets.total

       64 bit unsigned wrappable counter."
   ::= {pr1645v2EthPortSwIVlanInPQsEntry 67567616}

pr1645v2EthPortSwIVlanInPQsOctetsDirectTx OBJECT-TYPE
   SYNTAX      Counter64
   MAX-ACCESS  read-only
   STATUS      current
   DESCRIPTION
      "Path: swPort.performance.vlan.inPriorityQueues.octets.directTx

       64 bit unsigned wrappable counter."
   ::= {pr1645v2EthPortSwIVlanInPQsEntry 67174400}

pr1645v2EthPortSwIVlanInPQsOctetsQueued OBJECT-TYPE
   SYNTAX      Counter64
   MAX-ACCESS  read-only
   STATUS      current
   DESCRIPTION
      "Path: swPort.performance.vlan.inPriorityQueues.octets.queued

       64 bit unsigned wrappable counter."
   ::= {pr1645v2EthPortSwIVlanInPQsEntry 67239936}

pr1645v2EthPortSwIVlanInPQsOctetsDropped OBJECT-TYPE
   SYNTAX      Counter64
   MAX-ACCESS  read-only
   STATUS      current
   DESCRIPTION
      "Path: swPort.performance.vlan.inPriorityQueues.octets.dropped

       64 bit unsigned wrappable counter."
   ::= {pr1645v2EthPortSwIVlanInPQsEntry 67305472}

pr1645v2EthPortSwIVlanInPQsOctetsRedDropped OBJECT-TYPE
   SYNTAX      Counter64
   MAX-ACCESS  read-only
   STATUS      current
   DESCRIPTION
      "Path: swPort.performance.vlan.inPriorityQueues.octets.redDropped

       64 bit unsigned wrappable counter."
   ::= {pr1645v2EthPortSwIVlanInPQsEntry 67502080}

pr1645v2EthPortSwIVlanInPQsOctetsCirTx OBJECT-TYPE
   SYNTAX      Counter64
   MAX-ACCESS  read-only
   STATUS      current
   DESCRIPTION
      "Path: swPort.performance.vlan.inPriorityQueues.octets.cirTx

       64 bit unsigned wrappable counter."
   ::= {pr1645v2EthPortSwIVlanInPQsEntry 67371008}

pr1645v2EthPortSwIVlanInPQsOctetsEirTx OBJECT-TYPE
   SYNTAX      Counter64
   MAX-ACCESS  read-only
   STATUS      current
   DESCRIPTION
      "Path: swPort.performance.vlan.inPriorityQueues.octets.eirTx

       64 bit unsigned wrappable counter."
   ::= {pr1645v2EthPortSwIVlanInPQsEntry 67436544}

pr1645v2EthPortSwIVlanInPQsOctetsViolateTx OBJECT-TYPE
   SYNTAX      Counter64
   MAX-ACCESS  read-only
   STATUS      current
   DESCRIPTION
      "Path: swPort.performance.vlan.inPriorityQueues.octets.violateTx

       64 bit unsigned wrappable counter."
   ::= {pr1645v2EthPortSwIVlanInPQsEntry 67633152}

pr1645v2EthPortSwIVlanInPQsOctetsBandwidth15sec OBJECT-TYPE
   SYNTAX      Integer32
   MAX-ACCESS  read-only
   STATUS      current
   DESCRIPTION
      "Path: swPort.performance.vlan.inPriorityQueues.octets.bandwidth.15sec

       unit name = bps
       formula = 8 * ; 8 /"
   ::= {pr1645v2EthPortSwIVlanInPQsEntry 70386944}

pr1645v2EthPortSwIVlanInPQsOctetsBandwidth30sec OBJECT-TYPE
   SYNTAX      Integer32
   MAX-ACCESS  read-only
   STATUS      current
   DESCRIPTION
      "Path: swPort.performance.vlan.inPriorityQueues.octets.bandwidth.30sec

       unit name = bps
       formula = 8 * ; 8 /"
   ::= {pr1645v2EthPortSwIVlanInPQsEntry 70388224}

pr1645v2EthPortSwIVlanInPQsOctetsBandwidth1min OBJECT-TYPE
   SYNTAX      Integer32
   MAX-ACCESS  read-only
   STATUS      current
   DESCRIPTION
      "Path: swPort.performance.vlan.inPriorityQueues.octets.bandwidth.1min

       unit name = bps
       formula = 8 * ; 8 /"
   ::= {pr1645v2EthPortSwIVlanInPQsEntry 70390784}

pr1645v2EthPortSwIVlanInPQsOctetsBandwidth2min OBJECT-TYPE
   SYNTAX      Integer32
   MAX-ACCESS  read-only
   STATUS      current
   DESCRIPTION
      "Path: swPort.performance.vlan.inPriorityQueues.octets.bandwidth.2min

       unit name = bps
       formula = 8 * ; 8 /"
   ::= {pr1645v2EthPortSwIVlanInPQsEntry 70395904}

pr1645v2EthPortSwIVlanInPQsOctetsBandwidth5min OBJECT-TYPE
   SYNTAX      Integer32
   MAX-ACCESS  read-only
   STATUS      current
   DESCRIPTION
      "Path: swPort.performance.vlan.inPriorityQueues.octets.bandwidth.5min

       unit name = bps
       formula = 8 * ; 8 /"
   ::= {pr1645v2EthPortSwIVlanInPQsEntry 70411264}

pr1645v2EthPortSwIVlanInPQsH2Performance OBJECT-TYPE
   SYNTAX      SEQUENCE OF Pr1645v2EthPortSwIVlanInPQsH2PerformanceEntry
   MAX-ACCESS  not-accessible
   STATUS      current
   DESCRIPTION
      ""
   ::= {pr1645v2EthPortSwIVlan 100990976}

pr1645v2EthPortSwIVlanInPQsH2PerformanceEntry OBJECT-TYPE
   SYNTAX      Pr1645v2EthPortSwIVlanInPQsH2PerformanceEntry
   MAX-ACCESS  not-accessible
   STATUS      current
   DESCRIPTION
      ""
   INDEX      { pr1645v2EthPortSwIVlanInPQsH2PerformanceGlobalIx,
                pr1645v2EthPortSwIVlanTableIx,
                pr1645v2EthPortSwIVlanInPQsTableIx,
                pr1645v2EthPortSwIVlanInPQsH2PerformanceTableIx }
   ::= {pr1645v2EthPortSwIVlanInPQsH2Performance 1}

Pr1645v2EthPortSwIVlanInPQsH2PerformanceEntry ::=
   SEQUENCE
      {
      pr1645v2EthPortSwIVlanInPQsH2PerformanceGlobalIx
         GlobalIndex,
      pr1645v2EthPortSwIVlanInPQsH2PerformanceTableIx
         TableIndex,
      pr1645v2EthPortSwIVlanInPQsH2PerformanceSysUpTime
         TimeTicks,
      pr1645v2EthPortSwIVlanInPQsH2PerformanceTotPkts
         Counter64,
      pr1645v2EthPortSwIVlanInPQsH2PerformanceDirTxPkts
         Counter64,
      pr1645v2EthPortSwIVlanInPQsH2PerformanceQdPkts
         Counter64,
      pr1645v2EthPortSwIVlanInPQsH2PerformanceDropPkts
         Counter64,
      pr1645v2EthPortSwIVlanInPQsH2PerformanceRDropPkts
         Counter64,
      pr1645v2EthPortSwIVlanInPQsH2PerformanceCirTxPkts
         Counter64,
      pr1645v2EthPortSwIVlanInPQsH2PerformanceEirTxPkts
         Counter64,
      pr1645v2EthPortSwIVlanInPQsH2PerformanceViolTxPkts
         Counter64,
      pr1645v2EthPortSwIVlanInPQsH2PerformanceTotOcts
         Counter64,
      pr1645v2EthPortSwIVlanInPQsH2PerformanceDirTxOcts
         Counter64,
      pr1645v2EthPortSwIVlanInPQsH2PerformanceQdOcts
         Counter64,
      pr1645v2EthPortSwIVlanInPQsH2PerformanceDropOcts
         Counter64,
      pr1645v2EthPortSwIVlanInPQsH2PerformanceRDropOcts
         Counter64,
      pr1645v2EthPortSwIVlanInPQsH2PerformanceCirTxOcts
         Counter64,
      pr1645v2EthPortSwIVlanInPQsH2PerformanceEirTxOcts
         Counter64,
      pr1645v2EthPortSwIVlanInPQsH2PerformanceViolTxOcts
         Counter64,
      pr1645v2EthPortSwIVlanInPQsH2PerformanceBandwidth
         Integer32
      }

pr1645v2EthPortSwIVlanInPQsH2PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanInPQsH2PerformanceEntry 10}

pr1645v2EthPortSwIVlanInPQsH2PerformanceTableIx OBJECT-TYPE
   SYNTAX      TableIndex
   MAX-ACCESS  not-accessible
   STATUS      current
   DESCRIPTION
      ""
   ::= {pr1645v2EthPortSwIVlanInPQsH2PerformanceEntry 11}

pr1645v2EthPortSwIVlanInPQsH2PerformanceSysUpTime OBJECT-TYPE
   SYNTAX      TimeTicks
   MAX-ACCESS  read-only
   STATUS      current
   DESCRIPTION
      "Path: swPort.performance.vlan.inPriorityQueues.h2Performance.sysUpTime

       Time in centi-second."
   ::= {pr1645v2EthPortSwIVlanInPQsH2PerformanceEntry 16777216}

pr1645v2EthPortSwIVlanInPQsH2PerformanceTotPkts OBJECT-TYPE
   SYNTAX      Counter64
   MAX-ACCESS  read-only
   STATUS      current
   DESCRIPTION
      "Path: swPort.performance.vlan.inPriorityQueues.h2Performance.totalPkts

       64 bit unsigned wrappable counter."
   ::= {pr1645v2EthPortSwIVlanInPQsH2PerformanceEntry 234881024}

pr1645v2EthPortSwIVlanInPQsH2PerformanceDirTxPkts OBJECT-TYPE
   SYNTAX      Counter64
   MAX-ACCESS  read-only
   STATUS      current
   DESCRIPTION
      "Path: swPort.performance.vlan.inPriorityQueues.h2Performance.directTxPkts

       64 bit unsigned wrappable counter."
   ::= {pr1645v2EthPortSwIVlanInPQsH2PerformanceEntry 33554432}

pr1645v2EthPortSwIVlanInPQsH2PerformanceQdPkts OBJECT-TYPE
   SYNTAX      Counter64
   MAX-ACCESS  read-only
   STATUS      current
   DESCRIPTION
      "Path: swPort.performance.vlan.inPriorityQueues.h2Performance.queuedPkts

       64 bit unsigned wrappable counter."
   ::= {pr1645v2EthPortSwIVlanInPQsH2PerformanceEntry 50331648}

pr1645v2EthPortSwIVlanInPQsH2PerformanceDropPkts OBJECT-TYPE
   SYNTAX      Counter64
   MAX-ACCESS  read-only
   STATUS      current
   DESCRIPTION
      "Path: swPort.performance.vlan.inPriorityQueues.h2Performance.droppedPkts

       64 bit unsigned wrappable counter."
   ::= {pr1645v2EthPortSwIVlanInPQsH2PerformanceEntry 67108864}

pr1645v2EthPortSwIVlanInPQsH2PerformanceRDropPkts OBJECT-TYPE
   SYNTAX      Counter64
   MAX-ACCESS  read-only
   STATUS      current
   DESCRIPTION
      "Path: swPort.performance.vlan.inPriorityQueues.h2Performance.redDroppedPkts

       64 bit unsigned wrappable counter."
   ::= {pr1645v2EthPortSwIVlanInPQsH2PerformanceEntry 201326592}

pr1645v2EthPortSwIVlanInPQsH2PerformanceCirTxPkts OBJECT-TYPE
   SYNTAX      Counter64
   MAX-ACCESS  read-only
   STATUS      current
   DESCRIPTION
      "Path: swPort.performance.vlan.inPriorityQueues.h2Performance.cirTxPkts

       64 bit unsigned wrappable counter."
   ::= {pr1645v2EthPortSwIVlanInPQsH2PerformanceEntry 83886080}

pr1645v2EthPortSwIVlanInPQsH2PerformanceEirTxPkts OBJECT-TYPE
   SYNTAX      Counter64
   MAX-ACCESS  read-only
   STATUS      current
   DESCRIPTION
      "Path: swPort.performance.vlan.inPriorityQueues.h2Performance.eirTxPkts

       64 bit unsigned wrappable counter."
   ::= {pr1645v2EthPortSwIVlanInPQsH2PerformanceEntry 100663296}

pr1645v2EthPortSwIVlanInPQsH2PerformanceViolTxPkts OBJECT-TYPE
   SYNTAX      Counter64
   MAX-ACCESS  read-only
   STATUS      current
   DESCRIPTION
      "Path: swPort.performance.vlan.inPriorityQueues.h2Performance.violateTxPkts

       64 bit unsigned wrappable counter."
   ::= {pr1645v2EthPortSwIVlanInPQsH2PerformanceEntry 301989888}

pr1645v2EthPortSwIVlanInPQsH2PerformanceTotOcts OBJECT-TYPE
   SYNTAX      Counter64
   MAX-ACCESS  read-only
   STATUS      current
   DESCRIPTION
      "Path: swPort.performance.vlan.inPriorityQueues.h2Performance.totalOctets

       64 bit unsigned wrappable counter."
   ::= {pr1645v2EthPortSwIVlanInPQsH2PerformanceEntry 251658240}

pr1645v2EthPortSwIVlanInPQsH2PerformanceDirTxOcts OBJECT-TYPE
   SYNTAX      Counter64
   MAX-ACCESS  read-only
   STATUS      current
   DESCRIPTION
      "Path: swPort.performance.vlan.inPriorityQueues.h2Performance.directTxOctets

       64 bit unsigned wrappable counter."
   ::= {pr1645v2EthPortSwIVlanInPQsH2PerformanceEntry 117440512}

pr1645v2EthPortSwIVlanInPQsH2PerformanceQdOcts OBJECT-TYPE
   SYNTAX      Counter64
   MAX-ACCESS  read-only
   STATUS      current
   DESCRIPTION
      "Path: swPort.performance.vlan.inPriorityQueues.h2Performance.queuedOctets

       64 bit unsigned wrappable counter."
   ::= {pr1645v2EthPortSwIVlanInPQsH2PerformanceEntry 134217728}

pr1645v2EthPortSwIVlanInPQsH2PerformanceDropOcts OBJECT-TYPE
   SYNTAX      Counter64
   MAX-ACCESS  read-only
   STATUS      current
   DESCRIPTION
      "Path: swPort.performance.vlan.inPriorityQueues.h2Performance.droppedOctets

       64 bit unsigned wrappable counter."
   ::= {pr1645v2EthPortSwIVlanInPQsH2PerformanceEntry 150994944}

pr1645v2EthPortSwIVlanInPQsH2PerformanceRDropOcts OBJECT-TYPE
   SYNTAX      Counter64
   MAX-ACCESS  read-only
   STATUS      current
   DESCRIPTION
      "Path: swPort.performance.vlan.inPriorityQueues.h2Performance.redDroppedOctets

       64 bit unsigned wrappable counter."
   ::= {pr1645v2EthPortSwIVlanInPQsH2PerformanceEntry 218103808}

pr1645v2EthPortSwIVlanInPQsH2PerformanceCirTxOcts OBJECT-TYPE
   SYNTAX      Counter64
   MAX-ACCESS  read-only
   STATUS      current
   DESCRIPTION
      "Path: swPort.performance.vlan.inPriorityQueues.h2Performance.cirTxOctets

       64 bit unsigned wrappable counter."
   ::= {pr1645v2EthPortSwIVlanInPQsH2PerformanceEntry 167772160}

pr1645v2EthPortSwIVlanInPQsH2PerformanceEirTxOcts OBJECT-TYPE
   SYNTAX      Counter64
   MAX-ACCESS  read-only
   STATUS      current
   DESCRIPTION
      "Path: swPort.performance.vlan.inPriorityQueues.h2Performance.eirTxOctets

       64 bit unsigned wrappable counter."
   ::= {pr1645v2EthPortSwIVlanInPQsH2PerformanceEntry 184549376}

pr1645v2EthPortSwIVlanInPQsH2PerformanceViolTxOcts OBJECT-TYPE
   SYNTAX      Counter64
   MAX-ACCESS  read-only
   STATUS      current
   DESCRIPTION
      "Path: swPort.performance.vlan.inPriorityQueues.h2Performance.violateTxOctets

       64 bit unsigned wrappable counter."
   ::= {pr1645v2EthPortSwIVlanInPQsH2PerformanceEntry 318767104}

pr1645v2EthPortSwIVlanInPQsH2PerformanceBandwidth OBJECT-TYPE
   SYNTAX      Integer32
   MAX-ACCESS  read-only
   STATUS      current
   DESCRIPTION
      "Path: swPort.performance.vlan.inPriorityQueues.h2Performance.bandwidth

       unit name = bps
       formula = 8 * ; 8 /"
   ::= {pr1645v2EthPortSwIVlanInPQsH2PerformanceEntry 268435456}

pr1645v2EthPortSwIVlanInPQsH24Performance OBJECT-TYPE
   SYNTAX      SEQUENCE OF Pr1645v2EthPortSwIVlanInPQsH24PerformanceEntry
   MAX-ACCESS  not-accessible
   STATUS      current
   DESCRIPTION
      ""
   ::= {pr1645v2EthPortSwIVlan 101056512}

pr1645v2EthPortSwIVlanInPQsH24PerformanceEntry OBJECT-TYPE
   SYNTAX      Pr1645v2EthPortSwIVlanInPQsH24PerformanceEntry
   MAX-ACCESS  not-accessible
   STATUS      current
   DESCRIPTION
      ""
   INDEX      { pr1645v2EthPortSwIVlanInPQsH24PerformanceGlobalIx,
                pr1645v2EthPortSwIVlanTableIx,
                pr1645v2EthPortSwIVlanInPQsTableIx,
                pr1645v2EthPortSwIVlanInPQsH24PerformanceTableIx }
   ::= {pr1645v2EthPortSwIVlanInPQsH24Performance 1}

Pr1645v2EthPortSwIVlanInPQsH24PerformanceEntry ::=
   SEQUENCE
      {
      pr1645v2EthPortSwIVlanInPQsH24PerformanceGlobalIx
         GlobalIndex,
      pr1645v2EthPortSwIVlanInPQsH24PerformanceTableIx
         TableIndex,
      pr1645v2EthPortSwIVlanInPQsH24PerformanceSysUpTime
         TimeTicks,
      pr1645v2EthPortSwIVlanInPQsH24PerformanceTotPkts
         Counter64,
      pr1645v2EthPortSwIVlanInPQsH24PerformanceDirTxPkts
         Counter64,
      pr1645v2EthPortSwIVlanInPQsH24PerformanceQdPkts
         Counter64,
      pr1645v2EthPortSwIVlanInPQsH24PerformanceDropPkts
         Counter64,
      pr1645v2EthPortSwIVlanInPQsH24PerformanceRDropPkts
         Counter64,
      pr1645v2EthPortSwIVlanInPQsH24PerformanceCirTxPkts
         Counter64,
      pr1645v2EthPortSwIVlanInPQsH24PerformanceEirTxPkts
         Counter64,
      pr1645v2EthPortSwIVlanInPQsH24PerformanceViolTxPkts
         Counter64,
      pr1645v2EthPortSwIVlanInPQsH24PerformanceTotOcts
         Counter64,
      pr1645v2EthPortSwIVlanInPQsH24PerformanceDirTxOcts
         Counter64,
      pr1645v2EthPortSwIVlanInPQsH24PerformanceQdOcts
         Counter64,
      pr1645v2EthPortSwIVlanInPQsH24PerformanceDropOcts
         Counter64,
      pr1645v2EthPortSwIVlanInPQsH24PerformanceRDropOcts
         Counter64,
      pr1645v2EthPortSwIVlanInPQsH24PerformanceCirTxOcts
         Counter64,
      pr1645v2EthPortSwIVlanInPQsH24PerformanceEirTxOcts
         Counter64,
      pr1645v2EthPortSwIVlanInPQsH24PerformanceViolTxOcts
         Counter64,
      pr1645v2EthPortSwIVlanInPQsH24PerformanceBandwidth
         Integer32
      }

pr1645v2EthPortSwIVlanInPQsH24PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanInPQsH24PerformanceEntry 10}

pr1645v2EthPortSwIVlanInPQsH24PerformanceTableIx OBJECT-TYPE
   SYNTAX      TableIndex
   MAX-ACCESS  not-accessible
   STATUS      current
   DESCRIPTION
      ""
   ::= {pr1645v2EthPortSwIVlanInPQsH24PerformanceEntry 11}

pr1645v2EthPortSwIVlanInPQsH24PerformanceSysUpTime OBJECT-TYPE
   SYNTAX      TimeTicks
   MAX-ACCESS  read-only
   STATUS      current
   DESCRIPTION
      "Path: swPort.performance.vlan.inPriorityQueues.h24Performance.sysUpTime

       Time in centi-second."
   ::= {pr1645v2EthPortSwIVlanInPQsH24PerformanceEntry 16777216}

pr1645v2EthPortSwIVlanInPQsH24PerformanceTotPkts OBJECT-TYPE
   SYNTAX      Counter64
   MAX-ACCESS  read-only
   STATUS      current
   DESCRIPTION
      "Path: swPort.performance.vlan.inPriorityQueues.h24Performance.totalPkts

       64 bit unsigned wrappable counter."
   ::= {pr1645v2EthPortSwIVlanInPQsH24PerformanceEntry 234881024}

pr1645v2EthPortSwIVlanInPQsH24PerformanceDirTxPkts OBJECT-TYPE
   SYNTAX      Counter64
   MAX-ACCESS  read-only
   STATUS      current
   DESCRIPTION
      "Path: swPort.performance.vlan.inPriorityQueues.h24Performance.directTxPkts

       64 bit unsigned wrappable counter."
   ::= {pr1645v2EthPortSwIVlanInPQsH24PerformanceEntry 33554432}

pr1645v2EthPortSwIVlanInPQsH24PerformanceQdPkts OBJECT-TYPE
   SYNTAX      Counter64
   MAX-ACCESS  read-only
   STATUS      current
   DESCRIPTION
      "Path: swPort.performance.vlan.inPriorityQueues.h24Performance.queuedPkts

       64 bit unsigned wrappable counter."
   ::= {pr1645v2EthPortSwIVlanInPQsH24PerformanceEntry 50331648}

pr1645v2EthPortSwIVlanInPQsH24PerformanceDropPkts OBJECT-TYPE
   SYNTAX      Counter64
   MAX-ACCESS  read-only
   STATUS      current
   DESCRIPTION
      "Path: swPort.performance.vlan.inPriorityQueues.h24Performance.droppedPkts

       64 bit unsigned wrappable counter."
   ::= {pr1645v2EthPortSwIVlanInPQsH24PerformanceEntry 67108864}

pr1645v2EthPortSwIVlanInPQsH24PerformanceRDropPkts OBJECT-TYPE
   SYNTAX      Counter64
   MAX-ACCESS  read-only
   STATUS      current
   DESCRIPTION
      "Path: swPort.performance.vlan.inPriorityQueues.h24Performance.redDroppedPkts

       64 bit unsigned wrappable counter."
   ::= {pr1645v2EthPortSwIVlanInPQsH24PerformanceEntry 201326592}

pr1645v2EthPortSwIVlanInPQsH24PerformanceCirTxPkts OBJECT-TYPE
   SYNTAX      Counter64
   MAX-ACCESS  read-only
   STATUS      current
   DESCRIPTION
      "Path: swPort.performance.vlan.inPriorityQueues.h24Performance.cirTxPkts

       64 bit unsigned wrappable counter."
   ::= {pr1645v2EthPortSwIVlanInPQsH24PerformanceEntry 83886080}

pr1645v2EthPortSwIVlanInPQsH24PerformanceEirTxPkts OBJECT-TYPE
   SYNTAX      Counter64
   MAX-ACCESS  read-only
   STATUS      current
   DESCRIPTION
      "Path: swPort.performance.vlan.inPriorityQueues.h24Performance.eirTxPkts

       64 bit unsigned wrappable counter."
   ::= {pr1645v2EthPortSwIVlanInPQsH24PerformanceEntry 100663296}

pr1645v2EthPortSwIVlanInPQsH24PerformanceViolTxPkts OBJECT-TYPE
   SYNTAX      Counter64
   MAX-ACCESS  read-only
   STATUS      current
   DESCRIPTION
      "Path: swPort.performance.vlan.inPriorityQueues.h24Performance.violateTxPkts

       64 bit unsigned wrappable counter."
   ::= {pr1645v2EthPortSwIVlanInPQsH24PerformanceEntry 301989888}

pr1645v2EthPortSwIVlanInPQsH24PerformanceTotOcts OBJECT-TYPE
   SYNTAX      Counter64
   MAX-ACCESS  read-only
   STATUS      current
   DESCRIPTION
      "Path: swPort.performance.vlan.inPriorityQueues.h24Performance.totalOctets

       64 bit unsigned wrappable counter."
   ::= {pr1645v2EthPortSwIVlanInPQsH24PerformanceEntry 251658240}

pr1645v2EthPortSwIVlanInPQsH24PerformanceDirTxOcts OBJECT-TYPE
   SYNTAX      Counter64
   MAX-ACCESS  read-only
   STATUS      current
   DESCRIPTION
      "Path: swPort.performance.vlan.inPriorityQueues.h24Performance.directTxOctets

       64 bit unsigned wrappable counter."
   ::= {pr1645v2EthPortSwIVlanInPQsH24PerformanceEntry 117440512}

pr1645v2EthPortSwIVlanInPQsH24PerformanceQdOcts OBJECT-TYPE
   SYNTAX      Counter64
   MAX-ACCESS  read-only
   STATUS      current
   DESCRIPTION
      "Path: swPort.performance.vlan.inPriorityQueues.h24Performance.queuedOctets

       64 bit unsigned wrappable counter."
   ::= {pr1645v2EthPortSwIVlanInPQsH24PerformanceEntry 134217728}

pr1645v2EthPortSwIVlanInPQsH24PerformanceDropOcts OBJECT-TYPE
   SYNTAX      Counter64
   MAX-ACCESS  read-only
   STATUS      current
   DESCRIPTION
      "Path: swPort.performance.vlan.inPriorityQueues.h24Performance.droppedOctets

       64 bit unsigned wrappable counter."
   ::= {pr1645v2EthPortSwIVlanInPQsH24PerformanceEntry 150994944}

pr1645v2EthPortSwIVlanInPQsH24PerformanceRDropOcts OBJECT-TYPE
   SYNTAX      Counter64
   MAX-ACCESS  read-only
   STATUS      current
   DESCRIPTION
      "Path: swPort.performance.vlan.inPriorityQueues.h24Performance.redDroppedOctets

       64 bit unsigned wrappable counter."
   ::= {pr1645v2EthPortSwIVlanInPQsH24PerformanceEntry 218103808}

pr1645v2EthPortSwIVlanInPQsH24PerformanceCirTxOcts OBJECT-TYPE
   SYNTAX      Counter64
   MAX-ACCESS  read-only
   STATUS      current
   DESCRIPTION
      "Path: swPort.performance.vlan.inPriorityQueues.h24Performance.cirTxOctets

       64 bit unsigned wrappable counter."
   ::= {pr1645v2EthPortSwIVlanInPQsH24PerformanceEntry 167772160}

pr1645v2EthPortSwIVlanInPQsH24PerformanceEirTxOcts OBJECT-TYPE
   SYNTAX      Counter64
   MAX-ACCESS  read-only
   STATUS      current
   DESCRIPTION
      "Path: swPort.performance.vlan.inPriorityQueues.h24Performance.eirTxOctets

       64 bit unsigned wrappable counter."
   ::= {pr1645v2EthPortSwIVlanInPQsH24PerformanceEntry 184549376}

pr1645v2EthPortSwIVlanInPQsH24PerformanceViolTxOcts OBJECT-TYPE
   SYNTAX      Counter64
   MAX-ACCESS  read-only
   STATUS      current
   DESCRIPTION
      "Path: swPort.performance.vlan.inPriorityQueues.h24Performance.violateTxOctets

       64 bit unsigned wrappable counter."
   ::= {pr1645v2EthPortSwIVlanInPQsH24PerformanceEntry 318767104}

pr1645v2EthPortSwIVlanInPQsH24PerformanceBandwidth OBJECT-TYPE
   SYNTAX      Integer32
   MAX-ACCESS  read-only
   STATUS      current
   DESCRIPTION
      "Path: swPort.performance.vlan.inPriorityQueues.h24Performance.bandwidth

       unit name = bps
       formula = 8 * ; 8 /"
   ::= {pr1645v2EthPortSwIVlanInPQsH24PerformanceEntry 268435456}

pr1645v2EthPortSwIVlanInPQsD7Performance OBJECT-TYPE
   SYNTAX      SEQUENCE OF Pr1645v2EthPortSwIVlanInPQsD7PerformanceEntry
   MAX-ACCESS  not-accessible
   STATUS      current
   DESCRIPTION
      ""
   ::= {pr1645v2EthPortSwIVlan 101122048}

pr1645v2EthPortSwIVlanInPQsD7PerformanceEntry OBJECT-TYPE
   SYNTAX      Pr1645v2EthPortSwIVlanInPQsD7PerformanceEntry
   MAX-ACCESS  not-accessible
   STATUS      current
   DESCRIPTION
      ""
   INDEX      { pr1645v2EthPortSwIVlanInPQsD7PerformanceGlobalIx,
                pr1645v2EthPortSwIVlanTableIx,
                pr1645v2EthPortSwIVlanInPQsTableIx,
                pr1645v2EthPortSwIVlanInPQsD7PerformanceTableIx }
   ::= {pr1645v2EthPortSwIVlanInPQsD7Performance 1}

Pr1645v2EthPortSwIVlanInPQsD7PerformanceEntry ::=
   SEQUENCE
      {
      pr1645v2EthPortSwIVlanInPQsD7PerformanceGlobalIx
         GlobalIndex,
      pr1645v2EthPortSwIVlanInPQsD7PerformanceTableIx
         TableIndex,
      pr1645v2EthPortSwIVlanInPQsD7PerformanceSysUpTime
         TimeTicks,
      pr1645v2EthPortSwIVlanInPQsD7PerformanceTotPkts
         Counter64,
      pr1645v2EthPortSwIVlanInPQsD7PerformanceDirTxPkts
         Counter64,
      pr1645v2EthPortSwIVlanInPQsD7PerformanceQdPkts
         Counter64,
      pr1645v2EthPortSwIVlanInPQsD7PerformanceDropPkts
         Counter64,
      pr1645v2EthPortSwIVlanInPQsD7PerformanceRDropPkts
         Counter64,
      pr1645v2EthPortSwIVlanInPQsD7PerformanceCirTxPkts
         Counter64,
      pr1645v2EthPortSwIVlanInPQsD7PerformanceEirTxPkts
         Counter64,
      pr1645v2EthPortSwIVlanInPQsD7PerformanceViolTxPkts
         Counter64,
      pr1645v2EthPortSwIVlanInPQsD7PerformanceTotOcts
         Counter64,
      pr1645v2EthPortSwIVlanInPQsD7PerformanceDirTxOcts
         Counter64,
      pr1645v2EthPortSwIVlanInPQsD7PerformanceQdOcts
         Counter64,
      pr1645v2EthPortSwIVlanInPQsD7PerformanceDropOcts
         Counter64,
      pr1645v2EthPortSwIVlanInPQsD7PerformanceRDropOcts
         Counter64,
      pr1645v2EthPortSwIVlanInPQsD7PerformanceCirTxOcts
         Counter64,
      pr1645v2EthPortSwIVlanInPQsD7PerformanceEirTxOcts
         Counter64,
      pr1645v2EthPortSwIVlanInPQsD7PerformanceViolTxOcts
         Counter64,
      pr1645v2EthPortSwIVlanInPQsD7PerformanceBandwidth
         Integer32
      }

pr1645v2EthPortSwIVlanInPQsD7PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanInPQsD7PerformanceEntry 10}

pr1645v2EthPortSwIVlanInPQsD7PerformanceTableIx OBJECT-TYPE
   SYNTAX      TableIndex
   MAX-ACCESS  not-accessible
   STATUS      current
   DESCRIPTION
      ""
   ::= {pr1645v2EthPortSwIVlanInPQsD7PerformanceEntry 11}

pr1645v2EthPortSwIVlanInPQsD7PerformanceSysUpTime OBJECT-TYPE
   SYNTAX      TimeTicks
   MAX-ACCESS  read-only
   STATUS      current
   DESCRIPTION
      "Path: swPort.performance.vlan.inPriorityQueues.d7Performance.sysUpTime

       Time in centi-second."
   ::= {pr1645v2EthPortSwIVlanInPQsD7PerformanceEntry 16777216}

pr1645v2EthPortSwIVlanInPQsD7PerformanceTotPkts OBJECT-TYPE
   SYNTAX      Counter64
   MAX-ACCESS  read-only
   STATUS      current
   DESCRIPTION
      "Path: swPort.performance.vlan.inPriorityQueues.d7Performance.totalPkts

       64 bit unsigned wrappable counter."
   ::= {pr1645v2EthPortSwIVlanInPQsD7PerformanceEntry 234881024}

pr1645v2EthPortSwIVlanInPQsD7PerformanceDirTxPkts OBJECT-TYPE
   SYNTAX      Counter64
   MAX-ACCESS  read-only
   STATUS      current
   DESCRIPTION
      "Path: swPort.performance.vlan.inPriorityQueues.d7Performance.directTxPkts

       64 bit unsigned wrappable counter."
   ::= {pr1645v2EthPortSwIVlanInPQsD7PerformanceEntry 33554432}

pr1645v2EthPortSwIVlanInPQsD7PerformanceQdPkts OBJECT-TYPE
   SYNTAX      Counter64
   MAX-ACCESS  read-only
   STATUS      current
   DESCRIPTION
      "Path: swPort.performance.vlan.inPriorityQueues.d7Performance.queuedPkts

       64 bit unsigned wrappable counter."
   ::= {pr1645v2EthPortSwIVlanInPQsD7PerformanceEntry 50331648}

pr1645v2EthPortSwIVlanInPQsD7PerformanceDropPkts OBJECT-TYPE
   SYNTAX      Counter64
   MAX-ACCESS  read-only
   STATUS      current
   DESCRIPTION
      "Path: swPort.performance.vlan.inPriorityQueues.d7Performance.droppedPkts

       64 bit unsigned wrappable counter."
   ::= {pr1645v2EthPortSwIVlanInPQsD7PerformanceEntry 67108864}

pr1645v2EthPortSwIVlanInPQsD7PerformanceRDropPkts OBJECT-TYPE
   SYNTAX      Counter64
   MAX-ACCESS  read-only
   STATUS      current
   DESCRIPTION
      "Path: swPort.performance.vlan.inPriorityQueues.d7Performance.redDroppedPkts

       64 bit unsigned wrappable counter."
   ::= {pr1645v2EthPortSwIVlanInPQsD7PerformanceEntry 201326592}

pr1645v2EthPortSwIVlanInPQsD7PerformanceCirTxPkts OBJECT-TYPE
   SYNTAX      Counter64
   MAX-ACCESS  read-only
   STATUS      current
   DESCRIPTION
      "Path: swPort.performance.vlan.inPriorityQueues.d7Performance.cirTxPkts

       64 bit unsigned wrappable counter."
   ::= {pr1645v2EthPortSwIVlanInPQsD7PerformanceEntry 83886080}

pr1645v2EthPortSwIVlanInPQsD7PerformanceEirTxPkts OBJECT-TYPE
   SYNTAX      Counter64
   MAX-ACCESS  read-only
   STATUS      current
   DESCRIPTION
      "Path: swPort.performance.vlan.inPriorityQueues.d7Performance.eirTxPkts

       64 bit unsigned wrappable counter."
   ::= {pr1645v2EthPortSwIVlanInPQsD7PerformanceEntry 100663296}

pr1645v2EthPortSwIVlanInPQsD7PerformanceViolTxPkts OBJECT-TYPE
   SYNTAX      Counter64
   MAX-ACCESS  read-only
   STATUS      current
   DESCRIPTION
      "Path: swPort.performance.vlan.inPriorityQueues.d7Performance.violateTxPkts

       64 bit unsigned wrappable counter."
   ::= {pr1645v2EthPortSwIVlanInPQsD7PerformanceEntry 301989888}

pr1645v2EthPortSwIVlanInPQsD7PerformanceTotOcts OBJECT-TYPE
   SYNTAX      Counter64
   MAX-ACCESS  read-only
   STATUS      current
   DESCRIPTION
      "Path: swPort.performance.vlan.inPriorityQueues.d7Performance.totalOctets

       64 bit unsigned wrappable counter."
   ::= {pr1645v2EthPortSwIVlanInPQsD7PerformanceEntry 251658240}

pr1645v2EthPortSwIVlanInPQsD7PerformanceDirTxOcts OBJECT-TYPE
   SYNTAX      Counter64
   MAX-ACCESS  read-only
   STATUS      current
   DESCRIPTION
      "Path: swPort.performance.vlan.inPriorityQueues.d7Performance.directTxOctets

       64 bit unsigned wrappable counter."
   ::= {pr1645v2EthPortSwIVlanInPQsD7PerformanceEntry 117440512}

pr1645v2EthPortSwIVlanInPQsD7PerformanceQdOcts OBJECT-TYPE
   SYNTAX      Counter64
   MAX-ACCESS  read-only
   STATUS      current
   DESCRIPTION
      "Path: swPort.performance.vlan.inPriorityQueues.d7Performance.queuedOctets

       64 bit unsigned wrappable counter."
   ::= {pr1645v2EthPortSwIVlanInPQsD7PerformanceEntry 134217728}

pr1645v2EthPortSwIVlanInPQsD7PerformanceDropOcts OBJECT-TYPE
   SYNTAX      Counter64
   MAX-ACCESS  read-only
   STATUS      current
   DESCRIPTION
      "Path: swPort.performance.vlan.inPriorityQueues.d7Performance.droppedOctets

       64 bit unsigned wrappable counter."
   ::= {pr1645v2EthPortSwIVlanInPQsD7PerformanceEntry 150994944}

pr1645v2EthPortSwIVlanInPQsD7PerformanceRDropOcts OBJECT-TYPE
   SYNTAX      Counter64
   MAX-ACCESS  read-only
   STATUS      current
   DESCRIPTION
      "Path: swPort.performance.vlan.inPriorityQueues.d7Performance.redDroppedOctets

       64 bit unsigned wrappable counter."
   ::= {pr1645v2EthPortSwIVlanInPQsD7PerformanceEntry 218103808}

pr1645v2EthPortSwIVlanInPQsD7PerformanceCirTxOcts OBJECT-TYPE
   SYNTAX      Counter64
   MAX-ACCESS  read-only
   STATUS      current
   DESCRIPTION
      "Path: swPort.performance.vlan.inPriorityQueues.d7Performance.cirTxOctets

       64 bit unsigned wrappable counter."
   ::= {pr1645v2EthPortSwIVlanInPQsD7PerformanceEntry 167772160}

pr1645v2EthPortSwIVlanInPQsD7PerformanceEirTxOcts OBJECT-TYPE
   SYNTAX      Counter64
   MAX-ACCESS  read-only
   STATUS      current
   DESCRIPTION
      "Path: swPort.performance.vlan.inPriorityQueues.d7Performance.eirTxOctets

       64 bit unsigned wrappable counter."
   ::= {pr1645v2EthPortSwIVlanInPQsD7PerformanceEntry 184549376}

pr1645v2EthPortSwIVlanInPQsD7PerformanceViolTxOcts OBJECT-TYPE
   SYNTAX      Counter64
   MAX-ACCESS  read-only
   STATUS      current
   DESCRIPTION
      "Path: swPort.performance.vlan.inPriorityQueues.d7Performance.violateTxOctets

       64 bit unsigned wrappable counter."
   ::= {pr1645v2EthPortSwIVlanInPQsD7PerformanceEntry 318767104}

pr1645v2EthPortSwIVlanInPQsD7PerformanceBandwidth OBJECT-TYPE
   SYNTAX      Integer32
   MAX-ACCESS  read-only
   STATUS      current
   DESCRIPTION
      "Path: swPort.performance.vlan.inPriorityQueues.d7Performance.bandwidth

       unit name = bps
       formula = 8 * ; 8 /"
   ::= {pr1645v2EthPortSwIVlanInPQsD7PerformanceEntry 268435456}

pr1645v2EthPortSwIVlanOutPQs OBJECT-TYPE
   SYNTAX      SEQUENCE OF Pr1645v2EthPortSwIVlanOutPQsEntry
   MAX-ACCESS  not-accessible
   STATUS      current
   DESCRIPTION
      ""
   ::= {pr1645v2EthPortSwIVlan 83886080}

pr1645v2EthPortSwIVlanOutPQsEntry OBJECT-TYPE
   SYNTAX      Pr1645v2EthPortSwIVlanOutPQsEntry
   MAX-ACCESS  not-accessible
   STATUS      current
   DESCRIPTION
      ""
   INDEX      { pr1645v2EthPortSwIVlanOutPQsGlobalIx,
                pr1645v2EthPortSwIVlanTableIx,
                pr1645v2EthPortSwIVlanOutPQsTableIx }
   ::= {pr1645v2EthPortSwIVlanOutPQs 1}

Pr1645v2EthPortSwIVlanOutPQsEntry ::=
   SEQUENCE
      {
      pr1645v2EthPortSwIVlanOutPQsGlobalIx
         GlobalIndex,
      pr1645v2EthPortSwIVlanOutPQsTableIx
         TableIndex,
      pr1645v2EthPortSwIVlanOutPQsName
         INTEGER,
      pr1645v2EthPortSwIVlanOutPQsLength
         Integer32,
      pr1645v2EthPortSwIVlanOutPQsOctetLength
         Integer32,
      pr1645v2EthPortSwIVlanOutPQsRedLength
         Integer32,
      pr1645v2EthPortSwIVlanOutPQsPacketsTotal
         Counter64,
      pr1645v2EthPortSwIVlanOutPQsPacketsDirectTx
         Counter64,
      pr1645v2EthPortSwIVlanOutPQsPacketsQueued
         Counter64,
      pr1645v2EthPortSwIVlanOutPQsPacketsDropped
         Counter64,
      pr1645v2EthPortSwIVlanOutPQsPacketsRedDropped
         Counter64,
      pr1645v2EthPortSwIVlanOutPQsPacketsCirTx
         Counter64,
      pr1645v2EthPortSwIVlanOutPQsPacketsEirTx
         Counter64,
      pr1645v2EthPortSwIVlanOutPQsPacketsViolateTx
         Counter64,
      pr1645v2EthPortSwIVlanOutPQsOctetsTotal
         Counter64,
      pr1645v2EthPortSwIVlanOutPQsOctetsDirectTx
         Counter64,
      pr1645v2EthPortSwIVlanOutPQsOctetsQueued
         Counter64,
      pr1645v2EthPortSwIVlanOutPQsOctetsDropped
         Counter64,
      pr1645v2EthPortSwIVlanOutPQsOctetsRedDropped
         Counter64,
      pr1645v2EthPortSwIVlanOutPQsOctetsCirTx
         Counter64,
      pr1645v2EthPortSwIVlanOutPQsOctetsEirTx
         Counter64,
      pr1645v2EthPortSwIVlanOutPQsOctetsViolateTx
         Counter64,
      pr1645v2EthPortSwIVlanOutPQsOctetsBandwidth15sec
         Integer32,
      pr1645v2EthPortSwIVlanOutPQsOctetsBandwidth30sec
         Integer32,
      pr1645v2EthPortSwIVlanOutPQsOctetsBandwidth1min
         Integer32,
      pr1645v2EthPortSwIVlanOutPQsOctetsBandwidth2min
         Integer32,
      pr1645v2EthPortSwIVlanOutPQsOctetsBandwidth5min
         Integer32
      }

pr1645v2EthPortSwIVlanOutPQsGlobalIx OBJECT-TYPE
   SYNTAX      GlobalIndex
   MAX-ACCESS  not-accessible
   STATUS      current
   DESCRIPTION
      "The value of the tlsCntTreeGlobalIndex of the MANAGED OBJECT."
   ::= {pr1645v2EthPortSwIVlanOutPQsEntry 10}

pr1645v2EthPortSwIVlanOutPQsTableIx OBJECT-TYPE
   SYNTAX      TableIndex
   MAX-ACCESS  not-accessible
   STATUS      current
   DESCRIPTION
      ""
   ::= {pr1645v2EthPortSwIVlanOutPQsEntry 11}

pr1645v2EthPortSwIVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPortSwIVlanOutPQsEntry 16777216}

pr1645v2EthPortSwIVlanOutPQsLength OBJECT-TYPE
   SYNTAX      Integer32
   MAX-ACCESS  read-only
   STATUS      current
   DESCRIPTION
      "Path: swPort.performance.vlan.outPriorityQueues.length"
   ::= {pr1645v2EthPortSwIVlanOutPQsEntry 33554432}

pr1645v2EthPortSwIVlanOutPQsOctetLength OBJECT-TYPE
   SYNTAX      Integer32
   MAX-ACCESS  read-only
   STATUS      current
   DESCRIPTION
      "Path: swPort.performance.vlan.outPriorityQueues.octetLength"
   ::= {pr1645v2EthPortSwIVlanOutPQsEntry 150994944}

pr1645v2EthPortSwIVlanOutPQsRedLength OBJECT-TYPE
   SYNTAX      Integer32
   MAX-ACCESS  read-only
   STATUS      current
   DESCRIPTION
      "Path: swPort.performance.vlan.outPriorityQueues.redLength"
   ::= {pr1645v2EthPortSwIVlanOutPQsEntry 134217728}

pr1645v2EthPortSwIVlanOutPQsPacketsTotal OBJECT-TYPE
   SYNTAX      Counter64
   MAX-ACCESS  read-only
   STATUS      current
   DESCRIPTION
      "Path: swPort.performance.vlan.outPriorityQueues.packets.total

       64 bit unsigned wrappable counter."
   ::= {pr1645v2EthPortSwIVlanOutPQsEntry 50790400}

pr1645v2EthPortSwIVlanOutPQsPacketsDirectTx OBJECT-TYPE
   SYNTAX      Counter64
   MAX-ACCESS  read-only
   STATUS      current
   DESCRIPTION
      "Path: swPort.performance.vlan.outPriorityQueues.packets.directTx

       64 bit unsigned wrappable counter."
   ::= {pr1645v2EthPortSwIVlanOutPQsEntry 50397184}

pr1645v2EthPortSwIVlanOutPQsPacketsQueued OBJECT-TYPE
   SYNTAX      Counter64
   MAX-ACCESS  read-only
   STATUS      current
   DESCRIPTION
      "Path: swPort.performance.vlan.outPriorityQueues.packets.queued

       64 bit unsigned wrappable counter."
   ::= {pr1645v2EthPortSwIVlanOutPQsEntry 50462720}

pr1645v2EthPortSwIVlanOutPQsPacketsDropped OBJECT-TYPE
   SYNTAX      Counter64
   MAX-ACCESS  read-only
   STATUS      current
   DESCRIPTION
      "Path: swPort.performance.vlan.outPriorityQueues.packets.dropped

       64 bit unsigned wrappable counter."
   ::= {pr1645v2EthPortSwIVlanOutPQsEntry 50528256}

pr1645v2EthPortSwIVlanOutPQsPacketsRedDropped OBJECT-TYPE
   SYNTAX      Counter64
   MAX-ACCESS  read-only
   STATUS      current
   DESCRIPTION
      "Path: swPort.performance.vlan.outPriorityQueues.packets.redDropped

       64 bit unsigned wrappable counter."
   ::= {pr1645v2EthPortSwIVlanOutPQsEntry 50724864}

pr1645v2EthPortSwIVlanOutPQsPacketsCirTx OBJECT-TYPE
   SYNTAX      Counter64
   MAX-ACCESS  read-only
   STATUS      current
   DESCRIPTION
      "Path: swPort.performance.vlan.outPriorityQueues.packets.cirTx

       64 bit unsigned wrappable counter."
   ::= {pr1645v2EthPortSwIVlanOutPQsEntry 50593792}

pr1645v2EthPortSwIVlanOutPQsPacketsEirTx OBJECT-TYPE
   SYNTAX      Counter64
   MAX-ACCESS  read-only
   STATUS      current
   DESCRIPTION
      "Path: swPort.performance.vlan.outPriorityQueues.packets.eirTx

       64 bit unsigned wrappable counter."
   ::= {pr1645v2EthPortSwIVlanOutPQsEntry 50659328}

pr1645v2EthPortSwIVlanOutPQsPacketsViolateTx OBJECT-TYPE
   SYNTAX      Counter64
   MAX-ACCESS  read-only
   STATUS      current
   DESCRIPTION
      "Path: swPort.performance.vlan.outPriorityQueues.packets.violateTx

       64 bit unsigned wrappable counter."
   ::= {pr1645v2EthPortSwIVlanOutPQsEntry 50855936}

pr1645v2EthPortSwIVlanOutPQsOctetsTotal OBJECT-TYPE
   SYNTAX      Counter64
   MAX-ACCESS  read-only
   STATUS      current
   DESCRIPTION
      "Path: swPort.performance.vlan.outPriorityQueues.octets.total

       64 bit unsigned wrappable counter."
   ::= {pr1645v2EthPortSwIVlanOutPQsEntry 67567616}

pr1645v2EthPortSwIVlanOutPQsOctetsDirectTx OBJECT-TYPE
   SYNTAX      Counter64
   MAX-ACCESS  read-only
   STATUS      current
   DESCRIPTION
      "Path: swPort.performance.vlan.outPriorityQueues.octets.directTx

       64 bit unsigned wrappable counter."
   ::= {pr1645v2EthPortSwIVlanOutPQsEntry 67174400}

pr1645v2EthPortSwIVlanOutPQsOctetsQueued OBJECT-TYPE
   SYNTAX      Counter64
   MAX-ACCESS  read-only
   STATUS      current
   DESCRIPTION
      "Path: swPort.performance.vlan.outPriorityQueues.octets.queued

       64 bit unsigned wrappable counter."
   ::= {pr1645v2EthPortSwIVlanOutPQsEntry 67239936}

pr1645v2EthPortSwIVlanOutPQsOctetsDropped OBJECT-TYPE
   SYNTAX      Counter64
   MAX-ACCESS  read-only
   STATUS      current
   DESCRIPTION
      "Path: swPort.performance.vlan.outPriorityQueues.octets.dropped

       64 bit unsigned wrappable counter."
   ::= {pr1645v2EthPortSwIVlanOutPQsEntry 67305472}

pr1645v2EthPortSwIVlanOutPQsOctetsRedDropped OBJECT-TYPE
   SYNTAX      Counter64
   MAX-ACCESS  read-only
   STATUS      current
   DESCRIPTION
      "Path: swPort.performance.vlan.outPriorityQueues.octets.redDropped

       64 bit unsigned wrappable counter."
   ::= {pr1645v2EthPortSwIVlanOutPQsEntry 67502080}

pr1645v2EthPortSwIVlanOutPQsOctetsCirTx OBJECT-TYPE
   SYNTAX      Counter64
   MAX-ACCESS  read-only
   STATUS      current
   DESCRIPTION
      "Path: swPort.performance.vlan.outPriorityQueues.octets.cirTx

       64 bit unsigned wrappable counter."
   ::= {pr1645v2EthPortSwIVlanOutPQsEntry 67371008}

pr1645v2EthPortSwIVlanOutPQsOctetsEirTx OBJECT-TYPE
   SYNTAX      Counter64
   MAX-ACCESS  read-only
   STATUS      current
   DESCRIPTION
      "Path: swPort.performance.vlan.outPriorityQueues.octets.eirTx

       64 bit unsigned wrappable counter."
   ::= {pr1645v2EthPortSwIVlanOutPQsEntry 67436544}

pr1645v2EthPortSwIVlanOutPQsOctetsViolateTx OBJECT-TYPE
   SYNTAX      Counter64
   MAX-ACCESS  read-only
   STATUS      current
   DESCRIPTION
      "Path: swPort.performance.vlan.outPriorityQueues.octets.violateTx

       64 bit unsigned wrappable counter."
   ::= {pr1645v2EthPortSwIVlanOutPQsEntry 67633152}

pr1645v2EthPortSwIVlanOutPQsOctetsBandwidth15sec OBJECT-TYPE
   SYNTAX      Integer32
   MAX-ACCESS  read-only
   STATUS      current
   DESCRIPTION
      "Path: swPort.performance.vlan.outPriorityQueues.octets.bandwidth.15sec

       unit name = bps
       formula = 8 * ; 8 /"
   ::= {pr1645v2EthPortSwIVlanOutPQsEntry 70386944}

pr1645v2EthPortSwIVlanOutPQsOctetsBandwidth30sec OBJECT-TYPE
   SYNTAX      Integer32
   MAX-ACCESS  read-only
   STATUS      current
   DESCRIPTION
      "Path: swPort.performance.vlan.outPriorityQueues.octets.bandwidth.30sec

       unit name = bps
       formula = 8 * ; 8 /"
   ::= {pr1645v2EthPortSwIVlanOutPQsEntry 70388224}

pr1645v2EthPortSwIVlanOutPQsOctetsBandwidth1min OBJECT-TYPE
   SYNTAX      Integer32
   MAX-ACCESS  read-only
   STATUS      current
   DESCRIPTION
      "Path: swPort.performance.vlan.outPriorityQueues.octets.bandwidth.1min

       unit name = bps
       formula = 8 * ; 8 /"
   ::= {pr1645v2EthPortSwIVlanOutPQsEntry 70390784}

pr1645v2EthPortSwIVlanOutPQsOctetsBandwidth2min OBJECT-TYPE
   SYNTAX      Integer32
   MAX-ACCESS  read-only
   STATUS      current
   DESCRIPTION
      "Path: swPort.performance.vlan.outPriorityQueues.octets.bandwidth.2min

       unit name = bps
       formula = 8 * ; 8 /"
   ::= {pr1645v2EthPortSwIVlanOutPQsEntry 70395904}

pr1645v2EthPortSwIVlanOutPQsOctetsBandwidth5min OBJECT-TYPE
   SYNTAX      Integer32
   MAX-ACCESS  read-only
   STATUS      current
   DESCRIPTION
      "Path: swPort.performance.vlan.outPriorityQueues.octets.bandwidth.5min

       unit name = bps
       formula = 8 * ; 8 /"
   ::= {pr1645v2EthPortSwIVlanOutPQsEntry 70411264}

pr1645v2EthPortSwIVlanOutPQsH2Performance OBJECT-TYPE
   SYNTAX      SEQUENCE OF Pr1645v2EthPortSwIVlanOutPQsH2PerformanceEntry
   MAX-ACCESS  not-accessible
   STATUS      current
   DESCRIPTION
      ""
   ::= {pr1645v2EthPortSwIVlan 84213760}

pr1645v2EthPortSwIVlanOutPQsH2PerformanceEntry OBJECT-TYPE
   SYNTAX      Pr1645v2EthPortSwIVlanOutPQsH2PerformanceEntry
   MAX-ACCESS  not-accessible
   STATUS      current
   DESCRIPTION
      ""
   INDEX      { pr1645v2EthPortSwIVlanOutPQsH2PerformanceGlobalIx,
                pr1645v2EthPortSwIVlanTableIx,
                pr1645v2EthPortSwIVlanOutPQsTableIx,
                pr1645v2EthPortSwIVlanOutPQsH2PerformanceTableIx }
   ::= {pr1645v2EthPortSwIVlanOutPQsH2Performance 1}

Pr1645v2EthPortSwIVlanOutPQsH2PerformanceEntry ::=
   SEQUENCE
      {
      pr1645v2EthPortSwIVlanOutPQsH2PerformanceGlobalIx
         GlobalIndex,
      pr1645v2EthPortSwIVlanOutPQsH2PerformanceTableIx
         TableIndex,
      pr1645v2EthPortSwIVlanOutPQsH2PerformanceSysUpTime
         TimeTicks,
      pr1645v2EthPortSwIVlanOutPQsH2PerformanceTotPkts
         Counter64,
      pr1645v2EthPortSwIVlanOutPQsH2PerformanceDirTxPkts
         Counter64,
      pr1645v2EthPortSwIVlanOutPQsH2PerformanceQdPkts
         Counter64,
      pr1645v2EthPortSwIVlanOutPQsH2PerformanceDropPkts
         Counter64,
      pr1645v2EthPortSwIVlanOutPQsH2PerformanceRDropPkts
         Counter64,
      pr1645v2EthPortSwIVlanOutPQsH2PerformanceCirTxPkts
         Counter64,
      pr1645v2EthPortSwIVlanOutPQsH2PerformanceEirTxPkts
         Counter64,
      pr1645v2EthPortSwIVlanOutPQsH2PerformanceViolTxPkts
         Counter64,
      pr1645v2EthPortSwIVlanOutPQsH2PerformanceTotOcts
         Counter64,
      pr1645v2EthPortSwIVlanOutPQsH2PerformanceDirTxOcts
         Counter64,
      pr1645v2EthPortSwIVlanOutPQsH2PerformanceQdOcts
         Counter64,
      pr1645v2EthPortSwIVlanOutPQsH2PerformanceDropOcts
         Counter64,
      pr1645v2EthPortSwIVlanOutPQsH2PerformanceRDropOcts
         Counter64,
      pr1645v2EthPortSwIVlanOutPQsH2PerformanceCirTxOcts
         Counter64,
      pr1645v2EthPortSwIVlanOutPQsH2PerformanceEirTxOcts
         Counter64,
      pr1645v2EthPortSwIVlanOutPQsH2PerformanceViolTxOcts
         Counter64,
      pr1645v2EthPortSwIVlanOutPQsH2PerformanceBandwidth
         Integer32
      }

pr1645v2EthPortSwIVlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanOutPQsH2PerformanceEntry 10}

pr1645v2EthPortSwIVlanOutPQsH2PerformanceTableIx OBJECT-TYPE
   SYNTAX      TableIndex
   MAX-ACCESS  not-accessible
   STATUS      current
   DESCRIPTION
      ""
   ::= {pr1645v2EthPortSwIVlanOutPQsH2PerformanceEntry 11}

pr1645v2EthPortSwIVlanOutPQsH2PerformanceSysUpTime OBJECT-TYPE
   SYNTAX      TimeTicks
   MAX-ACCESS  read-only
   STATUS      current
   DESCRIPTION
      "Path: swPort.performance.vlan.outPriorityQueues.h2Performance.sysUpTime

       Time in centi-second."
   ::= {pr1645v2EthPortSwIVlanOutPQsH2PerformanceEntry 16777216}

pr1645v2EthPortSwIVlanOutPQsH2PerformanceTotPkts OBJECT-TYPE
   SYNTAX      Counter64
   MAX-ACCESS  read-only
   STATUS      current
   DESCRIPTION
      "Path: swPort.performance.vlan.outPriorityQueues.h2Performance.totalPkts

       64 bit unsigned wrappable counter."
   ::= {pr1645v2EthPortSwIVlanOutPQsH2PerformanceEntry 234881024}

pr1645v2EthPortSwIVlanOutPQsH2PerformanceDirTxPkts OBJECT-TYPE
   SYNTAX      Counter64
   MAX-ACCESS  read-only
   STATUS      current
   DESCRIPTION
      "Path: swPort.performance.vlan.outPriorityQueues.h2Performance.directTxPkts

       64 bit unsigned wrappable counter."
   ::= {pr1645v2EthPortSwIVlanOutPQsH2PerformanceEntry 33554432}

pr1645v2EthPortSwIVlanOutPQsH2PerformanceQdPkts OBJECT-TYPE
   SYNTAX      Counter64
   MAX-ACCESS  read-only
   STATUS      current
   DESCRIPTION
      "Path: swPort.performance.vlan.outPriorityQueues.h2Performance.queuedPkts

       64 bit unsigned wrappable counter."
   ::= {pr1645v2EthPortSwIVlanOutPQsH2PerformanceEntry 50331648}

pr1645v2EthPortSwIVlanOutPQsH2PerformanceDropPkts OBJECT-TYPE
   SYNTAX      Counter64
   MAX-ACCESS  read-only
   STATUS      current
   DESCRIPTION
      "Path: swPort.performance.vlan.outPriorityQueues.h2Performance.droppedPkts

       64 bit unsigned wrappable counter."
   ::= {pr1645v2EthPortSwIVlanOutPQsH2PerformanceEntry 67108864}

pr1645v2EthPortSwIVlanOutPQsH2PerformanceRDropPkts OBJECT-TYPE
   SYNTAX      Counter64
   MAX-ACCESS  read-only
   STATUS      current
   DESCRIPTION
      "Path: swPort.performance.vlan.outPriorityQueues.h2Performance.redDroppedPkts

       64 bit unsigned wrappable counter."
   ::= {pr1645v2EthPortSwIVlanOutPQsH2PerformanceEntry 201326592}

pr1645v2EthPortSwIVlanOutPQsH2PerformanceCirTxPkts OBJECT-TYPE
   SYNTAX      Counter64
   MAX-ACCESS  read-only
   STATUS      current
   DESCRIPTION
      "Path: swPort.performance.vlan.outPriorityQueues.h2Performance.cirTxPkts

       64 bit unsigned wrappable counter."
   ::= {pr1645v2EthPortSwIVlanOutPQsH2PerformanceEntry 83886080}

pr1645v2EthPortSwIVlanOutPQsH2PerformanceEirTxPkts OBJECT-TYPE
   SYNTAX      Counter64
   MAX-ACCESS  read-only
   STATUS      current
   DESCRIPTION
      "Path: swPort.performance.vlan.outPriorityQueues.h2Performance.eirTxPkts

       64 bit unsigned wrappable counter."
   ::= {pr1645v2EthPortSwIVlanOutPQsH2PerformanceEntry 100663296}

pr1645v2EthPortSwIVlanOutPQsH2PerformanceViolTxPkts OBJECT-TYPE
   SYNTAX      Counter64
   MAX-ACCESS  read-only
   STATUS      current
   DESCRIPTION
      "Path: swPort.performance.vlan.outPriorityQueues.h2Performance.violateTxPkts

       64 bit unsigned wrappable counter."
   ::= {pr1645v2EthPortSwIVlanOutPQsH2PerformanceEntry 301989888}

pr1645v2EthPortSwIVlanOutPQsH2PerformanceTotOcts OBJECT-TYPE
   SYNTAX      Counter64
   MAX-ACCESS  read-only
   STATUS      current
   DESCRIPTION
      "Path: swPort.performance.vlan.outPriorityQueues.h2Performance.totalOctets

       64 bit unsigned wrappable counter."
   ::= {pr1645v2EthPortSwIVlanOutPQsH2PerformanceEntry 251658240}

pr1645v2EthPortSwIVlanOutPQsH2PerformanceDirTxOcts OBJECT-TYPE
   SYNTAX      Counter64
   MAX-ACCESS  read-only
   STATUS      current
   DESCRIPTION
      "Path: swPort.performance.vlan.outPriorityQueues.h2Performance.directTxOctets

       64 bit unsigned wrappable counter."
   ::= {pr1645v2EthPortSwIVlanOutPQsH2PerformanceEntry 117440512}

pr1645v2EthPortSwIVlanOutPQsH2PerformanceQdOcts OBJECT-TYPE
   SYNTAX      Counter64
   MAX-ACCESS  read-only
   STATUS      current
   DESCRIPTION
      "Path: swPort.performance.vlan.outPriorityQueues.h2Performance.queuedOctets

       64 bit unsigned wrappable counter."
   ::= {pr1645v2EthPortSwIVlanOutPQsH2PerformanceEntry 134217728}

pr1645v2EthPortSwIVlanOutPQsH2PerformanceDropOcts OBJECT-TYPE
   SYNTAX      Counter64
   MAX-ACCESS  read-only
   STATUS      current
   DESCRIPTION
      "Path: swPort.performance.vlan.outPriorityQueues.h2Performance.droppedOctets

       64 bit unsigned wrappable counter."
   ::= {pr1645v2EthPortSwIVlanOutPQsH2PerformanceEntry 150994944}

pr1645v2EthPortSwIVlanOutPQsH2PerformanceRDropOcts OBJECT-TYPE
   SYNTAX      Counter64
   MAX-ACCESS  read-only
   STATUS      current
   DESCRIPTION
      "Path: swPort.performance.vlan.outPriorityQueues.h2Performance.redDroppedOctets

       64 bit unsigned wrappable counter."
   ::= {pr1645v2EthPortSwIVlanOutPQsH2PerformanceEntry 218103808}

pr1645v2EthPortSwIVlanOutPQsH2PerformanceCirTxOcts OBJECT-TYPE
   SYNTAX      Counter64
   MAX-ACCESS  read-only
   STATUS      current
   DESCRIPTION
      "Path: swPort.performance.vlan.outPriorityQueues.h2Performance.cirTxOctets

       64 bit unsigned wrappable counter."
   ::= {pr1645v2EthPortSwIVlanOutPQsH2PerformanceEntry 167772160}

pr1645v2EthPortSwIVlanOutPQsH2PerformanceEirTxOcts OBJECT-TYPE
   SYNTAX      Counter64
   MAX-ACCESS  read-only
   STATUS      current
   DESCRIPTION
      "Path: swPort.performance.vlan.outPriorityQueues.h2Performance.eirTxOctets

       64 bit unsigned wrappable counter."
   ::= {pr1645v2EthPortSwIVlanOutPQsH2PerformanceEntry 184549376}

pr1645v2EthPortSwIVlanOutPQsH2PerformanceViolTxOcts OBJECT-TYPE
   SYNTAX      Counter64
   MAX-ACCESS  read-only
   STATUS      current
   DESCRIPTION
      "Path: swPort.performance.vlan.outPriorityQueues.h2Performance.violateTxOctets

       64 bit unsigned wrappable counter."
   ::= {pr1645v2EthPortSwIVlanOutPQsH2PerformanceEntry 318767104}

pr1645v2EthPortSwIVlanOutPQsH2PerformanceBandwidth OBJECT-TYPE
   SYNTAX      Integer32
   MAX-ACCESS  read-only
   STATUS      current
   DESCRIPTION
      "Path: swPort.performance.vlan.outPriorityQueues.h2Performance.bandwidth

       unit name = bps
       formula = 8 * ; 8 /"
   ::= {pr1645v2EthPortSwIVlanOutPQsH2PerformanceEntry 268435456}

pr1645v2EthPortSwIVlanOutPQsH24Performance OBJECT-TYPE
   SYNTAX      SEQUENCE OF Pr1645v2EthPortSwIVlanOutPQsH24PerformanceEntry
   MAX-ACCESS  not-accessible
   STATUS      current
   DESCRIPTION
      ""
   ::= {pr1645v2EthPortSwIVlan 84279296}

pr1645v2EthPortSwIVlanOutPQsH24PerformanceEntry OBJECT-TYPE
   SYNTAX      Pr1645v2EthPortSwIVlanOutPQsH24PerformanceEntry
   MAX-ACCESS  not-accessible
   STATUS      current
   DESCRIPTION
      ""
   INDEX      { pr1645v2EthPortSwIVlanOutPQsH24PerformanceGlobalIx,
                pr1645v2EthPortSwIVlanTableIx,
                pr1645v2EthPortSwIVlanOutPQsTableIx,
                pr1645v2EthPortSwIVlanOutPQsH24PerformanceTableIx }
   ::= {pr1645v2EthPortSwIVlanOutPQsH24Performance 1}

Pr1645v2EthPortSwIVlanOutPQsH24PerformanceEntry ::=
   SEQUENCE
      {
      pr1645v2EthPortSwIVlanOutPQsH24PerformanceGlobalIx
         GlobalIndex,
      pr1645v2EthPortSwIVlanOutPQsH24PerformanceTableIx
         TableIndex,
      pr1645v2EthPortSwIVlanOutPQsH24PerformanceSysUpTime
         TimeTicks,
      pr1645v2EthPortSwIVlanOutPQsH24PerformanceTotPkts
         Counter64,
      pr1645v2EthPortSwIVlanOutPQsH24PerformanceDirTxPkts
         Counter64,
      pr1645v2EthPortSwIVlanOutPQsH24PerformanceQdPkts
         Counter64,
      pr1645v2EthPortSwIVlanOutPQsH24PerformanceDropPkts
         Counter64,
      pr1645v2EthPortSwIVlanOutPQsH24PerformanceRDropPkts
         Counter64,
      pr1645v2EthPortSwIVlanOutPQsH24PerformanceCirTxPkts
         Counter64,
      pr1645v2EthPortSwIVlanOutPQsH24PerformanceEirTxPkts
         Counter64,
      pr1645v2EthPortSwIVlanOutPQsH24PerformanceViolTxPkts
         Counter64,
      pr1645v2EthPortSwIVlanOutPQsH24PerformanceTotOcts
         Counter64,
      pr1645v2EthPortSwIVlanOutPQsH24PerformanceDirTxOcts
         Counter64,
      pr1645v2EthPortSwIVlanOutPQsH24PerformanceQdOcts
         Counter64,
      pr1645v2EthPortSwIVlanOutPQsH24PerformanceDropOcts
         Counter64,
      pr1645v2EthPortSwIVlanOutPQsH24PerformanceRDropOcts
         Counter64,
      pr1645v2EthPortSwIVlanOutPQsH24PerformanceCirTxOcts
         Counter64,
      pr1645v2EthPortSwIVlanOutPQsH24PerformanceEirTxOcts
         Counter64,
      pr1645v2EthPortSwIVlanOutPQsH24PerformanceViolTxOcts
         Counter64,
      pr1645v2EthPortSwIVlanOutPQsH24PerformanceBandwidth
         Integer32
      }

pr1645v2EthPortSwIVlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanOutPQsH24PerformanceEntry 10}

pr1645v2EthPortSwIVlanOutPQsH24PerformanceTableIx OBJECT-TYPE
   SYNTAX      TableIndex
   MAX-ACCESS  not-accessible
   STATUS      current
   DESCRIPTION
      ""
   ::= {pr1645v2EthPortSwIVlanOutPQsH24PerformanceEntry 11}

pr1645v2EthPortSwIVlanOutPQsH24PerformanceSysUpTime OBJECT-TYPE
   SYNTAX      TimeTicks
   MAX-ACCESS  read-only
   STATUS      current
   DESCRIPTION
      "Path: swPort.performance.vlan.outPriorityQueues.h24Performance.sysUpTime

       Time in centi-second."
   ::= {pr1645v2EthPortSwIVlanOutPQsH24PerformanceEntry 16777216}

pr1645v2EthPortSwIVlanOutPQsH24PerformanceTotPkts OBJECT-TYPE
   SYNTAX      Counter64
   MAX-ACCESS  read-only
   STATUS      current
   DESCRIPTION
      "Path: swPort.performance.vlan.outPriorityQueues.h24Performance.totalPkts

       64 bit unsigned wrappable counter."
   ::= {pr1645v2EthPortSwIVlanOutPQsH24PerformanceEntry 234881024}

pr1645v2EthPortSwIVlanOutPQsH24PerformanceDirTxPkts OBJECT-TYPE
   SYNTAX      Counter64
   MAX-ACCESS  read-only
   STATUS      current
   DESCRIPTION
      "Path: swPort.performance.vlan.outPriorityQueues.h24Performance.directTxPkts

       64 bit unsigned wrappable counter."
   ::= {pr1645v2EthPortSwIVlanOutPQsH24PerformanceEntry 33554432}

pr1645v2EthPortSwIVlanOutPQsH24PerformanceQdPkts OBJECT-TYPE
   SYNTAX      Counter64
   MAX-ACCESS  read-only
   STATUS      current
   DESCRIPTION
      "Path: swPort.performance.vlan.outPriorityQueues.h24Performance.queuedPkts

       64 bit unsigned wrappable counter."
   ::= {pr1645v2EthPortSwIVlanOutPQsH24PerformanceEntry 50331648}

pr1645v2EthPortSwIVlanOutPQsH24PerformanceDropPkts OBJECT-TYPE
   SYNTAX      Counter64
   MAX-ACCESS  read-only
   STATUS      current
   DESCRIPTION
      "Path: swPort.performance.vlan.outPriorityQueues.h24Performance.droppedPkts

       64 bit unsigned wrappable counter."
   ::= {pr1645v2EthPortSwIVlanOutPQsH24PerformanceEntry 67108864}

pr1645v2EthPortSwIVlanOutPQsH24PerformanceRDropPkts OBJECT-TYPE
   SYNTAX      Counter64
   MAX-ACCESS  read-only
   STATUS      current
   DESCRIPTION
      "Path: swPort.performance.vlan.outPriorityQueues.h24Performance.redDroppedPkts

       64 bit unsigned wrappable counter."
   ::= {pr1645v2EthPortSwIVlanOutPQsH24PerformanceEntry 201326592}

pr1645v2EthPortSwIVlanOutPQsH24PerformanceCirTxPkts OBJECT-TYPE
   SYNTAX      Counter64
   MAX-ACCESS  read-only
   STATUS      current
   DESCRIPTION
      "Path: swPort.performance.vlan.outPriorityQueues.h24Performance.cirTxPkts

       64 bit unsigned wrappable counter."
   ::= {pr1645v2EthPortSwIVlanOutPQsH24PerformanceEntry 83886080}

pr1645v2EthPortSwIVlanOutPQsH24PerformanceEirTxPkts OBJECT-TYPE
   SYNTAX      Counter64
   MAX-ACCESS  read-only
   STATUS      current
   DESCRIPTION
      "Path: swPort.performance.vlan.outPriorityQueues.h24Performance.eirTxPkts

       64 bit unsigned wrappable counter."
   ::= {pr1645v2EthPortSwIVlanOutPQsH24PerformanceEntry 100663296}

pr1645v2EthPortSwIVlanOutPQsH24PerformanceViolTxPkts OBJECT-TYPE
   SYNTAX      Counter64
   MAX-ACCESS  read-only
   STATUS      current
   DESCRIPTION
      "Path: swPort.performance.vlan.outPriorityQueues.h24Performance.violateTxPkts

       64 bit unsigned wrappable counter."
   ::= {pr1645v2EthPortSwIVlanOutPQsH24PerformanceEntry 301989888}

pr1645v2EthPortSwIVlanOutPQsH24PerformanceTotOcts OBJECT-TYPE
   SYNTAX      Counter64
   MAX-ACCESS  read-only
   STATUS      current
   DESCRIPTION
      "Path: swPort.performance.vlan.outPriorityQueues.h24Performance.totalOctets

       64 bit unsigned wrappable counter."
   ::= {pr1645v2EthPortSwIVlanOutPQsH24PerformanceEntry 251658240}

pr1645v2EthPortSwIVlanOutPQsH24PerformanceDirTxOcts OBJECT-TYPE
   SYNTAX      Counter64
   MAX-ACCESS  read-only
   STATUS      current
   DESCRIPTION
      "Path: swPort.performance.vlan.outPriorityQueues.h24Performance.directTxOctets

       64 bit unsigned wrappable counter."
   ::= {pr1645v2EthPortSwIVlanOutPQsH24PerformanceEntry 117440512}

pr1645v2EthPortSwIVlanOutPQsH24PerformanceQdOcts OBJECT-TYPE
   SYNTAX      Counter64
   MAX-ACCESS  read-only
   STATUS      current
   DESCRIPTION
      "Path: swPort.performance.vlan.outPriorityQueues.h24Performance.queuedOctets

       64 bit unsigned wrappable counter."
   ::= {pr1645v2EthPortSwIVlanOutPQsH24PerformanceEntry 134217728}

pr1645v2EthPortSwIVlanOutPQsH24PerformanceDropOcts OBJECT-TYPE
   SYNTAX      Counter64
   MAX-ACCESS  read-only
   STATUS      current
   DESCRIPTION
      "Path: swPort.performance.vlan.outPriorityQueues.h24Performance.droppedOctets

       64 bit unsigned wrappable counter."
   ::= {pr1645v2EthPortSwIVlanOutPQsH24PerformanceEntry 150994944}

pr1645v2EthPortSwIVlanOutPQsH24PerformanceRDropOcts OBJECT-TYPE
   SYNTAX      Counter64
   MAX-ACCESS  read-only
   STATUS      current
   DESCRIPTION
      "Path: swPort.performance.vlan.outPriorityQueues.h24Performance.redDroppedOctets

       64 bit unsigned wrappable counter."
   ::= {pr1645v2EthPortSwIVlanOutPQsH24PerformanceEntry 218103808}

pr1645v2EthPortSwIVlanOutPQsH24PerformanceCirTxOcts OBJECT-TYPE
   SYNTAX      Counter64
   MAX-ACCESS  read-only
   STATUS      current
   DESCRIPTION
      "Path: swPort.performance.vlan.outPriorityQueues.h24Performance.cirTxOctets

       64 bit unsigned wrappable counter."
   ::= {pr1645v2EthPortSwIVlanOutPQsH24PerformanceEntry 167772160}

pr1645v2EthPortSwIVlanOutPQsH24PerformanceEirTxOcts OBJECT-TYPE
   SYNTAX      Counter64
   MAX-ACCESS  read-only
   STATUS      current
   DESCRIPTION
      "Path: swPort.performance.vlan.outPriorityQueues.h24Performance.eirTxOctets

       64 bit unsigned wrappable counter."
   ::= {pr1645v2EthPortSwIVlanOutPQsH24PerformanceEntry 184549376}

pr1645v2EthPortSwIVlanOutPQsH24PerformanceViolTxOcts OBJECT-TYPE
   SYNTAX      Counter64
   MAX-ACCESS  read-only
   STATUS      current
   DESCRIPTION
      "Path: swPort.performance.vlan.outPriorityQueues.h24Performance.violateTxOctets

       64 bit unsigned wrappable counter."
   ::= {pr1645v2EthPortSwIVlanOutPQsH24PerformanceEntry 318767104}

pr1645v2EthPortSwIVlanOutPQsH24PerformanceBandwidth OBJECT-TYPE
   SYNTAX      Integer32
   MAX-ACCESS  read-only
   STATUS      current
   DESCRIPTION
      "Path: swPort.performance.vlan.outPriorityQueues.h24Performance.bandwidth

       unit name = bps
       formula = 8 * ; 8 /"
   ::= {pr1645v2EthPortSwIVlanOutPQsH24PerformanceEntry 268435456}

pr1645v2EthPortSwIVlanOutPQsD7Performance OBJECT-TYPE
   SYNTAX      SEQUENCE OF Pr1645v2EthPortSwIVlanOutPQsD7PerformanceEntry
   MAX-ACCESS  not-accessible
   STATUS      current
   DESCRIPTION
      ""
   ::= {pr1645v2EthPortSwIVlan 84344832}

pr1645v2EthPortSwIVlanOutPQsD7PerformanceEntry OBJECT-TYPE
   SYNTAX      Pr1645v2EthPortSwIVlanOutPQsD7PerformanceEntry
   MAX-ACCESS  not-accessible
   STATUS      current
   DESCRIPTION
      ""
   INDEX      { pr1645v2EthPortSwIVlanOutPQsD7PerformanceGlobalIx,
                pr1645v2EthPortSwIVlanTableIx,
                pr1645v2EthPortSwIVlanOutPQsTableIx,
                pr1645v2EthPortSwIVlanOutPQsD7PerformanceTableIx }
   ::= {pr1645v2EthPortSwIVlanOutPQsD7Performance 1}

Pr1645v2EthPortSwIVlanOutPQsD7PerformanceEntry ::=
   SEQUENCE
      {
      pr1645v2EthPortSwIVlanOutPQsD7PerformanceGlobalIx
         GlobalIndex,
      pr1645v2EthPortSwIVlanOutPQsD7PerformanceTableIx
         TableIndex,
      pr1645v2EthPortSwIVlanOutPQsD7PerformanceSysUpTime
         TimeTicks,
      pr1645v2EthPortSwIVlanOutPQsD7PerformanceTotPkts
         Counter64,
      pr1645v2EthPortSwIVlanOutPQsD7PerformanceDirTxPkts
         Counter64,
      pr1645v2EthPortSwIVlanOutPQsD7PerformanceQdPkts
         Counter64,
      pr1645v2EthPortSwIVlanOutPQsD7PerformanceDropPkts
         Counter64,
      pr1645v2EthPortSwIVlanOutPQsD7PerformanceRDropPkts
         Counter64,
      pr1645v2EthPortSwIVlanOutPQsD7PerformanceCirTxPkts
         Counter64,
      pr1645v2EthPortSwIVlanOutPQsD7PerformanceEirTxPkts
         Counter64,
      pr1645v2EthPortSwIVlanOutPQsD7PerformanceViolTxPkts
         Counter64,
      pr1645v2EthPortSwIVlanOutPQsD7PerformanceTotOcts
         Counter64,
      pr1645v2EthPortSwIVlanOutPQsD7PerformanceDirTxOcts
         Counter64,
      pr1645v2EthPortSwIVlanOutPQsD7PerformanceQdOcts
         Counter64,
      pr1645v2EthPortSwIVlanOutPQsD7PerformanceDropOcts
         Counter64,
      pr1645v2EthPortSwIVlanOutPQsD7PerformanceRDropOcts
         Counter64,
      pr1645v2EthPortSwIVlanOutPQsD7PerformanceCirTxOcts
         Counter64,
      pr1645v2EthPortSwIVlanOutPQsD7PerformanceEirTxOcts
         Counter64,
      pr1645v2EthPortSwIVlanOutPQsD7PerformanceViolTxOcts
         Counter64,
      pr1645v2EthPortSwIVlanOutPQsD7PerformanceBandwidth
         Integer32
      }

pr1645v2EthPortSwIVlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1645v2EthPortSwIVlanOutPQsD7PerformanceEntry 10}

pr1645v2EthPortSwIVlanOutPQsD7PerformanceTableIx OBJECT-TYPE
   SYNTAX      TableIndex
   MAX-ACCESS  not-accessible
   STATUS      current
   DESCRIPTION
      ""
   ::= {pr1645v2EthPortSwIVlanOutPQsD7PerformanceEntry 11}

pr1645v2EthPortSwIVlanOutPQsD7PerformanceSysUpTime OBJECT-TYPE
   SYNTAX      TimeTicks
   MAX-ACCESS  read-only
   STATUS      current
   DESCRIPTION
      "Path: swPort.performance.vlan.outPriorityQueues.d7Performance.sysUpTime

       Time in centi-second."
   ::= {pr1645v2EthPortSwIVlanOutPQsD7PerformanceEntry 16777216}

pr1645v2EthPortSwIVlanOutPQsD7PerformanceTotPkts OBJECT-TYPE
   SYNTAX      Counter64
   MAX-ACCESS  read-only
   STATUS      current
   DESCRIPTION
      "Path: swPort.performance.vlan.outPriorityQueues.d7Performance.totalPkts

       64 bit unsigned wrappable counter."
   ::= {pr1645v2EthPortSwIVlanOutPQsD7PerformanceEntry 234881024}

pr1645v2EthPortSwIVlanOutPQsD7PerformanceDirTxPkts OBJECT-TYPE
   SYNTAX      Counter64
   MAX-ACCESS  read-only
   STATUS      current
   DESCRIPTION
      "Path: swPort.performance.vlan.outPriorityQueues.d7Performance.directTxPkts

       64 bit unsigned wrappable counter."
   ::= {pr1645v2EthPortSwIVlanOutPQsD7PerformanceEntry 33554432}

pr1645v2EthPortSwIVlanOutPQsD7PerformanceQdPkts OBJECT-TYPE
   SYNTAX      Counter64
   MAX-ACCESS  read-only
   STATUS      current
   DESCRIPTION
      "Path: swPort.performance.vlan.outPriorityQueues.d7Performance.queuedPkts

       64 bit unsigned wrappable counter."
   ::= {pr1645v2EthPortSwIVlanOutPQsD7PerformanceEntry 50331648}

pr1645v2EthPortSwIVlanOutPQsD7PerformanceDropPkts OBJECT-TYPE
   SYNTAX      Counter64
   MAX-ACCESS  read-only
   STATUS      current
   DESCRIPTION
      "Path: swPort.performance.vlan.outPriorityQueues.d7Performance.droppedPkts

       64 bit unsigned wrappable counter."
   ::= {pr1645v2EthPortSwIVlanOutPQsD7PerformanceEntry 67108864}

pr1645v2EthPortSwIVlanOutPQsD7PerformanceRDropPkts OBJECT-TYPE
   SYNTAX      Counter64
   MAX-ACCESS  read-only
   STATUS      current
   DESCRIPTION
      "Path: swPort.performance.vlan.outPriorityQueues.d7Performance.redDroppedPkts

       64 bit unsigned wrappable counter."
   ::= {pr1645v2EthPortSwIVlanOutPQsD7PerformanceEntry 201326592}

pr1645v2EthPortSwIVlanOutPQsD7PerformanceCirTxPkts OBJECT-TYPE
   SYNTAX      Counter64
   MAX-ACCESS  read-only
   STATUS      current
   DESCRIPTION
      "Path: swPort.performance.vlan.outPriorityQueues.d7Performance.cirTxPkts

       64 bit unsigned wrappable counter."
   ::= {pr1645v2EthPortSwIVlanOutPQsD7PerformanceEntry 83886080}

pr1645v2EthPortSwIVlanOutPQsD7PerformanceEirTxPkts OBJECT-TYPE
   SYNTAX      Counter64
   MAX-ACCESS  read-only
   STATUS      current
   DESCRIPTION
      "Path: swPort.performance.vlan.outPriorityQueues.d7Performance.eirTxPkts

       64 bit unsigned wrappable counter."
   ::= {pr1645v2EthPortSwIVlanOutPQsD7PerformanceEntry 100663296}

pr1645v2EthPortSwIVlanOutPQsD7PerformanceViolTxPkts OBJECT-TYPE
   SYNTAX      Counter64
   MAX-ACCESS  read-only
   STATUS      current
   DESCRIPTION
      "Path: swPort.performance.vlan.outPriorityQueues.d7Performance.violateTxPkts

       64 bit unsigned wrappable counter."
   ::= {pr1645v2EthPortSwIVlanOutPQsD7PerformanceEntry 301989888}

pr1645v2EthPortSwIVlanOutPQsD7PerformanceTotOcts OBJECT-TYPE
   SYNTAX      Counter64
   MAX-ACCESS  read-only
   STATUS      current
   DESCRIPTION
      "Path: swPort.performance.vlan.outPriorityQueues.d7Performance.totalOctets

       64 bit unsigned wrappable counter."
   ::= {pr1645v2EthPortSwIVlanOutPQsD7PerformanceEntry 251658240}

pr1645v2EthPortSwIVlanOutPQsD7PerformanceDirTxOcts OBJECT-TYPE
   SYNTAX      Counter64
   MAX-ACCESS  read-only
   STATUS      current
   DESCRIPTION
      "Path: swPort.performance.vlan.outPriorityQueues.d7Performance.directTxOctets

       64 bit unsigned wrappable counter."
   ::= {pr1645v2EthPortSwIVlanOutPQsD7PerformanceEntry 117440512}

pr1645v2EthPortSwIVlanOutPQsD7PerformanceQdOcts OBJECT-TYPE
   SYNTAX      Counter64
   MAX-ACCESS  read-only
   STATUS      current
   DESCRIPTION
      "Path: swPort.performance.vlan.outPriorityQueues.d7Performance.queuedOctets

       64 bit unsigned wrappable counter."
   ::= {pr1645v2EthPortSwIVlanOutPQsD7PerformanceEntry 134217728}

pr1645v2EthPortSwIVlanOutPQsD7PerformanceDropOcts OBJECT-TYPE
   SYNTAX      Counter64
   MAX-ACCESS  read-only
   STATUS      current
   DESCRIPTION
      "Path: swPort.performance.vlan.outPriorityQueues.d7Performance.droppedOctets

       64 bit unsigned wrappable counter."
   ::= {pr1645v2EthPortSwIVlanOutPQsD7PerformanceEntry 150994944}

pr1645v2EthPortSwIVlanOutPQsD7PerformanceRDropOcts OBJECT-TYPE
   SYNTAX      Counter64
   MAX-ACCESS  read-only
   STATUS      current
   DESCRIPTION
      "Path: swPort.performance.vlan.outPriorityQueues.d7Performance.redDroppedOctets

       64 bit unsigned wrappable counter."
   ::= {pr1645v2EthPortSwIVlanOutPQsD7PerformanceEntry 218103808}

pr1645v2EthPortSwIVlanOutPQsD7PerformanceCirTxOcts OBJECT-TYPE
   SYNTAX      Counter64
   MAX-ACCESS  read-only
   STATUS      current
   DESCRIPTION
      "Path: swPort.performance.vlan.outPriorityQueues.d7Performance.cirTxOctets

       64 bit unsigned wrappable counter."
   ::= {pr1645v2EthPortSwIVlanOutPQsD7PerformanceEntry 167772160}

pr1645v2EthPortSwIVlanOutPQsD7PerformanceEirTxOcts OBJECT-TYPE
   SYNTAX      Counter64
   MAX-ACCESS  read-only
   STATUS      current
   DESCRIPTION
      "Path: swPort.performance.vlan.outPriorityQueues.d7Performance.eirTxOctets

       64 bit unsigned wrappable counter."
   ::= {pr1645v2EthPortSwIVlanOutPQsD7PerformanceEntry 184549376}

pr1645v2EthPortSwIVlanOutPQsD7PerformanceViolTxOcts OBJECT-TYPE
   SYNTAX      Counter64
   MAX-ACCESS  read-only
   STATUS      current
   DESCRIPTION
      "Path: swPort.performance.vlan.outPriorityQueues.d7Performance.violateTxOctets

       64 bit unsigned wrappable counter."
   ::= {pr1645v2EthPortSwIVlanOutPQsD7PerformanceEntry 318767104}

pr1645v2EthPortSwIVlanOutPQsD7PerformanceBandwidth OBJECT-TYPE
   SYNTAX      Integer32
   MAX-ACCESS  read-only
   STATUS      current
   DESCRIPTION
      "Path: swPort.performance.vlan.outPriorityQueues.d7Performance.bandwidth

       unit name = bps
       formula = 8 * ; 8 /"
   ::= {pr1645v2EthPortSwIVlanOutPQsD7PerformanceEntry 268435456}


pr1645v2EthPortSwIPPPoE OBJECT IDENTIFIER ::= {pr1645v2EthPortSwI 53}

pr1645v2EthPortSwIPPPoESSCTable OBJECT-TYPE
   SYNTAX      SEQUENCE OF Pr1645v2EthPortSwIPPPoEEntry
   MAX-ACCESS  not-accessible
   STATUS      current
   DESCRIPTION
      ""
   ::= {pr1645v2EthPortSwIPPPoE 1}

pr1645v2EthPortSwIPPPoEEntry OBJECT-TYPE
   SYNTAX      Pr1645v2EthPortSwIPPPoEEntry
   MAX-ACCESS  not-accessible
   STATUS      current
   DESCRIPTION
      ""
   INDEX      { pr1645v2EthPortSwIPPPoEGlobalIx,
                pr1645v2EthPortSwIPPPoETableIx }
   ::= {pr1645v2EthPortSwIPPPoESSCTable 1}

Pr1645v2EthPortSwIPPPoEEntry ::=
   SEQUENCE
      {
      pr1645v2EthPortSwIPPPoEGlobalIx
         GlobalIndex,
      pr1645v2EthPortSwIPPPoETableIx
         TableIndex,
      pr1645v2EthPortSwIPPPoEName
         DisplayString,
      pr1645v2EthPortSwIPPPoEMCInOctets
         Counter64,
      pr1645v2EthPortSwIPPPoEMCInUcast
         Counter64,
      pr1645v2EthPortSwIPPPoEMCInNUcastPkts
         Counter64,
      pr1645v2EthPortSwIPPPoEMCInBcastPkts
         Counter64,
      pr1645v2EthPortSwIPPPoEMCInMcastPkts
         Counter64,
      pr1645v2EthPortSwIPPPoEMCInDiscards
         Counter64,
      pr1645v2EthPortSwIPPPoEMCInErrors
         Counter64,
      pr1645v2EthPortSwIPPPoEMCInUnknownProtos
         Counter64,
      pr1645v2EthPortSwIPPPoEMCInDropEx
         Counter64,
      pr1645v2EthPortSwIPPPoEMCInDropNoMac
         Counter64,
      pr1645v2EthPortSwIPPPoEMCInDropNUCast
         Counter64,
      pr1645v2EthPortSwIPPPoEMCInDropFilter
         Counter64,
      pr1645v2EthPortSwIPPPoEMCInBandwidth15sec
         Integer32,
      pr1645v2EthPortSwIPPPoEMCInBandwidth30sec
         Integer32,
      pr1645v2EthPortSwIPPPoEMCInBandwidth1min
         Integer32,
      pr1645v2EthPortSwIPPPoEMCInBandwidth2min
         Integer32,
      pr1645v2EthPortSwIPPPoEMCInBandwidth5min
         Integer32,
      pr1645v2EthPortSwIPPPoEMCOutOctets
         Counter64,
      pr1645v2EthPortSwIPPPoEMCOutUcastPkts
         Counter64,
      pr1645v2EthPortSwIPPPoEMCOutNUcastPkts
         Counter64,
      pr1645v2EthPortSwIPPPoEMCOutBcastPkts
         Counter64,
      pr1645v2EthPortSwIPPPoEMCOutMcastPkts
         Counter64,
      pr1645v2EthPortSwIPPPoEMCOutDiscards
         Counter64,
      pr1645v2EthPortSwIPPPoEMCOutErrors
         Counter64,
      pr1645v2EthPortSwIPPPoEMCOutQLen
         Counter32,
      pr1645v2EthPortSwIPPPoEMCOutDropEx
         Counter64,
      pr1645v2EthPortSwIPPPoEMCOutDropNoArp
         Counter64,
      pr1645v2EthPortSwIPPPoEMCOutDropFilter
         Counter64,
      pr1645v2EthPortSwIPPPoEMCOutBandwidth15sec
         Integer32,
      pr1645v2EthPortSwIPPPoEMCOutBandwidth30sec
         Integer32,
      pr1645v2EthPortSwIPPPoEMCOutBandwidth1min
         Integer32,
      pr1645v2EthPortSwIPPPoEMCOutBandwidth2min
         Integer32,
      pr1645v2EthPortSwIPPPoEMCOutBandwidth5min
         Integer32,
      pr1645v2EthPortSwIPPPoEPppLinkMonitoringRequestsSent
         Gauge32,
      pr1645v2EthPortSwIPPPoEPppLinkMonitoringRepliesRcvd
         Gauge32,
      pr1645v2EthPortSwIPPPoEPppLinkMonitoringRequestsRcvd
         Gauge32,
      pr1645v2EthPortSwIPPPoEPppLinkMonitoringRepliesSent
         Gauge32
      }

pr1645v2EthPortSwIPPPoEGlobalIx OBJECT-TYPE
   SYNTAX      GlobalIndex
   MAX-ACCESS  not-accessible
   STATUS      current
   DESCRIPTION
      "The value of the tlsCntTreeGlobalIndex of the MANAGED OBJECT."
   ::= {pr1645v2EthPortSwIPPPoEEntry 10}

pr1645v2EthPortSwIPPPoETableIx OBJECT-TYPE
   SYNTAX      TableIndex
   MAX-ACCESS  not-accessible
   STATUS      current
   DESCRIPTION
      ""
   ::= {pr1645v2EthPortSwIPPPoEEntry 11}

pr1645v2EthPortSwIPPPoEName OBJECT-TYPE
   SYNTAX      DisplayString
   MAX-ACCESS  read-only
   STATUS      current
   DESCRIPTION
      "Path: swPort.performance.pppoEClient.name"
   ::= {pr1645v2EthPortSwIPPPoEEntry 16777216}

pr1645v2EthPortSwIPPPoEMCInOctets OBJECT-TYPE
   SYNTAX      Counter64
   MAX-ACCESS  read-only
   STATUS      current
   DESCRIPTION
      "Path: swPort.performance.pppoEClient.mibCounters.ifInOctets

       64 bit unsigned wrappable counter."
   ::= {pr1645v2EthPortSwIPPPoEEntry 40697856}

pr1645v2EthPortSwIPPPoEMCInUcast OBJECT-TYPE
   SYNTAX      Counter64
   MAX-ACCESS  read-only
   STATUS      current
   DESCRIPTION
      "Path: swPort.performance.pppoEClient.mibCounters.ifInUcastPkts

       64 bit unsigned wrappable counter."
   ::= {pr1645v2EthPortSwIPPPoEEntry 40763392}

pr1645v2EthPortSwIPPPoEMCInNUcastPkts OBJECT-TYPE
   SYNTAX      Counter64
   MAX-ACCESS  read-only
   STATUS      current
   DESCRIPTION
      "Path: swPort.performance.pppoEClient.mibCounters.ifInNUcastPkts

       64 bit unsigned wrappable counter."
   ::= {pr1645v2EthPortSwIPPPoEEntry 40828928}

pr1645v2EthPortSwIPPPoEMCInBcastPkts OBJECT-TYPE
   SYNTAX      Counter64
   MAX-ACCESS  read-only
   STATUS      current
   DESCRIPTION
      "Path: swPort.performance.pppoEClient.mibCounters.ifInBcastPkts

       64 bit unsigned wrappable counter."
   ::= {pr1645v2EthPortSwIPPPoEEntry 47382528}

pr1645v2EthPortSwIPPPoEMCInMcastPkts OBJECT-TYPE
   SYNTAX      Counter64
   MAX-ACCESS  read-only
   STATUS      current
   DESCRIPTION
      "Path: swPort.performance.pppoEClient.mibCounters.ifInMcastPkts

       64 bit unsigned wrappable counter."
   ::= {pr1645v2EthPortSwIPPPoEEntry 48037888}

pr1645v2EthPortSwIPPPoEMCInDiscards OBJECT-TYPE
   SYNTAX      Counter64
   MAX-ACCESS  read-only
   STATUS      current
   DESCRIPTION
      "Path: swPort.performance.pppoEClient.mibCounters.ifInDiscards

       64 bit unsigned wrappable counter."
   ::= {pr1645v2EthPortSwIPPPoEEntry 40894464}

pr1645v2EthPortSwIPPPoEMCInErrors OBJECT-TYPE
   SYNTAX      Counter64
   MAX-ACCESS  read-only
   STATUS      current
   DESCRIPTION
      "Path: swPort.performance.pppoEClient.mibCounters.ifInErrors

       64 bit unsigned wrappable counter."
   ::= {pr1645v2EthPortSwIPPPoEEntry 40960000}

pr1645v2EthPortSwIPPPoEMCInUnknownProtos OBJECT-TYPE
   SYNTAX      Counter64
   MAX-ACCESS  read-only
   STATUS      current
   DESCRIPTION
      "Path: swPort.performance.pppoEClient.mibCounters.ifInUnknownProtos

       64 bit unsigned wrappable counter."
   ::= {pr1645v2EthPortSwIPPPoEEntry 41025536}

pr1645v2EthPortSwIPPPoEMCInDropEx OBJECT-TYPE
   SYNTAX      Counter64
   MAX-ACCESS  read-only
   STATUS      current
   DESCRIPTION
      "Path: swPort.performance.pppoEClient.mibCounters.ifInDropLevelExceeded

       64 bit unsigned wrappable counter."
   ::= {pr1645v2EthPortSwIPPPoEEntry 42074112}

pr1645v2EthPortSwIPPPoEMCInDropNoMac OBJECT-TYPE
   SYNTAX      Counter64
   MAX-ACCESS  read-only
   STATUS      current
   DESCRIPTION
      "Path: swPort.performance.pppoEClient.mibCounters.ifInDiscardsNoMacFit

       64 bit unsigned wrappable counter."
   ::= {pr1645v2EthPortSwIPPPoEEntry 42270720}

pr1645v2EthPortSwIPPPoEMCInDropNUCast OBJECT-TYPE
   SYNTAX      Counter64
   MAX-ACCESS  read-only
   STATUS      current
   DESCRIPTION
      "Path: swPort.performance.pppoEClient.mibCounters.ifInDiscardsNUCast

       64 bit unsigned wrappable counter."
   ::= {pr1645v2EthPortSwIPPPoEEntry 42467328}

pr1645v2EthPortSwIPPPoEMCInDropFilter OBJECT-TYPE
   SYNTAX      Counter64
   MAX-ACCESS  read-only
   STATUS      current
   DESCRIPTION
      "Path: swPort.performance.pppoEClient.mibCounters.ifInDiscardsFilter

       64 bit unsigned wrappable counter."
   ::= {pr1645v2EthPortSwIPPPoEEntry 42532864}

pr1645v2EthPortSwIPPPoEMCInBandwidth15sec OBJECT-TYPE
   SYNTAX      Integer32
   MAX-ACCESS  read-only
   STATUS      current
   DESCRIPTION
      "Path: swPort.performance.pppoEClient.mibCounters.ifInBandwidth.15sec

       unit name = bps
       formula = 8 * ; 8 /"
   ::= {pr1645v2EthPortSwIPPPoEEntry 45417728}

pr1645v2EthPortSwIPPPoEMCInBandwidth30sec OBJECT-TYPE
   SYNTAX      Integer32
   MAX-ACCESS  read-only
   STATUS      current
   DESCRIPTION
      "Path: swPort.performance.pppoEClient.mibCounters.ifInBandwidth.30sec

       unit name = bps
       formula = 8 * ; 8 /"
   ::= {pr1645v2EthPortSwIPPPoEEntry 45419008}

pr1645v2EthPortSwIPPPoEMCInBandwidth1min OBJECT-TYPE
   SYNTAX      Integer32
   MAX-ACCESS  read-only
   STATUS      current
   DESCRIPTION
      "Path: swPort.performance.pppoEClient.mibCounters.ifInBandwidth.1min

       unit name = bps
       formula = 8 * ; 8 /"
   ::= {pr1645v2EthPortSwIPPPoEEntry 45421568}

pr1645v2EthPortSwIPPPoEMCInBandwidth2min OBJECT-TYPE
   SYNTAX      Integer32
   MAX-ACCESS  read-only
   STATUS      current
   DESCRIPTION
      "Path: swPort.performance.pppoEClient.mibCounters.ifInBandwidth.2min

       unit name = bps
       formula = 8 * ; 8 /"
   ::= {pr1645v2EthPortSwIPPPoEEntry 45426688}

pr1645v2EthPortSwIPPPoEMCInBandwidth5min OBJECT-TYPE
   SYNTAX      Integer32
   MAX-ACCESS  read-only
   STATUS      current
   DESCRIPTION
      "Path: swPort.performance.pppoEClient.mibCounters.ifInBandwidth.5min

       unit name = bps
       formula = 8 * ; 8 /"
   ::= {pr1645v2EthPortSwIPPPoEEntry 45442048}

pr1645v2EthPortSwIPPPoEMCOutOctets OBJECT-TYPE
   SYNTAX      Counter64
   MAX-ACCESS  read-only
   STATUS      current
   DESCRIPTION
      "Path: swPort.performance.pppoEClient.mibCounters.ifOutOctets

       64 bit unsigned wrappable counter."
   ::= {pr1645v2EthPortSwIPPPoEEntry 41091072}

pr1645v2EthPortSwIPPPoEMCOutUcastPkts OBJECT-TYPE
   SYNTAX      Counter64
   MAX-ACCESS  read-only
   STATUS      current
   DESCRIPTION
      "Path: swPort.performance.pppoEClient.mibCounters.ifOutUcastPkts

       64 bit unsigned wrappable counter."
   ::= {pr1645v2EthPortSwIPPPoEEntry 41156608}

pr1645v2EthPortSwIPPPoEMCOutNUcastPkts OBJECT-TYPE
   SYNTAX      Counter64
   MAX-ACCESS  read-only
   STATUS      current
   DESCRIPTION
      "Path: swPort.performance.pppoEClient.mibCounters.ifOutNUcastPkts

       64 bit unsigned wrappable counter."
   ::= {pr1645v2EthPortSwIPPPoEEntry 41222144}

pr1645v2EthPortSwIPPPoEMCOutBcastPkts OBJECT-TYPE
   SYNTAX      Counter64
   MAX-ACCESS  read-only
   STATUS      current
   DESCRIPTION
      "Path: swPort.performance.pppoEClient.mibCounters.ifOutBcastPkts

       64 bit unsigned wrappable counter."
   ::= {pr1645v2EthPortSwIPPPoEEntry 47775744}

pr1645v2EthPortSwIPPPoEMCOutMcastPkts OBJECT-TYPE
   SYNTAX      Counter64
   MAX-ACCESS  read-only
   STATUS      current
   DESCRIPTION
      "Path: swPort.performance.pppoEClient.mibCounters.ifOutMcastPkts

       64 bit unsigned wrappable counter."
   ::= {pr1645v2EthPortSwIPPPoEEntry 48431104}

pr1645v2EthPortSwIPPPoEMCOutDiscards OBJECT-TYPE
   SYNTAX      Counter64
   MAX-ACCESS  read-only
   STATUS      current
   DESCRIPTION
      "Path: swPort.performance.pppoEClient.mibCounters.ifOutDiscards

       64 bit unsigned wrappable counter."
   ::= {pr1645v2EthPortSwIPPPoEEntry 41287680}

pr1645v2EthPortSwIPPPoEMCOutErrors OBJECT-TYPE
   SYNTAX      Counter64
   MAX-ACCESS  read-only
   STATUS      current
   DESCRIPTION
      "Path: swPort.performance.pppoEClient.mibCounters.ifOutErrors

       64 bit unsigned wrappable counter."
   ::= {pr1645v2EthPortSwIPPPoEEntry 41353216}

pr1645v2EthPortSwIPPPoEMCOutQLen OBJECT-TYPE
   SYNTAX      Counter32
   MAX-ACCESS  read-only
   STATUS      current
   DESCRIPTION
      "Path: swPort.performance.pppoEClient.mibCounters.ifOutQLen

       32 bit unsigned wrappable counter."
   ::= {pr1645v2EthPortSwIPPPoEEntry 41418752}

pr1645v2EthPortSwIPPPoEMCOutDropEx OBJECT-TYPE
   SYNTAX      Counter64
   MAX-ACCESS  read-only
   STATUS      current
   DESCRIPTION
      "Path: swPort.performance.pppoEClient.mibCounters.ifOutDropLevelExceeded

       64 bit unsigned wrappable counter."
   ::= {pr1645v2EthPortSwIPPPoEEntry 41484288}

pr1645v2EthPortSwIPPPoEMCOutDropNoArp OBJECT-TYPE
   SYNTAX      Counter64
   MAX-ACCESS  read-only
   STATUS      current
   DESCRIPTION
      "Path: swPort.performance.pppoEClient.mibCounters.ifOutDiscardsNoArp

       64 bit unsigned wrappable counter."
   ::= {pr1645v2EthPortSwIPPPoEEntry 42336256}

pr1645v2EthPortSwIPPPoEMCOutDropFilter OBJECT-TYPE
   SYNTAX      Counter64
   MAX-ACCESS  read-only
   STATUS      current
   DESCRIPTION
      "Path: swPort.performance.pppoEClient.mibCounters.ifOutDiscardsFilter

       64 bit unsigned wrappable counter."
   ::= {pr1645v2EthPortSwIPPPoEEntry 42598400}

pr1645v2EthPortSwIPPPoEMCOutBandwidth15sec OBJECT-TYPE
   SYNTAX      Integer32
   MAX-ACCESS  read-only
   STATUS      current
   DESCRIPTION
      "Path: swPort.performance.pppoEClient.mibCounters.ifOutBandwidth.15sec

       unit name = bps
       formula = 8 * ; 8 /"
   ::= {pr1645v2EthPortSwIPPPoEEntry 45483264}

pr1645v2EthPortSwIPPPoEMCOutBandwidth30sec OBJECT-TYPE
   SYNTAX      Integer32
   MAX-ACCESS  read-only
   STATUS      current
   DESCRIPTION
      "Path: swPort.performance.pppoEClient.mibCounters.ifOutBandwidth.30sec

       unit name = bps
       formula = 8 * ; 8 /"
   ::= {pr1645v2EthPortSwIPPPoEEntry 45484544}

pr1645v2EthPortSwIPPPoEMCOutBandwidth1min OBJECT-TYPE
   SYNTAX      Integer32
   MAX-ACCESS  read-only
   STATUS      current
   DESCRIPTION
      "Path: swPort.performance.pppoEClient.mibCounters.ifOutBandwidth.1min

       unit name = bps
       formula = 8 * ; 8 /"
   ::= {pr1645v2EthPortSwIPPPoEEntry 45487104}

pr1645v2EthPortSwIPPPoEMCOutBandwidth2min OBJECT-TYPE
   SYNTAX      Integer32
   MAX-ACCESS  read-only
   STATUS      current
   DESCRIPTION
      "Path: swPort.performance.pppoEClient.mibCounters.ifOutBandwidth.2min

       unit name = bps
       formula = 8 * ; 8 /"
   ::= {pr1645v2EthPortSwIPPPoEEntry 45492224}

pr1645v2EthPortSwIPPPoEMCOutBandwidth5min OBJECT-TYPE
   SYNTAX      Integer32
   MAX-ACCESS  read-only
   STATUS      current
   DESCRIPTION
      "Path: swPort.performance.pppoEClient.mibCounters.ifOutBandwidth.5min

       unit name = bps
       formula = 8 * ; 8 /"
   ::= {pr1645v2EthPortSwIPPPoEEntry 45507584}

pr1645v2EthPortSwIPPPoEPppLinkMonitoringRequestsSent OBJECT-TYPE
   SYNTAX      Gauge32
   MAX-ACCESS  read-only
   STATUS      current
   DESCRIPTION
      "Path: swPort.performance.pppoEClient.ppp.linkMonitoring.requestsSent

       32 bit unsigned gauge value."
   ::= {pr1645v2EthPortSwIPPPoEEntry 50397440}

pr1645v2EthPortSwIPPPoEPppLinkMonitoringRepliesRcvd OBJECT-TYPE
   SYNTAX      Gauge32
   MAX-ACCESS  read-only
   STATUS      current
   DESCRIPTION
      "Path: swPort.performance.pppoEClient.ppp.linkMonitoring.repliesRcvd

       32 bit unsigned gauge value."
   ::= {pr1645v2EthPortSwIPPPoEEntry 50397696}

pr1645v2EthPortSwIPPPoEPppLinkMonitoringRequestsRcvd OBJECT-TYPE
   SYNTAX      Gauge32
   MAX-ACCESS  read-only
   STATUS      current
   DESCRIPTION
      "Path: swPort.performance.pppoEClient.ppp.linkMonitoring.requestsRcvd

       32 bit unsigned gauge value."
   ::= {pr1645v2EthPortSwIPPPoEEntry 50397952}

pr1645v2EthPortSwIPPPoEPppLinkMonitoringRepliesSent OBJECT-TYPE
   SYNTAX      Gauge32
   MAX-ACCESS  read-only
   STATUS      current
   DESCRIPTION
      "Path: swPort.performance.pppoEClient.ppp.linkMonitoring.repliesSent

       32 bit unsigned gauge value."
   ::= {pr1645v2EthPortSwIPPPoEEntry 50398208}

pr1645v2EthPortSwIPPPoEMCH2P OBJECT-TYPE
   SYNTAX      SEQUENCE OF Pr1645v2EthPortSwIPPPoEMCH2PEntry
   MAX-ACCESS  not-accessible
   STATUS      current
   DESCRIPTION
      ""
   ::= {pr1645v2EthPortSwIPPPoE 41549824}

pr1645v2EthPortSwIPPPoEMCH2PEntry OBJECT-TYPE
   SYNTAX      Pr1645v2EthPortSwIPPPoEMCH2PEntry
   MAX-ACCESS  not-accessible
   STATUS      current
   DESCRIPTION
      ""
   INDEX      { pr1645v2EthPortSwIPPPoEMCH2PGlobalIx,
                pr1645v2EthPortSwIPPPoETableIx,
                pr1645v2EthPortSwIPPPoEMCH2PTableIx }
   ::= {pr1645v2EthPortSwIPPPoEMCH2P 1}

Pr1645v2EthPortSwIPPPoEMCH2PEntry ::=
   SEQUENCE
      {
      pr1645v2EthPortSwIPPPoEMCH2PGlobalIx
         GlobalIndex,
      pr1645v2EthPortSwIPPPoEMCH2PTableIx
         TableIndex,
      pr1645v2EthPortSwIPPPoEMCH2PSysUpTime
         TimeTicks,
      pr1645v2EthPortSwIPPPoEMCH2PIfUpTime
         TimeTicks,
      pr1645v2EthPortSwIPPPoEMCH2PIfStatChanges
         Counter32,
      pr1645v2EthPortSwIPPPoEMCH2PIfInOctets
         Counter64,
      pr1645v2EthPortSwIPPPoEMCH2PIfInUCPkts
         Counter64,
      pr1645v2EthPortSwIPPPoEMCH2PIfInNUCPkts
         Counter64,
      pr1645v2EthPortSwIPPPoEMCH2PIfInBCPkts
         Counter64,
      pr1645v2EthPortSwIPPPoEMCH2PIfInMCPkts
         Counter64,
      pr1645v2EthPortSwIPPPoEMCH2PIfInDiscards
         Counter64,
      pr1645v2EthPortSwIPPPoEMCH2PIfInErrors
         Counter64,
      pr1645v2EthPortSwIPPPoEMCH2PIfInUnkwn
         Counter64,
      pr1645v2EthPortSwIPPPoEMCH2PInDropEx
         Counter64,
      pr1645v2EthPortSwIPPPoEMCH2PInDropNoMac
         Counter64,
      pr1645v2EthPortSwIPPPoEMCH2PInDropNUCast
         Counter64,
      pr1645v2EthPortSwIPPPoEMCH2PInDropFilter
         Counter64,
      pr1645v2EthPortSwIPPPoEMCH2PIfInBandwidth
         Integer32,
      pr1645v2EthPortSwIPPPoEMCH2PIfOutOctets
         Counter64,
      pr1645v2EthPortSwIPPPoEMCH2PIfOutUCPkts
         Counter64,
      pr1645v2EthPortSwIPPPoEMCH2PIfOutNUCPkts
         Counter64,
      pr1645v2EthPortSwIPPPoEMCH2PIfOutBCPkts
         Counter64,
      pr1645v2EthPortSwIPPPoEMCH2PIfOutMCPkts
         Counter64,
      pr1645v2EthPortSwIPPPoEMCH2PIfOutDiscards
         Counter64,
      pr1645v2EthPortSwIPPPoEMCH2PIfOutErrors
         Counter64,
      pr1645v2EthPortSwIPPPoEMCH2POutDropEx
         Counter64,
      pr1645v2EthPortSwIPPPoEMCH2POutDropNoArp
         Counter64,
      pr1645v2EthPortSwIPPPoEMCH2POutDropFilter
         Counter64,
      pr1645v2EthPortSwIPPPoEMCH2PIfOutBandwidth
         Integer32,
      pr1645v2EthPortSwIPPPoEMCH2PIfErrSec
         Counter32
      }

pr1645v2EthPortSwIPPPoEMCH2PGlobalIx OBJECT-TYPE
   SYNTAX      GlobalIndex
   MAX-ACCESS  not-accessible
   STATUS      current
   DESCRIPTION
      "The value of the tlsCntTreeGlobalIndex of the MANAGED OBJECT."
   ::= {pr1645v2EthPortSwIPPPoEMCH2PEntry 10}

pr1645v2EthPortSwIPPPoEMCH2PTableIx OBJECT-TYPE
   SYNTAX      TableIndex
   MAX-ACCESS  not-accessible
   STATUS      current
   DESCRIPTION
      ""
   ::= {pr1645v2EthPortSwIPPPoEMCH2PEntry 11}

pr1645v2EthPortSwIPPPoEMCH2PSysUpTime OBJECT-TYPE
   SYNTAX      TimeTicks
   MAX-ACCESS  read-only
   STATUS      current
   DESCRIPTION
      "Path: swPort.performance.pppoEClient.mibCounters.h2Performance.sysUpTime

       Time in centi-second."
   ::= {pr1645v2EthPortSwIPPPoEMCH2PEntry 16777216}

pr1645v2EthPortSwIPPPoEMCH2PIfUpTime OBJECT-TYPE
   SYNTAX      TimeTicks
   MAX-ACCESS  read-only
   STATUS      current
   DESCRIPTION
      "Path: swPort.performance.pppoEClient.mibCounters.h2Performance.ifUpTime

       Time in centi-second."
   ::= {pr1645v2EthPortSwIPPPoEMCH2PEntry 33554432}

pr1645v2EthPortSwIPPPoEMCH2PIfStatChanges OBJECT-TYPE
   SYNTAX      Counter32
   MAX-ACCESS  read-only
   STATUS      current
   DESCRIPTION
      "Path: swPort.performance.pppoEClient.mibCounters.h2Performance.ifStatusChanges

       32 bit unsigned wrappable counter."
   ::= {pr1645v2EthPortSwIPPPoEMCH2PEntry 50331648}

pr1645v2EthPortSwIPPPoEMCH2PIfInOctets OBJECT-TYPE
   SYNTAX      Counter64
   MAX-ACCESS  read-only
   STATUS      current
   DESCRIPTION
      "Path: swPort.performance.pppoEClient.mibCounters.h2Performance.ifInOctets

       64 bit unsigned wrappable counter."
   ::= {pr1645v2EthPortSwIPPPoEMCH2PEntry 67108864}

pr1645v2EthPortSwIPPPoEMCH2PIfInUCPkts OBJECT-TYPE
   SYNTAX      Counter64
   MAX-ACCESS  read-only
   STATUS      current
   DESCRIPTION
      "Path: swPort.performance.pppoEClient.mibCounters.h2Performance.ifInUcastPkts

       64 bit unsigned wrappable counter."
   ::= {pr1645v2EthPortSwIPPPoEMCH2PEntry 83886080}

pr1645v2EthPortSwIPPPoEMCH2PIfInNUCPkts OBJECT-TYPE
   SYNTAX      Counter64
   MAX-ACCESS  read-only
   STATUS      current
   DESCRIPTION
      "Path: swPort.performance.pppoEClient.mibCounters.h2Performance.ifInNUcastPkts

       64 bit unsigned wrappable counter."
   ::= {pr1645v2EthPortSwIPPPoEMCH2PEntry 100663296}

pr1645v2EthPortSwIPPPoEMCH2PIfInBCPkts OBJECT-TYPE
   SYNTAX      Counter64
   MAX-ACCESS  read-only
   STATUS      current
   DESCRIPTION
      "Path: swPort.performance.pppoEClient.mibCounters.h2Performance.ifInBcastPkts

       64 bit unsigned wrappable counter."
   ::= {pr1645v2EthPortSwIPPPoEMCH2PEntry 419430400}

pr1645v2EthPortSwIPPPoEMCH2PIfInMCPkts OBJECT-TYPE
   SYNTAX      Counter64
   MAX-ACCESS  read-only
   STATUS      current
   DESCRIPTION
      "Path: swPort.performance.pppoEClient.mibCounters.h2Performance.ifInMcastPkts

       64 bit unsigned wrappable counter."
   ::= {pr1645v2EthPortSwIPPPoEMCH2PEntry 436207616}

pr1645v2EthPortSwIPPPoEMCH2PIfInDiscards OBJECT-TYPE
   SYNTAX      Counter64
   MAX-ACCESS  read-only
   STATUS      current
   DESCRIPTION
      "Path: swPort.performance.pppoEClient.mibCounters.h2Performance.ifInDiscards

       64 bit unsigned wrappable counter."
   ::= {pr1645v2EthPortSwIPPPoEMCH2PEntry 117440512}

pr1645v2EthPortSwIPPPoEMCH2PIfInErrors OBJECT-TYPE
   SYNTAX      Counter64
   MAX-ACCESS  read-only
   STATUS      current
   DESCRIPTION
      "Path: swPort.performance.pppoEClient.mibCounters.h2Performance.ifInErrors

       64 bit unsigned wrappable counter."
   ::= {pr1645v2EthPortSwIPPPoEMCH2PEntry 134217728}

pr1645v2EthPortSwIPPPoEMCH2PIfInUnkwn OBJECT-TYPE
   SYNTAX      Counter64
   MAX-ACCESS  read-only
   STATUS      current
   DESCRIPTION
      "Path: swPort.performance.pppoEClient.mibCounters.h2Performance.ifInUnknownProtos

       64 bit unsigned wrappable counter."
   ::= {pr1645v2EthPortSwIPPPoEMCH2PEntry 150994944}

pr1645v2EthPortSwIPPPoEMCH2PInDropEx OBJECT-TYPE
   SYNTAX      Counter64
   MAX-ACCESS  read-only
   STATUS      current
   DESCRIPTION
      "Path: swPort.performance.pppoEClient.mibCounters.h2Performance.ifInDropLevelExceeded

       64 bit unsigned wrappable counter."
   ::= {pr1645v2EthPortSwIPPPoEMCH2PEntry 335544320}

pr1645v2EthPortSwIPPPoEMCH2PInDropNoMac OBJECT-TYPE
   SYNTAX      Counter64
   MAX-ACCESS  read-only
   STATUS      current
   DESCRIPTION
      "Path: swPort.performance.pppoEClient.mibCounters.h2Performance.fInDiscardsNoMacFit

       64 bit unsigned wrappable counter."
   ::= {pr1645v2EthPortSwIPPPoEMCH2PEntry 301989888}

pr1645v2EthPortSwIPPPoEMCH2PInDropNUCast OBJECT-TYPE
   SYNTAX      Counter64
   MAX-ACCESS  read-only
   STATUS      current
   DESCRIPTION
      "Path: swPort.performance.pppoEClient.mibCounters.h2Performance.fInDiscardsNUCast

       64 bit unsigned wrappable counter."
   ::= {pr1645v2EthPortSwIPPPoEMCH2PEntry 318767104}

pr1645v2EthPortSwIPPPoEMCH2PInDropFilter OBJECT-TYPE
   SYNTAX      Counter64
   MAX-ACCESS  read-only
   STATUS      current
   DESCRIPTION
      "Path: swPort.performance.pppoEClient.mibCounters.h2Performance.fInDiscardsFilter

       64 bit unsigned wrappable counter."
   ::= {pr1645v2EthPortSwIPPPoEMCH2PEntry 385875968}

pr1645v2EthPortSwIPPPoEMCH2PIfInBandwidth OBJECT-TYPE
   SYNTAX      Integer32
   MAX-ACCESS  read-only
   STATUS      current
   DESCRIPTION
      "Path: swPort.performance.pppoEClient.mibCounters.h2Performance.ifInBandwidth

       unit name = bps
       formula = 8 * ; 8 /"
   ::= {pr1645v2EthPortSwIPPPoEMCH2PEntry 268435456}

pr1645v2EthPortSwIPPPoEMCH2PIfOutOctets OBJECT-TYPE
   SYNTAX      Counter64
   MAX-ACCESS  read-only
   STATUS      current
   DESCRIPTION
      "Path: swPort.performance.pppoEClient.mibCounters.h2Performance.ifOutOctets

       64 bit unsigned wrappable counter."
   ::= {pr1645v2EthPortSwIPPPoEMCH2PEntry 167772160}

pr1645v2EthPortSwIPPPoEMCH2PIfOutUCPkts OBJECT-TYPE
   SYNTAX      Counter64
   MAX-ACCESS  read-only
   STATUS      current
   DESCRIPTION
      "Path: swPort.performance.pppoEClient.mibCounters.h2Performance.ifOutUcastPkts

       64 bit unsigned wrappable counter."
   ::= {pr1645v2EthPortSwIPPPoEMCH2PEntry 184549376}

pr1645v2EthPortSwIPPPoEMCH2PIfOutNUCPkts OBJECT-TYPE
   SYNTAX      Counter64
   MAX-ACCESS  read-only
   STATUS      current
   DESCRIPTION
      "Path: swPort.performance.pppoEClient.mibCounters.h2Performance.ifOutNUcastPkts

       64 bit unsigned wrappable counter."
   ::= {pr1645v2EthPortSwIPPPoEMCH2PEntry 201326592}

pr1645v2EthPortSwIPPPoEMCH2PIfOutBCPkts OBJECT-TYPE
   SYNTAX      Counter64
   MAX-ACCESS  read-only
   STATUS      current
   DESCRIPTION
      "Path: swPort.performance.pppoEClient.mibCounters.h2Performance.ifOutBcastPkts

       64 bit unsigned wrappable counter."
   ::= {pr1645v2EthPortSwIPPPoEMCH2PEntry 452984832}

pr1645v2EthPortSwIPPPoEMCH2PIfOutMCPkts OBJECT-TYPE
   SYNTAX      Counter64
   MAX-ACCESS  read-only
   STATUS      current
   DESCRIPTION
      "Path: swPort.performance.pppoEClient.mibCounters.h2Performance.ifOutMcastPkts

       64 bit unsigned wrappable counter."
   ::= {pr1645v2EthPortSwIPPPoEMCH2PEntry 469762048}

pr1645v2EthPortSwIPPPoEMCH2PIfOutDiscards OBJECT-TYPE
   SYNTAX      Counter64
   MAX-ACCESS  read-only
   STATUS      current
   DESCRIPTION
      "Path: swPort.performance.pppoEClient.mibCounters.h2Performance.ifOutDiscards

       64 bit unsigned wrappable counter."
   ::= {pr1645v2EthPortSwIPPPoEMCH2PEntry 218103808}

pr1645v2EthPortSwIPPPoEMCH2PIfOutErrors OBJECT-TYPE
   SYNTAX      Counter64
   MAX-ACCESS  read-only
   STATUS      current
   DESCRIPTION
      "Path: swPort.performance.pppoEClient.mibCounters.h2Performance.ifOutErrors

       64 bit unsigned wrappable counter."
   ::= {pr1645v2EthPortSwIPPPoEMCH2PEntry 234881024}

pr1645v2EthPortSwIPPPoEMCH2POutDropEx OBJECT-TYPE
   SYNTAX      Counter64
   MAX-ACCESS  read-only
   STATUS      current
   DESCRIPTION
      "Path: swPort.performance.pppoEClient.mibCounters.h2Performance.ifOutDropLevelExceeded

       64 bit unsigned wrappable counter."
   ::= {pr1645v2EthPortSwIPPPoEMCH2PEntry 352321536}

pr1645v2EthPortSwIPPPoEMCH2POutDropNoArp OBJECT-TYPE
   SYNTAX      Counter64
   MAX-ACCESS  read-only
   STATUS      current
   DESCRIPTION
      "Path: swPort.performance.pppoEClient.mibCounters.h2Performance.ifOutDiscardsNoArp

       64 bit unsigned wrappable counter."
   ::= {pr1645v2EthPortSwIPPPoEMCH2PEntry 369098752}

pr1645v2EthPortSwIPPPoEMCH2POutDropFilter OBJECT-TYPE
   SYNTAX      Counter64
   MAX-ACCESS  read-only
   STATUS      current
   DESCRIPTION
      "Path: swPort.performance.pppoEClient.mibCounters.h2Performance.ifOutDiscardsFilter

       64 bit unsigned wrappable counter."
   ::= {pr1645v2EthPortSwIPPPoEMCH2PEntry 402653184}

pr1645v2EthPortSwIPPPoEMCH2PIfOutBandwidth OBJECT-TYPE
   SYNTAX      Integer32
   MAX-ACCESS  read-only
   STATUS      current
   DESCRIPTION
      "Path: swPort.performance.pppoEClient.mibCounters.h2Performance.ifOutBandwidth

       unit name = bps
       formula = 8 * ; 8 /"
   ::= {pr1645v2EthPortSwIPPPoEMCH2PEntry 285212672}

pr1645v2EthPortSwIPPPoEMCH2PIfErrSec OBJECT-TYPE
   SYNTAX      Counter32
   MAX-ACCESS  read-only
   STATUS      current
   DESCRIPTION
      "Path: swPort.performance.pppoEClient.mibCounters.h2Performance.ifErrSec

       32 bit unsigned wrappable counter."
   ::= {pr1645v2EthPortSwIPPPoEMCH2PEntry 251658240}

pr1645v2EthPortSwIPPPoEMCH24P OBJECT-TYPE
   SYNTAX      SEQUENCE OF Pr1645v2EthPortSwIPPPoEMCH24PEntry
   MAX-ACCESS  not-accessible
   STATUS      current
   DESCRIPTION
      ""
   ::= {pr1645v2EthPortSwIPPPoE 41615360}

pr1645v2EthPortSwIPPPoEMCH24PEntry OBJECT-TYPE
   SYNTAX      Pr1645v2EthPortSwIPPPoEMCH24PEntry
   MAX-ACCESS  not-accessible
   STATUS      current
   DESCRIPTION
      ""
   INDEX      { pr1645v2EthPortSwIPPPoEMCH24PGlobalIx,
                pr1645v2EthPortSwIPPPoETableIx,
                pr1645v2EthPortSwIPPPoEMCH24PTableIx }
   ::= {pr1645v2EthPortSwIPPPoEMCH24P 1}

Pr1645v2EthPortSwIPPPoEMCH24PEntry ::=
   SEQUENCE
      {
      pr1645v2EthPortSwIPPPoEMCH24PGlobalIx
         GlobalIndex,
      pr1645v2EthPortSwIPPPoEMCH24PTableIx
         TableIndex,
      pr1645v2EthPortSwIPPPoEMCH24PSysUpTime
         TimeTicks,
      pr1645v2EthPortSwIPPPoEMCH24PIfUpTime
         TimeTicks,
      pr1645v2EthPortSwIPPPoEMCH24PIfStatChanges
         Counter32,
      pr1645v2EthPortSwIPPPoEMCH24PIfInOctets
         Counter64,
      pr1645v2EthPortSwIPPPoEMCH24PIfInUCPkts
         Counter64,
      pr1645v2EthPortSwIPPPoEMCH24PIfInNUCPkts
         Counter64,
      pr1645v2EthPortSwIPPPoEMCH24PIfInBCPkts
         Counter64,
      pr1645v2EthPortSwIPPPoEMCH24PIfInMCPkts
         Counter64,
      pr1645v2EthPortSwIPPPoEMCH24PIfInDiscards
         Counter64,
      pr1645v2EthPortSwIPPPoEMCH24PIfInErrors
         Counter64,
      pr1645v2EthPortSwIPPPoEMCH24PIfInUnkwn
         Counter64,
      pr1645v2EthPortSwIPPPoEMCH24PInDropEx
         Counter64,
      pr1645v2EthPortSwIPPPoEMCH24PInDropNoMac
         Counter64,
      pr1645v2EthPortSwIPPPoEMCH24PInDropNUCast
         Counter64,
      pr1645v2EthPortSwIPPPoEMCH24PInDropFilter
         Counter64,
      pr1645v2EthPortSwIPPPoEMCH24PIfInBandwidth
         Integer32,
      pr1645v2EthPortSwIPPPoEMCH24PIfOutOctets
         Counter64,
      pr1645v2EthPortSwIPPPoEMCH24PIfOutUCPkts
         Counter64,
      pr1645v2EthPortSwIPPPoEMCH24PIfOutNUCPkts
         Counter64,
      pr1645v2EthPortSwIPPPoEMCH24PIfOutBCPkts
         Counter64,
      pr1645v2EthPortSwIPPPoEMCH24PIfOutMCPkts
         Counter64,
      pr1645v2EthPortSwIPPPoEMCH24PIfOutDiscards
         Counter64,
      pr1645v2EthPortSwIPPPoEMCH24PIfOutErrors
         Counter64,
      pr1645v2EthPortSwIPPPoEMCH24POutDropEx
         Counter64,
      pr1645v2EthPortSwIPPPoEMCH24POutDropNoArp
         Counter64,
      pr1645v2EthPortSwIPPPoEMCH24POutDropFilter
         Counter64,
      pr1645v2EthPortSwIPPPoEMCH24PIfOutBandwidth
         Integer32,
      pr1645v2EthPortSwIPPPoEMCH24PIfErrSec
         Counter32
      }

pr1645v2EthPortSwIPPPoEMCH24PGlobalIx OBJECT-TYPE
   SYNTAX      GlobalIndex
   MAX-ACCESS  not-accessible
   STATUS      current
   DESCRIPTION
      "The value of the tlsCntTreeGlobalIndex of the MANAGED OBJECT."
   ::= {pr1645v2EthPortSwIPPPoEMCH24PEntry 10}

pr1645v2EthPortSwIPPPoEMCH24PTableIx OBJECT-TYPE
   SYNTAX      TableIndex
   MAX-ACCESS  not-accessible
   STATUS      current
   DESCRIPTION
      ""
   ::= {pr1645v2EthPortSwIPPPoEMCH24PEntry 11}

pr1645v2EthPortSwIPPPoEMCH24PSysUpTime OBJECT-TYPE
   SYNTAX      TimeTicks
   MAX-ACCESS  read-only
   STATUS      current
   DESCRIPTION
      "Path: swPort.performance.pppoEClient.mibCounters.h24Performance.sysUpTime

       Time in centi-second."
   ::= {pr1645v2EthPortSwIPPPoEMCH24PEntry 16777216}

pr1645v2EthPortSwIPPPoEMCH24PIfUpTime OBJECT-TYPE
   SYNTAX      TimeTicks
   MAX-ACCESS  read-only
   STATUS      current
   DESCRIPTION
      "Path: swPort.performance.pppoEClient.mibCounters.h24Performance.ifUpTime

       Time in centi-second."
   ::= {pr1645v2EthPortSwIPPPoEMCH24PEntry 33554432}

pr1645v2EthPortSwIPPPoEMCH24PIfStatChanges OBJECT-TYPE
   SYNTAX      Counter32
   MAX-ACCESS  read-only
   STATUS      current
   DESCRIPTION
      "Path: swPort.performance.pppoEClient.mibCounters.h24Performance.ifStatusChanges

       32 bit unsigned wrappable counter."
   ::= {pr1645v2EthPortSwIPPPoEMCH24PEntry 50331648}

pr1645v2EthPortSwIPPPoEMCH24PIfInOctets OBJECT-TYPE
   SYNTAX      Counter64
   MAX-ACCESS  read-only
   STATUS      current
   DESCRIPTION
      "Path: swPort.performance.pppoEClient.mibCounters.h24Performance.ifInOctets

       64 bit unsigned wrappable counter."
   ::= {pr1645v2EthPortSwIPPPoEMCH24PEntry 67108864}

pr1645v2EthPortSwIPPPoEMCH24PIfInUCPkts OBJECT-TYPE
   SYNTAX      Counter64
   MAX-ACCESS  read-only
   STATUS      current
   DESCRIPTION
      "Path: swPort.performance.pppoEClient.mibCounters.h24Performance.ifInUcastPkts

       64 bit unsigned wrappable counter."
   ::= {pr1645v2EthPortSwIPPPoEMCH24PEntry 83886080}

pr1645v2EthPortSwIPPPoEMCH24PIfInNUCPkts OBJECT-TYPE
   SYNTAX      Counter64
   MAX-ACCESS  read-only
   STATUS      current
   DESCRIPTION
      "Path: swPort.performance.pppoEClient.mibCounters.h24Performance.ifInNUcastPkts

       64 bit unsigned wrappable counter."
   ::= {pr1645v2EthPortSwIPPPoEMCH24PEntry 100663296}

pr1645v2EthPortSwIPPPoEMCH24PIfInBCPkts OBJECT-TYPE
   SYNTAX      Counter64
   MAX-ACCESS  read-only
   STATUS      current
   DESCRIPTION
      "Path: swPort.performance.pppoEClient.mibCounters.h24Performance.ifInBcastPkts

       64 bit unsigned wrappable counter."
   ::= {pr1645v2EthPortSwIPPPoEMCH24PEntry 419430400}

pr1645v2EthPortSwIPPPoEMCH24PIfInMCPkts OBJECT-TYPE
   SYNTAX      Counter64
   MAX-ACCESS  read-only
   STATUS      current
   DESCRIPTION
      "Path: swPort.performance.pppoEClient.mibCounters.h24Performance.ifInMcastPkts

       64 bit unsigned wrappable counter."
   ::= {pr1645v2EthPortSwIPPPoEMCH24PEntry 436207616}

pr1645v2EthPortSwIPPPoEMCH24PIfInDiscards OBJECT-TYPE
   SYNTAX      Counter64
   MAX-ACCESS  read-only
   STATUS      current
   DESCRIPTION
      "Path: swPort.performance.pppoEClient.mibCounters.h24Performance.ifInDiscards

       64 bit unsigned wrappable counter."
   ::= {pr1645v2EthPortSwIPPPoEMCH24PEntry 117440512}

pr1645v2EthPortSwIPPPoEMCH24PIfInErrors OBJECT-TYPE
   SYNTAX      Counter64
   MAX-ACCESS  read-only
   STATUS      current
   DESCRIPTION
      "Path: swPort.performance.pppoEClient.mibCounters.h24Performance.ifInErrors

       64 bit unsigned wrappable counter."
   ::= {pr1645v2EthPortSwIPPPoEMCH24PEntry 134217728}

pr1645v2EthPortSwIPPPoEMCH24PIfInUnkwn OBJECT-TYPE
   SYNTAX      Counter64
   MAX-ACCESS  read-only
   STATUS      current
   DESCRIPTION
      "Path: swPort.performance.pppoEClient.mibCounters.h24Performance.ifInUnknownProtos

       64 bit unsigned wrappable counter."
   ::= {pr1645v2EthPortSwIPPPoEMCH24PEntry 150994944}

pr1645v2EthPortSwIPPPoEMCH24PInDropEx OBJECT-TYPE
   SYNTAX      Counter64
   MAX-ACCESS  read-only
   STATUS      current
   DESCRIPTION
      "Path: swPort.performance.pppoEClient.mibCounters.h24Performance.ifInDropLevelExceeded

       64 bit unsigned wrappable counter."
   ::= {pr1645v2EthPortSwIPPPoEMCH24PEntry 335544320}

pr1645v2EthPortSwIPPPoEMCH24PInDropNoMac OBJECT-TYPE
   SYNTAX      Counter64
   MAX-ACCESS  read-only
   STATUS      current
   DESCRIPTION
      "Path: swPort.performance.pppoEClient.mibCounters.h24Performance.fInDiscardsNoMacFit

       64 bit unsigned wrappable counter."
   ::= {pr1645v2EthPortSwIPPPoEMCH24PEntry 301989888}

pr1645v2EthPortSwIPPPoEMCH24PInDropNUCast OBJECT-TYPE
   SYNTAX      Counter64
   MAX-ACCESS  read-only
   STATUS      current
   DESCRIPTION
      "Path: swPort.performance.pppoEClient.mibCounters.h24Performance.fInDiscardsNUCast

       64 bit unsigned wrappable counter."
   ::= {pr1645v2EthPortSwIPPPoEMCH24PEntry 318767104}

pr1645v2EthPortSwIPPPoEMCH24PInDropFilter OBJECT-TYPE
   SYNTAX      Counter64
   MAX-ACCESS  read-only
   STATUS      current
   DESCRIPTION
      "Path: swPort.performance.pppoEClient.mibCounters.h24Performance.fInDiscardsFilter

       64 bit unsigned wrappable counter."
   ::= {pr1645v2EthPortSwIPPPoEMCH24PEntry 385875968}

pr1645v2EthPortSwIPPPoEMCH24PIfInBandwidth OBJECT-TYPE
   SYNTAX      Integer32
   MAX-ACCESS  read-only
   STATUS      current
   DESCRIPTION
      "Path: swPort.performance.pppoEClient.mibCounters.h24Performance.ifInBandwidth

       unit name = bps
       formula = 8 * ; 8 /"
   ::= {pr1645v2EthPortSwIPPPoEMCH24PEntry 268435456}

pr1645v2EthPortSwIPPPoEMCH24PIfOutOctets OBJECT-TYPE
   SYNTAX      Counter64
   MAX-ACCESS  read-only
   STATUS      current
   DESCRIPTION
      "Path: swPort.performance.pppoEClient.mibCounters.h24Performance.ifOutOctets

       64 bit unsigned wrappable counter."
   ::= {pr1645v2EthPortSwIPPPoEMCH24PEntry 167772160}

pr1645v2EthPortSwIPPPoEMCH24PIfOutUCPkts OBJECT-TYPE
   SYNTAX      Counter64
   MAX-ACCESS  read-only
   STATUS      current
   DESCRIPTION
      "Path: swPort.performance.pppoEClient.mibCounters.h24Performance.ifOutUcastPkts

       64 bit unsigned wrappable counter."
   ::= {pr1645v2EthPortSwIPPPoEMCH24PEntry 184549376}

pr1645v2EthPortSwIPPPoEMCH24PIfOutNUCPkts OBJECT-TYPE
   SYNTAX      Counter64
   MAX-ACCESS  read-only
   STATUS      current
   DESCRIPTION
      "Path: swPort.performance.pppoEClient.mibCounters.h24Performance.ifOutNUcastPkts

       64 bit unsigned wrappable counter."
   ::= {pr1645v2EthPortSwIPPPoEMCH24PEntry 201326592}

pr1645v2EthPortSwIPPPoEMCH24PIfOutBCPkts OBJECT-TYPE
   SYNTAX      Counter64
   MAX-ACCESS  read-only
   STATUS      current
   DESCRIPTION
      "Path: swPort.performance.pppoEClient.mibCounters.h24Performance.ifOutBcastPkts

       64 bit unsigned wrappable counter."
   ::= {pr1645v2EthPortSwIPPPoEMCH24PEntry 452984832}

pr1645v2EthPortSwIPPPoEMCH24PIfOutMCPkts OBJECT-TYPE
   SYNTAX      Counter64
   MAX-ACCESS  read-only
   STATUS      current
   DESCRIPTION
      "Path: swPort.performance.pppoEClient.mibCounters.h24Performance.ifOutMcastPkts

       64 bit unsigned wrappable counter."
   ::= {pr1645v2EthPortSwIPPPoEMCH24PEntry 469762048}

pr1645v2EthPortSwIPPPoEMCH24PIfOutDiscards OBJECT-TYPE
   SYNTAX      Counter64
   MAX-ACCESS  read-only
   STATUS      current
   DESCRIPTION
      "Path: swPort.performance.pppoEClient.mibCounters.h24Performance.ifOutDiscards

       64 bit unsigned wrappable counter."
   ::= {pr1645v2EthPortSwIPPPoEMCH24PEntry 218103808}

pr1645v2EthPortSwIPPPoEMCH24PIfOutErrors OBJECT-TYPE
   SYNTAX      Counter64
   MAX-ACCESS  read-only
   STATUS      current
   DESCRIPTION
      "Path: swPort.performance.pppoEClient.mibCounters.h24Performance.ifOutErrors

       64 bit unsigned wrappable counter."
   ::= {pr1645v2EthPortSwIPPPoEMCH24PEntry 234881024}

pr1645v2EthPortSwIPPPoEMCH24POutDropEx OBJECT-TYPE
   SYNTAX      Counter64
   MAX-ACCESS  read-only
   STATUS      current
   DESCRIPTION
      "Path: swPort.performance.pppoEClient.mibCounters.h24Performance.ifOutDropLevelExceeded

       64 bit unsigned wrappable counter."
   ::= {pr1645v2EthPortSwIPPPoEMCH24PEntry 352321536}

pr1645v2EthPortSwIPPPoEMCH24POutDropNoArp OBJECT-TYPE
   SYNTAX      Counter64
   MAX-ACCESS  read-only
   STATUS      current
   DESCRIPTION
      "Path: swPort.performance.pppoEClient.mibCounters.h24Performance.ifOutDiscardsNoArp

       64 bit unsigned wrappable counter."
   ::= {pr1645v2EthPortSwIPPPoEMCH24PEntry 369098752}

pr1645v2EthPortSwIPPPoEMCH24POutDropFilter OBJECT-TYPE
   SYNTAX      Counter64
   MAX-ACCESS  read-only
   STATUS      current
   DESCRIPTION
      "Path: swPort.performance.pppoEClient.mibCounters.h24Performance.ifOutDiscardsFilter

       64 bit unsigned wrappable counter."
   ::= {pr1645v2EthPortSwIPPPoEMCH24PEntry 402653184}

pr1645v2EthPortSwIPPPoEMCH24PIfOutBandwidth OBJECT-TYPE
   SYNTAX      Integer32
   MAX-ACCESS  read-only
   STATUS      current
   DESCRIPTION
      "Path: swPort.performance.pppoEClient.mibCounters.h24Performance.ifOutBandwidth

       unit name = bps
       formula = 8 * ; 8 /"
   ::= {pr1645v2EthPortSwIPPPoEMCH24PEntry 285212672}

pr1645v2EthPortSwIPPPoEMCH24PIfErrSec OBJECT-TYPE
   SYNTAX      Counter32
   MAX-ACCESS  read-only
   STATUS      current
   DESCRIPTION
      "Path: swPort.performance.pppoEClient.mibCounters.h24Performance.ifErrSec

       32 bit unsigned wrappable counter."
   ::= {pr1645v2EthPortSwIPPPoEMCH24PEntry 251658240}

pr1645v2EthPortSwIPPPoEMCD7P OBJECT-TYPE
   SYNTAX      SEQUENCE OF Pr1645v2EthPortSwIPPPoEMCD7PEntry
   MAX-ACCESS  not-accessible
   STATUS      current
   DESCRIPTION
      ""
   ::= {pr1645v2EthPortSwIPPPoE 41680896}

pr1645v2EthPortSwIPPPoEMCD7PEntry OBJECT-TYPE
   SYNTAX      Pr1645v2EthPortSwIPPPoEMCD7PEntry
   MAX-ACCESS  not-accessible
   STATUS      current
   DESCRIPTION
      ""
   INDEX      { pr1645v2EthPortSwIPPPoEMCD7PGlobalIx,
                pr1645v2EthPortSwIPPPoETableIx,
                pr1645v2EthPortSwIPPPoEMCD7PTableIx }
   ::= {pr1645v2EthPortSwIPPPoEMCD7P 1}

Pr1645v2EthPortSwIPPPoEMCD7PEntry ::=
   SEQUENCE
      {
      pr1645v2EthPortSwIPPPoEMCD7PGlobalIx
         GlobalIndex,
      pr1645v2EthPortSwIPPPoEMCD7PTableIx
         TableIndex,
      pr1645v2EthPortSwIPPPoEMCD7PSysUpTime
         TimeTicks,
      pr1645v2EthPortSwIPPPoEMCD7PIfUpTime
         TimeTicks,
      pr1645v2EthPortSwIPPPoEMCD7PIfStatChanges
         Counter32,
      pr1645v2EthPortSwIPPPoEMCD7PIfInOctets
         Counter64,
      pr1645v2EthPortSwIPPPoEMCD7PIfInUCPkts
         Counter64,
      pr1645v2EthPortSwIPPPoEMCD7PIfInNUCPkts
         Counter64,
      pr1645v2EthPortSwIPPPoEMCD7PIfInBCPkts
         Counter64,
      pr1645v2EthPortSwIPPPoEMCD7PIfInMCPkts
         Counter64,
      pr1645v2EthPortSwIPPPoEMCD7PIfInDiscards
         Counter64,
      pr1645v2EthPortSwIPPPoEMCD7PIfInErrors
         Counter64,
      pr1645v2EthPortSwIPPPoEMCD7PIfInUnkwn
         Counter64,
      pr1645v2EthPortSwIPPPoEMCD7PInDropEx
         Counter64,
      pr1645v2EthPortSwIPPPoEMCD7PInDropNoMac
         Counter64,
      pr1645v2EthPortSwIPPPoEMCD7PInDropNUCast
         Counter64,
      pr1645v2EthPortSwIPPPoEMCD7PInDropFilter
         Counter64,
      pr1645v2EthPortSwIPPPoEMCD7PIfInBandwidth
         Integer32,
      pr1645v2EthPortSwIPPPoEMCD7PIfOutOctets
         Counter64,
      pr1645v2EthPortSwIPPPoEMCD7PIfOutUCPkts
         Counter64,
      pr1645v2EthPortSwIPPPoEMCD7PIfOutNUCPkts
         Counter64,
      pr1645v2EthPortSwIPPPoEMCD7PIfOutBCPkts
         Counter64,
      pr1645v2EthPortSwIPPPoEMCD7PIfOutMCPkts
         Counter64,
      pr1645v2EthPortSwIPPPoEMCD7PIfOutDiscards
         Counter64,
      pr1645v2EthPortSwIPPPoEMCD7PIfOutErrors
         Counter64,
      pr1645v2EthPortSwIPPPoEMCD7POutDropEx
         Counter64,
      pr1645v2EthPortSwIPPPoEMCD7POutDropNoArp
         Counter64,
      pr1645v2EthPortSwIPPPoEMCD7POutDropFilter
         Counter64,
      pr1645v2EthPortSwIPPPoEMCD7PIfOutBandwidth
         Integer32,
      pr1645v2EthPortSwIPPPoEMCD7PIfErrSec
         Counter32
      }

pr1645v2EthPortSwIPPPoEMCD7PGlobalIx OBJECT-TYPE
   SYNTAX      GlobalIndex
   MAX-ACCESS  not-accessible
   STATUS      current
   DESCRIPTION
      "The value of the tlsCntTreeGlobalIndex of the MANAGED OBJECT."
   ::= {pr1645v2EthPortSwIPPPoEMCD7PEntry 10}

pr1645v2EthPortSwIPPPoEMCD7PTableIx OBJECT-TYPE
   SYNTAX      TableIndex
   MAX-ACCESS  not-accessible
   STATUS      current
   DESCRIPTION
      ""
   ::= {pr1645v2EthPortSwIPPPoEMCD7PEntry 11}

pr1645v2EthPortSwIPPPoEMCD7PSysUpTime OBJECT-TYPE
   SYNTAX      TimeTicks
   MAX-ACCESS  read-only
   STATUS      current
   DESCRIPTION
      "Path: swPort.performance.pppoEClient.mibCounters.d7Performance.sysUpTime

       Time in centi-second."
   ::= {pr1645v2EthPortSwIPPPoEMCD7PEntry 16777216}

pr1645v2EthPortSwIPPPoEMCD7PIfUpTime OBJECT-TYPE
   SYNTAX      TimeTicks
   MAX-ACCESS  read-only
   STATUS      current
   DESCRIPTION
      "Path: swPort.performance.pppoEClient.mibCounters.d7Performance.ifUpTime

       Time in centi-second."
   ::= {pr1645v2EthPortSwIPPPoEMCD7PEntry 33554432}

pr1645v2EthPortSwIPPPoEMCD7PIfStatChanges OBJECT-TYPE
   SYNTAX      Counter32
   MAX-ACCESS  read-only
   STATUS      current
   DESCRIPTION
      "Path: swPort.performance.pppoEClient.mibCounters.d7Performance.ifStatusChanges

       32 bit unsigned wrappable counter."
   ::= {pr1645v2EthPortSwIPPPoEMCD7PEntry 50331648}

pr1645v2EthPortSwIPPPoEMCD7PIfInOctets OBJECT-TYPE
   SYNTAX      Counter64
   MAX-ACCESS  read-only
   STATUS      current
   DESCRIPTION
      "Path: swPort.performance.pppoEClient.mibCounters.d7Performance.ifInOctets

       64 bit unsigned wrappable counter."
   ::= {pr1645v2EthPortSwIPPPoEMCD7PEntry 67108864}

pr1645v2EthPortSwIPPPoEMCD7PIfInUCPkts OBJECT-TYPE
   SYNTAX      Counter64
   MAX-ACCESS  read-only
   STATUS      current
   DESCRIPTION
      "Path: swPort.performance.pppoEClient.mibCounters.d7Performance.ifInUcastPkts

       64 bit unsigned wrappable counter."
   ::= {pr1645v2EthPortSwIPPPoEMCD7PEntry 83886080}

pr1645v2EthPortSwIPPPoEMCD7PIfInNUCPkts OBJECT-TYPE
   SYNTAX      Counter64
   MAX-ACCESS  read-only
   STATUS      current
   DESCRIPTION
      "Path: swPort.performance.pppoEClient.mibCounters.d7Performance.ifInNUcastPkts

       64 bit unsigned wrappable counter."
   ::= {pr1645v2EthPortSwIPPPoEMCD7PEntry 100663296}

pr1645v2EthPortSwIPPPoEMCD7PIfInBCPkts OBJECT-TYPE
   SYNTAX      Counter64
   MAX-ACCESS  read-only
   STATUS      current
   DESCRIPTION
      "Path: swPort.performance.pppoEClient.mibCounters.d7Performance.ifInBcastPkts

       64 bit unsigned wrappable counter."
   ::= {pr1645v2EthPortSwIPPPoEMCD7PEntry 419430400}

pr1645v2EthPortSwIPPPoEMCD7PIfInMCPkts OBJECT-TYPE
   SYNTAX      Counter64
   MAX-ACCESS  read-only
   STATUS      current
   DESCRIPTION
      "Path: swPort.performance.pppoEClient.mibCounters.d7Performance.ifInMcastPkts

       64 bit unsigned wrappable counter."
   ::= {pr1645v2EthPortSwIPPPoEMCD7PEntry 436207616}

pr1645v2EthPortSwIPPPoEMCD7PIfInDiscards OBJECT-TYPE
   SYNTAX      Counter64
   MAX-ACCESS  read-only
   STATUS      current
   DESCRIPTION
      "Path: swPort.performance.pppoEClient.mibCounters.d7Performance.ifInDiscards

       64 bit unsigned wrappable counter."
   ::= {pr1645v2EthPortSwIPPPoEMCD7PEntry 117440512}

pr1645v2EthPortSwIPPPoEMCD7PIfInErrors OBJECT-TYPE
   SYNTAX      Counter64
   MAX-ACCESS  read-only
   STATUS      current
   DESCRIPTION
      "Path: swPort.performance.pppoEClient.mibCounters.d7Performance.ifInErrors

       64 bit unsigned wrappable counter."
   ::= {pr1645v2EthPortSwIPPPoEMCD7PEntry 134217728}

pr1645v2EthPortSwIPPPoEMCD7PIfInUnkwn OBJECT-TYPE
   SYNTAX      Counter64
   MAX-ACCESS  read-only
   STATUS      current
   DESCRIPTION
      "Path: swPort.performance.pppoEClient.mibCounters.d7Performance.ifInUnknownProtos

       64 bit unsigned wrappable counter."
   ::= {pr1645v2EthPortSwIPPPoEMCD7PEntry 150994944}

pr1645v2EthPortSwIPPPoEMCD7PInDropEx OBJECT-TYPE
   SYNTAX      Counter64
   MAX-ACCESS  read-only
   STATUS      current
   DESCRIPTION
      "Path: swPort.performance.pppoEClient.mibCounters.d7Performance.ifInDropLevelExceeded

       64 bit unsigned wrappable counter."
   ::= {pr1645v2EthPortSwIPPPoEMCD7PEntry 335544320}

pr1645v2EthPortSwIPPPoEMCD7PInDropNoMac OBJECT-TYPE
   SYNTAX      Counter64
   MAX-ACCESS  read-only
   STATUS      current
   DESCRIPTION
      "Path: swPort.performance.pppoEClient.mibCounters.d7Performance.fInDiscardsNoMacFit

       64 bit unsigned wrappable counter."
   ::= {pr1645v2EthPortSwIPPPoEMCD7PEntry 301989888}

pr1645v2EthPortSwIPPPoEMCD7PInDropNUCast OBJECT-TYPE
   SYNTAX      Counter64
   MAX-ACCESS  read-only
   STATUS      current
   DESCRIPTION
      "Path: swPort.performance.pppoEClient.mibCounters.d7Performance.fInDiscardsNUCast

       64 bit unsigned wrappable counter."
   ::= {pr1645v2EthPortSwIPPPoEMCD7PEntry 318767104}

pr1645v2EthPortSwIPPPoEMCD7PInDropFilter OBJECT-TYPE
   SYNTAX      Counter64
   MAX-ACCESS  read-only
   STATUS      current
   DESCRIPTION
      "Path: swPort.performance.pppoEClient.mibCounters.d7Performance.fInDiscardsFilter

       64 bit unsigned wrappable counter."
   ::= {pr1645v2EthPortSwIPPPoEMCD7PEntry 385875968}

pr1645v2EthPortSwIPPPoEMCD7PIfInBandwidth OBJECT-TYPE
   SYNTAX      Integer32
   MAX-ACCESS  read-only
   STATUS      current
   DESCRIPTION
      "Path: swPort.performance.pppoEClient.mibCounters.d7Performance.ifInBandwidth

       unit name = bps
       formula = 8 * ; 8 /"
   ::= {pr1645v2EthPortSwIPPPoEMCD7PEntry 268435456}

pr1645v2EthPortSwIPPPoEMCD7PIfOutOctets OBJECT-TYPE
   SYNTAX      Counter64
   MAX-ACCESS  read-only
   STATUS      current
   DESCRIPTION
      "Path: swPort.performance.pppoEClient.mibCounters.d7Performance.ifOutOctets

       64 bit unsigned wrappable counter."
   ::= {pr1645v2EthPortSwIPPPoEMCD7PEntry 167772160}

pr1645v2EthPortSwIPPPoEMCD7PIfOutUCPkts OBJECT-TYPE
   SYNTAX      Counter64
   MAX-ACCESS  read-only
   STATUS      current
   DESCRIPTION
      "Path: swPort.performance.pppoEClient.mibCounters.d7Performance.ifOutUcastPkts

       64 bit unsigned wrappable counter."
   ::= {pr1645v2EthPortSwIPPPoEMCD7PEntry 184549376}

pr1645v2EthPortSwIPPPoEMCD7PIfOutNUCPkts OBJECT-TYPE
   SYNTAX      Counter64
   MAX-ACCESS  read-only
   STATUS      current
   DESCRIPTION
      "Path: swPort.performance.pppoEClient.mibCounters.d7Performance.ifOutNUcastPkts

       64 bit unsigned wrappable counter."
   ::= {pr1645v2EthPortSwIPPPoEMCD7PEntry 201326592}

pr1645v2EthPortSwIPPPoEMCD7PIfOutBCPkts OBJECT-TYPE
   SYNTAX      Counter64
   MAX-ACCESS  read-only
   STATUS      current
   DESCRIPTION
      "Path: swPort.performance.pppoEClient.mibCounters.d7Performance.ifOutBcastPkts

       64 bit unsigned wrappable counter."
   ::= {pr1645v2EthPortSwIPPPoEMCD7PEntry 452984832}

pr1645v2EthPortSwIPPPoEMCD7PIfOutMCPkts OBJECT-TYPE
   SYNTAX      Counter64
   MAX-ACCESS  read-only
   STATUS      current
   DESCRIPTION
      "Path: swPort.performance.pppoEClient.mibCounters.d7Performance.ifOutMcastPkts

       64 bit unsigned wrappable counter."
   ::= {pr1645v2EthPortSwIPPPoEMCD7PEntry 469762048}

pr1645v2EthPortSwIPPPoEMCD7PIfOutDiscards OBJECT-TYPE
   SYNTAX      Counter64
   MAX-ACCESS  read-only
   STATUS      current
   DESCRIPTION
      "Path: swPort.performance.pppoEClient.mibCounters.d7Performance.ifOutDiscards

       64 bit unsigned wrappable counter."
   ::= {pr1645v2EthPortSwIPPPoEMCD7PEntry 218103808}

pr1645v2EthPortSwIPPPoEMCD7PIfOutErrors OBJECT-TYPE
   SYNTAX      Counter64
   MAX-ACCESS  read-only
   STATUS      current
   DESCRIPTION
      "Path: swPort.performance.pppoEClient.mibCounters.d7Performance.ifOutErrors

       64 bit unsigned wrappable counter."
   ::= {pr1645v2EthPortSwIPPPoEMCD7PEntry 234881024}

pr1645v2EthPortSwIPPPoEMCD7POutDropEx OBJECT-TYPE
   SYNTAX      Counter64
   MAX-ACCESS  read-only
   STATUS      current
   DESCRIPTION
      "Path: swPort.performance.pppoEClient.mibCounters.d7Performance.ifOutDropLevelExceeded

       64 bit unsigned wrappable counter."
   ::= {pr1645v2EthPortSwIPPPoEMCD7PEntry 352321536}

pr1645v2EthPortSwIPPPoEMCD7POutDropNoArp OBJECT-TYPE
   SYNTAX      Counter64
   MAX-ACCESS  read-only
   STATUS      current
   DESCRIPTION
      "Path: swPort.performance.pppoEClient.mibCounters.d7Performance.ifOutDiscardsNoArp

       64 bit unsigned wrappable counter."
   ::= {pr1645v2EthPortSwIPPPoEMCD7PEntry 369098752}

pr1645v2EthPortSwIPPPoEMCD7POutDropFilter OBJECT-TYPE
   SYNTAX      Counter64
   MAX-ACCESS  read-only
   STATUS      current
   DESCRIPTION
      "Path: swPort.performance.pppoEClient.mibCounters.d7Performance.ifOutDiscardsFilter

       64 bit unsigned wrappable counter."
   ::= {pr1645v2EthPortSwIPPPoEMCD7PEntry 402653184}

pr1645v2EthPortSwIPPPoEMCD7PIfOutBandwidth OBJECT-TYPE
   SYNTAX      Integer32
   MAX-ACCESS  read-only
   STATUS      current
   DESCRIPTION
      "Path: swPort.performance.pppoEClient.mibCounters.d7Performance.ifOutBandwidth

       unit name = bps
       formula = 8 * ; 8 /"
   ::= {pr1645v2EthPortSwIPPPoEMCD7PEntry 285212672}

pr1645v2EthPortSwIPPPoEMCD7PIfErrSec OBJECT-TYPE
   SYNTAX      Counter32
   MAX-ACCESS  read-only
   STATUS      current
   DESCRIPTION
      "Path: swPort.performance.pppoEClient.mibCounters.d7Performance.ifErrSec

       32 bit unsigned wrappable counter."
   ::= {pr1645v2EthPortSwIPPPoEMCD7PEntry 251658240}



ar1645v2EthPortSwI OBJECT IDENTIFIER ::= {r1645v2EthPortSwI 16}


ar1645v2EthPortSwIClearCounters OBJECT IDENTIFIER ::= {ar1645v2EthPortSwI 263}

ar1645v2EthPortSwIClearCountersTable OBJECT-TYPE
   SYNTAX      SEQUENCE OF Ar1645v2EthPortSwIClearCountersEntry
   MAX-ACCESS  not-accessible
   STATUS      current
   DESCRIPTION
      "reset counters"
   ::= {ar1645v2EthPortSwIClearCounters 1}

ar1645v2EthPortSwIClearCountersEntry OBJECT-TYPE
   SYNTAX      Ar1645v2EthPortSwIClearCountersEntry
   MAX-ACCESS  not-accessible
   STATUS      current
   DESCRIPTION
      ""
   INDEX      { ar1645v2EthPortSwIClearCountersGlobalIx }
   ::= {ar1645v2EthPortSwIClearCountersTable 1}

Ar1645v2EthPortSwIClearCountersEntry ::=
   SEQUENCE
      {
      ar1645v2EthPortSwIClearCountersGlobalIx
         GlobalIndex,
      ar1645v2EthPortSwIClearCountersValue
         Integer32
      }

ar1645v2EthPortSwIClearCountersGlobalIx OBJECT-TYPE
   SYNTAX      GlobalIndex
   MAX-ACCESS  not-accessible
   STATUS      current
   DESCRIPTION
      "The value of the tlsCntTreeGlobalIndex of the MANAGED OBJECT."
   ::= {ar1645v2EthPortSwIClearCountersEntry 10}

ar1645v2EthPortSwIClearCountersValue OBJECT-TYPE
   SYNTAX      Integer32
   MAX-ACCESS  read-write
   STATUS      current
   DESCRIPTION
      "Path: swPort.actions.clearCounters"
   ::= {ar1645v2EthPortSwIClearCountersEntry 2147483648}


ar1645v2EthPortSwIRestartIntf OBJECT IDENTIFIER ::= {ar1645v2EthPortSwI 67}

ar1645v2EthPortSwIRestartIntfTable OBJECT-TYPE
   SYNTAX      SEQUENCE OF Ar1645v2EthPortSwIRestartIntfEntry
   MAX-ACCESS  not-accessible
   STATUS      current
   DESCRIPTION
      "action in the debug group"
   ::= {ar1645v2EthPortSwIRestartIntf 1}

ar1645v2EthPortSwIRestartIntfEntry OBJECT-TYPE
   SYNTAX      Ar1645v2EthPortSwIRestartIntfEntry
   MAX-ACCESS  not-accessible
   STATUS      current
   DESCRIPTION
      ""
   INDEX      { ar1645v2EthPortSwIRestartIntfGlobalIx }
   ::= {ar1645v2EthPortSwIRestartIntfTable 1}

Ar1645v2EthPortSwIRestartIntfEntry ::=
   SEQUENCE
      {
      ar1645v2EthPortSwIRestartIntfGlobalIx
         GlobalIndex,
      ar1645v2EthPortSwIRestartIntfValue
         Integer32
      }

ar1645v2EthPortSwIRestartIntfGlobalIx OBJECT-TYPE
   SYNTAX      GlobalIndex
   MAX-ACCESS  not-accessible
   STATUS      current
   DESCRIPTION
      "The value of the tlsCntTreeGlobalIndex of the MANAGED OBJECT."
   ::= {ar1645v2EthPortSwIRestartIntfEntry 10}

ar1645v2EthPortSwIRestartIntfValue OBJECT-TYPE
   SYNTAX      Integer32
   MAX-ACCESS  read-write
   STATUS      current
   DESCRIPTION
      "Path: swPort.actions.restartIntf"
   ::= {ar1645v2EthPortSwIRestartIntfEntry 2147483648}


ar1645v2EthPortSwIClearOamEventLog OBJECT IDENTIFIER ::= {ar1645v2EthPortSwI 916}

ar1645v2EthPortSwIClearOamEventLogTable OBJECT-TYPE
   SYNTAX      SEQUENCE OF Ar1645v2EthPortSwIClearOamEventLogEntry
   MAX-ACCESS  not-accessible
   STATUS      current
   DESCRIPTION
      "clear the OAM event log"
   ::= {ar1645v2EthPortSwIClearOamEventLog 1}

ar1645v2EthPortSwIClearOamEventLogEntry OBJECT-TYPE
   SYNTAX      Ar1645v2EthPortSwIClearOamEventLogEntry
   MAX-ACCESS  not-accessible
   STATUS      current
   DESCRIPTION
      ""
   INDEX      { ar1645v2EthPortSwIClearOamEventLogGlobalIx }
   ::= {ar1645v2EthPortSwIClearOamEventLogTable 1}

Ar1645v2EthPortSwIClearOamEventLogEntry ::=
   SEQUENCE
      {
      ar1645v2EthPortSwIClearOamEventLogGlobalIx
         GlobalIndex,
      ar1645v2EthPortSwIClearOamEventLogValue
         Integer32
      }

ar1645v2EthPortSwIClearOamEventLogGlobalIx OBJECT-TYPE
   SYNTAX      GlobalIndex
   MAX-ACCESS  not-accessible
   STATUS      current
   DESCRIPTION
      "The value of the tlsCntTreeGlobalIndex of the MANAGED OBJECT."
   ::= {ar1645v2EthPortSwIClearOamEventLogEntry 10}

ar1645v2EthPortSwIClearOamEventLogValue OBJECT-TYPE
   SYNTAX      Integer32
   MAX-ACCESS  read-write
   STATUS      current
   DESCRIPTION
      "Path: swPort.actions.clearOamEventLog"
   ::= {ar1645v2EthPortSwIClearOamEventLogEntry 2147483648}


ar1645v2EthPortSwILoopback OBJECT IDENTIFIER ::= {ar1645v2EthPortSwI 914}

ar1645v2EthPortSwILoopbackTable OBJECT-TYPE
   SYNTAX      SEQUENCE OF Ar1645v2EthPortSwILoopbackEntry
   MAX-ACCESS  not-accessible
   STATUS      current
   DESCRIPTION
      "ethernet loopback"
   ::= {ar1645v2EthPortSwILoopback 1}

ar1645v2EthPortSwILoopbackEntry OBJECT-TYPE
   SYNTAX      Ar1645v2EthPortSwILoopbackEntry
   MAX-ACCESS  not-accessible
   STATUS      current
   DESCRIPTION
      ""
   INDEX      { ar1645v2EthPortSwILoopbackGlobalIx }
   ::= {ar1645v2EthPortSwILoopbackTable 1}

Ar1645v2EthPortSwILoopbackEntry ::=
   SEQUENCE
      {
      ar1645v2EthPortSwILoopbackGlobalIx
         GlobalIndex,
      ar1645v2EthPortSwILoopbackValue
         Integer32
      }

ar1645v2EthPortSwILoopbackGlobalIx OBJECT-TYPE
   SYNTAX      GlobalIndex
   MAX-ACCESS  not-accessible
   STATUS      current
   DESCRIPTION
      "The value of the tlsCntTreeGlobalIndex of the MANAGED OBJECT."
   ::= {ar1645v2EthPortSwILoopbackEntry 10}

ar1645v2EthPortSwILoopbackValue OBJECT-TYPE
   SYNTAX      Integer32
   MAX-ACCESS  read-write
   STATUS      current
   DESCRIPTION
      "Path: swPort.actions.loopback"
   ::= {ar1645v2EthPortSwILoopbackEntry 2147483648}


ar1645v2EthPortSwILoop OBJECT IDENTIFIER ::= {ar1645v2EthPortSwI 915}

ar1645v2EthPortSwILoopSSCTable OBJECT-TYPE
   SYNTAX      SEQUENCE OF Ar1645v2EthPortSwILoopEntry
   MAX-ACCESS  not-accessible
   STATUS      current
   DESCRIPTION
      "ethernet loopback type"
   ::= {ar1645v2EthPortSwILoop 1}

ar1645v2EthPortSwILoopEntry OBJECT-TYPE
   SYNTAX      Ar1645v2EthPortSwILoopEntry
   MAX-ACCESS  not-accessible
   STATUS      current
   DESCRIPTION
      ""
   INDEX      { ar1645v2EthPortSwILoopGlobalIx }
   ::= {ar1645v2EthPortSwILoopSSCTable 1}

Ar1645v2EthPortSwILoopEntry ::=
   SEQUENCE
      {
      ar1645v2EthPortSwILoopGlobalIx
         GlobalIndex,
      ar1645v2EthPortSwILoopAction
         INTEGER,
      ar1645v2EthPortSwILoopTime
         TimeTicks,
      ar1645v2EthPortSwILoopIntfName
         DisplayString
      }

ar1645v2EthPortSwILoopGlobalIx OBJECT-TYPE
   SYNTAX      GlobalIndex
   MAX-ACCESS  not-accessible
   STATUS      current
   DESCRIPTION
      "The value of the tlsCntTreeGlobalIndex of the MANAGED OBJECT."
   ::= {ar1645v2EthPortSwILoopEntry 10}

ar1645v2EthPortSwILoopAction OBJECT-TYPE
   SYNTAX      INTEGER
               {
               start (1),
               stop (2)
               }
   MAX-ACCESS  read-write
   STATUS      current
   DESCRIPTION
      "Path: swPort.actions.loop.action

       Possibilities:
               start   (1)
               stop   (2)"
   ::= {ar1645v2EthPortSwILoopEntry 16777216}

ar1645v2EthPortSwILoopTime OBJECT-TYPE
   SYNTAX      TimeTicks
   MAX-ACCESS  read-write
   STATUS      current
   DESCRIPTION
      "Path: swPort.actions.loop.time

       Time in centi-second."
   ::= {ar1645v2EthPortSwILoopEntry 50331648}

ar1645v2EthPortSwILoopIntfName OBJECT-TYPE
   SYNTAX      DisplayString
   MAX-ACCESS  read-write
   STATUS      current
   DESCRIPTION
      "Path: swPort.actions.loop.intfName"
   ::= {ar1645v2EthPortSwILoopEntry 67108864}


ar1645v2EthPortSwIOamRemLoopback OBJECT IDENTIFIER ::= {ar1645v2EthPortSwI 912}

ar1645v2EthPortSwIOamRemLoopbackTable OBJECT-TYPE
   SYNTAX      SEQUENCE OF Ar1645v2EthPortSwIOamRemLoopbackEntry
   MAX-ACCESS  not-accessible
   STATUS      current
   DESCRIPTION
      "OAM Remote Loopback"
   ::= {ar1645v2EthPortSwIOamRemLoopback 1}

ar1645v2EthPortSwIOamRemLoopbackEntry OBJECT-TYPE
   SYNTAX      Ar1645v2EthPortSwIOamRemLoopbackEntry
   MAX-ACCESS  not-accessible
   STATUS      current
   DESCRIPTION
      ""
   INDEX      { ar1645v2EthPortSwIOamRemLoopbackGlobalIx }
   ::= {ar1645v2EthPortSwIOamRemLoopbackTable 1}

Ar1645v2EthPortSwIOamRemLoopbackEntry ::=
   SEQUENCE
      {
      ar1645v2EthPortSwIOamRemLoopbackGlobalIx
         GlobalIndex,
      ar1645v2EthPortSwIOamRemLoopbackValue
         Integer32
      }

ar1645v2EthPortSwIOamRemLoopbackGlobalIx OBJECT-TYPE
   SYNTAX      GlobalIndex
   MAX-ACCESS  not-accessible
   STATUS      current
   DESCRIPTION
      "The value of the tlsCntTreeGlobalIndex of the MANAGED OBJECT."
   ::= {ar1645v2EthPortSwIOamRemLoopbackEntry 10}

ar1645v2EthPortSwIOamRemLoopbackValue OBJECT-TYPE
   SYNTAX      Integer32
   MAX-ACCESS  read-write
   STATUS      current
   DESCRIPTION
      "Path: swPort.actions.oamRemLoopback"
   ::= {ar1645v2EthPortSwIOamRemLoopbackEntry 2147483648}


ar1645v2EthPortSwIType OBJECT IDENTIFIER ::= {ar1645v2EthPortSwI 913}

ar1645v2EthPortSwITypeTable OBJECT-TYPE
   SYNTAX      SEQUENCE OF Ar1645v2EthPortSwITypeEntry
   MAX-ACCESS  not-accessible
   STATUS      current
   DESCRIPTION
      "OAM Remote Loopback type"
   ::= {ar1645v2EthPortSwIType 1}

ar1645v2EthPortSwITypeEntry OBJECT-TYPE
   SYNTAX      Ar1645v2EthPortSwITypeEntry
   MAX-ACCESS  not-accessible
   STATUS      current
   DESCRIPTION
      ""
   INDEX      { ar1645v2EthPortSwITypeGlobalIx }
   ::= {ar1645v2EthPortSwITypeTable 1}

Ar1645v2EthPortSwITypeEntry ::=
   SEQUENCE
      {
      ar1645v2EthPortSwITypeGlobalIx
         GlobalIndex,
      ar1645v2EthPortSwITypeValue
         INTEGER
      }

ar1645v2EthPortSwITypeGlobalIx OBJECT-TYPE
   SYNTAX      GlobalIndex
   MAX-ACCESS  not-accessible
   STATUS      current
   DESCRIPTION
      "The value of the tlsCntTreeGlobalIndex of the MANAGED OBJECT."
   ::= {ar1645v2EthPortSwITypeEntry 10}

ar1645v2EthPortSwITypeValue OBJECT-TYPE
   SYNTAX      INTEGER
               {
               start (0),
               stop (1)
               }
   MAX-ACCESS  read-write
   STATUS      current
   DESCRIPTION
      "Path: swPort.actions.type

       Possibilities:
               start   (0)
               stop   (1)"
   ::= {ar1645v2EthPortSwITypeEntry 2147483648}


ar1645v2EthPortSwISendWOL OBJECT IDENTIFIER ::= {ar1645v2EthPortSwI 333}

ar1645v2EthPortSwISendWOLTable OBJECT-TYPE
   SYNTAX      SEQUENCE OF Ar1645v2EthPortSwISendWOLEntry
   MAX-ACCESS  not-accessible
   STATUS      current
   DESCRIPTION
      "send a WakeOnLan message on this interface"
   ::= {ar1645v2EthPortSwISendWOL 1}

ar1645v2EthPortSwISendWOLEntry OBJECT-TYPE
   SYNTAX      Ar1645v2EthPortSwISendWOLEntry
   MAX-ACCESS  not-accessible
   STATUS      current
   DESCRIPTION
      ""
   INDEX      { ar1645v2EthPortSwISendWOLGlobalIx }
   ::= {ar1645v2EthPortSwISendWOLTable 1}

Ar1645v2EthPortSwISendWOLEntry ::=
   SEQUENCE
      {
      ar1645v2EthPortSwISendWOLGlobalIx
         GlobalIndex,
      ar1645v2EthPortSwISendWOLValue
         Integer32
      }

ar1645v2EthPortSwISendWOLGlobalIx OBJECT-TYPE
   SYNTAX      GlobalIndex
   MAX-ACCESS  not-accessible
   STATUS      current
   DESCRIPTION
      "The value of the tlsCntTreeGlobalIndex of the MANAGED OBJECT."
   ::= {ar1645v2EthPortSwISendWOLEntry 10}

ar1645v2EthPortSwISendWOLValue OBJECT-TYPE
   SYNTAX      Integer32
   MAX-ACCESS  read-write
   STATUS      current
   DESCRIPTION
      "Path: swPort.actions.sendWOL"
   ::= {ar1645v2EthPortSwISendWOLEntry 2147483648}


ar1645v2EthPortSwIWolInfo OBJECT IDENTIFIER ::= {ar1645v2EthPortSwI 332}

ar1645v2EthPortSwIWolInfoSSCTable OBJECT-TYPE
   SYNTAX      SEQUENCE OF Ar1645v2EthPortSwIWolInfoEntry
   MAX-ACCESS  not-accessible
   STATUS      current
   DESCRIPTION
      "content of a WakeOnLan message"
   ::= {ar1645v2EthPortSwIWolInfo 1}

ar1645v2EthPortSwIWolInfoEntry OBJECT-TYPE
   SYNTAX      Ar1645v2EthPortSwIWolInfoEntry
   MAX-ACCESS  not-accessible
   STATUS      current
   DESCRIPTION
      ""
   INDEX      { ar1645v2EthPortSwIWolInfoGlobalIx }
   ::= {ar1645v2EthPortSwIWolInfoSSCTable 1}

Ar1645v2EthPortSwIWolInfoEntry ::=
   SEQUENCE
      {
      ar1645v2EthPortSwIWolInfoGlobalIx
         GlobalIndex,
      ar1645v2EthPortSwIWolInfoTargetMAC
         OCTET STRING,
      ar1645v2EthPortSwIWolInfoPassword
         OCTET STRING
      }

ar1645v2EthPortSwIWolInfoGlobalIx OBJECT-TYPE
   SYNTAX      GlobalIndex
   MAX-ACCESS  not-accessible
   STATUS      current
   DESCRIPTION
      "The value of the tlsCntTreeGlobalIndex of the MANAGED OBJECT."
   ::= {ar1645v2EthPortSwIWolInfoEntry 10}

ar1645v2EthPortSwIWolInfoTargetMAC OBJECT-TYPE
   SYNTAX      OCTET STRING
   MAX-ACCESS  read-write
   STATUS      current
   DESCRIPTION
      "Path: swPort.actions.wolInfo.targetMAC

       MAC address."
   ::= {ar1645v2EthPortSwIWolInfoEntry 16777216}

ar1645v2EthPortSwIWolInfoPassword OBJECT-TYPE
   SYNTAX      OCTET STRING
   MAX-ACCESS  read-write
   STATUS      current
   DESCRIPTION
      "Path: swPort.actions.wolInfo.password"
   ::= {ar1645v2EthPortSwIWolInfoEntry 33554432}


ar1645v2EthPortSwIClearArpCache OBJECT IDENTIFIER ::= {ar1645v2EthPortSwI 25}

ar1645v2EthPortSwIClearArpCacheTable OBJECT-TYPE
   SYNTAX      SEQUENCE OF Ar1645v2EthPortSwIClearArpCacheEntry
   MAX-ACCESS  not-accessible
   STATUS      current
   DESCRIPTION
      "clear all dynamic enties in ARP cache table"
   ::= {ar1645v2EthPortSwIClearArpCache 1}

ar1645v2EthPortSwIClearArpCacheEntry OBJECT-TYPE
   SYNTAX      Ar1645v2EthPortSwIClearArpCacheEntry
   MAX-ACCESS  not-accessible
   STATUS      current
   DESCRIPTION
      ""
   INDEX      { ar1645v2EthPortSwIClearArpCacheGlobalIx }
   ::= {ar1645v2EthPortSwIClearArpCacheTable 1}

Ar1645v2EthPortSwIClearArpCacheEntry ::=
   SEQUENCE
      {
      ar1645v2EthPortSwIClearArpCacheGlobalIx
         GlobalIndex,
      ar1645v2EthPortSwIClearArpCacheValue
         Integer32
      }

ar1645v2EthPortSwIClearArpCacheGlobalIx OBJECT-TYPE
   SYNTAX      GlobalIndex
   MAX-ACCESS  not-accessible
   STATUS      current
   DESCRIPTION
      "The value of the tlsCntTreeGlobalIndex of the MANAGED OBJECT."
   ::= {ar1645v2EthPortSwIClearArpCacheEntry 10}

ar1645v2EthPortSwIClearArpCacheValue OBJECT-TYPE
   SYNTAX      Integer32
   MAX-ACCESS  read-write
   STATUS      current
   DESCRIPTION
      "Path: swPort.actions.clearArpCache"
   ::= {ar1645v2EthPortSwIClearArpCacheEntry 2147483648}



fr1645v2EthPortSwI OBJECT IDENTIFIER ::= {r1645v2EthPortSwI 13}


fr1645v2EthPortSwIAlarm OBJECT IDENTIFIER ::= {fr1645v2EthPortSwI 207}

fr1645v2EthPortSwIAlarmSSCTable OBJECT-TYPE
   SYNTAX      SEQUENCE OF Fr1645v2EthPortSwIAlarmEntry
   MAX-ACCESS  not-accessible
   STATUS      current
   DESCRIPTION
      "IfAlarmInfo"
   ::= {fr1645v2EthPortSwIAlarm 1}

fr1645v2EthPortSwIAlarmEntry OBJECT-TYPE
   SYNTAX      Fr1645v2EthPortSwIAlarmEntry
   MAX-ACCESS  not-accessible
   STATUS      current
   DESCRIPTION
      ""
   INDEX      { fr1645v2EthPortSwIAlarmGlobalIx }
   ::= {fr1645v2EthPortSwIAlarmSSCTable 1}

Fr1645v2EthPortSwIAlarmEntry ::=
   SEQUENCE
      {
      fr1645v2EthPortSwIAlarmGlobalIx
         GlobalIndex,
      fr1645v2EthPortSwIAlarmDiscriminator
         Integer32,
      fr1645v2EthPortSwIAlarmCurrent
         Integer32,
      fr1645v2EthPortSwIAlarmPrevious
         Integer32,
      fr1645v2EthPortSwIAlarmMask
         Integer32,
      fr1645v2EthPortSwIAlarmLevLinkDown
         Integer32,
      fr1645v2EthPortSwIAlarmLevPppoEDown
         Integer32
      }

fr1645v2EthPortSwIAlarmGlobalIx OBJECT-TYPE
   SYNTAX      GlobalIndex
   MAX-ACCESS  not-accessible
   STATUS      current
   DESCRIPTION
      "The value of the tlsCntTreeGlobalIndex of the MANAGED OBJECT."
   ::= {fr1645v2EthPortSwIAlarmEntry 10}

fr1645v2EthPortSwIAlarmDiscriminator OBJECT-TYPE
   SYNTAX      Integer32
   MAX-ACCESS  read-only
   STATUS      current
   DESCRIPTION
      "Path: swPort.alarms.alarmInfo.discriminator"
   ::= {fr1645v2EthPortSwIAlarmEntry 16777216}

fr1645v2EthPortSwIAlarmCurrent OBJECT-TYPE
   SYNTAX      Integer32
   MAX-ACCESS  read-only
   STATUS      current
   DESCRIPTION
      "Path: swPort.alarms.alarmInfo.currentAlarms

       Bit meanings:
               bit 0 = linkDown,
               bit 9 = pppoEDown"
   ::= {fr1645v2EthPortSwIAlarmEntry 33554432}

fr1645v2EthPortSwIAlarmPrevious OBJECT-TYPE
   SYNTAX      Integer32
   MAX-ACCESS  read-only
   STATUS      current
   DESCRIPTION
      "Path: swPort.alarms.alarmInfo.previousAlarms

       Bit meanings:
               bit 0 = linkDown,
               bit 9 = pppoEDown"
   ::= {fr1645v2EthPortSwIAlarmEntry 50331648}

fr1645v2EthPortSwIAlarmMask OBJECT-TYPE
   SYNTAX      Integer32
   MAX-ACCESS  read-only
   STATUS      current
   DESCRIPTION
      "Path: swPort.alarms.alarmInfo.alarmMask

       Bit meanings:
               bit 0 = linkDown,
               bit 9 = pppoEDown"
   ::= {fr1645v2EthPortSwIAlarmEntry 67108864}

fr1645v2EthPortSwIAlarmLevLinkDown OBJECT-TYPE
   SYNTAX      Integer32
   MAX-ACCESS  read-only
   STATUS      current
   DESCRIPTION
      "Path: swPort.alarms.alarmInfo.alarmLevel.linkDown"
   ::= {fr1645v2EthPortSwIAlarmEntry 83951616}

fr1645v2EthPortSwIAlarmLevPppoEDown OBJECT-TYPE
   SYNTAX      Integer32
   MAX-ACCESS  read-only
   STATUS      current
   DESCRIPTION
      "Path: swPort.alarms.alarmInfo.alarmLevel.pppoEDown"
   ::= {fr1645v2EthPortSwIAlarmEntry 84541440}


fr1645v2EthPortSwIAlarmE2 OBJECT IDENTIFIER ::= {fr1645v2EthPortSwIAlarm 2}

fr1645v2EthPortSwIAlarmE2Entry OBJECT IDENTIFIER ::= {fr1645v2EthPortSwIAlarmE2 1}

fr1645v2EthPortSwIAlarmE2LinkDown OBJECT IDENTIFIER ::= {fr1645v2EthPortSwIAlarmE2Entry 10}

fr1645v2EthPortSwIAlarmE2LinkDownPfx OBJECT IDENTIFIER ::= {fr1645v2EthPortSwIAlarmE2LinkDown 0}

fr1645v2EthPortSwIAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwInst'
                (root='router1645') has changed from the ON to the OFF state."
   ::= {fr1645v2EthPortSwIAlarmE2LinkDownPfx 1}

fr1645v2EthPortSwIAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwInst'
                (root='router1645') has changed from the OFF to the ON state."
   ::= {fr1645v2EthPortSwIAlarmE2LinkDownPfx 2}

fr1645v2EthPortSwIAlarmE2PppoEDown OBJECT IDENTIFIER ::= {fr1645v2EthPortSwIAlarmE2Entry 19}

fr1645v2EthPortSwIAlarmE2PppoEDownPfx OBJECT IDENTIFIER ::= {fr1645v2EthPortSwIAlarmE2PppoEDown 0}

fr1645v2EthPortSwIAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwInst'
                (root='router1645') has changed from the ON to the OFF state."
   ::= {fr1645v2EthPortSwIAlarmE2PppoEDownPfx 1}

fr1645v2EthPortSwIAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwInst'
                (root='router1645') has changed from the OFF to the ON state."
   ::= {fr1645v2EthPortSwIAlarmE2PppoEDownPfx 2}



END
