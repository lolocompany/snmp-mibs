OneAccess-R1646v2-2361-ShCusPr DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2ShCusPr OBJECT IDENTIFIER ::= {r1646Rootv2 2361}

r1646v2ShCusPrMOProp OBJECT-TYPE
   SYNTAX      SEQUENCE OF R1646v2ShCusPrMOPropEntry
   MAX-ACCESS  not-accessible
   STATUS      current
   DESCRIPTION
      ""
   ::= {r1646v2ShCusPr 1}

r1646v2ShCusPrMOPropEntry OBJECT-TYPE
   SYNTAX      R1646v2ShCusPrMOPropEntry
   MAX-ACCESS  not-accessible
   STATUS      current
   DESCRIPTION
      ""
   INDEX      { r1646v2ShCusPrMOPropGlobalIx }
   ::= {r1646v2ShCusPrMOProp 1}

R1646v2ShCusPrMOPropEntry ::=
   SEQUENCE
      {
      r1646v2ShCusPrMOPropPath
         ContainmentPath,
      r1646v2ShCusPrMOPropRev
         ObjectRevision,
      r1646v2ShCusPrMOPropGlobalIx
         GlobalIndex
      }

r1646v2ShCusPrMOPropPath OBJECT-TYPE
   SYNTAX      ContainmentPath
   MAX-ACCESS  read-only
   STATUS      current
   DESCRIPTION
      "Textual description of the containment tree from the instance of
       the root object down to the instance of the current object."
   ::= {r1646v2ShCusPrMOPropEntry 3}

r1646v2ShCusPrMOPropRev OBJECT-TYPE
   SYNTAX      ObjectRevision
   MAX-ACCESS  read-only
   STATUS      current
   DESCRIPTION
      "This value corresponds with the revision of the MANAGED OBJECT."
   ::= {r1646v2ShCusPrMOPropEntry 4}

r1646v2ShCusPrMOPropGlobalIx OBJECT-TYPE
   SYNTAX      GlobalIndex
   MAX-ACCESS  read-only
   STATUS      current
   DESCRIPTION
      "The value of the tlsCntTreeGlobalIndex of the MANAGED OBJECT."
   ::= {r1646v2ShCusPrMOPropEntry 10}



sr1646v2ShCusPr OBJECT IDENTIFIER ::= {r1646v2ShCusPr 14}


sr1646v2ShCusPrLineAttenuation OBJECT IDENTIFIER ::= {sr1646v2ShCusPr 8}

sr1646v2ShCusPrLineAttenuationTable OBJECT-TYPE
   SYNTAX      SEQUENCE OF Sr1646v2ShCusPrLineAttenuationEntry
   MAX-ACCESS  not-accessible
   STATUS      current
   DESCRIPTION
      "lineAttenuation"
   ::= {sr1646v2ShCusPrLineAttenuation 1}

sr1646v2ShCusPrLineAttenuationEntry OBJECT-TYPE
   SYNTAX      Sr1646v2ShCusPrLineAttenuationEntry
   MAX-ACCESS  not-accessible
   STATUS      current
   DESCRIPTION
      ""
   INDEX      { sr1646v2ShCusPrLineAttenuationGlobalIx }
   ::= {sr1646v2ShCusPrLineAttenuationTable 1}

Sr1646v2ShCusPrLineAttenuationEntry ::=
   SEQUENCE
      {
      sr1646v2ShCusPrLineAttenuationGlobalIx
         GlobalIndex,
      sr1646v2ShCusPrLineAttenuationValue
         Integer32
      }

sr1646v2ShCusPrLineAttenuationGlobalIx OBJECT-TYPE
   SYNTAX      GlobalIndex
   MAX-ACCESS  not-accessible
   STATUS      current
   DESCRIPTION
      "The value of the tlsCntTreeGlobalIndex of the MANAGED OBJECT."
   ::= {sr1646v2ShCusPrLineAttenuationEntry 10}

sr1646v2ShCusPrLineAttenuationValue OBJECT-TYPE
   SYNTAX      Integer32
   MAX-ACCESS  read-only
   STATUS      current
   DESCRIPTION
      "Path: customerLinePair.status.lineAttenuation

       unit name = dB
       formula = 10 / ; 10 *"
   ::= {sr1646v2ShCusPrLineAttenuationEntry 2147483648}


sr1646v2ShCusPrNoiseMargin OBJECT IDENTIFIER ::= {sr1646v2ShCusPr 9}

sr1646v2ShCusPrNoiseMarginTable OBJECT-TYPE
   SYNTAX      SEQUENCE OF Sr1646v2ShCusPrNoiseMarginEntry
   MAX-ACCESS  not-accessible
   STATUS      current
   DESCRIPTION
      "noiseMargin"
   ::= {sr1646v2ShCusPrNoiseMargin 1}

sr1646v2ShCusPrNoiseMarginEntry OBJECT-TYPE
   SYNTAX      Sr1646v2ShCusPrNoiseMarginEntry
   MAX-ACCESS  not-accessible
   STATUS      current
   DESCRIPTION
      ""
   INDEX      { sr1646v2ShCusPrNoiseMarginGlobalIx }
   ::= {sr1646v2ShCusPrNoiseMarginTable 1}

Sr1646v2ShCusPrNoiseMarginEntry ::=
   SEQUENCE
      {
      sr1646v2ShCusPrNoiseMarginGlobalIx
         GlobalIndex,
      sr1646v2ShCusPrNoiseMarginValue
         Integer32
      }

sr1646v2ShCusPrNoiseMarginGlobalIx OBJECT-TYPE
   SYNTAX      GlobalIndex
   MAX-ACCESS  not-accessible
   STATUS      current
   DESCRIPTION
      "The value of the tlsCntTreeGlobalIndex of the MANAGED OBJECT."
   ::= {sr1646v2ShCusPrNoiseMarginEntry 10}

sr1646v2ShCusPrNoiseMarginValue OBJECT-TYPE
   SYNTAX      Integer32
   MAX-ACCESS  read-only
   STATUS      current
   DESCRIPTION
      "Path: customerLinePair.status.noiseMargin

       unit name = dB
       formula = 10 / ; 10 *"
   ::= {sr1646v2ShCusPrNoiseMarginEntry 2147483648}


sr1646v2ShCusPrSnmpIndex OBJECT IDENTIFIER ::= {sr1646v2ShCusPr 269}

sr1646v2ShCusPrSnmpIndexTable OBJECT-TYPE
   SYNTAX      SEQUENCE OF Sr1646v2ShCusPrSnmpIndexEntry
   MAX-ACCESS  not-accessible
   STATUS      current
   DESCRIPTION
      "SNMP index assigned to this object"
   ::= {sr1646v2ShCusPrSnmpIndex 1}

sr1646v2ShCusPrSnmpIndexEntry OBJECT-TYPE
   SYNTAX      Sr1646v2ShCusPrSnmpIndexEntry
   MAX-ACCESS  not-accessible
   STATUS      current
   DESCRIPTION
      ""
   INDEX      { sr1646v2ShCusPrSnmpIndexGlobalIx }
   ::= {sr1646v2ShCusPrSnmpIndexTable 1}

Sr1646v2ShCusPrSnmpIndexEntry ::=
   SEQUENCE
      {
      sr1646v2ShCusPrSnmpIndexGlobalIx
         GlobalIndex,
      sr1646v2ShCusPrSnmpIndexValue
         Integer32
      }

sr1646v2ShCusPrSnmpIndexGlobalIx OBJECT-TYPE
   SYNTAX      GlobalIndex
   MAX-ACCESS  not-accessible
   STATUS      current
   DESCRIPTION
      "The value of the tlsCntTreeGlobalIndex of the MANAGED OBJECT."
   ::= {sr1646v2ShCusPrSnmpIndexEntry 10}

sr1646v2ShCusPrSnmpIndexValue OBJECT-TYPE
   SYNTAX      Integer32
   MAX-ACCESS  read-only
   STATUS      current
   DESCRIPTION
      "Path: customerLinePair.status.snmpIndex"
   ::= {sr1646v2ShCusPrSnmpIndexEntry 2147483648}



pr1646v2ShCusPr OBJECT IDENTIFIER ::= {r1646v2ShCusPr 12}


pr1646v2ShCusPrH2Perf OBJECT IDENTIFIER ::= {pr1646v2ShCusPr 12}

pr1646v2ShCusPrH2PerfSSCTable OBJECT-TYPE
   SYNTAX      SEQUENCE OF Pr1646v2ShCusPrH2PerfEntry
   MAX-ACCESS  not-accessible
   STATUS      current
   DESCRIPTION
      "h2Performance"
   ::= {pr1646v2ShCusPrH2Perf 1}

pr1646v2ShCusPrH2PerfEntry OBJECT-TYPE
   SYNTAX      Pr1646v2ShCusPrH2PerfEntry
   MAX-ACCESS  not-accessible
   STATUS      current
   DESCRIPTION
      ""
   INDEX      { pr1646v2ShCusPrH2PerfGlobalIx,
                pr1646v2ShCusPrH2PerfTableIx }
   ::= {pr1646v2ShCusPrH2PerfSSCTable 1}

Pr1646v2ShCusPrH2PerfEntry ::=
   SEQUENCE
      {
      pr1646v2ShCusPrH2PerfGlobalIx
         GlobalIndex,
      pr1646v2ShCusPrH2PerfTableIx
         TableIndex,
      pr1646v2ShCusPrH2PerfSysUpTime
         TimeTicks,
      pr1646v2ShCusPrH2PerfCViol
         Counter32,
      pr1646v2ShCusPrH2PerfErrSec
         TimeTicks,
      pr1646v2ShCusPrH2PerfSevErrSec
         TimeTicks,
      pr1646v2ShCusPrH2PerfUnavSec
         TimeTicks,
      pr1646v2ShCusPrH2PerfLoswSec
         TimeTicks,
      pr1646v2ShCusPrH2PerfMSec
         TimeTicks
      }

pr1646v2ShCusPrH2PerfGlobalIx OBJECT-TYPE
   SYNTAX      GlobalIndex
   MAX-ACCESS  not-accessible
   STATUS      current
   DESCRIPTION
      "The value of the tlsCntTreeGlobalIndex of the MANAGED OBJECT."
   ::= {pr1646v2ShCusPrH2PerfEntry 10}

pr1646v2ShCusPrH2PerfTableIx OBJECT-TYPE
   SYNTAX      TableIndex
   MAX-ACCESS  not-accessible
   STATUS      current
   DESCRIPTION
      ""
   ::= {pr1646v2ShCusPrH2PerfEntry 11}

pr1646v2ShCusPrH2PerfSysUpTime OBJECT-TYPE
   SYNTAX      TimeTicks
   MAX-ACCESS  read-only
   STATUS      current
   DESCRIPTION
      "Path: customerLinePair.performance.h2Performance.sysUpTime

       Time in centi-second."
   ::= {pr1646v2ShCusPrH2PerfEntry 16777216}

pr1646v2ShCusPrH2PerfCViol OBJECT-TYPE
   SYNTAX      Counter32
   MAX-ACCESS  read-only
   STATUS      current
   DESCRIPTION
      "Path: customerLinePair.performance.h2Performance.codeViolations

       32 bit unsigned wrappable counter."
   ::= {pr1646v2ShCusPrH2PerfEntry 33554432}

pr1646v2ShCusPrH2PerfErrSec OBJECT-TYPE
   SYNTAX      TimeTicks
   MAX-ACCESS  read-only
   STATUS      current
   DESCRIPTION
      "Path: customerLinePair.performance.h2Performance.errSec

       Time in centi-second."
   ::= {pr1646v2ShCusPrH2PerfEntry 50331648}

pr1646v2ShCusPrH2PerfSevErrSec OBJECT-TYPE
   SYNTAX      TimeTicks
   MAX-ACCESS  read-only
   STATUS      current
   DESCRIPTION
      "Path: customerLinePair.performance.h2Performance.sevErrSec

       Time in centi-second."
   ::= {pr1646v2ShCusPrH2PerfEntry 67108864}

pr1646v2ShCusPrH2PerfUnavSec OBJECT-TYPE
   SYNTAX      TimeTicks
   MAX-ACCESS  read-only
   STATUS      current
   DESCRIPTION
      "Path: customerLinePair.performance.h2Performance.unavailSec

       Time in centi-second."
   ::= {pr1646v2ShCusPrH2PerfEntry 83886080}

pr1646v2ShCusPrH2PerfLoswSec OBJECT-TYPE
   SYNTAX      TimeTicks
   MAX-ACCESS  read-only
   STATUS      current
   DESCRIPTION
      "Path: customerLinePair.performance.h2Performance.loswSec

       Time in centi-second."
   ::= {pr1646v2ShCusPrH2PerfEntry 100663296}

pr1646v2ShCusPrH2PerfMSec OBJECT-TYPE
   SYNTAX      TimeTicks
   MAX-ACCESS  read-only
   STATUS      current
   DESCRIPTION
      "Path: customerLinePair.performance.h2Performance.moniSec

       Time in centi-second."
   ::= {pr1646v2ShCusPrH2PerfEntry 134217728}


pr1646v2ShCusPrH24Perf OBJECT IDENTIFIER ::= {pr1646v2ShCusPr 15}

pr1646v2ShCusPrH24PerfSSCTable OBJECT-TYPE
   SYNTAX      SEQUENCE OF Pr1646v2ShCusPrH24PerfEntry
   MAX-ACCESS  not-accessible
   STATUS      current
   DESCRIPTION
      "h24Performance"
   ::= {pr1646v2ShCusPrH24Perf 1}

pr1646v2ShCusPrH24PerfEntry OBJECT-TYPE
   SYNTAX      Pr1646v2ShCusPrH24PerfEntry
   MAX-ACCESS  not-accessible
   STATUS      current
   DESCRIPTION
      ""
   INDEX      { pr1646v2ShCusPrH24PerfGlobalIx,
                pr1646v2ShCusPrH24PerfTableIx }
   ::= {pr1646v2ShCusPrH24PerfSSCTable 1}

Pr1646v2ShCusPrH24PerfEntry ::=
   SEQUENCE
      {
      pr1646v2ShCusPrH24PerfGlobalIx
         GlobalIndex,
      pr1646v2ShCusPrH24PerfTableIx
         TableIndex,
      pr1646v2ShCusPrH24PerfSysUpTime
         TimeTicks,
      pr1646v2ShCusPrH24PerfCViol
         Counter32,
      pr1646v2ShCusPrH24PerfErrSec
         TimeTicks,
      pr1646v2ShCusPrH24PerfSevErrSec
         TimeTicks,
      pr1646v2ShCusPrH24PerfUnavSec
         TimeTicks,
      pr1646v2ShCusPrH24PerfLoswSec
         TimeTicks,
      pr1646v2ShCusPrH24PerfMSec
         TimeTicks
      }

pr1646v2ShCusPrH24PerfGlobalIx OBJECT-TYPE
   SYNTAX      GlobalIndex
   MAX-ACCESS  not-accessible
   STATUS      current
   DESCRIPTION
      "The value of the tlsCntTreeGlobalIndex of the MANAGED OBJECT."
   ::= {pr1646v2ShCusPrH24PerfEntry 10}

pr1646v2ShCusPrH24PerfTableIx OBJECT-TYPE
   SYNTAX      TableIndex
   MAX-ACCESS  not-accessible
   STATUS      current
   DESCRIPTION
      ""
   ::= {pr1646v2ShCusPrH24PerfEntry 11}

pr1646v2ShCusPrH24PerfSysUpTime OBJECT-TYPE
   SYNTAX      TimeTicks
   MAX-ACCESS  read-only
   STATUS      current
   DESCRIPTION
      "Path: customerLinePair.performance.h24Performance.sysUpTime

       Time in centi-second."
   ::= {pr1646v2ShCusPrH24PerfEntry 16777216}

pr1646v2ShCusPrH24PerfCViol OBJECT-TYPE
   SYNTAX      Counter32
   MAX-ACCESS  read-only
   STATUS      current
   DESCRIPTION
      "Path: customerLinePair.performance.h24Performance.codeViolations

       32 bit unsigned wrappable counter."
   ::= {pr1646v2ShCusPrH24PerfEntry 33554432}

pr1646v2ShCusPrH24PerfErrSec OBJECT-TYPE
   SYNTAX      TimeTicks
   MAX-ACCESS  read-only
   STATUS      current
   DESCRIPTION
      "Path: customerLinePair.performance.h24Performance.errSec

       Time in centi-second."
   ::= {pr1646v2ShCusPrH24PerfEntry 50331648}

pr1646v2ShCusPrH24PerfSevErrSec OBJECT-TYPE
   SYNTAX      TimeTicks
   MAX-ACCESS  read-only
   STATUS      current
   DESCRIPTION
      "Path: customerLinePair.performance.h24Performance.sevErrSec

       Time in centi-second."
   ::= {pr1646v2ShCusPrH24PerfEntry 67108864}

pr1646v2ShCusPrH24PerfUnavSec OBJECT-TYPE
   SYNTAX      TimeTicks
   MAX-ACCESS  read-only
   STATUS      current
   DESCRIPTION
      "Path: customerLinePair.performance.h24Performance.unavailSec

       Time in centi-second."
   ::= {pr1646v2ShCusPrH24PerfEntry 83886080}

pr1646v2ShCusPrH24PerfLoswSec OBJECT-TYPE
   SYNTAX      TimeTicks
   MAX-ACCESS  read-only
   STATUS      current
   DESCRIPTION
      "Path: customerLinePair.performance.h24Performance.loswSec

       Time in centi-second."
   ::= {pr1646v2ShCusPrH24PerfEntry 100663296}

pr1646v2ShCusPrH24PerfMSec OBJECT-TYPE
   SYNTAX      TimeTicks
   MAX-ACCESS  read-only
   STATUS      current
   DESCRIPTION
      "Path: customerLinePair.performance.h24Performance.moniSec

       Time in centi-second."
   ::= {pr1646v2ShCusPrH24PerfEntry 134217728}


pr1646v2ShCusPrD7Perf OBJECT IDENTIFIER ::= {pr1646v2ShCusPr 21}

pr1646v2ShCusPrD7PerfSSCTable OBJECT-TYPE
   SYNTAX      SEQUENCE OF Pr1646v2ShCusPrD7PerfEntry
   MAX-ACCESS  not-accessible
   STATUS      current
   DESCRIPTION
      "d7Performance"
   ::= {pr1646v2ShCusPrD7Perf 1}

pr1646v2ShCusPrD7PerfEntry OBJECT-TYPE
   SYNTAX      Pr1646v2ShCusPrD7PerfEntry
   MAX-ACCESS  not-accessible
   STATUS      current
   DESCRIPTION
      ""
   INDEX      { pr1646v2ShCusPrD7PerfGlobalIx,
                pr1646v2ShCusPrD7PerfTableIx }
   ::= {pr1646v2ShCusPrD7PerfSSCTable 1}

Pr1646v2ShCusPrD7PerfEntry ::=
   SEQUENCE
      {
      pr1646v2ShCusPrD7PerfGlobalIx
         GlobalIndex,
      pr1646v2ShCusPrD7PerfTableIx
         TableIndex,
      pr1646v2ShCusPrD7PerfSysUpTime
         TimeTicks,
      pr1646v2ShCusPrD7PerfCViol
         Counter32,
      pr1646v2ShCusPrD7PerfErrSec
         TimeTicks,
      pr1646v2ShCusPrD7PerfSevErrSec
         TimeTicks,
      pr1646v2ShCusPrD7PerfUnavSec
         TimeTicks,
      pr1646v2ShCusPrD7PerfLoswSec
         TimeTicks,
      pr1646v2ShCusPrD7PerfMSec
         TimeTicks
      }

pr1646v2ShCusPrD7PerfGlobalIx OBJECT-TYPE
   SYNTAX      GlobalIndex
   MAX-ACCESS  not-accessible
   STATUS      current
   DESCRIPTION
      "The value of the tlsCntTreeGlobalIndex of the MANAGED OBJECT."
   ::= {pr1646v2ShCusPrD7PerfEntry 10}

pr1646v2ShCusPrD7PerfTableIx OBJECT-TYPE
   SYNTAX      TableIndex
   MAX-ACCESS  not-accessible
   STATUS      current
   DESCRIPTION
      ""
   ::= {pr1646v2ShCusPrD7PerfEntry 11}

pr1646v2ShCusPrD7PerfSysUpTime OBJECT-TYPE
   SYNTAX      TimeTicks
   MAX-ACCESS  read-only
   STATUS      current
   DESCRIPTION
      "Path: customerLinePair.performance.d7Performance.sysUpTime

       Time in centi-second."
   ::= {pr1646v2ShCusPrD7PerfEntry 16777216}

pr1646v2ShCusPrD7PerfCViol OBJECT-TYPE
   SYNTAX      Counter32
   MAX-ACCESS  read-only
   STATUS      current
   DESCRIPTION
      "Path: customerLinePair.performance.d7Performance.codeViolations

       32 bit unsigned wrappable counter."
   ::= {pr1646v2ShCusPrD7PerfEntry 33554432}

pr1646v2ShCusPrD7PerfErrSec OBJECT-TYPE
   SYNTAX      TimeTicks
   MAX-ACCESS  read-only
   STATUS      current
   DESCRIPTION
      "Path: customerLinePair.performance.d7Performance.errSec

       Time in centi-second."
   ::= {pr1646v2ShCusPrD7PerfEntry 50331648}

pr1646v2ShCusPrD7PerfSevErrSec OBJECT-TYPE
   SYNTAX      TimeTicks
   MAX-ACCESS  read-only
   STATUS      current
   DESCRIPTION
      "Path: customerLinePair.performance.d7Performance.sevErrSec

       Time in centi-second."
   ::= {pr1646v2ShCusPrD7PerfEntry 67108864}

pr1646v2ShCusPrD7PerfUnavSec OBJECT-TYPE
   SYNTAX      TimeTicks
   MAX-ACCESS  read-only
   STATUS      current
   DESCRIPTION
      "Path: customerLinePair.performance.d7Performance.unavailSec

       Time in centi-second."
   ::= {pr1646v2ShCusPrD7PerfEntry 83886080}

pr1646v2ShCusPrD7PerfLoswSec OBJECT-TYPE
   SYNTAX      TimeTicks
   MAX-ACCESS  read-only
   STATUS      current
   DESCRIPTION
      "Path: customerLinePair.performance.d7Performance.loswSec

       Time in centi-second."
   ::= {pr1646v2ShCusPrD7PerfEntry 100663296}

pr1646v2ShCusPrD7PerfMSec OBJECT-TYPE
   SYNTAX      TimeTicks
   MAX-ACCESS  read-only
   STATUS      current
   DESCRIPTION
      "Path: customerLinePair.performance.d7Performance.moniSec

       Time in centi-second."
   ::= {pr1646v2ShCusPrD7PerfEntry 134217728}


pr1646v2ShCusPrPerf OBJECT IDENTIFIER ::= {pr1646v2ShCusPr 26}

pr1646v2ShCusPrPerfSSCTable OBJECT-TYPE
   SYNTAX      SEQUENCE OF Pr1646v2ShCusPrPerfEntry
   MAX-ACCESS  not-accessible
   STATUS      current
   DESCRIPTION
      "linePerformance"
   ::= {pr1646v2ShCusPrPerf 1}

pr1646v2ShCusPrPerfEntry OBJECT-TYPE
   SYNTAX      Pr1646v2ShCusPrPerfEntry
   MAX-ACCESS  not-accessible
   STATUS      current
   DESCRIPTION
      ""
   INDEX      { pr1646v2ShCusPrPerfGlobalIx }
   ::= {pr1646v2ShCusPrPerfSSCTable 1}

Pr1646v2ShCusPrPerfEntry ::=
   SEQUENCE
      {
      pr1646v2ShCusPrPerfGlobalIx
         GlobalIndex,
      pr1646v2ShCusPrPerfCViol
         Counter32,
      pr1646v2ShCusPrPerfErrSec
         TimeTicks,
      pr1646v2ShCusPrPerfSevErrSec
         TimeTicks,
      pr1646v2ShCusPrPerfUnavSec
         TimeTicks,
      pr1646v2ShCusPrPerfLoswSec
         TimeTicks
      }

pr1646v2ShCusPrPerfGlobalIx OBJECT-TYPE
   SYNTAX      GlobalIndex
   MAX-ACCESS  not-accessible
   STATUS      current
   DESCRIPTION
      "The value of the tlsCntTreeGlobalIndex of the MANAGED OBJECT."
   ::= {pr1646v2ShCusPrPerfEntry 10}

pr1646v2ShCusPrPerfCViol OBJECT-TYPE
   SYNTAX      Counter32
   MAX-ACCESS  read-only
   STATUS      current
   DESCRIPTION
      "Path: customerLinePair.performance.performance.codeViolations

       32 bit unsigned wrappable counter."
   ::= {pr1646v2ShCusPrPerfEntry 16777216}

pr1646v2ShCusPrPerfErrSec OBJECT-TYPE
   SYNTAX      TimeTicks
   MAX-ACCESS  read-only
   STATUS      current
   DESCRIPTION
      "Path: customerLinePair.performance.performance.errSec

       Time in centi-second."
   ::= {pr1646v2ShCusPrPerfEntry 33554432}

pr1646v2ShCusPrPerfSevErrSec OBJECT-TYPE
   SYNTAX      TimeTicks
   MAX-ACCESS  read-only
   STATUS      current
   DESCRIPTION
      "Path: customerLinePair.performance.performance.sevErrSec

       Time in centi-second."
   ::= {pr1646v2ShCusPrPerfEntry 50331648}

pr1646v2ShCusPrPerfUnavSec OBJECT-TYPE
   SYNTAX      TimeTicks
   MAX-ACCESS  read-only
   STATUS      current
   DESCRIPTION
      "Path: customerLinePair.performance.performance.unavailSec

       Time in centi-second."
   ::= {pr1646v2ShCusPrPerfEntry 67108864}

pr1646v2ShCusPrPerfLoswSec OBJECT-TYPE
   SYNTAX      TimeTicks
   MAX-ACCESS  read-only
   STATUS      current
   DESCRIPTION
      "Path: customerLinePair.performance.performance.loswSec

       Time in centi-second."
   ::= {pr1646v2ShCusPrPerfEntry 83886080}


pr1646v2ShCusPrH2Params OBJECT IDENTIFIER ::= {pr1646v2ShCusPr 11}

pr1646v2ShCusPrH2ParamsSSCTable OBJECT-TYPE
   SYNTAX      SEQUENCE OF Pr1646v2ShCusPrH2ParamsEntry
   MAX-ACCESS  not-accessible
   STATUS      current
   DESCRIPTION
      "h2LineParameters"
   ::= {pr1646v2ShCusPrH2Params 1}

pr1646v2ShCusPrH2ParamsEntry OBJECT-TYPE
   SYNTAX      Pr1646v2ShCusPrH2ParamsEntry
   MAX-ACCESS  not-accessible
   STATUS      current
   DESCRIPTION
      ""
   INDEX      { pr1646v2ShCusPrH2ParamsGlobalIx,
                pr1646v2ShCusPrH2ParamsTableIx }
   ::= {pr1646v2ShCusPrH2ParamsSSCTable 1}

Pr1646v2ShCusPrH2ParamsEntry ::=
   SEQUENCE
      {
      pr1646v2ShCusPrH2ParamsGlobalIx
         GlobalIndex,
      pr1646v2ShCusPrH2ParamsTableIx
         TableIndex,
      pr1646v2ShCusPrH2ParamsSysUpTime
         TimeTicks,
      pr1646v2ShCusPrH2ParamsLineAttMin
         Integer32,
      pr1646v2ShCusPrH2ParamsLineAttAvrg
         Integer32,
      pr1646v2ShCusPrH2ParamsLineAttMax
         Integer32,
      pr1646v2ShCusPrH2ParamsNmMin
         Integer32,
      pr1646v2ShCusPrH2ParamsNmAvrg
         Integer32,
      pr1646v2ShCusPrH2ParamsNmMax
         Integer32
      }

pr1646v2ShCusPrH2ParamsGlobalIx OBJECT-TYPE
   SYNTAX      GlobalIndex
   MAX-ACCESS  not-accessible
   STATUS      current
   DESCRIPTION
      "The value of the tlsCntTreeGlobalIndex of the MANAGED OBJECT."
   ::= {pr1646v2ShCusPrH2ParamsEntry 10}

pr1646v2ShCusPrH2ParamsTableIx OBJECT-TYPE
   SYNTAX      TableIndex
   MAX-ACCESS  not-accessible
   STATUS      current
   DESCRIPTION
      ""
   ::= {pr1646v2ShCusPrH2ParamsEntry 11}

pr1646v2ShCusPrH2ParamsSysUpTime OBJECT-TYPE
   SYNTAX      TimeTicks
   MAX-ACCESS  read-only
   STATUS      current
   DESCRIPTION
      "Path: customerLinePair.performance.h2LineParameters.sysUpTime

       Time in centi-second."
   ::= {pr1646v2ShCusPrH2ParamsEntry 16777216}

pr1646v2ShCusPrH2ParamsLineAttMin OBJECT-TYPE
   SYNTAX      Integer32
   MAX-ACCESS  read-only
   STATUS      current
   DESCRIPTION
      "Path: customerLinePair.performance.h2LineParameters.lineAttenuationMin

       unit name = dB
       formula = 10 / ; 10 *"
   ::= {pr1646v2ShCusPrH2ParamsEntry 33554432}

pr1646v2ShCusPrH2ParamsLineAttAvrg OBJECT-TYPE
   SYNTAX      Integer32
   MAX-ACCESS  read-only
   STATUS      current
   DESCRIPTION
      "Path: customerLinePair.performance.h2LineParameters.lineAttenuationAvrg

       unit name = dB
       formula = 10 / ; 10 *"
   ::= {pr1646v2ShCusPrH2ParamsEntry 50331648}

pr1646v2ShCusPrH2ParamsLineAttMax OBJECT-TYPE
   SYNTAX      Integer32
   MAX-ACCESS  read-only
   STATUS      current
   DESCRIPTION
      "Path: customerLinePair.performance.h2LineParameters.lineAttenuationMax

       unit name = dB
       formula = 10 / ; 10 *"
   ::= {pr1646v2ShCusPrH2ParamsEntry 67108864}

pr1646v2ShCusPrH2ParamsNmMin OBJECT-TYPE
   SYNTAX      Integer32
   MAX-ACCESS  read-only
   STATUS      current
   DESCRIPTION
      "Path: customerLinePair.performance.h2LineParameters.noiseMarginMin

       unit name = dB
       formula = 10 / ; 10 *"
   ::= {pr1646v2ShCusPrH2ParamsEntry 83886080}

pr1646v2ShCusPrH2ParamsNmAvrg OBJECT-TYPE
   SYNTAX      Integer32
   MAX-ACCESS  read-only
   STATUS      current
   DESCRIPTION
      "Path: customerLinePair.performance.h2LineParameters.noiseMarginAvrg

       unit name = dB
       formula = 10 / ; 10 *"
   ::= {pr1646v2ShCusPrH2ParamsEntry 100663296}

pr1646v2ShCusPrH2ParamsNmMax OBJECT-TYPE
   SYNTAX      Integer32
   MAX-ACCESS  read-only
   STATUS      current
   DESCRIPTION
      "Path: customerLinePair.performance.h2LineParameters.noiseMarginMax

       unit name = dB
       formula = 10 / ; 10 *"
   ::= {pr1646v2ShCusPrH2ParamsEntry 117440512}


pr1646v2ShCusPrH24Params OBJECT IDENTIFIER ::= {pr1646v2ShCusPr 14}

pr1646v2ShCusPrH24ParamsSSCTable OBJECT-TYPE
   SYNTAX      SEQUENCE OF Pr1646v2ShCusPrH24ParamsEntry
   MAX-ACCESS  not-accessible
   STATUS      current
   DESCRIPTION
      "h24LineParameters"
   ::= {pr1646v2ShCusPrH24Params 1}

pr1646v2ShCusPrH24ParamsEntry OBJECT-TYPE
   SYNTAX      Pr1646v2ShCusPrH24ParamsEntry
   MAX-ACCESS  not-accessible
   STATUS      current
   DESCRIPTION
      ""
   INDEX      { pr1646v2ShCusPrH24ParamsGlobalIx,
                pr1646v2ShCusPrH24ParamsTableIx }
   ::= {pr1646v2ShCusPrH24ParamsSSCTable 1}

Pr1646v2ShCusPrH24ParamsEntry ::=
   SEQUENCE
      {
      pr1646v2ShCusPrH24ParamsGlobalIx
         GlobalIndex,
      pr1646v2ShCusPrH24ParamsTableIx
         TableIndex,
      pr1646v2ShCusPrH24ParamsSysUpTime
         TimeTicks,
      pr1646v2ShCusPrH24ParamsLineAttMin
         Integer32,
      pr1646v2ShCusPrH24ParamsLineAttAvrg
         Integer32,
      pr1646v2ShCusPrH24ParamsLineAttMax
         Integer32,
      pr1646v2ShCusPrH24ParamsNmMin
         Integer32,
      pr1646v2ShCusPrH24ParamsNmAvrg
         Integer32,
      pr1646v2ShCusPrH24ParamsNmMax
         Integer32
      }

pr1646v2ShCusPrH24ParamsGlobalIx OBJECT-TYPE
   SYNTAX      GlobalIndex
   MAX-ACCESS  not-accessible
   STATUS      current
   DESCRIPTION
      "The value of the tlsCntTreeGlobalIndex of the MANAGED OBJECT."
   ::= {pr1646v2ShCusPrH24ParamsEntry 10}

pr1646v2ShCusPrH24ParamsTableIx OBJECT-TYPE
   SYNTAX      TableIndex
   MAX-ACCESS  not-accessible
   STATUS      current
   DESCRIPTION
      ""
   ::= {pr1646v2ShCusPrH24ParamsEntry 11}

pr1646v2ShCusPrH24ParamsSysUpTime OBJECT-TYPE
   SYNTAX      TimeTicks
   MAX-ACCESS  read-only
   STATUS      current
   DESCRIPTION
      "Path: customerLinePair.performance.h24LineParameters.sysUpTime

       Time in centi-second."
   ::= {pr1646v2ShCusPrH24ParamsEntry 16777216}

pr1646v2ShCusPrH24ParamsLineAttMin OBJECT-TYPE
   SYNTAX      Integer32
   MAX-ACCESS  read-only
   STATUS      current
   DESCRIPTION
      "Path: customerLinePair.performance.h24LineParameters.lineAttenuationMin

       unit name = dB
       formula = 10 / ; 10 *"
   ::= {pr1646v2ShCusPrH24ParamsEntry 33554432}

pr1646v2ShCusPrH24ParamsLineAttAvrg OBJECT-TYPE
   SYNTAX      Integer32
   MAX-ACCESS  read-only
   STATUS      current
   DESCRIPTION
      "Path: customerLinePair.performance.h24LineParameters.lineAttenuationAvrg

       unit name = dB
       formula = 10 / ; 10 *"
   ::= {pr1646v2ShCusPrH24ParamsEntry 50331648}

pr1646v2ShCusPrH24ParamsLineAttMax OBJECT-TYPE
   SYNTAX      Integer32
   MAX-ACCESS  read-only
   STATUS      current
   DESCRIPTION
      "Path: customerLinePair.performance.h24LineParameters.lineAttenuationMax

       unit name = dB
       formula = 10 / ; 10 *"
   ::= {pr1646v2ShCusPrH24ParamsEntry 67108864}

pr1646v2ShCusPrH24ParamsNmMin OBJECT-TYPE
   SYNTAX      Integer32
   MAX-ACCESS  read-only
   STATUS      current
   DESCRIPTION
      "Path: customerLinePair.performance.h24LineParameters.noiseMarginMin

       unit name = dB
       formula = 10 / ; 10 *"
   ::= {pr1646v2ShCusPrH24ParamsEntry 83886080}

pr1646v2ShCusPrH24ParamsNmAvrg OBJECT-TYPE
   SYNTAX      Integer32
   MAX-ACCESS  read-only
   STATUS      current
   DESCRIPTION
      "Path: customerLinePair.performance.h24LineParameters.noiseMarginAvrg

       unit name = dB
       formula = 10 / ; 10 *"
   ::= {pr1646v2ShCusPrH24ParamsEntry 100663296}

pr1646v2ShCusPrH24ParamsNmMax OBJECT-TYPE
   SYNTAX      Integer32
   MAX-ACCESS  read-only
   STATUS      current
   DESCRIPTION
      "Path: customerLinePair.performance.h24LineParameters.noiseMarginMax

       unit name = dB
       formula = 10 / ; 10 *"
   ::= {pr1646v2ShCusPrH24ParamsEntry 117440512}


pr1646v2ShCusPrD7Params OBJECT IDENTIFIER ::= {pr1646v2ShCusPr 17}

pr1646v2ShCusPrD7ParamsSSCTable OBJECT-TYPE
   SYNTAX      SEQUENCE OF Pr1646v2ShCusPrD7ParamsEntry
   MAX-ACCESS  not-accessible
   STATUS      current
   DESCRIPTION
      "d7LineParameters"
   ::= {pr1646v2ShCusPrD7Params 1}

pr1646v2ShCusPrD7ParamsEntry OBJECT-TYPE
   SYNTAX      Pr1646v2ShCusPrD7ParamsEntry
   MAX-ACCESS  not-accessible
   STATUS      current
   DESCRIPTION
      ""
   INDEX      { pr1646v2ShCusPrD7ParamsGlobalIx,
                pr1646v2ShCusPrD7ParamsTableIx }
   ::= {pr1646v2ShCusPrD7ParamsSSCTable 1}

Pr1646v2ShCusPrD7ParamsEntry ::=
   SEQUENCE
      {
      pr1646v2ShCusPrD7ParamsGlobalIx
         GlobalIndex,
      pr1646v2ShCusPrD7ParamsTableIx
         TableIndex,
      pr1646v2ShCusPrD7ParamsSysUpTime
         TimeTicks,
      pr1646v2ShCusPrD7ParamsLineAttMin
         Integer32,
      pr1646v2ShCusPrD7ParamsLineAttAvrg
         Integer32,
      pr1646v2ShCusPrD7ParamsLineAttMax
         Integer32,
      pr1646v2ShCusPrD7ParamsNmMin
         Integer32,
      pr1646v2ShCusPrD7ParamsNmAvrg
         Integer32,
      pr1646v2ShCusPrD7ParamsNmMax
         Integer32
      }

pr1646v2ShCusPrD7ParamsGlobalIx OBJECT-TYPE
   SYNTAX      GlobalIndex
   MAX-ACCESS  not-accessible
   STATUS      current
   DESCRIPTION
      "The value of the tlsCntTreeGlobalIndex of the MANAGED OBJECT."
   ::= {pr1646v2ShCusPrD7ParamsEntry 10}

pr1646v2ShCusPrD7ParamsTableIx OBJECT-TYPE
   SYNTAX      TableIndex
   MAX-ACCESS  not-accessible
   STATUS      current
   DESCRIPTION
      ""
   ::= {pr1646v2ShCusPrD7ParamsEntry 11}

pr1646v2ShCusPrD7ParamsSysUpTime OBJECT-TYPE
   SYNTAX      TimeTicks
   MAX-ACCESS  read-only
   STATUS      current
   DESCRIPTION
      "Path: customerLinePair.performance.d7LineParameters.sysUpTime

       Time in centi-second."
   ::= {pr1646v2ShCusPrD7ParamsEntry 16777216}

pr1646v2ShCusPrD7ParamsLineAttMin OBJECT-TYPE
   SYNTAX      Integer32
   MAX-ACCESS  read-only
   STATUS      current
   DESCRIPTION
      "Path: customerLinePair.performance.d7LineParameters.lineAttenuationMin

       unit name = dB
       formula = 10 / ; 10 *"
   ::= {pr1646v2ShCusPrD7ParamsEntry 33554432}

pr1646v2ShCusPrD7ParamsLineAttAvrg OBJECT-TYPE
   SYNTAX      Integer32
   MAX-ACCESS  read-only
   STATUS      current
   DESCRIPTION
      "Path: customerLinePair.performance.d7LineParameters.lineAttenuationAvrg

       unit name = dB
       formula = 10 / ; 10 *"
   ::= {pr1646v2ShCusPrD7ParamsEntry 50331648}

pr1646v2ShCusPrD7ParamsLineAttMax OBJECT-TYPE
   SYNTAX      Integer32
   MAX-ACCESS  read-only
   STATUS      current
   DESCRIPTION
      "Path: customerLinePair.performance.d7LineParameters.lineAttenuationMax

       unit name = dB
       formula = 10 / ; 10 *"
   ::= {pr1646v2ShCusPrD7ParamsEntry 67108864}

pr1646v2ShCusPrD7ParamsNmMin OBJECT-TYPE
   SYNTAX      Integer32
   MAX-ACCESS  read-only
   STATUS      current
   DESCRIPTION
      "Path: customerLinePair.performance.d7LineParameters.noiseMarginMin

       unit name = dB
       formula = 10 / ; 10 *"
   ::= {pr1646v2ShCusPrD7ParamsEntry 83886080}

pr1646v2ShCusPrD7ParamsNmAvrg OBJECT-TYPE
   SYNTAX      Integer32
   MAX-ACCESS  read-only
   STATUS      current
   DESCRIPTION
      "Path: customerLinePair.performance.d7LineParameters.noiseMarginAvrg

       unit name = dB
       formula = 10 / ; 10 *"
   ::= {pr1646v2ShCusPrD7ParamsEntry 100663296}

pr1646v2ShCusPrD7ParamsNmMax OBJECT-TYPE
   SYNTAX      Integer32
   MAX-ACCESS  read-only
   STATUS      current
   DESCRIPTION
      "Path: customerLinePair.performance.d7LineParameters.noiseMarginMax

       unit name = dB
       formula = 10 / ; 10 *"
   ::= {pr1646v2ShCusPrD7ParamsEntry 117440512}


pr1646v2ShCusPrParams OBJECT IDENTIFIER ::= {pr1646v2ShCusPr 22}

pr1646v2ShCusPrParamsSSCTable OBJECT-TYPE
   SYNTAX      SEQUENCE OF Pr1646v2ShCusPrParamsEntry
   MAX-ACCESS  not-accessible
   STATUS      current
   DESCRIPTION
      "lineParameters"
   ::= {pr1646v2ShCusPrParams 1}

pr1646v2ShCusPrParamsEntry OBJECT-TYPE
   SYNTAX      Pr1646v2ShCusPrParamsEntry
   MAX-ACCESS  not-accessible
   STATUS      current
   DESCRIPTION
      ""
   INDEX      { pr1646v2ShCusPrParamsGlobalIx }
   ::= {pr1646v2ShCusPrParamsSSCTable 1}

Pr1646v2ShCusPrParamsEntry ::=
   SEQUENCE
      {
      pr1646v2ShCusPrParamsGlobalIx
         GlobalIndex,
      pr1646v2ShCusPrParamsLineAtt
         Integer32,
      pr1646v2ShCusPrParamsNm
         Integer32
      }

pr1646v2ShCusPrParamsGlobalIx OBJECT-TYPE
   SYNTAX      GlobalIndex
   MAX-ACCESS  not-accessible
   STATUS      current
   DESCRIPTION
      "The value of the tlsCntTreeGlobalIndex of the MANAGED OBJECT."
   ::= {pr1646v2ShCusPrParamsEntry 10}

pr1646v2ShCusPrParamsLineAtt OBJECT-TYPE
   SYNTAX      Integer32
   MAX-ACCESS  read-only
   STATUS      current
   DESCRIPTION
      "Path: customerLinePair.performance.lineParameters.lineAttenuation

       unit name = dB
       formula = 10 / ; 10 *"
   ::= {pr1646v2ShCusPrParamsEntry 16777216}

pr1646v2ShCusPrParamsNm OBJECT-TYPE
   SYNTAX      Integer32
   MAX-ACCESS  read-only
   STATUS      current
   DESCRIPTION
      "Path: customerLinePair.performance.lineParameters.noiseMargin

       unit name = dB
       formula = 10 / ; 10 *"
   ::= {pr1646v2ShCusPrParamsEntry 33554432}



ar1646v2ShCusPr OBJECT IDENTIFIER ::= {r1646v2ShCusPr 16}


ar1646v2ShCusPrClearCounters OBJECT IDENTIFIER ::= {ar1646v2ShCusPr 263}

ar1646v2ShCusPrClearCountersTable OBJECT-TYPE
   SYNTAX      SEQUENCE OF Ar1646v2ShCusPrClearCountersEntry
   MAX-ACCESS  not-accessible
   STATUS      current
   DESCRIPTION
      "reset counters"
   ::= {ar1646v2ShCusPrClearCounters 1}

ar1646v2ShCusPrClearCountersEntry OBJECT-TYPE
   SYNTAX      Ar1646v2ShCusPrClearCountersEntry
   MAX-ACCESS  not-accessible
   STATUS      current
   DESCRIPTION
      ""
   INDEX      { ar1646v2ShCusPrClearCountersGlobalIx }
   ::= {ar1646v2ShCusPrClearCountersTable 1}

Ar1646v2ShCusPrClearCountersEntry ::=
   SEQUENCE
      {
      ar1646v2ShCusPrClearCountersGlobalIx
         GlobalIndex,
      ar1646v2ShCusPrClearCountersValue
         Integer32
      }

ar1646v2ShCusPrClearCountersGlobalIx OBJECT-TYPE
   SYNTAX      GlobalIndex
   MAX-ACCESS  not-accessible
   STATUS      current
   DESCRIPTION
      "The value of the tlsCntTreeGlobalIndex of the MANAGED OBJECT."
   ::= {ar1646v2ShCusPrClearCountersEntry 10}

ar1646v2ShCusPrClearCountersValue OBJECT-TYPE
   SYNTAX      Integer32
   MAX-ACCESS  read-write
   STATUS      current
   DESCRIPTION
      "Path: customerLinePair.actions.clearCounters"
   ::= {ar1646v2ShCusPrClearCountersEntry 2147483648}



fr1646v2ShCusPr OBJECT IDENTIFIER ::= {r1646v2ShCusPr 13}


fr1646v2ShCusPrAlInfo OBJECT IDENTIFIER ::= {fr1646v2ShCusPr 202}

fr1646v2ShCusPrAlInfoSSCTable OBJECT-TYPE
   SYNTAX      SEQUENCE OF Fr1646v2ShCusPrAlInfoEntry
   MAX-ACCESS  not-accessible
   STATUS      current
   DESCRIPTION
      "linePairAlarmInfo"
   ::= {fr1646v2ShCusPrAlInfo 1}

fr1646v2ShCusPrAlInfoEntry OBJECT-TYPE
   SYNTAX      Fr1646v2ShCusPrAlInfoEntry
   MAX-ACCESS  not-accessible
   STATUS      current
   DESCRIPTION
      ""
   INDEX      { fr1646v2ShCusPrAlInfoGlobalIx }
   ::= {fr1646v2ShCusPrAlInfoSSCTable 1}

Fr1646v2ShCusPrAlInfoEntry ::=
   SEQUENCE
      {
      fr1646v2ShCusPrAlInfoGlobalIx
         GlobalIndex,
      fr1646v2ShCusPrAlInfoDiscr
         Integer32,
      fr1646v2ShCusPrAlInfoCurrAlms
         Integer32,
      fr1646v2ShCusPrAlInfoPrevAlms
         Integer32,
      fr1646v2ShCusPrAlInfoAlMask
         Integer32,
      fr1646v2ShCusPrAlInfoAlLvlLpatt
         Integer32,
      fr1646v2ShCusPrAlInfoAlLvlNm
         Integer32,
      fr1646v2ShCusPrAlInfoAlLvlEsrExc
         Integer32,
      fr1646v2ShCusPrAlInfoAlLvlSesrExc
         Integer32,
      fr1646v2ShCusPrAlInfoAlLvlBberExc
         Integer32
      }

fr1646v2ShCusPrAlInfoGlobalIx OBJECT-TYPE
   SYNTAX      GlobalIndex
   MAX-ACCESS  not-accessible
   STATUS      current
   DESCRIPTION
      "The value of the tlsCntTreeGlobalIndex of the MANAGED OBJECT."
   ::= {fr1646v2ShCusPrAlInfoEntry 10}

fr1646v2ShCusPrAlInfoDiscr OBJECT-TYPE
   SYNTAX      Integer32
   MAX-ACCESS  read-only
   STATUS      current
   DESCRIPTION
      "Path: customerLinePair.alarms.alarmInfo.discriminator"
   ::= {fr1646v2ShCusPrAlInfoEntry 16777216}

fr1646v2ShCusPrAlInfoCurrAlms OBJECT-TYPE
   SYNTAX      Integer32
   MAX-ACCESS  read-only
   STATUS      current
   DESCRIPTION
      "Path: customerLinePair.alarms.alarmInfo.currentAlarms

       Bit meanings:
               bit 1 = lineAttenuation,
               bit 2 = noiseMargin,
               bit 3 = errSecRatioExceeded,
               bit 4 = sevErrSecRatioExceeded,
               bit 5 = bBErrRatioExceeded"
   ::= {fr1646v2ShCusPrAlInfoEntry 33554432}

fr1646v2ShCusPrAlInfoPrevAlms OBJECT-TYPE
   SYNTAX      Integer32
   MAX-ACCESS  read-only
   STATUS      current
   DESCRIPTION
      "Path: customerLinePair.alarms.alarmInfo.previousAlarms

       Bit meanings:
               bit 1 = lineAttenuation,
               bit 2 = noiseMargin,
               bit 3 = errSecRatioExceeded,
               bit 4 = sevErrSecRatioExceeded,
               bit 5 = bBErrRatioExceeded"
   ::= {fr1646v2ShCusPrAlInfoEntry 50331648}

fr1646v2ShCusPrAlInfoAlMask OBJECT-TYPE
   SYNTAX      Integer32
   MAX-ACCESS  read-only
   STATUS      current
   DESCRIPTION
      "Path: customerLinePair.alarms.alarmInfo.alarmMask

       Bit meanings:
               bit 1 = lineAttenuation,
               bit 2 = noiseMargin,
               bit 3 = errSecRatioExceeded,
               bit 4 = sevErrSecRatioExceeded,
               bit 5 = bBErrRatioExceeded"
   ::= {fr1646v2ShCusPrAlInfoEntry 67108864}

fr1646v2ShCusPrAlInfoAlLvlLpatt OBJECT-TYPE
   SYNTAX      Integer32
   MAX-ACCESS  read-only
   STATUS      current
   DESCRIPTION
      "Path: customerLinePair.alarms.alarmInfo.alarmLevel.lineAttenuation"
   ::= {fr1646v2ShCusPrAlInfoEntry 84017152}

fr1646v2ShCusPrAlInfoAlLvlNm OBJECT-TYPE
   SYNTAX      Integer32
   MAX-ACCESS  read-only
   STATUS      current
   DESCRIPTION
      "Path: customerLinePair.alarms.alarmInfo.alarmLevel.noiseMargin"
   ::= {fr1646v2ShCusPrAlInfoEntry 84082688}

fr1646v2ShCusPrAlInfoAlLvlEsrExc OBJECT-TYPE
   SYNTAX      Integer32
   MAX-ACCESS  read-only
   STATUS      current
   DESCRIPTION
      "Path: customerLinePair.alarms.alarmInfo.alarmLevel.errSecRatioExceeded"
   ::= {fr1646v2ShCusPrAlInfoEntry 84148224}

fr1646v2ShCusPrAlInfoAlLvlSesrExc OBJECT-TYPE
   SYNTAX      Integer32
   MAX-ACCESS  read-only
   STATUS      current
   DESCRIPTION
      "Path: customerLinePair.alarms.alarmInfo.alarmLevel.sevErrSecRatioExceeded"
   ::= {fr1646v2ShCusPrAlInfoEntry 84213760}

fr1646v2ShCusPrAlInfoAlLvlBberExc OBJECT-TYPE
   SYNTAX      Integer32
   MAX-ACCESS  read-only
   STATUS      current
   DESCRIPTION
      "Path: customerLinePair.alarms.alarmInfo.alarmLevel.bBErrRatioExceeded"
   ::= {fr1646v2ShCusPrAlInfoEntry 84279296}


fr1646v2ShCusPrAlInfoE2 OBJECT IDENTIFIER ::= {fr1646v2ShCusPrAlInfo 2}

fr1646v2ShCusPrAlInfoE2Entry OBJECT IDENTIFIER ::= {fr1646v2ShCusPrAlInfoE2 1}

fr1646v2ShCusPrAlInfoE2Lpatt OBJECT IDENTIFIER ::= {fr1646v2ShCusPrAlInfoE2Entry 11}

fr1646v2ShCusPrAlInfoE2LpattPfx OBJECT IDENTIFIER ::= {fr1646v2ShCusPrAlInfoE2Lpatt 0}

fr1646v2ShCusPrAlInfoE2LpattOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lineAttenuation'
                representing an alarm condition in the alarm word
                of attribute 'alarmInfo' of managed object 'shdslCustomerPairNm'
                (root='router1646') has changed from the ON to the OFF state."
   ::= {fr1646v2ShCusPrAlInfoE2LpattPfx 1}

fr1646v2ShCusPrAlInfoE2LpattOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lineAttenuation'
                representing an alarm condition in the alarm word
                of attribute 'alarmInfo' of managed object 'shdslCustomerPairNm'
                (root='router1646') has changed from the OFF to the ON state."
   ::= {fr1646v2ShCusPrAlInfoE2LpattPfx 2}

fr1646v2ShCusPrAlInfoE2Nm OBJECT IDENTIFIER ::= {fr1646v2ShCusPrAlInfoE2Entry 12}

fr1646v2ShCusPrAlInfoE2NmPfx OBJECT IDENTIFIER ::= {fr1646v2ShCusPrAlInfoE2Nm 0}

fr1646v2ShCusPrAlInfoE2NmOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'noiseMargin'
                representing an alarm condition in the alarm word
                of attribute 'alarmInfo' of managed object 'shdslCustomerPairNm'
                (root='router1646') has changed from the ON to the OFF state."
   ::= {fr1646v2ShCusPrAlInfoE2NmPfx 1}

fr1646v2ShCusPrAlInfoE2NmOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'noiseMargin'
                representing an alarm condition in the alarm word
                of attribute 'alarmInfo' of managed object 'shdslCustomerPairNm'
                (root='router1646') has changed from the OFF to the ON state."
   ::= {fr1646v2ShCusPrAlInfoE2NmPfx 2}

fr1646v2ShCusPrAlInfoE2EsrExc OBJECT IDENTIFIER ::= {fr1646v2ShCusPrAlInfoE2Entry 13}

fr1646v2ShCusPrAlInfoE2EsrExcPfx OBJECT IDENTIFIER ::= {fr1646v2ShCusPrAlInfoE2EsrExc 0}

fr1646v2ShCusPrAlInfoE2EsrExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'errSecRatioExceeded'
                representing an alarm condition in the alarm word
                of attribute 'alarmInfo' of managed object 'shdslCustomerPairNm'
                (root='router1646') has changed from the ON to the OFF state."
   ::= {fr1646v2ShCusPrAlInfoE2EsrExcPfx 1}

fr1646v2ShCusPrAlInfoE2EsrExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'errSecRatioExceeded'
                representing an alarm condition in the alarm word
                of attribute 'alarmInfo' of managed object 'shdslCustomerPairNm'
                (root='router1646') has changed from the OFF to the ON state."
   ::= {fr1646v2ShCusPrAlInfoE2EsrExcPfx 2}

fr1646v2ShCusPrAlInfoE2SesrExc OBJECT IDENTIFIER ::= {fr1646v2ShCusPrAlInfoE2Entry 14}

fr1646v2ShCusPrAlInfoE2SesrExcPfx OBJECT IDENTIFIER ::= {fr1646v2ShCusPrAlInfoE2SesrExc 0}

fr1646v2ShCusPrAlInfoE2SesrExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'sevErrSecRatioExceeded'
                representing an alarm condition in the alarm word
                of attribute 'alarmInfo' of managed object 'shdslCustomerPairNm'
                (root='router1646') has changed from the ON to the OFF state."
   ::= {fr1646v2ShCusPrAlInfoE2SesrExcPfx 1}

fr1646v2ShCusPrAlInfoE2SesrExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'sevErrSecRatioExceeded'
                representing an alarm condition in the alarm word
                of attribute 'alarmInfo' of managed object 'shdslCustomerPairNm'
                (root='router1646') has changed from the OFF to the ON state."
   ::= {fr1646v2ShCusPrAlInfoE2SesrExcPfx 2}

fr1646v2ShCusPrAlInfoE2BberExc OBJECT IDENTIFIER ::= {fr1646v2ShCusPrAlInfoE2Entry 15}

fr1646v2ShCusPrAlInfoE2BberExcPfx OBJECT IDENTIFIER ::= {fr1646v2ShCusPrAlInfoE2BberExc 0}

fr1646v2ShCusPrAlInfoE2BberExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'bBErrRatioExceeded'
                representing an alarm condition in the alarm word
                of attribute 'alarmInfo' of managed object 'shdslCustomerPairNm'
                (root='router1646') has changed from the ON to the OFF state."
   ::= {fr1646v2ShCusPrAlInfoE2BberExcPfx 1}

fr1646v2ShCusPrAlInfoE2BberExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'bBErrRatioExceeded'
                representing an alarm condition in the alarm word
                of attribute 'alarmInfo' of managed object 'shdslCustomerPairNm'
                (root='router1646') has changed from the OFF to the ON state."
   ::= {fr1646v2ShCusPrAlInfoE2BberExcPfx 2}



END
