OneAccess-R1645v2-4619-EthpdpF DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2EthpdpF OBJECT IDENTIFIER ::= {r1645Rootv2 4619}

r1645v2EthpdpFMOProp OBJECT-TYPE
   SYNTAX      SEQUENCE OF R1645v2EthpdpFMOPropEntry
   MAX-ACCESS  not-accessible
   STATUS      current
   DESCRIPTION
      ""
   ::= {r1645v2EthpdpF 1}

r1645v2EthpdpFMOPropEntry OBJECT-TYPE
   SYNTAX      R1645v2EthpdpFMOPropEntry
   MAX-ACCESS  not-accessible
   STATUS      current
   DESCRIPTION
      ""
   INDEX      { r1645v2EthpdpFMOPropGlobalIx }
   ::= {r1645v2EthpdpFMOProp 1}

R1645v2EthpdpFMOPropEntry ::=
   SEQUENCE
      {
      r1645v2EthpdpFMOPropPath
         ContainmentPath,
      r1645v2EthpdpFMOPropRev
         ObjectRevision,
      r1645v2EthpdpFMOPropGlobalIx
         GlobalIndex
      }

r1645v2EthpdpFMOPropPath OBJECT-TYPE
   SYNTAX      ContainmentPath
   MAX-ACCESS  read-only
   STATUS      current
   DESCRIPTION
      "Textual description of the containment tree from the instance of
       the root object down to the instance of the current object."
   ::= {r1645v2EthpdpFMOPropEntry 3}

r1645v2EthpdpFMOPropRev OBJECT-TYPE
   SYNTAX      ObjectRevision
   MAX-ACCESS  read-only
   STATUS      current
   DESCRIPTION
      "This value corresponds with the revision of the MANAGED OBJECT."
   ::= {r1645v2EthpdpFMOPropEntry 4}

r1645v2EthpdpFMOPropGlobalIx OBJECT-TYPE
   SYNTAX      GlobalIndex
   MAX-ACCESS  read-only
   STATUS      current
   DESCRIPTION
      "The value of the tlsCntTreeGlobalIndex of the MANAGED OBJECT."
   ::= {r1645v2EthpdpFMOPropEntry 10}



er1645v2EthpdpF OBJECT IDENTIFIER ::= {r1645v2EthpdpF 11}


er1645v2EthpdpFName OBJECT IDENTIFIER ::= {er1645v2EthpdpF 2}

er1645v2EthpdpFNameTable OBJECT-TYPE
   SYNTAX      SEQUENCE OF Er1645v2EthpdpFNameEntry
   MAX-ACCESS  not-accessible
   STATUS      current
   DESCRIPTION
      "config interface name"
   ::= {er1645v2EthpdpFName 1}

er1645v2EthpdpFNameEntry OBJECT-TYPE
   SYNTAX      Er1645v2EthpdpFNameEntry
   MAX-ACCESS  not-accessible
   STATUS      current
   DESCRIPTION
      ""
   INDEX      { er1645v2EthpdpFNameGlobalIx }
   ::= {er1645v2EthpdpFNameTable 1}

Er1645v2EthpdpFNameEntry ::=
   SEQUENCE
      {
      er1645v2EthpdpFNameGlobalIx
         GlobalIndex,
      er1645v2EthpdpFNameValue
         DisplayString
      }

er1645v2EthpdpFNameGlobalIx OBJECT-TYPE
   SYNTAX      GlobalIndex
   MAX-ACCESS  not-accessible
   STATUS      current
   DESCRIPTION
      "The value of the tlsCntTreeGlobalIndex of the MANAGED OBJECT."
   ::= {er1645v2EthpdpFNameEntry 10}

er1645v2EthpdpFNameValue OBJECT-TYPE
   SYNTAX      DisplayString
   MAX-ACCESS  read-write
   STATUS      current
   DESCRIPTION
      "Path: ethernetPdp.editConf.name"
   ::= {er1645v2EthpdpFNameEntry 2147483648}


er1645v2EthpdpFRemark OBJECT IDENTIFIER ::= {er1645v2EthpdpF 321}

er1645v2EthpdpFRemarkTable OBJECT-TYPE
   SYNTAX      SEQUENCE OF Er1645v2EthpdpFRemarkEntry
   MAX-ACCESS  not-accessible
   STATUS      current
   DESCRIPTION
      "intfRemark"
   ::= {er1645v2EthpdpFRemark 1}

er1645v2EthpdpFRemarkEntry OBJECT-TYPE
   SYNTAX      Er1645v2EthpdpFRemarkEntry
   MAX-ACCESS  not-accessible
   STATUS      current
   DESCRIPTION
      ""
   INDEX      { er1645v2EthpdpFRemarkGlobalIx }
   ::= {er1645v2EthpdpFRemarkTable 1}

Er1645v2EthpdpFRemarkEntry ::=
   SEQUENCE
      {
      er1645v2EthpdpFRemarkGlobalIx
         GlobalIndex,
      er1645v2EthpdpFRemarkValue
         DisplayString
      }

er1645v2EthpdpFRemarkGlobalIx OBJECT-TYPE
   SYNTAX      GlobalIndex
   MAX-ACCESS  not-accessible
   STATUS      current
   DESCRIPTION
      "The value of the tlsCntTreeGlobalIndex of the MANAGED OBJECT."
   ::= {er1645v2EthpdpFRemarkEntry 10}

er1645v2EthpdpFRemarkValue OBJECT-TYPE
   SYNTAX      DisplayString
   MAX-ACCESS  read-write
   STATUS      current
   DESCRIPTION
      "Path: ethernetPdp.editConf.remark"
   ::= {er1645v2EthpdpFRemarkEntry 2147483648}


er1645v2EthpdpFDataProfile OBJECT IDENTIFIER ::= {er1645v2EthpdpF 8}

er1645v2EthpdpFDataProfileTable OBJECT-TYPE
   SYNTAX      SEQUENCE OF Er1645v2EthpdpFDataProfileEntry
   MAX-ACCESS  not-accessible
   STATUS      current
   DESCRIPTION
      "cellular profile"
   ::= {er1645v2EthpdpFDataProfile 1}

er1645v2EthpdpFDataProfileEntry OBJECT-TYPE
   SYNTAX      Er1645v2EthpdpFDataProfileEntry
   MAX-ACCESS  not-accessible
   STATUS      current
   DESCRIPTION
      ""
   INDEX      { er1645v2EthpdpFDataProfileGlobalIx }
   ::= {er1645v2EthpdpFDataProfileTable 1}

Er1645v2EthpdpFDataProfileEntry ::=
   SEQUENCE
      {
      er1645v2EthpdpFDataProfileGlobalIx
         GlobalIndex,
      er1645v2EthpdpFDataProfileValue
         DisplayString
      }

er1645v2EthpdpFDataProfileGlobalIx OBJECT-TYPE
   SYNTAX      GlobalIndex
   MAX-ACCESS  not-accessible
   STATUS      current
   DESCRIPTION
      "The value of the tlsCntTreeGlobalIndex of the MANAGED OBJECT."
   ::= {er1645v2EthpdpFDataProfileEntry 10}

er1645v2EthpdpFDataProfileValue OBJECT-TYPE
   SYNTAX      DisplayString
   MAX-ACCESS  read-write
   STATUS      current
   DESCRIPTION
      "Path: ethernetPdp.editConf.dataProfile"
   ::= {er1645v2EthpdpFDataProfileEntry 2147483648}


er1645v2EthpdpFAdminStatus OBJECT IDENTIFIER ::= {er1645v2EthpdpF 106}

er1645v2EthpdpFAdminStatusTable OBJECT-TYPE
   SYNTAX      SEQUENCE OF Er1645v2EthpdpFAdminStatusEntry
   MAX-ACCESS  not-accessible
   STATUS      current
   DESCRIPTION
      "admin status"
   ::= {er1645v2EthpdpFAdminStatus 1}

er1645v2EthpdpFAdminStatusEntry OBJECT-TYPE
   SYNTAX      Er1645v2EthpdpFAdminStatusEntry
   MAX-ACCESS  not-accessible
   STATUS      current
   DESCRIPTION
      ""
   INDEX      { er1645v2EthpdpFAdminStatusGlobalIx }
   ::= {er1645v2EthpdpFAdminStatusTable 1}

Er1645v2EthpdpFAdminStatusEntry ::=
   SEQUENCE
      {
      er1645v2EthpdpFAdminStatusGlobalIx
         GlobalIndex,
      er1645v2EthpdpFAdminStatusValue
         INTEGER
      }

er1645v2EthpdpFAdminStatusGlobalIx OBJECT-TYPE
   SYNTAX      GlobalIndex
   MAX-ACCESS  not-accessible
   STATUS      current
   DESCRIPTION
      "The value of the tlsCntTreeGlobalIndex of the MANAGED OBJECT."
   ::= {er1645v2EthpdpFAdminStatusEntry 10}

er1645v2EthpdpFAdminStatusValue OBJECT-TYPE
   SYNTAX      INTEGER
               {
               up (1),
               down (2)
               }
   MAX-ACCESS  read-write
   STATUS      current
   DESCRIPTION
      "Path: ethernetPdp.editConf.adminStatus

       Possibilities:
               up   (1)
               down   (2)"
   ::= {er1645v2EthpdpFAdminStatusEntry 2147483648}


er1645v2EthpdpFVirtEthernet OBJECT IDENTIFIER ::= {er1645v2EthpdpF 5}

er1645v2EthpdpFVirtEthernetSSCTable OBJECT-TYPE
   SYNTAX      SEQUENCE OF Er1645v2EthpdpFVirtEthernetEntry
   MAX-ACCESS  not-accessible
   STATUS      current
   DESCRIPTION
      ""
   ::= {er1645v2EthpdpFVirtEthernet 1}

er1645v2EthpdpFVirtEthernetEntry OBJECT-TYPE
   SYNTAX      Er1645v2EthpdpFVirtEthernetEntry
   MAX-ACCESS  not-accessible
   STATUS      current
   DESCRIPTION
      ""
   INDEX      { er1645v2EthpdpFVirtEthernetGlobalIx }
   ::= {er1645v2EthpdpFVirtEthernetSSCTable 1}

Er1645v2EthpdpFVirtEthernetEntry ::=
   SEQUENCE
      {
      er1645v2EthpdpFVirtEthernetGlobalIx
         GlobalIndex,
      er1645v2EthpdpFVirtEthernetVirtualEthernet
         DisplayString
      }

er1645v2EthpdpFVirtEthernetGlobalIx OBJECT-TYPE
   SYNTAX      GlobalIndex
   MAX-ACCESS  not-accessible
   STATUS      current
   DESCRIPTION
      "The value of the tlsCntTreeGlobalIndex of the MANAGED OBJECT."
   ::= {er1645v2EthpdpFVirtEthernetEntry 10}

er1645v2EthpdpFVirtEthernetVirtualEthernet OBJECT-TYPE
   SYNTAX      DisplayString
   MAX-ACCESS  read-write
   STATUS      current
   DESCRIPTION
      "Path: ethernetPdp.editConf.virtEthernet.virtualEthernet"
   ::= {er1645v2EthpdpFVirtEthernetEntry 16777216}


er1645v2EthpdpFStartDelay OBJECT IDENTIFIER ::= {er1645v2EthpdpF 7}

er1645v2EthpdpFStartDelayTable OBJECT-TYPE
   SYNTAX      SEQUENCE OF Er1645v2EthpdpFStartDelayEntry
   MAX-ACCESS  not-accessible
   STATUS      current
   DESCRIPTION
      "the amount of time the ethernetPdp module starts after network registration"
   ::= {er1645v2EthpdpFStartDelay 1}

er1645v2EthpdpFStartDelayEntry OBJECT-TYPE
   SYNTAX      Er1645v2EthpdpFStartDelayEntry
   MAX-ACCESS  not-accessible
   STATUS      current
   DESCRIPTION
      ""
   INDEX      { er1645v2EthpdpFStartDelayGlobalIx }
   ::= {er1645v2EthpdpFStartDelayTable 1}

Er1645v2EthpdpFStartDelayEntry ::=
   SEQUENCE
      {
      er1645v2EthpdpFStartDelayGlobalIx
         GlobalIndex,
      er1645v2EthpdpFStartDelayValue
         INTEGER
      }

er1645v2EthpdpFStartDelayGlobalIx OBJECT-TYPE
   SYNTAX      GlobalIndex
   MAX-ACCESS  not-accessible
   STATUS      current
   DESCRIPTION
      "The value of the tlsCntTreeGlobalIndex of the MANAGED OBJECT."
   ::= {er1645v2EthpdpFStartDelayEntry 10}

er1645v2EthpdpFStartDelayValue OBJECT-TYPE
   SYNTAX      INTEGER
               {
               disabled (0)
               }
   MAX-ACCESS  read-write
   STATUS      current
   DESCRIPTION
      "Path: ethernetPdp.editConf.startDelay

       Possibilities:
               disabled   (0)"
   ::= {er1645v2EthpdpFStartDelayEntry 2147483648}


er1645v2EthpdpFBw OBJECT IDENTIFIER ::= {er1645v2EthpdpF 37}

er1645v2EthpdpFBwSSCTable OBJECT-TYPE
   SYNTAX      SEQUENCE OF Er1645v2EthpdpFBwEntry
   MAX-ACCESS  not-accessible
   STATUS      current
   DESCRIPTION
      ""
   ::= {er1645v2EthpdpFBw 1}

er1645v2EthpdpFBwEntry OBJECT-TYPE
   SYNTAX      Er1645v2EthpdpFBwEntry
   MAX-ACCESS  not-accessible
   STATUS      current
   DESCRIPTION
      ""
   INDEX      { er1645v2EthpdpFBwGlobalIx }
   ::= {er1645v2EthpdpFBwSSCTable 1}

Er1645v2EthpdpFBwEntry ::=
   SEQUENCE
      {
      er1645v2EthpdpFBwGlobalIx
         GlobalIndex,
      er1645v2EthpdpFBwMode
         INTEGER,
      er1645v2EthpdpFBwCir
         Integer32,
      er1645v2EthpdpFBwEir
         Integer32,
      er1645v2EthpdpFBwUnit
         INTEGER,
      er1645v2EthpdpFBwTc
         INTEGER,
      er1645v2EthpdpFBwTcFactor
         INTEGER,
      er1645v2EthpdpFBwCorrType
         INTEGER,
      er1645v2EthpdpFBwCorrPredefEncapsFrameRelay
         DisplayString,
      er1645v2EthpdpFBwCorrPredefEncapsPpp
         DisplayString,
      er1645v2EthpdpFBwCorrPredefEncapsAtmHl
         INTEGER,
      er1645v2EthpdpFBwCorrPredefEncapsAtmMp
         INTEGER,
      er1645v2EthpdpFBwCorrPredefEncapsHdlc
         DisplayString,
      er1645v2EthpdpFBwCorrPredefEncapsEfmFs
         Integer32,
      er1645v2EthpdpFBwCorrPredefEncapsEfmIb
         Integer32,
      er1645v2EthpdpFBwCorrPredefMode
         INTEGER,
      er1645v2EthpdpFBwCorrManualOverhead
         Integer32,
      er1645v2EthpdpFBwCorrManualFrameData
         Counter32,
      er1645v2EthpdpFBwCorrManualFrameHeader
         Counter32,
      er1645v2EthpdpFBwMaxFifoQLen
         Integer32,
      er1645v2EthpdpFBwDeFlagCir
         INTEGER,
      er1645v2EthpdpFBwDeFlagEir
         INTEGER,
      er1645v2EthpdpFBwDeFlagViolate
         INTEGER,
      er1645v2EthpdpFBwActCirActNone
         OCTET STRING,
      er1645v2EthpdpFBwActCirActEthCos1
         INTEGER,
      er1645v2EthpdpFBwActCirActEthDei1
         INTEGER,
      er1645v2EthpdpFBwActCirActEthCos2
         INTEGER,
      er1645v2EthpdpFBwActCirActEthDei2
         INTEGER,
      er1645v2EthpdpFBwActCirActEthCos3
         INTEGER,
      er1645v2EthpdpFBwActCirActEthDei3
         INTEGER,
      er1645v2EthpdpFBwActCirActEthCos4
         INTEGER,
      er1645v2EthpdpFBwActCirActEthDei4
         INTEGER,
      er1645v2EthpdpFBwActCirActEthCos5
         INTEGER,
      er1645v2EthpdpFBwActCirActEthDei5
         INTEGER,
      er1645v2EthpdpFBwActCirActEthCos6
         INTEGER,
      er1645v2EthpdpFBwActCirActEthDei6
         INTEGER,
      er1645v2EthpdpFBwActCirActEthCos7
         INTEGER,
      er1645v2EthpdpFBwActCirActEthDei7
         INTEGER,
      er1645v2EthpdpFBwActCirActEthCos8
         INTEGER,
      er1645v2EthpdpFBwActCirActEthDei8
         INTEGER,
      er1645v2EthpdpFBwActCirActEthTos
         INTEGER,
      er1645v2EthpdpFBwActCirActEthQueue
         INTEGER,
      er1645v2EthpdpFBwActCirActEthDrpLev
         INTEGER,
      er1645v2EthpdpFBwActCirActEthDeFlag
         INTEGER,
      er1645v2EthpdpFBwActCirActIpTos
         INTEGER,
      er1645v2EthpdpFBwActCirActIpQueue
         INTEGER,
      er1645v2EthpdpFBwActCirActIpDrpLev
         INTEGER,
      er1645v2EthpdpFBwActCirActIpDeFlag
         INTEGER,
      er1645v2EthpdpFBwActEirActNone
         OCTET STRING,
      er1645v2EthpdpFBwActEirActEthCos1
         INTEGER,
      er1645v2EthpdpFBwActEirActEthDei1
         INTEGER,
      er1645v2EthpdpFBwActEirActEthCos2
         INTEGER,
      er1645v2EthpdpFBwActEirActEthDei2
         INTEGER,
      er1645v2EthpdpFBwActEirActEthCos3
         INTEGER,
      er1645v2EthpdpFBwActEirActEthDei3
         INTEGER,
      er1645v2EthpdpFBwActEirActEthCos4
         INTEGER,
      er1645v2EthpdpFBwActEirActEthDei4
         INTEGER,
      er1645v2EthpdpFBwActEirActEthCos5
         INTEGER,
      er1645v2EthpdpFBwActEirActEthDei5
         INTEGER,
      er1645v2EthpdpFBwActEirActEthCos6
         INTEGER,
      er1645v2EthpdpFBwActEirActEthDei6
         INTEGER,
      er1645v2EthpdpFBwActEirActEthCos7
         INTEGER,
      er1645v2EthpdpFBwActEirActEthDei7
         INTEGER,
      er1645v2EthpdpFBwActEirActEthCos8
         INTEGER,
      er1645v2EthpdpFBwActEirActEthDei8
         INTEGER,
      er1645v2EthpdpFBwActEirActEthTos
         INTEGER,
      er1645v2EthpdpFBwActEirActEthQueue
         INTEGER,
      er1645v2EthpdpFBwActEirActEthDrpLev
         INTEGER,
      er1645v2EthpdpFBwActEirActEthDeFlag
         INTEGER,
      er1645v2EthpdpFBwActEirActIpTos
         INTEGER,
      er1645v2EthpdpFBwActEirActIpQueue
         INTEGER,
      er1645v2EthpdpFBwActEirActIpDrpLev
         INTEGER,
      er1645v2EthpdpFBwActEirActIpDeFlag
         INTEGER,
      er1645v2EthpdpFBwActViolActNone
         OCTET STRING,
      er1645v2EthpdpFBwActViolActDrop
         OCTET STRING,
      er1645v2EthpdpFBwActViolActEthCos1
         INTEGER,
      er1645v2EthpdpFBwActViolActEthDei1
         INTEGER,
      er1645v2EthpdpFBwActViolActEthCos2
         INTEGER,
      er1645v2EthpdpFBwActViolActEthDei2
         INTEGER,
      er1645v2EthpdpFBwActViolActEthCos3
         INTEGER,
      er1645v2EthpdpFBwActViolActEthDei3
         INTEGER,
      er1645v2EthpdpFBwActViolActEthCos4
         INTEGER,
      er1645v2EthpdpFBwActViolActEthDei4
         INTEGER,
      er1645v2EthpdpFBwActViolActEthCos5
         INTEGER,
      er1645v2EthpdpFBwActViolActEthDei5
         INTEGER,
      er1645v2EthpdpFBwActViolActEthCos6
         INTEGER,
      er1645v2EthpdpFBwActViolActEthDei6
         INTEGER,
      er1645v2EthpdpFBwActViolActEthCos7
         INTEGER,
      er1645v2EthpdpFBwActViolActEthDei7
         INTEGER,
      er1645v2EthpdpFBwActViolActEthCos8
         INTEGER,
      er1645v2EthpdpFBwActViolActEthDei8
         INTEGER,
      er1645v2EthpdpFBwActViolActEthTos
         INTEGER,
      er1645v2EthpdpFBwActViolActEthQueue
         INTEGER,
      er1645v2EthpdpFBwActViolActEthDrpLev
         INTEGER,
      er1645v2EthpdpFBwActViolActEthDeFlag
         INTEGER,
      er1645v2EthpdpFBwActViolActIpTos
         INTEGER,
      er1645v2EthpdpFBwActViolActIpQueue
         INTEGER,
      er1645v2EthpdpFBwActViolActIpDrpLev
         INTEGER,
      er1645v2EthpdpFBwActViolActIpDeFlag
         INTEGER
      }

er1645v2EthpdpFBwGlobalIx OBJECT-TYPE
   SYNTAX      GlobalIndex
   MAX-ACCESS  not-accessible
   STATUS      current
   DESCRIPTION
      "The value of the tlsCntTreeGlobalIndex of the MANAGED OBJECT."
   ::= {er1645v2EthpdpFBwEntry 10}

er1645v2EthpdpFBwMode OBJECT-TYPE
   SYNTAX      INTEGER
               {
               reshaping (1),
               policing (2),
               policingReshape (3)
               }
   MAX-ACCESS  read-write
   STATUS      current
   DESCRIPTION
      "Path: ethernetPdp.editConf.bandwidth.mode

       Possibilities:
               reshaping   (1)
               policing   (2)
               policingReshape   (3)"
   ::= {er1645v2EthpdpFBwEntry 3758096384}

er1645v2EthpdpFBwCir OBJECT-TYPE
   SYNTAX      Integer32
   MAX-ACCESS  read-write
   STATUS      current
   DESCRIPTION
      "Path: ethernetPdp.editConf.bandwidth.cir"
   ::= {er1645v2EthpdpFBwEntry 268435456}

er1645v2EthpdpFBwEir OBJECT-TYPE
   SYNTAX      Integer32
   MAX-ACCESS  read-write
   STATUS      current
   DESCRIPTION
      "Path: ethernetPdp.editConf.bandwidth.eir"
   ::= {er1645v2EthpdpFBwEntry 1879048192}

er1645v2EthpdpFBwUnit OBJECT-TYPE
   SYNTAX      INTEGER
               {
               bitssec (1),
               percent (2)
               }
   MAX-ACCESS  read-write
   STATUS      current
   DESCRIPTION
      "Path: ethernetPdp.editConf.bandwidth.unit

       Possibilities:
               bits/sec   (1)
               percent   (2)"
   ::= {er1645v2EthpdpFBwEntry 1342177280}

er1645v2EthpdpFBwTc OBJECT-TYPE
   SYNTAX      INTEGER
               {
               auto (0)
               }
   MAX-ACCESS  read-write
   STATUS      current
   DESCRIPTION
      "Path: ethernetPdp.editConf.bandwidth.tc

       Possibilities:
               auto   (0)"
   ::= {er1645v2EthpdpFBwEntry 1610612736}

er1645v2EthpdpFBwTcFactor OBJECT-TYPE
   SYNTAX      INTEGER
               {
               ms (10),
               s100us (1)
               }
   MAX-ACCESS  read-write
   STATUS      current
   DESCRIPTION
      "Path: ethernetPdp.editConf.bandwidth.tcFactor

       Possibilities:
               ms   (10)
               *100us   (1)"
   ::= {er1645v2EthpdpFBwEntry 2147483648}

er1645v2EthpdpFBwCorrType OBJECT-TYPE
   SYNTAX      INTEGER
               {
               noCorrection (0),
               predefined (1),
               manual (2)
               }
   MAX-ACCESS  read-write
   STATUS      current
   DESCRIPTION
      "Path: ethernetPdp.editConf.bandwidth.correction.type

       Possibilities:
               noCorrection   (0)
               predefined   (1)
               manual   (2)"
   ::= {er1645v2EthpdpFBwEntry 570425344}

er1645v2EthpdpFBwCorrPredefEncapsFrameRelay OBJECT-TYPE
   SYNTAX      DisplayString
   MAX-ACCESS  read-write
   STATUS      current
   DESCRIPTION
      "Path: ethernetPdp.editConf.bandwidth.correction.predefined.encapsulation.frameRelay"
   ::= {er1645v2EthpdpFBwEntry 608436224}

er1645v2EthpdpFBwCorrPredefEncapsPpp OBJECT-TYPE
   SYNTAX      DisplayString
   MAX-ACCESS  read-write
   STATUS      current
   DESCRIPTION
      "Path: ethernetPdp.editConf.bandwidth.correction.predefined.encapsulation.ppp"
   ::= {er1645v2EthpdpFBwEntry 608698368}

er1645v2EthpdpFBwCorrPredefEncapsAtmHl OBJECT-TYPE
   SYNTAX      INTEGER
               {
               rfc2684 (0),
               ppp (1),
               pppOverEthernet (2)
               }
   MAX-ACCESS  read-write
   STATUS      current
   DESCRIPTION
      "Path: ethernetPdp.editConf.bandwidth.correction.predefined.encapsulation.atm.higherLayer

       Possibilities:
               rfc2684   (0)
               ppp   (1)
               pppOverEthernet   (2)"
   ::= {er1645v2EthpdpFBwEntry 608993280}

er1645v2EthpdpFBwCorrPredefEncapsAtmMp OBJECT-TYPE
   SYNTAX      INTEGER
               {
               llcEncapsulation (0),
               vcMultiplexing (1)
               }
   MAX-ACCESS  read-write
   STATUS      current
   DESCRIPTION
      "Path: ethernetPdp.editConf.bandwidth.correction.predefined.encapsulation.atm.multiProtocol

       Possibilities:
               llcEncapsulation   (0)
               vcMultiplexing   (1)"
   ::= {er1645v2EthpdpFBwEntry 609026048}

er1645v2EthpdpFBwCorrPredefEncapsHdlc OBJECT-TYPE
   SYNTAX      DisplayString
   MAX-ACCESS  read-write
   STATUS      current
   DESCRIPTION
      "Path: ethernetPdp.editConf.bandwidth.correction.predefined.encapsulation.hdlc"
   ::= {er1645v2EthpdpFBwEntry 609222656}

er1645v2EthpdpFBwCorrPredefEncapsEfmFs OBJECT-TYPE
   SYNTAX      Integer32
   MAX-ACCESS  read-write
   STATUS      current
   DESCRIPTION
      "Path: ethernetPdp.editConf.bandwidth.correction.predefined.encapsulation.efm.fragmentSize"
   ::= {er1645v2EthpdpFBwEntry 609517568}

er1645v2EthpdpFBwCorrPredefEncapsEfmIb OBJECT-TYPE
   SYNTAX      Integer32
   MAX-ACCESS  read-write
   STATUS      current
   DESCRIPTION
      "Path: ethernetPdp.editConf.bandwidth.correction.predefined.encapsulation.efm.idleBytes"
   ::= {er1645v2EthpdpFBwEntry 609550336}

er1645v2EthpdpFBwCorrPredefMode OBJECT-TYPE
   SYNTAX      INTEGER
               {
               routing (0),
               bridging (1)
               }
   MAX-ACCESS  read-write
   STATUS      current
   DESCRIPTION
      "Path: ethernetPdp.editConf.bandwidth.correction.predefined.mode

       Possibilities:
               routing   (0)
               bridging   (1)"
   ::= {er1645v2EthpdpFBwEntry 612368384}

er1645v2EthpdpFBwCorrManualOverhead OBJECT-TYPE
   SYNTAX      Integer32
   MAX-ACCESS  read-write
   STATUS      current
   DESCRIPTION
      "Path: ethernetPdp.editConf.bandwidth.correction.manual.overhead"
   ::= {er1645v2EthpdpFBwEntry 637665280}

er1645v2EthpdpFBwCorrManualFrameData OBJECT-TYPE
   SYNTAX      Counter32
   MAX-ACCESS  read-write
   STATUS      current
   DESCRIPTION
      "Path: ethernetPdp.editConf.bandwidth.correction.manual.frameData

       32 bit unsigned wrappable counter."
   ::= {er1645v2EthpdpFBwEntry 637796352}

er1645v2EthpdpFBwCorrManualFrameHeader OBJECT-TYPE
   SYNTAX      Counter32
   MAX-ACCESS  read-write
   STATUS      current
   DESCRIPTION
      "Path: ethernetPdp.editConf.bandwidth.correction.manual.frameHeader

       32 bit unsigned wrappable counter."
   ::= {er1645v2EthpdpFBwEntry 637927424}

er1645v2EthpdpFBwMaxFifoQLen OBJECT-TYPE
   SYNTAX      Integer32
   MAX-ACCESS  read-write
   STATUS      current
   DESCRIPTION
      "Path: ethernetPdp.editConf.bandwidth.maxFifoQLen"
   ::= {er1645v2EthpdpFBwEntry 805306368}

er1645v2EthpdpFBwDeFlagCir OBJECT-TYPE
   SYNTAX      INTEGER
               {
               allowed (1),
               notAllowed (2)
               }
   MAX-ACCESS  read-write
   STATUS      current
   DESCRIPTION
      "Path: ethernetPdp.editConf.bandwidth.deFlag.cir

       Possibilities:
               allowed   (1)
               notAllowed   (2)"
   ::= {er1645v2EthpdpFBwEntry 3490709504}

er1645v2EthpdpFBwDeFlagEir OBJECT-TYPE
   SYNTAX      INTEGER
               {
               allowed (1),
               notAllowed (2)
               }
   MAX-ACCESS  read-write
   STATUS      current
   DESCRIPTION
      "Path: ethernetPdp.editConf.bandwidth.deFlag.eir

       Possibilities:
               allowed   (1)
               notAllowed   (2)"
   ::= {er1645v2EthpdpFBwEntry 3491758080}

er1645v2EthpdpFBwDeFlagViolate OBJECT-TYPE
   SYNTAX      INTEGER
               {
               allowed (1),
               notAllowed (2)
               }
   MAX-ACCESS  read-write
   STATUS      current
   DESCRIPTION
      "Path: ethernetPdp.editConf.bandwidth.deFlag.violate

       Possibilities:
               allowed   (1)
               notAllowed   (2)"
   ::= {er1645v2EthpdpFBwEntry 3492806656}

er1645v2EthpdpFBwActCirActNone OBJECT-TYPE
   SYNTAX      OCTET STRING
   MAX-ACCESS  read-write
   STATUS      current
   DESCRIPTION
      "Path: ethernetPdp.editConf.bandwidth.action.cirAction.none"
   ::= {er1645v2EthpdpFBwEntry 4062183424}

er1645v2EthpdpFBwActCirActEthCos1 OBJECT-TYPE
   SYNTAX      INTEGER
               {
               unchanged (256)
               }
   MAX-ACCESS  read-write
   STATUS      current
   DESCRIPTION
      "Path: ethernetPdp.editConf.bandwidth.action.cirAction.ethernet.cosDepth1

       Possibilities:
               unchanged   (256)"
   ::= {er1645v2EthpdpFBwEntry 4064346112}

er1645v2EthpdpFBwActCirActEthDei1 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth1

       Possibilities:
               unchanged   (255)
               clear   (0)
               set   (1)"
   ::= {er1645v2EthpdpFBwEntry 4065656832}

er1645v2EthpdpFBwActCirActEthCos2 OBJECT-TYPE
   SYNTAX      INTEGER
               {
               unchanged (256)
               }
   MAX-ACCESS  read-write
   STATUS      current
   DESCRIPTION
      "Path: ethernetPdp.editConf.bandwidth.action.cirAction.ethernet.cosDepth2

       Possibilities:
               unchanged   (256)"
   ::= {er1645v2EthpdpFBwEntry 4064411648}

er1645v2EthpdpFBwActCirActEthDei2 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth2

       Possibilities:
               unchanged   (255)
               clear   (0)
               set   (1)"
   ::= {er1645v2EthpdpFBwEntry 4065722368}

er1645v2EthpdpFBwActCirActEthCos3 OBJECT-TYPE
   SYNTAX      INTEGER
               {
               unchanged (256)
               }
   MAX-ACCESS  read-write
   STATUS      current
   DESCRIPTION
      "Path: ethernetPdp.editConf.bandwidth.action.cirAction.ethernet.cosDepth3

       Possibilities:
               unchanged   (256)"
   ::= {er1645v2EthpdpFBwEntry 4064477184}

er1645v2EthpdpFBwActCirActEthDei3 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth3

       Possibilities:
               unchanged   (255)
               clear   (0)
               set   (1)"
   ::= {er1645v2EthpdpFBwEntry 4065787904}

er1645v2EthpdpFBwActCirActEthCos4 OBJECT-TYPE
   SYNTAX      INTEGER
               {
               unchanged (256)
               }
   MAX-ACCESS  read-write
   STATUS      current
   DESCRIPTION
      "Path: ethernetPdp.editConf.bandwidth.action.cirAction.ethernet.cosDepth4

       Possibilities:
               unchanged   (256)"
   ::= {er1645v2EthpdpFBwEntry 4064542720}

er1645v2EthpdpFBwActCirActEthDei4 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth4

       Possibilities:
               unchanged   (255)
               clear   (0)
               set   (1)"
   ::= {er1645v2EthpdpFBwEntry 4065853440}

er1645v2EthpdpFBwActCirActEthCos5 OBJECT-TYPE
   SYNTAX      INTEGER
               {
               unchanged (256)
               }
   MAX-ACCESS  read-write
   STATUS      current
   DESCRIPTION
      "Path: ethernetPdp.editConf.bandwidth.action.cirAction.ethernet.cosDepth5

       Possibilities:
               unchanged   (256)"
   ::= {er1645v2EthpdpFBwEntry 4064608256}

er1645v2EthpdpFBwActCirActEthDei5 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth5

       Possibilities:
               unchanged   (255)
               clear   (0)
               set   (1)"
   ::= {er1645v2EthpdpFBwEntry 4065918976}

er1645v2EthpdpFBwActCirActEthCos6 OBJECT-TYPE
   SYNTAX      INTEGER
               {
               unchanged (256)
               }
   MAX-ACCESS  read-write
   STATUS      current
   DESCRIPTION
      "Path: ethernetPdp.editConf.bandwidth.action.cirAction.ethernet.cosDepth6

       Possibilities:
               unchanged   (256)"
   ::= {er1645v2EthpdpFBwEntry 4064673792}

er1645v2EthpdpFBwActCirActEthDei6 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth6

       Possibilities:
               unchanged   (255)
               clear   (0)
               set   (1)"
   ::= {er1645v2EthpdpFBwEntry 4065984512}

er1645v2EthpdpFBwActCirActEthCos7 OBJECT-TYPE
   SYNTAX      INTEGER
               {
               unchanged (256)
               }
   MAX-ACCESS  read-write
   STATUS      current
   DESCRIPTION
      "Path: ethernetPdp.editConf.bandwidth.action.cirAction.ethernet.cosDepth7

       Possibilities:
               unchanged   (256)"
   ::= {er1645v2EthpdpFBwEntry 4064739328}

er1645v2EthpdpFBwActCirActEthDei7 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth7

       Possibilities:
               unchanged   (255)
               clear   (0)
               set   (1)"
   ::= {er1645v2EthpdpFBwEntry 4066050048}

er1645v2EthpdpFBwActCirActEthCos8 OBJECT-TYPE
   SYNTAX      INTEGER
               {
               unchanged (256)
               }
   MAX-ACCESS  read-write
   STATUS      current
   DESCRIPTION
      "Path: ethernetPdp.editConf.bandwidth.action.cirAction.ethernet.cosDepth8

       Possibilities:
               unchanged   (256)"
   ::= {er1645v2EthpdpFBwEntry 4064804864}

er1645v2EthpdpFBwActCirActEthDei8 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth8

       Possibilities:
               unchanged   (255)
               clear   (0)
               set   (1)"
   ::= {er1645v2EthpdpFBwEntry 4066115584}

er1645v2EthpdpFBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4064870400}

er1645v2EthpdpFBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4064935936}

er1645v2EthpdpFBwActCirActEthDrpLev OBJECT-TYPE
   SYNTAX      INTEGER
               {
               unchanged (0)
               }
   MAX-ACCESS  read-write
   STATUS      current
   DESCRIPTION
      "Path: ethernetPdp.editConf.bandwidth.action.cirAction.ethernet.dropLevel

       Possibilities:
               unchanged   (0)"
   ::= {er1645v2EthpdpFBwEntry 4065001472}

er1645v2EthpdpFBwActCirActEthDeFlag OBJECT-TYPE
   SYNTAX      INTEGER
               {
               unchanged (255),
               clear (0),
               set (1)
               }
   MAX-ACCESS  read-write
   STATUS      current
   DESCRIPTION
      "Path: ethernetPdp.editConf.bandwidth.action.cirAction.ethernet.deFlag

       Possibilities:
               unchanged   (255)
               clear   (0)
               set   (1)"
   ::= {er1645v2EthpdpFBwEntry 4065198080}

er1645v2EthpdpFBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4071161856}

er1645v2EthpdpFBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4071227392}

er1645v2EthpdpFBwActCirActIpDrpLev OBJECT-TYPE
   SYNTAX      INTEGER
               {
               unchanged (0)
               }
   MAX-ACCESS  read-write
   STATUS      current
   DESCRIPTION
      "Path: ethernetPdp.editConf.bandwidth.action.cirAction.ip.dropLevel

       Possibilities:
               unchanged   (0)"
   ::= {er1645v2EthpdpFBwEntry 4071292928}

er1645v2EthpdpFBwActCirActIpDeFlag OBJECT-TYPE
   SYNTAX      INTEGER
               {
               unchanged (255),
               clear (0),
               set (1)
               }
   MAX-ACCESS  read-write
   STATUS      current
   DESCRIPTION
      "Path: ethernetPdp.editConf.bandwidth.action.cirAction.ip.deFlag

       Possibilities:
               unchanged   (255)
               clear   (0)
               set   (1)"
   ::= {er1645v2EthpdpFBwEntry 4071489536}

er1645v2EthpdpFBwActEirActNone OBJECT-TYPE
   SYNTAX      OCTET STRING
   MAX-ACCESS  read-write
   STATUS      current
   DESCRIPTION
      "Path: ethernetPdp.editConf.bandwidth.action.eirAction.none"
   ::= {er1645v2EthpdpFBwEntry 4095737856}

er1645v2EthpdpFBwActEirActEthCos1 OBJECT-TYPE
   SYNTAX      INTEGER
               {
               unchanged (256)
               }
   MAX-ACCESS  read-write
   STATUS      current
   DESCRIPTION
      "Path: ethernetPdp.editConf.bandwidth.action.eirAction.ethernet.cosDepth1

       Possibilities:
               unchanged   (256)"
   ::= {er1645v2EthpdpFBwEntry 4097900544}

er1645v2EthpdpFBwActEirActEthDei1 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth1

       Possibilities:
               unchanged   (255)
               clear   (0)
               set   (1)"
   ::= {er1645v2EthpdpFBwEntry 4099211264}

er1645v2EthpdpFBwActEirActEthCos2 OBJECT-TYPE
   SYNTAX      INTEGER
               {
               unchanged (256)
               }
   MAX-ACCESS  read-write
   STATUS      current
   DESCRIPTION
      "Path: ethernetPdp.editConf.bandwidth.action.eirAction.ethernet.cosDepth2

       Possibilities:
               unchanged   (256)"
   ::= {er1645v2EthpdpFBwEntry 4097966080}

er1645v2EthpdpFBwActEirActEthDei2 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth2

       Possibilities:
               unchanged   (255)
               clear   (0)
               set   (1)"
   ::= {er1645v2EthpdpFBwEntry 4099276800}

er1645v2EthpdpFBwActEirActEthCos3 OBJECT-TYPE
   SYNTAX      INTEGER
               {
               unchanged (256)
               }
   MAX-ACCESS  read-write
   STATUS      current
   DESCRIPTION
      "Path: ethernetPdp.editConf.bandwidth.action.eirAction.ethernet.cosDepth3

       Possibilities:
               unchanged   (256)"
   ::= {er1645v2EthpdpFBwEntry 4098031616}

er1645v2EthpdpFBwActEirActEthDei3 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth3

       Possibilities:
               unchanged   (255)
               clear   (0)
               set   (1)"
   ::= {er1645v2EthpdpFBwEntry 4099342336}

er1645v2EthpdpFBwActEirActEthCos4 OBJECT-TYPE
   SYNTAX      INTEGER
               {
               unchanged (256)
               }
   MAX-ACCESS  read-write
   STATUS      current
   DESCRIPTION
      "Path: ethernetPdp.editConf.bandwidth.action.eirAction.ethernet.cosDepth4

       Possibilities:
               unchanged   (256)"
   ::= {er1645v2EthpdpFBwEntry 4098097152}

er1645v2EthpdpFBwActEirActEthDei4 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth4

       Possibilities:
               unchanged   (255)
               clear   (0)
               set   (1)"
   ::= {er1645v2EthpdpFBwEntry 4099407872}

er1645v2EthpdpFBwActEirActEthCos5 OBJECT-TYPE
   SYNTAX      INTEGER
               {
               unchanged (256)
               }
   MAX-ACCESS  read-write
   STATUS      current
   DESCRIPTION
      "Path: ethernetPdp.editConf.bandwidth.action.eirAction.ethernet.cosDepth5

       Possibilities:
               unchanged   (256)"
   ::= {er1645v2EthpdpFBwEntry 4098162688}

er1645v2EthpdpFBwActEirActEthDei5 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth5

       Possibilities:
               unchanged   (255)
               clear   (0)
               set   (1)"
   ::= {er1645v2EthpdpFBwEntry 4099473408}

er1645v2EthpdpFBwActEirActEthCos6 OBJECT-TYPE
   SYNTAX      INTEGER
               {
               unchanged (256)
               }
   MAX-ACCESS  read-write
   STATUS      current
   DESCRIPTION
      "Path: ethernetPdp.editConf.bandwidth.action.eirAction.ethernet.cosDepth6

       Possibilities:
               unchanged   (256)"
   ::= {er1645v2EthpdpFBwEntry 4098228224}

er1645v2EthpdpFBwActEirActEthDei6 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth6

       Possibilities:
               unchanged   (255)
               clear   (0)
               set   (1)"
   ::= {er1645v2EthpdpFBwEntry 4099538944}

er1645v2EthpdpFBwActEirActEthCos7 OBJECT-TYPE
   SYNTAX      INTEGER
               {
               unchanged (256)
               }
   MAX-ACCESS  read-write
   STATUS      current
   DESCRIPTION
      "Path: ethernetPdp.editConf.bandwidth.action.eirAction.ethernet.cosDepth7

       Possibilities:
               unchanged   (256)"
   ::= {er1645v2EthpdpFBwEntry 4098293760}

er1645v2EthpdpFBwActEirActEthDei7 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth7

       Possibilities:
               unchanged   (255)
               clear   (0)
               set   (1)"
   ::= {er1645v2EthpdpFBwEntry 4099604480}

er1645v2EthpdpFBwActEirActEthCos8 OBJECT-TYPE
   SYNTAX      INTEGER
               {
               unchanged (256)
               }
   MAX-ACCESS  read-write
   STATUS      current
   DESCRIPTION
      "Path: ethernetPdp.editConf.bandwidth.action.eirAction.ethernet.cosDepth8

       Possibilities:
               unchanged   (256)"
   ::= {er1645v2EthpdpFBwEntry 4098359296}

er1645v2EthpdpFBwActEirActEthDei8 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth8

       Possibilities:
               unchanged   (255)
               clear   (0)
               set   (1)"
   ::= {er1645v2EthpdpFBwEntry 4099670016}

er1645v2EthpdpFBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4098424832}

er1645v2EthpdpFBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4098490368}

er1645v2EthpdpFBwActEirActEthDrpLev OBJECT-TYPE
   SYNTAX      INTEGER
               {
               unchanged (0)
               }
   MAX-ACCESS  read-write
   STATUS      current
   DESCRIPTION
      "Path: ethernetPdp.editConf.bandwidth.action.eirAction.ethernet.dropLevel

       Possibilities:
               unchanged   (0)"
   ::= {er1645v2EthpdpFBwEntry 4098555904}

er1645v2EthpdpFBwActEirActEthDeFlag OBJECT-TYPE
   SYNTAX      INTEGER
               {
               unchanged (255),
               clear (0),
               set (1)
               }
   MAX-ACCESS  read-write
   STATUS      current
   DESCRIPTION
      "Path: ethernetPdp.editConf.bandwidth.action.eirAction.ethernet.deFlag

       Possibilities:
               unchanged   (255)
               clear   (0)
               set   (1)"
   ::= {er1645v2EthpdpFBwEntry 4098752512}

er1645v2EthpdpFBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4104716288}

er1645v2EthpdpFBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4104781824}

er1645v2EthpdpFBwActEirActIpDrpLev OBJECT-TYPE
   SYNTAX      INTEGER
               {
               unchanged (0)
               }
   MAX-ACCESS  read-write
   STATUS      current
   DESCRIPTION
      "Path: ethernetPdp.editConf.bandwidth.action.eirAction.ip.dropLevel

       Possibilities:
               unchanged   (0)"
   ::= {er1645v2EthpdpFBwEntry 4104847360}

er1645v2EthpdpFBwActEirActIpDeFlag OBJECT-TYPE
   SYNTAX      INTEGER
               {
               unchanged (255),
               clear (0),
               set (1)
               }
   MAX-ACCESS  read-write
   STATUS      current
   DESCRIPTION
      "Path: ethernetPdp.editConf.bandwidth.action.eirAction.ip.deFlag

       Possibilities:
               unchanged   (255)
               clear   (0)
               set   (1)"
   ::= {er1645v2EthpdpFBwEntry 4105043968}

er1645v2EthpdpFBwActViolActNone OBJECT-TYPE
   SYNTAX      OCTET STRING
   MAX-ACCESS  read-write
   STATUS      current
   DESCRIPTION
      "Path: ethernetPdp.editConf.bandwidth.action.violateAction.none"
   ::= {er1645v2EthpdpFBwEntry 4129292288}

er1645v2EthpdpFBwActViolActDrop OBJECT-TYPE
   SYNTAX      OCTET STRING
   MAX-ACCESS  read-write
   STATUS      current
   DESCRIPTION
      "Path: ethernetPdp.editConf.bandwidth.action.violateAction.drop"
   ::= {er1645v2EthpdpFBwEntry 4133486592}

er1645v2EthpdpFBwActViolActEthCos1 OBJECT-TYPE
   SYNTAX      INTEGER
               {
               unchanged (256)
               }
   MAX-ACCESS  read-write
   STATUS      current
   DESCRIPTION
      "Path: ethernetPdp.editConf.bandwidth.action.violateAction.ethernet.cosDepth1

       Possibilities:
               unchanged   (256)"
   ::= {er1645v2EthpdpFBwEntry 4131454976}

er1645v2EthpdpFBwActViolActEthDei1 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth1

       Possibilities:
               unchanged   (255)
               clear   (0)
               set   (1)"
   ::= {er1645v2EthpdpFBwEntry 4132765696}

er1645v2EthpdpFBwActViolActEthCos2 OBJECT-TYPE
   SYNTAX      INTEGER
               {
               unchanged (256)
               }
   MAX-ACCESS  read-write
   STATUS      current
   DESCRIPTION
      "Path: ethernetPdp.editConf.bandwidth.action.violateAction.ethernet.cosDepth2

       Possibilities:
               unchanged   (256)"
   ::= {er1645v2EthpdpFBwEntry 4131520512}

er1645v2EthpdpFBwActViolActEthDei2 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth2

       Possibilities:
               unchanged   (255)
               clear   (0)
               set   (1)"
   ::= {er1645v2EthpdpFBwEntry 4132831232}

er1645v2EthpdpFBwActViolActEthCos3 OBJECT-TYPE
   SYNTAX      INTEGER
               {
               unchanged (256)
               }
   MAX-ACCESS  read-write
   STATUS      current
   DESCRIPTION
      "Path: ethernetPdp.editConf.bandwidth.action.violateAction.ethernet.cosDepth3

       Possibilities:
               unchanged   (256)"
   ::= {er1645v2EthpdpFBwEntry 4131586048}

er1645v2EthpdpFBwActViolActEthDei3 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth3

       Possibilities:
               unchanged   (255)
               clear   (0)
               set   (1)"
   ::= {er1645v2EthpdpFBwEntry 4132896768}

er1645v2EthpdpFBwActViolActEthCos4 OBJECT-TYPE
   SYNTAX      INTEGER
               {
               unchanged (256)
               }
   MAX-ACCESS  read-write
   STATUS      current
   DESCRIPTION
      "Path: ethernetPdp.editConf.bandwidth.action.violateAction.ethernet.cosDepth4

       Possibilities:
               unchanged   (256)"
   ::= {er1645v2EthpdpFBwEntry 4131651584}

er1645v2EthpdpFBwActViolActEthDei4 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth4

       Possibilities:
               unchanged   (255)
               clear   (0)
               set   (1)"
   ::= {er1645v2EthpdpFBwEntry 4132962304}

er1645v2EthpdpFBwActViolActEthCos5 OBJECT-TYPE
   SYNTAX      INTEGER
               {
               unchanged (256)
               }
   MAX-ACCESS  read-write
   STATUS      current
   DESCRIPTION
      "Path: ethernetPdp.editConf.bandwidth.action.violateAction.ethernet.cosDepth5

       Possibilities:
               unchanged   (256)"
   ::= {er1645v2EthpdpFBwEntry 4131717120}

er1645v2EthpdpFBwActViolActEthDei5 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth5

       Possibilities:
               unchanged   (255)
               clear   (0)
               set   (1)"
   ::= {er1645v2EthpdpFBwEntry 4133027840}

er1645v2EthpdpFBwActViolActEthCos6 OBJECT-TYPE
   SYNTAX      INTEGER
               {
               unchanged (256)
               }
   MAX-ACCESS  read-write
   STATUS      current
   DESCRIPTION
      "Path: ethernetPdp.editConf.bandwidth.action.violateAction.ethernet.cosDepth6

       Possibilities:
               unchanged   (256)"
   ::= {er1645v2EthpdpFBwEntry 4131782656}

er1645v2EthpdpFBwActViolActEthDei6 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth6

       Possibilities:
               unchanged   (255)
               clear   (0)
               set   (1)"
   ::= {er1645v2EthpdpFBwEntry 4133093376}

er1645v2EthpdpFBwActViolActEthCos7 OBJECT-TYPE
   SYNTAX      INTEGER
               {
               unchanged (256)
               }
   MAX-ACCESS  read-write
   STATUS      current
   DESCRIPTION
      "Path: ethernetPdp.editConf.bandwidth.action.violateAction.ethernet.cosDepth7

       Possibilities:
               unchanged   (256)"
   ::= {er1645v2EthpdpFBwEntry 4131848192}

er1645v2EthpdpFBwActViolActEthDei7 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth7

       Possibilities:
               unchanged   (255)
               clear   (0)
               set   (1)"
   ::= {er1645v2EthpdpFBwEntry 4133158912}

er1645v2EthpdpFBwActViolActEthCos8 OBJECT-TYPE
   SYNTAX      INTEGER
               {
               unchanged (256)
               }
   MAX-ACCESS  read-write
   STATUS      current
   DESCRIPTION
      "Path: ethernetPdp.editConf.bandwidth.action.violateAction.ethernet.cosDepth8

       Possibilities:
               unchanged   (256)"
   ::= {er1645v2EthpdpFBwEntry 4131913728}

er1645v2EthpdpFBwActViolActEthDei8 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth8

       Possibilities:
               unchanged   (255)
               clear   (0)
               set   (1)"
   ::= {er1645v2EthpdpFBwEntry 4133224448}

er1645v2EthpdpFBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4131979264}

er1645v2EthpdpFBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4132044800}

er1645v2EthpdpFBwActViolActEthDrpLev OBJECT-TYPE
   SYNTAX      INTEGER
               {
               unchanged (0)
               }
   MAX-ACCESS  read-write
   STATUS      current
   DESCRIPTION
      "Path: ethernetPdp.editConf.bandwidth.action.violateAction.ethernet.dropLevel

       Possibilities:
               unchanged   (0)"
   ::= {er1645v2EthpdpFBwEntry 4132110336}

er1645v2EthpdpFBwActViolActEthDeFlag OBJECT-TYPE
   SYNTAX      INTEGER
               {
               unchanged (255),
               clear (0),
               set (1)
               }
   MAX-ACCESS  read-write
   STATUS      current
   DESCRIPTION
      "Path: ethernetPdp.editConf.bandwidth.action.violateAction.ethernet.deFlag

       Possibilities:
               unchanged   (255)
               clear   (0)
               set   (1)"
   ::= {er1645v2EthpdpFBwEntry 4132306944}

er1645v2EthpdpFBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpFBwEntry 4138270720}

er1645v2EthpdpFBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpFBwEntry 4138336256}

er1645v2EthpdpFBwActViolActIpDrpLev OBJECT-TYPE
   SYNTAX      INTEGER
               {
               unchanged (0)
               }
   MAX-ACCESS  read-write
   STATUS      current
   DESCRIPTION
      "Path: ethernetPdp.editConf.bandwidth.action.violateAction.ip.dropLevel

       Possibilities:
               unchanged   (0)"
   ::= {er1645v2EthpdpFBwEntry 4138401792}

er1645v2EthpdpFBwActViolActIpDeFlag OBJECT-TYPE
   SYNTAX      INTEGER
               {
               unchanged (255),
               clear (0),
               set (1)
               }
   MAX-ACCESS  read-write
   STATUS      current
   DESCRIPTION
      "Path: ethernetPdp.editConf.bandwidth.action.violateAction.ip.deFlag

       Possibilities:
               unchanged   (255)
               clear   (0)
               set   (1)"
   ::= {er1645v2EthpdpFBwEntry 4138598400}


er1645v2EthpdpFPriorityPolicy OBJECT IDENTIFIER ::= {er1645v2EthpdpF 39}

er1645v2EthpdpFPriorityPolicyTable OBJECT-TYPE
   SYNTAX      SEQUENCE OF Er1645v2EthpdpFPriorityPolicyEntry
   MAX-ACCESS  not-accessible
   STATUS      current
   DESCRIPTION
      "Preferred Policy"
   ::= {er1645v2EthpdpFPriorityPolicy 1}

er1645v2EthpdpFPriorityPolicyEntry OBJECT-TYPE
   SYNTAX      Er1645v2EthpdpFPriorityPolicyEntry
   MAX-ACCESS  not-accessible
   STATUS      current
   DESCRIPTION
      ""
   INDEX      { er1645v2EthpdpFPriorityPolicyGlobalIx }
   ::= {er1645v2EthpdpFPriorityPolicyTable 1}

Er1645v2EthpdpFPriorityPolicyEntry ::=
   SEQUENCE
      {
      er1645v2EthpdpFPriorityPolicyGlobalIx
         GlobalIndex,
      er1645v2EthpdpFPriorityPolicyValue
         DisplayString
      }

er1645v2EthpdpFPriorityPolicyGlobalIx OBJECT-TYPE
   SYNTAX      GlobalIndex
   MAX-ACCESS  not-accessible
   STATUS      current
   DESCRIPTION
      "The value of the tlsCntTreeGlobalIndex of the MANAGED OBJECT."
   ::= {er1645v2EthpdpFPriorityPolicyEntry 10}

er1645v2EthpdpFPriorityPolicyValue OBJECT-TYPE
   SYNTAX      DisplayString
   MAX-ACCESS  read-write
   STATUS      current
   DESCRIPTION
      "Path: ethernetPdp.editConf.priorityPolicy"
   ::= {er1645v2EthpdpFPriorityPolicyEntry 2147483648}



sr1645v2EthpdpF OBJECT IDENTIFIER ::= {r1645v2EthpdpF 14}


sr1645v2EthpdpFDescr OBJECT IDENTIFIER ::= {sr1645v2EthpdpF 101}

sr1645v2EthpdpFDescrTable OBJECT-TYPE
   SYNTAX      SEQUENCE OF Sr1645v2EthpdpFDescrEntry
   MAX-ACCESS  not-accessible
   STATUS      current
   DESCRIPTION
      "ifDescr"
   ::= {sr1645v2EthpdpFDescr 1}

sr1645v2EthpdpFDescrEntry OBJECT-TYPE
   SYNTAX      Sr1645v2EthpdpFDescrEntry
   MAX-ACCESS  not-accessible
   STATUS      current
   DESCRIPTION
      ""
   INDEX      { sr1645v2EthpdpFDescrGlobalIx }
   ::= {sr1645v2EthpdpFDescrTable 1}

Sr1645v2EthpdpFDescrEntry ::=
   SEQUENCE
      {
      sr1645v2EthpdpFDescrGlobalIx
         GlobalIndex,
      sr1645v2EthpdpFDescrValue
         DisplayString
      }

sr1645v2EthpdpFDescrGlobalIx OBJECT-TYPE
   SYNTAX      GlobalIndex
   MAX-ACCESS  not-accessible
   STATUS      current
   DESCRIPTION
      "The value of the tlsCntTreeGlobalIndex of the MANAGED OBJECT."
   ::= {sr1645v2EthpdpFDescrEntry 10}

sr1645v2EthpdpFDescrValue OBJECT-TYPE
   SYNTAX      DisplayString
   MAX-ACCESS  read-only
   STATUS      current
   DESCRIPTION
      "Path: ethernetPdp.status.ifDescr"
   ::= {sr1645v2EthpdpFDescrEntry 2147483648}


sr1645v2EthpdpFState OBJECT IDENTIFIER ::= {sr1645v2EthpdpF 47}

sr1645v2EthpdpFStateTable OBJECT-TYPE
   SYNTAX      SEQUENCE OF Sr1645v2EthpdpFStateEntry
   MAX-ACCESS  not-accessible
   STATUS      current
   DESCRIPTION
      "call state"
   ::= {sr1645v2EthpdpFState 1}

sr1645v2EthpdpFStateEntry OBJECT-TYPE
   SYNTAX      Sr1645v2EthpdpFStateEntry
   MAX-ACCESS  not-accessible
   STATUS      current
   DESCRIPTION
      ""
   INDEX      { sr1645v2EthpdpFStateGlobalIx }
   ::= {sr1645v2EthpdpFStateTable 1}

Sr1645v2EthpdpFStateEntry ::=
   SEQUENCE
      {
      sr1645v2EthpdpFStateGlobalIx
         GlobalIndex,
      sr1645v2EthpdpFStateValue
         INTEGER
      }

sr1645v2EthpdpFStateGlobalIx OBJECT-TYPE
   SYNTAX      GlobalIndex
   MAX-ACCESS  not-accessible
   STATUS      current
   DESCRIPTION
      "The value of the tlsCntTreeGlobalIndex of the MANAGED OBJECT."
   ::= {sr1645v2EthpdpFStateEntry 10}

sr1645v2EthpdpFStateValue OBJECT-TYPE
   SYNTAX      INTEGER
               {
               init (0),
               l1Down (1),
               ready (2),
               dialing (3),
               up (4),
               releasing (5)
               }
   MAX-ACCESS  read-only
   STATUS      current
   DESCRIPTION
      "Path: ethernetPdp.status.state

       Possibilities:
               init   (0)
               l1Down   (1)
               ready   (2)
               dialing   (3)
               up   (4)
               releasing   (5)"
   ::= {sr1645v2EthpdpFStateEntry 2147483648}


sr1645v2EthpdpFIfMtu OBJECT IDENTIFIER ::= {sr1645v2EthpdpF 103}

sr1645v2EthpdpFIfMtuTable OBJECT-TYPE
   SYNTAX      SEQUENCE OF Sr1645v2EthpdpFIfMtuEntry
   MAX-ACCESS  not-accessible
   STATUS      current
   DESCRIPTION
      "ifMtu"
   ::= {sr1645v2EthpdpFIfMtu 1}

sr1645v2EthpdpFIfMtuEntry OBJECT-TYPE
   SYNTAX      Sr1645v2EthpdpFIfMtuEntry
   MAX-ACCESS  not-accessible
   STATUS      current
   DESCRIPTION
      ""
   INDEX      { sr1645v2EthpdpFIfMtuGlobalIx }
   ::= {sr1645v2EthpdpFIfMtuTable 1}

Sr1645v2EthpdpFIfMtuEntry ::=
   SEQUENCE
      {
      sr1645v2EthpdpFIfMtuGlobalIx
         GlobalIndex,
      sr1645v2EthpdpFIfMtuValue
         Integer32
      }

sr1645v2EthpdpFIfMtuGlobalIx OBJECT-TYPE
   SYNTAX      GlobalIndex
   MAX-ACCESS  not-accessible
   STATUS      current
   DESCRIPTION
      "The value of the tlsCntTreeGlobalIndex of the MANAGED OBJECT."
   ::= {sr1645v2EthpdpFIfMtuEntry 10}

sr1645v2EthpdpFIfMtuValue OBJECT-TYPE
   SYNTAX      Integer32
   MAX-ACCESS  read-only
   STATUS      current
   DESCRIPTION
      "Path: ethernetPdp.status.ifMtu"
   ::= {sr1645v2EthpdpFIfMtuEntry 2147483648}


sr1645v2EthpdpFSnmpIndex OBJECT IDENTIFIER ::= {sr1645v2EthpdpF 269}

sr1645v2EthpdpFSnmpIndexTable OBJECT-TYPE
   SYNTAX      SEQUENCE OF Sr1645v2EthpdpFSnmpIndexEntry
   MAX-ACCESS  not-accessible
   STATUS      current
   DESCRIPTION
      "SNMP index assigned to this object"
   ::= {sr1645v2EthpdpFSnmpIndex 1}

sr1645v2EthpdpFSnmpIndexEntry OBJECT-TYPE
   SYNTAX      Sr1645v2EthpdpFSnmpIndexEntry
   MAX-ACCESS  not-accessible
   STATUS      current
   DESCRIPTION
      ""
   INDEX      { sr1645v2EthpdpFSnmpIndexGlobalIx }
   ::= {sr1645v2EthpdpFSnmpIndexTable 1}

Sr1645v2EthpdpFSnmpIndexEntry ::=
   SEQUENCE
      {
      sr1645v2EthpdpFSnmpIndexGlobalIx
         GlobalIndex,
      sr1645v2EthpdpFSnmpIndexValue
         Integer32
      }

sr1645v2EthpdpFSnmpIndexGlobalIx OBJECT-TYPE
   SYNTAX      GlobalIndex
   MAX-ACCESS  not-accessible
   STATUS      current
   DESCRIPTION
      "The value of the tlsCntTreeGlobalIndex of the MANAGED OBJECT."
   ::= {sr1645v2EthpdpFSnmpIndexEntry 10}

sr1645v2EthpdpFSnmpIndexValue OBJECT-TYPE
   SYNTAX      Integer32
   MAX-ACCESS  read-only
   STATUS      current
   DESCRIPTION
      "Path: ethernetPdp.status.snmpIndex"
   ::= {sr1645v2EthpdpFSnmpIndexEntry 2147483648}



pr1645v2EthpdpF OBJECT IDENTIFIER ::= {r1645v2EthpdpF 12}


pr1645v2EthpdpFInOctets OBJECT IDENTIFIER ::= {pr1645v2EthpdpF 109}

pr1645v2EthpdpFInOctetsTable OBJECT-TYPE
   SYNTAX      SEQUENCE OF Pr1645v2EthpdpFInOctetsEntry
   MAX-ACCESS  not-accessible
   STATUS      current
   DESCRIPTION
      "ifInOctets"
   ::= {pr1645v2EthpdpFInOctets 1}

pr1645v2EthpdpFInOctetsEntry OBJECT-TYPE
   SYNTAX      Pr1645v2EthpdpFInOctetsEntry
   MAX-ACCESS  not-accessible
   STATUS      current
   DESCRIPTION
      ""
   INDEX      { pr1645v2EthpdpFInOctetsGlobalIx }
   ::= {pr1645v2EthpdpFInOctetsTable 1}

Pr1645v2EthpdpFInOctetsEntry ::=
   SEQUENCE
      {
      pr1645v2EthpdpFInOctetsGlobalIx
         GlobalIndex,
      pr1645v2EthpdpFInOctetsValue
         Counter64
      }

pr1645v2EthpdpFInOctetsGlobalIx OBJECT-TYPE
   SYNTAX      GlobalIndex
   MAX-ACCESS  not-accessible
   STATUS      current
   DESCRIPTION
      "The value of the tlsCntTreeGlobalIndex of the MANAGED OBJECT."
   ::= {pr1645v2EthpdpFInOctetsEntry 10}

pr1645v2EthpdpFInOctetsValue OBJECT-TYPE
   SYNTAX      Counter64
   MAX-ACCESS  read-only
   STATUS      current
   DESCRIPTION
      "Path: ethernetPdp.performance.ifInOctets

       64 bit unsigned wrappable counter."
   ::= {pr1645v2EthpdpFInOctetsEntry 2147483648}


pr1645v2EthpdpFInUcast OBJECT IDENTIFIER ::= {pr1645v2EthpdpF 110}

pr1645v2EthpdpFInUcastTable OBJECT-TYPE
   SYNTAX      SEQUENCE OF Pr1645v2EthpdpFInUcastEntry
   MAX-ACCESS  not-accessible
   STATUS      current
   DESCRIPTION
      "ifInUcastPkts"
   ::= {pr1645v2EthpdpFInUcast 1}

pr1645v2EthpdpFInUcastEntry OBJECT-TYPE
   SYNTAX      Pr1645v2EthpdpFInUcastEntry
   MAX-ACCESS  not-accessible
   STATUS      current
   DESCRIPTION
      ""
   INDEX      { pr1645v2EthpdpFInUcastGlobalIx }
   ::= {pr1645v2EthpdpFInUcastTable 1}

Pr1645v2EthpdpFInUcastEntry ::=
   SEQUENCE
      {
      pr1645v2EthpdpFInUcastGlobalIx
         GlobalIndex,
      pr1645v2EthpdpFInUcastValue
         Counter64
      }

pr1645v2EthpdpFInUcastGlobalIx OBJECT-TYPE
   SYNTAX      GlobalIndex
   MAX-ACCESS  not-accessible
   STATUS      current
   DESCRIPTION
      "The value of the tlsCntTreeGlobalIndex of the MANAGED OBJECT."
   ::= {pr1645v2EthpdpFInUcastEntry 10}

pr1645v2EthpdpFInUcastValue OBJECT-TYPE
   SYNTAX      Counter64
   MAX-ACCESS  read-only
   STATUS      current
   DESCRIPTION
      "Path: ethernetPdp.performance.ifInUcastPkts

       64 bit unsigned wrappable counter."
   ::= {pr1645v2EthpdpFInUcastEntry 2147483648}


pr1645v2EthpdpFInNUcastPkts OBJECT IDENTIFIER ::= {pr1645v2EthpdpF 111}

pr1645v2EthpdpFInNUcastPktsTable OBJECT-TYPE
   SYNTAX      SEQUENCE OF Pr1645v2EthpdpFInNUcastPktsEntry
   MAX-ACCESS  not-accessible
   STATUS      current
   DESCRIPTION
      "ifInNUcastPkts"
   ::= {pr1645v2EthpdpFInNUcastPkts 1}

pr1645v2EthpdpFInNUcastPktsEntry OBJECT-TYPE
   SYNTAX      Pr1645v2EthpdpFInNUcastPktsEntry
   MAX-ACCESS  not-accessible
   STATUS      current
   DESCRIPTION
      ""
   INDEX      { pr1645v2EthpdpFInNUcastPktsGlobalIx }
   ::= {pr1645v2EthpdpFInNUcastPktsTable 1}

Pr1645v2EthpdpFInNUcastPktsEntry ::=
   SEQUENCE
      {
      pr1645v2EthpdpFInNUcastPktsGlobalIx
         GlobalIndex,
      pr1645v2EthpdpFInNUcastPktsValue
         Counter64
      }

pr1645v2EthpdpFInNUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpFInNUcastPktsEntry 10}

pr1645v2EthpdpFInNUcastPktsValue OBJECT-TYPE
   SYNTAX      Counter64
   MAX-ACCESS  read-only
   STATUS      current
   DESCRIPTION
      "Path: ethernetPdp.performance.ifInNUcastPkts

       64 bit unsigned wrappable counter."
   ::= {pr1645v2EthpdpFInNUcastPktsEntry 2147483648}


pr1645v2EthpdpFInDiscards OBJECT IDENTIFIER ::= {pr1645v2EthpdpF 112}

pr1645v2EthpdpFInDiscardsTable OBJECT-TYPE
   SYNTAX      SEQUENCE OF Pr1645v2EthpdpFInDiscardsEntry
   MAX-ACCESS  not-accessible
   STATUS      current
   DESCRIPTION
      "ifInDiscards"
   ::= {pr1645v2EthpdpFInDiscards 1}

pr1645v2EthpdpFInDiscardsEntry OBJECT-TYPE
   SYNTAX      Pr1645v2EthpdpFInDiscardsEntry
   MAX-ACCESS  not-accessible
   STATUS      current
   DESCRIPTION
      ""
   INDEX      { pr1645v2EthpdpFInDiscardsGlobalIx }
   ::= {pr1645v2EthpdpFInDiscardsTable 1}

Pr1645v2EthpdpFInDiscardsEntry ::=
   SEQUENCE
      {
      pr1645v2EthpdpFInDiscardsGlobalIx
         GlobalIndex,
      pr1645v2EthpdpFInDiscardsValue
         Counter64
      }

pr1645v2EthpdpFInDiscardsGlobalIx OBJECT-TYPE
   SYNTAX      GlobalIndex
   MAX-ACCESS  not-accessible
   STATUS      current
   DESCRIPTION
      "The value of the tlsCntTreeGlobalIndex of the MANAGED OBJECT."
   ::= {pr1645v2EthpdpFInDiscardsEntry 10}

pr1645v2EthpdpFInDiscardsValue OBJECT-TYPE
   SYNTAX      Counter64
   MAX-ACCESS  read-only
   STATUS      current
   DESCRIPTION
      "Path: ethernetPdp.performance.ifInDiscards

       64 bit unsigned wrappable counter."
   ::= {pr1645v2EthpdpFInDiscardsEntry 2147483648}


pr1645v2EthpdpFInErrors OBJECT IDENTIFIER ::= {pr1645v2EthpdpF 113}

pr1645v2EthpdpFInErrorsTable OBJECT-TYPE
   SYNTAX      SEQUENCE OF Pr1645v2EthpdpFInErrorsEntry
   MAX-ACCESS  not-accessible
   STATUS      current
   DESCRIPTION
      "ifInErrors"
   ::= {pr1645v2EthpdpFInErrors 1}

pr1645v2EthpdpFInErrorsEntry OBJECT-TYPE
   SYNTAX      Pr1645v2EthpdpFInErrorsEntry
   MAX-ACCESS  not-accessible
   STATUS      current
   DESCRIPTION
      ""
   INDEX      { pr1645v2EthpdpFInErrorsGlobalIx }
   ::= {pr1645v2EthpdpFInErrorsTable 1}

Pr1645v2EthpdpFInErrorsEntry ::=
   SEQUENCE
      {
      pr1645v2EthpdpFInErrorsGlobalIx
         GlobalIndex,
      pr1645v2EthpdpFInErrorsValue
         Counter64
      }

pr1645v2EthpdpFInErrorsGlobalIx OBJECT-TYPE
   SYNTAX      GlobalIndex
   MAX-ACCESS  not-accessible
   STATUS      current
   DESCRIPTION
      "The value of the tlsCntTreeGlobalIndex of the MANAGED OBJECT."
   ::= {pr1645v2EthpdpFInErrorsEntry 10}

pr1645v2EthpdpFInErrorsValue OBJECT-TYPE
   SYNTAX      Counter64
   MAX-ACCESS  read-only
   STATUS      current
   DESCRIPTION
      "Path: ethernetPdp.performance.ifInErrors

       64 bit unsigned wrappable counter."
   ::= {pr1645v2EthpdpFInErrorsEntry 2147483648}


pr1645v2EthpdpFInUnknownProtos OBJECT IDENTIFIER ::= {pr1645v2EthpdpF 114}

pr1645v2EthpdpFInUnknownProtosTable OBJECT-TYPE
   SYNTAX      SEQUENCE OF Pr1645v2EthpdpFInUnknownProtosEntry
   MAX-ACCESS  not-accessible
   STATUS      current
   DESCRIPTION
      "ifInUnknownprotos"
   ::= {pr1645v2EthpdpFInUnknownProtos 1}

pr1645v2EthpdpFInUnknownProtosEntry OBJECT-TYPE
   SYNTAX      Pr1645v2EthpdpFInUnknownProtosEntry
   MAX-ACCESS  not-accessible
   STATUS      current
   DESCRIPTION
      ""
   INDEX      { pr1645v2EthpdpFInUnknownProtosGlobalIx }
   ::= {pr1645v2EthpdpFInUnknownProtosTable 1}

Pr1645v2EthpdpFInUnknownProtosEntry ::=
   SEQUENCE
      {
      pr1645v2EthpdpFInUnknownProtosGlobalIx
         GlobalIndex,
      pr1645v2EthpdpFInUnknownProtosValue
         Counter64
      }

pr1645v2EthpdpFInUnknownProtosGlobalIx OBJECT-TYPE
   SYNTAX      GlobalIndex
   MAX-ACCESS  not-accessible
   STATUS      current
   DESCRIPTION
      "The value of the tlsCntTreeGlobalIndex of the MANAGED OBJECT."
   ::= {pr1645v2EthpdpFInUnknownProtosEntry 10}

pr1645v2EthpdpFInUnknownProtosValue OBJECT-TYPE
   SYNTAX      Counter64
   MAX-ACCESS  read-only
   STATUS      current
   DESCRIPTION
      "Path: ethernetPdp.performance.ifInUnknownProtos

       64 bit unsigned wrappable counter."
   ::= {pr1645v2EthpdpFInUnknownProtosEntry 2147483648}


pr1645v2EthpdpFInQLen OBJECT IDENTIFIER ::= {pr1645v2EthpdpF 128}

pr1645v2EthpdpFInQLenTable OBJECT-TYPE
   SYNTAX      SEQUENCE OF Pr1645v2EthpdpFInQLenEntry
   MAX-ACCESS  not-accessible
   STATUS      current
   DESCRIPTION
      "ifInQLen"
   ::= {pr1645v2EthpdpFInQLen 1}

pr1645v2EthpdpFInQLenEntry OBJECT-TYPE
   SYNTAX      Pr1645v2EthpdpFInQLenEntry
   MAX-ACCESS  not-accessible
   STATUS      current
   DESCRIPTION
      ""
   INDEX      { pr1645v2EthpdpFInQLenGlobalIx }
   ::= {pr1645v2EthpdpFInQLenTable 1}

Pr1645v2EthpdpFInQLenEntry ::=
   SEQUENCE
      {
      pr1645v2EthpdpFInQLenGlobalIx
         GlobalIndex,
      pr1645v2EthpdpFInQLenValue
         Gauge32
      }

pr1645v2EthpdpFInQLenGlobalIx OBJECT-TYPE
   SYNTAX      GlobalIndex
   MAX-ACCESS  not-accessible
   STATUS      current
   DESCRIPTION
      "The value of the tlsCntTreeGlobalIndex of the MANAGED OBJECT."
   ::= {pr1645v2EthpdpFInQLenEntry 10}

pr1645v2EthpdpFInQLenValue OBJECT-TYPE
   SYNTAX      Gauge32
   MAX-ACCESS  read-only
   STATUS      current
   DESCRIPTION
      "Path: ethernetPdp.performance.ifInQLen

       32 bit unsigned gauge value."
   ::= {pr1645v2EthpdpFInQLenEntry 2147483648}


pr1645v2EthpdpFInDropEx OBJECT IDENTIFIER ::= {pr1645v2EthpdpF 130}

pr1645v2EthpdpFInDropExTable OBJECT-TYPE
   SYNTAX      SEQUENCE OF Pr1645v2EthpdpFInDropExEntry
   MAX-ACCESS  not-accessible
   STATUS      current
   DESCRIPTION
      "ifInDiscards"
   ::= {pr1645v2EthpdpFInDropEx 1}

pr1645v2EthpdpFInDropExEntry OBJECT-TYPE
   SYNTAX      Pr1645v2EthpdpFInDropExEntry
   MAX-ACCESS  not-accessible
   STATUS      current
   DESCRIPTION
      ""
   INDEX      { pr1645v2EthpdpFInDropExGlobalIx }
   ::= {pr1645v2EthpdpFInDropExTable 1}

Pr1645v2EthpdpFInDropExEntry ::=
   SEQUENCE
      {
      pr1645v2EthpdpFInDropExGlobalIx
         GlobalIndex,
      pr1645v2EthpdpFInDropExValue
         Counter64
      }

pr1645v2EthpdpFInDropExGlobalIx OBJECT-TYPE
   SYNTAX      GlobalIndex
   MAX-ACCESS  not-accessible
   STATUS      current
   DESCRIPTION
      "The value of the tlsCntTreeGlobalIndex of the MANAGED OBJECT."
   ::= {pr1645v2EthpdpFInDropExEntry 10}

pr1645v2EthpdpFInDropExValue OBJECT-TYPE
   SYNTAX      Counter64
   MAX-ACCESS  read-only
   STATUS      current
   DESCRIPTION
      "Path: ethernetPdp.performance.ifInDropLevelExceeded

       64 bit unsigned wrappable counter."
   ::= {pr1645v2EthpdpFInDropExEntry 2147483648}


pr1645v2EthpdpFInDropNoMac OBJECT IDENTIFIER ::= {pr1645v2EthpdpF 133}

pr1645v2EthpdpFInDropNoMacTable OBJECT-TYPE
   SYNTAX      SEQUENCE OF Pr1645v2EthpdpFInDropNoMacEntry
   MAX-ACCESS  not-accessible
   STATUS      current
   DESCRIPTION
      "ifInDiscards"
   ::= {pr1645v2EthpdpFInDropNoMac 1}

pr1645v2EthpdpFInDropNoMacEntry OBJECT-TYPE
   SYNTAX      Pr1645v2EthpdpFInDropNoMacEntry
   MAX-ACCESS  not-accessible
   STATUS      current
   DESCRIPTION
      ""
   INDEX      { pr1645v2EthpdpFInDropNoMacGlobalIx }
   ::= {pr1645v2EthpdpFInDropNoMacTable 1}

Pr1645v2EthpdpFInDropNoMacEntry ::=
   SEQUENCE
      {
      pr1645v2EthpdpFInDropNoMacGlobalIx
         GlobalIndex,
      pr1645v2EthpdpFInDropNoMacValue
         Counter64
      }

pr1645v2EthpdpFInDropNoMacGlobalIx OBJECT-TYPE
   SYNTAX      GlobalIndex
   MAX-ACCESS  not-accessible
   STATUS      current
   DESCRIPTION
      "The value of the tlsCntTreeGlobalIndex of the MANAGED OBJECT."
   ::= {pr1645v2EthpdpFInDropNoMacEntry 10}

pr1645v2EthpdpFInDropNoMacValue OBJECT-TYPE
   SYNTAX      Counter64
   MAX-ACCESS  read-only
   STATUS      current
   DESCRIPTION
      "Path: ethernetPdp.performance.ifInDiscardsNoMacFit

       64 bit unsigned wrappable counter."
   ::= {pr1645v2EthpdpFInDropNoMacEntry 2147483648}


pr1645v2EthpdpFInDropNUCast OBJECT IDENTIFIER ::= {pr1645v2EthpdpF 136}

pr1645v2EthpdpFInDropNUCastTable OBJECT-TYPE
   SYNTAX      SEQUENCE OF Pr1645v2EthpdpFInDropNUCastEntry
   MAX-ACCESS  not-accessible
   STATUS      current
   DESCRIPTION
      "ifInDiscards"
   ::= {pr1645v2EthpdpFInDropNUCast 1}

pr1645v2EthpdpFInDropNUCastEntry OBJECT-TYPE
   SYNTAX      Pr1645v2EthpdpFInDropNUCastEntry
   MAX-ACCESS  not-accessible
   STATUS      current
   DESCRIPTION
      ""
   INDEX      { pr1645v2EthpdpFInDropNUCastGlobalIx }
   ::= {pr1645v2EthpdpFInDropNUCastTable 1}

Pr1645v2EthpdpFInDropNUCastEntry ::=
   SEQUENCE
      {
      pr1645v2EthpdpFInDropNUCastGlobalIx
         GlobalIndex,
      pr1645v2EthpdpFInDropNUCastValue
         Counter64
      }

pr1645v2EthpdpFInDropNUCastGlobalIx OBJECT-TYPE
   SYNTAX      GlobalIndex
   MAX-ACCESS  not-accessible
   STATUS      current
   DESCRIPTION
      "The value of the tlsCntTreeGlobalIndex of the MANAGED OBJECT."
   ::= {pr1645v2EthpdpFInDropNUCastEntry 10}

pr1645v2EthpdpFInDropNUCastValue OBJECT-TYPE
   SYNTAX      Counter64
   MAX-ACCESS  read-only
   STATUS      current
   DESCRIPTION
      "Path: ethernetPdp.performance.ifInDiscardsNUCast

       64 bit unsigned wrappable counter."
   ::= {pr1645v2EthpdpFInDropNUCastEntry 2147483648}


pr1645v2EthpdpFInDropFilter OBJECT IDENTIFIER ::= {pr1645v2EthpdpF 137}

pr1645v2EthpdpFInDropFilterTable OBJECT-TYPE
   SYNTAX      SEQUENCE OF Pr1645v2EthpdpFInDropFilterEntry
   MAX-ACCESS  not-accessible
   STATUS      current
   DESCRIPTION
      "ifInDiscards"
   ::= {pr1645v2EthpdpFInDropFilter 1}

pr1645v2EthpdpFInDropFilterEntry OBJECT-TYPE
   SYNTAX      Pr1645v2EthpdpFInDropFilterEntry
   MAX-ACCESS  not-accessible
   STATUS      current
   DESCRIPTION
      ""
   INDEX      { pr1645v2EthpdpFInDropFilterGlobalIx }
   ::= {pr1645v2EthpdpFInDropFilterTable 1}

Pr1645v2EthpdpFInDropFilterEntry ::=
   SEQUENCE
      {
      pr1645v2EthpdpFInDropFilterGlobalIx
         GlobalIndex,
      pr1645v2EthpdpFInDropFilterValue
         Counter64
      }

pr1645v2EthpdpFInDropFilterGlobalIx OBJECT-TYPE
   SYNTAX      GlobalIndex
   MAX-ACCESS  not-accessible
   STATUS      current
   DESCRIPTION
      "The value of the tlsCntTreeGlobalIndex of the MANAGED OBJECT."
   ::= {pr1645v2EthpdpFInDropFilterEntry 10}

pr1645v2EthpdpFInDropFilterValue OBJECT-TYPE
   SYNTAX      Counter64
   MAX-ACCESS  read-only
   STATUS      current
   DESCRIPTION
      "Path: ethernetPdp.performance.ifInDiscardsFilter

       64 bit unsigned wrappable counter."
   ::= {pr1645v2EthpdpFInDropFilterEntry 2147483648}


pr1645v2EthpdpFInQueues OBJECT IDENTIFIER ::= {pr1645v2EthpdpF 131}

pr1645v2EthpdpFInQueuesSSCTable OBJECT-TYPE
   SYNTAX      SEQUENCE OF Pr1645v2EthpdpFInQueuesEntry
   MAX-ACCESS  not-accessible
   STATUS      current
   DESCRIPTION
      "Queue Lengths"
   ::= {pr1645v2EthpdpFInQueues 1}

pr1645v2EthpdpFInQueuesEntry OBJECT-TYPE
   SYNTAX      Pr1645v2EthpdpFInQueuesEntry
   MAX-ACCESS  not-accessible
   STATUS      current
   DESCRIPTION
      ""
   INDEX      { pr1645v2EthpdpFInQueuesGlobalIx,
                pr1645v2EthpdpFInQueuesTableIx }
   ::= {pr1645v2EthpdpFInQueuesSSCTable 1}

Pr1645v2EthpdpFInQueuesEntry ::=
   SEQUENCE
      {
      pr1645v2EthpdpFInQueuesGlobalIx
         GlobalIndex,
      pr1645v2EthpdpFInQueuesTableIx
         TableIndex,
      pr1645v2EthpdpFInQueuesName
         INTEGER,
      pr1645v2EthpdpFInQueuesLength
         Integer32,
      pr1645v2EthpdpFInQueuesOctetLength
         Integer32,
      pr1645v2EthpdpFInQueuesRedLength
         Integer32,
      pr1645v2EthpdpFInQueuesPacketsTotal
         Counter64,
      pr1645v2EthpdpFInQueuesPacketsDirectTx
         Counter64,
      pr1645v2EthpdpFInQueuesPacketsQueued
         Counter64,
      pr1645v2EthpdpFInQueuesPacketsDropped
         Counter64,
      pr1645v2EthpdpFInQueuesPacketsRedDropped
         Counter64,
      pr1645v2EthpdpFInQueuesPacketsCirTx
         Counter64,
      pr1645v2EthpdpFInQueuesPacketsEirTx
         Counter64,
      pr1645v2EthpdpFInQueuesPacketsViolateTx
         Counter64,
      pr1645v2EthpdpFInQueuesOctetsTotal
         Counter64,
      pr1645v2EthpdpFInQueuesOctetsDirectTx
         Counter64,
      pr1645v2EthpdpFInQueuesOctetsQueued
         Counter64,
      pr1645v2EthpdpFInQueuesOctetsDropped
         Counter64,
      pr1645v2EthpdpFInQueuesOctetsRedDropped
         Counter64,
      pr1645v2EthpdpFInQueuesOctetsCirTx
         Counter64,
      pr1645v2EthpdpFInQueuesOctetsEirTx
         Counter64,
      pr1645v2EthpdpFInQueuesOctetsViolateTx
         Counter64,
      pr1645v2EthpdpFInQueuesOctetsBandwidth15sec
         Integer32,
      pr1645v2EthpdpFInQueuesOctetsBandwidth30sec
         Integer32,
      pr1645v2EthpdpFInQueuesOctetsBandwidth1min
         Integer32,
      pr1645v2EthpdpFInQueuesOctetsBandwidth2min
         Integer32,
      pr1645v2EthpdpFInQueuesOctetsBandwidth5min
         Integer32
      }

pr1645v2EthpdpFInQueuesGlobalIx OBJECT-TYPE
   SYNTAX      GlobalIndex
   MAX-ACCESS  not-accessible
   STATUS      current
   DESCRIPTION
      "The value of the tlsCntTreeGlobalIndex of the MANAGED OBJECT."
   ::= {pr1645v2EthpdpFInQueuesEntry 10}

pr1645v2EthpdpFInQueuesTableIx OBJECT-TYPE
   SYNTAX      TableIndex
   MAX-ACCESS  not-accessible
   STATUS      current
   DESCRIPTION
      ""
   ::= {pr1645v2EthpdpFInQueuesEntry 11}

pr1645v2EthpdpFInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernetPdp.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthpdpFInQueuesEntry 16777216}

pr1645v2EthpdpFInQueuesLength OBJECT-TYPE
   SYNTAX      Integer32
   MAX-ACCESS  read-only
   STATUS      current
   DESCRIPTION
      "Path: ethernetPdp.performance.ifInPriorityQueues.length"
   ::= {pr1645v2EthpdpFInQueuesEntry 33554432}

pr1645v2EthpdpFInQueuesOctetLength OBJECT-TYPE
   SYNTAX      Integer32
   MAX-ACCESS  read-only
   STATUS      current
   DESCRIPTION
      "Path: ethernetPdp.performance.ifInPriorityQueues.octetLength"
   ::= {pr1645v2EthpdpFInQueuesEntry 150994944}

pr1645v2EthpdpFInQueuesRedLength OBJECT-TYPE
   SYNTAX      Integer32
   MAX-ACCESS  read-only
   STATUS      current
   DESCRIPTION
      "Path: ethernetPdp.performance.ifInPriorityQueues.redLength"
   ::= {pr1645v2EthpdpFInQueuesEntry 134217728}

pr1645v2EthpdpFInQueuesPacketsTotal OBJECT-TYPE
   SYNTAX      Counter64
   MAX-ACCESS  read-only
   STATUS      current
   DESCRIPTION
      "Path: ethernetPdp.performance.ifInPriorityQueues.packets.total

       64 bit unsigned wrappable counter."
   ::= {pr1645v2EthpdpFInQueuesEntry 50790400}

pr1645v2EthpdpFInQueuesPacketsDirectTx OBJECT-TYPE
   SYNTAX      Counter64
   MAX-ACCESS  read-only
   STATUS      current
   DESCRIPTION
      "Path: ethernetPdp.performance.ifInPriorityQueues.packets.directTx

       64 bit unsigned wrappable counter."
   ::= {pr1645v2EthpdpFInQueuesEntry 50397184}

pr1645v2EthpdpFInQueuesPacketsQueued OBJECT-TYPE
   SYNTAX      Counter64
   MAX-ACCESS  read-only
   STATUS      current
   DESCRIPTION
      "Path: ethernetPdp.performance.ifInPriorityQueues.packets.queued

       64 bit unsigned wrappable counter."
   ::= {pr1645v2EthpdpFInQueuesEntry 50462720}

pr1645v2EthpdpFInQueuesPacketsDropped OBJECT-TYPE
   SYNTAX      Counter64
   MAX-ACCESS  read-only
   STATUS      current
   DESCRIPTION
      "Path: ethernetPdp.performance.ifInPriorityQueues.packets.dropped

       64 bit unsigned wrappable counter."
   ::= {pr1645v2EthpdpFInQueuesEntry 50528256}

pr1645v2EthpdpFInQueuesPacketsRedDropped OBJECT-TYPE
   SYNTAX      Counter64
   MAX-ACCESS  read-only
   STATUS      current
   DESCRIPTION
      "Path: ethernetPdp.performance.ifInPriorityQueues.packets.redDropped

       64 bit unsigned wrappable counter."
   ::= {pr1645v2EthpdpFInQueuesEntry 50724864}

pr1645v2EthpdpFInQueuesPacketsCirTx OBJECT-TYPE
   SYNTAX      Counter64
   MAX-ACCESS  read-only
   STATUS      current
   DESCRIPTION
      "Path: ethernetPdp.performance.ifInPriorityQueues.packets.cirTx

       64 bit unsigned wrappable counter."
   ::= {pr1645v2EthpdpFInQueuesEntry 50593792}

pr1645v2EthpdpFInQueuesPacketsEirTx OBJECT-TYPE
   SYNTAX      Counter64
   MAX-ACCESS  read-only
   STATUS      current
   DESCRIPTION
      "Path: ethernetPdp.performance.ifInPriorityQueues.packets.eirTx

       64 bit unsigned wrappable counter."
   ::= {pr1645v2EthpdpFInQueuesEntry 50659328}

pr1645v2EthpdpFInQueuesPacketsViolateTx OBJECT-TYPE
   SYNTAX      Counter64
   MAX-ACCESS  read-only
   STATUS      current
   DESCRIPTION
      "Path: ethernetPdp.performance.ifInPriorityQueues.packets.violateTx

       64 bit unsigned wrappable counter."
   ::= {pr1645v2EthpdpFInQueuesEntry 50855936}

pr1645v2EthpdpFInQueuesOctetsTotal OBJECT-TYPE
   SYNTAX      Counter64
   MAX-ACCESS  read-only
   STATUS      current
   DESCRIPTION
      "Path: ethernetPdp.performance.ifInPriorityQueues.octets.total

       64 bit unsigned wrappable counter."
   ::= {pr1645v2EthpdpFInQueuesEntry 67567616}

pr1645v2EthpdpFInQueuesOctetsDirectTx OBJECT-TYPE
   SYNTAX      Counter64
   MAX-ACCESS  read-only
   STATUS      current
   DESCRIPTION
      "Path: ethernetPdp.performance.ifInPriorityQueues.octets.directTx

       64 bit unsigned wrappable counter."
   ::= {pr1645v2EthpdpFInQueuesEntry 67174400}

pr1645v2EthpdpFInQueuesOctetsQueued OBJECT-TYPE
   SYNTAX      Counter64
   MAX-ACCESS  read-only
   STATUS      current
   DESCRIPTION
      "Path: ethernetPdp.performance.ifInPriorityQueues.octets.queued

       64 bit unsigned wrappable counter."
   ::= {pr1645v2EthpdpFInQueuesEntry 67239936}

pr1645v2EthpdpFInQueuesOctetsDropped OBJECT-TYPE
   SYNTAX      Counter64
   MAX-ACCESS  read-only
   STATUS      current
   DESCRIPTION
      "Path: ethernetPdp.performance.ifInPriorityQueues.octets.dropped

       64 bit unsigned wrappable counter."
   ::= {pr1645v2EthpdpFInQueuesEntry 67305472}

pr1645v2EthpdpFInQueuesOctetsRedDropped OBJECT-TYPE
   SYNTAX      Counter64
   MAX-ACCESS  read-only
   STATUS      current
   DESCRIPTION
      "Path: ethernetPdp.performance.ifInPriorityQueues.octets.redDropped

       64 bit unsigned wrappable counter."
   ::= {pr1645v2EthpdpFInQueuesEntry 67502080}

pr1645v2EthpdpFInQueuesOctetsCirTx OBJECT-TYPE
   SYNTAX      Counter64
   MAX-ACCESS  read-only
   STATUS      current
   DESCRIPTION
      "Path: ethernetPdp.performance.ifInPriorityQueues.octets.cirTx

       64 bit unsigned wrappable counter."
   ::= {pr1645v2EthpdpFInQueuesEntry 67371008}

pr1645v2EthpdpFInQueuesOctetsEirTx OBJECT-TYPE
   SYNTAX      Counter64
   MAX-ACCESS  read-only
   STATUS      current
   DESCRIPTION
      "Path: ethernetPdp.performance.ifInPriorityQueues.octets.eirTx

       64 bit unsigned wrappable counter."
   ::= {pr1645v2EthpdpFInQueuesEntry 67436544}

pr1645v2EthpdpFInQueuesOctetsViolateTx OBJECT-TYPE
   SYNTAX      Counter64
   MAX-ACCESS  read-only
   STATUS      current
   DESCRIPTION
      "Path: ethernetPdp.performance.ifInPriorityQueues.octets.violateTx

       64 bit unsigned wrappable counter."
   ::= {pr1645v2EthpdpFInQueuesEntry 67633152}

pr1645v2EthpdpFInQueuesOctetsBandwidth15sec OBJECT-TYPE
   SYNTAX      Integer32
   MAX-ACCESS  read-only
   STATUS      current
   DESCRIPTION
      "Path: ethernetPdp.performance.ifInPriorityQueues.octets.bandwidth.15sec

       unit name = bps
       formula = 8 * ; 8 /"
   ::= {pr1645v2EthpdpFInQueuesEntry 70386944}

pr1645v2EthpdpFInQueuesOctetsBandwidth30sec OBJECT-TYPE
   SYNTAX      Integer32
   MAX-ACCESS  read-only
   STATUS      current
   DESCRIPTION
      "Path: ethernetPdp.performance.ifInPriorityQueues.octets.bandwidth.30sec

       unit name = bps
       formula = 8 * ; 8 /"
   ::= {pr1645v2EthpdpFInQueuesEntry 70388224}

pr1645v2EthpdpFInQueuesOctetsBandwidth1min OBJECT-TYPE
   SYNTAX      Integer32
   MAX-ACCESS  read-only
   STATUS      current
   DESCRIPTION
      "Path: ethernetPdp.performance.ifInPriorityQueues.octets.bandwidth.1min

       unit name = bps
       formula = 8 * ; 8 /"
   ::= {pr1645v2EthpdpFInQueuesEntry 70390784}

pr1645v2EthpdpFInQueuesOctetsBandwidth2min OBJECT-TYPE
   SYNTAX      Integer32
   MAX-ACCESS  read-only
   STATUS      current
   DESCRIPTION
      "Path: ethernetPdp.performance.ifInPriorityQueues.octets.bandwidth.2min

       unit name = bps
       formula = 8 * ; 8 /"
   ::= {pr1645v2EthpdpFInQueuesEntry 70395904}

pr1645v2EthpdpFInQueuesOctetsBandwidth5min OBJECT-TYPE
   SYNTAX      Integer32
   MAX-ACCESS  read-only
   STATUS      current
   DESCRIPTION
      "Path: ethernetPdp.performance.ifInPriorityQueues.octets.bandwidth.5min

       unit name = bps
       formula = 8 * ; 8 /"
   ::= {pr1645v2EthpdpFInQueuesEntry 70411264}

pr1645v2EthpdpFInQueuesH2Performance OBJECT-TYPE
   SYNTAX      SEQUENCE OF Pr1645v2EthpdpFInQueuesH2PerformanceEntry
   MAX-ACCESS  not-accessible
   STATUS      current
   DESCRIPTION
      ""
   ::= {pr1645v2EthpdpFInQueues 83886080}

pr1645v2EthpdpFInQueuesH2PerformanceEntry OBJECT-TYPE
   SYNTAX      Pr1645v2EthpdpFInQueuesH2PerformanceEntry
   MAX-ACCESS  not-accessible
   STATUS      current
   DESCRIPTION
      ""
   INDEX      { pr1645v2EthpdpFInQueuesH2PerformanceGlobalIx,
                pr1645v2EthpdpFInQueuesTableIx,
                pr1645v2EthpdpFInQueuesH2PerformanceTableIx }
   ::= {pr1645v2EthpdpFInQueuesH2Performance 1}

Pr1645v2EthpdpFInQueuesH2PerformanceEntry ::=
   SEQUENCE
      {
      pr1645v2EthpdpFInQueuesH2PerformanceGlobalIx
         GlobalIndex,
      pr1645v2EthpdpFInQueuesH2PerformanceTableIx
         TableIndex,
      pr1645v2EthpdpFInQueuesH2PerformanceSysUpTime
         TimeTicks,
      pr1645v2EthpdpFInQueuesH2PerformanceTotPkts
         Counter64,
      pr1645v2EthpdpFInQueuesH2PerformanceDirTxPkts
         Counter64,
      pr1645v2EthpdpFInQueuesH2PerformanceQdPkts
         Counter64,
      pr1645v2EthpdpFInQueuesH2PerformanceDropPkts
         Counter64,
      pr1645v2EthpdpFInQueuesH2PerformanceRDropPkts
         Counter64,
      pr1645v2EthpdpFInQueuesH2PerformanceCirTxPkts
         Counter64,
      pr1645v2EthpdpFInQueuesH2PerformanceEirTxPkts
         Counter64,
      pr1645v2EthpdpFInQueuesH2PerformanceViolTxPkts
         Counter64,
      pr1645v2EthpdpFInQueuesH2PerformanceTotOcts
         Counter64,
      pr1645v2EthpdpFInQueuesH2PerformanceDirTxOcts
         Counter64,
      pr1645v2EthpdpFInQueuesH2PerformanceQdOcts
         Counter64,
      pr1645v2EthpdpFInQueuesH2PerformanceDropOcts
         Counter64,
      pr1645v2EthpdpFInQueuesH2PerformanceRDropOcts
         Counter64,
      pr1645v2EthpdpFInQueuesH2PerformanceCirTxOcts
         Counter64,
      pr1645v2EthpdpFInQueuesH2PerformanceEirTxOcts
         Counter64,
      pr1645v2EthpdpFInQueuesH2PerformanceViolTxOcts
         Counter64,
      pr1645v2EthpdpFInQueuesH2PerformanceBandwidth
         Integer32
      }

pr1645v2EthpdpFInQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFInQueuesH2PerformanceEntry 10}

pr1645v2EthpdpFInQueuesH2PerformanceTableIx OBJECT-TYPE
   SYNTAX      TableIndex
   MAX-ACCESS  not-accessible
   STATUS      current
   DESCRIPTION
      ""
   ::= {pr1645v2EthpdpFInQueuesH2PerformanceEntry 11}

pr1645v2EthpdpFInQueuesH2PerformanceSysUpTime OBJECT-TYPE
   SYNTAX      TimeTicks
   MAX-ACCESS  read-only
   STATUS      current
   DESCRIPTION
      "Path: ethernetPdp.performance.ifInPriorityQueues.h2Performance.sysUpTime

       Time in centi-second."
   ::= {pr1645v2EthpdpFInQueuesH2PerformanceEntry 16777216}

pr1645v2EthpdpFInQueuesH2PerformanceTotPkts OBJECT-TYPE
   SYNTAX      Counter64
   MAX-ACCESS  read-only
   STATUS      current
   DESCRIPTION
      "Path: ethernetPdp.performance.ifInPriorityQueues.h2Performance.totalPkts

       64 bit unsigned wrappable counter."
   ::= {pr1645v2EthpdpFInQueuesH2PerformanceEntry 234881024}

pr1645v2EthpdpFInQueuesH2PerformanceDirTxPkts OBJECT-TYPE
   SYNTAX      Counter64
   MAX-ACCESS  read-only
   STATUS      current
   DESCRIPTION
      "Path: ethernetPdp.performance.ifInPriorityQueues.h2Performance.directTxPkts

       64 bit unsigned wrappable counter."
   ::= {pr1645v2EthpdpFInQueuesH2PerformanceEntry 33554432}

pr1645v2EthpdpFInQueuesH2PerformanceQdPkts OBJECT-TYPE
   SYNTAX      Counter64
   MAX-ACCESS  read-only
   STATUS      current
   DESCRIPTION
      "Path: ethernetPdp.performance.ifInPriorityQueues.h2Performance.queuedPkts

       64 bit unsigned wrappable counter."
   ::= {pr1645v2EthpdpFInQueuesH2PerformanceEntry 50331648}

pr1645v2EthpdpFInQueuesH2PerformanceDropPkts OBJECT-TYPE
   SYNTAX      Counter64
   MAX-ACCESS  read-only
   STATUS      current
   DESCRIPTION
      "Path: ethernetPdp.performance.ifInPriorityQueues.h2Performance.droppedPkts

       64 bit unsigned wrappable counter."
   ::= {pr1645v2EthpdpFInQueuesH2PerformanceEntry 67108864}

pr1645v2EthpdpFInQueuesH2PerformanceRDropPkts OBJECT-TYPE
   SYNTAX      Counter64
   MAX-ACCESS  read-only
   STATUS      current
   DESCRIPTION
      "Path: ethernetPdp.performance.ifInPriorityQueues.h2Performance.redDroppedPkts

       64 bit unsigned wrappable counter."
   ::= {pr1645v2EthpdpFInQueuesH2PerformanceEntry 201326592}

pr1645v2EthpdpFInQueuesH2PerformanceCirTxPkts OBJECT-TYPE
   SYNTAX      Counter64
   MAX-ACCESS  read-only
   STATUS      current
   DESCRIPTION
      "Path: ethernetPdp.performance.ifInPriorityQueues.h2Performance.cirTxPkts

       64 bit unsigned wrappable counter."
   ::= {pr1645v2EthpdpFInQueuesH2PerformanceEntry 83886080}

pr1645v2EthpdpFInQueuesH2PerformanceEirTxPkts OBJECT-TYPE
   SYNTAX      Counter64
   MAX-ACCESS  read-only
   STATUS      current
   DESCRIPTION
      "Path: ethernetPdp.performance.ifInPriorityQueues.h2Performance.eirTxPkts

       64 bit unsigned wrappable counter."
   ::= {pr1645v2EthpdpFInQueuesH2PerformanceEntry 100663296}

pr1645v2EthpdpFInQueuesH2PerformanceViolTxPkts OBJECT-TYPE
   SYNTAX      Counter64
   MAX-ACCESS  read-only
   STATUS      current
   DESCRIPTION
      "Path: ethernetPdp.performance.ifInPriorityQueues.h2Performance.violateTxPkts

       64 bit unsigned wrappable counter."
   ::= {pr1645v2EthpdpFInQueuesH2PerformanceEntry 301989888}

pr1645v2EthpdpFInQueuesH2PerformanceTotOcts OBJECT-TYPE
   SYNTAX      Counter64
   MAX-ACCESS  read-only
   STATUS      current
   DESCRIPTION
      "Path: ethernetPdp.performance.ifInPriorityQueues.h2Performance.totalOctets

       64 bit unsigned wrappable counter."
   ::= {pr1645v2EthpdpFInQueuesH2PerformanceEntry 251658240}

pr1645v2EthpdpFInQueuesH2PerformanceDirTxOcts OBJECT-TYPE
   SYNTAX      Counter64
   MAX-ACCESS  read-only
   STATUS      current
   DESCRIPTION
      "Path: ethernetPdp.performance.ifInPriorityQueues.h2Performance.directTxOctets

       64 bit unsigned wrappable counter."
   ::= {pr1645v2EthpdpFInQueuesH2PerformanceEntry 117440512}

pr1645v2EthpdpFInQueuesH2PerformanceQdOcts OBJECT-TYPE
   SYNTAX      Counter64
   MAX-ACCESS  read-only
   STATUS      current
   DESCRIPTION
      "Path: ethernetPdp.performance.ifInPriorityQueues.h2Performance.queuedOctets

       64 bit unsigned wrappable counter."
   ::= {pr1645v2EthpdpFInQueuesH2PerformanceEntry 134217728}

pr1645v2EthpdpFInQueuesH2PerformanceDropOcts OBJECT-TYPE
   SYNTAX      Counter64
   MAX-ACCESS  read-only
   STATUS      current
   DESCRIPTION
      "Path: ethernetPdp.performance.ifInPriorityQueues.h2Performance.droppedOctets

       64 bit unsigned wrappable counter."
   ::= {pr1645v2EthpdpFInQueuesH2PerformanceEntry 150994944}

pr1645v2EthpdpFInQueuesH2PerformanceRDropOcts OBJECT-TYPE
   SYNTAX      Counter64
   MAX-ACCESS  read-only
   STATUS      current
   DESCRIPTION
      "Path: ethernetPdp.performance.ifInPriorityQueues.h2Performance.redDroppedOctets

       64 bit unsigned wrappable counter."
   ::= {pr1645v2EthpdpFInQueuesH2PerformanceEntry 218103808}

pr1645v2EthpdpFInQueuesH2PerformanceCirTxOcts OBJECT-TYPE
   SYNTAX      Counter64
   MAX-ACCESS  read-only
   STATUS      current
   DESCRIPTION
      "Path: ethernetPdp.performance.ifInPriorityQueues.h2Performance.cirTxOctets

       64 bit unsigned wrappable counter."
   ::= {pr1645v2EthpdpFInQueuesH2PerformanceEntry 167772160}

pr1645v2EthpdpFInQueuesH2PerformanceEirTxOcts OBJECT-TYPE
   SYNTAX      Counter64
   MAX-ACCESS  read-only
   STATUS      current
   DESCRIPTION
      "Path: ethernetPdp.performance.ifInPriorityQueues.h2Performance.eirTxOctets

       64 bit unsigned wrappable counter."
   ::= {pr1645v2EthpdpFInQueuesH2PerformanceEntry 184549376}

pr1645v2EthpdpFInQueuesH2PerformanceViolTxOcts OBJECT-TYPE
   SYNTAX      Counter64
   MAX-ACCESS  read-only
   STATUS      current
   DESCRIPTION
      "Path: ethernetPdp.performance.ifInPriorityQueues.h2Performance.violateTxOctets

       64 bit unsigned wrappable counter."
   ::= {pr1645v2EthpdpFInQueuesH2PerformanceEntry 318767104}

pr1645v2EthpdpFInQueuesH2PerformanceBandwidth OBJECT-TYPE
   SYNTAX      Integer32
   MAX-ACCESS  read-only
   STATUS      current
   DESCRIPTION
      "Path: ethernetPdp.performance.ifInPriorityQueues.h2Performance.bandwidth

       unit name = bps
       formula = 8 * ; 8 /"
   ::= {pr1645v2EthpdpFInQueuesH2PerformanceEntry 268435456}

pr1645v2EthpdpFInQueuesH24Performance OBJECT-TYPE
   SYNTAX      SEQUENCE OF Pr1645v2EthpdpFInQueuesH24PerformanceEntry
   MAX-ACCESS  not-accessible
   STATUS      current
   DESCRIPTION
      ""
   ::= {pr1645v2EthpdpFInQueues 100663296}

pr1645v2EthpdpFInQueuesH24PerformanceEntry OBJECT-TYPE
   SYNTAX      Pr1645v2EthpdpFInQueuesH24PerformanceEntry
   MAX-ACCESS  not-accessible
   STATUS      current
   DESCRIPTION
      ""
   INDEX      { pr1645v2EthpdpFInQueuesH24PerformanceGlobalIx,
                pr1645v2EthpdpFInQueuesTableIx,
                pr1645v2EthpdpFInQueuesH24PerformanceTableIx }
   ::= {pr1645v2EthpdpFInQueuesH24Performance 1}

Pr1645v2EthpdpFInQueuesH24PerformanceEntry ::=
   SEQUENCE
      {
      pr1645v2EthpdpFInQueuesH24PerformanceGlobalIx
         GlobalIndex,
      pr1645v2EthpdpFInQueuesH24PerformanceTableIx
         TableIndex,
      pr1645v2EthpdpFInQueuesH24PerformanceSysUpTime
         TimeTicks,
      pr1645v2EthpdpFInQueuesH24PerformanceTotPkts
         Counter64,
      pr1645v2EthpdpFInQueuesH24PerformanceDirTxPkts
         Counter64,
      pr1645v2EthpdpFInQueuesH24PerformanceQdPkts
         Counter64,
      pr1645v2EthpdpFInQueuesH24PerformanceDropPkts
         Counter64,
      pr1645v2EthpdpFInQueuesH24PerformanceRDropPkts
         Counter64,
      pr1645v2EthpdpFInQueuesH24PerformanceCirTxPkts
         Counter64,
      pr1645v2EthpdpFInQueuesH24PerformanceEirTxPkts
         Counter64,
      pr1645v2EthpdpFInQueuesH24PerformanceViolTxPkts
         Counter64,
      pr1645v2EthpdpFInQueuesH24PerformanceTotOcts
         Counter64,
      pr1645v2EthpdpFInQueuesH24PerformanceDirTxOcts
         Counter64,
      pr1645v2EthpdpFInQueuesH24PerformanceQdOcts
         Counter64,
      pr1645v2EthpdpFInQueuesH24PerformanceDropOcts
         Counter64,
      pr1645v2EthpdpFInQueuesH24PerformanceRDropOcts
         Counter64,
      pr1645v2EthpdpFInQueuesH24PerformanceCirTxOcts
         Counter64,
      pr1645v2EthpdpFInQueuesH24PerformanceEirTxOcts
         Counter64,
      pr1645v2EthpdpFInQueuesH24PerformanceViolTxOcts
         Counter64,
      pr1645v2EthpdpFInQueuesH24PerformanceBandwidth
         Integer32
      }

pr1645v2EthpdpFInQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFInQueuesH24PerformanceEntry 10}

pr1645v2EthpdpFInQueuesH24PerformanceTableIx OBJECT-TYPE
   SYNTAX      TableIndex
   MAX-ACCESS  not-accessible
   STATUS      current
   DESCRIPTION
      ""
   ::= {pr1645v2EthpdpFInQueuesH24PerformanceEntry 11}

pr1645v2EthpdpFInQueuesH24PerformanceSysUpTime OBJECT-TYPE
   SYNTAX      TimeTicks
   MAX-ACCESS  read-only
   STATUS      current
   DESCRIPTION
      "Path: ethernetPdp.performance.ifInPriorityQueues.h24Performance.sysUpTime

       Time in centi-second."
   ::= {pr1645v2EthpdpFInQueuesH24PerformanceEntry 16777216}

pr1645v2EthpdpFInQueuesH24PerformanceTotPkts OBJECT-TYPE
   SYNTAX      Counter64
   MAX-ACCESS  read-only
   STATUS      current
   DESCRIPTION
      "Path: ethernetPdp.performance.ifInPriorityQueues.h24Performance.totalPkts

       64 bit unsigned wrappable counter."
   ::= {pr1645v2EthpdpFInQueuesH24PerformanceEntry 234881024}

pr1645v2EthpdpFInQueuesH24PerformanceDirTxPkts OBJECT-TYPE
   SYNTAX      Counter64
   MAX-ACCESS  read-only
   STATUS      current
   DESCRIPTION
      "Path: ethernetPdp.performance.ifInPriorityQueues.h24Performance.directTxPkts

       64 bit unsigned wrappable counter."
   ::= {pr1645v2EthpdpFInQueuesH24PerformanceEntry 33554432}

pr1645v2EthpdpFInQueuesH24PerformanceQdPkts OBJECT-TYPE
   SYNTAX      Counter64
   MAX-ACCESS  read-only
   STATUS      current
   DESCRIPTION
      "Path: ethernetPdp.performance.ifInPriorityQueues.h24Performance.queuedPkts

       64 bit unsigned wrappable counter."
   ::= {pr1645v2EthpdpFInQueuesH24PerformanceEntry 50331648}

pr1645v2EthpdpFInQueuesH24PerformanceDropPkts OBJECT-TYPE
   SYNTAX      Counter64
   MAX-ACCESS  read-only
   STATUS      current
   DESCRIPTION
      "Path: ethernetPdp.performance.ifInPriorityQueues.h24Performance.droppedPkts

       64 bit unsigned wrappable counter."
   ::= {pr1645v2EthpdpFInQueuesH24PerformanceEntry 67108864}

pr1645v2EthpdpFInQueuesH24PerformanceRDropPkts OBJECT-TYPE
   SYNTAX      Counter64
   MAX-ACCESS  read-only
   STATUS      current
   DESCRIPTION
      "Path: ethernetPdp.performance.ifInPriorityQueues.h24Performance.redDroppedPkts

       64 bit unsigned wrappable counter."
   ::= {pr1645v2EthpdpFInQueuesH24PerformanceEntry 201326592}

pr1645v2EthpdpFInQueuesH24PerformanceCirTxPkts OBJECT-TYPE
   SYNTAX      Counter64
   MAX-ACCESS  read-only
   STATUS      current
   DESCRIPTION
      "Path: ethernetPdp.performance.ifInPriorityQueues.h24Performance.cirTxPkts

       64 bit unsigned wrappable counter."
   ::= {pr1645v2EthpdpFInQueuesH24PerformanceEntry 83886080}

pr1645v2EthpdpFInQueuesH24PerformanceEirTxPkts OBJECT-TYPE
   SYNTAX      Counter64
   MAX-ACCESS  read-only
   STATUS      current
   DESCRIPTION
      "Path: ethernetPdp.performance.ifInPriorityQueues.h24Performance.eirTxPkts

       64 bit unsigned wrappable counter."
   ::= {pr1645v2EthpdpFInQueuesH24PerformanceEntry 100663296}

pr1645v2EthpdpFInQueuesH24PerformanceViolTxPkts OBJECT-TYPE
   SYNTAX      Counter64
   MAX-ACCESS  read-only
   STATUS      current
   DESCRIPTION
      "Path: ethernetPdp.performance.ifInPriorityQueues.h24Performance.violateTxPkts

       64 bit unsigned wrappable counter."
   ::= {pr1645v2EthpdpFInQueuesH24PerformanceEntry 301989888}

pr1645v2EthpdpFInQueuesH24PerformanceTotOcts OBJECT-TYPE
   SYNTAX      Counter64
   MAX-ACCESS  read-only
   STATUS      current
   DESCRIPTION
      "Path: ethernetPdp.performance.ifInPriorityQueues.h24Performance.totalOctets

       64 bit unsigned wrappable counter."
   ::= {pr1645v2EthpdpFInQueuesH24PerformanceEntry 251658240}

pr1645v2EthpdpFInQueuesH24PerformanceDirTxOcts OBJECT-TYPE
   SYNTAX      Counter64
   MAX-ACCESS  read-only
   STATUS      current
   DESCRIPTION
      "Path: ethernetPdp.performance.ifInPriorityQueues.h24Performance.directTxOctets

       64 bit unsigned wrappable counter."
   ::= {pr1645v2EthpdpFInQueuesH24PerformanceEntry 117440512}

pr1645v2EthpdpFInQueuesH24PerformanceQdOcts OBJECT-TYPE
   SYNTAX      Counter64
   MAX-ACCESS  read-only
   STATUS      current
   DESCRIPTION
      "Path: ethernetPdp.performance.ifInPriorityQueues.h24Performance.queuedOctets

       64 bit unsigned wrappable counter."
   ::= {pr1645v2EthpdpFInQueuesH24PerformanceEntry 134217728}

pr1645v2EthpdpFInQueuesH24PerformanceDropOcts OBJECT-TYPE
   SYNTAX      Counter64
   MAX-ACCESS  read-only
   STATUS      current
   DESCRIPTION
      "Path: ethernetPdp.performance.ifInPriorityQueues.h24Performance.droppedOctets

       64 bit unsigned wrappable counter."
   ::= {pr1645v2EthpdpFInQueuesH24PerformanceEntry 150994944}

pr1645v2EthpdpFInQueuesH24PerformanceRDropOcts OBJECT-TYPE
   SYNTAX      Counter64
   MAX-ACCESS  read-only
   STATUS      current
   DESCRIPTION
      "Path: ethernetPdp.performance.ifInPriorityQueues.h24Performance.redDroppedOctets

       64 bit unsigned wrappable counter."
   ::= {pr1645v2EthpdpFInQueuesH24PerformanceEntry 218103808}

pr1645v2EthpdpFInQueuesH24PerformanceCirTxOcts OBJECT-TYPE
   SYNTAX      Counter64
   MAX-ACCESS  read-only
   STATUS      current
   DESCRIPTION
      "Path: ethernetPdp.performance.ifInPriorityQueues.h24Performance.cirTxOctets

       64 bit unsigned wrappable counter."
   ::= {pr1645v2EthpdpFInQueuesH24PerformanceEntry 167772160}

pr1645v2EthpdpFInQueuesH24PerformanceEirTxOcts OBJECT-TYPE
   SYNTAX      Counter64
   MAX-ACCESS  read-only
   STATUS      current
   DESCRIPTION
      "Path: ethernetPdp.performance.ifInPriorityQueues.h24Performance.eirTxOctets

       64 bit unsigned wrappable counter."
   ::= {pr1645v2EthpdpFInQueuesH24PerformanceEntry 184549376}

pr1645v2EthpdpFInQueuesH24PerformanceViolTxOcts OBJECT-TYPE
   SYNTAX      Counter64
   MAX-ACCESS  read-only
   STATUS      current
   DESCRIPTION
      "Path: ethernetPdp.performance.ifInPriorityQueues.h24Performance.violateTxOctets

       64 bit unsigned wrappable counter."
   ::= {pr1645v2EthpdpFInQueuesH24PerformanceEntry 318767104}

pr1645v2EthpdpFInQueuesH24PerformanceBandwidth OBJECT-TYPE
   SYNTAX      Integer32
   MAX-ACCESS  read-only
   STATUS      current
   DESCRIPTION
      "Path: ethernetPdp.performance.ifInPriorityQueues.h24Performance.bandwidth

       unit name = bps
       formula = 8 * ; 8 /"
   ::= {pr1645v2EthpdpFInQueuesH24PerformanceEntry 268435456}

pr1645v2EthpdpFInQueuesD7Performance OBJECT-TYPE
   SYNTAX      SEQUENCE OF Pr1645v2EthpdpFInQueuesD7PerformanceEntry
   MAX-ACCESS  not-accessible
   STATUS      current
   DESCRIPTION
      ""
   ::= {pr1645v2EthpdpFInQueues 117440512}

pr1645v2EthpdpFInQueuesD7PerformanceEntry OBJECT-TYPE
   SYNTAX      Pr1645v2EthpdpFInQueuesD7PerformanceEntry
   MAX-ACCESS  not-accessible
   STATUS      current
   DESCRIPTION
      ""
   INDEX      { pr1645v2EthpdpFInQueuesD7PerformanceGlobalIx,
                pr1645v2EthpdpFInQueuesTableIx,
                pr1645v2EthpdpFInQueuesD7PerformanceTableIx }
   ::= {pr1645v2EthpdpFInQueuesD7Performance 1}

Pr1645v2EthpdpFInQueuesD7PerformanceEntry ::=
   SEQUENCE
      {
      pr1645v2EthpdpFInQueuesD7PerformanceGlobalIx
         GlobalIndex,
      pr1645v2EthpdpFInQueuesD7PerformanceTableIx
         TableIndex,
      pr1645v2EthpdpFInQueuesD7PerformanceSysUpTime
         TimeTicks,
      pr1645v2EthpdpFInQueuesD7PerformanceTotPkts
         Counter64,
      pr1645v2EthpdpFInQueuesD7PerformanceDirTxPkts
         Counter64,
      pr1645v2EthpdpFInQueuesD7PerformanceQdPkts
         Counter64,
      pr1645v2EthpdpFInQueuesD7PerformanceDropPkts
         Counter64,
      pr1645v2EthpdpFInQueuesD7PerformanceRDropPkts
         Counter64,
      pr1645v2EthpdpFInQueuesD7PerformanceCirTxPkts
         Counter64,
      pr1645v2EthpdpFInQueuesD7PerformanceEirTxPkts
         Counter64,
      pr1645v2EthpdpFInQueuesD7PerformanceViolTxPkts
         Counter64,
      pr1645v2EthpdpFInQueuesD7PerformanceTotOcts
         Counter64,
      pr1645v2EthpdpFInQueuesD7PerformanceDirTxOcts
         Counter64,
      pr1645v2EthpdpFInQueuesD7PerformanceQdOcts
         Counter64,
      pr1645v2EthpdpFInQueuesD7PerformanceDropOcts
         Counter64,
      pr1645v2EthpdpFInQueuesD7PerformanceRDropOcts
         Counter64,
      pr1645v2EthpdpFInQueuesD7PerformanceCirTxOcts
         Counter64,
      pr1645v2EthpdpFInQueuesD7PerformanceEirTxOcts
         Counter64,
      pr1645v2EthpdpFInQueuesD7PerformanceViolTxOcts
         Counter64,
      pr1645v2EthpdpFInQueuesD7PerformanceBandwidth
         Integer32
      }

pr1645v2EthpdpFInQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFInQueuesD7PerformanceEntry 10}

pr1645v2EthpdpFInQueuesD7PerformanceTableIx OBJECT-TYPE
   SYNTAX      TableIndex
   MAX-ACCESS  not-accessible
   STATUS      current
   DESCRIPTION
      ""
   ::= {pr1645v2EthpdpFInQueuesD7PerformanceEntry 11}

pr1645v2EthpdpFInQueuesD7PerformanceSysUpTime OBJECT-TYPE
   SYNTAX      TimeTicks
   MAX-ACCESS  read-only
   STATUS      current
   DESCRIPTION
      "Path: ethernetPdp.performance.ifInPriorityQueues.d7Performance.sysUpTime

       Time in centi-second."
   ::= {pr1645v2EthpdpFInQueuesD7PerformanceEntry 16777216}

pr1645v2EthpdpFInQueuesD7PerformanceTotPkts OBJECT-TYPE
   SYNTAX      Counter64
   MAX-ACCESS  read-only
   STATUS      current
   DESCRIPTION
      "Path: ethernetPdp.performance.ifInPriorityQueues.d7Performance.totalPkts

       64 bit unsigned wrappable counter."
   ::= {pr1645v2EthpdpFInQueuesD7PerformanceEntry 234881024}

pr1645v2EthpdpFInQueuesD7PerformanceDirTxPkts OBJECT-TYPE
   SYNTAX      Counter64
   MAX-ACCESS  read-only
   STATUS      current
   DESCRIPTION
      "Path: ethernetPdp.performance.ifInPriorityQueues.d7Performance.directTxPkts

       64 bit unsigned wrappable counter."
   ::= {pr1645v2EthpdpFInQueuesD7PerformanceEntry 33554432}

pr1645v2EthpdpFInQueuesD7PerformanceQdPkts OBJECT-TYPE
   SYNTAX      Counter64
   MAX-ACCESS  read-only
   STATUS      current
   DESCRIPTION
      "Path: ethernetPdp.performance.ifInPriorityQueues.d7Performance.queuedPkts

       64 bit unsigned wrappable counter."
   ::= {pr1645v2EthpdpFInQueuesD7PerformanceEntry 50331648}

pr1645v2EthpdpFInQueuesD7PerformanceDropPkts OBJECT-TYPE
   SYNTAX      Counter64
   MAX-ACCESS  read-only
   STATUS      current
   DESCRIPTION
      "Path: ethernetPdp.performance.ifInPriorityQueues.d7Performance.droppedPkts

       64 bit unsigned wrappable counter."
   ::= {pr1645v2EthpdpFInQueuesD7PerformanceEntry 67108864}

pr1645v2EthpdpFInQueuesD7PerformanceRDropPkts OBJECT-TYPE
   SYNTAX      Counter64
   MAX-ACCESS  read-only
   STATUS      current
   DESCRIPTION
      "Path: ethernetPdp.performance.ifInPriorityQueues.d7Performance.redDroppedPkts

       64 bit unsigned wrappable counter."
   ::= {pr1645v2EthpdpFInQueuesD7PerformanceEntry 201326592}

pr1645v2EthpdpFInQueuesD7PerformanceCirTxPkts OBJECT-TYPE
   SYNTAX      Counter64
   MAX-ACCESS  read-only
   STATUS      current
   DESCRIPTION
      "Path: ethernetPdp.performance.ifInPriorityQueues.d7Performance.cirTxPkts

       64 bit unsigned wrappable counter."
   ::= {pr1645v2EthpdpFInQueuesD7PerformanceEntry 83886080}

pr1645v2EthpdpFInQueuesD7PerformanceEirTxPkts OBJECT-TYPE
   SYNTAX      Counter64
   MAX-ACCESS  read-only
   STATUS      current
   DESCRIPTION
      "Path: ethernetPdp.performance.ifInPriorityQueues.d7Performance.eirTxPkts

       64 bit unsigned wrappable counter."
   ::= {pr1645v2EthpdpFInQueuesD7PerformanceEntry 100663296}

pr1645v2EthpdpFInQueuesD7PerformanceViolTxPkts OBJECT-TYPE
   SYNTAX      Counter64
   MAX-ACCESS  read-only
   STATUS      current
   DESCRIPTION
      "Path: ethernetPdp.performance.ifInPriorityQueues.d7Performance.violateTxPkts

       64 bit unsigned wrappable counter."
   ::= {pr1645v2EthpdpFInQueuesD7PerformanceEntry 301989888}

pr1645v2EthpdpFInQueuesD7PerformanceTotOcts OBJECT-TYPE
   SYNTAX      Counter64
   MAX-ACCESS  read-only
   STATUS      current
   DESCRIPTION
      "Path: ethernetPdp.performance.ifInPriorityQueues.d7Performance.totalOctets

       64 bit unsigned wrappable counter."
   ::= {pr1645v2EthpdpFInQueuesD7PerformanceEntry 251658240}

pr1645v2EthpdpFInQueuesD7PerformanceDirTxOcts OBJECT-TYPE
   SYNTAX      Counter64
   MAX-ACCESS  read-only
   STATUS      current
   DESCRIPTION
      "Path: ethernetPdp.performance.ifInPriorityQueues.d7Performance.directTxOctets

       64 bit unsigned wrappable counter."
   ::= {pr1645v2EthpdpFInQueuesD7PerformanceEntry 117440512}

pr1645v2EthpdpFInQueuesD7PerformanceQdOcts OBJECT-TYPE
   SYNTAX      Counter64
   MAX-ACCESS  read-only
   STATUS      current
   DESCRIPTION
      "Path: ethernetPdp.performance.ifInPriorityQueues.d7Performance.queuedOctets

       64 bit unsigned wrappable counter."
   ::= {pr1645v2EthpdpFInQueuesD7PerformanceEntry 134217728}

pr1645v2EthpdpFInQueuesD7PerformanceDropOcts OBJECT-TYPE
   SYNTAX      Counter64
   MAX-ACCESS  read-only
   STATUS      current
   DESCRIPTION
      "Path: ethernetPdp.performance.ifInPriorityQueues.d7Performance.droppedOctets

       64 bit unsigned wrappable counter."
   ::= {pr1645v2EthpdpFInQueuesD7PerformanceEntry 150994944}

pr1645v2EthpdpFInQueuesD7PerformanceRDropOcts OBJECT-TYPE
   SYNTAX      Counter64
   MAX-ACCESS  read-only
   STATUS      current
   DESCRIPTION
      "Path: ethernetPdp.performance.ifInPriorityQueues.d7Performance.redDroppedOctets

       64 bit unsigned wrappable counter."
   ::= {pr1645v2EthpdpFInQueuesD7PerformanceEntry 218103808}

pr1645v2EthpdpFInQueuesD7PerformanceCirTxOcts OBJECT-TYPE
   SYNTAX      Counter64
   MAX-ACCESS  read-only
   STATUS      current
   DESCRIPTION
      "Path: ethernetPdp.performance.ifInPriorityQueues.d7Performance.cirTxOctets

       64 bit unsigned wrappable counter."
   ::= {pr1645v2EthpdpFInQueuesD7PerformanceEntry 167772160}

pr1645v2EthpdpFInQueuesD7PerformanceEirTxOcts OBJECT-TYPE
   SYNTAX      Counter64
   MAX-ACCESS  read-only
   STATUS      current
   DESCRIPTION
      "Path: ethernetPdp.performance.ifInPriorityQueues.d7Performance.eirTxOctets

       64 bit unsigned wrappable counter."
   ::= {pr1645v2EthpdpFInQueuesD7PerformanceEntry 184549376}

pr1645v2EthpdpFInQueuesD7PerformanceViolTxOcts OBJECT-TYPE
   SYNTAX      Counter64
   MAX-ACCESS  read-only
   STATUS      current
   DESCRIPTION
      "Path: ethernetPdp.performance.ifInPriorityQueues.d7Performance.violateTxOctets

       64 bit unsigned wrappable counter."
   ::= {pr1645v2EthpdpFInQueuesD7PerformanceEntry 318767104}

pr1645v2EthpdpFInQueuesD7PerformanceBandwidth OBJECT-TYPE
   SYNTAX      Integer32
   MAX-ACCESS  read-only
   STATUS      current
   DESCRIPTION
      "Path: ethernetPdp.performance.ifInPriorityQueues.d7Performance.bandwidth

       unit name = bps
       formula = 8 * ; 8 /"
   ::= {pr1645v2EthpdpFInQueuesD7PerformanceEntry 268435456}


pr1645v2EthpdpFInBandwidth OBJECT IDENTIFIER ::= {pr1645v2EthpdpF 181}

pr1645v2EthpdpFInBandwidthSSCTable OBJECT-TYPE
   SYNTAX      SEQUENCE OF Pr1645v2EthpdpFInBandwidthEntry
   MAX-ACCESS  not-accessible
   STATUS      current
   DESCRIPTION
      "bandwidth"
   ::= {pr1645v2EthpdpFInBandwidth 1}

pr1645v2EthpdpFInBandwidthEntry OBJECT-TYPE
   SYNTAX      Pr1645v2EthpdpFInBandwidthEntry
   MAX-ACCESS  not-accessible
   STATUS      current
   DESCRIPTION
      ""
   INDEX      { pr1645v2EthpdpFInBandwidthGlobalIx }
   ::= {pr1645v2EthpdpFInBandwidthSSCTable 1}

Pr1645v2EthpdpFInBandwidthEntry ::=
   SEQUENCE
      {
      pr1645v2EthpdpFInBandwidthGlobalIx
         GlobalIndex,
      pr1645v2EthpdpFInBandwidth15sec
         Integer32,
      pr1645v2EthpdpFInBandwidth30sec
         Integer32,
      pr1645v2EthpdpFInBandwidth1min
         Integer32,
      pr1645v2EthpdpFInBandwidth2min
         Integer32,
      pr1645v2EthpdpFInBandwidth5min
         Integer32
      }

pr1645v2EthpdpFInBandwidthGlobalIx OBJECT-TYPE
   SYNTAX      GlobalIndex
   MAX-ACCESS  not-accessible
   STATUS      current
   DESCRIPTION
      "The value of the tlsCntTreeGlobalIndex of the MANAGED OBJECT."
   ::= {pr1645v2EthpdpFInBandwidthEntry 10}

pr1645v2EthpdpFInBandwidth15sec OBJECT-TYPE
   SYNTAX      Integer32
   MAX-ACCESS  read-only
   STATUS      current
   DESCRIPTION
      "Path: ethernetPdp.performance.ifInBandwidth.15sec

       unit name = bps
       formula = 8 * ; 8 /"
   ::= {pr1645v2EthpdpFInBandwidthEntry 83886080}

pr1645v2EthpdpFInBandwidth30sec OBJECT-TYPE
   SYNTAX      Integer32
   MAX-ACCESS  read-only
   STATUS      current
   DESCRIPTION
      "Path: ethernetPdp.performance.ifInBandwidth.30sec

       unit name = bps
       formula = 8 * ; 8 /"
   ::= {pr1645v2EthpdpFInBandwidthEntry 167772160}

pr1645v2EthpdpFInBandwidth1min OBJECT-TYPE
   SYNTAX      Integer32
   MAX-ACCESS  read-only
   STATUS      current
   DESCRIPTION
      "Path: ethernetPdp.performance.ifInBandwidth.1min

       unit name = bps
       formula = 8 * ; 8 /"
   ::= {pr1645v2EthpdpFInBandwidthEntry 335544320}

pr1645v2EthpdpFInBandwidth2min OBJECT-TYPE
   SYNTAX      Integer32
   MAX-ACCESS  read-only
   STATUS      current
   DESCRIPTION
      "Path: ethernetPdp.performance.ifInBandwidth.2min

       unit name = bps
       formula = 8 * ; 8 /"
   ::= {pr1645v2EthpdpFInBandwidthEntry 671088640}

pr1645v2EthpdpFInBandwidth5min OBJECT-TYPE
   SYNTAX      Integer32
   MAX-ACCESS  read-only
   STATUS      current
   DESCRIPTION
      "Path: ethernetPdp.performance.ifInBandwidth.5min

       unit name = bps
       formula = 8 * ; 8 /"
   ::= {pr1645v2EthpdpFInBandwidthEntry 1677721600}


pr1645v2EthpdpFOutOctets OBJECT IDENTIFIER ::= {pr1645v2EthpdpF 115}

pr1645v2EthpdpFOutOctetsTable OBJECT-TYPE
   SYNTAX      SEQUENCE OF Pr1645v2EthpdpFOutOctetsEntry
   MAX-ACCESS  not-accessible
   STATUS      current
   DESCRIPTION
      "ifOutOctets"
   ::= {pr1645v2EthpdpFOutOctets 1}

pr1645v2EthpdpFOutOctetsEntry OBJECT-TYPE
   SYNTAX      Pr1645v2EthpdpFOutOctetsEntry
   MAX-ACCESS  not-accessible
   STATUS      current
   DESCRIPTION
      ""
   INDEX      { pr1645v2EthpdpFOutOctetsGlobalIx }
   ::= {pr1645v2EthpdpFOutOctetsTable 1}

Pr1645v2EthpdpFOutOctetsEntry ::=
   SEQUENCE
      {
      pr1645v2EthpdpFOutOctetsGlobalIx
         GlobalIndex,
      pr1645v2EthpdpFOutOctetsValue
         Counter64
      }

pr1645v2EthpdpFOutOctetsGlobalIx OBJECT-TYPE
   SYNTAX      GlobalIndex
   MAX-ACCESS  not-accessible
   STATUS      current
   DESCRIPTION
      "The value of the tlsCntTreeGlobalIndex of the MANAGED OBJECT."
   ::= {pr1645v2EthpdpFOutOctetsEntry 10}

pr1645v2EthpdpFOutOctetsValue OBJECT-TYPE
   SYNTAX      Counter64
   MAX-ACCESS  read-only
   STATUS      current
   DESCRIPTION
      "Path: ethernetPdp.performance.ifOutOctets

       64 bit unsigned wrappable counter."
   ::= {pr1645v2EthpdpFOutOctetsEntry 2147483648}


pr1645v2EthpdpFOutUcastPkts OBJECT IDENTIFIER ::= {pr1645v2EthpdpF 116}

pr1645v2EthpdpFOutUcastPktsTable OBJECT-TYPE
   SYNTAX      SEQUENCE OF Pr1645v2EthpdpFOutUcastPktsEntry
   MAX-ACCESS  not-accessible
   STATUS      current
   DESCRIPTION
      "ifOutUcastPkts"
   ::= {pr1645v2EthpdpFOutUcastPkts 1}

pr1645v2EthpdpFOutUcastPktsEntry OBJECT-TYPE
   SYNTAX      Pr1645v2EthpdpFOutUcastPktsEntry
   MAX-ACCESS  not-accessible
   STATUS      current
   DESCRIPTION
      ""
   INDEX      { pr1645v2EthpdpFOutUcastPktsGlobalIx }
   ::= {pr1645v2EthpdpFOutUcastPktsTable 1}

Pr1645v2EthpdpFOutUcastPktsEntry ::=
   SEQUENCE
      {
      pr1645v2EthpdpFOutUcastPktsGlobalIx
         GlobalIndex,
      pr1645v2EthpdpFOutUcastPktsValue
         Counter64
      }

pr1645v2EthpdpFOutUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpFOutUcastPktsEntry 10}

pr1645v2EthpdpFOutUcastPktsValue OBJECT-TYPE
   SYNTAX      Counter64
   MAX-ACCESS  read-only
   STATUS      current
   DESCRIPTION
      "Path: ethernetPdp.performance.ifOutUcastPkts

       64 bit unsigned wrappable counter."
   ::= {pr1645v2EthpdpFOutUcastPktsEntry 2147483648}


pr1645v2EthpdpFOutNUcastPkts OBJECT IDENTIFIER ::= {pr1645v2EthpdpF 117}

pr1645v2EthpdpFOutNUcastPktsTable OBJECT-TYPE
   SYNTAX      SEQUENCE OF Pr1645v2EthpdpFOutNUcastPktsEntry
   MAX-ACCESS  not-accessible
   STATUS      current
   DESCRIPTION
      "ifOutNUcastPkts"
   ::= {pr1645v2EthpdpFOutNUcastPkts 1}

pr1645v2EthpdpFOutNUcastPktsEntry OBJECT-TYPE
   SYNTAX      Pr1645v2EthpdpFOutNUcastPktsEntry
   MAX-ACCESS  not-accessible
   STATUS      current
   DESCRIPTION
      ""
   INDEX      { pr1645v2EthpdpFOutNUcastPktsGlobalIx }
   ::= {pr1645v2EthpdpFOutNUcastPktsTable 1}

Pr1645v2EthpdpFOutNUcastPktsEntry ::=
   SEQUENCE
      {
      pr1645v2EthpdpFOutNUcastPktsGlobalIx
         GlobalIndex,
      pr1645v2EthpdpFOutNUcastPktsValue
         Counter64
      }

pr1645v2EthpdpFOutNUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpFOutNUcastPktsEntry 10}

pr1645v2EthpdpFOutNUcastPktsValue OBJECT-TYPE
   SYNTAX      Counter64
   MAX-ACCESS  read-only
   STATUS      current
   DESCRIPTION
      "Path: ethernetPdp.performance.ifOutNUcastPkts

       64 bit unsigned wrappable counter."
   ::= {pr1645v2EthpdpFOutNUcastPktsEntry 2147483648}


pr1645v2EthpdpFOutDiscards OBJECT IDENTIFIER ::= {pr1645v2EthpdpF 118}

pr1645v2EthpdpFOutDiscardsTable OBJECT-TYPE
   SYNTAX      SEQUENCE OF Pr1645v2EthpdpFOutDiscardsEntry
   MAX-ACCESS  not-accessible
   STATUS      current
   DESCRIPTION
      "ifOutDiscards"
   ::= {pr1645v2EthpdpFOutDiscards 1}

pr1645v2EthpdpFOutDiscardsEntry OBJECT-TYPE
   SYNTAX      Pr1645v2EthpdpFOutDiscardsEntry
   MAX-ACCESS  not-accessible
   STATUS      current
   DESCRIPTION
      ""
   INDEX      { pr1645v2EthpdpFOutDiscardsGlobalIx }
   ::= {pr1645v2EthpdpFOutDiscardsTable 1}

Pr1645v2EthpdpFOutDiscardsEntry ::=
   SEQUENCE
      {
      pr1645v2EthpdpFOutDiscardsGlobalIx
         GlobalIndex,
      pr1645v2EthpdpFOutDiscardsValue
         Counter64
      }

pr1645v2EthpdpFOutDiscardsGlobalIx OBJECT-TYPE
   SYNTAX      GlobalIndex
   MAX-ACCESS  not-accessible
   STATUS      current
   DESCRIPTION
      "The value of the tlsCntTreeGlobalIndex of the MANAGED OBJECT."
   ::= {pr1645v2EthpdpFOutDiscardsEntry 10}

pr1645v2EthpdpFOutDiscardsValue OBJECT-TYPE
   SYNTAX      Counter64
   MAX-ACCESS  read-only
   STATUS      current
   DESCRIPTION
      "Path: ethernetPdp.performance.ifOutDiscards

       64 bit unsigned wrappable counter."
   ::= {pr1645v2EthpdpFOutDiscardsEntry 2147483648}


pr1645v2EthpdpFOutErrors OBJECT IDENTIFIER ::= {pr1645v2EthpdpF 119}

pr1645v2EthpdpFOutErrorsTable OBJECT-TYPE
   SYNTAX      SEQUENCE OF Pr1645v2EthpdpFOutErrorsEntry
   MAX-ACCESS  not-accessible
   STATUS      current
   DESCRIPTION
      "ifOutErrors"
   ::= {pr1645v2EthpdpFOutErrors 1}

pr1645v2EthpdpFOutErrorsEntry OBJECT-TYPE
   SYNTAX      Pr1645v2EthpdpFOutErrorsEntry
   MAX-ACCESS  not-accessible
   STATUS      current
   DESCRIPTION
      ""
   INDEX      { pr1645v2EthpdpFOutErrorsGlobalIx }
   ::= {pr1645v2EthpdpFOutErrorsTable 1}

Pr1645v2EthpdpFOutErrorsEntry ::=
   SEQUENCE
      {
      pr1645v2EthpdpFOutErrorsGlobalIx
         GlobalIndex,
      pr1645v2EthpdpFOutErrorsValue
         Counter64
      }

pr1645v2EthpdpFOutErrorsGlobalIx OBJECT-TYPE
   SYNTAX      GlobalIndex
   MAX-ACCESS  not-accessible
   STATUS      current
   DESCRIPTION
      "The value of the tlsCntTreeGlobalIndex of the MANAGED OBJECT."
   ::= {pr1645v2EthpdpFOutErrorsEntry 10}

pr1645v2EthpdpFOutErrorsValue OBJECT-TYPE
   SYNTAX      Counter64
   MAX-ACCESS  read-only
   STATUS      current
   DESCRIPTION
      "Path: ethernetPdp.performance.ifOutErrors

       64 bit unsigned wrappable counter."
   ::= {pr1645v2EthpdpFOutErrorsEntry 2147483648}


pr1645v2EthpdpFOutQLen OBJECT IDENTIFIER ::= {pr1645v2EthpdpF 120}

pr1645v2EthpdpFOutQLenTable OBJECT-TYPE
   SYNTAX      SEQUENCE OF Pr1645v2EthpdpFOutQLenEntry
   MAX-ACCESS  not-accessible
   STATUS      current
   DESCRIPTION
      "ifOutQLen"
   ::= {pr1645v2EthpdpFOutQLen 1}

pr1645v2EthpdpFOutQLenEntry OBJECT-TYPE
   SYNTAX      Pr1645v2EthpdpFOutQLenEntry
   MAX-ACCESS  not-accessible
   STATUS      current
   DESCRIPTION
      ""
   INDEX      { pr1645v2EthpdpFOutQLenGlobalIx }
   ::= {pr1645v2EthpdpFOutQLenTable 1}

Pr1645v2EthpdpFOutQLenEntry ::=
   SEQUENCE
      {
      pr1645v2EthpdpFOutQLenGlobalIx
         GlobalIndex,
      pr1645v2EthpdpFOutQLenValue
         Gauge32
      }

pr1645v2EthpdpFOutQLenGlobalIx OBJECT-TYPE
   SYNTAX      GlobalIndex
   MAX-ACCESS  not-accessible
   STATUS      current
   DESCRIPTION
      "The value of the tlsCntTreeGlobalIndex of the MANAGED OBJECT."
   ::= {pr1645v2EthpdpFOutQLenEntry 10}

pr1645v2EthpdpFOutQLenValue OBJECT-TYPE
   SYNTAX      Gauge32
   MAX-ACCESS  read-only
   STATUS      current
   DESCRIPTION
      "Path: ethernetPdp.performance.ifOutQLen

       32 bit unsigned gauge value."
   ::= {pr1645v2EthpdpFOutQLenEntry 2147483648}


pr1645v2EthpdpFOutDropEx OBJECT IDENTIFIER ::= {pr1645v2EthpdpF 127}

pr1645v2EthpdpFOutDropExTable OBJECT-TYPE
   SYNTAX      SEQUENCE OF Pr1645v2EthpdpFOutDropExEntry
   MAX-ACCESS  not-accessible
   STATUS      current
   DESCRIPTION
      "ifOutDiscards"
   ::= {pr1645v2EthpdpFOutDropEx 1}

pr1645v2EthpdpFOutDropExEntry OBJECT-TYPE
   SYNTAX      Pr1645v2EthpdpFOutDropExEntry
   MAX-ACCESS  not-accessible
   STATUS      current
   DESCRIPTION
      ""
   INDEX      { pr1645v2EthpdpFOutDropExGlobalIx }
   ::= {pr1645v2EthpdpFOutDropExTable 1}

Pr1645v2EthpdpFOutDropExEntry ::=
   SEQUENCE
      {
      pr1645v2EthpdpFOutDropExGlobalIx
         GlobalIndex,
      pr1645v2EthpdpFOutDropExValue
         Counter64
      }

pr1645v2EthpdpFOutDropExGlobalIx OBJECT-TYPE
   SYNTAX      GlobalIndex
   MAX-ACCESS  not-accessible
   STATUS      current
   DESCRIPTION
      "The value of the tlsCntTreeGlobalIndex of the MANAGED OBJECT."
   ::= {pr1645v2EthpdpFOutDropExEntry 10}

pr1645v2EthpdpFOutDropExValue OBJECT-TYPE
   SYNTAX      Counter64
   MAX-ACCESS  read-only
   STATUS      current
   DESCRIPTION
      "Path: ethernetPdp.performance.ifOutDropLevelExceeded

       64 bit unsigned wrappable counter."
   ::= {pr1645v2EthpdpFOutDropExEntry 2147483648}


pr1645v2EthpdpFOutDropNoArp OBJECT IDENTIFIER ::= {pr1645v2EthpdpF 134}

pr1645v2EthpdpFOutDropNoArpTable OBJECT-TYPE
   SYNTAX      SEQUENCE OF Pr1645v2EthpdpFOutDropNoArpEntry
   MAX-ACCESS  not-accessible
   STATUS      current
   DESCRIPTION
      "ifOutDiscards"
   ::= {pr1645v2EthpdpFOutDropNoArp 1}

pr1645v2EthpdpFOutDropNoArpEntry OBJECT-TYPE
   SYNTAX      Pr1645v2EthpdpFOutDropNoArpEntry
   MAX-ACCESS  not-accessible
   STATUS      current
   DESCRIPTION
      ""
   INDEX      { pr1645v2EthpdpFOutDropNoArpGlobalIx }
   ::= {pr1645v2EthpdpFOutDropNoArpTable 1}

Pr1645v2EthpdpFOutDropNoArpEntry ::=
   SEQUENCE
      {
      pr1645v2EthpdpFOutDropNoArpGlobalIx
         GlobalIndex,
      pr1645v2EthpdpFOutDropNoArpValue
         Counter64
      }

pr1645v2EthpdpFOutDropNoArpGlobalIx OBJECT-TYPE
   SYNTAX      GlobalIndex
   MAX-ACCESS  not-accessible
   STATUS      current
   DESCRIPTION
      "The value of the tlsCntTreeGlobalIndex of the MANAGED OBJECT."
   ::= {pr1645v2EthpdpFOutDropNoArpEntry 10}

pr1645v2EthpdpFOutDropNoArpValue OBJECT-TYPE
   SYNTAX      Counter64
   MAX-ACCESS  read-only
   STATUS      current
   DESCRIPTION
      "Path: ethernetPdp.performance.ifOutDiscardsNoArp

       64 bit unsigned wrappable counter."
   ::= {pr1645v2EthpdpFOutDropNoArpEntry 2147483648}


pr1645v2EthpdpFOutDropFilter OBJECT IDENTIFIER ::= {pr1645v2EthpdpF 138}

pr1645v2EthpdpFOutDropFilterTable OBJECT-TYPE
   SYNTAX      SEQUENCE OF Pr1645v2EthpdpFOutDropFilterEntry
   MAX-ACCESS  not-accessible
   STATUS      current
   DESCRIPTION
      "ifOutDiscards"
   ::= {pr1645v2EthpdpFOutDropFilter 1}

pr1645v2EthpdpFOutDropFilterEntry OBJECT-TYPE
   SYNTAX      Pr1645v2EthpdpFOutDropFilterEntry
   MAX-ACCESS  not-accessible
   STATUS      current
   DESCRIPTION
      ""
   INDEX      { pr1645v2EthpdpFOutDropFilterGlobalIx }
   ::= {pr1645v2EthpdpFOutDropFilterTable 1}

Pr1645v2EthpdpFOutDropFilterEntry ::=
   SEQUENCE
      {
      pr1645v2EthpdpFOutDropFilterGlobalIx
         GlobalIndex,
      pr1645v2EthpdpFOutDropFilterValue
         Counter64
      }

pr1645v2EthpdpFOutDropFilterGlobalIx OBJECT-TYPE
   SYNTAX      GlobalIndex
   MAX-ACCESS  not-accessible
   STATUS      current
   DESCRIPTION
      "The value of the tlsCntTreeGlobalIndex of the MANAGED OBJECT."
   ::= {pr1645v2EthpdpFOutDropFilterEntry 10}

pr1645v2EthpdpFOutDropFilterValue OBJECT-TYPE
   SYNTAX      Counter64
   MAX-ACCESS  read-only
   STATUS      current
   DESCRIPTION
      "Path: ethernetPdp.performance.ifOutDiscardsFilter

       64 bit unsigned wrappable counter."
   ::= {pr1645v2EthpdpFOutDropFilterEntry 2147483648}


pr1645v2EthpdpFOutQueues OBJECT IDENTIFIER ::= {pr1645v2EthpdpF 129}

pr1645v2EthpdpFOutQueuesSSCTable OBJECT-TYPE
   SYNTAX      SEQUENCE OF Pr1645v2EthpdpFOutQueuesEntry
   MAX-ACCESS  not-accessible
   STATUS      current
   DESCRIPTION
      "Queue Lengths"
   ::= {pr1645v2EthpdpFOutQueues 1}

pr1645v2EthpdpFOutQueuesEntry OBJECT-TYPE
   SYNTAX      Pr1645v2EthpdpFOutQueuesEntry
   MAX-ACCESS  not-accessible
   STATUS      current
   DESCRIPTION
      ""
   INDEX      { pr1645v2EthpdpFOutQueuesGlobalIx,
                pr1645v2EthpdpFOutQueuesTableIx }
   ::= {pr1645v2EthpdpFOutQueuesSSCTable 1}

Pr1645v2EthpdpFOutQueuesEntry ::=
   SEQUENCE
      {
      pr1645v2EthpdpFOutQueuesGlobalIx
         GlobalIndex,
      pr1645v2EthpdpFOutQueuesTableIx
         TableIndex,
      pr1645v2EthpdpFOutQueuesName
         INTEGER,
      pr1645v2EthpdpFOutQueuesLength
         Integer32,
      pr1645v2EthpdpFOutQueuesOctetLength
         Integer32,
      pr1645v2EthpdpFOutQueuesRedLength
         Integer32,
      pr1645v2EthpdpFOutQueuesPacketsTotal
         Counter64,
      pr1645v2EthpdpFOutQueuesPacketsDirectTx
         Counter64,
      pr1645v2EthpdpFOutQueuesPacketsQueued
         Counter64,
      pr1645v2EthpdpFOutQueuesPacketsDropped
         Counter64,
      pr1645v2EthpdpFOutQueuesPacketsRedDropped
         Counter64,
      pr1645v2EthpdpFOutQueuesPacketsCirTx
         Counter64,
      pr1645v2EthpdpFOutQueuesPacketsEirTx
         Counter64,
      pr1645v2EthpdpFOutQueuesPacketsViolateTx
         Counter64,
      pr1645v2EthpdpFOutQueuesOctetsTotal
         Counter64,
      pr1645v2EthpdpFOutQueuesOctetsDirectTx
         Counter64,
      pr1645v2EthpdpFOutQueuesOctetsQueued
         Counter64,
      pr1645v2EthpdpFOutQueuesOctetsDropped
         Counter64,
      pr1645v2EthpdpFOutQueuesOctetsRedDropped
         Counter64,
      pr1645v2EthpdpFOutQueuesOctetsCirTx
         Counter64,
      pr1645v2EthpdpFOutQueuesOctetsEirTx
         Counter64,
      pr1645v2EthpdpFOutQueuesOctetsViolateTx
         Counter64,
      pr1645v2EthpdpFOutQueuesOctetsBandwidth15sec
         Integer32,
      pr1645v2EthpdpFOutQueuesOctetsBandwidth30sec
         Integer32,
      pr1645v2EthpdpFOutQueuesOctetsBandwidth1min
         Integer32,
      pr1645v2EthpdpFOutQueuesOctetsBandwidth2min
         Integer32,
      pr1645v2EthpdpFOutQueuesOctetsBandwidth5min
         Integer32
      }

pr1645v2EthpdpFOutQueuesGlobalIx OBJECT-TYPE
   SYNTAX      GlobalIndex
   MAX-ACCESS  not-accessible
   STATUS      current
   DESCRIPTION
      "The value of the tlsCntTreeGlobalIndex of the MANAGED OBJECT."
   ::= {pr1645v2EthpdpFOutQueuesEntry 10}

pr1645v2EthpdpFOutQueuesTableIx OBJECT-TYPE
   SYNTAX      TableIndex
   MAX-ACCESS  not-accessible
   STATUS      current
   DESCRIPTION
      ""
   ::= {pr1645v2EthpdpFOutQueuesEntry 11}

pr1645v2EthpdpFOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernetPdp.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthpdpFOutQueuesEntry 16777216}

pr1645v2EthpdpFOutQueuesLength OBJECT-TYPE
   SYNTAX      Integer32
   MAX-ACCESS  read-only
   STATUS      current
   DESCRIPTION
      "Path: ethernetPdp.performance.ifOutPriorityQueues.length"
   ::= {pr1645v2EthpdpFOutQueuesEntry 33554432}

pr1645v2EthpdpFOutQueuesOctetLength OBJECT-TYPE
   SYNTAX      Integer32
   MAX-ACCESS  read-only
   STATUS      current
   DESCRIPTION
      "Path: ethernetPdp.performance.ifOutPriorityQueues.octetLength"
   ::= {pr1645v2EthpdpFOutQueuesEntry 150994944}

pr1645v2EthpdpFOutQueuesRedLength OBJECT-TYPE
   SYNTAX      Integer32
   MAX-ACCESS  read-only
   STATUS      current
   DESCRIPTION
      "Path: ethernetPdp.performance.ifOutPriorityQueues.redLength"
   ::= {pr1645v2EthpdpFOutQueuesEntry 134217728}

pr1645v2EthpdpFOutQueuesPacketsTotal OBJECT-TYPE
   SYNTAX      Counter64
   MAX-ACCESS  read-only
   STATUS      current
   DESCRIPTION
      "Path: ethernetPdp.performance.ifOutPriorityQueues.packets.total

       64 bit unsigned wrappable counter."
   ::= {pr1645v2EthpdpFOutQueuesEntry 50790400}

pr1645v2EthpdpFOutQueuesPacketsDirectTx OBJECT-TYPE
   SYNTAX      Counter64
   MAX-ACCESS  read-only
   STATUS      current
   DESCRIPTION
      "Path: ethernetPdp.performance.ifOutPriorityQueues.packets.directTx

       64 bit unsigned wrappable counter."
   ::= {pr1645v2EthpdpFOutQueuesEntry 50397184}

pr1645v2EthpdpFOutQueuesPacketsQueued OBJECT-TYPE
   SYNTAX      Counter64
   MAX-ACCESS  read-only
   STATUS      current
   DESCRIPTION
      "Path: ethernetPdp.performance.ifOutPriorityQueues.packets.queued

       64 bit unsigned wrappable counter."
   ::= {pr1645v2EthpdpFOutQueuesEntry 50462720}

pr1645v2EthpdpFOutQueuesPacketsDropped OBJECT-TYPE
   SYNTAX      Counter64
   MAX-ACCESS  read-only
   STATUS      current
   DESCRIPTION
      "Path: ethernetPdp.performance.ifOutPriorityQueues.packets.dropped

       64 bit unsigned wrappable counter."
   ::= {pr1645v2EthpdpFOutQueuesEntry 50528256}

pr1645v2EthpdpFOutQueuesPacketsRedDropped OBJECT-TYPE
   SYNTAX      Counter64
   MAX-ACCESS  read-only
   STATUS      current
   DESCRIPTION
      "Path: ethernetPdp.performance.ifOutPriorityQueues.packets.redDropped

       64 bit unsigned wrappable counter."
   ::= {pr1645v2EthpdpFOutQueuesEntry 50724864}

pr1645v2EthpdpFOutQueuesPacketsCirTx OBJECT-TYPE
   SYNTAX      Counter64
   MAX-ACCESS  read-only
   STATUS      current
   DESCRIPTION
      "Path: ethernetPdp.performance.ifOutPriorityQueues.packets.cirTx

       64 bit unsigned wrappable counter."
   ::= {pr1645v2EthpdpFOutQueuesEntry 50593792}

pr1645v2EthpdpFOutQueuesPacketsEirTx OBJECT-TYPE
   SYNTAX      Counter64
   MAX-ACCESS  read-only
   STATUS      current
   DESCRIPTION
      "Path: ethernetPdp.performance.ifOutPriorityQueues.packets.eirTx

       64 bit unsigned wrappable counter."
   ::= {pr1645v2EthpdpFOutQueuesEntry 50659328}

pr1645v2EthpdpFOutQueuesPacketsViolateTx OBJECT-TYPE
   SYNTAX      Counter64
   MAX-ACCESS  read-only
   STATUS      current
   DESCRIPTION
      "Path: ethernetPdp.performance.ifOutPriorityQueues.packets.violateTx

       64 bit unsigned wrappable counter."
   ::= {pr1645v2EthpdpFOutQueuesEntry 50855936}

pr1645v2EthpdpFOutQueuesOctetsTotal OBJECT-TYPE
   SYNTAX      Counter64
   MAX-ACCESS  read-only
   STATUS      current
   DESCRIPTION
      "Path: ethernetPdp.performance.ifOutPriorityQueues.octets.total

       64 bit unsigned wrappable counter."
   ::= {pr1645v2EthpdpFOutQueuesEntry 67567616}

pr1645v2EthpdpFOutQueuesOctetsDirectTx OBJECT-TYPE
   SYNTAX      Counter64
   MAX-ACCESS  read-only
   STATUS      current
   DESCRIPTION
      "Path: ethernetPdp.performance.ifOutPriorityQueues.octets.directTx

       64 bit unsigned wrappable counter."
   ::= {pr1645v2EthpdpFOutQueuesEntry 67174400}

pr1645v2EthpdpFOutQueuesOctetsQueued OBJECT-TYPE
   SYNTAX      Counter64
   MAX-ACCESS  read-only
   STATUS      current
   DESCRIPTION
      "Path: ethernetPdp.performance.ifOutPriorityQueues.octets.queued

       64 bit unsigned wrappable counter."
   ::= {pr1645v2EthpdpFOutQueuesEntry 67239936}

pr1645v2EthpdpFOutQueuesOctetsDropped OBJECT-TYPE
   SYNTAX      Counter64
   MAX-ACCESS  read-only
   STATUS      current
   DESCRIPTION
      "Path: ethernetPdp.performance.ifOutPriorityQueues.octets.dropped

       64 bit unsigned wrappable counter."
   ::= {pr1645v2EthpdpFOutQueuesEntry 67305472}

pr1645v2EthpdpFOutQueuesOctetsRedDropped OBJECT-TYPE
   SYNTAX      Counter64
   MAX-ACCESS  read-only
   STATUS      current
   DESCRIPTION
      "Path: ethernetPdp.performance.ifOutPriorityQueues.octets.redDropped

       64 bit unsigned wrappable counter."
   ::= {pr1645v2EthpdpFOutQueuesEntry 67502080}

pr1645v2EthpdpFOutQueuesOctetsCirTx OBJECT-TYPE
   SYNTAX      Counter64
   MAX-ACCESS  read-only
   STATUS      current
   DESCRIPTION
      "Path: ethernetPdp.performance.ifOutPriorityQueues.octets.cirTx

       64 bit unsigned wrappable counter."
   ::= {pr1645v2EthpdpFOutQueuesEntry 67371008}

pr1645v2EthpdpFOutQueuesOctetsEirTx OBJECT-TYPE
   SYNTAX      Counter64
   MAX-ACCESS  read-only
   STATUS      current
   DESCRIPTION
      "Path: ethernetPdp.performance.ifOutPriorityQueues.octets.eirTx

       64 bit unsigned wrappable counter."
   ::= {pr1645v2EthpdpFOutQueuesEntry 67436544}

pr1645v2EthpdpFOutQueuesOctetsViolateTx OBJECT-TYPE
   SYNTAX      Counter64
   MAX-ACCESS  read-only
   STATUS      current
   DESCRIPTION
      "Path: ethernetPdp.performance.ifOutPriorityQueues.octets.violateTx

       64 bit unsigned wrappable counter."
   ::= {pr1645v2EthpdpFOutQueuesEntry 67633152}

pr1645v2EthpdpFOutQueuesOctetsBandwidth15sec OBJECT-TYPE
   SYNTAX      Integer32
   MAX-ACCESS  read-only
   STATUS      current
   DESCRIPTION
      "Path: ethernetPdp.performance.ifOutPriorityQueues.octets.bandwidth.15sec

       unit name = bps
       formula = 8 * ; 8 /"
   ::= {pr1645v2EthpdpFOutQueuesEntry 70386944}

pr1645v2EthpdpFOutQueuesOctetsBandwidth30sec OBJECT-TYPE
   SYNTAX      Integer32
   MAX-ACCESS  read-only
   STATUS      current
   DESCRIPTION
      "Path: ethernetPdp.performance.ifOutPriorityQueues.octets.bandwidth.30sec

       unit name = bps
       formula = 8 * ; 8 /"
   ::= {pr1645v2EthpdpFOutQueuesEntry 70388224}

pr1645v2EthpdpFOutQueuesOctetsBandwidth1min OBJECT-TYPE
   SYNTAX      Integer32
   MAX-ACCESS  read-only
   STATUS      current
   DESCRIPTION
      "Path: ethernetPdp.performance.ifOutPriorityQueues.octets.bandwidth.1min

       unit name = bps
       formula = 8 * ; 8 /"
   ::= {pr1645v2EthpdpFOutQueuesEntry 70390784}

pr1645v2EthpdpFOutQueuesOctetsBandwidth2min OBJECT-TYPE
   SYNTAX      Integer32
   MAX-ACCESS  read-only
   STATUS      current
   DESCRIPTION
      "Path: ethernetPdp.performance.ifOutPriorityQueues.octets.bandwidth.2min

       unit name = bps
       formula = 8 * ; 8 /"
   ::= {pr1645v2EthpdpFOutQueuesEntry 70395904}

pr1645v2EthpdpFOutQueuesOctetsBandwidth5min OBJECT-TYPE
   SYNTAX      Integer32
   MAX-ACCESS  read-only
   STATUS      current
   DESCRIPTION
      "Path: ethernetPdp.performance.ifOutPriorityQueues.octets.bandwidth.5min

       unit name = bps
       formula = 8 * ; 8 /"
   ::= {pr1645v2EthpdpFOutQueuesEntry 70411264}

pr1645v2EthpdpFOutQueuesH2Performance OBJECT-TYPE
   SYNTAX      SEQUENCE OF Pr1645v2EthpdpFOutQueuesH2PerformanceEntry
   MAX-ACCESS  not-accessible
   STATUS      current
   DESCRIPTION
      ""
   ::= {pr1645v2EthpdpFOutQueues 83886080}

pr1645v2EthpdpFOutQueuesH2PerformanceEntry OBJECT-TYPE
   SYNTAX      Pr1645v2EthpdpFOutQueuesH2PerformanceEntry
   MAX-ACCESS  not-accessible
   STATUS      current
   DESCRIPTION
      ""
   INDEX      { pr1645v2EthpdpFOutQueuesH2PerformanceGlobalIx,
                pr1645v2EthpdpFOutQueuesTableIx,
                pr1645v2EthpdpFOutQueuesH2PerformanceTableIx }
   ::= {pr1645v2EthpdpFOutQueuesH2Performance 1}

Pr1645v2EthpdpFOutQueuesH2PerformanceEntry ::=
   SEQUENCE
      {
      pr1645v2EthpdpFOutQueuesH2PerformanceGlobalIx
         GlobalIndex,
      pr1645v2EthpdpFOutQueuesH2PerformanceTableIx
         TableIndex,
      pr1645v2EthpdpFOutQueuesH2PerformanceSysUpTime
         TimeTicks,
      pr1645v2EthpdpFOutQueuesH2PerformanceTotPkts
         Counter64,
      pr1645v2EthpdpFOutQueuesH2PerformanceDirTxPkts
         Counter64,
      pr1645v2EthpdpFOutQueuesH2PerformanceQdPkts
         Counter64,
      pr1645v2EthpdpFOutQueuesH2PerformanceDropPkts
         Counter64,
      pr1645v2EthpdpFOutQueuesH2PerformanceRDropPkts
         Counter64,
      pr1645v2EthpdpFOutQueuesH2PerformanceCirTxPkts
         Counter64,
      pr1645v2EthpdpFOutQueuesH2PerformanceEirTxPkts
         Counter64,
      pr1645v2EthpdpFOutQueuesH2PerformanceViolTxPkts
         Counter64,
      pr1645v2EthpdpFOutQueuesH2PerformanceTotOcts
         Counter64,
      pr1645v2EthpdpFOutQueuesH2PerformanceDirTxOcts
         Counter64,
      pr1645v2EthpdpFOutQueuesH2PerformanceQdOcts
         Counter64,
      pr1645v2EthpdpFOutQueuesH2PerformanceDropOcts
         Counter64,
      pr1645v2EthpdpFOutQueuesH2PerformanceRDropOcts
         Counter64,
      pr1645v2EthpdpFOutQueuesH2PerformanceCirTxOcts
         Counter64,
      pr1645v2EthpdpFOutQueuesH2PerformanceEirTxOcts
         Counter64,
      pr1645v2EthpdpFOutQueuesH2PerformanceViolTxOcts
         Counter64,
      pr1645v2EthpdpFOutQueuesH2PerformanceBandwidth
         Integer32
      }

pr1645v2EthpdpFOutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFOutQueuesH2PerformanceEntry 10}

pr1645v2EthpdpFOutQueuesH2PerformanceTableIx OBJECT-TYPE
   SYNTAX      TableIndex
   MAX-ACCESS  not-accessible
   STATUS      current
   DESCRIPTION
      ""
   ::= {pr1645v2EthpdpFOutQueuesH2PerformanceEntry 11}

pr1645v2EthpdpFOutQueuesH2PerformanceSysUpTime OBJECT-TYPE
   SYNTAX      TimeTicks
   MAX-ACCESS  read-only
   STATUS      current
   DESCRIPTION
      "Path: ethernetPdp.performance.ifOutPriorityQueues.h2Performance.sysUpTime

       Time in centi-second."
   ::= {pr1645v2EthpdpFOutQueuesH2PerformanceEntry 16777216}

pr1645v2EthpdpFOutQueuesH2PerformanceTotPkts OBJECT-TYPE
   SYNTAX      Counter64
   MAX-ACCESS  read-only
   STATUS      current
   DESCRIPTION
      "Path: ethernetPdp.performance.ifOutPriorityQueues.h2Performance.totalPkts

       64 bit unsigned wrappable counter."
   ::= {pr1645v2EthpdpFOutQueuesH2PerformanceEntry 234881024}

pr1645v2EthpdpFOutQueuesH2PerformanceDirTxPkts OBJECT-TYPE
   SYNTAX      Counter64
   MAX-ACCESS  read-only
   STATUS      current
   DESCRIPTION
      "Path: ethernetPdp.performance.ifOutPriorityQueues.h2Performance.directTxPkts

       64 bit unsigned wrappable counter."
   ::= {pr1645v2EthpdpFOutQueuesH2PerformanceEntry 33554432}

pr1645v2EthpdpFOutQueuesH2PerformanceQdPkts OBJECT-TYPE
   SYNTAX      Counter64
   MAX-ACCESS  read-only
   STATUS      current
   DESCRIPTION
      "Path: ethernetPdp.performance.ifOutPriorityQueues.h2Performance.queuedPkts

       64 bit unsigned wrappable counter."
   ::= {pr1645v2EthpdpFOutQueuesH2PerformanceEntry 50331648}

pr1645v2EthpdpFOutQueuesH2PerformanceDropPkts OBJECT-TYPE
   SYNTAX      Counter64
   MAX-ACCESS  read-only
   STATUS      current
   DESCRIPTION
      "Path: ethernetPdp.performance.ifOutPriorityQueues.h2Performance.droppedPkts

       64 bit unsigned wrappable counter."
   ::= {pr1645v2EthpdpFOutQueuesH2PerformanceEntry 67108864}

pr1645v2EthpdpFOutQueuesH2PerformanceRDropPkts OBJECT-TYPE
   SYNTAX      Counter64
   MAX-ACCESS  read-only
   STATUS      current
   DESCRIPTION
      "Path: ethernetPdp.performance.ifOutPriorityQueues.h2Performance.redDroppedPkts

       64 bit unsigned wrappable counter."
   ::= {pr1645v2EthpdpFOutQueuesH2PerformanceEntry 201326592}

pr1645v2EthpdpFOutQueuesH2PerformanceCirTxPkts OBJECT-TYPE
   SYNTAX      Counter64
   MAX-ACCESS  read-only
   STATUS      current
   DESCRIPTION
      "Path: ethernetPdp.performance.ifOutPriorityQueues.h2Performance.cirTxPkts

       64 bit unsigned wrappable counter."
   ::= {pr1645v2EthpdpFOutQueuesH2PerformanceEntry 83886080}

pr1645v2EthpdpFOutQueuesH2PerformanceEirTxPkts OBJECT-TYPE
   SYNTAX      Counter64
   MAX-ACCESS  read-only
   STATUS      current
   DESCRIPTION
      "Path: ethernetPdp.performance.ifOutPriorityQueues.h2Performance.eirTxPkts

       64 bit unsigned wrappable counter."
   ::= {pr1645v2EthpdpFOutQueuesH2PerformanceEntry 100663296}

pr1645v2EthpdpFOutQueuesH2PerformanceViolTxPkts OBJECT-TYPE
   SYNTAX      Counter64
   MAX-ACCESS  read-only
   STATUS      current
   DESCRIPTION
      "Path: ethernetPdp.performance.ifOutPriorityQueues.h2Performance.violateTxPkts

       64 bit unsigned wrappable counter."
   ::= {pr1645v2EthpdpFOutQueuesH2PerformanceEntry 301989888}

pr1645v2EthpdpFOutQueuesH2PerformanceTotOcts OBJECT-TYPE
   SYNTAX      Counter64
   MAX-ACCESS  read-only
   STATUS      current
   DESCRIPTION
      "Path: ethernetPdp.performance.ifOutPriorityQueues.h2Performance.totalOctets

       64 bit unsigned wrappable counter."
   ::= {pr1645v2EthpdpFOutQueuesH2PerformanceEntry 251658240}

pr1645v2EthpdpFOutQueuesH2PerformanceDirTxOcts OBJECT-TYPE
   SYNTAX      Counter64
   MAX-ACCESS  read-only
   STATUS      current
   DESCRIPTION
      "Path: ethernetPdp.performance.ifOutPriorityQueues.h2Performance.directTxOctets

       64 bit unsigned wrappable counter."
   ::= {pr1645v2EthpdpFOutQueuesH2PerformanceEntry 117440512}

pr1645v2EthpdpFOutQueuesH2PerformanceQdOcts OBJECT-TYPE
   SYNTAX      Counter64
   MAX-ACCESS  read-only
   STATUS      current
   DESCRIPTION
      "Path: ethernetPdp.performance.ifOutPriorityQueues.h2Performance.queuedOctets

       64 bit unsigned wrappable counter."
   ::= {pr1645v2EthpdpFOutQueuesH2PerformanceEntry 134217728}

pr1645v2EthpdpFOutQueuesH2PerformanceDropOcts OBJECT-TYPE
   SYNTAX      Counter64
   MAX-ACCESS  read-only
   STATUS      current
   DESCRIPTION
      "Path: ethernetPdp.performance.ifOutPriorityQueues.h2Performance.droppedOctets

       64 bit unsigned wrappable counter."
   ::= {pr1645v2EthpdpFOutQueuesH2PerformanceEntry 150994944}

pr1645v2EthpdpFOutQueuesH2PerformanceRDropOcts OBJECT-TYPE
   SYNTAX      Counter64
   MAX-ACCESS  read-only
   STATUS      current
   DESCRIPTION
      "Path: ethernetPdp.performance.ifOutPriorityQueues.h2Performance.redDroppedOctets

       64 bit unsigned wrappable counter."
   ::= {pr1645v2EthpdpFOutQueuesH2PerformanceEntry 218103808}

pr1645v2EthpdpFOutQueuesH2PerformanceCirTxOcts OBJECT-TYPE
   SYNTAX      Counter64
   MAX-ACCESS  read-only
   STATUS      current
   DESCRIPTION
      "Path: ethernetPdp.performance.ifOutPriorityQueues.h2Performance.cirTxOctets

       64 bit unsigned wrappable counter."
   ::= {pr1645v2EthpdpFOutQueuesH2PerformanceEntry 167772160}

pr1645v2EthpdpFOutQueuesH2PerformanceEirTxOcts OBJECT-TYPE
   SYNTAX      Counter64
   MAX-ACCESS  read-only
   STATUS      current
   DESCRIPTION
      "Path: ethernetPdp.performance.ifOutPriorityQueues.h2Performance.eirTxOctets

       64 bit unsigned wrappable counter."
   ::= {pr1645v2EthpdpFOutQueuesH2PerformanceEntry 184549376}

pr1645v2EthpdpFOutQueuesH2PerformanceViolTxOcts OBJECT-TYPE
   SYNTAX      Counter64
   MAX-ACCESS  read-only
   STATUS      current
   DESCRIPTION
      "Path: ethernetPdp.performance.ifOutPriorityQueues.h2Performance.violateTxOctets

       64 bit unsigned wrappable counter."
   ::= {pr1645v2EthpdpFOutQueuesH2PerformanceEntry 318767104}

pr1645v2EthpdpFOutQueuesH2PerformanceBandwidth OBJECT-TYPE
   SYNTAX      Integer32
   MAX-ACCESS  read-only
   STATUS      current
   DESCRIPTION
      "Path: ethernetPdp.performance.ifOutPriorityQueues.h2Performance.bandwidth

       unit name = bps
       formula = 8 * ; 8 /"
   ::= {pr1645v2EthpdpFOutQueuesH2PerformanceEntry 268435456}

pr1645v2EthpdpFOutQueuesH24Performance OBJECT-TYPE
   SYNTAX      SEQUENCE OF Pr1645v2EthpdpFOutQueuesH24PerformanceEntry
   MAX-ACCESS  not-accessible
   STATUS      current
   DESCRIPTION
      ""
   ::= {pr1645v2EthpdpFOutQueues 100663296}

pr1645v2EthpdpFOutQueuesH24PerformanceEntry OBJECT-TYPE
   SYNTAX      Pr1645v2EthpdpFOutQueuesH24PerformanceEntry
   MAX-ACCESS  not-accessible
   STATUS      current
   DESCRIPTION
      ""
   INDEX      { pr1645v2EthpdpFOutQueuesH24PerformanceGlobalIx,
                pr1645v2EthpdpFOutQueuesTableIx,
                pr1645v2EthpdpFOutQueuesH24PerformanceTableIx }
   ::= {pr1645v2EthpdpFOutQueuesH24Performance 1}

Pr1645v2EthpdpFOutQueuesH24PerformanceEntry ::=
   SEQUENCE
      {
      pr1645v2EthpdpFOutQueuesH24PerformanceGlobalIx
         GlobalIndex,
      pr1645v2EthpdpFOutQueuesH24PerformanceTableIx
         TableIndex,
      pr1645v2EthpdpFOutQueuesH24PerformanceSysUpTime
         TimeTicks,
      pr1645v2EthpdpFOutQueuesH24PerformanceTotPkts
         Counter64,
      pr1645v2EthpdpFOutQueuesH24PerformanceDirTxPkts
         Counter64,
      pr1645v2EthpdpFOutQueuesH24PerformanceQdPkts
         Counter64,
      pr1645v2EthpdpFOutQueuesH24PerformanceDropPkts
         Counter64,
      pr1645v2EthpdpFOutQueuesH24PerformanceRDropPkts
         Counter64,
      pr1645v2EthpdpFOutQueuesH24PerformanceCirTxPkts
         Counter64,
      pr1645v2EthpdpFOutQueuesH24PerformanceEirTxPkts
         Counter64,
      pr1645v2EthpdpFOutQueuesH24PerformanceViolTxPkts
         Counter64,
      pr1645v2EthpdpFOutQueuesH24PerformanceTotOcts
         Counter64,
      pr1645v2EthpdpFOutQueuesH24PerformanceDirTxOcts
         Counter64,
      pr1645v2EthpdpFOutQueuesH24PerformanceQdOcts
         Counter64,
      pr1645v2EthpdpFOutQueuesH24PerformanceDropOcts
         Counter64,
      pr1645v2EthpdpFOutQueuesH24PerformanceRDropOcts
         Counter64,
      pr1645v2EthpdpFOutQueuesH24PerformanceCirTxOcts
         Counter64,
      pr1645v2EthpdpFOutQueuesH24PerformanceEirTxOcts
         Counter64,
      pr1645v2EthpdpFOutQueuesH24PerformanceViolTxOcts
         Counter64,
      pr1645v2EthpdpFOutQueuesH24PerformanceBandwidth
         Integer32
      }

pr1645v2EthpdpFOutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFOutQueuesH24PerformanceEntry 10}

pr1645v2EthpdpFOutQueuesH24PerformanceTableIx OBJECT-TYPE
   SYNTAX      TableIndex
   MAX-ACCESS  not-accessible
   STATUS      current
   DESCRIPTION
      ""
   ::= {pr1645v2EthpdpFOutQueuesH24PerformanceEntry 11}

pr1645v2EthpdpFOutQueuesH24PerformanceSysUpTime OBJECT-TYPE
   SYNTAX      TimeTicks
   MAX-ACCESS  read-only
   STATUS      current
   DESCRIPTION
      "Path: ethernetPdp.performance.ifOutPriorityQueues.h24Performance.sysUpTime

       Time in centi-second."
   ::= {pr1645v2EthpdpFOutQueuesH24PerformanceEntry 16777216}

pr1645v2EthpdpFOutQueuesH24PerformanceTotPkts OBJECT-TYPE
   SYNTAX      Counter64
   MAX-ACCESS  read-only
   STATUS      current
   DESCRIPTION
      "Path: ethernetPdp.performance.ifOutPriorityQueues.h24Performance.totalPkts

       64 bit unsigned wrappable counter."
   ::= {pr1645v2EthpdpFOutQueuesH24PerformanceEntry 234881024}

pr1645v2EthpdpFOutQueuesH24PerformanceDirTxPkts OBJECT-TYPE
   SYNTAX      Counter64
   MAX-ACCESS  read-only
   STATUS      current
   DESCRIPTION
      "Path: ethernetPdp.performance.ifOutPriorityQueues.h24Performance.directTxPkts

       64 bit unsigned wrappable counter."
   ::= {pr1645v2EthpdpFOutQueuesH24PerformanceEntry 33554432}

pr1645v2EthpdpFOutQueuesH24PerformanceQdPkts OBJECT-TYPE
   SYNTAX      Counter64
   MAX-ACCESS  read-only
   STATUS      current
   DESCRIPTION
      "Path: ethernetPdp.performance.ifOutPriorityQueues.h24Performance.queuedPkts

       64 bit unsigned wrappable counter."
   ::= {pr1645v2EthpdpFOutQueuesH24PerformanceEntry 50331648}

pr1645v2EthpdpFOutQueuesH24PerformanceDropPkts OBJECT-TYPE
   SYNTAX      Counter64
   MAX-ACCESS  read-only
   STATUS      current
   DESCRIPTION
      "Path: ethernetPdp.performance.ifOutPriorityQueues.h24Performance.droppedPkts

       64 bit unsigned wrappable counter."
   ::= {pr1645v2EthpdpFOutQueuesH24PerformanceEntry 67108864}

pr1645v2EthpdpFOutQueuesH24PerformanceRDropPkts OBJECT-TYPE
   SYNTAX      Counter64
   MAX-ACCESS  read-only
   STATUS      current
   DESCRIPTION
      "Path: ethernetPdp.performance.ifOutPriorityQueues.h24Performance.redDroppedPkts

       64 bit unsigned wrappable counter."
   ::= {pr1645v2EthpdpFOutQueuesH24PerformanceEntry 201326592}

pr1645v2EthpdpFOutQueuesH24PerformanceCirTxPkts OBJECT-TYPE
   SYNTAX      Counter64
   MAX-ACCESS  read-only
   STATUS      current
   DESCRIPTION
      "Path: ethernetPdp.performance.ifOutPriorityQueues.h24Performance.cirTxPkts

       64 bit unsigned wrappable counter."
   ::= {pr1645v2EthpdpFOutQueuesH24PerformanceEntry 83886080}

pr1645v2EthpdpFOutQueuesH24PerformanceEirTxPkts OBJECT-TYPE
   SYNTAX      Counter64
   MAX-ACCESS  read-only
   STATUS      current
   DESCRIPTION
      "Path: ethernetPdp.performance.ifOutPriorityQueues.h24Performance.eirTxPkts

       64 bit unsigned wrappable counter."
   ::= {pr1645v2EthpdpFOutQueuesH24PerformanceEntry 100663296}

pr1645v2EthpdpFOutQueuesH24PerformanceViolTxPkts OBJECT-TYPE
   SYNTAX      Counter64
   MAX-ACCESS  read-only
   STATUS      current
   DESCRIPTION
      "Path: ethernetPdp.performance.ifOutPriorityQueues.h24Performance.violateTxPkts

       64 bit unsigned wrappable counter."
   ::= {pr1645v2EthpdpFOutQueuesH24PerformanceEntry 301989888}

pr1645v2EthpdpFOutQueuesH24PerformanceTotOcts OBJECT-TYPE
   SYNTAX      Counter64
   MAX-ACCESS  read-only
   STATUS      current
   DESCRIPTION
      "Path: ethernetPdp.performance.ifOutPriorityQueues.h24Performance.totalOctets

       64 bit unsigned wrappable counter."
   ::= {pr1645v2EthpdpFOutQueuesH24PerformanceEntry 251658240}

pr1645v2EthpdpFOutQueuesH24PerformanceDirTxOcts OBJECT-TYPE
   SYNTAX      Counter64
   MAX-ACCESS  read-only
   STATUS      current
   DESCRIPTION
      "Path: ethernetPdp.performance.ifOutPriorityQueues.h24Performance.directTxOctets

       64 bit unsigned wrappable counter."
   ::= {pr1645v2EthpdpFOutQueuesH24PerformanceEntry 117440512}

pr1645v2EthpdpFOutQueuesH24PerformanceQdOcts OBJECT-TYPE
   SYNTAX      Counter64
   MAX-ACCESS  read-only
   STATUS      current
   DESCRIPTION
      "Path: ethernetPdp.performance.ifOutPriorityQueues.h24Performance.queuedOctets

       64 bit unsigned wrappable counter."
   ::= {pr1645v2EthpdpFOutQueuesH24PerformanceEntry 134217728}

pr1645v2EthpdpFOutQueuesH24PerformanceDropOcts OBJECT-TYPE
   SYNTAX      Counter64
   MAX-ACCESS  read-only
   STATUS      current
   DESCRIPTION
      "Path: ethernetPdp.performance.ifOutPriorityQueues.h24Performance.droppedOctets

       64 bit unsigned wrappable counter."
   ::= {pr1645v2EthpdpFOutQueuesH24PerformanceEntry 150994944}

pr1645v2EthpdpFOutQueuesH24PerformanceRDropOcts OBJECT-TYPE
   SYNTAX      Counter64
   MAX-ACCESS  read-only
   STATUS      current
   DESCRIPTION
      "Path: ethernetPdp.performance.ifOutPriorityQueues.h24Performance.redDroppedOctets

       64 bit unsigned wrappable counter."
   ::= {pr1645v2EthpdpFOutQueuesH24PerformanceEntry 218103808}

pr1645v2EthpdpFOutQueuesH24PerformanceCirTxOcts OBJECT-TYPE
   SYNTAX      Counter64
   MAX-ACCESS  read-only
   STATUS      current
   DESCRIPTION
      "Path: ethernetPdp.performance.ifOutPriorityQueues.h24Performance.cirTxOctets

       64 bit unsigned wrappable counter."
   ::= {pr1645v2EthpdpFOutQueuesH24PerformanceEntry 167772160}

pr1645v2EthpdpFOutQueuesH24PerformanceEirTxOcts OBJECT-TYPE
   SYNTAX      Counter64
   MAX-ACCESS  read-only
   STATUS      current
   DESCRIPTION
      "Path: ethernetPdp.performance.ifOutPriorityQueues.h24Performance.eirTxOctets

       64 bit unsigned wrappable counter."
   ::= {pr1645v2EthpdpFOutQueuesH24PerformanceEntry 184549376}

pr1645v2EthpdpFOutQueuesH24PerformanceViolTxOcts OBJECT-TYPE
   SYNTAX      Counter64
   MAX-ACCESS  read-only
   STATUS      current
   DESCRIPTION
      "Path: ethernetPdp.performance.ifOutPriorityQueues.h24Performance.violateTxOctets

       64 bit unsigned wrappable counter."
   ::= {pr1645v2EthpdpFOutQueuesH24PerformanceEntry 318767104}

pr1645v2EthpdpFOutQueuesH24PerformanceBandwidth OBJECT-TYPE
   SYNTAX      Integer32
   MAX-ACCESS  read-only
   STATUS      current
   DESCRIPTION
      "Path: ethernetPdp.performance.ifOutPriorityQueues.h24Performance.bandwidth

       unit name = bps
       formula = 8 * ; 8 /"
   ::= {pr1645v2EthpdpFOutQueuesH24PerformanceEntry 268435456}

pr1645v2EthpdpFOutQueuesD7Performance OBJECT-TYPE
   SYNTAX      SEQUENCE OF Pr1645v2EthpdpFOutQueuesD7PerformanceEntry
   MAX-ACCESS  not-accessible
   STATUS      current
   DESCRIPTION
      ""
   ::= {pr1645v2EthpdpFOutQueues 117440512}

pr1645v2EthpdpFOutQueuesD7PerformanceEntry OBJECT-TYPE
   SYNTAX      Pr1645v2EthpdpFOutQueuesD7PerformanceEntry
   MAX-ACCESS  not-accessible
   STATUS      current
   DESCRIPTION
      ""
   INDEX      { pr1645v2EthpdpFOutQueuesD7PerformanceGlobalIx,
                pr1645v2EthpdpFOutQueuesTableIx,
                pr1645v2EthpdpFOutQueuesD7PerformanceTableIx }
   ::= {pr1645v2EthpdpFOutQueuesD7Performance 1}

Pr1645v2EthpdpFOutQueuesD7PerformanceEntry ::=
   SEQUENCE
      {
      pr1645v2EthpdpFOutQueuesD7PerformanceGlobalIx
         GlobalIndex,
      pr1645v2EthpdpFOutQueuesD7PerformanceTableIx
         TableIndex,
      pr1645v2EthpdpFOutQueuesD7PerformanceSysUpTime
         TimeTicks,
      pr1645v2EthpdpFOutQueuesD7PerformanceTotPkts
         Counter64,
      pr1645v2EthpdpFOutQueuesD7PerformanceDirTxPkts
         Counter64,
      pr1645v2EthpdpFOutQueuesD7PerformanceQdPkts
         Counter64,
      pr1645v2EthpdpFOutQueuesD7PerformanceDropPkts
         Counter64,
      pr1645v2EthpdpFOutQueuesD7PerformanceRDropPkts
         Counter64,
      pr1645v2EthpdpFOutQueuesD7PerformanceCirTxPkts
         Counter64,
      pr1645v2EthpdpFOutQueuesD7PerformanceEirTxPkts
         Counter64,
      pr1645v2EthpdpFOutQueuesD7PerformanceViolTxPkts
         Counter64,
      pr1645v2EthpdpFOutQueuesD7PerformanceTotOcts
         Counter64,
      pr1645v2EthpdpFOutQueuesD7PerformanceDirTxOcts
         Counter64,
      pr1645v2EthpdpFOutQueuesD7PerformanceQdOcts
         Counter64,
      pr1645v2EthpdpFOutQueuesD7PerformanceDropOcts
         Counter64,
      pr1645v2EthpdpFOutQueuesD7PerformanceRDropOcts
         Counter64,
      pr1645v2EthpdpFOutQueuesD7PerformanceCirTxOcts
         Counter64,
      pr1645v2EthpdpFOutQueuesD7PerformanceEirTxOcts
         Counter64,
      pr1645v2EthpdpFOutQueuesD7PerformanceViolTxOcts
         Counter64,
      pr1645v2EthpdpFOutQueuesD7PerformanceBandwidth
         Integer32
      }

pr1645v2EthpdpFOutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthpdpFOutQueuesD7PerformanceEntry 10}

pr1645v2EthpdpFOutQueuesD7PerformanceTableIx OBJECT-TYPE
   SYNTAX      TableIndex
   MAX-ACCESS  not-accessible
   STATUS      current
   DESCRIPTION
      ""
   ::= {pr1645v2EthpdpFOutQueuesD7PerformanceEntry 11}

pr1645v2EthpdpFOutQueuesD7PerformanceSysUpTime OBJECT-TYPE
   SYNTAX      TimeTicks
   MAX-ACCESS  read-only
   STATUS      current
   DESCRIPTION
      "Path: ethernetPdp.performance.ifOutPriorityQueues.d7Performance.sysUpTime

       Time in centi-second."
   ::= {pr1645v2EthpdpFOutQueuesD7PerformanceEntry 16777216}

pr1645v2EthpdpFOutQueuesD7PerformanceTotPkts OBJECT-TYPE
   SYNTAX      Counter64
   MAX-ACCESS  read-only
   STATUS      current
   DESCRIPTION
      "Path: ethernetPdp.performance.ifOutPriorityQueues.d7Performance.totalPkts

       64 bit unsigned wrappable counter."
   ::= {pr1645v2EthpdpFOutQueuesD7PerformanceEntry 234881024}

pr1645v2EthpdpFOutQueuesD7PerformanceDirTxPkts OBJECT-TYPE
   SYNTAX      Counter64
   MAX-ACCESS  read-only
   STATUS      current
   DESCRIPTION
      "Path: ethernetPdp.performance.ifOutPriorityQueues.d7Performance.directTxPkts

       64 bit unsigned wrappable counter."
   ::= {pr1645v2EthpdpFOutQueuesD7PerformanceEntry 33554432}

pr1645v2EthpdpFOutQueuesD7PerformanceQdPkts OBJECT-TYPE
   SYNTAX      Counter64
   MAX-ACCESS  read-only
   STATUS      current
   DESCRIPTION
      "Path: ethernetPdp.performance.ifOutPriorityQueues.d7Performance.queuedPkts

       64 bit unsigned wrappable counter."
   ::= {pr1645v2EthpdpFOutQueuesD7PerformanceEntry 50331648}

pr1645v2EthpdpFOutQueuesD7PerformanceDropPkts OBJECT-TYPE
   SYNTAX      Counter64
   MAX-ACCESS  read-only
   STATUS      current
   DESCRIPTION
      "Path: ethernetPdp.performance.ifOutPriorityQueues.d7Performance.droppedPkts

       64 bit unsigned wrappable counter."
   ::= {pr1645v2EthpdpFOutQueuesD7PerformanceEntry 67108864}

pr1645v2EthpdpFOutQueuesD7PerformanceRDropPkts OBJECT-TYPE
   SYNTAX      Counter64
   MAX-ACCESS  read-only
   STATUS      current
   DESCRIPTION
      "Path: ethernetPdp.performance.ifOutPriorityQueues.d7Performance.redDroppedPkts

       64 bit unsigned wrappable counter."
   ::= {pr1645v2EthpdpFOutQueuesD7PerformanceEntry 201326592}

pr1645v2EthpdpFOutQueuesD7PerformanceCirTxPkts OBJECT-TYPE
   SYNTAX      Counter64
   MAX-ACCESS  read-only
   STATUS      current
   DESCRIPTION
      "Path: ethernetPdp.performance.ifOutPriorityQueues.d7Performance.cirTxPkts

       64 bit unsigned wrappable counter."
   ::= {pr1645v2EthpdpFOutQueuesD7PerformanceEntry 83886080}

pr1645v2EthpdpFOutQueuesD7PerformanceEirTxPkts OBJECT-TYPE
   SYNTAX      Counter64
   MAX-ACCESS  read-only
   STATUS      current
   DESCRIPTION
      "Path: ethernetPdp.performance.ifOutPriorityQueues.d7Performance.eirTxPkts

       64 bit unsigned wrappable counter."
   ::= {pr1645v2EthpdpFOutQueuesD7PerformanceEntry 100663296}

pr1645v2EthpdpFOutQueuesD7PerformanceViolTxPkts OBJECT-TYPE
   SYNTAX      Counter64
   MAX-ACCESS  read-only
   STATUS      current
   DESCRIPTION
      "Path: ethernetPdp.performance.ifOutPriorityQueues.d7Performance.violateTxPkts

       64 bit unsigned wrappable counter."
   ::= {pr1645v2EthpdpFOutQueuesD7PerformanceEntry 301989888}

pr1645v2EthpdpFOutQueuesD7PerformanceTotOcts OBJECT-TYPE
   SYNTAX      Counter64
   MAX-ACCESS  read-only
   STATUS      current
   DESCRIPTION
      "Path: ethernetPdp.performance.ifOutPriorityQueues.d7Performance.totalOctets

       64 bit unsigned wrappable counter."
   ::= {pr1645v2EthpdpFOutQueuesD7PerformanceEntry 251658240}

pr1645v2EthpdpFOutQueuesD7PerformanceDirTxOcts OBJECT-TYPE
   SYNTAX      Counter64
   MAX-ACCESS  read-only
   STATUS      current
   DESCRIPTION
      "Path: ethernetPdp.performance.ifOutPriorityQueues.d7Performance.directTxOctets

       64 bit unsigned wrappable counter."
   ::= {pr1645v2EthpdpFOutQueuesD7PerformanceEntry 117440512}

pr1645v2EthpdpFOutQueuesD7PerformanceQdOcts OBJECT-TYPE
   SYNTAX      Counter64
   MAX-ACCESS  read-only
   STATUS      current
   DESCRIPTION
      "Path: ethernetPdp.performance.ifOutPriorityQueues.d7Performance.queuedOctets

       64 bit unsigned wrappable counter."
   ::= {pr1645v2EthpdpFOutQueuesD7PerformanceEntry 134217728}

pr1645v2EthpdpFOutQueuesD7PerformanceDropOcts OBJECT-TYPE
   SYNTAX      Counter64
   MAX-ACCESS  read-only
   STATUS      current
   DESCRIPTION
      "Path: ethernetPdp.performance.ifOutPriorityQueues.d7Performance.droppedOctets

       64 bit unsigned wrappable counter."
   ::= {pr1645v2EthpdpFOutQueuesD7PerformanceEntry 150994944}

pr1645v2EthpdpFOutQueuesD7PerformanceRDropOcts OBJECT-TYPE
   SYNTAX      Counter64
   MAX-ACCESS  read-only
   STATUS      current
   DESCRIPTION
      "Path: ethernetPdp.performance.ifOutPriorityQueues.d7Performance.redDroppedOctets

       64 bit unsigned wrappable counter."
   ::= {pr1645v2EthpdpFOutQueuesD7PerformanceEntry 218103808}

pr1645v2EthpdpFOutQueuesD7PerformanceCirTxOcts OBJECT-TYPE
   SYNTAX      Counter64
   MAX-ACCESS  read-only
   STATUS      current
   DESCRIPTION
      "Path: ethernetPdp.performance.ifOutPriorityQueues.d7Performance.cirTxOctets

       64 bit unsigned wrappable counter."
   ::= {pr1645v2EthpdpFOutQueuesD7PerformanceEntry 167772160}

pr1645v2EthpdpFOutQueuesD7PerformanceEirTxOcts OBJECT-TYPE
   SYNTAX      Counter64
   MAX-ACCESS  read-only
   STATUS      current
   DESCRIPTION
      "Path: ethernetPdp.performance.ifOutPriorityQueues.d7Performance.eirTxOctets

       64 bit unsigned wrappable counter."
   ::= {pr1645v2EthpdpFOutQueuesD7PerformanceEntry 184549376}

pr1645v2EthpdpFOutQueuesD7PerformanceViolTxOcts OBJECT-TYPE
   SYNTAX      Counter64
   MAX-ACCESS  read-only
   STATUS      current
   DESCRIPTION
      "Path: ethernetPdp.performance.ifOutPriorityQueues.d7Performance.violateTxOctets

       64 bit unsigned wrappable counter."
   ::= {pr1645v2EthpdpFOutQueuesD7PerformanceEntry 318767104}

pr1645v2EthpdpFOutQueuesD7PerformanceBandwidth OBJECT-TYPE
   SYNTAX      Integer32
   MAX-ACCESS  read-only
   STATUS      current
   DESCRIPTION
      "Path: ethernetPdp.performance.ifOutPriorityQueues.d7Performance.bandwidth

       unit name = bps
       formula = 8 * ; 8 /"
   ::= {pr1645v2EthpdpFOutQueuesD7PerformanceEntry 268435456}


pr1645v2EthpdpFOutBandwidth OBJECT IDENTIFIER ::= {pr1645v2EthpdpF 182}

pr1645v2EthpdpFOutBandwidthSSCTable OBJECT-TYPE
   SYNTAX      SEQUENCE OF Pr1645v2EthpdpFOutBandwidthEntry
   MAX-ACCESS  not-accessible
   STATUS      current
   DESCRIPTION
      "bandwidth"
   ::= {pr1645v2EthpdpFOutBandwidth 1}

pr1645v2EthpdpFOutBandwidthEntry OBJECT-TYPE
   SYNTAX      Pr1645v2EthpdpFOutBandwidthEntry
   MAX-ACCESS  not-accessible
   STATUS      current
   DESCRIPTION
      ""
   INDEX      { pr1645v2EthpdpFOutBandwidthGlobalIx }
   ::= {pr1645v2EthpdpFOutBandwidthSSCTable 1}

Pr1645v2EthpdpFOutBandwidthEntry ::=
   SEQUENCE
      {
      pr1645v2EthpdpFOutBandwidthGlobalIx
         GlobalIndex,
      pr1645v2EthpdpFOutBandwidth15sec
         Integer32,
      pr1645v2EthpdpFOutBandwidth30sec
         Integer32,
      pr1645v2EthpdpFOutBandwidth1min
         Integer32,
      pr1645v2EthpdpFOutBandwidth2min
         Integer32,
      pr1645v2EthpdpFOutBandwidth5min
         Integer32
      }

pr1645v2EthpdpFOutBandwidthGlobalIx OBJECT-TYPE
   SYNTAX      GlobalIndex
   MAX-ACCESS  not-accessible
   STATUS      current
   DESCRIPTION
      "The value of the tlsCntTreeGlobalIndex of the MANAGED OBJECT."
   ::= {pr1645v2EthpdpFOutBandwidthEntry 10}

pr1645v2EthpdpFOutBandwidth15sec OBJECT-TYPE
   SYNTAX      Integer32
   MAX-ACCESS  read-only
   STATUS      current
   DESCRIPTION
      "Path: ethernetPdp.performance.ifOutBandwidth.15sec

       unit name = bps
       formula = 8 * ; 8 /"
   ::= {pr1645v2EthpdpFOutBandwidthEntry 83886080}

pr1645v2EthpdpFOutBandwidth30sec OBJECT-TYPE
   SYNTAX      Integer32
   MAX-ACCESS  read-only
   STATUS      current
   DESCRIPTION
      "Path: ethernetPdp.performance.ifOutBandwidth.30sec

       unit name = bps
       formula = 8 * ; 8 /"
   ::= {pr1645v2EthpdpFOutBandwidthEntry 167772160}

pr1645v2EthpdpFOutBandwidth1min OBJECT-TYPE
   SYNTAX      Integer32
   MAX-ACCESS  read-only
   STATUS      current
   DESCRIPTION
      "Path: ethernetPdp.performance.ifOutBandwidth.1min

       unit name = bps
       formula = 8 * ; 8 /"
   ::= {pr1645v2EthpdpFOutBandwidthEntry 335544320}

pr1645v2EthpdpFOutBandwidth2min OBJECT-TYPE
   SYNTAX      Integer32
   MAX-ACCESS  read-only
   STATUS      current
   DESCRIPTION
      "Path: ethernetPdp.performance.ifOutBandwidth.2min

       unit name = bps
       formula = 8 * ; 8 /"
   ::= {pr1645v2EthpdpFOutBandwidthEntry 671088640}

pr1645v2EthpdpFOutBandwidth5min OBJECT-TYPE
   SYNTAX      Integer32
   MAX-ACCESS  read-only
   STATUS      current
   DESCRIPTION
      "Path: ethernetPdp.performance.ifOutBandwidth.5min

       unit name = bps
       formula = 8 * ; 8 /"
   ::= {pr1645v2EthpdpFOutBandwidthEntry 1677721600}


pr1645v2EthpdpFInP OBJECT IDENTIFIER ::= {pr1645v2EthpdpF 307}

pr1645v2EthpdpFInPSSCTable OBJECT-TYPE
   SYNTAX      SEQUENCE OF Pr1645v2EthpdpFInPEntry
   MAX-ACCESS  not-accessible
   STATUS      current
   DESCRIPTION
      "h2IfInPerformance"
   ::= {pr1645v2EthpdpFInP 1}

pr1645v2EthpdpFInPEntry OBJECT-TYPE
   SYNTAX      Pr1645v2EthpdpFInPEntry
   MAX-ACCESS  not-accessible
   STATUS      current
   DESCRIPTION
      ""
   INDEX      { pr1645v2EthpdpFInPGlobalIx,
                pr1645v2EthpdpFInPTableIx }
   ::= {pr1645v2EthpdpFInPSSCTable 1}

Pr1645v2EthpdpFInPEntry ::=
   SEQUENCE
      {
      pr1645v2EthpdpFInPGlobalIx
         GlobalIndex,
      pr1645v2EthpdpFInPTableIx
         TableIndex,
      pr1645v2EthpdpFInPSysUpTime
         TimeTicks,
      pr1645v2EthpdpFInPIfUpTime
         TimeTicks,
      pr1645v2EthpdpFInPIfStatChanges
         Counter32,
      pr1645v2EthpdpFInPIfInOctets
         Counter64,
      pr1645v2EthpdpFInPIfInUCPkts
         Counter64,
      pr1645v2EthpdpFInPIfInNUCPkts
         Counter64,
      pr1645v2EthpdpFInPIfInBCPkts
         Counter64,
      pr1645v2EthpdpFInPIfInMCPkts
         Counter64,
      pr1645v2EthpdpFInPIfInDiscards
         Counter64,
      pr1645v2EthpdpFInPIfInErrors
         Counter64,
      pr1645v2EthpdpFInPIfInUnkwn
         Counter64,
      pr1645v2EthpdpFInPInDropEx
         Counter64,
      pr1645v2EthpdpFInPInDropNoMac
         Counter64,
      pr1645v2EthpdpFInPInDropNUCast
         Counter64,
      pr1645v2EthpdpFInPInDropFilter
         Counter64,
      pr1645v2EthpdpFInPIfInBandwidth
         Integer32,
      pr1645v2EthpdpFInPIfOutOctets
         Counter64,
      pr1645v2EthpdpFInPIfOutUCPkts
         Counter64,
      pr1645v2EthpdpFInPIfOutNUCPkts
         Counter64,
      pr1645v2EthpdpFInPIfOutBCPkts
         Counter64,
      pr1645v2EthpdpFInPIfOutMCPkts
         Counter64,
      pr1645v2EthpdpFInPIfOutDiscards
         Counter64,
      pr1645v2EthpdpFInPIfOutErrors
         Counter64,
      pr1645v2EthpdpFInPOutDropEx
         Counter64,
      pr1645v2EthpdpFInPOutDropNoArp
         Counter64,
      pr1645v2EthpdpFInPOutDropFilter
         Counter64,
      pr1645v2EthpdpFInPIfOutBandwidth
         Integer32,
      pr1645v2EthpdpFInPIfErrSec
         Counter32
      }

pr1645v2EthpdpFInPGlobalIx OBJECT-TYPE
   SYNTAX      GlobalIndex
   MAX-ACCESS  not-accessible
   STATUS      current
   DESCRIPTION
      "The value of the tlsCntTreeGlobalIndex of the MANAGED OBJECT."
   ::= {pr1645v2EthpdpFInPEntry 10}

pr1645v2EthpdpFInPTableIx OBJECT-TYPE
   SYNTAX      TableIndex
   MAX-ACCESS  not-accessible
   STATUS      current
   DESCRIPTION
      ""
   ::= {pr1645v2EthpdpFInPEntry 11}

pr1645v2EthpdpFInPSysUpTime OBJECT-TYPE
   SYNTAX      TimeTicks
   MAX-ACCESS  read-only
   STATUS      current
   DESCRIPTION
      "Path: ethernetPdp.performance.h2Performance.sysUpTime

       Time in centi-second."
   ::= {pr1645v2EthpdpFInPEntry 16777216}

pr1645v2EthpdpFInPIfUpTime OBJECT-TYPE
   SYNTAX      TimeTicks
   MAX-ACCESS  read-only
   STATUS      current
   DESCRIPTION
      "Path: ethernetPdp.performance.h2Performance.ifUpTime

       Time in centi-second."
   ::= {pr1645v2EthpdpFInPEntry 33554432}

pr1645v2EthpdpFInPIfStatChanges OBJECT-TYPE
   SYNTAX      Counter32
   MAX-ACCESS  read-only
   STATUS      current
   DESCRIPTION
      "Path: ethernetPdp.performance.h2Performance.ifStatusChanges

       32 bit unsigned wrappable counter."
   ::= {pr1645v2EthpdpFInPEntry 50331648}

pr1645v2EthpdpFInPIfInOctets OBJECT-TYPE
   SYNTAX      Counter64
   MAX-ACCESS  read-only
   STATUS      current
   DESCRIPTION
      "Path: ethernetPdp.performance.h2Performance.ifInOctets

       64 bit unsigned wrappable counter."
   ::= {pr1645v2EthpdpFInPEntry 67108864}

pr1645v2EthpdpFInPIfInUCPkts OBJECT-TYPE
   SYNTAX      Counter64
   MAX-ACCESS  read-only
   STATUS      current
   DESCRIPTION
      "Path: ethernetPdp.performance.h2Performance.ifInUcastPkts

       64 bit unsigned wrappable counter."
   ::= {pr1645v2EthpdpFInPEntry 83886080}

pr1645v2EthpdpFInPIfInNUCPkts OBJECT-TYPE
   SYNTAX      Counter64
   MAX-ACCESS  read-only
   STATUS      current
   DESCRIPTION
      "Path: ethernetPdp.performance.h2Performance.ifInNUcastPkts

       64 bit unsigned wrappable counter."
   ::= {pr1645v2EthpdpFInPEntry 100663296}

pr1645v2EthpdpFInPIfInBCPkts OBJECT-TYPE
   SYNTAX      Counter64
   MAX-ACCESS  read-only
   STATUS      current
   DESCRIPTION
      "Path: ethernetPdp.performance.h2Performance.ifInBcastPkts

       64 bit unsigned wrappable counter."
   ::= {pr1645v2EthpdpFInPEntry 419430400}

pr1645v2EthpdpFInPIfInMCPkts OBJECT-TYPE
   SYNTAX      Counter64
   MAX-ACCESS  read-only
   STATUS      current
   DESCRIPTION
      "Path: ethernetPdp.performance.h2Performance.ifInMcastPkts

       64 bit unsigned wrappable counter."
   ::= {pr1645v2EthpdpFInPEntry 436207616}

pr1645v2EthpdpFInPIfInDiscards OBJECT-TYPE
   SYNTAX      Counter64
   MAX-ACCESS  read-only
   STATUS      current
   DESCRIPTION
      "Path: ethernetPdp.performance.h2Performance.ifInDiscards

       64 bit unsigned wrappable counter."
   ::= {pr1645v2EthpdpFInPEntry 117440512}

pr1645v2EthpdpFInPIfInErrors OBJECT-TYPE
   SYNTAX      Counter64
   MAX-ACCESS  read-only
   STATUS      current
   DESCRIPTION
      "Path: ethernetPdp.performance.h2Performance.ifInErrors

       64 bit unsigned wrappable counter."
   ::= {pr1645v2EthpdpFInPEntry 134217728}

pr1645v2EthpdpFInPIfInUnkwn OBJECT-TYPE
   SYNTAX      Counter64
   MAX-ACCESS  read-only
   STATUS      current
   DESCRIPTION
      "Path: ethernetPdp.performance.h2Performance.ifInUnknownProtos

       64 bit unsigned wrappable counter."
   ::= {pr1645v2EthpdpFInPEntry 150994944}

pr1645v2EthpdpFInPInDropEx OBJECT-TYPE
   SYNTAX      Counter64
   MAX-ACCESS  read-only
   STATUS      current
   DESCRIPTION
      "Path: ethernetPdp.performance.h2Performance.ifInDropLevelExceeded

       64 bit unsigned wrappable counter."
   ::= {pr1645v2EthpdpFInPEntry 335544320}

pr1645v2EthpdpFInPInDropNoMac OBJECT-TYPE
   SYNTAX      Counter64
   MAX-ACCESS  read-only
   STATUS      current
   DESCRIPTION
      "Path: ethernetPdp.performance.h2Performance.fInDiscardsNoMacFit

       64 bit unsigned wrappable counter."
   ::= {pr1645v2EthpdpFInPEntry 301989888}

pr1645v2EthpdpFInPInDropNUCast OBJECT-TYPE
   SYNTAX      Counter64
   MAX-ACCESS  read-only
   STATUS      current
   DESCRIPTION
      "Path: ethernetPdp.performance.h2Performance.fInDiscardsNUCast

       64 bit unsigned wrappable counter."
   ::= {pr1645v2EthpdpFInPEntry 318767104}

pr1645v2EthpdpFInPInDropFilter OBJECT-TYPE
   SYNTAX      Counter64
   MAX-ACCESS  read-only
   STATUS      current
   DESCRIPTION
      "Path: ethernetPdp.performance.h2Performance.fInDiscardsFilter

       64 bit unsigned wrappable counter."
   ::= {pr1645v2EthpdpFInPEntry 385875968}

pr1645v2EthpdpFInPIfInBandwidth OBJECT-TYPE
   SYNTAX      Integer32
   MAX-ACCESS  read-only
   STATUS      current
   DESCRIPTION
      "Path: ethernetPdp.performance.h2Performance.ifInBandwidth

       unit name = bps
       formula = 8 * ; 8 /"
   ::= {pr1645v2EthpdpFInPEntry 268435456}

pr1645v2EthpdpFInPIfOutOctets OBJECT-TYPE
   SYNTAX      Counter64
   MAX-ACCESS  read-only
   STATUS      current
   DESCRIPTION
      "Path: ethernetPdp.performance.h2Performance.ifOutOctets

       64 bit unsigned wrappable counter."
   ::= {pr1645v2EthpdpFInPEntry 167772160}

pr1645v2EthpdpFInPIfOutUCPkts OBJECT-TYPE
   SYNTAX      Counter64
   MAX-ACCESS  read-only
   STATUS      current
   DESCRIPTION
      "Path: ethernetPdp.performance.h2Performance.ifOutUcastPkts

       64 bit unsigned wrappable counter."
   ::= {pr1645v2EthpdpFInPEntry 184549376}

pr1645v2EthpdpFInPIfOutNUCPkts OBJECT-TYPE
   SYNTAX      Counter64
   MAX-ACCESS  read-only
   STATUS      current
   DESCRIPTION
      "Path: ethernetPdp.performance.h2Performance.ifOutNUcastPkts

       64 bit unsigned wrappable counter."
   ::= {pr1645v2EthpdpFInPEntry 201326592}

pr1645v2EthpdpFInPIfOutBCPkts OBJECT-TYPE
   SYNTAX      Counter64
   MAX-ACCESS  read-only
   STATUS      current
   DESCRIPTION
      "Path: ethernetPdp.performance.h2Performance.ifOutBcastPkts

       64 bit unsigned wrappable counter."
   ::= {pr1645v2EthpdpFInPEntry 452984832}

pr1645v2EthpdpFInPIfOutMCPkts OBJECT-TYPE
   SYNTAX      Counter64
   MAX-ACCESS  read-only
   STATUS      current
   DESCRIPTION
      "Path: ethernetPdp.performance.h2Performance.ifOutMcastPkts

       64 bit unsigned wrappable counter."
   ::= {pr1645v2EthpdpFInPEntry 469762048}

pr1645v2EthpdpFInPIfOutDiscards OBJECT-TYPE
   SYNTAX      Counter64
   MAX-ACCESS  read-only
   STATUS      current
   DESCRIPTION
      "Path: ethernetPdp.performance.h2Performance.ifOutDiscards

       64 bit unsigned wrappable counter."
   ::= {pr1645v2EthpdpFInPEntry 218103808}

pr1645v2EthpdpFInPIfOutErrors OBJECT-TYPE
   SYNTAX      Counter64
   MAX-ACCESS  read-only
   STATUS      current
   DESCRIPTION
      "Path: ethernetPdp.performance.h2Performance.ifOutErrors

       64 bit unsigned wrappable counter."
   ::= {pr1645v2EthpdpFInPEntry 234881024}

pr1645v2EthpdpFInPOutDropEx OBJECT-TYPE
   SYNTAX      Counter64
   MAX-ACCESS  read-only
   STATUS      current
   DESCRIPTION
      "Path: ethernetPdp.performance.h2Performance.ifOutDropLevelExceeded

       64 bit unsigned wrappable counter."
   ::= {pr1645v2EthpdpFInPEntry 352321536}

pr1645v2EthpdpFInPOutDropNoArp OBJECT-TYPE
   SYNTAX      Counter64
   MAX-ACCESS  read-only
   STATUS      current
   DESCRIPTION
      "Path: ethernetPdp.performance.h2Performance.ifOutDiscardsNoArp

       64 bit unsigned wrappable counter."
   ::= {pr1645v2EthpdpFInPEntry 369098752}

pr1645v2EthpdpFInPOutDropFilter OBJECT-TYPE
   SYNTAX      Counter64
   MAX-ACCESS  read-only
   STATUS      current
   DESCRIPTION
      "Path: ethernetPdp.performance.h2Performance.ifOutDiscardsFilter

       64 bit unsigned wrappable counter."
   ::= {pr1645v2EthpdpFInPEntry 402653184}

pr1645v2EthpdpFInPIfOutBandwidth OBJECT-TYPE
   SYNTAX      Integer32
   MAX-ACCESS  read-only
   STATUS      current
   DESCRIPTION
      "Path: ethernetPdp.performance.h2Performance.ifOutBandwidth

       unit name = bps
       formula = 8 * ; 8 /"
   ::= {pr1645v2EthpdpFInPEntry 285212672}

pr1645v2EthpdpFInPIfErrSec OBJECT-TYPE
   SYNTAX      Counter32
   MAX-ACCESS  read-only
   STATUS      current
   DESCRIPTION
      "Path: ethernetPdp.performance.h2Performance.ifErrSec

       32 bit unsigned wrappable counter."
   ::= {pr1645v2EthpdpFInPEntry 251658240}


pr1645v2EthpdpFH24InP OBJECT IDENTIFIER ::= {pr1645v2EthpdpF 308}

pr1645v2EthpdpFH24InPSSCTable OBJECT-TYPE
   SYNTAX      SEQUENCE OF Pr1645v2EthpdpFH24InPEntry
   MAX-ACCESS  not-accessible
   STATUS      current
   DESCRIPTION
      "h24IfInPerformance"
   ::= {pr1645v2EthpdpFH24InP 1}

pr1645v2EthpdpFH24InPEntry OBJECT-TYPE
   SYNTAX      Pr1645v2EthpdpFH24InPEntry
   MAX-ACCESS  not-accessible
   STATUS      current
   DESCRIPTION
      ""
   INDEX      { pr1645v2EthpdpFH24InPGlobalIx,
                pr1645v2EthpdpFH24InPTableIx }
   ::= {pr1645v2EthpdpFH24InPSSCTable 1}

Pr1645v2EthpdpFH24InPEntry ::=
   SEQUENCE
      {
      pr1645v2EthpdpFH24InPGlobalIx
         GlobalIndex,
      pr1645v2EthpdpFH24InPTableIx
         TableIndex,
      pr1645v2EthpdpFH24InPSysUpTime
         TimeTicks,
      pr1645v2EthpdpFH24InPIfUpTime
         TimeTicks,
      pr1645v2EthpdpFH24InPIfStatChanges
         Counter32,
      pr1645v2EthpdpFH24InPIfInOctets
         Counter64,
      pr1645v2EthpdpFH24InPIfInUCPkts
         Counter64,
      pr1645v2EthpdpFH24InPIfInNUCPkts
         Counter64,
      pr1645v2EthpdpFH24InPIfInBCPkts
         Counter64,
      pr1645v2EthpdpFH24InPIfInMCPkts
         Counter64,
      pr1645v2EthpdpFH24InPIfInDiscards
         Counter64,
      pr1645v2EthpdpFH24InPIfInErrors
         Counter64,
      pr1645v2EthpdpFH24InPIfInUnkwn
         Counter64,
      pr1645v2EthpdpFH24InPInDropEx
         Counter64,
      pr1645v2EthpdpFH24InPInDropNoMac
         Counter64,
      pr1645v2EthpdpFH24InPInDropNUCast
         Counter64,
      pr1645v2EthpdpFH24InPInDropFilter
         Counter64,
      pr1645v2EthpdpFH24InPIfInBandwidth
         Integer32,
      pr1645v2EthpdpFH24InPIfOutOctets
         Counter64,
      pr1645v2EthpdpFH24InPIfOutUCPkts
         Counter64,
      pr1645v2EthpdpFH24InPIfOutNUCPkts
         Counter64,
      pr1645v2EthpdpFH24InPIfOutBCPkts
         Counter64,
      pr1645v2EthpdpFH24InPIfOutMCPkts
         Counter64,
      pr1645v2EthpdpFH24InPIfOutDiscards
         Counter64,
      pr1645v2EthpdpFH24InPIfOutErrors
         Counter64,
      pr1645v2EthpdpFH24InPOutDropEx
         Counter64,
      pr1645v2EthpdpFH24InPOutDropNoArp
         Counter64,
      pr1645v2EthpdpFH24InPOutDropFilter
         Counter64,
      pr1645v2EthpdpFH24InPIfOutBandwidth
         Integer32,
      pr1645v2EthpdpFH24InPIfErrSec
         Counter32
      }

pr1645v2EthpdpFH24InPGlobalIx OBJECT-TYPE
   SYNTAX      GlobalIndex
   MAX-ACCESS  not-accessible
   STATUS      current
   DESCRIPTION
      "The value of the tlsCntTreeGlobalIndex of the MANAGED OBJECT."
   ::= {pr1645v2EthpdpFH24InPEntry 10}

pr1645v2EthpdpFH24InPTableIx OBJECT-TYPE
   SYNTAX      TableIndex
   MAX-ACCESS  not-accessible
   STATUS      current
   DESCRIPTION
      ""
   ::= {pr1645v2EthpdpFH24InPEntry 11}

pr1645v2EthpdpFH24InPSysUpTime OBJECT-TYPE
   SYNTAX      TimeTicks
   MAX-ACCESS  read-only
   STATUS      current
   DESCRIPTION
      "Path: ethernetPdp.performance.h24Performance.sysUpTime

       Time in centi-second."
   ::= {pr1645v2EthpdpFH24InPEntry 16777216}

pr1645v2EthpdpFH24InPIfUpTime OBJECT-TYPE
   SYNTAX      TimeTicks
   MAX-ACCESS  read-only
   STATUS      current
   DESCRIPTION
      "Path: ethernetPdp.performance.h24Performance.ifUpTime

       Time in centi-second."
   ::= {pr1645v2EthpdpFH24InPEntry 33554432}

pr1645v2EthpdpFH24InPIfStatChanges OBJECT-TYPE
   SYNTAX      Counter32
   MAX-ACCESS  read-only
   STATUS      current
   DESCRIPTION
      "Path: ethernetPdp.performance.h24Performance.ifStatusChanges

       32 bit unsigned wrappable counter."
   ::= {pr1645v2EthpdpFH24InPEntry 50331648}

pr1645v2EthpdpFH24InPIfInOctets OBJECT-TYPE
   SYNTAX      Counter64
   MAX-ACCESS  read-only
   STATUS      current
   DESCRIPTION
      "Path: ethernetPdp.performance.h24Performance.ifInOctets

       64 bit unsigned wrappable counter."
   ::= {pr1645v2EthpdpFH24InPEntry 67108864}

pr1645v2EthpdpFH24InPIfInUCPkts OBJECT-TYPE
   SYNTAX      Counter64
   MAX-ACCESS  read-only
   STATUS      current
   DESCRIPTION
      "Path: ethernetPdp.performance.h24Performance.ifInUcastPkts

       64 bit unsigned wrappable counter."
   ::= {pr1645v2EthpdpFH24InPEntry 83886080}

pr1645v2EthpdpFH24InPIfInNUCPkts OBJECT-TYPE
   SYNTAX      Counter64
   MAX-ACCESS  read-only
   STATUS      current
   DESCRIPTION
      "Path: ethernetPdp.performance.h24Performance.ifInNUcastPkts

       64 bit unsigned wrappable counter."
   ::= {pr1645v2EthpdpFH24InPEntry 100663296}

pr1645v2EthpdpFH24InPIfInBCPkts OBJECT-TYPE
   SYNTAX      Counter64
   MAX-ACCESS  read-only
   STATUS      current
   DESCRIPTION
      "Path: ethernetPdp.performance.h24Performance.ifInBcastPkts

       64 bit unsigned wrappable counter."
   ::= {pr1645v2EthpdpFH24InPEntry 419430400}

pr1645v2EthpdpFH24InPIfInMCPkts OBJECT-TYPE
   SYNTAX      Counter64
   MAX-ACCESS  read-only
   STATUS      current
   DESCRIPTION
      "Path: ethernetPdp.performance.h24Performance.ifInMcastPkts

       64 bit unsigned wrappable counter."
   ::= {pr1645v2EthpdpFH24InPEntry 436207616}

pr1645v2EthpdpFH24InPIfInDiscards OBJECT-TYPE
   SYNTAX      Counter64
   MAX-ACCESS  read-only
   STATUS      current
   DESCRIPTION
      "Path: ethernetPdp.performance.h24Performance.ifInDiscards

       64 bit unsigned wrappable counter."
   ::= {pr1645v2EthpdpFH24InPEntry 117440512}

pr1645v2EthpdpFH24InPIfInErrors OBJECT-TYPE
   SYNTAX      Counter64
   MAX-ACCESS  read-only
   STATUS      current
   DESCRIPTION
      "Path: ethernetPdp.performance.h24Performance.ifInErrors

       64 bit unsigned wrappable counter."
   ::= {pr1645v2EthpdpFH24InPEntry 134217728}

pr1645v2EthpdpFH24InPIfInUnkwn OBJECT-TYPE
   SYNTAX      Counter64
   MAX-ACCESS  read-only
   STATUS      current
   DESCRIPTION
      "Path: ethernetPdp.performance.h24Performance.ifInUnknownProtos

       64 bit unsigned wrappable counter."
   ::= {pr1645v2EthpdpFH24InPEntry 150994944}

pr1645v2EthpdpFH24InPInDropEx OBJECT-TYPE
   SYNTAX      Counter64
   MAX-ACCESS  read-only
   STATUS      current
   DESCRIPTION
      "Path: ethernetPdp.performance.h24Performance.ifInDropLevelExceeded

       64 bit unsigned wrappable counter."
   ::= {pr1645v2EthpdpFH24InPEntry 335544320}

pr1645v2EthpdpFH24InPInDropNoMac OBJECT-TYPE
   SYNTAX      Counter64
   MAX-ACCESS  read-only
   STATUS      current
   DESCRIPTION
      "Path: ethernetPdp.performance.h24Performance.fInDiscardsNoMacFit

       64 bit unsigned wrappable counter."
   ::= {pr1645v2EthpdpFH24InPEntry 301989888}

pr1645v2EthpdpFH24InPInDropNUCast OBJECT-TYPE
   SYNTAX      Counter64
   MAX-ACCESS  read-only
   STATUS      current
   DESCRIPTION
      "Path: ethernetPdp.performance.h24Performance.fInDiscardsNUCast

       64 bit unsigned wrappable counter."
   ::= {pr1645v2EthpdpFH24InPEntry 318767104}

pr1645v2EthpdpFH24InPInDropFilter OBJECT-TYPE
   SYNTAX      Counter64
   MAX-ACCESS  read-only
   STATUS      current
   DESCRIPTION
      "Path: ethernetPdp.performance.h24Performance.fInDiscardsFilter

       64 bit unsigned wrappable counter."
   ::= {pr1645v2EthpdpFH24InPEntry 385875968}

pr1645v2EthpdpFH24InPIfInBandwidth OBJECT-TYPE
   SYNTAX      Integer32
   MAX-ACCESS  read-only
   STATUS      current
   DESCRIPTION
      "Path: ethernetPdp.performance.h24Performance.ifInBandwidth

       unit name = bps
       formula = 8 * ; 8 /"
   ::= {pr1645v2EthpdpFH24InPEntry 268435456}

pr1645v2EthpdpFH24InPIfOutOctets OBJECT-TYPE
   SYNTAX      Counter64
   MAX-ACCESS  read-only
   STATUS      current
   DESCRIPTION
      "Path: ethernetPdp.performance.h24Performance.ifOutOctets

       64 bit unsigned wrappable counter."
   ::= {pr1645v2EthpdpFH24InPEntry 167772160}

pr1645v2EthpdpFH24InPIfOutUCPkts OBJECT-TYPE
   SYNTAX      Counter64
   MAX-ACCESS  read-only
   STATUS      current
   DESCRIPTION
      "Path: ethernetPdp.performance.h24Performance.ifOutUcastPkts

       64 bit unsigned wrappable counter."
   ::= {pr1645v2EthpdpFH24InPEntry 184549376}

pr1645v2EthpdpFH24InPIfOutNUCPkts OBJECT-TYPE
   SYNTAX      Counter64
   MAX-ACCESS  read-only
   STATUS      current
   DESCRIPTION
      "Path: ethernetPdp.performance.h24Performance.ifOutNUcastPkts

       64 bit unsigned wrappable counter."
   ::= {pr1645v2EthpdpFH24InPEntry 201326592}

pr1645v2EthpdpFH24InPIfOutBCPkts OBJECT-TYPE
   SYNTAX      Counter64
   MAX-ACCESS  read-only
   STATUS      current
   DESCRIPTION
      "Path: ethernetPdp.performance.h24Performance.ifOutBcastPkts

       64 bit unsigned wrappable counter."
   ::= {pr1645v2EthpdpFH24InPEntry 452984832}

pr1645v2EthpdpFH24InPIfOutMCPkts OBJECT-TYPE
   SYNTAX      Counter64
   MAX-ACCESS  read-only
   STATUS      current
   DESCRIPTION
      "Path: ethernetPdp.performance.h24Performance.ifOutMcastPkts

       64 bit unsigned wrappable counter."
   ::= {pr1645v2EthpdpFH24InPEntry 469762048}

pr1645v2EthpdpFH24InPIfOutDiscards OBJECT-TYPE
   SYNTAX      Counter64
   MAX-ACCESS  read-only
   STATUS      current
   DESCRIPTION
      "Path: ethernetPdp.performance.h24Performance.ifOutDiscards

       64 bit unsigned wrappable counter."
   ::= {pr1645v2EthpdpFH24InPEntry 218103808}

pr1645v2EthpdpFH24InPIfOutErrors OBJECT-TYPE
   SYNTAX      Counter64
   MAX-ACCESS  read-only
   STATUS      current
   DESCRIPTION
      "Path: ethernetPdp.performance.h24Performance.ifOutErrors

       64 bit unsigned wrappable counter."
   ::= {pr1645v2EthpdpFH24InPEntry 234881024}

pr1645v2EthpdpFH24InPOutDropEx OBJECT-TYPE
   SYNTAX      Counter64
   MAX-ACCESS  read-only
   STATUS      current
   DESCRIPTION
      "Path: ethernetPdp.performance.h24Performance.ifOutDropLevelExceeded

       64 bit unsigned wrappable counter."
   ::= {pr1645v2EthpdpFH24InPEntry 352321536}

pr1645v2EthpdpFH24InPOutDropNoArp OBJECT-TYPE
   SYNTAX      Counter64
   MAX-ACCESS  read-only
   STATUS      current
   DESCRIPTION
      "Path: ethernetPdp.performance.h24Performance.ifOutDiscardsNoArp

       64 bit unsigned wrappable counter."
   ::= {pr1645v2EthpdpFH24InPEntry 369098752}

pr1645v2EthpdpFH24InPOutDropFilter OBJECT-TYPE
   SYNTAX      Counter64
   MAX-ACCESS  read-only
   STATUS      current
   DESCRIPTION
      "Path: ethernetPdp.performance.h24Performance.ifOutDiscardsFilter

       64 bit unsigned wrappable counter."
   ::= {pr1645v2EthpdpFH24InPEntry 402653184}

pr1645v2EthpdpFH24InPIfOutBandwidth OBJECT-TYPE
   SYNTAX      Integer32
   MAX-ACCESS  read-only
   STATUS      current
   DESCRIPTION
      "Path: ethernetPdp.performance.h24Performance.ifOutBandwidth

       unit name = bps
       formula = 8 * ; 8 /"
   ::= {pr1645v2EthpdpFH24InPEntry 285212672}

pr1645v2EthpdpFH24InPIfErrSec OBJECT-TYPE
   SYNTAX      Counter32
   MAX-ACCESS  read-only
   STATUS      current
   DESCRIPTION
      "Path: ethernetPdp.performance.h24Performance.ifErrSec

       32 bit unsigned wrappable counter."
   ::= {pr1645v2EthpdpFH24InPEntry 251658240}


pr1645v2EthpdpFD7InP OBJECT IDENTIFIER ::= {pr1645v2EthpdpF 309}

pr1645v2EthpdpFD7InPSSCTable OBJECT-TYPE
   SYNTAX      SEQUENCE OF Pr1645v2EthpdpFD7InPEntry
   MAX-ACCESS  not-accessible
   STATUS      current
   DESCRIPTION
      "d7IfInPerformance"
   ::= {pr1645v2EthpdpFD7InP 1}

pr1645v2EthpdpFD7InPEntry OBJECT-TYPE
   SYNTAX      Pr1645v2EthpdpFD7InPEntry
   MAX-ACCESS  not-accessible
   STATUS      current
   DESCRIPTION
      ""
   INDEX      { pr1645v2EthpdpFD7InPGlobalIx,
                pr1645v2EthpdpFD7InPTableIx }
   ::= {pr1645v2EthpdpFD7InPSSCTable 1}

Pr1645v2EthpdpFD7InPEntry ::=
   SEQUENCE
      {
      pr1645v2EthpdpFD7InPGlobalIx
         GlobalIndex,
      pr1645v2EthpdpFD7InPTableIx
         TableIndex,
      pr1645v2EthpdpFD7InPSysUpTime
         TimeTicks,
      pr1645v2EthpdpFD7InPIfUpTime
         TimeTicks,
      pr1645v2EthpdpFD7InPIfStatChanges
         Counter32,
      pr1645v2EthpdpFD7InPIfInOctets
         Counter64,
      pr1645v2EthpdpFD7InPIfInUCPkts
         Counter64,
      pr1645v2EthpdpFD7InPIfInNUCPkts
         Counter64,
      pr1645v2EthpdpFD7InPIfInBCPkts
         Counter64,
      pr1645v2EthpdpFD7InPIfInMCPkts
         Counter64,
      pr1645v2EthpdpFD7InPIfInDiscards
         Counter64,
      pr1645v2EthpdpFD7InPIfInErrors
         Counter64,
      pr1645v2EthpdpFD7InPIfInUnkwn
         Counter64,
      pr1645v2EthpdpFD7InPInDropEx
         Counter64,
      pr1645v2EthpdpFD7InPInDropNoMac
         Counter64,
      pr1645v2EthpdpFD7InPInDropNUCast
         Counter64,
      pr1645v2EthpdpFD7InPInDropFilter
         Counter64,
      pr1645v2EthpdpFD7InPIfInBandwidth
         Integer32,
      pr1645v2EthpdpFD7InPIfOutOctets
         Counter64,
      pr1645v2EthpdpFD7InPIfOutUCPkts
         Counter64,
      pr1645v2EthpdpFD7InPIfOutNUCPkts
         Counter64,
      pr1645v2EthpdpFD7InPIfOutBCPkts
         Counter64,
      pr1645v2EthpdpFD7InPIfOutMCPkts
         Counter64,
      pr1645v2EthpdpFD7InPIfOutDiscards
         Counter64,
      pr1645v2EthpdpFD7InPIfOutErrors
         Counter64,
      pr1645v2EthpdpFD7InPOutDropEx
         Counter64,
      pr1645v2EthpdpFD7InPOutDropNoArp
         Counter64,
      pr1645v2EthpdpFD7InPOutDropFilter
         Counter64,
      pr1645v2EthpdpFD7InPIfOutBandwidth
         Integer32,
      pr1645v2EthpdpFD7InPIfErrSec
         Counter32
      }

pr1645v2EthpdpFD7InPGlobalIx OBJECT-TYPE
   SYNTAX      GlobalIndex
   MAX-ACCESS  not-accessible
   STATUS      current
   DESCRIPTION
      "The value of the tlsCntTreeGlobalIndex of the MANAGED OBJECT."
   ::= {pr1645v2EthpdpFD7InPEntry 10}

pr1645v2EthpdpFD7InPTableIx OBJECT-TYPE
   SYNTAX      TableIndex
   MAX-ACCESS  not-accessible
   STATUS      current
   DESCRIPTION
      ""
   ::= {pr1645v2EthpdpFD7InPEntry 11}

pr1645v2EthpdpFD7InPSysUpTime OBJECT-TYPE
   SYNTAX      TimeTicks
   MAX-ACCESS  read-only
   STATUS      current
   DESCRIPTION
      "Path: ethernetPdp.performance.d7Performance.sysUpTime

       Time in centi-second."
   ::= {pr1645v2EthpdpFD7InPEntry 16777216}

pr1645v2EthpdpFD7InPIfUpTime OBJECT-TYPE
   SYNTAX      TimeTicks
   MAX-ACCESS  read-only
   STATUS      current
   DESCRIPTION
      "Path: ethernetPdp.performance.d7Performance.ifUpTime

       Time in centi-second."
   ::= {pr1645v2EthpdpFD7InPEntry 33554432}

pr1645v2EthpdpFD7InPIfStatChanges OBJECT-TYPE
   SYNTAX      Counter32
   MAX-ACCESS  read-only
   STATUS      current
   DESCRIPTION
      "Path: ethernetPdp.performance.d7Performance.ifStatusChanges

       32 bit unsigned wrappable counter."
   ::= {pr1645v2EthpdpFD7InPEntry 50331648}

pr1645v2EthpdpFD7InPIfInOctets OBJECT-TYPE
   SYNTAX      Counter64
   MAX-ACCESS  read-only
   STATUS      current
   DESCRIPTION
      "Path: ethernetPdp.performance.d7Performance.ifInOctets

       64 bit unsigned wrappable counter."
   ::= {pr1645v2EthpdpFD7InPEntry 67108864}

pr1645v2EthpdpFD7InPIfInUCPkts OBJECT-TYPE
   SYNTAX      Counter64
   MAX-ACCESS  read-only
   STATUS      current
   DESCRIPTION
      "Path: ethernetPdp.performance.d7Performance.ifInUcastPkts

       64 bit unsigned wrappable counter."
   ::= {pr1645v2EthpdpFD7InPEntry 83886080}

pr1645v2EthpdpFD7InPIfInNUCPkts OBJECT-TYPE
   SYNTAX      Counter64
   MAX-ACCESS  read-only
   STATUS      current
   DESCRIPTION
      "Path: ethernetPdp.performance.d7Performance.ifInNUcastPkts

       64 bit unsigned wrappable counter."
   ::= {pr1645v2EthpdpFD7InPEntry 100663296}

pr1645v2EthpdpFD7InPIfInBCPkts OBJECT-TYPE
   SYNTAX      Counter64
   MAX-ACCESS  read-only
   STATUS      current
   DESCRIPTION
      "Path: ethernetPdp.performance.d7Performance.ifInBcastPkts

       64 bit unsigned wrappable counter."
   ::= {pr1645v2EthpdpFD7InPEntry 419430400}

pr1645v2EthpdpFD7InPIfInMCPkts OBJECT-TYPE
   SYNTAX      Counter64
   MAX-ACCESS  read-only
   STATUS      current
   DESCRIPTION
      "Path: ethernetPdp.performance.d7Performance.ifInMcastPkts

       64 bit unsigned wrappable counter."
   ::= {pr1645v2EthpdpFD7InPEntry 436207616}

pr1645v2EthpdpFD7InPIfInDiscards OBJECT-TYPE
   SYNTAX      Counter64
   MAX-ACCESS  read-only
   STATUS      current
   DESCRIPTION
      "Path: ethernetPdp.performance.d7Performance.ifInDiscards

       64 bit unsigned wrappable counter."
   ::= {pr1645v2EthpdpFD7InPEntry 117440512}

pr1645v2EthpdpFD7InPIfInErrors OBJECT-TYPE
   SYNTAX      Counter64
   MAX-ACCESS  read-only
   STATUS      current
   DESCRIPTION
      "Path: ethernetPdp.performance.d7Performance.ifInErrors

       64 bit unsigned wrappable counter."
   ::= {pr1645v2EthpdpFD7InPEntry 134217728}

pr1645v2EthpdpFD7InPIfInUnkwn OBJECT-TYPE
   SYNTAX      Counter64
   MAX-ACCESS  read-only
   STATUS      current
   DESCRIPTION
      "Path: ethernetPdp.performance.d7Performance.ifInUnknownProtos

       64 bit unsigned wrappable counter."
   ::= {pr1645v2EthpdpFD7InPEntry 150994944}

pr1645v2EthpdpFD7InPInDropEx OBJECT-TYPE
   SYNTAX      Counter64
   MAX-ACCESS  read-only
   STATUS      current
   DESCRIPTION
      "Path: ethernetPdp.performance.d7Performance.ifInDropLevelExceeded

       64 bit unsigned wrappable counter."
   ::= {pr1645v2EthpdpFD7InPEntry 335544320}

pr1645v2EthpdpFD7InPInDropNoMac OBJECT-TYPE
   SYNTAX      Counter64
   MAX-ACCESS  read-only
   STATUS      current
   DESCRIPTION
      "Path: ethernetPdp.performance.d7Performance.fInDiscardsNoMacFit

       64 bit unsigned wrappable counter."
   ::= {pr1645v2EthpdpFD7InPEntry 301989888}

pr1645v2EthpdpFD7InPInDropNUCast OBJECT-TYPE
   SYNTAX      Counter64
   MAX-ACCESS  read-only
   STATUS      current
   DESCRIPTION
      "Path: ethernetPdp.performance.d7Performance.fInDiscardsNUCast

       64 bit unsigned wrappable counter."
   ::= {pr1645v2EthpdpFD7InPEntry 318767104}

pr1645v2EthpdpFD7InPInDropFilter OBJECT-TYPE
   SYNTAX      Counter64
   MAX-ACCESS  read-only
   STATUS      current
   DESCRIPTION
      "Path: ethernetPdp.performance.d7Performance.fInDiscardsFilter

       64 bit unsigned wrappable counter."
   ::= {pr1645v2EthpdpFD7InPEntry 385875968}

pr1645v2EthpdpFD7InPIfInBandwidth OBJECT-TYPE
   SYNTAX      Integer32
   MAX-ACCESS  read-only
   STATUS      current
   DESCRIPTION
      "Path: ethernetPdp.performance.d7Performance.ifInBandwidth

       unit name = bps
       formula = 8 * ; 8 /"
   ::= {pr1645v2EthpdpFD7InPEntry 268435456}

pr1645v2EthpdpFD7InPIfOutOctets OBJECT-TYPE
   SYNTAX      Counter64
   MAX-ACCESS  read-only
   STATUS      current
   DESCRIPTION
      "Path: ethernetPdp.performance.d7Performance.ifOutOctets

       64 bit unsigned wrappable counter."
   ::= {pr1645v2EthpdpFD7InPEntry 167772160}

pr1645v2EthpdpFD7InPIfOutUCPkts OBJECT-TYPE
   SYNTAX      Counter64
   MAX-ACCESS  read-only
   STATUS      current
   DESCRIPTION
      "Path: ethernetPdp.performance.d7Performance.ifOutUcastPkts

       64 bit unsigned wrappable counter."
   ::= {pr1645v2EthpdpFD7InPEntry 184549376}

pr1645v2EthpdpFD7InPIfOutNUCPkts OBJECT-TYPE
   SYNTAX      Counter64
   MAX-ACCESS  read-only
   STATUS      current
   DESCRIPTION
      "Path: ethernetPdp.performance.d7Performance.ifOutNUcastPkts

       64 bit unsigned wrappable counter."
   ::= {pr1645v2EthpdpFD7InPEntry 201326592}

pr1645v2EthpdpFD7InPIfOutBCPkts OBJECT-TYPE
   SYNTAX      Counter64
   MAX-ACCESS  read-only
   STATUS      current
   DESCRIPTION
      "Path: ethernetPdp.performance.d7Performance.ifOutBcastPkts

       64 bit unsigned wrappable counter."
   ::= {pr1645v2EthpdpFD7InPEntry 452984832}

pr1645v2EthpdpFD7InPIfOutMCPkts OBJECT-TYPE
   SYNTAX      Counter64
   MAX-ACCESS  read-only
   STATUS      current
   DESCRIPTION
      "Path: ethernetPdp.performance.d7Performance.ifOutMcastPkts

       64 bit unsigned wrappable counter."
   ::= {pr1645v2EthpdpFD7InPEntry 469762048}

pr1645v2EthpdpFD7InPIfOutDiscards OBJECT-TYPE
   SYNTAX      Counter64
   MAX-ACCESS  read-only
   STATUS      current
   DESCRIPTION
      "Path: ethernetPdp.performance.d7Performance.ifOutDiscards

       64 bit unsigned wrappable counter."
   ::= {pr1645v2EthpdpFD7InPEntry 218103808}

pr1645v2EthpdpFD7InPIfOutErrors OBJECT-TYPE
   SYNTAX      Counter64
   MAX-ACCESS  read-only
   STATUS      current
   DESCRIPTION
      "Path: ethernetPdp.performance.d7Performance.ifOutErrors

       64 bit unsigned wrappable counter."
   ::= {pr1645v2EthpdpFD7InPEntry 234881024}

pr1645v2EthpdpFD7InPOutDropEx OBJECT-TYPE
   SYNTAX      Counter64
   MAX-ACCESS  read-only
   STATUS      current
   DESCRIPTION
      "Path: ethernetPdp.performance.d7Performance.ifOutDropLevelExceeded

       64 bit unsigned wrappable counter."
   ::= {pr1645v2EthpdpFD7InPEntry 352321536}

pr1645v2EthpdpFD7InPOutDropNoArp OBJECT-TYPE
   SYNTAX      Counter64
   MAX-ACCESS  read-only
   STATUS      current
   DESCRIPTION
      "Path: ethernetPdp.performance.d7Performance.ifOutDiscardsNoArp

       64 bit unsigned wrappable counter."
   ::= {pr1645v2EthpdpFD7InPEntry 369098752}

pr1645v2EthpdpFD7InPOutDropFilter OBJECT-TYPE
   SYNTAX      Counter64
   MAX-ACCESS  read-only
   STATUS      current
   DESCRIPTION
      "Path: ethernetPdp.performance.d7Performance.ifOutDiscardsFilter

       64 bit unsigned wrappable counter."
   ::= {pr1645v2EthpdpFD7InPEntry 402653184}

pr1645v2EthpdpFD7InPIfOutBandwidth OBJECT-TYPE
   SYNTAX      Integer32
   MAX-ACCESS  read-only
   STATUS      current
   DESCRIPTION
      "Path: ethernetPdp.performance.d7Performance.ifOutBandwidth

       unit name = bps
       formula = 8 * ; 8 /"
   ::= {pr1645v2EthpdpFD7InPEntry 285212672}

pr1645v2EthpdpFD7InPIfErrSec OBJECT-TYPE
   SYNTAX      Counter32
   MAX-ACCESS  read-only
   STATUS      current
   DESCRIPTION
      "Path: ethernetPdp.performance.d7Performance.ifErrSec

       32 bit unsigned wrappable counter."
   ::= {pr1645v2EthpdpFD7InPEntry 251658240}



ar1645v2EthpdpF OBJECT IDENTIFIER ::= {r1645v2EthpdpF 16}


ar1645v2EthpdpFClearCounters OBJECT IDENTIFIER ::= {ar1645v2EthpdpF 263}

ar1645v2EthpdpFClearCountersTable OBJECT-TYPE
   SYNTAX      SEQUENCE OF Ar1645v2EthpdpFClearCountersEntry
   MAX-ACCESS  not-accessible
   STATUS      current
   DESCRIPTION
      "reset counters"
   ::= {ar1645v2EthpdpFClearCounters 1}

ar1645v2EthpdpFClearCountersEntry OBJECT-TYPE
   SYNTAX      Ar1645v2EthpdpFClearCountersEntry
   MAX-ACCESS  not-accessible
   STATUS      current
   DESCRIPTION
      ""
   INDEX      { ar1645v2EthpdpFClearCountersGlobalIx }
   ::= {ar1645v2EthpdpFClearCountersTable 1}

Ar1645v2EthpdpFClearCountersEntry ::=
   SEQUENCE
      {
      ar1645v2EthpdpFClearCountersGlobalIx
         GlobalIndex,
      ar1645v2EthpdpFClearCountersValue
         Integer32
      }

ar1645v2EthpdpFClearCountersGlobalIx OBJECT-TYPE
   SYNTAX      GlobalIndex
   MAX-ACCESS  not-accessible
   STATUS      current
   DESCRIPTION
      "The value of the tlsCntTreeGlobalIndex of the MANAGED OBJECT."
   ::= {ar1645v2EthpdpFClearCountersEntry 10}

ar1645v2EthpdpFClearCountersValue OBJECT-TYPE
   SYNTAX      Integer32
   MAX-ACCESS  read-write
   STATUS      current
   DESCRIPTION
      "Path: ethernetPdp.actions.clearCounters"
   ::= {ar1645v2EthpdpFClearCountersEntry 2147483648}



END
