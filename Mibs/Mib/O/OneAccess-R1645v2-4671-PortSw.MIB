OneAccess-R1645v2-4671-PortSw DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PortSw OBJECT IDENTIFIER ::= {r1645Rootv2 4671}

r1645v2PortSwMOProp OBJECT IDENTIFIER ::= {r1645v2PortSw 1}

r1645v2PortSwMOPropEntry OBJECT IDENTIFIER ::= {r1645v2PortSwMOProp 1}

r1645v2PortSwMOPropPath OBJECT-TYPE
   SYNTAX      ContainmentPath
   MAX-ACCESS  read-only
   STATUS      current
   DESCRIPTION
      "Textual description of the containment tree from the instance of
       the root object down to the instance of the current object."
   ::= {r1645v2PortSwMOPropEntry 3}

r1645v2PortSwMOPropRev OBJECT-TYPE
   SYNTAX      ObjectRevision
   MAX-ACCESS  read-only
   STATUS      current
   DESCRIPTION
      "This value corresponds with the revision of the MANAGED OBJECT."
   ::= {r1645v2PortSwMOPropEntry 4}



er1645v2PortSw OBJECT IDENTIFIER ::= {r1645v2PortSw 11}


er1645v2PortSwRemark OBJECT-TYPE
   SYNTAX      DisplayString
   MAX-ACCESS  read-write
   STATUS      current
   DESCRIPTION
      "Path: ethernet1.editConf.remark
       Info: intfRemark"
   ::= {er1645v2PortSw 321}


er1645v2PortSwAdminStatus OBJECT-TYPE
   SYNTAX      INTEGER
               {
               up (1),
               down (2)
               }
   MAX-ACCESS  read-write
   STATUS      current
   DESCRIPTION
      "Path: ethernet1.editConf.adminStatus
       Info: ifAdminStatus

       Possibilities:
               up   (1)
               down   (2)"
   ::= {er1645v2PortSw 106}


er1645v2PortSwAlarmMask OBJECT-TYPE
   SYNTAX      Integer32
   MAX-ACCESS  read-write
   STATUS      current
   DESCRIPTION
      "Path: ethernet1.editConf.alarmMask
       Info: ifAlarmMask

       Bit meanings:
               bit 0 = linkDown"
   ::= {er1645v2PortSw 135}


er1645v2PortSwAlarmLev OBJECT IDENTIFIER ::= {er1645v2PortSw 170}

er1645v2PortSwAlarmLevSSC OBJECT IDENTIFIER ::= {er1645v2PortSwAlarmLev 1}

er1645v2PortSwAlarmLevEntry OBJECT IDENTIFIER ::= {er1645v2PortSwAlarmLevSSC 1}

er1645v2PortSwAlarmLevLinkDown OBJECT-TYPE
   SYNTAX      Integer32
   MAX-ACCESS  read-write
   STATUS      current
   DESCRIPTION
      "Path: ethernet1.editConf.alarmLevel.linkDown"
   ::= {er1645v2PortSwAlarmLevEntry 16777216}


er1645v2PortSwBw OBJECT IDENTIFIER ::= {er1645v2PortSw 5}

er1645v2PortSwBwSSC OBJECT IDENTIFIER ::= {er1645v2PortSwBw 1}

er1645v2PortSwBwEntry OBJECT IDENTIFIER ::= {er1645v2PortSwBwSSC 1}

er1645v2PortSwBwMode OBJECT-TYPE
   SYNTAX      INTEGER
               {
               reshaping (1),
               policing (2),
               policingReshape (3)
               }
   MAX-ACCESS  read-write
   STATUS      current
   DESCRIPTION
      "Path: ethernet1.editConf.bandwidth.mode

       Possibilities:
               reshaping   (1)
               policing   (2)
               policingReshape   (3)"
   ::= {er1645v2PortSwBwEntry 3758096384}

er1645v2PortSwBwCir OBJECT-TYPE
   SYNTAX      Integer32
   MAX-ACCESS  read-write
   STATUS      current
   DESCRIPTION
      "Path: ethernet1.editConf.bandwidth.cir"
   ::= {er1645v2PortSwBwEntry 268435456}

er1645v2PortSwBwEir OBJECT-TYPE
   SYNTAX      Integer32
   MAX-ACCESS  read-write
   STATUS      current
   DESCRIPTION
      "Path: ethernet1.editConf.bandwidth.eir"
   ::= {er1645v2PortSwBwEntry 1879048192}

er1645v2PortSwBwUnit OBJECT-TYPE
   SYNTAX      INTEGER
               {
               bitssec (1),
               percent (2)
               }
   MAX-ACCESS  read-write
   STATUS      current
   DESCRIPTION
      "Path: ethernet1.editConf.bandwidth.unit

       Possibilities:
               bits/sec   (1)
               percent   (2)"
   ::= {er1645v2PortSwBwEntry 1342177280}

er1645v2PortSwBwTc OBJECT-TYPE
   SYNTAX      INTEGER
               {
               auto (0)
               }
   MAX-ACCESS  read-write
   STATUS      current
   DESCRIPTION
      "Path: ethernet1.editConf.bandwidth.tc

       Possibilities:
               auto   (0)"
   ::= {er1645v2PortSwBwEntry 1610612736}

er1645v2PortSwBwTcFactor OBJECT-TYPE
   SYNTAX      INTEGER
               {
               ms (10),
               s100us (1)
               }
   MAX-ACCESS  read-write
   STATUS      current
   DESCRIPTION
      "Path: ethernet1.editConf.bandwidth.tcFactor

       Possibilities:
               ms   (10)
               *100us   (1)"
   ::= {er1645v2PortSwBwEntry 2147483648}

er1645v2PortSwBwCorrType OBJECT-TYPE
   SYNTAX      INTEGER
               {
               noCorrection (0),
               predefined (1),
               manual (2)
               }
   MAX-ACCESS  read-write
   STATUS      current
   DESCRIPTION
      "Path: ethernet1.editConf.bandwidth.correction.type

       Possibilities:
               noCorrection   (0)
               predefined   (1)
               manual   (2)"
   ::= {er1645v2PortSwBwEntry 570425344}

er1645v2PortSwBwCorrPredefEncapsFrameRelay OBJECT-TYPE
   SYNTAX      DisplayString
   MAX-ACCESS  read-write
   STATUS      current
   DESCRIPTION
      "Path: ethernet1.editConf.bandwidth.correction.predefined.encapsulation.frameRelay"
   ::= {er1645v2PortSwBwEntry 608436224}

er1645v2PortSwBwCorrPredefEncapsPpp OBJECT-TYPE
   SYNTAX      DisplayString
   MAX-ACCESS  read-write
   STATUS      current
   DESCRIPTION
      "Path: ethernet1.editConf.bandwidth.correction.predefined.encapsulation.ppp"
   ::= {er1645v2PortSwBwEntry 608698368}

er1645v2PortSwBwCorrPredefEncapsAtmHl OBJECT-TYPE
   SYNTAX      INTEGER
               {
               rfc2684 (0),
               ppp (1),
               pppOverEthernet (2)
               }
   MAX-ACCESS  read-write
   STATUS      current
   DESCRIPTION
      "Path: ethernet1.editConf.bandwidth.correction.predefined.encapsulation.atm.higherLayer

       Possibilities:
               rfc2684   (0)
               ppp   (1)
               pppOverEthernet   (2)"
   ::= {er1645v2PortSwBwEntry 608993280}

er1645v2PortSwBwCorrPredefEncapsAtmMp OBJECT-TYPE
   SYNTAX      INTEGER
               {
               llcEncapsulation (0),
               vcMultiplexing (1)
               }
   MAX-ACCESS  read-write
   STATUS      current
   DESCRIPTION
      "Path: ethernet1.editConf.bandwidth.correction.predefined.encapsulation.atm.multiProtocol

       Possibilities:
               llcEncapsulation   (0)
               vcMultiplexing   (1)"
   ::= {er1645v2PortSwBwEntry 609026048}

er1645v2PortSwBwCorrPredefEncapsHdlc OBJECT-TYPE
   SYNTAX      DisplayString
   MAX-ACCESS  read-write
   STATUS      current
   DESCRIPTION
      "Path: ethernet1.editConf.bandwidth.correction.predefined.encapsulation.hdlc"
   ::= {er1645v2PortSwBwEntry 609222656}

er1645v2PortSwBwCorrPredefEncapsEfmFs OBJECT-TYPE
   SYNTAX      Integer32
   MAX-ACCESS  read-write
   STATUS      current
   DESCRIPTION
      "Path: ethernet1.editConf.bandwidth.correction.predefined.encapsulation.efm.fragmentSize"
   ::= {er1645v2PortSwBwEntry 609517568}

er1645v2PortSwBwCorrPredefEncapsEfmIb OBJECT-TYPE
   SYNTAX      Integer32
   MAX-ACCESS  read-write
   STATUS      current
   DESCRIPTION
      "Path: ethernet1.editConf.bandwidth.correction.predefined.encapsulation.efm.idleBytes"
   ::= {er1645v2PortSwBwEntry 609550336}

er1645v2PortSwBwCorrPredefMode OBJECT-TYPE
   SYNTAX      INTEGER
               {
               routing (0),
               bridging (1)
               }
   MAX-ACCESS  read-write
   STATUS      current
   DESCRIPTION
      "Path: ethernet1.editConf.bandwidth.correction.predefined.mode

       Possibilities:
               routing   (0)
               bridging   (1)"
   ::= {er1645v2PortSwBwEntry 612368384}

er1645v2PortSwBwCorrManualOverhead OBJECT-TYPE
   SYNTAX      Integer32
   MAX-ACCESS  read-write
   STATUS      current
   DESCRIPTION
      "Path: ethernet1.editConf.bandwidth.correction.manual.overhead"
   ::= {er1645v2PortSwBwEntry 637665280}

er1645v2PortSwBwCorrManualFrameData OBJECT-TYPE
   SYNTAX      Counter32
   MAX-ACCESS  read-write
   STATUS      current
   DESCRIPTION
      "Path: ethernet1.editConf.bandwidth.correction.manual.frameData

       32 bit unsigned wrappable counter."
   ::= {er1645v2PortSwBwEntry 637796352}

er1645v2PortSwBwCorrManualFrameHeader OBJECT-TYPE
   SYNTAX      Counter32
   MAX-ACCESS  read-write
   STATUS      current
   DESCRIPTION
      "Path: ethernet1.editConf.bandwidth.correction.manual.frameHeader

       32 bit unsigned wrappable counter."
   ::= {er1645v2PortSwBwEntry 637927424}

er1645v2PortSwBwMaxFifoQLen OBJECT-TYPE
   SYNTAX      Integer32
   MAX-ACCESS  read-write
   STATUS      current
   DESCRIPTION
      "Path: ethernet1.editConf.bandwidth.maxFifoQLen"
   ::= {er1645v2PortSwBwEntry 805306368}

er1645v2PortSwBwDeFlagCir OBJECT-TYPE
   SYNTAX      INTEGER
               {
               allowed (1),
               notAllowed (2)
               }
   MAX-ACCESS  read-write
   STATUS      current
   DESCRIPTION
      "Path: ethernet1.editConf.bandwidth.deFlag.cir

       Possibilities:
               allowed   (1)
               notAllowed   (2)"
   ::= {er1645v2PortSwBwEntry 3490709504}

er1645v2PortSwBwDeFlagEir OBJECT-TYPE
   SYNTAX      INTEGER
               {
               allowed (1),
               notAllowed (2)
               }
   MAX-ACCESS  read-write
   STATUS      current
   DESCRIPTION
      "Path: ethernet1.editConf.bandwidth.deFlag.eir

       Possibilities:
               allowed   (1)
               notAllowed   (2)"
   ::= {er1645v2PortSwBwEntry 3491758080}

er1645v2PortSwBwDeFlagViolate OBJECT-TYPE
   SYNTAX      INTEGER
               {
               allowed (1),
               notAllowed (2)
               }
   MAX-ACCESS  read-write
   STATUS      current
   DESCRIPTION
      "Path: ethernet1.editConf.bandwidth.deFlag.violate

       Possibilities:
               allowed   (1)
               notAllowed   (2)"
   ::= {er1645v2PortSwBwEntry 3492806656}

er1645v2PortSwBwActCirActNone OBJECT-TYPE
   SYNTAX      OCTET STRING
   MAX-ACCESS  read-write
   STATUS      current
   DESCRIPTION
      "Path: ethernet1.editConf.bandwidth.action.cirAction.none"
   ::= {er1645v2PortSwBwEntry 4062183424}

er1645v2PortSwBwActCirActEthCos1 OBJECT-TYPE
   SYNTAX      INTEGER
               {
               unchanged (256)
               }
   MAX-ACCESS  read-write
   STATUS      current
   DESCRIPTION
      "Path: ethernet1.editConf.bandwidth.action.cirAction.ethernet.cosDepth1

       Possibilities:
               unchanged   (256)"
   ::= {er1645v2PortSwBwEntry 4064346112}

er1645v2PortSwBwActCirActEthDei1 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth1

       Possibilities:
               unchanged   (255)
               clear   (0)
               set   (1)"
   ::= {er1645v2PortSwBwEntry 4065656832}

er1645v2PortSwBwActCirActEthCos2 OBJECT-TYPE
   SYNTAX      INTEGER
               {
               unchanged (256)
               }
   MAX-ACCESS  read-write
   STATUS      current
   DESCRIPTION
      "Path: ethernet1.editConf.bandwidth.action.cirAction.ethernet.cosDepth2

       Possibilities:
               unchanged   (256)"
   ::= {er1645v2PortSwBwEntry 4064411648}

er1645v2PortSwBwActCirActEthDei2 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth2

       Possibilities:
               unchanged   (255)
               clear   (0)
               set   (1)"
   ::= {er1645v2PortSwBwEntry 4065722368}

er1645v2PortSwBwActCirActEthCos3 OBJECT-TYPE
   SYNTAX      INTEGER
               {
               unchanged (256)
               }
   MAX-ACCESS  read-write
   STATUS      current
   DESCRIPTION
      "Path: ethernet1.editConf.bandwidth.action.cirAction.ethernet.cosDepth3

       Possibilities:
               unchanged   (256)"
   ::= {er1645v2PortSwBwEntry 4064477184}

er1645v2PortSwBwActCirActEthDei3 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth3

       Possibilities:
               unchanged   (255)
               clear   (0)
               set   (1)"
   ::= {er1645v2PortSwBwEntry 4065787904}

er1645v2PortSwBwActCirActEthCos4 OBJECT-TYPE
   SYNTAX      INTEGER
               {
               unchanged (256)
               }
   MAX-ACCESS  read-write
   STATUS      current
   DESCRIPTION
      "Path: ethernet1.editConf.bandwidth.action.cirAction.ethernet.cosDepth4

       Possibilities:
               unchanged   (256)"
   ::= {er1645v2PortSwBwEntry 4064542720}

er1645v2PortSwBwActCirActEthDei4 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth4

       Possibilities:
               unchanged   (255)
               clear   (0)
               set   (1)"
   ::= {er1645v2PortSwBwEntry 4065853440}

er1645v2PortSwBwActCirActEthCos5 OBJECT-TYPE
   SYNTAX      INTEGER
               {
               unchanged (256)
               }
   MAX-ACCESS  read-write
   STATUS      current
   DESCRIPTION
      "Path: ethernet1.editConf.bandwidth.action.cirAction.ethernet.cosDepth5

       Possibilities:
               unchanged   (256)"
   ::= {er1645v2PortSwBwEntry 4064608256}

er1645v2PortSwBwActCirActEthDei5 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth5

       Possibilities:
               unchanged   (255)
               clear   (0)
               set   (1)"
   ::= {er1645v2PortSwBwEntry 4065918976}

er1645v2PortSwBwActCirActEthCos6 OBJECT-TYPE
   SYNTAX      INTEGER
               {
               unchanged (256)
               }
   MAX-ACCESS  read-write
   STATUS      current
   DESCRIPTION
      "Path: ethernet1.editConf.bandwidth.action.cirAction.ethernet.cosDepth6

       Possibilities:
               unchanged   (256)"
   ::= {er1645v2PortSwBwEntry 4064673792}

er1645v2PortSwBwActCirActEthDei6 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth6

       Possibilities:
               unchanged   (255)
               clear   (0)
               set   (1)"
   ::= {er1645v2PortSwBwEntry 4065984512}

er1645v2PortSwBwActCirActEthCos7 OBJECT-TYPE
   SYNTAX      INTEGER
               {
               unchanged (256)
               }
   MAX-ACCESS  read-write
   STATUS      current
   DESCRIPTION
      "Path: ethernet1.editConf.bandwidth.action.cirAction.ethernet.cosDepth7

       Possibilities:
               unchanged   (256)"
   ::= {er1645v2PortSwBwEntry 4064739328}

er1645v2PortSwBwActCirActEthDei7 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth7

       Possibilities:
               unchanged   (255)
               clear   (0)
               set   (1)"
   ::= {er1645v2PortSwBwEntry 4066050048}

er1645v2PortSwBwActCirActEthCos8 OBJECT-TYPE
   SYNTAX      INTEGER
               {
               unchanged (256)
               }
   MAX-ACCESS  read-write
   STATUS      current
   DESCRIPTION
      "Path: ethernet1.editConf.bandwidth.action.cirAction.ethernet.cosDepth8

       Possibilities:
               unchanged   (256)"
   ::= {er1645v2PortSwBwEntry 4064804864}

er1645v2PortSwBwActCirActEthDei8 OBJECT-TYPE
   SYNTAX      INTEGER
               {
               unchanged (255),
               clear (0),
               set (1)
               }
   MAX-ACCESS  read-write
   STATUS      current
   DESCRIPTION
      "Path: ethernet1.editConf.bandwidth.action.cirAction.ethernet.deiDepth8

       Possibilities:
               unchanged   (255)
               clear   (0)
               set   (1)"
   ::= {er1645v2PortSwBwEntry 4066115584}

er1645v2PortSwBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4064870400}

er1645v2PortSwBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4064935936}

er1645v2PortSwBwActCirActEthDrpLev OBJECT-TYPE
   SYNTAX      INTEGER
               {
               unchanged (0)
               }
   MAX-ACCESS  read-write
   STATUS      current
   DESCRIPTION
      "Path: ethernet1.editConf.bandwidth.action.cirAction.ethernet.dropLevel

       Possibilities:
               unchanged   (0)"
   ::= {er1645v2PortSwBwEntry 4065001472}

er1645v2PortSwBwActCirActEthDeFlag OBJECT-TYPE
   SYNTAX      INTEGER
               {
               unchanged (255),
               clear (0),
               set (1)
               }
   MAX-ACCESS  read-write
   STATUS      current
   DESCRIPTION
      "Path: ethernet1.editConf.bandwidth.action.cirAction.ethernet.deFlag

       Possibilities:
               unchanged   (255)
               clear   (0)
               set   (1)"
   ::= {er1645v2PortSwBwEntry 4065198080}

er1645v2PortSwBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4071161856}

er1645v2PortSwBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4071227392}

er1645v2PortSwBwActCirActIpDrpLev OBJECT-TYPE
   SYNTAX      INTEGER
               {
               unchanged (0)
               }
   MAX-ACCESS  read-write
   STATUS      current
   DESCRIPTION
      "Path: ethernet1.editConf.bandwidth.action.cirAction.ip.dropLevel

       Possibilities:
               unchanged   (0)"
   ::= {er1645v2PortSwBwEntry 4071292928}

er1645v2PortSwBwActCirActIpDeFlag OBJECT-TYPE
   SYNTAX      INTEGER
               {
               unchanged (255),
               clear (0),
               set (1)
               }
   MAX-ACCESS  read-write
   STATUS      current
   DESCRIPTION
      "Path: ethernet1.editConf.bandwidth.action.cirAction.ip.deFlag

       Possibilities:
               unchanged   (255)
               clear   (0)
               set   (1)"
   ::= {er1645v2PortSwBwEntry 4071489536}

er1645v2PortSwBwActEirActNone OBJECT-TYPE
   SYNTAX      OCTET STRING
   MAX-ACCESS  read-write
   STATUS      current
   DESCRIPTION
      "Path: ethernet1.editConf.bandwidth.action.eirAction.none"
   ::= {er1645v2PortSwBwEntry 4095737856}

er1645v2PortSwBwActEirActEthCos1 OBJECT-TYPE
   SYNTAX      INTEGER
               {
               unchanged (256)
               }
   MAX-ACCESS  read-write
   STATUS      current
   DESCRIPTION
      "Path: ethernet1.editConf.bandwidth.action.eirAction.ethernet.cosDepth1

       Possibilities:
               unchanged   (256)"
   ::= {er1645v2PortSwBwEntry 4097900544}

er1645v2PortSwBwActEirActEthDei1 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth1

       Possibilities:
               unchanged   (255)
               clear   (0)
               set   (1)"
   ::= {er1645v2PortSwBwEntry 4099211264}

er1645v2PortSwBwActEirActEthCos2 OBJECT-TYPE
   SYNTAX      INTEGER
               {
               unchanged (256)
               }
   MAX-ACCESS  read-write
   STATUS      current
   DESCRIPTION
      "Path: ethernet1.editConf.bandwidth.action.eirAction.ethernet.cosDepth2

       Possibilities:
               unchanged   (256)"
   ::= {er1645v2PortSwBwEntry 4097966080}

er1645v2PortSwBwActEirActEthDei2 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth2

       Possibilities:
               unchanged   (255)
               clear   (0)
               set   (1)"
   ::= {er1645v2PortSwBwEntry 4099276800}

er1645v2PortSwBwActEirActEthCos3 OBJECT-TYPE
   SYNTAX      INTEGER
               {
               unchanged (256)
               }
   MAX-ACCESS  read-write
   STATUS      current
   DESCRIPTION
      "Path: ethernet1.editConf.bandwidth.action.eirAction.ethernet.cosDepth3

       Possibilities:
               unchanged   (256)"
   ::= {er1645v2PortSwBwEntry 4098031616}

er1645v2PortSwBwActEirActEthDei3 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth3

       Possibilities:
               unchanged   (255)
               clear   (0)
               set   (1)"
   ::= {er1645v2PortSwBwEntry 4099342336}

er1645v2PortSwBwActEirActEthCos4 OBJECT-TYPE
   SYNTAX      INTEGER
               {
               unchanged (256)
               }
   MAX-ACCESS  read-write
   STATUS      current
   DESCRIPTION
      "Path: ethernet1.editConf.bandwidth.action.eirAction.ethernet.cosDepth4

       Possibilities:
               unchanged   (256)"
   ::= {er1645v2PortSwBwEntry 4098097152}

er1645v2PortSwBwActEirActEthDei4 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth4

       Possibilities:
               unchanged   (255)
               clear   (0)
               set   (1)"
   ::= {er1645v2PortSwBwEntry 4099407872}

er1645v2PortSwBwActEirActEthCos5 OBJECT-TYPE
   SYNTAX      INTEGER
               {
               unchanged (256)
               }
   MAX-ACCESS  read-write
   STATUS      current
   DESCRIPTION
      "Path: ethernet1.editConf.bandwidth.action.eirAction.ethernet.cosDepth5

       Possibilities:
               unchanged   (256)"
   ::= {er1645v2PortSwBwEntry 4098162688}

er1645v2PortSwBwActEirActEthDei5 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth5

       Possibilities:
               unchanged   (255)
               clear   (0)
               set   (1)"
   ::= {er1645v2PortSwBwEntry 4099473408}

er1645v2PortSwBwActEirActEthCos6 OBJECT-TYPE
   SYNTAX      INTEGER
               {
               unchanged (256)
               }
   MAX-ACCESS  read-write
   STATUS      current
   DESCRIPTION
      "Path: ethernet1.editConf.bandwidth.action.eirAction.ethernet.cosDepth6

       Possibilities:
               unchanged   (256)"
   ::= {er1645v2PortSwBwEntry 4098228224}

er1645v2PortSwBwActEirActEthDei6 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth6

       Possibilities:
               unchanged   (255)
               clear   (0)
               set   (1)"
   ::= {er1645v2PortSwBwEntry 4099538944}

er1645v2PortSwBwActEirActEthCos7 OBJECT-TYPE
   SYNTAX      INTEGER
               {
               unchanged (256)
               }
   MAX-ACCESS  read-write
   STATUS      current
   DESCRIPTION
      "Path: ethernet1.editConf.bandwidth.action.eirAction.ethernet.cosDepth7

       Possibilities:
               unchanged   (256)"
   ::= {er1645v2PortSwBwEntry 4098293760}

er1645v2PortSwBwActEirActEthDei7 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth7

       Possibilities:
               unchanged   (255)
               clear   (0)
               set   (1)"
   ::= {er1645v2PortSwBwEntry 4099604480}

er1645v2PortSwBwActEirActEthCos8 OBJECT-TYPE
   SYNTAX      INTEGER
               {
               unchanged (256)
               }
   MAX-ACCESS  read-write
   STATUS      current
   DESCRIPTION
      "Path: ethernet1.editConf.bandwidth.action.eirAction.ethernet.cosDepth8

       Possibilities:
               unchanged   (256)"
   ::= {er1645v2PortSwBwEntry 4098359296}

er1645v2PortSwBwActEirActEthDei8 OBJECT-TYPE
   SYNTAX      INTEGER
               {
               unchanged (255),
               clear (0),
               set (1)
               }
   MAX-ACCESS  read-write
   STATUS      current
   DESCRIPTION
      "Path: ethernet1.editConf.bandwidth.action.eirAction.ethernet.deiDepth8

       Possibilities:
               unchanged   (255)
               clear   (0)
               set   (1)"
   ::= {er1645v2PortSwBwEntry 4099670016}

er1645v2PortSwBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4098424832}

er1645v2PortSwBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4098490368}

er1645v2PortSwBwActEirActEthDrpLev OBJECT-TYPE
   SYNTAX      INTEGER
               {
               unchanged (0)
               }
   MAX-ACCESS  read-write
   STATUS      current
   DESCRIPTION
      "Path: ethernet1.editConf.bandwidth.action.eirAction.ethernet.dropLevel

       Possibilities:
               unchanged   (0)"
   ::= {er1645v2PortSwBwEntry 4098555904}

er1645v2PortSwBwActEirActEthDeFlag OBJECT-TYPE
   SYNTAX      INTEGER
               {
               unchanged (255),
               clear (0),
               set (1)
               }
   MAX-ACCESS  read-write
   STATUS      current
   DESCRIPTION
      "Path: ethernet1.editConf.bandwidth.action.eirAction.ethernet.deFlag

       Possibilities:
               unchanged   (255)
               clear   (0)
               set   (1)"
   ::= {er1645v2PortSwBwEntry 4098752512}

er1645v2PortSwBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4104716288}

er1645v2PortSwBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4104781824}

er1645v2PortSwBwActEirActIpDrpLev OBJECT-TYPE
   SYNTAX      INTEGER
               {
               unchanged (0)
               }
   MAX-ACCESS  read-write
   STATUS      current
   DESCRIPTION
      "Path: ethernet1.editConf.bandwidth.action.eirAction.ip.dropLevel

       Possibilities:
               unchanged   (0)"
   ::= {er1645v2PortSwBwEntry 4104847360}

er1645v2PortSwBwActEirActIpDeFlag OBJECT-TYPE
   SYNTAX      INTEGER
               {
               unchanged (255),
               clear (0),
               set (1)
               }
   MAX-ACCESS  read-write
   STATUS      current
   DESCRIPTION
      "Path: ethernet1.editConf.bandwidth.action.eirAction.ip.deFlag

       Possibilities:
               unchanged   (255)
               clear   (0)
               set   (1)"
   ::= {er1645v2PortSwBwEntry 4105043968}

er1645v2PortSwBwActViolActNone OBJECT-TYPE
   SYNTAX      OCTET STRING
   MAX-ACCESS  read-write
   STATUS      current
   DESCRIPTION
      "Path: ethernet1.editConf.bandwidth.action.violateAction.none"
   ::= {er1645v2PortSwBwEntry 4129292288}

er1645v2PortSwBwActViolActDrop OBJECT-TYPE
   SYNTAX      OCTET STRING
   MAX-ACCESS  read-write
   STATUS      current
   DESCRIPTION
      "Path: ethernet1.editConf.bandwidth.action.violateAction.drop"
   ::= {er1645v2PortSwBwEntry 4133486592}

er1645v2PortSwBwActViolActEthCos1 OBJECT-TYPE
   SYNTAX      INTEGER
               {
               unchanged (256)
               }
   MAX-ACCESS  read-write
   STATUS      current
   DESCRIPTION
      "Path: ethernet1.editConf.bandwidth.action.violateAction.ethernet.cosDepth1

       Possibilities:
               unchanged   (256)"
   ::= {er1645v2PortSwBwEntry 4131454976}

er1645v2PortSwBwActViolActEthDei1 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth1

       Possibilities:
               unchanged   (255)
               clear   (0)
               set   (1)"
   ::= {er1645v2PortSwBwEntry 4132765696}

er1645v2PortSwBwActViolActEthCos2 OBJECT-TYPE
   SYNTAX      INTEGER
               {
               unchanged (256)
               }
   MAX-ACCESS  read-write
   STATUS      current
   DESCRIPTION
      "Path: ethernet1.editConf.bandwidth.action.violateAction.ethernet.cosDepth2

       Possibilities:
               unchanged   (256)"
   ::= {er1645v2PortSwBwEntry 4131520512}

er1645v2PortSwBwActViolActEthDei2 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth2

       Possibilities:
               unchanged   (255)
               clear   (0)
               set   (1)"
   ::= {er1645v2PortSwBwEntry 4132831232}

er1645v2PortSwBwActViolActEthCos3 OBJECT-TYPE
   SYNTAX      INTEGER
               {
               unchanged (256)
               }
   MAX-ACCESS  read-write
   STATUS      current
   DESCRIPTION
      "Path: ethernet1.editConf.bandwidth.action.violateAction.ethernet.cosDepth3

       Possibilities:
               unchanged   (256)"
   ::= {er1645v2PortSwBwEntry 4131586048}

er1645v2PortSwBwActViolActEthDei3 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth3

       Possibilities:
               unchanged   (255)
               clear   (0)
               set   (1)"
   ::= {er1645v2PortSwBwEntry 4132896768}

er1645v2PortSwBwActViolActEthCos4 OBJECT-TYPE
   SYNTAX      INTEGER
               {
               unchanged (256)
               }
   MAX-ACCESS  read-write
   STATUS      current
   DESCRIPTION
      "Path: ethernet1.editConf.bandwidth.action.violateAction.ethernet.cosDepth4

       Possibilities:
               unchanged   (256)"
   ::= {er1645v2PortSwBwEntry 4131651584}

er1645v2PortSwBwActViolActEthDei4 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth4

       Possibilities:
               unchanged   (255)
               clear   (0)
               set   (1)"
   ::= {er1645v2PortSwBwEntry 4132962304}

er1645v2PortSwBwActViolActEthCos5 OBJECT-TYPE
   SYNTAX      INTEGER
               {
               unchanged (256)
               }
   MAX-ACCESS  read-write
   STATUS      current
   DESCRIPTION
      "Path: ethernet1.editConf.bandwidth.action.violateAction.ethernet.cosDepth5

       Possibilities:
               unchanged   (256)"
   ::= {er1645v2PortSwBwEntry 4131717120}

er1645v2PortSwBwActViolActEthDei5 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth5

       Possibilities:
               unchanged   (255)
               clear   (0)
               set   (1)"
   ::= {er1645v2PortSwBwEntry 4133027840}

er1645v2PortSwBwActViolActEthCos6 OBJECT-TYPE
   SYNTAX      INTEGER
               {
               unchanged (256)
               }
   MAX-ACCESS  read-write
   STATUS      current
   DESCRIPTION
      "Path: ethernet1.editConf.bandwidth.action.violateAction.ethernet.cosDepth6

       Possibilities:
               unchanged   (256)"
   ::= {er1645v2PortSwBwEntry 4131782656}

er1645v2PortSwBwActViolActEthDei6 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth6

       Possibilities:
               unchanged   (255)
               clear   (0)
               set   (1)"
   ::= {er1645v2PortSwBwEntry 4133093376}

er1645v2PortSwBwActViolActEthCos7 OBJECT-TYPE
   SYNTAX      INTEGER
               {
               unchanged (256)
               }
   MAX-ACCESS  read-write
   STATUS      current
   DESCRIPTION
      "Path: ethernet1.editConf.bandwidth.action.violateAction.ethernet.cosDepth7

       Possibilities:
               unchanged   (256)"
   ::= {er1645v2PortSwBwEntry 4131848192}

er1645v2PortSwBwActViolActEthDei7 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth7

       Possibilities:
               unchanged   (255)
               clear   (0)
               set   (1)"
   ::= {er1645v2PortSwBwEntry 4133158912}

er1645v2PortSwBwActViolActEthCos8 OBJECT-TYPE
   SYNTAX      INTEGER
               {
               unchanged (256)
               }
   MAX-ACCESS  read-write
   STATUS      current
   DESCRIPTION
      "Path: ethernet1.editConf.bandwidth.action.violateAction.ethernet.cosDepth8

       Possibilities:
               unchanged   (256)"
   ::= {er1645v2PortSwBwEntry 4131913728}

er1645v2PortSwBwActViolActEthDei8 OBJECT-TYPE
   SYNTAX      INTEGER
               {
               unchanged (255),
               clear (0),
               set (1)
               }
   MAX-ACCESS  read-write
   STATUS      current
   DESCRIPTION
      "Path: ethernet1.editConf.bandwidth.action.violateAction.ethernet.deiDepth8

       Possibilities:
               unchanged   (255)
               clear   (0)
               set   (1)"
   ::= {er1645v2PortSwBwEntry 4133224448}

er1645v2PortSwBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4131979264}

er1645v2PortSwBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4132044800}

er1645v2PortSwBwActViolActEthDrpLev OBJECT-TYPE
   SYNTAX      INTEGER
               {
               unchanged (0)
               }
   MAX-ACCESS  read-write
   STATUS      current
   DESCRIPTION
      "Path: ethernet1.editConf.bandwidth.action.violateAction.ethernet.dropLevel

       Possibilities:
               unchanged   (0)"
   ::= {er1645v2PortSwBwEntry 4132110336}

er1645v2PortSwBwActViolActEthDeFlag OBJECT-TYPE
   SYNTAX      INTEGER
               {
               unchanged (255),
               clear (0),
               set (1)
               }
   MAX-ACCESS  read-write
   STATUS      current
   DESCRIPTION
      "Path: ethernet1.editConf.bandwidth.action.violateAction.ethernet.deFlag

       Possibilities:
               unchanged   (255)
               clear   (0)
               set   (1)"
   ::= {er1645v2PortSwBwEntry 4132306944}

er1645v2PortSwBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwBwEntry 4138270720}

er1645v2PortSwBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwBwEntry 4138336256}

er1645v2PortSwBwActViolActIpDrpLev OBJECT-TYPE
   SYNTAX      INTEGER
               {
               unchanged (0)
               }
   MAX-ACCESS  read-write
   STATUS      current
   DESCRIPTION
      "Path: ethernet1.editConf.bandwidth.action.violateAction.ip.dropLevel

       Possibilities:
               unchanged   (0)"
   ::= {er1645v2PortSwBwEntry 4138401792}

er1645v2PortSwBwActViolActIpDeFlag OBJECT-TYPE
   SYNTAX      INTEGER
               {
               unchanged (255),
               clear (0),
               set (1)
               }
   MAX-ACCESS  read-write
   STATUS      current
   DESCRIPTION
      "Path: ethernet1.editConf.bandwidth.action.violateAction.ip.deFlag

       Possibilities:
               unchanged   (255)
               clear   (0)
               set   (1)"
   ::= {er1645v2PortSwBwEntry 4138598400}


er1645v2PortSwPriorityPolicy OBJECT-TYPE
   SYNTAX      DisplayString
   MAX-ACCESS  read-write
   STATUS      current
   DESCRIPTION
      "Path: ethernet1.editConf.priorityPolicy
       Info: Preferred Policy"
   ::= {er1645v2PortSw 39}


er1645v2PortSwMru OBJECT-TYPE
   SYNTAX      Integer32
   MAX-ACCESS  read-write
   STATUS      current
   DESCRIPTION
      "Path: ethernet1.editConf.mru"
   ::= {er1645v2PortSw 43}


er1645v2PortSwDelayOptimisation OBJECT-TYPE
   SYNTAX      INTEGER
               {
               disabled (0),
               enabled (1)
               }
   MAX-ACCESS  read-write
   STATUS      current
   DESCRIPTION
      "Path: ethernet1.editConf.delayOptimisation
       Info: optimise delay

       Possibilities:
               disabled   (0)
               enabled   (1)"
   ::= {er1645v2PortSw 80}


er1645v2PortSwIbw OBJECT IDENTIFIER ::= {er1645v2PortSw 13}

er1645v2PortSwIbwSSC OBJECT IDENTIFIER ::= {er1645v2PortSwIbw 1}

er1645v2PortSwIbwEntry OBJECT IDENTIFIER ::= {er1645v2PortSwIbwSSC 1}

er1645v2PortSwIbwMode OBJECT-TYPE
   SYNTAX      INTEGER
               {
               reshaping (1),
               policing (2)
               }
   MAX-ACCESS  read-write
   STATUS      current
   DESCRIPTION
      "Path: ethernet1.editConf.inboundBandwidth.mode

       Possibilities:
               reshaping   (1)
               policing   (2)"
   ::= {er1645v2PortSwIbwEntry 3758096384}

er1645v2PortSwIbwCir OBJECT-TYPE
   SYNTAX      Integer32
   MAX-ACCESS  read-write
   STATUS      current
   DESCRIPTION
      "Path: ethernet1.editConf.inboundBandwidth.cir"
   ::= {er1645v2PortSwIbwEntry 268435456}

er1645v2PortSwIbwEir OBJECT-TYPE
   SYNTAX      Integer32
   MAX-ACCESS  read-write
   STATUS      current
   DESCRIPTION
      "Path: ethernet1.editConf.inboundBandwidth.eir"
   ::= {er1645v2PortSwIbwEntry 1879048192}

er1645v2PortSwIbwTc OBJECT-TYPE
   SYNTAX      INTEGER
               {
               auto (0)
               }
   MAX-ACCESS  read-write
   STATUS      current
   DESCRIPTION
      "Path: ethernet1.editConf.inboundBandwidth.tc

       Possibilities:
               auto   (0)"
   ::= {er1645v2PortSwIbwEntry 1610612736}

er1645v2PortSwIbwTcFactor OBJECT-TYPE
   SYNTAX      INTEGER
               {
               ms (10),
               s100us (1)
               }
   MAX-ACCESS  read-write
   STATUS      current
   DESCRIPTION
      "Path: ethernet1.editConf.inboundBandwidth.tcFactor

       Possibilities:
               ms   (10)
               *100us   (1)"
   ::= {er1645v2PortSwIbwEntry 2147483648}

er1645v2PortSwIbwCorrType OBJECT-TYPE
   SYNTAX      INTEGER
               {
               noCorrection (0),
               predefined (1),
               manual (2)
               }
   MAX-ACCESS  read-write
   STATUS      current
   DESCRIPTION
      "Path: ethernet1.editConf.inboundBandwidth.correction.type

       Possibilities:
               noCorrection   (0)
               predefined   (1)
               manual   (2)"
   ::= {er1645v2PortSwIbwEntry 570425344}

er1645v2PortSwIbwCorrPredefEncapsFrameRelay OBJECT-TYPE
   SYNTAX      DisplayString
   MAX-ACCESS  read-write
   STATUS      current
   DESCRIPTION
      "Path: ethernet1.editConf.inboundBandwidth.correction.predefined.encapsulation.frameRelay"
   ::= {er1645v2PortSwIbwEntry 608436224}

er1645v2PortSwIbwCorrPredefEncapsPpp OBJECT-TYPE
   SYNTAX      DisplayString
   MAX-ACCESS  read-write
   STATUS      current
   DESCRIPTION
      "Path: ethernet1.editConf.inboundBandwidth.correction.predefined.encapsulation.ppp"
   ::= {er1645v2PortSwIbwEntry 608698368}

er1645v2PortSwIbwCorrPredefEncapsAtmHl OBJECT-TYPE
   SYNTAX      INTEGER
               {
               rfc2684 (0),
               ppp (1),
               pppOverEthernet (2)
               }
   MAX-ACCESS  read-write
   STATUS      current
   DESCRIPTION
      "Path: ethernet1.editConf.inboundBandwidth.correction.predefined.encapsulation.atm.higherLayer

       Possibilities:
               rfc2684   (0)
               ppp   (1)
               pppOverEthernet   (2)"
   ::= {er1645v2PortSwIbwEntry 608993280}

er1645v2PortSwIbwCorrPredefEncapsAtmMp OBJECT-TYPE
   SYNTAX      INTEGER
               {
               llcEncapsulation (0),
               vcMultiplexing (1)
               }
   MAX-ACCESS  read-write
   STATUS      current
   DESCRIPTION
      "Path: ethernet1.editConf.inboundBandwidth.correction.predefined.encapsulation.atm.multiProtocol

       Possibilities:
               llcEncapsulation   (0)
               vcMultiplexing   (1)"
   ::= {er1645v2PortSwIbwEntry 609026048}

er1645v2PortSwIbwCorrPredefEncapsHdlc OBJECT-TYPE
   SYNTAX      DisplayString
   MAX-ACCESS  read-write
   STATUS      current
   DESCRIPTION
      "Path: ethernet1.editConf.inboundBandwidth.correction.predefined.encapsulation.hdlc"
   ::= {er1645v2PortSwIbwEntry 609222656}

er1645v2PortSwIbwCorrPredefEncapsEfmFs OBJECT-TYPE
   SYNTAX      Integer32
   MAX-ACCESS  read-write
   STATUS      current
   DESCRIPTION
      "Path: ethernet1.editConf.inboundBandwidth.correction.predefined.encapsulation.efm.fragmentSize"
   ::= {er1645v2PortSwIbwEntry 609517568}

er1645v2PortSwIbwCorrPredefEncapsEfmIb OBJECT-TYPE
   SYNTAX      Integer32
   MAX-ACCESS  read-write
   STATUS      current
   DESCRIPTION
      "Path: ethernet1.editConf.inboundBandwidth.correction.predefined.encapsulation.efm.idleBytes"
   ::= {er1645v2PortSwIbwEntry 609550336}

er1645v2PortSwIbwCorrPredefMode OBJECT-TYPE
   SYNTAX      INTEGER
               {
               routing (0),
               bridging (1)
               }
   MAX-ACCESS  read-write
   STATUS      current
   DESCRIPTION
      "Path: ethernet1.editConf.inboundBandwidth.correction.predefined.mode

       Possibilities:
               routing   (0)
               bridging   (1)"
   ::= {er1645v2PortSwIbwEntry 612368384}

er1645v2PortSwIbwCorrManualOverhead OBJECT-TYPE
   SYNTAX      Integer32
   MAX-ACCESS  read-write
   STATUS      current
   DESCRIPTION
      "Path: ethernet1.editConf.inboundBandwidth.correction.manual.overhead"
   ::= {er1645v2PortSwIbwEntry 637665280}

er1645v2PortSwIbwCorrManualFrameData OBJECT-TYPE
   SYNTAX      Counter32
   MAX-ACCESS  read-write
   STATUS      current
   DESCRIPTION
      "Path: ethernet1.editConf.inboundBandwidth.correction.manual.frameData

       32 bit unsigned wrappable counter."
   ::= {er1645v2PortSwIbwEntry 637796352}

er1645v2PortSwIbwCorrManualFrameHeader OBJECT-TYPE
   SYNTAX      Counter32
   MAX-ACCESS  read-write
   STATUS      current
   DESCRIPTION
      "Path: ethernet1.editConf.inboundBandwidth.correction.manual.frameHeader

       32 bit unsigned wrappable counter."
   ::= {er1645v2PortSwIbwEntry 637927424}

er1645v2PortSwIbwMaxFifoQLen OBJECT-TYPE
   SYNTAX      Integer32
   MAX-ACCESS  read-write
   STATUS      current
   DESCRIPTION
      "Path: ethernet1.editConf.inboundBandwidth.maxFifoQLen"
   ::= {er1645v2PortSwIbwEntry 805306368}

er1645v2PortSwIbwPriorityPolicy OBJECT-TYPE
   SYNTAX      DisplayString
   MAX-ACCESS  read-write
   STATUS      current
   DESCRIPTION
      "Path: ethernet1.editConf.inboundBandwidth.priorityPolicy"
   ::= {er1645v2PortSwIbwEntry 1073741824}

er1645v2PortSwIbwDeFlagCir OBJECT-TYPE
   SYNTAX      INTEGER
               {
               allowed (1),
               notAllowed (2)
               }
   MAX-ACCESS  read-write
   STATUS      current
   DESCRIPTION
      "Path: ethernet1.editConf.inboundBandwidth.deFlag.cir

       Possibilities:
               allowed   (1)
               notAllowed   (2)"
   ::= {er1645v2PortSwIbwEntry 3490709504}

er1645v2PortSwIbwDeFlagEir OBJECT-TYPE
   SYNTAX      INTEGER
               {
               allowed (1),
               notAllowed (2)
               }
   MAX-ACCESS  read-write
   STATUS      current
   DESCRIPTION
      "Path: ethernet1.editConf.inboundBandwidth.deFlag.eir

       Possibilities:
               allowed   (1)
               notAllowed   (2)"
   ::= {er1645v2PortSwIbwEntry 3491758080}

er1645v2PortSwIbwDeFlagViolate OBJECT-TYPE
   SYNTAX      INTEGER
               {
               allowed (1),
               notAllowed (2)
               }
   MAX-ACCESS  read-write
   STATUS      current
   DESCRIPTION
      "Path: ethernet1.editConf.inboundBandwidth.deFlag.violate

       Possibilities:
               allowed   (1)
               notAllowed   (2)"
   ::= {er1645v2PortSwIbwEntry 3492806656}

er1645v2PortSwIbwActCirActNone OBJECT-TYPE
   SYNTAX      OCTET STRING
   MAX-ACCESS  read-write
   STATUS      current
   DESCRIPTION
      "Path: ethernet1.editConf.inboundBandwidth.action.cirAction.none"
   ::= {er1645v2PortSwIbwEntry 4062183424}

er1645v2PortSwIbwActCirActEthCos1 OBJECT-TYPE
   SYNTAX      INTEGER
               {
               unchanged (256)
               }
   MAX-ACCESS  read-write
   STATUS      current
   DESCRIPTION
      "Path: ethernet1.editConf.inboundBandwidth.action.cirAction.ethernet.cosDepth1

       Possibilities:
               unchanged   (256)"
   ::= {er1645v2PortSwIbwEntry 4064346112}

er1645v2PortSwIbwActCirActEthDei1 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth1

       Possibilities:
               unchanged   (255)
               clear   (0)
               set   (1)"
   ::= {er1645v2PortSwIbwEntry 4065656832}

er1645v2PortSwIbwActCirActEthCos2 OBJECT-TYPE
   SYNTAX      INTEGER
               {
               unchanged (256)
               }
   MAX-ACCESS  read-write
   STATUS      current
   DESCRIPTION
      "Path: ethernet1.editConf.inboundBandwidth.action.cirAction.ethernet.cosDepth2

       Possibilities:
               unchanged   (256)"
   ::= {er1645v2PortSwIbwEntry 4064411648}

er1645v2PortSwIbwActCirActEthDei2 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth2

       Possibilities:
               unchanged   (255)
               clear   (0)
               set   (1)"
   ::= {er1645v2PortSwIbwEntry 4065722368}

er1645v2PortSwIbwActCirActEthCos3 OBJECT-TYPE
   SYNTAX      INTEGER
               {
               unchanged (256)
               }
   MAX-ACCESS  read-write
   STATUS      current
   DESCRIPTION
      "Path: ethernet1.editConf.inboundBandwidth.action.cirAction.ethernet.cosDepth3

       Possibilities:
               unchanged   (256)"
   ::= {er1645v2PortSwIbwEntry 4064477184}

er1645v2PortSwIbwActCirActEthDei3 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth3

       Possibilities:
               unchanged   (255)
               clear   (0)
               set   (1)"
   ::= {er1645v2PortSwIbwEntry 4065787904}

er1645v2PortSwIbwActCirActEthCos4 OBJECT-TYPE
   SYNTAX      INTEGER
               {
               unchanged (256)
               }
   MAX-ACCESS  read-write
   STATUS      current
   DESCRIPTION
      "Path: ethernet1.editConf.inboundBandwidth.action.cirAction.ethernet.cosDepth4

       Possibilities:
               unchanged   (256)"
   ::= {er1645v2PortSwIbwEntry 4064542720}

er1645v2PortSwIbwActCirActEthDei4 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth4

       Possibilities:
               unchanged   (255)
               clear   (0)
               set   (1)"
   ::= {er1645v2PortSwIbwEntry 4065853440}

er1645v2PortSwIbwActCirActEthCos5 OBJECT-TYPE
   SYNTAX      INTEGER
               {
               unchanged (256)
               }
   MAX-ACCESS  read-write
   STATUS      current
   DESCRIPTION
      "Path: ethernet1.editConf.inboundBandwidth.action.cirAction.ethernet.cosDepth5

       Possibilities:
               unchanged   (256)"
   ::= {er1645v2PortSwIbwEntry 4064608256}

er1645v2PortSwIbwActCirActEthDei5 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth5

       Possibilities:
               unchanged   (255)
               clear   (0)
               set   (1)"
   ::= {er1645v2PortSwIbwEntry 4065918976}

er1645v2PortSwIbwActCirActEthCos6 OBJECT-TYPE
   SYNTAX      INTEGER
               {
               unchanged (256)
               }
   MAX-ACCESS  read-write
   STATUS      current
   DESCRIPTION
      "Path: ethernet1.editConf.inboundBandwidth.action.cirAction.ethernet.cosDepth6

       Possibilities:
               unchanged   (256)"
   ::= {er1645v2PortSwIbwEntry 4064673792}

er1645v2PortSwIbwActCirActEthDei6 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth6

       Possibilities:
               unchanged   (255)
               clear   (0)
               set   (1)"
   ::= {er1645v2PortSwIbwEntry 4065984512}

er1645v2PortSwIbwActCirActEthCos7 OBJECT-TYPE
   SYNTAX      INTEGER
               {
               unchanged (256)
               }
   MAX-ACCESS  read-write
   STATUS      current
   DESCRIPTION
      "Path: ethernet1.editConf.inboundBandwidth.action.cirAction.ethernet.cosDepth7

       Possibilities:
               unchanged   (256)"
   ::= {er1645v2PortSwIbwEntry 4064739328}

er1645v2PortSwIbwActCirActEthDei7 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth7

       Possibilities:
               unchanged   (255)
               clear   (0)
               set   (1)"
   ::= {er1645v2PortSwIbwEntry 4066050048}

er1645v2PortSwIbwActCirActEthCos8 OBJECT-TYPE
   SYNTAX      INTEGER
               {
               unchanged (256)
               }
   MAX-ACCESS  read-write
   STATUS      current
   DESCRIPTION
      "Path: ethernet1.editConf.inboundBandwidth.action.cirAction.ethernet.cosDepth8

       Possibilities:
               unchanged   (256)"
   ::= {er1645v2PortSwIbwEntry 4064804864}

er1645v2PortSwIbwActCirActEthDei8 OBJECT-TYPE
   SYNTAX      INTEGER
               {
               unchanged (255),
               clear (0),
               set (1)
               }
   MAX-ACCESS  read-write
   STATUS      current
   DESCRIPTION
      "Path: ethernet1.editConf.inboundBandwidth.action.cirAction.ethernet.deiDepth8

       Possibilities:
               unchanged   (255)
               clear   (0)
               set   (1)"
   ::= {er1645v2PortSwIbwEntry 4066115584}

er1645v2PortSwIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4064870400}

er1645v2PortSwIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4064935936}

er1645v2PortSwIbwActCirActEthDrpLev OBJECT-TYPE
   SYNTAX      INTEGER
               {
               unchanged (0)
               }
   MAX-ACCESS  read-write
   STATUS      current
   DESCRIPTION
      "Path: ethernet1.editConf.inboundBandwidth.action.cirAction.ethernet.dropLevel

       Possibilities:
               unchanged   (0)"
   ::= {er1645v2PortSwIbwEntry 4065001472}

er1645v2PortSwIbwActCirActEthDeFlag OBJECT-TYPE
   SYNTAX      INTEGER
               {
               unchanged (255),
               clear (0),
               set (1)
               }
   MAX-ACCESS  read-write
   STATUS      current
   DESCRIPTION
      "Path: ethernet1.editConf.inboundBandwidth.action.cirAction.ethernet.deFlag

       Possibilities:
               unchanged   (255)
               clear   (0)
               set   (1)"
   ::= {er1645v2PortSwIbwEntry 4065198080}

er1645v2PortSwIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4071161856}

er1645v2PortSwIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4071227392}

er1645v2PortSwIbwActCirActIpDrpLev OBJECT-TYPE
   SYNTAX      INTEGER
               {
               unchanged (0)
               }
   MAX-ACCESS  read-write
   STATUS      current
   DESCRIPTION
      "Path: ethernet1.editConf.inboundBandwidth.action.cirAction.ip.dropLevel

       Possibilities:
               unchanged   (0)"
   ::= {er1645v2PortSwIbwEntry 4071292928}

er1645v2PortSwIbwActCirActIpDeFlag OBJECT-TYPE
   SYNTAX      INTEGER
               {
               unchanged (255),
               clear (0),
               set (1)
               }
   MAX-ACCESS  read-write
   STATUS      current
   DESCRIPTION
      "Path: ethernet1.editConf.inboundBandwidth.action.cirAction.ip.deFlag

       Possibilities:
               unchanged   (255)
               clear   (0)
               set   (1)"
   ::= {er1645v2PortSwIbwEntry 4071489536}

er1645v2PortSwIbwActEirActNone OBJECT-TYPE
   SYNTAX      OCTET STRING
   MAX-ACCESS  read-write
   STATUS      current
   DESCRIPTION
      "Path: ethernet1.editConf.inboundBandwidth.action.eirAction.none"
   ::= {er1645v2PortSwIbwEntry 4095737856}

er1645v2PortSwIbwActEirActEthCos1 OBJECT-TYPE
   SYNTAX      INTEGER
               {
               unchanged (256)
               }
   MAX-ACCESS  read-write
   STATUS      current
   DESCRIPTION
      "Path: ethernet1.editConf.inboundBandwidth.action.eirAction.ethernet.cosDepth1

       Possibilities:
               unchanged   (256)"
   ::= {er1645v2PortSwIbwEntry 4097900544}

er1645v2PortSwIbwActEirActEthDei1 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth1

       Possibilities:
               unchanged   (255)
               clear   (0)
               set   (1)"
   ::= {er1645v2PortSwIbwEntry 4099211264}

er1645v2PortSwIbwActEirActEthCos2 OBJECT-TYPE
   SYNTAX      INTEGER
               {
               unchanged (256)
               }
   MAX-ACCESS  read-write
   STATUS      current
   DESCRIPTION
      "Path: ethernet1.editConf.inboundBandwidth.action.eirAction.ethernet.cosDepth2

       Possibilities:
               unchanged   (256)"
   ::= {er1645v2PortSwIbwEntry 4097966080}

er1645v2PortSwIbwActEirActEthDei2 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth2

       Possibilities:
               unchanged   (255)
               clear   (0)
               set   (1)"
   ::= {er1645v2PortSwIbwEntry 4099276800}

er1645v2PortSwIbwActEirActEthCos3 OBJECT-TYPE
   SYNTAX      INTEGER
               {
               unchanged (256)
               }
   MAX-ACCESS  read-write
   STATUS      current
   DESCRIPTION
      "Path: ethernet1.editConf.inboundBandwidth.action.eirAction.ethernet.cosDepth3

       Possibilities:
               unchanged   (256)"
   ::= {er1645v2PortSwIbwEntry 4098031616}

er1645v2PortSwIbwActEirActEthDei3 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth3

       Possibilities:
               unchanged   (255)
               clear   (0)
               set   (1)"
   ::= {er1645v2PortSwIbwEntry 4099342336}

er1645v2PortSwIbwActEirActEthCos4 OBJECT-TYPE
   SYNTAX      INTEGER
               {
               unchanged (256)
               }
   MAX-ACCESS  read-write
   STATUS      current
   DESCRIPTION
      "Path: ethernet1.editConf.inboundBandwidth.action.eirAction.ethernet.cosDepth4

       Possibilities:
               unchanged   (256)"
   ::= {er1645v2PortSwIbwEntry 4098097152}

er1645v2PortSwIbwActEirActEthDei4 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth4

       Possibilities:
               unchanged   (255)
               clear   (0)
               set   (1)"
   ::= {er1645v2PortSwIbwEntry 4099407872}

er1645v2PortSwIbwActEirActEthCos5 OBJECT-TYPE
   SYNTAX      INTEGER
               {
               unchanged (256)
               }
   MAX-ACCESS  read-write
   STATUS      current
   DESCRIPTION
      "Path: ethernet1.editConf.inboundBandwidth.action.eirAction.ethernet.cosDepth5

       Possibilities:
               unchanged   (256)"
   ::= {er1645v2PortSwIbwEntry 4098162688}

er1645v2PortSwIbwActEirActEthDei5 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth5

       Possibilities:
               unchanged   (255)
               clear   (0)
               set   (1)"
   ::= {er1645v2PortSwIbwEntry 4099473408}

er1645v2PortSwIbwActEirActEthCos6 OBJECT-TYPE
   SYNTAX      INTEGER
               {
               unchanged (256)
               }
   MAX-ACCESS  read-write
   STATUS      current
   DESCRIPTION
      "Path: ethernet1.editConf.inboundBandwidth.action.eirAction.ethernet.cosDepth6

       Possibilities:
               unchanged   (256)"
   ::= {er1645v2PortSwIbwEntry 4098228224}

er1645v2PortSwIbwActEirActEthDei6 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth6

       Possibilities:
               unchanged   (255)
               clear   (0)
               set   (1)"
   ::= {er1645v2PortSwIbwEntry 4099538944}

er1645v2PortSwIbwActEirActEthCos7 OBJECT-TYPE
   SYNTAX      INTEGER
               {
               unchanged (256)
               }
   MAX-ACCESS  read-write
   STATUS      current
   DESCRIPTION
      "Path: ethernet1.editConf.inboundBandwidth.action.eirAction.ethernet.cosDepth7

       Possibilities:
               unchanged   (256)"
   ::= {er1645v2PortSwIbwEntry 4098293760}

er1645v2PortSwIbwActEirActEthDei7 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth7

       Possibilities:
               unchanged   (255)
               clear   (0)
               set   (1)"
   ::= {er1645v2PortSwIbwEntry 4099604480}

er1645v2PortSwIbwActEirActEthCos8 OBJECT-TYPE
   SYNTAX      INTEGER
               {
               unchanged (256)
               }
   MAX-ACCESS  read-write
   STATUS      current
   DESCRIPTION
      "Path: ethernet1.editConf.inboundBandwidth.action.eirAction.ethernet.cosDepth8

       Possibilities:
               unchanged   (256)"
   ::= {er1645v2PortSwIbwEntry 4098359296}

er1645v2PortSwIbwActEirActEthDei8 OBJECT-TYPE
   SYNTAX      INTEGER
               {
               unchanged (255),
               clear (0),
               set (1)
               }
   MAX-ACCESS  read-write
   STATUS      current
   DESCRIPTION
      "Path: ethernet1.editConf.inboundBandwidth.action.eirAction.ethernet.deiDepth8

       Possibilities:
               unchanged   (255)
               clear   (0)
               set   (1)"
   ::= {er1645v2PortSwIbwEntry 4099670016}

er1645v2PortSwIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4098424832}

er1645v2PortSwIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4098490368}

er1645v2PortSwIbwActEirActEthDrpLev OBJECT-TYPE
   SYNTAX      INTEGER
               {
               unchanged (0)
               }
   MAX-ACCESS  read-write
   STATUS      current
   DESCRIPTION
      "Path: ethernet1.editConf.inboundBandwidth.action.eirAction.ethernet.dropLevel

       Possibilities:
               unchanged   (0)"
   ::= {er1645v2PortSwIbwEntry 4098555904}

er1645v2PortSwIbwActEirActEthDeFlag OBJECT-TYPE
   SYNTAX      INTEGER
               {
               unchanged (255),
               clear (0),
               set (1)
               }
   MAX-ACCESS  read-write
   STATUS      current
   DESCRIPTION
      "Path: ethernet1.editConf.inboundBandwidth.action.eirAction.ethernet.deFlag

       Possibilities:
               unchanged   (255)
               clear   (0)
               set   (1)"
   ::= {er1645v2PortSwIbwEntry 4098752512}

er1645v2PortSwIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4104716288}

er1645v2PortSwIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4104781824}

er1645v2PortSwIbwActEirActIpDrpLev OBJECT-TYPE
   SYNTAX      INTEGER
               {
               unchanged (0)
               }
   MAX-ACCESS  read-write
   STATUS      current
   DESCRIPTION
      "Path: ethernet1.editConf.inboundBandwidth.action.eirAction.ip.dropLevel

       Possibilities:
               unchanged   (0)"
   ::= {er1645v2PortSwIbwEntry 4104847360}

er1645v2PortSwIbwActEirActIpDeFlag OBJECT-TYPE
   SYNTAX      INTEGER
               {
               unchanged (255),
               clear (0),
               set (1)
               }
   MAX-ACCESS  read-write
   STATUS      current
   DESCRIPTION
      "Path: ethernet1.editConf.inboundBandwidth.action.eirAction.ip.deFlag

       Possibilities:
               unchanged   (255)
               clear   (0)
               set   (1)"
   ::= {er1645v2PortSwIbwEntry 4105043968}

er1645v2PortSwIbwActViolActNone OBJECT-TYPE
   SYNTAX      OCTET STRING
   MAX-ACCESS  read-write
   STATUS      current
   DESCRIPTION
      "Path: ethernet1.editConf.inboundBandwidth.action.violateAction.none"
   ::= {er1645v2PortSwIbwEntry 4129292288}

er1645v2PortSwIbwActViolActDrop OBJECT-TYPE
   SYNTAX      OCTET STRING
   MAX-ACCESS  read-write
   STATUS      current
   DESCRIPTION
      "Path: ethernet1.editConf.inboundBandwidth.action.violateAction.drop"
   ::= {er1645v2PortSwIbwEntry 4133486592}

er1645v2PortSwIbwActViolActEthCos1 OBJECT-TYPE
   SYNTAX      INTEGER
               {
               unchanged (256)
               }
   MAX-ACCESS  read-write
   STATUS      current
   DESCRIPTION
      "Path: ethernet1.editConf.inboundBandwidth.action.violateAction.ethernet.cosDepth1

       Possibilities:
               unchanged   (256)"
   ::= {er1645v2PortSwIbwEntry 4131454976}

er1645v2PortSwIbwActViolActEthDei1 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth1

       Possibilities:
               unchanged   (255)
               clear   (0)
               set   (1)"
   ::= {er1645v2PortSwIbwEntry 4132765696}

er1645v2PortSwIbwActViolActEthCos2 OBJECT-TYPE
   SYNTAX      INTEGER
               {
               unchanged (256)
               }
   MAX-ACCESS  read-write
   STATUS      current
   DESCRIPTION
      "Path: ethernet1.editConf.inboundBandwidth.action.violateAction.ethernet.cosDepth2

       Possibilities:
               unchanged   (256)"
   ::= {er1645v2PortSwIbwEntry 4131520512}

er1645v2PortSwIbwActViolActEthDei2 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth2

       Possibilities:
               unchanged   (255)
               clear   (0)
               set   (1)"
   ::= {er1645v2PortSwIbwEntry 4132831232}

er1645v2PortSwIbwActViolActEthCos3 OBJECT-TYPE
   SYNTAX      INTEGER
               {
               unchanged (256)
               }
   MAX-ACCESS  read-write
   STATUS      current
   DESCRIPTION
      "Path: ethernet1.editConf.inboundBandwidth.action.violateAction.ethernet.cosDepth3

       Possibilities:
               unchanged   (256)"
   ::= {er1645v2PortSwIbwEntry 4131586048}

er1645v2PortSwIbwActViolActEthDei3 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth3

       Possibilities:
               unchanged   (255)
               clear   (0)
               set   (1)"
   ::= {er1645v2PortSwIbwEntry 4132896768}

er1645v2PortSwIbwActViolActEthCos4 OBJECT-TYPE
   SYNTAX      INTEGER
               {
               unchanged (256)
               }
   MAX-ACCESS  read-write
   STATUS      current
   DESCRIPTION
      "Path: ethernet1.editConf.inboundBandwidth.action.violateAction.ethernet.cosDepth4

       Possibilities:
               unchanged   (256)"
   ::= {er1645v2PortSwIbwEntry 4131651584}

er1645v2PortSwIbwActViolActEthDei4 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth4

       Possibilities:
               unchanged   (255)
               clear   (0)
               set   (1)"
   ::= {er1645v2PortSwIbwEntry 4132962304}

er1645v2PortSwIbwActViolActEthCos5 OBJECT-TYPE
   SYNTAX      INTEGER
               {
               unchanged (256)
               }
   MAX-ACCESS  read-write
   STATUS      current
   DESCRIPTION
      "Path: ethernet1.editConf.inboundBandwidth.action.violateAction.ethernet.cosDepth5

       Possibilities:
               unchanged   (256)"
   ::= {er1645v2PortSwIbwEntry 4131717120}

er1645v2PortSwIbwActViolActEthDei5 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth5

       Possibilities:
               unchanged   (255)
               clear   (0)
               set   (1)"
   ::= {er1645v2PortSwIbwEntry 4133027840}

er1645v2PortSwIbwActViolActEthCos6 OBJECT-TYPE
   SYNTAX      INTEGER
               {
               unchanged (256)
               }
   MAX-ACCESS  read-write
   STATUS      current
   DESCRIPTION
      "Path: ethernet1.editConf.inboundBandwidth.action.violateAction.ethernet.cosDepth6

       Possibilities:
               unchanged   (256)"
   ::= {er1645v2PortSwIbwEntry 4131782656}

er1645v2PortSwIbwActViolActEthDei6 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth6

       Possibilities:
               unchanged   (255)
               clear   (0)
               set   (1)"
   ::= {er1645v2PortSwIbwEntry 4133093376}

er1645v2PortSwIbwActViolActEthCos7 OBJECT-TYPE
   SYNTAX      INTEGER
               {
               unchanged (256)
               }
   MAX-ACCESS  read-write
   STATUS      current
   DESCRIPTION
      "Path: ethernet1.editConf.inboundBandwidth.action.violateAction.ethernet.cosDepth7

       Possibilities:
               unchanged   (256)"
   ::= {er1645v2PortSwIbwEntry 4131848192}

er1645v2PortSwIbwActViolActEthDei7 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth7

       Possibilities:
               unchanged   (255)
               clear   (0)
               set   (1)"
   ::= {er1645v2PortSwIbwEntry 4133158912}

er1645v2PortSwIbwActViolActEthCos8 OBJECT-TYPE
   SYNTAX      INTEGER
               {
               unchanged (256)
               }
   MAX-ACCESS  read-write
   STATUS      current
   DESCRIPTION
      "Path: ethernet1.editConf.inboundBandwidth.action.violateAction.ethernet.cosDepth8

       Possibilities:
               unchanged   (256)"
   ::= {er1645v2PortSwIbwEntry 4131913728}

er1645v2PortSwIbwActViolActEthDei8 OBJECT-TYPE
   SYNTAX      INTEGER
               {
               unchanged (255),
               clear (0),
               set (1)
               }
   MAX-ACCESS  read-write
   STATUS      current
   DESCRIPTION
      "Path: ethernet1.editConf.inboundBandwidth.action.violateAction.ethernet.deiDepth8

       Possibilities:
               unchanged   (255)
               clear   (0)
               set   (1)"
   ::= {er1645v2PortSwIbwEntry 4133224448}

er1645v2PortSwIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4131979264}

er1645v2PortSwIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4132044800}

er1645v2PortSwIbwActViolActEthDrpLev OBJECT-TYPE
   SYNTAX      INTEGER
               {
               unchanged (0)
               }
   MAX-ACCESS  read-write
   STATUS      current
   DESCRIPTION
      "Path: ethernet1.editConf.inboundBandwidth.action.violateAction.ethernet.dropLevel

       Possibilities:
               unchanged   (0)"
   ::= {er1645v2PortSwIbwEntry 4132110336}

er1645v2PortSwIbwActViolActEthDeFlag OBJECT-TYPE
   SYNTAX      INTEGER
               {
               unchanged (255),
               clear (0),
               set (1)
               }
   MAX-ACCESS  read-write
   STATUS      current
   DESCRIPTION
      "Path: ethernet1.editConf.inboundBandwidth.action.violateAction.ethernet.deFlag

       Possibilities:
               unchanged   (255)
               clear   (0)
               set   (1)"
   ::= {er1645v2PortSwIbwEntry 4132306944}

er1645v2PortSwIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet1.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwIbwEntry 4138270720}

er1645v2PortSwIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwIbwEntry 4138336256}

er1645v2PortSwIbwActViolActIpDrpLev OBJECT-TYPE
   SYNTAX      INTEGER
               {
               unchanged (0)
               }
   MAX-ACCESS  read-write
   STATUS      current
   DESCRIPTION
      "Path: ethernet1.editConf.inboundBandwidth.action.violateAction.ip.dropLevel

       Possibilities:
               unchanged   (0)"
   ::= {er1645v2PortSwIbwEntry 4138401792}

er1645v2PortSwIbwActViolActIpDeFlag OBJECT-TYPE
   SYNTAX      INTEGER
               {
               unchanged (255),
               clear (0),
               set (1)
               }
   MAX-ACCESS  read-write
   STATUS      current
   DESCRIPTION
      "Path: ethernet1.editConf.inboundBandwidth.action.violateAction.ip.deFlag

       Possibilities:
               unchanged   (255)
               clear   (0)
               set   (1)"
   ::= {er1645v2PortSwIbwEntry 4138598400}

er1645v2PortSwIbwSubInterfacesExcluded OBJECT-TYPE
   SYNTAX      INTEGER
               {
               s (1)
               }
   MAX-ACCESS  read-write
   STATUS      current
   DESCRIPTION
      "Path: ethernet1.editConf.inboundBandwidth.subInterfaces.excluded

       Possibilities:
                  (1)"
   ::= {er1645v2PortSwIbwEntry 2416967680}

er1645v2PortSwIbwSubInterfacesIncludedInAccessList OBJECT-TYPE
   SYNTAX      DisplayString
   MAX-ACCESS  read-write
   STATUS      current
   DESCRIPTION
      "Path: ethernet1.editConf.inboundBandwidth.subInterfaces.included.inAccessList"
   ::= {er1645v2PortSwIbwEntry 2418020352}


er1645v2PortSwInboundNUcastPriority OBJECT IDENTIFIER ::= {er1645v2PortSw 230}

er1645v2PortSwInboundNUcastPrioritySSC OBJECT IDENTIFIER ::= {er1645v2PortSwInboundNUcastPriority 1}

er1645v2PortSwInboundNUcastPriorityEntry OBJECT IDENTIFIER ::= {er1645v2PortSwInboundNUcastPrioritySSC 1}

er1645v2PortSwInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2PortSwInboundNUcastPriorityEntry 16777216}

er1645v2PortSwInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet1.editConf.inboundNUcastPriority.multicast

       Possibilities:
               queue1   (0)
               queue2   (1)
               queue3   (2)
               queue4   (3)
               queue5   (4)
               lowDelayQueue   (5)
               lowDelay2Queue   (6)
               systemQueue   (7)"
   ::= {er1645v2PortSwInboundNUcastPriorityEntry 33554432}


er1645v2PortSwInboundHwPriority OBJECT IDENTIFIER ::= {er1645v2PortSw 231}

er1645v2PortSwInboundHwPrioritySSC OBJECT IDENTIFIER ::= {er1645v2PortSwInboundHwPriority 1}

er1645v2PortSwInboundHwPriorityEntry OBJECT IDENTIFIER ::= {er1645v2PortSwInboundHwPrioritySSC 1}

er1645v2PortSwInboundHwPriorityNone OBJECT-TYPE
   SYNTAX      OCTET STRING
   MAX-ACCESS  read-write
   STATUS      current
   DESCRIPTION
      "Path: ethernet1.editConf.inboundHwPriority.none"
   ::= {er1645v2PortSwInboundHwPriorityEntry 16777216}

er1645v2PortSwInboundHwPriorityMapCosToQueueP0 OBJECT-TYPE
   SYNTAX      INTEGER
               {
               queue1 (1),
               queue2 (2)
               }
   MAX-ACCESS  read-write
   STATUS      current
   DESCRIPTION
      "Path: ethernet1.editConf.inboundHwPriority.mapCosToQueue.p0

       Possibilities:
               queue1   (1)
               queue2   (2)"
   ::= {er1645v2PortSwInboundHwPriorityEntry 33619968}

er1645v2PortSwInboundHwPriorityMapCosToQueueP1 OBJECT-TYPE
   SYNTAX      INTEGER
               {
               queue1 (1),
               queue2 (2)
               }
   MAX-ACCESS  read-write
   STATUS      current
   DESCRIPTION
      "Path: ethernet1.editConf.inboundHwPriority.mapCosToQueue.p1

       Possibilities:
               queue1   (1)
               queue2   (2)"
   ::= {er1645v2PortSwInboundHwPriorityEntry 33685504}

er1645v2PortSwInboundHwPriorityMapCosToQueueP2 OBJECT-TYPE
   SYNTAX      INTEGER
               {
               queue1 (1),
               queue2 (2)
               }
   MAX-ACCESS  read-write
   STATUS      current
   DESCRIPTION
      "Path: ethernet1.editConf.inboundHwPriority.mapCosToQueue.p2

       Possibilities:
               queue1   (1)
               queue2   (2)"
   ::= {er1645v2PortSwInboundHwPriorityEntry 33751040}

er1645v2PortSwInboundHwPriorityMapCosToQueueP3 OBJECT-TYPE
   SYNTAX      INTEGER
               {
               queue1 (1),
               queue2 (2)
               }
   MAX-ACCESS  read-write
   STATUS      current
   DESCRIPTION
      "Path: ethernet1.editConf.inboundHwPriority.mapCosToQueue.p3

       Possibilities:
               queue1   (1)
               queue2   (2)"
   ::= {er1645v2PortSwInboundHwPriorityEntry 33816576}

er1645v2PortSwInboundHwPriorityMapCosToQueueP4 OBJECT-TYPE
   SYNTAX      INTEGER
               {
               queue1 (1),
               queue2 (2)
               }
   MAX-ACCESS  read-write
   STATUS      current
   DESCRIPTION
      "Path: ethernet1.editConf.inboundHwPriority.mapCosToQueue.p4

       Possibilities:
               queue1   (1)
               queue2   (2)"
   ::= {er1645v2PortSwInboundHwPriorityEntry 33882112}

er1645v2PortSwInboundHwPriorityMapCosToQueueP5 OBJECT-TYPE
   SYNTAX      INTEGER
               {
               queue1 (1),
               queue2 (2)
               }
   MAX-ACCESS  read-write
   STATUS      current
   DESCRIPTION
      "Path: ethernet1.editConf.inboundHwPriority.mapCosToQueue.p5

       Possibilities:
               queue1   (1)
               queue2   (2)"
   ::= {er1645v2PortSwInboundHwPriorityEntry 33947648}

er1645v2PortSwInboundHwPriorityMapCosToQueueP6 OBJECT-TYPE
   SYNTAX      INTEGER
               {
               queue1 (1),
               queue2 (2)
               }
   MAX-ACCESS  read-write
   STATUS      current
   DESCRIPTION
      "Path: ethernet1.editConf.inboundHwPriority.mapCosToQueue.p6

       Possibilities:
               queue1   (1)
               queue2   (2)"
   ::= {er1645v2PortSwInboundHwPriorityEntry 34013184}

er1645v2PortSwInboundHwPriorityMapCosToQueueP7 OBJECT-TYPE
   SYNTAX      INTEGER
               {
               queue1 (1),
               queue2 (2)
               }
   MAX-ACCESS  read-write
   STATUS      current
   DESCRIPTION
      "Path: ethernet1.editConf.inboundHwPriority.mapCosToQueue.p7

       Possibilities:
               queue1   (1)
               queue2   (2)"
   ::= {er1645v2PortSwInboundHwPriorityEntry 34078720}

er1645v2PortSwInboundHwPriorityMapDscpToQueue OBJECT-TYPE
   SYNTAX      SEQUENCE OF Er1645v2PortSwInboundHwPriorityMapDscpToQueueEntry
   MAX-ACCESS  not-accessible
   STATUS      current
   DESCRIPTION
      ""
   ::= {er1645v2PortSwInboundHwPriority 50331648}

er1645v2PortSwInboundHwPriorityMapDscpToQueueEntry OBJECT-TYPE
   SYNTAX      Er1645v2PortSwInboundHwPriorityMapDscpToQueueEntry
   MAX-ACCESS  not-accessible
   STATUS      current
   DESCRIPTION
      ""
   INDEX      { er1645v2PortSwInboundHwPriorityMapDscpToQueueTableIx }
   ::= {er1645v2PortSwInboundHwPriorityMapDscpToQueue 1}

Er1645v2PortSwInboundHwPriorityMapDscpToQueueEntry ::=
   SEQUENCE
      {
      er1645v2PortSwInboundHwPriorityMapDscpToQueueActions
         VariableLengthTableActions,
      er1645v2PortSwInboundHwPriorityMapDscpToQueueTableIx
         TableIndex,
      er1645v2PortSwInboundHwPriorityMapDscpToQueueStartDscp
         INTEGER,
      er1645v2PortSwInboundHwPriorityMapDscpToQueueEndDscp
         INTEGER,
      er1645v2PortSwInboundHwPriorityMapDscpToQueueQueue
         INTEGER
      }

er1645v2PortSwInboundHwPriorityMapDscpToQueueActions OBJECT-TYPE
   SYNTAX      VariableLengthTableActions
   MAX-ACCESS  read-write
   STATUS      current
   DESCRIPTION
      "By way of this field, some manipulations
       on this table may be performed."
   ::= {er1645v2PortSwInboundHwPriorityMapDscpToQueueEntry 2}

er1645v2PortSwInboundHwPriorityMapDscpToQueueTableIx OBJECT-TYPE
   SYNTAX      TableIndex
   MAX-ACCESS  not-accessible
   STATUS      current
   DESCRIPTION
      ""
   ::= {er1645v2PortSwInboundHwPriorityMapDscpToQueueEntry 11}

er1645v2PortSwInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet1.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2PortSwInboundHwPriorityMapDscpToQueueEntry 16777216}

er1645v2PortSwInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet1.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2PortSwInboundHwPriorityMapDscpToQueueEntry 33554432}

er1645v2PortSwInboundHwPriorityMapDscpToQueueQueue OBJECT-TYPE
   SYNTAX      INTEGER
               {
               queue1 (1),
               queue2 (2)
               }
   MAX-ACCESS  read-write
   STATUS      current
   DESCRIPTION
      "Path: ethernet1.editConf.inboundHwPriority.mapDscpToQueue.queue

       Possibilities:
               queue1   (1)
               queue2   (2)"
   ::= {er1645v2PortSwInboundHwPriorityMapDscpToQueueEntry 50331648}


er1645v2PortSwName OBJECT-TYPE
   SYNTAX      DisplayString
   MAX-ACCESS  read-write
   STATUS      current
   DESCRIPTION
      "Path: ethernet1.editConf.name
       Info: config interface name"
   ::= {er1645v2PortSw 2}



sr1645v2PortSw OBJECT IDENTIFIER ::= {r1645v2PortSw 14}


sr1645v2PortSwDescr OBJECT-TYPE
   SYNTAX      DisplayString
   MAX-ACCESS  read-only
   STATUS      current
   DESCRIPTION
      "Path: ethernet1.status.ifDescr
       Info: ifDescr"
   ::= {sr1645v2PortSw 101}


sr1645v2PortSwType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet1.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2PortSw 102}


sr1645v2PortSwMtu OBJECT-TYPE
   SYNTAX      Integer32
   MAX-ACCESS  read-only
   STATUS      current
   DESCRIPTION
      "Path: ethernet1.status.ifMtu
       Info: ifMtu"
   ::= {sr1645v2PortSw 103}


sr1645v2PortSwOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet1.status.ifOperStatus
       Info: ifOperStatus

       Possibilities:
               up   (1)
               down   (2)
               testing   (3)
               unknown   (4)
               dormant   (5)
               notPresent   (6)
               lowerLayerDown   (7)"
   ::= {sr1645v2PortSw 107}


sr1645v2PortSwLastChange OBJECT-TYPE
   SYNTAX      TimeTicks
   MAX-ACCESS  read-only
   STATUS      current
   DESCRIPTION
      "Path: ethernet1.status.ifLastChange
       Info: ifLastChange

       Time in centi-second."
   ::= {sr1645v2PortSw 108}


sr1645v2PortSwLastChangeD OBJECT-TYPE
   SYNTAX      DisplayString
   MAX-ACCESS  read-only
   STATUS      current
   DESCRIPTION
      "Path: ethernet1.status.ifLastChangeDate
       Info: ifLastChangeDate"
   ::= {sr1645v2PortSw 183}


sr1645v2PortSwSpeed OBJECT-TYPE
   SYNTAX      Gauge32
   MAX-ACCESS  read-only
   STATUS      current
   DESCRIPTION
      "Path: ethernet1.status.ifSpeed
       Info: ifSpeed

       32 bit unsigned gauge value."
   ::= {sr1645v2PortSw 104}


sr1645v2PortSwSnmpIndex OBJECT-TYPE
   SYNTAX      Integer32
   MAX-ACCESS  read-only
   STATUS      current
   DESCRIPTION
      "Path: ethernet1.status.snmpIndex
       Info: SNMP index assigned to this object"
   ::= {sr1645v2PortSw 269}


sr1645v2PortSwPorts OBJECT IDENTIFIER ::= {sr1645v2PortSw 146}

sr1645v2PortSwPortsSSCTable OBJECT-TYPE
   SYNTAX      SEQUENCE OF Sr1645v2PortSwPortsEntry
   MAX-ACCESS  not-accessible
   STATUS      current
   DESCRIPTION
      "Ethernet Switch 4 Gigabit Ports Status without vlan"
   ::= {sr1645v2PortSwPorts 1}

sr1645v2PortSwPortsEntry OBJECT-TYPE
   SYNTAX      Sr1645v2PortSwPortsEntry
   MAX-ACCESS  not-accessible
   STATUS      current
   DESCRIPTION
      ""
   INDEX      { sr1645v2PortSwPortsTableIx }
   ::= {sr1645v2PortSwPortsSSCTable 1}

Sr1645v2PortSwPortsEntry ::=
   SEQUENCE
      {
      sr1645v2PortSwPortsTableIx
         TableIndex,
      sr1645v2PortSwPortsPortName
         INTEGER,
      sr1645v2PortSwPortsOperStatus
         INTEGER,
      sr1645v2PortSwPortsSpeed
         INTEGER,
      sr1645v2PortSwPortsDuplex
         INTEGER,
      sr1645v2PortSwPortsAutoNeg
         INTEGER,
      sr1645v2PortSwPortsPartnerCapsFlowCtrl
         INTEGER,
      sr1645v2PortSwPortsPartnerCapsHD10
         INTEGER,
      sr1645v2PortSwPortsPartnerCapsFD10
         INTEGER,
      sr1645v2PortSwPortsPartnerCapsHD100
         INTEGER,
      sr1645v2PortSwPortsPartnerCapsFD100
         INTEGER,
      sr1645v2PortSwPortsPartnerCapsFD1000
         INTEGER,
      sr1645v2PortSwPortsCir
         Integer32,
      sr1645v2PortSwPortsSwPort
         INTEGER
      }

sr1645v2PortSwPortsTableIx OBJECT-TYPE
   SYNTAX      TableIndex
   MAX-ACCESS  not-accessible
   STATUS      current
   DESCRIPTION
      ""
   ::= {sr1645v2PortSwPortsEntry 11}

sr1645v2PortSwPortsPortName OBJECT-TYPE
   SYNTAX      INTEGER
               {
               hwPortu1 (1),
               hwPortu2 (2),
               hwPortu3 (3),
               hwPortu4 (4),
               hwPortu5 (5),
               hwPortu6 (6),
               hwPortuLocalPort (255)
               }
   MAX-ACCESS  read-only
   STATUS      current
   DESCRIPTION
      "Path: ethernet1.status.ports.portName

       Possibilities:
               hwPort_1   (1)
               hwPort_2   (2)
               hwPort_3   (3)
               hwPort_4   (4)
               hwPort_5   (5)
               hwPort_6   (6)
               hwPort_LocalPort   (255)"
   ::= {sr1645v2PortSwPortsEntry 16777216}

sr1645v2PortSwPortsOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet1.status.ports.ifOperStatus

       Possibilities:
               up   (1)
               down   (2)
               testing   (3)
               unknown   (4)
               dormant   (5)
               notPresent   (6)
               lowerLayerDown   (7)"
   ::= {sr1645v2PortSwPortsEntry 33554432}

sr1645v2PortSwPortsSpeed OBJECT-TYPE
   SYNTAX      INTEGER
               {
               s10 (0),
               s100 (1),
               s1000 (2),
               s200 (3)
               }
   MAX-ACCESS  read-only
   STATUS      current
   DESCRIPTION
      "Path: ethernet1.status.ports.speed

       Possibilities:
               10   (0)
               100   (1)
               1000   (2)
               200   (3)"
   ::= {sr1645v2PortSwPortsEntry 50331648}

sr1645v2PortSwPortsDuplex OBJECT-TYPE
   SYNTAX      INTEGER
               {
               halfDuplex (0),
               fullDuplex (1)
               }
   MAX-ACCESS  read-only
   STATUS      current
   DESCRIPTION
      "Path: ethernet1.status.ports.duplex

       Possibilities:
               halfDuplex   (0)
               fullDuplex   (1)"
   ::= {sr1645v2PortSwPortsEntry 67108864}

sr1645v2PortSwPortsAutoNeg OBJECT-TYPE
   SYNTAX      INTEGER
               {
               disabled (0),
               done (1),
               notDone (2)
               }
   MAX-ACCESS  read-only
   STATUS      current
   DESCRIPTION
      "Path: ethernet1.status.ports.autoNegotiate

       Possibilities:
               disabled   (0)
               done   (1)
               notDone   (2)"
   ::= {sr1645v2PortSwPortsEntry 83886080}

sr1645v2PortSwPortsPartnerCapsFlowCtrl OBJECT-TYPE
   SYNTAX      INTEGER
               {
               notCapable (0),
               capable (1),
               unknown (2)
               }
   MAX-ACCESS  read-only
   STATUS      current
   DESCRIPTION
      "Path: ethernet1.status.ports.linkPartnerCaps.flowControl

       Possibilities:
               notCapable   (0)
               capable   (1)
               unknown   (2)"
   ::= {sr1645v2PortSwPortsEntry 100728832}

sr1645v2PortSwPortsPartnerCapsHD10 OBJECT-TYPE
   SYNTAX      INTEGER
               {
               notCapable (0),
               capable (1),
               unknown (2)
               }
   MAX-ACCESS  read-only
   STATUS      current
   DESCRIPTION
      "Path: ethernet1.status.ports.linkPartnerCaps.10Mb/halfDuplex

       Possibilities:
               notCapable   (0)
               capable   (1)
               unknown   (2)"
   ::= {sr1645v2PortSwPortsEntry 100794368}

sr1645v2PortSwPortsPartnerCapsFD10 OBJECT-TYPE
   SYNTAX      INTEGER
               {
               notCapable (0),
               capable (1),
               unknown (2)
               }
   MAX-ACCESS  read-only
   STATUS      current
   DESCRIPTION
      "Path: ethernet1.status.ports.linkPartnerCaps.10Mb/fullDuplex

       Possibilities:
               notCapable   (0)
               capable   (1)
               unknown   (2)"
   ::= {sr1645v2PortSwPortsEntry 100859904}

sr1645v2PortSwPortsPartnerCapsHD100 OBJECT-TYPE
   SYNTAX      INTEGER
               {
               notCapable (0),
               capable (1),
               unknown (2)
               }
   MAX-ACCESS  read-only
   STATUS      current
   DESCRIPTION
      "Path: ethernet1.status.ports.linkPartnerCaps.100Mb/halfDuplex

       Possibilities:
               notCapable   (0)
               capable   (1)
               unknown   (2)"
   ::= {sr1645v2PortSwPortsEntry 100925440}

sr1645v2PortSwPortsPartnerCapsFD100 OBJECT-TYPE
   SYNTAX      INTEGER
               {
               notCapable (0),
               capable (1),
               unknown (2)
               }
   MAX-ACCESS  read-only
   STATUS      current
   DESCRIPTION
      "Path: ethernet1.status.ports.linkPartnerCaps.100Mb/fullDuplex

       Possibilities:
               notCapable   (0)
               capable   (1)
               unknown   (2)"
   ::= {sr1645v2PortSwPortsEntry 100990976}

sr1645v2PortSwPortsPartnerCapsFD1000 OBJECT-TYPE
   SYNTAX      INTEGER
               {
               notCapable (0),
               capable (1),
               unknown (2)
               }
   MAX-ACCESS  read-only
   STATUS      current
   DESCRIPTION
      "Path: ethernet1.status.ports.linkPartnerCaps.1000Mb/fullDuplex

       Possibilities:
               notCapable   (0)
               capable   (1)
               unknown   (2)"
   ::= {sr1645v2PortSwPortsEntry 101056512}

sr1645v2PortSwPortsCir OBJECT-TYPE
   SYNTAX      Integer32
   MAX-ACCESS  read-only
   STATUS      current
   DESCRIPTION
      "Path: ethernet1.status.ports.cir"
   ::= {sr1645v2PortSwPortsEntry 134217728}

sr1645v2PortSwPortsSwPort OBJECT-TYPE
   SYNTAX      INTEGER
               {
               swPort1 (1),
               swPort2 (2),
               swPort3 (3),
               swPort4 (4),
               swPort5 (5),
               swPort6 (6),
               swPort7 (7),
               swPort8 (8),
               none (255),
               all (65535)
               }
   MAX-ACCESS  read-only
   STATUS      current
   DESCRIPTION
      "Path: ethernet1.status.ports.swPort

       Possibilities:
               swPort[1]   (1)
               swPort[2]   (2)
               swPort[3]   (3)
               swPort[4]   (4)
               swPort[5]   (5)
               swPort[6]   (6)
               swPort[7]   (7)
               swPort[8]   (8)
               none   (255)
               all   (65535)"
   ::= {sr1645v2PortSwPortsEntry 150994944}


sr1645v2PortSwSwitchCache OBJECT IDENTIFIER ::= {sr1645v2PortSw 10}

sr1645v2PortSwSwitchCacheSSCTable OBJECT-TYPE
   SYNTAX      SEQUENCE OF Sr1645v2PortSwSwitchCacheEntry
   MAX-ACCESS  not-accessible
   STATUS      current
   DESCRIPTION
      "switch MAC cache"
   ::= {sr1645v2PortSwSwitchCache 1}

sr1645v2PortSwSwitchCacheEntry OBJECT-TYPE
   SYNTAX      Sr1645v2PortSwSwitchCacheEntry
   MAX-ACCESS  not-accessible
   STATUS      current
   DESCRIPTION
      ""
   INDEX      { sr1645v2PortSwSwitchCacheTableIx }
   ::= {sr1645v2PortSwSwitchCacheSSCTable 1}

Sr1645v2PortSwSwitchCacheEntry ::=
   SEQUENCE
      {
      sr1645v2PortSwSwitchCacheTableIx
         TableIndex,
      sr1645v2PortSwSwitchCacheMacAddress
         OCTET STRING,
      sr1645v2PortSwSwitchCachePort
         INTEGER,
      sr1645v2PortSwSwitchCacheType
         INTEGER,
      sr1645v2PortSwSwitchCacheTimeout
         TimeTicks,
      sr1645v2PortSwSwitchCacheDbNum
         Integer32
      }

sr1645v2PortSwSwitchCacheTableIx OBJECT-TYPE
   SYNTAX      TableIndex
   MAX-ACCESS  not-accessible
   STATUS      current
   DESCRIPTION
      ""
   ::= {sr1645v2PortSwSwitchCacheEntry 11}

sr1645v2PortSwSwitchCacheMacAddress OBJECT-TYPE
   SYNTAX      OCTET STRING
   MAX-ACCESS  read-only
   STATUS      current
   DESCRIPTION
      "Path: ethernet1.status.switchCache.macAddress

       MAC address."
   ::= {sr1645v2PortSwSwitchCacheEntry 16777216}

sr1645v2PortSwSwitchCachePort OBJECT-TYPE
   SYNTAX      INTEGER
               {
               none (0),
               hwPortu1 (1),
               hwPortu2 (2),
               hwPortu3 (3),
               hwPortu4 (4),
               hwPortu5 (5),
               hwPortuLocalPort (6),
               hwPortuLocalPort2 (7)
               }
   MAX-ACCESS  read-only
   STATUS      current
   DESCRIPTION
      "Path: ethernet1.status.switchCache.port

       Possibilities:
               none   (0)
               hwPort_1   (1)
               hwPort_2   (2)
               hwPort_3   (3)
               hwPort_4   (4)
               hwPort_5   (5)
               hwPort_LocalPort   (6)
               hwPort_LocalPort2   (7)"
   ::= {sr1645v2PortSwSwitchCacheEntry 33554432}

sr1645v2PortSwSwitchCacheType OBJECT-TYPE
   SYNTAX      INTEGER
               {
               static (0),
               dynamic (1)
               }
   MAX-ACCESS  read-only
   STATUS      current
   DESCRIPTION
      "Path: ethernet1.status.switchCache.type

       Possibilities:
               static   (0)
               dynamic   (1)"
   ::= {sr1645v2PortSwSwitchCacheEntry 50331648}

sr1645v2PortSwSwitchCacheTimeout OBJECT-TYPE
   SYNTAX      TimeTicks
   MAX-ACCESS  read-only
   STATUS      current
   DESCRIPTION
      "Path: ethernet1.status.switchCache.timeout

       Time in centi-second."
   ::= {sr1645v2PortSwSwitchCacheEntry 67108864}

sr1645v2PortSwSwitchCacheDbNum OBJECT-TYPE
   SYNTAX      Integer32
   MAX-ACCESS  read-only
   STATUS      current
   DESCRIPTION
      "Path: ethernet1.status.switchCache.dbNum"
   ::= {sr1645v2PortSwSwitchCacheEntry 83886080}


sr1645v2PortSwVtuTable OBJECT IDENTIFIER ::= {sr1645v2PortSw 89}

sr1645v2PortSwVtuTableSSCTable OBJECT-TYPE
   SYNTAX      SEQUENCE OF Sr1645v2PortSwVtuTableEntry
   MAX-ACCESS  not-accessible
   STATUS      current
   DESCRIPTION
      "VTU table"
   ::= {sr1645v2PortSwVtuTable 1}

sr1645v2PortSwVtuTableEntry OBJECT-TYPE
   SYNTAX      Sr1645v2PortSwVtuTableEntry
   MAX-ACCESS  not-accessible
   STATUS      current
   DESCRIPTION
      ""
   INDEX      { sr1645v2PortSwVtuTableTableIx }
   ::= {sr1645v2PortSwVtuTableSSCTable 1}

Sr1645v2PortSwVtuTableEntry ::=
   SEQUENCE
      {
      sr1645v2PortSwVtuTableTableIx
         TableIndex,
      sr1645v2PortSwVtuTableVid
         INTEGER,
      sr1645v2PortSwVtuTableHwPort1
         INTEGER,
      sr1645v2PortSwVtuTableHwPort2
         INTEGER,
      sr1645v2PortSwVtuTableHwPort3
         INTEGER,
      sr1645v2PortSwVtuTableHwPort4
         INTEGER,
      sr1645v2PortSwVtuTableHwPortLocalPort
         INTEGER,
      sr1645v2PortSwVtuTableDbNum
         Integer32
      }

sr1645v2PortSwVtuTableTableIx OBJECT-TYPE
   SYNTAX      TableIndex
   MAX-ACCESS  not-accessible
   STATUS      current
   DESCRIPTION
      ""
   ::= {sr1645v2PortSwVtuTableEntry 11}

sr1645v2PortSwVtuTableVid OBJECT-TYPE
   SYNTAX      INTEGER
               {
               untagged (0)
               }
   MAX-ACCESS  read-only
   STATUS      current
   DESCRIPTION
      "Path: ethernet1.status.vtuTable.vid

       Possibilities:
               untagged   (0)"
   ::= {sr1645v2PortSwVtuTableEntry 16777216}

sr1645v2PortSwVtuTableHwPort1 OBJECT-TYPE
   SYNTAX      INTEGER
               {
               pass (0),
               untag (1),
               tag (2),
               smm (3)
               }
   MAX-ACCESS  read-only
   STATUS      current
   DESCRIPTION
      "Path: ethernet1.status.vtuTable.hwPort1

       Possibilities:
               pass   (0)
               untag   (1)
               tag   (2)
               --   (3)"
   ::= {sr1645v2PortSwVtuTableEntry 33554432}

sr1645v2PortSwVtuTableHwPort2 OBJECT-TYPE
   SYNTAX      INTEGER
               {
               pass (0),
               untag (1),
               tag (2),
               smm (3)
               }
   MAX-ACCESS  read-only
   STATUS      current
   DESCRIPTION
      "Path: ethernet1.status.vtuTable.hwPort2

       Possibilities:
               pass   (0)
               untag   (1)
               tag   (2)
               --   (3)"
   ::= {sr1645v2PortSwVtuTableEntry 50331648}

sr1645v2PortSwVtuTableHwPort3 OBJECT-TYPE
   SYNTAX      INTEGER
               {
               pass (0),
               untag (1),
               tag (2),
               smm (3)
               }
   MAX-ACCESS  read-only
   STATUS      current
   DESCRIPTION
      "Path: ethernet1.status.vtuTable.hwPort3

       Possibilities:
               pass   (0)
               untag   (1)
               tag   (2)
               --   (3)"
   ::= {sr1645v2PortSwVtuTableEntry 67108864}

sr1645v2PortSwVtuTableHwPort4 OBJECT-TYPE
   SYNTAX      INTEGER
               {
               pass (0),
               untag (1),
               tag (2),
               smm (3)
               }
   MAX-ACCESS  read-only
   STATUS      current
   DESCRIPTION
      "Path: ethernet1.status.vtuTable.hwPort4

       Possibilities:
               pass   (0)
               untag   (1)
               tag   (2)
               --   (3)"
   ::= {sr1645v2PortSwVtuTableEntry 83886080}

sr1645v2PortSwVtuTableHwPortLocalPort OBJECT-TYPE
   SYNTAX      INTEGER
               {
               pass (0),
               untag (1),
               tag (2),
               smm (3)
               }
   MAX-ACCESS  read-only
   STATUS      current
   DESCRIPTION
      "Path: ethernet1.status.vtuTable.hwPortLocalPort

       Possibilities:
               pass   (0)
               untag   (1)
               tag   (2)
               --   (3)"
   ::= {sr1645v2PortSwVtuTableEntry 117440512}

sr1645v2PortSwVtuTableDbNum OBJECT-TYPE
   SYNTAX      Integer32
   MAX-ACCESS  read-only
   STATUS      current
   DESCRIPTION
      "Path: ethernet1.status.vtuTable.dbNum"
   ::= {sr1645v2PortSwVtuTableEntry 134217728}



pr1645v2PortSw OBJECT IDENTIFIER ::= {r1645v2PortSw 12}


pr1645v2PortSwInOctets OBJECT-TYPE
   SYNTAX      Counter64
   MAX-ACCESS  read-only
   STATUS      current
   DESCRIPTION
      "Path: ethernet1.performance.ifInOctets
       Info: ifInOctets

       64 bit unsigned wrappable counter."
   ::= {pr1645v2PortSw 109}


pr1645v2PortSwInUcast OBJECT-TYPE
   SYNTAX      Counter64
   MAX-ACCESS  read-only
   STATUS      current
   DESCRIPTION
      "Path: ethernet1.performance.ifInUcastPkts
       Info: ifInUcastPkts

       64 bit unsigned wrappable counter."
   ::= {pr1645v2PortSw 110}


pr1645v2PortSwInNUcastPkts OBJECT-TYPE
   SYNTAX      Counter64
   MAX-ACCESS  read-only
   STATUS      current
   DESCRIPTION
      "Path: ethernet1.performance.ifInNUcastPkts
       Info: ifInNUcastPkts

       64 bit unsigned wrappable counter."
   ::= {pr1645v2PortSw 111}


pr1645v2PortSwInBcastPkts OBJECT-TYPE
   SYNTAX      Counter64
   MAX-ACCESS  read-only
   STATUS      current
   DESCRIPTION
      "Path: ethernet1.performance.ifInBcastPkts
       Info: ifInBcastPkts

       64 bit unsigned wrappable counter."
   ::= {pr1645v2PortSw 211}


pr1645v2PortSwInMcastPkts OBJECT-TYPE
   SYNTAX      Counter64
   MAX-ACCESS  read-only
   STATUS      current
   DESCRIPTION
      "Path: ethernet1.performance.ifInMcastPkts
       Info: ifInNUcastPkts

       64 bit unsigned wrappable counter."
   ::= {pr1645v2PortSw 221}


pr1645v2PortSwInDiscards OBJECT-TYPE
   SYNTAX      Counter64
   MAX-ACCESS  read-only
   STATUS      current
   DESCRIPTION
      "Path: ethernet1.performance.ifInDiscards
       Info: ifInDiscards

       64 bit unsigned wrappable counter."
   ::= {pr1645v2PortSw 112}


pr1645v2PortSwInErrors OBJECT-TYPE
   SYNTAX      Counter64
   MAX-ACCESS  read-only
   STATUS      current
   DESCRIPTION
      "Path: ethernet1.performance.ifInErrors
       Info: ifInErrors

       64 bit unsigned wrappable counter."
   ::= {pr1645v2PortSw 113}


pr1645v2PortSwInUnknownProtos OBJECT-TYPE
   SYNTAX      Counter64
   MAX-ACCESS  read-only
   STATUS      current
   DESCRIPTION
      "Path: ethernet1.performance.ifInUnknownProtos
       Info: ifInUnknownprotos

       64 bit unsigned wrappable counter."
   ::= {pr1645v2PortSw 114}


pr1645v2PortSwInQLen OBJECT-TYPE
   SYNTAX      Gauge32
   MAX-ACCESS  read-only
   STATUS      current
   DESCRIPTION
      "Path: ethernet1.performance.ifInQLen
       Info: ifInQLen

       32 bit unsigned gauge value."
   ::= {pr1645v2PortSw 128}


pr1645v2PortSwInDropEx OBJECT-TYPE
   SYNTAX      Counter64
   MAX-ACCESS  read-only
   STATUS      current
   DESCRIPTION
      "Path: ethernet1.performance.ifInDropLevelExceeded
       Info: ifInDiscards

       64 bit unsigned wrappable counter."
   ::= {pr1645v2PortSw 130}


pr1645v2PortSwInDropNoMac OBJECT-TYPE
   SYNTAX      Counter64
   MAX-ACCESS  read-only
   STATUS      current
   DESCRIPTION
      "Path: ethernet1.performance.ifInDiscardsNoMacFit
       Info: ifInDiscards

       64 bit unsigned wrappable counter."
   ::= {pr1645v2PortSw 133}


pr1645v2PortSwInDropNUCast OBJECT-TYPE
   SYNTAX      Counter64
   MAX-ACCESS  read-only
   STATUS      current
   DESCRIPTION
      "Path: ethernet1.performance.ifInDiscardsNUCast
       Info: ifInDiscards

       64 bit unsigned wrappable counter."
   ::= {pr1645v2PortSw 136}


pr1645v2PortSwInDropFilter OBJECT-TYPE
   SYNTAX      Counter64
   MAX-ACCESS  read-only
   STATUS      current
   DESCRIPTION
      "Path: ethernet1.performance.ifInDiscardsFilter
       Info: ifInDiscards

       64 bit unsigned wrappable counter."
   ::= {pr1645v2PortSw 137}


pr1645v2PortSwInBandwidth OBJECT IDENTIFIER ::= {pr1645v2PortSw 181}

pr1645v2PortSwInBandwidthSSC OBJECT IDENTIFIER ::= {pr1645v2PortSwInBandwidth 1}

pr1645v2PortSwInBandwidthEntry OBJECT IDENTIFIER ::= {pr1645v2PortSwInBandwidthSSC 1}

pr1645v2PortSwInBandwidth15sec OBJECT-TYPE
   SYNTAX      Integer32
   MAX-ACCESS  read-only
   STATUS      current
   DESCRIPTION
      "Path: ethernet1.performance.ifInBandwidth.15sec

       unit name = bps
       formula = 8 * ; 8 /"
   ::= {pr1645v2PortSwInBandwidthEntry 83886080}

pr1645v2PortSwInBandwidth30sec OBJECT-TYPE
   SYNTAX      Integer32
   MAX-ACCESS  read-only
   STATUS      current
   DESCRIPTION
      "Path: ethernet1.performance.ifInBandwidth.30sec

       unit name = bps
       formula = 8 * ; 8 /"
   ::= {pr1645v2PortSwInBandwidthEntry 167772160}

pr1645v2PortSwInBandwidth1min OBJECT-TYPE
   SYNTAX      Integer32
   MAX-ACCESS  read-only
   STATUS      current
   DESCRIPTION
      "Path: ethernet1.performance.ifInBandwidth.1min

       unit name = bps
       formula = 8 * ; 8 /"
   ::= {pr1645v2PortSwInBandwidthEntry 335544320}

pr1645v2PortSwInBandwidth2min OBJECT-TYPE
   SYNTAX      Integer32
   MAX-ACCESS  read-only
   STATUS      current
   DESCRIPTION
      "Path: ethernet1.performance.ifInBandwidth.2min

       unit name = bps
       formula = 8 * ; 8 /"
   ::= {pr1645v2PortSwInBandwidthEntry 671088640}

pr1645v2PortSwInBandwidth5min OBJECT-TYPE
   SYNTAX      Integer32
   MAX-ACCESS  read-only
   STATUS      current
   DESCRIPTION
      "Path: ethernet1.performance.ifInBandwidth.5min

       unit name = bps
       formula = 8 * ; 8 /"
   ::= {pr1645v2PortSwInBandwidthEntry 1677721600}


pr1645v2PortSwOutOctets OBJECT-TYPE
   SYNTAX      Counter64
   MAX-ACCESS  read-only
   STATUS      current
   DESCRIPTION
      "Path: ethernet1.performance.ifOutOctets
       Info: ifOutOctets

       64 bit unsigned wrappable counter."
   ::= {pr1645v2PortSw 115}


pr1645v2PortSwOutUcastPkts OBJECT-TYPE
   SYNTAX      Counter64
   MAX-ACCESS  read-only
   STATUS      current
   DESCRIPTION
      "Path: ethernet1.performance.ifOutUcastPkts
       Info: ifOutUcastPkts

       64 bit unsigned wrappable counter."
   ::= {pr1645v2PortSw 116}


pr1645v2PortSwOutNUcastPkts OBJECT-TYPE
   SYNTAX      Counter64
   MAX-ACCESS  read-only
   STATUS      current
   DESCRIPTION
      "Path: ethernet1.performance.ifOutNUcastPkts
       Info: ifOutNUcastPkts

       64 bit unsigned wrappable counter."
   ::= {pr1645v2PortSw 117}


pr1645v2PortSwOutBcastPkts OBJECT-TYPE
   SYNTAX      Counter64
   MAX-ACCESS  read-only
   STATUS      current
   DESCRIPTION
      "Path: ethernet1.performance.ifOutBcastPkts
       Info: ifOutBcastPkts

       64 bit unsigned wrappable counter."
   ::= {pr1645v2PortSw 217}


pr1645v2PortSwOutMcastPkts OBJECT-TYPE
   SYNTAX      Counter64
   MAX-ACCESS  read-only
   STATUS      current
   DESCRIPTION
      "Path: ethernet1.performance.ifOutMcastPkts
       Info: ifOutMcastPkts

       64 bit unsigned wrappable counter."
   ::= {pr1645v2PortSw 227}


pr1645v2PortSwOutDiscards OBJECT-TYPE
   SYNTAX      Counter64
   MAX-ACCESS  read-only
   STATUS      current
   DESCRIPTION
      "Path: ethernet1.performance.ifOutDiscards
       Info: ifOutDiscards

       64 bit unsigned wrappable counter."
   ::= {pr1645v2PortSw 118}


pr1645v2PortSwOutErrors OBJECT-TYPE
   SYNTAX      Counter64
   MAX-ACCESS  read-only
   STATUS      current
   DESCRIPTION
      "Path: ethernet1.performance.ifOutErrors
       Info: ifOutErrors

       64 bit unsigned wrappable counter."
   ::= {pr1645v2PortSw 119}


pr1645v2PortSwOutQLen OBJECT-TYPE
   SYNTAX      Gauge32
   MAX-ACCESS  read-only
   STATUS      current
   DESCRIPTION
      "Path: ethernet1.performance.ifOutQLen
       Info: ifOutQLen

       32 bit unsigned gauge value."
   ::= {pr1645v2PortSw 120}


pr1645v2PortSwOutDropEx OBJECT-TYPE
   SYNTAX      Counter64
   MAX-ACCESS  read-only
   STATUS      current
   DESCRIPTION
      "Path: ethernet1.performance.ifOutDropLevelExceeded
       Info: ifOutDiscards

       64 bit unsigned wrappable counter."
   ::= {pr1645v2PortSw 127}


pr1645v2PortSwOutDropNoArp OBJECT-TYPE
   SYNTAX      Counter64
   MAX-ACCESS  read-only
   STATUS      current
   DESCRIPTION
      "Path: ethernet1.performance.ifOutDiscardsNoArp
       Info: ifOutDiscards

       64 bit unsigned wrappable counter."
   ::= {pr1645v2PortSw 134}


pr1645v2PortSwOutDropFilter OBJECT-TYPE
   SYNTAX      Counter64
   MAX-ACCESS  read-only
   STATUS      current
   DESCRIPTION
      "Path: ethernet1.performance.ifOutDiscardsFilter
       Info: ifOutDiscards

       64 bit unsigned wrappable counter."
   ::= {pr1645v2PortSw 138}


pr1645v2PortSwOutQueues OBJECT IDENTIFIER ::= {pr1645v2PortSw 129}

pr1645v2PortSwOutQueuesSSCTable OBJECT-TYPE
   SYNTAX      SEQUENCE OF Pr1645v2PortSwOutQueuesEntry
   MAX-ACCESS  not-accessible
   STATUS      current
   DESCRIPTION
      "Queue Lengths"
   ::= {pr1645v2PortSwOutQueues 1}

pr1645v2PortSwOutQueuesEntry OBJECT-TYPE
   SYNTAX      Pr1645v2PortSwOutQueuesEntry
   MAX-ACCESS  not-accessible
   STATUS      current
   DESCRIPTION
      ""
   INDEX      { pr1645v2PortSwOutQueuesTableIx }
   ::= {pr1645v2PortSwOutQueuesSSCTable 1}

Pr1645v2PortSwOutQueuesEntry ::=
   SEQUENCE
      {
      pr1645v2PortSwOutQueuesTableIx
         TableIndex,
      pr1645v2PortSwOutQueuesName
         INTEGER,
      pr1645v2PortSwOutQueuesLength
         Integer32,
      pr1645v2PortSwOutQueuesOctetLength
         Integer32,
      pr1645v2PortSwOutQueuesRedLength
         Integer32,
      pr1645v2PortSwOutQueuesPacketsTotal
         Counter64,
      pr1645v2PortSwOutQueuesPacketsDirectTx
         Counter64,
      pr1645v2PortSwOutQueuesPacketsQueued
         Counter64,
      pr1645v2PortSwOutQueuesPacketsDropped
         Counter64,
      pr1645v2PortSwOutQueuesPacketsRedDropped
         Counter64,
      pr1645v2PortSwOutQueuesPacketsCirTx
         Counter64,
      pr1645v2PortSwOutQueuesPacketsEirTx
         Counter64,
      pr1645v2PortSwOutQueuesPacketsViolateTx
         Counter64,
      pr1645v2PortSwOutQueuesOctetsTotal
         Counter64,
      pr1645v2PortSwOutQueuesOctetsDirectTx
         Counter64,
      pr1645v2PortSwOutQueuesOctetsQueued
         Counter64,
      pr1645v2PortSwOutQueuesOctetsDropped
         Counter64,
      pr1645v2PortSwOutQueuesOctetsRedDropped
         Counter64,
      pr1645v2PortSwOutQueuesOctetsCirTx
         Counter64,
      pr1645v2PortSwOutQueuesOctetsEirTx
         Counter64,
      pr1645v2PortSwOutQueuesOctetsViolateTx
         Counter64,
      pr1645v2PortSwOutQueuesOctetsBandwidth15sec
         Integer32,
      pr1645v2PortSwOutQueuesOctetsBandwidth30sec
         Integer32,
      pr1645v2PortSwOutQueuesOctetsBandwidth1min
         Integer32,
      pr1645v2PortSwOutQueuesOctetsBandwidth2min
         Integer32,
      pr1645v2PortSwOutQueuesOctetsBandwidth5min
         Integer32
      }

pr1645v2PortSwOutQueuesTableIx OBJECT-TYPE
   SYNTAX      TableIndex
   MAX-ACCESS  not-accessible
   STATUS      current
   DESCRIPTION
      ""
   ::= {pr1645v2PortSwOutQueuesEntry 11}

pr1645v2PortSwOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwOutQueuesEntry 16777216}

pr1645v2PortSwOutQueuesLength OBJECT-TYPE
   SYNTAX      Integer32
   MAX-ACCESS  read-only
   STATUS      current
   DESCRIPTION
      "Path: ethernet1.performance.ifOutPriorityQueues.length"
   ::= {pr1645v2PortSwOutQueuesEntry 33554432}

pr1645v2PortSwOutQueuesOctetLength OBJECT-TYPE
   SYNTAX      Integer32
   MAX-ACCESS  read-only
   STATUS      current
   DESCRIPTION
      "Path: ethernet1.performance.ifOutPriorityQueues.octetLength"
   ::= {pr1645v2PortSwOutQueuesEntry 150994944}

pr1645v2PortSwOutQueuesRedLength OBJECT-TYPE
   SYNTAX      Integer32
   MAX-ACCESS  read-only
   STATUS      current
   DESCRIPTION
      "Path: ethernet1.performance.ifOutPriorityQueues.redLength"
   ::= {pr1645v2PortSwOutQueuesEntry 134217728}

pr1645v2PortSwOutQueuesPacketsTotal OBJECT-TYPE
   SYNTAX      Counter64
   MAX-ACCESS  read-only
   STATUS      current
   DESCRIPTION
      "Path: ethernet1.performance.ifOutPriorityQueues.packets.total

       64 bit unsigned wrappable counter."
   ::= {pr1645v2PortSwOutQueuesEntry 50790400}

pr1645v2PortSwOutQueuesPacketsDirectTx OBJECT-TYPE
   SYNTAX      Counter64
   MAX-ACCESS  read-only
   STATUS      current
   DESCRIPTION
      "Path: ethernet1.performance.ifOutPriorityQueues.packets.directTx

       64 bit unsigned wrappable counter."
   ::= {pr1645v2PortSwOutQueuesEntry 50397184}

pr1645v2PortSwOutQueuesPacketsQueued OBJECT-TYPE
   SYNTAX      Counter64
   MAX-ACCESS  read-only
   STATUS      current
   DESCRIPTION
      "Path: ethernet1.performance.ifOutPriorityQueues.packets.queued

       64 bit unsigned wrappable counter."
   ::= {pr1645v2PortSwOutQueuesEntry 50462720}

pr1645v2PortSwOutQueuesPacketsDropped OBJECT-TYPE
   SYNTAX      Counter64
   MAX-ACCESS  read-only
   STATUS      current
   DESCRIPTION
      "Path: ethernet1.performance.ifOutPriorityQueues.packets.dropped

       64 bit unsigned wrappable counter."
   ::= {pr1645v2PortSwOutQueuesEntry 50528256}

pr1645v2PortSwOutQueuesPacketsRedDropped OBJECT-TYPE
   SYNTAX      Counter64
   MAX-ACCESS  read-only
   STATUS      current
   DESCRIPTION
      "Path: ethernet1.performance.ifOutPriorityQueues.packets.redDropped

       64 bit unsigned wrappable counter."
   ::= {pr1645v2PortSwOutQueuesEntry 50724864}

pr1645v2PortSwOutQueuesPacketsCirTx OBJECT-TYPE
   SYNTAX      Counter64
   MAX-ACCESS  read-only
   STATUS      current
   DESCRIPTION
      "Path: ethernet1.performance.ifOutPriorityQueues.packets.cirTx

       64 bit unsigned wrappable counter."
   ::= {pr1645v2PortSwOutQueuesEntry 50593792}

pr1645v2PortSwOutQueuesPacketsEirTx OBJECT-TYPE
   SYNTAX      Counter64
   MAX-ACCESS  read-only
   STATUS      current
   DESCRIPTION
      "Path: ethernet1.performance.ifOutPriorityQueues.packets.eirTx

       64 bit unsigned wrappable counter."
   ::= {pr1645v2PortSwOutQueuesEntry 50659328}

pr1645v2PortSwOutQueuesPacketsViolateTx OBJECT-TYPE
   SYNTAX      Counter64
   MAX-ACCESS  read-only
   STATUS      current
   DESCRIPTION
      "Path: ethernet1.performance.ifOutPriorityQueues.packets.violateTx

       64 bit unsigned wrappable counter."
   ::= {pr1645v2PortSwOutQueuesEntry 50855936}

pr1645v2PortSwOutQueuesOctetsTotal OBJECT-TYPE
   SYNTAX      Counter64
   MAX-ACCESS  read-only
   STATUS      current
   DESCRIPTION
      "Path: ethernet1.performance.ifOutPriorityQueues.octets.total

       64 bit unsigned wrappable counter."
   ::= {pr1645v2PortSwOutQueuesEntry 67567616}

pr1645v2PortSwOutQueuesOctetsDirectTx OBJECT-TYPE
   SYNTAX      Counter64
   MAX-ACCESS  read-only
   STATUS      current
   DESCRIPTION
      "Path: ethernet1.performance.ifOutPriorityQueues.octets.directTx

       64 bit unsigned wrappable counter."
   ::= {pr1645v2PortSwOutQueuesEntry 67174400}

pr1645v2PortSwOutQueuesOctetsQueued OBJECT-TYPE
   SYNTAX      Counter64
   MAX-ACCESS  read-only
   STATUS      current
   DESCRIPTION
      "Path: ethernet1.performance.ifOutPriorityQueues.octets.queued

       64 bit unsigned wrappable counter."
   ::= {pr1645v2PortSwOutQueuesEntry 67239936}

pr1645v2PortSwOutQueuesOctetsDropped OBJECT-TYPE
   SYNTAX      Counter64
   MAX-ACCESS  read-only
   STATUS      current
   DESCRIPTION
      "Path: ethernet1.performance.ifOutPriorityQueues.octets.dropped

       64 bit unsigned wrappable counter."
   ::= {pr1645v2PortSwOutQueuesEntry 67305472}

pr1645v2PortSwOutQueuesOctetsRedDropped OBJECT-TYPE
   SYNTAX      Counter64
   MAX-ACCESS  read-only
   STATUS      current
   DESCRIPTION
      "Path: ethernet1.performance.ifOutPriorityQueues.octets.redDropped

       64 bit unsigned wrappable counter."
   ::= {pr1645v2PortSwOutQueuesEntry 67502080}

pr1645v2PortSwOutQueuesOctetsCirTx OBJECT-TYPE
   SYNTAX      Counter64
   MAX-ACCESS  read-only
   STATUS      current
   DESCRIPTION
      "Path: ethernet1.performance.ifOutPriorityQueues.octets.cirTx

       64 bit unsigned wrappable counter."
   ::= {pr1645v2PortSwOutQueuesEntry 67371008}

pr1645v2PortSwOutQueuesOctetsEirTx OBJECT-TYPE
   SYNTAX      Counter64
   MAX-ACCESS  read-only
   STATUS      current
   DESCRIPTION
      "Path: ethernet1.performance.ifOutPriorityQueues.octets.eirTx

       64 bit unsigned wrappable counter."
   ::= {pr1645v2PortSwOutQueuesEntry 67436544}

pr1645v2PortSwOutQueuesOctetsViolateTx OBJECT-TYPE
   SYNTAX      Counter64
   MAX-ACCESS  read-only
   STATUS      current
   DESCRIPTION
      "Path: ethernet1.performance.ifOutPriorityQueues.octets.violateTx

       64 bit unsigned wrappable counter."
   ::= {pr1645v2PortSwOutQueuesEntry 67633152}

pr1645v2PortSwOutQueuesOctetsBandwidth15sec OBJECT-TYPE
   SYNTAX      Integer32
   MAX-ACCESS  read-only
   STATUS      current
   DESCRIPTION
      "Path: ethernet1.performance.ifOutPriorityQueues.octets.bandwidth.15sec

       unit name = bps
       formula = 8 * ; 8 /"
   ::= {pr1645v2PortSwOutQueuesEntry 70386944}

pr1645v2PortSwOutQueuesOctetsBandwidth30sec OBJECT-TYPE
   SYNTAX      Integer32
   MAX-ACCESS  read-only
   STATUS      current
   DESCRIPTION
      "Path: ethernet1.performance.ifOutPriorityQueues.octets.bandwidth.30sec

       unit name = bps
       formula = 8 * ; 8 /"
   ::= {pr1645v2PortSwOutQueuesEntry 70388224}

pr1645v2PortSwOutQueuesOctetsBandwidth1min OBJECT-TYPE
   SYNTAX      Integer32
   MAX-ACCESS  read-only
   STATUS      current
   DESCRIPTION
      "Path: ethernet1.performance.ifOutPriorityQueues.octets.bandwidth.1min

       unit name = bps
       formula = 8 * ; 8 /"
   ::= {pr1645v2PortSwOutQueuesEntry 70390784}

pr1645v2PortSwOutQueuesOctetsBandwidth2min OBJECT-TYPE
   SYNTAX      Integer32
   MAX-ACCESS  read-only
   STATUS      current
   DESCRIPTION
      "Path: ethernet1.performance.ifOutPriorityQueues.octets.bandwidth.2min

       unit name = bps
       formula = 8 * ; 8 /"
   ::= {pr1645v2PortSwOutQueuesEntry 70395904}

pr1645v2PortSwOutQueuesOctetsBandwidth5min OBJECT-TYPE
   SYNTAX      Integer32
   MAX-ACCESS  read-only
   STATUS      current
   DESCRIPTION
      "Path: ethernet1.performance.ifOutPriorityQueues.octets.bandwidth.5min

       unit name = bps
       formula = 8 * ; 8 /"
   ::= {pr1645v2PortSwOutQueuesEntry 70411264}

pr1645v2PortSwOutQueuesH2Performance OBJECT-TYPE
   SYNTAX      SEQUENCE OF Pr1645v2PortSwOutQueuesH2PerformanceEntry
   MAX-ACCESS  not-accessible
   STATUS      current
   DESCRIPTION
      ""
   ::= {pr1645v2PortSwOutQueues 83886080}

pr1645v2PortSwOutQueuesH2PerformanceEntry OBJECT-TYPE
   SYNTAX      Pr1645v2PortSwOutQueuesH2PerformanceEntry
   MAX-ACCESS  not-accessible
   STATUS      current
   DESCRIPTION
      ""
   INDEX      { pr1645v2PortSwOutQueuesTableIx,
                pr1645v2PortSwOutQueuesH2PerformanceTableIx }
   ::= {pr1645v2PortSwOutQueuesH2Performance 1}

Pr1645v2PortSwOutQueuesH2PerformanceEntry ::=
   SEQUENCE
      {
      pr1645v2PortSwOutQueuesH2PerformanceTableIx
         TableIndex,
      pr1645v2PortSwOutQueuesH2PerformanceSysUpTime
         TimeTicks,
      pr1645v2PortSwOutQueuesH2PerformanceTotPkts
         Counter64,
      pr1645v2PortSwOutQueuesH2PerformanceDirTxPkts
         Counter64,
      pr1645v2PortSwOutQueuesH2PerformanceQdPkts
         Counter64,
      pr1645v2PortSwOutQueuesH2PerformanceDropPkts
         Counter64,
      pr1645v2PortSwOutQueuesH2PerformanceRDropPkts
         Counter64,
      pr1645v2PortSwOutQueuesH2PerformanceCirTxPkts
         Counter64,
      pr1645v2PortSwOutQueuesH2PerformanceEirTxPkts
         Counter64,
      pr1645v2PortSwOutQueuesH2PerformanceViolTxPkts
         Counter64,
      pr1645v2PortSwOutQueuesH2PerformanceTotOcts
         Counter64,
      pr1645v2PortSwOutQueuesH2PerformanceDirTxOcts
         Counter64,
      pr1645v2PortSwOutQueuesH2PerformanceQdOcts
         Counter64,
      pr1645v2PortSwOutQueuesH2PerformanceDropOcts
         Counter64,
      pr1645v2PortSwOutQueuesH2PerformanceRDropOcts
         Counter64,
      pr1645v2PortSwOutQueuesH2PerformanceCirTxOcts
         Counter64,
      pr1645v2PortSwOutQueuesH2PerformanceEirTxOcts
         Counter64,
      pr1645v2PortSwOutQueuesH2PerformanceViolTxOcts
         Counter64,
      pr1645v2PortSwOutQueuesH2PerformanceBandwidth
         Integer32
      }

pr1645v2PortSwOutQueuesH2PerformanceTableIx OBJECT-TYPE
   SYNTAX      TableIndex
   MAX-ACCESS  not-accessible
   STATUS      current
   DESCRIPTION
      ""
   ::= {pr1645v2PortSwOutQueuesH2PerformanceEntry 11}

pr1645v2PortSwOutQueuesH2PerformanceSysUpTime OBJECT-TYPE
   SYNTAX      TimeTicks
   MAX-ACCESS  read-only
   STATUS      current
   DESCRIPTION
      "Path: ethernet1.performance.ifOutPriorityQueues.h2Performance.sysUpTime

       Time in centi-second."
   ::= {pr1645v2PortSwOutQueuesH2PerformanceEntry 16777216}

pr1645v2PortSwOutQueuesH2PerformanceTotPkts OBJECT-TYPE
   SYNTAX      Counter64
   MAX-ACCESS  read-only
   STATUS      current
   DESCRIPTION
      "Path: ethernet1.performance.ifOutPriorityQueues.h2Performance.totalPkts

       64 bit unsigned wrappable counter."
   ::= {pr1645v2PortSwOutQueuesH2PerformanceEntry 234881024}

pr1645v2PortSwOutQueuesH2PerformanceDirTxPkts OBJECT-TYPE
   SYNTAX      Counter64
   MAX-ACCESS  read-only
   STATUS      current
   DESCRIPTION
      "Path: ethernet1.performance.ifOutPriorityQueues.h2Performance.directTxPkts

       64 bit unsigned wrappable counter."
   ::= {pr1645v2PortSwOutQueuesH2PerformanceEntry 33554432}

pr1645v2PortSwOutQueuesH2PerformanceQdPkts OBJECT-TYPE
   SYNTAX      Counter64
   MAX-ACCESS  read-only
   STATUS      current
   DESCRIPTION
      "Path: ethernet1.performance.ifOutPriorityQueues.h2Performance.queuedPkts

       64 bit unsigned wrappable counter."
   ::= {pr1645v2PortSwOutQueuesH2PerformanceEntry 50331648}

pr1645v2PortSwOutQueuesH2PerformanceDropPkts OBJECT-TYPE
   SYNTAX      Counter64
   MAX-ACCESS  read-only
   STATUS      current
   DESCRIPTION
      "Path: ethernet1.performance.ifOutPriorityQueues.h2Performance.droppedPkts

       64 bit unsigned wrappable counter."
   ::= {pr1645v2PortSwOutQueuesH2PerformanceEntry 67108864}

pr1645v2PortSwOutQueuesH2PerformanceRDropPkts OBJECT-TYPE
   SYNTAX      Counter64
   MAX-ACCESS  read-only
   STATUS      current
   DESCRIPTION
      "Path: ethernet1.performance.ifOutPriorityQueues.h2Performance.redDroppedPkts

       64 bit unsigned wrappable counter."
   ::= {pr1645v2PortSwOutQueuesH2PerformanceEntry 201326592}

pr1645v2PortSwOutQueuesH2PerformanceCirTxPkts OBJECT-TYPE
   SYNTAX      Counter64
   MAX-ACCESS  read-only
   STATUS      current
   DESCRIPTION
      "Path: ethernet1.performance.ifOutPriorityQueues.h2Performance.cirTxPkts

       64 bit unsigned wrappable counter."
   ::= {pr1645v2PortSwOutQueuesH2PerformanceEntry 83886080}

pr1645v2PortSwOutQueuesH2PerformanceEirTxPkts OBJECT-TYPE
   SYNTAX      Counter64
   MAX-ACCESS  read-only
   STATUS      current
   DESCRIPTION
      "Path: ethernet1.performance.ifOutPriorityQueues.h2Performance.eirTxPkts

       64 bit unsigned wrappable counter."
   ::= {pr1645v2PortSwOutQueuesH2PerformanceEntry 100663296}

pr1645v2PortSwOutQueuesH2PerformanceViolTxPkts OBJECT-TYPE
   SYNTAX      Counter64
   MAX-ACCESS  read-only
   STATUS      current
   DESCRIPTION
      "Path: ethernet1.performance.ifOutPriorityQueues.h2Performance.violateTxPkts

       64 bit unsigned wrappable counter."
   ::= {pr1645v2PortSwOutQueuesH2PerformanceEntry 301989888}

pr1645v2PortSwOutQueuesH2PerformanceTotOcts OBJECT-TYPE
   SYNTAX      Counter64
   MAX-ACCESS  read-only
   STATUS      current
   DESCRIPTION
      "Path: ethernet1.performance.ifOutPriorityQueues.h2Performance.totalOctets

       64 bit unsigned wrappable counter."
   ::= {pr1645v2PortSwOutQueuesH2PerformanceEntry 251658240}

pr1645v2PortSwOutQueuesH2PerformanceDirTxOcts OBJECT-TYPE
   SYNTAX      Counter64
   MAX-ACCESS  read-only
   STATUS      current
   DESCRIPTION
      "Path: ethernet1.performance.ifOutPriorityQueues.h2Performance.directTxOctets

       64 bit unsigned wrappable counter."
   ::= {pr1645v2PortSwOutQueuesH2PerformanceEntry 117440512}

pr1645v2PortSwOutQueuesH2PerformanceQdOcts OBJECT-TYPE
   SYNTAX      Counter64
   MAX-ACCESS  read-only
   STATUS      current
   DESCRIPTION
      "Path: ethernet1.performance.ifOutPriorityQueues.h2Performance.queuedOctets

       64 bit unsigned wrappable counter."
   ::= {pr1645v2PortSwOutQueuesH2PerformanceEntry 134217728}

pr1645v2PortSwOutQueuesH2PerformanceDropOcts OBJECT-TYPE
   SYNTAX      Counter64
   MAX-ACCESS  read-only
   STATUS      current
   DESCRIPTION
      "Path: ethernet1.performance.ifOutPriorityQueues.h2Performance.droppedOctets

       64 bit unsigned wrappable counter."
   ::= {pr1645v2PortSwOutQueuesH2PerformanceEntry 150994944}

pr1645v2PortSwOutQueuesH2PerformanceRDropOcts OBJECT-TYPE
   SYNTAX      Counter64
   MAX-ACCESS  read-only
   STATUS      current
   DESCRIPTION
      "Path: ethernet1.performance.ifOutPriorityQueues.h2Performance.redDroppedOctets

       64 bit unsigned wrappable counter."
   ::= {pr1645v2PortSwOutQueuesH2PerformanceEntry 218103808}

pr1645v2PortSwOutQueuesH2PerformanceCirTxOcts OBJECT-TYPE
   SYNTAX      Counter64
   MAX-ACCESS  read-only
   STATUS      current
   DESCRIPTION
      "Path: ethernet1.performance.ifOutPriorityQueues.h2Performance.cirTxOctets

       64 bit unsigned wrappable counter."
   ::= {pr1645v2PortSwOutQueuesH2PerformanceEntry 167772160}

pr1645v2PortSwOutQueuesH2PerformanceEirTxOcts OBJECT-TYPE
   SYNTAX      Counter64
   MAX-ACCESS  read-only
   STATUS      current
   DESCRIPTION
      "Path: ethernet1.performance.ifOutPriorityQueues.h2Performance.eirTxOctets

       64 bit unsigned wrappable counter."
   ::= {pr1645v2PortSwOutQueuesH2PerformanceEntry 184549376}

pr1645v2PortSwOutQueuesH2PerformanceViolTxOcts OBJECT-TYPE
   SYNTAX      Counter64
   MAX-ACCESS  read-only
   STATUS      current
   DESCRIPTION
      "Path: ethernet1.performance.ifOutPriorityQueues.h2Performance.violateTxOctets

       64 bit unsigned wrappable counter."
   ::= {pr1645v2PortSwOutQueuesH2PerformanceEntry 318767104}

pr1645v2PortSwOutQueuesH2PerformanceBandwidth OBJECT-TYPE
   SYNTAX      Integer32
   MAX-ACCESS  read-only
   STATUS      current
   DESCRIPTION
      "Path: ethernet1.performance.ifOutPriorityQueues.h2Performance.bandwidth

       unit name = bps
       formula = 8 * ; 8 /"
   ::= {pr1645v2PortSwOutQueuesH2PerformanceEntry 268435456}

pr1645v2PortSwOutQueuesH24Performance OBJECT-TYPE
   SYNTAX      SEQUENCE OF Pr1645v2PortSwOutQueuesH24PerformanceEntry
   MAX-ACCESS  not-accessible
   STATUS      current
   DESCRIPTION
      ""
   ::= {pr1645v2PortSwOutQueues 100663296}

pr1645v2PortSwOutQueuesH24PerformanceEntry OBJECT-TYPE
   SYNTAX      Pr1645v2PortSwOutQueuesH24PerformanceEntry
   MAX-ACCESS  not-accessible
   STATUS      current
   DESCRIPTION
      ""
   INDEX      { pr1645v2PortSwOutQueuesTableIx,
                pr1645v2PortSwOutQueuesH24PerformanceTableIx }
   ::= {pr1645v2PortSwOutQueuesH24Performance 1}

Pr1645v2PortSwOutQueuesH24PerformanceEntry ::=
   SEQUENCE
      {
      pr1645v2PortSwOutQueuesH24PerformanceTableIx
         TableIndex,
      pr1645v2PortSwOutQueuesH24PerformanceSysUpTime
         TimeTicks,
      pr1645v2PortSwOutQueuesH24PerformanceTotPkts
         Counter64,
      pr1645v2PortSwOutQueuesH24PerformanceDirTxPkts
         Counter64,
      pr1645v2PortSwOutQueuesH24PerformanceQdPkts
         Counter64,
      pr1645v2PortSwOutQueuesH24PerformanceDropPkts
         Counter64,
      pr1645v2PortSwOutQueuesH24PerformanceRDropPkts
         Counter64,
      pr1645v2PortSwOutQueuesH24PerformanceCirTxPkts
         Counter64,
      pr1645v2PortSwOutQueuesH24PerformanceEirTxPkts
         Counter64,
      pr1645v2PortSwOutQueuesH24PerformanceViolTxPkts
         Counter64,
      pr1645v2PortSwOutQueuesH24PerformanceTotOcts
         Counter64,
      pr1645v2PortSwOutQueuesH24PerformanceDirTxOcts
         Counter64,
      pr1645v2PortSwOutQueuesH24PerformanceQdOcts
         Counter64,
      pr1645v2PortSwOutQueuesH24PerformanceDropOcts
         Counter64,
      pr1645v2PortSwOutQueuesH24PerformanceRDropOcts
         Counter64,
      pr1645v2PortSwOutQueuesH24PerformanceCirTxOcts
         Counter64,
      pr1645v2PortSwOutQueuesH24PerformanceEirTxOcts
         Counter64,
      pr1645v2PortSwOutQueuesH24PerformanceViolTxOcts
         Counter64,
      pr1645v2PortSwOutQueuesH24PerformanceBandwidth
         Integer32
      }

pr1645v2PortSwOutQueuesH24PerformanceTableIx OBJECT-TYPE
   SYNTAX      TableIndex
   MAX-ACCESS  not-accessible
   STATUS      current
   DESCRIPTION
      ""
   ::= {pr1645v2PortSwOutQueuesH24PerformanceEntry 11}

pr1645v2PortSwOutQueuesH24PerformanceSysUpTime OBJECT-TYPE
   SYNTAX      TimeTicks
   MAX-ACCESS  read-only
   STATUS      current
   DESCRIPTION
      "Path: ethernet1.performance.ifOutPriorityQueues.h24Performance.sysUpTime

       Time in centi-second."
   ::= {pr1645v2PortSwOutQueuesH24PerformanceEntry 16777216}

pr1645v2PortSwOutQueuesH24PerformanceTotPkts OBJECT-TYPE
   SYNTAX      Counter64
   MAX-ACCESS  read-only
   STATUS      current
   DESCRIPTION
      "Path: ethernet1.performance.ifOutPriorityQueues.h24Performance.totalPkts

       64 bit unsigned wrappable counter."
   ::= {pr1645v2PortSwOutQueuesH24PerformanceEntry 234881024}

pr1645v2PortSwOutQueuesH24PerformanceDirTxPkts OBJECT-TYPE
   SYNTAX      Counter64
   MAX-ACCESS  read-only
   STATUS      current
   DESCRIPTION
      "Path: ethernet1.performance.ifOutPriorityQueues.h24Performance.directTxPkts

       64 bit unsigned wrappable counter."
   ::= {pr1645v2PortSwOutQueuesH24PerformanceEntry 33554432}

pr1645v2PortSwOutQueuesH24PerformanceQdPkts OBJECT-TYPE
   SYNTAX      Counter64
   MAX-ACCESS  read-only
   STATUS      current
   DESCRIPTION
      "Path: ethernet1.performance.ifOutPriorityQueues.h24Performance.queuedPkts

       64 bit unsigned wrappable counter."
   ::= {pr1645v2PortSwOutQueuesH24PerformanceEntry 50331648}

pr1645v2PortSwOutQueuesH24PerformanceDropPkts OBJECT-TYPE
   SYNTAX      Counter64
   MAX-ACCESS  read-only
   STATUS      current
   DESCRIPTION
      "Path: ethernet1.performance.ifOutPriorityQueues.h24Performance.droppedPkts

       64 bit unsigned wrappable counter."
   ::= {pr1645v2PortSwOutQueuesH24PerformanceEntry 67108864}

pr1645v2PortSwOutQueuesH24PerformanceRDropPkts OBJECT-TYPE
   SYNTAX      Counter64
   MAX-ACCESS  read-only
   STATUS      current
   DESCRIPTION
      "Path: ethernet1.performance.ifOutPriorityQueues.h24Performance.redDroppedPkts

       64 bit unsigned wrappable counter."
   ::= {pr1645v2PortSwOutQueuesH24PerformanceEntry 201326592}

pr1645v2PortSwOutQueuesH24PerformanceCirTxPkts OBJECT-TYPE
   SYNTAX      Counter64
   MAX-ACCESS  read-only
   STATUS      current
   DESCRIPTION
      "Path: ethernet1.performance.ifOutPriorityQueues.h24Performance.cirTxPkts

       64 bit unsigned wrappable counter."
   ::= {pr1645v2PortSwOutQueuesH24PerformanceEntry 83886080}

pr1645v2PortSwOutQueuesH24PerformanceEirTxPkts OBJECT-TYPE
   SYNTAX      Counter64
   MAX-ACCESS  read-only
   STATUS      current
   DESCRIPTION
      "Path: ethernet1.performance.ifOutPriorityQueues.h24Performance.eirTxPkts

       64 bit unsigned wrappable counter."
   ::= {pr1645v2PortSwOutQueuesH24PerformanceEntry 100663296}

pr1645v2PortSwOutQueuesH24PerformanceViolTxPkts OBJECT-TYPE
   SYNTAX      Counter64
   MAX-ACCESS  read-only
   STATUS      current
   DESCRIPTION
      "Path: ethernet1.performance.ifOutPriorityQueues.h24Performance.violateTxPkts

       64 bit unsigned wrappable counter."
   ::= {pr1645v2PortSwOutQueuesH24PerformanceEntry 301989888}

pr1645v2PortSwOutQueuesH24PerformanceTotOcts OBJECT-TYPE
   SYNTAX      Counter64
   MAX-ACCESS  read-only
   STATUS      current
   DESCRIPTION
      "Path: ethernet1.performance.ifOutPriorityQueues.h24Performance.totalOctets

       64 bit unsigned wrappable counter."
   ::= {pr1645v2PortSwOutQueuesH24PerformanceEntry 251658240}

pr1645v2PortSwOutQueuesH24PerformanceDirTxOcts OBJECT-TYPE
   SYNTAX      Counter64
   MAX-ACCESS  read-only
   STATUS      current
   DESCRIPTION
      "Path: ethernet1.performance.ifOutPriorityQueues.h24Performance.directTxOctets

       64 bit unsigned wrappable counter."
   ::= {pr1645v2PortSwOutQueuesH24PerformanceEntry 117440512}

pr1645v2PortSwOutQueuesH24PerformanceQdOcts OBJECT-TYPE
   SYNTAX      Counter64
   MAX-ACCESS  read-only
   STATUS      current
   DESCRIPTION
      "Path: ethernet1.performance.ifOutPriorityQueues.h24Performance.queuedOctets

       64 bit unsigned wrappable counter."
   ::= {pr1645v2PortSwOutQueuesH24PerformanceEntry 134217728}

pr1645v2PortSwOutQueuesH24PerformanceDropOcts OBJECT-TYPE
   SYNTAX      Counter64
   MAX-ACCESS  read-only
   STATUS      current
   DESCRIPTION
      "Path: ethernet1.performance.ifOutPriorityQueues.h24Performance.droppedOctets

       64 bit unsigned wrappable counter."
   ::= {pr1645v2PortSwOutQueuesH24PerformanceEntry 150994944}

pr1645v2PortSwOutQueuesH24PerformanceRDropOcts OBJECT-TYPE
   SYNTAX      Counter64
   MAX-ACCESS  read-only
   STATUS      current
   DESCRIPTION
      "Path: ethernet1.performance.ifOutPriorityQueues.h24Performance.redDroppedOctets

       64 bit unsigned wrappable counter."
   ::= {pr1645v2PortSwOutQueuesH24PerformanceEntry 218103808}

pr1645v2PortSwOutQueuesH24PerformanceCirTxOcts OBJECT-TYPE
   SYNTAX      Counter64
   MAX-ACCESS  read-only
   STATUS      current
   DESCRIPTION
      "Path: ethernet1.performance.ifOutPriorityQueues.h24Performance.cirTxOctets

       64 bit unsigned wrappable counter."
   ::= {pr1645v2PortSwOutQueuesH24PerformanceEntry 167772160}

pr1645v2PortSwOutQueuesH24PerformanceEirTxOcts OBJECT-TYPE
   SYNTAX      Counter64
   MAX-ACCESS  read-only
   STATUS      current
   DESCRIPTION
      "Path: ethernet1.performance.ifOutPriorityQueues.h24Performance.eirTxOctets

       64 bit unsigned wrappable counter."
   ::= {pr1645v2PortSwOutQueuesH24PerformanceEntry 184549376}

pr1645v2PortSwOutQueuesH24PerformanceViolTxOcts OBJECT-TYPE
   SYNTAX      Counter64
   MAX-ACCESS  read-only
   STATUS      current
   DESCRIPTION
      "Path: ethernet1.performance.ifOutPriorityQueues.h24Performance.violateTxOctets

       64 bit unsigned wrappable counter."
   ::= {pr1645v2PortSwOutQueuesH24PerformanceEntry 318767104}

pr1645v2PortSwOutQueuesH24PerformanceBandwidth OBJECT-TYPE
   SYNTAX      Integer32
   MAX-ACCESS  read-only
   STATUS      current
   DESCRIPTION
      "Path: ethernet1.performance.ifOutPriorityQueues.h24Performance.bandwidth

       unit name = bps
       formula = 8 * ; 8 /"
   ::= {pr1645v2PortSwOutQueuesH24PerformanceEntry 268435456}

pr1645v2PortSwOutQueuesD7Performance OBJECT-TYPE
   SYNTAX      SEQUENCE OF Pr1645v2PortSwOutQueuesD7PerformanceEntry
   MAX-ACCESS  not-accessible
   STATUS      current
   DESCRIPTION
      ""
   ::= {pr1645v2PortSwOutQueues 117440512}

pr1645v2PortSwOutQueuesD7PerformanceEntry OBJECT-TYPE
   SYNTAX      Pr1645v2PortSwOutQueuesD7PerformanceEntry
   MAX-ACCESS  not-accessible
   STATUS      current
   DESCRIPTION
      ""
   INDEX      { pr1645v2PortSwOutQueuesTableIx,
                pr1645v2PortSwOutQueuesD7PerformanceTableIx }
   ::= {pr1645v2PortSwOutQueuesD7Performance 1}

Pr1645v2PortSwOutQueuesD7PerformanceEntry ::=
   SEQUENCE
      {
      pr1645v2PortSwOutQueuesD7PerformanceTableIx
         TableIndex,
      pr1645v2PortSwOutQueuesD7PerformanceSysUpTime
         TimeTicks,
      pr1645v2PortSwOutQueuesD7PerformanceTotPkts
         Counter64,
      pr1645v2PortSwOutQueuesD7PerformanceDirTxPkts
         Counter64,
      pr1645v2PortSwOutQueuesD7PerformanceQdPkts
         Counter64,
      pr1645v2PortSwOutQueuesD7PerformanceDropPkts
         Counter64,
      pr1645v2PortSwOutQueuesD7PerformanceRDropPkts
         Counter64,
      pr1645v2PortSwOutQueuesD7PerformanceCirTxPkts
         Counter64,
      pr1645v2PortSwOutQueuesD7PerformanceEirTxPkts
         Counter64,
      pr1645v2PortSwOutQueuesD7PerformanceViolTxPkts
         Counter64,
      pr1645v2PortSwOutQueuesD7PerformanceTotOcts
         Counter64,
      pr1645v2PortSwOutQueuesD7PerformanceDirTxOcts
         Counter64,
      pr1645v2PortSwOutQueuesD7PerformanceQdOcts
         Counter64,
      pr1645v2PortSwOutQueuesD7PerformanceDropOcts
         Counter64,
      pr1645v2PortSwOutQueuesD7PerformanceRDropOcts
         Counter64,
      pr1645v2PortSwOutQueuesD7PerformanceCirTxOcts
         Counter64,
      pr1645v2PortSwOutQueuesD7PerformanceEirTxOcts
         Counter64,
      pr1645v2PortSwOutQueuesD7PerformanceViolTxOcts
         Counter64,
      pr1645v2PortSwOutQueuesD7PerformanceBandwidth
         Integer32
      }

pr1645v2PortSwOutQueuesD7PerformanceTableIx OBJECT-TYPE
   SYNTAX      TableIndex
   MAX-ACCESS  not-accessible
   STATUS      current
   DESCRIPTION
      ""
   ::= {pr1645v2PortSwOutQueuesD7PerformanceEntry 11}

pr1645v2PortSwOutQueuesD7PerformanceSysUpTime OBJECT-TYPE
   SYNTAX      TimeTicks
   MAX-ACCESS  read-only
   STATUS      current
   DESCRIPTION
      "Path: ethernet1.performance.ifOutPriorityQueues.d7Performance.sysUpTime

       Time in centi-second."
   ::= {pr1645v2PortSwOutQueuesD7PerformanceEntry 16777216}

pr1645v2PortSwOutQueuesD7PerformanceTotPkts OBJECT-TYPE
   SYNTAX      Counter64
   MAX-ACCESS  read-only
   STATUS      current
   DESCRIPTION
      "Path: ethernet1.performance.ifOutPriorityQueues.d7Performance.totalPkts

       64 bit unsigned wrappable counter."
   ::= {pr1645v2PortSwOutQueuesD7PerformanceEntry 234881024}

pr1645v2PortSwOutQueuesD7PerformanceDirTxPkts OBJECT-TYPE
   SYNTAX      Counter64
   MAX-ACCESS  read-only
   STATUS      current
   DESCRIPTION
      "Path: ethernet1.performance.ifOutPriorityQueues.d7Performance.directTxPkts

       64 bit unsigned wrappable counter."
   ::= {pr1645v2PortSwOutQueuesD7PerformanceEntry 33554432}

pr1645v2PortSwOutQueuesD7PerformanceQdPkts OBJECT-TYPE
   SYNTAX      Counter64
   MAX-ACCESS  read-only
   STATUS      current
   DESCRIPTION
      "Path: ethernet1.performance.ifOutPriorityQueues.d7Performance.queuedPkts

       64 bit unsigned wrappable counter."
   ::= {pr1645v2PortSwOutQueuesD7PerformanceEntry 50331648}

pr1645v2PortSwOutQueuesD7PerformanceDropPkts OBJECT-TYPE
   SYNTAX      Counter64
   MAX-ACCESS  read-only
   STATUS      current
   DESCRIPTION
      "Path: ethernet1.performance.ifOutPriorityQueues.d7Performance.droppedPkts

       64 bit unsigned wrappable counter."
   ::= {pr1645v2PortSwOutQueuesD7PerformanceEntry 67108864}

pr1645v2PortSwOutQueuesD7PerformanceRDropPkts OBJECT-TYPE
   SYNTAX      Counter64
   MAX-ACCESS  read-only
   STATUS      current
   DESCRIPTION
      "Path: ethernet1.performance.ifOutPriorityQueues.d7Performance.redDroppedPkts

       64 bit unsigned wrappable counter."
   ::= {pr1645v2PortSwOutQueuesD7PerformanceEntry 201326592}

pr1645v2PortSwOutQueuesD7PerformanceCirTxPkts OBJECT-TYPE
   SYNTAX      Counter64
   MAX-ACCESS  read-only
   STATUS      current
   DESCRIPTION
      "Path: ethernet1.performance.ifOutPriorityQueues.d7Performance.cirTxPkts

       64 bit unsigned wrappable counter."
   ::= {pr1645v2PortSwOutQueuesD7PerformanceEntry 83886080}

pr1645v2PortSwOutQueuesD7PerformanceEirTxPkts OBJECT-TYPE
   SYNTAX      Counter64
   MAX-ACCESS  read-only
   STATUS      current
   DESCRIPTION
      "Path: ethernet1.performance.ifOutPriorityQueues.d7Performance.eirTxPkts

       64 bit unsigned wrappable counter."
   ::= {pr1645v2PortSwOutQueuesD7PerformanceEntry 100663296}

pr1645v2PortSwOutQueuesD7PerformanceViolTxPkts OBJECT-TYPE
   SYNTAX      Counter64
   MAX-ACCESS  read-only
   STATUS      current
   DESCRIPTION
      "Path: ethernet1.performance.ifOutPriorityQueues.d7Performance.violateTxPkts

       64 bit unsigned wrappable counter."
   ::= {pr1645v2PortSwOutQueuesD7PerformanceEntry 301989888}

pr1645v2PortSwOutQueuesD7PerformanceTotOcts OBJECT-TYPE
   SYNTAX      Counter64
   MAX-ACCESS  read-only
   STATUS      current
   DESCRIPTION
      "Path: ethernet1.performance.ifOutPriorityQueues.d7Performance.totalOctets

       64 bit unsigned wrappable counter."
   ::= {pr1645v2PortSwOutQueuesD7PerformanceEntry 251658240}

pr1645v2PortSwOutQueuesD7PerformanceDirTxOcts OBJECT-TYPE
   SYNTAX      Counter64
   MAX-ACCESS  read-only
   STATUS      current
   DESCRIPTION
      "Path: ethernet1.performance.ifOutPriorityQueues.d7Performance.directTxOctets

       64 bit unsigned wrappable counter."
   ::= {pr1645v2PortSwOutQueuesD7PerformanceEntry 117440512}

pr1645v2PortSwOutQueuesD7PerformanceQdOcts OBJECT-TYPE
   SYNTAX      Counter64
   MAX-ACCESS  read-only
   STATUS      current
   DESCRIPTION
      "Path: ethernet1.performance.ifOutPriorityQueues.d7Performance.queuedOctets

       64 bit unsigned wrappable counter."
   ::= {pr1645v2PortSwOutQueuesD7PerformanceEntry 134217728}

pr1645v2PortSwOutQueuesD7PerformanceDropOcts OBJECT-TYPE
   SYNTAX      Counter64
   MAX-ACCESS  read-only
   STATUS      current
   DESCRIPTION
      "Path: ethernet1.performance.ifOutPriorityQueues.d7Performance.droppedOctets

       64 bit unsigned wrappable counter."
   ::= {pr1645v2PortSwOutQueuesD7PerformanceEntry 150994944}

pr1645v2PortSwOutQueuesD7PerformanceRDropOcts OBJECT-TYPE
   SYNTAX      Counter64
   MAX-ACCESS  read-only
   STATUS      current
   DESCRIPTION
      "Path: ethernet1.performance.ifOutPriorityQueues.d7Performance.redDroppedOctets

       64 bit unsigned wrappable counter."
   ::= {pr1645v2PortSwOutQueuesD7PerformanceEntry 218103808}

pr1645v2PortSwOutQueuesD7PerformanceCirTxOcts OBJECT-TYPE
   SYNTAX      Counter64
   MAX-ACCESS  read-only
   STATUS      current
   DESCRIPTION
      "Path: ethernet1.performance.ifOutPriorityQueues.d7Performance.cirTxOctets

       64 bit unsigned wrappable counter."
   ::= {pr1645v2PortSwOutQueuesD7PerformanceEntry 167772160}

pr1645v2PortSwOutQueuesD7PerformanceEirTxOcts OBJECT-TYPE
   SYNTAX      Counter64
   MAX-ACCESS  read-only
   STATUS      current
   DESCRIPTION
      "Path: ethernet1.performance.ifOutPriorityQueues.d7Performance.eirTxOctets

       64 bit unsigned wrappable counter."
   ::= {pr1645v2PortSwOutQueuesD7PerformanceEntry 184549376}

pr1645v2PortSwOutQueuesD7PerformanceViolTxOcts OBJECT-TYPE
   SYNTAX      Counter64
   MAX-ACCESS  read-only
   STATUS      current
   DESCRIPTION
      "Path: ethernet1.performance.ifOutPriorityQueues.d7Performance.violateTxOctets

       64 bit unsigned wrappable counter."
   ::= {pr1645v2PortSwOutQueuesD7PerformanceEntry 318767104}

pr1645v2PortSwOutQueuesD7PerformanceBandwidth OBJECT-TYPE
   SYNTAX      Integer32
   MAX-ACCESS  read-only
   STATUS      current
   DESCRIPTION
      "Path: ethernet1.performance.ifOutPriorityQueues.d7Performance.bandwidth

       unit name = bps
       formula = 8 * ; 8 /"
   ::= {pr1645v2PortSwOutQueuesD7PerformanceEntry 268435456}


pr1645v2PortSwOutBandwidth OBJECT IDENTIFIER ::= {pr1645v2PortSw 182}

pr1645v2PortSwOutBandwidthSSC OBJECT IDENTIFIER ::= {pr1645v2PortSwOutBandwidth 1}

pr1645v2PortSwOutBandwidthEntry OBJECT IDENTIFIER ::= {pr1645v2PortSwOutBandwidthSSC 1}

pr1645v2PortSwOutBandwidth15sec OBJECT-TYPE
   SYNTAX      Integer32
   MAX-ACCESS  read-only
   STATUS      current
   DESCRIPTION
      "Path: ethernet1.performance.ifOutBandwidth.15sec

       unit name = bps
       formula = 8 * ; 8 /"
   ::= {pr1645v2PortSwOutBandwidthEntry 83886080}

pr1645v2PortSwOutBandwidth30sec OBJECT-TYPE
   SYNTAX      Integer32
   MAX-ACCESS  read-only
   STATUS      current
   DESCRIPTION
      "Path: ethernet1.performance.ifOutBandwidth.30sec

       unit name = bps
       formula = 8 * ; 8 /"
   ::= {pr1645v2PortSwOutBandwidthEntry 167772160}

pr1645v2PortSwOutBandwidth1min OBJECT-TYPE
   SYNTAX      Integer32
   MAX-ACCESS  read-only
   STATUS      current
   DESCRIPTION
      "Path: ethernet1.performance.ifOutBandwidth.1min

       unit name = bps
       formula = 8 * ; 8 /"
   ::= {pr1645v2PortSwOutBandwidthEntry 335544320}

pr1645v2PortSwOutBandwidth2min OBJECT-TYPE
   SYNTAX      Integer32
   MAX-ACCESS  read-only
   STATUS      current
   DESCRIPTION
      "Path: ethernet1.performance.ifOutBandwidth.2min

       unit name = bps
       formula = 8 * ; 8 /"
   ::= {pr1645v2PortSwOutBandwidthEntry 671088640}

pr1645v2PortSwOutBandwidth5min OBJECT-TYPE
   SYNTAX      Integer32
   MAX-ACCESS  read-only
   STATUS      current
   DESCRIPTION
      "Path: ethernet1.performance.ifOutBandwidth.5min

       unit name = bps
       formula = 8 * ; 8 /"
   ::= {pr1645v2PortSwOutBandwidthEntry 1677721600}


pr1645v2PortSwInP OBJECT IDENTIFIER ::= {pr1645v2PortSw 307}

pr1645v2PortSwInPSSCTable OBJECT-TYPE
   SYNTAX      SEQUENCE OF Pr1645v2PortSwInPEntry
   MAX-ACCESS  not-accessible
   STATUS      current
   DESCRIPTION
      "h2IfInPerformance"
   ::= {pr1645v2PortSwInP 1}

pr1645v2PortSwInPEntry OBJECT-TYPE
   SYNTAX      Pr1645v2PortSwInPEntry
   MAX-ACCESS  not-accessible
   STATUS      current
   DESCRIPTION
      ""
   INDEX      { pr1645v2PortSwInPTableIx }
   ::= {pr1645v2PortSwInPSSCTable 1}

Pr1645v2PortSwInPEntry ::=
   SEQUENCE
      {
      pr1645v2PortSwInPTableIx
         TableIndex,
      pr1645v2PortSwInPSysUpTime
         TimeTicks,
      pr1645v2PortSwInPIfUpTime
         TimeTicks,
      pr1645v2PortSwInPIfStatChanges
         Counter32,
      pr1645v2PortSwInPIfInOctets
         Counter64,
      pr1645v2PortSwInPIfInUCPkts
         Counter64,
      pr1645v2PortSwInPIfInNUCPkts
         Counter64,
      pr1645v2PortSwInPIfInBCPkts
         Counter64,
      pr1645v2PortSwInPIfInMCPkts
         Counter64,
      pr1645v2PortSwInPIfInDiscards
         Counter64,
      pr1645v2PortSwInPIfInErrors
         Counter64,
      pr1645v2PortSwInPIfInUnkwn
         Counter64,
      pr1645v2PortSwInPInDropEx
         Counter64,
      pr1645v2PortSwInPInDropNoMac
         Counter64,
      pr1645v2PortSwInPInDropNUCast
         Counter64,
      pr1645v2PortSwInPInDropFilter
         Counter64,
      pr1645v2PortSwInPIfInBandwidth
         Integer32,
      pr1645v2PortSwInPIfOutOctets
         Counter64,
      pr1645v2PortSwInPIfOutUCPkts
         Counter64,
      pr1645v2PortSwInPIfOutNUCPkts
         Counter64,
      pr1645v2PortSwInPIfOutBCPkts
         Counter64,
      pr1645v2PortSwInPIfOutMCPkts
         Counter64,
      pr1645v2PortSwInPIfOutDiscards
         Counter64,
      pr1645v2PortSwInPIfOutErrors
         Counter64,
      pr1645v2PortSwInPOutDropEx
         Counter64,
      pr1645v2PortSwInPOutDropNoArp
         Counter64,
      pr1645v2PortSwInPOutDropFilter
         Counter64,
      pr1645v2PortSwInPIfOutBandwidth
         Integer32,
      pr1645v2PortSwInPIfErrSec
         Counter32
      }

pr1645v2PortSwInPTableIx OBJECT-TYPE
   SYNTAX      TableIndex
   MAX-ACCESS  not-accessible
   STATUS      current
   DESCRIPTION
      ""
   ::= {pr1645v2PortSwInPEntry 11}

pr1645v2PortSwInPSysUpTime OBJECT-TYPE
   SYNTAX      TimeTicks
   MAX-ACCESS  read-only
   STATUS      current
   DESCRIPTION
      "Path: ethernet1.performance.h2Performance.sysUpTime

       Time in centi-second."
   ::= {pr1645v2PortSwInPEntry 16777216}

pr1645v2PortSwInPIfUpTime OBJECT-TYPE
   SYNTAX      TimeTicks
   MAX-ACCESS  read-only
   STATUS      current
   DESCRIPTION
      "Path: ethernet1.performance.h2Performance.ifUpTime

       Time in centi-second."
   ::= {pr1645v2PortSwInPEntry 33554432}

pr1645v2PortSwInPIfStatChanges OBJECT-TYPE
   SYNTAX      Counter32
   MAX-ACCESS  read-only
   STATUS      current
   DESCRIPTION
      "Path: ethernet1.performance.h2Performance.ifStatusChanges

       32 bit unsigned wrappable counter."
   ::= {pr1645v2PortSwInPEntry 50331648}

pr1645v2PortSwInPIfInOctets OBJECT-TYPE
   SYNTAX      Counter64
   MAX-ACCESS  read-only
   STATUS      current
   DESCRIPTION
      "Path: ethernet1.performance.h2Performance.ifInOctets

       64 bit unsigned wrappable counter."
   ::= {pr1645v2PortSwInPEntry 67108864}

pr1645v2PortSwInPIfInUCPkts OBJECT-TYPE
   SYNTAX      Counter64
   MAX-ACCESS  read-only
   STATUS      current
   DESCRIPTION
      "Path: ethernet1.performance.h2Performance.ifInUcastPkts

       64 bit unsigned wrappable counter."
   ::= {pr1645v2PortSwInPEntry 83886080}

pr1645v2PortSwInPIfInNUCPkts OBJECT-TYPE
   SYNTAX      Counter64
   MAX-ACCESS  read-only
   STATUS      current
   DESCRIPTION
      "Path: ethernet1.performance.h2Performance.ifInNUcastPkts

       64 bit unsigned wrappable counter."
   ::= {pr1645v2PortSwInPEntry 100663296}

pr1645v2PortSwInPIfInBCPkts OBJECT-TYPE
   SYNTAX      Counter64
   MAX-ACCESS  read-only
   STATUS      current
   DESCRIPTION
      "Path: ethernet1.performance.h2Performance.ifInBcastPkts

       64 bit unsigned wrappable counter."
   ::= {pr1645v2PortSwInPEntry 419430400}

pr1645v2PortSwInPIfInMCPkts OBJECT-TYPE
   SYNTAX      Counter64
   MAX-ACCESS  read-only
   STATUS      current
   DESCRIPTION
      "Path: ethernet1.performance.h2Performance.ifInMcastPkts

       64 bit unsigned wrappable counter."
   ::= {pr1645v2PortSwInPEntry 436207616}

pr1645v2PortSwInPIfInDiscards OBJECT-TYPE
   SYNTAX      Counter64
   MAX-ACCESS  read-only
   STATUS      current
   DESCRIPTION
      "Path: ethernet1.performance.h2Performance.ifInDiscards

       64 bit unsigned wrappable counter."
   ::= {pr1645v2PortSwInPEntry 117440512}

pr1645v2PortSwInPIfInErrors OBJECT-TYPE
   SYNTAX      Counter64
   MAX-ACCESS  read-only
   STATUS      current
   DESCRIPTION
      "Path: ethernet1.performance.h2Performance.ifInErrors

       64 bit unsigned wrappable counter."
   ::= {pr1645v2PortSwInPEntry 134217728}

pr1645v2PortSwInPIfInUnkwn OBJECT-TYPE
   SYNTAX      Counter64
   MAX-ACCESS  read-only
   STATUS      current
   DESCRIPTION
      "Path: ethernet1.performance.h2Performance.ifInUnknownProtos

       64 bit unsigned wrappable counter."
   ::= {pr1645v2PortSwInPEntry 150994944}

pr1645v2PortSwInPInDropEx OBJECT-TYPE
   SYNTAX      Counter64
   MAX-ACCESS  read-only
   STATUS      current
   DESCRIPTION
      "Path: ethernet1.performance.h2Performance.ifInDropLevelExceeded

       64 bit unsigned wrappable counter."
   ::= {pr1645v2PortSwInPEntry 335544320}

pr1645v2PortSwInPInDropNoMac OBJECT-TYPE
   SYNTAX      Counter64
   MAX-ACCESS  read-only
   STATUS      current
   DESCRIPTION
      "Path: ethernet1.performance.h2Performance.fInDiscardsNoMacFit

       64 bit unsigned wrappable counter."
   ::= {pr1645v2PortSwInPEntry 301989888}

pr1645v2PortSwInPInDropNUCast OBJECT-TYPE
   SYNTAX      Counter64
   MAX-ACCESS  read-only
   STATUS      current
   DESCRIPTION
      "Path: ethernet1.performance.h2Performance.fInDiscardsNUCast

       64 bit unsigned wrappable counter."
   ::= {pr1645v2PortSwInPEntry 318767104}

pr1645v2PortSwInPInDropFilter OBJECT-TYPE
   SYNTAX      Counter64
   MAX-ACCESS  read-only
   STATUS      current
   DESCRIPTION
      "Path: ethernet1.performance.h2Performance.fInDiscardsFilter

       64 bit unsigned wrappable counter."
   ::= {pr1645v2PortSwInPEntry 385875968}

pr1645v2PortSwInPIfInBandwidth OBJECT-TYPE
   SYNTAX      Integer32
   MAX-ACCESS  read-only
   STATUS      current
   DESCRIPTION
      "Path: ethernet1.performance.h2Performance.ifInBandwidth

       unit name = bps
       formula = 8 * ; 8 /"
   ::= {pr1645v2PortSwInPEntry 268435456}

pr1645v2PortSwInPIfOutOctets OBJECT-TYPE
   SYNTAX      Counter64
   MAX-ACCESS  read-only
   STATUS      current
   DESCRIPTION
      "Path: ethernet1.performance.h2Performance.ifOutOctets

       64 bit unsigned wrappable counter."
   ::= {pr1645v2PortSwInPEntry 167772160}

pr1645v2PortSwInPIfOutUCPkts OBJECT-TYPE
   SYNTAX      Counter64
   MAX-ACCESS  read-only
   STATUS      current
   DESCRIPTION
      "Path: ethernet1.performance.h2Performance.ifOutUcastPkts

       64 bit unsigned wrappable counter."
   ::= {pr1645v2PortSwInPEntry 184549376}

pr1645v2PortSwInPIfOutNUCPkts OBJECT-TYPE
   SYNTAX      Counter64
   MAX-ACCESS  read-only
   STATUS      current
   DESCRIPTION
      "Path: ethernet1.performance.h2Performance.ifOutNUcastPkts

       64 bit unsigned wrappable counter."
   ::= {pr1645v2PortSwInPEntry 201326592}

pr1645v2PortSwInPIfOutBCPkts OBJECT-TYPE
   SYNTAX      Counter64
   MAX-ACCESS  read-only
   STATUS      current
   DESCRIPTION
      "Path: ethernet1.performance.h2Performance.ifOutBcastPkts

       64 bit unsigned wrappable counter."
   ::= {pr1645v2PortSwInPEntry 452984832}

pr1645v2PortSwInPIfOutMCPkts OBJECT-TYPE
   SYNTAX      Counter64
   MAX-ACCESS  read-only
   STATUS      current
   DESCRIPTION
      "Path: ethernet1.performance.h2Performance.ifOutMcastPkts

       64 bit unsigned wrappable counter."
   ::= {pr1645v2PortSwInPEntry 469762048}

pr1645v2PortSwInPIfOutDiscards OBJECT-TYPE
   SYNTAX      Counter64
   MAX-ACCESS  read-only
   STATUS      current
   DESCRIPTION
      "Path: ethernet1.performance.h2Performance.ifOutDiscards

       64 bit unsigned wrappable counter."
   ::= {pr1645v2PortSwInPEntry 218103808}

pr1645v2PortSwInPIfOutErrors OBJECT-TYPE
   SYNTAX      Counter64
   MAX-ACCESS  read-only
   STATUS      current
   DESCRIPTION
      "Path: ethernet1.performance.h2Performance.ifOutErrors

       64 bit unsigned wrappable counter."
   ::= {pr1645v2PortSwInPEntry 234881024}

pr1645v2PortSwInPOutDropEx OBJECT-TYPE
   SYNTAX      Counter64
   MAX-ACCESS  read-only
   STATUS      current
   DESCRIPTION
      "Path: ethernet1.performance.h2Performance.ifOutDropLevelExceeded

       64 bit unsigned wrappable counter."
   ::= {pr1645v2PortSwInPEntry 352321536}

pr1645v2PortSwInPOutDropNoArp OBJECT-TYPE
   SYNTAX      Counter64
   MAX-ACCESS  read-only
   STATUS      current
   DESCRIPTION
      "Path: ethernet1.performance.h2Performance.ifOutDiscardsNoArp

       64 bit unsigned wrappable counter."
   ::= {pr1645v2PortSwInPEntry 369098752}

pr1645v2PortSwInPOutDropFilter OBJECT-TYPE
   SYNTAX      Counter64
   MAX-ACCESS  read-only
   STATUS      current
   DESCRIPTION
      "Path: ethernet1.performance.h2Performance.ifOutDiscardsFilter

       64 bit unsigned wrappable counter."
   ::= {pr1645v2PortSwInPEntry 402653184}

pr1645v2PortSwInPIfOutBandwidth OBJECT-TYPE
   SYNTAX      Integer32
   MAX-ACCESS  read-only
   STATUS      current
   DESCRIPTION
      "Path: ethernet1.performance.h2Performance.ifOutBandwidth

       unit name = bps
       formula = 8 * ; 8 /"
   ::= {pr1645v2PortSwInPEntry 285212672}

pr1645v2PortSwInPIfErrSec OBJECT-TYPE
   SYNTAX      Counter32
   MAX-ACCESS  read-only
   STATUS      current
   DESCRIPTION
      "Path: ethernet1.performance.h2Performance.ifErrSec

       32 bit unsigned wrappable counter."
   ::= {pr1645v2PortSwInPEntry 251658240}


pr1645v2PortSwH24InP OBJECT IDENTIFIER ::= {pr1645v2PortSw 308}

pr1645v2PortSwH24InPSSCTable OBJECT-TYPE
   SYNTAX      SEQUENCE OF Pr1645v2PortSwH24InPEntry
   MAX-ACCESS  not-accessible
   STATUS      current
   DESCRIPTION
      "h24IfInPerformance"
   ::= {pr1645v2PortSwH24InP 1}

pr1645v2PortSwH24InPEntry OBJECT-TYPE
   SYNTAX      Pr1645v2PortSwH24InPEntry
   MAX-ACCESS  not-accessible
   STATUS      current
   DESCRIPTION
      ""
   INDEX      { pr1645v2PortSwH24InPTableIx }
   ::= {pr1645v2PortSwH24InPSSCTable 1}

Pr1645v2PortSwH24InPEntry ::=
   SEQUENCE
      {
      pr1645v2PortSwH24InPTableIx
         TableIndex,
      pr1645v2PortSwH24InPSysUpTime
         TimeTicks,
      pr1645v2PortSwH24InPIfUpTime
         TimeTicks,
      pr1645v2PortSwH24InPIfStatChanges
         Counter32,
      pr1645v2PortSwH24InPIfInOctets
         Counter64,
      pr1645v2PortSwH24InPIfInUCPkts
         Counter64,
      pr1645v2PortSwH24InPIfInNUCPkts
         Counter64,
      pr1645v2PortSwH24InPIfInBCPkts
         Counter64,
      pr1645v2PortSwH24InPIfInMCPkts
         Counter64,
      pr1645v2PortSwH24InPIfInDiscards
         Counter64,
      pr1645v2PortSwH24InPIfInErrors
         Counter64,
      pr1645v2PortSwH24InPIfInUnkwn
         Counter64,
      pr1645v2PortSwH24InPInDropEx
         Counter64,
      pr1645v2PortSwH24InPInDropNoMac
         Counter64,
      pr1645v2PortSwH24InPInDropNUCast
         Counter64,
      pr1645v2PortSwH24InPInDropFilter
         Counter64,
      pr1645v2PortSwH24InPIfInBandwidth
         Integer32,
      pr1645v2PortSwH24InPIfOutOctets
         Counter64,
      pr1645v2PortSwH24InPIfOutUCPkts
         Counter64,
      pr1645v2PortSwH24InPIfOutNUCPkts
         Counter64,
      pr1645v2PortSwH24InPIfOutBCPkts
         Counter64,
      pr1645v2PortSwH24InPIfOutMCPkts
         Counter64,
      pr1645v2PortSwH24InPIfOutDiscards
         Counter64,
      pr1645v2PortSwH24InPIfOutErrors
         Counter64,
      pr1645v2PortSwH24InPOutDropEx
         Counter64,
      pr1645v2PortSwH24InPOutDropNoArp
         Counter64,
      pr1645v2PortSwH24InPOutDropFilter
         Counter64,
      pr1645v2PortSwH24InPIfOutBandwidth
         Integer32,
      pr1645v2PortSwH24InPIfErrSec
         Counter32
      }

pr1645v2PortSwH24InPTableIx OBJECT-TYPE
   SYNTAX      TableIndex
   MAX-ACCESS  not-accessible
   STATUS      current
   DESCRIPTION
      ""
   ::= {pr1645v2PortSwH24InPEntry 11}

pr1645v2PortSwH24InPSysUpTime OBJECT-TYPE
   SYNTAX      TimeTicks
   MAX-ACCESS  read-only
   STATUS      current
   DESCRIPTION
      "Path: ethernet1.performance.h24Performance.sysUpTime

       Time in centi-second."
   ::= {pr1645v2PortSwH24InPEntry 16777216}

pr1645v2PortSwH24InPIfUpTime OBJECT-TYPE
   SYNTAX      TimeTicks
   MAX-ACCESS  read-only
   STATUS      current
   DESCRIPTION
      "Path: ethernet1.performance.h24Performance.ifUpTime

       Time in centi-second."
   ::= {pr1645v2PortSwH24InPEntry 33554432}

pr1645v2PortSwH24InPIfStatChanges OBJECT-TYPE
   SYNTAX      Counter32
   MAX-ACCESS  read-only
   STATUS      current
   DESCRIPTION
      "Path: ethernet1.performance.h24Performance.ifStatusChanges

       32 bit unsigned wrappable counter."
   ::= {pr1645v2PortSwH24InPEntry 50331648}

pr1645v2PortSwH24InPIfInOctets OBJECT-TYPE
   SYNTAX      Counter64
   MAX-ACCESS  read-only
   STATUS      current
   DESCRIPTION
      "Path: ethernet1.performance.h24Performance.ifInOctets

       64 bit unsigned wrappable counter."
   ::= {pr1645v2PortSwH24InPEntry 67108864}

pr1645v2PortSwH24InPIfInUCPkts OBJECT-TYPE
   SYNTAX      Counter64
   MAX-ACCESS  read-only
   STATUS      current
   DESCRIPTION
      "Path: ethernet1.performance.h24Performance.ifInUcastPkts

       64 bit unsigned wrappable counter."
   ::= {pr1645v2PortSwH24InPEntry 83886080}

pr1645v2PortSwH24InPIfInNUCPkts OBJECT-TYPE
   SYNTAX      Counter64
   MAX-ACCESS  read-only
   STATUS      current
   DESCRIPTION
      "Path: ethernet1.performance.h24Performance.ifInNUcastPkts

       64 bit unsigned wrappable counter."
   ::= {pr1645v2PortSwH24InPEntry 100663296}

pr1645v2PortSwH24InPIfInBCPkts OBJECT-TYPE
   SYNTAX      Counter64
   MAX-ACCESS  read-only
   STATUS      current
   DESCRIPTION
      "Path: ethernet1.performance.h24Performance.ifInBcastPkts

       64 bit unsigned wrappable counter."
   ::= {pr1645v2PortSwH24InPEntry 419430400}

pr1645v2PortSwH24InPIfInMCPkts OBJECT-TYPE
   SYNTAX      Counter64
   MAX-ACCESS  read-only
   STATUS      current
   DESCRIPTION
      "Path: ethernet1.performance.h24Performance.ifInMcastPkts

       64 bit unsigned wrappable counter."
   ::= {pr1645v2PortSwH24InPEntry 436207616}

pr1645v2PortSwH24InPIfInDiscards OBJECT-TYPE
   SYNTAX      Counter64
   MAX-ACCESS  read-only
   STATUS      current
   DESCRIPTION
      "Path: ethernet1.performance.h24Performance.ifInDiscards

       64 bit unsigned wrappable counter."
   ::= {pr1645v2PortSwH24InPEntry 117440512}

pr1645v2PortSwH24InPIfInErrors OBJECT-TYPE
   SYNTAX      Counter64
   MAX-ACCESS  read-only
   STATUS      current
   DESCRIPTION
      "Path: ethernet1.performance.h24Performance.ifInErrors

       64 bit unsigned wrappable counter."
   ::= {pr1645v2PortSwH24InPEntry 134217728}

pr1645v2PortSwH24InPIfInUnkwn OBJECT-TYPE
   SYNTAX      Counter64
   MAX-ACCESS  read-only
   STATUS      current
   DESCRIPTION
      "Path: ethernet1.performance.h24Performance.ifInUnknownProtos

       64 bit unsigned wrappable counter."
   ::= {pr1645v2PortSwH24InPEntry 150994944}

pr1645v2PortSwH24InPInDropEx OBJECT-TYPE
   SYNTAX      Counter64
   MAX-ACCESS  read-only
   STATUS      current
   DESCRIPTION
      "Path: ethernet1.performance.h24Performance.ifInDropLevelExceeded

       64 bit unsigned wrappable counter."
   ::= {pr1645v2PortSwH24InPEntry 335544320}

pr1645v2PortSwH24InPInDropNoMac OBJECT-TYPE
   SYNTAX      Counter64
   MAX-ACCESS  read-only
   STATUS      current
   DESCRIPTION
      "Path: ethernet1.performance.h24Performance.fInDiscardsNoMacFit

       64 bit unsigned wrappable counter."
   ::= {pr1645v2PortSwH24InPEntry 301989888}

pr1645v2PortSwH24InPInDropNUCast OBJECT-TYPE
   SYNTAX      Counter64
   MAX-ACCESS  read-only
   STATUS      current
   DESCRIPTION
      "Path: ethernet1.performance.h24Performance.fInDiscardsNUCast

       64 bit unsigned wrappable counter."
   ::= {pr1645v2PortSwH24InPEntry 318767104}

pr1645v2PortSwH24InPInDropFilter OBJECT-TYPE
   SYNTAX      Counter64
   MAX-ACCESS  read-only
   STATUS      current
   DESCRIPTION
      "Path: ethernet1.performance.h24Performance.fInDiscardsFilter

       64 bit unsigned wrappable counter."
   ::= {pr1645v2PortSwH24InPEntry 385875968}

pr1645v2PortSwH24InPIfInBandwidth OBJECT-TYPE
   SYNTAX      Integer32
   MAX-ACCESS  read-only
   STATUS      current
   DESCRIPTION
      "Path: ethernet1.performance.h24Performance.ifInBandwidth

       unit name = bps
       formula = 8 * ; 8 /"
   ::= {pr1645v2PortSwH24InPEntry 268435456}

pr1645v2PortSwH24InPIfOutOctets OBJECT-TYPE
   SYNTAX      Counter64
   MAX-ACCESS  read-only
   STATUS      current
   DESCRIPTION
      "Path: ethernet1.performance.h24Performance.ifOutOctets

       64 bit unsigned wrappable counter."
   ::= {pr1645v2PortSwH24InPEntry 167772160}

pr1645v2PortSwH24InPIfOutUCPkts OBJECT-TYPE
   SYNTAX      Counter64
   MAX-ACCESS  read-only
   STATUS      current
   DESCRIPTION
      "Path: ethernet1.performance.h24Performance.ifOutUcastPkts

       64 bit unsigned wrappable counter."
   ::= {pr1645v2PortSwH24InPEntry 184549376}

pr1645v2PortSwH24InPIfOutNUCPkts OBJECT-TYPE
   SYNTAX      Counter64
   MAX-ACCESS  read-only
   STATUS      current
   DESCRIPTION
      "Path: ethernet1.performance.h24Performance.ifOutNUcastPkts

       64 bit unsigned wrappable counter."
   ::= {pr1645v2PortSwH24InPEntry 201326592}

pr1645v2PortSwH24InPIfOutBCPkts OBJECT-TYPE
   SYNTAX      Counter64
   MAX-ACCESS  read-only
   STATUS      current
   DESCRIPTION
      "Path: ethernet1.performance.h24Performance.ifOutBcastPkts

       64 bit unsigned wrappable counter."
   ::= {pr1645v2PortSwH24InPEntry 452984832}

pr1645v2PortSwH24InPIfOutMCPkts OBJECT-TYPE
   SYNTAX      Counter64
   MAX-ACCESS  read-only
   STATUS      current
   DESCRIPTION
      "Path: ethernet1.performance.h24Performance.ifOutMcastPkts

       64 bit unsigned wrappable counter."
   ::= {pr1645v2PortSwH24InPEntry 469762048}

pr1645v2PortSwH24InPIfOutDiscards OBJECT-TYPE
   SYNTAX      Counter64
   MAX-ACCESS  read-only
   STATUS      current
   DESCRIPTION
      "Path: ethernet1.performance.h24Performance.ifOutDiscards

       64 bit unsigned wrappable counter."
   ::= {pr1645v2PortSwH24InPEntry 218103808}

pr1645v2PortSwH24InPIfOutErrors OBJECT-TYPE
   SYNTAX      Counter64
   MAX-ACCESS  read-only
   STATUS      current
   DESCRIPTION
      "Path: ethernet1.performance.h24Performance.ifOutErrors

       64 bit unsigned wrappable counter."
   ::= {pr1645v2PortSwH24InPEntry 234881024}

pr1645v2PortSwH24InPOutDropEx OBJECT-TYPE
   SYNTAX      Counter64
   MAX-ACCESS  read-only
   STATUS      current
   DESCRIPTION
      "Path: ethernet1.performance.h24Performance.ifOutDropLevelExceeded

       64 bit unsigned wrappable counter."
   ::= {pr1645v2PortSwH24InPEntry 352321536}

pr1645v2PortSwH24InPOutDropNoArp OBJECT-TYPE
   SYNTAX      Counter64
   MAX-ACCESS  read-only
   STATUS      current
   DESCRIPTION
      "Path: ethernet1.performance.h24Performance.ifOutDiscardsNoArp

       64 bit unsigned wrappable counter."
   ::= {pr1645v2PortSwH24InPEntry 369098752}

pr1645v2PortSwH24InPOutDropFilter OBJECT-TYPE
   SYNTAX      Counter64
   MAX-ACCESS  read-only
   STATUS      current
   DESCRIPTION
      "Path: ethernet1.performance.h24Performance.ifOutDiscardsFilter

       64 bit unsigned wrappable counter."
   ::= {pr1645v2PortSwH24InPEntry 402653184}

pr1645v2PortSwH24InPIfOutBandwidth OBJECT-TYPE
   SYNTAX      Integer32
   MAX-ACCESS  read-only
   STATUS      current
   DESCRIPTION
      "Path: ethernet1.performance.h24Performance.ifOutBandwidth

       unit name = bps
       formula = 8 * ; 8 /"
   ::= {pr1645v2PortSwH24InPEntry 285212672}

pr1645v2PortSwH24InPIfErrSec OBJECT-TYPE
   SYNTAX      Counter32
   MAX-ACCESS  read-only
   STATUS      current
   DESCRIPTION
      "Path: ethernet1.performance.h24Performance.ifErrSec

       32 bit unsigned wrappable counter."
   ::= {pr1645v2PortSwH24InPEntry 251658240}


pr1645v2PortSwD7InP OBJECT IDENTIFIER ::= {pr1645v2PortSw 309}

pr1645v2PortSwD7InPSSCTable OBJECT-TYPE
   SYNTAX      SEQUENCE OF Pr1645v2PortSwD7InPEntry
   MAX-ACCESS  not-accessible
   STATUS      current
   DESCRIPTION
      "d7IfInPerformance"
   ::= {pr1645v2PortSwD7InP 1}

pr1645v2PortSwD7InPEntry OBJECT-TYPE
   SYNTAX      Pr1645v2PortSwD7InPEntry
   MAX-ACCESS  not-accessible
   STATUS      current
   DESCRIPTION
      ""
   INDEX      { pr1645v2PortSwD7InPTableIx }
   ::= {pr1645v2PortSwD7InPSSCTable 1}

Pr1645v2PortSwD7InPEntry ::=
   SEQUENCE
      {
      pr1645v2PortSwD7InPTableIx
         TableIndex,
      pr1645v2PortSwD7InPSysUpTime
         TimeTicks,
      pr1645v2PortSwD7InPIfUpTime
         TimeTicks,
      pr1645v2PortSwD7InPIfStatChanges
         Counter32,
      pr1645v2PortSwD7InPIfInOctets
         Counter64,
      pr1645v2PortSwD7InPIfInUCPkts
         Counter64,
      pr1645v2PortSwD7InPIfInNUCPkts
         Counter64,
      pr1645v2PortSwD7InPIfInBCPkts
         Counter64,
      pr1645v2PortSwD7InPIfInMCPkts
         Counter64,
      pr1645v2PortSwD7InPIfInDiscards
         Counter64,
      pr1645v2PortSwD7InPIfInErrors
         Counter64,
      pr1645v2PortSwD7InPIfInUnkwn
         Counter64,
      pr1645v2PortSwD7InPInDropEx
         Counter64,
      pr1645v2PortSwD7InPInDropNoMac
         Counter64,
      pr1645v2PortSwD7InPInDropNUCast
         Counter64,
      pr1645v2PortSwD7InPInDropFilter
         Counter64,
      pr1645v2PortSwD7InPIfInBandwidth
         Integer32,
      pr1645v2PortSwD7InPIfOutOctets
         Counter64,
      pr1645v2PortSwD7InPIfOutUCPkts
         Counter64,
      pr1645v2PortSwD7InPIfOutNUCPkts
         Counter64,
      pr1645v2PortSwD7InPIfOutBCPkts
         Counter64,
      pr1645v2PortSwD7InPIfOutMCPkts
         Counter64,
      pr1645v2PortSwD7InPIfOutDiscards
         Counter64,
      pr1645v2PortSwD7InPIfOutErrors
         Counter64,
      pr1645v2PortSwD7InPOutDropEx
         Counter64,
      pr1645v2PortSwD7InPOutDropNoArp
         Counter64,
      pr1645v2PortSwD7InPOutDropFilter
         Counter64,
      pr1645v2PortSwD7InPIfOutBandwidth
         Integer32,
      pr1645v2PortSwD7InPIfErrSec
         Counter32
      }

pr1645v2PortSwD7InPTableIx OBJECT-TYPE
   SYNTAX      TableIndex
   MAX-ACCESS  not-accessible
   STATUS      current
   DESCRIPTION
      ""
   ::= {pr1645v2PortSwD7InPEntry 11}

pr1645v2PortSwD7InPSysUpTime OBJECT-TYPE
   SYNTAX      TimeTicks
   MAX-ACCESS  read-only
   STATUS      current
   DESCRIPTION
      "Path: ethernet1.performance.d7Performance.sysUpTime

       Time in centi-second."
   ::= {pr1645v2PortSwD7InPEntry 16777216}

pr1645v2PortSwD7InPIfUpTime OBJECT-TYPE
   SYNTAX      TimeTicks
   MAX-ACCESS  read-only
   STATUS      current
   DESCRIPTION
      "Path: ethernet1.performance.d7Performance.ifUpTime

       Time in centi-second."
   ::= {pr1645v2PortSwD7InPEntry 33554432}

pr1645v2PortSwD7InPIfStatChanges OBJECT-TYPE
   SYNTAX      Counter32
   MAX-ACCESS  read-only
   STATUS      current
   DESCRIPTION
      "Path: ethernet1.performance.d7Performance.ifStatusChanges

       32 bit unsigned wrappable counter."
   ::= {pr1645v2PortSwD7InPEntry 50331648}

pr1645v2PortSwD7InPIfInOctets OBJECT-TYPE
   SYNTAX      Counter64
   MAX-ACCESS  read-only
   STATUS      current
   DESCRIPTION
      "Path: ethernet1.performance.d7Performance.ifInOctets

       64 bit unsigned wrappable counter."
   ::= {pr1645v2PortSwD7InPEntry 67108864}

pr1645v2PortSwD7InPIfInUCPkts OBJECT-TYPE
   SYNTAX      Counter64
   MAX-ACCESS  read-only
   STATUS      current
   DESCRIPTION
      "Path: ethernet1.performance.d7Performance.ifInUcastPkts

       64 bit unsigned wrappable counter."
   ::= {pr1645v2PortSwD7InPEntry 83886080}

pr1645v2PortSwD7InPIfInNUCPkts OBJECT-TYPE
   SYNTAX      Counter64
   MAX-ACCESS  read-only
   STATUS      current
   DESCRIPTION
      "Path: ethernet1.performance.d7Performance.ifInNUcastPkts

       64 bit unsigned wrappable counter."
   ::= {pr1645v2PortSwD7InPEntry 100663296}

pr1645v2PortSwD7InPIfInBCPkts OBJECT-TYPE
   SYNTAX      Counter64
   MAX-ACCESS  read-only
   STATUS      current
   DESCRIPTION
      "Path: ethernet1.performance.d7Performance.ifInBcastPkts

       64 bit unsigned wrappable counter."
   ::= {pr1645v2PortSwD7InPEntry 419430400}

pr1645v2PortSwD7InPIfInMCPkts OBJECT-TYPE
   SYNTAX      Counter64
   MAX-ACCESS  read-only
   STATUS      current
   DESCRIPTION
      "Path: ethernet1.performance.d7Performance.ifInMcastPkts

       64 bit unsigned wrappable counter."
   ::= {pr1645v2PortSwD7InPEntry 436207616}

pr1645v2PortSwD7InPIfInDiscards OBJECT-TYPE
   SYNTAX      Counter64
   MAX-ACCESS  read-only
   STATUS      current
   DESCRIPTION
      "Path: ethernet1.performance.d7Performance.ifInDiscards

       64 bit unsigned wrappable counter."
   ::= {pr1645v2PortSwD7InPEntry 117440512}

pr1645v2PortSwD7InPIfInErrors OBJECT-TYPE
   SYNTAX      Counter64
   MAX-ACCESS  read-only
   STATUS      current
   DESCRIPTION
      "Path: ethernet1.performance.d7Performance.ifInErrors

       64 bit unsigned wrappable counter."
   ::= {pr1645v2PortSwD7InPEntry 134217728}

pr1645v2PortSwD7InPIfInUnkwn OBJECT-TYPE
   SYNTAX      Counter64
   MAX-ACCESS  read-only
   STATUS      current
   DESCRIPTION
      "Path: ethernet1.performance.d7Performance.ifInUnknownProtos

       64 bit unsigned wrappable counter."
   ::= {pr1645v2PortSwD7InPEntry 150994944}

pr1645v2PortSwD7InPInDropEx OBJECT-TYPE
   SYNTAX      Counter64
   MAX-ACCESS  read-only
   STATUS      current
   DESCRIPTION
      "Path: ethernet1.performance.d7Performance.ifInDropLevelExceeded

       64 bit unsigned wrappable counter."
   ::= {pr1645v2PortSwD7InPEntry 335544320}

pr1645v2PortSwD7InPInDropNoMac OBJECT-TYPE
   SYNTAX      Counter64
   MAX-ACCESS  read-only
   STATUS      current
   DESCRIPTION
      "Path: ethernet1.performance.d7Performance.fInDiscardsNoMacFit

       64 bit unsigned wrappable counter."
   ::= {pr1645v2PortSwD7InPEntry 301989888}

pr1645v2PortSwD7InPInDropNUCast OBJECT-TYPE
   SYNTAX      Counter64
   MAX-ACCESS  read-only
   STATUS      current
   DESCRIPTION
      "Path: ethernet1.performance.d7Performance.fInDiscardsNUCast

       64 bit unsigned wrappable counter."
   ::= {pr1645v2PortSwD7InPEntry 318767104}

pr1645v2PortSwD7InPInDropFilter OBJECT-TYPE
   SYNTAX      Counter64
   MAX-ACCESS  read-only
   STATUS      current
   DESCRIPTION
      "Path: ethernet1.performance.d7Performance.fInDiscardsFilter

       64 bit unsigned wrappable counter."
   ::= {pr1645v2PortSwD7InPEntry 385875968}

pr1645v2PortSwD7InPIfInBandwidth OBJECT-TYPE
   SYNTAX      Integer32
   MAX-ACCESS  read-only
   STATUS      current
   DESCRIPTION
      "Path: ethernet1.performance.d7Performance.ifInBandwidth

       unit name = bps
       formula = 8 * ; 8 /"
   ::= {pr1645v2PortSwD7InPEntry 268435456}

pr1645v2PortSwD7InPIfOutOctets OBJECT-TYPE
   SYNTAX      Counter64
   MAX-ACCESS  read-only
   STATUS      current
   DESCRIPTION
      "Path: ethernet1.performance.d7Performance.ifOutOctets

       64 bit unsigned wrappable counter."
   ::= {pr1645v2PortSwD7InPEntry 167772160}

pr1645v2PortSwD7InPIfOutUCPkts OBJECT-TYPE
   SYNTAX      Counter64
   MAX-ACCESS  read-only
   STATUS      current
   DESCRIPTION
      "Path: ethernet1.performance.d7Performance.ifOutUcastPkts

       64 bit unsigned wrappable counter."
   ::= {pr1645v2PortSwD7InPEntry 184549376}

pr1645v2PortSwD7InPIfOutNUCPkts OBJECT-TYPE
   SYNTAX      Counter64
   MAX-ACCESS  read-only
   STATUS      current
   DESCRIPTION
      "Path: ethernet1.performance.d7Performance.ifOutNUcastPkts

       64 bit unsigned wrappable counter."
   ::= {pr1645v2PortSwD7InPEntry 201326592}

pr1645v2PortSwD7InPIfOutBCPkts OBJECT-TYPE
   SYNTAX      Counter64
   MAX-ACCESS  read-only
   STATUS      current
   DESCRIPTION
      "Path: ethernet1.performance.d7Performance.ifOutBcastPkts

       64 bit unsigned wrappable counter."
   ::= {pr1645v2PortSwD7InPEntry 452984832}

pr1645v2PortSwD7InPIfOutMCPkts OBJECT-TYPE
   SYNTAX      Counter64
   MAX-ACCESS  read-only
   STATUS      current
   DESCRIPTION
      "Path: ethernet1.performance.d7Performance.ifOutMcastPkts

       64 bit unsigned wrappable counter."
   ::= {pr1645v2PortSwD7InPEntry 469762048}

pr1645v2PortSwD7InPIfOutDiscards OBJECT-TYPE
   SYNTAX      Counter64
   MAX-ACCESS  read-only
   STATUS      current
   DESCRIPTION
      "Path: ethernet1.performance.d7Performance.ifOutDiscards

       64 bit unsigned wrappable counter."
   ::= {pr1645v2PortSwD7InPEntry 218103808}

pr1645v2PortSwD7InPIfOutErrors OBJECT-TYPE
   SYNTAX      Counter64
   MAX-ACCESS  read-only
   STATUS      current
   DESCRIPTION
      "Path: ethernet1.performance.d7Performance.ifOutErrors

       64 bit unsigned wrappable counter."
   ::= {pr1645v2PortSwD7InPEntry 234881024}

pr1645v2PortSwD7InPOutDropEx OBJECT-TYPE
   SYNTAX      Counter64
   MAX-ACCESS  read-only
   STATUS      current
   DESCRIPTION
      "Path: ethernet1.performance.d7Performance.ifOutDropLevelExceeded

       64 bit unsigned wrappable counter."
   ::= {pr1645v2PortSwD7InPEntry 352321536}

pr1645v2PortSwD7InPOutDropNoArp OBJECT-TYPE
   SYNTAX      Counter64
   MAX-ACCESS  read-only
   STATUS      current
   DESCRIPTION
      "Path: ethernet1.performance.d7Performance.ifOutDiscardsNoArp

       64 bit unsigned wrappable counter."
   ::= {pr1645v2PortSwD7InPEntry 369098752}

pr1645v2PortSwD7InPOutDropFilter OBJECT-TYPE
   SYNTAX      Counter64
   MAX-ACCESS  read-only
   STATUS      current
   DESCRIPTION
      "Path: ethernet1.performance.d7Performance.ifOutDiscardsFilter

       64 bit unsigned wrappable counter."
   ::= {pr1645v2PortSwD7InPEntry 402653184}

pr1645v2PortSwD7InPIfOutBandwidth OBJECT-TYPE
   SYNTAX      Integer32
   MAX-ACCESS  read-only
   STATUS      current
   DESCRIPTION
      "Path: ethernet1.performance.d7Performance.ifOutBandwidth

       unit name = bps
       formula = 8 * ; 8 /"
   ::= {pr1645v2PortSwD7InPEntry 285212672}

pr1645v2PortSwD7InPIfErrSec OBJECT-TYPE
   SYNTAX      Counter32
   MAX-ACCESS  read-only
   STATUS      current
   DESCRIPTION
      "Path: ethernet1.performance.d7Performance.ifErrSec

       32 bit unsigned wrappable counter."
   ::= {pr1645v2PortSwD7InPEntry 251658240}


pr1645v2PortSwIfInPriorityQueues OBJECT IDENTIFIER ::= {pr1645v2PortSw 131}

pr1645v2PortSwIfInPriorityQueuesSSCTable OBJECT-TYPE
   SYNTAX      SEQUENCE OF Pr1645v2PortSwIfInPriorityQueuesEntry
   MAX-ACCESS  not-accessible
   STATUS      current
   DESCRIPTION
      "Queue Lengths"
   ::= {pr1645v2PortSwIfInPriorityQueues 1}

pr1645v2PortSwIfInPriorityQueuesEntry OBJECT-TYPE
   SYNTAX      Pr1645v2PortSwIfInPriorityQueuesEntry
   MAX-ACCESS  not-accessible
   STATUS      current
   DESCRIPTION
      ""
   INDEX      { pr1645v2PortSwIfInPriorityQueuesTableIx }
   ::= {pr1645v2PortSwIfInPriorityQueuesSSCTable 1}

Pr1645v2PortSwIfInPriorityQueuesEntry ::=
   SEQUENCE
      {
      pr1645v2PortSwIfInPriorityQueuesTableIx
         TableIndex,
      pr1645v2PortSwIfInPriorityQueuesName
         INTEGER,
      pr1645v2PortSwIfInPriorityQueuesLength
         Integer32,
      pr1645v2PortSwIfInPriorityQueuesOctetLength
         Integer32,
      pr1645v2PortSwIfInPriorityQueuesRedLength
         Integer32,
      pr1645v2PortSwIfInPriorityQueuesPacketsTotal
         Counter64,
      pr1645v2PortSwIfInPriorityQueuesPacketsDirectTx
         Counter64,
      pr1645v2PortSwIfInPriorityQueuesPacketsQueued
         Counter64,
      pr1645v2PortSwIfInPriorityQueuesPacketsDropped
         Counter64,
      pr1645v2PortSwIfInPriorityQueuesPacketsRedDropped
         Counter64,
      pr1645v2PortSwIfInPriorityQueuesPacketsCirTx
         Counter64,
      pr1645v2PortSwIfInPriorityQueuesPacketsEirTx
         Counter64,
      pr1645v2PortSwIfInPriorityQueuesPacketsViolateTx
         Counter64,
      pr1645v2PortSwIfInPriorityQueuesOctetsTotal
         Counter64,
      pr1645v2PortSwIfInPriorityQueuesOctetsDirectTx
         Counter64,
      pr1645v2PortSwIfInPriorityQueuesOctetsQueued
         Counter64,
      pr1645v2PortSwIfInPriorityQueuesOctetsDropped
         Counter64,
      pr1645v2PortSwIfInPriorityQueuesOctetsRedDropped
         Counter64,
      pr1645v2PortSwIfInPriorityQueuesOctetsCirTx
         Counter64,
      pr1645v2PortSwIfInPriorityQueuesOctetsEirTx
         Counter64,
      pr1645v2PortSwIfInPriorityQueuesOctetsViolateTx
         Counter64,
      pr1645v2PortSwIfInPriorityQueuesOctetsBandwidth15sec
         Integer32,
      pr1645v2PortSwIfInPriorityQueuesOctetsBandwidth30sec
         Integer32,
      pr1645v2PortSwIfInPriorityQueuesOctetsBandwidth1min
         Integer32,
      pr1645v2PortSwIfInPriorityQueuesOctetsBandwidth2min
         Integer32,
      pr1645v2PortSwIfInPriorityQueuesOctetsBandwidth5min
         Integer32
      }

pr1645v2PortSwIfInPriorityQueuesTableIx OBJECT-TYPE
   SYNTAX      TableIndex
   MAX-ACCESS  not-accessible
   STATUS      current
   DESCRIPTION
      ""
   ::= {pr1645v2PortSwIfInPriorityQueuesEntry 11}

pr1645v2PortSwIfInPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwIfInPriorityQueuesEntry 16777216}

pr1645v2PortSwIfInPriorityQueuesLength OBJECT-TYPE
   SYNTAX      Integer32
   MAX-ACCESS  read-only
   STATUS      current
   DESCRIPTION
      "Path: ethernet1.performance.ifInPriorityQueues.length"
   ::= {pr1645v2PortSwIfInPriorityQueuesEntry 33554432}

pr1645v2PortSwIfInPriorityQueuesOctetLength OBJECT-TYPE
   SYNTAX      Integer32
   MAX-ACCESS  read-only
   STATUS      current
   DESCRIPTION
      "Path: ethernet1.performance.ifInPriorityQueues.octetLength"
   ::= {pr1645v2PortSwIfInPriorityQueuesEntry 150994944}

pr1645v2PortSwIfInPriorityQueuesRedLength OBJECT-TYPE
   SYNTAX      Integer32
   MAX-ACCESS  read-only
   STATUS      current
   DESCRIPTION
      "Path: ethernet1.performance.ifInPriorityQueues.redLength"
   ::= {pr1645v2PortSwIfInPriorityQueuesEntry 134217728}

pr1645v2PortSwIfInPriorityQueuesPacketsTotal OBJECT-TYPE
   SYNTAX      Counter64
   MAX-ACCESS  read-only
   STATUS      current
   DESCRIPTION
      "Path: ethernet1.performance.ifInPriorityQueues.packets.total

       64 bit unsigned wrappable counter."
   ::= {pr1645v2PortSwIfInPriorityQueuesEntry 50790400}

pr1645v2PortSwIfInPriorityQueuesPacketsDirectTx OBJECT-TYPE
   SYNTAX      Counter64
   MAX-ACCESS  read-only
   STATUS      current
   DESCRIPTION
      "Path: ethernet1.performance.ifInPriorityQueues.packets.directTx

       64 bit unsigned wrappable counter."
   ::= {pr1645v2PortSwIfInPriorityQueuesEntry 50397184}

pr1645v2PortSwIfInPriorityQueuesPacketsQueued OBJECT-TYPE
   SYNTAX      Counter64
   MAX-ACCESS  read-only
   STATUS      current
   DESCRIPTION
      "Path: ethernet1.performance.ifInPriorityQueues.packets.queued

       64 bit unsigned wrappable counter."
   ::= {pr1645v2PortSwIfInPriorityQueuesEntry 50462720}

pr1645v2PortSwIfInPriorityQueuesPacketsDropped OBJECT-TYPE
   SYNTAX      Counter64
   MAX-ACCESS  read-only
   STATUS      current
   DESCRIPTION
      "Path: ethernet1.performance.ifInPriorityQueues.packets.dropped

       64 bit unsigned wrappable counter."
   ::= {pr1645v2PortSwIfInPriorityQueuesEntry 50528256}

pr1645v2PortSwIfInPriorityQueuesPacketsRedDropped OBJECT-TYPE
   SYNTAX      Counter64
   MAX-ACCESS  read-only
   STATUS      current
   DESCRIPTION
      "Path: ethernet1.performance.ifInPriorityQueues.packets.redDropped

       64 bit unsigned wrappable counter."
   ::= {pr1645v2PortSwIfInPriorityQueuesEntry 50724864}

pr1645v2PortSwIfInPriorityQueuesPacketsCirTx OBJECT-TYPE
   SYNTAX      Counter64
   MAX-ACCESS  read-only
   STATUS      current
   DESCRIPTION
      "Path: ethernet1.performance.ifInPriorityQueues.packets.cirTx

       64 bit unsigned wrappable counter."
   ::= {pr1645v2PortSwIfInPriorityQueuesEntry 50593792}

pr1645v2PortSwIfInPriorityQueuesPacketsEirTx OBJECT-TYPE
   SYNTAX      Counter64
   MAX-ACCESS  read-only
   STATUS      current
   DESCRIPTION
      "Path: ethernet1.performance.ifInPriorityQueues.packets.eirTx

       64 bit unsigned wrappable counter."
   ::= {pr1645v2PortSwIfInPriorityQueuesEntry 50659328}

pr1645v2PortSwIfInPriorityQueuesPacketsViolateTx OBJECT-TYPE
   SYNTAX      Counter64
   MAX-ACCESS  read-only
   STATUS      current
   DESCRIPTION
      "Path: ethernet1.performance.ifInPriorityQueues.packets.violateTx

       64 bit unsigned wrappable counter."
   ::= {pr1645v2PortSwIfInPriorityQueuesEntry 50855936}

pr1645v2PortSwIfInPriorityQueuesOctetsTotal OBJECT-TYPE
   SYNTAX      Counter64
   MAX-ACCESS  read-only
   STATUS      current
   DESCRIPTION
      "Path: ethernet1.performance.ifInPriorityQueues.octets.total

       64 bit unsigned wrappable counter."
   ::= {pr1645v2PortSwIfInPriorityQueuesEntry 67567616}

pr1645v2PortSwIfInPriorityQueuesOctetsDirectTx OBJECT-TYPE
   SYNTAX      Counter64
   MAX-ACCESS  read-only
   STATUS      current
   DESCRIPTION
      "Path: ethernet1.performance.ifInPriorityQueues.octets.directTx

       64 bit unsigned wrappable counter."
   ::= {pr1645v2PortSwIfInPriorityQueuesEntry 67174400}

pr1645v2PortSwIfInPriorityQueuesOctetsQueued OBJECT-TYPE
   SYNTAX      Counter64
   MAX-ACCESS  read-only
   STATUS      current
   DESCRIPTION
      "Path: ethernet1.performance.ifInPriorityQueues.octets.queued

       64 bit unsigned wrappable counter."
   ::= {pr1645v2PortSwIfInPriorityQueuesEntry 67239936}

pr1645v2PortSwIfInPriorityQueuesOctetsDropped OBJECT-TYPE
   SYNTAX      Counter64
   MAX-ACCESS  read-only
   STATUS      current
   DESCRIPTION
      "Path: ethernet1.performance.ifInPriorityQueues.octets.dropped

       64 bit unsigned wrappable counter."
   ::= {pr1645v2PortSwIfInPriorityQueuesEntry 67305472}

pr1645v2PortSwIfInPriorityQueuesOctetsRedDropped OBJECT-TYPE
   SYNTAX      Counter64
   MAX-ACCESS  read-only
   STATUS      current
   DESCRIPTION
      "Path: ethernet1.performance.ifInPriorityQueues.octets.redDropped

       64 bit unsigned wrappable counter."
   ::= {pr1645v2PortSwIfInPriorityQueuesEntry 67502080}

pr1645v2PortSwIfInPriorityQueuesOctetsCirTx OBJECT-TYPE
   SYNTAX      Counter64
   MAX-ACCESS  read-only
   STATUS      current
   DESCRIPTION
      "Path: ethernet1.performance.ifInPriorityQueues.octets.cirTx

       64 bit unsigned wrappable counter."
   ::= {pr1645v2PortSwIfInPriorityQueuesEntry 67371008}

pr1645v2PortSwIfInPriorityQueuesOctetsEirTx OBJECT-TYPE
   SYNTAX      Counter64
   MAX-ACCESS  read-only
   STATUS      current
   DESCRIPTION
      "Path: ethernet1.performance.ifInPriorityQueues.octets.eirTx

       64 bit unsigned wrappable counter."
   ::= {pr1645v2PortSwIfInPriorityQueuesEntry 67436544}

pr1645v2PortSwIfInPriorityQueuesOctetsViolateTx OBJECT-TYPE
   SYNTAX      Counter64
   MAX-ACCESS  read-only
   STATUS      current
   DESCRIPTION
      "Path: ethernet1.performance.ifInPriorityQueues.octets.violateTx

       64 bit unsigned wrappable counter."
   ::= {pr1645v2PortSwIfInPriorityQueuesEntry 67633152}

pr1645v2PortSwIfInPriorityQueuesOctetsBandwidth15sec OBJECT-TYPE
   SYNTAX      Integer32
   MAX-ACCESS  read-only
   STATUS      current
   DESCRIPTION
      "Path: ethernet1.performance.ifInPriorityQueues.octets.bandwidth.15sec

       unit name = bps
       formula = 8 * ; 8 /"
   ::= {pr1645v2PortSwIfInPriorityQueuesEntry 70386944}

pr1645v2PortSwIfInPriorityQueuesOctetsBandwidth30sec OBJECT-TYPE
   SYNTAX      Integer32
   MAX-ACCESS  read-only
   STATUS      current
   DESCRIPTION
      "Path: ethernet1.performance.ifInPriorityQueues.octets.bandwidth.30sec

       unit name = bps
       formula = 8 * ; 8 /"
   ::= {pr1645v2PortSwIfInPriorityQueuesEntry 70388224}

pr1645v2PortSwIfInPriorityQueuesOctetsBandwidth1min OBJECT-TYPE
   SYNTAX      Integer32
   MAX-ACCESS  read-only
   STATUS      current
   DESCRIPTION
      "Path: ethernet1.performance.ifInPriorityQueues.octets.bandwidth.1min

       unit name = bps
       formula = 8 * ; 8 /"
   ::= {pr1645v2PortSwIfInPriorityQueuesEntry 70390784}

pr1645v2PortSwIfInPriorityQueuesOctetsBandwidth2min OBJECT-TYPE
   SYNTAX      Integer32
   MAX-ACCESS  read-only
   STATUS      current
   DESCRIPTION
      "Path: ethernet1.performance.ifInPriorityQueues.octets.bandwidth.2min

       unit name = bps
       formula = 8 * ; 8 /"
   ::= {pr1645v2PortSwIfInPriorityQueuesEntry 70395904}

pr1645v2PortSwIfInPriorityQueuesOctetsBandwidth5min OBJECT-TYPE
   SYNTAX      Integer32
   MAX-ACCESS  read-only
   STATUS      current
   DESCRIPTION
      "Path: ethernet1.performance.ifInPriorityQueues.octets.bandwidth.5min

       unit name = bps
       formula = 8 * ; 8 /"
   ::= {pr1645v2PortSwIfInPriorityQueuesEntry 70411264}

pr1645v2PortSwIfInPriorityQueuesH2Performance OBJECT-TYPE
   SYNTAX      SEQUENCE OF Pr1645v2PortSwIfInPriorityQueuesH2PerformanceEntry
   MAX-ACCESS  not-accessible
   STATUS      current
   DESCRIPTION
      ""
   ::= {pr1645v2PortSwIfInPriorityQueues 83886080}

pr1645v2PortSwIfInPriorityQueuesH2PerformanceEntry OBJECT-TYPE
   SYNTAX      Pr1645v2PortSwIfInPriorityQueuesH2PerformanceEntry
   MAX-ACCESS  not-accessible
   STATUS      current
   DESCRIPTION
      ""
   INDEX      { pr1645v2PortSwIfInPriorityQueuesTableIx,
                pr1645v2PortSwIfInPriorityQueuesH2PerformanceTableIx }
   ::= {pr1645v2PortSwIfInPriorityQueuesH2Performance 1}

Pr1645v2PortSwIfInPriorityQueuesH2PerformanceEntry ::=
   SEQUENCE
      {
      pr1645v2PortSwIfInPriorityQueuesH2PerformanceTableIx
         TableIndex,
      pr1645v2PortSwIfInPriorityQueuesH2PerformanceSysUpTime
         TimeTicks,
      pr1645v2PortSwIfInPriorityQueuesH2PerformanceTotPkts
         Counter64,
      pr1645v2PortSwIfInPriorityQueuesH2PerformanceDirTxPkts
         Counter64,
      pr1645v2PortSwIfInPriorityQueuesH2PerformanceQdPkts
         Counter64,
      pr1645v2PortSwIfInPriorityQueuesH2PerformanceDropPkts
         Counter64,
      pr1645v2PortSwIfInPriorityQueuesH2PerformanceRDropPkts
         Counter64,
      pr1645v2PortSwIfInPriorityQueuesH2PerformanceCirTxPkts
         Counter64,
      pr1645v2PortSwIfInPriorityQueuesH2PerformanceEirTxPkts
         Counter64,
      pr1645v2PortSwIfInPriorityQueuesH2PerformanceViolTxPkts
         Counter64,
      pr1645v2PortSwIfInPriorityQueuesH2PerformanceTotOcts
         Counter64,
      pr1645v2PortSwIfInPriorityQueuesH2PerformanceDirTxOcts
         Counter64,
      pr1645v2PortSwIfInPriorityQueuesH2PerformanceQdOcts
         Counter64,
      pr1645v2PortSwIfInPriorityQueuesH2PerformanceDropOcts
         Counter64,
      pr1645v2PortSwIfInPriorityQueuesH2PerformanceRDropOcts
         Counter64,
      pr1645v2PortSwIfInPriorityQueuesH2PerformanceCirTxOcts
         Counter64,
      pr1645v2PortSwIfInPriorityQueuesH2PerformanceEirTxOcts
         Counter64,
      pr1645v2PortSwIfInPriorityQueuesH2PerformanceViolTxOcts
         Counter64,
      pr1645v2PortSwIfInPriorityQueuesH2PerformanceBandwidth
         Integer32
      }

pr1645v2PortSwIfInPriorityQueuesH2PerformanceTableIx OBJECT-TYPE
   SYNTAX      TableIndex
   MAX-ACCESS  not-accessible
   STATUS      current
   DESCRIPTION
      ""
   ::= {pr1645v2PortSwIfInPriorityQueuesH2PerformanceEntry 11}

pr1645v2PortSwIfInPriorityQueuesH2PerformanceSysUpTime OBJECT-TYPE
   SYNTAX      TimeTicks
   MAX-ACCESS  read-only
   STATUS      current
   DESCRIPTION
      "Path: ethernet1.performance.ifInPriorityQueues.h2Performance.sysUpTime

       Time in centi-second."
   ::= {pr1645v2PortSwIfInPriorityQueuesH2PerformanceEntry 16777216}

pr1645v2PortSwIfInPriorityQueuesH2PerformanceTotPkts OBJECT-TYPE
   SYNTAX      Counter64
   MAX-ACCESS  read-only
   STATUS      current
   DESCRIPTION
      "Path: ethernet1.performance.ifInPriorityQueues.h2Performance.totalPkts

       64 bit unsigned wrappable counter."
   ::= {pr1645v2PortSwIfInPriorityQueuesH2PerformanceEntry 234881024}

pr1645v2PortSwIfInPriorityQueuesH2PerformanceDirTxPkts OBJECT-TYPE
   SYNTAX      Counter64
   MAX-ACCESS  read-only
   STATUS      current
   DESCRIPTION
      "Path: ethernet1.performance.ifInPriorityQueues.h2Performance.directTxPkts

       64 bit unsigned wrappable counter."
   ::= {pr1645v2PortSwIfInPriorityQueuesH2PerformanceEntry 33554432}

pr1645v2PortSwIfInPriorityQueuesH2PerformanceQdPkts OBJECT-TYPE
   SYNTAX      Counter64
   MAX-ACCESS  read-only
   STATUS      current
   DESCRIPTION
      "Path: ethernet1.performance.ifInPriorityQueues.h2Performance.queuedPkts

       64 bit unsigned wrappable counter."
   ::= {pr1645v2PortSwIfInPriorityQueuesH2PerformanceEntry 50331648}

pr1645v2PortSwIfInPriorityQueuesH2PerformanceDropPkts OBJECT-TYPE
   SYNTAX      Counter64
   MAX-ACCESS  read-only
   STATUS      current
   DESCRIPTION
      "Path: ethernet1.performance.ifInPriorityQueues.h2Performance.droppedPkts

       64 bit unsigned wrappable counter."
   ::= {pr1645v2PortSwIfInPriorityQueuesH2PerformanceEntry 67108864}

pr1645v2PortSwIfInPriorityQueuesH2PerformanceRDropPkts OBJECT-TYPE
   SYNTAX      Counter64
   MAX-ACCESS  read-only
   STATUS      current
   DESCRIPTION
      "Path: ethernet1.performance.ifInPriorityQueues.h2Performance.redDroppedPkts

       64 bit unsigned wrappable counter."
   ::= {pr1645v2PortSwIfInPriorityQueuesH2PerformanceEntry 201326592}

pr1645v2PortSwIfInPriorityQueuesH2PerformanceCirTxPkts OBJECT-TYPE
   SYNTAX      Counter64
   MAX-ACCESS  read-only
   STATUS      current
   DESCRIPTION
      "Path: ethernet1.performance.ifInPriorityQueues.h2Performance.cirTxPkts

       64 bit unsigned wrappable counter."
   ::= {pr1645v2PortSwIfInPriorityQueuesH2PerformanceEntry 83886080}

pr1645v2PortSwIfInPriorityQueuesH2PerformanceEirTxPkts OBJECT-TYPE
   SYNTAX      Counter64
   MAX-ACCESS  read-only
   STATUS      current
   DESCRIPTION
      "Path: ethernet1.performance.ifInPriorityQueues.h2Performance.eirTxPkts

       64 bit unsigned wrappable counter."
   ::= {pr1645v2PortSwIfInPriorityQueuesH2PerformanceEntry 100663296}

pr1645v2PortSwIfInPriorityQueuesH2PerformanceViolTxPkts OBJECT-TYPE
   SYNTAX      Counter64
   MAX-ACCESS  read-only
   STATUS      current
   DESCRIPTION
      "Path: ethernet1.performance.ifInPriorityQueues.h2Performance.violateTxPkts

       64 bit unsigned wrappable counter."
   ::= {pr1645v2PortSwIfInPriorityQueuesH2PerformanceEntry 301989888}

pr1645v2PortSwIfInPriorityQueuesH2PerformanceTotOcts OBJECT-TYPE
   SYNTAX      Counter64
   MAX-ACCESS  read-only
   STATUS      current
   DESCRIPTION
      "Path: ethernet1.performance.ifInPriorityQueues.h2Performance.totalOctets

       64 bit unsigned wrappable counter."
   ::= {pr1645v2PortSwIfInPriorityQueuesH2PerformanceEntry 251658240}

pr1645v2PortSwIfInPriorityQueuesH2PerformanceDirTxOcts OBJECT-TYPE
   SYNTAX      Counter64
   MAX-ACCESS  read-only
   STATUS      current
   DESCRIPTION
      "Path: ethernet1.performance.ifInPriorityQueues.h2Performance.directTxOctets

       64 bit unsigned wrappable counter."
   ::= {pr1645v2PortSwIfInPriorityQueuesH2PerformanceEntry 117440512}

pr1645v2PortSwIfInPriorityQueuesH2PerformanceQdOcts OBJECT-TYPE
   SYNTAX      Counter64
   MAX-ACCESS  read-only
   STATUS      current
   DESCRIPTION
      "Path: ethernet1.performance.ifInPriorityQueues.h2Performance.queuedOctets

       64 bit unsigned wrappable counter."
   ::= {pr1645v2PortSwIfInPriorityQueuesH2PerformanceEntry 134217728}

pr1645v2PortSwIfInPriorityQueuesH2PerformanceDropOcts OBJECT-TYPE
   SYNTAX      Counter64
   MAX-ACCESS  read-only
   STATUS      current
   DESCRIPTION
      "Path: ethernet1.performance.ifInPriorityQueues.h2Performance.droppedOctets

       64 bit unsigned wrappable counter."
   ::= {pr1645v2PortSwIfInPriorityQueuesH2PerformanceEntry 150994944}

pr1645v2PortSwIfInPriorityQueuesH2PerformanceRDropOcts OBJECT-TYPE
   SYNTAX      Counter64
   MAX-ACCESS  read-only
   STATUS      current
   DESCRIPTION
      "Path: ethernet1.performance.ifInPriorityQueues.h2Performance.redDroppedOctets

       64 bit unsigned wrappable counter."
   ::= {pr1645v2PortSwIfInPriorityQueuesH2PerformanceEntry 218103808}

pr1645v2PortSwIfInPriorityQueuesH2PerformanceCirTxOcts OBJECT-TYPE
   SYNTAX      Counter64
   MAX-ACCESS  read-only
   STATUS      current
   DESCRIPTION
      "Path: ethernet1.performance.ifInPriorityQueues.h2Performance.cirTxOctets

       64 bit unsigned wrappable counter."
   ::= {pr1645v2PortSwIfInPriorityQueuesH2PerformanceEntry 167772160}

pr1645v2PortSwIfInPriorityQueuesH2PerformanceEirTxOcts OBJECT-TYPE
   SYNTAX      Counter64
   MAX-ACCESS  read-only
   STATUS      current
   DESCRIPTION
      "Path: ethernet1.performance.ifInPriorityQueues.h2Performance.eirTxOctets

       64 bit unsigned wrappable counter."
   ::= {pr1645v2PortSwIfInPriorityQueuesH2PerformanceEntry 184549376}

pr1645v2PortSwIfInPriorityQueuesH2PerformanceViolTxOcts OBJECT-TYPE
   SYNTAX      Counter64
   MAX-ACCESS  read-only
   STATUS      current
   DESCRIPTION
      "Path: ethernet1.performance.ifInPriorityQueues.h2Performance.violateTxOctets

       64 bit unsigned wrappable counter."
   ::= {pr1645v2PortSwIfInPriorityQueuesH2PerformanceEntry 318767104}

pr1645v2PortSwIfInPriorityQueuesH2PerformanceBandwidth OBJECT-TYPE
   SYNTAX      Integer32
   MAX-ACCESS  read-only
   STATUS      current
   DESCRIPTION
      "Path: ethernet1.performance.ifInPriorityQueues.h2Performance.bandwidth

       unit name = bps
       formula = 8 * ; 8 /"
   ::= {pr1645v2PortSwIfInPriorityQueuesH2PerformanceEntry 268435456}

pr1645v2PortSwIfInPriorityQueuesH24Performance OBJECT-TYPE
   SYNTAX      SEQUENCE OF Pr1645v2PortSwIfInPriorityQueuesH24PerformanceEntry
   MAX-ACCESS  not-accessible
   STATUS      current
   DESCRIPTION
      ""
   ::= {pr1645v2PortSwIfInPriorityQueues 100663296}

pr1645v2PortSwIfInPriorityQueuesH24PerformanceEntry OBJECT-TYPE
   SYNTAX      Pr1645v2PortSwIfInPriorityQueuesH24PerformanceEntry
   MAX-ACCESS  not-accessible
   STATUS      current
   DESCRIPTION
      ""
   INDEX      { pr1645v2PortSwIfInPriorityQueuesTableIx,
                pr1645v2PortSwIfInPriorityQueuesH24PerformanceTableIx }
   ::= {pr1645v2PortSwIfInPriorityQueuesH24Performance 1}

Pr1645v2PortSwIfInPriorityQueuesH24PerformanceEntry ::=
   SEQUENCE
      {
      pr1645v2PortSwIfInPriorityQueuesH24PerformanceTableIx
         TableIndex,
      pr1645v2PortSwIfInPriorityQueuesH24PerformanceSysUpTime
         TimeTicks,
      pr1645v2PortSwIfInPriorityQueuesH24PerformanceTotPkts
         Counter64,
      pr1645v2PortSwIfInPriorityQueuesH24PerformanceDirTxPkts
         Counter64,
      pr1645v2PortSwIfInPriorityQueuesH24PerformanceQdPkts
         Counter64,
      pr1645v2PortSwIfInPriorityQueuesH24PerformanceDropPkts
         Counter64,
      pr1645v2PortSwIfInPriorityQueuesH24PerformanceRDropPkts
         Counter64,
      pr1645v2PortSwIfInPriorityQueuesH24PerformanceCirTxPkts
         Counter64,
      pr1645v2PortSwIfInPriorityQueuesH24PerformanceEirTxPkts
         Counter64,
      pr1645v2PortSwIfInPriorityQueuesH24PerformanceViolTxPkts
         Counter64,
      pr1645v2PortSwIfInPriorityQueuesH24PerformanceTotOcts
         Counter64,
      pr1645v2PortSwIfInPriorityQueuesH24PerformanceDirTxOcts
         Counter64,
      pr1645v2PortSwIfInPriorityQueuesH24PerformanceQdOcts
         Counter64,
      pr1645v2PortSwIfInPriorityQueuesH24PerformanceDropOcts
         Counter64,
      pr1645v2PortSwIfInPriorityQueuesH24PerformanceRDropOcts
         Counter64,
      pr1645v2PortSwIfInPriorityQueuesH24PerformanceCirTxOcts
         Counter64,
      pr1645v2PortSwIfInPriorityQueuesH24PerformanceEirTxOcts
         Counter64,
      pr1645v2PortSwIfInPriorityQueuesH24PerformanceViolTxOcts
         Counter64,
      pr1645v2PortSwIfInPriorityQueuesH24PerformanceBandwidth
         Integer32
      }

pr1645v2PortSwIfInPriorityQueuesH24PerformanceTableIx OBJECT-TYPE
   SYNTAX      TableIndex
   MAX-ACCESS  not-accessible
   STATUS      current
   DESCRIPTION
      ""
   ::= {pr1645v2PortSwIfInPriorityQueuesH24PerformanceEntry 11}

pr1645v2PortSwIfInPriorityQueuesH24PerformanceSysUpTime OBJECT-TYPE
   SYNTAX      TimeTicks
   MAX-ACCESS  read-only
   STATUS      current
   DESCRIPTION
      "Path: ethernet1.performance.ifInPriorityQueues.h24Performance.sysUpTime

       Time in centi-second."
   ::= {pr1645v2PortSwIfInPriorityQueuesH24PerformanceEntry 16777216}

pr1645v2PortSwIfInPriorityQueuesH24PerformanceTotPkts OBJECT-TYPE
   SYNTAX      Counter64
   MAX-ACCESS  read-only
   STATUS      current
   DESCRIPTION
      "Path: ethernet1.performance.ifInPriorityQueues.h24Performance.totalPkts

       64 bit unsigned wrappable counter."
   ::= {pr1645v2PortSwIfInPriorityQueuesH24PerformanceEntry 234881024}

pr1645v2PortSwIfInPriorityQueuesH24PerformanceDirTxPkts OBJECT-TYPE
   SYNTAX      Counter64
   MAX-ACCESS  read-only
   STATUS      current
   DESCRIPTION
      "Path: ethernet1.performance.ifInPriorityQueues.h24Performance.directTxPkts

       64 bit unsigned wrappable counter."
   ::= {pr1645v2PortSwIfInPriorityQueuesH24PerformanceEntry 33554432}

pr1645v2PortSwIfInPriorityQueuesH24PerformanceQdPkts OBJECT-TYPE
   SYNTAX      Counter64
   MAX-ACCESS  read-only
   STATUS      current
   DESCRIPTION
      "Path: ethernet1.performance.ifInPriorityQueues.h24Performance.queuedPkts

       64 bit unsigned wrappable counter."
   ::= {pr1645v2PortSwIfInPriorityQueuesH24PerformanceEntry 50331648}

pr1645v2PortSwIfInPriorityQueuesH24PerformanceDropPkts OBJECT-TYPE
   SYNTAX      Counter64
   MAX-ACCESS  read-only
   STATUS      current
   DESCRIPTION
      "Path: ethernet1.performance.ifInPriorityQueues.h24Performance.droppedPkts

       64 bit unsigned wrappable counter."
   ::= {pr1645v2PortSwIfInPriorityQueuesH24PerformanceEntry 67108864}

pr1645v2PortSwIfInPriorityQueuesH24PerformanceRDropPkts OBJECT-TYPE
   SYNTAX      Counter64
   MAX-ACCESS  read-only
   STATUS      current
   DESCRIPTION
      "Path: ethernet1.performance.ifInPriorityQueues.h24Performance.redDroppedPkts

       64 bit unsigned wrappable counter."
   ::= {pr1645v2PortSwIfInPriorityQueuesH24PerformanceEntry 201326592}

pr1645v2PortSwIfInPriorityQueuesH24PerformanceCirTxPkts OBJECT-TYPE
   SYNTAX      Counter64
   MAX-ACCESS  read-only
   STATUS      current
   DESCRIPTION
      "Path: ethernet1.performance.ifInPriorityQueues.h24Performance.cirTxPkts

       64 bit unsigned wrappable counter."
   ::= {pr1645v2PortSwIfInPriorityQueuesH24PerformanceEntry 83886080}

pr1645v2PortSwIfInPriorityQueuesH24PerformanceEirTxPkts OBJECT-TYPE
   SYNTAX      Counter64
   MAX-ACCESS  read-only
   STATUS      current
   DESCRIPTION
      "Path: ethernet1.performance.ifInPriorityQueues.h24Performance.eirTxPkts

       64 bit unsigned wrappable counter."
   ::= {pr1645v2PortSwIfInPriorityQueuesH24PerformanceEntry 100663296}

pr1645v2PortSwIfInPriorityQueuesH24PerformanceViolTxPkts OBJECT-TYPE
   SYNTAX      Counter64
   MAX-ACCESS  read-only
   STATUS      current
   DESCRIPTION
      "Path: ethernet1.performance.ifInPriorityQueues.h24Performance.violateTxPkts

       64 bit unsigned wrappable counter."
   ::= {pr1645v2PortSwIfInPriorityQueuesH24PerformanceEntry 301989888}

pr1645v2PortSwIfInPriorityQueuesH24PerformanceTotOcts OBJECT-TYPE
   SYNTAX      Counter64
   MAX-ACCESS  read-only
   STATUS      current
   DESCRIPTION
      "Path: ethernet1.performance.ifInPriorityQueues.h24Performance.totalOctets

       64 bit unsigned wrappable counter."
   ::= {pr1645v2PortSwIfInPriorityQueuesH24PerformanceEntry 251658240}

pr1645v2PortSwIfInPriorityQueuesH24PerformanceDirTxOcts OBJECT-TYPE
   SYNTAX      Counter64
   MAX-ACCESS  read-only
   STATUS      current
   DESCRIPTION
      "Path: ethernet1.performance.ifInPriorityQueues.h24Performance.directTxOctets

       64 bit unsigned wrappable counter."
   ::= {pr1645v2PortSwIfInPriorityQueuesH24PerformanceEntry 117440512}

pr1645v2PortSwIfInPriorityQueuesH24PerformanceQdOcts OBJECT-TYPE
   SYNTAX      Counter64
   MAX-ACCESS  read-only
   STATUS      current
   DESCRIPTION
      "Path: ethernet1.performance.ifInPriorityQueues.h24Performance.queuedOctets

       64 bit unsigned wrappable counter."
   ::= {pr1645v2PortSwIfInPriorityQueuesH24PerformanceEntry 134217728}

pr1645v2PortSwIfInPriorityQueuesH24PerformanceDropOcts OBJECT-TYPE
   SYNTAX      Counter64
   MAX-ACCESS  read-only
   STATUS      current
   DESCRIPTION
      "Path: ethernet1.performance.ifInPriorityQueues.h24Performance.droppedOctets

       64 bit unsigned wrappable counter."
   ::= {pr1645v2PortSwIfInPriorityQueuesH24PerformanceEntry 150994944}

pr1645v2PortSwIfInPriorityQueuesH24PerformanceRDropOcts OBJECT-TYPE
   SYNTAX      Counter64
   MAX-ACCESS  read-only
   STATUS      current
   DESCRIPTION
      "Path: ethernet1.performance.ifInPriorityQueues.h24Performance.redDroppedOctets

       64 bit unsigned wrappable counter."
   ::= {pr1645v2PortSwIfInPriorityQueuesH24PerformanceEntry 218103808}

pr1645v2PortSwIfInPriorityQueuesH24PerformanceCirTxOcts OBJECT-TYPE
   SYNTAX      Counter64
   MAX-ACCESS  read-only
   STATUS      current
   DESCRIPTION
      "Path: ethernet1.performance.ifInPriorityQueues.h24Performance.cirTxOctets

       64 bit unsigned wrappable counter."
   ::= {pr1645v2PortSwIfInPriorityQueuesH24PerformanceEntry 167772160}

pr1645v2PortSwIfInPriorityQueuesH24PerformanceEirTxOcts OBJECT-TYPE
   SYNTAX      Counter64
   MAX-ACCESS  read-only
   STATUS      current
   DESCRIPTION
      "Path: ethernet1.performance.ifInPriorityQueues.h24Performance.eirTxOctets

       64 bit unsigned wrappable counter."
   ::= {pr1645v2PortSwIfInPriorityQueuesH24PerformanceEntry 184549376}

pr1645v2PortSwIfInPriorityQueuesH24PerformanceViolTxOcts OBJECT-TYPE
   SYNTAX      Counter64
   MAX-ACCESS  read-only
   STATUS      current
   DESCRIPTION
      "Path: ethernet1.performance.ifInPriorityQueues.h24Performance.violateTxOctets

       64 bit unsigned wrappable counter."
   ::= {pr1645v2PortSwIfInPriorityQueuesH24PerformanceEntry 318767104}

pr1645v2PortSwIfInPriorityQueuesH24PerformanceBandwidth OBJECT-TYPE
   SYNTAX      Integer32
   MAX-ACCESS  read-only
   STATUS      current
   DESCRIPTION
      "Path: ethernet1.performance.ifInPriorityQueues.h24Performance.bandwidth

       unit name = bps
       formula = 8 * ; 8 /"
   ::= {pr1645v2PortSwIfInPriorityQueuesH24PerformanceEntry 268435456}

pr1645v2PortSwIfInPriorityQueuesD7Performance OBJECT-TYPE
   SYNTAX      SEQUENCE OF Pr1645v2PortSwIfInPriorityQueuesD7PerformanceEntry
   MAX-ACCESS  not-accessible
   STATUS      current
   DESCRIPTION
      ""
   ::= {pr1645v2PortSwIfInPriorityQueues 117440512}

pr1645v2PortSwIfInPriorityQueuesD7PerformanceEntry OBJECT-TYPE
   SYNTAX      Pr1645v2PortSwIfInPriorityQueuesD7PerformanceEntry
   MAX-ACCESS  not-accessible
   STATUS      current
   DESCRIPTION
      ""
   INDEX      { pr1645v2PortSwIfInPriorityQueuesTableIx,
                pr1645v2PortSwIfInPriorityQueuesD7PerformanceTableIx }
   ::= {pr1645v2PortSwIfInPriorityQueuesD7Performance 1}

Pr1645v2PortSwIfInPriorityQueuesD7PerformanceEntry ::=
   SEQUENCE
      {
      pr1645v2PortSwIfInPriorityQueuesD7PerformanceTableIx
         TableIndex,
      pr1645v2PortSwIfInPriorityQueuesD7PerformanceSysUpTime
         TimeTicks,
      pr1645v2PortSwIfInPriorityQueuesD7PerformanceTotPkts
         Counter64,
      pr1645v2PortSwIfInPriorityQueuesD7PerformanceDirTxPkts
         Counter64,
      pr1645v2PortSwIfInPriorityQueuesD7PerformanceQdPkts
         Counter64,
      pr1645v2PortSwIfInPriorityQueuesD7PerformanceDropPkts
         Counter64,
      pr1645v2PortSwIfInPriorityQueuesD7PerformanceRDropPkts
         Counter64,
      pr1645v2PortSwIfInPriorityQueuesD7PerformanceCirTxPkts
         Counter64,
      pr1645v2PortSwIfInPriorityQueuesD7PerformanceEirTxPkts
         Counter64,
      pr1645v2PortSwIfInPriorityQueuesD7PerformanceViolTxPkts
         Counter64,
      pr1645v2PortSwIfInPriorityQueuesD7PerformanceTotOcts
         Counter64,
      pr1645v2PortSwIfInPriorityQueuesD7PerformanceDirTxOcts
         Counter64,
      pr1645v2PortSwIfInPriorityQueuesD7PerformanceQdOcts
         Counter64,
      pr1645v2PortSwIfInPriorityQueuesD7PerformanceDropOcts
         Counter64,
      pr1645v2PortSwIfInPriorityQueuesD7PerformanceRDropOcts
         Counter64,
      pr1645v2PortSwIfInPriorityQueuesD7PerformanceCirTxOcts
         Counter64,
      pr1645v2PortSwIfInPriorityQueuesD7PerformanceEirTxOcts
         Counter64,
      pr1645v2PortSwIfInPriorityQueuesD7PerformanceViolTxOcts
         Counter64,
      pr1645v2PortSwIfInPriorityQueuesD7PerformanceBandwidth
         Integer32
      }

pr1645v2PortSwIfInPriorityQueuesD7PerformanceTableIx OBJECT-TYPE
   SYNTAX      TableIndex
   MAX-ACCESS  not-accessible
   STATUS      current
   DESCRIPTION
      ""
   ::= {pr1645v2PortSwIfInPriorityQueuesD7PerformanceEntry 11}

pr1645v2PortSwIfInPriorityQueuesD7PerformanceSysUpTime OBJECT-TYPE
   SYNTAX      TimeTicks
   MAX-ACCESS  read-only
   STATUS      current
   DESCRIPTION
      "Path: ethernet1.performance.ifInPriorityQueues.d7Performance.sysUpTime

       Time in centi-second."
   ::= {pr1645v2PortSwIfInPriorityQueuesD7PerformanceEntry 16777216}

pr1645v2PortSwIfInPriorityQueuesD7PerformanceTotPkts OBJECT-TYPE
   SYNTAX      Counter64
   MAX-ACCESS  read-only
   STATUS      current
   DESCRIPTION
      "Path: ethernet1.performance.ifInPriorityQueues.d7Performance.totalPkts

       64 bit unsigned wrappable counter."
   ::= {pr1645v2PortSwIfInPriorityQueuesD7PerformanceEntry 234881024}

pr1645v2PortSwIfInPriorityQueuesD7PerformanceDirTxPkts OBJECT-TYPE
   SYNTAX      Counter64
   MAX-ACCESS  read-only
   STATUS      current
   DESCRIPTION
      "Path: ethernet1.performance.ifInPriorityQueues.d7Performance.directTxPkts

       64 bit unsigned wrappable counter."
   ::= {pr1645v2PortSwIfInPriorityQueuesD7PerformanceEntry 33554432}

pr1645v2PortSwIfInPriorityQueuesD7PerformanceQdPkts OBJECT-TYPE
   SYNTAX      Counter64
   MAX-ACCESS  read-only
   STATUS      current
   DESCRIPTION
      "Path: ethernet1.performance.ifInPriorityQueues.d7Performance.queuedPkts

       64 bit unsigned wrappable counter."
   ::= {pr1645v2PortSwIfInPriorityQueuesD7PerformanceEntry 50331648}

pr1645v2PortSwIfInPriorityQueuesD7PerformanceDropPkts OBJECT-TYPE
   SYNTAX      Counter64
   MAX-ACCESS  read-only
   STATUS      current
   DESCRIPTION
      "Path: ethernet1.performance.ifInPriorityQueues.d7Performance.droppedPkts

       64 bit unsigned wrappable counter."
   ::= {pr1645v2PortSwIfInPriorityQueuesD7PerformanceEntry 67108864}

pr1645v2PortSwIfInPriorityQueuesD7PerformanceRDropPkts OBJECT-TYPE
   SYNTAX      Counter64
   MAX-ACCESS  read-only
   STATUS      current
   DESCRIPTION
      "Path: ethernet1.performance.ifInPriorityQueues.d7Performance.redDroppedPkts

       64 bit unsigned wrappable counter."
   ::= {pr1645v2PortSwIfInPriorityQueuesD7PerformanceEntry 201326592}

pr1645v2PortSwIfInPriorityQueuesD7PerformanceCirTxPkts OBJECT-TYPE
   SYNTAX      Counter64
   MAX-ACCESS  read-only
   STATUS      current
   DESCRIPTION
      "Path: ethernet1.performance.ifInPriorityQueues.d7Performance.cirTxPkts

       64 bit unsigned wrappable counter."
   ::= {pr1645v2PortSwIfInPriorityQueuesD7PerformanceEntry 83886080}

pr1645v2PortSwIfInPriorityQueuesD7PerformanceEirTxPkts OBJECT-TYPE
   SYNTAX      Counter64
   MAX-ACCESS  read-only
   STATUS      current
   DESCRIPTION
      "Path: ethernet1.performance.ifInPriorityQueues.d7Performance.eirTxPkts

       64 bit unsigned wrappable counter."
   ::= {pr1645v2PortSwIfInPriorityQueuesD7PerformanceEntry 100663296}

pr1645v2PortSwIfInPriorityQueuesD7PerformanceViolTxPkts OBJECT-TYPE
   SYNTAX      Counter64
   MAX-ACCESS  read-only
   STATUS      current
   DESCRIPTION
      "Path: ethernet1.performance.ifInPriorityQueues.d7Performance.violateTxPkts

       64 bit unsigned wrappable counter."
   ::= {pr1645v2PortSwIfInPriorityQueuesD7PerformanceEntry 301989888}

pr1645v2PortSwIfInPriorityQueuesD7PerformanceTotOcts OBJECT-TYPE
   SYNTAX      Counter64
   MAX-ACCESS  read-only
   STATUS      current
   DESCRIPTION
      "Path: ethernet1.performance.ifInPriorityQueues.d7Performance.totalOctets

       64 bit unsigned wrappable counter."
   ::= {pr1645v2PortSwIfInPriorityQueuesD7PerformanceEntry 251658240}

pr1645v2PortSwIfInPriorityQueuesD7PerformanceDirTxOcts OBJECT-TYPE
   SYNTAX      Counter64
   MAX-ACCESS  read-only
   STATUS      current
   DESCRIPTION
      "Path: ethernet1.performance.ifInPriorityQueues.d7Performance.directTxOctets

       64 bit unsigned wrappable counter."
   ::= {pr1645v2PortSwIfInPriorityQueuesD7PerformanceEntry 117440512}

pr1645v2PortSwIfInPriorityQueuesD7PerformanceQdOcts OBJECT-TYPE
   SYNTAX      Counter64
   MAX-ACCESS  read-only
   STATUS      current
   DESCRIPTION
      "Path: ethernet1.performance.ifInPriorityQueues.d7Performance.queuedOctets

       64 bit unsigned wrappable counter."
   ::= {pr1645v2PortSwIfInPriorityQueuesD7PerformanceEntry 134217728}

pr1645v2PortSwIfInPriorityQueuesD7PerformanceDropOcts OBJECT-TYPE
   SYNTAX      Counter64
   MAX-ACCESS  read-only
   STATUS      current
   DESCRIPTION
      "Path: ethernet1.performance.ifInPriorityQueues.d7Performance.droppedOctets

       64 bit unsigned wrappable counter."
   ::= {pr1645v2PortSwIfInPriorityQueuesD7PerformanceEntry 150994944}

pr1645v2PortSwIfInPriorityQueuesD7PerformanceRDropOcts OBJECT-TYPE
   SYNTAX      Counter64
   MAX-ACCESS  read-only
   STATUS      current
   DESCRIPTION
      "Path: ethernet1.performance.ifInPriorityQueues.d7Performance.redDroppedOctets

       64 bit unsigned wrappable counter."
   ::= {pr1645v2PortSwIfInPriorityQueuesD7PerformanceEntry 218103808}

pr1645v2PortSwIfInPriorityQueuesD7PerformanceCirTxOcts OBJECT-TYPE
   SYNTAX      Counter64
   MAX-ACCESS  read-only
   STATUS      current
   DESCRIPTION
      "Path: ethernet1.performance.ifInPriorityQueues.d7Performance.cirTxOctets

       64 bit unsigned wrappable counter."
   ::= {pr1645v2PortSwIfInPriorityQueuesD7PerformanceEntry 167772160}

pr1645v2PortSwIfInPriorityQueuesD7PerformanceEirTxOcts OBJECT-TYPE
   SYNTAX      Counter64
   MAX-ACCESS  read-only
   STATUS      current
   DESCRIPTION
      "Path: ethernet1.performance.ifInPriorityQueues.d7Performance.eirTxOctets

       64 bit unsigned wrappable counter."
   ::= {pr1645v2PortSwIfInPriorityQueuesD7PerformanceEntry 184549376}

pr1645v2PortSwIfInPriorityQueuesD7PerformanceViolTxOcts OBJECT-TYPE
   SYNTAX      Counter64
   MAX-ACCESS  read-only
   STATUS      current
   DESCRIPTION
      "Path: ethernet1.performance.ifInPriorityQueues.d7Performance.violateTxOctets

       64 bit unsigned wrappable counter."
   ::= {pr1645v2PortSwIfInPriorityQueuesD7PerformanceEntry 318767104}

pr1645v2PortSwIfInPriorityQueuesD7PerformanceBandwidth OBJECT-TYPE
   SYNTAX      Integer32
   MAX-ACCESS  read-only
   STATUS      current
   DESCRIPTION
      "Path: ethernet1.performance.ifInPriorityQueues.d7Performance.bandwidth

       unit name = bps
       formula = 8 * ; 8 /"
   ::= {pr1645v2PortSwIfInPriorityQueuesD7PerformanceEntry 268435456}


pr1645v2PortSwIfInHwPriorityQueues OBJECT IDENTIFIER ::= {pr1645v2PortSw 132}

pr1645v2PortSwIfInHwPriorityQueuesSSCTable OBJECT-TYPE
   SYNTAX      SEQUENCE OF Pr1645v2PortSwIfInHwPriorityQueuesEntry
   MAX-ACCESS  not-accessible
   STATUS      current
   DESCRIPTION
      "hwPriorityQueues"
   ::= {pr1645v2PortSwIfInHwPriorityQueues 1}

pr1645v2PortSwIfInHwPriorityQueuesEntry OBJECT-TYPE
   SYNTAX      Pr1645v2PortSwIfInHwPriorityQueuesEntry
   MAX-ACCESS  not-accessible
   STATUS      current
   DESCRIPTION
      ""
   INDEX      { pr1645v2PortSwIfInHwPriorityQueuesTableIx }
   ::= {pr1645v2PortSwIfInHwPriorityQueuesSSCTable 1}

Pr1645v2PortSwIfInHwPriorityQueuesEntry ::=
   SEQUENCE
      {
      pr1645v2PortSwIfInHwPriorityQueuesTableIx
         TableIndex,
      pr1645v2PortSwIfInHwPriorityQueuesName
         INTEGER,
      pr1645v2PortSwIfInHwPriorityQueuesLength
         Integer32,
      pr1645v2PortSwIfInHwPriorityQueuesPacketsTotal
         Counter64,
      pr1645v2PortSwIfInHwPriorityQueuesOctetsTotal
         Counter64,
      pr1645v2PortSwIfInHwPriorityQueuesOctetsBandwidth15sec
         Integer32,
      pr1645v2PortSwIfInHwPriorityQueuesOctetsBandwidth30sec
         Integer32,
      pr1645v2PortSwIfInHwPriorityQueuesOctetsBandwidth1min
         Integer32,
      pr1645v2PortSwIfInHwPriorityQueuesOctetsBandwidth2min
         Integer32,
      pr1645v2PortSwIfInHwPriorityQueuesOctetsBandwidth5min
         Integer32
      }

pr1645v2PortSwIfInHwPriorityQueuesTableIx OBJECT-TYPE
   SYNTAX      TableIndex
   MAX-ACCESS  not-accessible
   STATUS      current
   DESCRIPTION
      ""
   ::= {pr1645v2PortSwIfInHwPriorityQueuesEntry 11}

pr1645v2PortSwIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet1.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwIfInHwPriorityQueuesEntry 16777216}

pr1645v2PortSwIfInHwPriorityQueuesLength OBJECT-TYPE
   SYNTAX      Integer32
   MAX-ACCESS  read-only
   STATUS      current
   DESCRIPTION
      "Path: ethernet1.performance.ifInHwPriorityQueues.length"
   ::= {pr1645v2PortSwIfInHwPriorityQueuesEntry 33554432}

pr1645v2PortSwIfInHwPriorityQueuesPacketsTotal OBJECT-TYPE
   SYNTAX      Counter64
   MAX-ACCESS  read-only
   STATUS      current
   DESCRIPTION
      "Path: ethernet1.performance.ifInHwPriorityQueues.packets.total

       64 bit unsigned wrappable counter."
   ::= {pr1645v2PortSwIfInHwPriorityQueuesEntry 50790400}

pr1645v2PortSwIfInHwPriorityQueuesOctetsTotal OBJECT-TYPE
   SYNTAX      Counter64
   MAX-ACCESS  read-only
   STATUS      current
   DESCRIPTION
      "Path: ethernet1.performance.ifInHwPriorityQueues.octets.total

       64 bit unsigned wrappable counter."
   ::= {pr1645v2PortSwIfInHwPriorityQueuesEntry 67567616}

pr1645v2PortSwIfInHwPriorityQueuesOctetsBandwidth15sec OBJECT-TYPE
   SYNTAX      Integer32
   MAX-ACCESS  read-only
   STATUS      current
   DESCRIPTION
      "Path: ethernet1.performance.ifInHwPriorityQueues.octets.bandwidth.15sec

       unit name = bps
       formula = 8 * ; 8 /"
   ::= {pr1645v2PortSwIfInHwPriorityQueuesEntry 70386944}

pr1645v2PortSwIfInHwPriorityQueuesOctetsBandwidth30sec OBJECT-TYPE
   SYNTAX      Integer32
   MAX-ACCESS  read-only
   STATUS      current
   DESCRIPTION
      "Path: ethernet1.performance.ifInHwPriorityQueues.octets.bandwidth.30sec

       unit name = bps
       formula = 8 * ; 8 /"
   ::= {pr1645v2PortSwIfInHwPriorityQueuesEntry 70388224}

pr1645v2PortSwIfInHwPriorityQueuesOctetsBandwidth1min OBJECT-TYPE
   SYNTAX      Integer32
   MAX-ACCESS  read-only
   STATUS      current
   DESCRIPTION
      "Path: ethernet1.performance.ifInHwPriorityQueues.octets.bandwidth.1min

       unit name = bps
       formula = 8 * ; 8 /"
   ::= {pr1645v2PortSwIfInHwPriorityQueuesEntry 70390784}

pr1645v2PortSwIfInHwPriorityQueuesOctetsBandwidth2min OBJECT-TYPE
   SYNTAX      Integer32
   MAX-ACCESS  read-only
   STATUS      current
   DESCRIPTION
      "Path: ethernet1.performance.ifInHwPriorityQueues.octets.bandwidth.2min

       unit name = bps
       formula = 8 * ; 8 /"
   ::= {pr1645v2PortSwIfInHwPriorityQueuesEntry 70395904}

pr1645v2PortSwIfInHwPriorityQueuesOctetsBandwidth5min OBJECT-TYPE
   SYNTAX      Integer32
   MAX-ACCESS  read-only
   STATUS      current
   DESCRIPTION
      "Path: ethernet1.performance.ifInHwPriorityQueues.octets.bandwidth.5min

       unit name = bps
       formula = 8 * ; 8 /"
   ::= {pr1645v2PortSwIfInHwPriorityQueuesEntry 70411264}

pr1645v2PortSwIfInHwPriorityQueuesH2Performance OBJECT-TYPE
   SYNTAX      SEQUENCE OF Pr1645v2PortSwIfInHwPriorityQueuesH2PerformanceEntry
   MAX-ACCESS  not-accessible
   STATUS      current
   DESCRIPTION
      ""
   ::= {pr1645v2PortSwIfInHwPriorityQueues 83886080}

pr1645v2PortSwIfInHwPriorityQueuesH2PerformanceEntry OBJECT-TYPE
   SYNTAX      Pr1645v2PortSwIfInHwPriorityQueuesH2PerformanceEntry
   MAX-ACCESS  not-accessible
   STATUS      current
   DESCRIPTION
      ""
   INDEX      { pr1645v2PortSwIfInHwPriorityQueuesTableIx,
                pr1645v2PortSwIfInHwPriorityQueuesH2PerformanceTableIx }
   ::= {pr1645v2PortSwIfInHwPriorityQueuesH2Performance 1}

Pr1645v2PortSwIfInHwPriorityQueuesH2PerformanceEntry ::=
   SEQUENCE
      {
      pr1645v2PortSwIfInHwPriorityQueuesH2PerformanceTableIx
         TableIndex,
      pr1645v2PortSwIfInHwPriorityQueuesH2PerformanceSysUpTime
         TimeTicks,
      pr1645v2PortSwIfInHwPriorityQueuesH2PerformanceTotPkts
         Counter64,
      pr1645v2PortSwIfInHwPriorityQueuesH2PerformanceTotOcts
         Counter64,
      pr1645v2PortSwIfInHwPriorityQueuesH2PerformanceBandwidth
         Integer32
      }

pr1645v2PortSwIfInHwPriorityQueuesH2PerformanceTableIx OBJECT-TYPE
   SYNTAX      TableIndex
   MAX-ACCESS  not-accessible
   STATUS      current
   DESCRIPTION
      ""
   ::= {pr1645v2PortSwIfInHwPriorityQueuesH2PerformanceEntry 11}

pr1645v2PortSwIfInHwPriorityQueuesH2PerformanceSysUpTime OBJECT-TYPE
   SYNTAX      TimeTicks
   MAX-ACCESS  read-only
   STATUS      current
   DESCRIPTION
      "Path: ethernet1.performance.ifInHwPriorityQueues.h2Performance.sysUpTime

       Time in centi-second."
   ::= {pr1645v2PortSwIfInHwPriorityQueuesH2PerformanceEntry 16777216}

pr1645v2PortSwIfInHwPriorityQueuesH2PerformanceTotPkts OBJECT-TYPE
   SYNTAX      Counter64
   MAX-ACCESS  read-only
   STATUS      current
   DESCRIPTION
      "Path: ethernet1.performance.ifInHwPriorityQueues.h2Performance.totalPkts

       64 bit unsigned wrappable counter."
   ::= {pr1645v2PortSwIfInHwPriorityQueuesH2PerformanceEntry 234881024}

pr1645v2PortSwIfInHwPriorityQueuesH2PerformanceTotOcts OBJECT-TYPE
   SYNTAX      Counter64
   MAX-ACCESS  read-only
   STATUS      current
   DESCRIPTION
      "Path: ethernet1.performance.ifInHwPriorityQueues.h2Performance.totalOctets

       64 bit unsigned wrappable counter."
   ::= {pr1645v2PortSwIfInHwPriorityQueuesH2PerformanceEntry 251658240}

pr1645v2PortSwIfInHwPriorityQueuesH2PerformanceBandwidth OBJECT-TYPE
   SYNTAX      Integer32
   MAX-ACCESS  read-only
   STATUS      current
   DESCRIPTION
      "Path: ethernet1.performance.ifInHwPriorityQueues.h2Performance.bandwidth

       unit name = bps
       formula = 8 * ; 8 /"
   ::= {pr1645v2PortSwIfInHwPriorityQueuesH2PerformanceEntry 268435456}

pr1645v2PortSwIfInHwPriorityQueuesH24Performance OBJECT-TYPE
   SYNTAX      SEQUENCE OF Pr1645v2PortSwIfInHwPriorityQueuesH24PerformanceEntry
   MAX-ACCESS  not-accessible
   STATUS      current
   DESCRIPTION
      ""
   ::= {pr1645v2PortSwIfInHwPriorityQueues 100663296}

pr1645v2PortSwIfInHwPriorityQueuesH24PerformanceEntry OBJECT-TYPE
   SYNTAX      Pr1645v2PortSwIfInHwPriorityQueuesH24PerformanceEntry
   MAX-ACCESS  not-accessible
   STATUS      current
   DESCRIPTION
      ""
   INDEX      { pr1645v2PortSwIfInHwPriorityQueuesTableIx,
                pr1645v2PortSwIfInHwPriorityQueuesH24PerformanceTableIx }
   ::= {pr1645v2PortSwIfInHwPriorityQueuesH24Performance 1}

Pr1645v2PortSwIfInHwPriorityQueuesH24PerformanceEntry ::=
   SEQUENCE
      {
      pr1645v2PortSwIfInHwPriorityQueuesH24PerformanceTableIx
         TableIndex,
      pr1645v2PortSwIfInHwPriorityQueuesH24PerformanceSysUpTime
         TimeTicks,
      pr1645v2PortSwIfInHwPriorityQueuesH24PerformanceTotPkts
         Counter64,
      pr1645v2PortSwIfInHwPriorityQueuesH24PerformanceTotOcts
         Counter64,
      pr1645v2PortSwIfInHwPriorityQueuesH24PerformanceBandwidth
         Integer32
      }

pr1645v2PortSwIfInHwPriorityQueuesH24PerformanceTableIx OBJECT-TYPE
   SYNTAX      TableIndex
   MAX-ACCESS  not-accessible
   STATUS      current
   DESCRIPTION
      ""
   ::= {pr1645v2PortSwIfInHwPriorityQueuesH24PerformanceEntry 11}

pr1645v2PortSwIfInHwPriorityQueuesH24PerformanceSysUpTime OBJECT-TYPE
   SYNTAX      TimeTicks
   MAX-ACCESS  read-only
   STATUS      current
   DESCRIPTION
      "Path: ethernet1.performance.ifInHwPriorityQueues.h24Performance.sysUpTime

       Time in centi-second."
   ::= {pr1645v2PortSwIfInHwPriorityQueuesH24PerformanceEntry 16777216}

pr1645v2PortSwIfInHwPriorityQueuesH24PerformanceTotPkts OBJECT-TYPE
   SYNTAX      Counter64
   MAX-ACCESS  read-only
   STATUS      current
   DESCRIPTION
      "Path: ethernet1.performance.ifInHwPriorityQueues.h24Performance.totalPkts

       64 bit unsigned wrappable counter."
   ::= {pr1645v2PortSwIfInHwPriorityQueuesH24PerformanceEntry 234881024}

pr1645v2PortSwIfInHwPriorityQueuesH24PerformanceTotOcts OBJECT-TYPE
   SYNTAX      Counter64
   MAX-ACCESS  read-only
   STATUS      current
   DESCRIPTION
      "Path: ethernet1.performance.ifInHwPriorityQueues.h24Performance.totalOctets

       64 bit unsigned wrappable counter."
   ::= {pr1645v2PortSwIfInHwPriorityQueuesH24PerformanceEntry 251658240}

pr1645v2PortSwIfInHwPriorityQueuesH24PerformanceBandwidth OBJECT-TYPE
   SYNTAX      Integer32
   MAX-ACCESS  read-only
   STATUS      current
   DESCRIPTION
      "Path: ethernet1.performance.ifInHwPriorityQueues.h24Performance.bandwidth

       unit name = bps
       formula = 8 * ; 8 /"
   ::= {pr1645v2PortSwIfInHwPriorityQueuesH24PerformanceEntry 268435456}

pr1645v2PortSwIfInHwPriorityQueuesD7Performance OBJECT-TYPE
   SYNTAX      SEQUENCE OF Pr1645v2PortSwIfInHwPriorityQueuesD7PerformanceEntry
   MAX-ACCESS  not-accessible
   STATUS      current
   DESCRIPTION
      ""
   ::= {pr1645v2PortSwIfInHwPriorityQueues 117440512}

pr1645v2PortSwIfInHwPriorityQueuesD7PerformanceEntry OBJECT-TYPE
   SYNTAX      Pr1645v2PortSwIfInHwPriorityQueuesD7PerformanceEntry
   MAX-ACCESS  not-accessible
   STATUS      current
   DESCRIPTION
      ""
   INDEX      { pr1645v2PortSwIfInHwPriorityQueuesTableIx,
                pr1645v2PortSwIfInHwPriorityQueuesD7PerformanceTableIx }
   ::= {pr1645v2PortSwIfInHwPriorityQueuesD7Performance 1}

Pr1645v2PortSwIfInHwPriorityQueuesD7PerformanceEntry ::=
   SEQUENCE
      {
      pr1645v2PortSwIfInHwPriorityQueuesD7PerformanceTableIx
         TableIndex,
      pr1645v2PortSwIfInHwPriorityQueuesD7PerformanceSysUpTime
         TimeTicks,
      pr1645v2PortSwIfInHwPriorityQueuesD7PerformanceTotPkts
         Counter64,
      pr1645v2PortSwIfInHwPriorityQueuesD7PerformanceTotOcts
         Counter64,
      pr1645v2PortSwIfInHwPriorityQueuesD7PerformanceBandwidth
         Integer32
      }

pr1645v2PortSwIfInHwPriorityQueuesD7PerformanceTableIx OBJECT-TYPE
   SYNTAX      TableIndex
   MAX-ACCESS  not-accessible
   STATUS      current
   DESCRIPTION
      ""
   ::= {pr1645v2PortSwIfInHwPriorityQueuesD7PerformanceEntry 11}

pr1645v2PortSwIfInHwPriorityQueuesD7PerformanceSysUpTime OBJECT-TYPE
   SYNTAX      TimeTicks
   MAX-ACCESS  read-only
   STATUS      current
   DESCRIPTION
      "Path: ethernet1.performance.ifInHwPriorityQueues.d7Performance.sysUpTime

       Time in centi-second."
   ::= {pr1645v2PortSwIfInHwPriorityQueuesD7PerformanceEntry 16777216}

pr1645v2PortSwIfInHwPriorityQueuesD7PerformanceTotPkts OBJECT-TYPE
   SYNTAX      Counter64
   MAX-ACCESS  read-only
   STATUS      current
   DESCRIPTION
      "Path: ethernet1.performance.ifInHwPriorityQueues.d7Performance.totalPkts

       64 bit unsigned wrappable counter."
   ::= {pr1645v2PortSwIfInHwPriorityQueuesD7PerformanceEntry 234881024}

pr1645v2PortSwIfInHwPriorityQueuesD7PerformanceTotOcts OBJECT-TYPE
   SYNTAX      Counter64
   MAX-ACCESS  read-only
   STATUS      current
   DESCRIPTION
      "Path: ethernet1.performance.ifInHwPriorityQueues.d7Performance.totalOctets

       64 bit unsigned wrappable counter."
   ::= {pr1645v2PortSwIfInHwPriorityQueuesD7PerformanceEntry 251658240}

pr1645v2PortSwIfInHwPriorityQueuesD7PerformanceBandwidth OBJECT-TYPE
   SYNTAX      Integer32
   MAX-ACCESS  read-only
   STATUS      current
   DESCRIPTION
      "Path: ethernet1.performance.ifInHwPriorityQueues.d7Performance.bandwidth

       unit name = bps
       formula = 8 * ; 8 /"
   ::= {pr1645v2PortSwIfInHwPriorityQueuesD7PerformanceEntry 268435456}


pr1645v2PortSwMibCntrs OBJECT IDENTIFIER ::= {pr1645v2PortSw 198}

pr1645v2PortSwMibCntrsSSCTable OBJECT-TYPE
   SYNTAX      SEQUENCE OF Pr1645v2PortSwMibCntrsEntry
   MAX-ACCESS  not-accessible
   STATUS      current
   DESCRIPTION
      "Ethernet Switch MIB Counters"
   ::= {pr1645v2PortSwMibCntrs 1}

pr1645v2PortSwMibCntrsEntry OBJECT-TYPE
   SYNTAX      Pr1645v2PortSwMibCntrsEntry
   MAX-ACCESS  not-accessible
   STATUS      current
   DESCRIPTION
      ""
   INDEX      { pr1645v2PortSwMibCntrsTableIx }
   ::= {pr1645v2PortSwMibCntrsSSCTable 1}

Pr1645v2PortSwMibCntrsEntry ::=
   SEQUENCE
      {
      pr1645v2PortSwMibCntrsTableIx
         TableIndex,
      pr1645v2PortSwMibCntrsPortName
         INTEGER,
      pr1645v2PortSwMibCntrsInOctets
         Counter64,
      pr1645v2PortSwMibCntrsInUcast
         Counter64,
      pr1645v2PortSwMibCntrsInNUcastPkts
         Counter64,
      pr1645v2PortSwMibCntrsInDiscards
         Counter64,
      pr1645v2PortSwMibCntrsInPause
         Counter64,
      pr1645v2PortSwMibCntrsInErrors
         Counter64,
      pr1645v2PortSwMibCntrsInBandwidth15sec
         Integer32,
      pr1645v2PortSwMibCntrsInBandwidth30sec
         Integer32,
      pr1645v2PortSwMibCntrsInBandwidth1min
         Integer32,
      pr1645v2PortSwMibCntrsInBandwidth2min
         Integer32,
      pr1645v2PortSwMibCntrsInBandwidth5min
         Integer32,
      pr1645v2PortSwMibCntrsOutOctets
         Counter64,
      pr1645v2PortSwMibCntrsOutUcastPkts
         Counter64,
      pr1645v2PortSwMibCntrsOutNUcastPkts
         Counter64,
      pr1645v2PortSwMibCntrsOutDiscards
         Counter64,
      pr1645v2PortSwMibCntrsOutPause
         Counter64,
      pr1645v2PortSwMibCntrsOutErrors
         Counter64,
      pr1645v2PortSwMibCntrsOutBandwidth15sec
         Integer32,
      pr1645v2PortSwMibCntrsOutBandwidth30sec
         Integer32,
      pr1645v2PortSwMibCntrsOutBandwidth1min
         Integer32,
      pr1645v2PortSwMibCntrsOutBandwidth2min
         Integer32,
      pr1645v2PortSwMibCntrsOutBandwidth5min
         Integer32
      }

pr1645v2PortSwMibCntrsTableIx OBJECT-TYPE
   SYNTAX      TableIndex
   MAX-ACCESS  not-accessible
   STATUS      current
   DESCRIPTION
      ""
   ::= {pr1645v2PortSwMibCntrsEntry 11}

pr1645v2PortSwMibCntrsPortName OBJECT-TYPE
   SYNTAX      INTEGER
               {
               hwPortu1 (1),
               hwPortu2 (2),
               hwPortu3 (3),
               hwPortu4 (4),
               hwPortu5 (5),
               hwPortu6 (6),
               hwPortuLocalPort (255)
               }
   MAX-ACCESS  read-only
   STATUS      current
   DESCRIPTION
      "Path: ethernet1.performance.mibCounters.portName

       Possibilities:
               hwPort_1   (1)
               hwPort_2   (2)
               hwPort_3   (3)
               hwPort_4   (4)
               hwPort_5   (5)
               hwPort_6   (6)
               hwPort_LocalPort   (255)"
   ::= {pr1645v2PortSwMibCntrsEntry 16777216}

pr1645v2PortSwMibCntrsInOctets OBJECT-TYPE
   SYNTAX      Counter64
   MAX-ACCESS  read-only
   STATUS      current
   DESCRIPTION
      "Path: ethernet1.performance.mibCounters.ifInOctets

       64 bit unsigned wrappable counter."
   ::= {pr1645v2PortSwMibCntrsEntry 1828716544}

pr1645v2PortSwMibCntrsInUcast OBJECT-TYPE
   SYNTAX      Counter64
   MAX-ACCESS  read-only
   STATUS      current
   DESCRIPTION
      "Path: ethernet1.performance.mibCounters.ifInUcastPkts

       64 bit unsigned wrappable counter."
   ::= {pr1645v2PortSwMibCntrsEntry 1845493760}

pr1645v2PortSwMibCntrsInNUcastPkts OBJECT-TYPE
   SYNTAX      Counter64
   MAX-ACCESS  read-only
   STATUS      current
   DESCRIPTION
      "Path: ethernet1.performance.mibCounters.ifInNUcastPkts

       64 bit unsigned wrappable counter."
   ::= {pr1645v2PortSwMibCntrsEntry 1862270976}

pr1645v2PortSwMibCntrsInDiscards OBJECT-TYPE
   SYNTAX      Counter64
   MAX-ACCESS  read-only
   STATUS      current
   DESCRIPTION
      "Path: ethernet1.performance.mibCounters.ifInDiscards

       64 bit unsigned wrappable counter."
   ::= {pr1645v2PortSwMibCntrsEntry 1879048192}

pr1645v2PortSwMibCntrsInPause OBJECT-TYPE
   SYNTAX      Counter64
   MAX-ACCESS  read-only
   STATUS      current
   DESCRIPTION
      "Path: ethernet1.performance.mibCounters.ifInPause

       64 bit unsigned wrappable counter."
   ::= {pr1645v2PortSwMibCntrsEntry 4194304000}

pr1645v2PortSwMibCntrsInErrors OBJECT-TYPE
   SYNTAX      Counter64
   MAX-ACCESS  read-only
   STATUS      current
   DESCRIPTION
      "Path: ethernet1.performance.mibCounters.ifInErrors

       64 bit unsigned wrappable counter."
   ::= {pr1645v2PortSwMibCntrsEntry 1895825408}

pr1645v2PortSwMibCntrsInBandwidth15sec OBJECT-TYPE
   SYNTAX      Integer32
   MAX-ACCESS  read-only
   STATUS      current
   DESCRIPTION
      "Path: ethernet1.performance.mibCounters.ifInBandwidth.15sec

       unit name = bps
       formula = 8 * ; 8 /"
   ::= {pr1645v2PortSwMibCntrsEntry 3037003776}

pr1645v2PortSwMibCntrsInBandwidth30sec OBJECT-TYPE
   SYNTAX      Integer32
   MAX-ACCESS  read-only
   STATUS      current
   DESCRIPTION
      "Path: ethernet1.performance.mibCounters.ifInBandwidth.30sec

       unit name = bps
       formula = 8 * ; 8 /"
   ::= {pr1645v2PortSwMibCntrsEntry 3037331456}

pr1645v2PortSwMibCntrsInBandwidth1min OBJECT-TYPE
   SYNTAX      Integer32
   MAX-ACCESS  read-only
   STATUS      current
   DESCRIPTION
      "Path: ethernet1.performance.mibCounters.ifInBandwidth.1min

       unit name = bps
       formula = 8 * ; 8 /"
   ::= {pr1645v2PortSwMibCntrsEntry 3037986816}

pr1645v2PortSwMibCntrsInBandwidth2min OBJECT-TYPE
   SYNTAX      Integer32
   MAX-ACCESS  read-only
   STATUS      current
   DESCRIPTION
      "Path: ethernet1.performance.mibCounters.ifInBandwidth.2min

       unit name = bps
       formula = 8 * ; 8 /"
   ::= {pr1645v2PortSwMibCntrsEntry 3039297536}

pr1645v2PortSwMibCntrsInBandwidth5min OBJECT-TYPE
   SYNTAX      Integer32
   MAX-ACCESS  read-only
   STATUS      current
   DESCRIPTION
      "Path: ethernet1.performance.mibCounters.ifInBandwidth.5min

       unit name = bps
       formula = 8 * ; 8 /"
   ::= {pr1645v2PortSwMibCntrsEntry 3043229696}

pr1645v2PortSwMibCntrsOutOctets OBJECT-TYPE
   SYNTAX      Counter64
   MAX-ACCESS  read-only
   STATUS      current
   DESCRIPTION
      "Path: ethernet1.performance.mibCounters.ifOutOctets

       64 bit unsigned wrappable counter."
   ::= {pr1645v2PortSwMibCntrsEntry 1929379840}

pr1645v2PortSwMibCntrsOutUcastPkts OBJECT-TYPE
   SYNTAX      Counter64
   MAX-ACCESS  read-only
   STATUS      current
   DESCRIPTION
      "Path: ethernet1.performance.mibCounters.ifOutUcastPkts

       64 bit unsigned wrappable counter."
   ::= {pr1645v2PortSwMibCntrsEntry 1946157056}

pr1645v2PortSwMibCntrsOutNUcastPkts OBJECT-TYPE
   SYNTAX      Counter64
   MAX-ACCESS  read-only
   STATUS      current
   DESCRIPTION
      "Path: ethernet1.performance.mibCounters.ifOutNUcastPkts

       64 bit unsigned wrappable counter."
   ::= {pr1645v2PortSwMibCntrsEntry 1962934272}

pr1645v2PortSwMibCntrsOutDiscards OBJECT-TYPE
   SYNTAX      Counter64
   MAX-ACCESS  read-only
   STATUS      current
   DESCRIPTION
      "Path: ethernet1.performance.mibCounters.ifOutDiscards

       64 bit unsigned wrappable counter."
   ::= {pr1645v2PortSwMibCntrsEntry 1979711488}

pr1645v2PortSwMibCntrsOutPause OBJECT-TYPE
   SYNTAX      Counter64
   MAX-ACCESS  read-only
   STATUS      current
   DESCRIPTION
      "Path: ethernet1.performance.mibCounters.ifOutPause

       64 bit unsigned wrappable counter."
   ::= {pr1645v2PortSwMibCntrsEntry 4211081216}

pr1645v2PortSwMibCntrsOutErrors OBJECT-TYPE
   SYNTAX      Counter64
   MAX-ACCESS  read-only
   STATUS      current
   DESCRIPTION
      "Path: ethernet1.performance.mibCounters.ifOutErrors

       64 bit unsigned wrappable counter."
   ::= {pr1645v2PortSwMibCntrsEntry 1996488704}

pr1645v2PortSwMibCntrsOutBandwidth15sec OBJECT-TYPE
   SYNTAX      Integer32
   MAX-ACCESS  read-only
   STATUS      current
   DESCRIPTION
      "Path: ethernet1.performance.mibCounters.ifOutBandwidth.15sec

       unit name = bps
       formula = 8 * ; 8 /"
   ::= {pr1645v2PortSwMibCntrsEntry 3053780992}

pr1645v2PortSwMibCntrsOutBandwidth30sec OBJECT-TYPE
   SYNTAX      Integer32
   MAX-ACCESS  read-only
   STATUS      current
   DESCRIPTION
      "Path: ethernet1.performance.mibCounters.ifOutBandwidth.30sec

       unit name = bps
       formula = 8 * ; 8 /"
   ::= {pr1645v2PortSwMibCntrsEntry 3054108672}

pr1645v2PortSwMibCntrsOutBandwidth1min OBJECT-TYPE
   SYNTAX      Integer32
   MAX-ACCESS  read-only
   STATUS      current
   DESCRIPTION
      "Path: ethernet1.performance.mibCounters.ifOutBandwidth.1min

       unit name = bps
       formula = 8 * ; 8 /"
   ::= {pr1645v2PortSwMibCntrsEntry 3054764032}

pr1645v2PortSwMibCntrsOutBandwidth2min OBJECT-TYPE
   SYNTAX      Integer32
   MAX-ACCESS  read-only
   STATUS      current
   DESCRIPTION
      "Path: ethernet1.performance.mibCounters.ifOutBandwidth.2min

       unit name = bps
       formula = 8 * ; 8 /"
   ::= {pr1645v2PortSwMibCntrsEntry 3056074752}

pr1645v2PortSwMibCntrsOutBandwidth5min OBJECT-TYPE
   SYNTAX      Integer32
   MAX-ACCESS  read-only
   STATUS      current
   DESCRIPTION
      "Path: ethernet1.performance.mibCounters.ifOutBandwidth.5min

       unit name = bps
       formula = 8 * ; 8 /"
   ::= {pr1645v2PortSwMibCntrsEntry 3060006912}

pr1645v2PortSwMibCntrsH2P OBJECT-TYPE
   SYNTAX      SEQUENCE OF Pr1645v2PortSwMibCntrsH2PEntry
   MAX-ACCESS  not-accessible
   STATUS      current
   DESCRIPTION
      ""
   ::= {pr1645v2PortSwMibCntrs 2046820352}

pr1645v2PortSwMibCntrsH2PEntry OBJECT-TYPE
   SYNTAX      Pr1645v2PortSwMibCntrsH2PEntry
   MAX-ACCESS  not-accessible
   STATUS      current
   DESCRIPTION
      ""
   INDEX      { pr1645v2PortSwMibCntrsTableIx,
                pr1645v2PortSwMibCntrsH2PTableIx }
   ::= {pr1645v2PortSwMibCntrsH2P 1}

Pr1645v2PortSwMibCntrsH2PEntry ::=
   SEQUENCE
      {
      pr1645v2PortSwMibCntrsH2PTableIx
         TableIndex,
      pr1645v2PortSwMibCntrsH2PSysUpTime
         TimeTicks,
      pr1645v2PortSwMibCntrsH2PIfUpTime
         TimeTicks,
      pr1645v2PortSwMibCntrsH2PIfStatChanges
         Counter32,
      pr1645v2PortSwMibCntrsH2PIfInOctets
         Counter64,
      pr1645v2PortSwMibCntrsH2PIfInUCPkts
         Counter64,
      pr1645v2PortSwMibCntrsH2PIfInNUCPkts
         Counter64,
      pr1645v2PortSwMibCntrsH2PIfInDiscards
         Counter64,
      pr1645v2PortSwMibCntrsH2PIfInErrors
         Counter64,
      pr1645v2PortSwMibCntrsH2PIfInBandwidth
         Integer32,
      pr1645v2PortSwMibCntrsH2PIfOutOctets
         Counter64,
      pr1645v2PortSwMibCntrsH2PIfOutUCPkts
         Counter64,
      pr1645v2PortSwMibCntrsH2PIfOutNUCPkts
         Counter64,
      pr1645v2PortSwMibCntrsH2PIfOutDiscards
         Counter64,
      pr1645v2PortSwMibCntrsH2PIfOutErrors
         Counter64,
      pr1645v2PortSwMibCntrsH2PIfOutBandwidth
         Integer32,
      pr1645v2PortSwMibCntrsH2PIfErrSec
         Counter32
      }

pr1645v2PortSwMibCntrsH2PTableIx OBJECT-TYPE
   SYNTAX      TableIndex
   MAX-ACCESS  not-accessible
   STATUS      current
   DESCRIPTION
      ""
   ::= {pr1645v2PortSwMibCntrsH2PEntry 11}

pr1645v2PortSwMibCntrsH2PSysUpTime OBJECT-TYPE
   SYNTAX      TimeTicks
   MAX-ACCESS  read-only
   STATUS      current
   DESCRIPTION
      "Path: ethernet1.performance.mibCounters.h2Performance.sysUpTime

       Time in centi-second."
   ::= {pr1645v2PortSwMibCntrsH2PEntry 16777216}

pr1645v2PortSwMibCntrsH2PIfUpTime OBJECT-TYPE
   SYNTAX      TimeTicks
   MAX-ACCESS  read-only
   STATUS      current
   DESCRIPTION
      "Path: ethernet1.performance.mibCounters.h2Performance.ifUpTime

       Time in centi-second."
   ::= {pr1645v2PortSwMibCntrsH2PEntry 33554432}

pr1645v2PortSwMibCntrsH2PIfStatChanges OBJECT-TYPE
   SYNTAX      Counter32
   MAX-ACCESS  read-only
   STATUS      current
   DESCRIPTION
      "Path: ethernet1.performance.mibCounters.h2Performance.ifStatusChanges

       32 bit unsigned wrappable counter."
   ::= {pr1645v2PortSwMibCntrsH2PEntry 50331648}

pr1645v2PortSwMibCntrsH2PIfInOctets OBJECT-TYPE
   SYNTAX      Counter64
   MAX-ACCESS  read-only
   STATUS      current
   DESCRIPTION
      "Path: ethernet1.performance.mibCounters.h2Performance.ifInOctets

       64 bit unsigned wrappable counter."
   ::= {pr1645v2PortSwMibCntrsH2PEntry 67108864}

pr1645v2PortSwMibCntrsH2PIfInUCPkts OBJECT-TYPE
   SYNTAX      Counter64
   MAX-ACCESS  read-only
   STATUS      current
   DESCRIPTION
      "Path: ethernet1.performance.mibCounters.h2Performance.ifInUcastPkts

       64 bit unsigned wrappable counter."
   ::= {pr1645v2PortSwMibCntrsH2PEntry 83886080}

pr1645v2PortSwMibCntrsH2PIfInNUCPkts OBJECT-TYPE
   SYNTAX      Counter64
   MAX-ACCESS  read-only
   STATUS      current
   DESCRIPTION
      "Path: ethernet1.performance.mibCounters.h2Performance.ifInNUcastPkts

       64 bit unsigned wrappable counter."
   ::= {pr1645v2PortSwMibCntrsH2PEntry 100663296}

pr1645v2PortSwMibCntrsH2PIfInDiscards OBJECT-TYPE
   SYNTAX      Counter64
   MAX-ACCESS  read-only
   STATUS      current
   DESCRIPTION
      "Path: ethernet1.performance.mibCounters.h2Performance.ifInDiscards

       64 bit unsigned wrappable counter."
   ::= {pr1645v2PortSwMibCntrsH2PEntry 117440512}

pr1645v2PortSwMibCntrsH2PIfInErrors OBJECT-TYPE
   SYNTAX      Counter64
   MAX-ACCESS  read-only
   STATUS      current
   DESCRIPTION
      "Path: ethernet1.performance.mibCounters.h2Performance.ifInErrors

       64 bit unsigned wrappable counter."
   ::= {pr1645v2PortSwMibCntrsH2PEntry 134217728}

pr1645v2PortSwMibCntrsH2PIfInBandwidth OBJECT-TYPE
   SYNTAX      Integer32
   MAX-ACCESS  read-only
   STATUS      current
   DESCRIPTION
      "Path: ethernet1.performance.mibCounters.h2Performance.ifInBandwidth

       unit name = bps
       formula = 8 * ; 8 /"
   ::= {pr1645v2PortSwMibCntrsH2PEntry 268435456}

pr1645v2PortSwMibCntrsH2PIfOutOctets OBJECT-TYPE
   SYNTAX      Counter64
   MAX-ACCESS  read-only
   STATUS      current
   DESCRIPTION
      "Path: ethernet1.performance.mibCounters.h2Performance.ifOutOctets

       64 bit unsigned wrappable counter."
   ::= {pr1645v2PortSwMibCntrsH2PEntry 167772160}

pr1645v2PortSwMibCntrsH2PIfOutUCPkts OBJECT-TYPE
   SYNTAX      Counter64
   MAX-ACCESS  read-only
   STATUS      current
   DESCRIPTION
      "Path: ethernet1.performance.mibCounters.h2Performance.ifOutUcastPkts

       64 bit unsigned wrappable counter."
   ::= {pr1645v2PortSwMibCntrsH2PEntry 184549376}

pr1645v2PortSwMibCntrsH2PIfOutNUCPkts OBJECT-TYPE
   SYNTAX      Counter64
   MAX-ACCESS  read-only
   STATUS      current
   DESCRIPTION
      "Path: ethernet1.performance.mibCounters.h2Performance.ifOutNUcastPkts

       64 bit unsigned wrappable counter."
   ::= {pr1645v2PortSwMibCntrsH2PEntry 201326592}

pr1645v2PortSwMibCntrsH2PIfOutDiscards OBJECT-TYPE
   SYNTAX      Counter64
   MAX-ACCESS  read-only
   STATUS      current
   DESCRIPTION
      "Path: ethernet1.performance.mibCounters.h2Performance.ifOutDiscards

       64 bit unsigned wrappable counter."
   ::= {pr1645v2PortSwMibCntrsH2PEntry 218103808}

pr1645v2PortSwMibCntrsH2PIfOutErrors OBJECT-TYPE
   SYNTAX      Counter64
   MAX-ACCESS  read-only
   STATUS      current
   DESCRIPTION
      "Path: ethernet1.performance.mibCounters.h2Performance.ifOutErrors

       64 bit unsigned wrappable counter."
   ::= {pr1645v2PortSwMibCntrsH2PEntry 234881024}

pr1645v2PortSwMibCntrsH2PIfOutBandwidth OBJECT-TYPE
   SYNTAX      Integer32
   MAX-ACCESS  read-only
   STATUS      current
   DESCRIPTION
      "Path: ethernet1.performance.mibCounters.h2Performance.ifOutBandwidth

       unit name = bps
       formula = 8 * ; 8 /"
   ::= {pr1645v2PortSwMibCntrsH2PEntry 285212672}

pr1645v2PortSwMibCntrsH2PIfErrSec OBJECT-TYPE
   SYNTAX      Counter32
   MAX-ACCESS  read-only
   STATUS      current
   DESCRIPTION
      "Path: ethernet1.performance.mibCounters.h2Performance.ifErrSec

       32 bit unsigned wrappable counter."
   ::= {pr1645v2PortSwMibCntrsH2PEntry 251658240}

pr1645v2PortSwMibCntrsH24P OBJECT-TYPE
   SYNTAX      SEQUENCE OF Pr1645v2PortSwMibCntrsH24PEntry
   MAX-ACCESS  not-accessible
   STATUS      current
   DESCRIPTION
      ""
   ::= {pr1645v2PortSwMibCntrs 2063597568}

pr1645v2PortSwMibCntrsH24PEntry OBJECT-TYPE
   SYNTAX      Pr1645v2PortSwMibCntrsH24PEntry
   MAX-ACCESS  not-accessible
   STATUS      current
   DESCRIPTION
      ""
   INDEX      { pr1645v2PortSwMibCntrsTableIx,
                pr1645v2PortSwMibCntrsH24PTableIx }
   ::= {pr1645v2PortSwMibCntrsH24P 1}

Pr1645v2PortSwMibCntrsH24PEntry ::=
   SEQUENCE
      {
      pr1645v2PortSwMibCntrsH24PTableIx
         TableIndex,
      pr1645v2PortSwMibCntrsH24PSysUpTime
         TimeTicks,
      pr1645v2PortSwMibCntrsH24PIfUpTime
         TimeTicks,
      pr1645v2PortSwMibCntrsH24PIfStatChanges
         Counter32,
      pr1645v2PortSwMibCntrsH24PIfInOctets
         Counter64,
      pr1645v2PortSwMibCntrsH24PIfInUCPkts
         Counter64,
      pr1645v2PortSwMibCntrsH24PIfInNUCPkts
         Counter64,
      pr1645v2PortSwMibCntrsH24PIfInDiscards
         Counter64,
      pr1645v2PortSwMibCntrsH24PIfInErrors
         Counter64,
      pr1645v2PortSwMibCntrsH24PIfInBandwidth
         Integer32,
      pr1645v2PortSwMibCntrsH24PIfOutOctets
         Counter64,
      pr1645v2PortSwMibCntrsH24PIfOutUCPkts
         Counter64,
      pr1645v2PortSwMibCntrsH24PIfOutNUCPkts
         Counter64,
      pr1645v2PortSwMibCntrsH24PIfOutDiscards
         Counter64,
      pr1645v2PortSwMibCntrsH24PIfOutErrors
         Counter64,
      pr1645v2PortSwMibCntrsH24PIfOutBandwidth
         Integer32,
      pr1645v2PortSwMibCntrsH24PIfErrSec
         Counter32
      }

pr1645v2PortSwMibCntrsH24PTableIx OBJECT-TYPE
   SYNTAX      TableIndex
   MAX-ACCESS  not-accessible
   STATUS      current
   DESCRIPTION
      ""
   ::= {pr1645v2PortSwMibCntrsH24PEntry 11}

pr1645v2PortSwMibCntrsH24PSysUpTime OBJECT-TYPE
   SYNTAX      TimeTicks
   MAX-ACCESS  read-only
   STATUS      current
   DESCRIPTION
      "Path: ethernet1.performance.mibCounters.h24Performance.sysUpTime

       Time in centi-second."
   ::= {pr1645v2PortSwMibCntrsH24PEntry 16777216}

pr1645v2PortSwMibCntrsH24PIfUpTime OBJECT-TYPE
   SYNTAX      TimeTicks
   MAX-ACCESS  read-only
   STATUS      current
   DESCRIPTION
      "Path: ethernet1.performance.mibCounters.h24Performance.ifUpTime

       Time in centi-second."
   ::= {pr1645v2PortSwMibCntrsH24PEntry 33554432}

pr1645v2PortSwMibCntrsH24PIfStatChanges OBJECT-TYPE
   SYNTAX      Counter32
   MAX-ACCESS  read-only
   STATUS      current
   DESCRIPTION
      "Path: ethernet1.performance.mibCounters.h24Performance.ifStatusChanges

       32 bit unsigned wrappable counter."
   ::= {pr1645v2PortSwMibCntrsH24PEntry 50331648}

pr1645v2PortSwMibCntrsH24PIfInOctets OBJECT-TYPE
   SYNTAX      Counter64
   MAX-ACCESS  read-only
   STATUS      current
   DESCRIPTION
      "Path: ethernet1.performance.mibCounters.h24Performance.ifInOctets

       64 bit unsigned wrappable counter."
   ::= {pr1645v2PortSwMibCntrsH24PEntry 67108864}

pr1645v2PortSwMibCntrsH24PIfInUCPkts OBJECT-TYPE
   SYNTAX      Counter64
   MAX-ACCESS  read-only
   STATUS      current
   DESCRIPTION
      "Path: ethernet1.performance.mibCounters.h24Performance.ifInUcastPkts

       64 bit unsigned wrappable counter."
   ::= {pr1645v2PortSwMibCntrsH24PEntry 83886080}

pr1645v2PortSwMibCntrsH24PIfInNUCPkts OBJECT-TYPE
   SYNTAX      Counter64
   MAX-ACCESS  read-only
   STATUS      current
   DESCRIPTION
      "Path: ethernet1.performance.mibCounters.h24Performance.ifInNUcastPkts

       64 bit unsigned wrappable counter."
   ::= {pr1645v2PortSwMibCntrsH24PEntry 100663296}

pr1645v2PortSwMibCntrsH24PIfInDiscards OBJECT-TYPE
   SYNTAX      Counter64
   MAX-ACCESS  read-only
   STATUS      current
   DESCRIPTION
      "Path: ethernet1.performance.mibCounters.h24Performance.ifInDiscards

       64 bit unsigned wrappable counter."
   ::= {pr1645v2PortSwMibCntrsH24PEntry 117440512}

pr1645v2PortSwMibCntrsH24PIfInErrors OBJECT-TYPE
   SYNTAX      Counter64
   MAX-ACCESS  read-only
   STATUS      current
   DESCRIPTION
      "Path: ethernet1.performance.mibCounters.h24Performance.ifInErrors

       64 bit unsigned wrappable counter."
   ::= {pr1645v2PortSwMibCntrsH24PEntry 134217728}

pr1645v2PortSwMibCntrsH24PIfInBandwidth OBJECT-TYPE
   SYNTAX      Integer32
   MAX-ACCESS  read-only
   STATUS      current
   DESCRIPTION
      "Path: ethernet1.performance.mibCounters.h24Performance.ifInBandwidth

       unit name = bps
       formula = 8 * ; 8 /"
   ::= {pr1645v2PortSwMibCntrsH24PEntry 268435456}

pr1645v2PortSwMibCntrsH24PIfOutOctets OBJECT-TYPE
   SYNTAX      Counter64
   MAX-ACCESS  read-only
   STATUS      current
   DESCRIPTION
      "Path: ethernet1.performance.mibCounters.h24Performance.ifOutOctets

       64 bit unsigned wrappable counter."
   ::= {pr1645v2PortSwMibCntrsH24PEntry 167772160}

pr1645v2PortSwMibCntrsH24PIfOutUCPkts OBJECT-TYPE
   SYNTAX      Counter64
   MAX-ACCESS  read-only
   STATUS      current
   DESCRIPTION
      "Path: ethernet1.performance.mibCounters.h24Performance.ifOutUcastPkts

       64 bit unsigned wrappable counter."
   ::= {pr1645v2PortSwMibCntrsH24PEntry 184549376}

pr1645v2PortSwMibCntrsH24PIfOutNUCPkts OBJECT-TYPE
   SYNTAX      Counter64
   MAX-ACCESS  read-only
   STATUS      current
   DESCRIPTION
      "Path: ethernet1.performance.mibCounters.h24Performance.ifOutNUcastPkts

       64 bit unsigned wrappable counter."
   ::= {pr1645v2PortSwMibCntrsH24PEntry 201326592}

pr1645v2PortSwMibCntrsH24PIfOutDiscards OBJECT-TYPE
   SYNTAX      Counter64
   MAX-ACCESS  read-only
   STATUS      current
   DESCRIPTION
      "Path: ethernet1.performance.mibCounters.h24Performance.ifOutDiscards

       64 bit unsigned wrappable counter."
   ::= {pr1645v2PortSwMibCntrsH24PEntry 218103808}

pr1645v2PortSwMibCntrsH24PIfOutErrors OBJECT-TYPE
   SYNTAX      Counter64
   MAX-ACCESS  read-only
   STATUS      current
   DESCRIPTION
      "Path: ethernet1.performance.mibCounters.h24Performance.ifOutErrors

       64 bit unsigned wrappable counter."
   ::= {pr1645v2PortSwMibCntrsH24PEntry 234881024}

pr1645v2PortSwMibCntrsH24PIfOutBandwidth OBJECT-TYPE
   SYNTAX      Integer32
   MAX-ACCESS  read-only
   STATUS      current
   DESCRIPTION
      "Path: ethernet1.performance.mibCounters.h24Performance.ifOutBandwidth

       unit name = bps
       formula = 8 * ; 8 /"
   ::= {pr1645v2PortSwMibCntrsH24PEntry 285212672}

pr1645v2PortSwMibCntrsH24PIfErrSec OBJECT-TYPE
   SYNTAX      Counter32
   MAX-ACCESS  read-only
   STATUS      current
   DESCRIPTION
      "Path: ethernet1.performance.mibCounters.h24Performance.ifErrSec

       32 bit unsigned wrappable counter."
   ::= {pr1645v2PortSwMibCntrsH24PEntry 251658240}

pr1645v2PortSwMibCntrsD7P OBJECT-TYPE
   SYNTAX      SEQUENCE OF Pr1645v2PortSwMibCntrsD7PEntry
   MAX-ACCESS  not-accessible
   STATUS      current
   DESCRIPTION
      ""
   ::= {pr1645v2PortSwMibCntrs 2080374784}

pr1645v2PortSwMibCntrsD7PEntry OBJECT-TYPE
   SYNTAX      Pr1645v2PortSwMibCntrsD7PEntry
   MAX-ACCESS  not-accessible
   STATUS      current
   DESCRIPTION
      ""
   INDEX      { pr1645v2PortSwMibCntrsTableIx,
                pr1645v2PortSwMibCntrsD7PTableIx }
   ::= {pr1645v2PortSwMibCntrsD7P 1}

Pr1645v2PortSwMibCntrsD7PEntry ::=
   SEQUENCE
      {
      pr1645v2PortSwMibCntrsD7PTableIx
         TableIndex,
      pr1645v2PortSwMibCntrsD7PSysUpTime
         TimeTicks,
      pr1645v2PortSwMibCntrsD7PIfUpTime
         TimeTicks,
      pr1645v2PortSwMibCntrsD7PIfStatChanges
         Counter32,
      pr1645v2PortSwMibCntrsD7PIfInOctets
         Counter64,
      pr1645v2PortSwMibCntrsD7PIfInUCPkts
         Counter64,
      pr1645v2PortSwMibCntrsD7PIfInNUCPkts
         Counter64,
      pr1645v2PortSwMibCntrsD7PIfInDiscards
         Counter64,
      pr1645v2PortSwMibCntrsD7PIfInErrors
         Counter64,
      pr1645v2PortSwMibCntrsD7PIfInBandwidth
         Integer32,
      pr1645v2PortSwMibCntrsD7PIfOutOctets
         Counter64,
      pr1645v2PortSwMibCntrsD7PIfOutUCPkts
         Counter64,
      pr1645v2PortSwMibCntrsD7PIfOutNUCPkts
         Counter64,
      pr1645v2PortSwMibCntrsD7PIfOutDiscards
         Counter64,
      pr1645v2PortSwMibCntrsD7PIfOutErrors
         Counter64,
      pr1645v2PortSwMibCntrsD7PIfOutBandwidth
         Integer32,
      pr1645v2PortSwMibCntrsD7PIfErrSec
         Counter32
      }

pr1645v2PortSwMibCntrsD7PTableIx OBJECT-TYPE
   SYNTAX      TableIndex
   MAX-ACCESS  not-accessible
   STATUS      current
   DESCRIPTION
      ""
   ::= {pr1645v2PortSwMibCntrsD7PEntry 11}

pr1645v2PortSwMibCntrsD7PSysUpTime OBJECT-TYPE
   SYNTAX      TimeTicks
   MAX-ACCESS  read-only
   STATUS      current
   DESCRIPTION
      "Path: ethernet1.performance.mibCounters.d7Performance.sysUpTime

       Time in centi-second."
   ::= {pr1645v2PortSwMibCntrsD7PEntry 16777216}

pr1645v2PortSwMibCntrsD7PIfUpTime OBJECT-TYPE
   SYNTAX      TimeTicks
   MAX-ACCESS  read-only
   STATUS      current
   DESCRIPTION
      "Path: ethernet1.performance.mibCounters.d7Performance.ifUpTime

       Time in centi-second."
   ::= {pr1645v2PortSwMibCntrsD7PEntry 33554432}

pr1645v2PortSwMibCntrsD7PIfStatChanges OBJECT-TYPE
   SYNTAX      Counter32
   MAX-ACCESS  read-only
   STATUS      current
   DESCRIPTION
      "Path: ethernet1.performance.mibCounters.d7Performance.ifStatusChanges

       32 bit unsigned wrappable counter."
   ::= {pr1645v2PortSwMibCntrsD7PEntry 50331648}

pr1645v2PortSwMibCntrsD7PIfInOctets OBJECT-TYPE
   SYNTAX      Counter64
   MAX-ACCESS  read-only
   STATUS      current
   DESCRIPTION
      "Path: ethernet1.performance.mibCounters.d7Performance.ifInOctets

       64 bit unsigned wrappable counter."
   ::= {pr1645v2PortSwMibCntrsD7PEntry 67108864}

pr1645v2PortSwMibCntrsD7PIfInUCPkts OBJECT-TYPE
   SYNTAX      Counter64
   MAX-ACCESS  read-only
   STATUS      current
   DESCRIPTION
      "Path: ethernet1.performance.mibCounters.d7Performance.ifInUcastPkts

       64 bit unsigned wrappable counter."
   ::= {pr1645v2PortSwMibCntrsD7PEntry 83886080}

pr1645v2PortSwMibCntrsD7PIfInNUCPkts OBJECT-TYPE
   SYNTAX      Counter64
   MAX-ACCESS  read-only
   STATUS      current
   DESCRIPTION
      "Path: ethernet1.performance.mibCounters.d7Performance.ifInNUcastPkts

       64 bit unsigned wrappable counter."
   ::= {pr1645v2PortSwMibCntrsD7PEntry 100663296}

pr1645v2PortSwMibCntrsD7PIfInDiscards OBJECT-TYPE
   SYNTAX      Counter64
   MAX-ACCESS  read-only
   STATUS      current
   DESCRIPTION
      "Path: ethernet1.performance.mibCounters.d7Performance.ifInDiscards

       64 bit unsigned wrappable counter."
   ::= {pr1645v2PortSwMibCntrsD7PEntry 117440512}

pr1645v2PortSwMibCntrsD7PIfInErrors OBJECT-TYPE
   SYNTAX      Counter64
   MAX-ACCESS  read-only
   STATUS      current
   DESCRIPTION
      "Path: ethernet1.performance.mibCounters.d7Performance.ifInErrors

       64 bit unsigned wrappable counter."
   ::= {pr1645v2PortSwMibCntrsD7PEntry 134217728}

pr1645v2PortSwMibCntrsD7PIfInBandwidth OBJECT-TYPE
   SYNTAX      Integer32
   MAX-ACCESS  read-only
   STATUS      current
   DESCRIPTION
      "Path: ethernet1.performance.mibCounters.d7Performance.ifInBandwidth

       unit name = bps
       formula = 8 * ; 8 /"
   ::= {pr1645v2PortSwMibCntrsD7PEntry 268435456}

pr1645v2PortSwMibCntrsD7PIfOutOctets OBJECT-TYPE
   SYNTAX      Counter64
   MAX-ACCESS  read-only
   STATUS      current
   DESCRIPTION
      "Path: ethernet1.performance.mibCounters.d7Performance.ifOutOctets

       64 bit unsigned wrappable counter."
   ::= {pr1645v2PortSwMibCntrsD7PEntry 167772160}

pr1645v2PortSwMibCntrsD7PIfOutUCPkts OBJECT-TYPE
   SYNTAX      Counter64
   MAX-ACCESS  read-only
   STATUS      current
   DESCRIPTION
      "Path: ethernet1.performance.mibCounters.d7Performance.ifOutUcastPkts

       64 bit unsigned wrappable counter."
   ::= {pr1645v2PortSwMibCntrsD7PEntry 184549376}

pr1645v2PortSwMibCntrsD7PIfOutNUCPkts OBJECT-TYPE
   SYNTAX      Counter64
   MAX-ACCESS  read-only
   STATUS      current
   DESCRIPTION
      "Path: ethernet1.performance.mibCounters.d7Performance.ifOutNUcastPkts

       64 bit unsigned wrappable counter."
   ::= {pr1645v2PortSwMibCntrsD7PEntry 201326592}

pr1645v2PortSwMibCntrsD7PIfOutDiscards OBJECT-TYPE
   SYNTAX      Counter64
   MAX-ACCESS  read-only
   STATUS      current
   DESCRIPTION
      "Path: ethernet1.performance.mibCounters.d7Performance.ifOutDiscards

       64 bit unsigned wrappable counter."
   ::= {pr1645v2PortSwMibCntrsD7PEntry 218103808}

pr1645v2PortSwMibCntrsD7PIfOutErrors OBJECT-TYPE
   SYNTAX      Counter64
   MAX-ACCESS  read-only
   STATUS      current
   DESCRIPTION
      "Path: ethernet1.performance.mibCounters.d7Performance.ifOutErrors

       64 bit unsigned wrappable counter."
   ::= {pr1645v2PortSwMibCntrsD7PEntry 234881024}

pr1645v2PortSwMibCntrsD7PIfOutBandwidth OBJECT-TYPE
   SYNTAX      Integer32
   MAX-ACCESS  read-only
   STATUS      current
   DESCRIPTION
      "Path: ethernet1.performance.mibCounters.d7Performance.ifOutBandwidth

       unit name = bps
       formula = 8 * ; 8 /"
   ::= {pr1645v2PortSwMibCntrsD7PEntry 285212672}

pr1645v2PortSwMibCntrsD7PIfErrSec OBJECT-TYPE
   SYNTAX      Counter32
   MAX-ACCESS  read-only
   STATUS      current
   DESCRIPTION
      "Path: ethernet1.performance.mibCounters.d7Performance.ifErrSec

       32 bit unsigned wrappable counter."
   ::= {pr1645v2PortSwMibCntrsD7PEntry 251658240}



fr1645v2PortSw OBJECT IDENTIFIER ::= {r1645v2PortSw 13}


fr1645v2PortSwAlarm OBJECT IDENTIFIER ::= {fr1645v2PortSw 207}

fr1645v2PortSwAlarmSSC OBJECT IDENTIFIER ::= {fr1645v2PortSwAlarm 1}

fr1645v2PortSwAlarmEntry OBJECT IDENTIFIER ::= {fr1645v2PortSwAlarmSSC 1}

fr1645v2PortSwAlarmDiscriminator OBJECT-TYPE
   SYNTAX      Integer32
   MAX-ACCESS  read-only
   STATUS      current
   DESCRIPTION
      "Path: ethernet1.alarms.alarmInfo.discriminator"
   ::= {fr1645v2PortSwAlarmEntry 16777216}

fr1645v2PortSwAlarmCurrent OBJECT-TYPE
   SYNTAX      Integer32
   MAX-ACCESS  read-only
   STATUS      current
   DESCRIPTION
      "Path: ethernet1.alarms.alarmInfo.currentAlarms

       Bit meanings:
               bit 0 = linkDown"
   ::= {fr1645v2PortSwAlarmEntry 33554432}

fr1645v2PortSwAlarmPrevious OBJECT-TYPE
   SYNTAX      Integer32
   MAX-ACCESS  read-only
   STATUS      current
   DESCRIPTION
      "Path: ethernet1.alarms.alarmInfo.previousAlarms

       Bit meanings:
               bit 0 = linkDown"
   ::= {fr1645v2PortSwAlarmEntry 50331648}

fr1645v2PortSwAlarmMask OBJECT-TYPE
   SYNTAX      Integer32
   MAX-ACCESS  read-only
   STATUS      current
   DESCRIPTION
      "Path: ethernet1.alarms.alarmInfo.alarmMask

       Bit meanings:
               bit 0 = linkDown"
   ::= {fr1645v2PortSwAlarmEntry 67108864}

fr1645v2PortSwAlarmLevLinkDown OBJECT-TYPE
   SYNTAX      Integer32
   MAX-ACCESS  read-only
   STATUS      current
   DESCRIPTION
      "Path: ethernet1.alarms.alarmInfo.alarmLevel.linkDown"
   ::= {fr1645v2PortSwAlarmEntry 83951616}


fr1645v2PortSwAlarmE2 OBJECT IDENTIFIER ::= {fr1645v2PortSwAlarm 2}

fr1645v2PortSwAlarmE2Entry OBJECT IDENTIFIER ::= {fr1645v2PortSwAlarmE2 1}

fr1645v2PortSwAlarmE2LinkDown OBJECT IDENTIFIER ::= {fr1645v2PortSwAlarmE2Entry 10}

fr1645v2PortSwAlarmE2LinkDownPfx OBJECT IDENTIFIER ::= {fr1645v2PortSwAlarmE2LinkDown 0}

fr1645v2PortSwAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitch1G'
                (root='router1645') has changed from the ON to the OFF state."
   ::= {fr1645v2PortSwAlarmE2LinkDownPfx 1}

fr1645v2PortSwAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitch1G'
                (root='router1645') has changed from the OFF to the ON state."
   ::= {fr1645v2PortSwAlarmE2LinkDownPfx 2}



ar1645v2PortSw OBJECT IDENTIFIER ::= {r1645v2PortSw 16}


ar1645v2PortSwClearCounters OBJECT-TYPE
   SYNTAX      Integer32
   MAX-ACCESS  read-write
   STATUS      current
   DESCRIPTION
      "Path: ethernet1.actions.clearCounters
       Info: reset counters"
   ::= {ar1645v2PortSw 263}


ar1645v2PortSwSalAction OBJECT-TYPE
   SYNTAX      Integer32
   MAX-ACCESS  read-write
   STATUS      current
   DESCRIPTION
      "Path: ethernet1.actions.salAction
       Info: action in the debug group"
   ::= {ar1645v2PortSw 97}


ar1645v2PortSwRegAction OBJECT-TYPE
   SYNTAX      Integer32
   MAX-ACCESS  read-write
   STATUS      current
   DESCRIPTION
      "Path: ethernet1.actions.regAction
       Info: action in the debug group"
   ::= {ar1645v2PortSw 95}


ar1645v2PortSwMeasTemp OBJECT-TYPE
   SYNTAX      Integer32
   MAX-ACCESS  read-write
   STATUS      current
   DESCRIPTION
      "Path: ethernet1.actions.measTemp
       Info: action in the debug group"
   ::= {ar1645v2PortSw 85}


ar1645v2PortSwClearAction OBJECT-TYPE
   SYNTAX      Integer32
   MAX-ACCESS  read-write
   STATUS      current
   DESCRIPTION
      "Path: ethernet1.actions.clearAction
       Info: action in the debug group"
   ::= {ar1645v2PortSw 84}


ar1645v2PortSwClearSwitchCache OBJECT-TYPE
   SYNTAX      Integer32
   MAX-ACCESS  read-write
   STATUS      current
   DESCRIPTION
      "Path: ethernet1.actions.clearSwitchCache
       Info: Clear the dnamic entries in the swith MAC cache"
   ::= {ar1645v2PortSw 81}


ar1645v2PortSwEnableRds OBJECT-TYPE
   SYNTAX      Integer32
   MAX-ACCESS  read-write
   STATUS      current
   DESCRIPTION
      "Path: ethernet1.actions.enableRds
       Info: action in the debug group"
   ::= {ar1645v2PortSw 367}


ar1645v2PortSwDisableRds OBJECT-TYPE
   SYNTAX      Integer32
   MAX-ACCESS  read-write
   STATUS      current
   DESCRIPTION
      "Path: ethernet1.actions.disableRds
       Info: action in the debug group"
   ::= {ar1645v2PortSw 366}


ar1645v2PortSwEnableTds OBJECT-TYPE
   SYNTAX      Integer32
   MAX-ACCESS  read-write
   STATUS      current
   DESCRIPTION
      "Path: ethernet1.actions.enableTds
       Info: action in the debug group"
   ::= {ar1645v2PortSw 365}


ar1645v2PortSwDisableTds OBJECT-TYPE
   SYNTAX      Integer32
   MAX-ACCESS  read-write
   STATUS      current
   DESCRIPTION
      "Path: ethernet1.actions.disableTds
       Info: action in the debug group"
   ::= {ar1645v2PortSw 364}


ar1645v2PortSwClearTsecStats OBJECT-TYPE
   SYNTAX      Integer32
   MAX-ACCESS  read-write
   STATUS      current
   DESCRIPTION
      "Path: ethernet1.actions.clearTsecStats
       Info: action in the debug group"
   ::= {ar1645v2PortSw 363}


ar1645v2PortSwStopTsecStats OBJECT-TYPE
   SYNTAX      Integer32
   MAX-ACCESS  read-write
   STATUS      current
   DESCRIPTION
      "Path: ethernet1.actions.stopTsecStats
       Info: action in the debug group"
   ::= {ar1645v2PortSw 362}


ar1645v2PortSwStartTsecStats OBJECT-TYPE
   SYNTAX      Integer32
   MAX-ACCESS  read-write
   STATUS      current
   DESCRIPTION
      "Path: ethernet1.actions.startTsecStats
       Info: action in the debug group"
   ::= {ar1645v2PortSw 361}


ar1645v2PortSwClearDebugCounters OBJECT-TYPE
   SYNTAX      Integer32
   MAX-ACCESS  read-write
   STATUS      current
   DESCRIPTION
      "Path: ethernet1.actions.clearDebugCounters
       Info: action in the debug group"
   ::= {ar1645v2PortSw 76}



END
