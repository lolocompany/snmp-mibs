OneAccess-R1645v2-4821-Lan3 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Lan3 OBJECT IDENTIFIER ::= {r1645Rootv2 4821}

r1645v2Lan3MOProp OBJECT IDENTIFIER ::= {r1645v2Lan3 1}

r1645v2Lan3MOPropEntry OBJECT IDENTIFIER ::= {r1645v2Lan3MOProp 1}

r1645v2Lan3MOPropPath OBJECT-TYPE
   SYNTAX      ContainmentPath
   MAX-ACCESS  read-only
   STATUS      current
   DESCRIPTION
      "Textual description of the containment tree from the instance of
       the root object down to the instance of the current object."
   ::= {r1645v2Lan3MOPropEntry 3}

r1645v2Lan3MOPropRev OBJECT-TYPE
   SYNTAX      ObjectRevision
   MAX-ACCESS  read-only
   STATUS      current
   DESCRIPTION
      "This value corresponds with the revision of the MANAGED OBJECT."
   ::= {r1645v2Lan3MOPropEntry 4}



er1645v2Lan3 OBJECT IDENTIFIER ::= {r1645v2Lan3 11}


er1645v2Lan3Remark OBJECT-TYPE
   SYNTAX      DisplayString
   MAX-ACCESS  read-write
   STATUS      current
   DESCRIPTION
      "Path: ethernet3.editConf.remark
       Info: intfRemark"
   ::= {er1645v2Lan3 321}


er1645v2Lan3AdminStatus OBJECT-TYPE
   SYNTAX      INTEGER
               {
               up (1),
               down (2)
               }
   MAX-ACCESS  read-write
   STATUS      current
   DESCRIPTION
      "Path: ethernet3.editConf.adminStatus
       Info: ifAdminStatus

       Possibilities:
               up   (1)
               down   (2)"
   ::= {er1645v2Lan3 106}


er1645v2Lan3Bw OBJECT IDENTIFIER ::= {er1645v2Lan3 5}

er1645v2Lan3BwSSC OBJECT IDENTIFIER ::= {er1645v2Lan3Bw 1}

er1645v2Lan3BwEntry OBJECT IDENTIFIER ::= {er1645v2Lan3BwSSC 1}

er1645v2Lan3BwMode OBJECT-TYPE
   SYNTAX      INTEGER
               {
               reshaping (1),
               policing (2),
               policingReshape (3)
               }
   MAX-ACCESS  read-write
   STATUS      current
   DESCRIPTION
      "Path: ethernet3.editConf.bandwidth.mode

       Possibilities:
               reshaping   (1)
               policing   (2)
               policingReshape   (3)"
   ::= {er1645v2Lan3BwEntry 3758096384}

er1645v2Lan3BwCir OBJECT-TYPE
   SYNTAX      Integer32
   MAX-ACCESS  read-write
   STATUS      current
   DESCRIPTION
      "Path: ethernet3.editConf.bandwidth.cir"
   ::= {er1645v2Lan3BwEntry 268435456}

er1645v2Lan3BwEir OBJECT-TYPE
   SYNTAX      Integer32
   MAX-ACCESS  read-write
   STATUS      current
   DESCRIPTION
      "Path: ethernet3.editConf.bandwidth.eir"
   ::= {er1645v2Lan3BwEntry 1879048192}

er1645v2Lan3BwUnit OBJECT-TYPE
   SYNTAX      INTEGER
               {
               bitssec (1),
               percent (2)
               }
   MAX-ACCESS  read-write
   STATUS      current
   DESCRIPTION
      "Path: ethernet3.editConf.bandwidth.unit

       Possibilities:
               bits/sec   (1)
               percent   (2)"
   ::= {er1645v2Lan3BwEntry 1342177280}

er1645v2Lan3BwTc OBJECT-TYPE
   SYNTAX      INTEGER
               {
               auto (0)
               }
   MAX-ACCESS  read-write
   STATUS      current
   DESCRIPTION
      "Path: ethernet3.editConf.bandwidth.tc

       Possibilities:
               auto   (0)"
   ::= {er1645v2Lan3BwEntry 1610612736}

er1645v2Lan3BwTcFactor OBJECT-TYPE
   SYNTAX      INTEGER
               {
               ms (10),
               s100us (1)
               }
   MAX-ACCESS  read-write
   STATUS      current
   DESCRIPTION
      "Path: ethernet3.editConf.bandwidth.tcFactor

       Possibilities:
               ms   (10)
               *100us   (1)"
   ::= {er1645v2Lan3BwEntry 2147483648}

er1645v2Lan3BwCorrType OBJECT-TYPE
   SYNTAX      INTEGER
               {
               noCorrection (0),
               predefined (1),
               manual (2)
               }
   MAX-ACCESS  read-write
   STATUS      current
   DESCRIPTION
      "Path: ethernet3.editConf.bandwidth.correction.type

       Possibilities:
               noCorrection   (0)
               predefined   (1)
               manual   (2)"
   ::= {er1645v2Lan3BwEntry 570425344}

er1645v2Lan3BwCorrPredefEncapsFrameRelay OBJECT-TYPE
   SYNTAX      DisplayString
   MAX-ACCESS  read-write
   STATUS      current
   DESCRIPTION
      "Path: ethernet3.editConf.bandwidth.correction.predefined.encapsulation.frameRelay"
   ::= {er1645v2Lan3BwEntry 608436224}

er1645v2Lan3BwCorrPredefEncapsPpp OBJECT-TYPE
   SYNTAX      DisplayString
   MAX-ACCESS  read-write
   STATUS      current
   DESCRIPTION
      "Path: ethernet3.editConf.bandwidth.correction.predefined.encapsulation.ppp"
   ::= {er1645v2Lan3BwEntry 608698368}

er1645v2Lan3BwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.bandwidth.correction.predefined.encapsulation.atm.higherLayer

       Possibilities:
               rfc2684   (0)
               ppp   (1)
               pppOverEthernet   (2)"
   ::= {er1645v2Lan3BwEntry 608993280}

er1645v2Lan3BwCorrPredefEncapsAtmMp OBJECT-TYPE
   SYNTAX      INTEGER
               {
               llcEncapsulation (0),
               vcMultiplexing (1)
               }
   MAX-ACCESS  read-write
   STATUS      current
   DESCRIPTION
      "Path: ethernet3.editConf.bandwidth.correction.predefined.encapsulation.atm.multiProtocol

       Possibilities:
               llcEncapsulation   (0)
               vcMultiplexing   (1)"
   ::= {er1645v2Lan3BwEntry 609026048}

er1645v2Lan3BwCorrPredefEncapsHdlc OBJECT-TYPE
   SYNTAX      DisplayString
   MAX-ACCESS  read-write
   STATUS      current
   DESCRIPTION
      "Path: ethernet3.editConf.bandwidth.correction.predefined.encapsulation.hdlc"
   ::= {er1645v2Lan3BwEntry 609222656}

er1645v2Lan3BwCorrPredefEncapsEfmFs OBJECT-TYPE
   SYNTAX      Integer32
   MAX-ACCESS  read-write
   STATUS      current
   DESCRIPTION
      "Path: ethernet3.editConf.bandwidth.correction.predefined.encapsulation.efm.fragmentSize"
   ::= {er1645v2Lan3BwEntry 609517568}

er1645v2Lan3BwCorrPredefEncapsEfmIb OBJECT-TYPE
   SYNTAX      Integer32
   MAX-ACCESS  read-write
   STATUS      current
   DESCRIPTION
      "Path: ethernet3.editConf.bandwidth.correction.predefined.encapsulation.efm.idleBytes"
   ::= {er1645v2Lan3BwEntry 609550336}

er1645v2Lan3BwCorrPredefMode OBJECT-TYPE
   SYNTAX      INTEGER
               {
               routing (0),
               bridging (1)
               }
   MAX-ACCESS  read-write
   STATUS      current
   DESCRIPTION
      "Path: ethernet3.editConf.bandwidth.correction.predefined.mode

       Possibilities:
               routing   (0)
               bridging   (1)"
   ::= {er1645v2Lan3BwEntry 612368384}

er1645v2Lan3BwCorrManualOverhead OBJECT-TYPE
   SYNTAX      Integer32
   MAX-ACCESS  read-write
   STATUS      current
   DESCRIPTION
      "Path: ethernet3.editConf.bandwidth.correction.manual.overhead"
   ::= {er1645v2Lan3BwEntry 637665280}

er1645v2Lan3BwCorrManualFrameData OBJECT-TYPE
   SYNTAX      Counter32
   MAX-ACCESS  read-write
   STATUS      current
   DESCRIPTION
      "Path: ethernet3.editConf.bandwidth.correction.manual.frameData

       32 bit unsigned wrappable counter."
   ::= {er1645v2Lan3BwEntry 637796352}

er1645v2Lan3BwCorrManualFrameHeader OBJECT-TYPE
   SYNTAX      Counter32
   MAX-ACCESS  read-write
   STATUS      current
   DESCRIPTION
      "Path: ethernet3.editConf.bandwidth.correction.manual.frameHeader

       32 bit unsigned wrappable counter."
   ::= {er1645v2Lan3BwEntry 637927424}

er1645v2Lan3BwMaxFifoQLen OBJECT-TYPE
   SYNTAX      Integer32
   MAX-ACCESS  read-write
   STATUS      current
   DESCRIPTION
      "Path: ethernet3.editConf.bandwidth.maxFifoQLen"
   ::= {er1645v2Lan3BwEntry 805306368}

er1645v2Lan3BwDeFlagCir OBJECT-TYPE
   SYNTAX      INTEGER
               {
               allowed (1),
               notAllowed (2)
               }
   MAX-ACCESS  read-write
   STATUS      current
   DESCRIPTION
      "Path: ethernet3.editConf.bandwidth.deFlag.cir

       Possibilities:
               allowed   (1)
               notAllowed   (2)"
   ::= {er1645v2Lan3BwEntry 3490709504}

er1645v2Lan3BwDeFlagEir OBJECT-TYPE
   SYNTAX      INTEGER
               {
               allowed (1),
               notAllowed (2)
               }
   MAX-ACCESS  read-write
   STATUS      current
   DESCRIPTION
      "Path: ethernet3.editConf.bandwidth.deFlag.eir

       Possibilities:
               allowed   (1)
               notAllowed   (2)"
   ::= {er1645v2Lan3BwEntry 3491758080}

er1645v2Lan3BwDeFlagViolate OBJECT-TYPE
   SYNTAX      INTEGER
               {
               allowed (1),
               notAllowed (2)
               }
   MAX-ACCESS  read-write
   STATUS      current
   DESCRIPTION
      "Path: ethernet3.editConf.bandwidth.deFlag.violate

       Possibilities:
               allowed   (1)
               notAllowed   (2)"
   ::= {er1645v2Lan3BwEntry 3492806656}

er1645v2Lan3BwActCirActNone OBJECT-TYPE
   SYNTAX      OCTET STRING
   MAX-ACCESS  read-write
   STATUS      current
   DESCRIPTION
      "Path: ethernet3.editConf.bandwidth.action.cirAction.none"
   ::= {er1645v2Lan3BwEntry 4062183424}

er1645v2Lan3BwActCirActEthCos1 OBJECT-TYPE
   SYNTAX      INTEGER
               {
               unchanged (256)
               }
   MAX-ACCESS  read-write
   STATUS      current
   DESCRIPTION
      "Path: ethernet3.editConf.bandwidth.action.cirAction.ethernet.cosDepth1

       Possibilities:
               unchanged   (256)"
   ::= {er1645v2Lan3BwEntry 4064346112}

er1645v2Lan3BwActCirActEthDei1 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth1

       Possibilities:
               unchanged   (255)
               clear   (0)
               set   (1)"
   ::= {er1645v2Lan3BwEntry 4065656832}

er1645v2Lan3BwActCirActEthCos2 OBJECT-TYPE
   SYNTAX      INTEGER
               {
               unchanged (256)
               }
   MAX-ACCESS  read-write
   STATUS      current
   DESCRIPTION
      "Path: ethernet3.editConf.bandwidth.action.cirAction.ethernet.cosDepth2

       Possibilities:
               unchanged   (256)"
   ::= {er1645v2Lan3BwEntry 4064411648}

er1645v2Lan3BwActCirActEthDei2 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth2

       Possibilities:
               unchanged   (255)
               clear   (0)
               set   (1)"
   ::= {er1645v2Lan3BwEntry 4065722368}

er1645v2Lan3BwActCirActEthCos3 OBJECT-TYPE
   SYNTAX      INTEGER
               {
               unchanged (256)
               }
   MAX-ACCESS  read-write
   STATUS      current
   DESCRIPTION
      "Path: ethernet3.editConf.bandwidth.action.cirAction.ethernet.cosDepth3

       Possibilities:
               unchanged   (256)"
   ::= {er1645v2Lan3BwEntry 4064477184}

er1645v2Lan3BwActCirActEthDei3 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth3

       Possibilities:
               unchanged   (255)
               clear   (0)
               set   (1)"
   ::= {er1645v2Lan3BwEntry 4065787904}

er1645v2Lan3BwActCirActEthCos4 OBJECT-TYPE
   SYNTAX      INTEGER
               {
               unchanged (256)
               }
   MAX-ACCESS  read-write
   STATUS      current
   DESCRIPTION
      "Path: ethernet3.editConf.bandwidth.action.cirAction.ethernet.cosDepth4

       Possibilities:
               unchanged   (256)"
   ::= {er1645v2Lan3BwEntry 4064542720}

er1645v2Lan3BwActCirActEthDei4 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth4

       Possibilities:
               unchanged   (255)
               clear   (0)
               set   (1)"
   ::= {er1645v2Lan3BwEntry 4065853440}

er1645v2Lan3BwActCirActEthCos5 OBJECT-TYPE
   SYNTAX      INTEGER
               {
               unchanged (256)
               }
   MAX-ACCESS  read-write
   STATUS      current
   DESCRIPTION
      "Path: ethernet3.editConf.bandwidth.action.cirAction.ethernet.cosDepth5

       Possibilities:
               unchanged   (256)"
   ::= {er1645v2Lan3BwEntry 4064608256}

er1645v2Lan3BwActCirActEthDei5 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth5

       Possibilities:
               unchanged   (255)
               clear   (0)
               set   (1)"
   ::= {er1645v2Lan3BwEntry 4065918976}

er1645v2Lan3BwActCirActEthCos6 OBJECT-TYPE
   SYNTAX      INTEGER
               {
               unchanged (256)
               }
   MAX-ACCESS  read-write
   STATUS      current
   DESCRIPTION
      "Path: ethernet3.editConf.bandwidth.action.cirAction.ethernet.cosDepth6

       Possibilities:
               unchanged   (256)"
   ::= {er1645v2Lan3BwEntry 4064673792}

er1645v2Lan3BwActCirActEthDei6 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth6

       Possibilities:
               unchanged   (255)
               clear   (0)
               set   (1)"
   ::= {er1645v2Lan3BwEntry 4065984512}

er1645v2Lan3BwActCirActEthCos7 OBJECT-TYPE
   SYNTAX      INTEGER
               {
               unchanged (256)
               }
   MAX-ACCESS  read-write
   STATUS      current
   DESCRIPTION
      "Path: ethernet3.editConf.bandwidth.action.cirAction.ethernet.cosDepth7

       Possibilities:
               unchanged   (256)"
   ::= {er1645v2Lan3BwEntry 4064739328}

er1645v2Lan3BwActCirActEthDei7 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth7

       Possibilities:
               unchanged   (255)
               clear   (0)
               set   (1)"
   ::= {er1645v2Lan3BwEntry 4066050048}

er1645v2Lan3BwActCirActEthCos8 OBJECT-TYPE
   SYNTAX      INTEGER
               {
               unchanged (256)
               }
   MAX-ACCESS  read-write
   STATUS      current
   DESCRIPTION
      "Path: ethernet3.editConf.bandwidth.action.cirAction.ethernet.cosDepth8

       Possibilities:
               unchanged   (256)"
   ::= {er1645v2Lan3BwEntry 4064804864}

er1645v2Lan3BwActCirActEthDei8 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth8

       Possibilities:
               unchanged   (255)
               clear   (0)
               set   (1)"
   ::= {er1645v2Lan3BwEntry 4066115584}

er1645v2Lan3BwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4064870400}

er1645v2Lan3BwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4064935936}

er1645v2Lan3BwActCirActEthDrpLev OBJECT-TYPE
   SYNTAX      INTEGER
               {
               unchanged (0)
               }
   MAX-ACCESS  read-write
   STATUS      current
   DESCRIPTION
      "Path: ethernet3.editConf.bandwidth.action.cirAction.ethernet.dropLevel

       Possibilities:
               unchanged   (0)"
   ::= {er1645v2Lan3BwEntry 4065001472}

er1645v2Lan3BwActCirActEthDeFlag OBJECT-TYPE
   SYNTAX      INTEGER
               {
               unchanged (255),
               clear (0),
               set (1)
               }
   MAX-ACCESS  read-write
   STATUS      current
   DESCRIPTION
      "Path: ethernet3.editConf.bandwidth.action.cirAction.ethernet.deFlag

       Possibilities:
               unchanged   (255)
               clear   (0)
               set   (1)"
   ::= {er1645v2Lan3BwEntry 4065198080}

er1645v2Lan3BwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4071161856}

er1645v2Lan3BwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4071227392}

er1645v2Lan3BwActCirActIpDrpLev OBJECT-TYPE
   SYNTAX      INTEGER
               {
               unchanged (0)
               }
   MAX-ACCESS  read-write
   STATUS      current
   DESCRIPTION
      "Path: ethernet3.editConf.bandwidth.action.cirAction.ip.dropLevel

       Possibilities:
               unchanged   (0)"
   ::= {er1645v2Lan3BwEntry 4071292928}

er1645v2Lan3BwActCirActIpDeFlag OBJECT-TYPE
   SYNTAX      INTEGER
               {
               unchanged (255),
               clear (0),
               set (1)
               }
   MAX-ACCESS  read-write
   STATUS      current
   DESCRIPTION
      "Path: ethernet3.editConf.bandwidth.action.cirAction.ip.deFlag

       Possibilities:
               unchanged   (255)
               clear   (0)
               set   (1)"
   ::= {er1645v2Lan3BwEntry 4071489536}

er1645v2Lan3BwActEirActNone OBJECT-TYPE
   SYNTAX      OCTET STRING
   MAX-ACCESS  read-write
   STATUS      current
   DESCRIPTION
      "Path: ethernet3.editConf.bandwidth.action.eirAction.none"
   ::= {er1645v2Lan3BwEntry 4095737856}

er1645v2Lan3BwActEirActEthCos1 OBJECT-TYPE
   SYNTAX      INTEGER
               {
               unchanged (256)
               }
   MAX-ACCESS  read-write
   STATUS      current
   DESCRIPTION
      "Path: ethernet3.editConf.bandwidth.action.eirAction.ethernet.cosDepth1

       Possibilities:
               unchanged   (256)"
   ::= {er1645v2Lan3BwEntry 4097900544}

er1645v2Lan3BwActEirActEthDei1 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth1

       Possibilities:
               unchanged   (255)
               clear   (0)
               set   (1)"
   ::= {er1645v2Lan3BwEntry 4099211264}

er1645v2Lan3BwActEirActEthCos2 OBJECT-TYPE
   SYNTAX      INTEGER
               {
               unchanged (256)
               }
   MAX-ACCESS  read-write
   STATUS      current
   DESCRIPTION
      "Path: ethernet3.editConf.bandwidth.action.eirAction.ethernet.cosDepth2

       Possibilities:
               unchanged   (256)"
   ::= {er1645v2Lan3BwEntry 4097966080}

er1645v2Lan3BwActEirActEthDei2 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth2

       Possibilities:
               unchanged   (255)
               clear   (0)
               set   (1)"
   ::= {er1645v2Lan3BwEntry 4099276800}

er1645v2Lan3BwActEirActEthCos3 OBJECT-TYPE
   SYNTAX      INTEGER
               {
               unchanged (256)
               }
   MAX-ACCESS  read-write
   STATUS      current
   DESCRIPTION
      "Path: ethernet3.editConf.bandwidth.action.eirAction.ethernet.cosDepth3

       Possibilities:
               unchanged   (256)"
   ::= {er1645v2Lan3BwEntry 4098031616}

er1645v2Lan3BwActEirActEthDei3 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth3

       Possibilities:
               unchanged   (255)
               clear   (0)
               set   (1)"
   ::= {er1645v2Lan3BwEntry 4099342336}

er1645v2Lan3BwActEirActEthCos4 OBJECT-TYPE
   SYNTAX      INTEGER
               {
               unchanged (256)
               }
   MAX-ACCESS  read-write
   STATUS      current
   DESCRIPTION
      "Path: ethernet3.editConf.bandwidth.action.eirAction.ethernet.cosDepth4

       Possibilities:
               unchanged   (256)"
   ::= {er1645v2Lan3BwEntry 4098097152}

er1645v2Lan3BwActEirActEthDei4 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth4

       Possibilities:
               unchanged   (255)
               clear   (0)
               set   (1)"
   ::= {er1645v2Lan3BwEntry 4099407872}

er1645v2Lan3BwActEirActEthCos5 OBJECT-TYPE
   SYNTAX      INTEGER
               {
               unchanged (256)
               }
   MAX-ACCESS  read-write
   STATUS      current
   DESCRIPTION
      "Path: ethernet3.editConf.bandwidth.action.eirAction.ethernet.cosDepth5

       Possibilities:
               unchanged   (256)"
   ::= {er1645v2Lan3BwEntry 4098162688}

er1645v2Lan3BwActEirActEthDei5 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth5

       Possibilities:
               unchanged   (255)
               clear   (0)
               set   (1)"
   ::= {er1645v2Lan3BwEntry 4099473408}

er1645v2Lan3BwActEirActEthCos6 OBJECT-TYPE
   SYNTAX      INTEGER
               {
               unchanged (256)
               }
   MAX-ACCESS  read-write
   STATUS      current
   DESCRIPTION
      "Path: ethernet3.editConf.bandwidth.action.eirAction.ethernet.cosDepth6

       Possibilities:
               unchanged   (256)"
   ::= {er1645v2Lan3BwEntry 4098228224}

er1645v2Lan3BwActEirActEthDei6 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth6

       Possibilities:
               unchanged   (255)
               clear   (0)
               set   (1)"
   ::= {er1645v2Lan3BwEntry 4099538944}

er1645v2Lan3BwActEirActEthCos7 OBJECT-TYPE
   SYNTAX      INTEGER
               {
               unchanged (256)
               }
   MAX-ACCESS  read-write
   STATUS      current
   DESCRIPTION
      "Path: ethernet3.editConf.bandwidth.action.eirAction.ethernet.cosDepth7

       Possibilities:
               unchanged   (256)"
   ::= {er1645v2Lan3BwEntry 4098293760}

er1645v2Lan3BwActEirActEthDei7 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth7

       Possibilities:
               unchanged   (255)
               clear   (0)
               set   (1)"
   ::= {er1645v2Lan3BwEntry 4099604480}

er1645v2Lan3BwActEirActEthCos8 OBJECT-TYPE
   SYNTAX      INTEGER
               {
               unchanged (256)
               }
   MAX-ACCESS  read-write
   STATUS      current
   DESCRIPTION
      "Path: ethernet3.editConf.bandwidth.action.eirAction.ethernet.cosDepth8

       Possibilities:
               unchanged   (256)"
   ::= {er1645v2Lan3BwEntry 4098359296}

er1645v2Lan3BwActEirActEthDei8 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth8

       Possibilities:
               unchanged   (255)
               clear   (0)
               set   (1)"
   ::= {er1645v2Lan3BwEntry 4099670016}

er1645v2Lan3BwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4098424832}

er1645v2Lan3BwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4098490368}

er1645v2Lan3BwActEirActEthDrpLev OBJECT-TYPE
   SYNTAX      INTEGER
               {
               unchanged (0)
               }
   MAX-ACCESS  read-write
   STATUS      current
   DESCRIPTION
      "Path: ethernet3.editConf.bandwidth.action.eirAction.ethernet.dropLevel

       Possibilities:
               unchanged   (0)"
   ::= {er1645v2Lan3BwEntry 4098555904}

er1645v2Lan3BwActEirActEthDeFlag OBJECT-TYPE
   SYNTAX      INTEGER
               {
               unchanged (255),
               clear (0),
               set (1)
               }
   MAX-ACCESS  read-write
   STATUS      current
   DESCRIPTION
      "Path: ethernet3.editConf.bandwidth.action.eirAction.ethernet.deFlag

       Possibilities:
               unchanged   (255)
               clear   (0)
               set   (1)"
   ::= {er1645v2Lan3BwEntry 4098752512}

er1645v2Lan3BwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4104716288}

er1645v2Lan3BwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4104781824}

er1645v2Lan3BwActEirActIpDrpLev OBJECT-TYPE
   SYNTAX      INTEGER
               {
               unchanged (0)
               }
   MAX-ACCESS  read-write
   STATUS      current
   DESCRIPTION
      "Path: ethernet3.editConf.bandwidth.action.eirAction.ip.dropLevel

       Possibilities:
               unchanged   (0)"
   ::= {er1645v2Lan3BwEntry 4104847360}

er1645v2Lan3BwActEirActIpDeFlag OBJECT-TYPE
   SYNTAX      INTEGER
               {
               unchanged (255),
               clear (0),
               set (1)
               }
   MAX-ACCESS  read-write
   STATUS      current
   DESCRIPTION
      "Path: ethernet3.editConf.bandwidth.action.eirAction.ip.deFlag

       Possibilities:
               unchanged   (255)
               clear   (0)
               set   (1)"
   ::= {er1645v2Lan3BwEntry 4105043968}

er1645v2Lan3BwActViolActNone OBJECT-TYPE
   SYNTAX      OCTET STRING
   MAX-ACCESS  read-write
   STATUS      current
   DESCRIPTION
      "Path: ethernet3.editConf.bandwidth.action.violateAction.none"
   ::= {er1645v2Lan3BwEntry 4129292288}

er1645v2Lan3BwActViolActDrop OBJECT-TYPE
   SYNTAX      OCTET STRING
   MAX-ACCESS  read-write
   STATUS      current
   DESCRIPTION
      "Path: ethernet3.editConf.bandwidth.action.violateAction.drop"
   ::= {er1645v2Lan3BwEntry 4133486592}

er1645v2Lan3BwActViolActEthCos1 OBJECT-TYPE
   SYNTAX      INTEGER
               {
               unchanged (256)
               }
   MAX-ACCESS  read-write
   STATUS      current
   DESCRIPTION
      "Path: ethernet3.editConf.bandwidth.action.violateAction.ethernet.cosDepth1

       Possibilities:
               unchanged   (256)"
   ::= {er1645v2Lan3BwEntry 4131454976}

er1645v2Lan3BwActViolActEthDei1 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth1

       Possibilities:
               unchanged   (255)
               clear   (0)
               set   (1)"
   ::= {er1645v2Lan3BwEntry 4132765696}

er1645v2Lan3BwActViolActEthCos2 OBJECT-TYPE
   SYNTAX      INTEGER
               {
               unchanged (256)
               }
   MAX-ACCESS  read-write
   STATUS      current
   DESCRIPTION
      "Path: ethernet3.editConf.bandwidth.action.violateAction.ethernet.cosDepth2

       Possibilities:
               unchanged   (256)"
   ::= {er1645v2Lan3BwEntry 4131520512}

er1645v2Lan3BwActViolActEthDei2 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth2

       Possibilities:
               unchanged   (255)
               clear   (0)
               set   (1)"
   ::= {er1645v2Lan3BwEntry 4132831232}

er1645v2Lan3BwActViolActEthCos3 OBJECT-TYPE
   SYNTAX      INTEGER
               {
               unchanged (256)
               }
   MAX-ACCESS  read-write
   STATUS      current
   DESCRIPTION
      "Path: ethernet3.editConf.bandwidth.action.violateAction.ethernet.cosDepth3

       Possibilities:
               unchanged   (256)"
   ::= {er1645v2Lan3BwEntry 4131586048}

er1645v2Lan3BwActViolActEthDei3 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth3

       Possibilities:
               unchanged   (255)
               clear   (0)
               set   (1)"
   ::= {er1645v2Lan3BwEntry 4132896768}

er1645v2Lan3BwActViolActEthCos4 OBJECT-TYPE
   SYNTAX      INTEGER
               {
               unchanged (256)
               }
   MAX-ACCESS  read-write
   STATUS      current
   DESCRIPTION
      "Path: ethernet3.editConf.bandwidth.action.violateAction.ethernet.cosDepth4

       Possibilities:
               unchanged   (256)"
   ::= {er1645v2Lan3BwEntry 4131651584}

er1645v2Lan3BwActViolActEthDei4 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth4

       Possibilities:
               unchanged   (255)
               clear   (0)
               set   (1)"
   ::= {er1645v2Lan3BwEntry 4132962304}

er1645v2Lan3BwActViolActEthCos5 OBJECT-TYPE
   SYNTAX      INTEGER
               {
               unchanged (256)
               }
   MAX-ACCESS  read-write
   STATUS      current
   DESCRIPTION
      "Path: ethernet3.editConf.bandwidth.action.violateAction.ethernet.cosDepth5

       Possibilities:
               unchanged   (256)"
   ::= {er1645v2Lan3BwEntry 4131717120}

er1645v2Lan3BwActViolActEthDei5 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth5

       Possibilities:
               unchanged   (255)
               clear   (0)
               set   (1)"
   ::= {er1645v2Lan3BwEntry 4133027840}

er1645v2Lan3BwActViolActEthCos6 OBJECT-TYPE
   SYNTAX      INTEGER
               {
               unchanged (256)
               }
   MAX-ACCESS  read-write
   STATUS      current
   DESCRIPTION
      "Path: ethernet3.editConf.bandwidth.action.violateAction.ethernet.cosDepth6

       Possibilities:
               unchanged   (256)"
   ::= {er1645v2Lan3BwEntry 4131782656}

er1645v2Lan3BwActViolActEthDei6 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth6

       Possibilities:
               unchanged   (255)
               clear   (0)
               set   (1)"
   ::= {er1645v2Lan3BwEntry 4133093376}

er1645v2Lan3BwActViolActEthCos7 OBJECT-TYPE
   SYNTAX      INTEGER
               {
               unchanged (256)
               }
   MAX-ACCESS  read-write
   STATUS      current
   DESCRIPTION
      "Path: ethernet3.editConf.bandwidth.action.violateAction.ethernet.cosDepth7

       Possibilities:
               unchanged   (256)"
   ::= {er1645v2Lan3BwEntry 4131848192}

er1645v2Lan3BwActViolActEthDei7 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth7

       Possibilities:
               unchanged   (255)
               clear   (0)
               set   (1)"
   ::= {er1645v2Lan3BwEntry 4133158912}

er1645v2Lan3BwActViolActEthCos8 OBJECT-TYPE
   SYNTAX      INTEGER
               {
               unchanged (256)
               }
   MAX-ACCESS  read-write
   STATUS      current
   DESCRIPTION
      "Path: ethernet3.editConf.bandwidth.action.violateAction.ethernet.cosDepth8

       Possibilities:
               unchanged   (256)"
   ::= {er1645v2Lan3BwEntry 4131913728}

er1645v2Lan3BwActViolActEthDei8 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth8

       Possibilities:
               unchanged   (255)
               clear   (0)
               set   (1)"
   ::= {er1645v2Lan3BwEntry 4133224448}

er1645v2Lan3BwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4131979264}

er1645v2Lan3BwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4132044800}

er1645v2Lan3BwActViolActEthDrpLev OBJECT-TYPE
   SYNTAX      INTEGER
               {
               unchanged (0)
               }
   MAX-ACCESS  read-write
   STATUS      current
   DESCRIPTION
      "Path: ethernet3.editConf.bandwidth.action.violateAction.ethernet.dropLevel

       Possibilities:
               unchanged   (0)"
   ::= {er1645v2Lan3BwEntry 4132110336}

er1645v2Lan3BwActViolActEthDeFlag OBJECT-TYPE
   SYNTAX      INTEGER
               {
               unchanged (255),
               clear (0),
               set (1)
               }
   MAX-ACCESS  read-write
   STATUS      current
   DESCRIPTION
      "Path: ethernet3.editConf.bandwidth.action.violateAction.ethernet.deFlag

       Possibilities:
               unchanged   (255)
               clear   (0)
               set   (1)"
   ::= {er1645v2Lan3BwEntry 4132306944}

er1645v2Lan3BwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3BwEntry 4138270720}

er1645v2Lan3BwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3BwEntry 4138336256}

er1645v2Lan3BwActViolActIpDrpLev OBJECT-TYPE
   SYNTAX      INTEGER
               {
               unchanged (0)
               }
   MAX-ACCESS  read-write
   STATUS      current
   DESCRIPTION
      "Path: ethernet3.editConf.bandwidth.action.violateAction.ip.dropLevel

       Possibilities:
               unchanged   (0)"
   ::= {er1645v2Lan3BwEntry 4138401792}

er1645v2Lan3BwActViolActIpDeFlag OBJECT-TYPE
   SYNTAX      INTEGER
               {
               unchanged (255),
               clear (0),
               set (1)
               }
   MAX-ACCESS  read-write
   STATUS      current
   DESCRIPTION
      "Path: ethernet3.editConf.bandwidth.action.violateAction.ip.deFlag

       Possibilities:
               unchanged   (255)
               clear   (0)
               set   (1)"
   ::= {er1645v2Lan3BwEntry 4138598400}


er1645v2Lan3Ibw OBJECT IDENTIFIER ::= {er1645v2Lan3 13}

er1645v2Lan3IbwSSC OBJECT IDENTIFIER ::= {er1645v2Lan3Ibw 1}

er1645v2Lan3IbwEntry OBJECT IDENTIFIER ::= {er1645v2Lan3IbwSSC 1}

er1645v2Lan3IbwMode OBJECT-TYPE
   SYNTAX      INTEGER
               {
               reshaping (1),
               policing (2)
               }
   MAX-ACCESS  read-write
   STATUS      current
   DESCRIPTION
      "Path: ethernet3.editConf.inboundBandwidth.mode

       Possibilities:
               reshaping   (1)
               policing   (2)"
   ::= {er1645v2Lan3IbwEntry 3758096384}

er1645v2Lan3IbwCir OBJECT-TYPE
   SYNTAX      Integer32
   MAX-ACCESS  read-write
   STATUS      current
   DESCRIPTION
      "Path: ethernet3.editConf.inboundBandwidth.cir"
   ::= {er1645v2Lan3IbwEntry 268435456}

er1645v2Lan3IbwEir OBJECT-TYPE
   SYNTAX      Integer32
   MAX-ACCESS  read-write
   STATUS      current
   DESCRIPTION
      "Path: ethernet3.editConf.inboundBandwidth.eir"
   ::= {er1645v2Lan3IbwEntry 1879048192}

er1645v2Lan3IbwUnit OBJECT-TYPE
   SYNTAX      INTEGER
               {
               bitssec (1),
               percent (2)
               }
   MAX-ACCESS  read-write
   STATUS      current
   DESCRIPTION
      "Path: ethernet3.editConf.inboundBandwidth.unit

       Possibilities:
               bits/sec   (1)
               percent   (2)"
   ::= {er1645v2Lan3IbwEntry 1342177280}

er1645v2Lan3IbwTc OBJECT-TYPE
   SYNTAX      INTEGER
               {
               auto (0)
               }
   MAX-ACCESS  read-write
   STATUS      current
   DESCRIPTION
      "Path: ethernet3.editConf.inboundBandwidth.tc

       Possibilities:
               auto   (0)"
   ::= {er1645v2Lan3IbwEntry 1610612736}

er1645v2Lan3IbwTcFactor OBJECT-TYPE
   SYNTAX      INTEGER
               {
               ms (10),
               s100us (1)
               }
   MAX-ACCESS  read-write
   STATUS      current
   DESCRIPTION
      "Path: ethernet3.editConf.inboundBandwidth.tcFactor

       Possibilities:
               ms   (10)
               *100us   (1)"
   ::= {er1645v2Lan3IbwEntry 2147483648}

er1645v2Lan3IbwCorrType OBJECT-TYPE
   SYNTAX      INTEGER
               {
               noCorrection (0),
               predefined (1),
               manual (2)
               }
   MAX-ACCESS  read-write
   STATUS      current
   DESCRIPTION
      "Path: ethernet3.editConf.inboundBandwidth.correction.type

       Possibilities:
               noCorrection   (0)
               predefined   (1)
               manual   (2)"
   ::= {er1645v2Lan3IbwEntry 570425344}

er1645v2Lan3IbwCorrPredefEncapsFrameRelay OBJECT-TYPE
   SYNTAX      DisplayString
   MAX-ACCESS  read-write
   STATUS      current
   DESCRIPTION
      "Path: ethernet3.editConf.inboundBandwidth.correction.predefined.encapsulation.frameRelay"
   ::= {er1645v2Lan3IbwEntry 608436224}

er1645v2Lan3IbwCorrPredefEncapsPpp OBJECT-TYPE
   SYNTAX      DisplayString
   MAX-ACCESS  read-write
   STATUS      current
   DESCRIPTION
      "Path: ethernet3.editConf.inboundBandwidth.correction.predefined.encapsulation.ppp"
   ::= {er1645v2Lan3IbwEntry 608698368}

er1645v2Lan3IbwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.inboundBandwidth.correction.predefined.encapsulation.atm.higherLayer

       Possibilities:
               rfc2684   (0)
               ppp   (1)
               pppOverEthernet   (2)"
   ::= {er1645v2Lan3IbwEntry 608993280}

er1645v2Lan3IbwCorrPredefEncapsAtmMp OBJECT-TYPE
   SYNTAX      INTEGER
               {
               llcEncapsulation (0),
               vcMultiplexing (1)
               }
   MAX-ACCESS  read-write
   STATUS      current
   DESCRIPTION
      "Path: ethernet3.editConf.inboundBandwidth.correction.predefined.encapsulation.atm.multiProtocol

       Possibilities:
               llcEncapsulation   (0)
               vcMultiplexing   (1)"
   ::= {er1645v2Lan3IbwEntry 609026048}

er1645v2Lan3IbwCorrPredefEncapsHdlc OBJECT-TYPE
   SYNTAX      DisplayString
   MAX-ACCESS  read-write
   STATUS      current
   DESCRIPTION
      "Path: ethernet3.editConf.inboundBandwidth.correction.predefined.encapsulation.hdlc"
   ::= {er1645v2Lan3IbwEntry 609222656}

er1645v2Lan3IbwCorrPredefEncapsEfmFs OBJECT-TYPE
   SYNTAX      Integer32
   MAX-ACCESS  read-write
   STATUS      current
   DESCRIPTION
      "Path: ethernet3.editConf.inboundBandwidth.correction.predefined.encapsulation.efm.fragmentSize"
   ::= {er1645v2Lan3IbwEntry 609517568}

er1645v2Lan3IbwCorrPredefEncapsEfmIb OBJECT-TYPE
   SYNTAX      Integer32
   MAX-ACCESS  read-write
   STATUS      current
   DESCRIPTION
      "Path: ethernet3.editConf.inboundBandwidth.correction.predefined.encapsulation.efm.idleBytes"
   ::= {er1645v2Lan3IbwEntry 609550336}

er1645v2Lan3IbwCorrPredefMode OBJECT-TYPE
   SYNTAX      INTEGER
               {
               routing (0),
               bridging (1)
               }
   MAX-ACCESS  read-write
   STATUS      current
   DESCRIPTION
      "Path: ethernet3.editConf.inboundBandwidth.correction.predefined.mode

       Possibilities:
               routing   (0)
               bridging   (1)"
   ::= {er1645v2Lan3IbwEntry 612368384}

er1645v2Lan3IbwCorrManualOverhead OBJECT-TYPE
   SYNTAX      Integer32
   MAX-ACCESS  read-write
   STATUS      current
   DESCRIPTION
      "Path: ethernet3.editConf.inboundBandwidth.correction.manual.overhead"
   ::= {er1645v2Lan3IbwEntry 637665280}

er1645v2Lan3IbwCorrManualFrameData OBJECT-TYPE
   SYNTAX      Counter32
   MAX-ACCESS  read-write
   STATUS      current
   DESCRIPTION
      "Path: ethernet3.editConf.inboundBandwidth.correction.manual.frameData

       32 bit unsigned wrappable counter."
   ::= {er1645v2Lan3IbwEntry 637796352}

er1645v2Lan3IbwCorrManualFrameHeader OBJECT-TYPE
   SYNTAX      Counter32
   MAX-ACCESS  read-write
   STATUS      current
   DESCRIPTION
      "Path: ethernet3.editConf.inboundBandwidth.correction.manual.frameHeader

       32 bit unsigned wrappable counter."
   ::= {er1645v2Lan3IbwEntry 637927424}

er1645v2Lan3IbwMaxFifoQLen OBJECT-TYPE
   SYNTAX      Integer32
   MAX-ACCESS  read-write
   STATUS      current
   DESCRIPTION
      "Path: ethernet3.editConf.inboundBandwidth.maxFifoQLen"
   ::= {er1645v2Lan3IbwEntry 805306368}

er1645v2Lan3IbwPriorityPolicy OBJECT-TYPE
   SYNTAX      DisplayString
   MAX-ACCESS  read-write
   STATUS      current
   DESCRIPTION
      "Path: ethernet3.editConf.inboundBandwidth.priorityPolicy"
   ::= {er1645v2Lan3IbwEntry 1073741824}

er1645v2Lan3IbwDeFlagCir OBJECT-TYPE
   SYNTAX      INTEGER
               {
               allowed (1),
               notAllowed (2)
               }
   MAX-ACCESS  read-write
   STATUS      current
   DESCRIPTION
      "Path: ethernet3.editConf.inboundBandwidth.deFlag.cir

       Possibilities:
               allowed   (1)
               notAllowed   (2)"
   ::= {er1645v2Lan3IbwEntry 3490709504}

er1645v2Lan3IbwDeFlagEir OBJECT-TYPE
   SYNTAX      INTEGER
               {
               allowed (1),
               notAllowed (2)
               }
   MAX-ACCESS  read-write
   STATUS      current
   DESCRIPTION
      "Path: ethernet3.editConf.inboundBandwidth.deFlag.eir

       Possibilities:
               allowed   (1)
               notAllowed   (2)"
   ::= {er1645v2Lan3IbwEntry 3491758080}

er1645v2Lan3IbwDeFlagViolate OBJECT-TYPE
   SYNTAX      INTEGER
               {
               allowed (1),
               notAllowed (2)
               }
   MAX-ACCESS  read-write
   STATUS      current
   DESCRIPTION
      "Path: ethernet3.editConf.inboundBandwidth.deFlag.violate

       Possibilities:
               allowed   (1)
               notAllowed   (2)"
   ::= {er1645v2Lan3IbwEntry 3492806656}

er1645v2Lan3IbwActCirActNone OBJECT-TYPE
   SYNTAX      OCTET STRING
   MAX-ACCESS  read-write
   STATUS      current
   DESCRIPTION
      "Path: ethernet3.editConf.inboundBandwidth.action.cirAction.none"
   ::= {er1645v2Lan3IbwEntry 4062183424}

er1645v2Lan3IbwActCirActEthCos1 OBJECT-TYPE
   SYNTAX      INTEGER
               {
               unchanged (256)
               }
   MAX-ACCESS  read-write
   STATUS      current
   DESCRIPTION
      "Path: ethernet3.editConf.inboundBandwidth.action.cirAction.ethernet.cosDepth1

       Possibilities:
               unchanged   (256)"
   ::= {er1645v2Lan3IbwEntry 4064346112}

er1645v2Lan3IbwActCirActEthDei1 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth1

       Possibilities:
               unchanged   (255)
               clear   (0)
               set   (1)"
   ::= {er1645v2Lan3IbwEntry 4065656832}

er1645v2Lan3IbwActCirActEthCos2 OBJECT-TYPE
   SYNTAX      INTEGER
               {
               unchanged (256)
               }
   MAX-ACCESS  read-write
   STATUS      current
   DESCRIPTION
      "Path: ethernet3.editConf.inboundBandwidth.action.cirAction.ethernet.cosDepth2

       Possibilities:
               unchanged   (256)"
   ::= {er1645v2Lan3IbwEntry 4064411648}

er1645v2Lan3IbwActCirActEthDei2 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth2

       Possibilities:
               unchanged   (255)
               clear   (0)
               set   (1)"
   ::= {er1645v2Lan3IbwEntry 4065722368}

er1645v2Lan3IbwActCirActEthCos3 OBJECT-TYPE
   SYNTAX      INTEGER
               {
               unchanged (256)
               }
   MAX-ACCESS  read-write
   STATUS      current
   DESCRIPTION
      "Path: ethernet3.editConf.inboundBandwidth.action.cirAction.ethernet.cosDepth3

       Possibilities:
               unchanged   (256)"
   ::= {er1645v2Lan3IbwEntry 4064477184}

er1645v2Lan3IbwActCirActEthDei3 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth3

       Possibilities:
               unchanged   (255)
               clear   (0)
               set   (1)"
   ::= {er1645v2Lan3IbwEntry 4065787904}

er1645v2Lan3IbwActCirActEthCos4 OBJECT-TYPE
   SYNTAX      INTEGER
               {
               unchanged (256)
               }
   MAX-ACCESS  read-write
   STATUS      current
   DESCRIPTION
      "Path: ethernet3.editConf.inboundBandwidth.action.cirAction.ethernet.cosDepth4

       Possibilities:
               unchanged   (256)"
   ::= {er1645v2Lan3IbwEntry 4064542720}

er1645v2Lan3IbwActCirActEthDei4 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth4

       Possibilities:
               unchanged   (255)
               clear   (0)
               set   (1)"
   ::= {er1645v2Lan3IbwEntry 4065853440}

er1645v2Lan3IbwActCirActEthCos5 OBJECT-TYPE
   SYNTAX      INTEGER
               {
               unchanged (256)
               }
   MAX-ACCESS  read-write
   STATUS      current
   DESCRIPTION
      "Path: ethernet3.editConf.inboundBandwidth.action.cirAction.ethernet.cosDepth5

       Possibilities:
               unchanged   (256)"
   ::= {er1645v2Lan3IbwEntry 4064608256}

er1645v2Lan3IbwActCirActEthDei5 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth5

       Possibilities:
               unchanged   (255)
               clear   (0)
               set   (1)"
   ::= {er1645v2Lan3IbwEntry 4065918976}

er1645v2Lan3IbwActCirActEthCos6 OBJECT-TYPE
   SYNTAX      INTEGER
               {
               unchanged (256)
               }
   MAX-ACCESS  read-write
   STATUS      current
   DESCRIPTION
      "Path: ethernet3.editConf.inboundBandwidth.action.cirAction.ethernet.cosDepth6

       Possibilities:
               unchanged   (256)"
   ::= {er1645v2Lan3IbwEntry 4064673792}

er1645v2Lan3IbwActCirActEthDei6 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth6

       Possibilities:
               unchanged   (255)
               clear   (0)
               set   (1)"
   ::= {er1645v2Lan3IbwEntry 4065984512}

er1645v2Lan3IbwActCirActEthCos7 OBJECT-TYPE
   SYNTAX      INTEGER
               {
               unchanged (256)
               }
   MAX-ACCESS  read-write
   STATUS      current
   DESCRIPTION
      "Path: ethernet3.editConf.inboundBandwidth.action.cirAction.ethernet.cosDepth7

       Possibilities:
               unchanged   (256)"
   ::= {er1645v2Lan3IbwEntry 4064739328}

er1645v2Lan3IbwActCirActEthDei7 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth7

       Possibilities:
               unchanged   (255)
               clear   (0)
               set   (1)"
   ::= {er1645v2Lan3IbwEntry 4066050048}

er1645v2Lan3IbwActCirActEthCos8 OBJECT-TYPE
   SYNTAX      INTEGER
               {
               unchanged (256)
               }
   MAX-ACCESS  read-write
   STATUS      current
   DESCRIPTION
      "Path: ethernet3.editConf.inboundBandwidth.action.cirAction.ethernet.cosDepth8

       Possibilities:
               unchanged   (256)"
   ::= {er1645v2Lan3IbwEntry 4064804864}

er1645v2Lan3IbwActCirActEthDei8 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth8

       Possibilities:
               unchanged   (255)
               clear   (0)
               set   (1)"
   ::= {er1645v2Lan3IbwEntry 4066115584}

er1645v2Lan3IbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4064870400}

er1645v2Lan3IbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4064935936}

er1645v2Lan3IbwActCirActEthDrpLev OBJECT-TYPE
   SYNTAX      INTEGER
               {
               unchanged (0)
               }
   MAX-ACCESS  read-write
   STATUS      current
   DESCRIPTION
      "Path: ethernet3.editConf.inboundBandwidth.action.cirAction.ethernet.dropLevel

       Possibilities:
               unchanged   (0)"
   ::= {er1645v2Lan3IbwEntry 4065001472}

er1645v2Lan3IbwActCirActEthDeFlag OBJECT-TYPE
   SYNTAX      INTEGER
               {
               unchanged (255),
               clear (0),
               set (1)
               }
   MAX-ACCESS  read-write
   STATUS      current
   DESCRIPTION
      "Path: ethernet3.editConf.inboundBandwidth.action.cirAction.ethernet.deFlag

       Possibilities:
               unchanged   (255)
               clear   (0)
               set   (1)"
   ::= {er1645v2Lan3IbwEntry 4065198080}

er1645v2Lan3IbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4071161856}

er1645v2Lan3IbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4071227392}

er1645v2Lan3IbwActCirActIpDrpLev OBJECT-TYPE
   SYNTAX      INTEGER
               {
               unchanged (0)
               }
   MAX-ACCESS  read-write
   STATUS      current
   DESCRIPTION
      "Path: ethernet3.editConf.inboundBandwidth.action.cirAction.ip.dropLevel

       Possibilities:
               unchanged   (0)"
   ::= {er1645v2Lan3IbwEntry 4071292928}

er1645v2Lan3IbwActCirActIpDeFlag OBJECT-TYPE
   SYNTAX      INTEGER
               {
               unchanged (255),
               clear (0),
               set (1)
               }
   MAX-ACCESS  read-write
   STATUS      current
   DESCRIPTION
      "Path: ethernet3.editConf.inboundBandwidth.action.cirAction.ip.deFlag

       Possibilities:
               unchanged   (255)
               clear   (0)
               set   (1)"
   ::= {er1645v2Lan3IbwEntry 4071489536}

er1645v2Lan3IbwActEirActNone OBJECT-TYPE
   SYNTAX      OCTET STRING
   MAX-ACCESS  read-write
   STATUS      current
   DESCRIPTION
      "Path: ethernet3.editConf.inboundBandwidth.action.eirAction.none"
   ::= {er1645v2Lan3IbwEntry 4095737856}

er1645v2Lan3IbwActEirActEthCos1 OBJECT-TYPE
   SYNTAX      INTEGER
               {
               unchanged (256)
               }
   MAX-ACCESS  read-write
   STATUS      current
   DESCRIPTION
      "Path: ethernet3.editConf.inboundBandwidth.action.eirAction.ethernet.cosDepth1

       Possibilities:
               unchanged   (256)"
   ::= {er1645v2Lan3IbwEntry 4097900544}

er1645v2Lan3IbwActEirActEthDei1 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth1

       Possibilities:
               unchanged   (255)
               clear   (0)
               set   (1)"
   ::= {er1645v2Lan3IbwEntry 4099211264}

er1645v2Lan3IbwActEirActEthCos2 OBJECT-TYPE
   SYNTAX      INTEGER
               {
               unchanged (256)
               }
   MAX-ACCESS  read-write
   STATUS      current
   DESCRIPTION
      "Path: ethernet3.editConf.inboundBandwidth.action.eirAction.ethernet.cosDepth2

       Possibilities:
               unchanged   (256)"
   ::= {er1645v2Lan3IbwEntry 4097966080}

er1645v2Lan3IbwActEirActEthDei2 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth2

       Possibilities:
               unchanged   (255)
               clear   (0)
               set   (1)"
   ::= {er1645v2Lan3IbwEntry 4099276800}

er1645v2Lan3IbwActEirActEthCos3 OBJECT-TYPE
   SYNTAX      INTEGER
               {
               unchanged (256)
               }
   MAX-ACCESS  read-write
   STATUS      current
   DESCRIPTION
      "Path: ethernet3.editConf.inboundBandwidth.action.eirAction.ethernet.cosDepth3

       Possibilities:
               unchanged   (256)"
   ::= {er1645v2Lan3IbwEntry 4098031616}

er1645v2Lan3IbwActEirActEthDei3 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth3

       Possibilities:
               unchanged   (255)
               clear   (0)
               set   (1)"
   ::= {er1645v2Lan3IbwEntry 4099342336}

er1645v2Lan3IbwActEirActEthCos4 OBJECT-TYPE
   SYNTAX      INTEGER
               {
               unchanged (256)
               }
   MAX-ACCESS  read-write
   STATUS      current
   DESCRIPTION
      "Path: ethernet3.editConf.inboundBandwidth.action.eirAction.ethernet.cosDepth4

       Possibilities:
               unchanged   (256)"
   ::= {er1645v2Lan3IbwEntry 4098097152}

er1645v2Lan3IbwActEirActEthDei4 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth4

       Possibilities:
               unchanged   (255)
               clear   (0)
               set   (1)"
   ::= {er1645v2Lan3IbwEntry 4099407872}

er1645v2Lan3IbwActEirActEthCos5 OBJECT-TYPE
   SYNTAX      INTEGER
               {
               unchanged (256)
               }
   MAX-ACCESS  read-write
   STATUS      current
   DESCRIPTION
      "Path: ethernet3.editConf.inboundBandwidth.action.eirAction.ethernet.cosDepth5

       Possibilities:
               unchanged   (256)"
   ::= {er1645v2Lan3IbwEntry 4098162688}

er1645v2Lan3IbwActEirActEthDei5 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth5

       Possibilities:
               unchanged   (255)
               clear   (0)
               set   (1)"
   ::= {er1645v2Lan3IbwEntry 4099473408}

er1645v2Lan3IbwActEirActEthCos6 OBJECT-TYPE
   SYNTAX      INTEGER
               {
               unchanged (256)
               }
   MAX-ACCESS  read-write
   STATUS      current
   DESCRIPTION
      "Path: ethernet3.editConf.inboundBandwidth.action.eirAction.ethernet.cosDepth6

       Possibilities:
               unchanged   (256)"
   ::= {er1645v2Lan3IbwEntry 4098228224}

er1645v2Lan3IbwActEirActEthDei6 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth6

       Possibilities:
               unchanged   (255)
               clear   (0)
               set   (1)"
   ::= {er1645v2Lan3IbwEntry 4099538944}

er1645v2Lan3IbwActEirActEthCos7 OBJECT-TYPE
   SYNTAX      INTEGER
               {
               unchanged (256)
               }
   MAX-ACCESS  read-write
   STATUS      current
   DESCRIPTION
      "Path: ethernet3.editConf.inboundBandwidth.action.eirAction.ethernet.cosDepth7

       Possibilities:
               unchanged   (256)"
   ::= {er1645v2Lan3IbwEntry 4098293760}

er1645v2Lan3IbwActEirActEthDei7 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth7

       Possibilities:
               unchanged   (255)
               clear   (0)
               set   (1)"
   ::= {er1645v2Lan3IbwEntry 4099604480}

er1645v2Lan3IbwActEirActEthCos8 OBJECT-TYPE
   SYNTAX      INTEGER
               {
               unchanged (256)
               }
   MAX-ACCESS  read-write
   STATUS      current
   DESCRIPTION
      "Path: ethernet3.editConf.inboundBandwidth.action.eirAction.ethernet.cosDepth8

       Possibilities:
               unchanged   (256)"
   ::= {er1645v2Lan3IbwEntry 4098359296}

er1645v2Lan3IbwActEirActEthDei8 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth8

       Possibilities:
               unchanged   (255)
               clear   (0)
               set   (1)"
   ::= {er1645v2Lan3IbwEntry 4099670016}

er1645v2Lan3IbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4098424832}

er1645v2Lan3IbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4098490368}

er1645v2Lan3IbwActEirActEthDrpLev OBJECT-TYPE
   SYNTAX      INTEGER
               {
               unchanged (0)
               }
   MAX-ACCESS  read-write
   STATUS      current
   DESCRIPTION
      "Path: ethernet3.editConf.inboundBandwidth.action.eirAction.ethernet.dropLevel

       Possibilities:
               unchanged   (0)"
   ::= {er1645v2Lan3IbwEntry 4098555904}

er1645v2Lan3IbwActEirActEthDeFlag OBJECT-TYPE
   SYNTAX      INTEGER
               {
               unchanged (255),
               clear (0),
               set (1)
               }
   MAX-ACCESS  read-write
   STATUS      current
   DESCRIPTION
      "Path: ethernet3.editConf.inboundBandwidth.action.eirAction.ethernet.deFlag

       Possibilities:
               unchanged   (255)
               clear   (0)
               set   (1)"
   ::= {er1645v2Lan3IbwEntry 4098752512}

er1645v2Lan3IbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4104716288}

er1645v2Lan3IbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4104781824}

er1645v2Lan3IbwActEirActIpDrpLev OBJECT-TYPE
   SYNTAX      INTEGER
               {
               unchanged (0)
               }
   MAX-ACCESS  read-write
   STATUS      current
   DESCRIPTION
      "Path: ethernet3.editConf.inboundBandwidth.action.eirAction.ip.dropLevel

       Possibilities:
               unchanged   (0)"
   ::= {er1645v2Lan3IbwEntry 4104847360}

er1645v2Lan3IbwActEirActIpDeFlag OBJECT-TYPE
   SYNTAX      INTEGER
               {
               unchanged (255),
               clear (0),
               set (1)
               }
   MAX-ACCESS  read-write
   STATUS      current
   DESCRIPTION
      "Path: ethernet3.editConf.inboundBandwidth.action.eirAction.ip.deFlag

       Possibilities:
               unchanged   (255)
               clear   (0)
               set   (1)"
   ::= {er1645v2Lan3IbwEntry 4105043968}

er1645v2Lan3IbwActViolActNone OBJECT-TYPE
   SYNTAX      OCTET STRING
   MAX-ACCESS  read-write
   STATUS      current
   DESCRIPTION
      "Path: ethernet3.editConf.inboundBandwidth.action.violateAction.none"
   ::= {er1645v2Lan3IbwEntry 4129292288}

er1645v2Lan3IbwActViolActDrop OBJECT-TYPE
   SYNTAX      OCTET STRING
   MAX-ACCESS  read-write
   STATUS      current
   DESCRIPTION
      "Path: ethernet3.editConf.inboundBandwidth.action.violateAction.drop"
   ::= {er1645v2Lan3IbwEntry 4133486592}

er1645v2Lan3IbwActViolActEthCos1 OBJECT-TYPE
   SYNTAX      INTEGER
               {
               unchanged (256)
               }
   MAX-ACCESS  read-write
   STATUS      current
   DESCRIPTION
      "Path: ethernet3.editConf.inboundBandwidth.action.violateAction.ethernet.cosDepth1

       Possibilities:
               unchanged   (256)"
   ::= {er1645v2Lan3IbwEntry 4131454976}

er1645v2Lan3IbwActViolActEthDei1 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth1

       Possibilities:
               unchanged   (255)
               clear   (0)
               set   (1)"
   ::= {er1645v2Lan3IbwEntry 4132765696}

er1645v2Lan3IbwActViolActEthCos2 OBJECT-TYPE
   SYNTAX      INTEGER
               {
               unchanged (256)
               }
   MAX-ACCESS  read-write
   STATUS      current
   DESCRIPTION
      "Path: ethernet3.editConf.inboundBandwidth.action.violateAction.ethernet.cosDepth2

       Possibilities:
               unchanged   (256)"
   ::= {er1645v2Lan3IbwEntry 4131520512}

er1645v2Lan3IbwActViolActEthDei2 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth2

       Possibilities:
               unchanged   (255)
               clear   (0)
               set   (1)"
   ::= {er1645v2Lan3IbwEntry 4132831232}

er1645v2Lan3IbwActViolActEthCos3 OBJECT-TYPE
   SYNTAX      INTEGER
               {
               unchanged (256)
               }
   MAX-ACCESS  read-write
   STATUS      current
   DESCRIPTION
      "Path: ethernet3.editConf.inboundBandwidth.action.violateAction.ethernet.cosDepth3

       Possibilities:
               unchanged   (256)"
   ::= {er1645v2Lan3IbwEntry 4131586048}

er1645v2Lan3IbwActViolActEthDei3 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth3

       Possibilities:
               unchanged   (255)
               clear   (0)
               set   (1)"
   ::= {er1645v2Lan3IbwEntry 4132896768}

er1645v2Lan3IbwActViolActEthCos4 OBJECT-TYPE
   SYNTAX      INTEGER
               {
               unchanged (256)
               }
   MAX-ACCESS  read-write
   STATUS      current
   DESCRIPTION
      "Path: ethernet3.editConf.inboundBandwidth.action.violateAction.ethernet.cosDepth4

       Possibilities:
               unchanged   (256)"
   ::= {er1645v2Lan3IbwEntry 4131651584}

er1645v2Lan3IbwActViolActEthDei4 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth4

       Possibilities:
               unchanged   (255)
               clear   (0)
               set   (1)"
   ::= {er1645v2Lan3IbwEntry 4132962304}

er1645v2Lan3IbwActViolActEthCos5 OBJECT-TYPE
   SYNTAX      INTEGER
               {
               unchanged (256)
               }
   MAX-ACCESS  read-write
   STATUS      current
   DESCRIPTION
      "Path: ethernet3.editConf.inboundBandwidth.action.violateAction.ethernet.cosDepth5

       Possibilities:
               unchanged   (256)"
   ::= {er1645v2Lan3IbwEntry 4131717120}

er1645v2Lan3IbwActViolActEthDei5 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth5

       Possibilities:
               unchanged   (255)
               clear   (0)
               set   (1)"
   ::= {er1645v2Lan3IbwEntry 4133027840}

er1645v2Lan3IbwActViolActEthCos6 OBJECT-TYPE
   SYNTAX      INTEGER
               {
               unchanged (256)
               }
   MAX-ACCESS  read-write
   STATUS      current
   DESCRIPTION
      "Path: ethernet3.editConf.inboundBandwidth.action.violateAction.ethernet.cosDepth6

       Possibilities:
               unchanged   (256)"
   ::= {er1645v2Lan3IbwEntry 4131782656}

er1645v2Lan3IbwActViolActEthDei6 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth6

       Possibilities:
               unchanged   (255)
               clear   (0)
               set   (1)"
   ::= {er1645v2Lan3IbwEntry 4133093376}

er1645v2Lan3IbwActViolActEthCos7 OBJECT-TYPE
   SYNTAX      INTEGER
               {
               unchanged (256)
               }
   MAX-ACCESS  read-write
   STATUS      current
   DESCRIPTION
      "Path: ethernet3.editConf.inboundBandwidth.action.violateAction.ethernet.cosDepth7

       Possibilities:
               unchanged   (256)"
   ::= {er1645v2Lan3IbwEntry 4131848192}

er1645v2Lan3IbwActViolActEthDei7 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth7

       Possibilities:
               unchanged   (255)
               clear   (0)
               set   (1)"
   ::= {er1645v2Lan3IbwEntry 4133158912}

er1645v2Lan3IbwActViolActEthCos8 OBJECT-TYPE
   SYNTAX      INTEGER
               {
               unchanged (256)
               }
   MAX-ACCESS  read-write
   STATUS      current
   DESCRIPTION
      "Path: ethernet3.editConf.inboundBandwidth.action.violateAction.ethernet.cosDepth8

       Possibilities:
               unchanged   (256)"
   ::= {er1645v2Lan3IbwEntry 4131913728}

er1645v2Lan3IbwActViolActEthDei8 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth8

       Possibilities:
               unchanged   (255)
               clear   (0)
               set   (1)"
   ::= {er1645v2Lan3IbwEntry 4133224448}

er1645v2Lan3IbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4131979264}

er1645v2Lan3IbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4132044800}

er1645v2Lan3IbwActViolActEthDrpLev OBJECT-TYPE
   SYNTAX      INTEGER
               {
               unchanged (0)
               }
   MAX-ACCESS  read-write
   STATUS      current
   DESCRIPTION
      "Path: ethernet3.editConf.inboundBandwidth.action.violateAction.ethernet.dropLevel

       Possibilities:
               unchanged   (0)"
   ::= {er1645v2Lan3IbwEntry 4132110336}

er1645v2Lan3IbwActViolActEthDeFlag OBJECT-TYPE
   SYNTAX      INTEGER
               {
               unchanged (255),
               clear (0),
               set (1)
               }
   MAX-ACCESS  read-write
   STATUS      current
   DESCRIPTION
      "Path: ethernet3.editConf.inboundBandwidth.action.violateAction.ethernet.deFlag

       Possibilities:
               unchanged   (255)
               clear   (0)
               set   (1)"
   ::= {er1645v2Lan3IbwEntry 4132306944}

er1645v2Lan3IbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3IbwEntry 4138270720}

er1645v2Lan3IbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3IbwEntry 4138336256}

er1645v2Lan3IbwActViolActIpDrpLev OBJECT-TYPE
   SYNTAX      INTEGER
               {
               unchanged (0)
               }
   MAX-ACCESS  read-write
   STATUS      current
   DESCRIPTION
      "Path: ethernet3.editConf.inboundBandwidth.action.violateAction.ip.dropLevel

       Possibilities:
               unchanged   (0)"
   ::= {er1645v2Lan3IbwEntry 4138401792}

er1645v2Lan3IbwActViolActIpDeFlag OBJECT-TYPE
   SYNTAX      INTEGER
               {
               unchanged (255),
               clear (0),
               set (1)
               }
   MAX-ACCESS  read-write
   STATUS      current
   DESCRIPTION
      "Path: ethernet3.editConf.inboundBandwidth.action.violateAction.ip.deFlag

       Possibilities:
               unchanged   (255)
               clear   (0)
               set   (1)"
   ::= {er1645v2Lan3IbwEntry 4138598400}

er1645v2Lan3IbwSubInterfacesExcluded OBJECT-TYPE
   SYNTAX      INTEGER
               {
               s (1)
               }
   MAX-ACCESS  read-write
   STATUS      current
   DESCRIPTION
      "Path: ethernet3.editConf.inboundBandwidth.subInterfaces.excluded

       Possibilities:
                  (1)"
   ::= {er1645v2Lan3IbwEntry 2416967680}

er1645v2Lan3IbwSubInterfacesIncludedInAccessList OBJECT-TYPE
   SYNTAX      DisplayString
   MAX-ACCESS  read-write
   STATUS      current
   DESCRIPTION
      "Path: ethernet3.editConf.inboundBandwidth.subInterfaces.included.inAccessList"
   ::= {er1645v2Lan3IbwEntry 2418020352}


er1645v2Lan3PriorityPolicy OBJECT-TYPE
   SYNTAX      DisplayString
   MAX-ACCESS  read-write
   STATUS      current
   DESCRIPTION
      "Path: ethernet3.editConf.priorityPolicy
       Info: Preferred Policy"
   ::= {er1645v2Lan3 39}


er1645v2Lan3Mru OBJECT-TYPE
   SYNTAX      Integer32
   MAX-ACCESS  read-write
   STATUS      current
   DESCRIPTION
      "Path: ethernet3.editConf.mru"
   ::= {er1645v2Lan3 43}


er1645v2Lan3DelayOptimisation OBJECT-TYPE
   SYNTAX      INTEGER
               {
               disabled (0),
               enabled (1)
               }
   MAX-ACCESS  read-write
   STATUS      current
   DESCRIPTION
      "Path: ethernet3.editConf.delayOptimisation
       Info: optimise delay

       Possibilities:
               disabled   (0)
               enabled   (1)"
   ::= {er1645v2Lan3 80}


er1645v2Lan3AlarmMask OBJECT-TYPE
   SYNTAX      Integer32
   MAX-ACCESS  read-write
   STATUS      current
   DESCRIPTION
      "Path: ethernet3.editConf.alarmMask
       Info: ifAlarmMask

       Bit meanings:
               bit 0 = linkDown,
               bit 9 = pppoEDown"
   ::= {er1645v2Lan3 135}


er1645v2Lan3AlarmLev OBJECT IDENTIFIER ::= {er1645v2Lan3 170}

er1645v2Lan3AlarmLevSSC OBJECT IDENTIFIER ::= {er1645v2Lan3AlarmLev 1}

er1645v2Lan3AlarmLevEntry OBJECT IDENTIFIER ::= {er1645v2Lan3AlarmLevSSC 1}

er1645v2Lan3AlarmLevLinkDown OBJECT-TYPE
   SYNTAX      Integer32
   MAX-ACCESS  read-write
   STATUS      current
   DESCRIPTION
      "Path: ethernet3.editConf.alarmLevel.linkDown"
   ::= {er1645v2Lan3AlarmLevEntry 16777216}

er1645v2Lan3AlarmLevPppoEDown OBJECT-TYPE
   SYNTAX      Integer32
   MAX-ACCESS  read-write
   STATUS      current
   DESCRIPTION
      "Path: ethernet3.editConf.alarmLevel.pppoEDown"
   ::= {er1645v2Lan3AlarmLevEntry 167772160}


er1645v2Lan3Arp OBJECT IDENTIFIER ::= {er1645v2Lan3 19}

er1645v2Lan3ArpSSC OBJECT IDENTIFIER ::= {er1645v2Lan3Arp 1}

er1645v2Lan3ArpEntry OBJECT IDENTIFIER ::= {er1645v2Lan3ArpSSC 1}

er1645v2Lan3ArpTimeOut OBJECT-TYPE
   SYNTAX      TimeTicks
   MAX-ACCESS  read-write
   STATUS      current
   DESCRIPTION
      "Path: ethernet3.editConf.arp.timeOut

       Time in centi-second."
   ::= {er1645v2Lan3ArpEntry 201326592}

er1645v2Lan3ArpProxyArp OBJECT-TYPE
   SYNTAX      INTEGER
               {
               disabled (0),
               enabled (1)
               }
   MAX-ACCESS  read-write
   STATUS      current
   DESCRIPTION
      "Path: ethernet3.editConf.arp.proxyArp

       Possibilities:
               disabled   (0)
               enabled   (1)"
   ::= {er1645v2Lan3ArpEntry 838860800}

er1645v2Lan3ArpStaticArp OBJECT-TYPE
   SYNTAX      SEQUENCE OF Er1645v2Lan3ArpStaticArpEntry
   MAX-ACCESS  not-accessible
   STATUS      current
   DESCRIPTION
      ""
   ::= {er1645v2Lan3Arp 50331648}

er1645v2Lan3ArpStaticArpEntry OBJECT-TYPE
   SYNTAX      Er1645v2Lan3ArpStaticArpEntry
   MAX-ACCESS  not-accessible
   STATUS      current
   DESCRIPTION
      ""
   INDEX      { er1645v2Lan3ArpStaticArpTableIx }
   ::= {er1645v2Lan3ArpStaticArp 1}

Er1645v2Lan3ArpStaticArpEntry ::=
   SEQUENCE
      {
      er1645v2Lan3ArpStaticArpActions
         VariableLengthTableActions,
      er1645v2Lan3ArpStaticArpTableIx
         TableIndex,
      er1645v2Lan3ArpStaticArpMacAddress
         OCTET STRING,
      er1645v2Lan3ArpStaticArpIpAddress
         IpAddress
      }

er1645v2Lan3ArpStaticArpActions OBJECT-TYPE
   SYNTAX      VariableLengthTableActions
   MAX-ACCESS  read-write
   STATUS      current
   DESCRIPTION
      "By way of this field, some manipulations
       on this table may be performed."
   ::= {er1645v2Lan3ArpStaticArpEntry 2}

er1645v2Lan3ArpStaticArpTableIx OBJECT-TYPE
   SYNTAX      TableIndex
   MAX-ACCESS  not-accessible
   STATUS      current
   DESCRIPTION
      ""
   ::= {er1645v2Lan3ArpStaticArpEntry 11}

er1645v2Lan3ArpStaticArpMacAddress OBJECT-TYPE
   SYNTAX      OCTET STRING
   MAX-ACCESS  read-write
   STATUS      current
   DESCRIPTION
      "Path: ethernet3.editConf.arp.staticArp.macAddress

       MAC address."
   ::= {er1645v2Lan3ArpStaticArpEntry 16777216}

er1645v2Lan3ArpStaticArpIpAddress OBJECT-TYPE
   SYNTAX      IpAddress
   MAX-ACCESS  read-write
   STATUS      current
   DESCRIPTION
      "Path: ethernet3.editConf.arp.staticArp.ipAddress"
   ::= {er1645v2Lan3ArpStaticArpEntry 33554432}


er1645v2Lan3BrC OBJECT IDENTIFIER ::= {er1645v2Lan3 27}

er1645v2Lan3BrCSSC OBJECT IDENTIFIER ::= {er1645v2Lan3BrC 1}

er1645v2Lan3BrCEntry OBJECT IDENTIFIER ::= {er1645v2Lan3BrCSSC 1}

er1645v2Lan3BrCAccessList OBJECT-TYPE
   SYNTAX      DisplayString
   MAX-ACCESS  read-write
   STATUS      current
   DESCRIPTION
      "Path: ethernet3.editConf.bridging.accessList"
   ::= {er1645v2Lan3BrCEntry 83886080}

er1645v2Lan3BrCInAccessList OBJECT-TYPE
   SYNTAX      DisplayString
   MAX-ACCESS  read-write
   STATUS      current
   DESCRIPTION
      "Path: ethernet3.editConf.bridging.inAccessList"
   ::= {er1645v2Lan3BrCEntry 251658240}

er1645v2Lan3BrCTp OBJECT-TYPE
   SYNTAX      DisplayString
   MAX-ACCESS  read-write
   STATUS      current
   DESCRIPTION
      "Path: ethernet3.editConf.bridging.trafficPolicy"
   ::= {er1645v2Lan3BrCEntry 100663296}

er1645v2Lan3BrCBridgeGroup OBJECT-TYPE
   SYNTAX      DisplayString
   MAX-ACCESS  read-write
   STATUS      current
   DESCRIPTION
      "Path: ethernet3.editConf.bridging.bridgeGroup"
   ::= {er1645v2Lan3BrCEntry 117440512}

er1645v2Lan3BrCLimBC OBJECT-TYPE
   SYNTAX      INTEGER
               {
               disabled (0),
               enabled (1)
               }
   MAX-ACCESS  read-write
   STATUS      current
   DESCRIPTION
      "Path: ethernet3.editConf.bridging.limitBroadcasts

       Possibilities:
               disabled   (0)
               enabled   (1)"
   ::= {er1645v2Lan3BrCEntry 134217728}

er1645v2Lan3BrCPrivateMode OBJECT-TYPE
   SYNTAX      INTEGER
               {
               disabled (0),
               enabled (1)
               }
   MAX-ACCESS  read-write
   STATUS      current
   DESCRIPTION
      "Path: ethernet3.editConf.bridging.privateMode

       Possibilities:
               disabled   (0)
               enabled   (1)"
   ::= {er1645v2Lan3BrCEntry 419430400}

er1645v2Lan3BrCLearning OBJECT-TYPE
   SYNTAX      INTEGER
               {
               disabled (0),
               enabled (1)
               }
   MAX-ACCESS  read-write
   STATUS      current
   DESCRIPTION
      "Path: ethernet3.editConf.bridging.learning

       Possibilities:
               disabled   (0)
               enabled   (1)"
   ::= {er1645v2Lan3BrCEntry 201326592}

er1645v2Lan3BrCMaxCacheSize OBJECT-TYPE
   SYNTAX      INTEGER
               {
               unlimited (0)
               }
   MAX-ACCESS  read-write
   STATUS      current
   DESCRIPTION
      "Path: ethernet3.editConf.bridging.maxCacheSize

       Possibilities:
               unlimited   (0)"
   ::= {er1645v2Lan3BrCEntry 218103808}

er1645v2Lan3BrCRelearnDropOnRelearn OBJECT-TYPE
   SYNTAX      INTEGER
               {
               disabled (0),
               enabled (1)
               }
   MAX-ACCESS  read-write
   STATUS      current
   DESCRIPTION
      "Path: ethernet3.editConf.bridging.relearn.dropOnRelearn

       Possibilities:
               disabled   (0)
               enabled   (1)"
   ::= {er1645v2Lan3BrCEntry 234946560}

er1645v2Lan3BrCRelearnShutdownThreshold OBJECT-TYPE
   SYNTAX      Integer32
   MAX-ACCESS  read-write
   STATUS      current
   DESCRIPTION
      "Path: ethernet3.editConf.bridging.relearn.shutdownThreshold"
   ::= {er1645v2Lan3BrCEntry 235012096}

er1645v2Lan3BrCRelearnShutdownTime OBJECT-TYPE
   SYNTAX      TimeTicks
   MAX-ACCESS  read-write
   STATUS      current
   DESCRIPTION
      "Path: ethernet3.editConf.bridging.relearn.shutdownTime

       Time in centi-second."
   ::= {er1645v2Lan3BrCEntry 235077632}

er1645v2Lan3BrCRelearnLoopDetection OBJECT-TYPE
   SYNTAX      INTEGER
               {
               disabled (0),
               passive (1),
               active (2)
               }
   MAX-ACCESS  read-write
   STATUS      current
   DESCRIPTION
      "Path: ethernet3.editConf.bridging.relearn.loopDetection

       Possibilities:
               disabled   (0)
               passive   (1)
               active   (2)"
   ::= {er1645v2Lan3BrCEntry 235143168}

er1645v2Lan3BrCRelearnLoopDetectionInterval OBJECT-TYPE
   SYNTAX      TimeTicks
   MAX-ACCESS  read-write
   STATUS      current
   DESCRIPTION
      "Path: ethernet3.editConf.bridging.relearn.loopDetectionInterval

       Time in centi-second."
   ::= {er1645v2Lan3BrCEntry 235208704}

er1645v2Lan3BrCVlanMemberShip OBJECT-TYPE
   SYNTAX      INTEGER
               {
               all (0),
               none (1),
               grouped (2)
               }
   MAX-ACCESS  read-write
   STATUS      current
   DESCRIPTION
      "Path: ethernet3.editConf.bridging.vlanMemberShip

       Possibilities:
               all   (0)
               none   (1)
               grouped   (2)"
   ::= {er1645v2Lan3BrCEntry 318767104}

er1645v2Lan3BrCDot1adType OBJECT-TYPE
   SYNTAX      INTEGER
               {
               slOPTg (0),
               cPort (4),
               sPort (1),
               nni (2)
               }
   MAX-ACCESS  read-write
   STATUS      current
   DESCRIPTION
      "Path: ethernet3.editConf.bridging.dot1ad.type

       Possibilities:
               <OPT>   (0)
               cPort   (4)
               sPort   (1)
               nni   (2)"
   ::= {er1645v2Lan3BrCEntry 503382016}

er1645v2Lan3BrCPriority OBJECT-TYPE
   SYNTAX      Integer32
   MAX-ACCESS  read-write
   STATUS      current
   DESCRIPTION
      "Path: ethernet3.editConf.bridging.priority"
   ::= {er1645v2Lan3BrCEntry 33554432}

er1645v2Lan3BrCPathCost OBJECT-TYPE
   SYNTAX      Integer32
   MAX-ACCESS  read-write
   STATUS      current
   DESCRIPTION
      "Path: ethernet3.editConf.bridging.pathCost"
   ::= {er1645v2Lan3BrCEntry 50331648}

er1645v2Lan3BrCInternalPathCost OBJECT-TYPE
   SYNTAX      Integer32
   MAX-ACCESS  read-write
   STATUS      current
   DESCRIPTION
      "Path: ethernet3.editConf.bridging.internalPathCost"
   ::= {er1645v2Lan3BrCEntry 301989888}

er1645v2Lan3BrCTCD OBJECT-TYPE
   SYNTAX      INTEGER
               {
               disabled (0),
               enabled (1)
               }
   MAX-ACCESS  read-write
   STATUS      current
   DESCRIPTION
      "Path: ethernet3.editConf.bridging.topologyChangeDetection

       Possibilities:
               disabled   (0)
               enabled   (1)"
   ::= {er1645v2Lan3BrCEntry 67108864}

er1645v2Lan3BrCRestrictedRole OBJECT-TYPE
   SYNTAX      INTEGER
               {
               disabled (0),
               enabled (1)
               }
   MAX-ACCESS  read-write
   STATUS      current
   DESCRIPTION
      "Path: ethernet3.editConf.bridging.restrictedRole

       Possibilities:
               disabled   (0)
               enabled   (1)"
   ::= {er1645v2Lan3BrCEntry 335544320}

er1645v2Lan3BrCAdminEdge OBJECT-TYPE
   SYNTAX      INTEGER
               {
               disabled (0),
               enabled (1)
               }
   MAX-ACCESS  read-write
   STATUS      current
   DESCRIPTION
      "Path: ethernet3.editConf.bridging.adminEdge

       Possibilities:
               disabled   (0)
               enabled   (1)"
   ::= {er1645v2Lan3BrCEntry 268435456}

er1645v2Lan3BrCMgmtInline OBJECT-TYPE
   SYNTAX      INTEGER
               {
               disabled (0),
               enabled (1)
               }
   MAX-ACCESS  read-write
   STATUS      current
   DESCRIPTION
      "Path: ethernet3.editConf.bridging.mgmtInline

       Possibilities:
               disabled   (0)
               enabled   (1)"
   ::= {er1645v2Lan3BrCEntry 369098752}

er1645v2Lan3BrCL2ptMode OBJECT-TYPE
   SYNTAX      INTEGER
               {
               disabled (0),
               enabled (1)
               }
   MAX-ACCESS  read-write
   STATUS      current
   DESCRIPTION
      "Path: ethernet3.editConf.bridging.l2ProtTunnel.mode

       Possibilities:
               disabled   (0)
               enabled   (1)"
   ::= {er1645v2Lan3BrCEntry 403701760}

er1645v2Lan3BrCL2ptProtocols OBJECT-TYPE
   SYNTAX      Integer32
   MAX-ACCESS  read-write
   STATUS      current
   DESCRIPTION
      "Path: ethernet3.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan3BrCEntry 404750336}

er1645v2Lan3BrCL2ptDestMac OBJECT-TYPE
   SYNTAX      OCTET STRING
   MAX-ACCESS  read-write
   STATUS      current
   DESCRIPTION
      "Path: ethernet3.editConf.bridging.l2ProtTunnel.destinationMac

       MAC address."
   ::= {er1645v2Lan3BrCEntry 405798912}

er1645v2Lan3BrCL2ptCos OBJECT-TYPE
   SYNTAX      INTEGER
               {
               unchanged (255)
               }
   MAX-ACCESS  read-write
   STATUS      current
   DESCRIPTION
      "Path: ethernet3.editConf.bridging.l2ProtTunnel.cos

       Possibilities:
               unchanged   (255)"
   ::= {er1645v2Lan3BrCEntry 406847488}

er1645v2Lan3BrCL2ptDropThrStp OBJECT-TYPE
   SYNTAX      INTEGER
               {
               unlimited (0)
               }
   UNITS       "packets/sec"
   MAX-ACCESS  read-write
   STATUS      current
   DESCRIPTION
      "Path: ethernet3.editConf.bridging.l2ProtTunnel.dropThresholds.stp

       unit name = packets/sec

       Possibilities:
               unlimited   (0)"
   ::= {er1645v2Lan3BrCEntry 407900160}

er1645v2Lan3BrCL2ptDropThrLldp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lldp

       unit name = packets/sec

       Possibilities:
               unlimited   (0)"
   ::= {er1645v2Lan3BrCEntry 407904256}

er1645v2Lan3BrCL2ptDropThrOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.oam

       unit name = packets/sec

       Possibilities:
               unlimited   (0)"
   ::= {er1645v2Lan3BrCEntry 407908352}

er1645v2Lan3BrCL2ptDropThrCdp OBJECT-TYPE
   SYNTAX      INTEGER
               {
               unlimited (0)
               }
   UNITS       "packets/sec"
   MAX-ACCESS  read-write
   STATUS      current
   DESCRIPTION
      "Path: ethernet3.editConf.bridging.l2ProtTunnel.dropThresholds.cdp

       unit name = packets/sec

       Possibilities:
               unlimited   (0)"
   ::= {er1645v2Lan3BrCEntry 407912448}

er1645v2Lan3BrCL2ptDropThrVtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.vtp

       unit name = packets/sec

       Possibilities:
               unlimited   (0)"
   ::= {er1645v2Lan3BrCEntry 407916544}

er1645v2Lan3BrCL2ptDropThrLacp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lacp

       unit name = packets/sec

       Possibilities:
               unlimited   (0)"
   ::= {er1645v2Lan3BrCEntry 407920640}

er1645v2Lan3BrCL2ptDropThrEfmOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.efmOam

       unit name = packets/sec

       Possibilities:
               unlimited   (0)"
   ::= {er1645v2Lan3BrCEntry 407924736}

er1645v2Lan3BrCL2ptDropThrPvst OBJECT-TYPE
   SYNTAX      INTEGER
               {
               unlimited (0)
               }
   UNITS       "packets/sec"
   MAX-ACCESS  read-write
   STATUS      current
   DESCRIPTION
      "Path: ethernet3.editConf.bridging.l2ProtTunnel.dropThresholds.pvst

       unit name = packets/sec

       Possibilities:
               unlimited   (0)"
   ::= {er1645v2Lan3BrCEntry 407928832}

er1645v2Lan3BrCL2ptDropThrMmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mmrp

       unit name = packets/sec

       Possibilities:
               unlimited   (0)"
   ::= {er1645v2Lan3BrCEntry 407932928}

er1645v2Lan3BrCL2ptDropThrMvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mvrp

       unit name = packets/sec

       Possibilities:
               unlimited   (0)"
   ::= {er1645v2Lan3BrCEntry 407937024}

er1645v2Lan3BrCL2ptDropThrGvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gvrp

       unit name = packets/sec

       Possibilities:
               unlimited   (0)"
   ::= {er1645v2Lan3BrCEntry 407941120}

er1645v2Lan3BrCL2ptDropThrGmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gmrp

       unit name = packets/sec

       Possibilities:
               unlimited   (0)"
   ::= {er1645v2Lan3BrCEntry 407945216}

er1645v2Lan3BrCL2ptDropThrDtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.dtp

       unit name = packets/sec

       Possibilities:
               unlimited   (0)"
   ::= {er1645v2Lan3BrCEntry 407949312}

er1645v2Lan3BrCL2ptDropThrPagp OBJECT-TYPE
   SYNTAX      INTEGER
               {
               unlimited (0)
               }
   UNITS       "packets/sec"
   MAX-ACCESS  read-write
   STATUS      current
   DESCRIPTION
      "Path: ethernet3.editConf.bridging.l2ProtTunnel.dropThresholds.pagp

       unit name = packets/sec

       Possibilities:
               unlimited   (0)"
   ::= {er1645v2Lan3BrCEntry 407953408}

er1645v2Lan3BrCL2ptDropThrUdld OBJECT-TYPE
   SYNTAX      INTEGER
               {
               unlimited (0)
               }
   UNITS       "packets/sec"
   MAX-ACCESS  read-write
   STATUS      current
   DESCRIPTION
      "Path: ethernet3.editConf.bridging.l2ProtTunnel.dropThresholds.udld

       unit name = packets/sec

       Possibilities:
               unlimited   (0)"
   ::= {er1645v2Lan3BrCEntry 407957504}


er1645v2Lan3VlanTagging OBJECT IDENTIFIER ::= {er1645v2Lan3 14}

er1645v2Lan3VlanTaggingSSC OBJECT IDENTIFIER ::= {er1645v2Lan3VlanTagging 1}

er1645v2Lan3VlanTaggingEntry OBJECT IDENTIFIER ::= {er1645v2Lan3VlanTaggingSSC 1}

er1645v2Lan3VlanTaggingUntaggedAction OBJECT-TYPE
   SYNTAX      INTEGER
               {
               discard (0),
               accept (1),
               tag (2)
               }
   MAX-ACCESS  read-write
   STATUS      current
   DESCRIPTION
      "Path: ethernet3.editConf.vlanTagging.untagged.action

       Possibilities:
               discard   (0)
               accept   (1)
               tag   (2)"
   ::= {er1645v2Lan3VlanTaggingEntry 671088640}

er1645v2Lan3VlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.untagged.tagInfo.tpid

       Possibilities:
               dot1Q   (33024)
               dot1ad   (34984)
               0x9100   (37120)
               0x9200   (37376)
               0x9300   (37632)"
   ::= {er1645v2Lan3VlanTaggingEntry 746586112}

er1645v2Lan3VlanTaggingUntaggedTagInfoVid OBJECT-TYPE
   SYNTAX      Integer32
   MAX-ACCESS  read-write
   STATUS      current
   DESCRIPTION
      "Path: ethernet3.editConf.vlanTagging.untagged.tagInfo.vid"
   ::= {er1645v2Lan3VlanTaggingEntry 754974720}

er1645v2Lan3VlanTaggingUnknownVlansAction OBJECT-TYPE
   SYNTAX      INTEGER
               {
               discard (0),
               accept (1),
               tag (2)
               }
   MAX-ACCESS  read-write
   STATUS      current
   DESCRIPTION
      "Path: ethernet3.editConf.vlanTagging.unknownVlans.action

       Possibilities:
               discard   (0)
               accept   (1)
               tag   (2)"
   ::= {er1645v2Lan3VlanTaggingEntry 1744830464}

er1645v2Lan3VlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.unknownVlans.tagInfo.tpid

       Possibilities:
               dot1Q   (33024)
               dot1ad   (34984)
               0x9100   (37120)
               0x9200   (37376)
               0x9300   (37632)"
   ::= {er1645v2Lan3VlanTaggingEntry 1820327936}

er1645v2Lan3VlanTaggingUnknownVlansTagInfoVid OBJECT-TYPE
   SYNTAX      Integer32
   MAX-ACCESS  read-write
   STATUS      current
   DESCRIPTION
      "Path: ethernet3.editConf.vlanTagging.unknownVlans.tagInfo.vid"
   ::= {er1645v2Lan3VlanTaggingEntry 1828716544}

er1645v2Lan3VlanTaggingVlans OBJECT-TYPE
   SYNTAX      SEQUENCE OF Er1645v2Lan3VlanTaggingVlansEntry
   MAX-ACCESS  not-accessible
   STATUS      current
   DESCRIPTION
      ""
   ::= {er1645v2Lan3VlanTagging 1073741824}

er1645v2Lan3VlanTaggingVlansEntry OBJECT-TYPE
   SYNTAX      Er1645v2Lan3VlanTaggingVlansEntry
   MAX-ACCESS  not-accessible
   STATUS      current
   DESCRIPTION
      ""
   INDEX      { er1645v2Lan3VlanTaggingVlansTableIx }
   ::= {er1645v2Lan3VlanTaggingVlans 1}

Er1645v2Lan3VlanTaggingVlansEntry ::=
   SEQUENCE
      {
      er1645v2Lan3VlanTaggingVlansActions
         VariableLengthTableActions,
      er1645v2Lan3VlanTaggingVlansTableIx
         TableIndex,
      er1645v2Lan3VlanTaggingVlansVid
         Integer32,
      er1645v2Lan3VlanTaggingVlansEndVid
         Integer32,
      er1645v2Lan3VlanTaggingVlansAction
         INTEGER,
      er1645v2Lan3VlanTaggingVlansTagInfoTpid
         INTEGER,
      er1645v2Lan3VlanTaggingVlansTagInfoVid
         Integer32
      }

er1645v2Lan3VlanTaggingVlansActions OBJECT-TYPE
   SYNTAX      VariableLengthTableActions
   MAX-ACCESS  read-write
   STATUS      current
   DESCRIPTION
      "By way of this field, some manipulations
       on this table may be performed."
   ::= {er1645v2Lan3VlanTaggingVlansEntry 2}

er1645v2Lan3VlanTaggingVlansTableIx OBJECT-TYPE
   SYNTAX      TableIndex
   MAX-ACCESS  not-accessible
   STATUS      current
   DESCRIPTION
      ""
   ::= {er1645v2Lan3VlanTaggingVlansEntry 11}

er1645v2Lan3VlanTaggingVlansVid OBJECT-TYPE
   SYNTAX      Integer32
   MAX-ACCESS  read-write
   STATUS      current
   DESCRIPTION
      "Path: ethernet3.editConf.vlanTagging.vlans.vid"
   ::= {er1645v2Lan3VlanTaggingVlansEntry 536870912}

er1645v2Lan3VlanTaggingVlansEndVid OBJECT-TYPE
   SYNTAX      Integer32
   MAX-ACCESS  read-write
   STATUS      current
   DESCRIPTION
      "Path: ethernet3.editConf.vlanTagging.vlans.endVid"
   ::= {er1645v2Lan3VlanTaggingVlansEntry 2147483648}

er1645v2Lan3VlanTaggingVlansAction OBJECT-TYPE
   SYNTAX      INTEGER
               {
               discard (0),
               accept (1),
               tag (2)
               }
   MAX-ACCESS  read-write
   STATUS      current
   DESCRIPTION
      "Path: ethernet3.editConf.vlanTagging.vlans.action

       Possibilities:
               discard   (0)
               accept   (1)
               tag   (2)"
   ::= {er1645v2Lan3VlanTaggingVlansEntry 1073741824}

er1645v2Lan3VlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.vlans.tagInfo.tpid

       Possibilities:
               dot1Q   (33024)
               dot1ad   (34984)
               0x9100   (37120)
               0x9200   (37376)
               0x9300   (37632)"
   ::= {er1645v2Lan3VlanTaggingVlansEntry 1677721600}

er1645v2Lan3VlanTaggingVlansTagInfoVid OBJECT-TYPE
   SYNTAX      Integer32
   MAX-ACCESS  read-write
   STATUS      current
   DESCRIPTION
      "Path: ethernet3.editConf.vlanTagging.vlans.tagInfo.vid"
   ::= {er1645v2Lan3VlanTaggingVlansEntry 1744830464}


er1645v2Lan3Oam OBJECT IDENTIFIER ::= {er1645v2Lan3 900}

er1645v2Lan3OamSSC OBJECT IDENTIFIER ::= {er1645v2Lan3Oam 1}

er1645v2Lan3OamEntry OBJECT IDENTIFIER ::= {er1645v2Lan3OamSSC 1}

er1645v2Lan3OamMode OBJECT-TYPE
   SYNTAX      INTEGER
               {
               disabled (0),
               passive (3),
               active (2)
               }
   MAX-ACCESS  read-write
   STATUS      current
   DESCRIPTION
      "Path: ethernet3.editConf.oam.mode

       Possibilities:
               disabled   (0)
               passive   (3)
               active   (2)"
   ::= {er1645v2Lan3OamEntry 16777216}

er1645v2Lan3OamLpbkLocalParAction OBJECT-TYPE
   SYNTAX      INTEGER
               {
               discard (0),
               forward (1)
               }
   MAX-ACCESS  read-write
   STATUS      current
   DESCRIPTION
      "Path: ethernet3.editConf.oam.loopbackLocalParserAction

       Possibilities:
               discard   (0)
               forward   (1)"
   ::= {er1645v2Lan3OamEntry 33554432}

er1645v2Lan3OamLpbkSwapMacAddr OBJECT-TYPE
   SYNTAX      INTEGER
               {
               disabled (0),
               enabled (1)
               }
   MAX-ACCESS  read-write
   STATUS      current
   DESCRIPTION
      "Path: ethernet3.editConf.oam.loopbackSwapMacAddresses

       Possibilities:
               disabled   (0)
               enabled   (1)"
   ::= {er1645v2Lan3OamEntry 50331648}

er1645v2Lan3OamLoopbackIgnoreRx OBJECT-TYPE
   SYNTAX      INTEGER
               {
               no (0),
               yes (1)
               }
   MAX-ACCESS  read-write
   STATUS      current
   DESCRIPTION
      "Path: ethernet3.editConf.oam.loopbackIgnoreRx

       Possibilities:
               no   (0)
               yes   (1)"
   ::= {er1645v2Lan3OamEntry 67108864}

er1645v2Lan3OamEventsErroredSymbolEnabled OBJECT-TYPE
   SYNTAX      INTEGER
               {
               no (0),
               yes (1)
               }
   MAX-ACCESS  read-write
   STATUS      current
   DESCRIPTION
      "Path: ethernet3.editConf.oam.events.erroredSymbol.enabled

       Possibilities:
               no   (0)
               yes   (1)"
   ::= {er1645v2Lan3OamEntry 83951872}

er1645v2Lan3OamEventsErroredSymbolWindowHi OBJECT-TYPE
   SYNTAX      INTEGER
               {
               default (0)
               }
   UNITS       "symbols"
   MAX-ACCESS  read-write
   STATUS      current
   DESCRIPTION
      "Path: ethernet3.editConf.oam.events.erroredSymbol.windowHi

       unit name = symbols

       Possibilities:
               default   (0)"
   ::= {er1645v2Lan3OamEntry 83952128}

er1645v2Lan3OamEventsErroredSymbolWindowLo OBJECT-TYPE
   SYNTAX      INTEGER
               {
               default (0)
               }
   UNITS       "symbols"
   MAX-ACCESS  read-write
   STATUS      current
   DESCRIPTION
      "Path: ethernet3.editConf.oam.events.erroredSymbol.windowLo

       unit name = symbols

       Possibilities:
               default   (0)"
   ::= {er1645v2Lan3OamEntry 83952384}

er1645v2Lan3OamEventsErroredSymbolThresholdHi OBJECT-TYPE
   SYNTAX      Integer32
   UNITS       "symbols"
   MAX-ACCESS  read-write
   STATUS      current
   DESCRIPTION
      "Path: ethernet3.editConf.oam.events.erroredSymbol.thresholdHi

       unit name = symbols"
   ::= {er1645v2Lan3OamEntry 83952640}

er1645v2Lan3OamEventsErroredSymbolThresholdLo OBJECT-TYPE
   SYNTAX      Integer32
   UNITS       "symbols"
   MAX-ACCESS  read-write
   STATUS      current
   DESCRIPTION
      "Path: ethernet3.editConf.oam.events.erroredSymbol.thresholdLo

       unit name = symbols"
   ::= {er1645v2Lan3OamEntry 83952896}

er1645v2Lan3OamEventsErroredFramePeriodEnabled OBJECT-TYPE
   SYNTAX      INTEGER
               {
               no (0),
               yes (1)
               }
   MAX-ACCESS  read-write
   STATUS      current
   DESCRIPTION
      "Path: ethernet3.editConf.oam.events.erroredFramePeriod.enabled

       Possibilities:
               no   (0)
               yes   (1)"
   ::= {er1645v2Lan3OamEntry 84017408}

er1645v2Lan3OamEventsErroredFramePeriodWindow OBJECT-TYPE
   SYNTAX      INTEGER
               {
               default (0)
               }
   UNITS       "frames"
   MAX-ACCESS  read-write
   STATUS      current
   DESCRIPTION
      "Path: ethernet3.editConf.oam.events.erroredFramePeriod.window

       unit name = frames

       Possibilities:
               default   (0)"
   ::= {er1645v2Lan3OamEntry 84017664}

er1645v2Lan3OamEventsErroredFramePeriodThreshold OBJECT-TYPE
   SYNTAX      Integer32
   UNITS       "frames"
   MAX-ACCESS  read-write
   STATUS      current
   DESCRIPTION
      "Path: ethernet3.editConf.oam.events.erroredFramePeriod.threshold

       unit name = frames"
   ::= {er1645v2Lan3OamEntry 84017920}

er1645v2Lan3OamEventsErroredFrameEnabled OBJECT-TYPE
   SYNTAX      INTEGER
               {
               no (0),
               yes (1)
               }
   MAX-ACCESS  read-write
   STATUS      current
   DESCRIPTION
      "Path: ethernet3.editConf.oam.events.erroredFrame.enabled

       Possibilities:
               no   (0)
               yes   (1)"
   ::= {er1645v2Lan3OamEntry 84082944}

er1645v2Lan3OamEventsErroredFrameWindow OBJECT-TYPE
   SYNTAX      Integer32
   UNITS       "100msec"
   MAX-ACCESS  read-write
   STATUS      current
   DESCRIPTION
      "Path: ethernet3.editConf.oam.events.erroredFrame.window

       unit name = 100msec"
   ::= {er1645v2Lan3OamEntry 84083200}

er1645v2Lan3OamEventsErroredFrameThreshold OBJECT-TYPE
   SYNTAX      Integer32
   UNITS       "frames"
   MAX-ACCESS  read-write
   STATUS      current
   DESCRIPTION
      "Path: ethernet3.editConf.oam.events.erroredFrame.threshold

       unit name = frames"
   ::= {er1645v2Lan3OamEntry 84083456}

er1645v2Lan3OamEventsErroredFrameSecondsEnabled OBJECT-TYPE
   SYNTAX      INTEGER
               {
               no (0),
               yes (1)
               }
   MAX-ACCESS  read-write
   STATUS      current
   DESCRIPTION
      "Path: ethernet3.editConf.oam.events.erroredFrameSeconds.enabled

       Possibilities:
               no   (0)
               yes   (1)"
   ::= {er1645v2Lan3OamEntry 84148480}

er1645v2Lan3OamEventsErroredFrameSecondsWindow OBJECT-TYPE
   SYNTAX      Integer32
   UNITS       "100msec"
   MAX-ACCESS  read-write
   STATUS      current
   DESCRIPTION
      "Path: ethernet3.editConf.oam.events.erroredFrameSeconds.window

       unit name = 100msec"
   ::= {er1645v2Lan3OamEntry 84148736}

er1645v2Lan3OamEventsErroredFrameSecondsThreshold OBJECT-TYPE
   SYNTAX      Integer32
   UNITS       "frames"
   MAX-ACCESS  read-write
   STATUS      current
   DESCRIPTION
      "Path: ethernet3.editConf.oam.events.erroredFrameSeconds.threshold

       unit name = frames"
   ::= {er1645v2Lan3OamEntry 84148992}

er1645v2Lan3OamEventsDyingGasp OBJECT-TYPE
   SYNTAX      INTEGER
               {
               disabled (0),
               enabled (1)
               }
   MAX-ACCESS  read-write
   STATUS      current
   DESCRIPTION
      "Path: ethernet3.editConf.oam.events.dyingGasp

       Possibilities:
               disabled   (0)
               enabled   (1)"
   ::= {er1645v2Lan3OamEntry 84213760}

er1645v2Lan3OamEventsCriticalEvent OBJECT-TYPE
   SYNTAX      INTEGER
               {
               disabled (0),
               enabled (1)
               }
   MAX-ACCESS  read-write
   STATUS      current
   DESCRIPTION
      "Path: ethernet3.editConf.oam.events.criticalEvent

       Possibilities:
               disabled   (0)
               enabled   (1)"
   ::= {er1645v2Lan3OamEntry 84279296}


er1645v2Lan3Lst OBJECT IDENTIFIER ::= {er1645v2Lan3 12}

er1645v2Lan3LstSSC OBJECT IDENTIFIER ::= {er1645v2Lan3Lst 1}

er1645v2Lan3LstEntry OBJECT IDENTIFIER ::= {er1645v2Lan3LstSSC 1}

er1645v2Lan3LstTrackedInterface OBJECT-TYPE
   SYNTAX      DisplayString
   MAX-ACCESS  read-write
   STATUS      current
   DESCRIPTION
      "Path: ethernet3.editConf.linkStateTracking.trackedInterface"
   ::= {er1645v2Lan3LstEntry 16777216}


er1645v2Lan3Dot1x OBJECT IDENTIFIER ::= {er1645v2Lan3 191}

er1645v2Lan3Dot1xSSC OBJECT IDENTIFIER ::= {er1645v2Lan3Dot1x 1}

er1645v2Lan3Dot1xEntry OBJECT IDENTIFIER ::= {er1645v2Lan3Dot1xSSC 1}

er1645v2Lan3Dot1xMode OBJECT-TYPE
   SYNTAX      INTEGER
               {
               inactive (0),
               auto (1)
               }
   MAX-ACCESS  read-write
   STATUS      current
   DESCRIPTION
      "Path: ethernet3.editConf.dot1x.mode

       Possibilities:
               inactive   (0)
               auto   (1)"
   ::= {er1645v2Lan3Dot1xEntry 16777216}

er1645v2Lan3Dot1xMaxHosts OBJECT-TYPE
   SYNTAX      Integer32
   MAX-ACCESS  read-write
   STATUS      current
   DESCRIPTION
      "Path: ethernet3.editConf.dot1x.maxHosts"
   ::= {er1645v2Lan3Dot1xEntry 33554432}

er1645v2Lan3Dot1xReAuthentication OBJECT-TYPE
   SYNTAX      INTEGER
               {
               disabled (0),
               enabled (1)
               }
   MAX-ACCESS  read-write
   STATUS      current
   DESCRIPTION
      "Path: ethernet3.editConf.dot1x.reAuthentication

       Possibilities:
               disabled   (0)
               enabled   (1)"
   ::= {er1645v2Lan3Dot1xEntry 50331648}

er1645v2Lan3Dot1xReAuthPeriod OBJECT-TYPE
   SYNTAX      TimeTicks
   MAX-ACCESS  read-write
   STATUS      current
   DESCRIPTION
      "Path: ethernet3.editConf.dot1x.reAuthPeriod

       Time in centi-second."
   ::= {er1645v2Lan3Dot1xEntry 67108864}

er1645v2Lan3Dot1xQuietPeriod OBJECT-TYPE
   SYNTAX      TimeTicks
   MAX-ACCESS  read-write
   STATUS      current
   DESCRIPTION
      "Path: ethernet3.editConf.dot1x.quietPeriod

       Time in centi-second."
   ::= {er1645v2Lan3Dot1xEntry 83886080}

er1645v2Lan3Dot1xSupplTimeout OBJECT-TYPE
   SYNTAX      TimeTicks
   MAX-ACCESS  read-write
   STATUS      current
   DESCRIPTION
      "Path: ethernet3.editConf.dot1x.supplTimeout

       Time in centi-second."
   ::= {er1645v2Lan3Dot1xEntry 100663296}

er1645v2Lan3Dot1xServerTimeout OBJECT-TYPE
   SYNTAX      TimeTicks
   MAX-ACCESS  read-write
   STATUS      current
   DESCRIPTION
      "Path: ethernet3.editConf.dot1x.serverTimeout

       Time in centi-second."
   ::= {er1645v2Lan3Dot1xEntry 117440512}

er1645v2Lan3Dot1xMaxReqCount OBJECT-TYPE
   SYNTAX      Integer32
   MAX-ACCESS  read-write
   STATUS      current
   DESCRIPTION
      "Path: ethernet3.editConf.dot1x.maxReqCount"
   ::= {er1645v2Lan3Dot1xEntry 134217728}


er1645v2Lan3Mode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet3.editConf.mode
       Info: routing and/or bridging or ipV6 or multilink selection

       Possibilities:
               bridging   (0)
               routing   (1)
               routingAndBridging   (2)
               ipV6   (3)
               ipV6/ipV4   (4)
               multilink   (5)"
   ::= {er1645v2Lan3 29}


er1645v2Lan3IpV6 OBJECT IDENTIFIER ::= {er1645v2Lan3 15}

er1645v2Lan3IpV6SSC OBJECT IDENTIFIER ::= {er1645v2Lan3IpV6 1}

er1645v2Lan3IpV6Entry OBJECT IDENTIFIER ::= {er1645v2Lan3IpV6SSC 1}

er1645v2Lan3IpV6VrfRouter OBJECT-TYPE
   SYNTAX      DisplayString
   MAX-ACCESS  read-write
   STATUS      current
   DESCRIPTION
      "Path: ethernet3.editConf.ipV6.vrfRouter"
   ::= {er1645v2Lan3IpV6Entry 16777216}

er1645v2Lan3IpV6AddrAutoConfigNrDupAddrDetects OBJECT-TYPE
   SYNTAX      Integer32
   MAX-ACCESS  read-write
   STATUS      current
   DESCRIPTION
      "Path: ethernet3.editConf.ipV6.addrAutoConfig.nrDupAddrDetects"
   ::= {er1645v2Lan3IpV6Entry 67174400}

er1645v2Lan3IpV6AddrAutoConfigAcceptRa OBJECT-TYPE
   SYNTAX      INTEGER
               {
               disabled (0),
               enabled (1)
               }
   MAX-ACCESS  read-write
   STATUS      current
   DESCRIPTION
      "Path: ethernet3.editConf.ipV6.addrAutoConfig.acceptRa

       Possibilities:
               disabled   (0)
               enabled   (1)"
   ::= {er1645v2Lan3IpV6Entry 67239936}

er1645v2Lan3IpV6AddrAutoConfigAcceptRaRdnss OBJECT-TYPE
   SYNTAX      INTEGER
               {
               disabled (0),
               enabled (1)
               }
   MAX-ACCESS  read-write
   STATUS      current
   DESCRIPTION
      "Path: ethernet3.editConf.ipV6.addrAutoConfig.acceptRaRdnss

       Possibilities:
               disabled   (0)
               enabled   (1)"
   ::= {er1645v2Lan3IpV6Entry 67305472}

er1645v2Lan3IpV6AddrAutoConfigAcceptRaDnssl OBJECT-TYPE
   SYNTAX      INTEGER
               {
               disabled (0),
               enabled (1)
               }
   MAX-ACCESS  read-write
   STATUS      current
   DESCRIPTION
      "Path: ethernet3.editConf.ipV6.addrAutoConfig.acceptRaDnssl

       Possibilities:
               disabled   (0)
               enabled   (1)"
   ::= {er1645v2Lan3IpV6Entry 67371008}

er1645v2Lan3IpV6DefaultRoute OBJECT-TYPE
   SYNTAX      INTEGER
               {
               disabled (0),
               enabled (1)
               }
   MAX-ACCESS  read-write
   STATUS      current
   DESCRIPTION
      "Path: ethernet3.editConf.ipV6.defaultRoute

       Possibilities:
               disabled   (0)
               enabled   (1)"
   ::= {er1645v2Lan3IpV6Entry 83886080}

er1645v2Lan3IpV6RaSend OBJECT-TYPE
   SYNTAX      INTEGER
               {
               disabled (0),
               enabled (1)
               }
   MAX-ACCESS  read-write
   STATUS      current
   DESCRIPTION
      "Path: ethernet3.editConf.ipV6.ra.send

       Possibilities:
               disabled   (0)
               enabled   (1)"
   ::= {er1645v2Lan3IpV6Entry 100728832}

er1645v2Lan3IpV6RaMinInterval OBJECT-TYPE
   SYNTAX      TimeTicks
   MAX-ACCESS  read-write
   STATUS      current
   DESCRIPTION
      "Path: ethernet3.editConf.ipV6.ra.minInterval

       Time in centi-second."
   ::= {er1645v2Lan3IpV6Entry 100794368}

er1645v2Lan3IpV6RaMaxInterval OBJECT-TYPE
   SYNTAX      TimeTicks
   MAX-ACCESS  read-write
   STATUS      current
   DESCRIPTION
      "Path: ethernet3.editConf.ipV6.ra.maxInterval

       Time in centi-second."
   ::= {er1645v2Lan3IpV6Entry 100859904}

er1645v2Lan3IpV6RaManagedFlag OBJECT-TYPE
   SYNTAX      INTEGER
               {
               disabled (0),
               enabled (1)
               }
   MAX-ACCESS  read-write
   STATUS      current
   DESCRIPTION
      "Path: ethernet3.editConf.ipV6.ra.managedFlag

       Possibilities:
               disabled   (0)
               enabled   (1)"
   ::= {er1645v2Lan3IpV6Entry 100925440}

er1645v2Lan3IpV6RaOtherConfFlag OBJECT-TYPE
   SYNTAX      INTEGER
               {
               disabled (0),
               enabled (1)
               }
   MAX-ACCESS  read-write
   STATUS      current
   DESCRIPTION
      "Path: ethernet3.editConf.ipV6.ra.otherConfFlag

       Possibilities:
               disabled   (0)
               enabled   (1)"
   ::= {er1645v2Lan3IpV6Entry 100990976}

er1645v2Lan3IpV6RaLinkMtu OBJECT-TYPE
   SYNTAX      Integer32
   MAX-ACCESS  read-write
   STATUS      current
   DESCRIPTION
      "Path: ethernet3.editConf.ipV6.ra.linkMtu"
   ::= {er1645v2Lan3IpV6Entry 101056512}

er1645v2Lan3IpV6RaReachableTime OBJECT-TYPE
   SYNTAX      TimeTicks
   MAX-ACCESS  read-write
   STATUS      current
   DESCRIPTION
      "Path: ethernet3.editConf.ipV6.ra.reachableTime

       Time in centi-second."
   ::= {er1645v2Lan3IpV6Entry 101122048}

er1645v2Lan3IpV6RaRetransmitTime OBJECT-TYPE
   SYNTAX      TimeTicks
   MAX-ACCESS  read-write
   STATUS      current
   DESCRIPTION
      "Path: ethernet3.editConf.ipV6.ra.retransmitTime

       Time in centi-second."
   ::= {er1645v2Lan3IpV6Entry 101187584}

er1645v2Lan3IpV6RaHopLimit OBJECT-TYPE
   SYNTAX      Integer32
   MAX-ACCESS  read-write
   STATUS      current
   DESCRIPTION
      "Path: ethernet3.editConf.ipV6.ra.hopLimit"
   ::= {er1645v2Lan3IpV6Entry 101253120}

er1645v2Lan3IpV6RaDefaultLifeTime OBJECT-TYPE
   SYNTAX      TimeTicks
   MAX-ACCESS  read-write
   STATUS      current
   DESCRIPTION
      "Path: ethernet3.editConf.ipV6.ra.defaultLifeTime

       Time in centi-second."
   ::= {er1645v2Lan3IpV6Entry 101318656}

er1645v2Lan3IpV6RaDnsOptionsRdnssLifeTime OBJECT-TYPE
   SYNTAX      TimeTicks
   MAX-ACCESS  read-write
   STATUS      current
   DESCRIPTION
      "Path: ethernet3.editConf.ipV6.ra.dnsOptions.rdnss.lifeTime

       Time in centi-second."
   ::= {er1645v2Lan3IpV6Entry 101393408}

er1645v2Lan3IpV6RaDnsOptionsRdnssImportServers OBJECT-TYPE
   SYNTAX      INTEGER
               {
               disabled (0),
               enabled (1)
               }
   MAX-ACCESS  read-write
   STATUS      current
   DESCRIPTION
      "Path: ethernet3.editConf.ipV6.ra.dnsOptions.rdnss.importServers

       Possibilities:
               disabled   (0)
               enabled   (1)"
   ::= {er1645v2Lan3IpV6Entry 101395456}

er1645v2Lan3IpV6RaDnsOptionsDnsslLifeTime OBJECT-TYPE
   SYNTAX      TimeTicks
   MAX-ACCESS  read-write
   STATUS      current
   DESCRIPTION
      "Path: ethernet3.editConf.ipV6.ra.dnsOptions.dnssl.lifeTime

       Time in centi-second."
   ::= {er1645v2Lan3IpV6Entry 101401600}

er1645v2Lan3IpV6RaDnsOptionsDnsslImportDomains OBJECT-TYPE
   SYNTAX      INTEGER
               {
               disabled (0),
               enabled (1)
               }
   MAX-ACCESS  read-write
   STATUS      current
   DESCRIPTION
      "Path: ethernet3.editConf.ipV6.ra.dnsOptions.dnssl.importDomains

       Possibilities:
               disabled   (0)
               enabled   (1)"
   ::= {er1645v2Lan3IpV6Entry 101403648}

er1645v2Lan3IpV6RsSend OBJECT-TYPE
   SYNTAX      INTEGER
               {
               disabled (0),
               enabled (1)
               }
   MAX-ACCESS  read-write
   STATUS      current
   DESCRIPTION
      "Path: ethernet3.editConf.ipV6.rs.send

       Possibilities:
               disabled   (0)
               enabled   (1)"
   ::= {er1645v2Lan3IpV6Entry 335609856}

er1645v2Lan3IpV6RsMaxRandomDelay OBJECT-TYPE
   SYNTAX      TimeTicks
   MAX-ACCESS  read-write
   STATUS      current
   DESCRIPTION
      "Path: ethernet3.editConf.ipV6.rs.maxRandomDelay

       Time in centi-second."
   ::= {er1645v2Lan3IpV6Entry 335675392}

er1645v2Lan3IpV6RsInterval OBJECT-TYPE
   SYNTAX      TimeTicks
   MAX-ACCESS  read-write
   STATUS      current
   DESCRIPTION
      "Path: ethernet3.editConf.ipV6.rs.interval

       Time in centi-second."
   ::= {er1645v2Lan3IpV6Entry 335740928}

er1645v2Lan3IpV6RsMaxSolicitations OBJECT-TYPE
   SYNTAX      Integer32
   MAX-ACCESS  read-write
   STATUS      current
   DESCRIPTION
      "Path: ethernet3.editConf.ipV6.rs.maxSolicitations"
   ::= {er1645v2Lan3IpV6Entry 335806464}

er1645v2Lan3IpV6TrafficPolicyInbound OBJECT-TYPE
   SYNTAX      DisplayString
   MAX-ACCESS  read-write
   STATUS      current
   DESCRIPTION
      "Path: ethernet3.editConf.ipV6.trafficPolicy.inbound"
   ::= {er1645v2Lan3IpV6Entry 184614912}

er1645v2Lan3IpV6TrafficPolicyOutbound OBJECT-TYPE
   SYNTAX      DisplayString
   MAX-ACCESS  read-write
   STATUS      current
   DESCRIPTION
      "Path: ethernet3.editConf.ipV6.trafficPolicy.outbound"
   ::= {er1645v2Lan3IpV6Entry 184680448}

er1645v2Lan3IpV6FirewallZone OBJECT-TYPE
   SYNTAX      DisplayString
   MAX-ACCESS  read-write
   STATUS      current
   DESCRIPTION
      "Path: ethernet3.editConf.ipV6.firewall.zone"
   ::= {er1645v2Lan3IpV6Entry 201392128}

er1645v2Lan3IpV6DhcpClientAddrAC OBJECT-TYPE
   SYNTAX      INTEGER
               {
               disabled (0),
               enabled (1)
               }
   MAX-ACCESS  read-write
   STATUS      current
   DESCRIPTION
      "Path: ethernet3.editConf.ipV6.dhcp.client.addrAutoConfig

       Possibilities:
               disabled   (0)
               enabled   (1)"
   ::= {er1645v2Lan3IpV6Entry 170131456}

er1645v2Lan3IpV6DhcpClientPrDelMode OBJECT-TYPE
   SYNTAX      INTEGER
               {
               disabled (0),
               enabled (1)
               }
   MAX-ACCESS  read-write
   STATUS      current
   DESCRIPTION
      "Path: ethernet3.editConf.ipV6.dhcp.client.pd.mode

       Possibilities:
               disabled   (0)
               enabled   (1)"
   ::= {er1645v2Lan3IpV6Entry 170394624}

er1645v2Lan3IpV6DhcpClientPrDelPool OBJECT-TYPE
   SYNTAX      DisplayString
   MAX-ACCESS  read-write
   STATUS      current
   DESCRIPTION
      "Path: ethernet3.editConf.ipV6.dhcp.client.pd.pool"
   ::= {er1645v2Lan3IpV6Entry 170395648}

er1645v2Lan3IpV6DhcpClientPrDelPdExclOpt OBJECT-TYPE
   SYNTAX      INTEGER
               {
               disabled (0),
               enabled (1)
               }
   MAX-ACCESS  read-write
   STATUS      current
   DESCRIPTION
      "Path: ethernet3.editConf.ipV6.dhcp.client.pd.pdExclOpt

       Possibilities:
               disabled   (0)
               enabled   (1)"
   ::= {er1645v2Lan3IpV6Entry 170396672}

er1645v2Lan3IpV6DhcpClientDnsServerPref OBJECT-TYPE
   SYNTAX      Integer32
   MAX-ACCESS  read-write
   STATUS      current
   DESCRIPTION
      "Path: ethernet3.editConf.ipV6.dhcp.client.dns.serverPref"
   ::= {er1645v2Lan3IpV6Entry 170918912}

er1645v2Lan3IpV6DhcpClientRapidCommit OBJECT-TYPE
   SYNTAX      INTEGER
               {
               disabled (0),
               enabled (1)
               }
   MAX-ACCESS  read-write
   STATUS      current
   DESCRIPTION
      "Path: ethernet3.editConf.ipV6.dhcp.client.rapidCommit

       Possibilities:
               disabled   (0)
               enabled   (1)"
   ::= {er1645v2Lan3IpV6Entry 170655744}

er1645v2Lan3IpV6DhcpClientTimersSolTimeOut OBJECT-TYPE
   SYNTAX      TimeTicks
   MAX-ACCESS  read-write
   STATUS      current
   DESCRIPTION
      "Path: ethernet3.editConf.ipV6.dhcp.client.timers.solTimeOut

       Time in centi-second."
   ::= {er1645v2Lan3IpV6Entry 171181056}

er1645v2Lan3IpV6DhcpClientTimersSolMaxRt OBJECT-TYPE
   SYNTAX      TimeTicks
   MAX-ACCESS  read-write
   STATUS      current
   DESCRIPTION
      "Path: ethernet3.editConf.ipV6.dhcp.client.timers.solMaxRt

       Time in centi-second."
   ::= {er1645v2Lan3IpV6Entry 171182080}

er1645v2Lan3IpV6DhcpClientTimersInfoRefresh OBJECT-TYPE
   SYNTAX      TimeTicks
   MAX-ACCESS  read-write
   STATUS      current
   DESCRIPTION
      "Path: ethernet3.editConf.ipV6.dhcp.client.timers.infoRefresh

       Time in centi-second."
   ::= {er1645v2Lan3IpV6Entry 171183104}

er1645v2Lan3IpV6DhcpServerMode OBJECT-TYPE
   SYNTAX      INTEGER
               {
               disabled (0),
               enabled (1)
               }
   MAX-ACCESS  read-write
   STATUS      current
   DESCRIPTION
      "Path: ethernet3.editConf.ipV6.dhcp.server.mode

       Possibilities:
               disabled   (0)
               enabled   (1)"
   ::= {er1645v2Lan3IpV6Entry 172228608}

er1645v2Lan3IpV6DhcpServerPreference OBJECT-TYPE
   SYNTAX      Integer32
   MAX-ACCESS  read-write
   STATUS      current
   DESCRIPTION
      "Path: ethernet3.editConf.ipV6.dhcp.server.preference"
   ::= {er1645v2Lan3IpV6Entry 172490752}

er1645v2Lan3IpV6DhcpServerPool OBJECT-TYPE
   SYNTAX      DisplayString
   MAX-ACCESS  read-write
   STATUS      current
   DESCRIPTION
      "Path: ethernet3.editConf.ipV6.dhcp.server.pool"
   ::= {er1645v2Lan3IpV6Entry 172752896}

er1645v2Lan3IpV6DhcpServerRapidCommit OBJECT-TYPE
   SYNTAX      INTEGER
               {
               disabled (0),
               enabled (1)
               }
   MAX-ACCESS  read-write
   STATUS      current
   DESCRIPTION
      "Path: ethernet3.editConf.ipV6.dhcp.server.rapidCommit

       Possibilities:
               disabled   (0)
               enabled   (1)"
   ::= {er1645v2Lan3IpV6Entry 173015040}

er1645v2Lan3IpV6DhcpServerTimersInfoRefresh OBJECT-TYPE
   SYNTAX      TimeTicks
   MAX-ACCESS  read-write
   STATUS      current
   DESCRIPTION
      "Path: ethernet3.editConf.ipV6.dhcp.server.timers.infoRefresh

       Time in centi-second."
   ::= {er1645v2Lan3IpV6Entry 173278208}

er1645v2Lan3IpV6DhcpRelayMode OBJECT-TYPE
   SYNTAX      INTEGER
               {
               disabled (0),
               enabled (1)
               }
   MAX-ACCESS  read-write
   STATUS      current
   DESCRIPTION
      "Path: ethernet3.editConf.ipV6.dhcp.relay.mode

       Possibilities:
               disabled   (0)
               enabled   (1)"
   ::= {er1645v2Lan3IpV6Entry 174071808}

er1645v2Lan3IpV6SendRedirect OBJECT-TYPE
   SYNTAX      INTEGER
               {
               disabled (0),
               enabled (1)
               }
   MAX-ACCESS  read-write
   STATUS      current
   DESCRIPTION
      "Path: ethernet3.editConf.ipV6.sendRedirect

       Possibilities:
               disabled   (0)
               enabled   (1)"
   ::= {er1645v2Lan3IpV6Entry 117440512}

er1645v2Lan3IpV6LinkMtu OBJECT-TYPE
   SYNTAX      Integer32
   MAX-ACCESS  read-write
   STATUS      current
   DESCRIPTION
      "Path: ethernet3.editConf.ipV6.linkMtu"
   ::= {er1645v2Lan3IpV6Entry 134217728}

er1645v2Lan3IpV6InterfaceId OBJECT-TYPE
   SYNTAX      OCTET STRING
   MAX-ACCESS  read-write
   STATUS      current
   DESCRIPTION
      "Path: ethernet3.editConf.ipV6.interfaceId"
   ::= {er1645v2Lan3IpV6Entry 150994944}

er1645v2Lan3IpV6MF OBJECT-TYPE
   SYNTAX      Integer32
   MAX-ACCESS  read-write
   STATUS      current
   DESCRIPTION
      "Path: ethernet3.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3IpV6Entry 285212672}

er1645v2Lan3IpV6IcmpMessagesNoRoute OBJECT-TYPE
   SYNTAX      INTEGER
               {
               disabled (0),
               enabled (1)
               }
   MAX-ACCESS  read-write
   STATUS      current
   DESCRIPTION
      "Path: ethernet3.editConf.ipV6.icmpMessages.noRoute

       Possibilities:
               disabled   (0)
               enabled   (1)"
   ::= {er1645v2Lan3IpV6Entry 302055424}

er1645v2Lan3IpV6IcmpMessagesBeyondScope OBJECT-TYPE
   SYNTAX      INTEGER
               {
               disabled (0),
               enabled (1)
               }
   MAX-ACCESS  read-write
   STATUS      current
   DESCRIPTION
      "Path: ethernet3.editConf.ipV6.icmpMessages.beyondScope

       Possibilities:
               disabled   (0)
               enabled   (1)"
   ::= {er1645v2Lan3IpV6Entry 302186496}

er1645v2Lan3IpV6IcmpMessagesAddressUnreachable OBJECT-TYPE
   SYNTAX      INTEGER
               {
               disabled (0),
               enabled (1)
               }
   MAX-ACCESS  read-write
   STATUS      current
   DESCRIPTION
      "Path: ethernet3.editConf.ipV6.icmpMessages.addressUnreachable

       Possibilities:
               disabled   (0)
               enabled   (1)"
   ::= {er1645v2Lan3IpV6Entry 302252032}

er1645v2Lan3IpV6IcmpMessagesPortUnreachable OBJECT-TYPE
   SYNTAX      INTEGER
               {
               disabled (0),
               enabled (1)
               }
   MAX-ACCESS  read-write
   STATUS      current
   DESCRIPTION
      "Path: ethernet3.editConf.ipV6.icmpMessages.portUnreachable

       Possibilities:
               disabled   (0)
               enabled   (1)"
   ::= {er1645v2Lan3IpV6Entry 302317568}

er1645v2Lan3IpV6IcmpMessagesPacketTooBig OBJECT-TYPE
   SYNTAX      INTEGER
               {
               disabled (0),
               enabled (1)
               }
   MAX-ACCESS  read-write
   STATUS      current
   DESCRIPTION
      "Path: ethernet3.editConf.ipV6.icmpMessages.packetTooBig

       Possibilities:
               disabled   (0)
               enabled   (1)"
   ::= {er1645v2Lan3IpV6Entry 302645248}

er1645v2Lan3IpV6IcmpMessagesHopLimitExceeded OBJECT-TYPE
   SYNTAX      INTEGER
               {
               disabled (0),
               enabled (1)
               }
   MAX-ACCESS  read-write
   STATUS      current
   DESCRIPTION
      "Path: ethernet3.editConf.ipV6.icmpMessages.hopLimitExceeded

       Possibilities:
               disabled   (0)
               enabled   (1)"
   ::= {er1645v2Lan3IpV6Entry 303300608}

er1645v2Lan3IpV6IcmpMessagesFragTimeExceeded OBJECT-TYPE
   SYNTAX      INTEGER
               {
               disabled (0),
               enabled (1)
               }
   MAX-ACCESS  read-write
   STATUS      current
   DESCRIPTION
      "Path: ethernet3.editConf.ipV6.icmpMessages.fragTimeExceeded

       Possibilities:
               disabled   (0)
               enabled   (1)"
   ::= {er1645v2Lan3IpV6Entry 303366144}

er1645v2Lan3IpV6IcmpMessagesHeaderFieldErr OBJECT-TYPE
   SYNTAX      INTEGER
               {
               disabled (0),
               enabled (1)
               }
   MAX-ACCESS  read-write
   STATUS      current
   DESCRIPTION
      "Path: ethernet3.editConf.ipV6.icmpMessages.headerFieldErr

       Possibilities:
               disabled   (0)
               enabled   (1)"
   ::= {er1645v2Lan3IpV6Entry 303955968}

er1645v2Lan3IpV6IcmpMessagesOptionUnrecognized OBJECT-TYPE
   SYNTAX      INTEGER
               {
               disabled (0),
               enabled (1)
               }
   MAX-ACCESS  read-write
   STATUS      current
   DESCRIPTION
      "Path: ethernet3.editConf.ipV6.icmpMessages.optionUnrecognized

       Possibilities:
               disabled   (0)
               enabled   (1)"
   ::= {er1645v2Lan3IpV6Entry 304087040}

er1645v2Lan3IpV6IcmpMessagesRedirect OBJECT-TYPE
   SYNTAX      INTEGER
               {
               disabled (0),
               enabled (1)
               }
   MAX-ACCESS  read-write
   STATUS      current
   DESCRIPTION
      "Path: ethernet3.editConf.ipV6.icmpMessages.redirect

       Possibilities:
               disabled   (0)
               enabled   (1)"
   ::= {er1645v2Lan3IpV6Entry 304611328}

er1645v2Lan3IpV6Addresses OBJECT-TYPE
   SYNTAX      SEQUENCE OF Er1645v2Lan3IpV6AddressesEntry
   MAX-ACCESS  not-accessible
   STATUS      current
   DESCRIPTION
      ""
   ::= {er1645v2Lan3IpV6 50331648}

er1645v2Lan3IpV6AddressesEntry OBJECT-TYPE
   SYNTAX      Er1645v2Lan3IpV6AddressesEntry
   MAX-ACCESS  not-accessible
   STATUS      current
   DESCRIPTION
      ""
   INDEX      { er1645v2Lan3IpV6AddressesTableIx }
   ::= {er1645v2Lan3IpV6Addresses 1}

Er1645v2Lan3IpV6AddressesEntry ::=
   SEQUENCE
      {
      er1645v2Lan3IpV6AddressesActions
         VariableLengthTableActions,
      er1645v2Lan3IpV6AddressesTableIx
         TableIndex,
      er1645v2Lan3IpV6AddressesType
         INTEGER,
      er1645v2Lan3IpV6AddressesAddress
         Ipv6Address,
      er1645v2Lan3IpV6AddressesPrefixLength
         Integer32,
      er1645v2Lan3IpV6AddressesGeneralPrefix
         DisplayString,
      er1645v2Lan3IpV6AddressesRaSend
         INTEGER,
      er1645v2Lan3IpV6AddressesRaOnLinkFlag
         INTEGER,
      er1645v2Lan3IpV6AddressesRaAutoFlag
         INTEGER,
      er1645v2Lan3IpV6AddressesRaValidLifeTime
         TimeTicks,
      er1645v2Lan3IpV6AddressesRaValidLTMode
         INTEGER,
      er1645v2Lan3IpV6AddressesRaPrefLifeTime
         TimeTicks,
      er1645v2Lan3IpV6AddressesRaPrefLTMode
         INTEGER
      }

er1645v2Lan3IpV6AddressesActions OBJECT-TYPE
   SYNTAX      VariableLengthTableActions
   MAX-ACCESS  read-write
   STATUS      current
   DESCRIPTION
      "By way of this field, some manipulations
       on this table may be performed."
   ::= {er1645v2Lan3IpV6AddressesEntry 2}

er1645v2Lan3IpV6AddressesTableIx OBJECT-TYPE
   SYNTAX      TableIndex
   MAX-ACCESS  not-accessible
   STATUS      current
   DESCRIPTION
      ""
   ::= {er1645v2Lan3IpV6AddressesEntry 11}

er1645v2Lan3IpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.ipV6.addresses.type

       Possibilities:
               unicast   (0)
               eui64   (1)
               anycast   (2)
               linkLocal   (3)
               generalPrefix   (4)"
   ::= {er1645v2Lan3IpV6AddressesEntry 50331648}

er1645v2Lan3IpV6AddressesAddress OBJECT-TYPE
   SYNTAX      Ipv6Address
   MAX-ACCESS  read-write
   STATUS      current
   DESCRIPTION
      "Path: ethernet3.editConf.ipV6.addresses.address

       ipv6 address"
   ::= {er1645v2Lan3IpV6AddressesEntry 16777216}

er1645v2Lan3IpV6AddressesPrefixLength OBJECT-TYPE
   SYNTAX      Integer32
   MAX-ACCESS  read-write
   STATUS      current
   DESCRIPTION
      "Path: ethernet3.editConf.ipV6.addresses.prefixLength"
   ::= {er1645v2Lan3IpV6AddressesEntry 33554432}

er1645v2Lan3IpV6AddressesGeneralPrefix OBJECT-TYPE
   SYNTAX      DisplayString
   MAX-ACCESS  read-write
   STATUS      current
   DESCRIPTION
      "Path: ethernet3.editConf.ipV6.addresses.generalPrefix"
   ::= {er1645v2Lan3IpV6AddressesEntry 83886080}

er1645v2Lan3IpV6AddressesRaSend OBJECT-TYPE
   SYNTAX      INTEGER
               {
               disabled (0),
               enabled (1)
               }
   MAX-ACCESS  read-write
   STATUS      current
   DESCRIPTION
      "Path: ethernet3.editConf.ipV6.addresses.ra.send

       Possibilities:
               disabled   (0)
               enabled   (1)"
   ::= {er1645v2Lan3IpV6AddressesEntry 67174400}

er1645v2Lan3IpV6AddressesRaOnLinkFlag OBJECT-TYPE
   SYNTAX      INTEGER
               {
               disabled (0),
               enabled (1)
               }
   MAX-ACCESS  read-write
   STATUS      current
   DESCRIPTION
      "Path: ethernet3.editConf.ipV6.addresses.ra.onLinkFlag

       Possibilities:
               disabled   (0)
               enabled   (1)"
   ::= {er1645v2Lan3IpV6AddressesEntry 67371008}

er1645v2Lan3IpV6AddressesRaAutoFlag OBJECT-TYPE
   SYNTAX      INTEGER
               {
               disabled (0),
               enabled (1)
               }
   MAX-ACCESS  read-write
   STATUS      current
   DESCRIPTION
      "Path: ethernet3.editConf.ipV6.addresses.ra.autonomousFlag

       Possibilities:
               disabled   (0)
               enabled   (1)"
   ::= {er1645v2Lan3IpV6AddressesEntry 67567616}

er1645v2Lan3IpV6AddressesRaValidLifeTime OBJECT-TYPE
   SYNTAX      TimeTicks
   MAX-ACCESS  read-write
   STATUS      current
   DESCRIPTION
      "Path: ethernet3.editConf.ipV6.addresses.ra.validLifeTime

       Time in centi-second."
   ::= {er1645v2Lan3IpV6AddressesEntry 67239936}

er1645v2Lan3IpV6AddressesRaValidLTMode OBJECT-TYPE
   SYNTAX      INTEGER
               {
               fixed (0),
               infinite (2)
               }
   MAX-ACCESS  read-write
   STATUS      current
   DESCRIPTION
      "Path: ethernet3.editConf.ipV6.addresses.ra.validLifeTimeMode

       Possibilities:
               fixed   (0)
               infinite   (2)"
   ::= {er1645v2Lan3IpV6AddressesEntry 67305472}

er1645v2Lan3IpV6AddressesRaPrefLifeTime OBJECT-TYPE
   SYNTAX      TimeTicks
   MAX-ACCESS  read-write
   STATUS      current
   DESCRIPTION
      "Path: ethernet3.editConf.ipV6.addresses.ra.prefLifeTime

       Time in centi-second."
   ::= {er1645v2Lan3IpV6AddressesEntry 67436544}

er1645v2Lan3IpV6AddressesRaPrefLTMode OBJECT-TYPE
   SYNTAX      INTEGER
               {
               fixed (0),
               infinite (2)
               }
   MAX-ACCESS  read-write
   STATUS      current
   DESCRIPTION
      "Path: ethernet3.editConf.ipV6.addresses.ra.prefLifeTimeMode

       Possibilities:
               fixed   (0)
               infinite   (2)"
   ::= {er1645v2Lan3IpV6AddressesEntry 67502080}

er1645v2Lan3IpV6RaDnsOptionsRdnssServers OBJECT-TYPE
   SYNTAX      SEQUENCE OF Er1645v2Lan3IpV6RaDnsOptionsRdnssServersEntry
   MAX-ACCESS  not-accessible
   STATUS      current
   DESCRIPTION
      ""
   ::= {er1645v2Lan3IpV6 101394432}

er1645v2Lan3IpV6RaDnsOptionsRdnssServersEntry OBJECT-TYPE
   SYNTAX      Er1645v2Lan3IpV6RaDnsOptionsRdnssServersEntry
   MAX-ACCESS  not-accessible
   STATUS      current
   DESCRIPTION
      ""
   INDEX      { er1645v2Lan3IpV6RaDnsOptionsRdnssServersTableIx }
   ::= {er1645v2Lan3IpV6RaDnsOptionsRdnssServers 1}

Er1645v2Lan3IpV6RaDnsOptionsRdnssServersEntry ::=
   SEQUENCE
      {
      er1645v2Lan3IpV6RaDnsOptionsRdnssServersActions
         VariableLengthTableActions,
      er1645v2Lan3IpV6RaDnsOptionsRdnssServersTableIx
         TableIndex,
      er1645v2Lan3IpV6RaDnsOptionsRdnssServersAddress
         Ipv6Address
      }

er1645v2Lan3IpV6RaDnsOptionsRdnssServersActions OBJECT-TYPE
   SYNTAX      VariableLengthTableActions
   MAX-ACCESS  read-write
   STATUS      current
   DESCRIPTION
      "By way of this field, some manipulations
       on this table may be performed."
   ::= {er1645v2Lan3IpV6RaDnsOptionsRdnssServersEntry 2}

er1645v2Lan3IpV6RaDnsOptionsRdnssServersTableIx OBJECT-TYPE
   SYNTAX      TableIndex
   MAX-ACCESS  not-accessible
   STATUS      current
   DESCRIPTION
      ""
   ::= {er1645v2Lan3IpV6RaDnsOptionsRdnssServersEntry 11}

er1645v2Lan3IpV6RaDnsOptionsRdnssServersAddress OBJECT-TYPE
   SYNTAX      Ipv6Address
   MAX-ACCESS  read-write
   STATUS      current
   DESCRIPTION
      "Path: ethernet3.editConf.ipV6.ra.dnsOptions.rdnss.servers.address

       ipv6 address"
   ::= {er1645v2Lan3IpV6RaDnsOptionsRdnssServersEntry 16777216}

er1645v2Lan3IpV6RaDnsOptionsDnsslDomains OBJECT-TYPE
   SYNTAX      SEQUENCE OF Er1645v2Lan3IpV6RaDnsOptionsDnsslDomainsEntry
   MAX-ACCESS  not-accessible
   STATUS      current
   DESCRIPTION
      ""
   ::= {er1645v2Lan3IpV6 101402624}

er1645v2Lan3IpV6RaDnsOptionsDnsslDomainsEntry OBJECT-TYPE
   SYNTAX      Er1645v2Lan3IpV6RaDnsOptionsDnsslDomainsEntry
   MAX-ACCESS  not-accessible
   STATUS      current
   DESCRIPTION
      ""
   INDEX      { er1645v2Lan3IpV6RaDnsOptionsDnsslDomainsTableIx }
   ::= {er1645v2Lan3IpV6RaDnsOptionsDnsslDomains 1}

Er1645v2Lan3IpV6RaDnsOptionsDnsslDomainsEntry ::=
   SEQUENCE
      {
      er1645v2Lan3IpV6RaDnsOptionsDnsslDomainsActions
         VariableLengthTableActions,
      er1645v2Lan3IpV6RaDnsOptionsDnsslDomainsTableIx
         TableIndex,
      er1645v2Lan3IpV6RaDnsOptionsDnsslDomainsName
         DisplayString
      }

er1645v2Lan3IpV6RaDnsOptionsDnsslDomainsActions OBJECT-TYPE
   SYNTAX      VariableLengthTableActions
   MAX-ACCESS  read-write
   STATUS      current
   DESCRIPTION
      "By way of this field, some manipulations
       on this table may be performed."
   ::= {er1645v2Lan3IpV6RaDnsOptionsDnsslDomainsEntry 2}

er1645v2Lan3IpV6RaDnsOptionsDnsslDomainsTableIx OBJECT-TYPE
   SYNTAX      TableIndex
   MAX-ACCESS  not-accessible
   STATUS      current
   DESCRIPTION
      ""
   ::= {er1645v2Lan3IpV6RaDnsOptionsDnsslDomainsEntry 11}

er1645v2Lan3IpV6RaDnsOptionsDnsslDomainsName OBJECT-TYPE
   SYNTAX      DisplayString
   MAX-ACCESS  read-write
   STATUS      current
   DESCRIPTION
      "Path: ethernet3.editConf.ipV6.ra.dnsOptions.dnssl.domains.name"
   ::= {er1645v2Lan3IpV6RaDnsOptionsDnsslDomainsEntry 16777216}

er1645v2Lan3IpV6DhcpClientUserClassOpt OBJECT-TYPE
   SYNTAX      SEQUENCE OF Er1645v2Lan3IpV6DhcpClientUserClassOptEntry
   MAX-ACCESS  not-accessible
   STATUS      current
   DESCRIPTION
      ""
   ::= {er1645v2Lan3IpV6 171442176}

er1645v2Lan3IpV6DhcpClientUserClassOptEntry OBJECT-TYPE
   SYNTAX      Er1645v2Lan3IpV6DhcpClientUserClassOptEntry
   MAX-ACCESS  not-accessible
   STATUS      current
   DESCRIPTION
      ""
   INDEX      { er1645v2Lan3IpV6DhcpClientUserClassOptTableIx }
   ::= {er1645v2Lan3IpV6DhcpClientUserClassOpt 1}

Er1645v2Lan3IpV6DhcpClientUserClassOptEntry ::=
   SEQUENCE
      {
      er1645v2Lan3IpV6DhcpClientUserClassOptActions
         VariableLengthTableActions,
      er1645v2Lan3IpV6DhcpClientUserClassOptTableIx
         TableIndex,
      er1645v2Lan3IpV6DhcpClientUserClassOptValueAscii
         DisplayString,
      er1645v2Lan3IpV6DhcpClientUserClassOptValueDecimal
         Integer32,
      er1645v2Lan3IpV6DhcpClientUserClassOptValueHexData
         OCTET STRING
      }

er1645v2Lan3IpV6DhcpClientUserClassOptActions OBJECT-TYPE
   SYNTAX      VariableLengthTableActions
   MAX-ACCESS  read-write
   STATUS      current
   DESCRIPTION
      "By way of this field, some manipulations
       on this table may be performed."
   ::= {er1645v2Lan3IpV6DhcpClientUserClassOptEntry 2}

er1645v2Lan3IpV6DhcpClientUserClassOptTableIx OBJECT-TYPE
   SYNTAX      TableIndex
   MAX-ACCESS  not-accessible
   STATUS      current
   DESCRIPTION
      ""
   ::= {er1645v2Lan3IpV6DhcpClientUserClassOptEntry 11}

er1645v2Lan3IpV6DhcpClientUserClassOptValueAscii OBJECT-TYPE
   SYNTAX      DisplayString
   MAX-ACCESS  read-write
   STATUS      current
   DESCRIPTION
      "Path: ethernet3.editConf.ipV6.dhcp.client.userClassOpt.value.ascii"
   ::= {er1645v2Lan3IpV6DhcpClientUserClassOptEntry 16842752}

er1645v2Lan3IpV6DhcpClientUserClassOptValueDecimal OBJECT-TYPE
   SYNTAX      Integer32
   MAX-ACCESS  read-write
   STATUS      current
   DESCRIPTION
      "Path: ethernet3.editConf.ipV6.dhcp.client.userClassOpt.value.decimal"
   ::= {er1645v2Lan3IpV6DhcpClientUserClassOptEntry 16908288}

er1645v2Lan3IpV6DhcpClientUserClassOptValueHexData OBJECT-TYPE
   SYNTAX      OCTET STRING
   MAX-ACCESS  read-write
   STATUS      current
   DESCRIPTION
      "Path: ethernet3.editConf.ipV6.dhcp.client.userClassOpt.value.hexData"
   ::= {er1645v2Lan3IpV6DhcpClientUserClassOptEntry 16973824}

er1645v2Lan3IpV6DhcpClientVendorCl OBJECT-TYPE
   SYNTAX      SEQUENCE OF Er1645v2Lan3IpV6DhcpClientVendorClEntry
   MAX-ACCESS  not-accessible
   STATUS      current
   DESCRIPTION
      ""
   ::= {er1645v2Lan3IpV6 171704320}

er1645v2Lan3IpV6DhcpClientVendorClEntry OBJECT-TYPE
   SYNTAX      Er1645v2Lan3IpV6DhcpClientVendorClEntry
   MAX-ACCESS  not-accessible
   STATUS      current
   DESCRIPTION
      ""
   INDEX      { er1645v2Lan3IpV6DhcpClientVendorClTableIx }
   ::= {er1645v2Lan3IpV6DhcpClientVendorCl 1}

Er1645v2Lan3IpV6DhcpClientVendorClEntry ::=
   SEQUENCE
      {
      er1645v2Lan3IpV6DhcpClientVendorClActions
         VariableLengthTableActions,
      er1645v2Lan3IpV6DhcpClientVendorClTableIx
         TableIndex,
      er1645v2Lan3IpV6DhcpClientVendorClValueAscii
         DisplayString,
      er1645v2Lan3IpV6DhcpClientVendorClValueDecimal
         Integer32,
      er1645v2Lan3IpV6DhcpClientVendorClValueHexData
         OCTET STRING
      }

er1645v2Lan3IpV6DhcpClientVendorClActions OBJECT-TYPE
   SYNTAX      VariableLengthTableActions
   MAX-ACCESS  read-write
   STATUS      current
   DESCRIPTION
      "By way of this field, some manipulations
       on this table may be performed."
   ::= {er1645v2Lan3IpV6DhcpClientVendorClEntry 2}

er1645v2Lan3IpV6DhcpClientVendorClTableIx OBJECT-TYPE
   SYNTAX      TableIndex
   MAX-ACCESS  not-accessible
   STATUS      current
   DESCRIPTION
      ""
   ::= {er1645v2Lan3IpV6DhcpClientVendorClEntry 11}

er1645v2Lan3IpV6DhcpClientVendorClValueAscii OBJECT-TYPE
   SYNTAX      DisplayString
   MAX-ACCESS  read-write
   STATUS      current
   DESCRIPTION
      "Path: ethernet3.editConf.ipV6.dhcp.client.vendorClassOpt.value.ascii"
   ::= {er1645v2Lan3IpV6DhcpClientVendorClEntry 16842752}

er1645v2Lan3IpV6DhcpClientVendorClValueDecimal OBJECT-TYPE
   SYNTAX      Integer32
   MAX-ACCESS  read-write
   STATUS      current
   DESCRIPTION
      "Path: ethernet3.editConf.ipV6.dhcp.client.vendorClassOpt.value.decimal"
   ::= {er1645v2Lan3IpV6DhcpClientVendorClEntry 16908288}

er1645v2Lan3IpV6DhcpClientVendorClValueHexData OBJECT-TYPE
   SYNTAX      OCTET STRING
   MAX-ACCESS  read-write
   STATUS      current
   DESCRIPTION
      "Path: ethernet3.editConf.ipV6.dhcp.client.vendorClassOpt.value.hexData"
   ::= {er1645v2Lan3IpV6DhcpClientVendorClEntry 16973824}

er1645v2Lan3IpV6DhcpRelayDestinations OBJECT-TYPE
   SYNTAX      SEQUENCE OF Er1645v2Lan3IpV6DhcpRelayDestinationsEntry
   MAX-ACCESS  not-accessible
   STATUS      current
   DESCRIPTION
      ""
   ::= {er1645v2Lan3IpV6 174080000}

er1645v2Lan3IpV6DhcpRelayDestinationsEntry OBJECT-TYPE
   SYNTAX      Er1645v2Lan3IpV6DhcpRelayDestinationsEntry
   MAX-ACCESS  not-accessible
   STATUS      current
   DESCRIPTION
      ""
   INDEX      { er1645v2Lan3IpV6DhcpRelayDestinationsTableIx }
   ::= {er1645v2Lan3IpV6DhcpRelayDestinations 1}

Er1645v2Lan3IpV6DhcpRelayDestinationsEntry ::=
   SEQUENCE
      {
      er1645v2Lan3IpV6DhcpRelayDestinationsActions
         VariableLengthTableActions,
      er1645v2Lan3IpV6DhcpRelayDestinationsTableIx
         TableIndex,
      er1645v2Lan3IpV6DhcpRelayDestinationsAddress
         Ipv6Address,
      er1645v2Lan3IpV6DhcpRelayDestinationsInterface
         DisplayString
      }

er1645v2Lan3IpV6DhcpRelayDestinationsActions OBJECT-TYPE
   SYNTAX      VariableLengthTableActions
   MAX-ACCESS  read-write
   STATUS      current
   DESCRIPTION
      "By way of this field, some manipulations
       on this table may be performed."
   ::= {er1645v2Lan3IpV6DhcpRelayDestinationsEntry 2}

er1645v2Lan3IpV6DhcpRelayDestinationsTableIx OBJECT-TYPE
   SYNTAX      TableIndex
   MAX-ACCESS  not-accessible
   STATUS      current
   DESCRIPTION
      ""
   ::= {er1645v2Lan3IpV6DhcpRelayDestinationsEntry 11}

er1645v2Lan3IpV6DhcpRelayDestinationsAddress OBJECT-TYPE
   SYNTAX      Ipv6Address
   MAX-ACCESS  read-write
   STATUS      current
   DESCRIPTION
      "Path: ethernet3.editConf.ipV6.dhcp.relay.destinations.address

       ipv6 address"
   ::= {er1645v2Lan3IpV6DhcpRelayDestinationsEntry 16777216}

er1645v2Lan3IpV6DhcpRelayDestinationsInterface OBJECT-TYPE
   SYNTAX      DisplayString
   MAX-ACCESS  read-write
   STATUS      current
   DESCRIPTION
      "Path: ethernet3.editConf.ipV6.dhcp.relay.destinations.interface"
   ::= {er1645v2Lan3IpV6DhcpRelayDestinationsEntry 33554432}


er1645v2Lan3FlowControl OBJECT-TYPE
   SYNTAX      INTEGER
               {
               disabled (1),
               rx (2),
               tx (3),
               rxAndTx (4)
               }
   MAX-ACCESS  read-write
   STATUS      current
   DESCRIPTION
      "Path: ethernet3.editConf.flowControl
       Info: LAN flow control

       Possibilities:
               disabled   (1)
               rx   (2)
               tx   (3)
               rxAndTx   (4)"
   ::= {er1645v2Lan3 7}


er1645v2Lan3InboundNUcastPriority OBJECT IDENTIFIER ::= {er1645v2Lan3 230}

er1645v2Lan3InboundNUcastPrioritySSC OBJECT IDENTIFIER ::= {er1645v2Lan3InboundNUcastPriority 1}

er1645v2Lan3InboundNUcastPriorityEntry OBJECT IDENTIFIER ::= {er1645v2Lan3InboundNUcastPrioritySSC 1}

er1645v2Lan3InboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2Lan3InboundNUcastPriorityEntry 16777216}

er1645v2Lan3InboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.multicast

       Possibilities:
               queue1   (0)
               queue2   (1)
               queue3   (2)
               queue4   (3)
               queue5   (4)
               lowDelayQueue   (5)
               lowDelay2Queue   (6)
               systemQueue   (7)"
   ::= {er1645v2Lan3InboundNUcastPriorityEntry 33554432}


er1645v2Lan3Ip OBJECT IDENTIFIER ::= {er1645v2Lan3 1}

er1645v2Lan3IpSSC OBJECT IDENTIFIER ::= {er1645v2Lan3Ip 1}

er1645v2Lan3IpEntry OBJECT IDENTIFIER ::= {er1645v2Lan3IpSSC 1}

er1645v2Lan3IpVrfRouter OBJECT-TYPE
   SYNTAX      DisplayString
   MAX-ACCESS  read-write
   STATUS      current
   DESCRIPTION
      "Path: ethernet3.editConf.ip.vrfRouter"
   ::= {er1645v2Lan3IpEntry 738197504}

er1645v2Lan3IpAdr OBJECT-TYPE
   SYNTAX      IpAddress
   MAX-ACCESS  read-write
   STATUS      current
   DESCRIPTION
      "Path: ethernet3.editConf.ip.address"
   ::= {er1645v2Lan3IpEntry 2030043136}

er1645v2Lan3IpNetm OBJECT-TYPE
   SYNTAX      IpAddress
   MAX-ACCESS  read-write
   STATUS      current
   DESCRIPTION
      "Path: ethernet3.editConf.ip.netMask"
   ::= {er1645v2Lan3IpEntry 2063597568}

er1645v2Lan3IpSNetName OBJECT-TYPE
   SYNTAX      INTEGER
               {
               slOPTg (0),
               corp (2),
               dmz (3),
               internet (1)
               }
   MAX-ACCESS  read-write
   STATUS      current
   DESCRIPTION
      "Path: ethernet3.editConf.ip.sNet.name

       Possibilities:
               <OPT>   (0)
               corp   (2)
               dmz   (3)
               internet   (1)"
   ::= {er1645v2Lan3IpEntry 855703552}

er1645v2Lan3IpSNetCust OBJECT-TYPE
   SYNTAX      DisplayString
   MAX-ACCESS  read-write
   STATUS      current
   DESCRIPTION
      "Path: ethernet3.editConf.ip.sNet.custom"
   ::= {er1645v2Lan3IpEntry 855769088}

er1645v2Lan3IpDhcpC OBJECT-TYPE
   SYNTAX      INTEGER
               {
               disabled (0),
               enabled (1)
               }
   MAX-ACCESS  read-write
   STATUS      current
   DESCRIPTION
      "Path: ethernet3.editConf.ip.dhcpClient

       Possibilities:
               disabled   (0)
               enabled   (1)"
   ::= {er1645v2Lan3IpEntry 838860800}

er1645v2Lan3IpDhcpGatewayPreference OBJECT-TYPE
   SYNTAX      Integer32
   MAX-ACCESS  read-write
   STATUS      current
   DESCRIPTION
      "Path: ethernet3.editConf.ip.dhcp.gatewayPreference"
   ::= {er1645v2Lan3IpEntry 872480768}

er1645v2Lan3IpDhcpRoutePreference OBJECT-TYPE
   SYNTAX      Integer32
   MAX-ACCESS  read-write
   STATUS      current
   DESCRIPTION
      "Path: ethernet3.editConf.ip.dhcp.routePreference"
   ::= {er1645v2Lan3IpEntry 872546304}

er1645v2Lan3IpDhcpDnsPreference OBJECT-TYPE
   SYNTAX      Integer32
   MAX-ACCESS  read-write
   STATUS      current
   DESCRIPTION
      "Path: ethernet3.editConf.ip.dhcp.dnsPreference"
   ::= {er1645v2Lan3IpEntry 872611840}

er1645v2Lan3IpMtu OBJECT-TYPE
   SYNTAX      Integer32
   MAX-ACCESS  read-write
   STATUS      current
   DESCRIPTION
      "Path: ethernet3.editConf.ip.mtu"
   ::= {er1645v2Lan3IpEntry 671088640}

er1645v2Lan3IpMssAdjust OBJECT-TYPE
   SYNTAX      INTEGER
               {
               disabled (0),
               auto (65536)
               }
   MAX-ACCESS  read-write
   STATUS      current
   DESCRIPTION
      "Path: ethernet3.editConf.ip.mssAdjust

       Possibilities:
               disabled   (0)
               auto   (65536)"
   ::= {er1645v2Lan3IpEntry 754974720}

er1645v2Lan3IpRipMetric OBJECT-TYPE
   SYNTAX      Integer32
   MAX-ACCESS  read-write
   STATUS      current
   DESCRIPTION
      "Path: ethernet3.editConf.ip.rip.metric"
   ::= {er1645v2Lan3IpEntry 353566720}

er1645v2Lan3IpRipMetricOut OBJECT-TYPE
   SYNTAX      Integer32
   MAX-ACCESS  read-write
   STATUS      current
   DESCRIPTION
      "Path: ethernet3.editConf.ip.rip.metricOut"
   ::= {er1645v2Lan3IpEntry 353632256}

er1645v2Lan3IpRipMode OBJECT-TYPE
   SYNTAX      INTEGER
               {
               disabled (0),
               passive (1),
               active (2)
               }
   MAX-ACCESS  read-write
   STATUS      current
   DESCRIPTION
      "Path: ethernet3.editConf.ip.rip.mode

       Possibilities:
               disabled   (0)
               passive   (1)
               active   (2)"
   ::= {er1645v2Lan3IpEntry 353697792}

er1645v2Lan3IpRipTxVer OBJECT-TYPE
   SYNTAX      INTEGER
               {
               rip1 (0),
               rip2 (1),
               rip1mcompatible (2)
               }
   MAX-ACCESS  read-write
   STATUS      current
   DESCRIPTION
      "Path: ethernet3.editConf.ip.rip.txVersion

       Possibilities:
               rip1   (0)
               rip2   (1)
               rip1-compatible   (2)"
   ::= {er1645v2Lan3IpEntry 354615296}

er1645v2Lan3IpRipRxVer OBJECT-TYPE
   SYNTAX      INTEGER
               {
               rip1only (0),
               rip2only (1),
               rip12 (2)
               }
   MAX-ACCESS  read-write
   STATUS      current
   DESCRIPTION
      "Path: ethernet3.editConf.ip.rip.rxVersion

       Possibilities:
               rip1only   (0)
               rip2only   (1)
               rip1&2   (2)"
   ::= {er1645v2Lan3IpEntry 354680832}

er1645v2Lan3IpRipSplitH OBJECT-TYPE
   SYNTAX      INTEGER
               {
               disabled (0),
               enabled (1),
               poisonedReverse (2)
               }
   MAX-ACCESS  read-write
   STATUS      current
   DESCRIPTION
      "Path: ethernet3.editConf.ip.rip.splitHorizon

       Possibilities:
               disabled   (0)
               enabled   (1)
               poisonedReverse   (2)"
   ::= {er1645v2Lan3IpEntry 353828864}

er1645v2Lan3IpRipAuth OBJECT-TYPE
   SYNTAX      INTEGER
               {
               disabled (0),
               texts (1),
               md5 (2)
               }
   MAX-ACCESS  read-write
   STATUS      current
   DESCRIPTION
      "Path: ethernet3.editConf.ip.rip.authentication

       Possibilities:
               disabled   (0)
               text    (1)
               md5   (2)"
   ::= {er1645v2Lan3IpEntry 353501184}

er1645v2Lan3IpRipFilter OBJECT-TYPE
   SYNTAX      DisplayString
   MAX-ACCESS  read-write
   STATUS      current
   DESCRIPTION
      "Path: ethernet3.editConf.ip.rip.filter"
   ::= {er1645v2Lan3IpEntry 354418688}

er1645v2Lan3IpRipFilterIn OBJECT-TYPE
   SYNTAX      DisplayString
   MAX-ACCESS  read-write
   STATUS      current
   DESCRIPTION
      "Path: ethernet3.editConf.ip.rip.filterIn"
   ::= {er1645v2Lan3IpEntry 354484224}

er1645v2Lan3IpRipClearNextHop OBJECT-TYPE
   SYNTAX      INTEGER
               {
               disabled (0),
               enabled (1)
               }
   MAX-ACCESS  read-write
   STATUS      current
   DESCRIPTION
      "Path: ethernet3.editConf.ip.rip.clearNextHop

       Possibilities:
               disabled   (0)
               enabled   (1)"
   ::= {er1645v2Lan3IpEntry 352452608}

er1645v2Lan3IpAccPol OBJECT-TYPE
   SYNTAX      DisplayString
   MAX-ACCESS  read-write
   STATUS      current
   DESCRIPTION
      "Path: ethernet3.editConf.ip.accessPolicy"
   ::= {er1645v2Lan3IpEntry 704643072}

er1645v2Lan3IpAB OBJECT-TYPE
   SYNTAX      DisplayString
   MAX-ACCESS  read-write
   STATUS      current
   DESCRIPTION
      "Path: ethernet3.editConf.ip.trafficPolicy"
   ::= {er1645v2Lan3IpEntry 234881024}

er1645v2Lan3IpMA OBJECT-TYPE
   SYNTAX      INTEGER
               {
               disabled (0),
               enabled (1)
               }
   MAX-ACCESS  read-write
   STATUS      current
   DESCRIPTION
      "Path: ethernet3.editConf.ip.mgmtAccess

       Possibilities:
               disabled   (0)
               enabled   (1)"
   ::= {er1645v2Lan3IpEntry 268435456}

er1645v2Lan3IpMF OBJECT-TYPE
   SYNTAX      Integer32
   MAX-ACCESS  read-write
   STATUS      current
   DESCRIPTION
      "Path: ethernet3.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3IpEntry 285212672}

er1645v2Lan3IpDB OBJECT-TYPE
   SYNTAX      INTEGER
               {
               disabled (0),
               enabled (1)
               }
   MAX-ACCESS  read-write
   STATUS      current
   DESCRIPTION
      "Path: ethernet3.editConf.ip.directedBroadcasts

       Possibilities:
               disabled   (0)
               enabled   (1)"
   ::= {er1645v2Lan3IpEntry 369098752}

er1645v2Lan3IpIR OBJECT-TYPE
   SYNTAX      INTEGER
               {
               disabled (0),
               enabled (1)
               }
   MAX-ACCESS  read-write
   STATUS      current
   DESCRIPTION
      "Path: ethernet3.editConf.ip.icmpRedirects

       Possibilities:
               disabled   (0)
               enabled   (1)"
   ::= {er1645v2Lan3IpEntry 436207616}

er1645v2Lan3IpIgmp OBJECT-TYPE
   SYNTAX      INTEGER
               {
               disabled (0),
               proxy (1),
               router (2),
               v3Router (5)
               }
   MAX-ACCESS  read-write
   STATUS      current
   DESCRIPTION
      "Path: ethernet3.editConf.ip.igmp

       Possibilities:
               disabled   (0)
               proxy   (1)
               router   (2)
               v3Router   (5)"
   ::= {er1645v2Lan3IpEntry 536870912}

er1645v2Lan3IpNN OBJECT-TYPE
   SYNTAX      DisplayString
   MAX-ACCESS  read-write
   STATUS      current
   DESCRIPTION
      "Path: ethernet3.editConf.ip.nat"
   ::= {er1645v2Lan3IpEntry 452984832}

er1645v2Lan3IpVrrp OBJECT-TYPE
   SYNTAX      INTEGER
               {
               disabled (0),
               enabled (1)
               }
   MAX-ACCESS  read-write
   STATUS      current
   DESCRIPTION
      "Path: ethernet3.editConf.ip.vrrp

       Possibilities:
               disabled   (0)
               enabled   (1)"
   ::= {er1645v2Lan3IpEntry 721420288}

er1645v2Lan3IpPimMode OBJECT-TYPE
   SYNTAX      INTEGER
               {
               disabled (0),
               sparse (1),
               passive (2)
               }
   MAX-ACCESS  read-write
   STATUS      current
   DESCRIPTION
      "Path: ethernet3.editConf.ip.pim.mode

       Possibilities:
               disabled   (0)
               sparse   (1)
               passive   (2)"
   ::= {er1645v2Lan3IpEntry 771817472}

er1645v2Lan3IpPimDrPriority OBJECT-TYPE
   SYNTAX      Counter32
   MAX-ACCESS  read-write
   STATUS      current
   DESCRIPTION
      "Path: ethernet3.editConf.ip.pim.drPriority

       32 bit unsigned wrappable counter."
   ::= {er1645v2Lan3IpEntry 771883008}

er1645v2Lan3IpPimHelloTime OBJECT-TYPE
   SYNTAX      TimeTicks
   MAX-ACCESS  read-write
   STATUS      current
   DESCRIPTION
      "Path: ethernet3.editConf.ip.pim.helloTime

       Time in centi-second."
   ::= {er1645v2Lan3IpEntry 771948544}

er1645v2Lan3IpPimPropagationDelay OBJECT-TYPE
   SYNTAX      TimeTicks
   MAX-ACCESS  read-write
   STATUS      current
   DESCRIPTION
      "Path: ethernet3.editConf.ip.pim.propagationDelay

       Time in centi-second."
   ::= {er1645v2Lan3IpEntry 772014080}

er1645v2Lan3IpPimOverrideInterval OBJECT-TYPE
   SYNTAX      TimeTicks
   MAX-ACCESS  read-write
   STATUS      current
   DESCRIPTION
      "Path: ethernet3.editConf.ip.pim.overrideInterval

       Time in centi-second."
   ::= {er1645v2Lan3IpEntry 772079616}

er1645v2Lan3IpPimBsrBorder OBJECT-TYPE
   SYNTAX      INTEGER
               {
               disabled (0),
               enabled (1)
               }
   MAX-ACCESS  read-write
   STATUS      current
   DESCRIPTION
      "Path: ethernet3.editConf.ip.pim.bsrBorder

       Possibilities:
               disabled   (0)
               enabled   (1)"
   ::= {er1645v2Lan3IpEntry 772145152}

er1645v2Lan3IpPimTtlThreshold OBJECT-TYPE
   SYNTAX      Integer32
   MAX-ACCESS  read-write
   STATUS      current
   DESCRIPTION
      "Path: ethernet3.editConf.ip.pim.ttlThreshold"
   ::= {er1645v2Lan3IpEntry 772210688}

er1645v2Lan3IpIMNetworkUnreachable OBJECT-TYPE
   SYNTAX      INTEGER
               {
               disabled (0),
               enabled (1)
               }
   MAX-ACCESS  read-write
   STATUS      current
   DESCRIPTION
      "Path: ethernet3.editConf.ip.icmpMessages.networkUnreachable

       Possibilities:
               disabled   (0)
               enabled   (1)"
   ::= {er1645v2Lan3IpEntry 788594688}

er1645v2Lan3IpIMHostUnreachable OBJECT-TYPE
   SYNTAX      INTEGER
               {
               disabled (0),
               enabled (1)
               }
   MAX-ACCESS  read-write
   STATUS      current
   DESCRIPTION
      "Path: ethernet3.editConf.ip.icmpMessages.hostUnreachable

       Possibilities:
               disabled   (0)
               enabled   (1)"
   ::= {er1645v2Lan3IpEntry 788660224}

er1645v2Lan3IpIMProtocolUnreachable OBJECT-TYPE
   SYNTAX      INTEGER
               {
               disabled (0),
               enabled (1)
               }
   MAX-ACCESS  read-write
   STATUS      current
   DESCRIPTION
      "Path: ethernet3.editConf.ip.icmpMessages.protocolUnreachable

       Possibilities:
               disabled   (0)
               enabled   (1)"
   ::= {er1645v2Lan3IpEntry 788725760}

er1645v2Lan3IpIMPortUnreachable OBJECT-TYPE
   SYNTAX      INTEGER
               {
               disabled (0),
               enabled (1)
               }
   MAX-ACCESS  read-write
   STATUS      current
   DESCRIPTION
      "Path: ethernet3.editConf.ip.icmpMessages.portUnreachable

       Possibilities:
               disabled   (0)
               enabled   (1)"
   ::= {er1645v2Lan3IpEntry 788791296}

er1645v2Lan3IpIMMtuExceeded OBJECT-TYPE
   SYNTAX      INTEGER
               {
               disabled (0),
               enabled (1)
               }
   MAX-ACCESS  read-write
   STATUS      current
   DESCRIPTION
      "Path: ethernet3.editConf.ip.icmpMessages.mtuExceeded

       Possibilities:
               disabled   (0)
               enabled   (1)"
   ::= {er1645v2Lan3IpEntry 788856832}

er1645v2Lan3IpIMAdminProhibited OBJECT-TYPE
   SYNTAX      INTEGER
               {
               disabled (0),
               enabled (1)
               }
   MAX-ACCESS  read-write
   STATUS      current
   DESCRIPTION
      "Path: ethernet3.editConf.ip.icmpMessages.adminProhibited

       Possibilities:
               disabled   (0)
               enabled   (1)"
   ::= {er1645v2Lan3IpEntry 788922368}

er1645v2Lan3IpIMTtlExceeded OBJECT-TYPE
   SYNTAX      INTEGER
               {
               disabled (0),
               enabled (1)
               }
   MAX-ACCESS  read-write
   STATUS      current
   DESCRIPTION
      "Path: ethernet3.editConf.ip.icmpMessages.ttlExceeded

       Possibilities:
               disabled   (0)
               enabled   (1)"
   ::= {er1645v2Lan3IpEntry 788987904}

er1645v2Lan3IpIMRedirect OBJECT-TYPE
   SYNTAX      INTEGER
               {
               disabled (0),
               enabled (1)
               }
   MAX-ACCESS  read-write
   STATUS      current
   DESCRIPTION
      "Path: ethernet3.editConf.ip.icmpMessages.redirect

       Possibilities:
               disabled   (0)
               enabled   (1)"
   ::= {er1645v2Lan3IpEntry 789053440}

er1645v2Lan3IpSaddr OBJECT-TYPE
   SYNTAX      SEQUENCE OF Er1645v2Lan3IpSaddrEntry
   MAX-ACCESS  not-accessible
   STATUS      current
   DESCRIPTION
      ""
   ::= {er1645v2Lan3Ip 385875968}

er1645v2Lan3IpSaddrEntry OBJECT-TYPE
   SYNTAX      Er1645v2Lan3IpSaddrEntry
   MAX-ACCESS  not-accessible
   STATUS      current
   DESCRIPTION
      ""
   INDEX      { er1645v2Lan3IpSaddrTableIx }
   ::= {er1645v2Lan3IpSaddr 1}

Er1645v2Lan3IpSaddrEntry ::=
   SEQUENCE
      {
      er1645v2Lan3IpSaddrActions
         VariableLengthTableActions,
      er1645v2Lan3IpSaddrTableIx
         TableIndex,
      er1645v2Lan3IpSaddrAddress
         IpAddress,
      er1645v2Lan3IpSaddrNetMask
         IpAddress
      }

er1645v2Lan3IpSaddrActions OBJECT-TYPE
   SYNTAX      VariableLengthTableActions
   MAX-ACCESS  read-write
   STATUS      current
   DESCRIPTION
      "By way of this field, some manipulations
       on this table may be performed."
   ::= {er1645v2Lan3IpSaddrEntry 2}

er1645v2Lan3IpSaddrTableIx OBJECT-TYPE
   SYNTAX      TableIndex
   MAX-ACCESS  not-accessible
   STATUS      current
   DESCRIPTION
      ""
   ::= {er1645v2Lan3IpSaddrEntry 11}

er1645v2Lan3IpSaddrAddress OBJECT-TYPE
   SYNTAX      IpAddress
   MAX-ACCESS  read-write
   STATUS      current
   DESCRIPTION
      "Path: ethernet3.editConf.ip.secondaryIp.address"
   ::= {er1645v2Lan3IpSaddrEntry 2030043136}

er1645v2Lan3IpSaddrNetMask OBJECT-TYPE
   SYNTAX      IpAddress
   MAX-ACCESS  read-write
   STATUS      current
   DESCRIPTION
      "Path: ethernet3.editConf.ip.secondaryIp.netMask"
   ::= {er1645v2Lan3IpSaddrEntry 2063597568}

er1645v2Lan3IpH OBJECT-TYPE
   SYNTAX      SEQUENCE OF Er1645v2Lan3IpHEntry
   MAX-ACCESS  not-accessible
   STATUS      current
   DESCRIPTION
      ""
   ::= {er1645v2Lan3Ip 251658240}

er1645v2Lan3IpHEntry OBJECT-TYPE
   SYNTAX      Er1645v2Lan3IpHEntry
   MAX-ACCESS  not-accessible
   STATUS      current
   DESCRIPTION
      ""
   INDEX      { er1645v2Lan3IpHTableIx }
   ::= {er1645v2Lan3IpH 1}

Er1645v2Lan3IpHEntry ::=
   SEQUENCE
      {
      er1645v2Lan3IpHActions
         VariableLengthTableActions,
      er1645v2Lan3IpHTableIx
         TableIndex,
      er1645v2Lan3IpHAddress
         IpAddress,
      er1645v2Lan3IpHDhcpRelayOptionSubscriberId
         DisplayString
      }

er1645v2Lan3IpHActions OBJECT-TYPE
   SYNTAX      VariableLengthTableActions
   MAX-ACCESS  read-write
   STATUS      current
   DESCRIPTION
      "By way of this field, some manipulations
       on this table may be performed."
   ::= {er1645v2Lan3IpHEntry 2}

er1645v2Lan3IpHTableIx OBJECT-TYPE
   SYNTAX      TableIndex
   MAX-ACCESS  not-accessible
   STATUS      current
   DESCRIPTION
      ""
   ::= {er1645v2Lan3IpHEntry 11}

er1645v2Lan3IpHAddress OBJECT-TYPE
   SYNTAX      IpAddress
   MAX-ACCESS  read-write
   STATUS      current
   DESCRIPTION
      "Path: ethernet3.editConf.ip.helpers.address"
   ::= {er1645v2Lan3IpHEntry 16777216}

er1645v2Lan3IpHDhcpRelayOptionSubscriberId OBJECT-TYPE
   SYNTAX      DisplayString
   MAX-ACCESS  read-write
   STATUS      current
   DESCRIPTION
      "Path: ethernet3.editConf.ip.helpers.dhcpRelayOption.subscriberId"
   ::= {er1645v2Lan3IpHEntry 33947648}


er1645v2Lan3Adapter OBJECT-TYPE
   SYNTAX      INTEGER
               {
               autoDetect (0),
               s10MbhalfDuplex (1),
               s10MbfullDuplex (2),
               s100MbhalfDuplex (3),
               s100MbfullDuplex (4),
               s1000MbfullDuplex (6)
               }
   MAX-ACCESS  read-write
   STATUS      current
   DESCRIPTION
      "Path: ethernet3.editConf.adapter

       Possibilities:
               autoDetect   (0)
               10Mb/halfDuplex   (1)
               10Mb/fullDuplex   (2)
               100Mb/halfDuplex   (3)
               100Mb/fullDuplex   (4)
               1000Mb/fullDuplex   (6)"
   ::= {er1645v2Lan3 32}


er1645v2Lan3Vlan OBJECT IDENTIFIER ::= {er1645v2Lan3 33}

er1645v2Lan3VlanSSCTable OBJECT-TYPE
   SYNTAX      SEQUENCE OF Er1645v2Lan3VlanEntry
   MAX-ACCESS  not-accessible
   STATUS      current
   DESCRIPTION
      ""
   ::= {er1645v2Lan3Vlan 1}

er1645v2Lan3VlanEntry OBJECT-TYPE
   SYNTAX      Er1645v2Lan3VlanEntry
   MAX-ACCESS  not-accessible
   STATUS      current
   DESCRIPTION
      ""
   INDEX      { er1645v2Lan3VlanTableIx }
   ::= {er1645v2Lan3VlanSSCTable 1}

Er1645v2Lan3VlanEntry ::=
   SEQUENCE
      {
      er1645v2Lan3VlanActions
         VariableLengthTableActions,
      er1645v2Lan3VlanTableIx
         TableIndex,
      er1645v2Lan3VlanName
         DisplayString,
      er1645v2Lan3VlanRemark
         DisplayString,
      er1645v2Lan3VlanAdminStatus
         INTEGER,
      er1645v2Lan3VlanMode
         INTEGER,
      er1645v2Lan3VlanPriorityPolicy
         DisplayString,
      er1645v2Lan3VlanIpVrfRouter
         DisplayString,
      er1645v2Lan3VlanIpAdr
         IpAddress,
      er1645v2Lan3VlanIpNetm
         IpAddress,
      er1645v2Lan3VlanIpSNetName
         INTEGER,
      er1645v2Lan3VlanIpSNetCust
         DisplayString,
      er1645v2Lan3VlanIpDhcpC
         INTEGER,
      er1645v2Lan3VlanIpDhcpGatewayPreference
         Integer32,
      er1645v2Lan3VlanIpDhcpRoutePreference
         Integer32,
      er1645v2Lan3VlanIpDhcpDnsPreference
         Integer32,
      er1645v2Lan3VlanIpMtu
         Integer32,
      er1645v2Lan3VlanIpMssAdjust
         INTEGER,
      er1645v2Lan3VlanIpRipMetric
         Integer32,
      er1645v2Lan3VlanIpRipMetricOut
         Integer32,
      er1645v2Lan3VlanIpRipMode
         INTEGER,
      er1645v2Lan3VlanIpRipTxVer
         INTEGER,
      er1645v2Lan3VlanIpRipRxVer
         INTEGER,
      er1645v2Lan3VlanIpRipSplitH
         INTEGER,
      er1645v2Lan3VlanIpRipAuth
         INTEGER,
      er1645v2Lan3VlanIpRipFilter
         DisplayString,
      er1645v2Lan3VlanIpRipFilterIn
         DisplayString,
      er1645v2Lan3VlanIpRipClearNextHop
         INTEGER,
      er1645v2Lan3VlanIpAccPol
         DisplayString,
      er1645v2Lan3VlanIpAB
         DisplayString,
      er1645v2Lan3VlanIpMA
         INTEGER,
      er1645v2Lan3VlanIpMF
         Integer32,
      er1645v2Lan3VlanIpDB
         INTEGER,
      er1645v2Lan3VlanIpIR
         INTEGER,
      er1645v2Lan3VlanIpIgmp
         INTEGER,
      er1645v2Lan3VlanIpNN
         DisplayString,
      er1645v2Lan3VlanIpVrrp
         INTEGER,
      er1645v2Lan3VlanIpPimMode
         INTEGER,
      er1645v2Lan3VlanIpPimDrPriority
         Counter32,
      er1645v2Lan3VlanIpPimHelloTime
         TimeTicks,
      er1645v2Lan3VlanIpPimPropagationDelay
         TimeTicks,
      er1645v2Lan3VlanIpPimOverrideInterval
         TimeTicks,
      er1645v2Lan3VlanIpPimBsrBorder
         INTEGER,
      er1645v2Lan3VlanIpPimTtlThreshold
         Integer32,
      er1645v2Lan3VlanIpIMNetworkUnreachable
         INTEGER,
      er1645v2Lan3VlanIpIMHostUnreachable
         INTEGER,
      er1645v2Lan3VlanIpIMProtocolUnreachable
         INTEGER,
      er1645v2Lan3VlanIpIMPortUnreachable
         INTEGER,
      er1645v2Lan3VlanIpIMMtuExceeded
         INTEGER,
      er1645v2Lan3VlanIpIMAdminProhibited
         INTEGER,
      er1645v2Lan3VlanIpIMTtlExceeded
         INTEGER,
      er1645v2Lan3VlanIpIMRedirect
         INTEGER,
      er1645v2Lan3VlanIpV6VrfRouter
         DisplayString,
      er1645v2Lan3VlanIpV6AddrAutoConfigNrDupAddrDetects
         Integer32,
      er1645v2Lan3VlanIpV6AddrAutoConfigAcceptRa
         INTEGER,
      er1645v2Lan3VlanIpV6AddrAutoConfigAcceptRaRdnss
         INTEGER,
      er1645v2Lan3VlanIpV6AddrAutoConfigAcceptRaDnssl
         INTEGER,
      er1645v2Lan3VlanIpV6DefaultRoute
         INTEGER,
      er1645v2Lan3VlanIpV6RaSend
         INTEGER,
      er1645v2Lan3VlanIpV6RaMinInterval
         TimeTicks,
      er1645v2Lan3VlanIpV6RaMaxInterval
         TimeTicks,
      er1645v2Lan3VlanIpV6RaManagedFlag
         INTEGER,
      er1645v2Lan3VlanIpV6RaOtherConfFlag
         INTEGER,
      er1645v2Lan3VlanIpV6RaLinkMtu
         Integer32,
      er1645v2Lan3VlanIpV6RaReachableTime
         TimeTicks,
      er1645v2Lan3VlanIpV6RaRetransmitTime
         TimeTicks,
      er1645v2Lan3VlanIpV6RaHopLimit
         Integer32,
      er1645v2Lan3VlanIpV6RaDefaultLifeTime
         TimeTicks,
      er1645v2Lan3VlanIpV6RaDnsOptionsRdnssLifeTime
         TimeTicks,
      er1645v2Lan3VlanIpV6RaDnsOptionsRdnssImportServers
         INTEGER,
      er1645v2Lan3VlanIpV6RaDnsOptionsDnsslLifeTime
         TimeTicks,
      er1645v2Lan3VlanIpV6RaDnsOptionsDnsslImportDomains
         INTEGER,
      er1645v2Lan3VlanIpV6RsSend
         INTEGER,
      er1645v2Lan3VlanIpV6RsMaxRandomDelay
         TimeTicks,
      er1645v2Lan3VlanIpV6RsInterval
         TimeTicks,
      er1645v2Lan3VlanIpV6RsMaxSolicitations
         Integer32,
      er1645v2Lan3VlanIpV6TrafficPolicyInbound
         DisplayString,
      er1645v2Lan3VlanIpV6TrafficPolicyOutbound
         DisplayString,
      er1645v2Lan3VlanIpV6FirewallZone
         DisplayString,
      er1645v2Lan3VlanIpV6DhcpClientAddrAC
         INTEGER,
      er1645v2Lan3VlanIpV6DhcpClientPrDelMode
         INTEGER,
      er1645v2Lan3VlanIpV6DhcpClientPrDelPool
         DisplayString,
      er1645v2Lan3VlanIpV6DhcpClientPrDelPdExclOpt
         INTEGER,
      er1645v2Lan3VlanIpV6DhcpClientDnsServerPref
         Integer32,
      er1645v2Lan3VlanIpV6DhcpClientRapidCommit
         INTEGER,
      er1645v2Lan3VlanIpV6DhcpClientTimersSolTimeOut
         TimeTicks,
      er1645v2Lan3VlanIpV6DhcpClientTimersSolMaxRt
         TimeTicks,
      er1645v2Lan3VlanIpV6DhcpClientTimersInfoRefresh
         TimeTicks,
      er1645v2Lan3VlanIpV6DhcpServerMode
         INTEGER,
      er1645v2Lan3VlanIpV6DhcpServerPreference
         Integer32,
      er1645v2Lan3VlanIpV6DhcpServerPool
         DisplayString,
      er1645v2Lan3VlanIpV6DhcpServerRapidCommit
         INTEGER,
      er1645v2Lan3VlanIpV6DhcpServerTimersInfoRefresh
         TimeTicks,
      er1645v2Lan3VlanIpV6DhcpRelayMode
         INTEGER,
      er1645v2Lan3VlanIpV6SendRedirect
         INTEGER,
      er1645v2Lan3VlanIpV6LinkMtu
         Integer32,
      er1645v2Lan3VlanIpV6InterfaceId
         OCTET STRING,
      er1645v2Lan3VlanIpV6MF
         Integer32,
      er1645v2Lan3VlanIpV6IcmpMessagesNoRoute
         INTEGER,
      er1645v2Lan3VlanIpV6IcmpMessagesBeyondScope
         INTEGER,
      er1645v2Lan3VlanIpV6IcmpMessagesAddressUnreachable
         INTEGER,
      er1645v2Lan3VlanIpV6IcmpMessagesPortUnreachable
         INTEGER,
      er1645v2Lan3VlanIpV6IcmpMessagesPacketTooBig
         INTEGER,
      er1645v2Lan3VlanIpV6IcmpMessagesHopLimitExceeded
         INTEGER,
      er1645v2Lan3VlanIpV6IcmpMessagesFragTimeExceeded
         INTEGER,
      er1645v2Lan3VlanIpV6IcmpMessagesHeaderFieldErr
         INTEGER,
      er1645v2Lan3VlanIpV6IcmpMessagesOptionUnrecognized
         INTEGER,
      er1645v2Lan3VlanIpV6IcmpMessagesRedirect
         INTEGER,
      er1645v2Lan3VlanBridgingAccList
         DisplayString,
      er1645v2Lan3VlanBridgingInACL
         DisplayString,
      er1645v2Lan3VlanBridgingTp
         DisplayString,
      er1645v2Lan3VlanBridgingBrGrp
         DisplayString,
      er1645v2Lan3VlanBridgingLimBC
         INTEGER,
      er1645v2Lan3VlanBridgingPrivateMode
         INTEGER,
      er1645v2Lan3VlanBridgingLearning
         INTEGER,
      er1645v2Lan3VlanBridgingMaxCacheSize
         INTEGER,
      er1645v2Lan3VlanBridgingRelearnDropOnRelearn
         INTEGER,
      er1645v2Lan3VlanBridgingRelearnShutdownThreshold
         Integer32,
      er1645v2Lan3VlanBridgingRelearnShutdownTime
         TimeTicks,
      er1645v2Lan3VlanBridgingRelearnLoopDetection
         INTEGER,
      er1645v2Lan3VlanBridgingRelearnLoopDetectionInterval
         TimeTicks,
      er1645v2Lan3VlanBridgingVlanMemberShip
         INTEGER,
      er1645v2Lan3VlanBridgingVlTUntaggedAction
         INTEGER,
      er1645v2Lan3VlanBridgingVlTUntaggedTagInfoTpid
         INTEGER,
      er1645v2Lan3VlanBridgingVlTUntaggedTagInfoVid
         Integer32,
      er1645v2Lan3VlanBridgingVlTUnknownVlansAction
         INTEGER,
      er1645v2Lan3VlanBridgingVlTUnknownVlansTagInfoTpid
         INTEGER,
      er1645v2Lan3VlanBridgingVlTUnknownVlansTagInfoVid
         Integer32,
      er1645v2Lan3VlanBridgingDot1adType
         INTEGER,
      er1645v2Lan3VlanBridgingPriority
         Integer32,
      er1645v2Lan3VlanBridgingPathCost
         Integer32,
      er1645v2Lan3VlanBridgingInternalPathCost
         Integer32,
      er1645v2Lan3VlanBridgingTCD
         INTEGER,
      er1645v2Lan3VlanBridgingRestrictedRole
         INTEGER,
      er1645v2Lan3VlanBridgingAdminEdge
         INTEGER,
      er1645v2Lan3VlanBridgingOamMacDeviceMac
         DisplayString,
      er1645v2Lan3VlanBridgingOamMacUserMac
         OCTET STRING,
      er1645v2Lan3VlanBridgingOamMacBridgeMac
         DisplayString,
      er1645v2Lan3VlanBridgingMgmtInline
         INTEGER,
      er1645v2Lan3VlanBridgingL2ptMode
         INTEGER,
      er1645v2Lan3VlanBridgingL2ptProtocols
         Integer32,
      er1645v2Lan3VlanBridgingL2ptDestMac
         OCTET STRING,
      er1645v2Lan3VlanBridgingL2ptCos
         INTEGER,
      er1645v2Lan3VlanBridgingL2ptDropThrStp
         INTEGER,
      er1645v2Lan3VlanBridgingL2ptDropThrLldp
         INTEGER,
      er1645v2Lan3VlanBridgingL2ptDropThrOam
         INTEGER,
      er1645v2Lan3VlanBridgingL2ptDropThrCdp
         INTEGER,
      er1645v2Lan3VlanBridgingL2ptDropThrVtp
         INTEGER,
      er1645v2Lan3VlanBridgingL2ptDropThrLacp
         INTEGER,
      er1645v2Lan3VlanBridgingL2ptDropThrEfmOam
         INTEGER,
      er1645v2Lan3VlanBridgingL2ptDropThrPvst
         INTEGER,
      er1645v2Lan3VlanBridgingL2ptDropThrMmrp
         INTEGER,
      er1645v2Lan3VlanBridgingL2ptDropThrMvrp
         INTEGER,
      er1645v2Lan3VlanBridgingL2ptDropThrGvrp
         INTEGER,
      er1645v2Lan3VlanBridgingL2ptDropThrGmrp
         INTEGER,
      er1645v2Lan3VlanBridgingL2ptDropThrDtp
         INTEGER,
      er1645v2Lan3VlanBridgingL2ptDropThrPagp
         INTEGER,
      er1645v2Lan3VlanBridgingL2ptDropThrUdld
         INTEGER,
      er1645v2Lan3VlanVlanVid
         INTEGER,
      er1645v2Lan3VlanVlanVidExtensionSingle
         OCTET STRING,
      er1645v2Lan3VlanVlanVidExtensionEndVid
         Integer32,
      er1645v2Lan3VlanVlanTpid
         INTEGER,
      er1645v2Lan3VlanVlanTagSign
         INTEGER,
      er1645v2Lan3VlanVlanChTos
         INTEGER,
      er1645v2Lan3VlanVlanCTMapP0
         INTEGER,
      er1645v2Lan3VlanVlanCTMapP1
         INTEGER,
      er1645v2Lan3VlanVlanCTMapP2
         INTEGER,
      er1645v2Lan3VlanVlanCTMapP3
         INTEGER,
      er1645v2Lan3VlanVlanCTMapP4
         INTEGER,
      er1645v2Lan3VlanVlanCTMapP5
         INTEGER,
      er1645v2Lan3VlanVlanCTMapP6
         INTEGER,
      er1645v2Lan3VlanVlanCTMapP7
         INTEGER,
      er1645v2Lan3VlanVlanTxCos
         INTEGER,
      er1645v2Lan3VlanVlanCCMapP0
         Integer32,
      er1645v2Lan3VlanVlanCCMapP1
         Integer32,
      er1645v2Lan3VlanVlanCCMapP2
         Integer32,
      er1645v2Lan3VlanVlanCCMapP3
         Integer32,
      er1645v2Lan3VlanVlanCCMapP4
         Integer32,
      er1645v2Lan3VlanVlanCCMapP5
         Integer32,
      er1645v2Lan3VlanVlanCCMapP6
         Integer32,
      er1645v2Lan3VlanVlanCCMapP7
         Integer32,
      er1645v2Lan3VlanVlanQCMapQueue1
         Integer32,
      er1645v2Lan3VlanVlanQCMapQueue2
         Integer32,
      er1645v2Lan3VlanVlanQCMapQueue3
         Integer32,
      er1645v2Lan3VlanVlanQCMapQueue4
         Integer32,
      er1645v2Lan3VlanVlanQCMapQueue5
         Integer32,
      er1645v2Lan3VlanVlanQCMapLowDelayQueue
         Integer32,
      er1645v2Lan3VlanVlanQCMapLowDelay2Queue
         Integer32,
      er1645v2Lan3VlanVlanQCMapSystemQueue
         Integer32,
      er1645v2Lan3VlanVlanQinQSVid
         Integer32,
      er1645v2Lan3VlanVlanQinQSTpid
         INTEGER,
      er1645v2Lan3VlanVlanArpTimeOut
         TimeTicks,
      er1645v2Lan3VlanVlanArpProxyArp
         INTEGER,
      er1645v2Lan3VlanBandwidthMode
         INTEGER,
      er1645v2Lan3VlanBandwidthCir
         Integer32,
      er1645v2Lan3VlanBandwidthEir
         Integer32,
      er1645v2Lan3VlanBandwidthUnit
         INTEGER,
      er1645v2Lan3VlanBandwidthTc
         INTEGER,
      er1645v2Lan3VlanBandwidthTcFactor
         INTEGER,
      er1645v2Lan3VlanBandwidthCorrType
         INTEGER,
      er1645v2Lan3VlanBandwidthCorrPredefEncapsFrameRelay
         DisplayString,
      er1645v2Lan3VlanBandwidthCorrPredefEncapsPpp
         DisplayString,
      er1645v2Lan3VlanBandwidthCorrPredefEncapsAtmHl
         INTEGER,
      er1645v2Lan3VlanBandwidthCorrPredefEncapsAtmMp
         INTEGER,
      er1645v2Lan3VlanBandwidthCorrPredefEncapsHdlc
         DisplayString,
      er1645v2Lan3VlanBandwidthCorrPredefEncapsEfmFs
         Integer32,
      er1645v2Lan3VlanBandwidthCorrPredefEncapsEfmIb
         Integer32,
      er1645v2Lan3VlanBandwidthCorrPredefMode
         INTEGER,
      er1645v2Lan3VlanBandwidthCorrManualOverhead
         Integer32,
      er1645v2Lan3VlanBandwidthCorrManualFrameData
         Counter32,
      er1645v2Lan3VlanBandwidthCorrManualFrameHeader
         Counter32,
      er1645v2Lan3VlanBandwidthMaxFifoQLen
         Integer32,
      er1645v2Lan3VlanBandwidthDeFlagCir
         INTEGER,
      er1645v2Lan3VlanBandwidthDeFlagEir
         INTEGER,
      er1645v2Lan3VlanBandwidthDeFlagViolate
         INTEGER,
      er1645v2Lan3VlanBandwidthActCirActNone
         OCTET STRING,
      er1645v2Lan3VlanBandwidthActCirActEthCos1
         INTEGER,
      er1645v2Lan3VlanBandwidthActCirActEthDei1
         INTEGER,
      er1645v2Lan3VlanBandwidthActCirActEthCos2
         INTEGER,
      er1645v2Lan3VlanBandwidthActCirActEthDei2
         INTEGER,
      er1645v2Lan3VlanBandwidthActCirActEthCos3
         INTEGER,
      er1645v2Lan3VlanBandwidthActCirActEthDei3
         INTEGER,
      er1645v2Lan3VlanBandwidthActCirActEthCos4
         INTEGER,
      er1645v2Lan3VlanBandwidthActCirActEthDei4
         INTEGER,
      er1645v2Lan3VlanBandwidthActCirActEthCos5
         INTEGER,
      er1645v2Lan3VlanBandwidthActCirActEthDei5
         INTEGER,
      er1645v2Lan3VlanBandwidthActCirActEthCos6
         INTEGER,
      er1645v2Lan3VlanBandwidthActCirActEthDei6
         INTEGER,
      er1645v2Lan3VlanBandwidthActCirActEthCos7
         INTEGER,
      er1645v2Lan3VlanBandwidthActCirActEthDei7
         INTEGER,
      er1645v2Lan3VlanBandwidthActCirActEthCos8
         INTEGER,
      er1645v2Lan3VlanBandwidthActCirActEthDei8
         INTEGER,
      er1645v2Lan3VlanBandwidthActCirActEthTos
         INTEGER,
      er1645v2Lan3VlanBandwidthActCirActEthQueue
         INTEGER,
      er1645v2Lan3VlanBandwidthActCirActEthDrpLev
         INTEGER,
      er1645v2Lan3VlanBandwidthActCirActEthDeFlag
         INTEGER,
      er1645v2Lan3VlanBandwidthActCirActIpTos
         INTEGER,
      er1645v2Lan3VlanBandwidthActCirActIpQueue
         INTEGER,
      er1645v2Lan3VlanBandwidthActCirActIpDrpLev
         INTEGER,
      er1645v2Lan3VlanBandwidthActCirActIpDeFlag
         INTEGER,
      er1645v2Lan3VlanBandwidthActEirActNone
         OCTET STRING,
      er1645v2Lan3VlanBandwidthActEirActEthCos1
         INTEGER,
      er1645v2Lan3VlanBandwidthActEirActEthDei1
         INTEGER,
      er1645v2Lan3VlanBandwidthActEirActEthCos2
         INTEGER,
      er1645v2Lan3VlanBandwidthActEirActEthDei2
         INTEGER,
      er1645v2Lan3VlanBandwidthActEirActEthCos3
         INTEGER,
      er1645v2Lan3VlanBandwidthActEirActEthDei3
         INTEGER,
      er1645v2Lan3VlanBandwidthActEirActEthCos4
         INTEGER,
      er1645v2Lan3VlanBandwidthActEirActEthDei4
         INTEGER,
      er1645v2Lan3VlanBandwidthActEirActEthCos5
         INTEGER,
      er1645v2Lan3VlanBandwidthActEirActEthDei5
         INTEGER,
      er1645v2Lan3VlanBandwidthActEirActEthCos6
         INTEGER,
      er1645v2Lan3VlanBandwidthActEirActEthDei6
         INTEGER,
      er1645v2Lan3VlanBandwidthActEirActEthCos7
         INTEGER,
      er1645v2Lan3VlanBandwidthActEirActEthDei7
         INTEGER,
      er1645v2Lan3VlanBandwidthActEirActEthCos8
         INTEGER,
      er1645v2Lan3VlanBandwidthActEirActEthDei8
         INTEGER,
      er1645v2Lan3VlanBandwidthActEirActEthTos
         INTEGER,
      er1645v2Lan3VlanBandwidthActEirActEthQueue
         INTEGER,
      er1645v2Lan3VlanBandwidthActEirActEthDrpLev
         INTEGER,
      er1645v2Lan3VlanBandwidthActEirActEthDeFlag
         INTEGER,
      er1645v2Lan3VlanBandwidthActEirActIpTos
         INTEGER,
      er1645v2Lan3VlanBandwidthActEirActIpQueue
         INTEGER,
      er1645v2Lan3VlanBandwidthActEirActIpDrpLev
         INTEGER,
      er1645v2Lan3VlanBandwidthActEirActIpDeFlag
         INTEGER,
      er1645v2Lan3VlanBandwidthActViolActNone
         OCTET STRING,
      er1645v2Lan3VlanBandwidthActViolActDrop
         OCTET STRING,
      er1645v2Lan3VlanBandwidthActViolActEthCos1
         INTEGER,
      er1645v2Lan3VlanBandwidthActViolActEthDei1
         INTEGER,
      er1645v2Lan3VlanBandwidthActViolActEthCos2
         INTEGER,
      er1645v2Lan3VlanBandwidthActViolActEthDei2
         INTEGER,
      er1645v2Lan3VlanBandwidthActViolActEthCos3
         INTEGER,
      er1645v2Lan3VlanBandwidthActViolActEthDei3
         INTEGER,
      er1645v2Lan3VlanBandwidthActViolActEthCos4
         INTEGER,
      er1645v2Lan3VlanBandwidthActViolActEthDei4
         INTEGER,
      er1645v2Lan3VlanBandwidthActViolActEthCos5
         INTEGER,
      er1645v2Lan3VlanBandwidthActViolActEthDei5
         INTEGER,
      er1645v2Lan3VlanBandwidthActViolActEthCos6
         INTEGER,
      er1645v2Lan3VlanBandwidthActViolActEthDei6
         INTEGER,
      er1645v2Lan3VlanBandwidthActViolActEthCos7
         INTEGER,
      er1645v2Lan3VlanBandwidthActViolActEthDei7
         INTEGER,
      er1645v2Lan3VlanBandwidthActViolActEthCos8
         INTEGER,
      er1645v2Lan3VlanBandwidthActViolActEthDei8
         INTEGER,
      er1645v2Lan3VlanBandwidthActViolActEthTos
         INTEGER,
      er1645v2Lan3VlanBandwidthActViolActEthQueue
         INTEGER,
      er1645v2Lan3VlanBandwidthActViolActEthDrpLev
         INTEGER,
      er1645v2Lan3VlanBandwidthActViolActEthDeFlag
         INTEGER,
      er1645v2Lan3VlanBandwidthActViolActIpTos
         INTEGER,
      er1645v2Lan3VlanBandwidthActViolActIpQueue
         INTEGER,
      er1645v2Lan3VlanBandwidthActViolActIpDrpLev
         INTEGER,
      er1645v2Lan3VlanBandwidthActViolActIpDeFlag
         INTEGER,
      er1645v2Lan3VlanInbBwMode
         INTEGER,
      er1645v2Lan3VlanInbBwCir
         Integer32,
      er1645v2Lan3VlanInbBwEir
         Integer32,
      er1645v2Lan3VlanInbBwUnit
         INTEGER,
      er1645v2Lan3VlanInbBwTc
         INTEGER,
      er1645v2Lan3VlanInbBwTcFactor
         INTEGER,
      er1645v2Lan3VlanInbBwCorrType
         INTEGER,
      er1645v2Lan3VlanInbBwCorrPredefEncapsFrameRelay
         DisplayString,
      er1645v2Lan3VlanInbBwCorrPredefEncapsPpp
         DisplayString,
      er1645v2Lan3VlanInbBwCorrPredefEncapsAtmHl
         INTEGER,
      er1645v2Lan3VlanInbBwCorrPredefEncapsAtmMp
         INTEGER,
      er1645v2Lan3VlanInbBwCorrPredefEncapsHdlc
         DisplayString,
      er1645v2Lan3VlanInbBwCorrPredefEncapsEfmFs
         Integer32,
      er1645v2Lan3VlanInbBwCorrPredefEncapsEfmIb
         Integer32,
      er1645v2Lan3VlanInbBwCorrPredefMode
         INTEGER,
      er1645v2Lan3VlanInbBwCorrManualOverhead
         Integer32,
      er1645v2Lan3VlanInbBwCorrManualFrameData
         Counter32,
      er1645v2Lan3VlanInbBwCorrManualFrameHeader
         Counter32,
      er1645v2Lan3VlanInbBwMaxFifoQLen
         Integer32,
      er1645v2Lan3VlanInbBwPriorityPolicy
         DisplayString,
      er1645v2Lan3VlanInbBwDeFlagCir
         INTEGER,
      er1645v2Lan3VlanInbBwDeFlagEir
         INTEGER,
      er1645v2Lan3VlanInbBwDeFlagViolate
         INTEGER,
      er1645v2Lan3VlanInbBwActCirActNone
         OCTET STRING,
      er1645v2Lan3VlanInbBwActCirActEthCos1
         INTEGER,
      er1645v2Lan3VlanInbBwActCirActEthDei1
         INTEGER,
      er1645v2Lan3VlanInbBwActCirActEthCos2
         INTEGER,
      er1645v2Lan3VlanInbBwActCirActEthDei2
         INTEGER,
      er1645v2Lan3VlanInbBwActCirActEthCos3
         INTEGER,
      er1645v2Lan3VlanInbBwActCirActEthDei3
         INTEGER,
      er1645v2Lan3VlanInbBwActCirActEthCos4
         INTEGER,
      er1645v2Lan3VlanInbBwActCirActEthDei4
         INTEGER,
      er1645v2Lan3VlanInbBwActCirActEthCos5
         INTEGER,
      er1645v2Lan3VlanInbBwActCirActEthDei5
         INTEGER,
      er1645v2Lan3VlanInbBwActCirActEthCos6
         INTEGER,
      er1645v2Lan3VlanInbBwActCirActEthDei6
         INTEGER,
      er1645v2Lan3VlanInbBwActCirActEthCos7
         INTEGER,
      er1645v2Lan3VlanInbBwActCirActEthDei7
         INTEGER,
      er1645v2Lan3VlanInbBwActCirActEthCos8
         INTEGER,
      er1645v2Lan3VlanInbBwActCirActEthDei8
         INTEGER,
      er1645v2Lan3VlanInbBwActCirActEthTos
         INTEGER,
      er1645v2Lan3VlanInbBwActCirActEthQueue
         INTEGER,
      er1645v2Lan3VlanInbBwActCirActEthDrpLev
         INTEGER,
      er1645v2Lan3VlanInbBwActCirActEthDeFlag
         INTEGER,
      er1645v2Lan3VlanInbBwActCirActIpTos
         INTEGER,
      er1645v2Lan3VlanInbBwActCirActIpQueue
         INTEGER,
      er1645v2Lan3VlanInbBwActCirActIpDrpLev
         INTEGER,
      er1645v2Lan3VlanInbBwActCirActIpDeFlag
         INTEGER,
      er1645v2Lan3VlanInbBwActEirActNone
         OCTET STRING,
      er1645v2Lan3VlanInbBwActEirActEthCos1
         INTEGER,
      er1645v2Lan3VlanInbBwActEirActEthDei1
         INTEGER,
      er1645v2Lan3VlanInbBwActEirActEthCos2
         INTEGER,
      er1645v2Lan3VlanInbBwActEirActEthDei2
         INTEGER,
      er1645v2Lan3VlanInbBwActEirActEthCos3
         INTEGER,
      er1645v2Lan3VlanInbBwActEirActEthDei3
         INTEGER,
      er1645v2Lan3VlanInbBwActEirActEthCos4
         INTEGER,
      er1645v2Lan3VlanInbBwActEirActEthDei4
         INTEGER,
      er1645v2Lan3VlanInbBwActEirActEthCos5
         INTEGER,
      er1645v2Lan3VlanInbBwActEirActEthDei5
         INTEGER,
      er1645v2Lan3VlanInbBwActEirActEthCos6
         INTEGER,
      er1645v2Lan3VlanInbBwActEirActEthDei6
         INTEGER,
      er1645v2Lan3VlanInbBwActEirActEthCos7
         INTEGER,
      er1645v2Lan3VlanInbBwActEirActEthDei7
         INTEGER,
      er1645v2Lan3VlanInbBwActEirActEthCos8
         INTEGER,
      er1645v2Lan3VlanInbBwActEirActEthDei8
         INTEGER,
      er1645v2Lan3VlanInbBwActEirActEthTos
         INTEGER,
      er1645v2Lan3VlanInbBwActEirActEthQueue
         INTEGER,
      er1645v2Lan3VlanInbBwActEirActEthDrpLev
         INTEGER,
      er1645v2Lan3VlanInbBwActEirActEthDeFlag
         INTEGER,
      er1645v2Lan3VlanInbBwActEirActIpTos
         INTEGER,
      er1645v2Lan3VlanInbBwActEirActIpQueue
         INTEGER,
      er1645v2Lan3VlanInbBwActEirActIpDrpLev
         INTEGER,
      er1645v2Lan3VlanInbBwActEirActIpDeFlag
         INTEGER,
      er1645v2Lan3VlanInbBwActViolActNone
         OCTET STRING,
      er1645v2Lan3VlanInbBwActViolActDrop
         OCTET STRING,
      er1645v2Lan3VlanInbBwActViolActEthCos1
         INTEGER,
      er1645v2Lan3VlanInbBwActViolActEthDei1
         INTEGER,
      er1645v2Lan3VlanInbBwActViolActEthCos2
         INTEGER,
      er1645v2Lan3VlanInbBwActViolActEthDei2
         INTEGER,
      er1645v2Lan3VlanInbBwActViolActEthCos3
         INTEGER,
      er1645v2Lan3VlanInbBwActViolActEthDei3
         INTEGER,
      er1645v2Lan3VlanInbBwActViolActEthCos4
         INTEGER,
      er1645v2Lan3VlanInbBwActViolActEthDei4
         INTEGER,
      er1645v2Lan3VlanInbBwActViolActEthCos5
         INTEGER,
      er1645v2Lan3VlanInbBwActViolActEthDei5
         INTEGER,
      er1645v2Lan3VlanInbBwActViolActEthCos6
         INTEGER,
      er1645v2Lan3VlanInbBwActViolActEthDei6
         INTEGER,
      er1645v2Lan3VlanInbBwActViolActEthCos7
         INTEGER,
      er1645v2Lan3VlanInbBwActViolActEthDei7
         INTEGER,
      er1645v2Lan3VlanInbBwActViolActEthCos8
         INTEGER,
      er1645v2Lan3VlanInbBwActViolActEthDei8
         INTEGER,
      er1645v2Lan3VlanInbBwActViolActEthTos
         INTEGER,
      er1645v2Lan3VlanInbBwActViolActEthQueue
         INTEGER,
      er1645v2Lan3VlanInbBwActViolActEthDrpLev
         INTEGER,
      er1645v2Lan3VlanInbBwActViolActEthDeFlag
         INTEGER,
      er1645v2Lan3VlanInbBwActViolActIpTos
         INTEGER,
      er1645v2Lan3VlanInbBwActViolActIpQueue
         INTEGER,
      er1645v2Lan3VlanInbBwActViolActIpDrpLev
         INTEGER,
      er1645v2Lan3VlanInbBwActViolActIpDeFlag
         INTEGER,
      er1645v2Lan3VlanPppoE
         INTEGER,
      er1645v2Lan3VlanPppLnkMOperation
         INTEGER,
      er1645v2Lan3VlanPppLnkMInterval
         TimeTicks,
      er1645v2Lan3VlanPppLnkMRepTimeOut
         TimeTicks,
      er1645v2Lan3VlanPppLnkMFailsPrmt
         Integer32,
      er1645v2Lan3VlanPppAuthentication
         INTEGER,
      er1645v2Lan3VlanPppAuthenPeriod
         TimeTicks,
      er1645v2Lan3VlanPppSessionName
         DisplayString,
      er1645v2Lan3VlanPppSessionSecret
         DisplayString,
      er1645v2Lan3VlanPppEncModeSessionSecret
         INTEGER,
      er1645v2Lan3VlanPppEncSessionSecret
         DisplayString,
      er1645v2Lan3VlanPppServiceName
         DisplayString,
      er1645v2Lan3VlanPbbMode
         INTEGER,
      er1645v2Lan3VlanPbbTxCos
         Integer32,
      er1645v2Lan3VlanPbbIsid
         Integer32,
      er1645v2Lan3VlanPbbDestMac
         OCTET STRING,
      er1645v2Lan3VlanPbbCustomGroupMac
         OCTET STRING
      }

er1645v2Lan3VlanActions OBJECT-TYPE
   SYNTAX      VariableLengthTableActions
   MAX-ACCESS  read-write
   STATUS      current
   DESCRIPTION
      "By way of this field, some manipulations
       on this table may be performed."
   ::= {er1645v2Lan3VlanEntry 2}

er1645v2Lan3VlanTableIx OBJECT-TYPE
   SYNTAX      TableIndex
   MAX-ACCESS  not-accessible
   STATUS      current
   DESCRIPTION
      ""
   ::= {er1645v2Lan3VlanEntry 11}

er1645v2Lan3VlanName OBJECT-TYPE
   SYNTAX      DisplayString
   MAX-ACCESS  read-write
   STATUS      current
   DESCRIPTION
      "Path: ethernet3.editConf.vlan.name"
   ::= {er1645v2Lan3VlanEntry 16777216}

er1645v2Lan3VlanRemark OBJECT-TYPE
   SYNTAX      DisplayString
   MAX-ACCESS  read-write
   STATUS      current
   DESCRIPTION
      "Path: ethernet3.editConf.vlan.remark"
   ::= {er1645v2Lan3VlanEntry 1157627904}

er1645v2Lan3VlanAdminStatus OBJECT-TYPE
   SYNTAX      INTEGER
               {
               up (1),
               down (2)
               }
   MAX-ACCESS  read-write
   STATUS      current
   DESCRIPTION
      "Path: ethernet3.editConf.vlan.adminStatus

       Possibilities:
               up   (1)
               down   (2)"
   ::= {er1645v2Lan3VlanEntry 33554432}

er1645v2Lan3VlanMode OBJECT-TYPE
   SYNTAX      INTEGER
               {
               routing (1),
               bridging (2),
               ipV6 (16),
               ipV6ipV4 (17),
               multilink (8)
               }
   MAX-ACCESS  read-write
   STATUS      current
   DESCRIPTION
      "Path: ethernet3.editConf.vlan.mode

       Possibilities:
               routing   (1)
               bridging   (2)
               ipV6   (16)
               ipV6/ipV4   (17)
               multilink   (8)"
   ::= {er1645v2Lan3VlanEntry 67108864}

er1645v2Lan3VlanPriorityPolicy OBJECT-TYPE
   SYNTAX      DisplayString
   MAX-ACCESS  read-write
   STATUS      current
   DESCRIPTION
      "Path: ethernet3.editConf.vlan.priorityPolicy"
   ::= {er1645v2Lan3VlanEntry 83886080}

er1645v2Lan3VlanIpVrfRouter OBJECT-TYPE
   SYNTAX      DisplayString
   MAX-ACCESS  read-write
   STATUS      current
   DESCRIPTION
      "Path: ethernet3.editConf.vlan.ip.vrfRouter"
   ::= {er1645v2Lan3VlanEntry 53215232}

er1645v2Lan3VlanIpAdr OBJECT-TYPE
   SYNTAX      IpAddress
   MAX-ACCESS  read-write
   STATUS      current
   DESCRIPTION
      "Path: ethernet3.editConf.vlan.ip.address"
   ::= {er1645v2Lan3VlanEntry 58261504}

er1645v2Lan3VlanIpNetm OBJECT-TYPE
   SYNTAX      IpAddress
   MAX-ACCESS  read-write
   STATUS      current
   DESCRIPTION
      "Path: ethernet3.editConf.vlan.ip.netMask"
   ::= {er1645v2Lan3VlanEntry 58392576}

er1645v2Lan3VlanIpSNetName OBJECT-TYPE
   SYNTAX      INTEGER
               {
               slOPTg (0),
               corp (2),
               dmz (3),
               internet (1)
               }
   MAX-ACCESS  read-write
   STATUS      current
   DESCRIPTION
      "Path: ethernet3.editConf.vlan.ip.sNet.name

       Possibilities:
               <OPT>   (0)
               corp   (2)
               dmz   (3)
               internet   (1)"
   ::= {er1645v2Lan3VlanEntry 53674240}

er1645v2Lan3VlanIpSNetCust OBJECT-TYPE
   SYNTAX      DisplayString
   MAX-ACCESS  read-write
   STATUS      current
   DESCRIPTION
      "Path: ethernet3.editConf.vlan.ip.sNet.custom"
   ::= {er1645v2Lan3VlanEntry 53674496}

er1645v2Lan3VlanIpDhcpC OBJECT-TYPE
   SYNTAX      INTEGER
               {
               disabled (0),
               enabled (1)
               }
   MAX-ACCESS  read-write
   STATUS      current
   DESCRIPTION
      "Path: ethernet3.editConf.vlan.ip.dhcpClient

       Possibilities:
               disabled   (0)
               enabled   (1)"
   ::= {er1645v2Lan3VlanEntry 53608448}

er1645v2Lan3VlanIpDhcpGatewayPreference OBJECT-TYPE
   SYNTAX      Integer32
   MAX-ACCESS  read-write
   STATUS      current
   DESCRIPTION
      "Path: ethernet3.editConf.vlan.ip.dhcp.gatewayPreference"
   ::= {er1645v2Lan3VlanEntry 53739776}

er1645v2Lan3VlanIpDhcpRoutePreference OBJECT-TYPE
   SYNTAX      Integer32
   MAX-ACCESS  read-write
   STATUS      current
   DESCRIPTION
      "Path: ethernet3.editConf.vlan.ip.dhcp.routePreference"
   ::= {er1645v2Lan3VlanEntry 53740032}

er1645v2Lan3VlanIpDhcpDnsPreference OBJECT-TYPE
   SYNTAX      Integer32
   MAX-ACCESS  read-write
   STATUS      current
   DESCRIPTION
      "Path: ethernet3.editConf.vlan.ip.dhcp.dnsPreference"
   ::= {er1645v2Lan3VlanEntry 53740288}

er1645v2Lan3VlanIpMtu OBJECT-TYPE
   SYNTAX      Integer32
   MAX-ACCESS  read-write
   STATUS      current
   DESCRIPTION
      "Path: ethernet3.editConf.vlan.ip.mtu"
   ::= {er1645v2Lan3VlanEntry 52953088}

er1645v2Lan3VlanIpMssAdjust OBJECT-TYPE
   SYNTAX      INTEGER
               {
               disabled (0),
               auto (65536)
               }
   MAX-ACCESS  read-write
   STATUS      current
   DESCRIPTION
      "Path: ethernet3.editConf.vlan.ip.mssAdjust

       Possibilities:
               disabled   (0)
               auto   (65536)"
   ::= {er1645v2Lan3VlanEntry 53280768}

er1645v2Lan3VlanIpRipMetric OBJECT-TYPE
   SYNTAX      Integer32
   MAX-ACCESS  read-write
   STATUS      current
   DESCRIPTION
      "Path: ethernet3.editConf.vlan.ip.rip.metric"
   ::= {er1645v2Lan3VlanEntry 51712768}

er1645v2Lan3VlanIpRipMetricOut OBJECT-TYPE
   SYNTAX      Integer32
   MAX-ACCESS  read-write
   STATUS      current
   DESCRIPTION
      "Path: ethernet3.editConf.vlan.ip.rip.metricOut"
   ::= {er1645v2Lan3VlanEntry 51713024}

er1645v2Lan3VlanIpRipMode OBJECT-TYPE
   SYNTAX      INTEGER
               {
               disabled (0),
               passive (1),
               active (2)
               }
   MAX-ACCESS  read-write
   STATUS      current
   DESCRIPTION
      "Path: ethernet3.editConf.vlan.ip.rip.mode

       Possibilities:
               disabled   (0)
               passive   (1)
               active   (2)"
   ::= {er1645v2Lan3VlanEntry 51713280}

er1645v2Lan3VlanIpRipTxVer OBJECT-TYPE
   SYNTAX      INTEGER
               {
               rip1 (0),
               rip2 (1),
               rip1mcompatible (2)
               }
   MAX-ACCESS  read-write
   STATUS      current
   DESCRIPTION
      "Path: ethernet3.editConf.vlan.ip.rip.txVersion

       Possibilities:
               rip1   (0)
               rip2   (1)
               rip1-compatible   (2)"
   ::= {er1645v2Lan3VlanEntry 51716864}

er1645v2Lan3VlanIpRipRxVer OBJECT-TYPE
   SYNTAX      INTEGER
               {
               rip1only (0),
               rip2only (1),
               rip12 (2)
               }
   MAX-ACCESS  read-write
   STATUS      current
   DESCRIPTION
      "Path: ethernet3.editConf.vlan.ip.rip.rxVersion

       Possibilities:
               rip1only   (0)
               rip2only   (1)
               rip1&2   (2)"
   ::= {er1645v2Lan3VlanEntry 51717120}

er1645v2Lan3VlanIpRipSplitH OBJECT-TYPE
   SYNTAX      INTEGER
               {
               disabled (0),
               enabled (1),
               poisonedReverse (2)
               }
   MAX-ACCESS  read-write
   STATUS      current
   DESCRIPTION
      "Path: ethernet3.editConf.vlan.ip.rip.splitHorizon

       Possibilities:
               disabled   (0)
               enabled   (1)
               poisonedReverse   (2)"
   ::= {er1645v2Lan3VlanEntry 51713792}

er1645v2Lan3VlanIpRipAuth OBJECT-TYPE
   SYNTAX      INTEGER
               {
               disabled (0),
               texts (1),
               md5 (2)
               }
   MAX-ACCESS  read-write
   STATUS      current
   DESCRIPTION
      "Path: ethernet3.editConf.vlan.ip.rip.authentication

       Possibilities:
               disabled   (0)
               text    (1)
               md5   (2)"
   ::= {er1645v2Lan3VlanEntry 51712512}

er1645v2Lan3VlanIpRipFilter OBJECT-TYPE
   SYNTAX      DisplayString
   MAX-ACCESS  read-write
   STATUS      current
   DESCRIPTION
      "Path: ethernet3.editConf.vlan.ip.rip.filter"
   ::= {er1645v2Lan3VlanEntry 51716096}

er1645v2Lan3VlanIpRipFilterIn OBJECT-TYPE
   SYNTAX      DisplayString
   MAX-ACCESS  read-write
   STATUS      current
   DESCRIPTION
      "Path: ethernet3.editConf.vlan.ip.rip.filterIn"
   ::= {er1645v2Lan3VlanEntry 51716352}

er1645v2Lan3VlanIpRipClearNextHop OBJECT-TYPE
   SYNTAX      INTEGER
               {
               disabled (0),
               enabled (1)
               }
   MAX-ACCESS  read-write
   STATUS      current
   DESCRIPTION
      "Path: ethernet3.editConf.vlan.ip.rip.clearNextHop

       Possibilities:
               disabled   (0)
               enabled   (1)"
   ::= {er1645v2Lan3VlanEntry 51708416}

er1645v2Lan3VlanIpAccPol OBJECT-TYPE
   SYNTAX      DisplayString
   MAX-ACCESS  read-write
   STATUS      current
   DESCRIPTION
      "Path: ethernet3.editConf.vlan.ip.accessPolicy"
   ::= {er1645v2Lan3VlanEntry 53084160}

er1645v2Lan3VlanIpAB OBJECT-TYPE
   SYNTAX      DisplayString
   MAX-ACCESS  read-write
   STATUS      current
   DESCRIPTION
      "Path: ethernet3.editConf.vlan.ip.trafficPolicy"
   ::= {er1645v2Lan3VlanEntry 51249152}

er1645v2Lan3VlanIpMA OBJECT-TYPE
   SYNTAX      INTEGER
               {
               disabled (0),
               enabled (1)
               }
   MAX-ACCESS  read-write
   STATUS      current
   DESCRIPTION
      "Path: ethernet3.editConf.vlan.ip.mgmtAccess

       Possibilities:
               disabled   (0)
               enabled   (1)"
   ::= {er1645v2Lan3VlanEntry 51380224}

er1645v2Lan3VlanIpMF OBJECT-TYPE
   SYNTAX      Integer32
   MAX-ACCESS  read-write
   STATUS      current
   DESCRIPTION
      "Path: ethernet3.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3VlanEntry 51445760}

er1645v2Lan3VlanIpDB OBJECT-TYPE
   SYNTAX      INTEGER
               {
               disabled (0),
               enabled (1)
               }
   MAX-ACCESS  read-write
   STATUS      current
   DESCRIPTION
      "Path: ethernet3.editConf.vlan.ip.directedBroadcasts

       Possibilities:
               disabled   (0)
               enabled   (1)"
   ::= {er1645v2Lan3VlanEntry 51773440}

er1645v2Lan3VlanIpIR OBJECT-TYPE
   SYNTAX      INTEGER
               {
               disabled (0),
               enabled (1)
               }
   MAX-ACCESS  read-write
   STATUS      current
   DESCRIPTION
      "Path: ethernet3.editConf.vlan.ip.icmpRedirects

       Possibilities:
               disabled   (0)
               enabled   (1)"
   ::= {er1645v2Lan3VlanEntry 52035584}

er1645v2Lan3VlanIpIgmp OBJECT-TYPE
   SYNTAX      INTEGER
               {
               disabled (0),
               proxy (1),
               router (2),
               v3Router (5)
               }
   MAX-ACCESS  read-write
   STATUS      current
   DESCRIPTION
      "Path: ethernet3.editConf.vlan.ip.igmp

       Possibilities:
               disabled   (0)
               proxy   (1)
               router   (2)
               v3Router   (5)"
   ::= {er1645v2Lan3VlanEntry 52428800}

er1645v2Lan3VlanIpNN OBJECT-TYPE
   SYNTAX      DisplayString
   MAX-ACCESS  read-write
   STATUS      current
   DESCRIPTION
      "Path: ethernet3.editConf.vlan.ip.nat"
   ::= {er1645v2Lan3VlanEntry 52101120}

er1645v2Lan3VlanIpVrrp OBJECT-TYPE
   SYNTAX      INTEGER
               {
               disabled (0),
               enabled (1)
               }
   MAX-ACCESS  read-write
   STATUS      current
   DESCRIPTION
      "Path: ethernet3.editConf.vlan.ip.vrrp

       Possibilities:
               disabled   (0)
               enabled   (1)"
   ::= {er1645v2Lan3VlanEntry 53149696}

er1645v2Lan3VlanIpPimMode OBJECT-TYPE
   SYNTAX      INTEGER
               {
               disabled (0),
               sparse (1),
               passive (2)
               }
   MAX-ACCESS  read-write
   STATUS      current
   DESCRIPTION
      "Path: ethernet3.editConf.vlan.ip.pim.mode

       Possibilities:
               disabled   (0)
               sparse   (1)
               passive   (2)"
   ::= {er1645v2Lan3VlanEntry 53346560}

er1645v2Lan3VlanIpPimDrPriority OBJECT-TYPE
   SYNTAX      Counter32
   MAX-ACCESS  read-write
   STATUS      current
   DESCRIPTION
      "Path: ethernet3.editConf.vlan.ip.pim.drPriority

       32 bit unsigned wrappable counter."
   ::= {er1645v2Lan3VlanEntry 53346816}

er1645v2Lan3VlanIpPimHelloTime OBJECT-TYPE
   SYNTAX      TimeTicks
   MAX-ACCESS  read-write
   STATUS      current
   DESCRIPTION
      "Path: ethernet3.editConf.vlan.ip.pim.helloTime

       Time in centi-second."
   ::= {er1645v2Lan3VlanEntry 53347072}

er1645v2Lan3VlanIpPimPropagationDelay OBJECT-TYPE
   SYNTAX      TimeTicks
   MAX-ACCESS  read-write
   STATUS      current
   DESCRIPTION
      "Path: ethernet3.editConf.vlan.ip.pim.propagationDelay

       Time in centi-second."
   ::= {er1645v2Lan3VlanEntry 53347328}

er1645v2Lan3VlanIpPimOverrideInterval OBJECT-TYPE
   SYNTAX      TimeTicks
   MAX-ACCESS  read-write
   STATUS      current
   DESCRIPTION
      "Path: ethernet3.editConf.vlan.ip.pim.overrideInterval

       Time in centi-second."
   ::= {er1645v2Lan3VlanEntry 53347584}

er1645v2Lan3VlanIpPimBsrBorder OBJECT-TYPE
   SYNTAX      INTEGER
               {
               disabled (0),
               enabled (1)
               }
   MAX-ACCESS  read-write
   STATUS      current
   DESCRIPTION
      "Path: ethernet3.editConf.vlan.ip.pim.bsrBorder

       Possibilities:
               disabled   (0)
               enabled   (1)"
   ::= {er1645v2Lan3VlanEntry 53347840}

er1645v2Lan3VlanIpPimTtlThreshold OBJECT-TYPE
   SYNTAX      Integer32
   MAX-ACCESS  read-write
   STATUS      current
   DESCRIPTION
      "Path: ethernet3.editConf.vlan.ip.pim.ttlThreshold"
   ::= {er1645v2Lan3VlanEntry 53348096}

er1645v2Lan3VlanIpIMNetworkUnreachable OBJECT-TYPE
   SYNTAX      INTEGER
               {
               disabled (0),
               enabled (1)
               }
   MAX-ACCESS  read-write
   STATUS      current
   DESCRIPTION
      "Path: ethernet3.editConf.vlan.ip.icmpMessages.networkUnreachable

       Possibilities:
               disabled   (0)
               enabled   (1)"
   ::= {er1645v2Lan3VlanEntry 53412096}

er1645v2Lan3VlanIpIMHostUnreachable OBJECT-TYPE
   SYNTAX      INTEGER
               {
               disabled (0),
               enabled (1)
               }
   MAX-ACCESS  read-write
   STATUS      current
   DESCRIPTION
      "Path: ethernet3.editConf.vlan.ip.icmpMessages.hostUnreachable

       Possibilities:
               disabled   (0)
               enabled   (1)"
   ::= {er1645v2Lan3VlanEntry 53412352}

er1645v2Lan3VlanIpIMProtocolUnreachable OBJECT-TYPE
   SYNTAX      INTEGER
               {
               disabled (0),
               enabled (1)
               }
   MAX-ACCESS  read-write
   STATUS      current
   DESCRIPTION
      "Path: ethernet3.editConf.vlan.ip.icmpMessages.protocolUnreachable

       Possibilities:
               disabled   (0)
               enabled   (1)"
   ::= {er1645v2Lan3VlanEntry 53412608}

er1645v2Lan3VlanIpIMPortUnreachable OBJECT-TYPE
   SYNTAX      INTEGER
               {
               disabled (0),
               enabled (1)
               }
   MAX-ACCESS  read-write
   STATUS      current
   DESCRIPTION
      "Path: ethernet3.editConf.vlan.ip.icmpMessages.portUnreachable

       Possibilities:
               disabled   (0)
               enabled   (1)"
   ::= {er1645v2Lan3VlanEntry 53412864}

er1645v2Lan3VlanIpIMMtuExceeded OBJECT-TYPE
   SYNTAX      INTEGER
               {
               disabled (0),
               enabled (1)
               }
   MAX-ACCESS  read-write
   STATUS      current
   DESCRIPTION
      "Path: ethernet3.editConf.vlan.ip.icmpMessages.mtuExceeded

       Possibilities:
               disabled   (0)
               enabled   (1)"
   ::= {er1645v2Lan3VlanEntry 53413120}

er1645v2Lan3VlanIpIMAdminProhibited OBJECT-TYPE
   SYNTAX      INTEGER
               {
               disabled (0),
               enabled (1)
               }
   MAX-ACCESS  read-write
   STATUS      current
   DESCRIPTION
      "Path: ethernet3.editConf.vlan.ip.icmpMessages.adminProhibited

       Possibilities:
               disabled   (0)
               enabled   (1)"
   ::= {er1645v2Lan3VlanEntry 53413376}

er1645v2Lan3VlanIpIMTtlExceeded OBJECT-TYPE
   SYNTAX      INTEGER
               {
               disabled (0),
               enabled (1)
               }
   MAX-ACCESS  read-write
   STATUS      current
   DESCRIPTION
      "Path: ethernet3.editConf.vlan.ip.icmpMessages.ttlExceeded

       Possibilities:
               disabled   (0)
               enabled   (1)"
   ::= {er1645v2Lan3VlanEntry 53413632}

er1645v2Lan3VlanIpIMRedirect OBJECT-TYPE
   SYNTAX      INTEGER
               {
               disabled (0),
               enabled (1)
               }
   MAX-ACCESS  read-write
   STATUS      current
   DESCRIPTION
      "Path: ethernet3.editConf.vlan.ip.icmpMessages.redirect

       Possibilities:
               disabled   (0)
               enabled   (1)"
   ::= {er1645v2Lan3VlanEntry 53413888}

er1645v2Lan3VlanIpV6VrfRouter OBJECT-TYPE
   SYNTAX      DisplayString
   MAX-ACCESS  read-write
   STATUS      current
   DESCRIPTION
      "Path: ethernet3.editConf.vlan.ipV6.vrfRouter"
   ::= {er1645v2Lan3VlanEntry 704708608}

er1645v2Lan3VlanIpV6AddrAutoConfigNrDupAddrDetects OBJECT-TYPE
   SYNTAX      Integer32
   MAX-ACCESS  read-write
   STATUS      current
   DESCRIPTION
      "Path: ethernet3.editConf.vlan.ipV6.addrAutoConfig.nrDupAddrDetects"
   ::= {er1645v2Lan3VlanEntry 704905472}

er1645v2Lan3VlanIpV6AddrAutoConfigAcceptRa OBJECT-TYPE
   SYNTAX      INTEGER
               {
               disabled (0),
               enabled (1)
               }
   MAX-ACCESS  read-write
   STATUS      current
   DESCRIPTION
      "Path: ethernet3.editConf.vlan.ipV6.addrAutoConfig.acceptRa

       Possibilities:
               disabled   (0)
               enabled   (1)"
   ::= {er1645v2Lan3VlanEntry 704905728}

er1645v2Lan3VlanIpV6AddrAutoConfigAcceptRaRdnss OBJECT-TYPE
   SYNTAX      INTEGER
               {
               disabled (0),
               enabled (1)
               }
   MAX-ACCESS  read-write
   STATUS      current
   DESCRIPTION
      "Path: ethernet3.editConf.vlan.ipV6.addrAutoConfig.acceptRaRdnss

       Possibilities:
               disabled   (0)
               enabled   (1)"
   ::= {er1645v2Lan3VlanEntry 704905984}

er1645v2Lan3VlanIpV6AddrAutoConfigAcceptRaDnssl OBJECT-TYPE
   SYNTAX      INTEGER
               {
               disabled (0),
               enabled (1)
               }
   MAX-ACCESS  read-write
   STATUS      current
   DESCRIPTION
      "Path: ethernet3.editConf.vlan.ipV6.addrAutoConfig.acceptRaDnssl

       Possibilities:
               disabled   (0)
               enabled   (1)"
   ::= {er1645v2Lan3VlanEntry 704906240}

er1645v2Lan3VlanIpV6DefaultRoute OBJECT-TYPE
   SYNTAX      INTEGER
               {
               disabled (0),
               enabled (1)
               }
   MAX-ACCESS  read-write
   STATUS      current
   DESCRIPTION
      "Path: ethernet3.editConf.vlan.ipV6.defaultRoute

       Possibilities:
               disabled   (0)
               enabled   (1)"
   ::= {er1645v2Lan3VlanEntry 704970752}

er1645v2Lan3VlanIpV6RaSend OBJECT-TYPE
   SYNTAX      INTEGER
               {
               disabled (0),
               enabled (1)
               }
   MAX-ACCESS  read-write
   STATUS      current
   DESCRIPTION
      "Path: ethernet3.editConf.vlan.ipV6.ra.send

       Possibilities:
               disabled   (0)
               enabled   (1)"
   ::= {er1645v2Lan3VlanEntry 705036544}

er1645v2Lan3VlanIpV6RaMinInterval OBJECT-TYPE
   SYNTAX      TimeTicks
   MAX-ACCESS  read-write
   STATUS      current
   DESCRIPTION
      "Path: ethernet3.editConf.vlan.ipV6.ra.minInterval

       Time in centi-second."
   ::= {er1645v2Lan3VlanEntry 705036800}

er1645v2Lan3VlanIpV6RaMaxInterval OBJECT-TYPE
   SYNTAX      TimeTicks
   MAX-ACCESS  read-write
   STATUS      current
   DESCRIPTION
      "Path: ethernet3.editConf.vlan.ipV6.ra.maxInterval

       Time in centi-second."
   ::= {er1645v2Lan3VlanEntry 705037056}

er1645v2Lan3VlanIpV6RaManagedFlag OBJECT-TYPE
   SYNTAX      INTEGER
               {
               disabled (0),
               enabled (1)
               }
   MAX-ACCESS  read-write
   STATUS      current
   DESCRIPTION
      "Path: ethernet3.editConf.vlan.ipV6.ra.managedFlag

       Possibilities:
               disabled   (0)
               enabled   (1)"
   ::= {er1645v2Lan3VlanEntry 705037312}

er1645v2Lan3VlanIpV6RaOtherConfFlag OBJECT-TYPE
   SYNTAX      INTEGER
               {
               disabled (0),
               enabled (1)
               }
   MAX-ACCESS  read-write
   STATUS      current
   DESCRIPTION
      "Path: ethernet3.editConf.vlan.ipV6.ra.otherConfFlag

       Possibilities:
               disabled   (0)
               enabled   (1)"
   ::= {er1645v2Lan3VlanEntry 705037568}

er1645v2Lan3VlanIpV6RaLinkMtu OBJECT-TYPE
   SYNTAX      Integer32
   MAX-ACCESS  read-write
   STATUS      current
   DESCRIPTION
      "Path: ethernet3.editConf.vlan.ipV6.ra.linkMtu"
   ::= {er1645v2Lan3VlanEntry 705037824}

er1645v2Lan3VlanIpV6RaReachableTime OBJECT-TYPE
   SYNTAX      TimeTicks
   MAX-ACCESS  read-write
   STATUS      current
   DESCRIPTION
      "Path: ethernet3.editConf.vlan.ipV6.ra.reachableTime

       Time in centi-second."
   ::= {er1645v2Lan3VlanEntry 705038080}

er1645v2Lan3VlanIpV6RaRetransmitTime OBJECT-TYPE
   SYNTAX      TimeTicks
   MAX-ACCESS  read-write
   STATUS      current
   DESCRIPTION
      "Path: ethernet3.editConf.vlan.ipV6.ra.retransmitTime

       Time in centi-second."
   ::= {er1645v2Lan3VlanEntry 705038336}

er1645v2Lan3VlanIpV6RaHopLimit OBJECT-TYPE
   SYNTAX      Integer32
   MAX-ACCESS  read-write
   STATUS      current
   DESCRIPTION
      "Path: ethernet3.editConf.vlan.ipV6.ra.hopLimit"
   ::= {er1645v2Lan3VlanEntry 705038592}

er1645v2Lan3VlanIpV6RaDefaultLifeTime OBJECT-TYPE
   SYNTAX      TimeTicks
   MAX-ACCESS  read-write
   STATUS      current
   DESCRIPTION
      "Path: ethernet3.editConf.vlan.ipV6.ra.defaultLifeTime

       Time in centi-second."
   ::= {er1645v2Lan3VlanEntry 705038848}

er1645v2Lan3VlanIpV6RaDnsOptionsRdnssLifeTime OBJECT-TYPE
   SYNTAX      TimeTicks
   MAX-ACCESS  read-write
   STATUS      current
   DESCRIPTION
      "Path: ethernet3.editConf.vlan.ipV6.ra.dnsOptions.rdnss.lifeTime

       Time in centi-second."
   ::= {er1645v2Lan3VlanEntry 705039140}

er1645v2Lan3VlanIpV6RaDnsOptionsRdnssImportServers OBJECT-TYPE
   SYNTAX      INTEGER
               {
               disabled (0),
               enabled (1)
               }
   MAX-ACCESS  read-write
   STATUS      current
   DESCRIPTION
      "Path: ethernet3.editConf.vlan.ipV6.ra.dnsOptions.rdnss.importServers

       Possibilities:
               disabled   (0)
               enabled   (1)"
   ::= {er1645v2Lan3VlanEntry 705039148}

er1645v2Lan3VlanIpV6RaDnsOptionsDnsslLifeTime OBJECT-TYPE
   SYNTAX      TimeTicks
   MAX-ACCESS  read-write
   STATUS      current
   DESCRIPTION
      "Path: ethernet3.editConf.vlan.ipV6.ra.dnsOptions.dnssl.lifeTime

       Time in centi-second."
   ::= {er1645v2Lan3VlanEntry 705039172}

er1645v2Lan3VlanIpV6RaDnsOptionsDnsslImportDomains OBJECT-TYPE
   SYNTAX      INTEGER
               {
               disabled (0),
               enabled (1)
               }
   MAX-ACCESS  read-write
   STATUS      current
   DESCRIPTION
      "Path: ethernet3.editConf.vlan.ipV6.ra.dnsOptions.dnssl.importDomains

       Possibilities:
               disabled   (0)
               enabled   (1)"
   ::= {er1645v2Lan3VlanEntry 705039180}

er1645v2Lan3VlanIpV6RsSend OBJECT-TYPE
   SYNTAX      INTEGER
               {
               disabled (0),
               enabled (1)
               }
   MAX-ACCESS  read-write
   STATUS      current
   DESCRIPTION
      "Path: ethernet3.editConf.vlan.ipV6.rs.send

       Possibilities:
               disabled   (0)
               enabled   (1)"
   ::= {er1645v2Lan3VlanEntry 705954048}

er1645v2Lan3VlanIpV6RsMaxRandomDelay OBJECT-TYPE
   SYNTAX      TimeTicks
   MAX-ACCESS  read-write
   STATUS      current
   DESCRIPTION
      "Path: ethernet3.editConf.vlan.ipV6.rs.maxRandomDelay

       Time in centi-second."
   ::= {er1645v2Lan3VlanEntry 705954304}

er1645v2Lan3VlanIpV6RsInterval OBJECT-TYPE
   SYNTAX      TimeTicks
   MAX-ACCESS  read-write
   STATUS      current
   DESCRIPTION
      "Path: ethernet3.editConf.vlan.ipV6.rs.interval

       Time in centi-second."
   ::= {er1645v2Lan3VlanEntry 705954560}

er1645v2Lan3VlanIpV6RsMaxSolicitations OBJECT-TYPE
   SYNTAX      Integer32
   MAX-ACCESS  read-write
   STATUS      current
   DESCRIPTION
      "Path: ethernet3.editConf.vlan.ipV6.rs.maxSolicitations"
   ::= {er1645v2Lan3VlanEntry 705954816}

er1645v2Lan3VlanIpV6TrafficPolicyInbound OBJECT-TYPE
   SYNTAX      DisplayString
   MAX-ACCESS  read-write
   STATUS      current
   DESCRIPTION
      "Path: ethernet3.editConf.vlan.ipV6.trafficPolicy.inbound"
   ::= {er1645v2Lan3VlanEntry 705364224}

er1645v2Lan3VlanIpV6TrafficPolicyOutbound OBJECT-TYPE
   SYNTAX      DisplayString
   MAX-ACCESS  read-write
   STATUS      current
   DESCRIPTION
      "Path: ethernet3.editConf.vlan.ipV6.trafficPolicy.outbound"
   ::= {er1645v2Lan3VlanEntry 705364480}

er1645v2Lan3VlanIpV6FirewallZone OBJECT-TYPE
   SYNTAX      DisplayString
   MAX-ACCESS  read-write
   STATUS      current
   DESCRIPTION
      "Path: ethernet3.editConf.vlan.ipV6.firewall.zone"
   ::= {er1645v2Lan3VlanEntry 705429760}

er1645v2Lan3VlanIpV6DhcpClientAddrAC OBJECT-TYPE
   SYNTAX      INTEGER
               {
               disabled (0),
               enabled (1)
               }
   MAX-ACCESS  read-write
   STATUS      current
   DESCRIPTION
      "Path: ethernet3.editConf.vlan.ipV6.dhcp.client.addrAutoConfig

       Possibilities:
               disabled   (0)
               enabled   (1)"
   ::= {er1645v2Lan3VlanEntry 705307648}

er1645v2Lan3VlanIpV6DhcpClientPrDelMode OBJECT-TYPE
   SYNTAX      INTEGER
               {
               disabled (0),
               enabled (1)
               }
   MAX-ACCESS  read-write
   STATUS      current
   DESCRIPTION
      "Path: ethernet3.editConf.vlan.ipV6.dhcp.client.pd.mode

       Possibilities:
               disabled   (0)
               enabled   (1)"
   ::= {er1645v2Lan3VlanEntry 705308676}

er1645v2Lan3VlanIpV6DhcpClientPrDelPool OBJECT-TYPE
   SYNTAX      DisplayString
   MAX-ACCESS  read-write
   STATUS      current
   DESCRIPTION
      "Path: ethernet3.editConf.vlan.ipV6.dhcp.client.pd.pool"
   ::= {er1645v2Lan3VlanEntry 705308680}

er1645v2Lan3VlanIpV6DhcpClientPrDelPdExclOpt OBJECT-TYPE
   SYNTAX      INTEGER
               {
               disabled (0),
               enabled (1)
               }
   MAX-ACCESS  read-write
   STATUS      current
   DESCRIPTION
      "Path: ethernet3.editConf.vlan.ipV6.dhcp.client.pd.pdExclOpt

       Possibilities:
               disabled   (0)
               enabled   (1)"
   ::= {er1645v2Lan3VlanEntry 705308684}

er1645v2Lan3VlanIpV6DhcpClientDnsServerPref OBJECT-TYPE
   SYNTAX      Integer32
   MAX-ACCESS  read-write
   STATUS      current
   DESCRIPTION
      "Path: ethernet3.editConf.vlan.ipV6.dhcp.client.dns.serverPref"
   ::= {er1645v2Lan3VlanEntry 705310724}

er1645v2Lan3VlanIpV6DhcpClientRapidCommit OBJECT-TYPE
   SYNTAX      INTEGER
               {
               disabled (0),
               enabled (1)
               }
   MAX-ACCESS  read-write
   STATUS      current
   DESCRIPTION
      "Path: ethernet3.editConf.vlan.ipV6.dhcp.client.rapidCommit

       Possibilities:
               disabled   (0)
               enabled   (1)"
   ::= {er1645v2Lan3VlanEntry 705309696}

er1645v2Lan3VlanIpV6DhcpClientTimersSolTimeOut OBJECT-TYPE
   SYNTAX      TimeTicks
   MAX-ACCESS  read-write
   STATUS      current
   DESCRIPTION
      "Path: ethernet3.editConf.vlan.ipV6.dhcp.client.timers.solTimeOut

       Time in centi-second."
   ::= {er1645v2Lan3VlanEntry 705311748}

er1645v2Lan3VlanIpV6DhcpClientTimersSolMaxRt OBJECT-TYPE
   SYNTAX      TimeTicks
   MAX-ACCESS  read-write
   STATUS      current
   DESCRIPTION
      "Path: ethernet3.editConf.vlan.ipV6.dhcp.client.timers.solMaxRt

       Time in centi-second."
   ::= {er1645v2Lan3VlanEntry 705311752}

er1645v2Lan3VlanIpV6DhcpClientTimersInfoRefresh OBJECT-TYPE
   SYNTAX      TimeTicks
   MAX-ACCESS  read-write
   STATUS      current
   DESCRIPTION
      "Path: ethernet3.editConf.vlan.ipV6.dhcp.client.timers.infoRefresh

       Time in centi-second."
   ::= {er1645v2Lan3VlanEntry 705311756}

er1645v2Lan3VlanIpV6DhcpServerMode OBJECT-TYPE
   SYNTAX      INTEGER
               {
               disabled (0),
               enabled (1)
               }
   MAX-ACCESS  read-write
   STATUS      current
   DESCRIPTION
      "Path: ethernet3.editConf.vlan.ipV6.dhcp.server.mode

       Possibilities:
               disabled   (0)
               enabled   (1)"
   ::= {er1645v2Lan3VlanEntry 705315840}

er1645v2Lan3VlanIpV6DhcpServerPreference OBJECT-TYPE
   SYNTAX      Integer32
   MAX-ACCESS  read-write
   STATUS      current
   DESCRIPTION
      "Path: ethernet3.editConf.vlan.ipV6.dhcp.server.preference"
   ::= {er1645v2Lan3VlanEntry 705316864}

er1645v2Lan3VlanIpV6DhcpServerPool OBJECT-TYPE
   SYNTAX      DisplayString
   MAX-ACCESS  read-write
   STATUS      current
   DESCRIPTION
      "Path: ethernet3.editConf.vlan.ipV6.dhcp.server.pool"
   ::= {er1645v2Lan3VlanEntry 705317888}

er1645v2Lan3VlanIpV6DhcpServerRapidCommit OBJECT-TYPE
   SYNTAX      INTEGER
               {
               disabled (0),
               enabled (1)
               }
   MAX-ACCESS  read-write
   STATUS      current
   DESCRIPTION
      "Path: ethernet3.editConf.vlan.ipV6.dhcp.server.rapidCommit

       Possibilities:
               disabled   (0)
               enabled   (1)"
   ::= {er1645v2Lan3VlanEntry 705318912}

er1645v2Lan3VlanIpV6DhcpServerTimersInfoRefresh OBJECT-TYPE
   SYNTAX      TimeTicks
   MAX-ACCESS  read-write
   STATUS      current
   DESCRIPTION
      "Path: ethernet3.editConf.vlan.ipV6.dhcp.server.timers.infoRefresh

       Time in centi-second."
   ::= {er1645v2Lan3VlanEntry 705319940}

er1645v2Lan3VlanIpV6DhcpRelayMode OBJECT-TYPE
   SYNTAX      INTEGER
               {
               disabled (0),
               enabled (1)
               }
   MAX-ACCESS  read-write
   STATUS      current
   DESCRIPTION
      "Path: ethernet3.editConf.vlan.ipV6.dhcp.relay.mode

       Possibilities:
               disabled   (0)
               enabled   (1)"
   ::= {er1645v2Lan3VlanEntry 705323040}

er1645v2Lan3VlanIpV6SendRedirect OBJECT-TYPE
   SYNTAX      INTEGER
               {
               disabled (0),
               enabled (1)
               }
   MAX-ACCESS  read-write
   STATUS      current
   DESCRIPTION
      "Path: ethernet3.editConf.vlan.ipV6.sendRedirect

       Possibilities:
               disabled   (0)
               enabled   (1)"
   ::= {er1645v2Lan3VlanEntry 705101824}

er1645v2Lan3VlanIpV6LinkMtu OBJECT-TYPE
   SYNTAX      Integer32
   MAX-ACCESS  read-write
   STATUS      current
   DESCRIPTION
      "Path: ethernet3.editConf.vlan.ipV6.linkMtu"
   ::= {er1645v2Lan3VlanEntry 705167360}

er1645v2Lan3VlanIpV6InterfaceId OBJECT-TYPE
   SYNTAX      OCTET STRING
   MAX-ACCESS  read-write
   STATUS      current
   DESCRIPTION
      "Path: ethernet3.editConf.vlan.ipV6.interfaceId"
   ::= {er1645v2Lan3VlanEntry 705232896}

er1645v2Lan3VlanIpV6MF OBJECT-TYPE
   SYNTAX      Integer32
   MAX-ACCESS  read-write
   STATUS      current
   DESCRIPTION
      "Path: ethernet3.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3VlanEntry 705757184}

er1645v2Lan3VlanIpV6IcmpMessagesNoRoute OBJECT-TYPE
   SYNTAX      INTEGER
               {
               disabled (0),
               enabled (1)
               }
   MAX-ACCESS  read-write
   STATUS      current
   DESCRIPTION
      "Path: ethernet3.editConf.vlan.ipV6.icmpMessages.noRoute

       Possibilities:
               disabled   (0)
               enabled   (1)"
   ::= {er1645v2Lan3VlanEntry 705822976}

er1645v2Lan3VlanIpV6IcmpMessagesBeyondScope OBJECT-TYPE
   SYNTAX      INTEGER
               {
               disabled (0),
               enabled (1)
               }
   MAX-ACCESS  read-write
   STATUS      current
   DESCRIPTION
      "Path: ethernet3.editConf.vlan.ipV6.icmpMessages.beyondScope

       Possibilities:
               disabled   (0)
               enabled   (1)"
   ::= {er1645v2Lan3VlanEntry 705823488}

er1645v2Lan3VlanIpV6IcmpMessagesAddressUnreachable OBJECT-TYPE
   SYNTAX      INTEGER
               {
               disabled (0),
               enabled (1)
               }
   MAX-ACCESS  read-write
   STATUS      current
   DESCRIPTION
      "Path: ethernet3.editConf.vlan.ipV6.icmpMessages.addressUnreachable

       Possibilities:
               disabled   (0)
               enabled   (1)"
   ::= {er1645v2Lan3VlanEntry 705823744}

er1645v2Lan3VlanIpV6IcmpMessagesPortUnreachable OBJECT-TYPE
   SYNTAX      INTEGER
               {
               disabled (0),
               enabled (1)
               }
   MAX-ACCESS  read-write
   STATUS      current
   DESCRIPTION
      "Path: ethernet3.editConf.vlan.ipV6.icmpMessages.portUnreachable

       Possibilities:
               disabled   (0)
               enabled   (1)"
   ::= {er1645v2Lan3VlanEntry 705824000}

er1645v2Lan3VlanIpV6IcmpMessagesPacketTooBig OBJECT-TYPE
   SYNTAX      INTEGER
               {
               disabled (0),
               enabled (1)
               }
   MAX-ACCESS  read-write
   STATUS      current
   DESCRIPTION
      "Path: ethernet3.editConf.vlan.ipV6.icmpMessages.packetTooBig

       Possibilities:
               disabled   (0)
               enabled   (1)"
   ::= {er1645v2Lan3VlanEntry 705825280}

er1645v2Lan3VlanIpV6IcmpMessagesHopLimitExceeded OBJECT-TYPE
   SYNTAX      INTEGER
               {
               disabled (0),
               enabled (1)
               }
   MAX-ACCESS  read-write
   STATUS      current
   DESCRIPTION
      "Path: ethernet3.editConf.vlan.ipV6.icmpMessages.hopLimitExceeded

       Possibilities:
               disabled   (0)
               enabled   (1)"
   ::= {er1645v2Lan3VlanEntry 705827840}

er1645v2Lan3VlanIpV6IcmpMessagesFragTimeExceeded OBJECT-TYPE
   SYNTAX      INTEGER
               {
               disabled (0),
               enabled (1)
               }
   MAX-ACCESS  read-write
   STATUS      current
   DESCRIPTION
      "Path: ethernet3.editConf.vlan.ipV6.icmpMessages.fragTimeExceeded

       Possibilities:
               disabled   (0)
               enabled   (1)"
   ::= {er1645v2Lan3VlanEntry 705828096}

er1645v2Lan3VlanIpV6IcmpMessagesHeaderFieldErr OBJECT-TYPE
   SYNTAX      INTEGER
               {
               disabled (0),
               enabled (1)
               }
   MAX-ACCESS  read-write
   STATUS      current
   DESCRIPTION
      "Path: ethernet3.editConf.vlan.ipV6.icmpMessages.headerFieldErr

       Possibilities:
               disabled   (0)
               enabled   (1)"
   ::= {er1645v2Lan3VlanEntry 705830400}

er1645v2Lan3VlanIpV6IcmpMessagesOptionUnrecognized OBJECT-TYPE
   SYNTAX      INTEGER
               {
               disabled (0),
               enabled (1)
               }
   MAX-ACCESS  read-write
   STATUS      current
   DESCRIPTION
      "Path: ethernet3.editConf.vlan.ipV6.icmpMessages.optionUnrecognized

       Possibilities:
               disabled   (0)
               enabled   (1)"
   ::= {er1645v2Lan3VlanEntry 705830912}

er1645v2Lan3VlanIpV6IcmpMessagesRedirect OBJECT-TYPE
   SYNTAX      INTEGER
               {
               disabled (0),
               enabled (1)
               }
   MAX-ACCESS  read-write
   STATUS      current
   DESCRIPTION
      "Path: ethernet3.editConf.vlan.ipV6.icmpMessages.redirect

       Possibilities:
               disabled   (0)
               enabled   (1)"
   ::= {er1645v2Lan3VlanEntry 705832960}

er1645v2Lan3VlanBridgingAccList OBJECT-TYPE
   SYNTAX      DisplayString
   MAX-ACCESS  read-write
   STATUS      current
   DESCRIPTION
      "Path: ethernet3.editConf.vlan.bridging.accessList"
   ::= {er1645v2Lan3VlanEntry 453246976}

er1645v2Lan3VlanBridgingInACL OBJECT-TYPE
   SYNTAX      DisplayString
   MAX-ACCESS  read-write
   STATUS      current
   DESCRIPTION
      "Path: ethernet3.editConf.vlan.bridging.inAccessList"
   ::= {er1645v2Lan3VlanEntry 456916992}

er1645v2Lan3VlanBridgingTp OBJECT-TYPE
   SYNTAX      DisplayString
   MAX-ACCESS  read-write
   STATUS      current
   DESCRIPTION
      "Path: ethernet3.editConf.vlan.bridging.trafficPolicy"
   ::= {er1645v2Lan3VlanEntry 454295552}

er1645v2Lan3VlanBridgingBrGrp OBJECT-TYPE
   SYNTAX      DisplayString
   MAX-ACCESS  read-write
   STATUS      current
   DESCRIPTION
      "Path: ethernet3.editConf.vlan.bridging.bridgeGroup"
   ::= {er1645v2Lan3VlanEntry 454819840}

er1645v2Lan3VlanBridgingLimBC OBJECT-TYPE
   SYNTAX      INTEGER
               {
               disabled (0),
               enabled (1)
               }
   MAX-ACCESS  read-write
   STATUS      current
   DESCRIPTION
      "Path: ethernet3.editConf.vlan.bridging.limitBroadcasts

       Possibilities:
               disabled   (0)
               enabled   (1)"
   ::= {er1645v2Lan3VlanEntry 455081984}

er1645v2Lan3VlanBridgingPrivateMode OBJECT-TYPE
   SYNTAX      INTEGER
               {
               disabled (0),
               enabled (1)
               }
   MAX-ACCESS  read-write
   STATUS      current
   DESCRIPTION
      "Path: ethernet3.editConf.vlan.bridging.privateMode

       Possibilities:
               disabled   (0)
               enabled   (1)"
   ::= {er1645v2Lan3VlanEntry 459538432}

er1645v2Lan3VlanBridgingLearning OBJECT-TYPE
   SYNTAX      INTEGER
               {
               disabled (0),
               enabled (1)
               }
   MAX-ACCESS  read-write
   STATUS      current
   DESCRIPTION
      "Path: ethernet3.editConf.vlan.bridging.learning

       Possibilities:
               disabled   (0)
               enabled   (1)"
   ::= {er1645v2Lan3VlanEntry 456130560}

er1645v2Lan3VlanBridgingMaxCacheSize OBJECT-TYPE
   SYNTAX      INTEGER
               {
               unlimited (0)
               }
   MAX-ACCESS  read-write
   STATUS      current
   DESCRIPTION
      "Path: ethernet3.editConf.vlan.bridging.maxCacheSize

       Possibilities:
               unlimited   (0)"
   ::= {er1645v2Lan3VlanEntry 456392704}

er1645v2Lan3VlanBridgingRelearnDropOnRelearn OBJECT-TYPE
   SYNTAX      INTEGER
               {
               disabled (0),
               enabled (1)
               }
   MAX-ACCESS  read-write
   STATUS      current
   DESCRIPTION
      "Path: ethernet3.editConf.vlan.bridging.relearn.dropOnRelearn

       Possibilities:
               disabled   (0)
               enabled   (1)"
   ::= {er1645v2Lan3VlanEntry 456655872}

er1645v2Lan3VlanBridgingRelearnShutdownThreshold OBJECT-TYPE
   SYNTAX      Integer32
   MAX-ACCESS  read-write
   STATUS      current
   DESCRIPTION
      "Path: ethernet3.editConf.vlan.bridging.relearn.shutdownThreshold"
   ::= {er1645v2Lan3VlanEntry 456656896}

er1645v2Lan3VlanBridgingRelearnShutdownTime OBJECT-TYPE
   SYNTAX      TimeTicks
   MAX-ACCESS  read-write
   STATUS      current
   DESCRIPTION
      "Path: ethernet3.editConf.vlan.bridging.relearn.shutdownTime

       Time in centi-second."
   ::= {er1645v2Lan3VlanEntry 456657920}

er1645v2Lan3VlanBridgingRelearnLoopDetection OBJECT-TYPE
   SYNTAX      INTEGER
               {
               disabled (0),
               passive (1),
               active (2)
               }
   MAX-ACCESS  read-write
   STATUS      current
   DESCRIPTION
      "Path: ethernet3.editConf.vlan.bridging.relearn.loopDetection

       Possibilities:
               disabled   (0)
               passive   (1)
               active   (2)"
   ::= {er1645v2Lan3VlanEntry 456658944}

er1645v2Lan3VlanBridgingRelearnLoopDetectionInterval OBJECT-TYPE
   SYNTAX      TimeTicks
   MAX-ACCESS  read-write
   STATUS      current
   DESCRIPTION
      "Path: ethernet3.editConf.vlan.bridging.relearn.loopDetectionInterval

       Time in centi-second."
   ::= {er1645v2Lan3VlanEntry 456659968}

er1645v2Lan3VlanBridgingVlanMemberShip OBJECT-TYPE
   SYNTAX      INTEGER
               {
               all (0),
               none (1),
               grouped (2)
               }
   MAX-ACCESS  read-write
   STATUS      current
   DESCRIPTION
      "Path: ethernet3.editConf.vlan.bridging.vlanMemberShip

       Possibilities:
               all   (0)
               none   (1)
               grouped   (2)"
   ::= {er1645v2Lan3VlanEntry 457965568}

er1645v2Lan3VlanBridgingVlTUntaggedAction OBJECT-TYPE
   SYNTAX      INTEGER
               {
               discard (0),
               accept (1),
               tag (2)
               }
   MAX-ACCESS  read-write
   STATUS      current
   DESCRIPTION
      "Path: ethernet3.editConf.vlan.bridging.vlanTagging.untagged.action

       Possibilities:
               discard   (0)
               accept   (1)
               tag   (2)"
   ::= {er1645v2Lan3VlanEntry 459055104}

er1645v2Lan3VlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.untagged.tagInfo.tpid

       Possibilities:
               dot1Q   (33024)
               dot1ad   (34984)
               0x9100   (37120)
               0x9200   (37376)
               0x9300   (37632)"
   ::= {er1645v2Lan3VlanEntry 459059712}

er1645v2Lan3VlanBridgingVlTUntaggedTagInfoVid OBJECT-TYPE
   SYNTAX      Integer32
   MAX-ACCESS  read-write
   STATUS      current
   DESCRIPTION
      "Path: ethernet3.editConf.vlan.bridging.vlanTagging.untagged.tagInfo.vid"
   ::= {er1645v2Lan3VlanEntry 459060224}

er1645v2Lan3VlanBridgingVlTUnknownVlansAction OBJECT-TYPE
   SYNTAX      INTEGER
               {
               discard (0),
               accept (1),
               tag (2)
               }
   MAX-ACCESS  read-write
   STATUS      current
   DESCRIPTION
      "Path: ethernet3.editConf.vlan.bridging.vlanTagging.unknownVlans.action

       Possibilities:
               discard   (0)
               accept   (1)
               tag   (2)"
   ::= {er1645v2Lan3VlanEntry 459120640}

er1645v2Lan3VlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.unknownVlans.tagInfo.tpid

       Possibilities:
               dot1Q   (33024)
               dot1ad   (34984)
               0x9100   (37120)
               0x9200   (37376)
               0x9300   (37632)"
   ::= {er1645v2Lan3VlanEntry 459125248}

er1645v2Lan3VlanBridgingVlTUnknownVlansTagInfoVid OBJECT-TYPE
   SYNTAX      Integer32
   MAX-ACCESS  read-write
   STATUS      current
   DESCRIPTION
      "Path: ethernet3.editConf.vlan.bridging.vlanTagging.unknownVlans.tagInfo.vid"
   ::= {er1645v2Lan3VlanEntry 459125760}

er1645v2Lan3VlanBridgingDot1adType OBJECT-TYPE
   SYNTAX      INTEGER
               {
               slOPTg (0),
               cPort (4),
               sPort (1),
               nni (2)
               }
   MAX-ACCESS  read-write
   STATUS      current
   DESCRIPTION
      "Path: ethernet3.editConf.vlan.bridging.dot1ad.type

       Possibilities:
               <OPT>   (0)
               cPort   (4)
               sPort   (1)
               nni   (2)"
   ::= {er1645v2Lan3VlanEntry 460850176}

er1645v2Lan3VlanBridgingPriority OBJECT-TYPE
   SYNTAX      Integer32
   MAX-ACCESS  read-write
   STATUS      current
   DESCRIPTION
      "Path: ethernet3.editConf.vlan.bridging.priority"
   ::= {er1645v2Lan3VlanEntry 453509120}

er1645v2Lan3VlanBridgingPathCost OBJECT-TYPE
   SYNTAX      Integer32
   MAX-ACCESS  read-write
   STATUS      current
   DESCRIPTION
      "Path: ethernet3.editConf.vlan.bridging.pathCost"
   ::= {er1645v2Lan3VlanEntry 453771264}

er1645v2Lan3VlanBridgingInternalPathCost OBJECT-TYPE
   SYNTAX      Integer32
   MAX-ACCESS  read-write
   STATUS      current
   DESCRIPTION
      "Path: ethernet3.editConf.vlan.bridging.internalPathCost"
   ::= {er1645v2Lan3VlanEntry 457703424}

er1645v2Lan3VlanBridgingTCD OBJECT-TYPE
   SYNTAX      INTEGER
               {
               disabled (0),
               enabled (1)
               }
   MAX-ACCESS  read-write
   STATUS      current
   DESCRIPTION
      "Path: ethernet3.editConf.vlan.bridging.topologyChangeDetection

       Possibilities:
               disabled   (0)
               enabled   (1)"
   ::= {er1645v2Lan3VlanEntry 454033408}

er1645v2Lan3VlanBridgingRestrictedRole OBJECT-TYPE
   SYNTAX      INTEGER
               {
               disabled (0),
               enabled (1)
               }
   MAX-ACCESS  read-write
   STATUS      current
   DESCRIPTION
      "Path: ethernet3.editConf.vlan.bridging.restrictedRole

       Possibilities:
               disabled   (0)
               enabled   (1)"
   ::= {er1645v2Lan3VlanEntry 458227712}

er1645v2Lan3VlanBridgingAdminEdge OBJECT-TYPE
   SYNTAX      INTEGER
               {
               disabled (0),
               enabled (1)
               }
   MAX-ACCESS  read-write
   STATUS      current
   DESCRIPTION
      "Path: ethernet3.editConf.vlan.bridging.adminEdge

       Possibilities:
               disabled   (0)
               enabled   (1)"
   ::= {er1645v2Lan3VlanEntry 457179136}

er1645v2Lan3VlanBridgingOamMacDeviceMac OBJECT-TYPE
   SYNTAX      DisplayString
   MAX-ACCESS  read-write
   STATUS      current
   DESCRIPTION
      "Path: ethernet3.editConf.vlan.bridging.ethOam.macAddress.deviceMac"
   ::= {er1645v2Lan3VlanEntry 458506496}

er1645v2Lan3VlanBridgingOamMacUserMac OBJECT-TYPE
   SYNTAX      OCTET STRING
   MAX-ACCESS  read-write
   STATUS      current
   DESCRIPTION
      "Path: ethernet3.editConf.vlan.bridging.ethOam.macAddress.userMac

       MAC address."
   ::= {er1645v2Lan3VlanEntry 458506368}

er1645v2Lan3VlanBridgingOamMacBridgeMac OBJECT-TYPE
   SYNTAX      DisplayString
   MAX-ACCESS  read-write
   STATUS      current
   DESCRIPTION
      "Path: ethernet3.editConf.vlan.bridging.ethOam.macAddress.bridgeMac"
   ::= {er1645v2Lan3VlanEntry 458506432}

er1645v2Lan3VlanBridgingMgmtInline OBJECT-TYPE
   SYNTAX      INTEGER
               {
               disabled (0),
               enabled (1)
               }
   MAX-ACCESS  read-write
   STATUS      current
   DESCRIPTION
      "Path: ethernet3.editConf.vlan.bridging.mgmtInline

       Possibilities:
               disabled   (0)
               enabled   (1)"
   ::= {er1645v2Lan3VlanEntry 458752000}

er1645v2Lan3VlanBridgingL2ptMode OBJECT-TYPE
   SYNTAX      INTEGER
               {
               disabled (0),
               enabled (1)
               }
   MAX-ACCESS  read-write
   STATUS      current
   DESCRIPTION
      "Path: ethernet3.editConf.vlan.bridging.l2ProtTunnel.mode

       Possibilities:
               disabled   (0)
               enabled   (1)"
   ::= {er1645v2Lan3VlanEntry 459292672}

er1645v2Lan3VlanBridgingL2ptProtocols OBJECT-TYPE
   SYNTAX      Integer32
   MAX-ACCESS  read-write
   STATUS      current
   DESCRIPTION
      "Path: ethernet3.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan3VlanEntry 459309056}

er1645v2Lan3VlanBridgingL2ptDestMac OBJECT-TYPE
   SYNTAX      OCTET STRING
   MAX-ACCESS  read-write
   STATUS      current
   DESCRIPTION
      "Path: ethernet3.editConf.vlan.bridging.l2ProtTunnel.destinationMac

       MAC address."
   ::= {er1645v2Lan3VlanEntry 459325440}

er1645v2Lan3VlanBridgingL2ptCos OBJECT-TYPE
   SYNTAX      INTEGER
               {
               unchanged (255)
               }
   MAX-ACCESS  read-write
   STATUS      current
   DESCRIPTION
      "Path: ethernet3.editConf.vlan.bridging.l2ProtTunnel.cos

       Possibilities:
               unchanged   (255)"
   ::= {er1645v2Lan3VlanEntry 459341824}

er1645v2Lan3VlanBridgingL2ptDropThrStp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.stp

       unit name = packets/sec

       Possibilities:
               unlimited   (0)"
   ::= {er1645v2Lan3VlanEntry 459358272}

er1645v2Lan3VlanBridgingL2ptDropThrLldp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lldp

       unit name = packets/sec

       Possibilities:
               unlimited   (0)"
   ::= {er1645v2Lan3VlanEntry 459358336}

er1645v2Lan3VlanBridgingL2ptDropThrOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.oam

       unit name = packets/sec

       Possibilities:
               unlimited   (0)"
   ::= {er1645v2Lan3VlanEntry 459358400}

er1645v2Lan3VlanBridgingL2ptDropThrCdp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.cdp

       unit name = packets/sec

       Possibilities:
               unlimited   (0)"
   ::= {er1645v2Lan3VlanEntry 459358464}

er1645v2Lan3VlanBridgingL2ptDropThrVtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.vtp

       unit name = packets/sec

       Possibilities:
               unlimited   (0)"
   ::= {er1645v2Lan3VlanEntry 459358528}

er1645v2Lan3VlanBridgingL2ptDropThrLacp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lacp

       unit name = packets/sec

       Possibilities:
               unlimited   (0)"
   ::= {er1645v2Lan3VlanEntry 459358592}

er1645v2Lan3VlanBridgingL2ptDropThrEfmOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.efmOam

       unit name = packets/sec

       Possibilities:
               unlimited   (0)"
   ::= {er1645v2Lan3VlanEntry 459358656}

er1645v2Lan3VlanBridgingL2ptDropThrPvst OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pvst

       unit name = packets/sec

       Possibilities:
               unlimited   (0)"
   ::= {er1645v2Lan3VlanEntry 459358720}

er1645v2Lan3VlanBridgingL2ptDropThrMmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mmrp

       unit name = packets/sec

       Possibilities:
               unlimited   (0)"
   ::= {er1645v2Lan3VlanEntry 459358784}

er1645v2Lan3VlanBridgingL2ptDropThrMvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mvrp

       unit name = packets/sec

       Possibilities:
               unlimited   (0)"
   ::= {er1645v2Lan3VlanEntry 459358848}

er1645v2Lan3VlanBridgingL2ptDropThrGvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gvrp

       unit name = packets/sec

       Possibilities:
               unlimited   (0)"
   ::= {er1645v2Lan3VlanEntry 459358912}

er1645v2Lan3VlanBridgingL2ptDropThrGmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gmrp

       unit name = packets/sec

       Possibilities:
               unlimited   (0)"
   ::= {er1645v2Lan3VlanEntry 459358976}

er1645v2Lan3VlanBridgingL2ptDropThrDtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.dtp

       unit name = packets/sec

       Possibilities:
               unlimited   (0)"
   ::= {er1645v2Lan3VlanEntry 459359040}

er1645v2Lan3VlanBridgingL2ptDropThrPagp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pagp

       unit name = packets/sec

       Possibilities:
               unlimited   (0)"
   ::= {er1645v2Lan3VlanEntry 459359104}

er1645v2Lan3VlanBridgingL2ptDropThrUdld OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.udld

       unit name = packets/sec

       Possibilities:
               unlimited   (0)"
   ::= {er1645v2Lan3VlanEntry 459359168}

er1645v2Lan3VlanVlanVid OBJECT-TYPE
   SYNTAX      INTEGER
               {
               untagged (0),
               prioTagged (4096),
               notUsed (4097)
               }
   MAX-ACCESS  read-write
   STATUS      current
   DESCRIPTION
      "Path: ethernet3.editConf.vlan.vlan.vid

       Possibilities:
               untagged   (0)
               prioTagged   (4096)
               notUsed   (4097)"
   ::= {er1645v2Lan3VlanEntry 234946560}

er1645v2Lan3VlanVlanVidExtensionSingle OBJECT-TYPE
   SYNTAX      OCTET STRING
   MAX-ACCESS  read-write
   STATUS      current
   DESCRIPTION
      "Path: ethernet3.editConf.vlan.vlan.vidExtension.single"
   ::= {er1645v2Lan3VlanEntry 235340032}

er1645v2Lan3VlanVlanVidExtensionEndVid OBJECT-TYPE
   SYNTAX      Integer32
   MAX-ACCESS  read-write
   STATUS      current
   DESCRIPTION
      "Path: ethernet3.editConf.vlan.vlan.vidExtension.endVid"
   ::= {er1645v2Lan3VlanEntry 235340288}

er1645v2Lan3VlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tpid

       Possibilities:
               dot1Q   (33024)
               dot1ad   (34984)
               0x9100   (37120)
               0x9200   (37376)
               0x9300   (37632)"
   ::= {er1645v2Lan3VlanEntry 241238016}

er1645v2Lan3VlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet3.editConf.vlan.vlan.tagSignificance

       Possibilities:
               global   (0)
               local   (1)
               sVlan   (2)
               sVlanGlobal   (6)
               cVlan   (3)
               scVlan   (5)
               cVlanLocal   (4)"
   ::= {er1645v2Lan3VlanEntry 235012096}

er1645v2Lan3VlanVlanChTos OBJECT-TYPE
   SYNTAX      INTEGER
               {
               disabled (0),
               enabled (1)
               }
   MAX-ACCESS  read-write
   STATUS      current
   DESCRIPTION
      "Path: ethernet3.editConf.vlan.vlan.changeTos

       Possibilities:
               disabled   (0)
               enabled   (1)"
   ::= {er1645v2Lan3VlanEntry 235208704}

er1645v2Lan3VlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235143424}

er1645v2Lan3VlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235143680}

er1645v2Lan3VlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235143936}

er1645v2Lan3VlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235144192}

er1645v2Lan3VlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235144448}

er1645v2Lan3VlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235144704}

er1645v2Lan3VlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235144960}

er1645v2Lan3VlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3VlanEntry 235145216}

er1645v2Lan3VlanVlanTxCos OBJECT-TYPE
   SYNTAX      INTEGER
               {
               tosCosMap (8),
               queueCosMap (16)
               }
   MAX-ACCESS  read-write
   STATUS      current
   DESCRIPTION
      "Path: ethernet3.editConf.vlan.vlan.txCos

       Possibilities:
               tosCosMap   (8)
               queueCosMap   (16)"
   ::= {er1645v2Lan3VlanEntry 235077632}

er1645v2Lan3VlanVlanCCMapP0 OBJECT-TYPE
   SYNTAX      Integer32
   MAX-ACCESS  read-write
   STATUS      current
   DESCRIPTION
      "Path: ethernet3.editConf.vlan.vlan.cosCosMap.p0"
   ::= {er1645v2Lan3VlanEntry 241303808}

er1645v2Lan3VlanVlanCCMapP1 OBJECT-TYPE
   SYNTAX      Integer32
   MAX-ACCESS  read-write
   STATUS      current
   DESCRIPTION
      "Path: ethernet3.editConf.vlan.vlan.cosCosMap.p1"
   ::= {er1645v2Lan3VlanEntry 241304064}

er1645v2Lan3VlanVlanCCMapP2 OBJECT-TYPE
   SYNTAX      Integer32
   MAX-ACCESS  read-write
   STATUS      current
   DESCRIPTION
      "Path: ethernet3.editConf.vlan.vlan.cosCosMap.p2"
   ::= {er1645v2Lan3VlanEntry 241304320}

er1645v2Lan3VlanVlanCCMapP3 OBJECT-TYPE
   SYNTAX      Integer32
   MAX-ACCESS  read-write
   STATUS      current
   DESCRIPTION
      "Path: ethernet3.editConf.vlan.vlan.cosCosMap.p3"
   ::= {er1645v2Lan3VlanEntry 241304576}

er1645v2Lan3VlanVlanCCMapP4 OBJECT-TYPE
   SYNTAX      Integer32
   MAX-ACCESS  read-write
   STATUS      current
   DESCRIPTION
      "Path: ethernet3.editConf.vlan.vlan.cosCosMap.p4"
   ::= {er1645v2Lan3VlanEntry 241304832}

er1645v2Lan3VlanVlanCCMapP5 OBJECT-TYPE
   SYNTAX      Integer32
   MAX-ACCESS  read-write
   STATUS      current
   DESCRIPTION
      "Path: ethernet3.editConf.vlan.vlan.cosCosMap.p5"
   ::= {er1645v2Lan3VlanEntry 241305088}

er1645v2Lan3VlanVlanCCMapP6 OBJECT-TYPE
   SYNTAX      Integer32
   MAX-ACCESS  read-write
   STATUS      current
   DESCRIPTION
      "Path: ethernet3.editConf.vlan.vlan.cosCosMap.p6"
   ::= {er1645v2Lan3VlanEntry 241305344}

er1645v2Lan3VlanVlanCCMapP7 OBJECT-TYPE
   SYNTAX      Integer32
   MAX-ACCESS  read-write
   STATUS      current
   DESCRIPTION
      "Path: ethernet3.editConf.vlan.vlan.cosCosMap.p7"
   ::= {er1645v2Lan3VlanEntry 241305600}

er1645v2Lan3VlanVlanQCMapQueue1 OBJECT-TYPE
   SYNTAX      Integer32
   MAX-ACCESS  read-write
   STATUS      current
   DESCRIPTION
      "Path: ethernet3.editConf.vlan.vlan.queueCosMap.queue1"
   ::= {er1645v2Lan3VlanEntry 241434880}

er1645v2Lan3VlanVlanQCMapQueue2 OBJECT-TYPE
   SYNTAX      Integer32
   MAX-ACCESS  read-write
   STATUS      current
   DESCRIPTION
      "Path: ethernet3.editConf.vlan.vlan.queueCosMap.queue2"
   ::= {er1645v2Lan3VlanEntry 241435136}

er1645v2Lan3VlanVlanQCMapQueue3 OBJECT-TYPE
   SYNTAX      Integer32
   MAX-ACCESS  read-write
   STATUS      current
   DESCRIPTION
      "Path: ethernet3.editConf.vlan.vlan.queueCosMap.queue3"
   ::= {er1645v2Lan3VlanEntry 241435392}

er1645v2Lan3VlanVlanQCMapQueue4 OBJECT-TYPE
   SYNTAX      Integer32
   MAX-ACCESS  read-write
   STATUS      current
   DESCRIPTION
      "Path: ethernet3.editConf.vlan.vlan.queueCosMap.queue4"
   ::= {er1645v2Lan3VlanEntry 241435648}

er1645v2Lan3VlanVlanQCMapQueue5 OBJECT-TYPE
   SYNTAX      Integer32
   MAX-ACCESS  read-write
   STATUS      current
   DESCRIPTION
      "Path: ethernet3.editConf.vlan.vlan.queueCosMap.queue5"
   ::= {er1645v2Lan3VlanEntry 241435904}

er1645v2Lan3VlanVlanQCMapLowDelayQueue OBJECT-TYPE
   SYNTAX      Integer32
   MAX-ACCESS  read-write
   STATUS      current
   DESCRIPTION
      "Path: ethernet3.editConf.vlan.vlan.queueCosMap.lowDelayQueue"
   ::= {er1645v2Lan3VlanEntry 241436160}

er1645v2Lan3VlanVlanQCMapLowDelay2Queue OBJECT-TYPE
   SYNTAX      Integer32
   MAX-ACCESS  read-write
   STATUS      current
   DESCRIPTION
      "Path: ethernet3.editConf.vlan.vlan.queueCosMap.lowDelay2Queue"
   ::= {er1645v2Lan3VlanEntry 241436416}

er1645v2Lan3VlanVlanQCMapSystemQueue OBJECT-TYPE
   SYNTAX      Integer32
   MAX-ACCESS  read-write
   STATUS      current
   DESCRIPTION
      "Path: ethernet3.editConf.vlan.vlan.queueCosMap.systemQueue"
   ::= {er1645v2Lan3VlanEntry 241436672}

er1645v2Lan3VlanVlanQinQSVid OBJECT-TYPE
   SYNTAX      Integer32
   MAX-ACCESS  read-write
   STATUS      current
   DESCRIPTION
      "Path: ethernet3.editConf.vlan.vlan.tunnel.sVid"
   ::= {er1645v2Lan3VlanEntry 241172736}

er1645v2Lan3VlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tunnel.sTpid

       Possibilities:
               dot1Q   (33024)
               dot1ad   (34984)
               0x9100   (37120)
               0x9200   (37376)
               0x9300   (37632)"
   ::= {er1645v2Lan3VlanEntry 241172992}

er1645v2Lan3VlanVlanArpTimeOut OBJECT-TYPE
   SYNTAX      TimeTicks
   MAX-ACCESS  read-write
   STATUS      current
   DESCRIPTION
      "Path: ethernet3.editConf.vlan.vlan.arp.timeOut

       Time in centi-second."
   ::= {er1645v2Lan3VlanEntry 235277312}

er1645v2Lan3VlanVlanArpProxyArp OBJECT-TYPE
   SYNTAX      INTEGER
               {
               disabled (0),
               enabled (1)
               }
   MAX-ACCESS  read-write
   STATUS      current
   DESCRIPTION
      "Path: ethernet3.editConf.vlan.vlan.arp.proxyArp

       Possibilities:
               disabled   (0)
               enabled   (1)"
   ::= {er1645v2Lan3VlanEntry 235287040}

er1645v2Lan3VlanBandwidthMode OBJECT-TYPE
   SYNTAX      INTEGER
               {
               reshaping (1),
               policing (2),
               policingReshape (3)
               }
   MAX-ACCESS  read-write
   STATUS      current
   DESCRIPTION
      "Path: ethernet3.editConf.vlan.bandwidth.mode

       Possibilities:
               reshaping   (1)
               policing   (2)
               policingReshape   (3)"
   ::= {er1645v2Lan3VlanEntry 148897792}

er1645v2Lan3VlanBandwidthCir OBJECT-TYPE
   SYNTAX      Integer32
   MAX-ACCESS  read-write
   STATUS      current
   DESCRIPTION
      "Path: ethernet3.editConf.vlan.bandwidth.cir"
   ::= {er1645v2Lan3VlanEntry 135266304}

er1645v2Lan3VlanBandwidthEir OBJECT-TYPE
   SYNTAX      Integer32
   MAX-ACCESS  read-write
   STATUS      current
   DESCRIPTION
      "Path: ethernet3.editConf.vlan.bandwidth.eir"
   ::= {er1645v2Lan3VlanEntry 141557760}

er1645v2Lan3VlanBandwidthUnit OBJECT-TYPE
   SYNTAX      INTEGER
               {
               bitssec (1),
               percent (2)
               }
   MAX-ACCESS  read-write
   STATUS      current
   DESCRIPTION
      "Path: ethernet3.editConf.vlan.bandwidth.unit

       Possibilities:
               bits/sec   (1)
               percent   (2)"
   ::= {er1645v2Lan3VlanEntry 139460608}

er1645v2Lan3VlanBandwidthTc OBJECT-TYPE
   SYNTAX      INTEGER
               {
               auto (0)
               }
   MAX-ACCESS  read-write
   STATUS      current
   DESCRIPTION
      "Path: ethernet3.editConf.vlan.bandwidth.tc

       Possibilities:
               auto   (0)"
   ::= {er1645v2Lan3VlanEntry 140509184}

er1645v2Lan3VlanBandwidthTcFactor OBJECT-TYPE
   SYNTAX      INTEGER
               {
               ms (10),
               s100us (1)
               }
   MAX-ACCESS  read-write
   STATUS      current
   DESCRIPTION
      "Path: ethernet3.editConf.vlan.bandwidth.tcFactor

       Possibilities:
               ms   (10)
               *100us   (1)"
   ::= {er1645v2Lan3VlanEntry 142606336}

er1645v2Lan3VlanBandwidthCorrType OBJECT-TYPE
   SYNTAX      INTEGER
               {
               noCorrection (0),
               predefined (1),
               manual (2)
               }
   MAX-ACCESS  read-write
   STATUS      current
   DESCRIPTION
      "Path: ethernet3.editConf.vlan.bandwidth.correction.type

       Possibilities:
               noCorrection   (0)
               predefined   (1)
               manual   (2)"
   ::= {er1645v2Lan3VlanEntry 136445952}

er1645v2Lan3VlanBandwidthCorrPredefEncapsFrameRelay OBJECT-TYPE
   SYNTAX      DisplayString
   MAX-ACCESS  read-write
   STATUS      current
   DESCRIPTION
      "Path: ethernet3.editConf.vlan.bandwidth.correction.predefined.encapsulation.frameRelay"
   ::= {er1645v2Lan3VlanEntry 136594432}

er1645v2Lan3VlanBandwidthCorrPredefEncapsPpp OBJECT-TYPE
   SYNTAX      DisplayString
   MAX-ACCESS  read-write
   STATUS      current
   DESCRIPTION
      "Path: ethernet3.editConf.vlan.bandwidth.correction.predefined.encapsulation.ppp"
   ::= {er1645v2Lan3VlanEntry 136595456}

er1645v2Lan3VlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.bandwidth.correction.predefined.encapsulation.atm.higherLayer

       Possibilities:
               rfc2684   (0)
               ppp   (1)
               pppOverEthernet   (2)"
   ::= {er1645v2Lan3VlanEntry 136596608}

er1645v2Lan3VlanBandwidthCorrPredefEncapsAtmMp OBJECT-TYPE
   SYNTAX      INTEGER
               {
               llcEncapsulation (0),
               vcMultiplexing (1)
               }
   MAX-ACCESS  read-write
   STATUS      current
   DESCRIPTION
      "Path: ethernet3.editConf.vlan.bandwidth.correction.predefined.encapsulation.atm.multiProtocol

       Possibilities:
               llcEncapsulation   (0)
               vcMultiplexing   (1)"
   ::= {er1645v2Lan3VlanEntry 136596736}

er1645v2Lan3VlanBandwidthCorrPredefEncapsHdlc OBJECT-TYPE
   SYNTAX      DisplayString
   MAX-ACCESS  read-write
   STATUS      current
   DESCRIPTION
      "Path: ethernet3.editConf.vlan.bandwidth.correction.predefined.encapsulation.hdlc"
   ::= {er1645v2Lan3VlanEntry 136597504}

er1645v2Lan3VlanBandwidthCorrPredefEncapsEfmFs OBJECT-TYPE
   SYNTAX      Integer32
   MAX-ACCESS  read-write
   STATUS      current
   DESCRIPTION
      "Path: ethernet3.editConf.vlan.bandwidth.correction.predefined.encapsulation.efm.fragmentSize"
   ::= {er1645v2Lan3VlanEntry 136598656}

er1645v2Lan3VlanBandwidthCorrPredefEncapsEfmIb OBJECT-TYPE
   SYNTAX      Integer32
   MAX-ACCESS  read-write
   STATUS      current
   DESCRIPTION
      "Path: ethernet3.editConf.vlan.bandwidth.correction.predefined.encapsulation.efm.idleBytes"
   ::= {er1645v2Lan3VlanEntry 136598784}

er1645v2Lan3VlanBandwidthCorrPredefMode OBJECT-TYPE
   SYNTAX      INTEGER
               {
               routing (0),
               bridging (1)
               }
   MAX-ACCESS  read-write
   STATUS      current
   DESCRIPTION
      "Path: ethernet3.editConf.vlan.bandwidth.correction.predefined.mode

       Possibilities:
               routing   (0)
               bridging   (1)"
   ::= {er1645v2Lan3VlanEntry 136609792}

er1645v2Lan3VlanBandwidthCorrManualOverhead OBJECT-TYPE
   SYNTAX      Integer32
   MAX-ACCESS  read-write
   STATUS      current
   DESCRIPTION
      "Path: ethernet3.editConf.vlan.bandwidth.correction.manual.overhead"
   ::= {er1645v2Lan3VlanEntry 136708608}

er1645v2Lan3VlanBandwidthCorrManualFrameData OBJECT-TYPE
   SYNTAX      Counter32
   MAX-ACCESS  read-write
   STATUS      current
   DESCRIPTION
      "Path: ethernet3.editConf.vlan.bandwidth.correction.manual.frameData

       32 bit unsigned wrappable counter."
   ::= {er1645v2Lan3VlanEntry 136709120}

er1645v2Lan3VlanBandwidthCorrManualFrameHeader OBJECT-TYPE
   SYNTAX      Counter32
   MAX-ACCESS  read-write
   STATUS      current
   DESCRIPTION
      "Path: ethernet3.editConf.vlan.bandwidth.correction.manual.frameHeader

       32 bit unsigned wrappable counter."
   ::= {er1645v2Lan3VlanEntry 136709632}

er1645v2Lan3VlanBandwidthMaxFifoQLen OBJECT-TYPE
   SYNTAX      Integer32
   MAX-ACCESS  read-write
   STATUS      current
   DESCRIPTION
      "Path: ethernet3.editConf.vlan.bandwidth.maxFifoQLen"
   ::= {er1645v2Lan3VlanEntry 137363456}

er1645v2Lan3VlanBandwidthDeFlagCir OBJECT-TYPE
   SYNTAX      INTEGER
               {
               allowed (1),
               notAllowed (2)
               }
   MAX-ACCESS  read-write
   STATUS      current
   DESCRIPTION
      "Path: ethernet3.editConf.vlan.bandwidth.deFlag.cir

       Possibilities:
               allowed   (1)
               notAllowed   (2)"
   ::= {er1645v2Lan3VlanEntry 147853312}

er1645v2Lan3VlanBandwidthDeFlagEir OBJECT-TYPE
   SYNTAX      INTEGER
               {
               allowed (1),
               notAllowed (2)
               }
   MAX-ACCESS  read-write
   STATUS      current
   DESCRIPTION
      "Path: ethernet3.editConf.vlan.bandwidth.deFlag.eir

       Possibilities:
               allowed   (1)
               notAllowed   (2)"
   ::= {er1645v2Lan3VlanEntry 147857408}

er1645v2Lan3VlanBandwidthDeFlagViolate OBJECT-TYPE
   SYNTAX      INTEGER
               {
               allowed (1),
               notAllowed (2)
               }
   MAX-ACCESS  read-write
   STATUS      current
   DESCRIPTION
      "Path: ethernet3.editConf.vlan.bandwidth.deFlag.violate

       Possibilities:
               allowed   (1)
               notAllowed   (2)"
   ::= {er1645v2Lan3VlanEntry 147861504}

er1645v2Lan3VlanBandwidthActCirActNone OBJECT-TYPE
   SYNTAX      OCTET STRING
   MAX-ACCESS  read-write
   STATUS      current
   DESCRIPTION
      "Path: ethernet3.editConf.vlan.bandwidth.action.cirAction.none"
   ::= {er1645v2Lan3VlanEntry 150085632}

er1645v2Lan3VlanBandwidthActCirActEthCos1 OBJECT-TYPE
   SYNTAX      INTEGER
               {
               unchanged (256)
               }
   MAX-ACCESS  read-write
   STATUS      current
   DESCRIPTION
      "Path: ethernet3.editConf.vlan.bandwidth.action.cirAction.ethernet.cosDepth1

       Possibilities:
               unchanged   (256)"
   ::= {er1645v2Lan3VlanEntry 150094080}

er1645v2Lan3VlanBandwidthActCirActEthDei1 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth1

       Possibilities:
               unchanged   (255)
               clear   (0)
               set   (1)"
   ::= {er1645v2Lan3VlanEntry 150099200}

er1645v2Lan3VlanBandwidthActCirActEthCos2 OBJECT-TYPE
   SYNTAX      INTEGER
               {
               unchanged (256)
               }
   MAX-ACCESS  read-write
   STATUS      current
   DESCRIPTION
      "Path: ethernet3.editConf.vlan.bandwidth.action.cirAction.ethernet.cosDepth2

       Possibilities:
               unchanged   (256)"
   ::= {er1645v2Lan3VlanEntry 150094336}

er1645v2Lan3VlanBandwidthActCirActEthDei2 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth2

       Possibilities:
               unchanged   (255)
               clear   (0)
               set   (1)"
   ::= {er1645v2Lan3VlanEntry 150099456}

er1645v2Lan3VlanBandwidthActCirActEthCos3 OBJECT-TYPE
   SYNTAX      INTEGER
               {
               unchanged (256)
               }
   MAX-ACCESS  read-write
   STATUS      current
   DESCRIPTION
      "Path: ethernet3.editConf.vlan.bandwidth.action.cirAction.ethernet.cosDepth3

       Possibilities:
               unchanged   (256)"
   ::= {er1645v2Lan3VlanEntry 150094592}

er1645v2Lan3VlanBandwidthActCirActEthDei3 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth3

       Possibilities:
               unchanged   (255)
               clear   (0)
               set   (1)"
   ::= {er1645v2Lan3VlanEntry 150099712}

er1645v2Lan3VlanBandwidthActCirActEthCos4 OBJECT-TYPE
   SYNTAX      INTEGER
               {
               unchanged (256)
               }
   MAX-ACCESS  read-write
   STATUS      current
   DESCRIPTION
      "Path: ethernet3.editConf.vlan.bandwidth.action.cirAction.ethernet.cosDepth4

       Possibilities:
               unchanged   (256)"
   ::= {er1645v2Lan3VlanEntry 150094848}

er1645v2Lan3VlanBandwidthActCirActEthDei4 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth4

       Possibilities:
               unchanged   (255)
               clear   (0)
               set   (1)"
   ::= {er1645v2Lan3VlanEntry 150099968}

er1645v2Lan3VlanBandwidthActCirActEthCos5 OBJECT-TYPE
   SYNTAX      INTEGER
               {
               unchanged (256)
               }
   MAX-ACCESS  read-write
   STATUS      current
   DESCRIPTION
      "Path: ethernet3.editConf.vlan.bandwidth.action.cirAction.ethernet.cosDepth5

       Possibilities:
               unchanged   (256)"
   ::= {er1645v2Lan3VlanEntry 150095104}

er1645v2Lan3VlanBandwidthActCirActEthDei5 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth5

       Possibilities:
               unchanged   (255)
               clear   (0)
               set   (1)"
   ::= {er1645v2Lan3VlanEntry 150100224}

er1645v2Lan3VlanBandwidthActCirActEthCos6 OBJECT-TYPE
   SYNTAX      INTEGER
               {
               unchanged (256)
               }
   MAX-ACCESS  read-write
   STATUS      current
   DESCRIPTION
      "Path: ethernet3.editConf.vlan.bandwidth.action.cirAction.ethernet.cosDepth6

       Possibilities:
               unchanged   (256)"
   ::= {er1645v2Lan3VlanEntry 150095360}

er1645v2Lan3VlanBandwidthActCirActEthDei6 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth6

       Possibilities:
               unchanged   (255)
               clear   (0)
               set   (1)"
   ::= {er1645v2Lan3VlanEntry 150100480}

er1645v2Lan3VlanBandwidthActCirActEthCos7 OBJECT-TYPE
   SYNTAX      INTEGER
               {
               unchanged (256)
               }
   MAX-ACCESS  read-write
   STATUS      current
   DESCRIPTION
      "Path: ethernet3.editConf.vlan.bandwidth.action.cirAction.ethernet.cosDepth7

       Possibilities:
               unchanged   (256)"
   ::= {er1645v2Lan3VlanEntry 150095616}

er1645v2Lan3VlanBandwidthActCirActEthDei7 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth7

       Possibilities:
               unchanged   (255)
               clear   (0)
               set   (1)"
   ::= {er1645v2Lan3VlanEntry 150100736}

er1645v2Lan3VlanBandwidthActCirActEthCos8 OBJECT-TYPE
   SYNTAX      INTEGER
               {
               unchanged (256)
               }
   MAX-ACCESS  read-write
   STATUS      current
   DESCRIPTION
      "Path: ethernet3.editConf.vlan.bandwidth.action.cirAction.ethernet.cosDepth8

       Possibilities:
               unchanged   (256)"
   ::= {er1645v2Lan3VlanEntry 150095872}

er1645v2Lan3VlanBandwidthActCirActEthDei8 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth8

       Possibilities:
               unchanged   (255)
               clear   (0)
               set   (1)"
   ::= {er1645v2Lan3VlanEntry 150100992}

er1645v2Lan3VlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150096128}

er1645v2Lan3VlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150096384}

er1645v2Lan3VlanBandwidthActCirActEthDrpLev OBJECT-TYPE
   SYNTAX      INTEGER
               {
               unchanged (0)
               }
   MAX-ACCESS  read-write
   STATUS      current
   DESCRIPTION
      "Path: ethernet3.editConf.vlan.bandwidth.action.cirAction.ethernet.dropLevel

       Possibilities:
               unchanged   (0)"
   ::= {er1645v2Lan3VlanEntry 150096640}

er1645v2Lan3VlanBandwidthActCirActEthDeFlag OBJECT-TYPE
   SYNTAX      INTEGER
               {
               unchanged (255),
               clear (0),
               set (1)
               }
   MAX-ACCESS  read-write
   STATUS      current
   DESCRIPTION
      "Path: ethernet3.editConf.vlan.bandwidth.action.cirAction.ethernet.deFlag

       Possibilities:
               unchanged   (255)
               clear   (0)
               set   (1)"
   ::= {er1645v2Lan3VlanEntry 150097408}

er1645v2Lan3VlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150120704}

er1645v2Lan3VlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150120960}

er1645v2Lan3VlanBandwidthActCirActIpDrpLev OBJECT-TYPE
   SYNTAX      INTEGER
               {
               unchanged (0)
               }
   MAX-ACCESS  read-write
   STATUS      current
   DESCRIPTION
      "Path: ethernet3.editConf.vlan.bandwidth.action.cirAction.ip.dropLevel

       Possibilities:
               unchanged   (0)"
   ::= {er1645v2Lan3VlanEntry 150121216}

er1645v2Lan3VlanBandwidthActCirActIpDeFlag OBJECT-TYPE
   SYNTAX      INTEGER
               {
               unchanged (255),
               clear (0),
               set (1)
               }
   MAX-ACCESS  read-write
   STATUS      current
   DESCRIPTION
      "Path: ethernet3.editConf.vlan.bandwidth.action.cirAction.ip.deFlag

       Possibilities:
               unchanged   (255)
               clear   (0)
               set   (1)"
   ::= {er1645v2Lan3VlanEntry 150121984}

er1645v2Lan3VlanBandwidthActEirActNone OBJECT-TYPE
   SYNTAX      OCTET STRING
   MAX-ACCESS  read-write
   STATUS      current
   DESCRIPTION
      "Path: ethernet3.editConf.vlan.bandwidth.action.eirAction.none"
   ::= {er1645v2Lan3VlanEntry 150216704}

er1645v2Lan3VlanBandwidthActEirActEthCos1 OBJECT-TYPE
   SYNTAX      INTEGER
               {
               unchanged (256)
               }
   MAX-ACCESS  read-write
   STATUS      current
   DESCRIPTION
      "Path: ethernet3.editConf.vlan.bandwidth.action.eirAction.ethernet.cosDepth1

       Possibilities:
               unchanged   (256)"
   ::= {er1645v2Lan3VlanEntry 150225152}

er1645v2Lan3VlanBandwidthActEirActEthDei1 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth1

       Possibilities:
               unchanged   (255)
               clear   (0)
               set   (1)"
   ::= {er1645v2Lan3VlanEntry 150230272}

er1645v2Lan3VlanBandwidthActEirActEthCos2 OBJECT-TYPE
   SYNTAX      INTEGER
               {
               unchanged (256)
               }
   MAX-ACCESS  read-write
   STATUS      current
   DESCRIPTION
      "Path: ethernet3.editConf.vlan.bandwidth.action.eirAction.ethernet.cosDepth2

       Possibilities:
               unchanged   (256)"
   ::= {er1645v2Lan3VlanEntry 150225408}

er1645v2Lan3VlanBandwidthActEirActEthDei2 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth2

       Possibilities:
               unchanged   (255)
               clear   (0)
               set   (1)"
   ::= {er1645v2Lan3VlanEntry 150230528}

er1645v2Lan3VlanBandwidthActEirActEthCos3 OBJECT-TYPE
   SYNTAX      INTEGER
               {
               unchanged (256)
               }
   MAX-ACCESS  read-write
   STATUS      current
   DESCRIPTION
      "Path: ethernet3.editConf.vlan.bandwidth.action.eirAction.ethernet.cosDepth3

       Possibilities:
               unchanged   (256)"
   ::= {er1645v2Lan3VlanEntry 150225664}

er1645v2Lan3VlanBandwidthActEirActEthDei3 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth3

       Possibilities:
               unchanged   (255)
               clear   (0)
               set   (1)"
   ::= {er1645v2Lan3VlanEntry 150230784}

er1645v2Lan3VlanBandwidthActEirActEthCos4 OBJECT-TYPE
   SYNTAX      INTEGER
               {
               unchanged (256)
               }
   MAX-ACCESS  read-write
   STATUS      current
   DESCRIPTION
      "Path: ethernet3.editConf.vlan.bandwidth.action.eirAction.ethernet.cosDepth4

       Possibilities:
               unchanged   (256)"
   ::= {er1645v2Lan3VlanEntry 150225920}

er1645v2Lan3VlanBandwidthActEirActEthDei4 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth4

       Possibilities:
               unchanged   (255)
               clear   (0)
               set   (1)"
   ::= {er1645v2Lan3VlanEntry 150231040}

er1645v2Lan3VlanBandwidthActEirActEthCos5 OBJECT-TYPE
   SYNTAX      INTEGER
               {
               unchanged (256)
               }
   MAX-ACCESS  read-write
   STATUS      current
   DESCRIPTION
      "Path: ethernet3.editConf.vlan.bandwidth.action.eirAction.ethernet.cosDepth5

       Possibilities:
               unchanged   (256)"
   ::= {er1645v2Lan3VlanEntry 150226176}

er1645v2Lan3VlanBandwidthActEirActEthDei5 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth5

       Possibilities:
               unchanged   (255)
               clear   (0)
               set   (1)"
   ::= {er1645v2Lan3VlanEntry 150231296}

er1645v2Lan3VlanBandwidthActEirActEthCos6 OBJECT-TYPE
   SYNTAX      INTEGER
               {
               unchanged (256)
               }
   MAX-ACCESS  read-write
   STATUS      current
   DESCRIPTION
      "Path: ethernet3.editConf.vlan.bandwidth.action.eirAction.ethernet.cosDepth6

       Possibilities:
               unchanged   (256)"
   ::= {er1645v2Lan3VlanEntry 150226432}

er1645v2Lan3VlanBandwidthActEirActEthDei6 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth6

       Possibilities:
               unchanged   (255)
               clear   (0)
               set   (1)"
   ::= {er1645v2Lan3VlanEntry 150231552}

er1645v2Lan3VlanBandwidthActEirActEthCos7 OBJECT-TYPE
   SYNTAX      INTEGER
               {
               unchanged (256)
               }
   MAX-ACCESS  read-write
   STATUS      current
   DESCRIPTION
      "Path: ethernet3.editConf.vlan.bandwidth.action.eirAction.ethernet.cosDepth7

       Possibilities:
               unchanged   (256)"
   ::= {er1645v2Lan3VlanEntry 150226688}

er1645v2Lan3VlanBandwidthActEirActEthDei7 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth7

       Possibilities:
               unchanged   (255)
               clear   (0)
               set   (1)"
   ::= {er1645v2Lan3VlanEntry 150231808}

er1645v2Lan3VlanBandwidthActEirActEthCos8 OBJECT-TYPE
   SYNTAX      INTEGER
               {
               unchanged (256)
               }
   MAX-ACCESS  read-write
   STATUS      current
   DESCRIPTION
      "Path: ethernet3.editConf.vlan.bandwidth.action.eirAction.ethernet.cosDepth8

       Possibilities:
               unchanged   (256)"
   ::= {er1645v2Lan3VlanEntry 150226944}

er1645v2Lan3VlanBandwidthActEirActEthDei8 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth8

       Possibilities:
               unchanged   (255)
               clear   (0)
               set   (1)"
   ::= {er1645v2Lan3VlanEntry 150232064}

er1645v2Lan3VlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150227200}

er1645v2Lan3VlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150227456}

er1645v2Lan3VlanBandwidthActEirActEthDrpLev OBJECT-TYPE
   SYNTAX      INTEGER
               {
               unchanged (0)
               }
   MAX-ACCESS  read-write
   STATUS      current
   DESCRIPTION
      "Path: ethernet3.editConf.vlan.bandwidth.action.eirAction.ethernet.dropLevel

       Possibilities:
               unchanged   (0)"
   ::= {er1645v2Lan3VlanEntry 150227712}

er1645v2Lan3VlanBandwidthActEirActEthDeFlag OBJECT-TYPE
   SYNTAX      INTEGER
               {
               unchanged (255),
               clear (0),
               set (1)
               }
   MAX-ACCESS  read-write
   STATUS      current
   DESCRIPTION
      "Path: ethernet3.editConf.vlan.bandwidth.action.eirAction.ethernet.deFlag

       Possibilities:
               unchanged   (255)
               clear   (0)
               set   (1)"
   ::= {er1645v2Lan3VlanEntry 150228480}

er1645v2Lan3VlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150251776}

er1645v2Lan3VlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150252032}

er1645v2Lan3VlanBandwidthActEirActIpDrpLev OBJECT-TYPE
   SYNTAX      INTEGER
               {
               unchanged (0)
               }
   MAX-ACCESS  read-write
   STATUS      current
   DESCRIPTION
      "Path: ethernet3.editConf.vlan.bandwidth.action.eirAction.ip.dropLevel

       Possibilities:
               unchanged   (0)"
   ::= {er1645v2Lan3VlanEntry 150252288}

er1645v2Lan3VlanBandwidthActEirActIpDeFlag OBJECT-TYPE
   SYNTAX      INTEGER
               {
               unchanged (255),
               clear (0),
               set (1)
               }
   MAX-ACCESS  read-write
   STATUS      current
   DESCRIPTION
      "Path: ethernet3.editConf.vlan.bandwidth.action.eirAction.ip.deFlag

       Possibilities:
               unchanged   (255)
               clear   (0)
               set   (1)"
   ::= {er1645v2Lan3VlanEntry 150253056}

er1645v2Lan3VlanBandwidthActViolActNone OBJECT-TYPE
   SYNTAX      OCTET STRING
   MAX-ACCESS  read-write
   STATUS      current
   DESCRIPTION
      "Path: ethernet3.editConf.vlan.bandwidth.action.violateAction.none"
   ::= {er1645v2Lan3VlanEntry 150347776}

er1645v2Lan3VlanBandwidthActViolActDrop OBJECT-TYPE
   SYNTAX      OCTET STRING
   MAX-ACCESS  read-write
   STATUS      current
   DESCRIPTION
      "Path: ethernet3.editConf.vlan.bandwidth.action.violateAction.drop"
   ::= {er1645v2Lan3VlanEntry 150364160}

er1645v2Lan3VlanBandwidthActViolActEthCos1 OBJECT-TYPE
   SYNTAX      INTEGER
               {
               unchanged (256)
               }
   MAX-ACCESS  read-write
   STATUS      current
   DESCRIPTION
      "Path: ethernet3.editConf.vlan.bandwidth.action.violateAction.ethernet.cosDepth1

       Possibilities:
               unchanged   (256)"
   ::= {er1645v2Lan3VlanEntry 150356224}

er1645v2Lan3VlanBandwidthActViolActEthDei1 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth1

       Possibilities:
               unchanged   (255)
               clear   (0)
               set   (1)"
   ::= {er1645v2Lan3VlanEntry 150361344}

er1645v2Lan3VlanBandwidthActViolActEthCos2 OBJECT-TYPE
   SYNTAX      INTEGER
               {
               unchanged (256)
               }
   MAX-ACCESS  read-write
   STATUS      current
   DESCRIPTION
      "Path: ethernet3.editConf.vlan.bandwidth.action.violateAction.ethernet.cosDepth2

       Possibilities:
               unchanged   (256)"
   ::= {er1645v2Lan3VlanEntry 150356480}

er1645v2Lan3VlanBandwidthActViolActEthDei2 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth2

       Possibilities:
               unchanged   (255)
               clear   (0)
               set   (1)"
   ::= {er1645v2Lan3VlanEntry 150361600}

er1645v2Lan3VlanBandwidthActViolActEthCos3 OBJECT-TYPE
   SYNTAX      INTEGER
               {
               unchanged (256)
               }
   MAX-ACCESS  read-write
   STATUS      current
   DESCRIPTION
      "Path: ethernet3.editConf.vlan.bandwidth.action.violateAction.ethernet.cosDepth3

       Possibilities:
               unchanged   (256)"
   ::= {er1645v2Lan3VlanEntry 150356736}

er1645v2Lan3VlanBandwidthActViolActEthDei3 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth3

       Possibilities:
               unchanged   (255)
               clear   (0)
               set   (1)"
   ::= {er1645v2Lan3VlanEntry 150361856}

er1645v2Lan3VlanBandwidthActViolActEthCos4 OBJECT-TYPE
   SYNTAX      INTEGER
               {
               unchanged (256)
               }
   MAX-ACCESS  read-write
   STATUS      current
   DESCRIPTION
      "Path: ethernet3.editConf.vlan.bandwidth.action.violateAction.ethernet.cosDepth4

       Possibilities:
               unchanged   (256)"
   ::= {er1645v2Lan3VlanEntry 150356992}

er1645v2Lan3VlanBandwidthActViolActEthDei4 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth4

       Possibilities:
               unchanged   (255)
               clear   (0)
               set   (1)"
   ::= {er1645v2Lan3VlanEntry 150362112}

er1645v2Lan3VlanBandwidthActViolActEthCos5 OBJECT-TYPE
   SYNTAX      INTEGER
               {
               unchanged (256)
               }
   MAX-ACCESS  read-write
   STATUS      current
   DESCRIPTION
      "Path: ethernet3.editConf.vlan.bandwidth.action.violateAction.ethernet.cosDepth5

       Possibilities:
               unchanged   (256)"
   ::= {er1645v2Lan3VlanEntry 150357248}

er1645v2Lan3VlanBandwidthActViolActEthDei5 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth5

       Possibilities:
               unchanged   (255)
               clear   (0)
               set   (1)"
   ::= {er1645v2Lan3VlanEntry 150362368}

er1645v2Lan3VlanBandwidthActViolActEthCos6 OBJECT-TYPE
   SYNTAX      INTEGER
               {
               unchanged (256)
               }
   MAX-ACCESS  read-write
   STATUS      current
   DESCRIPTION
      "Path: ethernet3.editConf.vlan.bandwidth.action.violateAction.ethernet.cosDepth6

       Possibilities:
               unchanged   (256)"
   ::= {er1645v2Lan3VlanEntry 150357504}

er1645v2Lan3VlanBandwidthActViolActEthDei6 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth6

       Possibilities:
               unchanged   (255)
               clear   (0)
               set   (1)"
   ::= {er1645v2Lan3VlanEntry 150362624}

er1645v2Lan3VlanBandwidthActViolActEthCos7 OBJECT-TYPE
   SYNTAX      INTEGER
               {
               unchanged (256)
               }
   MAX-ACCESS  read-write
   STATUS      current
   DESCRIPTION
      "Path: ethernet3.editConf.vlan.bandwidth.action.violateAction.ethernet.cosDepth7

       Possibilities:
               unchanged   (256)"
   ::= {er1645v2Lan3VlanEntry 150357760}

er1645v2Lan3VlanBandwidthActViolActEthDei7 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth7

       Possibilities:
               unchanged   (255)
               clear   (0)
               set   (1)"
   ::= {er1645v2Lan3VlanEntry 150362880}

er1645v2Lan3VlanBandwidthActViolActEthCos8 OBJECT-TYPE
   SYNTAX      INTEGER
               {
               unchanged (256)
               }
   MAX-ACCESS  read-write
   STATUS      current
   DESCRIPTION
      "Path: ethernet3.editConf.vlan.bandwidth.action.violateAction.ethernet.cosDepth8

       Possibilities:
               unchanged   (256)"
   ::= {er1645v2Lan3VlanEntry 150358016}

er1645v2Lan3VlanBandwidthActViolActEthDei8 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth8

       Possibilities:
               unchanged   (255)
               clear   (0)
               set   (1)"
   ::= {er1645v2Lan3VlanEntry 150363136}

er1645v2Lan3VlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150358272}

er1645v2Lan3VlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150358528}

er1645v2Lan3VlanBandwidthActViolActEthDrpLev OBJECT-TYPE
   SYNTAX      INTEGER
               {
               unchanged (0)
               }
   MAX-ACCESS  read-write
   STATUS      current
   DESCRIPTION
      "Path: ethernet3.editConf.vlan.bandwidth.action.violateAction.ethernet.dropLevel

       Possibilities:
               unchanged   (0)"
   ::= {er1645v2Lan3VlanEntry 150358784}

er1645v2Lan3VlanBandwidthActViolActEthDeFlag OBJECT-TYPE
   SYNTAX      INTEGER
               {
               unchanged (255),
               clear (0),
               set (1)
               }
   MAX-ACCESS  read-write
   STATUS      current
   DESCRIPTION
      "Path: ethernet3.editConf.vlan.bandwidth.action.violateAction.ethernet.deFlag

       Possibilities:
               unchanged   (255)
               clear   (0)
               set   (1)"
   ::= {er1645v2Lan3VlanEntry 150359552}

er1645v2Lan3VlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 150382848}

er1645v2Lan3VlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 150383104}

er1645v2Lan3VlanBandwidthActViolActIpDrpLev OBJECT-TYPE
   SYNTAX      INTEGER
               {
               unchanged (0)
               }
   MAX-ACCESS  read-write
   STATUS      current
   DESCRIPTION
      "Path: ethernet3.editConf.vlan.bandwidth.action.violateAction.ip.dropLevel

       Possibilities:
               unchanged   (0)"
   ::= {er1645v2Lan3VlanEntry 150383360}

er1645v2Lan3VlanBandwidthActViolActIpDeFlag OBJECT-TYPE
   SYNTAX      INTEGER
               {
               unchanged (255),
               clear (0),
               set (1)
               }
   MAX-ACCESS  read-write
   STATUS      current
   DESCRIPTION
      "Path: ethernet3.editConf.vlan.bandwidth.action.violateAction.ip.deFlag

       Possibilities:
               unchanged   (255)
               clear   (0)
               set   (1)"
   ::= {er1645v2Lan3VlanEntry 150384128}

er1645v2Lan3VlanInbBwMode OBJECT-TYPE
   SYNTAX      INTEGER
               {
               reshaping (1),
               policing (2)
               }
   MAX-ACCESS  read-write
   STATUS      current
   DESCRIPTION
      "Path: ethernet3.editConf.vlan.inboundBandwidth.mode

       Possibilities:
               reshaping   (1)
               policing   (2)"
   ::= {er1645v2Lan3VlanEntry 132120576}

er1645v2Lan3VlanInbBwCir OBJECT-TYPE
   SYNTAX      Integer32
   MAX-ACCESS  read-write
   STATUS      current
   DESCRIPTION
      "Path: ethernet3.editConf.vlan.inboundBandwidth.cir"
   ::= {er1645v2Lan3VlanEntry 118489088}

er1645v2Lan3VlanInbBwEir OBJECT-TYPE
   SYNTAX      Integer32
   MAX-ACCESS  read-write
   STATUS      current
   DESCRIPTION
      "Path: ethernet3.editConf.vlan.inboundBandwidth.eir"
   ::= {er1645v2Lan3VlanEntry 124780544}

er1645v2Lan3VlanInbBwUnit OBJECT-TYPE
   SYNTAX      INTEGER
               {
               bitssec (1),
               percent (2)
               }
   MAX-ACCESS  read-write
   STATUS      current
   DESCRIPTION
      "Path: ethernet3.editConf.vlan.inboundBandwidth.unit

       Possibilities:
               bits/sec   (1)
               percent   (2)"
   ::= {er1645v2Lan3VlanEntry 122683392}

er1645v2Lan3VlanInbBwTc OBJECT-TYPE
   SYNTAX      INTEGER
               {
               auto (0)
               }
   MAX-ACCESS  read-write
   STATUS      current
   DESCRIPTION
      "Path: ethernet3.editConf.vlan.inboundBandwidth.tc

       Possibilities:
               auto   (0)"
   ::= {er1645v2Lan3VlanEntry 123731968}

er1645v2Lan3VlanInbBwTcFactor OBJECT-TYPE
   SYNTAX      INTEGER
               {
               ms (10),
               s100us (1)
               }
   MAX-ACCESS  read-write
   STATUS      current
   DESCRIPTION
      "Path: ethernet3.editConf.vlan.inboundBandwidth.tcFactor

       Possibilities:
               ms   (10)
               *100us   (1)"
   ::= {er1645v2Lan3VlanEntry 125829120}

er1645v2Lan3VlanInbBwCorrType OBJECT-TYPE
   SYNTAX      INTEGER
               {
               noCorrection (0),
               predefined (1),
               manual (2)
               }
   MAX-ACCESS  read-write
   STATUS      current
   DESCRIPTION
      "Path: ethernet3.editConf.vlan.inboundBandwidth.correction.type

       Possibilities:
               noCorrection   (0)
               predefined   (1)
               manual   (2)"
   ::= {er1645v2Lan3VlanEntry 119668736}

er1645v2Lan3VlanInbBwCorrPredefEncapsFrameRelay OBJECT-TYPE
   SYNTAX      DisplayString
   MAX-ACCESS  read-write
   STATUS      current
   DESCRIPTION
      "Path: ethernet3.editConf.vlan.inboundBandwidth.correction.predefined.encapsulation.frameRelay"
   ::= {er1645v2Lan3VlanEntry 119817216}

er1645v2Lan3VlanInbBwCorrPredefEncapsPpp OBJECT-TYPE
   SYNTAX      DisplayString
   MAX-ACCESS  read-write
   STATUS      current
   DESCRIPTION
      "Path: ethernet3.editConf.vlan.inboundBandwidth.correction.predefined.encapsulation.ppp"
   ::= {er1645v2Lan3VlanEntry 119818240}

er1645v2Lan3VlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.inboundBandwidth.correction.predefined.encapsulation.atm.higherLayer

       Possibilities:
               rfc2684   (0)
               ppp   (1)
               pppOverEthernet   (2)"
   ::= {er1645v2Lan3VlanEntry 119819392}

er1645v2Lan3VlanInbBwCorrPredefEncapsAtmMp OBJECT-TYPE
   SYNTAX      INTEGER
               {
               llcEncapsulation (0),
               vcMultiplexing (1)
               }
   MAX-ACCESS  read-write
   STATUS      current
   DESCRIPTION
      "Path: ethernet3.editConf.vlan.inboundBandwidth.correction.predefined.encapsulation.atm.multiProtocol

       Possibilities:
               llcEncapsulation   (0)
               vcMultiplexing   (1)"
   ::= {er1645v2Lan3VlanEntry 119819520}

er1645v2Lan3VlanInbBwCorrPredefEncapsHdlc OBJECT-TYPE
   SYNTAX      DisplayString
   MAX-ACCESS  read-write
   STATUS      current
   DESCRIPTION
      "Path: ethernet3.editConf.vlan.inboundBandwidth.correction.predefined.encapsulation.hdlc"
   ::= {er1645v2Lan3VlanEntry 119820288}

er1645v2Lan3VlanInbBwCorrPredefEncapsEfmFs OBJECT-TYPE
   SYNTAX      Integer32
   MAX-ACCESS  read-write
   STATUS      current
   DESCRIPTION
      "Path: ethernet3.editConf.vlan.inboundBandwidth.correction.predefined.encapsulation.efm.fragmentSize"
   ::= {er1645v2Lan3VlanEntry 119821440}

er1645v2Lan3VlanInbBwCorrPredefEncapsEfmIb OBJECT-TYPE
   SYNTAX      Integer32
   MAX-ACCESS  read-write
   STATUS      current
   DESCRIPTION
      "Path: ethernet3.editConf.vlan.inboundBandwidth.correction.predefined.encapsulation.efm.idleBytes"
   ::= {er1645v2Lan3VlanEntry 119821568}

er1645v2Lan3VlanInbBwCorrPredefMode OBJECT-TYPE
   SYNTAX      INTEGER
               {
               routing (0),
               bridging (1)
               }
   MAX-ACCESS  read-write
   STATUS      current
   DESCRIPTION
      "Path: ethernet3.editConf.vlan.inboundBandwidth.correction.predefined.mode

       Possibilities:
               routing   (0)
               bridging   (1)"
   ::= {er1645v2Lan3VlanEntry 119832576}

er1645v2Lan3VlanInbBwCorrManualOverhead OBJECT-TYPE
   SYNTAX      Integer32
   MAX-ACCESS  read-write
   STATUS      current
   DESCRIPTION
      "Path: ethernet3.editConf.vlan.inboundBandwidth.correction.manual.overhead"
   ::= {er1645v2Lan3VlanEntry 119931392}

er1645v2Lan3VlanInbBwCorrManualFrameData OBJECT-TYPE
   SYNTAX      Counter32
   MAX-ACCESS  read-write
   STATUS      current
   DESCRIPTION
      "Path: ethernet3.editConf.vlan.inboundBandwidth.correction.manual.frameData

       32 bit unsigned wrappable counter."
   ::= {er1645v2Lan3VlanEntry 119931904}

er1645v2Lan3VlanInbBwCorrManualFrameHeader OBJECT-TYPE
   SYNTAX      Counter32
   MAX-ACCESS  read-write
   STATUS      current
   DESCRIPTION
      "Path: ethernet3.editConf.vlan.inboundBandwidth.correction.manual.frameHeader

       32 bit unsigned wrappable counter."
   ::= {er1645v2Lan3VlanEntry 119932416}

er1645v2Lan3VlanInbBwMaxFifoQLen OBJECT-TYPE
   SYNTAX      Integer32
   MAX-ACCESS  read-write
   STATUS      current
   DESCRIPTION
      "Path: ethernet3.editConf.vlan.inboundBandwidth.maxFifoQLen"
   ::= {er1645v2Lan3VlanEntry 120586240}

er1645v2Lan3VlanInbBwPriorityPolicy OBJECT-TYPE
   SYNTAX      DisplayString
   MAX-ACCESS  read-write
   STATUS      current
   DESCRIPTION
      "Path: ethernet3.editConf.vlan.inboundBandwidth.priorityPolicy"
   ::= {er1645v2Lan3VlanEntry 121634816}

er1645v2Lan3VlanInbBwDeFlagCir OBJECT-TYPE
   SYNTAX      INTEGER
               {
               allowed (1),
               notAllowed (2)
               }
   MAX-ACCESS  read-write
   STATUS      current
   DESCRIPTION
      "Path: ethernet3.editConf.vlan.inboundBandwidth.deFlag.cir

       Possibilities:
               allowed   (1)
               notAllowed   (2)"
   ::= {er1645v2Lan3VlanEntry 131076096}

er1645v2Lan3VlanInbBwDeFlagEir OBJECT-TYPE
   SYNTAX      INTEGER
               {
               allowed (1),
               notAllowed (2)
               }
   MAX-ACCESS  read-write
   STATUS      current
   DESCRIPTION
      "Path: ethernet3.editConf.vlan.inboundBandwidth.deFlag.eir

       Possibilities:
               allowed   (1)
               notAllowed   (2)"
   ::= {er1645v2Lan3VlanEntry 131080192}

er1645v2Lan3VlanInbBwDeFlagViolate OBJECT-TYPE
   SYNTAX      INTEGER
               {
               allowed (1),
               notAllowed (2)
               }
   MAX-ACCESS  read-write
   STATUS      current
   DESCRIPTION
      "Path: ethernet3.editConf.vlan.inboundBandwidth.deFlag.violate

       Possibilities:
               allowed   (1)
               notAllowed   (2)"
   ::= {er1645v2Lan3VlanEntry 131084288}

er1645v2Lan3VlanInbBwActCirActNone OBJECT-TYPE
   SYNTAX      OCTET STRING
   MAX-ACCESS  read-write
   STATUS      current
   DESCRIPTION
      "Path: ethernet3.editConf.vlan.inboundBandwidth.action.cirAction.none"
   ::= {er1645v2Lan3VlanEntry 133308416}

er1645v2Lan3VlanInbBwActCirActEthCos1 OBJECT-TYPE
   SYNTAX      INTEGER
               {
               unchanged (256)
               }
   MAX-ACCESS  read-write
   STATUS      current
   DESCRIPTION
      "Path: ethernet3.editConf.vlan.inboundBandwidth.action.cirAction.ethernet.cosDepth1

       Possibilities:
               unchanged   (256)"
   ::= {er1645v2Lan3VlanEntry 133316864}

er1645v2Lan3VlanInbBwActCirActEthDei1 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth1

       Possibilities:
               unchanged   (255)
               clear   (0)
               set   (1)"
   ::= {er1645v2Lan3VlanEntry 133321984}

er1645v2Lan3VlanInbBwActCirActEthCos2 OBJECT-TYPE
   SYNTAX      INTEGER
               {
               unchanged (256)
               }
   MAX-ACCESS  read-write
   STATUS      current
   DESCRIPTION
      "Path: ethernet3.editConf.vlan.inboundBandwidth.action.cirAction.ethernet.cosDepth2

       Possibilities:
               unchanged   (256)"
   ::= {er1645v2Lan3VlanEntry 133317120}

er1645v2Lan3VlanInbBwActCirActEthDei2 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth2

       Possibilities:
               unchanged   (255)
               clear   (0)
               set   (1)"
   ::= {er1645v2Lan3VlanEntry 133322240}

er1645v2Lan3VlanInbBwActCirActEthCos3 OBJECT-TYPE
   SYNTAX      INTEGER
               {
               unchanged (256)
               }
   MAX-ACCESS  read-write
   STATUS      current
   DESCRIPTION
      "Path: ethernet3.editConf.vlan.inboundBandwidth.action.cirAction.ethernet.cosDepth3

       Possibilities:
               unchanged   (256)"
   ::= {er1645v2Lan3VlanEntry 133317376}

er1645v2Lan3VlanInbBwActCirActEthDei3 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth3

       Possibilities:
               unchanged   (255)
               clear   (0)
               set   (1)"
   ::= {er1645v2Lan3VlanEntry 133322496}

er1645v2Lan3VlanInbBwActCirActEthCos4 OBJECT-TYPE
   SYNTAX      INTEGER
               {
               unchanged (256)
               }
   MAX-ACCESS  read-write
   STATUS      current
   DESCRIPTION
      "Path: ethernet3.editConf.vlan.inboundBandwidth.action.cirAction.ethernet.cosDepth4

       Possibilities:
               unchanged   (256)"
   ::= {er1645v2Lan3VlanEntry 133317632}

er1645v2Lan3VlanInbBwActCirActEthDei4 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth4

       Possibilities:
               unchanged   (255)
               clear   (0)
               set   (1)"
   ::= {er1645v2Lan3VlanEntry 133322752}

er1645v2Lan3VlanInbBwActCirActEthCos5 OBJECT-TYPE
   SYNTAX      INTEGER
               {
               unchanged (256)
               }
   MAX-ACCESS  read-write
   STATUS      current
   DESCRIPTION
      "Path: ethernet3.editConf.vlan.inboundBandwidth.action.cirAction.ethernet.cosDepth5

       Possibilities:
               unchanged   (256)"
   ::= {er1645v2Lan3VlanEntry 133317888}

er1645v2Lan3VlanInbBwActCirActEthDei5 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth5

       Possibilities:
               unchanged   (255)
               clear   (0)
               set   (1)"
   ::= {er1645v2Lan3VlanEntry 133323008}

er1645v2Lan3VlanInbBwActCirActEthCos6 OBJECT-TYPE
   SYNTAX      INTEGER
               {
               unchanged (256)
               }
   MAX-ACCESS  read-write
   STATUS      current
   DESCRIPTION
      "Path: ethernet3.editConf.vlan.inboundBandwidth.action.cirAction.ethernet.cosDepth6

       Possibilities:
               unchanged   (256)"
   ::= {er1645v2Lan3VlanEntry 133318144}

er1645v2Lan3VlanInbBwActCirActEthDei6 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth6

       Possibilities:
               unchanged   (255)
               clear   (0)
               set   (1)"
   ::= {er1645v2Lan3VlanEntry 133323264}

er1645v2Lan3VlanInbBwActCirActEthCos7 OBJECT-TYPE
   SYNTAX      INTEGER
               {
               unchanged (256)
               }
   MAX-ACCESS  read-write
   STATUS      current
   DESCRIPTION
      "Path: ethernet3.editConf.vlan.inboundBandwidth.action.cirAction.ethernet.cosDepth7

       Possibilities:
               unchanged   (256)"
   ::= {er1645v2Lan3VlanEntry 133318400}

er1645v2Lan3VlanInbBwActCirActEthDei7 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth7

       Possibilities:
               unchanged   (255)
               clear   (0)
               set   (1)"
   ::= {er1645v2Lan3VlanEntry 133323520}

er1645v2Lan3VlanInbBwActCirActEthCos8 OBJECT-TYPE
   SYNTAX      INTEGER
               {
               unchanged (256)
               }
   MAX-ACCESS  read-write
   STATUS      current
   DESCRIPTION
      "Path: ethernet3.editConf.vlan.inboundBandwidth.action.cirAction.ethernet.cosDepth8

       Possibilities:
               unchanged   (256)"
   ::= {er1645v2Lan3VlanEntry 133318656}

er1645v2Lan3VlanInbBwActCirActEthDei8 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth8

       Possibilities:
               unchanged   (255)
               clear   (0)
               set   (1)"
   ::= {er1645v2Lan3VlanEntry 133323776}

er1645v2Lan3VlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133318912}

er1645v2Lan3VlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133319168}

er1645v2Lan3VlanInbBwActCirActEthDrpLev OBJECT-TYPE
   SYNTAX      INTEGER
               {
               unchanged (0)
               }
   MAX-ACCESS  read-write
   STATUS      current
   DESCRIPTION
      "Path: ethernet3.editConf.vlan.inboundBandwidth.action.cirAction.ethernet.dropLevel

       Possibilities:
               unchanged   (0)"
   ::= {er1645v2Lan3VlanEntry 133319424}

er1645v2Lan3VlanInbBwActCirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deFlag

       Possibilities:
               unchanged   (255)
               clear   (0)
               set   (1)"
   ::= {er1645v2Lan3VlanEntry 133320192}

er1645v2Lan3VlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133343488}

er1645v2Lan3VlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133343744}

er1645v2Lan3VlanInbBwActCirActIpDrpLev OBJECT-TYPE
   SYNTAX      INTEGER
               {
               unchanged (0)
               }
   MAX-ACCESS  read-write
   STATUS      current
   DESCRIPTION
      "Path: ethernet3.editConf.vlan.inboundBandwidth.action.cirAction.ip.dropLevel

       Possibilities:
               unchanged   (0)"
   ::= {er1645v2Lan3VlanEntry 133344000}

er1645v2Lan3VlanInbBwActCirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ip.deFlag

       Possibilities:
               unchanged   (255)
               clear   (0)
               set   (1)"
   ::= {er1645v2Lan3VlanEntry 133344768}

er1645v2Lan3VlanInbBwActEirActNone OBJECT-TYPE
   SYNTAX      OCTET STRING
   MAX-ACCESS  read-write
   STATUS      current
   DESCRIPTION
      "Path: ethernet3.editConf.vlan.inboundBandwidth.action.eirAction.none"
   ::= {er1645v2Lan3VlanEntry 133439488}

er1645v2Lan3VlanInbBwActEirActEthCos1 OBJECT-TYPE
   SYNTAX      INTEGER
               {
               unchanged (256)
               }
   MAX-ACCESS  read-write
   STATUS      current
   DESCRIPTION
      "Path: ethernet3.editConf.vlan.inboundBandwidth.action.eirAction.ethernet.cosDepth1

       Possibilities:
               unchanged   (256)"
   ::= {er1645v2Lan3VlanEntry 133447936}

er1645v2Lan3VlanInbBwActEirActEthDei1 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth1

       Possibilities:
               unchanged   (255)
               clear   (0)
               set   (1)"
   ::= {er1645v2Lan3VlanEntry 133453056}

er1645v2Lan3VlanInbBwActEirActEthCos2 OBJECT-TYPE
   SYNTAX      INTEGER
               {
               unchanged (256)
               }
   MAX-ACCESS  read-write
   STATUS      current
   DESCRIPTION
      "Path: ethernet3.editConf.vlan.inboundBandwidth.action.eirAction.ethernet.cosDepth2

       Possibilities:
               unchanged   (256)"
   ::= {er1645v2Lan3VlanEntry 133448192}

er1645v2Lan3VlanInbBwActEirActEthDei2 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth2

       Possibilities:
               unchanged   (255)
               clear   (0)
               set   (1)"
   ::= {er1645v2Lan3VlanEntry 133453312}

er1645v2Lan3VlanInbBwActEirActEthCos3 OBJECT-TYPE
   SYNTAX      INTEGER
               {
               unchanged (256)
               }
   MAX-ACCESS  read-write
   STATUS      current
   DESCRIPTION
      "Path: ethernet3.editConf.vlan.inboundBandwidth.action.eirAction.ethernet.cosDepth3

       Possibilities:
               unchanged   (256)"
   ::= {er1645v2Lan3VlanEntry 133448448}

er1645v2Lan3VlanInbBwActEirActEthDei3 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth3

       Possibilities:
               unchanged   (255)
               clear   (0)
               set   (1)"
   ::= {er1645v2Lan3VlanEntry 133453568}

er1645v2Lan3VlanInbBwActEirActEthCos4 OBJECT-TYPE
   SYNTAX      INTEGER
               {
               unchanged (256)
               }
   MAX-ACCESS  read-write
   STATUS      current
   DESCRIPTION
      "Path: ethernet3.editConf.vlan.inboundBandwidth.action.eirAction.ethernet.cosDepth4

       Possibilities:
               unchanged   (256)"
   ::= {er1645v2Lan3VlanEntry 133448704}

er1645v2Lan3VlanInbBwActEirActEthDei4 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth4

       Possibilities:
               unchanged   (255)
               clear   (0)
               set   (1)"
   ::= {er1645v2Lan3VlanEntry 133453824}

er1645v2Lan3VlanInbBwActEirActEthCos5 OBJECT-TYPE
   SYNTAX      INTEGER
               {
               unchanged (256)
               }
   MAX-ACCESS  read-write
   STATUS      current
   DESCRIPTION
      "Path: ethernet3.editConf.vlan.inboundBandwidth.action.eirAction.ethernet.cosDepth5

       Possibilities:
               unchanged   (256)"
   ::= {er1645v2Lan3VlanEntry 133448960}

er1645v2Lan3VlanInbBwActEirActEthDei5 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth5

       Possibilities:
               unchanged   (255)
               clear   (0)
               set   (1)"
   ::= {er1645v2Lan3VlanEntry 133454080}

er1645v2Lan3VlanInbBwActEirActEthCos6 OBJECT-TYPE
   SYNTAX      INTEGER
               {
               unchanged (256)
               }
   MAX-ACCESS  read-write
   STATUS      current
   DESCRIPTION
      "Path: ethernet3.editConf.vlan.inboundBandwidth.action.eirAction.ethernet.cosDepth6

       Possibilities:
               unchanged   (256)"
   ::= {er1645v2Lan3VlanEntry 133449216}

er1645v2Lan3VlanInbBwActEirActEthDei6 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth6

       Possibilities:
               unchanged   (255)
               clear   (0)
               set   (1)"
   ::= {er1645v2Lan3VlanEntry 133454336}

er1645v2Lan3VlanInbBwActEirActEthCos7 OBJECT-TYPE
   SYNTAX      INTEGER
               {
               unchanged (256)
               }
   MAX-ACCESS  read-write
   STATUS      current
   DESCRIPTION
      "Path: ethernet3.editConf.vlan.inboundBandwidth.action.eirAction.ethernet.cosDepth7

       Possibilities:
               unchanged   (256)"
   ::= {er1645v2Lan3VlanEntry 133449472}

er1645v2Lan3VlanInbBwActEirActEthDei7 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth7

       Possibilities:
               unchanged   (255)
               clear   (0)
               set   (1)"
   ::= {er1645v2Lan3VlanEntry 133454592}

er1645v2Lan3VlanInbBwActEirActEthCos8 OBJECT-TYPE
   SYNTAX      INTEGER
               {
               unchanged (256)
               }
   MAX-ACCESS  read-write
   STATUS      current
   DESCRIPTION
      "Path: ethernet3.editConf.vlan.inboundBandwidth.action.eirAction.ethernet.cosDepth8

       Possibilities:
               unchanged   (256)"
   ::= {er1645v2Lan3VlanEntry 133449728}

er1645v2Lan3VlanInbBwActEirActEthDei8 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth8

       Possibilities:
               unchanged   (255)
               clear   (0)
               set   (1)"
   ::= {er1645v2Lan3VlanEntry 133454848}

er1645v2Lan3VlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133449984}

er1645v2Lan3VlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133450240}

er1645v2Lan3VlanInbBwActEirActEthDrpLev OBJECT-TYPE
   SYNTAX      INTEGER
               {
               unchanged (0)
               }
   MAX-ACCESS  read-write
   STATUS      current
   DESCRIPTION
      "Path: ethernet3.editConf.vlan.inboundBandwidth.action.eirAction.ethernet.dropLevel

       Possibilities:
               unchanged   (0)"
   ::= {er1645v2Lan3VlanEntry 133450496}

er1645v2Lan3VlanInbBwActEirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deFlag

       Possibilities:
               unchanged   (255)
               clear   (0)
               set   (1)"
   ::= {er1645v2Lan3VlanEntry 133451264}

er1645v2Lan3VlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133474560}

er1645v2Lan3VlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133474816}

er1645v2Lan3VlanInbBwActEirActIpDrpLev OBJECT-TYPE
   SYNTAX      INTEGER
               {
               unchanged (0)
               }
   MAX-ACCESS  read-write
   STATUS      current
   DESCRIPTION
      "Path: ethernet3.editConf.vlan.inboundBandwidth.action.eirAction.ip.dropLevel

       Possibilities:
               unchanged   (0)"
   ::= {er1645v2Lan3VlanEntry 133475072}

er1645v2Lan3VlanInbBwActEirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ip.deFlag

       Possibilities:
               unchanged   (255)
               clear   (0)
               set   (1)"
   ::= {er1645v2Lan3VlanEntry 133475840}

er1645v2Lan3VlanInbBwActViolActNone OBJECT-TYPE
   SYNTAX      OCTET STRING
   MAX-ACCESS  read-write
   STATUS      current
   DESCRIPTION
      "Path: ethernet3.editConf.vlan.inboundBandwidth.action.violateAction.none"
   ::= {er1645v2Lan3VlanEntry 133570560}

er1645v2Lan3VlanInbBwActViolActDrop OBJECT-TYPE
   SYNTAX      OCTET STRING
   MAX-ACCESS  read-write
   STATUS      current
   DESCRIPTION
      "Path: ethernet3.editConf.vlan.inboundBandwidth.action.violateAction.drop"
   ::= {er1645v2Lan3VlanEntry 133586944}

er1645v2Lan3VlanInbBwActViolActEthCos1 OBJECT-TYPE
   SYNTAX      INTEGER
               {
               unchanged (256)
               }
   MAX-ACCESS  read-write
   STATUS      current
   DESCRIPTION
      "Path: ethernet3.editConf.vlan.inboundBandwidth.action.violateAction.ethernet.cosDepth1

       Possibilities:
               unchanged   (256)"
   ::= {er1645v2Lan3VlanEntry 133579008}

er1645v2Lan3VlanInbBwActViolActEthDei1 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth1

       Possibilities:
               unchanged   (255)
               clear   (0)
               set   (1)"
   ::= {er1645v2Lan3VlanEntry 133584128}

er1645v2Lan3VlanInbBwActViolActEthCos2 OBJECT-TYPE
   SYNTAX      INTEGER
               {
               unchanged (256)
               }
   MAX-ACCESS  read-write
   STATUS      current
   DESCRIPTION
      "Path: ethernet3.editConf.vlan.inboundBandwidth.action.violateAction.ethernet.cosDepth2

       Possibilities:
               unchanged   (256)"
   ::= {er1645v2Lan3VlanEntry 133579264}

er1645v2Lan3VlanInbBwActViolActEthDei2 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth2

       Possibilities:
               unchanged   (255)
               clear   (0)
               set   (1)"
   ::= {er1645v2Lan3VlanEntry 133584384}

er1645v2Lan3VlanInbBwActViolActEthCos3 OBJECT-TYPE
   SYNTAX      INTEGER
               {
               unchanged (256)
               }
   MAX-ACCESS  read-write
   STATUS      current
   DESCRIPTION
      "Path: ethernet3.editConf.vlan.inboundBandwidth.action.violateAction.ethernet.cosDepth3

       Possibilities:
               unchanged   (256)"
   ::= {er1645v2Lan3VlanEntry 133579520}

er1645v2Lan3VlanInbBwActViolActEthDei3 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth3

       Possibilities:
               unchanged   (255)
               clear   (0)
               set   (1)"
   ::= {er1645v2Lan3VlanEntry 133584640}

er1645v2Lan3VlanInbBwActViolActEthCos4 OBJECT-TYPE
   SYNTAX      INTEGER
               {
               unchanged (256)
               }
   MAX-ACCESS  read-write
   STATUS      current
   DESCRIPTION
      "Path: ethernet3.editConf.vlan.inboundBandwidth.action.violateAction.ethernet.cosDepth4

       Possibilities:
               unchanged   (256)"
   ::= {er1645v2Lan3VlanEntry 133579776}

er1645v2Lan3VlanInbBwActViolActEthDei4 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth4

       Possibilities:
               unchanged   (255)
               clear   (0)
               set   (1)"
   ::= {er1645v2Lan3VlanEntry 133584896}

er1645v2Lan3VlanInbBwActViolActEthCos5 OBJECT-TYPE
   SYNTAX      INTEGER
               {
               unchanged (256)
               }
   MAX-ACCESS  read-write
   STATUS      current
   DESCRIPTION
      "Path: ethernet3.editConf.vlan.inboundBandwidth.action.violateAction.ethernet.cosDepth5

       Possibilities:
               unchanged   (256)"
   ::= {er1645v2Lan3VlanEntry 133580032}

er1645v2Lan3VlanInbBwActViolActEthDei5 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth5

       Possibilities:
               unchanged   (255)
               clear   (0)
               set   (1)"
   ::= {er1645v2Lan3VlanEntry 133585152}

er1645v2Lan3VlanInbBwActViolActEthCos6 OBJECT-TYPE
   SYNTAX      INTEGER
               {
               unchanged (256)
               }
   MAX-ACCESS  read-write
   STATUS      current
   DESCRIPTION
      "Path: ethernet3.editConf.vlan.inboundBandwidth.action.violateAction.ethernet.cosDepth6

       Possibilities:
               unchanged   (256)"
   ::= {er1645v2Lan3VlanEntry 133580288}

er1645v2Lan3VlanInbBwActViolActEthDei6 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth6

       Possibilities:
               unchanged   (255)
               clear   (0)
               set   (1)"
   ::= {er1645v2Lan3VlanEntry 133585408}

er1645v2Lan3VlanInbBwActViolActEthCos7 OBJECT-TYPE
   SYNTAX      INTEGER
               {
               unchanged (256)
               }
   MAX-ACCESS  read-write
   STATUS      current
   DESCRIPTION
      "Path: ethernet3.editConf.vlan.inboundBandwidth.action.violateAction.ethernet.cosDepth7

       Possibilities:
               unchanged   (256)"
   ::= {er1645v2Lan3VlanEntry 133580544}

er1645v2Lan3VlanInbBwActViolActEthDei7 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth7

       Possibilities:
               unchanged   (255)
               clear   (0)
               set   (1)"
   ::= {er1645v2Lan3VlanEntry 133585664}

er1645v2Lan3VlanInbBwActViolActEthCos8 OBJECT-TYPE
   SYNTAX      INTEGER
               {
               unchanged (256)
               }
   MAX-ACCESS  read-write
   STATUS      current
   DESCRIPTION
      "Path: ethernet3.editConf.vlan.inboundBandwidth.action.violateAction.ethernet.cosDepth8

       Possibilities:
               unchanged   (256)"
   ::= {er1645v2Lan3VlanEntry 133580800}

er1645v2Lan3VlanInbBwActViolActEthDei8 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth8

       Possibilities:
               unchanged   (255)
               clear   (0)
               set   (1)"
   ::= {er1645v2Lan3VlanEntry 133585920}

er1645v2Lan3VlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133581056}

er1645v2Lan3VlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133581312}

er1645v2Lan3VlanInbBwActViolActEthDrpLev OBJECT-TYPE
   SYNTAX      INTEGER
               {
               unchanged (0)
               }
   MAX-ACCESS  read-write
   STATUS      current
   DESCRIPTION
      "Path: ethernet3.editConf.vlan.inboundBandwidth.action.violateAction.ethernet.dropLevel

       Possibilities:
               unchanged   (0)"
   ::= {er1645v2Lan3VlanEntry 133581568}

er1645v2Lan3VlanInbBwActViolActEthDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deFlag

       Possibilities:
               unchanged   (255)
               clear   (0)
               set   (1)"
   ::= {er1645v2Lan3VlanEntry 133582336}

er1645v2Lan3VlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanEntry 133605632}

er1645v2Lan3VlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanEntry 133605888}

er1645v2Lan3VlanInbBwActViolActIpDrpLev OBJECT-TYPE
   SYNTAX      INTEGER
               {
               unchanged (0)
               }
   MAX-ACCESS  read-write
   STATUS      current
   DESCRIPTION
      "Path: ethernet3.editConf.vlan.inboundBandwidth.action.violateAction.ip.dropLevel

       Possibilities:
               unchanged   (0)"
   ::= {er1645v2Lan3VlanEntry 133606144}

er1645v2Lan3VlanInbBwActViolActIpDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ip.deFlag

       Possibilities:
               unchanged   (255)
               clear   (0)
               set   (1)"
   ::= {er1645v2Lan3VlanEntry 133606912}

er1645v2Lan3VlanPppoE OBJECT-TYPE
   SYNTAX      INTEGER
               {
               disabled (0),
               enabled (1)
               }
   MAX-ACCESS  read-write
   STATUS      current
   DESCRIPTION
      "Path: ethernet3.editConf.vlan.pppoE

       Possibilities:
               disabled   (0)
               enabled   (1)"
   ::= {er1645v2Lan3VlanEntry 838860800}

er1645v2Lan3VlanPppLnkMOperation OBJECT-TYPE
   SYNTAX      INTEGER
               {
               disabled (0),
               enabled (1)
               }
   MAX-ACCESS  read-write
   STATUS      current
   DESCRIPTION
      "Path: ethernet3.editConf.vlan.ppp.linkMonitoring.operation

       Possibilities:
               disabled   (0)
               enabled   (1)"
   ::= {er1645v2Lan3VlanEntry 251724032}

er1645v2Lan3VlanPppLnkMInterval OBJECT-TYPE
   SYNTAX      TimeTicks
   MAX-ACCESS  read-write
   STATUS      current
   DESCRIPTION
      "Path: ethernet3.editConf.vlan.ppp.linkMonitoring.interval

       Time in centi-second."
   ::= {er1645v2Lan3VlanEntry 251724288}

er1645v2Lan3VlanPppLnkMRepTimeOut OBJECT-TYPE
   SYNTAX      TimeTicks
   MAX-ACCESS  read-write
   STATUS      current
   DESCRIPTION
      "Path: ethernet3.editConf.vlan.ppp.linkMonitoring.replyTimeOut

       Time in centi-second."
   ::= {er1645v2Lan3VlanEntry 251724544}

er1645v2Lan3VlanPppLnkMFailsPrmt OBJECT-TYPE
   SYNTAX      Integer32
   MAX-ACCESS  read-write
   STATUS      current
   DESCRIPTION
      "Path: ethernet3.editConf.vlan.ppp.linkMonitoring.failsPermitted"
   ::= {er1645v2Lan3VlanEntry 251724800}

er1645v2Lan3VlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.vlan.ppp.authentication

       Possibilities:
               disabled   (0)
               chap   (1)
               pap   (2)
               chapOrPap   (3)
               msChap   (4)
               msChapV2   (5)"
   ::= {er1645v2Lan3VlanEntry 251789312}

er1645v2Lan3VlanPppAuthenPeriod OBJECT-TYPE
   SYNTAX      TimeTicks
   MAX-ACCESS  read-write
   STATUS      current
   DESCRIPTION
      "Path: ethernet3.editConf.vlan.ppp.authenPeriod

       Time in centi-second."
   ::= {er1645v2Lan3VlanEntry 251854848}

er1645v2Lan3VlanPppSessionName OBJECT-TYPE
   SYNTAX      DisplayString
   MAX-ACCESS  read-write
   STATUS      current
   DESCRIPTION
      "Path: ethernet3.editConf.vlan.ppp.sessionName"
   ::= {er1645v2Lan3VlanEntry 251985920}

er1645v2Lan3VlanPppSessionSecret OBJECT-TYPE
   SYNTAX      DisplayString
   MAX-ACCESS  read-write
   STATUS      current
   DESCRIPTION
      "Path: ethernet3.editConf.vlan.ppp.sessionSecret"
   ::= {er1645v2Lan3VlanEntry 252051456}

er1645v2Lan3VlanPppEncModeSessionSecret OBJECT-TYPE
   SYNTAX      INTEGER
               {
               none (1),
               encrypt (2),
               encType1 (3),
               invalid (128)
               }
   MAX-ACCESS  read-write
   STATUS      current
   DESCRIPTION
      "Path: ethernet3.editConf.vlan.ppp.encModeSessionSecret

       Possibilities:
               none   (1)
               encrypt   (2)
               encType1   (3)
               invalid   (128)"
   ::= {er1645v2Lan3VlanEntry 252182528}

er1645v2Lan3VlanPppEncSessionSecret OBJECT-TYPE
   SYNTAX      DisplayString
   MAX-ACCESS  read-write
   STATUS      current
   DESCRIPTION
      "Path: ethernet3.editConf.vlan.ppp.encSessionSecret"
   ::= {er1645v2Lan3VlanEntry 252248064}

er1645v2Lan3VlanPppServiceName OBJECT-TYPE
   SYNTAX      DisplayString
   MAX-ACCESS  read-write
   STATUS      current
   DESCRIPTION
      "Path: ethernet3.editConf.vlan.ppp.serviceName"
   ::= {er1645v2Lan3VlanEntry 252116992}

er1645v2Lan3VlanPbbMode OBJECT-TYPE
   SYNTAX      INTEGER
               {
               disabled (0),
               static (1),
               dynamicPtp (2),
               dynamicPtmp (3)
               }
   MAX-ACCESS  read-write
   STATUS      current
   DESCRIPTION
      "Path: ethernet3.editConf.vlan.pbb.mode

       Possibilities:
               disabled   (0)
               static   (1)
               dynamicPtp   (2)
               dynamicPtmp   (3)"
   ::= {er1645v2Lan3VlanEntry 1174667264}

er1645v2Lan3VlanPbbTxCos OBJECT-TYPE
   SYNTAX      Integer32
   MAX-ACCESS  read-write
   STATUS      current
   DESCRIPTION
      "Path: ethernet3.editConf.vlan.pbb.txCos"
   ::= {er1645v2Lan3VlanEntry 1175191552}

er1645v2Lan3VlanPbbIsid OBJECT-TYPE
   SYNTAX      Integer32
   MAX-ACCESS  read-write
   STATUS      current
   DESCRIPTION
      "Path: ethernet3.editConf.vlan.pbb.isid"
   ::= {er1645v2Lan3VlanEntry 1175453696}

er1645v2Lan3VlanPbbDestMac OBJECT-TYPE
   SYNTAX      OCTET STRING
   MAX-ACCESS  read-write
   STATUS      current
   DESCRIPTION
      "Path: ethernet3.editConf.vlan.pbb.destMac

       MAC address."
   ::= {er1645v2Lan3VlanEntry 1175715840}

er1645v2Lan3VlanPbbCustomGroupMac OBJECT-TYPE
   SYNTAX      OCTET STRING
   MAX-ACCESS  read-write
   STATUS      current
   DESCRIPTION
      "Path: ethernet3.editConf.vlan.pbb.customGroupMac

       MAC address."
   ::= {er1645v2Lan3VlanEntry 1175977984}

er1645v2Lan3VlanIpSaddr OBJECT-TYPE
   SYNTAX      SEQUENCE OF Er1645v2Lan3VlanIpSaddrEntry
   MAX-ACCESS  not-accessible
   STATUS      current
   DESCRIPTION
      ""
   ::= {er1645v2Lan3Vlan 51838976}

er1645v2Lan3VlanIpSaddrEntry OBJECT-TYPE
   SYNTAX      Er1645v2Lan3VlanIpSaddrEntry
   MAX-ACCESS  not-accessible
   STATUS      current
   DESCRIPTION
      ""
   INDEX      { er1645v2Lan3VlanTableIx,
                er1645v2Lan3VlanIpSaddrTableIx }
   ::= {er1645v2Lan3VlanIpSaddr 1}

Er1645v2Lan3VlanIpSaddrEntry ::=
   SEQUENCE
      {
      er1645v2Lan3VlanIpSaddrActions
         VariableLengthTableActions,
      er1645v2Lan3VlanIpSaddrTableIx
         TableIndex,
      er1645v2Lan3VlanIpSaddrAddress
         IpAddress,
      er1645v2Lan3VlanIpSaddrNetMask
         IpAddress
      }

er1645v2Lan3VlanIpSaddrActions OBJECT-TYPE
   SYNTAX      VariableLengthTableActions
   MAX-ACCESS  read-write
   STATUS      current
   DESCRIPTION
      "By way of this field, some manipulations
       on this table may be performed."
   ::= {er1645v2Lan3VlanIpSaddrEntry 2}

er1645v2Lan3VlanIpSaddrTableIx OBJECT-TYPE
   SYNTAX      TableIndex
   MAX-ACCESS  not-accessible
   STATUS      current
   DESCRIPTION
      ""
   ::= {er1645v2Lan3VlanIpSaddrEntry 11}

er1645v2Lan3VlanIpSaddrAddress OBJECT-TYPE
   SYNTAX      IpAddress
   MAX-ACCESS  read-write
   STATUS      current
   DESCRIPTION
      "Path: ethernet3.editConf.vlan.ip.secondaryIp.address"
   ::= {er1645v2Lan3VlanIpSaddrEntry 2030043136}

er1645v2Lan3VlanIpSaddrNetMask OBJECT-TYPE
   SYNTAX      IpAddress
   MAX-ACCESS  read-write
   STATUS      current
   DESCRIPTION
      "Path: ethernet3.editConf.vlan.ip.secondaryIp.netMask"
   ::= {er1645v2Lan3VlanIpSaddrEntry 2063597568}

er1645v2Lan3VlanIpH OBJECT-TYPE
   SYNTAX      SEQUENCE OF Er1645v2Lan3VlanIpHEntry
   MAX-ACCESS  not-accessible
   STATUS      current
   DESCRIPTION
      ""
   ::= {er1645v2Lan3Vlan 51314688}

er1645v2Lan3VlanIpHEntry OBJECT-TYPE
   SYNTAX      Er1645v2Lan3VlanIpHEntry
   MAX-ACCESS  not-accessible
   STATUS      current
   DESCRIPTION
      ""
   INDEX      { er1645v2Lan3VlanTableIx,
                er1645v2Lan3VlanIpHTableIx }
   ::= {er1645v2Lan3VlanIpH 1}

Er1645v2Lan3VlanIpHEntry ::=
   SEQUENCE
      {
      er1645v2Lan3VlanIpHActions
         VariableLengthTableActions,
      er1645v2Lan3VlanIpHTableIx
         TableIndex,
      er1645v2Lan3VlanIpHAddress
         IpAddress,
      er1645v2Lan3VlanIpHDhcpRelayOptionSubscriberId
         DisplayString
      }

er1645v2Lan3VlanIpHActions OBJECT-TYPE
   SYNTAX      VariableLengthTableActions
   MAX-ACCESS  read-write
   STATUS      current
   DESCRIPTION
      "By way of this field, some manipulations
       on this table may be performed."
   ::= {er1645v2Lan3VlanIpHEntry 2}

er1645v2Lan3VlanIpHTableIx OBJECT-TYPE
   SYNTAX      TableIndex
   MAX-ACCESS  not-accessible
   STATUS      current
   DESCRIPTION
      ""
   ::= {er1645v2Lan3VlanIpHEntry 11}

er1645v2Lan3VlanIpHAddress OBJECT-TYPE
   SYNTAX      IpAddress
   MAX-ACCESS  read-write
   STATUS      current
   DESCRIPTION
      "Path: ethernet3.editConf.vlan.ip.helpers.address"
   ::= {er1645v2Lan3VlanIpHEntry 16777216}

er1645v2Lan3VlanIpHDhcpRelayOptionSubscriberId OBJECT-TYPE
   SYNTAX      DisplayString
   MAX-ACCESS  read-write
   STATUS      current
   DESCRIPTION
      "Path: ethernet3.editConf.vlan.ip.helpers.dhcpRelayOption.subscriberId"
   ::= {er1645v2Lan3VlanIpHEntry 33947648}

er1645v2Lan3VlanIpV6Addresses OBJECT-TYPE
   SYNTAX      SEQUENCE OF Er1645v2Lan3VlanIpV6AddressesEntry
   MAX-ACCESS  not-accessible
   STATUS      current
   DESCRIPTION
      ""
   ::= {er1645v2Lan3Vlan 704839680}

er1645v2Lan3VlanIpV6AddressesEntry OBJECT-TYPE
   SYNTAX      Er1645v2Lan3VlanIpV6AddressesEntry
   MAX-ACCESS  not-accessible
   STATUS      current
   DESCRIPTION
      ""
   INDEX      { er1645v2Lan3VlanTableIx,
                er1645v2Lan3VlanIpV6AddressesTableIx }
   ::= {er1645v2Lan3VlanIpV6Addresses 1}

Er1645v2Lan3VlanIpV6AddressesEntry ::=
   SEQUENCE
      {
      er1645v2Lan3VlanIpV6AddressesActions
         VariableLengthTableActions,
      er1645v2Lan3VlanIpV6AddressesTableIx
         TableIndex,
      er1645v2Lan3VlanIpV6AddressesType
         INTEGER,
      er1645v2Lan3VlanIpV6AddressesAddress
         Ipv6Address,
      er1645v2Lan3VlanIpV6AddressesPrefixLength
         Integer32,
      er1645v2Lan3VlanIpV6AddressesGeneralPrefix
         DisplayString,
      er1645v2Lan3VlanIpV6AddressesRaSend
         INTEGER,
      er1645v2Lan3VlanIpV6AddressesRaOnLinkFlag
         INTEGER,
      er1645v2Lan3VlanIpV6AddressesRaAutoFlag
         INTEGER,
      er1645v2Lan3VlanIpV6AddressesRaValidLifeTime
         TimeTicks,
      er1645v2Lan3VlanIpV6AddressesRaValidLTMode
         INTEGER,
      er1645v2Lan3VlanIpV6AddressesRaPrefLifeTime
         TimeTicks,
      er1645v2Lan3VlanIpV6AddressesRaPrefLTMode
         INTEGER
      }

er1645v2Lan3VlanIpV6AddressesActions OBJECT-TYPE
   SYNTAX      VariableLengthTableActions
   MAX-ACCESS  read-write
   STATUS      current
   DESCRIPTION
      "By way of this field, some manipulations
       on this table may be performed."
   ::= {er1645v2Lan3VlanIpV6AddressesEntry 2}

er1645v2Lan3VlanIpV6AddressesTableIx OBJECT-TYPE
   SYNTAX      TableIndex
   MAX-ACCESS  not-accessible
   STATUS      current
   DESCRIPTION
      ""
   ::= {er1645v2Lan3VlanIpV6AddressesEntry 11}

er1645v2Lan3VlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.vlan.ipV6.addresses.type

       Possibilities:
               unicast   (0)
               eui64   (1)
               anycast   (2)
               linkLocal   (3)
               generalPrefix   (4)"
   ::= {er1645v2Lan3VlanIpV6AddressesEntry 50331648}

er1645v2Lan3VlanIpV6AddressesAddress OBJECT-TYPE
   SYNTAX      Ipv6Address
   MAX-ACCESS  read-write
   STATUS      current
   DESCRIPTION
      "Path: ethernet3.editConf.vlan.ipV6.addresses.address

       ipv6 address"
   ::= {er1645v2Lan3VlanIpV6AddressesEntry 16777216}

er1645v2Lan3VlanIpV6AddressesPrefixLength OBJECT-TYPE
   SYNTAX      Integer32
   MAX-ACCESS  read-write
   STATUS      current
   DESCRIPTION
      "Path: ethernet3.editConf.vlan.ipV6.addresses.prefixLength"
   ::= {er1645v2Lan3VlanIpV6AddressesEntry 33554432}

er1645v2Lan3VlanIpV6AddressesGeneralPrefix OBJECT-TYPE
   SYNTAX      DisplayString
   MAX-ACCESS  read-write
   STATUS      current
   DESCRIPTION
      "Path: ethernet3.editConf.vlan.ipV6.addresses.generalPrefix"
   ::= {er1645v2Lan3VlanIpV6AddressesEntry 83886080}

er1645v2Lan3VlanIpV6AddressesRaSend OBJECT-TYPE
   SYNTAX      INTEGER
               {
               disabled (0),
               enabled (1)
               }
   MAX-ACCESS  read-write
   STATUS      current
   DESCRIPTION
      "Path: ethernet3.editConf.vlan.ipV6.addresses.ra.send

       Possibilities:
               disabled   (0)
               enabled   (1)"
   ::= {er1645v2Lan3VlanIpV6AddressesEntry 67174400}

er1645v2Lan3VlanIpV6AddressesRaOnLinkFlag OBJECT-TYPE
   SYNTAX      INTEGER
               {
               disabled (0),
               enabled (1)
               }
   MAX-ACCESS  read-write
   STATUS      current
   DESCRIPTION
      "Path: ethernet3.editConf.vlan.ipV6.addresses.ra.onLinkFlag

       Possibilities:
               disabled   (0)
               enabled   (1)"
   ::= {er1645v2Lan3VlanIpV6AddressesEntry 67371008}

er1645v2Lan3VlanIpV6AddressesRaAutoFlag OBJECT-TYPE
   SYNTAX      INTEGER
               {
               disabled (0),
               enabled (1)
               }
   MAX-ACCESS  read-write
   STATUS      current
   DESCRIPTION
      "Path: ethernet3.editConf.vlan.ipV6.addresses.ra.autonomousFlag

       Possibilities:
               disabled   (0)
               enabled   (1)"
   ::= {er1645v2Lan3VlanIpV6AddressesEntry 67567616}

er1645v2Lan3VlanIpV6AddressesRaValidLifeTime OBJECT-TYPE
   SYNTAX      TimeTicks
   MAX-ACCESS  read-write
   STATUS      current
   DESCRIPTION
      "Path: ethernet3.editConf.vlan.ipV6.addresses.ra.validLifeTime

       Time in centi-second."
   ::= {er1645v2Lan3VlanIpV6AddressesEntry 67239936}

er1645v2Lan3VlanIpV6AddressesRaValidLTMode OBJECT-TYPE
   SYNTAX      INTEGER
               {
               fixed (0),
               infinite (2)
               }
   MAX-ACCESS  read-write
   STATUS      current
   DESCRIPTION
      "Path: ethernet3.editConf.vlan.ipV6.addresses.ra.validLifeTimeMode

       Possibilities:
               fixed   (0)
               infinite   (2)"
   ::= {er1645v2Lan3VlanIpV6AddressesEntry 67305472}

er1645v2Lan3VlanIpV6AddressesRaPrefLifeTime OBJECT-TYPE
   SYNTAX      TimeTicks
   MAX-ACCESS  read-write
   STATUS      current
   DESCRIPTION
      "Path: ethernet3.editConf.vlan.ipV6.addresses.ra.prefLifeTime

       Time in centi-second."
   ::= {er1645v2Lan3VlanIpV6AddressesEntry 67436544}

er1645v2Lan3VlanIpV6AddressesRaPrefLTMode OBJECT-TYPE
   SYNTAX      INTEGER
               {
               fixed (0),
               infinite (2)
               }
   MAX-ACCESS  read-write
   STATUS      current
   DESCRIPTION
      "Path: ethernet3.editConf.vlan.ipV6.addresses.ra.prefLifeTimeMode

       Possibilities:
               fixed   (0)
               infinite   (2)"
   ::= {er1645v2Lan3VlanIpV6AddressesEntry 67502080}

er1645v2Lan3VlanIpV6RaDnsOptionsRdnssServers OBJECT-TYPE
   SYNTAX      SEQUENCE OF Er1645v2Lan3VlanIpV6RaDnsOptionsRdnssServersEntry
   MAX-ACCESS  not-accessible
   STATUS      current
   DESCRIPTION
      ""
   ::= {er1645v2Lan3Vlan 705039144}

er1645v2Lan3VlanIpV6RaDnsOptionsRdnssServersEntry OBJECT-TYPE
   SYNTAX      Er1645v2Lan3VlanIpV6RaDnsOptionsRdnssServersEntry
   MAX-ACCESS  not-accessible
   STATUS      current
   DESCRIPTION
      ""
   INDEX      { er1645v2Lan3VlanTableIx,
                er1645v2Lan3VlanIpV6RaDnsOptionsRdnssServersTableIx }
   ::= {er1645v2Lan3VlanIpV6RaDnsOptionsRdnssServers 1}

Er1645v2Lan3VlanIpV6RaDnsOptionsRdnssServersEntry ::=
   SEQUENCE
      {
      er1645v2Lan3VlanIpV6RaDnsOptionsRdnssServersActions
         VariableLengthTableActions,
      er1645v2Lan3VlanIpV6RaDnsOptionsRdnssServersTableIx
         TableIndex,
      er1645v2Lan3VlanIpV6RaDnsOptionsRdnssServersAddress
         Ipv6Address
      }

er1645v2Lan3VlanIpV6RaDnsOptionsRdnssServersActions OBJECT-TYPE
   SYNTAX      VariableLengthTableActions
   MAX-ACCESS  read-write
   STATUS      current
   DESCRIPTION
      "By way of this field, some manipulations
       on this table may be performed."
   ::= {er1645v2Lan3VlanIpV6RaDnsOptionsRdnssServersEntry 2}

er1645v2Lan3VlanIpV6RaDnsOptionsRdnssServersTableIx OBJECT-TYPE
   SYNTAX      TableIndex
   MAX-ACCESS  not-accessible
   STATUS      current
   DESCRIPTION
      ""
   ::= {er1645v2Lan3VlanIpV6RaDnsOptionsRdnssServersEntry 11}

er1645v2Lan3VlanIpV6RaDnsOptionsRdnssServersAddress OBJECT-TYPE
   SYNTAX      Ipv6Address
   MAX-ACCESS  read-write
   STATUS      current
   DESCRIPTION
      "Path: ethernet3.editConf.vlan.ipV6.ra.dnsOptions.rdnss.servers.address

       ipv6 address"
   ::= {er1645v2Lan3VlanIpV6RaDnsOptionsRdnssServersEntry 16777216}

er1645v2Lan3VlanIpV6RaDnsOptionsDnsslDomains OBJECT-TYPE
   SYNTAX      SEQUENCE OF Er1645v2Lan3VlanIpV6RaDnsOptionsDnsslDomainsEntry
   MAX-ACCESS  not-accessible
   STATUS      current
   DESCRIPTION
      ""
   ::= {er1645v2Lan3Vlan 705039176}

er1645v2Lan3VlanIpV6RaDnsOptionsDnsslDomainsEntry OBJECT-TYPE
   SYNTAX      Er1645v2Lan3VlanIpV6RaDnsOptionsDnsslDomainsEntry
   MAX-ACCESS  not-accessible
   STATUS      current
   DESCRIPTION
      ""
   INDEX      { er1645v2Lan3VlanTableIx,
                er1645v2Lan3VlanIpV6RaDnsOptionsDnsslDomainsTableIx }
   ::= {er1645v2Lan3VlanIpV6RaDnsOptionsDnsslDomains 1}

Er1645v2Lan3VlanIpV6RaDnsOptionsDnsslDomainsEntry ::=
   SEQUENCE
      {
      er1645v2Lan3VlanIpV6RaDnsOptionsDnsslDomainsActions
         VariableLengthTableActions,
      er1645v2Lan3VlanIpV6RaDnsOptionsDnsslDomainsTableIx
         TableIndex,
      er1645v2Lan3VlanIpV6RaDnsOptionsDnsslDomainsName
         DisplayString
      }

er1645v2Lan3VlanIpV6RaDnsOptionsDnsslDomainsActions OBJECT-TYPE
   SYNTAX      VariableLengthTableActions
   MAX-ACCESS  read-write
   STATUS      current
   DESCRIPTION
      "By way of this field, some manipulations
       on this table may be performed."
   ::= {er1645v2Lan3VlanIpV6RaDnsOptionsDnsslDomainsEntry 2}

er1645v2Lan3VlanIpV6RaDnsOptionsDnsslDomainsTableIx OBJECT-TYPE
   SYNTAX      TableIndex
   MAX-ACCESS  not-accessible
   STATUS      current
   DESCRIPTION
      ""
   ::= {er1645v2Lan3VlanIpV6RaDnsOptionsDnsslDomainsEntry 11}

er1645v2Lan3VlanIpV6RaDnsOptionsDnsslDomainsName OBJECT-TYPE
   SYNTAX      DisplayString
   MAX-ACCESS  read-write
   STATUS      current
   DESCRIPTION
      "Path: ethernet3.editConf.vlan.ipV6.ra.dnsOptions.dnssl.domains.name"
   ::= {er1645v2Lan3VlanIpV6RaDnsOptionsDnsslDomainsEntry 16777216}

er1645v2Lan3VlanIpV6DhcpClientUserClassOpt OBJECT-TYPE
   SYNTAX      SEQUENCE OF Er1645v2Lan3VlanIpV6DhcpClientUserClassOptEntry
   MAX-ACCESS  not-accessible
   STATUS      current
   DESCRIPTION
      ""
   ::= {er1645v2Lan3Vlan 705312768}

er1645v2Lan3VlanIpV6DhcpClientUserClassOptEntry OBJECT-TYPE
   SYNTAX      Er1645v2Lan3VlanIpV6DhcpClientUserClassOptEntry
   MAX-ACCESS  not-accessible
   STATUS      current
   DESCRIPTION
      ""
   INDEX      { er1645v2Lan3VlanTableIx,
                er1645v2Lan3VlanIpV6DhcpClientUserClassOptTableIx }
   ::= {er1645v2Lan3VlanIpV6DhcpClientUserClassOpt 1}

Er1645v2Lan3VlanIpV6DhcpClientUserClassOptEntry ::=
   SEQUENCE
      {
      er1645v2Lan3VlanIpV6DhcpClientUserClassOptActions
         VariableLengthTableActions,
      er1645v2Lan3VlanIpV6DhcpClientUserClassOptTableIx
         TableIndex,
      er1645v2Lan3VlanIpV6DhcpClientUserClassOptValueAscii
         DisplayString,
      er1645v2Lan3VlanIpV6DhcpClientUserClassOptValueDecimal
         Integer32,
      er1645v2Lan3VlanIpV6DhcpClientUserClassOptValueHexData
         OCTET STRING
      }

er1645v2Lan3VlanIpV6DhcpClientUserClassOptActions OBJECT-TYPE
   SYNTAX      VariableLengthTableActions
   MAX-ACCESS  read-write
   STATUS      current
   DESCRIPTION
      "By way of this field, some manipulations
       on this table may be performed."
   ::= {er1645v2Lan3VlanIpV6DhcpClientUserClassOptEntry 2}

er1645v2Lan3VlanIpV6DhcpClientUserClassOptTableIx OBJECT-TYPE
   SYNTAX      TableIndex
   MAX-ACCESS  not-accessible
   STATUS      current
   DESCRIPTION
      ""
   ::= {er1645v2Lan3VlanIpV6DhcpClientUserClassOptEntry 11}

er1645v2Lan3VlanIpV6DhcpClientUserClassOptValueAscii OBJECT-TYPE
   SYNTAX      DisplayString
   MAX-ACCESS  read-write
   STATUS      current
   DESCRIPTION
      "Path: ethernet3.editConf.vlan.ipV6.dhcp.client.userClassOpt.value.ascii"
   ::= {er1645v2Lan3VlanIpV6DhcpClientUserClassOptEntry 16842752}

er1645v2Lan3VlanIpV6DhcpClientUserClassOptValueDecimal OBJECT-TYPE
   SYNTAX      Integer32
   MAX-ACCESS  read-write
   STATUS      current
   DESCRIPTION
      "Path: ethernet3.editConf.vlan.ipV6.dhcp.client.userClassOpt.value.decimal"
   ::= {er1645v2Lan3VlanIpV6DhcpClientUserClassOptEntry 16908288}

er1645v2Lan3VlanIpV6DhcpClientUserClassOptValueHexData OBJECT-TYPE
   SYNTAX      OCTET STRING
   MAX-ACCESS  read-write
   STATUS      current
   DESCRIPTION
      "Path: ethernet3.editConf.vlan.ipV6.dhcp.client.userClassOpt.value.hexData"
   ::= {er1645v2Lan3VlanIpV6DhcpClientUserClassOptEntry 16973824}

er1645v2Lan3VlanIpV6DhcpClientVendorCl OBJECT-TYPE
   SYNTAX      SEQUENCE OF Er1645v2Lan3VlanIpV6DhcpClientVendorClEntry
   MAX-ACCESS  not-accessible
   STATUS      current
   DESCRIPTION
      ""
   ::= {er1645v2Lan3Vlan 705313792}

er1645v2Lan3VlanIpV6DhcpClientVendorClEntry OBJECT-TYPE
   SYNTAX      Er1645v2Lan3VlanIpV6DhcpClientVendorClEntry
   MAX-ACCESS  not-accessible
   STATUS      current
   DESCRIPTION
      ""
   INDEX      { er1645v2Lan3VlanTableIx,
                er1645v2Lan3VlanIpV6DhcpClientVendorClTableIx }
   ::= {er1645v2Lan3VlanIpV6DhcpClientVendorCl 1}

Er1645v2Lan3VlanIpV6DhcpClientVendorClEntry ::=
   SEQUENCE
      {
      er1645v2Lan3VlanIpV6DhcpClientVendorClActions
         VariableLengthTableActions,
      er1645v2Lan3VlanIpV6DhcpClientVendorClTableIx
         TableIndex,
      er1645v2Lan3VlanIpV6DhcpClientVendorClValueAscii
         DisplayString,
      er1645v2Lan3VlanIpV6DhcpClientVendorClValueDecimal
         Integer32,
      er1645v2Lan3VlanIpV6DhcpClientVendorClValueHexData
         OCTET STRING
      }

er1645v2Lan3VlanIpV6DhcpClientVendorClActions OBJECT-TYPE
   SYNTAX      VariableLengthTableActions
   MAX-ACCESS  read-write
   STATUS      current
   DESCRIPTION
      "By way of this field, some manipulations
       on this table may be performed."
   ::= {er1645v2Lan3VlanIpV6DhcpClientVendorClEntry 2}

er1645v2Lan3VlanIpV6DhcpClientVendorClTableIx OBJECT-TYPE
   SYNTAX      TableIndex
   MAX-ACCESS  not-accessible
   STATUS      current
   DESCRIPTION
      ""
   ::= {er1645v2Lan3VlanIpV6DhcpClientVendorClEntry 11}

er1645v2Lan3VlanIpV6DhcpClientVendorClValueAscii OBJECT-TYPE
   SYNTAX      DisplayString
   MAX-ACCESS  read-write
   STATUS      current
   DESCRIPTION
      "Path: ethernet3.editConf.vlan.ipV6.dhcp.client.vendorClassOpt.value.ascii"
   ::= {er1645v2Lan3VlanIpV6DhcpClientVendorClEntry 16842752}

er1645v2Lan3VlanIpV6DhcpClientVendorClValueDecimal OBJECT-TYPE
   SYNTAX      Integer32
   MAX-ACCESS  read-write
   STATUS      current
   DESCRIPTION
      "Path: ethernet3.editConf.vlan.ipV6.dhcp.client.vendorClassOpt.value.decimal"
   ::= {er1645v2Lan3VlanIpV6DhcpClientVendorClEntry 16908288}

er1645v2Lan3VlanIpV6DhcpClientVendorClValueHexData OBJECT-TYPE
   SYNTAX      OCTET STRING
   MAX-ACCESS  read-write
   STATUS      current
   DESCRIPTION
      "Path: ethernet3.editConf.vlan.ipV6.dhcp.client.vendorClassOpt.value.hexData"
   ::= {er1645v2Lan3VlanIpV6DhcpClientVendorClEntry 16973824}

er1645v2Lan3VlanIpV6DhcpRelayDestinations OBJECT-TYPE
   SYNTAX      SEQUENCE OF Er1645v2Lan3VlanIpV6DhcpRelayDestinationsEntry
   MAX-ACCESS  not-accessible
   STATUS      current
   DESCRIPTION
      ""
   ::= {er1645v2Lan3Vlan 705323072}

er1645v2Lan3VlanIpV6DhcpRelayDestinationsEntry OBJECT-TYPE
   SYNTAX      Er1645v2Lan3VlanIpV6DhcpRelayDestinationsEntry
   MAX-ACCESS  not-accessible
   STATUS      current
   DESCRIPTION
      ""
   INDEX      { er1645v2Lan3VlanTableIx,
                er1645v2Lan3VlanIpV6DhcpRelayDestinationsTableIx }
   ::= {er1645v2Lan3VlanIpV6DhcpRelayDestinations 1}

Er1645v2Lan3VlanIpV6DhcpRelayDestinationsEntry ::=
   SEQUENCE
      {
      er1645v2Lan3VlanIpV6DhcpRelayDestinationsActions
         VariableLengthTableActions,
      er1645v2Lan3VlanIpV6DhcpRelayDestinationsTableIx
         TableIndex,
      er1645v2Lan3VlanIpV6DhcpRelayDestinationsAddress
         Ipv6Address,
      er1645v2Lan3VlanIpV6DhcpRelayDestinationsInterface
         DisplayString
      }

er1645v2Lan3VlanIpV6DhcpRelayDestinationsActions OBJECT-TYPE
   SYNTAX      VariableLengthTableActions
   MAX-ACCESS  read-write
   STATUS      current
   DESCRIPTION
      "By way of this field, some manipulations
       on this table may be performed."
   ::= {er1645v2Lan3VlanIpV6DhcpRelayDestinationsEntry 2}

er1645v2Lan3VlanIpV6DhcpRelayDestinationsTableIx OBJECT-TYPE
   SYNTAX      TableIndex
   MAX-ACCESS  not-accessible
   STATUS      current
   DESCRIPTION
      ""
   ::= {er1645v2Lan3VlanIpV6DhcpRelayDestinationsEntry 11}

er1645v2Lan3VlanIpV6DhcpRelayDestinationsAddress OBJECT-TYPE
   SYNTAX      Ipv6Address
   MAX-ACCESS  read-write
   STATUS      current
   DESCRIPTION
      "Path: ethernet3.editConf.vlan.ipV6.dhcp.relay.destinations.address

       ipv6 address"
   ::= {er1645v2Lan3VlanIpV6DhcpRelayDestinationsEntry 16777216}

er1645v2Lan3VlanIpV6DhcpRelayDestinationsInterface OBJECT-TYPE
   SYNTAX      DisplayString
   MAX-ACCESS  read-write
   STATUS      current
   DESCRIPTION
      "Path: ethernet3.editConf.vlan.ipV6.dhcp.relay.destinations.interface"
   ::= {er1645v2Lan3VlanIpV6DhcpRelayDestinationsEntry 33554432}

er1645v2Lan3VlanBridgingVlTVlans OBJECT-TYPE
   SYNTAX      SEQUENCE OF Er1645v2Lan3VlanBridgingVlTVlansEntry
   MAX-ACCESS  not-accessible
   STATUS      current
   DESCRIPTION
      ""
   ::= {er1645v2Lan3Vlan 459079680}

er1645v2Lan3VlanBridgingVlTVlansEntry OBJECT-TYPE
   SYNTAX      Er1645v2Lan3VlanBridgingVlTVlansEntry
   MAX-ACCESS  not-accessible
   STATUS      current
   DESCRIPTION
      ""
   INDEX      { er1645v2Lan3VlanTableIx,
                er1645v2Lan3VlanBridgingVlTVlansTableIx }
   ::= {er1645v2Lan3VlanBridgingVlTVlans 1}

Er1645v2Lan3VlanBridgingVlTVlansEntry ::=
   SEQUENCE
      {
      er1645v2Lan3VlanBridgingVlTVlansActions
         VariableLengthTableActions,
      er1645v2Lan3VlanBridgingVlTVlansTableIx
         TableIndex,
      er1645v2Lan3VlanBridgingVlTVlansVid
         Integer32,
      er1645v2Lan3VlanBridgingVlTVlansEndVid
         Integer32,
      er1645v2Lan3VlanBridgingVlTVlansAction
         INTEGER,
      er1645v2Lan3VlanBridgingVlTVlansTagInfoTpid
         INTEGER,
      er1645v2Lan3VlanBridgingVlTVlansTagInfoVid
         Integer32
      }

er1645v2Lan3VlanBridgingVlTVlansActions OBJECT-TYPE
   SYNTAX      VariableLengthTableActions
   MAX-ACCESS  read-write
   STATUS      current
   DESCRIPTION
      "By way of this field, some manipulations
       on this table may be performed."
   ::= {er1645v2Lan3VlanBridgingVlTVlansEntry 2}

er1645v2Lan3VlanBridgingVlTVlansTableIx OBJECT-TYPE
   SYNTAX      TableIndex
   MAX-ACCESS  not-accessible
   STATUS      current
   DESCRIPTION
      ""
   ::= {er1645v2Lan3VlanBridgingVlTVlansEntry 11}

er1645v2Lan3VlanBridgingVlTVlansVid OBJECT-TYPE
   SYNTAX      Integer32
   MAX-ACCESS  read-write
   STATUS      current
   DESCRIPTION
      "Path: ethernet3.editConf.vlan.bridging.vlanTagging.vlans.vid"
   ::= {er1645v2Lan3VlanBridgingVlTVlansEntry 536870912}

er1645v2Lan3VlanBridgingVlTVlansEndVid OBJECT-TYPE
   SYNTAX      Integer32
   MAX-ACCESS  read-write
   STATUS      current
   DESCRIPTION
      "Path: ethernet3.editConf.vlan.bridging.vlanTagging.vlans.endVid"
   ::= {er1645v2Lan3VlanBridgingVlTVlansEntry 2147483648}

er1645v2Lan3VlanBridgingVlTVlansAction OBJECT-TYPE
   SYNTAX      INTEGER
               {
               discard (0),
               accept (1),
               tag (2)
               }
   MAX-ACCESS  read-write
   STATUS      current
   DESCRIPTION
      "Path: ethernet3.editConf.vlan.bridging.vlanTagging.vlans.action

       Possibilities:
               discard   (0)
               accept   (1)
               tag   (2)"
   ::= {er1645v2Lan3VlanBridgingVlTVlansEntry 1073741824}

er1645v2Lan3VlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.vlans.tagInfo.tpid

       Possibilities:
               dot1Q   (33024)
               dot1ad   (34984)
               0x9100   (37120)
               0x9200   (37376)
               0x9300   (37632)"
   ::= {er1645v2Lan3VlanBridgingVlTVlansEntry 1677721600}

er1645v2Lan3VlanBridgingVlTVlansTagInfoVid OBJECT-TYPE
   SYNTAX      Integer32
   MAX-ACCESS  read-write
   STATUS      current
   DESCRIPTION
      "Path: ethernet3.editConf.vlan.bridging.vlanTagging.vlans.tagInfo.vid"
   ::= {er1645v2Lan3VlanBridgingVlTVlansEntry 1744830464}

er1645v2Lan3VlanVlanVidExtensionTable OBJECT-TYPE
   SYNTAX      SEQUENCE OF Er1645v2Lan3VlanVlanVidExtensionTableEntry
   MAX-ACCESS  not-accessible
   STATUS      current
   DESCRIPTION
      ""
   ::= {er1645v2Lan3Vlan 235340544}

er1645v2Lan3VlanVlanVidExtensionTableEntry OBJECT-TYPE
   SYNTAX      Er1645v2Lan3VlanVlanVidExtensionTableEntry
   MAX-ACCESS  not-accessible
   STATUS      current
   DESCRIPTION
      ""
   INDEX      { er1645v2Lan3VlanTableIx,
                er1645v2Lan3VlanVlanVidExtensionTableTableIx }
   ::= {er1645v2Lan3VlanVlanVidExtensionTable 1}

Er1645v2Lan3VlanVlanVidExtensionTableEntry ::=
   SEQUENCE
      {
      er1645v2Lan3VlanVlanVidExtensionTableActions
         VariableLengthTableActions,
      er1645v2Lan3VlanVlanVidExtensionTableTableIx
         TableIndex,
      er1645v2Lan3VlanVlanVidExtensionTableTpid
         INTEGER,
      er1645v2Lan3VlanVlanVidExtensionTableVid
         Integer32,
      er1645v2Lan3VlanVlanVidExtensionTableEndVid
         Integer32
      }

er1645v2Lan3VlanVlanVidExtensionTableActions OBJECT-TYPE
   SYNTAX      VariableLengthTableActions
   MAX-ACCESS  read-write
   STATUS      current
   DESCRIPTION
      "By way of this field, some manipulations
       on this table may be performed."
   ::= {er1645v2Lan3VlanVlanVidExtensionTableEntry 2}

er1645v2Lan3VlanVlanVidExtensionTableTableIx OBJECT-TYPE
   SYNTAX      TableIndex
   MAX-ACCESS  not-accessible
   STATUS      current
   DESCRIPTION
      ""
   ::= {er1645v2Lan3VlanVlanVidExtensionTableEntry 11}

er1645v2Lan3VlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.vidExtension.table.tpid

       Possibilities:
               dot1Q   (33024)
               dot1ad   (34984)
               0x9100   (37120)
               0x9200   (37376)
               0x9300   (37632)"
   ::= {er1645v2Lan3VlanVlanVidExtensionTableEntry 16777216}

er1645v2Lan3VlanVlanVidExtensionTableVid OBJECT-TYPE
   SYNTAX      Integer32
   MAX-ACCESS  read-write
   STATUS      current
   DESCRIPTION
      "Path: ethernet3.editConf.vlan.vlan.vidExtension.table.vid"
   ::= {er1645v2Lan3VlanVlanVidExtensionTableEntry 33554432}

er1645v2Lan3VlanVlanVidExtensionTableEndVid OBJECT-TYPE
   SYNTAX      Integer32
   MAX-ACCESS  read-write
   STATUS      current
   DESCRIPTION
      "Path: ethernet3.editConf.vlan.vlan.vidExtension.table.endVid"
   ::= {er1645v2Lan3VlanVlanVidExtensionTableEntry 50331648}

er1645v2Lan3VlanVlanCSMap OBJECT-TYPE
   SYNTAX      SEQUENCE OF Er1645v2Lan3VlanVlanCSMapEntry
   MAX-ACCESS  not-accessible
   STATUS      current
   DESCRIPTION
      ""
   ::= {er1645v2Lan3Vlan 235405312}

er1645v2Lan3VlanVlanCSMapEntry OBJECT-TYPE
   SYNTAX      Er1645v2Lan3VlanVlanCSMapEntry
   MAX-ACCESS  not-accessible
   STATUS      current
   DESCRIPTION
      ""
   INDEX      { er1645v2Lan3VlanTableIx,
                er1645v2Lan3VlanVlanCSMapTableIx }
   ::= {er1645v2Lan3VlanVlanCSMap 1}

Er1645v2Lan3VlanVlanCSMapEntry ::=
   SEQUENCE
      {
      er1645v2Lan3VlanVlanCSMapActions
         VariableLengthTableActions,
      er1645v2Lan3VlanVlanCSMapTableIx
         TableIndex,
      er1645v2Lan3VlanVlanCSMapCos
         INTEGER,
      er1645v2Lan3VlanVlanCSMapDei
         INTEGER,
      er1645v2Lan3VlanVlanCSMapTos
         INTEGER,
      er1645v2Lan3VlanVlanCSMapQueue
         INTEGER,
      er1645v2Lan3VlanVlanCSMapDropLevel
         INTEGER,
      er1645v2Lan3VlanVlanCSMapDeFlag
         INTEGER
      }

er1645v2Lan3VlanVlanCSMapActions OBJECT-TYPE
   SYNTAX      VariableLengthTableActions
   MAX-ACCESS  read-write
   STATUS      current
   DESCRIPTION
      "By way of this field, some manipulations
       on this table may be performed."
   ::= {er1645v2Lan3VlanVlanCSMapEntry 2}

er1645v2Lan3VlanVlanCSMapTableIx OBJECT-TYPE
   SYNTAX      TableIndex
   MAX-ACCESS  not-accessible
   STATUS      current
   DESCRIPTION
      ""
   ::= {er1645v2Lan3VlanVlanCSMapEntry 11}

er1645v2Lan3VlanVlanCSMapCos OBJECT-TYPE
   SYNTAX      INTEGER
               {
               any (8)
               }
   MAX-ACCESS  read-write
   STATUS      current
   DESCRIPTION
      "Path: ethernet3.editConf.vlan.vlan.cosMap.cos

       Possibilities:
               any   (8)"
   ::= {er1645v2Lan3VlanVlanCSMapEntry 16777216}

er1645v2Lan3VlanVlanCSMapDei OBJECT-TYPE
   SYNTAX      INTEGER
               {
               clear (0),
               set (1),
               any (2)
               }
   MAX-ACCESS  read-write
   STATUS      current
   DESCRIPTION
      "Path: ethernet3.editConf.vlan.vlan.cosMap.dei

       Possibilities:
               clear   (0)
               set   (1)
               any   (2)"
   ::= {er1645v2Lan3VlanVlanCSMapEntry 33554432}

er1645v2Lan3VlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3VlanVlanCSMapEntry 50331648}

er1645v2Lan3VlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2Lan3VlanVlanCSMapEntry 67108864}

er1645v2Lan3VlanVlanCSMapDropLevel OBJECT-TYPE
   SYNTAX      INTEGER
               {
               unchanged (-1),
               dropOnQueue (0)
               }
   MAX-ACCESS  read-write
   STATUS      current
   DESCRIPTION
      "Path: ethernet3.editConf.vlan.vlan.cosMap.dropLevel

       Possibilities:
               unchanged   (-1)
               dropOnQueue   (0)"
   ::= {er1645v2Lan3VlanVlanCSMapEntry 83886080}

er1645v2Lan3VlanVlanCSMapDeFlag OBJECT-TYPE
   SYNTAX      INTEGER
               {
               unchanged (255),
               clear (0),
               set (1)
               }
   MAX-ACCESS  read-write
   STATUS      current
   DESCRIPTION
      "Path: ethernet3.editConf.vlan.vlan.cosMap.deFlag

       Possibilities:
               unchanged   (255)
               clear   (0)
               set   (1)"
   ::= {er1645v2Lan3VlanVlanCSMapEntry 117440512}

er1645v2Lan3VlanVlanTCMap OBJECT-TYPE
   SYNTAX      SEQUENCE OF Er1645v2Lan3VlanVlanTCMapEntry
   MAX-ACCESS  not-accessible
   STATUS      current
   DESCRIPTION
      ""
   ::= {er1645v2Lan3Vlan 241369088}

er1645v2Lan3VlanVlanTCMapEntry OBJECT-TYPE
   SYNTAX      Er1645v2Lan3VlanVlanTCMapEntry
   MAX-ACCESS  not-accessible
   STATUS      current
   DESCRIPTION
      ""
   INDEX      { er1645v2Lan3VlanTableIx,
                er1645v2Lan3VlanVlanTCMapTableIx }
   ::= {er1645v2Lan3VlanVlanTCMap 1}

Er1645v2Lan3VlanVlanTCMapEntry ::=
   SEQUENCE
      {
      er1645v2Lan3VlanVlanTCMapActions
         VariableLengthTableActions,
      er1645v2Lan3VlanVlanTCMapTableIx
         TableIndex,
      er1645v2Lan3VlanVlanTCMapStartTos
         INTEGER,
      er1645v2Lan3VlanVlanTCMapEndTos
         INTEGER,
      er1645v2Lan3VlanVlanTCMapCos
         INTEGER
      }

er1645v2Lan3VlanVlanTCMapActions OBJECT-TYPE
   SYNTAX      VariableLengthTableActions
   MAX-ACCESS  read-write
   STATUS      current
   DESCRIPTION
      "By way of this field, some manipulations
       on this table may be performed."
   ::= {er1645v2Lan3VlanVlanTCMapEntry 2}

er1645v2Lan3VlanVlanTCMapTableIx OBJECT-TYPE
   SYNTAX      TableIndex
   MAX-ACCESS  not-accessible
   STATUS      current
   DESCRIPTION
      ""
   ::= {er1645v2Lan3VlanVlanTCMapEntry 11}

er1645v2Lan3VlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan3VlanVlanTCMapEntry 16777216}

er1645v2Lan3VlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan3VlanVlanTCMapEntry 33554432}

er1645v2Lan3VlanVlanTCMapCos OBJECT-TYPE
   SYNTAX      INTEGER
               {
               queueCosMap (8)
               }
   MAX-ACCESS  read-write
   STATUS      current
   DESCRIPTION
      "Path: ethernet3.editConf.vlan.vlan.tosCosMap.cos

       Possibilities:
               queueCosMap   (8)"
   ::= {er1645v2Lan3VlanVlanTCMapEntry 50331648}

er1645v2Lan3VlanVlanArpStaticArp OBJECT-TYPE
   SYNTAX      SEQUENCE OF Er1645v2Lan3VlanVlanArpStaticArpEntry
   MAX-ACCESS  not-accessible
   STATUS      current
   DESCRIPTION
      ""
   ::= {er1645v2Lan3Vlan 235275008}

er1645v2Lan3VlanVlanArpStaticArpEntry OBJECT-TYPE
   SYNTAX      Er1645v2Lan3VlanVlanArpStaticArpEntry
   MAX-ACCESS  not-accessible
   STATUS      current
   DESCRIPTION
      ""
   INDEX      { er1645v2Lan3VlanTableIx,
                er1645v2Lan3VlanVlanArpStaticArpTableIx }
   ::= {er1645v2Lan3VlanVlanArpStaticArp 1}

Er1645v2Lan3VlanVlanArpStaticArpEntry ::=
   SEQUENCE
      {
      er1645v2Lan3VlanVlanArpStaticArpActions
         VariableLengthTableActions,
      er1645v2Lan3VlanVlanArpStaticArpTableIx
         TableIndex,
      er1645v2Lan3VlanVlanArpStaticArpMacAddress
         OCTET STRING,
      er1645v2Lan3VlanVlanArpStaticArpIpAddress
         IpAddress
      }

er1645v2Lan3VlanVlanArpStaticArpActions OBJECT-TYPE
   SYNTAX      VariableLengthTableActions
   MAX-ACCESS  read-write
   STATUS      current
   DESCRIPTION
      "By way of this field, some manipulations
       on this table may be performed."
   ::= {er1645v2Lan3VlanVlanArpStaticArpEntry 2}

er1645v2Lan3VlanVlanArpStaticArpTableIx OBJECT-TYPE
   SYNTAX      TableIndex
   MAX-ACCESS  not-accessible
   STATUS      current
   DESCRIPTION
      ""
   ::= {er1645v2Lan3VlanVlanArpStaticArpEntry 11}

er1645v2Lan3VlanVlanArpStaticArpMacAddress OBJECT-TYPE
   SYNTAX      OCTET STRING
   MAX-ACCESS  read-write
   STATUS      current
   DESCRIPTION
      "Path: ethernet3.editConf.vlan.vlan.arp.staticArp.macAddress

       MAC address."
   ::= {er1645v2Lan3VlanVlanArpStaticArpEntry 16777216}

er1645v2Lan3VlanVlanArpStaticArpIpAddress OBJECT-TYPE
   SYNTAX      IpAddress
   MAX-ACCESS  read-write
   STATUS      current
   DESCRIPTION
      "Path: ethernet3.editConf.vlan.vlan.arp.staticArp.ipAddress"
   ::= {er1645v2Lan3VlanVlanArpStaticArpEntry 33554432}


er1645v2Lan3PppOE OBJECT IDENTIFIER ::= {er1645v2Lan3 35}

er1645v2Lan3PppOESSCTable OBJECT-TYPE
   SYNTAX      SEQUENCE OF Er1645v2Lan3PppOEEntry
   MAX-ACCESS  not-accessible
   STATUS      current
   DESCRIPTION
      ""
   ::= {er1645v2Lan3PppOE 1}

er1645v2Lan3PppOEEntry OBJECT-TYPE
   SYNTAX      Er1645v2Lan3PppOEEntry
   MAX-ACCESS  not-accessible
   STATUS      current
   DESCRIPTION
      ""
   INDEX      { er1645v2Lan3PppOETableIx }
   ::= {er1645v2Lan3PppOESSCTable 1}

Er1645v2Lan3PppOEEntry ::=
   SEQUENCE
      {
      er1645v2Lan3PppOEActions
         VariableLengthTableActions,
      er1645v2Lan3PppOETableIx
         TableIndex,
      er1645v2Lan3PppOEName
         DisplayString,
      er1645v2Lan3PppOERemark
         DisplayString,
      er1645v2Lan3PppOEAdminStatus
         INTEGER,
      er1645v2Lan3PppOEMode
         INTEGER,
      er1645v2Lan3PppOEIpVrfRouter
         DisplayString,
      er1645v2Lan3PppOEIpAdr
         IpAddress,
      er1645v2Lan3PppOEIpNetm
         IpAddress,
      er1645v2Lan3PppOEIpSNetName
         INTEGER,
      er1645v2Lan3PppOEIpSNetCust
         DisplayString,
      er1645v2Lan3PppOEIpRem
         IpAddress,
      er1645v2Lan3PppOEIpUnnumbered
         DisplayString,
      er1645v2Lan3PppOEIpGwPref
         Integer32,
      er1645v2Lan3PppOEIpRsn
         INTEGER,
      er1645v2Lan3PppOEIpMtu
         Integer32,
      er1645v2Lan3PppOEIpMssAdjust
         INTEGER,
      er1645v2Lan3PppOEIpRipMetric
         Integer32,
      er1645v2Lan3PppOEIpRipMetricOut
         Integer32,
      er1645v2Lan3PppOEIpRipMode
         INTEGER,
      er1645v2Lan3PppOEIpRipTxVer
         INTEGER,
      er1645v2Lan3PppOEIpRipRxVer
         INTEGER,
      er1645v2Lan3PppOEIpRipSplitH
         INTEGER,
      er1645v2Lan3PppOEIpRipAuth
         INTEGER,
      er1645v2Lan3PppOEIpRipFilter
         DisplayString,
      er1645v2Lan3PppOEIpRipFilterIn
         DisplayString,
      er1645v2Lan3PppOEIpRipClearNextHop
         INTEGER,
      er1645v2Lan3PppOEIpAccPol
         DisplayString,
      er1645v2Lan3PppOEIpAB
         DisplayString,
      er1645v2Lan3PppOEIpMA
         INTEGER,
      er1645v2Lan3PppOEIpMF
         Integer32,
      er1645v2Lan3PppOEIpDB
         INTEGER,
      er1645v2Lan3PppOEIpIR
         INTEGER,
      er1645v2Lan3PppOEIpIgmp
         INTEGER,
      er1645v2Lan3PppOEIpNN
         DisplayString,
      er1645v2Lan3PppOEIpPimMode
         INTEGER,
      er1645v2Lan3PppOEIpPimDrPriority
         Counter32,
      er1645v2Lan3PppOEIpPimHelloTime
         TimeTicks,
      er1645v2Lan3PppOEIpPimPropagationDelay
         TimeTicks,
      er1645v2Lan3PppOEIpPimOverrideInterval
         TimeTicks,
      er1645v2Lan3PppOEIpPimBsrBorder
         INTEGER,
      er1645v2Lan3PppOEIpPimTtlThreshold
         Integer32,
      er1645v2Lan3PppOEIpIMNetworkUnreachable
         INTEGER,
      er1645v2Lan3PppOEIpIMHostUnreachable
         INTEGER,
      er1645v2Lan3PppOEIpIMProtocolUnreachable
         INTEGER,
      er1645v2Lan3PppOEIpIMPortUnreachable
         INTEGER,
      er1645v2Lan3PppOEIpIMMtuExceeded
         INTEGER,
      er1645v2Lan3PppOEIpIMAdminProhibited
         INTEGER,
      er1645v2Lan3PppOEIpIMTtlExceeded
         INTEGER,
      er1645v2Lan3PppOEIpIMRedirect
         INTEGER,
      er1645v2Lan3PppOEIpV6VrfRouter
         DisplayString,
      er1645v2Lan3PppOEIpV6AddrAutoConfigNrDupAddrDetects
         Integer32,
      er1645v2Lan3PppOEIpV6AddrAutoConfigAcceptRa
         INTEGER,
      er1645v2Lan3PppOEIpV6AddrAutoConfigAcceptRaRdnss
         INTEGER,
      er1645v2Lan3PppOEIpV6AddrAutoConfigAcceptRaDnssl
         INTEGER,
      er1645v2Lan3PppOEIpV6DefaultRoute
         INTEGER,
      er1645v2Lan3PppOEIpV6RaSend
         INTEGER,
      er1645v2Lan3PppOEIpV6RaMinInterval
         TimeTicks,
      er1645v2Lan3PppOEIpV6RaMaxInterval
         TimeTicks,
      er1645v2Lan3PppOEIpV6RaManagedFlag
         INTEGER,
      er1645v2Lan3PppOEIpV6RaOtherConfFlag
         INTEGER,
      er1645v2Lan3PppOEIpV6RaLinkMtu
         Integer32,
      er1645v2Lan3PppOEIpV6RaReachableTime
         TimeTicks,
      er1645v2Lan3PppOEIpV6RaRetransmitTime
         TimeTicks,
      er1645v2Lan3PppOEIpV6RaHopLimit
         Integer32,
      er1645v2Lan3PppOEIpV6RaDefaultLifeTime
         TimeTicks,
      er1645v2Lan3PppOEIpV6RaDnsOptionsRdnssLifeTime
         TimeTicks,
      er1645v2Lan3PppOEIpV6RaDnsOptionsRdnssImportServers
         INTEGER,
      er1645v2Lan3PppOEIpV6RaDnsOptionsDnsslLifeTime
         TimeTicks,
      er1645v2Lan3PppOEIpV6RaDnsOptionsDnsslImportDomains
         INTEGER,
      er1645v2Lan3PppOEIpV6RsSend
         INTEGER,
      er1645v2Lan3PppOEIpV6RsMaxRandomDelay
         TimeTicks,
      er1645v2Lan3PppOEIpV6RsInterval
         TimeTicks,
      er1645v2Lan3PppOEIpV6RsMaxSolicitations
         Integer32,
      er1645v2Lan3PppOEIpV6TrafficPolicyInbound
         DisplayString,
      er1645v2Lan3PppOEIpV6TrafficPolicyOutbound
         DisplayString,
      er1645v2Lan3PppOEIpV6FirewallZone
         DisplayString,
      er1645v2Lan3PppOEIpV6DhcpClientAddrAC
         INTEGER,
      er1645v2Lan3PppOEIpV6DhcpClientPrDelMode
         INTEGER,
      er1645v2Lan3PppOEIpV6DhcpClientPrDelPool
         DisplayString,
      er1645v2Lan3PppOEIpV6DhcpClientPrDelPdExclOpt
         INTEGER,
      er1645v2Lan3PppOEIpV6DhcpClientDnsServerPref
         Integer32,
      er1645v2Lan3PppOEIpV6DhcpClientRapidCommit
         INTEGER,
      er1645v2Lan3PppOEIpV6DhcpClientTimersSolTimeOut
         TimeTicks,
      er1645v2Lan3PppOEIpV6DhcpClientTimersSolMaxRt
         TimeTicks,
      er1645v2Lan3PppOEIpV6DhcpClientTimersInfoRefresh
         TimeTicks,
      er1645v2Lan3PppOEIpV6DhcpServerMode
         INTEGER,
      er1645v2Lan3PppOEIpV6DhcpServerPreference
         Integer32,
      er1645v2Lan3PppOEIpV6DhcpServerPool
         DisplayString,
      er1645v2Lan3PppOEIpV6DhcpServerRapidCommit
         INTEGER,
      er1645v2Lan3PppOEIpV6DhcpServerTimersInfoRefresh
         TimeTicks,
      er1645v2Lan3PppOEIpV6DhcpRelayMode
         INTEGER,
      er1645v2Lan3PppOEIpV6SendRedirect
         INTEGER,
      er1645v2Lan3PppOEIpV6LinkMtu
         Integer32,
      er1645v2Lan3PppOEIpV6InterfaceId
         OCTET STRING,
      er1645v2Lan3PppOEIpV6MF
         Integer32,
      er1645v2Lan3PppOEIpV6IcmpMessagesNoRoute
         INTEGER,
      er1645v2Lan3PppOEIpV6IcmpMessagesBeyondScope
         INTEGER,
      er1645v2Lan3PppOEIpV6IcmpMessagesAddressUnreachable
         INTEGER,
      er1645v2Lan3PppOEIpV6IcmpMessagesPortUnreachable
         INTEGER,
      er1645v2Lan3PppOEIpV6IcmpMessagesPacketTooBig
         INTEGER,
      er1645v2Lan3PppOEIpV6IcmpMessagesHopLimitExceeded
         INTEGER,
      er1645v2Lan3PppOEIpV6IcmpMessagesFragTimeExceeded
         INTEGER,
      er1645v2Lan3PppOEIpV6IcmpMessagesHeaderFieldErr
         INTEGER,
      er1645v2Lan3PppOEIpV6IcmpMessagesOptionUnrecognized
         INTEGER,
      er1645v2Lan3PppOEIpV6IcmpMessagesRedirect
         INTEGER,
      er1645v2Lan3PppOEPppLnkMOperation
         INTEGER,
      er1645v2Lan3PppOEPppLnkMInterval
         TimeTicks,
      er1645v2Lan3PppOEPppLnkMRepTimeOut
         TimeTicks,
      er1645v2Lan3PppOEPppLnkMFailsPrmt
         Integer32,
      er1645v2Lan3PppOEPppAuthentication
         INTEGER,
      er1645v2Lan3PppOEPppAuthenPeriod
         TimeTicks,
      er1645v2Lan3PppOEPppSessionName
         DisplayString,
      er1645v2Lan3PppOEPppSessionSecret
         DisplayString,
      er1645v2Lan3PppOEPppEncModeSessionSecret
         INTEGER,
      er1645v2Lan3PppOEPppEncSessionSecret
         DisplayString,
      er1645v2Lan3PppOEPppServiceName
         DisplayString
      }

er1645v2Lan3PppOEActions OBJECT-TYPE
   SYNTAX      VariableLengthTableActions
   MAX-ACCESS  read-write
   STATUS      current
   DESCRIPTION
      "By way of this field, some manipulations
       on this table may be performed."
   ::= {er1645v2Lan3PppOEEntry 2}

er1645v2Lan3PppOETableIx OBJECT-TYPE
   SYNTAX      TableIndex
   MAX-ACCESS  not-accessible
   STATUS      current
   DESCRIPTION
      ""
   ::= {er1645v2Lan3PppOEEntry 11}

er1645v2Lan3PppOEName OBJECT-TYPE
   SYNTAX      DisplayString
   MAX-ACCESS  read-write
   STATUS      current
   DESCRIPTION
      "Path: ethernet3.editConf.pppoEClient.name"
   ::= {er1645v2Lan3PppOEEntry 16777216}

er1645v2Lan3PppOERemark OBJECT-TYPE
   SYNTAX      DisplayString
   MAX-ACCESS  read-write
   STATUS      current
   DESCRIPTION
      "Path: ethernet3.editConf.pppoEClient.remark"
   ::= {er1645v2Lan3PppOEEntry 1157627904}

er1645v2Lan3PppOEAdminStatus OBJECT-TYPE
   SYNTAX      INTEGER
               {
               up (1),
               down (2)
               }
   MAX-ACCESS  read-write
   STATUS      current
   DESCRIPTION
      "Path: ethernet3.editConf.pppoEClient.adminStatus

       Possibilities:
               up   (1)
               down   (2)"
   ::= {er1645v2Lan3PppOEEntry 33554432}

er1645v2Lan3PppOEMode OBJECT-TYPE
   SYNTAX      INTEGER
               {
               routing (1),
               multilink (8),
               ipV6 (16),
               ipV6ipV4 (17)
               }
   MAX-ACCESS  read-write
   STATUS      current
   DESCRIPTION
      "Path: ethernet3.editConf.pppoEClient.mode

       Possibilities:
               routing   (1)
               multilink   (8)
               ipV6   (16)
               ipV6/ipV4   (17)"
   ::= {er1645v2Lan3PppOEEntry 67108864}

er1645v2Lan3PppOEIpVrfRouter OBJECT-TYPE
   SYNTAX      DisplayString
   MAX-ACCESS  read-write
   STATUS      current
   DESCRIPTION
      "Path: ethernet3.editConf.pppoEClient.ip.vrfRouter"
   ::= {er1645v2Lan3PppOEEntry 53215232}

er1645v2Lan3PppOEIpAdr OBJECT-TYPE
   SYNTAX      IpAddress
   MAX-ACCESS  read-write
   STATUS      current
   DESCRIPTION
      "Path: ethernet3.editConf.pppoEClient.ip.address"
   ::= {er1645v2Lan3PppOEEntry 58261504}

er1645v2Lan3PppOEIpNetm OBJECT-TYPE
   SYNTAX      IpAddress
   MAX-ACCESS  read-write
   STATUS      current
   DESCRIPTION
      "Path: ethernet3.editConf.pppoEClient.ip.netMask"
   ::= {er1645v2Lan3PppOEEntry 58392576}

er1645v2Lan3PppOEIpSNetName OBJECT-TYPE
   SYNTAX      INTEGER
               {
               slOPTg (0),
               corp (2),
               dmz (3),
               internet (1)
               }
   MAX-ACCESS  read-write
   STATUS      current
   DESCRIPTION
      "Path: ethernet3.editConf.pppoEClient.ip.sNet.name

       Possibilities:
               <OPT>   (0)
               corp   (2)
               dmz   (3)
               internet   (1)"
   ::= {er1645v2Lan3PppOEEntry 53674240}

er1645v2Lan3PppOEIpSNetCust OBJECT-TYPE
   SYNTAX      DisplayString
   MAX-ACCESS  read-write
   STATUS      current
   DESCRIPTION
      "Path: ethernet3.editConf.pppoEClient.ip.sNet.custom"
   ::= {er1645v2Lan3PppOEEntry 53674496}

er1645v2Lan3PppOEIpRem OBJECT-TYPE
   SYNTAX      IpAddress
   MAX-ACCESS  read-write
   STATUS      current
   DESCRIPTION
      "Path: ethernet3.editConf.pppoEClient.ip.remote"
   ::= {er1645v2Lan3PppOEEntry 58458112}

er1645v2Lan3PppOEIpUnnumbered OBJECT-TYPE
   SYNTAX      DisplayString
   MAX-ACCESS  read-write
   STATUS      current
   DESCRIPTION
      "Path: ethernet3.editConf.pppoEClient.ip.unnumbered"
   ::= {er1645v2Lan3PppOEEntry 52625408}

er1645v2Lan3PppOEIpGwPref OBJECT-TYPE
   SYNTAX      Integer32
   MAX-ACCESS  read-write
   STATUS      current
   DESCRIPTION
      "Path: ethernet3.editConf.pppoEClient.ip.gatewayPreference"
   ::= {er1645v2Lan3PppOEEntry 52690944}

er1645v2Lan3PppOEIpRsn OBJECT-TYPE
   SYNTAX      INTEGER
               {
               disabled (0),
               enabled (1)
               }
   MAX-ACCESS  read-write
   STATUS      current
   DESCRIPTION
      "Path: ethernet3.editConf.pppoEClient.ip.requestSubnet

       Possibilities:
               disabled   (0)
               enabled   (1)"
   ::= {er1645v2Lan3PppOEEntry 56688640}

er1645v2Lan3PppOEIpMtu OBJECT-TYPE
   SYNTAX      Integer32
   MAX-ACCESS  read-write
   STATUS      current
   DESCRIPTION
      "Path: ethernet3.editConf.pppoEClient.ip.mtu"
   ::= {er1645v2Lan3PppOEEntry 52953088}

er1645v2Lan3PppOEIpMssAdjust OBJECT-TYPE
   SYNTAX      INTEGER
               {
               disabled (0),
               auto (65536)
               }
   MAX-ACCESS  read-write
   STATUS      current
   DESCRIPTION
      "Path: ethernet3.editConf.pppoEClient.ip.mssAdjust

       Possibilities:
               disabled   (0)
               auto   (65536)"
   ::= {er1645v2Lan3PppOEEntry 53280768}

er1645v2Lan3PppOEIpRipMetric OBJECT-TYPE
   SYNTAX      Integer32
   MAX-ACCESS  read-write
   STATUS      current
   DESCRIPTION
      "Path: ethernet3.editConf.pppoEClient.ip.rip.metric"
   ::= {er1645v2Lan3PppOEEntry 51712768}

er1645v2Lan3PppOEIpRipMetricOut OBJECT-TYPE
   SYNTAX      Integer32
   MAX-ACCESS  read-write
   STATUS      current
   DESCRIPTION
      "Path: ethernet3.editConf.pppoEClient.ip.rip.metricOut"
   ::= {er1645v2Lan3PppOEEntry 51713024}

er1645v2Lan3PppOEIpRipMode OBJECT-TYPE
   SYNTAX      INTEGER
               {
               disabled (0),
               passive (1),
               active (2)
               }
   MAX-ACCESS  read-write
   STATUS      current
   DESCRIPTION
      "Path: ethernet3.editConf.pppoEClient.ip.rip.mode

       Possibilities:
               disabled   (0)
               passive   (1)
               active   (2)"
   ::= {er1645v2Lan3PppOEEntry 51713280}

er1645v2Lan3PppOEIpRipTxVer OBJECT-TYPE
   SYNTAX      INTEGER
               {
               rip1 (0),
               rip2 (1),
               rip1mcompatible (2)
               }
   MAX-ACCESS  read-write
   STATUS      current
   DESCRIPTION
      "Path: ethernet3.editConf.pppoEClient.ip.rip.txVersion

       Possibilities:
               rip1   (0)
               rip2   (1)
               rip1-compatible   (2)"
   ::= {er1645v2Lan3PppOEEntry 51716864}

er1645v2Lan3PppOEIpRipRxVer OBJECT-TYPE
   SYNTAX      INTEGER
               {
               rip1only (0),
               rip2only (1),
               rip12 (2)
               }
   MAX-ACCESS  read-write
   STATUS      current
   DESCRIPTION
      "Path: ethernet3.editConf.pppoEClient.ip.rip.rxVersion

       Possibilities:
               rip1only   (0)
               rip2only   (1)
               rip1&2   (2)"
   ::= {er1645v2Lan3PppOEEntry 51717120}

er1645v2Lan3PppOEIpRipSplitH OBJECT-TYPE
   SYNTAX      INTEGER
               {
               disabled (0),
               enabled (1),
               poisonedReverse (2)
               }
   MAX-ACCESS  read-write
   STATUS      current
   DESCRIPTION
      "Path: ethernet3.editConf.pppoEClient.ip.rip.splitHorizon

       Possibilities:
               disabled   (0)
               enabled   (1)
               poisonedReverse   (2)"
   ::= {er1645v2Lan3PppOEEntry 51713792}

er1645v2Lan3PppOEIpRipAuth OBJECT-TYPE
   SYNTAX      INTEGER
               {
               disabled (0),
               texts (1),
               md5 (2)
               }
   MAX-ACCESS  read-write
   STATUS      current
   DESCRIPTION
      "Path: ethernet3.editConf.pppoEClient.ip.rip.authentication

       Possibilities:
               disabled   (0)
               text    (1)
               md5   (2)"
   ::= {er1645v2Lan3PppOEEntry 51712512}

er1645v2Lan3PppOEIpRipFilter OBJECT-TYPE
   SYNTAX      DisplayString
   MAX-ACCESS  read-write
   STATUS      current
   DESCRIPTION
      "Path: ethernet3.editConf.pppoEClient.ip.rip.filter"
   ::= {er1645v2Lan3PppOEEntry 51716096}

er1645v2Lan3PppOEIpRipFilterIn OBJECT-TYPE
   SYNTAX      DisplayString
   MAX-ACCESS  read-write
   STATUS      current
   DESCRIPTION
      "Path: ethernet3.editConf.pppoEClient.ip.rip.filterIn"
   ::= {er1645v2Lan3PppOEEntry 51716352}

er1645v2Lan3PppOEIpRipClearNextHop OBJECT-TYPE
   SYNTAX      INTEGER
               {
               disabled (0),
               enabled (1)
               }
   MAX-ACCESS  read-write
   STATUS      current
   DESCRIPTION
      "Path: ethernet3.editConf.pppoEClient.ip.rip.clearNextHop

       Possibilities:
               disabled   (0)
               enabled   (1)"
   ::= {er1645v2Lan3PppOEEntry 51708416}

er1645v2Lan3PppOEIpAccPol OBJECT-TYPE
   SYNTAX      DisplayString
   MAX-ACCESS  read-write
   STATUS      current
   DESCRIPTION
      "Path: ethernet3.editConf.pppoEClient.ip.accessPolicy"
   ::= {er1645v2Lan3PppOEEntry 53084160}

er1645v2Lan3PppOEIpAB OBJECT-TYPE
   SYNTAX      DisplayString
   MAX-ACCESS  read-write
   STATUS      current
   DESCRIPTION
      "Path: ethernet3.editConf.pppoEClient.ip.trafficPolicy"
   ::= {er1645v2Lan3PppOEEntry 51249152}

er1645v2Lan3PppOEIpMA OBJECT-TYPE
   SYNTAX      INTEGER
               {
               disabled (0),
               enabled (1)
               }
   MAX-ACCESS  read-write
   STATUS      current
   DESCRIPTION
      "Path: ethernet3.editConf.pppoEClient.ip.mgmtAccess

       Possibilities:
               disabled   (0)
               enabled   (1)"
   ::= {er1645v2Lan3PppOEEntry 51380224}

er1645v2Lan3PppOEIpMF OBJECT-TYPE
   SYNTAX      Integer32
   MAX-ACCESS  read-write
   STATUS      current
   DESCRIPTION
      "Path: ethernet3.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3PppOEEntry 51445760}

er1645v2Lan3PppOEIpDB OBJECT-TYPE
   SYNTAX      INTEGER
               {
               disabled (0),
               enabled (1)
               }
   MAX-ACCESS  read-write
   STATUS      current
   DESCRIPTION
      "Path: ethernet3.editConf.pppoEClient.ip.directedBroadcasts

       Possibilities:
               disabled   (0)
               enabled   (1)"
   ::= {er1645v2Lan3PppOEEntry 51773440}

er1645v2Lan3PppOEIpIR OBJECT-TYPE
   SYNTAX      INTEGER
               {
               disabled (0),
               enabled (1)
               }
   MAX-ACCESS  read-write
   STATUS      current
   DESCRIPTION
      "Path: ethernet3.editConf.pppoEClient.ip.icmpRedirects

       Possibilities:
               disabled   (0)
               enabled   (1)"
   ::= {er1645v2Lan3PppOEEntry 52035584}

er1645v2Lan3PppOEIpIgmp OBJECT-TYPE
   SYNTAX      INTEGER
               {
               disabled (0),
               proxy (1),
               router (2),
               v3Router (5)
               }
   MAX-ACCESS  read-write
   STATUS      current
   DESCRIPTION
      "Path: ethernet3.editConf.pppoEClient.ip.igmp

       Possibilities:
               disabled   (0)
               proxy   (1)
               router   (2)
               v3Router   (5)"
   ::= {er1645v2Lan3PppOEEntry 52428800}

er1645v2Lan3PppOEIpNN OBJECT-TYPE
   SYNTAX      DisplayString
   MAX-ACCESS  read-write
   STATUS      current
   DESCRIPTION
      "Path: ethernet3.editConf.pppoEClient.ip.nat"
   ::= {er1645v2Lan3PppOEEntry 52101120}

er1645v2Lan3PppOEIpPimMode OBJECT-TYPE
   SYNTAX      INTEGER
               {
               disabled (0),
               sparse (1),
               passive (2)
               }
   MAX-ACCESS  read-write
   STATUS      current
   DESCRIPTION
      "Path: ethernet3.editConf.pppoEClient.ip.pim.mode

       Possibilities:
               disabled   (0)
               sparse   (1)
               passive   (2)"
   ::= {er1645v2Lan3PppOEEntry 53346560}

er1645v2Lan3PppOEIpPimDrPriority OBJECT-TYPE
   SYNTAX      Counter32
   MAX-ACCESS  read-write
   STATUS      current
   DESCRIPTION
      "Path: ethernet3.editConf.pppoEClient.ip.pim.drPriority

       32 bit unsigned wrappable counter."
   ::= {er1645v2Lan3PppOEEntry 53346816}

er1645v2Lan3PppOEIpPimHelloTime OBJECT-TYPE
   SYNTAX      TimeTicks
   MAX-ACCESS  read-write
   STATUS      current
   DESCRIPTION
      "Path: ethernet3.editConf.pppoEClient.ip.pim.helloTime

       Time in centi-second."
   ::= {er1645v2Lan3PppOEEntry 53347072}

er1645v2Lan3PppOEIpPimPropagationDelay OBJECT-TYPE
   SYNTAX      TimeTicks
   MAX-ACCESS  read-write
   STATUS      current
   DESCRIPTION
      "Path: ethernet3.editConf.pppoEClient.ip.pim.propagationDelay

       Time in centi-second."
   ::= {er1645v2Lan3PppOEEntry 53347328}

er1645v2Lan3PppOEIpPimOverrideInterval OBJECT-TYPE
   SYNTAX      TimeTicks
   MAX-ACCESS  read-write
   STATUS      current
   DESCRIPTION
      "Path: ethernet3.editConf.pppoEClient.ip.pim.overrideInterval

       Time in centi-second."
   ::= {er1645v2Lan3PppOEEntry 53347584}

er1645v2Lan3PppOEIpPimBsrBorder OBJECT-TYPE
   SYNTAX      INTEGER
               {
               disabled (0),
               enabled (1)
               }
   MAX-ACCESS  read-write
   STATUS      current
   DESCRIPTION
      "Path: ethernet3.editConf.pppoEClient.ip.pim.bsrBorder

       Possibilities:
               disabled   (0)
               enabled   (1)"
   ::= {er1645v2Lan3PppOEEntry 53347840}

er1645v2Lan3PppOEIpPimTtlThreshold OBJECT-TYPE
   SYNTAX      Integer32
   MAX-ACCESS  read-write
   STATUS      current
   DESCRIPTION
      "Path: ethernet3.editConf.pppoEClient.ip.pim.ttlThreshold"
   ::= {er1645v2Lan3PppOEEntry 53348096}

er1645v2Lan3PppOEIpIMNetworkUnreachable OBJECT-TYPE
   SYNTAX      INTEGER
               {
               disabled (0),
               enabled (1)
               }
   MAX-ACCESS  read-write
   STATUS      current
   DESCRIPTION
      "Path: ethernet3.editConf.pppoEClient.ip.icmpMessages.networkUnreachable

       Possibilities:
               disabled   (0)
               enabled   (1)"
   ::= {er1645v2Lan3PppOEEntry 53412096}

er1645v2Lan3PppOEIpIMHostUnreachable OBJECT-TYPE
   SYNTAX      INTEGER
               {
               disabled (0),
               enabled (1)
               }
   MAX-ACCESS  read-write
   STATUS      current
   DESCRIPTION
      "Path: ethernet3.editConf.pppoEClient.ip.icmpMessages.hostUnreachable

       Possibilities:
               disabled   (0)
               enabled   (1)"
   ::= {er1645v2Lan3PppOEEntry 53412352}

er1645v2Lan3PppOEIpIMProtocolUnreachable OBJECT-TYPE
   SYNTAX      INTEGER
               {
               disabled (0),
               enabled (1)
               }
   MAX-ACCESS  read-write
   STATUS      current
   DESCRIPTION
      "Path: ethernet3.editConf.pppoEClient.ip.icmpMessages.protocolUnreachable

       Possibilities:
               disabled   (0)
               enabled   (1)"
   ::= {er1645v2Lan3PppOEEntry 53412608}

er1645v2Lan3PppOEIpIMPortUnreachable OBJECT-TYPE
   SYNTAX      INTEGER
               {
               disabled (0),
               enabled (1)
               }
   MAX-ACCESS  read-write
   STATUS      current
   DESCRIPTION
      "Path: ethernet3.editConf.pppoEClient.ip.icmpMessages.portUnreachable

       Possibilities:
               disabled   (0)
               enabled   (1)"
   ::= {er1645v2Lan3PppOEEntry 53412864}

er1645v2Lan3PppOEIpIMMtuExceeded OBJECT-TYPE
   SYNTAX      INTEGER
               {
               disabled (0),
               enabled (1)
               }
   MAX-ACCESS  read-write
   STATUS      current
   DESCRIPTION
      "Path: ethernet3.editConf.pppoEClient.ip.icmpMessages.mtuExceeded

       Possibilities:
               disabled   (0)
               enabled   (1)"
   ::= {er1645v2Lan3PppOEEntry 53413120}

er1645v2Lan3PppOEIpIMAdminProhibited OBJECT-TYPE
   SYNTAX      INTEGER
               {
               disabled (0),
               enabled (1)
               }
   MAX-ACCESS  read-write
   STATUS      current
   DESCRIPTION
      "Path: ethernet3.editConf.pppoEClient.ip.icmpMessages.adminProhibited

       Possibilities:
               disabled   (0)
               enabled   (1)"
   ::= {er1645v2Lan3PppOEEntry 53413376}

er1645v2Lan3PppOEIpIMTtlExceeded OBJECT-TYPE
   SYNTAX      INTEGER
               {
               disabled (0),
               enabled (1)
               }
   MAX-ACCESS  read-write
   STATUS      current
   DESCRIPTION
      "Path: ethernet3.editConf.pppoEClient.ip.icmpMessages.ttlExceeded

       Possibilities:
               disabled   (0)
               enabled   (1)"
   ::= {er1645v2Lan3PppOEEntry 53413632}

er1645v2Lan3PppOEIpIMRedirect OBJECT-TYPE
   SYNTAX      INTEGER
               {
               disabled (0),
               enabled (1)
               }
   MAX-ACCESS  read-write
   STATUS      current
   DESCRIPTION
      "Path: ethernet3.editConf.pppoEClient.ip.icmpMessages.redirect

       Possibilities:
               disabled   (0)
               enabled   (1)"
   ::= {er1645v2Lan3PppOEEntry 53413888}

er1645v2Lan3PppOEIpV6VrfRouter OBJECT-TYPE
   SYNTAX      DisplayString
   MAX-ACCESS  read-write
   STATUS      current
   DESCRIPTION
      "Path: ethernet3.editConf.pppoEClient.ipV6.vrfRouter"
   ::= {er1645v2Lan3PppOEEntry 704708608}

er1645v2Lan3PppOEIpV6AddrAutoConfigNrDupAddrDetects OBJECT-TYPE
   SYNTAX      Integer32
   MAX-ACCESS  read-write
   STATUS      current
   DESCRIPTION
      "Path: ethernet3.editConf.pppoEClient.ipV6.addrAutoConfig.nrDupAddrDetects"
   ::= {er1645v2Lan3PppOEEntry 704905472}

er1645v2Lan3PppOEIpV6AddrAutoConfigAcceptRa OBJECT-TYPE
   SYNTAX      INTEGER
               {
               disabled (0),
               enabled (1)
               }
   MAX-ACCESS  read-write
   STATUS      current
   DESCRIPTION
      "Path: ethernet3.editConf.pppoEClient.ipV6.addrAutoConfig.acceptRa

       Possibilities:
               disabled   (0)
               enabled   (1)"
   ::= {er1645v2Lan3PppOEEntry 704905728}

er1645v2Lan3PppOEIpV6AddrAutoConfigAcceptRaRdnss OBJECT-TYPE
   SYNTAX      INTEGER
               {
               disabled (0),
               enabled (1)
               }
   MAX-ACCESS  read-write
   STATUS      current
   DESCRIPTION
      "Path: ethernet3.editConf.pppoEClient.ipV6.addrAutoConfig.acceptRaRdnss

       Possibilities:
               disabled   (0)
               enabled   (1)"
   ::= {er1645v2Lan3PppOEEntry 704905984}

er1645v2Lan3PppOEIpV6AddrAutoConfigAcceptRaDnssl OBJECT-TYPE
   SYNTAX      INTEGER
               {
               disabled (0),
               enabled (1)
               }
   MAX-ACCESS  read-write
   STATUS      current
   DESCRIPTION
      "Path: ethernet3.editConf.pppoEClient.ipV6.addrAutoConfig.acceptRaDnssl

       Possibilities:
               disabled   (0)
               enabled   (1)"
   ::= {er1645v2Lan3PppOEEntry 704906240}

er1645v2Lan3PppOEIpV6DefaultRoute OBJECT-TYPE
   SYNTAX      INTEGER
               {
               disabled (0),
               enabled (1)
               }
   MAX-ACCESS  read-write
   STATUS      current
   DESCRIPTION
      "Path: ethernet3.editConf.pppoEClient.ipV6.defaultRoute

       Possibilities:
               disabled   (0)
               enabled   (1)"
   ::= {er1645v2Lan3PppOEEntry 704970752}

er1645v2Lan3PppOEIpV6RaSend OBJECT-TYPE
   SYNTAX      INTEGER
               {
               disabled (0),
               enabled (1)
               }
   MAX-ACCESS  read-write
   STATUS      current
   DESCRIPTION
      "Path: ethernet3.editConf.pppoEClient.ipV6.ra.send

       Possibilities:
               disabled   (0)
               enabled   (1)"
   ::= {er1645v2Lan3PppOEEntry 705036544}

er1645v2Lan3PppOEIpV6RaMinInterval OBJECT-TYPE
   SYNTAX      TimeTicks
   MAX-ACCESS  read-write
   STATUS      current
   DESCRIPTION
      "Path: ethernet3.editConf.pppoEClient.ipV6.ra.minInterval

       Time in centi-second."
   ::= {er1645v2Lan3PppOEEntry 705036800}

er1645v2Lan3PppOEIpV6RaMaxInterval OBJECT-TYPE
   SYNTAX      TimeTicks
   MAX-ACCESS  read-write
   STATUS      current
   DESCRIPTION
      "Path: ethernet3.editConf.pppoEClient.ipV6.ra.maxInterval

       Time in centi-second."
   ::= {er1645v2Lan3PppOEEntry 705037056}

er1645v2Lan3PppOEIpV6RaManagedFlag OBJECT-TYPE
   SYNTAX      INTEGER
               {
               disabled (0),
               enabled (1)
               }
   MAX-ACCESS  read-write
   STATUS      current
   DESCRIPTION
      "Path: ethernet3.editConf.pppoEClient.ipV6.ra.managedFlag

       Possibilities:
               disabled   (0)
               enabled   (1)"
   ::= {er1645v2Lan3PppOEEntry 705037312}

er1645v2Lan3PppOEIpV6RaOtherConfFlag OBJECT-TYPE
   SYNTAX      INTEGER
               {
               disabled (0),
               enabled (1)
               }
   MAX-ACCESS  read-write
   STATUS      current
   DESCRIPTION
      "Path: ethernet3.editConf.pppoEClient.ipV6.ra.otherConfFlag

       Possibilities:
               disabled   (0)
               enabled   (1)"
   ::= {er1645v2Lan3PppOEEntry 705037568}

er1645v2Lan3PppOEIpV6RaLinkMtu OBJECT-TYPE
   SYNTAX      Integer32
   MAX-ACCESS  read-write
   STATUS      current
   DESCRIPTION
      "Path: ethernet3.editConf.pppoEClient.ipV6.ra.linkMtu"
   ::= {er1645v2Lan3PppOEEntry 705037824}

er1645v2Lan3PppOEIpV6RaReachableTime OBJECT-TYPE
   SYNTAX      TimeTicks
   MAX-ACCESS  read-write
   STATUS      current
   DESCRIPTION
      "Path: ethernet3.editConf.pppoEClient.ipV6.ra.reachableTime

       Time in centi-second."
   ::= {er1645v2Lan3PppOEEntry 705038080}

er1645v2Lan3PppOEIpV6RaRetransmitTime OBJECT-TYPE
   SYNTAX      TimeTicks
   MAX-ACCESS  read-write
   STATUS      current
   DESCRIPTION
      "Path: ethernet3.editConf.pppoEClient.ipV6.ra.retransmitTime

       Time in centi-second."
   ::= {er1645v2Lan3PppOEEntry 705038336}

er1645v2Lan3PppOEIpV6RaHopLimit OBJECT-TYPE
   SYNTAX      Integer32
   MAX-ACCESS  read-write
   STATUS      current
   DESCRIPTION
      "Path: ethernet3.editConf.pppoEClient.ipV6.ra.hopLimit"
   ::= {er1645v2Lan3PppOEEntry 705038592}

er1645v2Lan3PppOEIpV6RaDefaultLifeTime OBJECT-TYPE
   SYNTAX      TimeTicks
   MAX-ACCESS  read-write
   STATUS      current
   DESCRIPTION
      "Path: ethernet3.editConf.pppoEClient.ipV6.ra.defaultLifeTime

       Time in centi-second."
   ::= {er1645v2Lan3PppOEEntry 705038848}

er1645v2Lan3PppOEIpV6RaDnsOptionsRdnssLifeTime OBJECT-TYPE
   SYNTAX      TimeTicks
   MAX-ACCESS  read-write
   STATUS      current
   DESCRIPTION
      "Path: ethernet3.editConf.pppoEClient.ipV6.ra.dnsOptions.rdnss.lifeTime

       Time in centi-second."
   ::= {er1645v2Lan3PppOEEntry 705039140}

er1645v2Lan3PppOEIpV6RaDnsOptionsRdnssImportServers OBJECT-TYPE
   SYNTAX      INTEGER
               {
               disabled (0),
               enabled (1)
               }
   MAX-ACCESS  read-write
   STATUS      current
   DESCRIPTION
      "Path: ethernet3.editConf.pppoEClient.ipV6.ra.dnsOptions.rdnss.importServers

       Possibilities:
               disabled   (0)
               enabled   (1)"
   ::= {er1645v2Lan3PppOEEntry 705039148}

er1645v2Lan3PppOEIpV6RaDnsOptionsDnsslLifeTime OBJECT-TYPE
   SYNTAX      TimeTicks
   MAX-ACCESS  read-write
   STATUS      current
   DESCRIPTION
      "Path: ethernet3.editConf.pppoEClient.ipV6.ra.dnsOptions.dnssl.lifeTime

       Time in centi-second."
   ::= {er1645v2Lan3PppOEEntry 705039172}

er1645v2Lan3PppOEIpV6RaDnsOptionsDnsslImportDomains OBJECT-TYPE
   SYNTAX      INTEGER
               {
               disabled (0),
               enabled (1)
               }
   MAX-ACCESS  read-write
   STATUS      current
   DESCRIPTION
      "Path: ethernet3.editConf.pppoEClient.ipV6.ra.dnsOptions.dnssl.importDomains

       Possibilities:
               disabled   (0)
               enabled   (1)"
   ::= {er1645v2Lan3PppOEEntry 705039180}

er1645v2Lan3PppOEIpV6RsSend OBJECT-TYPE
   SYNTAX      INTEGER
               {
               disabled (0),
               enabled (1)
               }
   MAX-ACCESS  read-write
   STATUS      current
   DESCRIPTION
      "Path: ethernet3.editConf.pppoEClient.ipV6.rs.send

       Possibilities:
               disabled   (0)
               enabled   (1)"
   ::= {er1645v2Lan3PppOEEntry 705954048}

er1645v2Lan3PppOEIpV6RsMaxRandomDelay OBJECT-TYPE
   SYNTAX      TimeTicks
   MAX-ACCESS  read-write
   STATUS      current
   DESCRIPTION
      "Path: ethernet3.editConf.pppoEClient.ipV6.rs.maxRandomDelay

       Time in centi-second."
   ::= {er1645v2Lan3PppOEEntry 705954304}

er1645v2Lan3PppOEIpV6RsInterval OBJECT-TYPE
   SYNTAX      TimeTicks
   MAX-ACCESS  read-write
   STATUS      current
   DESCRIPTION
      "Path: ethernet3.editConf.pppoEClient.ipV6.rs.interval

       Time in centi-second."
   ::= {er1645v2Lan3PppOEEntry 705954560}

er1645v2Lan3PppOEIpV6RsMaxSolicitations OBJECT-TYPE
   SYNTAX      Integer32
   MAX-ACCESS  read-write
   STATUS      current
   DESCRIPTION
      "Path: ethernet3.editConf.pppoEClient.ipV6.rs.maxSolicitations"
   ::= {er1645v2Lan3PppOEEntry 705954816}

er1645v2Lan3PppOEIpV6TrafficPolicyInbound OBJECT-TYPE
   SYNTAX      DisplayString
   MAX-ACCESS  read-write
   STATUS      current
   DESCRIPTION
      "Path: ethernet3.editConf.pppoEClient.ipV6.trafficPolicy.inbound"
   ::= {er1645v2Lan3PppOEEntry 705364224}

er1645v2Lan3PppOEIpV6TrafficPolicyOutbound OBJECT-TYPE
   SYNTAX      DisplayString
   MAX-ACCESS  read-write
   STATUS      current
   DESCRIPTION
      "Path: ethernet3.editConf.pppoEClient.ipV6.trafficPolicy.outbound"
   ::= {er1645v2Lan3PppOEEntry 705364480}

er1645v2Lan3PppOEIpV6FirewallZone OBJECT-TYPE
   SYNTAX      DisplayString
   MAX-ACCESS  read-write
   STATUS      current
   DESCRIPTION
      "Path: ethernet3.editConf.pppoEClient.ipV6.firewall.zone"
   ::= {er1645v2Lan3PppOEEntry 705429760}

er1645v2Lan3PppOEIpV6DhcpClientAddrAC OBJECT-TYPE
   SYNTAX      INTEGER
               {
               disabled (0),
               enabled (1)
               }
   MAX-ACCESS  read-write
   STATUS      current
   DESCRIPTION
      "Path: ethernet3.editConf.pppoEClient.ipV6.dhcp.client.addrAutoConfig

       Possibilities:
               disabled   (0)
               enabled   (1)"
   ::= {er1645v2Lan3PppOEEntry 705307648}

er1645v2Lan3PppOEIpV6DhcpClientPrDelMode OBJECT-TYPE
   SYNTAX      INTEGER
               {
               disabled (0),
               enabled (1)
               }
   MAX-ACCESS  read-write
   STATUS      current
   DESCRIPTION
      "Path: ethernet3.editConf.pppoEClient.ipV6.dhcp.client.pd.mode

       Possibilities:
               disabled   (0)
               enabled   (1)"
   ::= {er1645v2Lan3PppOEEntry 705308676}

er1645v2Lan3PppOEIpV6DhcpClientPrDelPool OBJECT-TYPE
   SYNTAX      DisplayString
   MAX-ACCESS  read-write
   STATUS      current
   DESCRIPTION
      "Path: ethernet3.editConf.pppoEClient.ipV6.dhcp.client.pd.pool"
   ::= {er1645v2Lan3PppOEEntry 705308680}

er1645v2Lan3PppOEIpV6DhcpClientPrDelPdExclOpt OBJECT-TYPE
   SYNTAX      INTEGER
               {
               disabled (0),
               enabled (1)
               }
   MAX-ACCESS  read-write
   STATUS      current
   DESCRIPTION
      "Path: ethernet3.editConf.pppoEClient.ipV6.dhcp.client.pd.pdExclOpt

       Possibilities:
               disabled   (0)
               enabled   (1)"
   ::= {er1645v2Lan3PppOEEntry 705308684}

er1645v2Lan3PppOEIpV6DhcpClientDnsServerPref OBJECT-TYPE
   SYNTAX      Integer32
   MAX-ACCESS  read-write
   STATUS      current
   DESCRIPTION
      "Path: ethernet3.editConf.pppoEClient.ipV6.dhcp.client.dns.serverPref"
   ::= {er1645v2Lan3PppOEEntry 705310724}

er1645v2Lan3PppOEIpV6DhcpClientRapidCommit OBJECT-TYPE
   SYNTAX      INTEGER
               {
               disabled (0),
               enabled (1)
               }
   MAX-ACCESS  read-write
   STATUS      current
   DESCRIPTION
      "Path: ethernet3.editConf.pppoEClient.ipV6.dhcp.client.rapidCommit

       Possibilities:
               disabled   (0)
               enabled   (1)"
   ::= {er1645v2Lan3PppOEEntry 705309696}

er1645v2Lan3PppOEIpV6DhcpClientTimersSolTimeOut OBJECT-TYPE
   SYNTAX      TimeTicks
   MAX-ACCESS  read-write
   STATUS      current
   DESCRIPTION
      "Path: ethernet3.editConf.pppoEClient.ipV6.dhcp.client.timers.solTimeOut

       Time in centi-second."
   ::= {er1645v2Lan3PppOEEntry 705311748}

er1645v2Lan3PppOEIpV6DhcpClientTimersSolMaxRt OBJECT-TYPE
   SYNTAX      TimeTicks
   MAX-ACCESS  read-write
   STATUS      current
   DESCRIPTION
      "Path: ethernet3.editConf.pppoEClient.ipV6.dhcp.client.timers.solMaxRt

       Time in centi-second."
   ::= {er1645v2Lan3PppOEEntry 705311752}

er1645v2Lan3PppOEIpV6DhcpClientTimersInfoRefresh OBJECT-TYPE
   SYNTAX      TimeTicks
   MAX-ACCESS  read-write
   STATUS      current
   DESCRIPTION
      "Path: ethernet3.editConf.pppoEClient.ipV6.dhcp.client.timers.infoRefresh

       Time in centi-second."
   ::= {er1645v2Lan3PppOEEntry 705311756}

er1645v2Lan3PppOEIpV6DhcpServerMode OBJECT-TYPE
   SYNTAX      INTEGER
               {
               disabled (0),
               enabled (1)
               }
   MAX-ACCESS  read-write
   STATUS      current
   DESCRIPTION
      "Path: ethernet3.editConf.pppoEClient.ipV6.dhcp.server.mode

       Possibilities:
               disabled   (0)
               enabled   (1)"
   ::= {er1645v2Lan3PppOEEntry 705315840}

er1645v2Lan3PppOEIpV6DhcpServerPreference OBJECT-TYPE
   SYNTAX      Integer32
   MAX-ACCESS  read-write
   STATUS      current
   DESCRIPTION
      "Path: ethernet3.editConf.pppoEClient.ipV6.dhcp.server.preference"
   ::= {er1645v2Lan3PppOEEntry 705316864}

er1645v2Lan3PppOEIpV6DhcpServerPool OBJECT-TYPE
   SYNTAX      DisplayString
   MAX-ACCESS  read-write
   STATUS      current
   DESCRIPTION
      "Path: ethernet3.editConf.pppoEClient.ipV6.dhcp.server.pool"
   ::= {er1645v2Lan3PppOEEntry 705317888}

er1645v2Lan3PppOEIpV6DhcpServerRapidCommit OBJECT-TYPE
   SYNTAX      INTEGER
               {
               disabled (0),
               enabled (1)
               }
   MAX-ACCESS  read-write
   STATUS      current
   DESCRIPTION
      "Path: ethernet3.editConf.pppoEClient.ipV6.dhcp.server.rapidCommit

       Possibilities:
               disabled   (0)
               enabled   (1)"
   ::= {er1645v2Lan3PppOEEntry 705318912}

er1645v2Lan3PppOEIpV6DhcpServerTimersInfoRefresh OBJECT-TYPE
   SYNTAX      TimeTicks
   MAX-ACCESS  read-write
   STATUS      current
   DESCRIPTION
      "Path: ethernet3.editConf.pppoEClient.ipV6.dhcp.server.timers.infoRefresh

       Time in centi-second."
   ::= {er1645v2Lan3PppOEEntry 705319940}

er1645v2Lan3PppOEIpV6DhcpRelayMode OBJECT-TYPE
   SYNTAX      INTEGER
               {
               disabled (0),
               enabled (1)
               }
   MAX-ACCESS  read-write
   STATUS      current
   DESCRIPTION
      "Path: ethernet3.editConf.pppoEClient.ipV6.dhcp.relay.mode

       Possibilities:
               disabled   (0)
               enabled   (1)"
   ::= {er1645v2Lan3PppOEEntry 705323040}

er1645v2Lan3PppOEIpV6SendRedirect OBJECT-TYPE
   SYNTAX      INTEGER
               {
               disabled (0),
               enabled (1)
               }
   MAX-ACCESS  read-write
   STATUS      current
   DESCRIPTION
      "Path: ethernet3.editConf.pppoEClient.ipV6.sendRedirect

       Possibilities:
               disabled   (0)
               enabled   (1)"
   ::= {er1645v2Lan3PppOEEntry 705101824}

er1645v2Lan3PppOEIpV6LinkMtu OBJECT-TYPE
   SYNTAX      Integer32
   MAX-ACCESS  read-write
   STATUS      current
   DESCRIPTION
      "Path: ethernet3.editConf.pppoEClient.ipV6.linkMtu"
   ::= {er1645v2Lan3PppOEEntry 705167360}

er1645v2Lan3PppOEIpV6InterfaceId OBJECT-TYPE
   SYNTAX      OCTET STRING
   MAX-ACCESS  read-write
   STATUS      current
   DESCRIPTION
      "Path: ethernet3.editConf.pppoEClient.ipV6.interfaceId"
   ::= {er1645v2Lan3PppOEEntry 705232896}

er1645v2Lan3PppOEIpV6MF OBJECT-TYPE
   SYNTAX      Integer32
   MAX-ACCESS  read-write
   STATUS      current
   DESCRIPTION
      "Path: ethernet3.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3PppOEEntry 705757184}

er1645v2Lan3PppOEIpV6IcmpMessagesNoRoute OBJECT-TYPE
   SYNTAX      INTEGER
               {
               disabled (0),
               enabled (1)
               }
   MAX-ACCESS  read-write
   STATUS      current
   DESCRIPTION
      "Path: ethernet3.editConf.pppoEClient.ipV6.icmpMessages.noRoute

       Possibilities:
               disabled   (0)
               enabled   (1)"
   ::= {er1645v2Lan3PppOEEntry 705822976}

er1645v2Lan3PppOEIpV6IcmpMessagesBeyondScope OBJECT-TYPE
   SYNTAX      INTEGER
               {
               disabled (0),
               enabled (1)
               }
   MAX-ACCESS  read-write
   STATUS      current
   DESCRIPTION
      "Path: ethernet3.editConf.pppoEClient.ipV6.icmpMessages.beyondScope

       Possibilities:
               disabled   (0)
               enabled   (1)"
   ::= {er1645v2Lan3PppOEEntry 705823488}

er1645v2Lan3PppOEIpV6IcmpMessagesAddressUnreachable OBJECT-TYPE
   SYNTAX      INTEGER
               {
               disabled (0),
               enabled (1)
               }
   MAX-ACCESS  read-write
   STATUS      current
   DESCRIPTION
      "Path: ethernet3.editConf.pppoEClient.ipV6.icmpMessages.addressUnreachable

       Possibilities:
               disabled   (0)
               enabled   (1)"
   ::= {er1645v2Lan3PppOEEntry 705823744}

er1645v2Lan3PppOEIpV6IcmpMessagesPortUnreachable OBJECT-TYPE
   SYNTAX      INTEGER
               {
               disabled (0),
               enabled (1)
               }
   MAX-ACCESS  read-write
   STATUS      current
   DESCRIPTION
      "Path: ethernet3.editConf.pppoEClient.ipV6.icmpMessages.portUnreachable

       Possibilities:
               disabled   (0)
               enabled   (1)"
   ::= {er1645v2Lan3PppOEEntry 705824000}

er1645v2Lan3PppOEIpV6IcmpMessagesPacketTooBig OBJECT-TYPE
   SYNTAX      INTEGER
               {
               disabled (0),
               enabled (1)
               }
   MAX-ACCESS  read-write
   STATUS      current
   DESCRIPTION
      "Path: ethernet3.editConf.pppoEClient.ipV6.icmpMessages.packetTooBig

       Possibilities:
               disabled   (0)
               enabled   (1)"
   ::= {er1645v2Lan3PppOEEntry 705825280}

er1645v2Lan3PppOEIpV6IcmpMessagesHopLimitExceeded OBJECT-TYPE
   SYNTAX      INTEGER
               {
               disabled (0),
               enabled (1)
               }
   MAX-ACCESS  read-write
   STATUS      current
   DESCRIPTION
      "Path: ethernet3.editConf.pppoEClient.ipV6.icmpMessages.hopLimitExceeded

       Possibilities:
               disabled   (0)
               enabled   (1)"
   ::= {er1645v2Lan3PppOEEntry 705827840}

er1645v2Lan3PppOEIpV6IcmpMessagesFragTimeExceeded OBJECT-TYPE
   SYNTAX      INTEGER
               {
               disabled (0),
               enabled (1)
               }
   MAX-ACCESS  read-write
   STATUS      current
   DESCRIPTION
      "Path: ethernet3.editConf.pppoEClient.ipV6.icmpMessages.fragTimeExceeded

       Possibilities:
               disabled   (0)
               enabled   (1)"
   ::= {er1645v2Lan3PppOEEntry 705828096}

er1645v2Lan3PppOEIpV6IcmpMessagesHeaderFieldErr OBJECT-TYPE
   SYNTAX      INTEGER
               {
               disabled (0),
               enabled (1)
               }
   MAX-ACCESS  read-write
   STATUS      current
   DESCRIPTION
      "Path: ethernet3.editConf.pppoEClient.ipV6.icmpMessages.headerFieldErr

       Possibilities:
               disabled   (0)
               enabled   (1)"
   ::= {er1645v2Lan3PppOEEntry 705830400}

er1645v2Lan3PppOEIpV6IcmpMessagesOptionUnrecognized OBJECT-TYPE
   SYNTAX      INTEGER
               {
               disabled (0),
               enabled (1)
               }
   MAX-ACCESS  read-write
   STATUS      current
   DESCRIPTION
      "Path: ethernet3.editConf.pppoEClient.ipV6.icmpMessages.optionUnrecognized

       Possibilities:
               disabled   (0)
               enabled   (1)"
   ::= {er1645v2Lan3PppOEEntry 705830912}

er1645v2Lan3PppOEIpV6IcmpMessagesRedirect OBJECT-TYPE
   SYNTAX      INTEGER
               {
               disabled (0),
               enabled (1)
               }
   MAX-ACCESS  read-write
   STATUS      current
   DESCRIPTION
      "Path: ethernet3.editConf.pppoEClient.ipV6.icmpMessages.redirect

       Possibilities:
               disabled   (0)
               enabled   (1)"
   ::= {er1645v2Lan3PppOEEntry 705832960}

er1645v2Lan3PppOEPppLnkMOperation OBJECT-TYPE
   SYNTAX      INTEGER
               {
               disabled (0),
               enabled (1)
               }
   MAX-ACCESS  read-write
   STATUS      current
   DESCRIPTION
      "Path: ethernet3.editConf.pppoEClient.ppp.linkMonitoring.operation

       Possibilities:
               disabled   (0)
               enabled   (1)"
   ::= {er1645v2Lan3PppOEEntry 251724032}

er1645v2Lan3PppOEPppLnkMInterval OBJECT-TYPE
   SYNTAX      TimeTicks
   MAX-ACCESS  read-write
   STATUS      current
   DESCRIPTION
      "Path: ethernet3.editConf.pppoEClient.ppp.linkMonitoring.interval

       Time in centi-second."
   ::= {er1645v2Lan3PppOEEntry 251724288}

er1645v2Lan3PppOEPppLnkMRepTimeOut OBJECT-TYPE
   SYNTAX      TimeTicks
   MAX-ACCESS  read-write
   STATUS      current
   DESCRIPTION
      "Path: ethernet3.editConf.pppoEClient.ppp.linkMonitoring.replyTimeOut

       Time in centi-second."
   ::= {er1645v2Lan3PppOEEntry 251724544}

er1645v2Lan3PppOEPppLnkMFailsPrmt OBJECT-TYPE
   SYNTAX      Integer32
   MAX-ACCESS  read-write
   STATUS      current
   DESCRIPTION
      "Path: ethernet3.editConf.pppoEClient.ppp.linkMonitoring.failsPermitted"
   ::= {er1645v2Lan3PppOEEntry 251724800}

er1645v2Lan3PppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.pppoEClient.ppp.authentication

       Possibilities:
               disabled   (0)
               chap   (1)
               pap   (2)
               chapOrPap   (3)
               msChap   (4)
               msChapV2   (5)"
   ::= {er1645v2Lan3PppOEEntry 251789312}

er1645v2Lan3PppOEPppAuthenPeriod OBJECT-TYPE
   SYNTAX      TimeTicks
   MAX-ACCESS  read-write
   STATUS      current
   DESCRIPTION
      "Path: ethernet3.editConf.pppoEClient.ppp.authenPeriod

       Time in centi-second."
   ::= {er1645v2Lan3PppOEEntry 251854848}

er1645v2Lan3PppOEPppSessionName OBJECT-TYPE
   SYNTAX      DisplayString
   MAX-ACCESS  read-write
   STATUS      current
   DESCRIPTION
      "Path: ethernet3.editConf.pppoEClient.ppp.sessionName"
   ::= {er1645v2Lan3PppOEEntry 251985920}

er1645v2Lan3PppOEPppSessionSecret OBJECT-TYPE
   SYNTAX      DisplayString
   MAX-ACCESS  read-write
   STATUS      current
   DESCRIPTION
      "Path: ethernet3.editConf.pppoEClient.ppp.sessionSecret"
   ::= {er1645v2Lan3PppOEEntry 252051456}

er1645v2Lan3PppOEPppEncModeSessionSecret OBJECT-TYPE
   SYNTAX      INTEGER
               {
               none (1),
               encrypt (2),
               encType1 (3),
               invalid (128)
               }
   MAX-ACCESS  read-write
   STATUS      current
   DESCRIPTION
      "Path: ethernet3.editConf.pppoEClient.ppp.encModeSessionSecret

       Possibilities:
               none   (1)
               encrypt   (2)
               encType1   (3)
               invalid   (128)"
   ::= {er1645v2Lan3PppOEEntry 252182528}

er1645v2Lan3PppOEPppEncSessionSecret OBJECT-TYPE
   SYNTAX      DisplayString
   MAX-ACCESS  read-write
   STATUS      current
   DESCRIPTION
      "Path: ethernet3.editConf.pppoEClient.ppp.encSessionSecret"
   ::= {er1645v2Lan3PppOEEntry 252248064}

er1645v2Lan3PppOEPppServiceName OBJECT-TYPE
   SYNTAX      DisplayString
   MAX-ACCESS  read-write
   STATUS      current
   DESCRIPTION
      "Path: ethernet3.editConf.pppoEClient.ppp.serviceName"
   ::= {er1645v2Lan3PppOEEntry 252116992}

er1645v2Lan3PppOEIpH OBJECT-TYPE
   SYNTAX      SEQUENCE OF Er1645v2Lan3PppOEIpHEntry
   MAX-ACCESS  not-accessible
   STATUS      current
   DESCRIPTION
      ""
   ::= {er1645v2Lan3PppOE 51314688}

er1645v2Lan3PppOEIpHEntry OBJECT-TYPE
   SYNTAX      Er1645v2Lan3PppOEIpHEntry
   MAX-ACCESS  not-accessible
   STATUS      current
   DESCRIPTION
      ""
   INDEX      { er1645v2Lan3PppOETableIx,
                er1645v2Lan3PppOEIpHTableIx }
   ::= {er1645v2Lan3PppOEIpH 1}

Er1645v2Lan3PppOEIpHEntry ::=
   SEQUENCE
      {
      er1645v2Lan3PppOEIpHActions
         VariableLengthTableActions,
      er1645v2Lan3PppOEIpHTableIx
         TableIndex,
      er1645v2Lan3PppOEIpHAddress
         IpAddress,
      er1645v2Lan3PppOEIpHDhcpRelayOptionSubscriberId
         DisplayString
      }

er1645v2Lan3PppOEIpHActions OBJECT-TYPE
   SYNTAX      VariableLengthTableActions
   MAX-ACCESS  read-write
   STATUS      current
   DESCRIPTION
      "By way of this field, some manipulations
       on this table may be performed."
   ::= {er1645v2Lan3PppOEIpHEntry 2}

er1645v2Lan3PppOEIpHTableIx OBJECT-TYPE
   SYNTAX      TableIndex
   MAX-ACCESS  not-accessible
   STATUS      current
   DESCRIPTION
      ""
   ::= {er1645v2Lan3PppOEIpHEntry 11}

er1645v2Lan3PppOEIpHAddress OBJECT-TYPE
   SYNTAX      IpAddress
   MAX-ACCESS  read-write
   STATUS      current
   DESCRIPTION
      "Path: ethernet3.editConf.pppoEClient.ip.helpers.address"
   ::= {er1645v2Lan3PppOEIpHEntry 16777216}

er1645v2Lan3PppOEIpHDhcpRelayOptionSubscriberId OBJECT-TYPE
   SYNTAX      DisplayString
   MAX-ACCESS  read-write
   STATUS      current
   DESCRIPTION
      "Path: ethernet3.editConf.pppoEClient.ip.helpers.dhcpRelayOption.subscriberId"
   ::= {er1645v2Lan3PppOEIpHEntry 33947648}

er1645v2Lan3PppOEIpV6Addresses OBJECT-TYPE
   SYNTAX      SEQUENCE OF Er1645v2Lan3PppOEIpV6AddressesEntry
   MAX-ACCESS  not-accessible
   STATUS      current
   DESCRIPTION
      ""
   ::= {er1645v2Lan3PppOE 704839680}

er1645v2Lan3PppOEIpV6AddressesEntry OBJECT-TYPE
   SYNTAX      Er1645v2Lan3PppOEIpV6AddressesEntry
   MAX-ACCESS  not-accessible
   STATUS      current
   DESCRIPTION
      ""
   INDEX      { er1645v2Lan3PppOETableIx,
                er1645v2Lan3PppOEIpV6AddressesTableIx }
   ::= {er1645v2Lan3PppOEIpV6Addresses 1}

Er1645v2Lan3PppOEIpV6AddressesEntry ::=
   SEQUENCE
      {
      er1645v2Lan3PppOEIpV6AddressesActions
         VariableLengthTableActions,
      er1645v2Lan3PppOEIpV6AddressesTableIx
         TableIndex,
      er1645v2Lan3PppOEIpV6AddressesType
         INTEGER,
      er1645v2Lan3PppOEIpV6AddressesAddress
         Ipv6Address,
      er1645v2Lan3PppOEIpV6AddressesPrefixLength
         Integer32,
      er1645v2Lan3PppOEIpV6AddressesGeneralPrefix
         DisplayString,
      er1645v2Lan3PppOEIpV6AddressesRaSend
         INTEGER,
      er1645v2Lan3PppOEIpV6AddressesRaOnLinkFlag
         INTEGER,
      er1645v2Lan3PppOEIpV6AddressesRaAutoFlag
         INTEGER,
      er1645v2Lan3PppOEIpV6AddressesRaValidLifeTime
         TimeTicks,
      er1645v2Lan3PppOEIpV6AddressesRaValidLTMode
         INTEGER,
      er1645v2Lan3PppOEIpV6AddressesRaPrefLifeTime
         TimeTicks,
      er1645v2Lan3PppOEIpV6AddressesRaPrefLTMode
         INTEGER
      }

er1645v2Lan3PppOEIpV6AddressesActions OBJECT-TYPE
   SYNTAX      VariableLengthTableActions
   MAX-ACCESS  read-write
   STATUS      current
   DESCRIPTION
      "By way of this field, some manipulations
       on this table may be performed."
   ::= {er1645v2Lan3PppOEIpV6AddressesEntry 2}

er1645v2Lan3PppOEIpV6AddressesTableIx OBJECT-TYPE
   SYNTAX      TableIndex
   MAX-ACCESS  not-accessible
   STATUS      current
   DESCRIPTION
      ""
   ::= {er1645v2Lan3PppOEIpV6AddressesEntry 11}

er1645v2Lan3PppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.pppoEClient.ipV6.addresses.type

       Possibilities:
               unicast   (0)
               eui64   (1)
               anycast   (2)
               linkLocal   (3)
               generalPrefix   (4)"
   ::= {er1645v2Lan3PppOEIpV6AddressesEntry 50331648}

er1645v2Lan3PppOEIpV6AddressesAddress OBJECT-TYPE
   SYNTAX      Ipv6Address
   MAX-ACCESS  read-write
   STATUS      current
   DESCRIPTION
      "Path: ethernet3.editConf.pppoEClient.ipV6.addresses.address

       ipv6 address"
   ::= {er1645v2Lan3PppOEIpV6AddressesEntry 16777216}

er1645v2Lan3PppOEIpV6AddressesPrefixLength OBJECT-TYPE
   SYNTAX      Integer32
   MAX-ACCESS  read-write
   STATUS      current
   DESCRIPTION
      "Path: ethernet3.editConf.pppoEClient.ipV6.addresses.prefixLength"
   ::= {er1645v2Lan3PppOEIpV6AddressesEntry 33554432}

er1645v2Lan3PppOEIpV6AddressesGeneralPrefix OBJECT-TYPE
   SYNTAX      DisplayString
   MAX-ACCESS  read-write
   STATUS      current
   DESCRIPTION
      "Path: ethernet3.editConf.pppoEClient.ipV6.addresses.generalPrefix"
   ::= {er1645v2Lan3PppOEIpV6AddressesEntry 83886080}

er1645v2Lan3PppOEIpV6AddressesRaSend OBJECT-TYPE
   SYNTAX      INTEGER
               {
               disabled (0),
               enabled (1)
               }
   MAX-ACCESS  read-write
   STATUS      current
   DESCRIPTION
      "Path: ethernet3.editConf.pppoEClient.ipV6.addresses.ra.send

       Possibilities:
               disabled   (0)
               enabled   (1)"
   ::= {er1645v2Lan3PppOEIpV6AddressesEntry 67174400}

er1645v2Lan3PppOEIpV6AddressesRaOnLinkFlag OBJECT-TYPE
   SYNTAX      INTEGER
               {
               disabled (0),
               enabled (1)
               }
   MAX-ACCESS  read-write
   STATUS      current
   DESCRIPTION
      "Path: ethernet3.editConf.pppoEClient.ipV6.addresses.ra.onLinkFlag

       Possibilities:
               disabled   (0)
               enabled   (1)"
   ::= {er1645v2Lan3PppOEIpV6AddressesEntry 67371008}

er1645v2Lan3PppOEIpV6AddressesRaAutoFlag OBJECT-TYPE
   SYNTAX      INTEGER
               {
               disabled (0),
               enabled (1)
               }
   MAX-ACCESS  read-write
   STATUS      current
   DESCRIPTION
      "Path: ethernet3.editConf.pppoEClient.ipV6.addresses.ra.autonomousFlag

       Possibilities:
               disabled   (0)
               enabled   (1)"
   ::= {er1645v2Lan3PppOEIpV6AddressesEntry 67567616}

er1645v2Lan3PppOEIpV6AddressesRaValidLifeTime OBJECT-TYPE
   SYNTAX      TimeTicks
   MAX-ACCESS  read-write
   STATUS      current
   DESCRIPTION
      "Path: ethernet3.editConf.pppoEClient.ipV6.addresses.ra.validLifeTime

       Time in centi-second."
   ::= {er1645v2Lan3PppOEIpV6AddressesEntry 67239936}

er1645v2Lan3PppOEIpV6AddressesRaValidLTMode OBJECT-TYPE
   SYNTAX      INTEGER
               {
               fixed (0),
               infinite (2)
               }
   MAX-ACCESS  read-write
   STATUS      current
   DESCRIPTION
      "Path: ethernet3.editConf.pppoEClient.ipV6.addresses.ra.validLifeTimeMode

       Possibilities:
               fixed   (0)
               infinite   (2)"
   ::= {er1645v2Lan3PppOEIpV6AddressesEntry 67305472}

er1645v2Lan3PppOEIpV6AddressesRaPrefLifeTime OBJECT-TYPE
   SYNTAX      TimeTicks
   MAX-ACCESS  read-write
   STATUS      current
   DESCRIPTION
      "Path: ethernet3.editConf.pppoEClient.ipV6.addresses.ra.prefLifeTime

       Time in centi-second."
   ::= {er1645v2Lan3PppOEIpV6AddressesEntry 67436544}

er1645v2Lan3PppOEIpV6AddressesRaPrefLTMode OBJECT-TYPE
   SYNTAX      INTEGER
               {
               fixed (0),
               infinite (2)
               }
   MAX-ACCESS  read-write
   STATUS      current
   DESCRIPTION
      "Path: ethernet3.editConf.pppoEClient.ipV6.addresses.ra.prefLifeTimeMode

       Possibilities:
               fixed   (0)
               infinite   (2)"
   ::= {er1645v2Lan3PppOEIpV6AddressesEntry 67502080}

er1645v2Lan3PppOEIpV6RaDnsOptionsRdnssServers OBJECT-TYPE
   SYNTAX      SEQUENCE OF Er1645v2Lan3PppOEIpV6RaDnsOptionsRdnssServersEntry
   MAX-ACCESS  not-accessible
   STATUS      current
   DESCRIPTION
      ""
   ::= {er1645v2Lan3PppOE 705039144}

er1645v2Lan3PppOEIpV6RaDnsOptionsRdnssServersEntry OBJECT-TYPE
   SYNTAX      Er1645v2Lan3PppOEIpV6RaDnsOptionsRdnssServersEntry
   MAX-ACCESS  not-accessible
   STATUS      current
   DESCRIPTION
      ""
   INDEX      { er1645v2Lan3PppOETableIx,
                er1645v2Lan3PppOEIpV6RaDnsOptionsRdnssServersTableIx }
   ::= {er1645v2Lan3PppOEIpV6RaDnsOptionsRdnssServers 1}

Er1645v2Lan3PppOEIpV6RaDnsOptionsRdnssServersEntry ::=
   SEQUENCE
      {
      er1645v2Lan3PppOEIpV6RaDnsOptionsRdnssServersActions
         VariableLengthTableActions,
      er1645v2Lan3PppOEIpV6RaDnsOptionsRdnssServersTableIx
         TableIndex,
      er1645v2Lan3PppOEIpV6RaDnsOptionsRdnssServersAddress
         Ipv6Address
      }

er1645v2Lan3PppOEIpV6RaDnsOptionsRdnssServersActions OBJECT-TYPE
   SYNTAX      VariableLengthTableActions
   MAX-ACCESS  read-write
   STATUS      current
   DESCRIPTION
      "By way of this field, some manipulations
       on this table may be performed."
   ::= {er1645v2Lan3PppOEIpV6RaDnsOptionsRdnssServersEntry 2}

er1645v2Lan3PppOEIpV6RaDnsOptionsRdnssServersTableIx OBJECT-TYPE
   SYNTAX      TableIndex
   MAX-ACCESS  not-accessible
   STATUS      current
   DESCRIPTION
      ""
   ::= {er1645v2Lan3PppOEIpV6RaDnsOptionsRdnssServersEntry 11}

er1645v2Lan3PppOEIpV6RaDnsOptionsRdnssServersAddress OBJECT-TYPE
   SYNTAX      Ipv6Address
   MAX-ACCESS  read-write
   STATUS      current
   DESCRIPTION
      "Path: ethernet3.editConf.pppoEClient.ipV6.ra.dnsOptions.rdnss.servers.address

       ipv6 address"
   ::= {er1645v2Lan3PppOEIpV6RaDnsOptionsRdnssServersEntry 16777216}

er1645v2Lan3PppOEIpV6RaDnsOptionsDnsslDomains OBJECT-TYPE
   SYNTAX      SEQUENCE OF Er1645v2Lan3PppOEIpV6RaDnsOptionsDnsslDomainsEntry
   MAX-ACCESS  not-accessible
   STATUS      current
   DESCRIPTION
      ""
   ::= {er1645v2Lan3PppOE 705039176}

er1645v2Lan3PppOEIpV6RaDnsOptionsDnsslDomainsEntry OBJECT-TYPE
   SYNTAX      Er1645v2Lan3PppOEIpV6RaDnsOptionsDnsslDomainsEntry
   MAX-ACCESS  not-accessible
   STATUS      current
   DESCRIPTION
      ""
   INDEX      { er1645v2Lan3PppOETableIx,
                er1645v2Lan3PppOEIpV6RaDnsOptionsDnsslDomainsTableIx }
   ::= {er1645v2Lan3PppOEIpV6RaDnsOptionsDnsslDomains 1}

Er1645v2Lan3PppOEIpV6RaDnsOptionsDnsslDomainsEntry ::=
   SEQUENCE
      {
      er1645v2Lan3PppOEIpV6RaDnsOptionsDnsslDomainsActions
         VariableLengthTableActions,
      er1645v2Lan3PppOEIpV6RaDnsOptionsDnsslDomainsTableIx
         TableIndex,
      er1645v2Lan3PppOEIpV6RaDnsOptionsDnsslDomainsName
         DisplayString
      }

er1645v2Lan3PppOEIpV6RaDnsOptionsDnsslDomainsActions OBJECT-TYPE
   SYNTAX      VariableLengthTableActions
   MAX-ACCESS  read-write
   STATUS      current
   DESCRIPTION
      "By way of this field, some manipulations
       on this table may be performed."
   ::= {er1645v2Lan3PppOEIpV6RaDnsOptionsDnsslDomainsEntry 2}

er1645v2Lan3PppOEIpV6RaDnsOptionsDnsslDomainsTableIx OBJECT-TYPE
   SYNTAX      TableIndex
   MAX-ACCESS  not-accessible
   STATUS      current
   DESCRIPTION
      ""
   ::= {er1645v2Lan3PppOEIpV6RaDnsOptionsDnsslDomainsEntry 11}

er1645v2Lan3PppOEIpV6RaDnsOptionsDnsslDomainsName OBJECT-TYPE
   SYNTAX      DisplayString
   MAX-ACCESS  read-write
   STATUS      current
   DESCRIPTION
      "Path: ethernet3.editConf.pppoEClient.ipV6.ra.dnsOptions.dnssl.domains.name"
   ::= {er1645v2Lan3PppOEIpV6RaDnsOptionsDnsslDomainsEntry 16777216}

er1645v2Lan3PppOEIpV6DhcpClientUserClassOpt OBJECT-TYPE
   SYNTAX      SEQUENCE OF Er1645v2Lan3PppOEIpV6DhcpClientUserClassOptEntry
   MAX-ACCESS  not-accessible
   STATUS      current
   DESCRIPTION
      ""
   ::= {er1645v2Lan3PppOE 705312768}

er1645v2Lan3PppOEIpV6DhcpClientUserClassOptEntry OBJECT-TYPE
   SYNTAX      Er1645v2Lan3PppOEIpV6DhcpClientUserClassOptEntry
   MAX-ACCESS  not-accessible
   STATUS      current
   DESCRIPTION
      ""
   INDEX      { er1645v2Lan3PppOETableIx,
                er1645v2Lan3PppOEIpV6DhcpClientUserClassOptTableIx }
   ::= {er1645v2Lan3PppOEIpV6DhcpClientUserClassOpt 1}

Er1645v2Lan3PppOEIpV6DhcpClientUserClassOptEntry ::=
   SEQUENCE
      {
      er1645v2Lan3PppOEIpV6DhcpClientUserClassOptActions
         VariableLengthTableActions,
      er1645v2Lan3PppOEIpV6DhcpClientUserClassOptTableIx
         TableIndex,
      er1645v2Lan3PppOEIpV6DhcpClientUserClassOptValueAscii
         DisplayString,
      er1645v2Lan3PppOEIpV6DhcpClientUserClassOptValueDecimal
         Integer32,
      er1645v2Lan3PppOEIpV6DhcpClientUserClassOptValueHexData
         OCTET STRING
      }

er1645v2Lan3PppOEIpV6DhcpClientUserClassOptActions OBJECT-TYPE
   SYNTAX      VariableLengthTableActions
   MAX-ACCESS  read-write
   STATUS      current
   DESCRIPTION
      "By way of this field, some manipulations
       on this table may be performed."
   ::= {er1645v2Lan3PppOEIpV6DhcpClientUserClassOptEntry 2}

er1645v2Lan3PppOEIpV6DhcpClientUserClassOptTableIx OBJECT-TYPE
   SYNTAX      TableIndex
   MAX-ACCESS  not-accessible
   STATUS      current
   DESCRIPTION
      ""
   ::= {er1645v2Lan3PppOEIpV6DhcpClientUserClassOptEntry 11}

er1645v2Lan3PppOEIpV6DhcpClientUserClassOptValueAscii OBJECT-TYPE
   SYNTAX      DisplayString
   MAX-ACCESS  read-write
   STATUS      current
   DESCRIPTION
      "Path: ethernet3.editConf.pppoEClient.ipV6.dhcp.client.userClassOpt.value.ascii"
   ::= {er1645v2Lan3PppOEIpV6DhcpClientUserClassOptEntry 16842752}

er1645v2Lan3PppOEIpV6DhcpClientUserClassOptValueDecimal OBJECT-TYPE
   SYNTAX      Integer32
   MAX-ACCESS  read-write
   STATUS      current
   DESCRIPTION
      "Path: ethernet3.editConf.pppoEClient.ipV6.dhcp.client.userClassOpt.value.decimal"
   ::= {er1645v2Lan3PppOEIpV6DhcpClientUserClassOptEntry 16908288}

er1645v2Lan3PppOEIpV6DhcpClientUserClassOptValueHexData OBJECT-TYPE
   SYNTAX      OCTET STRING
   MAX-ACCESS  read-write
   STATUS      current
   DESCRIPTION
      "Path: ethernet3.editConf.pppoEClient.ipV6.dhcp.client.userClassOpt.value.hexData"
   ::= {er1645v2Lan3PppOEIpV6DhcpClientUserClassOptEntry 16973824}

er1645v2Lan3PppOEIpV6DhcpClientVendorCl OBJECT-TYPE
   SYNTAX      SEQUENCE OF Er1645v2Lan3PppOEIpV6DhcpClientVendorClEntry
   MAX-ACCESS  not-accessible
   STATUS      current
   DESCRIPTION
      ""
   ::= {er1645v2Lan3PppOE 705313792}

er1645v2Lan3PppOEIpV6DhcpClientVendorClEntry OBJECT-TYPE
   SYNTAX      Er1645v2Lan3PppOEIpV6DhcpClientVendorClEntry
   MAX-ACCESS  not-accessible
   STATUS      current
   DESCRIPTION
      ""
   INDEX      { er1645v2Lan3PppOETableIx,
                er1645v2Lan3PppOEIpV6DhcpClientVendorClTableIx }
   ::= {er1645v2Lan3PppOEIpV6DhcpClientVendorCl 1}

Er1645v2Lan3PppOEIpV6DhcpClientVendorClEntry ::=
   SEQUENCE
      {
      er1645v2Lan3PppOEIpV6DhcpClientVendorClActions
         VariableLengthTableActions,
      er1645v2Lan3PppOEIpV6DhcpClientVendorClTableIx
         TableIndex,
      er1645v2Lan3PppOEIpV6DhcpClientVendorClValueAscii
         DisplayString,
      er1645v2Lan3PppOEIpV6DhcpClientVendorClValueDecimal
         Integer32,
      er1645v2Lan3PppOEIpV6DhcpClientVendorClValueHexData
         OCTET STRING
      }

er1645v2Lan3PppOEIpV6DhcpClientVendorClActions OBJECT-TYPE
   SYNTAX      VariableLengthTableActions
   MAX-ACCESS  read-write
   STATUS      current
   DESCRIPTION
      "By way of this field, some manipulations
       on this table may be performed."
   ::= {er1645v2Lan3PppOEIpV6DhcpClientVendorClEntry 2}

er1645v2Lan3PppOEIpV6DhcpClientVendorClTableIx OBJECT-TYPE
   SYNTAX      TableIndex
   MAX-ACCESS  not-accessible
   STATUS      current
   DESCRIPTION
      ""
   ::= {er1645v2Lan3PppOEIpV6DhcpClientVendorClEntry 11}

er1645v2Lan3PppOEIpV6DhcpClientVendorClValueAscii OBJECT-TYPE
   SYNTAX      DisplayString
   MAX-ACCESS  read-write
   STATUS      current
   DESCRIPTION
      "Path: ethernet3.editConf.pppoEClient.ipV6.dhcp.client.vendorClassOpt.value.ascii"
   ::= {er1645v2Lan3PppOEIpV6DhcpClientVendorClEntry 16842752}

er1645v2Lan3PppOEIpV6DhcpClientVendorClValueDecimal OBJECT-TYPE
   SYNTAX      Integer32
   MAX-ACCESS  read-write
   STATUS      current
   DESCRIPTION
      "Path: ethernet3.editConf.pppoEClient.ipV6.dhcp.client.vendorClassOpt.value.decimal"
   ::= {er1645v2Lan3PppOEIpV6DhcpClientVendorClEntry 16908288}

er1645v2Lan3PppOEIpV6DhcpClientVendorClValueHexData OBJECT-TYPE
   SYNTAX      OCTET STRING
   MAX-ACCESS  read-write
   STATUS      current
   DESCRIPTION
      "Path: ethernet3.editConf.pppoEClient.ipV6.dhcp.client.vendorClassOpt.value.hexData"
   ::= {er1645v2Lan3PppOEIpV6DhcpClientVendorClEntry 16973824}

er1645v2Lan3PppOEIpV6DhcpRelayDestinations OBJECT-TYPE
   SYNTAX      SEQUENCE OF Er1645v2Lan3PppOEIpV6DhcpRelayDestinationsEntry
   MAX-ACCESS  not-accessible
   STATUS      current
   DESCRIPTION
      ""
   ::= {er1645v2Lan3PppOE 705323072}

er1645v2Lan3PppOEIpV6DhcpRelayDestinationsEntry OBJECT-TYPE
   SYNTAX      Er1645v2Lan3PppOEIpV6DhcpRelayDestinationsEntry
   MAX-ACCESS  not-accessible
   STATUS      current
   DESCRIPTION
      ""
   INDEX      { er1645v2Lan3PppOETableIx,
                er1645v2Lan3PppOEIpV6DhcpRelayDestinationsTableIx }
   ::= {er1645v2Lan3PppOEIpV6DhcpRelayDestinations 1}

Er1645v2Lan3PppOEIpV6DhcpRelayDestinationsEntry ::=
   SEQUENCE
      {
      er1645v2Lan3PppOEIpV6DhcpRelayDestinationsActions
         VariableLengthTableActions,
      er1645v2Lan3PppOEIpV6DhcpRelayDestinationsTableIx
         TableIndex,
      er1645v2Lan3PppOEIpV6DhcpRelayDestinationsAddress
         Ipv6Address,
      er1645v2Lan3PppOEIpV6DhcpRelayDestinationsInterface
         DisplayString
      }

er1645v2Lan3PppOEIpV6DhcpRelayDestinationsActions OBJECT-TYPE
   SYNTAX      VariableLengthTableActions
   MAX-ACCESS  read-write
   STATUS      current
   DESCRIPTION
      "By way of this field, some manipulations
       on this table may be performed."
   ::= {er1645v2Lan3PppOEIpV6DhcpRelayDestinationsEntry 2}

er1645v2Lan3PppOEIpV6DhcpRelayDestinationsTableIx OBJECT-TYPE
   SYNTAX      TableIndex
   MAX-ACCESS  not-accessible
   STATUS      current
   DESCRIPTION
      ""
   ::= {er1645v2Lan3PppOEIpV6DhcpRelayDestinationsEntry 11}

er1645v2Lan3PppOEIpV6DhcpRelayDestinationsAddress OBJECT-TYPE
   SYNTAX      Ipv6Address
   MAX-ACCESS  read-write
   STATUS      current
   DESCRIPTION
      "Path: ethernet3.editConf.pppoEClient.ipV6.dhcp.relay.destinations.address

       ipv6 address"
   ::= {er1645v2Lan3PppOEIpV6DhcpRelayDestinationsEntry 16777216}

er1645v2Lan3PppOEIpV6DhcpRelayDestinationsInterface OBJECT-TYPE
   SYNTAX      DisplayString
   MAX-ACCESS  read-write
   STATUS      current
   DESCRIPTION
      "Path: ethernet3.editConf.pppoEClient.ipV6.dhcp.relay.destinations.interface"
   ::= {er1645v2Lan3PppOEIpV6DhcpRelayDestinationsEntry 33554432}


er1645v2Lan3PppoEServer OBJECT-TYPE
   SYNTAX      DisplayString
   MAX-ACCESS  read-write
   STATUS      current
   DESCRIPTION
      "Path: ethernet3.editConf.pppoEServer
       Info: ppp server name on interface"
   ::= {er1645v2Lan3 37}


er1645v2Lan3MediaType OBJECT-TYPE
   SYNTAX      INTEGER
               {
               utp (1),
               sfp (2),
               auto (3)
               }
   MAX-ACCESS  read-write
   STATUS      current
   DESCRIPTION
      "Path: ethernet3.editConf.mediaType

       Possibilities:
               utp   (1)
               sfp   (2)
               auto   (3)"
   ::= {er1645v2Lan3 38}


er1645v2Lan3InboundHwPriority OBJECT IDENTIFIER ::= {er1645v2Lan3 231}

er1645v2Lan3InboundHwPrioritySSC OBJECT IDENTIFIER ::= {er1645v2Lan3InboundHwPriority 1}

er1645v2Lan3InboundHwPriorityEntry OBJECT IDENTIFIER ::= {er1645v2Lan3InboundHwPrioritySSC 1}

er1645v2Lan3InboundHwPriorityNone OBJECT-TYPE
   SYNTAX      OCTET STRING
   MAX-ACCESS  read-write
   STATUS      current
   DESCRIPTION
      "Path: ethernet3.editConf.inboundHwPriority.none"
   ::= {er1645v2Lan3InboundHwPriorityEntry 16777216}

er1645v2Lan3InboundHwPriorityMapCosToQueueP0 OBJECT-TYPE
   SYNTAX      INTEGER
               {
               queue1 (1),
               queue2 (2)
               }
   MAX-ACCESS  read-write
   STATUS      current
   DESCRIPTION
      "Path: ethernet3.editConf.inboundHwPriority.mapCosToQueue.p0

       Possibilities:
               queue1   (1)
               queue2   (2)"
   ::= {er1645v2Lan3InboundHwPriorityEntry 33619968}

er1645v2Lan3InboundHwPriorityMapCosToQueueP1 OBJECT-TYPE
   SYNTAX      INTEGER
               {
               queue1 (1),
               queue2 (2)
               }
   MAX-ACCESS  read-write
   STATUS      current
   DESCRIPTION
      "Path: ethernet3.editConf.inboundHwPriority.mapCosToQueue.p1

       Possibilities:
               queue1   (1)
               queue2   (2)"
   ::= {er1645v2Lan3InboundHwPriorityEntry 33685504}

er1645v2Lan3InboundHwPriorityMapCosToQueueP2 OBJECT-TYPE
   SYNTAX      INTEGER
               {
               queue1 (1),
               queue2 (2)
               }
   MAX-ACCESS  read-write
   STATUS      current
   DESCRIPTION
      "Path: ethernet3.editConf.inboundHwPriority.mapCosToQueue.p2

       Possibilities:
               queue1   (1)
               queue2   (2)"
   ::= {er1645v2Lan3InboundHwPriorityEntry 33751040}

er1645v2Lan3InboundHwPriorityMapCosToQueueP3 OBJECT-TYPE
   SYNTAX      INTEGER
               {
               queue1 (1),
               queue2 (2)
               }
   MAX-ACCESS  read-write
   STATUS      current
   DESCRIPTION
      "Path: ethernet3.editConf.inboundHwPriority.mapCosToQueue.p3

       Possibilities:
               queue1   (1)
               queue2   (2)"
   ::= {er1645v2Lan3InboundHwPriorityEntry 33816576}

er1645v2Lan3InboundHwPriorityMapCosToQueueP4 OBJECT-TYPE
   SYNTAX      INTEGER
               {
               queue1 (1),
               queue2 (2)
               }
   MAX-ACCESS  read-write
   STATUS      current
   DESCRIPTION
      "Path: ethernet3.editConf.inboundHwPriority.mapCosToQueue.p4

       Possibilities:
               queue1   (1)
               queue2   (2)"
   ::= {er1645v2Lan3InboundHwPriorityEntry 33882112}

er1645v2Lan3InboundHwPriorityMapCosToQueueP5 OBJECT-TYPE
   SYNTAX      INTEGER
               {
               queue1 (1),
               queue2 (2)
               }
   MAX-ACCESS  read-write
   STATUS      current
   DESCRIPTION
      "Path: ethernet3.editConf.inboundHwPriority.mapCosToQueue.p5

       Possibilities:
               queue1   (1)
               queue2   (2)"
   ::= {er1645v2Lan3InboundHwPriorityEntry 33947648}

er1645v2Lan3InboundHwPriorityMapCosToQueueP6 OBJECT-TYPE
   SYNTAX      INTEGER
               {
               queue1 (1),
               queue2 (2)
               }
   MAX-ACCESS  read-write
   STATUS      current
   DESCRIPTION
      "Path: ethernet3.editConf.inboundHwPriority.mapCosToQueue.p6

       Possibilities:
               queue1   (1)
               queue2   (2)"
   ::= {er1645v2Lan3InboundHwPriorityEntry 34013184}

er1645v2Lan3InboundHwPriorityMapCosToQueueP7 OBJECT-TYPE
   SYNTAX      INTEGER
               {
               queue1 (1),
               queue2 (2)
               }
   MAX-ACCESS  read-write
   STATUS      current
   DESCRIPTION
      "Path: ethernet3.editConf.inboundHwPriority.mapCosToQueue.p7

       Possibilities:
               queue1   (1)
               queue2   (2)"
   ::= {er1645v2Lan3InboundHwPriorityEntry 34078720}

er1645v2Lan3InboundHwPriorityMapDscpToQueue OBJECT-TYPE
   SYNTAX      SEQUENCE OF Er1645v2Lan3InboundHwPriorityMapDscpToQueueEntry
   MAX-ACCESS  not-accessible
   STATUS      current
   DESCRIPTION
      ""
   ::= {er1645v2Lan3InboundHwPriority 50331648}

er1645v2Lan3InboundHwPriorityMapDscpToQueueEntry OBJECT-TYPE
   SYNTAX      Er1645v2Lan3InboundHwPriorityMapDscpToQueueEntry
   MAX-ACCESS  not-accessible
   STATUS      current
   DESCRIPTION
      ""
   INDEX      { er1645v2Lan3InboundHwPriorityMapDscpToQueueTableIx }
   ::= {er1645v2Lan3InboundHwPriorityMapDscpToQueue 1}

Er1645v2Lan3InboundHwPriorityMapDscpToQueueEntry ::=
   SEQUENCE
      {
      er1645v2Lan3InboundHwPriorityMapDscpToQueueActions
         VariableLengthTableActions,
      er1645v2Lan3InboundHwPriorityMapDscpToQueueTableIx
         TableIndex,
      er1645v2Lan3InboundHwPriorityMapDscpToQueueStartDscp
         INTEGER,
      er1645v2Lan3InboundHwPriorityMapDscpToQueueEndDscp
         INTEGER,
      er1645v2Lan3InboundHwPriorityMapDscpToQueueQueue
         INTEGER
      }

er1645v2Lan3InboundHwPriorityMapDscpToQueueActions OBJECT-TYPE
   SYNTAX      VariableLengthTableActions
   MAX-ACCESS  read-write
   STATUS      current
   DESCRIPTION
      "By way of this field, some manipulations
       on this table may be performed."
   ::= {er1645v2Lan3InboundHwPriorityMapDscpToQueueEntry 2}

er1645v2Lan3InboundHwPriorityMapDscpToQueueTableIx OBJECT-TYPE
   SYNTAX      TableIndex
   MAX-ACCESS  not-accessible
   STATUS      current
   DESCRIPTION
      ""
   ::= {er1645v2Lan3InboundHwPriorityMapDscpToQueueEntry 11}

er1645v2Lan3InboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan3InboundHwPriorityMapDscpToQueueEntry 16777216}

er1645v2Lan3InboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan3InboundHwPriorityMapDscpToQueueEntry 33554432}

er1645v2Lan3InboundHwPriorityMapDscpToQueueQueue OBJECT-TYPE
   SYNTAX      INTEGER
               {
               queue1 (1),
               queue2 (2)
               }
   MAX-ACCESS  read-write
   STATUS      current
   DESCRIPTION
      "Path: ethernet3.editConf.inboundHwPriority.mapDscpToQueue.queue

       Possibilities:
               queue1   (1)
               queue2   (2)"
   ::= {er1645v2Lan3InboundHwPriorityMapDscpToQueueEntry 50331648}


er1645v2Lan3Name OBJECT-TYPE
   SYNTAX      DisplayString
   MAX-ACCESS  read-write
   STATUS      current
   DESCRIPTION
      "Path: ethernet3.editConf.name
       Info: config interface name"
   ::= {er1645v2Lan3 2}



sr1645v2Lan3 OBJECT IDENTIFIER ::= {r1645v2Lan3 14}


sr1645v2Lan3Descr OBJECT-TYPE
   SYNTAX      DisplayString
   MAX-ACCESS  read-only
   STATUS      current
   DESCRIPTION
      "Path: ethernet3.status.ifDescr
       Info: ifDescr"
   ::= {sr1645v2Lan3 101}


sr1645v2Lan3Type OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet3.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2Lan3 102}


sr1645v2Lan3Mtu OBJECT-TYPE
   SYNTAX      Integer32
   MAX-ACCESS  read-only
   STATUS      current
   DESCRIPTION
      "Path: ethernet3.status.ifMtu
       Info: ifMtu"
   ::= {sr1645v2Lan3 103}


sr1645v2Lan3OperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ifOperStatus
       Info: ifOperStatus

       Possibilities:
               up   (1)
               down   (2)
               testing   (3)
               unknown   (4)
               dormant   (5)
               notPresent   (6)
               lowerLayerDown   (7)"
   ::= {sr1645v2Lan3 107}


sr1645v2Lan3LastChange OBJECT-TYPE
   SYNTAX      TimeTicks
   MAX-ACCESS  read-only
   STATUS      current
   DESCRIPTION
      "Path: ethernet3.status.ifLastChange
       Info: ifLastChange

       Time in centi-second."
   ::= {sr1645v2Lan3 108}


sr1645v2Lan3LastChangeD OBJECT-TYPE
   SYNTAX      DisplayString
   MAX-ACCESS  read-only
   STATUS      current
   DESCRIPTION
      "Path: ethernet3.status.ifLastChangeDate
       Info: ifLastChangeDate"
   ::= {sr1645v2Lan3 183}


sr1645v2Lan3Speed OBJECT-TYPE
   SYNTAX      Gauge32
   MAX-ACCESS  read-only
   STATUS      current
   DESCRIPTION
      "Path: ethernet3.status.ifSpeed
       Info: ifSpeed

       32 bit unsigned gauge value."
   ::= {sr1645v2Lan3 104}


sr1645v2Lan3SnmpIndex OBJECT-TYPE
   SYNTAX      Integer32
   MAX-ACCESS  read-only
   STATUS      current
   DESCRIPTION
      "Path: ethernet3.status.snmpIndex
       Info: SNMP index assigned to this object"
   ::= {sr1645v2Lan3 269}


sr1645v2Lan3Ip OBJECT IDENTIFIER ::= {sr1645v2Lan3 16}

sr1645v2Lan3IpSSC OBJECT IDENTIFIER ::= {sr1645v2Lan3Ip 1}

sr1645v2Lan3IpEntry OBJECT IDENTIFIER ::= {sr1645v2Lan3IpSSC 1}

sr1645v2Lan3IpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ip.status

       Possibilities:
               up   (1)
               down   (2)
               testing   (3)
               unknown   (4)
               dormant   (5)
               notPresent   (6)
               lowerLayerDown   (7)"
   ::= {sr1645v2Lan3IpEntry 1795162112}

sr1645v2Lan3IpAddress OBJECT-TYPE
   SYNTAX      IpAddress
   MAX-ACCESS  read-only
   STATUS      current
   DESCRIPTION
      "Path: ethernet3.status.ip.address"
   ::= {sr1645v2Lan3IpEntry 2030043136}

sr1645v2Lan3IpNetMask OBJECT-TYPE
   SYNTAX      IpAddress
   MAX-ACCESS  read-only
   STATUS      current
   DESCRIPTION
      "Path: ethernet3.status.ip.netMask"
   ::= {sr1645v2Lan3IpEntry 2063597568}

sr1645v2Lan3IpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.ip.dhcp.status

       Possibilities:
               none   (0)
               selecting   (1)
               requesting   (2)
               rebinding   (3)
               bound   (4)
               renewing   (5)
               rebooting   (6)
               initreboot   (7)"
   ::= {sr1645v2Lan3IpEntry 402718720}

sr1645v2Lan3IpDhcpLeaseTime OBJECT-TYPE
   SYNTAX      TimeTicks
   MAX-ACCESS  read-only
   STATUS      current
   DESCRIPTION
      "Path: ethernet3.status.ip.dhcp.leaseTime

       Time in centi-second."
   ::= {sr1645v2Lan3IpEntry 402784256}

sr1645v2Lan3IpSecondaryIp OBJECT-TYPE
   SYNTAX      SEQUENCE OF Sr1645v2Lan3IpSecondaryIpEntry
   MAX-ACCESS  not-accessible
   STATUS      current
   DESCRIPTION
      ""
   ::= {sr1645v2Lan3Ip 385875968}

sr1645v2Lan3IpSecondaryIpEntry OBJECT-TYPE
   SYNTAX      Sr1645v2Lan3IpSecondaryIpEntry
   MAX-ACCESS  not-accessible
   STATUS      current
   DESCRIPTION
      ""
   INDEX      { sr1645v2Lan3IpSecondaryIpTableIx }
   ::= {sr1645v2Lan3IpSecondaryIp 1}

Sr1645v2Lan3IpSecondaryIpEntry ::=
   SEQUENCE
      {
      sr1645v2Lan3IpSecondaryIpTableIx
         TableIndex,
      sr1645v2Lan3IpSecondaryIpAddress
         IpAddress,
      sr1645v2Lan3IpSecondaryIpNetMask
         IpAddress
      }

sr1645v2Lan3IpSecondaryIpTableIx OBJECT-TYPE
   SYNTAX      TableIndex
   MAX-ACCESS  not-accessible
   STATUS      current
   DESCRIPTION
      ""
   ::= {sr1645v2Lan3IpSecondaryIpEntry 11}

sr1645v2Lan3IpSecondaryIpAddress OBJECT-TYPE
   SYNTAX      IpAddress
   MAX-ACCESS  read-only
   STATUS      current
   DESCRIPTION
      "Path: ethernet3.status.ip.secondaryIp.address"
   ::= {sr1645v2Lan3IpSecondaryIpEntry 2030043136}

sr1645v2Lan3IpSecondaryIpNetMask OBJECT-TYPE
   SYNTAX      IpAddress
   MAX-ACCESS  read-only
   STATUS      current
   DESCRIPTION
      "Path: ethernet3.status.ip.secondaryIp.netMask"
   ::= {sr1645v2Lan3IpSecondaryIpEntry 2063597568}


sr1645v2Lan3ArpCache OBJECT IDENTIFIER ::= {sr1645v2Lan3 11}

sr1645v2Lan3ArpCacheSSCTable OBJECT-TYPE
   SYNTAX      SEQUENCE OF Sr1645v2Lan3ArpCacheEntry
   MAX-ACCESS  not-accessible
   STATUS      current
   DESCRIPTION
      "arp cache of ethernet interface"
   ::= {sr1645v2Lan3ArpCache 1}

sr1645v2Lan3ArpCacheEntry OBJECT-TYPE
   SYNTAX      Sr1645v2Lan3ArpCacheEntry
   MAX-ACCESS  not-accessible
   STATUS      current
   DESCRIPTION
      ""
   INDEX      { sr1645v2Lan3ArpCacheTableIx }
   ::= {sr1645v2Lan3ArpCacheSSCTable 1}

Sr1645v2Lan3ArpCacheEntry ::=
   SEQUENCE
      {
      sr1645v2Lan3ArpCacheTableIx
         TableIndex,
      sr1645v2Lan3ArpCacheMacAddress
         OCTET STRING,
      sr1645v2Lan3ArpCacheIpAddress
         IpAddress,
      sr1645v2Lan3ArpCacheType
         INTEGER,
      sr1645v2Lan3ArpCacheTimeOut
         TimeTicks
      }

sr1645v2Lan3ArpCacheTableIx OBJECT-TYPE
   SYNTAX      TableIndex
   MAX-ACCESS  not-accessible
   STATUS      current
   DESCRIPTION
      ""
   ::= {sr1645v2Lan3ArpCacheEntry 11}

sr1645v2Lan3ArpCacheMacAddress OBJECT-TYPE
   SYNTAX      OCTET STRING
   MAX-ACCESS  read-only
   STATUS      current
   DESCRIPTION
      "Path: ethernet3.status.arpCache.macAddress

       MAC address."
   ::= {sr1645v2Lan3ArpCacheEntry 16777216}

sr1645v2Lan3ArpCacheIpAddress OBJECT-TYPE
   SYNTAX      IpAddress
   MAX-ACCESS  read-only
   STATUS      current
   DESCRIPTION
      "Path: ethernet3.status.arpCache.ipAddress"
   ::= {sr1645v2Lan3ArpCacheEntry 33554432}

sr1645v2Lan3ArpCacheType OBJECT-TYPE
   SYNTAX      INTEGER
               {
               static (0),
               dynamic (1)
               }
   MAX-ACCESS  read-only
   STATUS      current
   DESCRIPTION
      "Path: ethernet3.status.arpCache.type

       Possibilities:
               static   (0)
               dynamic   (1)"
   ::= {sr1645v2Lan3ArpCacheEntry 50331648}

sr1645v2Lan3ArpCacheTimeOut OBJECT-TYPE
   SYNTAX      TimeTicks
   MAX-ACCESS  read-only
   STATUS      current
   DESCRIPTION
      "Path: ethernet3.status.arpCache.timeOut

       Time in centi-second."
   ::= {sr1645v2Lan3ArpCacheEntry 67108864}


sr1645v2Lan3BrS OBJECT IDENTIFIER ::= {sr1645v2Lan3 28}

sr1645v2Lan3BrSSSC OBJECT IDENTIFIER ::= {sr1645v2Lan3BrS 1}

sr1645v2Lan3BrSEntry OBJECT IDENTIFIER ::= {sr1645v2Lan3BrSSSC 1}

sr1645v2Lan3BrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.bridging.status

       Possibilities:
               disabled   (0)
               discarding   (1)
               learning   (2)
               forwarding   (3)
               backupBlockedIntfDown   (256)
               backupBlockedIntfUp   (259)
               shutdown   (255)"
   ::= {sr1645v2Lan3BrSEntry 16777216}

sr1645v2Lan3BrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.bridging.spanningTree.portRole

       Possibilities:
               none   (0)
               root   (1)
               designated   (2)
               alternate   (3)
               backup   (4)
               disabled   (5)
               master   (6)"
   ::= {sr1645v2Lan3BrSEntry 33619968}

sr1645v2Lan3BrSStPortId OBJECT-TYPE
   SYNTAX      Integer32
   MAX-ACCESS  read-only
   STATUS      current
   DESCRIPTION
      "Path: ethernet3.status.bridging.spanningTree.portId"
   ::= {sr1645v2Lan3BrSEntry 33685504}

sr1645v2Lan3BrSStPpCostExtPathCost OBJECT-TYPE
   SYNTAX      Integer32
   MAX-ACCESS  read-only
   STATUS      current
   DESCRIPTION
      "Path: ethernet3.status.bridging.spanningTree.portPathCosts.extPathCost"
   ::= {sr1645v2Lan3BrSEntry 33751296}

sr1645v2Lan3BrSStPpCostIntPathCost OBJECT-TYPE
   SYNTAX      Integer32
   MAX-ACCESS  read-only
   STATUS      current
   DESCRIPTION
      "Path: ethernet3.status.bridging.spanningTree.portPathCosts.intPathCost"
   ::= {sr1645v2Lan3BrSEntry 33751552}

sr1645v2Lan3BrSStExtRpCost OBJECT-TYPE
   SYNTAX      Integer32
   MAX-ACCESS  read-only
   STATUS      current
   DESCRIPTION
      "Path: ethernet3.status.bridging.spanningTree.extRootPathCost"
   ::= {sr1645v2Lan3BrSEntry 33816576}

sr1645v2Lan3BrSStIntRpCost OBJECT-TYPE
   SYNTAX      Integer32
   MAX-ACCESS  read-only
   STATUS      current
   DESCRIPTION
      "Path: ethernet3.status.bridging.spanningTree.intRootPathCost"
   ::= {sr1645v2Lan3BrSEntry 33882112}

sr1645v2Lan3BrSStDesBrIdPriority OBJECT-TYPE
   SYNTAX      Integer32
   MAX-ACCESS  read-only
   STATUS      current
   DESCRIPTION
      "Path: ethernet3.status.bridging.spanningTree.designatedBridgeId.priority"
   ::= {sr1645v2Lan3BrSEntry 33947904}

sr1645v2Lan3BrSStDesBrIdMacAddress OBJECT-TYPE
   SYNTAX      OCTET STRING
   MAX-ACCESS  read-only
   STATUS      current
   DESCRIPTION
      "Path: ethernet3.status.bridging.spanningTree.designatedBridgeId.macAddress

       MAC address."
   ::= {sr1645v2Lan3BrSEntry 33948160}

sr1645v2Lan3BrSStDesPrtId OBJECT-TYPE
   SYNTAX      Integer32
   MAX-ACCESS  read-only
   STATUS      current
   DESCRIPTION
      "Path: ethernet3.status.bridging.spanningTree.designatedPortId"
   ::= {sr1645v2Lan3BrSEntry 34013184}

sr1645v2Lan3BrSStDesInt OBJECT-TYPE
   SYNTAX      INTEGER
               {
               no (0),
               yes (1)
               }
   MAX-ACCESS  read-only
   STATUS      current
   DESCRIPTION
      "Path: ethernet3.status.bridging.spanningTree.designatedOrInternal

       Possibilities:
               no   (0)
               yes   (1)"
   ::= {sr1645v2Lan3BrSEntry 34078720}

sr1645v2Lan3BrSStEdgeDetection OBJECT-TYPE
   SYNTAX      INTEGER
               {
               none (0),
               edge (1),
               notEdge (2)
               }
   MAX-ACCESS  read-only
   STATUS      current
   DESCRIPTION
      "Path: ethernet3.status.bridging.spanningTree.edgeDetection

       Possibilities:
               none   (0)
               edge   (1)
               notEdge   (2)"
   ::= {sr1645v2Lan3BrSEntry 34144256}


sr1645v2Lan3MacAddress OBJECT-TYPE
   SYNTAX      OCTET STRING
   MAX-ACCESS  read-only
   STATUS      current
   DESCRIPTION
      "Path: ethernet3.status.macAddress
       Info: ifPhysAddress

       MAC address."
   ::= {sr1645v2Lan3 105}


sr1645v2Lan3IpAdEntBcastAddr OBJECT-TYPE
   SYNTAX      Integer32
   MAX-ACCESS  read-only
   STATUS      current
   DESCRIPTION
      "Path: ethernet3.status.ipAdEntBcastAddr
       Info: ipAdEntBcastAddr"
   ::= {sr1645v2Lan3 124}


sr1645v2Lan3IpAdEntReasmMaxSize OBJECT-TYPE
   SYNTAX      Integer32
   MAX-ACCESS  read-only
   STATUS      current
   DESCRIPTION
      "Path: ethernet3.status.ipAdEntReasmMaxSize
       Info: ipAdEntReasmMaxSize"
   ::= {sr1645v2Lan3 125}


sr1645v2Lan3Adapter OBJECT IDENTIFIER ::= {sr1645v2Lan3 145}

sr1645v2Lan3AdapterSSC OBJECT IDENTIFIER ::= {sr1645v2Lan3Adapter 1}

sr1645v2Lan3AdapterEntry OBJECT IDENTIFIER ::= {sr1645v2Lan3AdapterSSC 1}

sr1645v2Lan3AdapterSpeed OBJECT-TYPE
   SYNTAX      INTEGER
               {
               s10 (0),
               s100 (1),
               s1000 (2),
               s200 (3)
               }
   MAX-ACCESS  read-only
   STATUS      current
   DESCRIPTION
      "Path: ethernet3.status.adapter.speed

       Possibilities:
               10   (0)
               100   (1)
               1000   (2)
               200   (3)"
   ::= {sr1645v2Lan3AdapterEntry 16777216}

sr1645v2Lan3AdapterDuplex OBJECT-TYPE
   SYNTAX      INTEGER
               {
               halfDuplex (0),
               fullDuplex (1)
               }
   MAX-ACCESS  read-only
   STATUS      current
   DESCRIPTION
      "Path: ethernet3.status.adapter.duplex

       Possibilities:
               halfDuplex   (0)
               fullDuplex   (1)"
   ::= {sr1645v2Lan3AdapterEntry 33554432}


sr1645v2Lan3Oam OBJECT IDENTIFIER ::= {sr1645v2Lan3 901}

sr1645v2Lan3OamSSC OBJECT IDENTIFIER ::= {sr1645v2Lan3Oam 1}

sr1645v2Lan3OamEntry OBJECT IDENTIFIER ::= {sr1645v2Lan3OamSSC 1}

sr1645v2Lan3OamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet3.status.oam.discovery

       Possibilities:
               fault   (0)
               sendLocal   (1)
               passiveWait   (2)
               sendLocalRemote   (3)
               sendLocalRemoteOk   (4)
               sendAny   (5)"
   ::= {sr1645v2Lan3OamEntry 16777216}

sr1645v2Lan3OamLoopback OBJECT-TYPE
   SYNTAX      INTEGER
               {
               idle (0),
               waiting (1),
               localRunning (2),
               remoteRunning (3)
               }
   MAX-ACCESS  read-only
   STATUS      current
   DESCRIPTION
      "Path: ethernet3.status.oam.loopback

       Possibilities:
               idle   (0)
               waiting   (1)
               localRunning   (2)
               remoteRunning   (3)"
   ::= {sr1645v2Lan3OamEntry 33554432}

sr1645v2Lan3OamLocalInfoVersion OBJECT-TYPE
   SYNTAX      Integer32
   MAX-ACCESS  read-only
   STATUS      current
   DESCRIPTION
      "Path: ethernet3.status.oam.localInfo.version"
   ::= {sr1645v2Lan3OamEntry 50397184}

sr1645v2Lan3OamLocalInfoRevision OBJECT-TYPE
   SYNTAX      Integer32
   MAX-ACCESS  read-only
   STATUS      current
   DESCRIPTION
      "Path: ethernet3.status.oam.localInfo.revision"
   ::= {sr1645v2Lan3OamEntry 50462720}

sr1645v2Lan3OamLocalInfoStateMuxAction OBJECT-TYPE
   SYNTAX      INTEGER
               {
               forwarding (0),
               discarding (1)
               }
   MAX-ACCESS  read-only
   STATUS      current
   DESCRIPTION
      "Path: ethernet3.status.oam.localInfo.state.muxAction

       Possibilities:
               forwarding   (0)
               discarding   (1)"
   ::= {sr1645v2Lan3OamEntry 50528512}

sr1645v2Lan3OamLocalInfoStateParserAction OBJECT-TYPE
   SYNTAX      INTEGER
               {
               forwarding (0),
               loopback (1),
               discarding (2),
               reserved (3)
               }
   MAX-ACCESS  read-only
   STATUS      current
   DESCRIPTION
      "Path: ethernet3.status.oam.localInfo.state.parserAction

       Possibilities:
               forwarding   (0)
               loopback   (1)
               discarding   (2)
               reserved   (3)"
   ::= {sr1645v2Lan3OamEntry 50528768}

sr1645v2Lan3OamLocalInfoOui OBJECT-TYPE
   SYNTAX      OCTET STRING
   MAX-ACCESS  read-only
   STATUS      current
   DESCRIPTION
      "Path: ethernet3.status.oam.localInfo.oui"
   ::= {sr1645v2Lan3OamEntry 50593792}

sr1645v2Lan3OamLocalInfoVendorInfo OBJECT-TYPE
   SYNTAX      OCTET STRING
   MAX-ACCESS  read-only
   STATUS      current
   DESCRIPTION
      "Path: ethernet3.status.oam.localInfo.vendorInfo"
   ::= {sr1645v2Lan3OamEntry 50659328}

sr1645v2Lan3OamLocalInfoVarRetrieval OBJECT-TYPE
   SYNTAX      INTEGER
               {
               notSupported (0),
               supported (1)
               }
   MAX-ACCESS  read-only
   STATUS      current
   DESCRIPTION
      "Path: ethernet3.status.oam.localInfo.varRetrieval

       Possibilities:
               notSupported   (0)
               supported   (1)"
   ::= {sr1645v2Lan3OamEntry 50724864}

sr1645v2Lan3OamLocalInfoLinkEvents OBJECT-TYPE
   SYNTAX      INTEGER
               {
               ignored (0),
               interpreted (1)
               }
   MAX-ACCESS  read-only
   STATUS      current
   DESCRIPTION
      "Path: ethernet3.status.oam.localInfo.linkEvents

       Possibilities:
               ignored   (0)
               interpreted   (1)"
   ::= {sr1645v2Lan3OamEntry 50790400}

sr1645v2Lan3OamLocalInfoLoopback OBJECT-TYPE
   SYNTAX      INTEGER
               {
               notSupported (0),
               supported (1)
               }
   MAX-ACCESS  read-only
   STATUS      current
   DESCRIPTION
      "Path: ethernet3.status.oam.localInfo.loopback

       Possibilities:
               notSupported   (0)
               supported   (1)"
   ::= {sr1645v2Lan3OamEntry 50855936}

sr1645v2Lan3OamLocalInfoUnidirectional OBJECT-TYPE
   SYNTAX      INTEGER
               {
               notSupported (0),
               supported (1)
               }
   MAX-ACCESS  read-only
   STATUS      current
   DESCRIPTION
      "Path: ethernet3.status.oam.localInfo.unidirectional

       Possibilities:
               notSupported   (0)
               supported   (1)"
   ::= {sr1645v2Lan3OamEntry 50921472}

sr1645v2Lan3OamLocalInfoMode OBJECT-TYPE
   SYNTAX      INTEGER
               {
               passive (0),
               active (1)
               }
   MAX-ACCESS  read-only
   STATUS      current
   DESCRIPTION
      "Path: ethernet3.status.oam.localInfo.mode

       Possibilities:
               passive   (0)
               active   (1)"
   ::= {sr1645v2Lan3OamEntry 50987008}

sr1645v2Lan3OamLocalInfoMaxPduSize OBJECT-TYPE
   SYNTAX      Integer32
   MAX-ACCESS  read-only
   STATUS      current
   DESCRIPTION
      "Path: ethernet3.status.oam.localInfo.maxPduSize"
   ::= {sr1645v2Lan3OamEntry 51052544}

sr1645v2Lan3OamRemoteInfoVersion OBJECT-TYPE
   SYNTAX      Integer32
   MAX-ACCESS  read-only
   STATUS      current
   DESCRIPTION
      "Path: ethernet3.status.oam.remoteInfo.version"
   ::= {sr1645v2Lan3OamEntry 67174400}

sr1645v2Lan3OamRemoteInfoRevision OBJECT-TYPE
   SYNTAX      Integer32
   MAX-ACCESS  read-only
   STATUS      current
   DESCRIPTION
      "Path: ethernet3.status.oam.remoteInfo.revision"
   ::= {sr1645v2Lan3OamEntry 67239936}

sr1645v2Lan3OamRemoteInfoStateMuxAction OBJECT-TYPE
   SYNTAX      INTEGER
               {
               forwarding (0),
               discarding (1)
               }
   MAX-ACCESS  read-only
   STATUS      current
   DESCRIPTION
      "Path: ethernet3.status.oam.remoteInfo.state.muxAction

       Possibilities:
               forwarding   (0)
               discarding   (1)"
   ::= {sr1645v2Lan3OamEntry 67305728}

sr1645v2Lan3OamRemoteInfoStateParserAction OBJECT-TYPE
   SYNTAX      INTEGER
               {
               forwarding (0),
               loopback (1),
               discarding (2),
               reserved (3)
               }
   MAX-ACCESS  read-only
   STATUS      current
   DESCRIPTION
      "Path: ethernet3.status.oam.remoteInfo.state.parserAction

       Possibilities:
               forwarding   (0)
               loopback   (1)
               discarding   (2)
               reserved   (3)"
   ::= {sr1645v2Lan3OamEntry 67305984}

sr1645v2Lan3OamRemoteInfoOui OBJECT-TYPE
   SYNTAX      OCTET STRING
   MAX-ACCESS  read-only
   STATUS      current
   DESCRIPTION
      "Path: ethernet3.status.oam.remoteInfo.oui"
   ::= {sr1645v2Lan3OamEntry 67371008}

sr1645v2Lan3OamRemoteInfoVendorInfo OBJECT-TYPE
   SYNTAX      OCTET STRING
   MAX-ACCESS  read-only
   STATUS      current
   DESCRIPTION
      "Path: ethernet3.status.oam.remoteInfo.vendorInfo"
   ::= {sr1645v2Lan3OamEntry 67436544}

sr1645v2Lan3OamRemoteInfoVarRetrieval OBJECT-TYPE
   SYNTAX      INTEGER
               {
               notSupported (0),
               supported (1)
               }
   MAX-ACCESS  read-only
   STATUS      current
   DESCRIPTION
      "Path: ethernet3.status.oam.remoteInfo.varRetrieval

       Possibilities:
               notSupported   (0)
               supported   (1)"
   ::= {sr1645v2Lan3OamEntry 67502080}

sr1645v2Lan3OamRemoteInfoLinkEvents OBJECT-TYPE
   SYNTAX      INTEGER
               {
               ignored (0),
               interpreted (1)
               }
   MAX-ACCESS  read-only
   STATUS      current
   DESCRIPTION
      "Path: ethernet3.status.oam.remoteInfo.linkEvents

       Possibilities:
               ignored   (0)
               interpreted   (1)"
   ::= {sr1645v2Lan3OamEntry 67567616}

sr1645v2Lan3OamRemoteInfoLoopback OBJECT-TYPE
   SYNTAX      INTEGER
               {
               notSupported (0),
               supported (1)
               }
   MAX-ACCESS  read-only
   STATUS      current
   DESCRIPTION
      "Path: ethernet3.status.oam.remoteInfo.loopback

       Possibilities:
               notSupported   (0)
               supported   (1)"
   ::= {sr1645v2Lan3OamEntry 67633152}

sr1645v2Lan3OamRemoteInfoUnidirectional OBJECT-TYPE
   SYNTAX      INTEGER
               {
               notSupported (0),
               supported (1)
               }
   MAX-ACCESS  read-only
   STATUS      current
   DESCRIPTION
      "Path: ethernet3.status.oam.remoteInfo.unidirectional

       Possibilities:
               notSupported   (0)
               supported   (1)"
   ::= {sr1645v2Lan3OamEntry 67698688}

sr1645v2Lan3OamRemoteInfoMode OBJECT-TYPE
   SYNTAX      INTEGER
               {
               passive (0),
               active (1)
               }
   MAX-ACCESS  read-only
   STATUS      current
   DESCRIPTION
      "Path: ethernet3.status.oam.remoteInfo.mode

       Possibilities:
               passive   (0)
               active   (1)"
   ::= {sr1645v2Lan3OamEntry 67764224}

sr1645v2Lan3OamRemoteInfoMaxPduSize OBJECT-TYPE
   SYNTAX      Integer32
   MAX-ACCESS  read-only
   STATUS      current
   DESCRIPTION
      "Path: ethernet3.status.oam.remoteInfo.maxPduSize"
   ::= {sr1645v2Lan3OamEntry 67829760}

sr1645v2Lan3OamEventsErroredSymbolWindow OBJECT-TYPE
   SYNTAX      Integer32
   UNITS       "symbols"
   MAX-ACCESS  read-only
   STATUS      current
   DESCRIPTION
      "Path: ethernet3.status.oam.events.erroredSymbol.window

       unit name = symbols"
   ::= {sr1645v2Lan3OamEntry 83951872}

sr1645v2Lan3OamEventsErroredSymbolThreshold OBJECT-TYPE
   SYNTAX      OCTET STRING
   UNITS       "symbols"
   MAX-ACCESS  read-only
   STATUS      current
   DESCRIPTION
      "Path: ethernet3.status.oam.events.erroredSymbol.threshold

       unit name = symbols"
   ::= {sr1645v2Lan3OamEntry 83952128}

sr1645v2Lan3OamEventsErroredFramePeriodWindow OBJECT-TYPE
   SYNTAX      INTEGER
               {
               default (0)
               }
   UNITS       "frames"
   MAX-ACCESS  read-only
   STATUS      current
   DESCRIPTION
      "Path: ethernet3.status.oam.events.erroredFramePeriod.window

       unit name = frames

       Possibilities:
               default   (0)"
   ::= {sr1645v2Lan3OamEntry 84017408}

sr1645v2Lan3OamEventsErroredFramePeriodThreshold OBJECT-TYPE
   SYNTAX      Integer32
   UNITS       "frames"
   MAX-ACCESS  read-only
   STATUS      current
   DESCRIPTION
      "Path: ethernet3.status.oam.events.erroredFramePeriod.threshold

       unit name = frames"
   ::= {sr1645v2Lan3OamEntry 84017664}

sr1645v2Lan3OamEventsErroredFrameWindow OBJECT-TYPE
   SYNTAX      Integer32
   UNITS       "100msec"
   MAX-ACCESS  read-only
   STATUS      current
   DESCRIPTION
      "Path: ethernet3.status.oam.events.erroredFrame.window

       unit name = 100msec"
   ::= {sr1645v2Lan3OamEntry 84082944}

sr1645v2Lan3OamEventsErroredFrameThreshold OBJECT-TYPE
   SYNTAX      Integer32
   UNITS       "frames"
   MAX-ACCESS  read-only
   STATUS      current
   DESCRIPTION
      "Path: ethernet3.status.oam.events.erroredFrame.threshold

       unit name = frames"
   ::= {sr1645v2Lan3OamEntry 84083200}

sr1645v2Lan3OamEventsErroredFrameSecondsWindow OBJECT-TYPE
   SYNTAX      Integer32
   UNITS       "100msec"
   MAX-ACCESS  read-only
   STATUS      current
   DESCRIPTION
      "Path: ethernet3.status.oam.events.erroredFrameSeconds.window

       unit name = 100msec"
   ::= {sr1645v2Lan3OamEntry 84148480}

sr1645v2Lan3OamEventsErroredFrameSecondsThreshold OBJECT-TYPE
   SYNTAX      Integer32
   UNITS       "frames"
   MAX-ACCESS  read-only
   STATUS      current
   DESCRIPTION
      "Path: ethernet3.status.oam.events.erroredFrameSeconds.threshold

       unit name = frames"
   ::= {sr1645v2Lan3OamEntry 84148736}


sr1645v2Lan3OamEventLog OBJECT IDENTIFIER ::= {sr1645v2Lan3 911}

sr1645v2Lan3OamEventLogSSCTable OBJECT-TYPE
   SYNTAX      SEQUENCE OF Sr1645v2Lan3OamEventLogEntry
   MAX-ACCESS  not-accessible
   STATUS      current
   DESCRIPTION
      "OAM event log"
   ::= {sr1645v2Lan3OamEventLog 1}

sr1645v2Lan3OamEventLogEntry OBJECT-TYPE
   SYNTAX      Sr1645v2Lan3OamEventLogEntry
   MAX-ACCESS  not-accessible
   STATUS      current
   DESCRIPTION
      ""
   INDEX      { sr1645v2Lan3OamEventLogTableIx }
   ::= {sr1645v2Lan3OamEventLogSSCTable 1}

Sr1645v2Lan3OamEventLogEntry ::=
   SEQUENCE
      {
      sr1645v2Lan3OamEventLogTableIx
         TableIndex,
      sr1645v2Lan3OamEventLogSysUpTime
         TimeTicks,
      sr1645v2Lan3OamEventLogLocation
         INTEGER,
      sr1645v2Lan3OamEventLogType
         INTEGER,
      sr1645v2Lan3OamEventLogOui
         OCTET STRING,
      sr1645v2Lan3OamEventLogWindow
         Counter64,
      sr1645v2Lan3OamEventLogThreshold
         Counter64,
      sr1645v2Lan3OamEventLogTotal
         Counter32,
      sr1645v2Lan3OamEventLogValue
         Counter64,
      sr1645v2Lan3OamEventLogRunningTotal
         Counter64
      }

sr1645v2Lan3OamEventLogTableIx OBJECT-TYPE
   SYNTAX      TableIndex
   MAX-ACCESS  not-accessible
   STATUS      current
   DESCRIPTION
      ""
   ::= {sr1645v2Lan3OamEventLogEntry 11}

sr1645v2Lan3OamEventLogSysUpTime OBJECT-TYPE
   SYNTAX      TimeTicks
   MAX-ACCESS  read-only
   STATUS      current
   DESCRIPTION
      "Path: ethernet3.status.oamEventLog.sysUpTime

       Time in centi-second."
   ::= {sr1645v2Lan3OamEventLogEntry 16777216}

sr1645v2Lan3OamEventLogLocation OBJECT-TYPE
   SYNTAX      INTEGER
               {
               local (1),
               remote (2)
               }
   MAX-ACCESS  read-only
   STATUS      current
   DESCRIPTION
      "Path: ethernet3.status.oamEventLog.location

       Possibilities:
               local   (1)
               remote   (2)"
   ::= {sr1645v2Lan3OamEventLogEntry 33554432}

sr1645v2Lan3OamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet3.status.oamEventLog.type

       Possibilities:
               erroredSymbols   (1)
               erroredFramePeriod   (2)
               erroredFrame   (3)
               erroredFrameSeconds   (4)
               linkFault   (256)
               dyingGasp   (257)
               criticalLink   (258)"
   ::= {sr1645v2Lan3OamEventLogEntry 50331648}

sr1645v2Lan3OamEventLogOui OBJECT-TYPE
   SYNTAX      OCTET STRING
   MAX-ACCESS  read-only
   STATUS      current
   DESCRIPTION
      "Path: ethernet3.status.oamEventLog.oui"
   ::= {sr1645v2Lan3OamEventLogEntry 67108864}

sr1645v2Lan3OamEventLogWindow OBJECT-TYPE
   SYNTAX      Counter64
   MAX-ACCESS  read-only
   STATUS      current
   DESCRIPTION
      "Path: ethernet3.status.oamEventLog.window

       64 bit unsigned wrappable counter."
   ::= {sr1645v2Lan3OamEventLogEntry 83886080}

sr1645v2Lan3OamEventLogThreshold OBJECT-TYPE
   SYNTAX      Counter64
   MAX-ACCESS  read-only
   STATUS      current
   DESCRIPTION
      "Path: ethernet3.status.oamEventLog.threshold

       64 bit unsigned wrappable counter."
   ::= {sr1645v2Lan3OamEventLogEntry 100663296}

sr1645v2Lan3OamEventLogTotal OBJECT-TYPE
   SYNTAX      Counter32
   MAX-ACCESS  read-only
   STATUS      current
   DESCRIPTION
      "Path: ethernet3.status.oamEventLog.total

       32 bit unsigned wrappable counter."
   ::= {sr1645v2Lan3OamEventLogEntry 117440512}

sr1645v2Lan3OamEventLogValue OBJECT-TYPE
   SYNTAX      Counter64
   MAX-ACCESS  read-only
   STATUS      current
   DESCRIPTION
      "Path: ethernet3.status.oamEventLog.value

       64 bit unsigned wrappable counter."
   ::= {sr1645v2Lan3OamEventLogEntry 134217728}

sr1645v2Lan3OamEventLogRunningTotal OBJECT-TYPE
   SYNTAX      Counter64
   MAX-ACCESS  read-only
   STATUS      current
   DESCRIPTION
      "Path: ethernet3.status.oamEventLog.runningTotal

       64 bit unsigned wrappable counter."
   ::= {sr1645v2Lan3OamEventLogEntry 150994944}


sr1645v2Lan3Lst OBJECT IDENTIFIER ::= {sr1645v2Lan3 18}

sr1645v2Lan3LstSSC OBJECT IDENTIFIER ::= {sr1645v2Lan3Lst 1}

sr1645v2Lan3LstEntry OBJECT IDENTIFIER ::= {sr1645v2Lan3LstSSC 1}

sr1645v2Lan3LstTrackedInterface OBJECT-TYPE
   SYNTAX      DisplayString
   MAX-ACCESS  read-only
   STATUS      current
   DESCRIPTION
      "Path: ethernet3.status.linkStateTracking.trackedInterface"
   ::= {sr1645v2Lan3LstEntry 16777216}

sr1645v2Lan3LstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet3.status.linkStateTracking.ifOperStatus

       Possibilities:
               up   (1)
               down   (2)
               testing   (3)
               unknown   (4)
               dormant   (5)
               notPresent   (6)
               lowerLayerDown   (7)
                  (255)"
   ::= {sr1645v2Lan3LstEntry 50331648}


sr1645v2Lan3Vlan OBJECT IDENTIFIER ::= {sr1645v2Lan3 34}

sr1645v2Lan3VlanSSCTable OBJECT-TYPE
   SYNTAX      SEQUENCE OF Sr1645v2Lan3VlanEntry
   MAX-ACCESS  not-accessible
   STATUS      current
   DESCRIPTION
      ""
   ::= {sr1645v2Lan3Vlan 1}

sr1645v2Lan3VlanEntry OBJECT-TYPE
   SYNTAX      Sr1645v2Lan3VlanEntry
   MAX-ACCESS  not-accessible
   STATUS      current
   DESCRIPTION
      ""
   INDEX      { sr1645v2Lan3VlanTableIx }
   ::= {sr1645v2Lan3VlanSSCTable 1}

Sr1645v2Lan3VlanEntry ::=
   SEQUENCE
      {
      sr1645v2Lan3VlanTableIx
         TableIndex,
      sr1645v2Lan3VlanName
         DisplayString,
      sr1645v2Lan3VlanMode
         INTEGER,
      sr1645v2Lan3VlanIfOperStatus
         INTEGER,
      sr1645v2Lan3VlanIfLastChange
         TimeTicks,
      sr1645v2Lan3VlanIfLastChangeDate
         DisplayString,
      sr1645v2Lan3VlanIpAddress
         IpAddress,
      sr1645v2Lan3VlanIpNetMask
         IpAddress,
      sr1645v2Lan3VlanIpRemote
         IpAddress,
      sr1645v2Lan3VlanIpDhcpStatus
         INTEGER,
      sr1645v2Lan3VlanIpDhcpLeaseTime
         TimeTicks,
      sr1645v2Lan3VlanIpV6State
         INTEGER,
      sr1645v2Lan3VlanIpV6InterfaceId
         OCTET STRING,
      sr1645v2Lan3VlanIpV6LinkMtu
         Integer32,
      sr1645v2Lan3VlanIpV6HopLimit
         Integer32,
      sr1645v2Lan3VlanIpV6DhcpIaid
         Counter32,
      sr1645v2Lan3VlanIpV6RaRcvOption
         Integer32,
      sr1645v2Lan3VlanBridgingStatus
         INTEGER,
      sr1645v2Lan3VlanBridgingSpanningTreePortRole
         INTEGER,
      sr1645v2Lan3VlanBridgingSpanningTreePortId
         Integer32,
      sr1645v2Lan3VlanBridgingSpanningTreePpCostExtPathCost
         Integer32,
      sr1645v2Lan3VlanBridgingSpanningTreePpCostIntPathCost
         Integer32,
      sr1645v2Lan3VlanBridgingSpanningTreeExtRpCost
         Integer32,
      sr1645v2Lan3VlanBridgingSpanningTreeIntRpCost
         Integer32,
      sr1645v2Lan3VlanBridgingSpanningTreeDesBrIdPriority
         Integer32,
      sr1645v2Lan3VlanBridgingSpanningTreeDesBrIdMacAddress
         OCTET STRING,
      sr1645v2Lan3VlanBridgingSpanningTreeDesPrtId
         Integer32,
      sr1645v2Lan3VlanBridgingSpanningTreeDesInt
         INTEGER,
      sr1645v2Lan3VlanBridgingSpanningTreeEdgeDetection
         INTEGER,
      sr1645v2Lan3VlanVlanVid
         Integer32,
      sr1645v2Lan3VlanPppOEthDiscState
         INTEGER,
      sr1645v2Lan3VlanPppOEthPeerMac
         OCTET STRING,
      sr1645v2Lan3VlanPppOEthServiceName
         DisplayString,
      sr1645v2Lan3VlanPppLcpState
         INTEGER,
      sr1645v2Lan3VlanPppIpcpState
         INTEGER,
      sr1645v2Lan3VlanPppIp6cpState
         INTEGER,
      sr1645v2Lan3VlanPppMyAutSt
         INTEGER,
      sr1645v2Lan3VlanPppHisAutSt
         INTEGER,
      sr1645v2Lan3VlanPppMru
         Integer32
      }

sr1645v2Lan3VlanTableIx OBJECT-TYPE
   SYNTAX      TableIndex
   MAX-ACCESS  not-accessible
   STATUS      current
   DESCRIPTION
      ""
   ::= {sr1645v2Lan3VlanEntry 11}

sr1645v2Lan3VlanName OBJECT-TYPE
   SYNTAX      DisplayString
   MAX-ACCESS  read-only
   STATUS      current
   DESCRIPTION
      "Path: ethernet3.status.vlan.name"
   ::= {sr1645v2Lan3VlanEntry 16777216}

sr1645v2Lan3VlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan3VlanEntry 335544320}

sr1645v2Lan3VlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.vlan.ifOperStatus

       Possibilities:
               up   (1)
               down   (2)
               testing   (3)
               unknown   (4)
               dormant   (5)
               notPresent   (6)
               lowerLayerDown   (7)"
   ::= {sr1645v2Lan3VlanEntry 1795162112}

sr1645v2Lan3VlanIfLastChange OBJECT-TYPE
   SYNTAX      TimeTicks
   MAX-ACCESS  read-only
   STATUS      current
   DESCRIPTION
      "Path: ethernet3.status.vlan.ifLastChange

       Time in centi-second."
   ::= {sr1645v2Lan3VlanEntry 1811939328}

sr1645v2Lan3VlanIfLastChangeDate OBJECT-TYPE
   SYNTAX      DisplayString
   MAX-ACCESS  read-only
   STATUS      current
   DESCRIPTION
      "Path: ethernet3.status.vlan.ifLastChangeDate"
   ::= {sr1645v2Lan3VlanEntry 3070230528}

sr1645v2Lan3VlanIpAddress OBJECT-TYPE
   SYNTAX      IpAddress
   MAX-ACCESS  read-only
   STATUS      current
   DESCRIPTION
      "Path: ethernet3.status.vlan.ip.address"
   ::= {sr1645v2Lan3VlanEntry 51380224}

sr1645v2Lan3VlanIpNetMask OBJECT-TYPE
   SYNTAX      IpAddress
   MAX-ACCESS  read-only
   STATUS      current
   DESCRIPTION
      "Path: ethernet3.status.vlan.ip.netMask"
   ::= {sr1645v2Lan3VlanEntry 51445760}

sr1645v2Lan3VlanIpRemote OBJECT-TYPE
   SYNTAX      IpAddress
   MAX-ACCESS  read-only
   STATUS      current
   DESCRIPTION
      "Path: ethernet3.status.vlan.ip.remote"
   ::= {sr1645v2Lan3VlanEntry 51511296}

sr1645v2Lan3VlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.vlan.ip.dhcp.status

       Possibilities:
               none   (0)
               selecting   (1)
               requesting   (2)
               rebinding   (3)
               bound   (4)
               renewing   (5)
               rebooting   (6)
               initreboot   (7)"
   ::= {sr1645v2Lan3VlanEntry 51904768}

sr1645v2Lan3VlanIpDhcpLeaseTime OBJECT-TYPE
   SYNTAX      TimeTicks
   MAX-ACCESS  read-only
   STATUS      current
   DESCRIPTION
      "Path: ethernet3.status.vlan.ip.dhcp.leaseTime

       Time in centi-second."
   ::= {sr1645v2Lan3VlanEntry 51905024}

sr1645v2Lan3VlanIpV6State OBJECT-TYPE
   SYNTAX      INTEGER
               {
               disabled (0),
               enabled (1)
               }
   MAX-ACCESS  read-only
   STATUS      current
   DESCRIPTION
      "Path: ethernet3.status.vlan.ipV6.state

       Possibilities:
               disabled   (0)
               enabled   (1)"
   ::= {sr1645v2Lan3VlanEntry 100728832}

sr1645v2Lan3VlanIpV6InterfaceId OBJECT-TYPE
   SYNTAX      OCTET STRING
   MAX-ACCESS  read-only
   STATUS      current
   DESCRIPTION
      "Path: ethernet3.status.vlan.ipV6.interfaceId"
   ::= {sr1645v2Lan3VlanEntry 100794368}

sr1645v2Lan3VlanIpV6LinkMtu OBJECT-TYPE
   SYNTAX      Integer32
   MAX-ACCESS  read-only
   STATUS      current
   DESCRIPTION
      "Path: ethernet3.status.vlan.ipV6.linkMtu"
   ::= {sr1645v2Lan3VlanEntry 100925440}

sr1645v2Lan3VlanIpV6HopLimit OBJECT-TYPE
   SYNTAX      Integer32
   MAX-ACCESS  read-only
   STATUS      current
   DESCRIPTION
      "Path: ethernet3.status.vlan.ipV6.hopLimit"
   ::= {sr1645v2Lan3VlanEntry 100990976}

sr1645v2Lan3VlanIpV6DhcpIaid OBJECT-TYPE
   SYNTAX      Counter32
   MAX-ACCESS  read-only
   STATUS      current
   DESCRIPTION
      "Path: ethernet3.status.vlan.ipV6.dhcp.iaid

       32 bit unsigned wrappable counter."
   ::= {sr1645v2Lan3VlanEntry 101056768}

sr1645v2Lan3VlanIpV6RaRcvOption OBJECT-TYPE
   SYNTAX      Integer32
   MAX-ACCESS  read-only
   STATUS      current
   DESCRIPTION
      "Path: ethernet3.status.vlan.ipV6.raRcvOption

       Bit meanings:
               bit 0 = linkMtu,
               bit 1 = srcLinkLayer,
               bit 2 = prefixInfo,
               bit 3 = rdnss,
               bit 4 = dnssl"
   ::= {sr1645v2Lan3VlanEntry 101122048}

sr1645v2Lan3VlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.vlan.bridging.status

       Possibilities:
               disabled   (0)
               discarding   (1)
               learning   (2)
               forwarding   (3)
               backupBlockedIntfDown   (256)
               backupBlockedIntfUp   (259)
               shutdown   (255)"
   ::= {sr1645v2Lan3VlanEntry 453050368}

sr1645v2Lan3VlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.vlan.bridging.spanningTree.portRole

       Possibilities:
               none   (0)
               root   (1)
               designated   (2)
               alternate   (3)
               backup   (4)
               disabled   (5)
               master   (6)"
   ::= {sr1645v2Lan3VlanEntry 453116160}

sr1645v2Lan3VlanBridgingSpanningTreePortId OBJECT-TYPE
   SYNTAX      Integer32
   MAX-ACCESS  read-only
   STATUS      current
   DESCRIPTION
      "Path: ethernet3.status.vlan.bridging.spanningTree.portId"
   ::= {sr1645v2Lan3VlanEntry 453116416}

sr1645v2Lan3VlanBridgingSpanningTreePpCostExtPathCost OBJECT-TYPE
   SYNTAX      Integer32
   MAX-ACCESS  read-only
   STATUS      current
   DESCRIPTION
      "Path: ethernet3.status.vlan.bridging.spanningTree.portPathCosts.extPathCost"
   ::= {sr1645v2Lan3VlanEntry 453116673}

sr1645v2Lan3VlanBridgingSpanningTreePpCostIntPathCost OBJECT-TYPE
   SYNTAX      Integer32
   MAX-ACCESS  read-only
   STATUS      current
   DESCRIPTION
      "Path: ethernet3.status.vlan.bridging.spanningTree.portPathCosts.intPathCost"
   ::= {sr1645v2Lan3VlanEntry 453116674}

sr1645v2Lan3VlanBridgingSpanningTreeExtRpCost OBJECT-TYPE
   SYNTAX      Integer32
   MAX-ACCESS  read-only
   STATUS      current
   DESCRIPTION
      "Path: ethernet3.status.vlan.bridging.spanningTree.extRootPathCost"
   ::= {sr1645v2Lan3VlanEntry 453116928}

sr1645v2Lan3VlanBridgingSpanningTreeIntRpCost OBJECT-TYPE
   SYNTAX      Integer32
   MAX-ACCESS  read-only
   STATUS      current
   DESCRIPTION
      "Path: ethernet3.status.vlan.bridging.spanningTree.intRootPathCost"
   ::= {sr1645v2Lan3VlanEntry 453117184}

sr1645v2Lan3VlanBridgingSpanningTreeDesBrIdPriority OBJECT-TYPE
   SYNTAX      Integer32
   MAX-ACCESS  read-only
   STATUS      current
   DESCRIPTION
      "Path: ethernet3.status.vlan.bridging.spanningTree.designatedBridgeId.priority"
   ::= {sr1645v2Lan3VlanEntry 453117441}

sr1645v2Lan3VlanBridgingSpanningTreeDesBrIdMacAddress OBJECT-TYPE
   SYNTAX      OCTET STRING
   MAX-ACCESS  read-only
   STATUS      current
   DESCRIPTION
      "Path: ethernet3.status.vlan.bridging.spanningTree.designatedBridgeId.macAddress

       MAC address."
   ::= {sr1645v2Lan3VlanEntry 453117442}

sr1645v2Lan3VlanBridgingSpanningTreeDesPrtId OBJECT-TYPE
   SYNTAX      Integer32
   MAX-ACCESS  read-only
   STATUS      current
   DESCRIPTION
      "Path: ethernet3.status.vlan.bridging.spanningTree.designatedPortId"
   ::= {sr1645v2Lan3VlanEntry 453117696}

sr1645v2Lan3VlanBridgingSpanningTreeDesInt OBJECT-TYPE
   SYNTAX      INTEGER
               {
               no (0),
               yes (1)
               }
   MAX-ACCESS  read-only
   STATUS      current
   DESCRIPTION
      "Path: ethernet3.status.vlan.bridging.spanningTree.designatedOrInternal

       Possibilities:
               no   (0)
               yes   (1)"
   ::= {sr1645v2Lan3VlanEntry 453117952}

sr1645v2Lan3VlanBridgingSpanningTreeEdgeDetection OBJECT-TYPE
   SYNTAX      INTEGER
               {
               none (0),
               edge (1),
               notEdge (2)
               }
   MAX-ACCESS  read-only
   STATUS      current
   DESCRIPTION
      "Path: ethernet3.status.vlan.bridging.spanningTree.edgeDetection

       Possibilities:
               none   (0)
               edge   (1)
               notEdge   (2)"
   ::= {sr1645v2Lan3VlanEntry 453118208}

sr1645v2Lan3VlanVlanVid OBJECT-TYPE
   SYNTAX      Integer32
   MAX-ACCESS  read-only
   STATUS      current
   DESCRIPTION
      "Path: ethernet3.status.vlan.vlan.vid"
   ::= {sr1645v2Lan3VlanEntry 234946560}

sr1645v2Lan3VlanPppOEthDiscState OBJECT-TYPE
   SYNTAX      INTEGER
               {
               idle (0),
               waitForPADO (1),
               waitForPADS (2),
               established (3)
               }
   MAX-ACCESS  read-only
   STATUS      current
   DESCRIPTION
      "Path: ethernet3.status.vlan.pppOverEth.discState

       Possibilities:
               idle   (0)
               waitForPADO   (1)
               waitForPADS   (2)
               established   (3)"
   ::= {sr1645v2Lan3VlanEntry 67174400}

sr1645v2Lan3VlanPppOEthPeerMac OBJECT-TYPE
   SYNTAX      OCTET STRING
   MAX-ACCESS  read-only
   STATUS      current
   DESCRIPTION
      "Path: ethernet3.status.vlan.pppOverEth.remoteMacAddress

       MAC address."
   ::= {sr1645v2Lan3VlanEntry 67239936}

sr1645v2Lan3VlanPppOEthServiceName OBJECT-TYPE
   SYNTAX      DisplayString
   MAX-ACCESS  read-only
   STATUS      current
   DESCRIPTION
      "Path: ethernet3.status.vlan.pppOverEth.serviceName"
   ::= {sr1645v2Lan3VlanEntry 67305472}

sr1645v2Lan3VlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3VlanEntry 83951616}

sr1645v2Lan3VlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3VlanEntry 84017152}

sr1645v2Lan3VlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3VlanEntry 84869120}

sr1645v2Lan3VlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan3VlanEntry 84541440}

sr1645v2Lan3VlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan3VlanEntry 84606976}

sr1645v2Lan3VlanPppMru OBJECT-TYPE
   SYNTAX      Integer32
   MAX-ACCESS  read-only
   STATUS      current
   DESCRIPTION
      "Path: ethernet3.status.vlan.ppp.mru"
   ::= {sr1645v2Lan3VlanEntry 84934656}

sr1645v2Lan3VlanIpSecondaryIp OBJECT-TYPE
   SYNTAX      SEQUENCE OF Sr1645v2Lan3VlanIpSecondaryIpEntry
   MAX-ACCESS  not-accessible
   STATUS      current
   DESCRIPTION
      ""
   ::= {sr1645v2Lan3Vlan 51838976}

sr1645v2Lan3VlanIpSecondaryIpEntry OBJECT-TYPE
   SYNTAX      Sr1645v2Lan3VlanIpSecondaryIpEntry
   MAX-ACCESS  not-accessible
   STATUS      current
   DESCRIPTION
      ""
   INDEX      { sr1645v2Lan3VlanTableIx,
                sr1645v2Lan3VlanIpSecondaryIpTableIx }
   ::= {sr1645v2Lan3VlanIpSecondaryIp 1}

Sr1645v2Lan3VlanIpSecondaryIpEntry ::=
   SEQUENCE
      {
      sr1645v2Lan3VlanIpSecondaryIpTableIx
         TableIndex,
      sr1645v2Lan3VlanIpSecondaryIpAddress
         IpAddress,
      sr1645v2Lan3VlanIpSecondaryIpNetMask
         IpAddress
      }

sr1645v2Lan3VlanIpSecondaryIpTableIx OBJECT-TYPE
   SYNTAX      TableIndex
   MAX-ACCESS  not-accessible
   STATUS      current
   DESCRIPTION
      ""
   ::= {sr1645v2Lan3VlanIpSecondaryIpEntry 11}

sr1645v2Lan3VlanIpSecondaryIpAddress OBJECT-TYPE
   SYNTAX      IpAddress
   MAX-ACCESS  read-only
   STATUS      current
   DESCRIPTION
      "Path: ethernet3.status.vlan.ip.secondaryIp.address"
   ::= {sr1645v2Lan3VlanIpSecondaryIpEntry 2030043136}

sr1645v2Lan3VlanIpSecondaryIpNetMask OBJECT-TYPE
   SYNTAX      IpAddress
   MAX-ACCESS  read-only
   STATUS      current
   DESCRIPTION
      "Path: ethernet3.status.vlan.ip.secondaryIp.netMask"
   ::= {sr1645v2Lan3VlanIpSecondaryIpEntry 2063597568}

sr1645v2Lan3VlanIpV6Addresses OBJECT-TYPE
   SYNTAX      SEQUENCE OF Sr1645v2Lan3VlanIpV6AddressesEntry
   MAX-ACCESS  not-accessible
   STATUS      current
   DESCRIPTION
      ""
   ::= {sr1645v2Lan3Vlan 100859904}

sr1645v2Lan3VlanIpV6AddressesEntry OBJECT-TYPE
   SYNTAX      Sr1645v2Lan3VlanIpV6AddressesEntry
   MAX-ACCESS  not-accessible
   STATUS      current
   DESCRIPTION
      ""
   INDEX      { sr1645v2Lan3VlanTableIx,
                sr1645v2Lan3VlanIpV6AddressesTableIx }
   ::= {sr1645v2Lan3VlanIpV6Addresses 1}

Sr1645v2Lan3VlanIpV6AddressesEntry ::=
   SEQUENCE
      {
      sr1645v2Lan3VlanIpV6AddressesTableIx
         TableIndex,
      sr1645v2Lan3VlanIpV6AddressesAddress
         Ipv6Address,
      sr1645v2Lan3VlanIpV6AddressesPrefixLength
         Integer32,
      sr1645v2Lan3VlanIpV6AddressesStatus
         INTEGER,
      sr1645v2Lan3VlanIpV6AddressesOrigin
         INTEGER,
      sr1645v2Lan3VlanIpV6AddressesFlagsInterfaceId
         INTEGER,
      sr1645v2Lan3VlanIpV6AddressesFlagsAnycast
         INTEGER,
      sr1645v2Lan3VlanIpV6AddressesTimersValidLifeTime
         TimeTicks,
      sr1645v2Lan3VlanIpV6AddressesTimersPrefLifeTime
         TimeTicks
      }

sr1645v2Lan3VlanIpV6AddressesTableIx OBJECT-TYPE
   SYNTAX      TableIndex
   MAX-ACCESS  not-accessible
   STATUS      current
   DESCRIPTION
      ""
   ::= {sr1645v2Lan3VlanIpV6AddressesEntry 11}

sr1645v2Lan3VlanIpV6AddressesAddress OBJECT-TYPE
   SYNTAX      Ipv6Address
   MAX-ACCESS  read-only
   STATUS      current
   DESCRIPTION
      "Path: ethernet3.status.vlan.ipV6.addresses.address

       ipv6 address"
   ::= {sr1645v2Lan3VlanIpV6AddressesEntry 16777216}

sr1645v2Lan3VlanIpV6AddressesPrefixLength OBJECT-TYPE
   SYNTAX      Integer32
   MAX-ACCESS  read-only
   STATUS      current
   DESCRIPTION
      "Path: ethernet3.status.vlan.ipV6.addresses.prefixLength"
   ::= {sr1645v2Lan3VlanIpV6AddressesEntry 33554432}

sr1645v2Lan3VlanIpV6AddressesStatus OBJECT-TYPE
   SYNTAX      INTEGER
               {
               invalid (0),
               tentative (1),
               deprecated (2),
               preferred (3)
               }
   MAX-ACCESS  read-only
   STATUS      current
   DESCRIPTION
      "Path: ethernet3.status.vlan.ipV6.addresses.status

       Possibilities:
               invalid   (0)
               tentative   (1)
               deprecated   (2)
               preferred   (3)"
   ::= {sr1645v2Lan3VlanIpV6AddressesEntry 50331648}

sr1645v2Lan3VlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.vlan.ipV6.addresses.origin

       Possibilities:
               unknown   (0)
               manual   (1)
               generalPrefix   (2)
               statelessAuto   (3)
               statefullAuto   (4)"
   ::= {sr1645v2Lan3VlanIpV6AddressesEntry 67108864}

sr1645v2Lan3VlanIpV6AddressesFlagsInterfaceId OBJECT-TYPE
   SYNTAX      INTEGER
               {
               no (0),
               yes (1)
               }
   MAX-ACCESS  read-only
   STATUS      current
   DESCRIPTION
      "Path: ethernet3.status.vlan.ipV6.addresses.flags.interfaceId

       Possibilities:
               no   (0)
               yes   (1)"
   ::= {sr1645v2Lan3VlanIpV6AddressesEntry 83951616}

sr1645v2Lan3VlanIpV6AddressesFlagsAnycast OBJECT-TYPE
   SYNTAX      INTEGER
               {
               no (0),
               yes (1)
               }
   MAX-ACCESS  read-only
   STATUS      current
   DESCRIPTION
      "Path: ethernet3.status.vlan.ipV6.addresses.flags.anycast

       Possibilities:
               no   (0)
               yes   (1)"
   ::= {sr1645v2Lan3VlanIpV6AddressesEntry 84017152}

sr1645v2Lan3VlanIpV6AddressesTimersValidLifeTime OBJECT-TYPE
   SYNTAX      TimeTicks
   MAX-ACCESS  read-only
   STATUS      current
   DESCRIPTION
      "Path: ethernet3.status.vlan.ipV6.addresses.timers.validLifeTime

       Time in centi-second."
   ::= {sr1645v2Lan3VlanIpV6AddressesEntry 100794368}

sr1645v2Lan3VlanIpV6AddressesTimersPrefLifeTime OBJECT-TYPE
   SYNTAX      TimeTicks
   MAX-ACCESS  read-only
   STATUS      current
   DESCRIPTION
      "Path: ethernet3.status.vlan.ipV6.addresses.timers.prefLifeTime

       Time in centi-second."
   ::= {sr1645v2Lan3VlanIpV6AddressesEntry 100728832}

sr1645v2Lan3VlanVlanArpCache OBJECT-TYPE
   SYNTAX      SEQUENCE OF Sr1645v2Lan3VlanVlanArpCacheEntry
   MAX-ACCESS  not-accessible
   STATUS      current
   DESCRIPTION
      ""
   ::= {sr1645v2Lan3Vlan 235601920}

sr1645v2Lan3VlanVlanArpCacheEntry OBJECT-TYPE
   SYNTAX      Sr1645v2Lan3VlanVlanArpCacheEntry
   MAX-ACCESS  not-accessible
   STATUS      current
   DESCRIPTION
      ""
   INDEX      { sr1645v2Lan3VlanTableIx,
                sr1645v2Lan3VlanVlanArpCacheTableIx }
   ::= {sr1645v2Lan3VlanVlanArpCache 1}

Sr1645v2Lan3VlanVlanArpCacheEntry ::=
   SEQUENCE
      {
      sr1645v2Lan3VlanVlanArpCacheTableIx
         TableIndex,
      sr1645v2Lan3VlanVlanArpCacheMacAddress
         OCTET STRING,
      sr1645v2Lan3VlanVlanArpCacheIpAddress
         IpAddress,
      sr1645v2Lan3VlanVlanArpCacheType
         INTEGER,
      sr1645v2Lan3VlanVlanArpCacheTimeOut
         TimeTicks
      }

sr1645v2Lan3VlanVlanArpCacheTableIx OBJECT-TYPE
   SYNTAX      TableIndex
   MAX-ACCESS  not-accessible
   STATUS      current
   DESCRIPTION
      ""
   ::= {sr1645v2Lan3VlanVlanArpCacheEntry 11}

sr1645v2Lan3VlanVlanArpCacheMacAddress OBJECT-TYPE
   SYNTAX      OCTET STRING
   MAX-ACCESS  read-only
   STATUS      current
   DESCRIPTION
      "Path: ethernet3.status.vlan.vlan.arpCache.macAddress

       MAC address."
   ::= {sr1645v2Lan3VlanVlanArpCacheEntry 16777216}

sr1645v2Lan3VlanVlanArpCacheIpAddress OBJECT-TYPE
   SYNTAX      IpAddress
   MAX-ACCESS  read-only
   STATUS      current
   DESCRIPTION
      "Path: ethernet3.status.vlan.vlan.arpCache.ipAddress"
   ::= {sr1645v2Lan3VlanVlanArpCacheEntry 33554432}

sr1645v2Lan3VlanVlanArpCacheType OBJECT-TYPE
   SYNTAX      INTEGER
               {
               static (0),
               dynamic (1)
               }
   MAX-ACCESS  read-only
   STATUS      current
   DESCRIPTION
      "Path: ethernet3.status.vlan.vlan.arpCache.type

       Possibilities:
               static   (0)
               dynamic   (1)"
   ::= {sr1645v2Lan3VlanVlanArpCacheEntry 50331648}

sr1645v2Lan3VlanVlanArpCacheTimeOut OBJECT-TYPE
   SYNTAX      TimeTicks
   MAX-ACCESS  read-only
   STATUS      current
   DESCRIPTION
      "Path: ethernet3.status.vlan.vlan.arpCache.timeOut

       Time in centi-second."
   ::= {sr1645v2Lan3VlanVlanArpCacheEntry 67108864}


sr1645v2Lan3PppOE OBJECT IDENTIFIER ::= {sr1645v2Lan3 36}

sr1645v2Lan3PppOESSCTable OBJECT-TYPE
   SYNTAX      SEQUENCE OF Sr1645v2Lan3PppOEEntry
   MAX-ACCESS  not-accessible
   STATUS      current
   DESCRIPTION
      ""
   ::= {sr1645v2Lan3PppOE 1}

sr1645v2Lan3PppOEEntry OBJECT-TYPE
   SYNTAX      Sr1645v2Lan3PppOEEntry
   MAX-ACCESS  not-accessible
   STATUS      current
   DESCRIPTION
      ""
   INDEX      { sr1645v2Lan3PppOETableIx }
   ::= {sr1645v2Lan3PppOESSCTable 1}

Sr1645v2Lan3PppOEEntry ::=
   SEQUENCE
      {
      sr1645v2Lan3PppOETableIx
         TableIndex,
      sr1645v2Lan3PppOEName
         DisplayString,
      sr1645v2Lan3PppOEMode
         INTEGER,
      sr1645v2Lan3PppOEIfOperStatus
         INTEGER,
      sr1645v2Lan3PppOEIfLastChange
         TimeTicks,
      sr1645v2Lan3PppOEIfLastChangeDate
         DisplayString,
      sr1645v2Lan3PppOEIpAddress
         IpAddress,
      sr1645v2Lan3PppOEIpNetMask
         IpAddress,
      sr1645v2Lan3PppOEIpRemote
         IpAddress,
      sr1645v2Lan3PppOEPppOEthDiscState
         INTEGER,
      sr1645v2Lan3PppOEPppOEthPeerMac
         OCTET STRING,
      sr1645v2Lan3PppOEPppOEthServiceName
         DisplayString,
      sr1645v2Lan3PppOEPppLcpState
         INTEGER,
      sr1645v2Lan3PppOEPppIpcpState
         INTEGER,
      sr1645v2Lan3PppOEPppIp6cpState
         INTEGER,
      sr1645v2Lan3PppOEPppMyAutSt
         INTEGER,
      sr1645v2Lan3PppOEPppHisAutSt
         INTEGER,
      sr1645v2Lan3PppOEPppMru
         Integer32,
      sr1645v2Lan3PppOEIpV6State
         INTEGER,
      sr1645v2Lan3PppOEIpV6InterfaceId
         OCTET STRING,
      sr1645v2Lan3PppOEIpV6LinkMtu
         Integer32,
      sr1645v2Lan3PppOEIpV6HopLimit
         Integer32,
      sr1645v2Lan3PppOEIpV6DhcpIaid
         Counter32,
      sr1645v2Lan3PppOEIpV6RaRcvOption
         Integer32
      }

sr1645v2Lan3PppOETableIx OBJECT-TYPE
   SYNTAX      TableIndex
   MAX-ACCESS  not-accessible
   STATUS      current
   DESCRIPTION
      ""
   ::= {sr1645v2Lan3PppOEEntry 11}

sr1645v2Lan3PppOEName OBJECT-TYPE
   SYNTAX      DisplayString
   MAX-ACCESS  read-only
   STATUS      current
   DESCRIPTION
      "Path: ethernet3.status.pppoEClient.name"
   ::= {sr1645v2Lan3PppOEEntry 16777216}

sr1645v2Lan3PppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan3PppOEEntry 335544320}

sr1645v2Lan3PppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.pppoEClient.ifOperStatus

       Possibilities:
               up   (1)
               down   (2)
               testing   (3)
               unknown   (4)
               dormant   (5)
               notPresent   (6)
               lowerLayerDown   (7)"
   ::= {sr1645v2Lan3PppOEEntry 1795162112}

sr1645v2Lan3PppOEIfLastChange OBJECT-TYPE
   SYNTAX      TimeTicks
   MAX-ACCESS  read-only
   STATUS      current
   DESCRIPTION
      "Path: ethernet3.status.pppoEClient.ifLastChange

       Time in centi-second."
   ::= {sr1645v2Lan3PppOEEntry 1811939328}

sr1645v2Lan3PppOEIfLastChangeDate OBJECT-TYPE
   SYNTAX      DisplayString
   MAX-ACCESS  read-only
   STATUS      current
   DESCRIPTION
      "Path: ethernet3.status.pppoEClient.ifLastChangeDate"
   ::= {sr1645v2Lan3PppOEEntry 3070230528}

sr1645v2Lan3PppOEIpAddress OBJECT-TYPE
   SYNTAX      IpAddress
   MAX-ACCESS  read-only
   STATUS      current
   DESCRIPTION
      "Path: ethernet3.status.pppoEClient.ip.address"
   ::= {sr1645v2Lan3PppOEEntry 51380224}

sr1645v2Lan3PppOEIpNetMask OBJECT-TYPE
   SYNTAX      IpAddress
   MAX-ACCESS  read-only
   STATUS      current
   DESCRIPTION
      "Path: ethernet3.status.pppoEClient.ip.netMask"
   ::= {sr1645v2Lan3PppOEEntry 51445760}

sr1645v2Lan3PppOEIpRemote OBJECT-TYPE
   SYNTAX      IpAddress
   MAX-ACCESS  read-only
   STATUS      current
   DESCRIPTION
      "Path: ethernet3.status.pppoEClient.ip.remote"
   ::= {sr1645v2Lan3PppOEEntry 51511296}

sr1645v2Lan3PppOEPppOEthDiscState OBJECT-TYPE
   SYNTAX      INTEGER
               {
               idle (0),
               waitForPADO (1),
               waitForPADS (2),
               established (3)
               }
   MAX-ACCESS  read-only
   STATUS      current
   DESCRIPTION
      "Path: ethernet3.status.pppoEClient.pppOverEth.discState

       Possibilities:
               idle   (0)
               waitForPADO   (1)
               waitForPADS   (2)
               established   (3)"
   ::= {sr1645v2Lan3PppOEEntry 67174400}

sr1645v2Lan3PppOEPppOEthPeerMac OBJECT-TYPE
   SYNTAX      OCTET STRING
   MAX-ACCESS  read-only
   STATUS      current
   DESCRIPTION
      "Path: ethernet3.status.pppoEClient.pppOverEth.remoteMacAddress

       MAC address."
   ::= {sr1645v2Lan3PppOEEntry 67239936}

sr1645v2Lan3PppOEPppOEthServiceName OBJECT-TYPE
   SYNTAX      DisplayString
   MAX-ACCESS  read-only
   STATUS      current
   DESCRIPTION
      "Path: ethernet3.status.pppoEClient.pppOverEth.serviceName"
   ::= {sr1645v2Lan3PppOEEntry 67305472}

sr1645v2Lan3PppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3PppOEEntry 83951616}

sr1645v2Lan3PppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3PppOEEntry 84017152}

sr1645v2Lan3PppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3PppOEEntry 84869120}

sr1645v2Lan3PppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan3PppOEEntry 84541440}

sr1645v2Lan3PppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan3PppOEEntry 84606976}

sr1645v2Lan3PppOEPppMru OBJECT-TYPE
   SYNTAX      Integer32
   MAX-ACCESS  read-only
   STATUS      current
   DESCRIPTION
      "Path: ethernet3.status.pppoEClient.ppp.mru"
   ::= {sr1645v2Lan3PppOEEntry 84934656}

sr1645v2Lan3PppOEIpV6State OBJECT-TYPE
   SYNTAX      INTEGER
               {
               disabled (0),
               enabled (1)
               }
   MAX-ACCESS  read-only
   STATUS      current
   DESCRIPTION
      "Path: ethernet3.status.pppoEClient.ipV6.state

       Possibilities:
               disabled   (0)
               enabled   (1)"
   ::= {sr1645v2Lan3PppOEEntry 100728832}

sr1645v2Lan3PppOEIpV6InterfaceId OBJECT-TYPE
   SYNTAX      OCTET STRING
   MAX-ACCESS  read-only
   STATUS      current
   DESCRIPTION
      "Path: ethernet3.status.pppoEClient.ipV6.interfaceId"
   ::= {sr1645v2Lan3PppOEEntry 100794368}

sr1645v2Lan3PppOEIpV6LinkMtu OBJECT-TYPE
   SYNTAX      Integer32
   MAX-ACCESS  read-only
   STATUS      current
   DESCRIPTION
      "Path: ethernet3.status.pppoEClient.ipV6.linkMtu"
   ::= {sr1645v2Lan3PppOEEntry 100925440}

sr1645v2Lan3PppOEIpV6HopLimit OBJECT-TYPE
   SYNTAX      Integer32
   MAX-ACCESS  read-only
   STATUS      current
   DESCRIPTION
      "Path: ethernet3.status.pppoEClient.ipV6.hopLimit"
   ::= {sr1645v2Lan3PppOEEntry 100990976}

sr1645v2Lan3PppOEIpV6DhcpIaid OBJECT-TYPE
   SYNTAX      Counter32
   MAX-ACCESS  read-only
   STATUS      current
   DESCRIPTION
      "Path: ethernet3.status.pppoEClient.ipV6.dhcp.iaid

       32 bit unsigned wrappable counter."
   ::= {sr1645v2Lan3PppOEEntry 101056768}

sr1645v2Lan3PppOEIpV6RaRcvOption OBJECT-TYPE
   SYNTAX      Integer32
   MAX-ACCESS  read-only
   STATUS      current
   DESCRIPTION
      "Path: ethernet3.status.pppoEClient.ipV6.raRcvOption

       Bit meanings:
               bit 0 = linkMtu,
               bit 1 = srcLinkLayer,
               bit 2 = prefixInfo,
               bit 3 = rdnss,
               bit 4 = dnssl"
   ::= {sr1645v2Lan3PppOEEntry 101122048}

sr1645v2Lan3PppOEIpV6Addresses OBJECT-TYPE
   SYNTAX      SEQUENCE OF Sr1645v2Lan3PppOEIpV6AddressesEntry
   MAX-ACCESS  not-accessible
   STATUS      current
   DESCRIPTION
      ""
   ::= {sr1645v2Lan3PppOE 100859904}

sr1645v2Lan3PppOEIpV6AddressesEntry OBJECT-TYPE
   SYNTAX      Sr1645v2Lan3PppOEIpV6AddressesEntry
   MAX-ACCESS  not-accessible
   STATUS      current
   DESCRIPTION
      ""
   INDEX      { sr1645v2Lan3PppOETableIx,
                sr1645v2Lan3PppOEIpV6AddressesTableIx }
   ::= {sr1645v2Lan3PppOEIpV6Addresses 1}

Sr1645v2Lan3PppOEIpV6AddressesEntry ::=
   SEQUENCE
      {
      sr1645v2Lan3PppOEIpV6AddressesTableIx
         TableIndex,
      sr1645v2Lan3PppOEIpV6AddressesAddress
         Ipv6Address,
      sr1645v2Lan3PppOEIpV6AddressesPrefixLength
         Integer32,
      sr1645v2Lan3PppOEIpV6AddressesStatus
         INTEGER,
      sr1645v2Lan3PppOEIpV6AddressesOrigin
         INTEGER,
      sr1645v2Lan3PppOEIpV6AddressesFlagsInterfaceId
         INTEGER,
      sr1645v2Lan3PppOEIpV6AddressesFlagsAnycast
         INTEGER,
      sr1645v2Lan3PppOEIpV6AddressesTimersValidLifeTime
         TimeTicks,
      sr1645v2Lan3PppOEIpV6AddressesTimersPrefLifeTime
         TimeTicks
      }

sr1645v2Lan3PppOEIpV6AddressesTableIx OBJECT-TYPE
   SYNTAX      TableIndex
   MAX-ACCESS  not-accessible
   STATUS      current
   DESCRIPTION
      ""
   ::= {sr1645v2Lan3PppOEIpV6AddressesEntry 11}

sr1645v2Lan3PppOEIpV6AddressesAddress OBJECT-TYPE
   SYNTAX      Ipv6Address
   MAX-ACCESS  read-only
   STATUS      current
   DESCRIPTION
      "Path: ethernet3.status.pppoEClient.ipV6.addresses.address

       ipv6 address"
   ::= {sr1645v2Lan3PppOEIpV6AddressesEntry 16777216}

sr1645v2Lan3PppOEIpV6AddressesPrefixLength OBJECT-TYPE
   SYNTAX      Integer32
   MAX-ACCESS  read-only
   STATUS      current
   DESCRIPTION
      "Path: ethernet3.status.pppoEClient.ipV6.addresses.prefixLength"
   ::= {sr1645v2Lan3PppOEIpV6AddressesEntry 33554432}

sr1645v2Lan3PppOEIpV6AddressesStatus OBJECT-TYPE
   SYNTAX      INTEGER
               {
               invalid (0),
               tentative (1),
               deprecated (2),
               preferred (3)
               }
   MAX-ACCESS  read-only
   STATUS      current
   DESCRIPTION
      "Path: ethernet3.status.pppoEClient.ipV6.addresses.status

       Possibilities:
               invalid   (0)
               tentative   (1)
               deprecated   (2)
               preferred   (3)"
   ::= {sr1645v2Lan3PppOEIpV6AddressesEntry 50331648}

sr1645v2Lan3PppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.pppoEClient.ipV6.addresses.origin

       Possibilities:
               unknown   (0)
               manual   (1)
               generalPrefix   (2)
               statelessAuto   (3)
               statefullAuto   (4)"
   ::= {sr1645v2Lan3PppOEIpV6AddressesEntry 67108864}

sr1645v2Lan3PppOEIpV6AddressesFlagsInterfaceId OBJECT-TYPE
   SYNTAX      INTEGER
               {
               no (0),
               yes (1)
               }
   MAX-ACCESS  read-only
   STATUS      current
   DESCRIPTION
      "Path: ethernet3.status.pppoEClient.ipV6.addresses.flags.interfaceId

       Possibilities:
               no   (0)
               yes   (1)"
   ::= {sr1645v2Lan3PppOEIpV6AddressesEntry 83951616}

sr1645v2Lan3PppOEIpV6AddressesFlagsAnycast OBJECT-TYPE
   SYNTAX      INTEGER
               {
               no (0),
               yes (1)
               }
   MAX-ACCESS  read-only
   STATUS      current
   DESCRIPTION
      "Path: ethernet3.status.pppoEClient.ipV6.addresses.flags.anycast

       Possibilities:
               no   (0)
               yes   (1)"
   ::= {sr1645v2Lan3PppOEIpV6AddressesEntry 84017152}

sr1645v2Lan3PppOEIpV6AddressesTimersValidLifeTime OBJECT-TYPE
   SYNTAX      TimeTicks
   MAX-ACCESS  read-only
   STATUS      current
   DESCRIPTION
      "Path: ethernet3.status.pppoEClient.ipV6.addresses.timers.validLifeTime

       Time in centi-second."
   ::= {sr1645v2Lan3PppOEIpV6AddressesEntry 100794368}

sr1645v2Lan3PppOEIpV6AddressesTimersPrefLifeTime OBJECT-TYPE
   SYNTAX      TimeTicks
   MAX-ACCESS  read-only
   STATUS      current
   DESCRIPTION
      "Path: ethernet3.status.pppoEClient.ipV6.addresses.timers.prefLifeTime

       Time in centi-second."
   ::= {sr1645v2Lan3PppOEIpV6AddressesEntry 100728832}


sr1645v2Lan3Dot1x OBJECT IDENTIFIER ::= {sr1645v2Lan3 190}

sr1645v2Lan3Dot1xSSCTable OBJECT-TYPE
   SYNTAX      SEQUENCE OF Sr1645v2Lan3Dot1xEntry
   MAX-ACCESS  not-accessible
   STATUS      current
   DESCRIPTION
      "Ethernet Switch VLAN Table"
   ::= {sr1645v2Lan3Dot1x 1}

sr1645v2Lan3Dot1xEntry OBJECT-TYPE
   SYNTAX      Sr1645v2Lan3Dot1xEntry
   MAX-ACCESS  not-accessible
   STATUS      current
   DESCRIPTION
      ""
   INDEX      { sr1645v2Lan3Dot1xTableIx }
   ::= {sr1645v2Lan3Dot1xSSCTable 1}

Sr1645v2Lan3Dot1xEntry ::=
   SEQUENCE
      {
      sr1645v2Lan3Dot1xTableIx
         TableIndex,
      sr1645v2Lan3Dot1xRemote
         OCTET STRING,
      sr1645v2Lan3Dot1xAuthorized
         INTEGER,
      sr1645v2Lan3Dot1xAuthenticator
         INTEGER,
      sr1645v2Lan3Dot1xBackEnd
         INTEGER,
      sr1645v2Lan3Dot1xRetries
         Integer32,
      sr1645v2Lan3Dot1xReAuthTime
         TimeTicks,
      sr1645v2Lan3Dot1xHoldTime
         TimeTicks
      }

sr1645v2Lan3Dot1xTableIx OBJECT-TYPE
   SYNTAX      TableIndex
   MAX-ACCESS  not-accessible
   STATUS      current
   DESCRIPTION
      ""
   ::= {sr1645v2Lan3Dot1xEntry 11}

sr1645v2Lan3Dot1xRemote OBJECT-TYPE
   SYNTAX      OCTET STRING
   MAX-ACCESS  read-only
   STATUS      current
   DESCRIPTION
      "Path: ethernet3.status.dot1x.remote

       MAC address."
   ::= {sr1645v2Lan3Dot1xEntry 16777216}

sr1645v2Lan3Dot1xAuthorized OBJECT-TYPE
   SYNTAX      INTEGER
               {
               no (0),
               yes (1)
               }
   MAX-ACCESS  read-only
   STATUS      current
   DESCRIPTION
      "Path: ethernet3.status.dot1x.authorized

       Possibilities:
               no   (0)
               yes   (1)"
   ::= {sr1645v2Lan3Dot1xEntry 33554432}

sr1645v2Lan3Dot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet3.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2Lan3Dot1xEntry 50331648}

sr1645v2Lan3Dot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet3.status.dot1x.backEnd

       Possibilities:
               preInit   (0)
               initialize   (1)
               idle   (2)
               request   (3)
               response   (4)
               success   (5)
               failure   (6)
               radiusTimeout   (7)
               timeout   (8)"
   ::= {sr1645v2Lan3Dot1xEntry 67108864}

sr1645v2Lan3Dot1xRetries OBJECT-TYPE
   SYNTAX      Integer32
   MAX-ACCESS  read-only
   STATUS      current
   DESCRIPTION
      "Path: ethernet3.status.dot1x.retries"
   ::= {sr1645v2Lan3Dot1xEntry 83886080}

sr1645v2Lan3Dot1xReAuthTime OBJECT-TYPE
   SYNTAX      TimeTicks
   MAX-ACCESS  read-only
   STATUS      current
   DESCRIPTION
      "Path: ethernet3.status.dot1x.reAuthTime

       Time in centi-second."
   ::= {sr1645v2Lan3Dot1xEntry 100663296}

sr1645v2Lan3Dot1xHoldTime OBJECT-TYPE
   SYNTAX      TimeTicks
   MAX-ACCESS  read-only
   STATUS      current
   DESCRIPTION
      "Path: ethernet3.status.dot1x.holdTime

       Time in centi-second."
   ::= {sr1645v2Lan3Dot1xEntry 117440512}


sr1645v2Lan3IpV6 OBJECT IDENTIFIER ::= {sr1645v2Lan3 17}

sr1645v2Lan3IpV6SSC OBJECT IDENTIFIER ::= {sr1645v2Lan3IpV6 1}

sr1645v2Lan3IpV6Entry OBJECT IDENTIFIER ::= {sr1645v2Lan3IpV6SSC 1}

sr1645v2Lan3IpV6State OBJECT-TYPE
   SYNTAX      INTEGER
               {
               disabled (0),
               enabled (1)
               }
   MAX-ACCESS  read-only
   STATUS      current
   DESCRIPTION
      "Path: ethernet3.status.ipV6.state

       Possibilities:
               disabled   (0)
               enabled   (1)"
   ::= {sr1645v2Lan3IpV6Entry 16777216}

sr1645v2Lan3IpV6InterfaceId OBJECT-TYPE
   SYNTAX      OCTET STRING
   MAX-ACCESS  read-only
   STATUS      current
   DESCRIPTION
      "Path: ethernet3.status.ipV6.interfaceId"
   ::= {sr1645v2Lan3IpV6Entry 33554432}

sr1645v2Lan3IpV6LinkMtu OBJECT-TYPE
   SYNTAX      Integer32
   MAX-ACCESS  read-only
   STATUS      current
   DESCRIPTION
      "Path: ethernet3.status.ipV6.linkMtu"
   ::= {sr1645v2Lan3IpV6Entry 67108864}

sr1645v2Lan3IpV6HopLimit OBJECT-TYPE
   SYNTAX      Integer32
   MAX-ACCESS  read-only
   STATUS      current
   DESCRIPTION
      "Path: ethernet3.status.ipV6.hopLimit"
   ::= {sr1645v2Lan3IpV6Entry 83886080}

sr1645v2Lan3IpV6DhcpIaid OBJECT-TYPE
   SYNTAX      Counter32
   MAX-ACCESS  read-only
   STATUS      current
   DESCRIPTION
      "Path: ethernet3.status.ipV6.dhcp.iaid

       32 bit unsigned wrappable counter."
   ::= {sr1645v2Lan3IpV6Entry 100728832}

sr1645v2Lan3IpV6RaRcvOption OBJECT-TYPE
   SYNTAX      Integer32
   MAX-ACCESS  read-only
   STATUS      current
   DESCRIPTION
      "Path: ethernet3.status.ipV6.raRcvOption

       Bit meanings:
               bit 0 = linkMtu,
               bit 1 = srcLinkLayer,
               bit 2 = prefixInfo,
               bit 3 = rdnss,
               bit 4 = dnssl"
   ::= {sr1645v2Lan3IpV6Entry 117440512}

sr1645v2Lan3IpV6Addresses OBJECT-TYPE
   SYNTAX      SEQUENCE OF Sr1645v2Lan3IpV6AddressesEntry
   MAX-ACCESS  not-accessible
   STATUS      current
   DESCRIPTION
      ""
   ::= {sr1645v2Lan3IpV6 50331648}

sr1645v2Lan3IpV6AddressesEntry OBJECT-TYPE
   SYNTAX      Sr1645v2Lan3IpV6AddressesEntry
   MAX-ACCESS  not-accessible
   STATUS      current
   DESCRIPTION
      ""
   INDEX      { sr1645v2Lan3IpV6AddressesTableIx }
   ::= {sr1645v2Lan3IpV6Addresses 1}

Sr1645v2Lan3IpV6AddressesEntry ::=
   SEQUENCE
      {
      sr1645v2Lan3IpV6AddressesTableIx
         TableIndex,
      sr1645v2Lan3IpV6AddressesAddress
         Ipv6Address,
      sr1645v2Lan3IpV6AddressesPrefixLength
         Integer32,
      sr1645v2Lan3IpV6AddressesStatus
         INTEGER,
      sr1645v2Lan3IpV6AddressesOrigin
         INTEGER,
      sr1645v2Lan3IpV6AddressesFlagsInterfaceId
         INTEGER,
      sr1645v2Lan3IpV6AddressesFlagsAnycast
         INTEGER,
      sr1645v2Lan3IpV6AddressesTimersValidLifeTime
         TimeTicks,
      sr1645v2Lan3IpV6AddressesTimersPrefLifeTime
         TimeTicks
      }

sr1645v2Lan3IpV6AddressesTableIx OBJECT-TYPE
   SYNTAX      TableIndex
   MAX-ACCESS  not-accessible
   STATUS      current
   DESCRIPTION
      ""
   ::= {sr1645v2Lan3IpV6AddressesEntry 11}

sr1645v2Lan3IpV6AddressesAddress OBJECT-TYPE
   SYNTAX      Ipv6Address
   MAX-ACCESS  read-only
   STATUS      current
   DESCRIPTION
      "Path: ethernet3.status.ipV6.addresses.address

       ipv6 address"
   ::= {sr1645v2Lan3IpV6AddressesEntry 16777216}

sr1645v2Lan3IpV6AddressesPrefixLength OBJECT-TYPE
   SYNTAX      Integer32
   MAX-ACCESS  read-only
   STATUS      current
   DESCRIPTION
      "Path: ethernet3.status.ipV6.addresses.prefixLength"
   ::= {sr1645v2Lan3IpV6AddressesEntry 33554432}

sr1645v2Lan3IpV6AddressesStatus OBJECT-TYPE
   SYNTAX      INTEGER
               {
               invalid (0),
               tentative (1),
               deprecated (2),
               preferred (3)
               }
   MAX-ACCESS  read-only
   STATUS      current
   DESCRIPTION
      "Path: ethernet3.status.ipV6.addresses.status

       Possibilities:
               invalid   (0)
               tentative   (1)
               deprecated   (2)
               preferred   (3)"
   ::= {sr1645v2Lan3IpV6AddressesEntry 50331648}

sr1645v2Lan3IpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.ipV6.addresses.origin

       Possibilities:
               unknown   (0)
               manual   (1)
               generalPrefix   (2)
               statelessAuto   (3)
               statefullAuto   (4)"
   ::= {sr1645v2Lan3IpV6AddressesEntry 67108864}

sr1645v2Lan3IpV6AddressesFlagsInterfaceId OBJECT-TYPE
   SYNTAX      INTEGER
               {
               no (0),
               yes (1)
               }
   MAX-ACCESS  read-only
   STATUS      current
   DESCRIPTION
      "Path: ethernet3.status.ipV6.addresses.flags.interfaceId

       Possibilities:
               no   (0)
               yes   (1)"
   ::= {sr1645v2Lan3IpV6AddressesEntry 83951616}

sr1645v2Lan3IpV6AddressesFlagsAnycast OBJECT-TYPE
   SYNTAX      INTEGER
               {
               no (0),
               yes (1)
               }
   MAX-ACCESS  read-only
   STATUS      current
   DESCRIPTION
      "Path: ethernet3.status.ipV6.addresses.flags.anycast

       Possibilities:
               no   (0)
               yes   (1)"
   ::= {sr1645v2Lan3IpV6AddressesEntry 84017152}

sr1645v2Lan3IpV6AddressesTimersValidLifeTime OBJECT-TYPE
   SYNTAX      TimeTicks
   MAX-ACCESS  read-only
   STATUS      current
   DESCRIPTION
      "Path: ethernet3.status.ipV6.addresses.timers.validLifeTime

       Time in centi-second."
   ::= {sr1645v2Lan3IpV6AddressesEntry 100794368}

sr1645v2Lan3IpV6AddressesTimersPrefLifeTime OBJECT-TYPE
   SYNTAX      TimeTicks
   MAX-ACCESS  read-only
   STATUS      current
   DESCRIPTION
      "Path: ethernet3.status.ipV6.addresses.timers.prefLifeTime

       Time in centi-second."
   ::= {sr1645v2Lan3IpV6AddressesEntry 100728832}


sr1645v2Lan3MediaType OBJECT-TYPE
   SYNTAX      INTEGER
               {
               utp (1),
               sfp (2),
               down (255)
               }
   MAX-ACCESS  read-only
   STATUS      current
   DESCRIPTION
      "Path: ethernet3.status.mediaType

       Possibilities:
               utp   (1)
               sfp   (2)
               down   (255)"
   ::= {sr1645v2Lan3 500}



pr1645v2Lan3 OBJECT IDENTIFIER ::= {r1645v2Lan3 12}


pr1645v2Lan3InOctets OBJECT-TYPE
   SYNTAX      Counter64
   MAX-ACCESS  read-only
   STATUS      current
   DESCRIPTION
      "Path: ethernet3.performance.ifInOctets
       Info: ifInOctets

       64 bit unsigned wrappable counter."
   ::= {pr1645v2Lan3 109}


pr1645v2Lan3InUcast OBJECT-TYPE
   SYNTAX      Counter64
   MAX-ACCESS  read-only
   STATUS      current
   DESCRIPTION
      "Path: ethernet3.performance.ifInUcastPkts
       Info: ifInUcastPkts

       64 bit unsigned wrappable counter."
   ::= {pr1645v2Lan3 110}


pr1645v2Lan3InNUcastPkts OBJECT-TYPE
   SYNTAX      Counter64
   MAX-ACCESS  read-only
   STATUS      current
   DESCRIPTION
      "Path: ethernet3.performance.ifInNUcastPkts
       Info: ifInNUcastPkts

       64 bit unsigned wrappable counter."
   ::= {pr1645v2Lan3 111}


pr1645v2Lan3InBcastPkts OBJECT-TYPE
   SYNTAX      Counter64
   MAX-ACCESS  read-only
   STATUS      current
   DESCRIPTION
      "Path: ethernet3.performance.ifInBcastPkts
       Info: ifInBcastPkts

       64 bit unsigned wrappable counter."
   ::= {pr1645v2Lan3 211}


pr1645v2Lan3InMcastPkts OBJECT-TYPE
   SYNTAX      Counter64
   MAX-ACCESS  read-only
   STATUS      current
   DESCRIPTION
      "Path: ethernet3.performance.ifInMcastPkts
       Info: ifInNUcastPkts

       64 bit unsigned wrappable counter."
   ::= {pr1645v2Lan3 221}


pr1645v2Lan3InDiscards OBJECT-TYPE
   SYNTAX      Counter64
   MAX-ACCESS  read-only
   STATUS      current
   DESCRIPTION
      "Path: ethernet3.performance.ifInDiscards
       Info: ifInDiscards

       64 bit unsigned wrappable counter."
   ::= {pr1645v2Lan3 112}


pr1645v2Lan3InErrors OBJECT-TYPE
   SYNTAX      Counter64
   MAX-ACCESS  read-only
   STATUS      current
   DESCRIPTION
      "Path: ethernet3.performance.ifInErrors
       Info: ifInErrors

       64 bit unsigned wrappable counter."
   ::= {pr1645v2Lan3 113}


pr1645v2Lan3InUnknownProtos OBJECT-TYPE
   SYNTAX      Counter64
   MAX-ACCESS  read-only
   STATUS      current
   DESCRIPTION
      "Path: ethernet3.performance.ifInUnknownProtos
       Info: ifInUnknownprotos

       64 bit unsigned wrappable counter."
   ::= {pr1645v2Lan3 114}


pr1645v2Lan3InQLen OBJECT-TYPE
   SYNTAX      Gauge32
   MAX-ACCESS  read-only
   STATUS      current
   DESCRIPTION
      "Path: ethernet3.performance.ifInQLen
       Info: ifInQLen

       32 bit unsigned gauge value."
   ::= {pr1645v2Lan3 128}


pr1645v2Lan3InDropEx OBJECT-TYPE
   SYNTAX      Counter64
   MAX-ACCESS  read-only
   STATUS      current
   DESCRIPTION
      "Path: ethernet3.performance.ifInDropLevelExceeded
       Info: ifInDiscards

       64 bit unsigned wrappable counter."
   ::= {pr1645v2Lan3 130}


pr1645v2Lan3InDropNoMac OBJECT-TYPE
   SYNTAX      Counter64
   MAX-ACCESS  read-only
   STATUS      current
   DESCRIPTION
      "Path: ethernet3.performance.ifInDiscardsNoMacFit
       Info: ifInDiscards

       64 bit unsigned wrappable counter."
   ::= {pr1645v2Lan3 133}


pr1645v2Lan3InDropNUCast OBJECT-TYPE
   SYNTAX      Counter64
   MAX-ACCESS  read-only
   STATUS      current
   DESCRIPTION
      "Path: ethernet3.performance.ifInDiscardsNUCast
       Info: ifInDiscards

       64 bit unsigned wrappable counter."
   ::= {pr1645v2Lan3 136}


pr1645v2Lan3InDropFilter OBJECT-TYPE
   SYNTAX      Counter64
   MAX-ACCESS  read-only
   STATUS      current
   DESCRIPTION
      "Path: ethernet3.performance.ifInDiscardsFilter
       Info: ifInDiscards

       64 bit unsigned wrappable counter."
   ::= {pr1645v2Lan3 137}


pr1645v2Lan3InQueues OBJECT IDENTIFIER ::= {pr1645v2Lan3 131}

pr1645v2Lan3InQueuesSSCTable OBJECT-TYPE
   SYNTAX      SEQUENCE OF Pr1645v2Lan3InQueuesEntry
   MAX-ACCESS  not-accessible
   STATUS      current
   DESCRIPTION
      "Queue Lengths"
   ::= {pr1645v2Lan3InQueues 1}

pr1645v2Lan3InQueuesEntry OBJECT-TYPE
   SYNTAX      Pr1645v2Lan3InQueuesEntry
   MAX-ACCESS  not-accessible
   STATUS      current
   DESCRIPTION
      ""
   INDEX      { pr1645v2Lan3InQueuesTableIx }
   ::= {pr1645v2Lan3InQueuesSSCTable 1}

Pr1645v2Lan3InQueuesEntry ::=
   SEQUENCE
      {
      pr1645v2Lan3InQueuesTableIx
         TableIndex,
      pr1645v2Lan3InQueuesName
         INTEGER,
      pr1645v2Lan3InQueuesLength
         Integer32,
      pr1645v2Lan3InQueuesOctetLength
         Integer32,
      pr1645v2Lan3InQueuesRedLength
         Integer32,
      pr1645v2Lan3InQueuesPacketsTotal
         Counter64,
      pr1645v2Lan3InQueuesPacketsDirectTx
         Counter64,
      pr1645v2Lan3InQueuesPacketsQueued
         Counter64,
      pr1645v2Lan3InQueuesPacketsDropped
         Counter64,
      pr1645v2Lan3InQueuesPacketsRedDropped
         Counter64,
      pr1645v2Lan3InQueuesPacketsCirTx
         Counter64,
      pr1645v2Lan3InQueuesPacketsEirTx
         Counter64,
      pr1645v2Lan3InQueuesPacketsViolateTx
         Counter64,
      pr1645v2Lan3InQueuesOctetsTotal
         Counter64,
      pr1645v2Lan3InQueuesOctetsDirectTx
         Counter64,
      pr1645v2Lan3InQueuesOctetsQueued
         Counter64,
      pr1645v2Lan3InQueuesOctetsDropped
         Counter64,
      pr1645v2Lan3InQueuesOctetsRedDropped
         Counter64,
      pr1645v2Lan3InQueuesOctetsCirTx
         Counter64,
      pr1645v2Lan3InQueuesOctetsEirTx
         Counter64,
      pr1645v2Lan3InQueuesOctetsViolateTx
         Counter64,
      pr1645v2Lan3InQueuesOctetsBandwidth15sec
         Integer32,
      pr1645v2Lan3InQueuesOctetsBandwidth30sec
         Integer32,
      pr1645v2Lan3InQueuesOctetsBandwidth1min
         Integer32,
      pr1645v2Lan3InQueuesOctetsBandwidth2min
         Integer32,
      pr1645v2Lan3InQueuesOctetsBandwidth5min
         Integer32
      }

pr1645v2Lan3InQueuesTableIx OBJECT-TYPE
   SYNTAX      TableIndex
   MAX-ACCESS  not-accessible
   STATUS      current
   DESCRIPTION
      ""
   ::= {pr1645v2Lan3InQueuesEntry 11}

pr1645v2Lan3InQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3InQueuesEntry 16777216}

pr1645v2Lan3InQueuesLength OBJECT-TYPE
   SYNTAX      Integer32
   MAX-ACCESS  read-only
   STATUS      current
   DESCRIPTION
      "Path: ethernet3.performance.ifInPriorityQueues.length"
   ::= {pr1645v2Lan3InQueuesEntry 33554432}

pr1645v2Lan3InQueuesOctetLength OBJECT-TYPE
   SYNTAX      Integer32
   MAX-ACCESS  read-only
   STATUS      current
   DESCRIPTION
      "Path: ethernet3.performance.ifInPriorityQueues.octetLength"
   ::= {pr1645v2Lan3InQueuesEntry 150994944}

pr1645v2Lan3InQueuesRedLength OBJECT-TYPE
   SYNTAX      Integer32
   MAX-ACCESS  read-only
   STATUS      current
   DESCRIPTION
      "Path: ethernet3.performance.ifInPriorityQueues.redLength"
   ::= {pr1645v2Lan3InQueuesEntry 134217728}

pr1645v2Lan3InQueuesPacketsTotal OBJECT-TYPE
   SYNTAX      Counter64
   MAX-ACCESS  read-only
   STATUS      current
   DESCRIPTION
      "Path: ethernet3.performance.ifInPriorityQueues.packets.total

       64 bit unsigned wrappable counter."
   ::= {pr1645v2Lan3InQueuesEntry 50790400}

pr1645v2Lan3InQueuesPacketsDirectTx OBJECT-TYPE
   SYNTAX      Counter64
   MAX-ACCESS  read-only
   STATUS      current
   DESCRIPTION
      "Path: ethernet3.performance.ifInPriorityQueues.packets.directTx

       64 bit unsigned wrappable counter."
   ::= {pr1645v2Lan3InQueuesEntry 50397184}

pr1645v2Lan3InQueuesPacketsQueued OBJECT-TYPE
   SYNTAX      Counter64
   MAX-ACCESS  read-only
   STATUS      current
   DESCRIPTION
      "Path: ethernet3.performance.ifInPriorityQueues.packets.queued

       64 bit unsigned wrappable counter."
   ::= {pr1645v2Lan3InQueuesEntry 50462720}

pr1645v2Lan3InQueuesPacketsDropped OBJECT-TYPE
   SYNTAX      Counter64
   MAX-ACCESS  read-only
   STATUS      current
   DESCRIPTION
      "Path: ethernet3.performance.ifInPriorityQueues.packets.dropped

       64 bit unsigned wrappable counter."
   ::= {pr1645v2Lan3InQueuesEntry 50528256}

pr1645v2Lan3InQueuesPacketsRedDropped OBJECT-TYPE
   SYNTAX      Counter64
   MAX-ACCESS  read-only
   STATUS      current
   DESCRIPTION
      "Path: ethernet3.performance.ifInPriorityQueues.packets.redDropped

       64 bit unsigned wrappable counter."
   ::= {pr1645v2Lan3InQueuesEntry 50724864}

pr1645v2Lan3InQueuesPacketsCirTx OBJECT-TYPE
   SYNTAX      Counter64
   MAX-ACCESS  read-only
   STATUS      current
   DESCRIPTION
      "Path: ethernet3.performance.ifInPriorityQueues.packets.cirTx

       64 bit unsigned wrappable counter."
   ::= {pr1645v2Lan3InQueuesEntry 50593792}

pr1645v2Lan3InQueuesPacketsEirTx OBJECT-TYPE
   SYNTAX      Counter64
   MAX-ACCESS  read-only
   STATUS      current
   DESCRIPTION
      "Path: ethernet3.performance.ifInPriorityQueues.packets.eirTx

       64 bit unsigned wrappable counter."
   ::= {pr1645v2Lan3InQueuesEntry 50659328}

pr1645v2Lan3InQueuesPacketsViolateTx OBJECT-TYPE
   SYNTAX      Counter64
   MAX-ACCESS  read-only
   STATUS      current
   DESCRIPTION
      "Path: ethernet3.performance.ifInPriorityQueues.packets.violateTx

       64 bit unsigned wrappable counter."
   ::= {pr1645v2Lan3InQueuesEntry 50855936}

pr1645v2Lan3InQueuesOctetsTotal OBJECT-TYPE
   SYNTAX      Counter64
   MAX-ACCESS  read-only
   STATUS      current
   DESCRIPTION
      "Path: ethernet3.performance.ifInPriorityQueues.octets.total

       64 bit unsigned wrappable counter."
   ::= {pr1645v2Lan3InQueuesEntry 67567616}

pr1645v2Lan3InQueuesOctetsDirectTx OBJECT-TYPE
   SYNTAX      Counter64
   MAX-ACCESS  read-only
   STATUS      current
   DESCRIPTION
      "Path: ethernet3.performance.ifInPriorityQueues.octets.directTx

       64 bit unsigned wrappable counter."
   ::= {pr1645v2Lan3InQueuesEntry 67174400}

pr1645v2Lan3InQueuesOctetsQueued OBJECT-TYPE
   SYNTAX      Counter64
   MAX-ACCESS  read-only
   STATUS      current
   DESCRIPTION
      "Path: ethernet3.performance.ifInPriorityQueues.octets.queued

       64 bit unsigned wrappable counter."
   ::= {pr1645v2Lan3InQueuesEntry 67239936}

pr1645v2Lan3InQueuesOctetsDropped OBJECT-TYPE
   SYNTAX      Counter64
   MAX-ACCESS  read-only
   STATUS      current
   DESCRIPTION
      "Path: ethernet3.performance.ifInPriorityQueues.octets.dropped

       64 bit unsigned wrappable counter."
   ::= {pr1645v2Lan3InQueuesEntry 67305472}

pr1645v2Lan3InQueuesOctetsRedDropped OBJECT-TYPE
   SYNTAX      Counter64
   MAX-ACCESS  read-only
   STATUS      current
   DESCRIPTION
      "Path: ethernet3.performance.ifInPriorityQueues.octets.redDropped

       64 bit unsigned wrappable counter."
   ::= {pr1645v2Lan3InQueuesEntry 67502080}

pr1645v2Lan3InQueuesOctetsCirTx OBJECT-TYPE
   SYNTAX      Counter64
   MAX-ACCESS  read-only
   STATUS      current
   DESCRIPTION
      "Path: ethernet3.performance.ifInPriorityQueues.octets.cirTx

       64 bit unsigned wrappable counter."
   ::= {pr1645v2Lan3InQueuesEntry 67371008}

pr1645v2Lan3InQueuesOctetsEirTx OBJECT-TYPE
   SYNTAX      Counter64
   MAX-ACCESS  read-only
   STATUS      current
   DESCRIPTION
      "Path: ethernet3.performance.ifInPriorityQueues.octets.eirTx

       64 bit unsigned wrappable counter."
   ::= {pr1645v2Lan3InQueuesEntry 67436544}

pr1645v2Lan3InQueuesOctetsViolateTx OBJECT-TYPE
   SYNTAX      Counter64
   MAX-ACCESS  read-only
   STATUS      current
   DESCRIPTION
      "Path: ethernet3.performance.ifInPriorityQueues.octets.violateTx

       64 bit unsigned wrappable counter."
   ::= {pr1645v2Lan3InQueuesEntry 67633152}

pr1645v2Lan3InQueuesOctetsBandwidth15sec OBJECT-TYPE
   SYNTAX      Integer32
   MAX-ACCESS  read-only
   STATUS      current
   DESCRIPTION
      "Path: ethernet3.performance.ifInPriorityQueues.octets.bandwidth.15sec

       unit name = bps
       formula = 8 * ; 8 /"
   ::= {pr1645v2Lan3InQueuesEntry 70386944}

pr1645v2Lan3InQueuesOctetsBandwidth30sec OBJECT-TYPE
   SYNTAX      Integer32
   MAX-ACCESS  read-only
   STATUS      current
   DESCRIPTION
      "Path: ethernet3.performance.ifInPriorityQueues.octets.bandwidth.30sec

       unit name = bps
       formula = 8 * ; 8 /"
   ::= {pr1645v2Lan3InQueuesEntry 70388224}

pr1645v2Lan3InQueuesOctetsBandwidth1min OBJECT-TYPE
   SYNTAX      Integer32
   MAX-ACCESS  read-only
   STATUS      current
   DESCRIPTION
      "Path: ethernet3.performance.ifInPriorityQueues.octets.bandwidth.1min

       unit name = bps
       formula = 8 * ; 8 /"
   ::= {pr1645v2Lan3InQueuesEntry 70390784}

pr1645v2Lan3InQueuesOctetsBandwidth2min OBJECT-TYPE
   SYNTAX      Integer32
   MAX-ACCESS  read-only
   STATUS      current
   DESCRIPTION
      "Path: ethernet3.performance.ifInPriorityQueues.octets.bandwidth.2min

       unit name = bps
       formula = 8 * ; 8 /"
   ::= {pr1645v2Lan3InQueuesEntry 70395904}

pr1645v2Lan3InQueuesOctetsBandwidth5min OBJECT-TYPE
   SYNTAX      Integer32
   MAX-ACCESS  read-only
   STATUS      current
   DESCRIPTION
      "Path: ethernet3.performance.ifInPriorityQueues.octets.bandwidth.5min

       unit name = bps
       formula = 8 * ; 8 /"
   ::= {pr1645v2Lan3InQueuesEntry 70411264}

pr1645v2Lan3InQueuesH2Performance OBJECT-TYPE
   SYNTAX      SEQUENCE OF Pr1645v2Lan3InQueuesH2PerformanceEntry
   MAX-ACCESS  not-accessible
   STATUS      current
   DESCRIPTION
      ""
   ::= {pr1645v2Lan3InQueues 83886080}

pr1645v2Lan3InQueuesH2PerformanceEntry OBJECT-TYPE
   SYNTAX      Pr1645v2Lan3InQueuesH2PerformanceEntry
   MAX-ACCESS  not-accessible
   STATUS      current
   DESCRIPTION
      ""
   INDEX      { pr1645v2Lan3InQueuesTableIx,
                pr1645v2Lan3InQueuesH2PerformanceTableIx }
   ::= {pr1645v2Lan3InQueuesH2Performance 1}

Pr1645v2Lan3InQueuesH2PerformanceEntry ::=
   SEQUENCE
      {
      pr1645v2Lan3InQueuesH2PerformanceTableIx
         TableIndex,
      pr1645v2Lan3InQueuesH2PerformanceSysUpTime
         TimeTicks,
      pr1645v2Lan3InQueuesH2PerformanceTotPkts
         Counter64,
      pr1645v2Lan3InQueuesH2PerformanceDirTxPkts
         Counter64,
      pr1645v2Lan3InQueuesH2PerformanceQdPkts
         Counter64,
      pr1645v2Lan3InQueuesH2PerformanceDropPkts
         Counter64,
      pr1645v2Lan3InQueuesH2PerformanceRDropPkts
         Counter64,
      pr1645v2Lan3InQueuesH2PerformanceCirTxPkts
         Counter64,
      pr1645v2Lan3InQueuesH2PerformanceEirTxPkts
         Counter64,
      pr1645v2Lan3InQueuesH2PerformanceViolTxPkts
         Counter64,
      pr1645v2Lan3InQueuesH2PerformanceTotOcts
         Counter64,
      pr1645v2Lan3InQueuesH2PerformanceDirTxOcts
         Counter64,
      pr1645v2Lan3InQueuesH2PerformanceQdOcts
         Counter64,
      pr1645v2Lan3InQueuesH2PerformanceDropOcts
         Counter64,
      pr1645v2Lan3InQueuesH2PerformanceRDropOcts
         Counter64,
      pr1645v2Lan3InQueuesH2PerformanceCirTxOcts
         Counter64,
      pr1645v2Lan3InQueuesH2PerformanceEirTxOcts
         Counter64,
      pr1645v2Lan3InQueuesH2PerformanceViolTxOcts
         Counter64,
      pr1645v2Lan3InQueuesH2PerformanceBandwidth
         Integer32
      }

pr1645v2Lan3InQueuesH2PerformanceTableIx OBJECT-TYPE
   SYNTAX      TableIndex
   MAX-ACCESS  not-accessible
   STATUS      current
   DESCRIPTION
      ""
   ::= {pr1645v2Lan3InQueuesH2PerformanceEntry 11}

pr1645v2Lan3InQueuesH2PerformanceSysUpTime OBJECT-TYPE
   SYNTAX      TimeTicks
   MAX-ACCESS  read-only
   STATUS      current
   DESCRIPTION
      "Path: ethernet3.performance.ifInPriorityQueues.h2Performance.sysUpTime

       Time in centi-second."
   ::= {pr1645v2Lan3InQueuesH2PerformanceEntry 16777216}

pr1645v2Lan3InQueuesH2PerformanceTotPkts OBJECT-TYPE
   SYNTAX      Counter64
   MAX-ACCESS  read-only
   STATUS      current
   DESCRIPTION
      "Path: ethernet3.performance.ifInPriorityQueues.h2Performance.totalPkts

       64 bit unsigned wrappable counter."
   ::= {pr1645v2Lan3InQueuesH2PerformanceEntry 234881024}

pr1645v2Lan3InQueuesH2PerformanceDirTxPkts OBJECT-TYPE
   SYNTAX      Counter64
   MAX-ACCESS  read-only
   STATUS      current
   DESCRIPTION
      "Path: ethernet3.performance.ifInPriorityQueues.h2Performance.directTxPkts

       64 bit unsigned wrappable counter."
   ::= {pr1645v2Lan3InQueuesH2PerformanceEntry 33554432}

pr1645v2Lan3InQueuesH2PerformanceQdPkts OBJECT-TYPE
   SYNTAX      Counter64
   MAX-ACCESS  read-only
   STATUS      current
   DESCRIPTION
      "Path: ethernet3.performance.ifInPriorityQueues.h2Performance.queuedPkts

       64 bit unsigned wrappable counter."
   ::= {pr1645v2Lan3InQueuesH2PerformanceEntry 50331648}

pr1645v2Lan3InQueuesH2PerformanceDropPkts OBJECT-TYPE
   SYNTAX      Counter64
   MAX-ACCESS  read-only
   STATUS      current
   DESCRIPTION
      "Path: ethernet3.performance.ifInPriorityQueues.h2Performance.droppedPkts

       64 bit unsigned wrappable counter."
   ::= {pr1645v2Lan3InQueuesH2PerformanceEntry 67108864}

pr1645v2Lan3InQueuesH2PerformanceRDropPkts OBJECT-TYPE
   SYNTAX      Counter64
   MAX-ACCESS  read-only
   STATUS      current
   DESCRIPTION
      "Path: ethernet3.performance.ifInPriorityQueues.h2Performance.redDroppedPkts

       64 bit unsigned wrappable counter."
   ::= {pr1645v2Lan3InQueuesH2PerformanceEntry 201326592}

pr1645v2Lan3InQueuesH2PerformanceCirTxPkts OBJECT-TYPE
   SYNTAX      Counter64
   MAX-ACCESS  read-only
   STATUS      current
   DESCRIPTION
      "Path: ethernet3.performance.ifInPriorityQueues.h2Performance.cirTxPkts

       64 bit unsigned wrappable counter."
   ::= {pr1645v2Lan3InQueuesH2PerformanceEntry 83886080}

pr1645v2Lan3InQueuesH2PerformanceEirTxPkts OBJECT-TYPE
   SYNTAX      Counter64
   MAX-ACCESS  read-only
   STATUS      current
   DESCRIPTION
      "Path: ethernet3.performance.ifInPriorityQueues.h2Performance.eirTxPkts

       64 bit unsigned wrappable counter."
   ::= {pr1645v2Lan3InQueuesH2PerformanceEntry 100663296}

pr1645v2Lan3InQueuesH2PerformanceViolTxPkts OBJECT-TYPE
   SYNTAX      Counter64
   MAX-ACCESS  read-only
   STATUS      current
   DESCRIPTION
      "Path: ethernet3.performance.ifInPriorityQueues.h2Performance.violateTxPkts

       64 bit unsigned wrappable counter."
   ::= {pr1645v2Lan3InQueuesH2PerformanceEntry 301989888}

pr1645v2Lan3InQueuesH2PerformanceTotOcts OBJECT-TYPE
   SYNTAX      Counter64
   MAX-ACCESS  read-only
   STATUS      current
   DESCRIPTION
      "Path: ethernet3.performance.ifInPriorityQueues.h2Performance.totalOctets

       64 bit unsigned wrappable counter."
   ::= {pr1645v2Lan3InQueuesH2PerformanceEntry 251658240}

pr1645v2Lan3InQueuesH2PerformanceDirTxOcts OBJECT-TYPE
   SYNTAX      Counter64
   MAX-ACCESS  read-only
   STATUS      current
   DESCRIPTION
      "Path: ethernet3.performance.ifInPriorityQueues.h2Performance.directTxOctets

       64 bit unsigned wrappable counter."
   ::= {pr1645v2Lan3InQueuesH2PerformanceEntry 117440512}

pr1645v2Lan3InQueuesH2PerformanceQdOcts OBJECT-TYPE
   SYNTAX      Counter64
   MAX-ACCESS  read-only
   STATUS      current
   DESCRIPTION
      "Path: ethernet3.performance.ifInPriorityQueues.h2Performance.queuedOctets

       64 bit unsigned wrappable counter."
   ::= {pr1645v2Lan3InQueuesH2PerformanceEntry 134217728}

pr1645v2Lan3InQueuesH2PerformanceDropOcts OBJECT-TYPE
   SYNTAX      Counter64
   MAX-ACCESS  read-only
   STATUS      current
   DESCRIPTION
      "Path: ethernet3.performance.ifInPriorityQueues.h2Performance.droppedOctets

       64 bit unsigned wrappable counter."
   ::= {pr1645v2Lan3InQueuesH2PerformanceEntry 150994944}

pr1645v2Lan3InQueuesH2PerformanceRDropOcts OBJECT-TYPE
   SYNTAX      Counter64
   MAX-ACCESS  read-only
   STATUS      current
   DESCRIPTION
      "Path: ethernet3.performance.ifInPriorityQueues.h2Performance.redDroppedOctets

       64 bit unsigned wrappable counter."
   ::= {pr1645v2Lan3InQueuesH2PerformanceEntry 218103808}

pr1645v2Lan3InQueuesH2PerformanceCirTxOcts OBJECT-TYPE
   SYNTAX      Counter64
   MAX-ACCESS  read-only
   STATUS      current
   DESCRIPTION
      "Path: ethernet3.performance.ifInPriorityQueues.h2Performance.cirTxOctets

       64 bit unsigned wrappable counter."
   ::= {pr1645v2Lan3InQueuesH2PerformanceEntry 167772160}

pr1645v2Lan3InQueuesH2PerformanceEirTxOcts OBJECT-TYPE
   SYNTAX      Counter64
   MAX-ACCESS  read-only
   STATUS      current
   DESCRIPTION
      "Path: ethernet3.performance.ifInPriorityQueues.h2Performance.eirTxOctets

       64 bit unsigned wrappable counter."
   ::= {pr1645v2Lan3InQueuesH2PerformanceEntry 184549376}

pr1645v2Lan3InQueuesH2PerformanceViolTxOcts OBJECT-TYPE
   SYNTAX      Counter64
   MAX-ACCESS  read-only
   STATUS      current
   DESCRIPTION
      "Path: ethernet3.performance.ifInPriorityQueues.h2Performance.violateTxOctets

       64 bit unsigned wrappable counter."
   ::= {pr1645v2Lan3InQueuesH2PerformanceEntry 318767104}

pr1645v2Lan3InQueuesH2PerformanceBandwidth OBJECT-TYPE
   SYNTAX      Integer32
   MAX-ACCESS  read-only
   STATUS      current
   DESCRIPTION
      "Path: ethernet3.performance.ifInPriorityQueues.h2Performance.bandwidth

       unit name = bps
       formula = 8 * ; 8 /"
   ::= {pr1645v2Lan3InQueuesH2PerformanceEntry 268435456}

pr1645v2Lan3InQueuesH24Performance OBJECT-TYPE
   SYNTAX      SEQUENCE OF Pr1645v2Lan3InQueuesH24PerformanceEntry
   MAX-ACCESS  not-accessible
   STATUS      current
   DESCRIPTION
      ""
   ::= {pr1645v2Lan3InQueues 100663296}

pr1645v2Lan3InQueuesH24PerformanceEntry OBJECT-TYPE
   SYNTAX      Pr1645v2Lan3InQueuesH24PerformanceEntry
   MAX-ACCESS  not-accessible
   STATUS      current
   DESCRIPTION
      ""
   INDEX      { pr1645v2Lan3InQueuesTableIx,
                pr1645v2Lan3InQueuesH24PerformanceTableIx }
   ::= {pr1645v2Lan3InQueuesH24Performance 1}

Pr1645v2Lan3InQueuesH24PerformanceEntry ::=
   SEQUENCE
      {
      pr1645v2Lan3InQueuesH24PerformanceTableIx
         TableIndex,
      pr1645v2Lan3InQueuesH24PerformanceSysUpTime
         TimeTicks,
      pr1645v2Lan3InQueuesH24PerformanceTotPkts
         Counter64,
      pr1645v2Lan3InQueuesH24PerformanceDirTxPkts
         Counter64,
      pr1645v2Lan3InQueuesH24PerformanceQdPkts
         Counter64,
      pr1645v2Lan3InQueuesH24PerformanceDropPkts
         Counter64,
      pr1645v2Lan3InQueuesH24PerformanceRDropPkts
         Counter64,
      pr1645v2Lan3InQueuesH24PerformanceCirTxPkts
         Counter64,
      pr1645v2Lan3InQueuesH24PerformanceEirTxPkts
         Counter64,
      pr1645v2Lan3InQueuesH24PerformanceViolTxPkts
         Counter64,
      pr1645v2Lan3InQueuesH24PerformanceTotOcts
         Counter64,
      pr1645v2Lan3InQueuesH24PerformanceDirTxOcts
         Counter64,
      pr1645v2Lan3InQueuesH24PerformanceQdOcts
         Counter64,
      pr1645v2Lan3InQueuesH24PerformanceDropOcts
         Counter64,
      pr1645v2Lan3InQueuesH24PerformanceRDropOcts
         Counter64,
      pr1645v2Lan3InQueuesH24PerformanceCirTxOcts
         Counter64,
      pr1645v2Lan3InQueuesH24PerformanceEirTxOcts
         Counter64,
      pr1645v2Lan3InQueuesH24PerformanceViolTxOcts
         Counter64,
      pr1645v2Lan3InQueuesH24PerformanceBandwidth
         Integer32
      }

pr1645v2Lan3InQueuesH24PerformanceTableIx OBJECT-TYPE
   SYNTAX      TableIndex
   MAX-ACCESS  not-accessible
   STATUS      current
   DESCRIPTION
      ""
   ::= {pr1645v2Lan3InQueuesH24PerformanceEntry 11}

pr1645v2Lan3InQueuesH24PerformanceSysUpTime OBJECT-TYPE
   SYNTAX      TimeTicks
   MAX-ACCESS  read-only
   STATUS      current
   DESCRIPTION
      "Path: ethernet3.performance.ifInPriorityQueues.h24Performance.sysUpTime

       Time in centi-second."
   ::= {pr1645v2Lan3InQueuesH24PerformanceEntry 16777216}

pr1645v2Lan3InQueuesH24PerformanceTotPkts OBJECT-TYPE
   SYNTAX      Counter64
   MAX-ACCESS  read-only
   STATUS      current
   DESCRIPTION
      "Path: ethernet3.performance.ifInPriorityQueues.h24Performance.totalPkts

       64 bit unsigned wrappable counter."
   ::= {pr1645v2Lan3InQueuesH24PerformanceEntry 234881024}

pr1645v2Lan3InQueuesH24PerformanceDirTxPkts OBJECT-TYPE
   SYNTAX      Counter64
   MAX-ACCESS  read-only
   STATUS      current
   DESCRIPTION
      "Path: ethernet3.performance.ifInPriorityQueues.h24Performance.directTxPkts

       64 bit unsigned wrappable counter."
   ::= {pr1645v2Lan3InQueuesH24PerformanceEntry 33554432}

pr1645v2Lan3InQueuesH24PerformanceQdPkts OBJECT-TYPE
   SYNTAX      Counter64
   MAX-ACCESS  read-only
   STATUS      current
   DESCRIPTION
      "Path: ethernet3.performance.ifInPriorityQueues.h24Performance.queuedPkts

       64 bit unsigned wrappable counter."
   ::= {pr1645v2Lan3InQueuesH24PerformanceEntry 50331648}

pr1645v2Lan3InQueuesH24PerformanceDropPkts OBJECT-TYPE
   SYNTAX      Counter64
   MAX-ACCESS  read-only
   STATUS      current
   DESCRIPTION
      "Path: ethernet3.performance.ifInPriorityQueues.h24Performance.droppedPkts

       64 bit unsigned wrappable counter."
   ::= {pr1645v2Lan3InQueuesH24PerformanceEntry 67108864}

pr1645v2Lan3InQueuesH24PerformanceRDropPkts OBJECT-TYPE
   SYNTAX      Counter64
   MAX-ACCESS  read-only
   STATUS      current
   DESCRIPTION
      "Path: ethernet3.performance.ifInPriorityQueues.h24Performance.redDroppedPkts

       64 bit unsigned wrappable counter."
   ::= {pr1645v2Lan3InQueuesH24PerformanceEntry 201326592}

pr1645v2Lan3InQueuesH24PerformanceCirTxPkts OBJECT-TYPE
   SYNTAX      Counter64
   MAX-ACCESS  read-only
   STATUS      current
   DESCRIPTION
      "Path: ethernet3.performance.ifInPriorityQueues.h24Performance.cirTxPkts

       64 bit unsigned wrappable counter."
   ::= {pr1645v2Lan3InQueuesH24PerformanceEntry 83886080}

pr1645v2Lan3InQueuesH24PerformanceEirTxPkts OBJECT-TYPE
   SYNTAX      Counter64
   MAX-ACCESS  read-only
   STATUS      current
   DESCRIPTION
      "Path: ethernet3.performance.ifInPriorityQueues.h24Performance.eirTxPkts

       64 bit unsigned wrappable counter."
   ::= {pr1645v2Lan3InQueuesH24PerformanceEntry 100663296}

pr1645v2Lan3InQueuesH24PerformanceViolTxPkts OBJECT-TYPE
   SYNTAX      Counter64
   MAX-ACCESS  read-only
   STATUS      current
   DESCRIPTION
      "Path: ethernet3.performance.ifInPriorityQueues.h24Performance.violateTxPkts

       64 bit unsigned wrappable counter."
   ::= {pr1645v2Lan3InQueuesH24PerformanceEntry 301989888}

pr1645v2Lan3InQueuesH24PerformanceTotOcts OBJECT-TYPE
   SYNTAX      Counter64
   MAX-ACCESS  read-only
   STATUS      current
   DESCRIPTION
      "Path: ethernet3.performance.ifInPriorityQueues.h24Performance.totalOctets

       64 bit unsigned wrappable counter."
   ::= {pr1645v2Lan3InQueuesH24PerformanceEntry 251658240}

pr1645v2Lan3InQueuesH24PerformanceDirTxOcts OBJECT-TYPE
   SYNTAX      Counter64
   MAX-ACCESS  read-only
   STATUS      current
   DESCRIPTION
      "Path: ethernet3.performance.ifInPriorityQueues.h24Performance.directTxOctets

       64 bit unsigned wrappable counter."
   ::= {pr1645v2Lan3InQueuesH24PerformanceEntry 117440512}

pr1645v2Lan3InQueuesH24PerformanceQdOcts OBJECT-TYPE
   SYNTAX      Counter64
   MAX-ACCESS  read-only
   STATUS      current
   DESCRIPTION
      "Path: ethernet3.performance.ifInPriorityQueues.h24Performance.queuedOctets

       64 bit unsigned wrappable counter."
   ::= {pr1645v2Lan3InQueuesH24PerformanceEntry 134217728}

pr1645v2Lan3InQueuesH24PerformanceDropOcts OBJECT-TYPE
   SYNTAX      Counter64
   MAX-ACCESS  read-only
   STATUS      current
   DESCRIPTION
      "Path: ethernet3.performance.ifInPriorityQueues.h24Performance.droppedOctets

       64 bit unsigned wrappable counter."
   ::= {pr1645v2Lan3InQueuesH24PerformanceEntry 150994944}

pr1645v2Lan3InQueuesH24PerformanceRDropOcts OBJECT-TYPE
   SYNTAX      Counter64
   MAX-ACCESS  read-only
   STATUS      current
   DESCRIPTION
      "Path: ethernet3.performance.ifInPriorityQueues.h24Performance.redDroppedOctets

       64 bit unsigned wrappable counter."
   ::= {pr1645v2Lan3InQueuesH24PerformanceEntry 218103808}

pr1645v2Lan3InQueuesH24PerformanceCirTxOcts OBJECT-TYPE
   SYNTAX      Counter64
   MAX-ACCESS  read-only
   STATUS      current
   DESCRIPTION
      "Path: ethernet3.performance.ifInPriorityQueues.h24Performance.cirTxOctets

       64 bit unsigned wrappable counter."
   ::= {pr1645v2Lan3InQueuesH24PerformanceEntry 167772160}

pr1645v2Lan3InQueuesH24PerformanceEirTxOcts OBJECT-TYPE
   SYNTAX      Counter64
   MAX-ACCESS  read-only
   STATUS      current
   DESCRIPTION
      "Path: ethernet3.performance.ifInPriorityQueues.h24Performance.eirTxOctets

       64 bit unsigned wrappable counter."
   ::= {pr1645v2Lan3InQueuesH24PerformanceEntry 184549376}

pr1645v2Lan3InQueuesH24PerformanceViolTxOcts OBJECT-TYPE
   SYNTAX      Counter64
   MAX-ACCESS  read-only
   STATUS      current
   DESCRIPTION
      "Path: ethernet3.performance.ifInPriorityQueues.h24Performance.violateTxOctets

       64 bit unsigned wrappable counter."
   ::= {pr1645v2Lan3InQueuesH24PerformanceEntry 318767104}

pr1645v2Lan3InQueuesH24PerformanceBandwidth OBJECT-TYPE
   SYNTAX      Integer32
   MAX-ACCESS  read-only
   STATUS      current
   DESCRIPTION
      "Path: ethernet3.performance.ifInPriorityQueues.h24Performance.bandwidth

       unit name = bps
       formula = 8 * ; 8 /"
   ::= {pr1645v2Lan3InQueuesH24PerformanceEntry 268435456}

pr1645v2Lan3InQueuesD7Performance OBJECT-TYPE
   SYNTAX      SEQUENCE OF Pr1645v2Lan3InQueuesD7PerformanceEntry
   MAX-ACCESS  not-accessible
   STATUS      current
   DESCRIPTION
      ""
   ::= {pr1645v2Lan3InQueues 117440512}

pr1645v2Lan3InQueuesD7PerformanceEntry OBJECT-TYPE
   SYNTAX      Pr1645v2Lan3InQueuesD7PerformanceEntry
   MAX-ACCESS  not-accessible
   STATUS      current
   DESCRIPTION
      ""
   INDEX      { pr1645v2Lan3InQueuesTableIx,
                pr1645v2Lan3InQueuesD7PerformanceTableIx }
   ::= {pr1645v2Lan3InQueuesD7Performance 1}

Pr1645v2Lan3InQueuesD7PerformanceEntry ::=
   SEQUENCE
      {
      pr1645v2Lan3InQueuesD7PerformanceTableIx
         TableIndex,
      pr1645v2Lan3InQueuesD7PerformanceSysUpTime
         TimeTicks,
      pr1645v2Lan3InQueuesD7PerformanceTotPkts
         Counter64,
      pr1645v2Lan3InQueuesD7PerformanceDirTxPkts
         Counter64,
      pr1645v2Lan3InQueuesD7PerformanceQdPkts
         Counter64,
      pr1645v2Lan3InQueuesD7PerformanceDropPkts
         Counter64,
      pr1645v2Lan3InQueuesD7PerformanceRDropPkts
         Counter64,
      pr1645v2Lan3InQueuesD7PerformanceCirTxPkts
         Counter64,
      pr1645v2Lan3InQueuesD7PerformanceEirTxPkts
         Counter64,
      pr1645v2Lan3InQueuesD7PerformanceViolTxPkts
         Counter64,
      pr1645v2Lan3InQueuesD7PerformanceTotOcts
         Counter64,
      pr1645v2Lan3InQueuesD7PerformanceDirTxOcts
         Counter64,
      pr1645v2Lan3InQueuesD7PerformanceQdOcts
         Counter64,
      pr1645v2Lan3InQueuesD7PerformanceDropOcts
         Counter64,
      pr1645v2Lan3InQueuesD7PerformanceRDropOcts
         Counter64,
      pr1645v2Lan3InQueuesD7PerformanceCirTxOcts
         Counter64,
      pr1645v2Lan3InQueuesD7PerformanceEirTxOcts
         Counter64,
      pr1645v2Lan3InQueuesD7PerformanceViolTxOcts
         Counter64,
      pr1645v2Lan3InQueuesD7PerformanceBandwidth
         Integer32
      }

pr1645v2Lan3InQueuesD7PerformanceTableIx OBJECT-TYPE
   SYNTAX      TableIndex
   MAX-ACCESS  not-accessible
   STATUS      current
   DESCRIPTION
      ""
   ::= {pr1645v2Lan3InQueuesD7PerformanceEntry 11}

pr1645v2Lan3InQueuesD7PerformanceSysUpTime OBJECT-TYPE
   SYNTAX      TimeTicks
   MAX-ACCESS  read-only
   STATUS      current
   DESCRIPTION
      "Path: ethernet3.performance.ifInPriorityQueues.d7Performance.sysUpTime

       Time in centi-second."
   ::= {pr1645v2Lan3InQueuesD7PerformanceEntry 16777216}

pr1645v2Lan3InQueuesD7PerformanceTotPkts OBJECT-TYPE
   SYNTAX      Counter64
   MAX-ACCESS  read-only
   STATUS      current
   DESCRIPTION
      "Path: ethernet3.performance.ifInPriorityQueues.d7Performance.totalPkts

       64 bit unsigned wrappable counter."
   ::= {pr1645v2Lan3InQueuesD7PerformanceEntry 234881024}

pr1645v2Lan3InQueuesD7PerformanceDirTxPkts OBJECT-TYPE
   SYNTAX      Counter64
   MAX-ACCESS  read-only
   STATUS      current
   DESCRIPTION
      "Path: ethernet3.performance.ifInPriorityQueues.d7Performance.directTxPkts

       64 bit unsigned wrappable counter."
   ::= {pr1645v2Lan3InQueuesD7PerformanceEntry 33554432}

pr1645v2Lan3InQueuesD7PerformanceQdPkts OBJECT-TYPE
   SYNTAX      Counter64
   MAX-ACCESS  read-only
   STATUS      current
   DESCRIPTION
      "Path: ethernet3.performance.ifInPriorityQueues.d7Performance.queuedPkts

       64 bit unsigned wrappable counter."
   ::= {pr1645v2Lan3InQueuesD7PerformanceEntry 50331648}

pr1645v2Lan3InQueuesD7PerformanceDropPkts OBJECT-TYPE
   SYNTAX      Counter64
   MAX-ACCESS  read-only
   STATUS      current
   DESCRIPTION
      "Path: ethernet3.performance.ifInPriorityQueues.d7Performance.droppedPkts

       64 bit unsigned wrappable counter."
   ::= {pr1645v2Lan3InQueuesD7PerformanceEntry 67108864}

pr1645v2Lan3InQueuesD7PerformanceRDropPkts OBJECT-TYPE
   SYNTAX      Counter64
   MAX-ACCESS  read-only
   STATUS      current
   DESCRIPTION
      "Path: ethernet3.performance.ifInPriorityQueues.d7Performance.redDroppedPkts

       64 bit unsigned wrappable counter."
   ::= {pr1645v2Lan3InQueuesD7PerformanceEntry 201326592}

pr1645v2Lan3InQueuesD7PerformanceCirTxPkts OBJECT-TYPE
   SYNTAX      Counter64
   MAX-ACCESS  read-only
   STATUS      current
   DESCRIPTION
      "Path: ethernet3.performance.ifInPriorityQueues.d7Performance.cirTxPkts

       64 bit unsigned wrappable counter."
   ::= {pr1645v2Lan3InQueuesD7PerformanceEntry 83886080}

pr1645v2Lan3InQueuesD7PerformanceEirTxPkts OBJECT-TYPE
   SYNTAX      Counter64
   MAX-ACCESS  read-only
   STATUS      current
   DESCRIPTION
      "Path: ethernet3.performance.ifInPriorityQueues.d7Performance.eirTxPkts

       64 bit unsigned wrappable counter."
   ::= {pr1645v2Lan3InQueuesD7PerformanceEntry 100663296}

pr1645v2Lan3InQueuesD7PerformanceViolTxPkts OBJECT-TYPE
   SYNTAX      Counter64
   MAX-ACCESS  read-only
   STATUS      current
   DESCRIPTION
      "Path: ethernet3.performance.ifInPriorityQueues.d7Performance.violateTxPkts

       64 bit unsigned wrappable counter."
   ::= {pr1645v2Lan3InQueuesD7PerformanceEntry 301989888}

pr1645v2Lan3InQueuesD7PerformanceTotOcts OBJECT-TYPE
   SYNTAX      Counter64
   MAX-ACCESS  read-only
   STATUS      current
   DESCRIPTION
      "Path: ethernet3.performance.ifInPriorityQueues.d7Performance.totalOctets

       64 bit unsigned wrappable counter."
   ::= {pr1645v2Lan3InQueuesD7PerformanceEntry 251658240}

pr1645v2Lan3InQueuesD7PerformanceDirTxOcts OBJECT-TYPE
   SYNTAX      Counter64
   MAX-ACCESS  read-only
   STATUS      current
   DESCRIPTION
      "Path: ethernet3.performance.ifInPriorityQueues.d7Performance.directTxOctets

       64 bit unsigned wrappable counter."
   ::= {pr1645v2Lan3InQueuesD7PerformanceEntry 117440512}

pr1645v2Lan3InQueuesD7PerformanceQdOcts OBJECT-TYPE
   SYNTAX      Counter64
   MAX-ACCESS  read-only
   STATUS      current
   DESCRIPTION
      "Path: ethernet3.performance.ifInPriorityQueues.d7Performance.queuedOctets

       64 bit unsigned wrappable counter."
   ::= {pr1645v2Lan3InQueuesD7PerformanceEntry 134217728}

pr1645v2Lan3InQueuesD7PerformanceDropOcts OBJECT-TYPE
   SYNTAX      Counter64
   MAX-ACCESS  read-only
   STATUS      current
   DESCRIPTION
      "Path: ethernet3.performance.ifInPriorityQueues.d7Performance.droppedOctets

       64 bit unsigned wrappable counter."
   ::= {pr1645v2Lan3InQueuesD7PerformanceEntry 150994944}

pr1645v2Lan3InQueuesD7PerformanceRDropOcts OBJECT-TYPE
   SYNTAX      Counter64
   MAX-ACCESS  read-only
   STATUS      current
   DESCRIPTION
      "Path: ethernet3.performance.ifInPriorityQueues.d7Performance.redDroppedOctets

       64 bit unsigned wrappable counter."
   ::= {pr1645v2Lan3InQueuesD7PerformanceEntry 218103808}

pr1645v2Lan3InQueuesD7PerformanceCirTxOcts OBJECT-TYPE
   SYNTAX      Counter64
   MAX-ACCESS  read-only
   STATUS      current
   DESCRIPTION
      "Path: ethernet3.performance.ifInPriorityQueues.d7Performance.cirTxOctets

       64 bit unsigned wrappable counter."
   ::= {pr1645v2Lan3InQueuesD7PerformanceEntry 167772160}

pr1645v2Lan3InQueuesD7PerformanceEirTxOcts OBJECT-TYPE
   SYNTAX      Counter64
   MAX-ACCESS  read-only
   STATUS      current
   DESCRIPTION
      "Path: ethernet3.performance.ifInPriorityQueues.d7Performance.eirTxOctets

       64 bit unsigned wrappable counter."
   ::= {pr1645v2Lan3InQueuesD7PerformanceEntry 184549376}

pr1645v2Lan3InQueuesD7PerformanceViolTxOcts OBJECT-TYPE
   SYNTAX      Counter64
   MAX-ACCESS  read-only
   STATUS      current
   DESCRIPTION
      "Path: ethernet3.performance.ifInPriorityQueues.d7Performance.violateTxOctets

       64 bit unsigned wrappable counter."
   ::= {pr1645v2Lan3InQueuesD7PerformanceEntry 318767104}

pr1645v2Lan3InQueuesD7PerformanceBandwidth OBJECT-TYPE
   SYNTAX      Integer32
   MAX-ACCESS  read-only
   STATUS      current
   DESCRIPTION
      "Path: ethernet3.performance.ifInPriorityQueues.d7Performance.bandwidth

       unit name = bps
       formula = 8 * ; 8 /"
   ::= {pr1645v2Lan3InQueuesD7PerformanceEntry 268435456}


pr1645v2Lan3InBandwidth OBJECT IDENTIFIER ::= {pr1645v2Lan3 181}

pr1645v2Lan3InBandwidthSSC OBJECT IDENTIFIER ::= {pr1645v2Lan3InBandwidth 1}

pr1645v2Lan3InBandwidthEntry OBJECT IDENTIFIER ::= {pr1645v2Lan3InBandwidthSSC 1}

pr1645v2Lan3InBandwidth15sec OBJECT-TYPE
   SYNTAX      Integer32
   MAX-ACCESS  read-only
   STATUS      current
   DESCRIPTION
      "Path: ethernet3.performance.ifInBandwidth.15sec

       unit name = bps
       formula = 8 * ; 8 /"
   ::= {pr1645v2Lan3InBandwidthEntry 83886080}

pr1645v2Lan3InBandwidth30sec OBJECT-TYPE
   SYNTAX      Integer32
   MAX-ACCESS  read-only
   STATUS      current
   DESCRIPTION
      "Path: ethernet3.performance.ifInBandwidth.30sec

       unit name = bps
       formula = 8 * ; 8 /"
   ::= {pr1645v2Lan3InBandwidthEntry 167772160}

pr1645v2Lan3InBandwidth1min OBJECT-TYPE
   SYNTAX      Integer32
   MAX-ACCESS  read-only
   STATUS      current
   DESCRIPTION
      "Path: ethernet3.performance.ifInBandwidth.1min

       unit name = bps
       formula = 8 * ; 8 /"
   ::= {pr1645v2Lan3InBandwidthEntry 335544320}

pr1645v2Lan3InBandwidth2min OBJECT-TYPE
   SYNTAX      Integer32
   MAX-ACCESS  read-only
   STATUS      current
   DESCRIPTION
      "Path: ethernet3.performance.ifInBandwidth.2min

       unit name = bps
       formula = 8 * ; 8 /"
   ::= {pr1645v2Lan3InBandwidthEntry 671088640}

pr1645v2Lan3InBandwidth5min OBJECT-TYPE
   SYNTAX      Integer32
   MAX-ACCESS  read-only
   STATUS      current
   DESCRIPTION
      "Path: ethernet3.performance.ifInBandwidth.5min

       unit name = bps
       formula = 8 * ; 8 /"
   ::= {pr1645v2Lan3InBandwidthEntry 1677721600}


pr1645v2Lan3OutOctets OBJECT-TYPE
   SYNTAX      Counter64
   MAX-ACCESS  read-only
   STATUS      current
   DESCRIPTION
      "Path: ethernet3.performance.ifOutOctets
       Info: ifOutOctets

       64 bit unsigned wrappable counter."
   ::= {pr1645v2Lan3 115}


pr1645v2Lan3OutUcastPkts OBJECT-TYPE
   SYNTAX      Counter64
   MAX-ACCESS  read-only
   STATUS      current
   DESCRIPTION
      "Path: ethernet3.performance.ifOutUcastPkts
       Info: ifOutUcastPkts

       64 bit unsigned wrappable counter."
   ::= {pr1645v2Lan3 116}


pr1645v2Lan3OutNUcastPkts OBJECT-TYPE
   SYNTAX      Counter64
   MAX-ACCESS  read-only
   STATUS      current
   DESCRIPTION
      "Path: ethernet3.performance.ifOutNUcastPkts
       Info: ifOutNUcastPkts

       64 bit unsigned wrappable counter."
   ::= {pr1645v2Lan3 117}


pr1645v2Lan3OutBcastPkts OBJECT-TYPE
   SYNTAX      Counter64
   MAX-ACCESS  read-only
   STATUS      current
   DESCRIPTION
      "Path: ethernet3.performance.ifOutBcastPkts
       Info: ifOutBcastPkts

       64 bit unsigned wrappable counter."
   ::= {pr1645v2Lan3 217}


pr1645v2Lan3OutMcastPkts OBJECT-TYPE
   SYNTAX      Counter64
   MAX-ACCESS  read-only
   STATUS      current
   DESCRIPTION
      "Path: ethernet3.performance.ifOutMcastPkts
       Info: ifOutMcastPkts

       64 bit unsigned wrappable counter."
   ::= {pr1645v2Lan3 227}


pr1645v2Lan3OutDiscards OBJECT-TYPE
   SYNTAX      Counter64
   MAX-ACCESS  read-only
   STATUS      current
   DESCRIPTION
      "Path: ethernet3.performance.ifOutDiscards
       Info: ifOutDiscards

       64 bit unsigned wrappable counter."
   ::= {pr1645v2Lan3 118}


pr1645v2Lan3OutErrors OBJECT-TYPE
   SYNTAX      Counter64
   MAX-ACCESS  read-only
   STATUS      current
   DESCRIPTION
      "Path: ethernet3.performance.ifOutErrors
       Info: ifOutErrors

       64 bit unsigned wrappable counter."
   ::= {pr1645v2Lan3 119}


pr1645v2Lan3OutQLen OBJECT-TYPE
   SYNTAX      Gauge32
   MAX-ACCESS  read-only
   STATUS      current
   DESCRIPTION
      "Path: ethernet3.performance.ifOutQLen
       Info: ifOutQLen

       32 bit unsigned gauge value."
   ::= {pr1645v2Lan3 120}


pr1645v2Lan3OutDropEx OBJECT-TYPE
   SYNTAX      Counter64
   MAX-ACCESS  read-only
   STATUS      current
   DESCRIPTION
      "Path: ethernet3.performance.ifOutDropLevelExceeded
       Info: ifOutDiscards

       64 bit unsigned wrappable counter."
   ::= {pr1645v2Lan3 127}


pr1645v2Lan3OutDropNoArp OBJECT-TYPE
   SYNTAX      Counter64
   MAX-ACCESS  read-only
   STATUS      current
   DESCRIPTION
      "Path: ethernet3.performance.ifOutDiscardsNoArp
       Info: ifOutDiscards

       64 bit unsigned wrappable counter."
   ::= {pr1645v2Lan3 134}


pr1645v2Lan3OutDropFilter OBJECT-TYPE
   SYNTAX      Counter64
   MAX-ACCESS  read-only
   STATUS      current
   DESCRIPTION
      "Path: ethernet3.performance.ifOutDiscardsFilter
       Info: ifOutDiscards

       64 bit unsigned wrappable counter."
   ::= {pr1645v2Lan3 138}


pr1645v2Lan3OutQueues OBJECT IDENTIFIER ::= {pr1645v2Lan3 129}

pr1645v2Lan3OutQueuesSSCTable OBJECT-TYPE
   SYNTAX      SEQUENCE OF Pr1645v2Lan3OutQueuesEntry
   MAX-ACCESS  not-accessible
   STATUS      current
   DESCRIPTION
      "Queue Lengths"
   ::= {pr1645v2Lan3OutQueues 1}

pr1645v2Lan3OutQueuesEntry OBJECT-TYPE
   SYNTAX      Pr1645v2Lan3OutQueuesEntry
   MAX-ACCESS  not-accessible
   STATUS      current
   DESCRIPTION
      ""
   INDEX      { pr1645v2Lan3OutQueuesTableIx }
   ::= {pr1645v2Lan3OutQueuesSSCTable 1}

Pr1645v2Lan3OutQueuesEntry ::=
   SEQUENCE
      {
      pr1645v2Lan3OutQueuesTableIx
         TableIndex,
      pr1645v2Lan3OutQueuesName
         INTEGER,
      pr1645v2Lan3OutQueuesLength
         Integer32,
      pr1645v2Lan3OutQueuesOctetLength
         Integer32,
      pr1645v2Lan3OutQueuesRedLength
         Integer32,
      pr1645v2Lan3OutQueuesPacketsTotal
         Counter64,
      pr1645v2Lan3OutQueuesPacketsDirectTx
         Counter64,
      pr1645v2Lan3OutQueuesPacketsQueued
         Counter64,
      pr1645v2Lan3OutQueuesPacketsDropped
         Counter64,
      pr1645v2Lan3OutQueuesPacketsRedDropped
         Counter64,
      pr1645v2Lan3OutQueuesPacketsCirTx
         Counter64,
      pr1645v2Lan3OutQueuesPacketsEirTx
         Counter64,
      pr1645v2Lan3OutQueuesPacketsViolateTx
         Counter64,
      pr1645v2Lan3OutQueuesOctetsTotal
         Counter64,
      pr1645v2Lan3OutQueuesOctetsDirectTx
         Counter64,
      pr1645v2Lan3OutQueuesOctetsQueued
         Counter64,
      pr1645v2Lan3OutQueuesOctetsDropped
         Counter64,
      pr1645v2Lan3OutQueuesOctetsRedDropped
         Counter64,
      pr1645v2Lan3OutQueuesOctetsCirTx
         Counter64,
      pr1645v2Lan3OutQueuesOctetsEirTx
         Counter64,
      pr1645v2Lan3OutQueuesOctetsViolateTx
         Counter64,
      pr1645v2Lan3OutQueuesOctetsBandwidth15sec
         Integer32,
      pr1645v2Lan3OutQueuesOctetsBandwidth30sec
         Integer32,
      pr1645v2Lan3OutQueuesOctetsBandwidth1min
         Integer32,
      pr1645v2Lan3OutQueuesOctetsBandwidth2min
         Integer32,
      pr1645v2Lan3OutQueuesOctetsBandwidth5min
         Integer32
      }

pr1645v2Lan3OutQueuesTableIx OBJECT-TYPE
   SYNTAX      TableIndex
   MAX-ACCESS  not-accessible
   STATUS      current
   DESCRIPTION
      ""
   ::= {pr1645v2Lan3OutQueuesEntry 11}

pr1645v2Lan3OutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3OutQueuesEntry 16777216}

pr1645v2Lan3OutQueuesLength OBJECT-TYPE
   SYNTAX      Integer32
   MAX-ACCESS  read-only
   STATUS      current
   DESCRIPTION
      "Path: ethernet3.performance.ifOutPriorityQueues.length"
   ::= {pr1645v2Lan3OutQueuesEntry 33554432}

pr1645v2Lan3OutQueuesOctetLength OBJECT-TYPE
   SYNTAX      Integer32
   MAX-ACCESS  read-only
   STATUS      current
   DESCRIPTION
      "Path: ethernet3.performance.ifOutPriorityQueues.octetLength"
   ::= {pr1645v2Lan3OutQueuesEntry 150994944}

pr1645v2Lan3OutQueuesRedLength OBJECT-TYPE
   SYNTAX      Integer32
   MAX-ACCESS  read-only
   STATUS      current
   DESCRIPTION
      "Path: ethernet3.performance.ifOutPriorityQueues.redLength"
   ::= {pr1645v2Lan3OutQueuesEntry 134217728}

pr1645v2Lan3OutQueuesPacketsTotal OBJECT-TYPE
   SYNTAX      Counter64
   MAX-ACCESS  read-only
   STATUS      current
   DESCRIPTION
      "Path: ethernet3.performance.ifOutPriorityQueues.packets.total

       64 bit unsigned wrappable counter."
   ::= {pr1645v2Lan3OutQueuesEntry 50790400}

pr1645v2Lan3OutQueuesPacketsDirectTx OBJECT-TYPE
   SYNTAX      Counter64
   MAX-ACCESS  read-only
   STATUS      current
   DESCRIPTION
      "Path: ethernet3.performance.ifOutPriorityQueues.packets.directTx

       64 bit unsigned wrappable counter."
   ::= {pr1645v2Lan3OutQueuesEntry 50397184}

pr1645v2Lan3OutQueuesPacketsQueued OBJECT-TYPE
   SYNTAX      Counter64
   MAX-ACCESS  read-only
   STATUS      current
   DESCRIPTION
      "Path: ethernet3.performance.ifOutPriorityQueues.packets.queued

       64 bit unsigned wrappable counter."
   ::= {pr1645v2Lan3OutQueuesEntry 50462720}

pr1645v2Lan3OutQueuesPacketsDropped OBJECT-TYPE
   SYNTAX      Counter64
   MAX-ACCESS  read-only
   STATUS      current
   DESCRIPTION
      "Path: ethernet3.performance.ifOutPriorityQueues.packets.dropped

       64 bit unsigned wrappable counter."
   ::= {pr1645v2Lan3OutQueuesEntry 50528256}

pr1645v2Lan3OutQueuesPacketsRedDropped OBJECT-TYPE
   SYNTAX      Counter64
   MAX-ACCESS  read-only
   STATUS      current
   DESCRIPTION
      "Path: ethernet3.performance.ifOutPriorityQueues.packets.redDropped

       64 bit unsigned wrappable counter."
   ::= {pr1645v2Lan3OutQueuesEntry 50724864}

pr1645v2Lan3OutQueuesPacketsCirTx OBJECT-TYPE
   SYNTAX      Counter64
   MAX-ACCESS  read-only
   STATUS      current
   DESCRIPTION
      "Path: ethernet3.performance.ifOutPriorityQueues.packets.cirTx

       64 bit unsigned wrappable counter."
   ::= {pr1645v2Lan3OutQueuesEntry 50593792}

pr1645v2Lan3OutQueuesPacketsEirTx OBJECT-TYPE
   SYNTAX      Counter64
   MAX-ACCESS  read-only
   STATUS      current
   DESCRIPTION
      "Path: ethernet3.performance.ifOutPriorityQueues.packets.eirTx

       64 bit unsigned wrappable counter."
   ::= {pr1645v2Lan3OutQueuesEntry 50659328}

pr1645v2Lan3OutQueuesPacketsViolateTx OBJECT-TYPE
   SYNTAX      Counter64
   MAX-ACCESS  read-only
   STATUS      current
   DESCRIPTION
      "Path: ethernet3.performance.ifOutPriorityQueues.packets.violateTx

       64 bit unsigned wrappable counter."
   ::= {pr1645v2Lan3OutQueuesEntry 50855936}

pr1645v2Lan3OutQueuesOctetsTotal OBJECT-TYPE
   SYNTAX      Counter64
   MAX-ACCESS  read-only
   STATUS      current
   DESCRIPTION
      "Path: ethernet3.performance.ifOutPriorityQueues.octets.total

       64 bit unsigned wrappable counter."
   ::= {pr1645v2Lan3OutQueuesEntry 67567616}

pr1645v2Lan3OutQueuesOctetsDirectTx OBJECT-TYPE
   SYNTAX      Counter64
   MAX-ACCESS  read-only
   STATUS      current
   DESCRIPTION
      "Path: ethernet3.performance.ifOutPriorityQueues.octets.directTx

       64 bit unsigned wrappable counter."
   ::= {pr1645v2Lan3OutQueuesEntry 67174400}

pr1645v2Lan3OutQueuesOctetsQueued OBJECT-TYPE
   SYNTAX      Counter64
   MAX-ACCESS  read-only
   STATUS      current
   DESCRIPTION
      "Path: ethernet3.performance.ifOutPriorityQueues.octets.queued

       64 bit unsigned wrappable counter."
   ::= {pr1645v2Lan3OutQueuesEntry 67239936}

pr1645v2Lan3OutQueuesOctetsDropped OBJECT-TYPE
   SYNTAX      Counter64
   MAX-ACCESS  read-only
   STATUS      current
   DESCRIPTION
      "Path: ethernet3.performance.ifOutPriorityQueues.octets.dropped

       64 bit unsigned wrappable counter."
   ::= {pr1645v2Lan3OutQueuesEntry 67305472}

pr1645v2Lan3OutQueuesOctetsRedDropped OBJECT-TYPE
   SYNTAX      Counter64
   MAX-ACCESS  read-only
   STATUS      current
   DESCRIPTION
      "Path: ethernet3.performance.ifOutPriorityQueues.octets.redDropped

       64 bit unsigned wrappable counter."
   ::= {pr1645v2Lan3OutQueuesEntry 67502080}

pr1645v2Lan3OutQueuesOctetsCirTx OBJECT-TYPE
   SYNTAX      Counter64
   MAX-ACCESS  read-only
   STATUS      current
   DESCRIPTION
      "Path: ethernet3.performance.ifOutPriorityQueues.octets.cirTx

       64 bit unsigned wrappable counter."
   ::= {pr1645v2Lan3OutQueuesEntry 67371008}

pr1645v2Lan3OutQueuesOctetsEirTx OBJECT-TYPE
   SYNTAX      Counter64
   MAX-ACCESS  read-only
   STATUS      current
   DESCRIPTION
      "Path: ethernet3.performance.ifOutPriorityQueues.octets.eirTx

       64 bit unsigned wrappable counter."
   ::= {pr1645v2Lan3OutQueuesEntry 67436544}

pr1645v2Lan3OutQueuesOctetsViolateTx OBJECT-TYPE
   SYNTAX      Counter64
   MAX-ACCESS  read-only
   STATUS      current
   DESCRIPTION
      "Path: ethernet3.performance.ifOutPriorityQueues.octets.violateTx

       64 bit unsigned wrappable counter."
   ::= {pr1645v2Lan3OutQueuesEntry 67633152}

pr1645v2Lan3OutQueuesOctetsBandwidth15sec OBJECT-TYPE
   SYNTAX      Integer32
   MAX-ACCESS  read-only
   STATUS      current
   DESCRIPTION
      "Path: ethernet3.performance.ifOutPriorityQueues.octets.bandwidth.15sec

       unit name = bps
       formula = 8 * ; 8 /"
   ::= {pr1645v2Lan3OutQueuesEntry 70386944}

pr1645v2Lan3OutQueuesOctetsBandwidth30sec OBJECT-TYPE
   SYNTAX      Integer32
   MAX-ACCESS  read-only
   STATUS      current
   DESCRIPTION
      "Path: ethernet3.performance.ifOutPriorityQueues.octets.bandwidth.30sec

       unit name = bps
       formula = 8 * ; 8 /"
   ::= {pr1645v2Lan3OutQueuesEntry 70388224}

pr1645v2Lan3OutQueuesOctetsBandwidth1min OBJECT-TYPE
   SYNTAX      Integer32
   MAX-ACCESS  read-only
   STATUS      current
   DESCRIPTION
      "Path: ethernet3.performance.ifOutPriorityQueues.octets.bandwidth.1min

       unit name = bps
       formula = 8 * ; 8 /"
   ::= {pr1645v2Lan3OutQueuesEntry 70390784}

pr1645v2Lan3OutQueuesOctetsBandwidth2min OBJECT-TYPE
   SYNTAX      Integer32
   MAX-ACCESS  read-only
   STATUS      current
   DESCRIPTION
      "Path: ethernet3.performance.ifOutPriorityQueues.octets.bandwidth.2min

       unit name = bps
       formula = 8 * ; 8 /"
   ::= {pr1645v2Lan3OutQueuesEntry 70395904}

pr1645v2Lan3OutQueuesOctetsBandwidth5min OBJECT-TYPE
   SYNTAX      Integer32
   MAX-ACCESS  read-only
   STATUS      current
   DESCRIPTION
      "Path: ethernet3.performance.ifOutPriorityQueues.octets.bandwidth.5min

       unit name = bps
       formula = 8 * ; 8 /"
   ::= {pr1645v2Lan3OutQueuesEntry 70411264}

pr1645v2Lan3OutQueuesH2Performance OBJECT-TYPE
   SYNTAX      SEQUENCE OF Pr1645v2Lan3OutQueuesH2PerformanceEntry
   MAX-ACCESS  not-accessible
   STATUS      current
   DESCRIPTION
      ""
   ::= {pr1645v2Lan3OutQueues 83886080}

pr1645v2Lan3OutQueuesH2PerformanceEntry OBJECT-TYPE
   SYNTAX      Pr1645v2Lan3OutQueuesH2PerformanceEntry
   MAX-ACCESS  not-accessible
   STATUS      current
   DESCRIPTION
      ""
   INDEX      { pr1645v2Lan3OutQueuesTableIx,
                pr1645v2Lan3OutQueuesH2PerformanceTableIx }
   ::= {pr1645v2Lan3OutQueuesH2Performance 1}

Pr1645v2Lan3OutQueuesH2PerformanceEntry ::=
   SEQUENCE
      {
      pr1645v2Lan3OutQueuesH2PerformanceTableIx
         TableIndex,
      pr1645v2Lan3OutQueuesH2PerformanceSysUpTime
         TimeTicks,
      pr1645v2Lan3OutQueuesH2PerformanceTotPkts
         Counter64,
      pr1645v2Lan3OutQueuesH2PerformanceDirTxPkts
         Counter64,
      pr1645v2Lan3OutQueuesH2PerformanceQdPkts
         Counter64,
      pr1645v2Lan3OutQueuesH2PerformanceDropPkts
         Counter64,
      pr1645v2Lan3OutQueuesH2PerformanceRDropPkts
         Counter64,
      pr1645v2Lan3OutQueuesH2PerformanceCirTxPkts
         Counter64,
      pr1645v2Lan3OutQueuesH2PerformanceEirTxPkts
         Counter64,
      pr1645v2Lan3OutQueuesH2PerformanceViolTxPkts
         Counter64,
      pr1645v2Lan3OutQueuesH2PerformanceTotOcts
         Counter64,
      pr1645v2Lan3OutQueuesH2PerformanceDirTxOcts
         Counter64,
      pr1645v2Lan3OutQueuesH2PerformanceQdOcts
         Counter64,
      pr1645v2Lan3OutQueuesH2PerformanceDropOcts
         Counter64,
      pr1645v2Lan3OutQueuesH2PerformanceRDropOcts
         Counter64,
      pr1645v2Lan3OutQueuesH2PerformanceCirTxOcts
         Counter64,
      pr1645v2Lan3OutQueuesH2PerformanceEirTxOcts
         Counter64,
      pr1645v2Lan3OutQueuesH2PerformanceViolTxOcts
         Counter64,
      pr1645v2Lan3OutQueuesH2PerformanceBandwidth
         Integer32
      }

pr1645v2Lan3OutQueuesH2PerformanceTableIx OBJECT-TYPE
   SYNTAX      TableIndex
   MAX-ACCESS  not-accessible
   STATUS      current
   DESCRIPTION
      ""
   ::= {pr1645v2Lan3OutQueuesH2PerformanceEntry 11}

pr1645v2Lan3OutQueuesH2PerformanceSysUpTime OBJECT-TYPE
   SYNTAX      TimeTicks
   MAX-ACCESS  read-only
   STATUS      current
   DESCRIPTION
      "Path: ethernet3.performance.ifOutPriorityQueues.h2Performance.sysUpTime

       Time in centi-second."
   ::= {pr1645v2Lan3OutQueuesH2PerformanceEntry 16777216}

pr1645v2Lan3OutQueuesH2PerformanceTotPkts OBJECT-TYPE
   SYNTAX      Counter64
   MAX-ACCESS  read-only
   STATUS      current
   DESCRIPTION
      "Path: ethernet3.performance.ifOutPriorityQueues.h2Performance.totalPkts

       64 bit unsigned wrappable counter."
   ::= {pr1645v2Lan3OutQueuesH2PerformanceEntry 234881024}

pr1645v2Lan3OutQueuesH2PerformanceDirTxPkts OBJECT-TYPE
   SYNTAX      Counter64
   MAX-ACCESS  read-only
   STATUS      current
   DESCRIPTION
      "Path: ethernet3.performance.ifOutPriorityQueues.h2Performance.directTxPkts

       64 bit unsigned wrappable counter."
   ::= {pr1645v2Lan3OutQueuesH2PerformanceEntry 33554432}

pr1645v2Lan3OutQueuesH2PerformanceQdPkts OBJECT-TYPE
   SYNTAX      Counter64
   MAX-ACCESS  read-only
   STATUS      current
   DESCRIPTION
      "Path: ethernet3.performance.ifOutPriorityQueues.h2Performance.queuedPkts

       64 bit unsigned wrappable counter."
   ::= {pr1645v2Lan3OutQueuesH2PerformanceEntry 50331648}

pr1645v2Lan3OutQueuesH2PerformanceDropPkts OBJECT-TYPE
   SYNTAX      Counter64
   MAX-ACCESS  read-only
   STATUS      current
   DESCRIPTION
      "Path: ethernet3.performance.ifOutPriorityQueues.h2Performance.droppedPkts

       64 bit unsigned wrappable counter."
   ::= {pr1645v2Lan3OutQueuesH2PerformanceEntry 67108864}

pr1645v2Lan3OutQueuesH2PerformanceRDropPkts OBJECT-TYPE
   SYNTAX      Counter64
   MAX-ACCESS  read-only
   STATUS      current
   DESCRIPTION
      "Path: ethernet3.performance.ifOutPriorityQueues.h2Performance.redDroppedPkts

       64 bit unsigned wrappable counter."
   ::= {pr1645v2Lan3OutQueuesH2PerformanceEntry 201326592}

pr1645v2Lan3OutQueuesH2PerformanceCirTxPkts OBJECT-TYPE
   SYNTAX      Counter64
   MAX-ACCESS  read-only
   STATUS      current
   DESCRIPTION
      "Path: ethernet3.performance.ifOutPriorityQueues.h2Performance.cirTxPkts

       64 bit unsigned wrappable counter."
   ::= {pr1645v2Lan3OutQueuesH2PerformanceEntry 83886080}

pr1645v2Lan3OutQueuesH2PerformanceEirTxPkts OBJECT-TYPE
   SYNTAX      Counter64
   MAX-ACCESS  read-only
   STATUS      current
   DESCRIPTION
      "Path: ethernet3.performance.ifOutPriorityQueues.h2Performance.eirTxPkts

       64 bit unsigned wrappable counter."
   ::= {pr1645v2Lan3OutQueuesH2PerformanceEntry 100663296}

pr1645v2Lan3OutQueuesH2PerformanceViolTxPkts OBJECT-TYPE
   SYNTAX      Counter64
   MAX-ACCESS  read-only
   STATUS      current
   DESCRIPTION
      "Path: ethernet3.performance.ifOutPriorityQueues.h2Performance.violateTxPkts

       64 bit unsigned wrappable counter."
   ::= {pr1645v2Lan3OutQueuesH2PerformanceEntry 301989888}

pr1645v2Lan3OutQueuesH2PerformanceTotOcts OBJECT-TYPE
   SYNTAX      Counter64
   MAX-ACCESS  read-only
   STATUS      current
   DESCRIPTION
      "Path: ethernet3.performance.ifOutPriorityQueues.h2Performance.totalOctets

       64 bit unsigned wrappable counter."
   ::= {pr1645v2Lan3OutQueuesH2PerformanceEntry 251658240}

pr1645v2Lan3OutQueuesH2PerformanceDirTxOcts OBJECT-TYPE
   SYNTAX      Counter64
   MAX-ACCESS  read-only
   STATUS      current
   DESCRIPTION
      "Path: ethernet3.performance.ifOutPriorityQueues.h2Performance.directTxOctets

       64 bit unsigned wrappable counter."
   ::= {pr1645v2Lan3OutQueuesH2PerformanceEntry 117440512}

pr1645v2Lan3OutQueuesH2PerformanceQdOcts OBJECT-TYPE
   SYNTAX      Counter64
   MAX-ACCESS  read-only
   STATUS      current
   DESCRIPTION
      "Path: ethernet3.performance.ifOutPriorityQueues.h2Performance.queuedOctets

       64 bit unsigned wrappable counter."
   ::= {pr1645v2Lan3OutQueuesH2PerformanceEntry 134217728}

pr1645v2Lan3OutQueuesH2PerformanceDropOcts OBJECT-TYPE
   SYNTAX      Counter64
   MAX-ACCESS  read-only
   STATUS      current
   DESCRIPTION
      "Path: ethernet3.performance.ifOutPriorityQueues.h2Performance.droppedOctets

       64 bit unsigned wrappable counter."
   ::= {pr1645v2Lan3OutQueuesH2PerformanceEntry 150994944}

pr1645v2Lan3OutQueuesH2PerformanceRDropOcts OBJECT-TYPE
   SYNTAX      Counter64
   MAX-ACCESS  read-only
   STATUS      current
   DESCRIPTION
      "Path: ethernet3.performance.ifOutPriorityQueues.h2Performance.redDroppedOctets

       64 bit unsigned wrappable counter."
   ::= {pr1645v2Lan3OutQueuesH2PerformanceEntry 218103808}

pr1645v2Lan3OutQueuesH2PerformanceCirTxOcts OBJECT-TYPE
   SYNTAX      Counter64
   MAX-ACCESS  read-only
   STATUS      current
   DESCRIPTION
      "Path: ethernet3.performance.ifOutPriorityQueues.h2Performance.cirTxOctets

       64 bit unsigned wrappable counter."
   ::= {pr1645v2Lan3OutQueuesH2PerformanceEntry 167772160}

pr1645v2Lan3OutQueuesH2PerformanceEirTxOcts OBJECT-TYPE
   SYNTAX      Counter64
   MAX-ACCESS  read-only
   STATUS      current
   DESCRIPTION
      "Path: ethernet3.performance.ifOutPriorityQueues.h2Performance.eirTxOctets

       64 bit unsigned wrappable counter."
   ::= {pr1645v2Lan3OutQueuesH2PerformanceEntry 184549376}

pr1645v2Lan3OutQueuesH2PerformanceViolTxOcts OBJECT-TYPE
   SYNTAX      Counter64
   MAX-ACCESS  read-only
   STATUS      current
   DESCRIPTION
      "Path: ethernet3.performance.ifOutPriorityQueues.h2Performance.violateTxOctets

       64 bit unsigned wrappable counter."
   ::= {pr1645v2Lan3OutQueuesH2PerformanceEntry 318767104}

pr1645v2Lan3OutQueuesH2PerformanceBandwidth OBJECT-TYPE
   SYNTAX      Integer32
   MAX-ACCESS  read-only
   STATUS      current
   DESCRIPTION
      "Path: ethernet3.performance.ifOutPriorityQueues.h2Performance.bandwidth

       unit name = bps
       formula = 8 * ; 8 /"
   ::= {pr1645v2Lan3OutQueuesH2PerformanceEntry 268435456}

pr1645v2Lan3OutQueuesH24Performance OBJECT-TYPE
   SYNTAX      SEQUENCE OF Pr1645v2Lan3OutQueuesH24PerformanceEntry
   MAX-ACCESS  not-accessible
   STATUS      current
   DESCRIPTION
      ""
   ::= {pr1645v2Lan3OutQueues 100663296}

pr1645v2Lan3OutQueuesH24PerformanceEntry OBJECT-TYPE
   SYNTAX      Pr1645v2Lan3OutQueuesH24PerformanceEntry
   MAX-ACCESS  not-accessible
   STATUS      current
   DESCRIPTION
      ""
   INDEX      { pr1645v2Lan3OutQueuesTableIx,
                pr1645v2Lan3OutQueuesH24PerformanceTableIx }
   ::= {pr1645v2Lan3OutQueuesH24Performance 1}

Pr1645v2Lan3OutQueuesH24PerformanceEntry ::=
   SEQUENCE
      {
      pr1645v2Lan3OutQueuesH24PerformanceTableIx
         TableIndex,
      pr1645v2Lan3OutQueuesH24PerformanceSysUpTime
         TimeTicks,
      pr1645v2Lan3OutQueuesH24PerformanceTotPkts
         Counter64,
      pr1645v2Lan3OutQueuesH24PerformanceDirTxPkts
         Counter64,
      pr1645v2Lan3OutQueuesH24PerformanceQdPkts
         Counter64,
      pr1645v2Lan3OutQueuesH24PerformanceDropPkts
         Counter64,
      pr1645v2Lan3OutQueuesH24PerformanceRDropPkts
         Counter64,
      pr1645v2Lan3OutQueuesH24PerformanceCirTxPkts
         Counter64,
      pr1645v2Lan3OutQueuesH24PerformanceEirTxPkts
         Counter64,
      pr1645v2Lan3OutQueuesH24PerformanceViolTxPkts
         Counter64,
      pr1645v2Lan3OutQueuesH24PerformanceTotOcts
         Counter64,
      pr1645v2Lan3OutQueuesH24PerformanceDirTxOcts
         Counter64,
      pr1645v2Lan3OutQueuesH24PerformanceQdOcts
         Counter64,
      pr1645v2Lan3OutQueuesH24PerformanceDropOcts
         Counter64,
      pr1645v2Lan3OutQueuesH24PerformanceRDropOcts
         Counter64,
      pr1645v2Lan3OutQueuesH24PerformanceCirTxOcts
         Counter64,
      pr1645v2Lan3OutQueuesH24PerformanceEirTxOcts
         Counter64,
      pr1645v2Lan3OutQueuesH24PerformanceViolTxOcts
         Counter64,
      pr1645v2Lan3OutQueuesH24PerformanceBandwidth
         Integer32
      }

pr1645v2Lan3OutQueuesH24PerformanceTableIx OBJECT-TYPE
   SYNTAX      TableIndex
   MAX-ACCESS  not-accessible
   STATUS      current
   DESCRIPTION
      ""
   ::= {pr1645v2Lan3OutQueuesH24PerformanceEntry 11}

pr1645v2Lan3OutQueuesH24PerformanceSysUpTime OBJECT-TYPE
   SYNTAX      TimeTicks
   MAX-ACCESS  read-only
   STATUS      current
   DESCRIPTION
      "Path: ethernet3.performance.ifOutPriorityQueues.h24Performance.sysUpTime

       Time in centi-second."
   ::= {pr1645v2Lan3OutQueuesH24PerformanceEntry 16777216}

pr1645v2Lan3OutQueuesH24PerformanceTotPkts OBJECT-TYPE
   SYNTAX      Counter64
   MAX-ACCESS  read-only
   STATUS      current
   DESCRIPTION
      "Path: ethernet3.performance.ifOutPriorityQueues.h24Performance.totalPkts

       64 bit unsigned wrappable counter."
   ::= {pr1645v2Lan3OutQueuesH24PerformanceEntry 234881024}

pr1645v2Lan3OutQueuesH24PerformanceDirTxPkts OBJECT-TYPE
   SYNTAX      Counter64
   MAX-ACCESS  read-only
   STATUS      current
   DESCRIPTION
      "Path: ethernet3.performance.ifOutPriorityQueues.h24Performance.directTxPkts

       64 bit unsigned wrappable counter."
   ::= {pr1645v2Lan3OutQueuesH24PerformanceEntry 33554432}

pr1645v2Lan3OutQueuesH24PerformanceQdPkts OBJECT-TYPE
   SYNTAX      Counter64
   MAX-ACCESS  read-only
   STATUS      current
   DESCRIPTION
      "Path: ethernet3.performance.ifOutPriorityQueues.h24Performance.queuedPkts

       64 bit unsigned wrappable counter."
   ::= {pr1645v2Lan3OutQueuesH24PerformanceEntry 50331648}

pr1645v2Lan3OutQueuesH24PerformanceDropPkts OBJECT-TYPE
   SYNTAX      Counter64
   MAX-ACCESS  read-only
   STATUS      current
   DESCRIPTION
      "Path: ethernet3.performance.ifOutPriorityQueues.h24Performance.droppedPkts

       64 bit unsigned wrappable counter."
   ::= {pr1645v2Lan3OutQueuesH24PerformanceEntry 67108864}

pr1645v2Lan3OutQueuesH24PerformanceRDropPkts OBJECT-TYPE
   SYNTAX      Counter64
   MAX-ACCESS  read-only
   STATUS      current
   DESCRIPTION
      "Path: ethernet3.performance.ifOutPriorityQueues.h24Performance.redDroppedPkts

       64 bit unsigned wrappable counter."
   ::= {pr1645v2Lan3OutQueuesH24PerformanceEntry 201326592}

pr1645v2Lan3OutQueuesH24PerformanceCirTxPkts OBJECT-TYPE
   SYNTAX      Counter64
   MAX-ACCESS  read-only
   STATUS      current
   DESCRIPTION
      "Path: ethernet3.performance.ifOutPriorityQueues.h24Performance.cirTxPkts

       64 bit unsigned wrappable counter."
   ::= {pr1645v2Lan3OutQueuesH24PerformanceEntry 83886080}

pr1645v2Lan3OutQueuesH24PerformanceEirTxPkts OBJECT-TYPE
   SYNTAX      Counter64
   MAX-ACCESS  read-only
   STATUS      current
   DESCRIPTION
      "Path: ethernet3.performance.ifOutPriorityQueues.h24Performance.eirTxPkts

       64 bit unsigned wrappable counter."
   ::= {pr1645v2Lan3OutQueuesH24PerformanceEntry 100663296}

pr1645v2Lan3OutQueuesH24PerformanceViolTxPkts OBJECT-TYPE
   SYNTAX      Counter64
   MAX-ACCESS  read-only
   STATUS      current
   DESCRIPTION
      "Path: ethernet3.performance.ifOutPriorityQueues.h24Performance.violateTxPkts

       64 bit unsigned wrappable counter."
   ::= {pr1645v2Lan3OutQueuesH24PerformanceEntry 301989888}

pr1645v2Lan3OutQueuesH24PerformanceTotOcts OBJECT-TYPE
   SYNTAX      Counter64
   MAX-ACCESS  read-only
   STATUS      current
   DESCRIPTION
      "Path: ethernet3.performance.ifOutPriorityQueues.h24Performance.totalOctets

       64 bit unsigned wrappable counter."
   ::= {pr1645v2Lan3OutQueuesH24PerformanceEntry 251658240}

pr1645v2Lan3OutQueuesH24PerformanceDirTxOcts OBJECT-TYPE
   SYNTAX      Counter64
   MAX-ACCESS  read-only
   STATUS      current
   DESCRIPTION
      "Path: ethernet3.performance.ifOutPriorityQueues.h24Performance.directTxOctets

       64 bit unsigned wrappable counter."
   ::= {pr1645v2Lan3OutQueuesH24PerformanceEntry 117440512}

pr1645v2Lan3OutQueuesH24PerformanceQdOcts OBJECT-TYPE
   SYNTAX      Counter64
   MAX-ACCESS  read-only
   STATUS      current
   DESCRIPTION
      "Path: ethernet3.performance.ifOutPriorityQueues.h24Performance.queuedOctets

       64 bit unsigned wrappable counter."
   ::= {pr1645v2Lan3OutQueuesH24PerformanceEntry 134217728}

pr1645v2Lan3OutQueuesH24PerformanceDropOcts OBJECT-TYPE
   SYNTAX      Counter64
   MAX-ACCESS  read-only
   STATUS      current
   DESCRIPTION
      "Path: ethernet3.performance.ifOutPriorityQueues.h24Performance.droppedOctets

       64 bit unsigned wrappable counter."
   ::= {pr1645v2Lan3OutQueuesH24PerformanceEntry 150994944}

pr1645v2Lan3OutQueuesH24PerformanceRDropOcts OBJECT-TYPE
   SYNTAX      Counter64
   MAX-ACCESS  read-only
   STATUS      current
   DESCRIPTION
      "Path: ethernet3.performance.ifOutPriorityQueues.h24Performance.redDroppedOctets

       64 bit unsigned wrappable counter."
   ::= {pr1645v2Lan3OutQueuesH24PerformanceEntry 218103808}

pr1645v2Lan3OutQueuesH24PerformanceCirTxOcts OBJECT-TYPE
   SYNTAX      Counter64
   MAX-ACCESS  read-only
   STATUS      current
   DESCRIPTION
      "Path: ethernet3.performance.ifOutPriorityQueues.h24Performance.cirTxOctets

       64 bit unsigned wrappable counter."
   ::= {pr1645v2Lan3OutQueuesH24PerformanceEntry 167772160}

pr1645v2Lan3OutQueuesH24PerformanceEirTxOcts OBJECT-TYPE
   SYNTAX      Counter64
   MAX-ACCESS  read-only
   STATUS      current
   DESCRIPTION
      "Path: ethernet3.performance.ifOutPriorityQueues.h24Performance.eirTxOctets

       64 bit unsigned wrappable counter."
   ::= {pr1645v2Lan3OutQueuesH24PerformanceEntry 184549376}

pr1645v2Lan3OutQueuesH24PerformanceViolTxOcts OBJECT-TYPE
   SYNTAX      Counter64
   MAX-ACCESS  read-only
   STATUS      current
   DESCRIPTION
      "Path: ethernet3.performance.ifOutPriorityQueues.h24Performance.violateTxOctets

       64 bit unsigned wrappable counter."
   ::= {pr1645v2Lan3OutQueuesH24PerformanceEntry 318767104}

pr1645v2Lan3OutQueuesH24PerformanceBandwidth OBJECT-TYPE
   SYNTAX      Integer32
   MAX-ACCESS  read-only
   STATUS      current
   DESCRIPTION
      "Path: ethernet3.performance.ifOutPriorityQueues.h24Performance.bandwidth

       unit name = bps
       formula = 8 * ; 8 /"
   ::= {pr1645v2Lan3OutQueuesH24PerformanceEntry 268435456}

pr1645v2Lan3OutQueuesD7Performance OBJECT-TYPE
   SYNTAX      SEQUENCE OF Pr1645v2Lan3OutQueuesD7PerformanceEntry
   MAX-ACCESS  not-accessible
   STATUS      current
   DESCRIPTION
      ""
   ::= {pr1645v2Lan3OutQueues 117440512}

pr1645v2Lan3OutQueuesD7PerformanceEntry OBJECT-TYPE
   SYNTAX      Pr1645v2Lan3OutQueuesD7PerformanceEntry
   MAX-ACCESS  not-accessible
   STATUS      current
   DESCRIPTION
      ""
   INDEX      { pr1645v2Lan3OutQueuesTableIx,
                pr1645v2Lan3OutQueuesD7PerformanceTableIx }
   ::= {pr1645v2Lan3OutQueuesD7Performance 1}

Pr1645v2Lan3OutQueuesD7PerformanceEntry ::=
   SEQUENCE
      {
      pr1645v2Lan3OutQueuesD7PerformanceTableIx
         TableIndex,
      pr1645v2Lan3OutQueuesD7PerformanceSysUpTime
         TimeTicks,
      pr1645v2Lan3OutQueuesD7PerformanceTotPkts
         Counter64,
      pr1645v2Lan3OutQueuesD7PerformanceDirTxPkts
         Counter64,
      pr1645v2Lan3OutQueuesD7PerformanceQdPkts
         Counter64,
      pr1645v2Lan3OutQueuesD7PerformanceDropPkts
         Counter64,
      pr1645v2Lan3OutQueuesD7PerformanceRDropPkts
         Counter64,
      pr1645v2Lan3OutQueuesD7PerformanceCirTxPkts
         Counter64,
      pr1645v2Lan3OutQueuesD7PerformanceEirTxPkts
         Counter64,
      pr1645v2Lan3OutQueuesD7PerformanceViolTxPkts
         Counter64,
      pr1645v2Lan3OutQueuesD7PerformanceTotOcts
         Counter64,
      pr1645v2Lan3OutQueuesD7PerformanceDirTxOcts
         Counter64,
      pr1645v2Lan3OutQueuesD7PerformanceQdOcts
         Counter64,
      pr1645v2Lan3OutQueuesD7PerformanceDropOcts
         Counter64,
      pr1645v2Lan3OutQueuesD7PerformanceRDropOcts
         Counter64,
      pr1645v2Lan3OutQueuesD7PerformanceCirTxOcts
         Counter64,
      pr1645v2Lan3OutQueuesD7PerformanceEirTxOcts
         Counter64,
      pr1645v2Lan3OutQueuesD7PerformanceViolTxOcts
         Counter64,
      pr1645v2Lan3OutQueuesD7PerformanceBandwidth
         Integer32
      }

pr1645v2Lan3OutQueuesD7PerformanceTableIx OBJECT-TYPE
   SYNTAX      TableIndex
   MAX-ACCESS  not-accessible
   STATUS      current
   DESCRIPTION
      ""
   ::= {pr1645v2Lan3OutQueuesD7PerformanceEntry 11}

pr1645v2Lan3OutQueuesD7PerformanceSysUpTime OBJECT-TYPE
   SYNTAX      TimeTicks
   MAX-ACCESS  read-only
   STATUS      current
   DESCRIPTION
      "Path: ethernet3.performance.ifOutPriorityQueues.d7Performance.sysUpTime

       Time in centi-second."
   ::= {pr1645v2Lan3OutQueuesD7PerformanceEntry 16777216}

pr1645v2Lan3OutQueuesD7PerformanceTotPkts OBJECT-TYPE
   SYNTAX      Counter64
   MAX-ACCESS  read-only
   STATUS      current
   DESCRIPTION
      "Path: ethernet3.performance.ifOutPriorityQueues.d7Performance.totalPkts

       64 bit unsigned wrappable counter."
   ::= {pr1645v2Lan3OutQueuesD7PerformanceEntry 234881024}

pr1645v2Lan3OutQueuesD7PerformanceDirTxPkts OBJECT-TYPE
   SYNTAX      Counter64
   MAX-ACCESS  read-only
   STATUS      current
   DESCRIPTION
      "Path: ethernet3.performance.ifOutPriorityQueues.d7Performance.directTxPkts

       64 bit unsigned wrappable counter."
   ::= {pr1645v2Lan3OutQueuesD7PerformanceEntry 33554432}

pr1645v2Lan3OutQueuesD7PerformanceQdPkts OBJECT-TYPE
   SYNTAX      Counter64
   MAX-ACCESS  read-only
   STATUS      current
   DESCRIPTION
      "Path: ethernet3.performance.ifOutPriorityQueues.d7Performance.queuedPkts

       64 bit unsigned wrappable counter."
   ::= {pr1645v2Lan3OutQueuesD7PerformanceEntry 50331648}

pr1645v2Lan3OutQueuesD7PerformanceDropPkts OBJECT-TYPE
   SYNTAX      Counter64
   MAX-ACCESS  read-only
   STATUS      current
   DESCRIPTION
      "Path: ethernet3.performance.ifOutPriorityQueues.d7Performance.droppedPkts

       64 bit unsigned wrappable counter."
   ::= {pr1645v2Lan3OutQueuesD7PerformanceEntry 67108864}

pr1645v2Lan3OutQueuesD7PerformanceRDropPkts OBJECT-TYPE
   SYNTAX      Counter64
   MAX-ACCESS  read-only
   STATUS      current
   DESCRIPTION
      "Path: ethernet3.performance.ifOutPriorityQueues.d7Performance.redDroppedPkts

       64 bit unsigned wrappable counter."
   ::= {pr1645v2Lan3OutQueuesD7PerformanceEntry 201326592}

pr1645v2Lan3OutQueuesD7PerformanceCirTxPkts OBJECT-TYPE
   SYNTAX      Counter64
   MAX-ACCESS  read-only
   STATUS      current
   DESCRIPTION
      "Path: ethernet3.performance.ifOutPriorityQueues.d7Performance.cirTxPkts

       64 bit unsigned wrappable counter."
   ::= {pr1645v2Lan3OutQueuesD7PerformanceEntry 83886080}

pr1645v2Lan3OutQueuesD7PerformanceEirTxPkts OBJECT-TYPE
   SYNTAX      Counter64
   MAX-ACCESS  read-only
   STATUS      current
   DESCRIPTION
      "Path: ethernet3.performance.ifOutPriorityQueues.d7Performance.eirTxPkts

       64 bit unsigned wrappable counter."
   ::= {pr1645v2Lan3OutQueuesD7PerformanceEntry 100663296}

pr1645v2Lan3OutQueuesD7PerformanceViolTxPkts OBJECT-TYPE
   SYNTAX      Counter64
   MAX-ACCESS  read-only
   STATUS      current
   DESCRIPTION
      "Path: ethernet3.performance.ifOutPriorityQueues.d7Performance.violateTxPkts

       64 bit unsigned wrappable counter."
   ::= {pr1645v2Lan3OutQueuesD7PerformanceEntry 301989888}

pr1645v2Lan3OutQueuesD7PerformanceTotOcts OBJECT-TYPE
   SYNTAX      Counter64
   MAX-ACCESS  read-only
   STATUS      current
   DESCRIPTION
      "Path: ethernet3.performance.ifOutPriorityQueues.d7Performance.totalOctets

       64 bit unsigned wrappable counter."
   ::= {pr1645v2Lan3OutQueuesD7PerformanceEntry 251658240}

pr1645v2Lan3OutQueuesD7PerformanceDirTxOcts OBJECT-TYPE
   SYNTAX      Counter64
   MAX-ACCESS  read-only
   STATUS      current
   DESCRIPTION
      "Path: ethernet3.performance.ifOutPriorityQueues.d7Performance.directTxOctets

       64 bit unsigned wrappable counter."
   ::= {pr1645v2Lan3OutQueuesD7PerformanceEntry 117440512}

pr1645v2Lan3OutQueuesD7PerformanceQdOcts OBJECT-TYPE
   SYNTAX      Counter64
   MAX-ACCESS  read-only
   STATUS      current
   DESCRIPTION
      "Path: ethernet3.performance.ifOutPriorityQueues.d7Performance.queuedOctets

       64 bit unsigned wrappable counter."
   ::= {pr1645v2Lan3OutQueuesD7PerformanceEntry 134217728}

pr1645v2Lan3OutQueuesD7PerformanceDropOcts OBJECT-TYPE
   SYNTAX      Counter64
   MAX-ACCESS  read-only
   STATUS      current
   DESCRIPTION
      "Path: ethernet3.performance.ifOutPriorityQueues.d7Performance.droppedOctets

       64 bit unsigned wrappable counter."
   ::= {pr1645v2Lan3OutQueuesD7PerformanceEntry 150994944}

pr1645v2Lan3OutQueuesD7PerformanceRDropOcts OBJECT-TYPE
   SYNTAX      Counter64
   MAX-ACCESS  read-only
   STATUS      current
   DESCRIPTION
      "Path: ethernet3.performance.ifOutPriorityQueues.d7Performance.redDroppedOctets

       64 bit unsigned wrappable counter."
   ::= {pr1645v2Lan3OutQueuesD7PerformanceEntry 218103808}

pr1645v2Lan3OutQueuesD7PerformanceCirTxOcts OBJECT-TYPE
   SYNTAX      Counter64
   MAX-ACCESS  read-only
   STATUS      current
   DESCRIPTION
      "Path: ethernet3.performance.ifOutPriorityQueues.d7Performance.cirTxOctets

       64 bit unsigned wrappable counter."
   ::= {pr1645v2Lan3OutQueuesD7PerformanceEntry 167772160}

pr1645v2Lan3OutQueuesD7PerformanceEirTxOcts OBJECT-TYPE
   SYNTAX      Counter64
   MAX-ACCESS  read-only
   STATUS      current
   DESCRIPTION
      "Path: ethernet3.performance.ifOutPriorityQueues.d7Performance.eirTxOctets

       64 bit unsigned wrappable counter."
   ::= {pr1645v2Lan3OutQueuesD7PerformanceEntry 184549376}

pr1645v2Lan3OutQueuesD7PerformanceViolTxOcts OBJECT-TYPE
   SYNTAX      Counter64
   MAX-ACCESS  read-only
   STATUS      current
   DESCRIPTION
      "Path: ethernet3.performance.ifOutPriorityQueues.d7Performance.violateTxOctets

       64 bit unsigned wrappable counter."
   ::= {pr1645v2Lan3OutQueuesD7PerformanceEntry 318767104}

pr1645v2Lan3OutQueuesD7PerformanceBandwidth OBJECT-TYPE
   SYNTAX      Integer32
   MAX-ACCESS  read-only
   STATUS      current
   DESCRIPTION
      "Path: ethernet3.performance.ifOutPriorityQueues.d7Performance.bandwidth

       unit name = bps
       formula = 8 * ; 8 /"
   ::= {pr1645v2Lan3OutQueuesD7PerformanceEntry 268435456}


pr1645v2Lan3OutBandwidth OBJECT IDENTIFIER ::= {pr1645v2Lan3 182}

pr1645v2Lan3OutBandwidthSSC OBJECT IDENTIFIER ::= {pr1645v2Lan3OutBandwidth 1}

pr1645v2Lan3OutBandwidthEntry OBJECT IDENTIFIER ::= {pr1645v2Lan3OutBandwidthSSC 1}

pr1645v2Lan3OutBandwidth15sec OBJECT-TYPE
   SYNTAX      Integer32
   MAX-ACCESS  read-only
   STATUS      current
   DESCRIPTION
      "Path: ethernet3.performance.ifOutBandwidth.15sec

       unit name = bps
       formula = 8 * ; 8 /"
   ::= {pr1645v2Lan3OutBandwidthEntry 83886080}

pr1645v2Lan3OutBandwidth30sec OBJECT-TYPE
   SYNTAX      Integer32
   MAX-ACCESS  read-only
   STATUS      current
   DESCRIPTION
      "Path: ethernet3.performance.ifOutBandwidth.30sec

       unit name = bps
       formula = 8 * ; 8 /"
   ::= {pr1645v2Lan3OutBandwidthEntry 167772160}

pr1645v2Lan3OutBandwidth1min OBJECT-TYPE
   SYNTAX      Integer32
   MAX-ACCESS  read-only
   STATUS      current
   DESCRIPTION
      "Path: ethernet3.performance.ifOutBandwidth.1min

       unit name = bps
       formula = 8 * ; 8 /"
   ::= {pr1645v2Lan3OutBandwidthEntry 335544320}

pr1645v2Lan3OutBandwidth2min OBJECT-TYPE
   SYNTAX      Integer32
   MAX-ACCESS  read-only
   STATUS      current
   DESCRIPTION
      "Path: ethernet3.performance.ifOutBandwidth.2min

       unit name = bps
       formula = 8 * ; 8 /"
   ::= {pr1645v2Lan3OutBandwidthEntry 671088640}

pr1645v2Lan3OutBandwidth5min OBJECT-TYPE
   SYNTAX      Integer32
   MAX-ACCESS  read-only
   STATUS      current
   DESCRIPTION
      "Path: ethernet3.performance.ifOutBandwidth.5min

       unit name = bps
       formula = 8 * ; 8 /"
   ::= {pr1645v2Lan3OutBandwidthEntry 1677721600}


pr1645v2Lan3InP OBJECT IDENTIFIER ::= {pr1645v2Lan3 307}

pr1645v2Lan3InPSSCTable OBJECT-TYPE
   SYNTAX      SEQUENCE OF Pr1645v2Lan3InPEntry
   MAX-ACCESS  not-accessible
   STATUS      current
   DESCRIPTION
      "h2IfInPerformance"
   ::= {pr1645v2Lan3InP 1}

pr1645v2Lan3InPEntry OBJECT-TYPE
   SYNTAX      Pr1645v2Lan3InPEntry
   MAX-ACCESS  not-accessible
   STATUS      current
   DESCRIPTION
      ""
   INDEX      { pr1645v2Lan3InPTableIx }
   ::= {pr1645v2Lan3InPSSCTable 1}

Pr1645v2Lan3InPEntry ::=
   SEQUENCE
      {
      pr1645v2Lan3InPTableIx
         TableIndex,
      pr1645v2Lan3InPSysUpTime
         TimeTicks,
      pr1645v2Lan3InPIfUpTime
         TimeTicks,
      pr1645v2Lan3InPIfStatChanges
         Counter32,
      pr1645v2Lan3InPIfInOctets
         Counter64,
      pr1645v2Lan3InPIfInUCPkts
         Counter64,
      pr1645v2Lan3InPIfInNUCPkts
         Counter64,
      pr1645v2Lan3InPIfInBCPkts
         Counter64,
      pr1645v2Lan3InPIfInMCPkts
         Counter64,
      pr1645v2Lan3InPIfInDiscards
         Counter64,
      pr1645v2Lan3InPIfInErrors
         Counter64,
      pr1645v2Lan3InPIfInUnkwn
         Counter64,
      pr1645v2Lan3InPInDropEx
         Counter64,
      pr1645v2Lan3InPInDropNoMac
         Counter64,
      pr1645v2Lan3InPInDropNUCast
         Counter64,
      pr1645v2Lan3InPInDropFilter
         Counter64,
      pr1645v2Lan3InPIfInBandwidth
         Integer32,
      pr1645v2Lan3InPIfOutOctets
         Counter64,
      pr1645v2Lan3InPIfOutUCPkts
         Counter64,
      pr1645v2Lan3InPIfOutNUCPkts
         Counter64,
      pr1645v2Lan3InPIfOutBCPkts
         Counter64,
      pr1645v2Lan3InPIfOutMCPkts
         Counter64,
      pr1645v2Lan3InPIfOutDiscards
         Counter64,
      pr1645v2Lan3InPIfOutErrors
         Counter64,
      pr1645v2Lan3InPOutDropEx
         Counter64,
      pr1645v2Lan3InPOutDropNoArp
         Counter64,
      pr1645v2Lan3InPOutDropFilter
         Counter64,
      pr1645v2Lan3InPIfOutBandwidth
         Integer32,
      pr1645v2Lan3InPIfErrSec
         Counter32
      }

pr1645v2Lan3InPTableIx OBJECT-TYPE
   SYNTAX      TableIndex
   MAX-ACCESS  not-accessible
   STATUS      current
   DESCRIPTION
      ""
   ::= {pr1645v2Lan3InPEntry 11}

pr1645v2Lan3InPSysUpTime OBJECT-TYPE
   SYNTAX      TimeTicks
   MAX-ACCESS  read-only
   STATUS      current
   DESCRIPTION
      "Path: ethernet3.performance.h2Performance.sysUpTime

       Time in centi-second."
   ::= {pr1645v2Lan3InPEntry 16777216}

pr1645v2Lan3InPIfUpTime OBJECT-TYPE
   SYNTAX      TimeTicks
   MAX-ACCESS  read-only
   STATUS      current
   DESCRIPTION
      "Path: ethernet3.performance.h2Performance.ifUpTime

       Time in centi-second."
   ::= {pr1645v2Lan3InPEntry 33554432}

pr1645v2Lan3InPIfStatChanges OBJECT-TYPE
   SYNTAX      Counter32
   MAX-ACCESS  read-only
   STATUS      current
   DESCRIPTION
      "Path: ethernet3.performance.h2Performance.ifStatusChanges

       32 bit unsigned wrappable counter."
   ::= {pr1645v2Lan3InPEntry 50331648}

pr1645v2Lan3InPIfInOctets OBJECT-TYPE
   SYNTAX      Counter64
   MAX-ACCESS  read-only
   STATUS      current
   DESCRIPTION
      "Path: ethernet3.performance.h2Performance.ifInOctets

       64 bit unsigned wrappable counter."
   ::= {pr1645v2Lan3InPEntry 67108864}

pr1645v2Lan3InPIfInUCPkts OBJECT-TYPE
   SYNTAX      Counter64
   MAX-ACCESS  read-only
   STATUS      current
   DESCRIPTION
      "Path: ethernet3.performance.h2Performance.ifInUcastPkts

       64 bit unsigned wrappable counter."
   ::= {pr1645v2Lan3InPEntry 83886080}

pr1645v2Lan3InPIfInNUCPkts OBJECT-TYPE
   SYNTAX      Counter64
   MAX-ACCESS  read-only
   STATUS      current
   DESCRIPTION
      "Path: ethernet3.performance.h2Performance.ifInNUcastPkts

       64 bit unsigned wrappable counter."
   ::= {pr1645v2Lan3InPEntry 100663296}

pr1645v2Lan3InPIfInBCPkts OBJECT-TYPE
   SYNTAX      Counter64
   MAX-ACCESS  read-only
   STATUS      current
   DESCRIPTION
      "Path: ethernet3.performance.h2Performance.ifInBcastPkts

       64 bit unsigned wrappable counter."
   ::= {pr1645v2Lan3InPEntry 419430400}

pr1645v2Lan3InPIfInMCPkts OBJECT-TYPE
   SYNTAX      Counter64
   MAX-ACCESS  read-only
   STATUS      current
   DESCRIPTION
      "Path: ethernet3.performance.h2Performance.ifInMcastPkts

       64 bit unsigned wrappable counter."
   ::= {pr1645v2Lan3InPEntry 436207616}

pr1645v2Lan3InPIfInDiscards OBJECT-TYPE
   SYNTAX      Counter64
   MAX-ACCESS  read-only
   STATUS      current
   DESCRIPTION
      "Path: ethernet3.performance.h2Performance.ifInDiscards

       64 bit unsigned wrappable counter."
   ::= {pr1645v2Lan3InPEntry 117440512}

pr1645v2Lan3InPIfInErrors OBJECT-TYPE
   SYNTAX      Counter64
   MAX-ACCESS  read-only
   STATUS      current
   DESCRIPTION
      "Path: ethernet3.performance.h2Performance.ifInErrors

       64 bit unsigned wrappable counter."
   ::= {pr1645v2Lan3InPEntry 134217728}

pr1645v2Lan3InPIfInUnkwn OBJECT-TYPE
   SYNTAX      Counter64
   MAX-ACCESS  read-only
   STATUS      current
   DESCRIPTION
      "Path: ethernet3.performance.h2Performance.ifInUnknownProtos

       64 bit unsigned wrappable counter."
   ::= {pr1645v2Lan3InPEntry 150994944}

pr1645v2Lan3InPInDropEx OBJECT-TYPE
   SYNTAX      Counter64
   MAX-ACCESS  read-only
   STATUS      current
   DESCRIPTION
      "Path: ethernet3.performance.h2Performance.ifInDropLevelExceeded

       64 bit unsigned wrappable counter."
   ::= {pr1645v2Lan3InPEntry 335544320}

pr1645v2Lan3InPInDropNoMac OBJECT-TYPE
   SYNTAX      Counter64
   MAX-ACCESS  read-only
   STATUS      current
   DESCRIPTION
      "Path: ethernet3.performance.h2Performance.fInDiscardsNoMacFit

       64 bit unsigned wrappable counter."
   ::= {pr1645v2Lan3InPEntry 301989888}

pr1645v2Lan3InPInDropNUCast OBJECT-TYPE
   SYNTAX      Counter64
   MAX-ACCESS  read-only
   STATUS      current
   DESCRIPTION
      "Path: ethernet3.performance.h2Performance.fInDiscardsNUCast

       64 bit unsigned wrappable counter."
   ::= {pr1645v2Lan3InPEntry 318767104}

pr1645v2Lan3InPInDropFilter OBJECT-TYPE
   SYNTAX      Counter64
   MAX-ACCESS  read-only
   STATUS      current
   DESCRIPTION
      "Path: ethernet3.performance.h2Performance.fInDiscardsFilter

       64 bit unsigned wrappable counter."
   ::= {pr1645v2Lan3InPEntry 385875968}

pr1645v2Lan3InPIfInBandwidth OBJECT-TYPE
   SYNTAX      Integer32
   MAX-ACCESS  read-only
   STATUS      current
   DESCRIPTION
      "Path: ethernet3.performance.h2Performance.ifInBandwidth

       unit name = bps
       formula = 8 * ; 8 /"
   ::= {pr1645v2Lan3InPEntry 268435456}

pr1645v2Lan3InPIfOutOctets OBJECT-TYPE
   SYNTAX      Counter64
   MAX-ACCESS  read-only
   STATUS      current
   DESCRIPTION
      "Path: ethernet3.performance.h2Performance.ifOutOctets

       64 bit unsigned wrappable counter."
   ::= {pr1645v2Lan3InPEntry 167772160}

pr1645v2Lan3InPIfOutUCPkts OBJECT-TYPE
   SYNTAX      Counter64
   MAX-ACCESS  read-only
   STATUS      current
   DESCRIPTION
      "Path: ethernet3.performance.h2Performance.ifOutUcastPkts

       64 bit unsigned wrappable counter."
   ::= {pr1645v2Lan3InPEntry 184549376}

pr1645v2Lan3InPIfOutNUCPkts OBJECT-TYPE
   SYNTAX      Counter64
   MAX-ACCESS  read-only
   STATUS      current
   DESCRIPTION
      "Path: ethernet3.performance.h2Performance.ifOutNUcastPkts

       64 bit unsigned wrappable counter."
   ::= {pr1645v2Lan3InPEntry 201326592}

pr1645v2Lan3InPIfOutBCPkts OBJECT-TYPE
   SYNTAX      Counter64
   MAX-ACCESS  read-only
   STATUS      current
   DESCRIPTION
      "Path: ethernet3.performance.h2Performance.ifOutBcastPkts

       64 bit unsigned wrappable counter."
   ::= {pr1645v2Lan3InPEntry 452984832}

pr1645v2Lan3InPIfOutMCPkts OBJECT-TYPE
   SYNTAX      Counter64
   MAX-ACCESS  read-only
   STATUS      current
   DESCRIPTION
      "Path: ethernet3.performance.h2Performance.ifOutMcastPkts

       64 bit unsigned wrappable counter."
   ::= {pr1645v2Lan3InPEntry 469762048}

pr1645v2Lan3InPIfOutDiscards OBJECT-TYPE
   SYNTAX      Counter64
   MAX-ACCESS  read-only
   STATUS      current
   DESCRIPTION
      "Path: ethernet3.performance.h2Performance.ifOutDiscards

       64 bit unsigned wrappable counter."
   ::= {pr1645v2Lan3InPEntry 218103808}

pr1645v2Lan3InPIfOutErrors OBJECT-TYPE
   SYNTAX      Counter64
   MAX-ACCESS  read-only
   STATUS      current
   DESCRIPTION
      "Path: ethernet3.performance.h2Performance.ifOutErrors

       64 bit unsigned wrappable counter."
   ::= {pr1645v2Lan3InPEntry 234881024}

pr1645v2Lan3InPOutDropEx OBJECT-TYPE
   SYNTAX      Counter64
   MAX-ACCESS  read-only
   STATUS      current
   DESCRIPTION
      "Path: ethernet3.performance.h2Performance.ifOutDropLevelExceeded

       64 bit unsigned wrappable counter."
   ::= {pr1645v2Lan3InPEntry 352321536}

pr1645v2Lan3InPOutDropNoArp OBJECT-TYPE
   SYNTAX      Counter64
   MAX-ACCESS  read-only
   STATUS      current
   DESCRIPTION
      "Path: ethernet3.performance.h2Performance.ifOutDiscardsNoArp

       64 bit unsigned wrappable counter."
   ::= {pr1645v2Lan3InPEntry 369098752}

pr1645v2Lan3InPOutDropFilter OBJECT-TYPE
   SYNTAX      Counter64
   MAX-ACCESS  read-only
   STATUS      current
   DESCRIPTION
      "Path: ethernet3.performance.h2Performance.ifOutDiscardsFilter

       64 bit unsigned wrappable counter."
   ::= {pr1645v2Lan3InPEntry 402653184}

pr1645v2Lan3InPIfOutBandwidth OBJECT-TYPE
   SYNTAX      Integer32
   MAX-ACCESS  read-only
   STATUS      current
   DESCRIPTION
      "Path: ethernet3.performance.h2Performance.ifOutBandwidth

       unit name = bps
       formula = 8 * ; 8 /"
   ::= {pr1645v2Lan3InPEntry 285212672}

pr1645v2Lan3InPIfErrSec OBJECT-TYPE
   SYNTAX      Counter32
   MAX-ACCESS  read-only
   STATUS      current
   DESCRIPTION
      "Path: ethernet3.performance.h2Performance.ifErrSec

       32 bit unsigned wrappable counter."
   ::= {pr1645v2Lan3InPEntry 251658240}


pr1645v2Lan3H24InP OBJECT IDENTIFIER ::= {pr1645v2Lan3 308}

pr1645v2Lan3H24InPSSCTable OBJECT-TYPE
   SYNTAX      SEQUENCE OF Pr1645v2Lan3H24InPEntry
   MAX-ACCESS  not-accessible
   STATUS      current
   DESCRIPTION
      "h24IfInPerformance"
   ::= {pr1645v2Lan3H24InP 1}

pr1645v2Lan3H24InPEntry OBJECT-TYPE
   SYNTAX      Pr1645v2Lan3H24InPEntry
   MAX-ACCESS  not-accessible
   STATUS      current
   DESCRIPTION
      ""
   INDEX      { pr1645v2Lan3H24InPTableIx }
   ::= {pr1645v2Lan3H24InPSSCTable 1}

Pr1645v2Lan3H24InPEntry ::=
   SEQUENCE
      {
      pr1645v2Lan3H24InPTableIx
         TableIndex,
      pr1645v2Lan3H24InPSysUpTime
         TimeTicks,
      pr1645v2Lan3H24InPIfUpTime
         TimeTicks,
      pr1645v2Lan3H24InPIfStatChanges
         Counter32,
      pr1645v2Lan3H24InPIfInOctets
         Counter64,
      pr1645v2Lan3H24InPIfInUCPkts
         Counter64,
      pr1645v2Lan3H24InPIfInNUCPkts
         Counter64,
      pr1645v2Lan3H24InPIfInBCPkts
         Counter64,
      pr1645v2Lan3H24InPIfInMCPkts
         Counter64,
      pr1645v2Lan3H24InPIfInDiscards
         Counter64,
      pr1645v2Lan3H24InPIfInErrors
         Counter64,
      pr1645v2Lan3H24InPIfInUnkwn
         Counter64,
      pr1645v2Lan3H24InPInDropEx
         Counter64,
      pr1645v2Lan3H24InPInDropNoMac
         Counter64,
      pr1645v2Lan3H24InPInDropNUCast
         Counter64,
      pr1645v2Lan3H24InPInDropFilter
         Counter64,
      pr1645v2Lan3H24InPIfInBandwidth
         Integer32,
      pr1645v2Lan3H24InPIfOutOctets
         Counter64,
      pr1645v2Lan3H24InPIfOutUCPkts
         Counter64,
      pr1645v2Lan3H24InPIfOutNUCPkts
         Counter64,
      pr1645v2Lan3H24InPIfOutBCPkts
         Counter64,
      pr1645v2Lan3H24InPIfOutMCPkts
         Counter64,
      pr1645v2Lan3H24InPIfOutDiscards
         Counter64,
      pr1645v2Lan3H24InPIfOutErrors
         Counter64,
      pr1645v2Lan3H24InPOutDropEx
         Counter64,
      pr1645v2Lan3H24InPOutDropNoArp
         Counter64,
      pr1645v2Lan3H24InPOutDropFilter
         Counter64,
      pr1645v2Lan3H24InPIfOutBandwidth
         Integer32,
      pr1645v2Lan3H24InPIfErrSec
         Counter32
      }

pr1645v2Lan3H24InPTableIx OBJECT-TYPE
   SYNTAX      TableIndex
   MAX-ACCESS  not-accessible
   STATUS      current
   DESCRIPTION
      ""
   ::= {pr1645v2Lan3H24InPEntry 11}

pr1645v2Lan3H24InPSysUpTime OBJECT-TYPE
   SYNTAX      TimeTicks
   MAX-ACCESS  read-only
   STATUS      current
   DESCRIPTION
      "Path: ethernet3.performance.h24Performance.sysUpTime

       Time in centi-second."
   ::= {pr1645v2Lan3H24InPEntry 16777216}

pr1645v2Lan3H24InPIfUpTime OBJECT-TYPE
   SYNTAX      TimeTicks
   MAX-ACCESS  read-only
   STATUS      current
   DESCRIPTION
      "Path: ethernet3.performance.h24Performance.ifUpTime

       Time in centi-second."
   ::= {pr1645v2Lan3H24InPEntry 33554432}

pr1645v2Lan3H24InPIfStatChanges OBJECT-TYPE
   SYNTAX      Counter32
   MAX-ACCESS  read-only
   STATUS      current
   DESCRIPTION
      "Path: ethernet3.performance.h24Performance.ifStatusChanges

       32 bit unsigned wrappable counter."
   ::= {pr1645v2Lan3H24InPEntry 50331648}

pr1645v2Lan3H24InPIfInOctets OBJECT-TYPE
   SYNTAX      Counter64
   MAX-ACCESS  read-only
   STATUS      current
   DESCRIPTION
      "Path: ethernet3.performance.h24Performance.ifInOctets

       64 bit unsigned wrappable counter."
   ::= {pr1645v2Lan3H24InPEntry 67108864}

pr1645v2Lan3H24InPIfInUCPkts OBJECT-TYPE
   SYNTAX      Counter64
   MAX-ACCESS  read-only
   STATUS      current
   DESCRIPTION
      "Path: ethernet3.performance.h24Performance.ifInUcastPkts

       64 bit unsigned wrappable counter."
   ::= {pr1645v2Lan3H24InPEntry 83886080}

pr1645v2Lan3H24InPIfInNUCPkts OBJECT-TYPE
   SYNTAX      Counter64
   MAX-ACCESS  read-only
   STATUS      current
   DESCRIPTION
      "Path: ethernet3.performance.h24Performance.ifInNUcastPkts

       64 bit unsigned wrappable counter."
   ::= {pr1645v2Lan3H24InPEntry 100663296}

pr1645v2Lan3H24InPIfInBCPkts OBJECT-TYPE
   SYNTAX      Counter64
   MAX-ACCESS  read-only
   STATUS      current
   DESCRIPTION
      "Path: ethernet3.performance.h24Performance.ifInBcastPkts

       64 bit unsigned wrappable counter."
   ::= {pr1645v2Lan3H24InPEntry 419430400}

pr1645v2Lan3H24InPIfInMCPkts OBJECT-TYPE
   SYNTAX      Counter64
   MAX-ACCESS  read-only
   STATUS      current
   DESCRIPTION
      "Path: ethernet3.performance.h24Performance.ifInMcastPkts

       64 bit unsigned wrappable counter."
   ::= {pr1645v2Lan3H24InPEntry 436207616}

pr1645v2Lan3H24InPIfInDiscards OBJECT-TYPE
   SYNTAX      Counter64
   MAX-ACCESS  read-only
   STATUS      current
   DESCRIPTION
      "Path: ethernet3.performance.h24Performance.ifInDiscards

       64 bit unsigned wrappable counter."
   ::= {pr1645v2Lan3H24InPEntry 117440512}

pr1645v2Lan3H24InPIfInErrors OBJECT-TYPE
   SYNTAX      Counter64
   MAX-ACCESS  read-only
   STATUS      current
   DESCRIPTION
      "Path: ethernet3.performance.h24Performance.ifInErrors

       64 bit unsigned wrappable counter."
   ::= {pr1645v2Lan3H24InPEntry 134217728}

pr1645v2Lan3H24InPIfInUnkwn OBJECT-TYPE
   SYNTAX      Counter64
   MAX-ACCESS  read-only
   STATUS      current
   DESCRIPTION
      "Path: ethernet3.performance.h24Performance.ifInUnknownProtos

       64 bit unsigned wrappable counter."
   ::= {pr1645v2Lan3H24InPEntry 150994944}

pr1645v2Lan3H24InPInDropEx OBJECT-TYPE
   SYNTAX      Counter64
   MAX-ACCESS  read-only
   STATUS      current
   DESCRIPTION
      "Path: ethernet3.performance.h24Performance.ifInDropLevelExceeded

       64 bit unsigned wrappable counter."
   ::= {pr1645v2Lan3H24InPEntry 335544320}

pr1645v2Lan3H24InPInDropNoMac OBJECT-TYPE
   SYNTAX      Counter64
   MAX-ACCESS  read-only
   STATUS      current
   DESCRIPTION
      "Path: ethernet3.performance.h24Performance.fInDiscardsNoMacFit

       64 bit unsigned wrappable counter."
   ::= {pr1645v2Lan3H24InPEntry 301989888}

pr1645v2Lan3H24InPInDropNUCast OBJECT-TYPE
   SYNTAX      Counter64
   MAX-ACCESS  read-only
   STATUS      current
   DESCRIPTION
      "Path: ethernet3.performance.h24Performance.fInDiscardsNUCast

       64 bit unsigned wrappable counter."
   ::= {pr1645v2Lan3H24InPEntry 318767104}

pr1645v2Lan3H24InPInDropFilter OBJECT-TYPE
   SYNTAX      Counter64
   MAX-ACCESS  read-only
   STATUS      current
   DESCRIPTION
      "Path: ethernet3.performance.h24Performance.fInDiscardsFilter

       64 bit unsigned wrappable counter."
   ::= {pr1645v2Lan3H24InPEntry 385875968}

pr1645v2Lan3H24InPIfInBandwidth OBJECT-TYPE
   SYNTAX      Integer32
   MAX-ACCESS  read-only
   STATUS      current
   DESCRIPTION
      "Path: ethernet3.performance.h24Performance.ifInBandwidth

       unit name = bps
       formula = 8 * ; 8 /"
   ::= {pr1645v2Lan3H24InPEntry 268435456}

pr1645v2Lan3H24InPIfOutOctets OBJECT-TYPE
   SYNTAX      Counter64
   MAX-ACCESS  read-only
   STATUS      current
   DESCRIPTION
      "Path: ethernet3.performance.h24Performance.ifOutOctets

       64 bit unsigned wrappable counter."
   ::= {pr1645v2Lan3H24InPEntry 167772160}

pr1645v2Lan3H24InPIfOutUCPkts OBJECT-TYPE
   SYNTAX      Counter64
   MAX-ACCESS  read-only
   STATUS      current
   DESCRIPTION
      "Path: ethernet3.performance.h24Performance.ifOutUcastPkts

       64 bit unsigned wrappable counter."
   ::= {pr1645v2Lan3H24InPEntry 184549376}

pr1645v2Lan3H24InPIfOutNUCPkts OBJECT-TYPE
   SYNTAX      Counter64
   MAX-ACCESS  read-only
   STATUS      current
   DESCRIPTION
      "Path: ethernet3.performance.h24Performance.ifOutNUcastPkts

       64 bit unsigned wrappable counter."
   ::= {pr1645v2Lan3H24InPEntry 201326592}

pr1645v2Lan3H24InPIfOutBCPkts OBJECT-TYPE
   SYNTAX      Counter64
   MAX-ACCESS  read-only
   STATUS      current
   DESCRIPTION
      "Path: ethernet3.performance.h24Performance.ifOutBcastPkts

       64 bit unsigned wrappable counter."
   ::= {pr1645v2Lan3H24InPEntry 452984832}

pr1645v2Lan3H24InPIfOutMCPkts OBJECT-TYPE
   SYNTAX      Counter64
   MAX-ACCESS  read-only
   STATUS      current
   DESCRIPTION
      "Path: ethernet3.performance.h24Performance.ifOutMcastPkts

       64 bit unsigned wrappable counter."
   ::= {pr1645v2Lan3H24InPEntry 469762048}

pr1645v2Lan3H24InPIfOutDiscards OBJECT-TYPE
   SYNTAX      Counter64
   MAX-ACCESS  read-only
   STATUS      current
   DESCRIPTION
      "Path: ethernet3.performance.h24Performance.ifOutDiscards

       64 bit unsigned wrappable counter."
   ::= {pr1645v2Lan3H24InPEntry 218103808}

pr1645v2Lan3H24InPIfOutErrors OBJECT-TYPE
   SYNTAX      Counter64
   MAX-ACCESS  read-only
   STATUS      current
   DESCRIPTION
      "Path: ethernet3.performance.h24Performance.ifOutErrors

       64 bit unsigned wrappable counter."
   ::= {pr1645v2Lan3H24InPEntry 234881024}

pr1645v2Lan3H24InPOutDropEx OBJECT-TYPE
   SYNTAX      Counter64
   MAX-ACCESS  read-only
   STATUS      current
   DESCRIPTION
      "Path: ethernet3.performance.h24Performance.ifOutDropLevelExceeded

       64 bit unsigned wrappable counter."
   ::= {pr1645v2Lan3H24InPEntry 352321536}

pr1645v2Lan3H24InPOutDropNoArp OBJECT-TYPE
   SYNTAX      Counter64
   MAX-ACCESS  read-only
   STATUS      current
   DESCRIPTION
      "Path: ethernet3.performance.h24Performance.ifOutDiscardsNoArp

       64 bit unsigned wrappable counter."
   ::= {pr1645v2Lan3H24InPEntry 369098752}

pr1645v2Lan3H24InPOutDropFilter OBJECT-TYPE
   SYNTAX      Counter64
   MAX-ACCESS  read-only
   STATUS      current
   DESCRIPTION
      "Path: ethernet3.performance.h24Performance.ifOutDiscardsFilter

       64 bit unsigned wrappable counter."
   ::= {pr1645v2Lan3H24InPEntry 402653184}

pr1645v2Lan3H24InPIfOutBandwidth OBJECT-TYPE
   SYNTAX      Integer32
   MAX-ACCESS  read-only
   STATUS      current
   DESCRIPTION
      "Path: ethernet3.performance.h24Performance.ifOutBandwidth

       unit name = bps
       formula = 8 * ; 8 /"
   ::= {pr1645v2Lan3H24InPEntry 285212672}

pr1645v2Lan3H24InPIfErrSec OBJECT-TYPE
   SYNTAX      Counter32
   MAX-ACCESS  read-only
   STATUS      current
   DESCRIPTION
      "Path: ethernet3.performance.h24Performance.ifErrSec

       32 bit unsigned wrappable counter."
   ::= {pr1645v2Lan3H24InPEntry 251658240}


pr1645v2Lan3D7InP OBJECT IDENTIFIER ::= {pr1645v2Lan3 309}

pr1645v2Lan3D7InPSSCTable OBJECT-TYPE
   SYNTAX      SEQUENCE OF Pr1645v2Lan3D7InPEntry
   MAX-ACCESS  not-accessible
   STATUS      current
   DESCRIPTION
      "d7IfInPerformance"
   ::= {pr1645v2Lan3D7InP 1}

pr1645v2Lan3D7InPEntry OBJECT-TYPE
   SYNTAX      Pr1645v2Lan3D7InPEntry
   MAX-ACCESS  not-accessible
   STATUS      current
   DESCRIPTION
      ""
   INDEX      { pr1645v2Lan3D7InPTableIx }
   ::= {pr1645v2Lan3D7InPSSCTable 1}

Pr1645v2Lan3D7InPEntry ::=
   SEQUENCE
      {
      pr1645v2Lan3D7InPTableIx
         TableIndex,
      pr1645v2Lan3D7InPSysUpTime
         TimeTicks,
      pr1645v2Lan3D7InPIfUpTime
         TimeTicks,
      pr1645v2Lan3D7InPIfStatChanges
         Counter32,
      pr1645v2Lan3D7InPIfInOctets
         Counter64,
      pr1645v2Lan3D7InPIfInUCPkts
         Counter64,
      pr1645v2Lan3D7InPIfInNUCPkts
         Counter64,
      pr1645v2Lan3D7InPIfInBCPkts
         Counter64,
      pr1645v2Lan3D7InPIfInMCPkts
         Counter64,
      pr1645v2Lan3D7InPIfInDiscards
         Counter64,
      pr1645v2Lan3D7InPIfInErrors
         Counter64,
      pr1645v2Lan3D7InPIfInUnkwn
         Counter64,
      pr1645v2Lan3D7InPInDropEx
         Counter64,
      pr1645v2Lan3D7InPInDropNoMac
         Counter64,
      pr1645v2Lan3D7InPInDropNUCast
         Counter64,
      pr1645v2Lan3D7InPInDropFilter
         Counter64,
      pr1645v2Lan3D7InPIfInBandwidth
         Integer32,
      pr1645v2Lan3D7InPIfOutOctets
         Counter64,
      pr1645v2Lan3D7InPIfOutUCPkts
         Counter64,
      pr1645v2Lan3D7InPIfOutNUCPkts
         Counter64,
      pr1645v2Lan3D7InPIfOutBCPkts
         Counter64,
      pr1645v2Lan3D7InPIfOutMCPkts
         Counter64,
      pr1645v2Lan3D7InPIfOutDiscards
         Counter64,
      pr1645v2Lan3D7InPIfOutErrors
         Counter64,
      pr1645v2Lan3D7InPOutDropEx
         Counter64,
      pr1645v2Lan3D7InPOutDropNoArp
         Counter64,
      pr1645v2Lan3D7InPOutDropFilter
         Counter64,
      pr1645v2Lan3D7InPIfOutBandwidth
         Integer32,
      pr1645v2Lan3D7InPIfErrSec
         Counter32
      }

pr1645v2Lan3D7InPTableIx OBJECT-TYPE
   SYNTAX      TableIndex
   MAX-ACCESS  not-accessible
   STATUS      current
   DESCRIPTION
      ""
   ::= {pr1645v2Lan3D7InPEntry 11}

pr1645v2Lan3D7InPSysUpTime OBJECT-TYPE
   SYNTAX      TimeTicks
   MAX-ACCESS  read-only
   STATUS      current
   DESCRIPTION
      "Path: ethernet3.performance.d7Performance.sysUpTime

       Time in centi-second."
   ::= {pr1645v2Lan3D7InPEntry 16777216}

pr1645v2Lan3D7InPIfUpTime OBJECT-TYPE
   SYNTAX      TimeTicks
   MAX-ACCESS  read-only
   STATUS      current
   DESCRIPTION
      "Path: ethernet3.performance.d7Performance.ifUpTime

       Time in centi-second."
   ::= {pr1645v2Lan3D7InPEntry 33554432}

pr1645v2Lan3D7InPIfStatChanges OBJECT-TYPE
   SYNTAX      Counter32
   MAX-ACCESS  read-only
   STATUS      current
   DESCRIPTION
      "Path: ethernet3.performance.d7Performance.ifStatusChanges

       32 bit unsigned wrappable counter."
   ::= {pr1645v2Lan3D7InPEntry 50331648}

pr1645v2Lan3D7InPIfInOctets OBJECT-TYPE
   SYNTAX      Counter64
   MAX-ACCESS  read-only
   STATUS      current
   DESCRIPTION
      "Path: ethernet3.performance.d7Performance.ifInOctets

       64 bit unsigned wrappable counter."
   ::= {pr1645v2Lan3D7InPEntry 67108864}

pr1645v2Lan3D7InPIfInUCPkts OBJECT-TYPE
   SYNTAX      Counter64
   MAX-ACCESS  read-only
   STATUS      current
   DESCRIPTION
      "Path: ethernet3.performance.d7Performance.ifInUcastPkts

       64 bit unsigned wrappable counter."
   ::= {pr1645v2Lan3D7InPEntry 83886080}

pr1645v2Lan3D7InPIfInNUCPkts OBJECT-TYPE
   SYNTAX      Counter64
   MAX-ACCESS  read-only
   STATUS      current
   DESCRIPTION
      "Path: ethernet3.performance.d7Performance.ifInNUcastPkts

       64 bit unsigned wrappable counter."
   ::= {pr1645v2Lan3D7InPEntry 100663296}

pr1645v2Lan3D7InPIfInBCPkts OBJECT-TYPE
   SYNTAX      Counter64
   MAX-ACCESS  read-only
   STATUS      current
   DESCRIPTION
      "Path: ethernet3.performance.d7Performance.ifInBcastPkts

       64 bit unsigned wrappable counter."
   ::= {pr1645v2Lan3D7InPEntry 419430400}

pr1645v2Lan3D7InPIfInMCPkts OBJECT-TYPE
   SYNTAX      Counter64
   MAX-ACCESS  read-only
   STATUS      current
   DESCRIPTION
      "Path: ethernet3.performance.d7Performance.ifInMcastPkts

       64 bit unsigned wrappable counter."
   ::= {pr1645v2Lan3D7InPEntry 436207616}

pr1645v2Lan3D7InPIfInDiscards OBJECT-TYPE
   SYNTAX      Counter64
   MAX-ACCESS  read-only
   STATUS      current
   DESCRIPTION
      "Path: ethernet3.performance.d7Performance.ifInDiscards

       64 bit unsigned wrappable counter."
   ::= {pr1645v2Lan3D7InPEntry 117440512}

pr1645v2Lan3D7InPIfInErrors OBJECT-TYPE
   SYNTAX      Counter64
   MAX-ACCESS  read-only
   STATUS      current
   DESCRIPTION
      "Path: ethernet3.performance.d7Performance.ifInErrors

       64 bit unsigned wrappable counter."
   ::= {pr1645v2Lan3D7InPEntry 134217728}

pr1645v2Lan3D7InPIfInUnkwn OBJECT-TYPE
   SYNTAX      Counter64
   MAX-ACCESS  read-only
   STATUS      current
   DESCRIPTION
      "Path: ethernet3.performance.d7Performance.ifInUnknownProtos

       64 bit unsigned wrappable counter."
   ::= {pr1645v2Lan3D7InPEntry 150994944}

pr1645v2Lan3D7InPInDropEx OBJECT-TYPE
   SYNTAX      Counter64
   MAX-ACCESS  read-only
   STATUS      current
   DESCRIPTION
      "Path: ethernet3.performance.d7Performance.ifInDropLevelExceeded

       64 bit unsigned wrappable counter."
   ::= {pr1645v2Lan3D7InPEntry 335544320}

pr1645v2Lan3D7InPInDropNoMac OBJECT-TYPE
   SYNTAX      Counter64
   MAX-ACCESS  read-only
   STATUS      current
   DESCRIPTION
      "Path: ethernet3.performance.d7Performance.fInDiscardsNoMacFit

       64 bit unsigned wrappable counter."
   ::= {pr1645v2Lan3D7InPEntry 301989888}

pr1645v2Lan3D7InPInDropNUCast OBJECT-TYPE
   SYNTAX      Counter64
   MAX-ACCESS  read-only
   STATUS      current
   DESCRIPTION
      "Path: ethernet3.performance.d7Performance.fInDiscardsNUCast

       64 bit unsigned wrappable counter."
   ::= {pr1645v2Lan3D7InPEntry 318767104}

pr1645v2Lan3D7InPInDropFilter OBJECT-TYPE
   SYNTAX      Counter64
   MAX-ACCESS  read-only
   STATUS      current
   DESCRIPTION
      "Path: ethernet3.performance.d7Performance.fInDiscardsFilter

       64 bit unsigned wrappable counter."
   ::= {pr1645v2Lan3D7InPEntry 385875968}

pr1645v2Lan3D7InPIfInBandwidth OBJECT-TYPE
   SYNTAX      Integer32
   MAX-ACCESS  read-only
   STATUS      current
   DESCRIPTION
      "Path: ethernet3.performance.d7Performance.ifInBandwidth

       unit name = bps
       formula = 8 * ; 8 /"
   ::= {pr1645v2Lan3D7InPEntry 268435456}

pr1645v2Lan3D7InPIfOutOctets OBJECT-TYPE
   SYNTAX      Counter64
   MAX-ACCESS  read-only
   STATUS      current
   DESCRIPTION
      "Path: ethernet3.performance.d7Performance.ifOutOctets

       64 bit unsigned wrappable counter."
   ::= {pr1645v2Lan3D7InPEntry 167772160}

pr1645v2Lan3D7InPIfOutUCPkts OBJECT-TYPE
   SYNTAX      Counter64
   MAX-ACCESS  read-only
   STATUS      current
   DESCRIPTION
      "Path: ethernet3.performance.d7Performance.ifOutUcastPkts

       64 bit unsigned wrappable counter."
   ::= {pr1645v2Lan3D7InPEntry 184549376}

pr1645v2Lan3D7InPIfOutNUCPkts OBJECT-TYPE
   SYNTAX      Counter64
   MAX-ACCESS  read-only
   STATUS      current
   DESCRIPTION
      "Path: ethernet3.performance.d7Performance.ifOutNUcastPkts

       64 bit unsigned wrappable counter."
   ::= {pr1645v2Lan3D7InPEntry 201326592}

pr1645v2Lan3D7InPIfOutBCPkts OBJECT-TYPE
   SYNTAX      Counter64
   MAX-ACCESS  read-only
   STATUS      current
   DESCRIPTION
      "Path: ethernet3.performance.d7Performance.ifOutBcastPkts

       64 bit unsigned wrappable counter."
   ::= {pr1645v2Lan3D7InPEntry 452984832}

pr1645v2Lan3D7InPIfOutMCPkts OBJECT-TYPE
   SYNTAX      Counter64
   MAX-ACCESS  read-only
   STATUS      current
   DESCRIPTION
      "Path: ethernet3.performance.d7Performance.ifOutMcastPkts

       64 bit unsigned wrappable counter."
   ::= {pr1645v2Lan3D7InPEntry 469762048}

pr1645v2Lan3D7InPIfOutDiscards OBJECT-TYPE
   SYNTAX      Counter64
   MAX-ACCESS  read-only
   STATUS      current
   DESCRIPTION
      "Path: ethernet3.performance.d7Performance.ifOutDiscards

       64 bit unsigned wrappable counter."
   ::= {pr1645v2Lan3D7InPEntry 218103808}

pr1645v2Lan3D7InPIfOutErrors OBJECT-TYPE
   SYNTAX      Counter64
   MAX-ACCESS  read-only
   STATUS      current
   DESCRIPTION
      "Path: ethernet3.performance.d7Performance.ifOutErrors

       64 bit unsigned wrappable counter."
   ::= {pr1645v2Lan3D7InPEntry 234881024}

pr1645v2Lan3D7InPOutDropEx OBJECT-TYPE
   SYNTAX      Counter64
   MAX-ACCESS  read-only
   STATUS      current
   DESCRIPTION
      "Path: ethernet3.performance.d7Performance.ifOutDropLevelExceeded

       64 bit unsigned wrappable counter."
   ::= {pr1645v2Lan3D7InPEntry 352321536}

pr1645v2Lan3D7InPOutDropNoArp OBJECT-TYPE
   SYNTAX      Counter64
   MAX-ACCESS  read-only
   STATUS      current
   DESCRIPTION
      "Path: ethernet3.performance.d7Performance.ifOutDiscardsNoArp

       64 bit unsigned wrappable counter."
   ::= {pr1645v2Lan3D7InPEntry 369098752}

pr1645v2Lan3D7InPOutDropFilter OBJECT-TYPE
   SYNTAX      Counter64
   MAX-ACCESS  read-only
   STATUS      current
   DESCRIPTION
      "Path: ethernet3.performance.d7Performance.ifOutDiscardsFilter

       64 bit unsigned wrappable counter."
   ::= {pr1645v2Lan3D7InPEntry 402653184}

pr1645v2Lan3D7InPIfOutBandwidth OBJECT-TYPE
   SYNTAX      Integer32
   MAX-ACCESS  read-only
   STATUS      current
   DESCRIPTION
      "Path: ethernet3.performance.d7Performance.ifOutBandwidth

       unit name = bps
       formula = 8 * ; 8 /"
   ::= {pr1645v2Lan3D7InPEntry 285212672}

pr1645v2Lan3D7InPIfErrSec OBJECT-TYPE
   SYNTAX      Counter32
   MAX-ACCESS  read-only
   STATUS      current
   DESCRIPTION
      "Path: ethernet3.performance.d7Performance.ifErrSec

       32 bit unsigned wrappable counter."
   ::= {pr1645v2Lan3D7InPEntry 251658240}


pr1645v2Lan3Oam OBJECT IDENTIFIER ::= {pr1645v2Lan3 910}

pr1645v2Lan3OamSSC OBJECT IDENTIFIER ::= {pr1645v2Lan3Oam 1}

pr1645v2Lan3OamEntry OBJECT IDENTIFIER ::= {pr1645v2Lan3OamSSC 1}

pr1645v2Lan3OamInformationTx OBJECT-TYPE
   SYNTAX      Counter32
   MAX-ACCESS  read-only
   STATUS      current
   DESCRIPTION
      "Path: ethernet3.performance.oam.informationTx

       32 bit unsigned wrappable counter."
   ::= {pr1645v2Lan3OamEntry 16777216}

pr1645v2Lan3OamInformationRx OBJECT-TYPE
   SYNTAX      Counter32
   MAX-ACCESS  read-only
   STATUS      current
   DESCRIPTION
      "Path: ethernet3.performance.oam.informationRx

       32 bit unsigned wrappable counter."
   ::= {pr1645v2Lan3OamEntry 33554432}

pr1645v2Lan3OamUniqueEventNotifTx OBJECT-TYPE
   SYNTAX      Counter32
   MAX-ACCESS  read-only
   STATUS      current
   DESCRIPTION
      "Path: ethernet3.performance.oam.uniqueEventNotifTx

       32 bit unsigned wrappable counter."
   ::= {pr1645v2Lan3OamEntry 50331648}

pr1645v2Lan3OamUniqueEventNotifRx OBJECT-TYPE
   SYNTAX      Counter32
   MAX-ACCESS  read-only
   STATUS      current
   DESCRIPTION
      "Path: ethernet3.performance.oam.uniqueEventNotifRx

       32 bit unsigned wrappable counter."
   ::= {pr1645v2Lan3OamEntry 67108864}

pr1645v2Lan3OamLoopbackCtrlTx OBJECT-TYPE
   SYNTAX      Counter32
   MAX-ACCESS  read-only
   STATUS      current
   DESCRIPTION
      "Path: ethernet3.performance.oam.loopbackCtrlTx

       32 bit unsigned wrappable counter."
   ::= {pr1645v2Lan3OamEntry 117440512}

pr1645v2Lan3OamLoopbackCtrlRx OBJECT-TYPE
   SYNTAX      Counter32
   MAX-ACCESS  read-only
   STATUS      current
   DESCRIPTION
      "Path: ethernet3.performance.oam.loopbackCtrlRx

       32 bit unsigned wrappable counter."
   ::= {pr1645v2Lan3OamEntry 134217728}

pr1645v2Lan3OamVarReqTx OBJECT-TYPE
   SYNTAX      Counter32
   MAX-ACCESS  read-only
   STATUS      current
   DESCRIPTION
      "Path: ethernet3.performance.oam.varReqTx

       32 bit unsigned wrappable counter."
   ::= {pr1645v2Lan3OamEntry 150994944}

pr1645v2Lan3OamVarReqRx OBJECT-TYPE
   SYNTAX      Counter32
   MAX-ACCESS  read-only
   STATUS      current
   DESCRIPTION
      "Path: ethernet3.performance.oam.varReqRx

       32 bit unsigned wrappable counter."
   ::= {pr1645v2Lan3OamEntry 167772160}

pr1645v2Lan3OamVarRespTx OBJECT-TYPE
   SYNTAX      Counter32
   MAX-ACCESS  read-only
   STATUS      current
   DESCRIPTION
      "Path: ethernet3.performance.oam.varRespTx

       32 bit unsigned wrappable counter."
   ::= {pr1645v2Lan3OamEntry 184549376}

pr1645v2Lan3OamVarRespRx OBJECT-TYPE
   SYNTAX      Counter32
   MAX-ACCESS  read-only
   STATUS      current
   DESCRIPTION
      "Path: ethernet3.performance.oam.varRespRx

       32 bit unsigned wrappable counter."
   ::= {pr1645v2Lan3OamEntry 201326592}

pr1645v2Lan3OamOrgSpecificTx OBJECT-TYPE
   SYNTAX      Counter32
   MAX-ACCESS  read-only
   STATUS      current
   DESCRIPTION
      "Path: ethernet3.performance.oam.orgSpecificTx

       32 bit unsigned wrappable counter."
   ::= {pr1645v2Lan3OamEntry 218103808}

pr1645v2Lan3OamOrgSpecificRx OBJECT-TYPE
   SYNTAX      Counter32
   MAX-ACCESS  read-only
   STATUS      current
   DESCRIPTION
      "Path: ethernet3.performance.oam.orgSpecificRx

       32 bit unsigned wrappable counter."
   ::= {pr1645v2Lan3OamEntry 234881024}

pr1645v2Lan3OamUnsupportedCodesTx OBJECT-TYPE
   SYNTAX      Counter32
   MAX-ACCESS  read-only
   STATUS      current
   DESCRIPTION
      "Path: ethernet3.performance.oam.unsupportedCodesTx

       32 bit unsigned wrappable counter."
   ::= {pr1645v2Lan3OamEntry 251658240}

pr1645v2Lan3OamUnsupportedCodesRx OBJECT-TYPE
   SYNTAX      Counter32
   MAX-ACCESS  read-only
   STATUS      current
   DESCRIPTION
      "Path: ethernet3.performance.oam.unsupportedCodesRx

       32 bit unsigned wrappable counter."
   ::= {pr1645v2Lan3OamEntry 268435456}

pr1645v2Lan3OamPduDiscardRx OBJECT-TYPE
   SYNTAX      Counter32
   MAX-ACCESS  read-only
   STATUS      current
   DESCRIPTION
      "Path: ethernet3.performance.oam.pduDiscardRx

       32 bit unsigned wrappable counter."
   ::= {pr1645v2Lan3OamEntry 1694498816}

pr1645v2Lan3OamDataDiscardTx OBJECT-TYPE
   SYNTAX      Counter32
   MAX-ACCESS  read-only
   STATUS      current
   DESCRIPTION
      "Path: ethernet3.performance.oam.dataDiscardTx

       32 bit unsigned wrappable counter."
   ::= {pr1645v2Lan3OamEntry 1711276032}

pr1645v2Lan3OamDataDiscardRx OBJECT-TYPE
   SYNTAX      Counter32
   MAX-ACCESS  read-only
   STATUS      current
   DESCRIPTION
      "Path: ethernet3.performance.oam.dataDiscardRx

       32 bit unsigned wrappable counter."
   ::= {pr1645v2Lan3OamEntry 1728053248}


pr1645v2Lan3Vlan OBJECT IDENTIFIER ::= {pr1645v2Lan3 310}

pr1645v2Lan3VlanSSCTable OBJECT-TYPE
   SYNTAX      SEQUENCE OF Pr1645v2Lan3VlanEntry
   MAX-ACCESS  not-accessible
   STATUS      current
   DESCRIPTION
      ""
   ::= {pr1645v2Lan3Vlan 1}

pr1645v2Lan3VlanEntry OBJECT-TYPE
   SYNTAX      Pr1645v2Lan3VlanEntry
   MAX-ACCESS  not-accessible
   STATUS      current
   DESCRIPTION
      ""
   INDEX      { pr1645v2Lan3VlanTableIx }
   ::= {pr1645v2Lan3VlanSSCTable 1}

Pr1645v2Lan3VlanEntry ::=
   SEQUENCE
      {
      pr1645v2Lan3VlanTableIx
         TableIndex,
      pr1645v2Lan3VlanName
         DisplayString,
      pr1645v2Lan3VlanMCInOctets
         Counter64,
      pr1645v2Lan3VlanMCInUcast
         Counter64,
      pr1645v2Lan3VlanMCInNUcastPkts
         Counter64,
      pr1645v2Lan3VlanMCInBcastPkts
         Counter64,
      pr1645v2Lan3VlanMCInMcastPkts
         Counter64,
      pr1645v2Lan3VlanMCInDiscards
         Counter64,
      pr1645v2Lan3VlanMCInErrors
         Counter64,
      pr1645v2Lan3VlanMCInUnknownProtos
         Counter64,
      pr1645v2Lan3VlanMCInDropEx
         Counter64,
      pr1645v2Lan3VlanMCInDropNoMac
         Counter64,
      pr1645v2Lan3VlanMCInDropNUCast
         Counter64,
      pr1645v2Lan3VlanMCInDropFilter
         Counter64,
      pr1645v2Lan3VlanMCInBandwidth15sec
         Integer32,
      pr1645v2Lan3VlanMCInBandwidth30sec
         Integer32,
      pr1645v2Lan3VlanMCInBandwidth1min
         Integer32,
      pr1645v2Lan3VlanMCInBandwidth2min
         Integer32,
      pr1645v2Lan3VlanMCInBandwidth5min
         Integer32,
      pr1645v2Lan3VlanMCOutOctets
         Counter64,
      pr1645v2Lan3VlanMCOutUcastPkts
         Counter64,
      pr1645v2Lan3VlanMCOutNUcastPkts
         Counter64,
      pr1645v2Lan3VlanMCOutBcastPkts
         Counter64,
      pr1645v2Lan3VlanMCOutMcastPkts
         Counter64,
      pr1645v2Lan3VlanMCOutDiscards
         Counter64,
      pr1645v2Lan3VlanMCOutErrors
         Counter64,
      pr1645v2Lan3VlanMCOutQLen
         Counter32,
      pr1645v2Lan3VlanMCOutDropEx
         Counter64,
      pr1645v2Lan3VlanMCOutDropNoArp
         Counter64,
      pr1645v2Lan3VlanMCOutDropFilter
         Counter64,
      pr1645v2Lan3VlanMCOutBandwidth15sec
         Integer32,
      pr1645v2Lan3VlanMCOutBandwidth30sec
         Integer32,
      pr1645v2Lan3VlanMCOutBandwidth1min
         Integer32,
      pr1645v2Lan3VlanMCOutBandwidth2min
         Integer32,
      pr1645v2Lan3VlanMCOutBandwidth5min
         Integer32,
      pr1645v2Lan3VlanVlanVid
         Integer32,
      pr1645v2Lan3VlanPppLinkMonitoringRequestsSent
         Gauge32,
      pr1645v2Lan3VlanPppLinkMonitoringRepliesRcvd
         Gauge32,
      pr1645v2Lan3VlanPppLinkMonitoringRequestsRcvd
         Gauge32,
      pr1645v2Lan3VlanPppLinkMonitoringRepliesSent
         Gauge32
      }

pr1645v2Lan3VlanTableIx OBJECT-TYPE
   SYNTAX      TableIndex
   MAX-ACCESS  not-accessible
   STATUS      current
   DESCRIPTION
      ""
   ::= {pr1645v2Lan3VlanEntry 11}

pr1645v2Lan3VlanName OBJECT-TYPE
   SYNTAX      DisplayString
   MAX-ACCESS  read-only
   STATUS      current
   DESCRIPTION
      "Path: ethernet3.performance.vlan.name"
   ::= {pr1645v2Lan3VlanEntry 16777216}

pr1645v2Lan3VlanMCInOctets OBJECT-TYPE
   SYNTAX      Counter64
   MAX-ACCESS  read-only
   STATUS      current
   DESCRIPTION
      "Path: ethernet3.performance.vlan.mibCounters.ifInOctets

       64 bit unsigned wrappable counter."
   ::= {pr1645v2Lan3VlanEntry 40697856}

pr1645v2Lan3VlanMCInUcast OBJECT-TYPE
   SYNTAX      Counter64
   MAX-ACCESS  read-only
   STATUS      current
   DESCRIPTION
      "Path: ethernet3.performance.vlan.mibCounters.ifInUcastPkts

       64 bit unsigned wrappable counter."
   ::= {pr1645v2Lan3VlanEntry 40763392}

pr1645v2Lan3VlanMCInNUcastPkts OBJECT-TYPE
   SYNTAX      Counter64
   MAX-ACCESS  read-only
   STATUS      current
   DESCRIPTION
      "Path: ethernet3.performance.vlan.mibCounters.ifInNUcastPkts

       64 bit unsigned wrappable counter."
   ::= {pr1645v2Lan3VlanEntry 40828928}

pr1645v2Lan3VlanMCInBcastPkts OBJECT-TYPE
   SYNTAX      Counter64
   MAX-ACCESS  read-only
   STATUS      current
   DESCRIPTION
      "Path: ethernet3.performance.vlan.mibCounters.ifInBcastPkts

       64 bit unsigned wrappable counter."
   ::= {pr1645v2Lan3VlanEntry 47382528}

pr1645v2Lan3VlanMCInMcastPkts OBJECT-TYPE
   SYNTAX      Counter64
   MAX-ACCESS  read-only
   STATUS      current
   DESCRIPTION
      "Path: ethernet3.performance.vlan.mibCounters.ifInMcastPkts

       64 bit unsigned wrappable counter."
   ::= {pr1645v2Lan3VlanEntry 48037888}

pr1645v2Lan3VlanMCInDiscards OBJECT-TYPE
   SYNTAX      Counter64
   MAX-ACCESS  read-only
   STATUS      current
   DESCRIPTION
      "Path: ethernet3.performance.vlan.mibCounters.ifInDiscards

       64 bit unsigned wrappable counter."
   ::= {pr1645v2Lan3VlanEntry 40894464}

pr1645v2Lan3VlanMCInErrors OBJECT-TYPE
   SYNTAX      Counter64
   MAX-ACCESS  read-only
   STATUS      current
   DESCRIPTION
      "Path: ethernet3.performance.vlan.mibCounters.ifInErrors

       64 bit unsigned wrappable counter."
   ::= {pr1645v2Lan3VlanEntry 40960000}

pr1645v2Lan3VlanMCInUnknownProtos OBJECT-TYPE
   SYNTAX      Counter64
   MAX-ACCESS  read-only
   STATUS      current
   DESCRIPTION
      "Path: ethernet3.performance.vlan.mibCounters.ifInUnknownProtos

       64 bit unsigned wrappable counter."
   ::= {pr1645v2Lan3VlanEntry 41025536}

pr1645v2Lan3VlanMCInDropEx OBJECT-TYPE
   SYNTAX      Counter64
   MAX-ACCESS  read-only
   STATUS      current
   DESCRIPTION
      "Path: ethernet3.performance.vlan.mibCounters.ifInDropLevelExceeded

       64 bit unsigned wrappable counter."
   ::= {pr1645v2Lan3VlanEntry 42074112}

pr1645v2Lan3VlanMCInDropNoMac OBJECT-TYPE
   SYNTAX      Counter64
   MAX-ACCESS  read-only
   STATUS      current
   DESCRIPTION
      "Path: ethernet3.performance.vlan.mibCounters.ifInDiscardsNoMacFit

       64 bit unsigned wrappable counter."
   ::= {pr1645v2Lan3VlanEntry 42270720}

pr1645v2Lan3VlanMCInDropNUCast OBJECT-TYPE
   SYNTAX      Counter64
   MAX-ACCESS  read-only
   STATUS      current
   DESCRIPTION
      "Path: ethernet3.performance.vlan.mibCounters.ifInDiscardsNUCast

       64 bit unsigned wrappable counter."
   ::= {pr1645v2Lan3VlanEntry 42467328}

pr1645v2Lan3VlanMCInDropFilter OBJECT-TYPE
   SYNTAX      Counter64
   MAX-ACCESS  read-only
   STATUS      current
   DESCRIPTION
      "Path: ethernet3.performance.vlan.mibCounters.ifInDiscardsFilter

       64 bit unsigned wrappable counter."
   ::= {pr1645v2Lan3VlanEntry 42532864}

pr1645v2Lan3VlanMCInBandwidth15sec OBJECT-TYPE
   SYNTAX      Integer32
   MAX-ACCESS  read-only
   STATUS      current
   DESCRIPTION
      "Path: ethernet3.performance.vlan.mibCounters.ifInBandwidth.15sec

       unit name = bps
       formula = 8 * ; 8 /"
   ::= {pr1645v2Lan3VlanEntry 45417728}

pr1645v2Lan3VlanMCInBandwidth30sec OBJECT-TYPE
   SYNTAX      Integer32
   MAX-ACCESS  read-only
   STATUS      current
   DESCRIPTION
      "Path: ethernet3.performance.vlan.mibCounters.ifInBandwidth.30sec

       unit name = bps
       formula = 8 * ; 8 /"
   ::= {pr1645v2Lan3VlanEntry 45419008}

pr1645v2Lan3VlanMCInBandwidth1min OBJECT-TYPE
   SYNTAX      Integer32
   MAX-ACCESS  read-only
   STATUS      current
   DESCRIPTION
      "Path: ethernet3.performance.vlan.mibCounters.ifInBandwidth.1min

       unit name = bps
       formula = 8 * ; 8 /"
   ::= {pr1645v2Lan3VlanEntry 45421568}

pr1645v2Lan3VlanMCInBandwidth2min OBJECT-TYPE
   SYNTAX      Integer32
   MAX-ACCESS  read-only
   STATUS      current
   DESCRIPTION
      "Path: ethernet3.performance.vlan.mibCounters.ifInBandwidth.2min

       unit name = bps
       formula = 8 * ; 8 /"
   ::= {pr1645v2Lan3VlanEntry 45426688}

pr1645v2Lan3VlanMCInBandwidth5min OBJECT-TYPE
   SYNTAX      Integer32
   MAX-ACCESS  read-only
   STATUS      current
   DESCRIPTION
      "Path: ethernet3.performance.vlan.mibCounters.ifInBandwidth.5min

       unit name = bps
       formula = 8 * ; 8 /"
   ::= {pr1645v2Lan3VlanEntry 45442048}

pr1645v2Lan3VlanMCOutOctets OBJECT-TYPE
   SYNTAX      Counter64
   MAX-ACCESS  read-only
   STATUS      current
   DESCRIPTION
      "Path: ethernet3.performance.vlan.mibCounters.ifOutOctets

       64 bit unsigned wrappable counter."
   ::= {pr1645v2Lan3VlanEntry 41091072}

pr1645v2Lan3VlanMCOutUcastPkts OBJECT-TYPE
   SYNTAX      Counter64
   MAX-ACCESS  read-only
   STATUS      current
   DESCRIPTION
      "Path: ethernet3.performance.vlan.mibCounters.ifOutUcastPkts

       64 bit unsigned wrappable counter."
   ::= {pr1645v2Lan3VlanEntry 41156608}

pr1645v2Lan3VlanMCOutNUcastPkts OBJECT-TYPE
   SYNTAX      Counter64
   MAX-ACCESS  read-only
   STATUS      current
   DESCRIPTION
      "Path: ethernet3.performance.vlan.mibCounters.ifOutNUcastPkts

       64 bit unsigned wrappable counter."
   ::= {pr1645v2Lan3VlanEntry 41222144}

pr1645v2Lan3VlanMCOutBcastPkts OBJECT-TYPE
   SYNTAX      Counter64
   MAX-ACCESS  read-only
   STATUS      current
   DESCRIPTION
      "Path: ethernet3.performance.vlan.mibCounters.ifOutBcastPkts

       64 bit unsigned wrappable counter."
   ::= {pr1645v2Lan3VlanEntry 47775744}

pr1645v2Lan3VlanMCOutMcastPkts OBJECT-TYPE
   SYNTAX      Counter64
   MAX-ACCESS  read-only
   STATUS      current
   DESCRIPTION
      "Path: ethernet3.performance.vlan.mibCounters.ifOutMcastPkts

       64 bit unsigned wrappable counter."
   ::= {pr1645v2Lan3VlanEntry 48431104}

pr1645v2Lan3VlanMCOutDiscards OBJECT-TYPE
   SYNTAX      Counter64
   MAX-ACCESS  read-only
   STATUS      current
   DESCRIPTION
      "Path: ethernet3.performance.vlan.mibCounters.ifOutDiscards

       64 bit unsigned wrappable counter."
   ::= {pr1645v2Lan3VlanEntry 41287680}

pr1645v2Lan3VlanMCOutErrors OBJECT-TYPE
   SYNTAX      Counter64
   MAX-ACCESS  read-only
   STATUS      current
   DESCRIPTION
      "Path: ethernet3.performance.vlan.mibCounters.ifOutErrors

       64 bit unsigned wrappable counter."
   ::= {pr1645v2Lan3VlanEntry 41353216}

pr1645v2Lan3VlanMCOutQLen OBJECT-TYPE
   SYNTAX      Counter32
   MAX-ACCESS  read-only
   STATUS      current
   DESCRIPTION
      "Path: ethernet3.performance.vlan.mibCounters.ifOutQLen

       32 bit unsigned wrappable counter."
   ::= {pr1645v2Lan3VlanEntry 41418752}

pr1645v2Lan3VlanMCOutDropEx OBJECT-TYPE
   SYNTAX      Counter64
   MAX-ACCESS  read-only
   STATUS      current
   DESCRIPTION
      "Path: ethernet3.performance.vlan.mibCounters.ifOutDropLevelExceeded

       64 bit unsigned wrappable counter."
   ::= {pr1645v2Lan3VlanEntry 41484288}

pr1645v2Lan3VlanMCOutDropNoArp OBJECT-TYPE
   SYNTAX      Counter64
   MAX-ACCESS  read-only
   STATUS      current
   DESCRIPTION
      "Path: ethernet3.performance.vlan.mibCounters.ifOutDiscardsNoArp

       64 bit unsigned wrappable counter."
   ::= {pr1645v2Lan3VlanEntry 42336256}

pr1645v2Lan3VlanMCOutDropFilter OBJECT-TYPE
   SYNTAX      Counter64
   MAX-ACCESS  read-only
   STATUS      current
   DESCRIPTION
      "Path: ethernet3.performance.vlan.mibCounters.ifOutDiscardsFilter

       64 bit unsigned wrappable counter."
   ::= {pr1645v2Lan3VlanEntry 42598400}

pr1645v2Lan3VlanMCOutBandwidth15sec OBJECT-TYPE
   SYNTAX      Integer32
   MAX-ACCESS  read-only
   STATUS      current
   DESCRIPTION
      "Path: ethernet3.performance.vlan.mibCounters.ifOutBandwidth.15sec

       unit name = bps
       formula = 8 * ; 8 /"
   ::= {pr1645v2Lan3VlanEntry 45483264}

pr1645v2Lan3VlanMCOutBandwidth30sec OBJECT-TYPE
   SYNTAX      Integer32
   MAX-ACCESS  read-only
   STATUS      current
   DESCRIPTION
      "Path: ethernet3.performance.vlan.mibCounters.ifOutBandwidth.30sec

       unit name = bps
       formula = 8 * ; 8 /"
   ::= {pr1645v2Lan3VlanEntry 45484544}

pr1645v2Lan3VlanMCOutBandwidth1min OBJECT-TYPE
   SYNTAX      Integer32
   MAX-ACCESS  read-only
   STATUS      current
   DESCRIPTION
      "Path: ethernet3.performance.vlan.mibCounters.ifOutBandwidth.1min

       unit name = bps
       formula = 8 * ; 8 /"
   ::= {pr1645v2Lan3VlanEntry 45487104}

pr1645v2Lan3VlanMCOutBandwidth2min OBJECT-TYPE
   SYNTAX      Integer32
   MAX-ACCESS  read-only
   STATUS      current
   DESCRIPTION
      "Path: ethernet3.performance.vlan.mibCounters.ifOutBandwidth.2min

       unit name = bps
       formula = 8 * ; 8 /"
   ::= {pr1645v2Lan3VlanEntry 45492224}

pr1645v2Lan3VlanMCOutBandwidth5min OBJECT-TYPE
   SYNTAX      Integer32
   MAX-ACCESS  read-only
   STATUS      current
   DESCRIPTION
      "Path: ethernet3.performance.vlan.mibCounters.ifOutBandwidth.5min

       unit name = bps
       formula = 8 * ; 8 /"
   ::= {pr1645v2Lan3VlanEntry 45507584}

pr1645v2Lan3VlanVlanVid OBJECT-TYPE
   SYNTAX      Integer32
   MAX-ACCESS  read-only
   STATUS      current
   DESCRIPTION
      "Path: ethernet3.performance.vlan.vlan.vid"
   ::= {pr1645v2Lan3VlanEntry 234946560}

pr1645v2Lan3VlanPppLinkMonitoringRequestsSent OBJECT-TYPE
   SYNTAX      Gauge32
   MAX-ACCESS  read-only
   STATUS      current
   DESCRIPTION
      "Path: ethernet3.performance.vlan.ppp.linkMonitoring.requestsSent

       32 bit unsigned gauge value."
   ::= {pr1645v2Lan3VlanEntry 50397440}

pr1645v2Lan3VlanPppLinkMonitoringRepliesRcvd OBJECT-TYPE
   SYNTAX      Gauge32
   MAX-ACCESS  read-only
   STATUS      current
   DESCRIPTION
      "Path: ethernet3.performance.vlan.ppp.linkMonitoring.repliesRcvd

       32 bit unsigned gauge value."
   ::= {pr1645v2Lan3VlanEntry 50397696}

pr1645v2Lan3VlanPppLinkMonitoringRequestsRcvd OBJECT-TYPE
   SYNTAX      Gauge32
   MAX-ACCESS  read-only
   STATUS      current
   DESCRIPTION
      "Path: ethernet3.performance.vlan.ppp.linkMonitoring.requestsRcvd

       32 bit unsigned gauge value."
   ::= {pr1645v2Lan3VlanEntry 50397952}

pr1645v2Lan3VlanPppLinkMonitoringRepliesSent OBJECT-TYPE
   SYNTAX      Gauge32
   MAX-ACCESS  read-only
   STATUS      current
   DESCRIPTION
      "Path: ethernet3.performance.vlan.ppp.linkMonitoring.repliesSent

       32 bit unsigned gauge value."
   ::= {pr1645v2Lan3VlanEntry 50398208}

pr1645v2Lan3VlanMCH2P OBJECT-TYPE
   SYNTAX      SEQUENCE OF Pr1645v2Lan3VlanMCH2PEntry
   MAX-ACCESS  not-accessible
   STATUS      current
   DESCRIPTION
      ""
   ::= {pr1645v2Lan3Vlan 41549824}

pr1645v2Lan3VlanMCH2PEntry OBJECT-TYPE
   SYNTAX      Pr1645v2Lan3VlanMCH2PEntry
   MAX-ACCESS  not-accessible
   STATUS      current
   DESCRIPTION
      ""
   INDEX      { pr1645v2Lan3VlanTableIx,
                pr1645v2Lan3VlanMCH2PTableIx }
   ::= {pr1645v2Lan3VlanMCH2P 1}

Pr1645v2Lan3VlanMCH2PEntry ::=
   SEQUENCE
      {
      pr1645v2Lan3VlanMCH2PTableIx
         TableIndex,
      pr1645v2Lan3VlanMCH2PSysUpTime
         TimeTicks,
      pr1645v2Lan3VlanMCH2PIfUpTime
         TimeTicks,
      pr1645v2Lan3VlanMCH2PIfStatChanges
         Counter32,
      pr1645v2Lan3VlanMCH2PIfInOctets
         Counter64,
      pr1645v2Lan3VlanMCH2PIfInUCPkts
         Counter64,
      pr1645v2Lan3VlanMCH2PIfInNUCPkts
         Counter64,
      pr1645v2Lan3VlanMCH2PIfInBCPkts
         Counter64,
      pr1645v2Lan3VlanMCH2PIfInMCPkts
         Counter64,
      pr1645v2Lan3VlanMCH2PIfInDiscards
         Counter64,
      pr1645v2Lan3VlanMCH2PIfInErrors
         Counter64,
      pr1645v2Lan3VlanMCH2PIfInUnkwn
         Counter64,
      pr1645v2Lan3VlanMCH2PInDropEx
         Counter64,
      pr1645v2Lan3VlanMCH2PInDropNoMac
         Counter64,
      pr1645v2Lan3VlanMCH2PInDropNUCast
         Counter64,
      pr1645v2Lan3VlanMCH2PInDropFilter
         Counter64,
      pr1645v2Lan3VlanMCH2PIfInBandwidth
         Integer32,
      pr1645v2Lan3VlanMCH2PIfOutOctets
         Counter64,
      pr1645v2Lan3VlanMCH2PIfOutUCPkts
         Counter64,
      pr1645v2Lan3VlanMCH2PIfOutNUCPkts
         Counter64,
      pr1645v2Lan3VlanMCH2PIfOutBCPkts
         Counter64,
      pr1645v2Lan3VlanMCH2PIfOutMCPkts
         Counter64,
      pr1645v2Lan3VlanMCH2PIfOutDiscards
         Counter64,
      pr1645v2Lan3VlanMCH2PIfOutErrors
         Counter64,
      pr1645v2Lan3VlanMCH2POutDropEx
         Counter64,
      pr1645v2Lan3VlanMCH2POutDropNoArp
         Counter64,
      pr1645v2Lan3VlanMCH2POutDropFilter
         Counter64,
      pr1645v2Lan3VlanMCH2PIfOutBandwidth
         Integer32,
      pr1645v2Lan3VlanMCH2PIfErrSec
         Counter32
      }

pr1645v2Lan3VlanMCH2PTableIx OBJECT-TYPE
   SYNTAX      TableIndex
   MAX-ACCESS  not-accessible
   STATUS      current
   DESCRIPTION
      ""
   ::= {pr1645v2Lan3VlanMCH2PEntry 11}

pr1645v2Lan3VlanMCH2PSysUpTime OBJECT-TYPE
   SYNTAX      TimeTicks
   MAX-ACCESS  read-only
   STATUS      current
   DESCRIPTION
      "Path: ethernet3.performance.vlan.mibCounters.h2Performance.sysUpTime

       Time in centi-second."
   ::= {pr1645v2Lan3VlanMCH2PEntry 16777216}

pr1645v2Lan3VlanMCH2PIfUpTime OBJECT-TYPE
   SYNTAX      TimeTicks
   MAX-ACCESS  read-only
   STATUS      current
   DESCRIPTION
      "Path: ethernet3.performance.vlan.mibCounters.h2Performance.ifUpTime

       Time in centi-second."
   ::= {pr1645v2Lan3VlanMCH2PEntry 33554432}

pr1645v2Lan3VlanMCH2PIfStatChanges OBJECT-TYPE
   SYNTAX      Counter32
   MAX-ACCESS  read-only
   STATUS      current
   DESCRIPTION
      "Path: ethernet3.performance.vlan.mibCounters.h2Performance.ifStatusChanges

       32 bit unsigned wrappable counter."
   ::= {pr1645v2Lan3VlanMCH2PEntry 50331648}

pr1645v2Lan3VlanMCH2PIfInOctets OBJECT-TYPE
   SYNTAX      Counter64
   MAX-ACCESS  read-only
   STATUS      current
   DESCRIPTION
      "Path: ethernet3.performance.vlan.mibCounters.h2Performance.ifInOctets

       64 bit unsigned wrappable counter."
   ::= {pr1645v2Lan3VlanMCH2PEntry 67108864}

pr1645v2Lan3VlanMCH2PIfInUCPkts OBJECT-TYPE
   SYNTAX      Counter64
   MAX-ACCESS  read-only
   STATUS      current
   DESCRIPTION
      "Path: ethernet3.performance.vlan.mibCounters.h2Performance.ifInUcastPkts

       64 bit unsigned wrappable counter."
   ::= {pr1645v2Lan3VlanMCH2PEntry 83886080}

pr1645v2Lan3VlanMCH2PIfInNUCPkts OBJECT-TYPE
   SYNTAX      Counter64
   MAX-ACCESS  read-only
   STATUS      current
   DESCRIPTION
      "Path: ethernet3.performance.vlan.mibCounters.h2Performance.ifInNUcastPkts

       64 bit unsigned wrappable counter."
   ::= {pr1645v2Lan3VlanMCH2PEntry 100663296}

pr1645v2Lan3VlanMCH2PIfInBCPkts OBJECT-TYPE
   SYNTAX      Counter64
   MAX-ACCESS  read-only
   STATUS      current
   DESCRIPTION
      "Path: ethernet3.performance.vlan.mibCounters.h2Performance.ifInBcastPkts

       64 bit unsigned wrappable counter."
   ::= {pr1645v2Lan3VlanMCH2PEntry 419430400}

pr1645v2Lan3VlanMCH2PIfInMCPkts OBJECT-TYPE
   SYNTAX      Counter64
   MAX-ACCESS  read-only
   STATUS      current
   DESCRIPTION
      "Path: ethernet3.performance.vlan.mibCounters.h2Performance.ifInMcastPkts

       64 bit unsigned wrappable counter."
   ::= {pr1645v2Lan3VlanMCH2PEntry 436207616}

pr1645v2Lan3VlanMCH2PIfInDiscards OBJECT-TYPE
   SYNTAX      Counter64
   MAX-ACCESS  read-only
   STATUS      current
   DESCRIPTION
      "Path: ethernet3.performance.vlan.mibCounters.h2Performance.ifInDiscards

       64 bit unsigned wrappable counter."
   ::= {pr1645v2Lan3VlanMCH2PEntry 117440512}

pr1645v2Lan3VlanMCH2PIfInErrors OBJECT-TYPE
   SYNTAX      Counter64
   MAX-ACCESS  read-only
   STATUS      current
   DESCRIPTION
      "Path: ethernet3.performance.vlan.mibCounters.h2Performance.ifInErrors

       64 bit unsigned wrappable counter."
   ::= {pr1645v2Lan3VlanMCH2PEntry 134217728}

pr1645v2Lan3VlanMCH2PIfInUnkwn OBJECT-TYPE
   SYNTAX      Counter64
   MAX-ACCESS  read-only
   STATUS      current
   DESCRIPTION
      "Path: ethernet3.performance.vlan.mibCounters.h2Performance.ifInUnknownProtos

       64 bit unsigned wrappable counter."
   ::= {pr1645v2Lan3VlanMCH2PEntry 150994944}

pr1645v2Lan3VlanMCH2PInDropEx OBJECT-TYPE
   SYNTAX      Counter64
   MAX-ACCESS  read-only
   STATUS      current
   DESCRIPTION
      "Path: ethernet3.performance.vlan.mibCounters.h2Performance.ifInDropLevelExceeded

       64 bit unsigned wrappable counter."
   ::= {pr1645v2Lan3VlanMCH2PEntry 335544320}

pr1645v2Lan3VlanMCH2PInDropNoMac OBJECT-TYPE
   SYNTAX      Counter64
   MAX-ACCESS  read-only
   STATUS      current
   DESCRIPTION
      "Path: ethernet3.performance.vlan.mibCounters.h2Performance.fInDiscardsNoMacFit

       64 bit unsigned wrappable counter."
   ::= {pr1645v2Lan3VlanMCH2PEntry 301989888}

pr1645v2Lan3VlanMCH2PInDropNUCast OBJECT-TYPE
   SYNTAX      Counter64
   MAX-ACCESS  read-only
   STATUS      current
   DESCRIPTION
      "Path: ethernet3.performance.vlan.mibCounters.h2Performance.fInDiscardsNUCast

       64 bit unsigned wrappable counter."
   ::= {pr1645v2Lan3VlanMCH2PEntry 318767104}

pr1645v2Lan3VlanMCH2PInDropFilter OBJECT-TYPE
   SYNTAX      Counter64
   MAX-ACCESS  read-only
   STATUS      current
   DESCRIPTION
      "Path: ethernet3.performance.vlan.mibCounters.h2Performance.fInDiscardsFilter

       64 bit unsigned wrappable counter."
   ::= {pr1645v2Lan3VlanMCH2PEntry 385875968}

pr1645v2Lan3VlanMCH2PIfInBandwidth OBJECT-TYPE
   SYNTAX      Integer32
   MAX-ACCESS  read-only
   STATUS      current
   DESCRIPTION
      "Path: ethernet3.performance.vlan.mibCounters.h2Performance.ifInBandwidth

       unit name = bps
       formula = 8 * ; 8 /"
   ::= {pr1645v2Lan3VlanMCH2PEntry 268435456}

pr1645v2Lan3VlanMCH2PIfOutOctets OBJECT-TYPE
   SYNTAX      Counter64
   MAX-ACCESS  read-only
   STATUS      current
   DESCRIPTION
      "Path: ethernet3.performance.vlan.mibCounters.h2Performance.ifOutOctets

       64 bit unsigned wrappable counter."
   ::= {pr1645v2Lan3VlanMCH2PEntry 167772160}

pr1645v2Lan3VlanMCH2PIfOutUCPkts OBJECT-TYPE
   SYNTAX      Counter64
   MAX-ACCESS  read-only
   STATUS      current
   DESCRIPTION
      "Path: ethernet3.performance.vlan.mibCounters.h2Performance.ifOutUcastPkts

       64 bit unsigned wrappable counter."
   ::= {pr1645v2Lan3VlanMCH2PEntry 184549376}

pr1645v2Lan3VlanMCH2PIfOutNUCPkts OBJECT-TYPE
   SYNTAX      Counter64
   MAX-ACCESS  read-only
   STATUS      current
   DESCRIPTION
      "Path: ethernet3.performance.vlan.mibCounters.h2Performance.ifOutNUcastPkts

       64 bit unsigned wrappable counter."
   ::= {pr1645v2Lan3VlanMCH2PEntry 201326592}

pr1645v2Lan3VlanMCH2PIfOutBCPkts OBJECT-TYPE
   SYNTAX      Counter64
   MAX-ACCESS  read-only
   STATUS      current
   DESCRIPTION
      "Path: ethernet3.performance.vlan.mibCounters.h2Performance.ifOutBcastPkts

       64 bit unsigned wrappable counter."
   ::= {pr1645v2Lan3VlanMCH2PEntry 452984832}

pr1645v2Lan3VlanMCH2PIfOutMCPkts OBJECT-TYPE
   SYNTAX      Counter64
   MAX-ACCESS  read-only
   STATUS      current
   DESCRIPTION
      "Path: ethernet3.performance.vlan.mibCounters.h2Performance.ifOutMcastPkts

       64 bit unsigned wrappable counter."
   ::= {pr1645v2Lan3VlanMCH2PEntry 469762048}

pr1645v2Lan3VlanMCH2PIfOutDiscards OBJECT-TYPE
   SYNTAX      Counter64
   MAX-ACCESS  read-only
   STATUS      current
   DESCRIPTION
      "Path: ethernet3.performance.vlan.mibCounters.h2Performance.ifOutDiscards

       64 bit unsigned wrappable counter."
   ::= {pr1645v2Lan3VlanMCH2PEntry 218103808}

pr1645v2Lan3VlanMCH2PIfOutErrors OBJECT-TYPE
   SYNTAX      Counter64
   MAX-ACCESS  read-only
   STATUS      current
   DESCRIPTION
      "Path: ethernet3.performance.vlan.mibCounters.h2Performance.ifOutErrors

       64 bit unsigned wrappable counter."
   ::= {pr1645v2Lan3VlanMCH2PEntry 234881024}

pr1645v2Lan3VlanMCH2POutDropEx OBJECT-TYPE
   SYNTAX      Counter64
   MAX-ACCESS  read-only
   STATUS      current
   DESCRIPTION
      "Path: ethernet3.performance.vlan.mibCounters.h2Performance.ifOutDropLevelExceeded

       64 bit unsigned wrappable counter."
   ::= {pr1645v2Lan3VlanMCH2PEntry 352321536}

pr1645v2Lan3VlanMCH2POutDropNoArp OBJECT-TYPE
   SYNTAX      Counter64
   MAX-ACCESS  read-only
   STATUS      current
   DESCRIPTION
      "Path: ethernet3.performance.vlan.mibCounters.h2Performance.ifOutDiscardsNoArp

       64 bit unsigned wrappable counter."
   ::= {pr1645v2Lan3VlanMCH2PEntry 369098752}

pr1645v2Lan3VlanMCH2POutDropFilter OBJECT-TYPE
   SYNTAX      Counter64
   MAX-ACCESS  read-only
   STATUS      current
   DESCRIPTION
      "Path: ethernet3.performance.vlan.mibCounters.h2Performance.ifOutDiscardsFilter

       64 bit unsigned wrappable counter."
   ::= {pr1645v2Lan3VlanMCH2PEntry 402653184}

pr1645v2Lan3VlanMCH2PIfOutBandwidth OBJECT-TYPE
   SYNTAX      Integer32
   MAX-ACCESS  read-only
   STATUS      current
   DESCRIPTION
      "Path: ethernet3.performance.vlan.mibCounters.h2Performance.ifOutBandwidth

       unit name = bps
       formula = 8 * ; 8 /"
   ::= {pr1645v2Lan3VlanMCH2PEntry 285212672}

pr1645v2Lan3VlanMCH2PIfErrSec OBJECT-TYPE
   SYNTAX      Counter32
   MAX-ACCESS  read-only
   STATUS      current
   DESCRIPTION
      "Path: ethernet3.performance.vlan.mibCounters.h2Performance.ifErrSec

       32 bit unsigned wrappable counter."
   ::= {pr1645v2Lan3VlanMCH2PEntry 251658240}

pr1645v2Lan3VlanMCH24P OBJECT-TYPE
   SYNTAX      SEQUENCE OF Pr1645v2Lan3VlanMCH24PEntry
   MAX-ACCESS  not-accessible
   STATUS      current
   DESCRIPTION
      ""
   ::= {pr1645v2Lan3Vlan 41615360}

pr1645v2Lan3VlanMCH24PEntry OBJECT-TYPE
   SYNTAX      Pr1645v2Lan3VlanMCH24PEntry
   MAX-ACCESS  not-accessible
   STATUS      current
   DESCRIPTION
      ""
   INDEX      { pr1645v2Lan3VlanTableIx,
                pr1645v2Lan3VlanMCH24PTableIx }
   ::= {pr1645v2Lan3VlanMCH24P 1}

Pr1645v2Lan3VlanMCH24PEntry ::=
   SEQUENCE
      {
      pr1645v2Lan3VlanMCH24PTableIx
         TableIndex,
      pr1645v2Lan3VlanMCH24PSysUpTime
         TimeTicks,
      pr1645v2Lan3VlanMCH24PIfUpTime
         TimeTicks,
      pr1645v2Lan3VlanMCH24PIfStatChanges
         Counter32,
      pr1645v2Lan3VlanMCH24PIfInOctets
         Counter64,
      pr1645v2Lan3VlanMCH24PIfInUCPkts
         Counter64,
      pr1645v2Lan3VlanMCH24PIfInNUCPkts
         Counter64,
      pr1645v2Lan3VlanMCH24PIfInBCPkts
         Counter64,
      pr1645v2Lan3VlanMCH24PIfInMCPkts
         Counter64,
      pr1645v2Lan3VlanMCH24PIfInDiscards
         Counter64,
      pr1645v2Lan3VlanMCH24PIfInErrors
         Counter64,
      pr1645v2Lan3VlanMCH24PIfInUnkwn
         Counter64,
      pr1645v2Lan3VlanMCH24PInDropEx
         Counter64,
      pr1645v2Lan3VlanMCH24PInDropNoMac
         Counter64,
      pr1645v2Lan3VlanMCH24PInDropNUCast
         Counter64,
      pr1645v2Lan3VlanMCH24PInDropFilter
         Counter64,
      pr1645v2Lan3VlanMCH24PIfInBandwidth
         Integer32,
      pr1645v2Lan3VlanMCH24PIfOutOctets
         Counter64,
      pr1645v2Lan3VlanMCH24PIfOutUCPkts
         Counter64,
      pr1645v2Lan3VlanMCH24PIfOutNUCPkts
         Counter64,
      pr1645v2Lan3VlanMCH24PIfOutBCPkts
         Counter64,
      pr1645v2Lan3VlanMCH24PIfOutMCPkts
         Counter64,
      pr1645v2Lan3VlanMCH24PIfOutDiscards
         Counter64,
      pr1645v2Lan3VlanMCH24PIfOutErrors
         Counter64,
      pr1645v2Lan3VlanMCH24POutDropEx
         Counter64,
      pr1645v2Lan3VlanMCH24POutDropNoArp
         Counter64,
      pr1645v2Lan3VlanMCH24POutDropFilter
         Counter64,
      pr1645v2Lan3VlanMCH24PIfOutBandwidth
         Integer32,
      pr1645v2Lan3VlanMCH24PIfErrSec
         Counter32
      }

pr1645v2Lan3VlanMCH24PTableIx OBJECT-TYPE
   SYNTAX      TableIndex
   MAX-ACCESS  not-accessible
   STATUS      current
   DESCRIPTION
      ""
   ::= {pr1645v2Lan3VlanMCH24PEntry 11}

pr1645v2Lan3VlanMCH24PSysUpTime OBJECT-TYPE
   SYNTAX      TimeTicks
   MAX-ACCESS  read-only
   STATUS      current
   DESCRIPTION
      "Path: ethernet3.performance.vlan.mibCounters.h24Performance.sysUpTime

       Time in centi-second."
   ::= {pr1645v2Lan3VlanMCH24PEntry 16777216}

pr1645v2Lan3VlanMCH24PIfUpTime OBJECT-TYPE
   SYNTAX      TimeTicks
   MAX-ACCESS  read-only
   STATUS      current
   DESCRIPTION
      "Path: ethernet3.performance.vlan.mibCounters.h24Performance.ifUpTime

       Time in centi-second."
   ::= {pr1645v2Lan3VlanMCH24PEntry 33554432}

pr1645v2Lan3VlanMCH24PIfStatChanges OBJECT-TYPE
   SYNTAX      Counter32
   MAX-ACCESS  read-only
   STATUS      current
   DESCRIPTION
      "Path: ethernet3.performance.vlan.mibCounters.h24Performance.ifStatusChanges

       32 bit unsigned wrappable counter."
   ::= {pr1645v2Lan3VlanMCH24PEntry 50331648}

pr1645v2Lan3VlanMCH24PIfInOctets OBJECT-TYPE
   SYNTAX      Counter64
   MAX-ACCESS  read-only
   STATUS      current
   DESCRIPTION
      "Path: ethernet3.performance.vlan.mibCounters.h24Performance.ifInOctets

       64 bit unsigned wrappable counter."
   ::= {pr1645v2Lan3VlanMCH24PEntry 67108864}

pr1645v2Lan3VlanMCH24PIfInUCPkts OBJECT-TYPE
   SYNTAX      Counter64
   MAX-ACCESS  read-only
   STATUS      current
   DESCRIPTION
      "Path: ethernet3.performance.vlan.mibCounters.h24Performance.ifInUcastPkts

       64 bit unsigned wrappable counter."
   ::= {pr1645v2Lan3VlanMCH24PEntry 83886080}

pr1645v2Lan3VlanMCH24PIfInNUCPkts OBJECT-TYPE
   SYNTAX      Counter64
   MAX-ACCESS  read-only
   STATUS      current
   DESCRIPTION
      "Path: ethernet3.performance.vlan.mibCounters.h24Performance.ifInNUcastPkts

       64 bit unsigned wrappable counter."
   ::= {pr1645v2Lan3VlanMCH24PEntry 100663296}

pr1645v2Lan3VlanMCH24PIfInBCPkts OBJECT-TYPE
   SYNTAX      Counter64
   MAX-ACCESS  read-only
   STATUS      current
   DESCRIPTION
      "Path: ethernet3.performance.vlan.mibCounters.h24Performance.ifInBcastPkts

       64 bit unsigned wrappable counter."
   ::= {pr1645v2Lan3VlanMCH24PEntry 419430400}

pr1645v2Lan3VlanMCH24PIfInMCPkts OBJECT-TYPE
   SYNTAX      Counter64
   MAX-ACCESS  read-only
   STATUS      current
   DESCRIPTION
      "Path: ethernet3.performance.vlan.mibCounters.h24Performance.ifInMcastPkts

       64 bit unsigned wrappable counter."
   ::= {pr1645v2Lan3VlanMCH24PEntry 436207616}

pr1645v2Lan3VlanMCH24PIfInDiscards OBJECT-TYPE
   SYNTAX      Counter64
   MAX-ACCESS  read-only
   STATUS      current
   DESCRIPTION
      "Path: ethernet3.performance.vlan.mibCounters.h24Performance.ifInDiscards

       64 bit unsigned wrappable counter."
   ::= {pr1645v2Lan3VlanMCH24PEntry 117440512}

pr1645v2Lan3VlanMCH24PIfInErrors OBJECT-TYPE
   SYNTAX      Counter64
   MAX-ACCESS  read-only
   STATUS      current
   DESCRIPTION
      "Path: ethernet3.performance.vlan.mibCounters.h24Performance.ifInErrors

       64 bit unsigned wrappable counter."
   ::= {pr1645v2Lan3VlanMCH24PEntry 134217728}

pr1645v2Lan3VlanMCH24PIfInUnkwn OBJECT-TYPE
   SYNTAX      Counter64
   MAX-ACCESS  read-only
   STATUS      current
   DESCRIPTION
      "Path: ethernet3.performance.vlan.mibCounters.h24Performance.ifInUnknownProtos

       64 bit unsigned wrappable counter."
   ::= {pr1645v2Lan3VlanMCH24PEntry 150994944}

pr1645v2Lan3VlanMCH24PInDropEx OBJECT-TYPE
   SYNTAX      Counter64
   MAX-ACCESS  read-only
   STATUS      current
   DESCRIPTION
      "Path: ethernet3.performance.vlan.mibCounters.h24Performance.ifInDropLevelExceeded

       64 bit unsigned wrappable counter."
   ::= {pr1645v2Lan3VlanMCH24PEntry 335544320}

pr1645v2Lan3VlanMCH24PInDropNoMac OBJECT-TYPE
   SYNTAX      Counter64
   MAX-ACCESS  read-only
   STATUS      current
   DESCRIPTION
      "Path: ethernet3.performance.vlan.mibCounters.h24Performance.fInDiscardsNoMacFit

       64 bit unsigned wrappable counter."
   ::= {pr1645v2Lan3VlanMCH24PEntry 301989888}

pr1645v2Lan3VlanMCH24PInDropNUCast OBJECT-TYPE
   SYNTAX      Counter64
   MAX-ACCESS  read-only
   STATUS      current
   DESCRIPTION
      "Path: ethernet3.performance.vlan.mibCounters.h24Performance.fInDiscardsNUCast

       64 bit unsigned wrappable counter."
   ::= {pr1645v2Lan3VlanMCH24PEntry 318767104}

pr1645v2Lan3VlanMCH24PInDropFilter OBJECT-TYPE
   SYNTAX      Counter64
   MAX-ACCESS  read-only
   STATUS      current
   DESCRIPTION
      "Path: ethernet3.performance.vlan.mibCounters.h24Performance.fInDiscardsFilter

       64 bit unsigned wrappable counter."
   ::= {pr1645v2Lan3VlanMCH24PEntry 385875968}

pr1645v2Lan3VlanMCH24PIfInBandwidth OBJECT-TYPE
   SYNTAX      Integer32
   MAX-ACCESS  read-only
   STATUS      current
   DESCRIPTION
      "Path: ethernet3.performance.vlan.mibCounters.h24Performance.ifInBandwidth

       unit name = bps
       formula = 8 * ; 8 /"
   ::= {pr1645v2Lan3VlanMCH24PEntry 268435456}

pr1645v2Lan3VlanMCH24PIfOutOctets OBJECT-TYPE
   SYNTAX      Counter64
   MAX-ACCESS  read-only
   STATUS      current
   DESCRIPTION
      "Path: ethernet3.performance.vlan.mibCounters.h24Performance.ifOutOctets

       64 bit unsigned wrappable counter."
   ::= {pr1645v2Lan3VlanMCH24PEntry 167772160}

pr1645v2Lan3VlanMCH24PIfOutUCPkts OBJECT-TYPE
   SYNTAX      Counter64
   MAX-ACCESS  read-only
   STATUS      current
   DESCRIPTION
      "Path: ethernet3.performance.vlan.mibCounters.h24Performance.ifOutUcastPkts

       64 bit unsigned wrappable counter."
   ::= {pr1645v2Lan3VlanMCH24PEntry 184549376}

pr1645v2Lan3VlanMCH24PIfOutNUCPkts OBJECT-TYPE
   SYNTAX      Counter64
   MAX-ACCESS  read-only
   STATUS      current
   DESCRIPTION
      "Path: ethernet3.performance.vlan.mibCounters.h24Performance.ifOutNUcastPkts

       64 bit unsigned wrappable counter."
   ::= {pr1645v2Lan3VlanMCH24PEntry 201326592}

pr1645v2Lan3VlanMCH24PIfOutBCPkts OBJECT-TYPE
   SYNTAX      Counter64
   MAX-ACCESS  read-only
   STATUS      current
   DESCRIPTION
      "Path: ethernet3.performance.vlan.mibCounters.h24Performance.ifOutBcastPkts

       64 bit unsigned wrappable counter."
   ::= {pr1645v2Lan3VlanMCH24PEntry 452984832}

pr1645v2Lan3VlanMCH24PIfOutMCPkts OBJECT-TYPE
   SYNTAX      Counter64
   MAX-ACCESS  read-only
   STATUS      current
   DESCRIPTION
      "Path: ethernet3.performance.vlan.mibCounters.h24Performance.ifOutMcastPkts

       64 bit unsigned wrappable counter."
   ::= {pr1645v2Lan3VlanMCH24PEntry 469762048}

pr1645v2Lan3VlanMCH24PIfOutDiscards OBJECT-TYPE
   SYNTAX      Counter64
   MAX-ACCESS  read-only
   STATUS      current
   DESCRIPTION
      "Path: ethernet3.performance.vlan.mibCounters.h24Performance.ifOutDiscards

       64 bit unsigned wrappable counter."
   ::= {pr1645v2Lan3VlanMCH24PEntry 218103808}

pr1645v2Lan3VlanMCH24PIfOutErrors OBJECT-TYPE
   SYNTAX      Counter64
   MAX-ACCESS  read-only
   STATUS      current
   DESCRIPTION
      "Path: ethernet3.performance.vlan.mibCounters.h24Performance.ifOutErrors

       64 bit unsigned wrappable counter."
   ::= {pr1645v2Lan3VlanMCH24PEntry 234881024}

pr1645v2Lan3VlanMCH24POutDropEx OBJECT-TYPE
   SYNTAX      Counter64
   MAX-ACCESS  read-only
   STATUS      current
   DESCRIPTION
      "Path: ethernet3.performance.vlan.mibCounters.h24Performance.ifOutDropLevelExceeded

       64 bit unsigned wrappable counter."
   ::= {pr1645v2Lan3VlanMCH24PEntry 352321536}

pr1645v2Lan3VlanMCH24POutDropNoArp OBJECT-TYPE
   SYNTAX      Counter64
   MAX-ACCESS  read-only
   STATUS      current
   DESCRIPTION
      "Path: ethernet3.performance.vlan.mibCounters.h24Performance.ifOutDiscardsNoArp

       64 bit unsigned wrappable counter."
   ::= {pr1645v2Lan3VlanMCH24PEntry 369098752}

pr1645v2Lan3VlanMCH24POutDropFilter OBJECT-TYPE
   SYNTAX      Counter64
   MAX-ACCESS  read-only
   STATUS      current
   DESCRIPTION
      "Path: ethernet3.performance.vlan.mibCounters.h24Performance.ifOutDiscardsFilter

       64 bit unsigned wrappable counter."
   ::= {pr1645v2Lan3VlanMCH24PEntry 402653184}

pr1645v2Lan3VlanMCH24PIfOutBandwidth OBJECT-TYPE
   SYNTAX      Integer32
   MAX-ACCESS  read-only
   STATUS      current
   DESCRIPTION
      "Path: ethernet3.performance.vlan.mibCounters.h24Performance.ifOutBandwidth

       unit name = bps
       formula = 8 * ; 8 /"
   ::= {pr1645v2Lan3VlanMCH24PEntry 285212672}

pr1645v2Lan3VlanMCH24PIfErrSec OBJECT-TYPE
   SYNTAX      Counter32
   MAX-ACCESS  read-only
   STATUS      current
   DESCRIPTION
      "Path: ethernet3.performance.vlan.mibCounters.h24Performance.ifErrSec

       32 bit unsigned wrappable counter."
   ::= {pr1645v2Lan3VlanMCH24PEntry 251658240}

pr1645v2Lan3VlanMCD7P OBJECT-TYPE
   SYNTAX      SEQUENCE OF Pr1645v2Lan3VlanMCD7PEntry
   MAX-ACCESS  not-accessible
   STATUS      current
   DESCRIPTION
      ""
   ::= {pr1645v2Lan3Vlan 41680896}

pr1645v2Lan3VlanMCD7PEntry OBJECT-TYPE
   SYNTAX      Pr1645v2Lan3VlanMCD7PEntry
   MAX-ACCESS  not-accessible
   STATUS      current
   DESCRIPTION
      ""
   INDEX      { pr1645v2Lan3VlanTableIx,
                pr1645v2Lan3VlanMCD7PTableIx }
   ::= {pr1645v2Lan3VlanMCD7P 1}

Pr1645v2Lan3VlanMCD7PEntry ::=
   SEQUENCE
      {
      pr1645v2Lan3VlanMCD7PTableIx
         TableIndex,
      pr1645v2Lan3VlanMCD7PSysUpTime
         TimeTicks,
      pr1645v2Lan3VlanMCD7PIfUpTime
         TimeTicks,
      pr1645v2Lan3VlanMCD7PIfStatChanges
         Counter32,
      pr1645v2Lan3VlanMCD7PIfInOctets
         Counter64,
      pr1645v2Lan3VlanMCD7PIfInUCPkts
         Counter64,
      pr1645v2Lan3VlanMCD7PIfInNUCPkts
         Counter64,
      pr1645v2Lan3VlanMCD7PIfInBCPkts
         Counter64,
      pr1645v2Lan3VlanMCD7PIfInMCPkts
         Counter64,
      pr1645v2Lan3VlanMCD7PIfInDiscards
         Counter64,
      pr1645v2Lan3VlanMCD7PIfInErrors
         Counter64,
      pr1645v2Lan3VlanMCD7PIfInUnkwn
         Counter64,
      pr1645v2Lan3VlanMCD7PInDropEx
         Counter64,
      pr1645v2Lan3VlanMCD7PInDropNoMac
         Counter64,
      pr1645v2Lan3VlanMCD7PInDropNUCast
         Counter64,
      pr1645v2Lan3VlanMCD7PInDropFilter
         Counter64,
      pr1645v2Lan3VlanMCD7PIfInBandwidth
         Integer32,
      pr1645v2Lan3VlanMCD7PIfOutOctets
         Counter64,
      pr1645v2Lan3VlanMCD7PIfOutUCPkts
         Counter64,
      pr1645v2Lan3VlanMCD7PIfOutNUCPkts
         Counter64,
      pr1645v2Lan3VlanMCD7PIfOutBCPkts
         Counter64,
      pr1645v2Lan3VlanMCD7PIfOutMCPkts
         Counter64,
      pr1645v2Lan3VlanMCD7PIfOutDiscards
         Counter64,
      pr1645v2Lan3VlanMCD7PIfOutErrors
         Counter64,
      pr1645v2Lan3VlanMCD7POutDropEx
         Counter64,
      pr1645v2Lan3VlanMCD7POutDropNoArp
         Counter64,
      pr1645v2Lan3VlanMCD7POutDropFilter
         Counter64,
      pr1645v2Lan3VlanMCD7PIfOutBandwidth
         Integer32,
      pr1645v2Lan3VlanMCD7PIfErrSec
         Counter32
      }

pr1645v2Lan3VlanMCD7PTableIx OBJECT-TYPE
   SYNTAX      TableIndex
   MAX-ACCESS  not-accessible
   STATUS      current
   DESCRIPTION
      ""
   ::= {pr1645v2Lan3VlanMCD7PEntry 11}

pr1645v2Lan3VlanMCD7PSysUpTime OBJECT-TYPE
   SYNTAX      TimeTicks
   MAX-ACCESS  read-only
   STATUS      current
   DESCRIPTION
      "Path: ethernet3.performance.vlan.mibCounters.d7Performance.sysUpTime

       Time in centi-second."
   ::= {pr1645v2Lan3VlanMCD7PEntry 16777216}

pr1645v2Lan3VlanMCD7PIfUpTime OBJECT-TYPE
   SYNTAX      TimeTicks
   MAX-ACCESS  read-only
   STATUS      current
   DESCRIPTION
      "Path: ethernet3.performance.vlan.mibCounters.d7Performance.ifUpTime

       Time in centi-second."
   ::= {pr1645v2Lan3VlanMCD7PEntry 33554432}

pr1645v2Lan3VlanMCD7PIfStatChanges OBJECT-TYPE
   SYNTAX      Counter32
   MAX-ACCESS  read-only
   STATUS      current
   DESCRIPTION
      "Path: ethernet3.performance.vlan.mibCounters.d7Performance.ifStatusChanges

       32 bit unsigned wrappable counter."
   ::= {pr1645v2Lan3VlanMCD7PEntry 50331648}

pr1645v2Lan3VlanMCD7PIfInOctets OBJECT-TYPE
   SYNTAX      Counter64
   MAX-ACCESS  read-only
   STATUS      current
   DESCRIPTION
      "Path: ethernet3.performance.vlan.mibCounters.d7Performance.ifInOctets

       64 bit unsigned wrappable counter."
   ::= {pr1645v2Lan3VlanMCD7PEntry 67108864}

pr1645v2Lan3VlanMCD7PIfInUCPkts OBJECT-TYPE
   SYNTAX      Counter64
   MAX-ACCESS  read-only
   STATUS      current
   DESCRIPTION
      "Path: ethernet3.performance.vlan.mibCounters.d7Performance.ifInUcastPkts

       64 bit unsigned wrappable counter."
   ::= {pr1645v2Lan3VlanMCD7PEntry 83886080}

pr1645v2Lan3VlanMCD7PIfInNUCPkts OBJECT-TYPE
   SYNTAX      Counter64
   MAX-ACCESS  read-only
   STATUS      current
   DESCRIPTION
      "Path: ethernet3.performance.vlan.mibCounters.d7Performance.ifInNUcastPkts

       64 bit unsigned wrappable counter."
   ::= {pr1645v2Lan3VlanMCD7PEntry 100663296}

pr1645v2Lan3VlanMCD7PIfInBCPkts OBJECT-TYPE
   SYNTAX      Counter64
   MAX-ACCESS  read-only
   STATUS      current
   DESCRIPTION
      "Path: ethernet3.performance.vlan.mibCounters.d7Performance.ifInBcastPkts

       64 bit unsigned wrappable counter."
   ::= {pr1645v2Lan3VlanMCD7PEntry 419430400}

pr1645v2Lan3VlanMCD7PIfInMCPkts OBJECT-TYPE
   SYNTAX      Counter64
   MAX-ACCESS  read-only
   STATUS      current
   DESCRIPTION
      "Path: ethernet3.performance.vlan.mibCounters.d7Performance.ifInMcastPkts

       64 bit unsigned wrappable counter."
   ::= {pr1645v2Lan3VlanMCD7PEntry 436207616}

pr1645v2Lan3VlanMCD7PIfInDiscards OBJECT-TYPE
   SYNTAX      Counter64
   MAX-ACCESS  read-only
   STATUS      current
   DESCRIPTION
      "Path: ethernet3.performance.vlan.mibCounters.d7Performance.ifInDiscards

       64 bit unsigned wrappable counter."
   ::= {pr1645v2Lan3VlanMCD7PEntry 117440512}

pr1645v2Lan3VlanMCD7PIfInErrors OBJECT-TYPE
   SYNTAX      Counter64
   MAX-ACCESS  read-only
   STATUS      current
   DESCRIPTION
      "Path: ethernet3.performance.vlan.mibCounters.d7Performance.ifInErrors

       64 bit unsigned wrappable counter."
   ::= {pr1645v2Lan3VlanMCD7PEntry 134217728}

pr1645v2Lan3VlanMCD7PIfInUnkwn OBJECT-TYPE
   SYNTAX      Counter64
   MAX-ACCESS  read-only
   STATUS      current
   DESCRIPTION
      "Path: ethernet3.performance.vlan.mibCounters.d7Performance.ifInUnknownProtos

       64 bit unsigned wrappable counter."
   ::= {pr1645v2Lan3VlanMCD7PEntry 150994944}

pr1645v2Lan3VlanMCD7PInDropEx OBJECT-TYPE
   SYNTAX      Counter64
   MAX-ACCESS  read-only
   STATUS      current
   DESCRIPTION
      "Path: ethernet3.performance.vlan.mibCounters.d7Performance.ifInDropLevelExceeded

       64 bit unsigned wrappable counter."
   ::= {pr1645v2Lan3VlanMCD7PEntry 335544320}

pr1645v2Lan3VlanMCD7PInDropNoMac OBJECT-TYPE
   SYNTAX      Counter64
   MAX-ACCESS  read-only
   STATUS      current
   DESCRIPTION
      "Path: ethernet3.performance.vlan.mibCounters.d7Performance.fInDiscardsNoMacFit

       64 bit unsigned wrappable counter."
   ::= {pr1645v2Lan3VlanMCD7PEntry 301989888}

pr1645v2Lan3VlanMCD7PInDropNUCast OBJECT-TYPE
   SYNTAX      Counter64
   MAX-ACCESS  read-only
   STATUS      current
   DESCRIPTION
      "Path: ethernet3.performance.vlan.mibCounters.d7Performance.fInDiscardsNUCast

       64 bit unsigned wrappable counter."
   ::= {pr1645v2Lan3VlanMCD7PEntry 318767104}

pr1645v2Lan3VlanMCD7PInDropFilter OBJECT-TYPE
   SYNTAX      Counter64
   MAX-ACCESS  read-only
   STATUS      current
   DESCRIPTION
      "Path: ethernet3.performance.vlan.mibCounters.d7Performance.fInDiscardsFilter

       64 bit unsigned wrappable counter."
   ::= {pr1645v2Lan3VlanMCD7PEntry 385875968}

pr1645v2Lan3VlanMCD7PIfInBandwidth OBJECT-TYPE
   SYNTAX      Integer32
   MAX-ACCESS  read-only
   STATUS      current
   DESCRIPTION
      "Path: ethernet3.performance.vlan.mibCounters.d7Performance.ifInBandwidth

       unit name = bps
       formula = 8 * ; 8 /"
   ::= {pr1645v2Lan3VlanMCD7PEntry 268435456}

pr1645v2Lan3VlanMCD7PIfOutOctets OBJECT-TYPE
   SYNTAX      Counter64
   MAX-ACCESS  read-only
   STATUS      current
   DESCRIPTION
      "Path: ethernet3.performance.vlan.mibCounters.d7Performance.ifOutOctets

       64 bit unsigned wrappable counter."
   ::= {pr1645v2Lan3VlanMCD7PEntry 167772160}

pr1645v2Lan3VlanMCD7PIfOutUCPkts OBJECT-TYPE
   SYNTAX      Counter64
   MAX-ACCESS  read-only
   STATUS      current
   DESCRIPTION
      "Path: ethernet3.performance.vlan.mibCounters.d7Performance.ifOutUcastPkts

       64 bit unsigned wrappable counter."
   ::= {pr1645v2Lan3VlanMCD7PEntry 184549376}

pr1645v2Lan3VlanMCD7PIfOutNUCPkts OBJECT-TYPE
   SYNTAX      Counter64
   MAX-ACCESS  read-only
   STATUS      current
   DESCRIPTION
      "Path: ethernet3.performance.vlan.mibCounters.d7Performance.ifOutNUcastPkts

       64 bit unsigned wrappable counter."
   ::= {pr1645v2Lan3VlanMCD7PEntry 201326592}

pr1645v2Lan3VlanMCD7PIfOutBCPkts OBJECT-TYPE
   SYNTAX      Counter64
   MAX-ACCESS  read-only
   STATUS      current
   DESCRIPTION
      "Path: ethernet3.performance.vlan.mibCounters.d7Performance.ifOutBcastPkts

       64 bit unsigned wrappable counter."
   ::= {pr1645v2Lan3VlanMCD7PEntry 452984832}

pr1645v2Lan3VlanMCD7PIfOutMCPkts OBJECT-TYPE
   SYNTAX      Counter64
   MAX-ACCESS  read-only
   STATUS      current
   DESCRIPTION
      "Path: ethernet3.performance.vlan.mibCounters.d7Performance.ifOutMcastPkts

       64 bit unsigned wrappable counter."
   ::= {pr1645v2Lan3VlanMCD7PEntry 469762048}

pr1645v2Lan3VlanMCD7PIfOutDiscards OBJECT-TYPE
   SYNTAX      Counter64
   MAX-ACCESS  read-only
   STATUS      current
   DESCRIPTION
      "Path: ethernet3.performance.vlan.mibCounters.d7Performance.ifOutDiscards

       64 bit unsigned wrappable counter."
   ::= {pr1645v2Lan3VlanMCD7PEntry 218103808}

pr1645v2Lan3VlanMCD7PIfOutErrors OBJECT-TYPE
   SYNTAX      Counter64
   MAX-ACCESS  read-only
   STATUS      current
   DESCRIPTION
      "Path: ethernet3.performance.vlan.mibCounters.d7Performance.ifOutErrors

       64 bit unsigned wrappable counter."
   ::= {pr1645v2Lan3VlanMCD7PEntry 234881024}

pr1645v2Lan3VlanMCD7POutDropEx OBJECT-TYPE
   SYNTAX      Counter64
   MAX-ACCESS  read-only
   STATUS      current
   DESCRIPTION
      "Path: ethernet3.performance.vlan.mibCounters.d7Performance.ifOutDropLevelExceeded

       64 bit unsigned wrappable counter."
   ::= {pr1645v2Lan3VlanMCD7PEntry 352321536}

pr1645v2Lan3VlanMCD7POutDropNoArp OBJECT-TYPE
   SYNTAX      Counter64
   MAX-ACCESS  read-only
   STATUS      current
   DESCRIPTION
      "Path: ethernet3.performance.vlan.mibCounters.d7Performance.ifOutDiscardsNoArp

       64 bit unsigned wrappable counter."
   ::= {pr1645v2Lan3VlanMCD7PEntry 369098752}

pr1645v2Lan3VlanMCD7POutDropFilter OBJECT-TYPE
   SYNTAX      Counter64
   MAX-ACCESS  read-only
   STATUS      current
   DESCRIPTION
      "Path: ethernet3.performance.vlan.mibCounters.d7Performance.ifOutDiscardsFilter

       64 bit unsigned wrappable counter."
   ::= {pr1645v2Lan3VlanMCD7PEntry 402653184}

pr1645v2Lan3VlanMCD7PIfOutBandwidth OBJECT-TYPE
   SYNTAX      Integer32
   MAX-ACCESS  read-only
   STATUS      current
   DESCRIPTION
      "Path: ethernet3.performance.vlan.mibCounters.d7Performance.ifOutBandwidth

       unit name = bps
       formula = 8 * ; 8 /"
   ::= {pr1645v2Lan3VlanMCD7PEntry 285212672}

pr1645v2Lan3VlanMCD7PIfErrSec OBJECT-TYPE
   SYNTAX      Counter32
   MAX-ACCESS  read-only
   STATUS      current
   DESCRIPTION
      "Path: ethernet3.performance.vlan.mibCounters.d7Performance.ifErrSec

       32 bit unsigned wrappable counter."
   ::= {pr1645v2Lan3VlanMCD7PEntry 251658240}

pr1645v2Lan3VlanInPQs OBJECT-TYPE
   SYNTAX      SEQUENCE OF Pr1645v2Lan3VlanInPQsEntry
   MAX-ACCESS  not-accessible
   STATUS      current
   DESCRIPTION
      ""
   ::= {pr1645v2Lan3Vlan 100663296}

pr1645v2Lan3VlanInPQsEntry OBJECT-TYPE
   SYNTAX      Pr1645v2Lan3VlanInPQsEntry
   MAX-ACCESS  not-accessible
   STATUS      current
   DESCRIPTION
      ""
   INDEX      { pr1645v2Lan3VlanTableIx,
                pr1645v2Lan3VlanInPQsTableIx }
   ::= {pr1645v2Lan3VlanInPQs 1}

Pr1645v2Lan3VlanInPQsEntry ::=
   SEQUENCE
      {
      pr1645v2Lan3VlanInPQsTableIx
         TableIndex,
      pr1645v2Lan3VlanInPQsName
         INTEGER,
      pr1645v2Lan3VlanInPQsLength
         Integer32,
      pr1645v2Lan3VlanInPQsOctetLength
         Integer32,
      pr1645v2Lan3VlanInPQsRedLength
         Integer32,
      pr1645v2Lan3VlanInPQsPacketsTotal
         Counter64,
      pr1645v2Lan3VlanInPQsPacketsDirectTx
         Counter64,
      pr1645v2Lan3VlanInPQsPacketsQueued
         Counter64,
      pr1645v2Lan3VlanInPQsPacketsDropped
         Counter64,
      pr1645v2Lan3VlanInPQsPacketsRedDropped
         Counter64,
      pr1645v2Lan3VlanInPQsPacketsCirTx
         Counter64,
      pr1645v2Lan3VlanInPQsPacketsEirTx
         Counter64,
      pr1645v2Lan3VlanInPQsPacketsViolateTx
         Counter64,
      pr1645v2Lan3VlanInPQsOctetsTotal
         Counter64,
      pr1645v2Lan3VlanInPQsOctetsDirectTx
         Counter64,
      pr1645v2Lan3VlanInPQsOctetsQueued
         Counter64,
      pr1645v2Lan3VlanInPQsOctetsDropped
         Counter64,
      pr1645v2Lan3VlanInPQsOctetsRedDropped
         Counter64,
      pr1645v2Lan3VlanInPQsOctetsCirTx
         Counter64,
      pr1645v2Lan3VlanInPQsOctetsEirTx
         Counter64,
      pr1645v2Lan3VlanInPQsOctetsViolateTx
         Counter64,
      pr1645v2Lan3VlanInPQsOctetsBandwidth15sec
         Integer32,
      pr1645v2Lan3VlanInPQsOctetsBandwidth30sec
         Integer32,
      pr1645v2Lan3VlanInPQsOctetsBandwidth1min
         Integer32,
      pr1645v2Lan3VlanInPQsOctetsBandwidth2min
         Integer32,
      pr1645v2Lan3VlanInPQsOctetsBandwidth5min
         Integer32
      }

pr1645v2Lan3VlanInPQsTableIx OBJECT-TYPE
   SYNTAX      TableIndex
   MAX-ACCESS  not-accessible
   STATUS      current
   DESCRIPTION
      ""
   ::= {pr1645v2Lan3VlanInPQsEntry 11}

pr1645v2Lan3VlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3VlanInPQsEntry 16777216}

pr1645v2Lan3VlanInPQsLength OBJECT-TYPE
   SYNTAX      Integer32
   MAX-ACCESS  read-only
   STATUS      current
   DESCRIPTION
      "Path: ethernet3.performance.vlan.inPriorityQueues.length"
   ::= {pr1645v2Lan3VlanInPQsEntry 33554432}

pr1645v2Lan3VlanInPQsOctetLength OBJECT-TYPE
   SYNTAX      Integer32
   MAX-ACCESS  read-only
   STATUS      current
   DESCRIPTION
      "Path: ethernet3.performance.vlan.inPriorityQueues.octetLength"
   ::= {pr1645v2Lan3VlanInPQsEntry 150994944}

pr1645v2Lan3VlanInPQsRedLength OBJECT-TYPE
   SYNTAX      Integer32
   MAX-ACCESS  read-only
   STATUS      current
   DESCRIPTION
      "Path: ethernet3.performance.vlan.inPriorityQueues.redLength"
   ::= {pr1645v2Lan3VlanInPQsEntry 134217728}

pr1645v2Lan3VlanInPQsPacketsTotal OBJECT-TYPE
   SYNTAX      Counter64
   MAX-ACCESS  read-only
   STATUS      current
   DESCRIPTION
      "Path: ethernet3.performance.vlan.inPriorityQueues.packets.total

       64 bit unsigned wrappable counter."
   ::= {pr1645v2Lan3VlanInPQsEntry 50790400}

pr1645v2Lan3VlanInPQsPacketsDirectTx OBJECT-TYPE
   SYNTAX      Counter64
   MAX-ACCESS  read-only
   STATUS      current
   DESCRIPTION
      "Path: ethernet3.performance.vlan.inPriorityQueues.packets.directTx

       64 bit unsigned wrappable counter."
   ::= {pr1645v2Lan3VlanInPQsEntry 50397184}

pr1645v2Lan3VlanInPQsPacketsQueued OBJECT-TYPE
   SYNTAX      Counter64
   MAX-ACCESS  read-only
   STATUS      current
   DESCRIPTION
      "Path: ethernet3.performance.vlan.inPriorityQueues.packets.queued

       64 bit unsigned wrappable counter."
   ::= {pr1645v2Lan3VlanInPQsEntry 50462720}

pr1645v2Lan3VlanInPQsPacketsDropped OBJECT-TYPE
   SYNTAX      Counter64
   MAX-ACCESS  read-only
   STATUS      current
   DESCRIPTION
      "Path: ethernet3.performance.vlan.inPriorityQueues.packets.dropped

       64 bit unsigned wrappable counter."
   ::= {pr1645v2Lan3VlanInPQsEntry 50528256}

pr1645v2Lan3VlanInPQsPacketsRedDropped OBJECT-TYPE
   SYNTAX      Counter64
   MAX-ACCESS  read-only
   STATUS      current
   DESCRIPTION
      "Path: ethernet3.performance.vlan.inPriorityQueues.packets.redDropped

       64 bit unsigned wrappable counter."
   ::= {pr1645v2Lan3VlanInPQsEntry 50724864}

pr1645v2Lan3VlanInPQsPacketsCirTx OBJECT-TYPE
   SYNTAX      Counter64
   MAX-ACCESS  read-only
   STATUS      current
   DESCRIPTION
      "Path: ethernet3.performance.vlan.inPriorityQueues.packets.cirTx

       64 bit unsigned wrappable counter."
   ::= {pr1645v2Lan3VlanInPQsEntry 50593792}

pr1645v2Lan3VlanInPQsPacketsEirTx OBJECT-TYPE
   SYNTAX      Counter64
   MAX-ACCESS  read-only
   STATUS      current
   DESCRIPTION
      "Path: ethernet3.performance.vlan.inPriorityQueues.packets.eirTx

       64 bit unsigned wrappable counter."
   ::= {pr1645v2Lan3VlanInPQsEntry 50659328}

pr1645v2Lan3VlanInPQsPacketsViolateTx OBJECT-TYPE
   SYNTAX      Counter64
   MAX-ACCESS  read-only
   STATUS      current
   DESCRIPTION
      "Path: ethernet3.performance.vlan.inPriorityQueues.packets.violateTx

       64 bit unsigned wrappable counter."
   ::= {pr1645v2Lan3VlanInPQsEntry 50855936}

pr1645v2Lan3VlanInPQsOctetsTotal OBJECT-TYPE
   SYNTAX      Counter64
   MAX-ACCESS  read-only
   STATUS      current
   DESCRIPTION
      "Path: ethernet3.performance.vlan.inPriorityQueues.octets.total

       64 bit unsigned wrappable counter."
   ::= {pr1645v2Lan3VlanInPQsEntry 67567616}

pr1645v2Lan3VlanInPQsOctetsDirectTx OBJECT-TYPE
   SYNTAX      Counter64
   MAX-ACCESS  read-only
   STATUS      current
   DESCRIPTION
      "Path: ethernet3.performance.vlan.inPriorityQueues.octets.directTx

       64 bit unsigned wrappable counter."
   ::= {pr1645v2Lan3VlanInPQsEntry 67174400}

pr1645v2Lan3VlanInPQsOctetsQueued OBJECT-TYPE
   SYNTAX      Counter64
   MAX-ACCESS  read-only
   STATUS      current
   DESCRIPTION
      "Path: ethernet3.performance.vlan.inPriorityQueues.octets.queued

       64 bit unsigned wrappable counter."
   ::= {pr1645v2Lan3VlanInPQsEntry 67239936}

pr1645v2Lan3VlanInPQsOctetsDropped OBJECT-TYPE
   SYNTAX      Counter64
   MAX-ACCESS  read-only
   STATUS      current
   DESCRIPTION
      "Path: ethernet3.performance.vlan.inPriorityQueues.octets.dropped

       64 bit unsigned wrappable counter."
   ::= {pr1645v2Lan3VlanInPQsEntry 67305472}

pr1645v2Lan3VlanInPQsOctetsRedDropped OBJECT-TYPE
   SYNTAX      Counter64
   MAX-ACCESS  read-only
   STATUS      current
   DESCRIPTION
      "Path: ethernet3.performance.vlan.inPriorityQueues.octets.redDropped

       64 bit unsigned wrappable counter."
   ::= {pr1645v2Lan3VlanInPQsEntry 67502080}

pr1645v2Lan3VlanInPQsOctetsCirTx OBJECT-TYPE
   SYNTAX      Counter64
   MAX-ACCESS  read-only
   STATUS      current
   DESCRIPTION
      "Path: ethernet3.performance.vlan.inPriorityQueues.octets.cirTx

       64 bit unsigned wrappable counter."
   ::= {pr1645v2Lan3VlanInPQsEntry 67371008}

pr1645v2Lan3VlanInPQsOctetsEirTx OBJECT-TYPE
   SYNTAX      Counter64
   MAX-ACCESS  read-only
   STATUS      current
   DESCRIPTION
      "Path: ethernet3.performance.vlan.inPriorityQueues.octets.eirTx

       64 bit unsigned wrappable counter."
   ::= {pr1645v2Lan3VlanInPQsEntry 67436544}

pr1645v2Lan3VlanInPQsOctetsViolateTx OBJECT-TYPE
   SYNTAX      Counter64
   MAX-ACCESS  read-only
   STATUS      current
   DESCRIPTION
      "Path: ethernet3.performance.vlan.inPriorityQueues.octets.violateTx

       64 bit unsigned wrappable counter."
   ::= {pr1645v2Lan3VlanInPQsEntry 67633152}

pr1645v2Lan3VlanInPQsOctetsBandwidth15sec OBJECT-TYPE
   SYNTAX      Integer32
   MAX-ACCESS  read-only
   STATUS      current
   DESCRIPTION
      "Path: ethernet3.performance.vlan.inPriorityQueues.octets.bandwidth.15sec

       unit name = bps
       formula = 8 * ; 8 /"
   ::= {pr1645v2Lan3VlanInPQsEntry 70386944}

pr1645v2Lan3VlanInPQsOctetsBandwidth30sec OBJECT-TYPE
   SYNTAX      Integer32
   MAX-ACCESS  read-only
   STATUS      current
   DESCRIPTION
      "Path: ethernet3.performance.vlan.inPriorityQueues.octets.bandwidth.30sec

       unit name = bps
       formula = 8 * ; 8 /"
   ::= {pr1645v2Lan3VlanInPQsEntry 70388224}

pr1645v2Lan3VlanInPQsOctetsBandwidth1min OBJECT-TYPE
   SYNTAX      Integer32
   MAX-ACCESS  read-only
   STATUS      current
   DESCRIPTION
      "Path: ethernet3.performance.vlan.inPriorityQueues.octets.bandwidth.1min

       unit name = bps
       formula = 8 * ; 8 /"
   ::= {pr1645v2Lan3VlanInPQsEntry 70390784}

pr1645v2Lan3VlanInPQsOctetsBandwidth2min OBJECT-TYPE
   SYNTAX      Integer32
   MAX-ACCESS  read-only
   STATUS      current
   DESCRIPTION
      "Path: ethernet3.performance.vlan.inPriorityQueues.octets.bandwidth.2min

       unit name = bps
       formula = 8 * ; 8 /"
   ::= {pr1645v2Lan3VlanInPQsEntry 70395904}

pr1645v2Lan3VlanInPQsOctetsBandwidth5min OBJECT-TYPE
   SYNTAX      Integer32
   MAX-ACCESS  read-only
   STATUS      current
   DESCRIPTION
      "Path: ethernet3.performance.vlan.inPriorityQueues.octets.bandwidth.5min

       unit name = bps
       formula = 8 * ; 8 /"
   ::= {pr1645v2Lan3VlanInPQsEntry 70411264}

pr1645v2Lan3VlanInPQsH2Performance OBJECT-TYPE
   SYNTAX      SEQUENCE OF Pr1645v2Lan3VlanInPQsH2PerformanceEntry
   MAX-ACCESS  not-accessible
   STATUS      current
   DESCRIPTION
      ""
   ::= {pr1645v2Lan3Vlan 100990976}

pr1645v2Lan3VlanInPQsH2PerformanceEntry OBJECT-TYPE
   SYNTAX      Pr1645v2Lan3VlanInPQsH2PerformanceEntry
   MAX-ACCESS  not-accessible
   STATUS      current
   DESCRIPTION
      ""
   INDEX      { pr1645v2Lan3VlanTableIx,
                pr1645v2Lan3VlanInPQsTableIx,
                pr1645v2Lan3VlanInPQsH2PerformanceTableIx }
   ::= {pr1645v2Lan3VlanInPQsH2Performance 1}

Pr1645v2Lan3VlanInPQsH2PerformanceEntry ::=
   SEQUENCE
      {
      pr1645v2Lan3VlanInPQsH2PerformanceTableIx
         TableIndex,
      pr1645v2Lan3VlanInPQsH2PerformanceSysUpTime
         TimeTicks,
      pr1645v2Lan3VlanInPQsH2PerformanceTotPkts
         Counter64,
      pr1645v2Lan3VlanInPQsH2PerformanceDirTxPkts
         Counter64,
      pr1645v2Lan3VlanInPQsH2PerformanceQdPkts
         Counter64,
      pr1645v2Lan3VlanInPQsH2PerformanceDropPkts
         Counter64,
      pr1645v2Lan3VlanInPQsH2PerformanceRDropPkts
         Counter64,
      pr1645v2Lan3VlanInPQsH2PerformanceCirTxPkts
         Counter64,
      pr1645v2Lan3VlanInPQsH2PerformanceEirTxPkts
         Counter64,
      pr1645v2Lan3VlanInPQsH2PerformanceViolTxPkts
         Counter64,
      pr1645v2Lan3VlanInPQsH2PerformanceTotOcts
         Counter64,
      pr1645v2Lan3VlanInPQsH2PerformanceDirTxOcts
         Counter64,
      pr1645v2Lan3VlanInPQsH2PerformanceQdOcts
         Counter64,
      pr1645v2Lan3VlanInPQsH2PerformanceDropOcts
         Counter64,
      pr1645v2Lan3VlanInPQsH2PerformanceRDropOcts
         Counter64,
      pr1645v2Lan3VlanInPQsH2PerformanceCirTxOcts
         Counter64,
      pr1645v2Lan3VlanInPQsH2PerformanceEirTxOcts
         Counter64,
      pr1645v2Lan3VlanInPQsH2PerformanceViolTxOcts
         Counter64,
      pr1645v2Lan3VlanInPQsH2PerformanceBandwidth
         Integer32
      }

pr1645v2Lan3VlanInPQsH2PerformanceTableIx OBJECT-TYPE
   SYNTAX      TableIndex
   MAX-ACCESS  not-accessible
   STATUS      current
   DESCRIPTION
      ""
   ::= {pr1645v2Lan3VlanInPQsH2PerformanceEntry 11}

pr1645v2Lan3VlanInPQsH2PerformanceSysUpTime OBJECT-TYPE
   SYNTAX      TimeTicks
   MAX-ACCESS  read-only
   STATUS      current
   DESCRIPTION
      "Path: ethernet3.performance.vlan.inPriorityQueues.h2Performance.sysUpTime

       Time in centi-second."
   ::= {pr1645v2Lan3VlanInPQsH2PerformanceEntry 16777216}

pr1645v2Lan3VlanInPQsH2PerformanceTotPkts OBJECT-TYPE
   SYNTAX      Counter64
   MAX-ACCESS  read-only
   STATUS      current
   DESCRIPTION
      "Path: ethernet3.performance.vlan.inPriorityQueues.h2Performance.totalPkts

       64 bit unsigned wrappable counter."
   ::= {pr1645v2Lan3VlanInPQsH2PerformanceEntry 234881024}

pr1645v2Lan3VlanInPQsH2PerformanceDirTxPkts OBJECT-TYPE
   SYNTAX      Counter64
   MAX-ACCESS  read-only
   STATUS      current
   DESCRIPTION
      "Path: ethernet3.performance.vlan.inPriorityQueues.h2Performance.directTxPkts

       64 bit unsigned wrappable counter."
   ::= {pr1645v2Lan3VlanInPQsH2PerformanceEntry 33554432}

pr1645v2Lan3VlanInPQsH2PerformanceQdPkts OBJECT-TYPE
   SYNTAX      Counter64
   MAX-ACCESS  read-only
   STATUS      current
   DESCRIPTION
      "Path: ethernet3.performance.vlan.inPriorityQueues.h2Performance.queuedPkts

       64 bit unsigned wrappable counter."
   ::= {pr1645v2Lan3VlanInPQsH2PerformanceEntry 50331648}

pr1645v2Lan3VlanInPQsH2PerformanceDropPkts OBJECT-TYPE
   SYNTAX      Counter64
   MAX-ACCESS  read-only
   STATUS      current
   DESCRIPTION
      "Path: ethernet3.performance.vlan.inPriorityQueues.h2Performance.droppedPkts

       64 bit unsigned wrappable counter."
   ::= {pr1645v2Lan3VlanInPQsH2PerformanceEntry 67108864}

pr1645v2Lan3VlanInPQsH2PerformanceRDropPkts OBJECT-TYPE
   SYNTAX      Counter64
   MAX-ACCESS  read-only
   STATUS      current
   DESCRIPTION
      "Path: ethernet3.performance.vlan.inPriorityQueues.h2Performance.redDroppedPkts

       64 bit unsigned wrappable counter."
   ::= {pr1645v2Lan3VlanInPQsH2PerformanceEntry 201326592}

pr1645v2Lan3VlanInPQsH2PerformanceCirTxPkts OBJECT-TYPE
   SYNTAX      Counter64
   MAX-ACCESS  read-only
   STATUS      current
   DESCRIPTION
      "Path: ethernet3.performance.vlan.inPriorityQueues.h2Performance.cirTxPkts

       64 bit unsigned wrappable counter."
   ::= {pr1645v2Lan3VlanInPQsH2PerformanceEntry 83886080}

pr1645v2Lan3VlanInPQsH2PerformanceEirTxPkts OBJECT-TYPE
   SYNTAX      Counter64
   MAX-ACCESS  read-only
   STATUS      current
   DESCRIPTION
      "Path: ethernet3.performance.vlan.inPriorityQueues.h2Performance.eirTxPkts

       64 bit unsigned wrappable counter."
   ::= {pr1645v2Lan3VlanInPQsH2PerformanceEntry 100663296}

pr1645v2Lan3VlanInPQsH2PerformanceViolTxPkts OBJECT-TYPE
   SYNTAX      Counter64
   MAX-ACCESS  read-only
   STATUS      current
   DESCRIPTION
      "Path: ethernet3.performance.vlan.inPriorityQueues.h2Performance.violateTxPkts

       64 bit unsigned wrappable counter."
   ::= {pr1645v2Lan3VlanInPQsH2PerformanceEntry 301989888}

pr1645v2Lan3VlanInPQsH2PerformanceTotOcts OBJECT-TYPE
   SYNTAX      Counter64
   MAX-ACCESS  read-only
   STATUS      current
   DESCRIPTION
      "Path: ethernet3.performance.vlan.inPriorityQueues.h2Performance.totalOctets

       64 bit unsigned wrappable counter."
   ::= {pr1645v2Lan3VlanInPQsH2PerformanceEntry 251658240}

pr1645v2Lan3VlanInPQsH2PerformanceDirTxOcts OBJECT-TYPE
   SYNTAX      Counter64
   MAX-ACCESS  read-only
   STATUS      current
   DESCRIPTION
      "Path: ethernet3.performance.vlan.inPriorityQueues.h2Performance.directTxOctets

       64 bit unsigned wrappable counter."
   ::= {pr1645v2Lan3VlanInPQsH2PerformanceEntry 117440512}

pr1645v2Lan3VlanInPQsH2PerformanceQdOcts OBJECT-TYPE
   SYNTAX      Counter64
   MAX-ACCESS  read-only
   STATUS      current
   DESCRIPTION
      "Path: ethernet3.performance.vlan.inPriorityQueues.h2Performance.queuedOctets

       64 bit unsigned wrappable counter."
   ::= {pr1645v2Lan3VlanInPQsH2PerformanceEntry 134217728}

pr1645v2Lan3VlanInPQsH2PerformanceDropOcts OBJECT-TYPE
   SYNTAX      Counter64
   MAX-ACCESS  read-only
   STATUS      current
   DESCRIPTION
      "Path: ethernet3.performance.vlan.inPriorityQueues.h2Performance.droppedOctets

       64 bit unsigned wrappable counter."
   ::= {pr1645v2Lan3VlanInPQsH2PerformanceEntry 150994944}

pr1645v2Lan3VlanInPQsH2PerformanceRDropOcts OBJECT-TYPE
   SYNTAX      Counter64
   MAX-ACCESS  read-only
   STATUS      current
   DESCRIPTION
      "Path: ethernet3.performance.vlan.inPriorityQueues.h2Performance.redDroppedOctets

       64 bit unsigned wrappable counter."
   ::= {pr1645v2Lan3VlanInPQsH2PerformanceEntry 218103808}

pr1645v2Lan3VlanInPQsH2PerformanceCirTxOcts OBJECT-TYPE
   SYNTAX      Counter64
   MAX-ACCESS  read-only
   STATUS      current
   DESCRIPTION
      "Path: ethernet3.performance.vlan.inPriorityQueues.h2Performance.cirTxOctets

       64 bit unsigned wrappable counter."
   ::= {pr1645v2Lan3VlanInPQsH2PerformanceEntry 167772160}

pr1645v2Lan3VlanInPQsH2PerformanceEirTxOcts OBJECT-TYPE
   SYNTAX      Counter64
   MAX-ACCESS  read-only
   STATUS      current
   DESCRIPTION
      "Path: ethernet3.performance.vlan.inPriorityQueues.h2Performance.eirTxOctets

       64 bit unsigned wrappable counter."
   ::= {pr1645v2Lan3VlanInPQsH2PerformanceEntry 184549376}

pr1645v2Lan3VlanInPQsH2PerformanceViolTxOcts OBJECT-TYPE
   SYNTAX      Counter64
   MAX-ACCESS  read-only
   STATUS      current
   DESCRIPTION
      "Path: ethernet3.performance.vlan.inPriorityQueues.h2Performance.violateTxOctets

       64 bit unsigned wrappable counter."
   ::= {pr1645v2Lan3VlanInPQsH2PerformanceEntry 318767104}

pr1645v2Lan3VlanInPQsH2PerformanceBandwidth OBJECT-TYPE
   SYNTAX      Integer32
   MAX-ACCESS  read-only
   STATUS      current
   DESCRIPTION
      "Path: ethernet3.performance.vlan.inPriorityQueues.h2Performance.bandwidth

       unit name = bps
       formula = 8 * ; 8 /"
   ::= {pr1645v2Lan3VlanInPQsH2PerformanceEntry 268435456}

pr1645v2Lan3VlanInPQsH24Performance OBJECT-TYPE
   SYNTAX      SEQUENCE OF Pr1645v2Lan3VlanInPQsH24PerformanceEntry
   MAX-ACCESS  not-accessible
   STATUS      current
   DESCRIPTION
      ""
   ::= {pr1645v2Lan3Vlan 101056512}

pr1645v2Lan3VlanInPQsH24PerformanceEntry OBJECT-TYPE
   SYNTAX      Pr1645v2Lan3VlanInPQsH24PerformanceEntry
   MAX-ACCESS  not-accessible
   STATUS      current
   DESCRIPTION
      ""
   INDEX      { pr1645v2Lan3VlanTableIx,
                pr1645v2Lan3VlanInPQsTableIx,
                pr1645v2Lan3VlanInPQsH24PerformanceTableIx }
   ::= {pr1645v2Lan3VlanInPQsH24Performance 1}

Pr1645v2Lan3VlanInPQsH24PerformanceEntry ::=
   SEQUENCE
      {
      pr1645v2Lan3VlanInPQsH24PerformanceTableIx
         TableIndex,
      pr1645v2Lan3VlanInPQsH24PerformanceSysUpTime
         TimeTicks,
      pr1645v2Lan3VlanInPQsH24PerformanceTotPkts
         Counter64,
      pr1645v2Lan3VlanInPQsH24PerformanceDirTxPkts
         Counter64,
      pr1645v2Lan3VlanInPQsH24PerformanceQdPkts
         Counter64,
      pr1645v2Lan3VlanInPQsH24PerformanceDropPkts
         Counter64,
      pr1645v2Lan3VlanInPQsH24PerformanceRDropPkts
         Counter64,
      pr1645v2Lan3VlanInPQsH24PerformanceCirTxPkts
         Counter64,
      pr1645v2Lan3VlanInPQsH24PerformanceEirTxPkts
         Counter64,
      pr1645v2Lan3VlanInPQsH24PerformanceViolTxPkts
         Counter64,
      pr1645v2Lan3VlanInPQsH24PerformanceTotOcts
         Counter64,
      pr1645v2Lan3VlanInPQsH24PerformanceDirTxOcts
         Counter64,
      pr1645v2Lan3VlanInPQsH24PerformanceQdOcts
         Counter64,
      pr1645v2Lan3VlanInPQsH24PerformanceDropOcts
         Counter64,
      pr1645v2Lan3VlanInPQsH24PerformanceRDropOcts
         Counter64,
      pr1645v2Lan3VlanInPQsH24PerformanceCirTxOcts
         Counter64,
      pr1645v2Lan3VlanInPQsH24PerformanceEirTxOcts
         Counter64,
      pr1645v2Lan3VlanInPQsH24PerformanceViolTxOcts
         Counter64,
      pr1645v2Lan3VlanInPQsH24PerformanceBandwidth
         Integer32
      }

pr1645v2Lan3VlanInPQsH24PerformanceTableIx OBJECT-TYPE
   SYNTAX      TableIndex
   MAX-ACCESS  not-accessible
   STATUS      current
   DESCRIPTION
      ""
   ::= {pr1645v2Lan3VlanInPQsH24PerformanceEntry 11}

pr1645v2Lan3VlanInPQsH24PerformanceSysUpTime OBJECT-TYPE
   SYNTAX      TimeTicks
   MAX-ACCESS  read-only
   STATUS      current
   DESCRIPTION
      "Path: ethernet3.performance.vlan.inPriorityQueues.h24Performance.sysUpTime

       Time in centi-second."
   ::= {pr1645v2Lan3VlanInPQsH24PerformanceEntry 16777216}

pr1645v2Lan3VlanInPQsH24PerformanceTotPkts OBJECT-TYPE
   SYNTAX      Counter64
   MAX-ACCESS  read-only
   STATUS      current
   DESCRIPTION
      "Path: ethernet3.performance.vlan.inPriorityQueues.h24Performance.totalPkts

       64 bit unsigned wrappable counter."
   ::= {pr1645v2Lan3VlanInPQsH24PerformanceEntry 234881024}

pr1645v2Lan3VlanInPQsH24PerformanceDirTxPkts OBJECT-TYPE
   SYNTAX      Counter64
   MAX-ACCESS  read-only
   STATUS      current
   DESCRIPTION
      "Path: ethernet3.performance.vlan.inPriorityQueues.h24Performance.directTxPkts

       64 bit unsigned wrappable counter."
   ::= {pr1645v2Lan3VlanInPQsH24PerformanceEntry 33554432}

pr1645v2Lan3VlanInPQsH24PerformanceQdPkts OBJECT-TYPE
   SYNTAX      Counter64
   MAX-ACCESS  read-only
   STATUS      current
   DESCRIPTION
      "Path: ethernet3.performance.vlan.inPriorityQueues.h24Performance.queuedPkts

       64 bit unsigned wrappable counter."
   ::= {pr1645v2Lan3VlanInPQsH24PerformanceEntry 50331648}

pr1645v2Lan3VlanInPQsH24PerformanceDropPkts OBJECT-TYPE
   SYNTAX      Counter64
   MAX-ACCESS  read-only
   STATUS      current
   DESCRIPTION
      "Path: ethernet3.performance.vlan.inPriorityQueues.h24Performance.droppedPkts

       64 bit unsigned wrappable counter."
   ::= {pr1645v2Lan3VlanInPQsH24PerformanceEntry 67108864}

pr1645v2Lan3VlanInPQsH24PerformanceRDropPkts OBJECT-TYPE
   SYNTAX      Counter64
   MAX-ACCESS  read-only
   STATUS      current
   DESCRIPTION
      "Path: ethernet3.performance.vlan.inPriorityQueues.h24Performance.redDroppedPkts

       64 bit unsigned wrappable counter."
   ::= {pr1645v2Lan3VlanInPQsH24PerformanceEntry 201326592}

pr1645v2Lan3VlanInPQsH24PerformanceCirTxPkts OBJECT-TYPE
   SYNTAX      Counter64
   MAX-ACCESS  read-only
   STATUS      current
   DESCRIPTION
      "Path: ethernet3.performance.vlan.inPriorityQueues.h24Performance.cirTxPkts

       64 bit unsigned wrappable counter."
   ::= {pr1645v2Lan3VlanInPQsH24PerformanceEntry 83886080}

pr1645v2Lan3VlanInPQsH24PerformanceEirTxPkts OBJECT-TYPE
   SYNTAX      Counter64
   MAX-ACCESS  read-only
   STATUS      current
   DESCRIPTION
      "Path: ethernet3.performance.vlan.inPriorityQueues.h24Performance.eirTxPkts

       64 bit unsigned wrappable counter."
   ::= {pr1645v2Lan3VlanInPQsH24PerformanceEntry 100663296}

pr1645v2Lan3VlanInPQsH24PerformanceViolTxPkts OBJECT-TYPE
   SYNTAX      Counter64
   MAX-ACCESS  read-only
   STATUS      current
   DESCRIPTION
      "Path: ethernet3.performance.vlan.inPriorityQueues.h24Performance.violateTxPkts

       64 bit unsigned wrappable counter."
   ::= {pr1645v2Lan3VlanInPQsH24PerformanceEntry 301989888}

pr1645v2Lan3VlanInPQsH24PerformanceTotOcts OBJECT-TYPE
   SYNTAX      Counter64
   MAX-ACCESS  read-only
   STATUS      current
   DESCRIPTION
      "Path: ethernet3.performance.vlan.inPriorityQueues.h24Performance.totalOctets

       64 bit unsigned wrappable counter."
   ::= {pr1645v2Lan3VlanInPQsH24PerformanceEntry 251658240}

pr1645v2Lan3VlanInPQsH24PerformanceDirTxOcts OBJECT-TYPE
   SYNTAX      Counter64
   MAX-ACCESS  read-only
   STATUS      current
   DESCRIPTION
      "Path: ethernet3.performance.vlan.inPriorityQueues.h24Performance.directTxOctets

       64 bit unsigned wrappable counter."
   ::= {pr1645v2Lan3VlanInPQsH24PerformanceEntry 117440512}

pr1645v2Lan3VlanInPQsH24PerformanceQdOcts OBJECT-TYPE
   SYNTAX      Counter64
   MAX-ACCESS  read-only
   STATUS      current
   DESCRIPTION
      "Path: ethernet3.performance.vlan.inPriorityQueues.h24Performance.queuedOctets

       64 bit unsigned wrappable counter."
   ::= {pr1645v2Lan3VlanInPQsH24PerformanceEntry 134217728}

pr1645v2Lan3VlanInPQsH24PerformanceDropOcts OBJECT-TYPE
   SYNTAX      Counter64
   MAX-ACCESS  read-only
   STATUS      current
   DESCRIPTION
      "Path: ethernet3.performance.vlan.inPriorityQueues.h24Performance.droppedOctets

       64 bit unsigned wrappable counter."
   ::= {pr1645v2Lan3VlanInPQsH24PerformanceEntry 150994944}

pr1645v2Lan3VlanInPQsH24PerformanceRDropOcts OBJECT-TYPE
   SYNTAX      Counter64
   MAX-ACCESS  read-only
   STATUS      current
   DESCRIPTION
      "Path: ethernet3.performance.vlan.inPriorityQueues.h24Performance.redDroppedOctets

       64 bit unsigned wrappable counter."
   ::= {pr1645v2Lan3VlanInPQsH24PerformanceEntry 218103808}

pr1645v2Lan3VlanInPQsH24PerformanceCirTxOcts OBJECT-TYPE
   SYNTAX      Counter64
   MAX-ACCESS  read-only
   STATUS      current
   DESCRIPTION
      "Path: ethernet3.performance.vlan.inPriorityQueues.h24Performance.cirTxOctets

       64 bit unsigned wrappable counter."
   ::= {pr1645v2Lan3VlanInPQsH24PerformanceEntry 167772160}

pr1645v2Lan3VlanInPQsH24PerformanceEirTxOcts OBJECT-TYPE
   SYNTAX      Counter64
   MAX-ACCESS  read-only
   STATUS      current
   DESCRIPTION
      "Path: ethernet3.performance.vlan.inPriorityQueues.h24Performance.eirTxOctets

       64 bit unsigned wrappable counter."
   ::= {pr1645v2Lan3VlanInPQsH24PerformanceEntry 184549376}

pr1645v2Lan3VlanInPQsH24PerformanceViolTxOcts OBJECT-TYPE
   SYNTAX      Counter64
   MAX-ACCESS  read-only
   STATUS      current
   DESCRIPTION
      "Path: ethernet3.performance.vlan.inPriorityQueues.h24Performance.violateTxOctets

       64 bit unsigned wrappable counter."
   ::= {pr1645v2Lan3VlanInPQsH24PerformanceEntry 318767104}

pr1645v2Lan3VlanInPQsH24PerformanceBandwidth OBJECT-TYPE
   SYNTAX      Integer32
   MAX-ACCESS  read-only
   STATUS      current
   DESCRIPTION
      "Path: ethernet3.performance.vlan.inPriorityQueues.h24Performance.bandwidth

       unit name = bps
       formula = 8 * ; 8 /"
   ::= {pr1645v2Lan3VlanInPQsH24PerformanceEntry 268435456}

pr1645v2Lan3VlanInPQsD7Performance OBJECT-TYPE
   SYNTAX      SEQUENCE OF Pr1645v2Lan3VlanInPQsD7PerformanceEntry
   MAX-ACCESS  not-accessible
   STATUS      current
   DESCRIPTION
      ""
   ::= {pr1645v2Lan3Vlan 101122048}

pr1645v2Lan3VlanInPQsD7PerformanceEntry OBJECT-TYPE
   SYNTAX      Pr1645v2Lan3VlanInPQsD7PerformanceEntry
   MAX-ACCESS  not-accessible
   STATUS      current
   DESCRIPTION
      ""
   INDEX      { pr1645v2Lan3VlanTableIx,
                pr1645v2Lan3VlanInPQsTableIx,
                pr1645v2Lan3VlanInPQsD7PerformanceTableIx }
   ::= {pr1645v2Lan3VlanInPQsD7Performance 1}

Pr1645v2Lan3VlanInPQsD7PerformanceEntry ::=
   SEQUENCE
      {
      pr1645v2Lan3VlanInPQsD7PerformanceTableIx
         TableIndex,
      pr1645v2Lan3VlanInPQsD7PerformanceSysUpTime
         TimeTicks,
      pr1645v2Lan3VlanInPQsD7PerformanceTotPkts
         Counter64,
      pr1645v2Lan3VlanInPQsD7PerformanceDirTxPkts
         Counter64,
      pr1645v2Lan3VlanInPQsD7PerformanceQdPkts
         Counter64,
      pr1645v2Lan3VlanInPQsD7PerformanceDropPkts
         Counter64,
      pr1645v2Lan3VlanInPQsD7PerformanceRDropPkts
         Counter64,
      pr1645v2Lan3VlanInPQsD7PerformanceCirTxPkts
         Counter64,
      pr1645v2Lan3VlanInPQsD7PerformanceEirTxPkts
         Counter64,
      pr1645v2Lan3VlanInPQsD7PerformanceViolTxPkts
         Counter64,
      pr1645v2Lan3VlanInPQsD7PerformanceTotOcts
         Counter64,
      pr1645v2Lan3VlanInPQsD7PerformanceDirTxOcts
         Counter64,
      pr1645v2Lan3VlanInPQsD7PerformanceQdOcts
         Counter64,
      pr1645v2Lan3VlanInPQsD7PerformanceDropOcts
         Counter64,
      pr1645v2Lan3VlanInPQsD7PerformanceRDropOcts
         Counter64,
      pr1645v2Lan3VlanInPQsD7PerformanceCirTxOcts
         Counter64,
      pr1645v2Lan3VlanInPQsD7PerformanceEirTxOcts
         Counter64,
      pr1645v2Lan3VlanInPQsD7PerformanceViolTxOcts
         Counter64,
      pr1645v2Lan3VlanInPQsD7PerformanceBandwidth
         Integer32
      }

pr1645v2Lan3VlanInPQsD7PerformanceTableIx OBJECT-TYPE
   SYNTAX      TableIndex
   MAX-ACCESS  not-accessible
   STATUS      current
   DESCRIPTION
      ""
   ::= {pr1645v2Lan3VlanInPQsD7PerformanceEntry 11}

pr1645v2Lan3VlanInPQsD7PerformanceSysUpTime OBJECT-TYPE
   SYNTAX      TimeTicks
   MAX-ACCESS  read-only
   STATUS      current
   DESCRIPTION
      "Path: ethernet3.performance.vlan.inPriorityQueues.d7Performance.sysUpTime

       Time in centi-second."
   ::= {pr1645v2Lan3VlanInPQsD7PerformanceEntry 16777216}

pr1645v2Lan3VlanInPQsD7PerformanceTotPkts OBJECT-TYPE
   SYNTAX      Counter64
   MAX-ACCESS  read-only
   STATUS      current
   DESCRIPTION
      "Path: ethernet3.performance.vlan.inPriorityQueues.d7Performance.totalPkts

       64 bit unsigned wrappable counter."
   ::= {pr1645v2Lan3VlanInPQsD7PerformanceEntry 234881024}

pr1645v2Lan3VlanInPQsD7PerformanceDirTxPkts OBJECT-TYPE
   SYNTAX      Counter64
   MAX-ACCESS  read-only
   STATUS      current
   DESCRIPTION
      "Path: ethernet3.performance.vlan.inPriorityQueues.d7Performance.directTxPkts

       64 bit unsigned wrappable counter."
   ::= {pr1645v2Lan3VlanInPQsD7PerformanceEntry 33554432}

pr1645v2Lan3VlanInPQsD7PerformanceQdPkts OBJECT-TYPE
   SYNTAX      Counter64
   MAX-ACCESS  read-only
   STATUS      current
   DESCRIPTION
      "Path: ethernet3.performance.vlan.inPriorityQueues.d7Performance.queuedPkts

       64 bit unsigned wrappable counter."
   ::= {pr1645v2Lan3VlanInPQsD7PerformanceEntry 50331648}

pr1645v2Lan3VlanInPQsD7PerformanceDropPkts OBJECT-TYPE
   SYNTAX      Counter64
   MAX-ACCESS  read-only
   STATUS      current
   DESCRIPTION
      "Path: ethernet3.performance.vlan.inPriorityQueues.d7Performance.droppedPkts

       64 bit unsigned wrappable counter."
   ::= {pr1645v2Lan3VlanInPQsD7PerformanceEntry 67108864}

pr1645v2Lan3VlanInPQsD7PerformanceRDropPkts OBJECT-TYPE
   SYNTAX      Counter64
   MAX-ACCESS  read-only
   STATUS      current
   DESCRIPTION
      "Path: ethernet3.performance.vlan.inPriorityQueues.d7Performance.redDroppedPkts

       64 bit unsigned wrappable counter."
   ::= {pr1645v2Lan3VlanInPQsD7PerformanceEntry 201326592}

pr1645v2Lan3VlanInPQsD7PerformanceCirTxPkts OBJECT-TYPE
   SYNTAX      Counter64
   MAX-ACCESS  read-only
   STATUS      current
   DESCRIPTION
      "Path: ethernet3.performance.vlan.inPriorityQueues.d7Performance.cirTxPkts

       64 bit unsigned wrappable counter."
   ::= {pr1645v2Lan3VlanInPQsD7PerformanceEntry 83886080}

pr1645v2Lan3VlanInPQsD7PerformanceEirTxPkts OBJECT-TYPE
   SYNTAX      Counter64
   MAX-ACCESS  read-only
   STATUS      current
   DESCRIPTION
      "Path: ethernet3.performance.vlan.inPriorityQueues.d7Performance.eirTxPkts

       64 bit unsigned wrappable counter."
   ::= {pr1645v2Lan3VlanInPQsD7PerformanceEntry 100663296}

pr1645v2Lan3VlanInPQsD7PerformanceViolTxPkts OBJECT-TYPE
   SYNTAX      Counter64
   MAX-ACCESS  read-only
   STATUS      current
   DESCRIPTION
      "Path: ethernet3.performance.vlan.inPriorityQueues.d7Performance.violateTxPkts

       64 bit unsigned wrappable counter."
   ::= {pr1645v2Lan3VlanInPQsD7PerformanceEntry 301989888}

pr1645v2Lan3VlanInPQsD7PerformanceTotOcts OBJECT-TYPE
   SYNTAX      Counter64
   MAX-ACCESS  read-only
   STATUS      current
   DESCRIPTION
      "Path: ethernet3.performance.vlan.inPriorityQueues.d7Performance.totalOctets

       64 bit unsigned wrappable counter."
   ::= {pr1645v2Lan3VlanInPQsD7PerformanceEntry 251658240}

pr1645v2Lan3VlanInPQsD7PerformanceDirTxOcts OBJECT-TYPE
   SYNTAX      Counter64
   MAX-ACCESS  read-only
   STATUS      current
   DESCRIPTION
      "Path: ethernet3.performance.vlan.inPriorityQueues.d7Performance.directTxOctets

       64 bit unsigned wrappable counter."
   ::= {pr1645v2Lan3VlanInPQsD7PerformanceEntry 117440512}

pr1645v2Lan3VlanInPQsD7PerformanceQdOcts OBJECT-TYPE
   SYNTAX      Counter64
   MAX-ACCESS  read-only
   STATUS      current
   DESCRIPTION
      "Path: ethernet3.performance.vlan.inPriorityQueues.d7Performance.queuedOctets

       64 bit unsigned wrappable counter."
   ::= {pr1645v2Lan3VlanInPQsD7PerformanceEntry 134217728}

pr1645v2Lan3VlanInPQsD7PerformanceDropOcts OBJECT-TYPE
   SYNTAX      Counter64
   MAX-ACCESS  read-only
   STATUS      current
   DESCRIPTION
      "Path: ethernet3.performance.vlan.inPriorityQueues.d7Performance.droppedOctets

       64 bit unsigned wrappable counter."
   ::= {pr1645v2Lan3VlanInPQsD7PerformanceEntry 150994944}

pr1645v2Lan3VlanInPQsD7PerformanceRDropOcts OBJECT-TYPE
   SYNTAX      Counter64
   MAX-ACCESS  read-only
   STATUS      current
   DESCRIPTION
      "Path: ethernet3.performance.vlan.inPriorityQueues.d7Performance.redDroppedOctets

       64 bit unsigned wrappable counter."
   ::= {pr1645v2Lan3VlanInPQsD7PerformanceEntry 218103808}

pr1645v2Lan3VlanInPQsD7PerformanceCirTxOcts OBJECT-TYPE
   SYNTAX      Counter64
   MAX-ACCESS  read-only
   STATUS      current
   DESCRIPTION
      "Path: ethernet3.performance.vlan.inPriorityQueues.d7Performance.cirTxOctets

       64 bit unsigned wrappable counter."
   ::= {pr1645v2Lan3VlanInPQsD7PerformanceEntry 167772160}

pr1645v2Lan3VlanInPQsD7PerformanceEirTxOcts OBJECT-TYPE
   SYNTAX      Counter64
   MAX-ACCESS  read-only
   STATUS      current
   DESCRIPTION
      "Path: ethernet3.performance.vlan.inPriorityQueues.d7Performance.eirTxOctets

       64 bit unsigned wrappable counter."
   ::= {pr1645v2Lan3VlanInPQsD7PerformanceEntry 184549376}

pr1645v2Lan3VlanInPQsD7PerformanceViolTxOcts OBJECT-TYPE
   SYNTAX      Counter64
   MAX-ACCESS  read-only
   STATUS      current
   DESCRIPTION
      "Path: ethernet3.performance.vlan.inPriorityQueues.d7Performance.violateTxOctets

       64 bit unsigned wrappable counter."
   ::= {pr1645v2Lan3VlanInPQsD7PerformanceEntry 318767104}

pr1645v2Lan3VlanInPQsD7PerformanceBandwidth OBJECT-TYPE
   SYNTAX      Integer32
   MAX-ACCESS  read-only
   STATUS      current
   DESCRIPTION
      "Path: ethernet3.performance.vlan.inPriorityQueues.d7Performance.bandwidth

       unit name = bps
       formula = 8 * ; 8 /"
   ::= {pr1645v2Lan3VlanInPQsD7PerformanceEntry 268435456}

pr1645v2Lan3VlanOutPQs OBJECT-TYPE
   SYNTAX      SEQUENCE OF Pr1645v2Lan3VlanOutPQsEntry
   MAX-ACCESS  not-accessible
   STATUS      current
   DESCRIPTION
      ""
   ::= {pr1645v2Lan3Vlan 83886080}

pr1645v2Lan3VlanOutPQsEntry OBJECT-TYPE
   SYNTAX      Pr1645v2Lan3VlanOutPQsEntry
   MAX-ACCESS  not-accessible
   STATUS      current
   DESCRIPTION
      ""
   INDEX      { pr1645v2Lan3VlanTableIx,
                pr1645v2Lan3VlanOutPQsTableIx }
   ::= {pr1645v2Lan3VlanOutPQs 1}

Pr1645v2Lan3VlanOutPQsEntry ::=
   SEQUENCE
      {
      pr1645v2Lan3VlanOutPQsTableIx
         TableIndex,
      pr1645v2Lan3VlanOutPQsName
         INTEGER,
      pr1645v2Lan3VlanOutPQsLength
         Integer32,
      pr1645v2Lan3VlanOutPQsOctetLength
         Integer32,
      pr1645v2Lan3VlanOutPQsRedLength
         Integer32,
      pr1645v2Lan3VlanOutPQsPacketsTotal
         Counter64,
      pr1645v2Lan3VlanOutPQsPacketsDirectTx
         Counter64,
      pr1645v2Lan3VlanOutPQsPacketsQueued
         Counter64,
      pr1645v2Lan3VlanOutPQsPacketsDropped
         Counter64,
      pr1645v2Lan3VlanOutPQsPacketsRedDropped
         Counter64,
      pr1645v2Lan3VlanOutPQsPacketsCirTx
         Counter64,
      pr1645v2Lan3VlanOutPQsPacketsEirTx
         Counter64,
      pr1645v2Lan3VlanOutPQsPacketsViolateTx
         Counter64,
      pr1645v2Lan3VlanOutPQsOctetsTotal
         Counter64,
      pr1645v2Lan3VlanOutPQsOctetsDirectTx
         Counter64,
      pr1645v2Lan3VlanOutPQsOctetsQueued
         Counter64,
      pr1645v2Lan3VlanOutPQsOctetsDropped
         Counter64,
      pr1645v2Lan3VlanOutPQsOctetsRedDropped
         Counter64,
      pr1645v2Lan3VlanOutPQsOctetsCirTx
         Counter64,
      pr1645v2Lan3VlanOutPQsOctetsEirTx
         Counter64,
      pr1645v2Lan3VlanOutPQsOctetsViolateTx
         Counter64,
      pr1645v2Lan3VlanOutPQsOctetsBandwidth15sec
         Integer32,
      pr1645v2Lan3VlanOutPQsOctetsBandwidth30sec
         Integer32,
      pr1645v2Lan3VlanOutPQsOctetsBandwidth1min
         Integer32,
      pr1645v2Lan3VlanOutPQsOctetsBandwidth2min
         Integer32,
      pr1645v2Lan3VlanOutPQsOctetsBandwidth5min
         Integer32
      }

pr1645v2Lan3VlanOutPQsTableIx OBJECT-TYPE
   SYNTAX      TableIndex
   MAX-ACCESS  not-accessible
   STATUS      current
   DESCRIPTION
      ""
   ::= {pr1645v2Lan3VlanOutPQsEntry 11}

pr1645v2Lan3VlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3VlanOutPQsEntry 16777216}

pr1645v2Lan3VlanOutPQsLength OBJECT-TYPE
   SYNTAX      Integer32
   MAX-ACCESS  read-only
   STATUS      current
   DESCRIPTION
      "Path: ethernet3.performance.vlan.outPriorityQueues.length"
   ::= {pr1645v2Lan3VlanOutPQsEntry 33554432}

pr1645v2Lan3VlanOutPQsOctetLength OBJECT-TYPE
   SYNTAX      Integer32
   MAX-ACCESS  read-only
   STATUS      current
   DESCRIPTION
      "Path: ethernet3.performance.vlan.outPriorityQueues.octetLength"
   ::= {pr1645v2Lan3VlanOutPQsEntry 150994944}

pr1645v2Lan3VlanOutPQsRedLength OBJECT-TYPE
   SYNTAX      Integer32
   MAX-ACCESS  read-only
   STATUS      current
   DESCRIPTION
      "Path: ethernet3.performance.vlan.outPriorityQueues.redLength"
   ::= {pr1645v2Lan3VlanOutPQsEntry 134217728}

pr1645v2Lan3VlanOutPQsPacketsTotal OBJECT-TYPE
   SYNTAX      Counter64
   MAX-ACCESS  read-only
   STATUS      current
   DESCRIPTION
      "Path: ethernet3.performance.vlan.outPriorityQueues.packets.total

       64 bit unsigned wrappable counter."
   ::= {pr1645v2Lan3VlanOutPQsEntry 50790400}

pr1645v2Lan3VlanOutPQsPacketsDirectTx OBJECT-TYPE
   SYNTAX      Counter64
   MAX-ACCESS  read-only
   STATUS      current
   DESCRIPTION
      "Path: ethernet3.performance.vlan.outPriorityQueues.packets.directTx

       64 bit unsigned wrappable counter."
   ::= {pr1645v2Lan3VlanOutPQsEntry 50397184}

pr1645v2Lan3VlanOutPQsPacketsQueued OBJECT-TYPE
   SYNTAX      Counter64
   MAX-ACCESS  read-only
   STATUS      current
   DESCRIPTION
      "Path: ethernet3.performance.vlan.outPriorityQueues.packets.queued

       64 bit unsigned wrappable counter."
   ::= {pr1645v2Lan3VlanOutPQsEntry 50462720}

pr1645v2Lan3VlanOutPQsPacketsDropped OBJECT-TYPE
   SYNTAX      Counter64
   MAX-ACCESS  read-only
   STATUS      current
   DESCRIPTION
      "Path: ethernet3.performance.vlan.outPriorityQueues.packets.dropped

       64 bit unsigned wrappable counter."
   ::= {pr1645v2Lan3VlanOutPQsEntry 50528256}

pr1645v2Lan3VlanOutPQsPacketsRedDropped OBJECT-TYPE
   SYNTAX      Counter64
   MAX-ACCESS  read-only
   STATUS      current
   DESCRIPTION
      "Path: ethernet3.performance.vlan.outPriorityQueues.packets.redDropped

       64 bit unsigned wrappable counter."
   ::= {pr1645v2Lan3VlanOutPQsEntry 50724864}

pr1645v2Lan3VlanOutPQsPacketsCirTx OBJECT-TYPE
   SYNTAX      Counter64
   MAX-ACCESS  read-only
   STATUS      current
   DESCRIPTION
      "Path: ethernet3.performance.vlan.outPriorityQueues.packets.cirTx

       64 bit unsigned wrappable counter."
   ::= {pr1645v2Lan3VlanOutPQsEntry 50593792}

pr1645v2Lan3VlanOutPQsPacketsEirTx OBJECT-TYPE
   SYNTAX      Counter64
   MAX-ACCESS  read-only
   STATUS      current
   DESCRIPTION
      "Path: ethernet3.performance.vlan.outPriorityQueues.packets.eirTx

       64 bit unsigned wrappable counter."
   ::= {pr1645v2Lan3VlanOutPQsEntry 50659328}

pr1645v2Lan3VlanOutPQsPacketsViolateTx OBJECT-TYPE
   SYNTAX      Counter64
   MAX-ACCESS  read-only
   STATUS      current
   DESCRIPTION
      "Path: ethernet3.performance.vlan.outPriorityQueues.packets.violateTx

       64 bit unsigned wrappable counter."
   ::= {pr1645v2Lan3VlanOutPQsEntry 50855936}

pr1645v2Lan3VlanOutPQsOctetsTotal OBJECT-TYPE
   SYNTAX      Counter64
   MAX-ACCESS  read-only
   STATUS      current
   DESCRIPTION
      "Path: ethernet3.performance.vlan.outPriorityQueues.octets.total

       64 bit unsigned wrappable counter."
   ::= {pr1645v2Lan3VlanOutPQsEntry 67567616}

pr1645v2Lan3VlanOutPQsOctetsDirectTx OBJECT-TYPE
   SYNTAX      Counter64
   MAX-ACCESS  read-only
   STATUS      current
   DESCRIPTION
      "Path: ethernet3.performance.vlan.outPriorityQueues.octets.directTx

       64 bit unsigned wrappable counter."
   ::= {pr1645v2Lan3VlanOutPQsEntry 67174400}

pr1645v2Lan3VlanOutPQsOctetsQueued OBJECT-TYPE
   SYNTAX      Counter64
   MAX-ACCESS  read-only
   STATUS      current
   DESCRIPTION
      "Path: ethernet3.performance.vlan.outPriorityQueues.octets.queued

       64 bit unsigned wrappable counter."
   ::= {pr1645v2Lan3VlanOutPQsEntry 67239936}

pr1645v2Lan3VlanOutPQsOctetsDropped OBJECT-TYPE
   SYNTAX      Counter64
   MAX-ACCESS  read-only
   STATUS      current
   DESCRIPTION
      "Path: ethernet3.performance.vlan.outPriorityQueues.octets.dropped

       64 bit unsigned wrappable counter."
   ::= {pr1645v2Lan3VlanOutPQsEntry 67305472}

pr1645v2Lan3VlanOutPQsOctetsRedDropped OBJECT-TYPE
   SYNTAX      Counter64
   MAX-ACCESS  read-only
   STATUS      current
   DESCRIPTION
      "Path: ethernet3.performance.vlan.outPriorityQueues.octets.redDropped

       64 bit unsigned wrappable counter."
   ::= {pr1645v2Lan3VlanOutPQsEntry 67502080}

pr1645v2Lan3VlanOutPQsOctetsCirTx OBJECT-TYPE
   SYNTAX      Counter64
   MAX-ACCESS  read-only
   STATUS      current
   DESCRIPTION
      "Path: ethernet3.performance.vlan.outPriorityQueues.octets.cirTx

       64 bit unsigned wrappable counter."
   ::= {pr1645v2Lan3VlanOutPQsEntry 67371008}

pr1645v2Lan3VlanOutPQsOctetsEirTx OBJECT-TYPE
   SYNTAX      Counter64
   MAX-ACCESS  read-only
   STATUS      current
   DESCRIPTION
      "Path: ethernet3.performance.vlan.outPriorityQueues.octets.eirTx

       64 bit unsigned wrappable counter."
   ::= {pr1645v2Lan3VlanOutPQsEntry 67436544}

pr1645v2Lan3VlanOutPQsOctetsViolateTx OBJECT-TYPE
   SYNTAX      Counter64
   MAX-ACCESS  read-only
   STATUS      current
   DESCRIPTION
      "Path: ethernet3.performance.vlan.outPriorityQueues.octets.violateTx

       64 bit unsigned wrappable counter."
   ::= {pr1645v2Lan3VlanOutPQsEntry 67633152}

pr1645v2Lan3VlanOutPQsOctetsBandwidth15sec OBJECT-TYPE
   SYNTAX      Integer32
   MAX-ACCESS  read-only
   STATUS      current
   DESCRIPTION
      "Path: ethernet3.performance.vlan.outPriorityQueues.octets.bandwidth.15sec

       unit name = bps
       formula = 8 * ; 8 /"
   ::= {pr1645v2Lan3VlanOutPQsEntry 70386944}

pr1645v2Lan3VlanOutPQsOctetsBandwidth30sec OBJECT-TYPE
   SYNTAX      Integer32
   MAX-ACCESS  read-only
   STATUS      current
   DESCRIPTION
      "Path: ethernet3.performance.vlan.outPriorityQueues.octets.bandwidth.30sec

       unit name = bps
       formula = 8 * ; 8 /"
   ::= {pr1645v2Lan3VlanOutPQsEntry 70388224}

pr1645v2Lan3VlanOutPQsOctetsBandwidth1min OBJECT-TYPE
   SYNTAX      Integer32
   MAX-ACCESS  read-only
   STATUS      current
   DESCRIPTION
      "Path: ethernet3.performance.vlan.outPriorityQueues.octets.bandwidth.1min

       unit name = bps
       formula = 8 * ; 8 /"
   ::= {pr1645v2Lan3VlanOutPQsEntry 70390784}

pr1645v2Lan3VlanOutPQsOctetsBandwidth2min OBJECT-TYPE
   SYNTAX      Integer32
   MAX-ACCESS  read-only
   STATUS      current
   DESCRIPTION
      "Path: ethernet3.performance.vlan.outPriorityQueues.octets.bandwidth.2min

       unit name = bps
       formula = 8 * ; 8 /"
   ::= {pr1645v2Lan3VlanOutPQsEntry 70395904}

pr1645v2Lan3VlanOutPQsOctetsBandwidth5min OBJECT-TYPE
   SYNTAX      Integer32
   MAX-ACCESS  read-only
   STATUS      current
   DESCRIPTION
      "Path: ethernet3.performance.vlan.outPriorityQueues.octets.bandwidth.5min

       unit name = bps
       formula = 8 * ; 8 /"
   ::= {pr1645v2Lan3VlanOutPQsEntry 70411264}

pr1645v2Lan3VlanOutPQsH2Performance OBJECT-TYPE
   SYNTAX      SEQUENCE OF Pr1645v2Lan3VlanOutPQsH2PerformanceEntry
   MAX-ACCESS  not-accessible
   STATUS      current
   DESCRIPTION
      ""
   ::= {pr1645v2Lan3Vlan 84213760}

pr1645v2Lan3VlanOutPQsH2PerformanceEntry OBJECT-TYPE
   SYNTAX      Pr1645v2Lan3VlanOutPQsH2PerformanceEntry
   MAX-ACCESS  not-accessible
   STATUS      current
   DESCRIPTION
      ""
   INDEX      { pr1645v2Lan3VlanTableIx,
                pr1645v2Lan3VlanOutPQsTableIx,
                pr1645v2Lan3VlanOutPQsH2PerformanceTableIx }
   ::= {pr1645v2Lan3VlanOutPQsH2Performance 1}

Pr1645v2Lan3VlanOutPQsH2PerformanceEntry ::=
   SEQUENCE
      {
      pr1645v2Lan3VlanOutPQsH2PerformanceTableIx
         TableIndex,
      pr1645v2Lan3VlanOutPQsH2PerformanceSysUpTime
         TimeTicks,
      pr1645v2Lan3VlanOutPQsH2PerformanceTotPkts
         Counter64,
      pr1645v2Lan3VlanOutPQsH2PerformanceDirTxPkts
         Counter64,
      pr1645v2Lan3VlanOutPQsH2PerformanceQdPkts
         Counter64,
      pr1645v2Lan3VlanOutPQsH2PerformanceDropPkts
         Counter64,
      pr1645v2Lan3VlanOutPQsH2PerformanceRDropPkts
         Counter64,
      pr1645v2Lan3VlanOutPQsH2PerformanceCirTxPkts
         Counter64,
      pr1645v2Lan3VlanOutPQsH2PerformanceEirTxPkts
         Counter64,
      pr1645v2Lan3VlanOutPQsH2PerformanceViolTxPkts
         Counter64,
      pr1645v2Lan3VlanOutPQsH2PerformanceTotOcts
         Counter64,
      pr1645v2Lan3VlanOutPQsH2PerformanceDirTxOcts
         Counter64,
      pr1645v2Lan3VlanOutPQsH2PerformanceQdOcts
         Counter64,
      pr1645v2Lan3VlanOutPQsH2PerformanceDropOcts
         Counter64,
      pr1645v2Lan3VlanOutPQsH2PerformanceRDropOcts
         Counter64,
      pr1645v2Lan3VlanOutPQsH2PerformanceCirTxOcts
         Counter64,
      pr1645v2Lan3VlanOutPQsH2PerformanceEirTxOcts
         Counter64,
      pr1645v2Lan3VlanOutPQsH2PerformanceViolTxOcts
         Counter64,
      pr1645v2Lan3VlanOutPQsH2PerformanceBandwidth
         Integer32
      }

pr1645v2Lan3VlanOutPQsH2PerformanceTableIx OBJECT-TYPE
   SYNTAX      TableIndex
   MAX-ACCESS  not-accessible
   STATUS      current
   DESCRIPTION
      ""
   ::= {pr1645v2Lan3VlanOutPQsH2PerformanceEntry 11}

pr1645v2Lan3VlanOutPQsH2PerformanceSysUpTime OBJECT-TYPE
   SYNTAX      TimeTicks
   MAX-ACCESS  read-only
   STATUS      current
   DESCRIPTION
      "Path: ethernet3.performance.vlan.outPriorityQueues.h2Performance.sysUpTime

       Time in centi-second."
   ::= {pr1645v2Lan3VlanOutPQsH2PerformanceEntry 16777216}

pr1645v2Lan3VlanOutPQsH2PerformanceTotPkts OBJECT-TYPE
   SYNTAX      Counter64
   MAX-ACCESS  read-only
   STATUS      current
   DESCRIPTION
      "Path: ethernet3.performance.vlan.outPriorityQueues.h2Performance.totalPkts

       64 bit unsigned wrappable counter."
   ::= {pr1645v2Lan3VlanOutPQsH2PerformanceEntry 234881024}

pr1645v2Lan3VlanOutPQsH2PerformanceDirTxPkts OBJECT-TYPE
   SYNTAX      Counter64
   MAX-ACCESS  read-only
   STATUS      current
   DESCRIPTION
      "Path: ethernet3.performance.vlan.outPriorityQueues.h2Performance.directTxPkts

       64 bit unsigned wrappable counter."
   ::= {pr1645v2Lan3VlanOutPQsH2PerformanceEntry 33554432}

pr1645v2Lan3VlanOutPQsH2PerformanceQdPkts OBJECT-TYPE
   SYNTAX      Counter64
   MAX-ACCESS  read-only
   STATUS      current
   DESCRIPTION
      "Path: ethernet3.performance.vlan.outPriorityQueues.h2Performance.queuedPkts

       64 bit unsigned wrappable counter."
   ::= {pr1645v2Lan3VlanOutPQsH2PerformanceEntry 50331648}

pr1645v2Lan3VlanOutPQsH2PerformanceDropPkts OBJECT-TYPE
   SYNTAX      Counter64
   MAX-ACCESS  read-only
   STATUS      current
   DESCRIPTION
      "Path: ethernet3.performance.vlan.outPriorityQueues.h2Performance.droppedPkts

       64 bit unsigned wrappable counter."
   ::= {pr1645v2Lan3VlanOutPQsH2PerformanceEntry 67108864}

pr1645v2Lan3VlanOutPQsH2PerformanceRDropPkts OBJECT-TYPE
   SYNTAX      Counter64
   MAX-ACCESS  read-only
   STATUS      current
   DESCRIPTION
      "Path: ethernet3.performance.vlan.outPriorityQueues.h2Performance.redDroppedPkts

       64 bit unsigned wrappable counter."
   ::= {pr1645v2Lan3VlanOutPQsH2PerformanceEntry 201326592}

pr1645v2Lan3VlanOutPQsH2PerformanceCirTxPkts OBJECT-TYPE
   SYNTAX      Counter64
   MAX-ACCESS  read-only
   STATUS      current
   DESCRIPTION
      "Path: ethernet3.performance.vlan.outPriorityQueues.h2Performance.cirTxPkts

       64 bit unsigned wrappable counter."
   ::= {pr1645v2Lan3VlanOutPQsH2PerformanceEntry 83886080}

pr1645v2Lan3VlanOutPQsH2PerformanceEirTxPkts OBJECT-TYPE
   SYNTAX      Counter64
   MAX-ACCESS  read-only
   STATUS      current
   DESCRIPTION
      "Path: ethernet3.performance.vlan.outPriorityQueues.h2Performance.eirTxPkts

       64 bit unsigned wrappable counter."
   ::= {pr1645v2Lan3VlanOutPQsH2PerformanceEntry 100663296}

pr1645v2Lan3VlanOutPQsH2PerformanceViolTxPkts OBJECT-TYPE
   SYNTAX      Counter64
   MAX-ACCESS  read-only
   STATUS      current
   DESCRIPTION
      "Path: ethernet3.performance.vlan.outPriorityQueues.h2Performance.violateTxPkts

       64 bit unsigned wrappable counter."
   ::= {pr1645v2Lan3VlanOutPQsH2PerformanceEntry 301989888}

pr1645v2Lan3VlanOutPQsH2PerformanceTotOcts OBJECT-TYPE
   SYNTAX      Counter64
   MAX-ACCESS  read-only
   STATUS      current
   DESCRIPTION
      "Path: ethernet3.performance.vlan.outPriorityQueues.h2Performance.totalOctets

       64 bit unsigned wrappable counter."
   ::= {pr1645v2Lan3VlanOutPQsH2PerformanceEntry 251658240}

pr1645v2Lan3VlanOutPQsH2PerformanceDirTxOcts OBJECT-TYPE
   SYNTAX      Counter64
   MAX-ACCESS  read-only
   STATUS      current
   DESCRIPTION
      "Path: ethernet3.performance.vlan.outPriorityQueues.h2Performance.directTxOctets

       64 bit unsigned wrappable counter."
   ::= {pr1645v2Lan3VlanOutPQsH2PerformanceEntry 117440512}

pr1645v2Lan3VlanOutPQsH2PerformanceQdOcts OBJECT-TYPE
   SYNTAX      Counter64
   MAX-ACCESS  read-only
   STATUS      current
   DESCRIPTION
      "Path: ethernet3.performance.vlan.outPriorityQueues.h2Performance.queuedOctets

       64 bit unsigned wrappable counter."
   ::= {pr1645v2Lan3VlanOutPQsH2PerformanceEntry 134217728}

pr1645v2Lan3VlanOutPQsH2PerformanceDropOcts OBJECT-TYPE
   SYNTAX      Counter64
   MAX-ACCESS  read-only
   STATUS      current
   DESCRIPTION
      "Path: ethernet3.performance.vlan.outPriorityQueues.h2Performance.droppedOctets

       64 bit unsigned wrappable counter."
   ::= {pr1645v2Lan3VlanOutPQsH2PerformanceEntry 150994944}

pr1645v2Lan3VlanOutPQsH2PerformanceRDropOcts OBJECT-TYPE
   SYNTAX      Counter64
   MAX-ACCESS  read-only
   STATUS      current
   DESCRIPTION
      "Path: ethernet3.performance.vlan.outPriorityQueues.h2Performance.redDroppedOctets

       64 bit unsigned wrappable counter."
   ::= {pr1645v2Lan3VlanOutPQsH2PerformanceEntry 218103808}

pr1645v2Lan3VlanOutPQsH2PerformanceCirTxOcts OBJECT-TYPE
   SYNTAX      Counter64
   MAX-ACCESS  read-only
   STATUS      current
   DESCRIPTION
      "Path: ethernet3.performance.vlan.outPriorityQueues.h2Performance.cirTxOctets

       64 bit unsigned wrappable counter."
   ::= {pr1645v2Lan3VlanOutPQsH2PerformanceEntry 167772160}

pr1645v2Lan3VlanOutPQsH2PerformanceEirTxOcts OBJECT-TYPE
   SYNTAX      Counter64
   MAX-ACCESS  read-only
   STATUS      current
   DESCRIPTION
      "Path: ethernet3.performance.vlan.outPriorityQueues.h2Performance.eirTxOctets

       64 bit unsigned wrappable counter."
   ::= {pr1645v2Lan3VlanOutPQsH2PerformanceEntry 184549376}

pr1645v2Lan3VlanOutPQsH2PerformanceViolTxOcts OBJECT-TYPE
   SYNTAX      Counter64
   MAX-ACCESS  read-only
   STATUS      current
   DESCRIPTION
      "Path: ethernet3.performance.vlan.outPriorityQueues.h2Performance.violateTxOctets

       64 bit unsigned wrappable counter."
   ::= {pr1645v2Lan3VlanOutPQsH2PerformanceEntry 318767104}

pr1645v2Lan3VlanOutPQsH2PerformanceBandwidth OBJECT-TYPE
   SYNTAX      Integer32
   MAX-ACCESS  read-only
   STATUS      current
   DESCRIPTION
      "Path: ethernet3.performance.vlan.outPriorityQueues.h2Performance.bandwidth

       unit name = bps
       formula = 8 * ; 8 /"
   ::= {pr1645v2Lan3VlanOutPQsH2PerformanceEntry 268435456}

pr1645v2Lan3VlanOutPQsH24Performance OBJECT-TYPE
   SYNTAX      SEQUENCE OF Pr1645v2Lan3VlanOutPQsH24PerformanceEntry
   MAX-ACCESS  not-accessible
   STATUS      current
   DESCRIPTION
      ""
   ::= {pr1645v2Lan3Vlan 84279296}

pr1645v2Lan3VlanOutPQsH24PerformanceEntry OBJECT-TYPE
   SYNTAX      Pr1645v2Lan3VlanOutPQsH24PerformanceEntry
   MAX-ACCESS  not-accessible
   STATUS      current
   DESCRIPTION
      ""
   INDEX      { pr1645v2Lan3VlanTableIx,
                pr1645v2Lan3VlanOutPQsTableIx,
                pr1645v2Lan3VlanOutPQsH24PerformanceTableIx }
   ::= {pr1645v2Lan3VlanOutPQsH24Performance 1}

Pr1645v2Lan3VlanOutPQsH24PerformanceEntry ::=
   SEQUENCE
      {
      pr1645v2Lan3VlanOutPQsH24PerformanceTableIx
         TableIndex,
      pr1645v2Lan3VlanOutPQsH24PerformanceSysUpTime
         TimeTicks,
      pr1645v2Lan3VlanOutPQsH24PerformanceTotPkts
         Counter64,
      pr1645v2Lan3VlanOutPQsH24PerformanceDirTxPkts
         Counter64,
      pr1645v2Lan3VlanOutPQsH24PerformanceQdPkts
         Counter64,
      pr1645v2Lan3VlanOutPQsH24PerformanceDropPkts
         Counter64,
      pr1645v2Lan3VlanOutPQsH24PerformanceRDropPkts
         Counter64,
      pr1645v2Lan3VlanOutPQsH24PerformanceCirTxPkts
         Counter64,
      pr1645v2Lan3VlanOutPQsH24PerformanceEirTxPkts
         Counter64,
      pr1645v2Lan3VlanOutPQsH24PerformanceViolTxPkts
         Counter64,
      pr1645v2Lan3VlanOutPQsH24PerformanceTotOcts
         Counter64,
      pr1645v2Lan3VlanOutPQsH24PerformanceDirTxOcts
         Counter64,
      pr1645v2Lan3VlanOutPQsH24PerformanceQdOcts
         Counter64,
      pr1645v2Lan3VlanOutPQsH24PerformanceDropOcts
         Counter64,
      pr1645v2Lan3VlanOutPQsH24PerformanceRDropOcts
         Counter64,
      pr1645v2Lan3VlanOutPQsH24PerformanceCirTxOcts
         Counter64,
      pr1645v2Lan3VlanOutPQsH24PerformanceEirTxOcts
         Counter64,
      pr1645v2Lan3VlanOutPQsH24PerformanceViolTxOcts
         Counter64,
      pr1645v2Lan3VlanOutPQsH24PerformanceBandwidth
         Integer32
      }

pr1645v2Lan3VlanOutPQsH24PerformanceTableIx OBJECT-TYPE
   SYNTAX      TableIndex
   MAX-ACCESS  not-accessible
   STATUS      current
   DESCRIPTION
      ""
   ::= {pr1645v2Lan3VlanOutPQsH24PerformanceEntry 11}

pr1645v2Lan3VlanOutPQsH24PerformanceSysUpTime OBJECT-TYPE
   SYNTAX      TimeTicks
   MAX-ACCESS  read-only
   STATUS      current
   DESCRIPTION
      "Path: ethernet3.performance.vlan.outPriorityQueues.h24Performance.sysUpTime

       Time in centi-second."
   ::= {pr1645v2Lan3VlanOutPQsH24PerformanceEntry 16777216}

pr1645v2Lan3VlanOutPQsH24PerformanceTotPkts OBJECT-TYPE
   SYNTAX      Counter64
   MAX-ACCESS  read-only
   STATUS      current
   DESCRIPTION
      "Path: ethernet3.performance.vlan.outPriorityQueues.h24Performance.totalPkts

       64 bit unsigned wrappable counter."
   ::= {pr1645v2Lan3VlanOutPQsH24PerformanceEntry 234881024}

pr1645v2Lan3VlanOutPQsH24PerformanceDirTxPkts OBJECT-TYPE
   SYNTAX      Counter64
   MAX-ACCESS  read-only
   STATUS      current
   DESCRIPTION
      "Path: ethernet3.performance.vlan.outPriorityQueues.h24Performance.directTxPkts

       64 bit unsigned wrappable counter."
   ::= {pr1645v2Lan3VlanOutPQsH24PerformanceEntry 33554432}

pr1645v2Lan3VlanOutPQsH24PerformanceQdPkts OBJECT-TYPE
   SYNTAX      Counter64
   MAX-ACCESS  read-only
   STATUS      current
   DESCRIPTION
      "Path: ethernet3.performance.vlan.outPriorityQueues.h24Performance.queuedPkts

       64 bit unsigned wrappable counter."
   ::= {pr1645v2Lan3VlanOutPQsH24PerformanceEntry 50331648}

pr1645v2Lan3VlanOutPQsH24PerformanceDropPkts OBJECT-TYPE
   SYNTAX      Counter64
   MAX-ACCESS  read-only
   STATUS      current
   DESCRIPTION
      "Path: ethernet3.performance.vlan.outPriorityQueues.h24Performance.droppedPkts

       64 bit unsigned wrappable counter."
   ::= {pr1645v2Lan3VlanOutPQsH24PerformanceEntry 67108864}

pr1645v2Lan3VlanOutPQsH24PerformanceRDropPkts OBJECT-TYPE
   SYNTAX      Counter64
   MAX-ACCESS  read-only
   STATUS      current
   DESCRIPTION
      "Path: ethernet3.performance.vlan.outPriorityQueues.h24Performance.redDroppedPkts

       64 bit unsigned wrappable counter."
   ::= {pr1645v2Lan3VlanOutPQsH24PerformanceEntry 201326592}

pr1645v2Lan3VlanOutPQsH24PerformanceCirTxPkts OBJECT-TYPE
   SYNTAX      Counter64
   MAX-ACCESS  read-only
   STATUS      current
   DESCRIPTION
      "Path: ethernet3.performance.vlan.outPriorityQueues.h24Performance.cirTxPkts

       64 bit unsigned wrappable counter."
   ::= {pr1645v2Lan3VlanOutPQsH24PerformanceEntry 83886080}

pr1645v2Lan3VlanOutPQsH24PerformanceEirTxPkts OBJECT-TYPE
   SYNTAX      Counter64
   MAX-ACCESS  read-only
   STATUS      current
   DESCRIPTION
      "Path: ethernet3.performance.vlan.outPriorityQueues.h24Performance.eirTxPkts

       64 bit unsigned wrappable counter."
   ::= {pr1645v2Lan3VlanOutPQsH24PerformanceEntry 100663296}

pr1645v2Lan3VlanOutPQsH24PerformanceViolTxPkts OBJECT-TYPE
   SYNTAX      Counter64
   MAX-ACCESS  read-only
   STATUS      current
   DESCRIPTION
      "Path: ethernet3.performance.vlan.outPriorityQueues.h24Performance.violateTxPkts

       64 bit unsigned wrappable counter."
   ::= {pr1645v2Lan3VlanOutPQsH24PerformanceEntry 301989888}

pr1645v2Lan3VlanOutPQsH24PerformanceTotOcts OBJECT-TYPE
   SYNTAX      Counter64
   MAX-ACCESS  read-only
   STATUS      current
   DESCRIPTION
      "Path: ethernet3.performance.vlan.outPriorityQueues.h24Performance.totalOctets

       64 bit unsigned wrappable counter."
   ::= {pr1645v2Lan3VlanOutPQsH24PerformanceEntry 251658240}

pr1645v2Lan3VlanOutPQsH24PerformanceDirTxOcts OBJECT-TYPE
   SYNTAX      Counter64
   MAX-ACCESS  read-only
   STATUS      current
   DESCRIPTION
      "Path: ethernet3.performance.vlan.outPriorityQueues.h24Performance.directTxOctets

       64 bit unsigned wrappable counter."
   ::= {pr1645v2Lan3VlanOutPQsH24PerformanceEntry 117440512}

pr1645v2Lan3VlanOutPQsH24PerformanceQdOcts OBJECT-TYPE
   SYNTAX      Counter64
   MAX-ACCESS  read-only
   STATUS      current
   DESCRIPTION
      "Path: ethernet3.performance.vlan.outPriorityQueues.h24Performance.queuedOctets

       64 bit unsigned wrappable counter."
   ::= {pr1645v2Lan3VlanOutPQsH24PerformanceEntry 134217728}

pr1645v2Lan3VlanOutPQsH24PerformanceDropOcts OBJECT-TYPE
   SYNTAX      Counter64
   MAX-ACCESS  read-only
   STATUS      current
   DESCRIPTION
      "Path: ethernet3.performance.vlan.outPriorityQueues.h24Performance.droppedOctets

       64 bit unsigned wrappable counter."
   ::= {pr1645v2Lan3VlanOutPQsH24PerformanceEntry 150994944}

pr1645v2Lan3VlanOutPQsH24PerformanceRDropOcts OBJECT-TYPE
   SYNTAX      Counter64
   MAX-ACCESS  read-only
   STATUS      current
   DESCRIPTION
      "Path: ethernet3.performance.vlan.outPriorityQueues.h24Performance.redDroppedOctets

       64 bit unsigned wrappable counter."
   ::= {pr1645v2Lan3VlanOutPQsH24PerformanceEntry 218103808}

pr1645v2Lan3VlanOutPQsH24PerformanceCirTxOcts OBJECT-TYPE
   SYNTAX      Counter64
   MAX-ACCESS  read-only
   STATUS      current
   DESCRIPTION
      "Path: ethernet3.performance.vlan.outPriorityQueues.h24Performance.cirTxOctets

       64 bit unsigned wrappable counter."
   ::= {pr1645v2Lan3VlanOutPQsH24PerformanceEntry 167772160}

pr1645v2Lan3VlanOutPQsH24PerformanceEirTxOcts OBJECT-TYPE
   SYNTAX      Counter64
   MAX-ACCESS  read-only
   STATUS      current
   DESCRIPTION
      "Path: ethernet3.performance.vlan.outPriorityQueues.h24Performance.eirTxOctets

       64 bit unsigned wrappable counter."
   ::= {pr1645v2Lan3VlanOutPQsH24PerformanceEntry 184549376}

pr1645v2Lan3VlanOutPQsH24PerformanceViolTxOcts OBJECT-TYPE
   SYNTAX      Counter64
   MAX-ACCESS  read-only
   STATUS      current
   DESCRIPTION
      "Path: ethernet3.performance.vlan.outPriorityQueues.h24Performance.violateTxOctets

       64 bit unsigned wrappable counter."
   ::= {pr1645v2Lan3VlanOutPQsH24PerformanceEntry 318767104}

pr1645v2Lan3VlanOutPQsH24PerformanceBandwidth OBJECT-TYPE
   SYNTAX      Integer32
   MAX-ACCESS  read-only
   STATUS      current
   DESCRIPTION
      "Path: ethernet3.performance.vlan.outPriorityQueues.h24Performance.bandwidth

       unit name = bps
       formula = 8 * ; 8 /"
   ::= {pr1645v2Lan3VlanOutPQsH24PerformanceEntry 268435456}

pr1645v2Lan3VlanOutPQsD7Performance OBJECT-TYPE
   SYNTAX      SEQUENCE OF Pr1645v2Lan3VlanOutPQsD7PerformanceEntry
   MAX-ACCESS  not-accessible
   STATUS      current
   DESCRIPTION
      ""
   ::= {pr1645v2Lan3Vlan 84344832}

pr1645v2Lan3VlanOutPQsD7PerformanceEntry OBJECT-TYPE
   SYNTAX      Pr1645v2Lan3VlanOutPQsD7PerformanceEntry
   MAX-ACCESS  not-accessible
   STATUS      current
   DESCRIPTION
      ""
   INDEX      { pr1645v2Lan3VlanTableIx,
                pr1645v2Lan3VlanOutPQsTableIx,
                pr1645v2Lan3VlanOutPQsD7PerformanceTableIx }
   ::= {pr1645v2Lan3VlanOutPQsD7Performance 1}

Pr1645v2Lan3VlanOutPQsD7PerformanceEntry ::=
   SEQUENCE
      {
      pr1645v2Lan3VlanOutPQsD7PerformanceTableIx
         TableIndex,
      pr1645v2Lan3VlanOutPQsD7PerformanceSysUpTime
         TimeTicks,
      pr1645v2Lan3VlanOutPQsD7PerformanceTotPkts
         Counter64,
      pr1645v2Lan3VlanOutPQsD7PerformanceDirTxPkts
         Counter64,
      pr1645v2Lan3VlanOutPQsD7PerformanceQdPkts
         Counter64,
      pr1645v2Lan3VlanOutPQsD7PerformanceDropPkts
         Counter64,
      pr1645v2Lan3VlanOutPQsD7PerformanceRDropPkts
         Counter64,
      pr1645v2Lan3VlanOutPQsD7PerformanceCirTxPkts
         Counter64,
      pr1645v2Lan3VlanOutPQsD7PerformanceEirTxPkts
         Counter64,
      pr1645v2Lan3VlanOutPQsD7PerformanceViolTxPkts
         Counter64,
      pr1645v2Lan3VlanOutPQsD7PerformanceTotOcts
         Counter64,
      pr1645v2Lan3VlanOutPQsD7PerformanceDirTxOcts
         Counter64,
      pr1645v2Lan3VlanOutPQsD7PerformanceQdOcts
         Counter64,
      pr1645v2Lan3VlanOutPQsD7PerformanceDropOcts
         Counter64,
      pr1645v2Lan3VlanOutPQsD7PerformanceRDropOcts
         Counter64,
      pr1645v2Lan3VlanOutPQsD7PerformanceCirTxOcts
         Counter64,
      pr1645v2Lan3VlanOutPQsD7PerformanceEirTxOcts
         Counter64,
      pr1645v2Lan3VlanOutPQsD7PerformanceViolTxOcts
         Counter64,
      pr1645v2Lan3VlanOutPQsD7PerformanceBandwidth
         Integer32
      }

pr1645v2Lan3VlanOutPQsD7PerformanceTableIx OBJECT-TYPE
   SYNTAX      TableIndex
   MAX-ACCESS  not-accessible
   STATUS      current
   DESCRIPTION
      ""
   ::= {pr1645v2Lan3VlanOutPQsD7PerformanceEntry 11}

pr1645v2Lan3VlanOutPQsD7PerformanceSysUpTime OBJECT-TYPE
   SYNTAX      TimeTicks
   MAX-ACCESS  read-only
   STATUS      current
   DESCRIPTION
      "Path: ethernet3.performance.vlan.outPriorityQueues.d7Performance.sysUpTime

       Time in centi-second."
   ::= {pr1645v2Lan3VlanOutPQsD7PerformanceEntry 16777216}

pr1645v2Lan3VlanOutPQsD7PerformanceTotPkts OBJECT-TYPE
   SYNTAX      Counter64
   MAX-ACCESS  read-only
   STATUS      current
   DESCRIPTION
      "Path: ethernet3.performance.vlan.outPriorityQueues.d7Performance.totalPkts

       64 bit unsigned wrappable counter."
   ::= {pr1645v2Lan3VlanOutPQsD7PerformanceEntry 234881024}

pr1645v2Lan3VlanOutPQsD7PerformanceDirTxPkts OBJECT-TYPE
   SYNTAX      Counter64
   MAX-ACCESS  read-only
   STATUS      current
   DESCRIPTION
      "Path: ethernet3.performance.vlan.outPriorityQueues.d7Performance.directTxPkts

       64 bit unsigned wrappable counter."
   ::= {pr1645v2Lan3VlanOutPQsD7PerformanceEntry 33554432}

pr1645v2Lan3VlanOutPQsD7PerformanceQdPkts OBJECT-TYPE
   SYNTAX      Counter64
   MAX-ACCESS  read-only
   STATUS      current
   DESCRIPTION
      "Path: ethernet3.performance.vlan.outPriorityQueues.d7Performance.queuedPkts

       64 bit unsigned wrappable counter."
   ::= {pr1645v2Lan3VlanOutPQsD7PerformanceEntry 50331648}

pr1645v2Lan3VlanOutPQsD7PerformanceDropPkts OBJECT-TYPE
   SYNTAX      Counter64
   MAX-ACCESS  read-only
   STATUS      current
   DESCRIPTION
      "Path: ethernet3.performance.vlan.outPriorityQueues.d7Performance.droppedPkts

       64 bit unsigned wrappable counter."
   ::= {pr1645v2Lan3VlanOutPQsD7PerformanceEntry 67108864}

pr1645v2Lan3VlanOutPQsD7PerformanceRDropPkts OBJECT-TYPE
   SYNTAX      Counter64
   MAX-ACCESS  read-only
   STATUS      current
   DESCRIPTION
      "Path: ethernet3.performance.vlan.outPriorityQueues.d7Performance.redDroppedPkts

       64 bit unsigned wrappable counter."
   ::= {pr1645v2Lan3VlanOutPQsD7PerformanceEntry 201326592}

pr1645v2Lan3VlanOutPQsD7PerformanceCirTxPkts OBJECT-TYPE
   SYNTAX      Counter64
   MAX-ACCESS  read-only
   STATUS      current
   DESCRIPTION
      "Path: ethernet3.performance.vlan.outPriorityQueues.d7Performance.cirTxPkts

       64 bit unsigned wrappable counter."
   ::= {pr1645v2Lan3VlanOutPQsD7PerformanceEntry 83886080}

pr1645v2Lan3VlanOutPQsD7PerformanceEirTxPkts OBJECT-TYPE
   SYNTAX      Counter64
   MAX-ACCESS  read-only
   STATUS      current
   DESCRIPTION
      "Path: ethernet3.performance.vlan.outPriorityQueues.d7Performance.eirTxPkts

       64 bit unsigned wrappable counter."
   ::= {pr1645v2Lan3VlanOutPQsD7PerformanceEntry 100663296}

pr1645v2Lan3VlanOutPQsD7PerformanceViolTxPkts OBJECT-TYPE
   SYNTAX      Counter64
   MAX-ACCESS  read-only
   STATUS      current
   DESCRIPTION
      "Path: ethernet3.performance.vlan.outPriorityQueues.d7Performance.violateTxPkts

       64 bit unsigned wrappable counter."
   ::= {pr1645v2Lan3VlanOutPQsD7PerformanceEntry 301989888}

pr1645v2Lan3VlanOutPQsD7PerformanceTotOcts OBJECT-TYPE
   SYNTAX      Counter64
   MAX-ACCESS  read-only
   STATUS      current
   DESCRIPTION
      "Path: ethernet3.performance.vlan.outPriorityQueues.d7Performance.totalOctets

       64 bit unsigned wrappable counter."
   ::= {pr1645v2Lan3VlanOutPQsD7PerformanceEntry 251658240}

pr1645v2Lan3VlanOutPQsD7PerformanceDirTxOcts OBJECT-TYPE
   SYNTAX      Counter64
   MAX-ACCESS  read-only
   STATUS      current
   DESCRIPTION
      "Path: ethernet3.performance.vlan.outPriorityQueues.d7Performance.directTxOctets

       64 bit unsigned wrappable counter."
   ::= {pr1645v2Lan3VlanOutPQsD7PerformanceEntry 117440512}

pr1645v2Lan3VlanOutPQsD7PerformanceQdOcts OBJECT-TYPE
   SYNTAX      Counter64
   MAX-ACCESS  read-only
   STATUS      current
   DESCRIPTION
      "Path: ethernet3.performance.vlan.outPriorityQueues.d7Performance.queuedOctets

       64 bit unsigned wrappable counter."
   ::= {pr1645v2Lan3VlanOutPQsD7PerformanceEntry 134217728}

pr1645v2Lan3VlanOutPQsD7PerformanceDropOcts OBJECT-TYPE
   SYNTAX      Counter64
   MAX-ACCESS  read-only
   STATUS      current
   DESCRIPTION
      "Path: ethernet3.performance.vlan.outPriorityQueues.d7Performance.droppedOctets

       64 bit unsigned wrappable counter."
   ::= {pr1645v2Lan3VlanOutPQsD7PerformanceEntry 150994944}

pr1645v2Lan3VlanOutPQsD7PerformanceRDropOcts OBJECT-TYPE
   SYNTAX      Counter64
   MAX-ACCESS  read-only
   STATUS      current
   DESCRIPTION
      "Path: ethernet3.performance.vlan.outPriorityQueues.d7Performance.redDroppedOctets

       64 bit unsigned wrappable counter."
   ::= {pr1645v2Lan3VlanOutPQsD7PerformanceEntry 218103808}

pr1645v2Lan3VlanOutPQsD7PerformanceCirTxOcts OBJECT-TYPE
   SYNTAX      Counter64
   MAX-ACCESS  read-only
   STATUS      current
   DESCRIPTION
      "Path: ethernet3.performance.vlan.outPriorityQueues.d7Performance.cirTxOctets

       64 bit unsigned wrappable counter."
   ::= {pr1645v2Lan3VlanOutPQsD7PerformanceEntry 167772160}

pr1645v2Lan3VlanOutPQsD7PerformanceEirTxOcts OBJECT-TYPE
   SYNTAX      Counter64
   MAX-ACCESS  read-only
   STATUS      current
   DESCRIPTION
      "Path: ethernet3.performance.vlan.outPriorityQueues.d7Performance.eirTxOctets

       64 bit unsigned wrappable counter."
   ::= {pr1645v2Lan3VlanOutPQsD7PerformanceEntry 184549376}

pr1645v2Lan3VlanOutPQsD7PerformanceViolTxOcts OBJECT-TYPE
   SYNTAX      Counter64
   MAX-ACCESS  read-only
   STATUS      current
   DESCRIPTION
      "Path: ethernet3.performance.vlan.outPriorityQueues.d7Performance.violateTxOctets

       64 bit unsigned wrappable counter."
   ::= {pr1645v2Lan3VlanOutPQsD7PerformanceEntry 318767104}

pr1645v2Lan3VlanOutPQsD7PerformanceBandwidth OBJECT-TYPE
   SYNTAX      Integer32
   MAX-ACCESS  read-only
   STATUS      current
   DESCRIPTION
      "Path: ethernet3.performance.vlan.outPriorityQueues.d7Performance.bandwidth

       unit name = bps
       formula = 8 * ; 8 /"
   ::= {pr1645v2Lan3VlanOutPQsD7PerformanceEntry 268435456}


pr1645v2Lan3PPPoE OBJECT IDENTIFIER ::= {pr1645v2Lan3 53}

pr1645v2Lan3PPPoESSCTable OBJECT-TYPE
   SYNTAX      SEQUENCE OF Pr1645v2Lan3PPPoEEntry
   MAX-ACCESS  not-accessible
   STATUS      current
   DESCRIPTION
      ""
   ::= {pr1645v2Lan3PPPoE 1}

pr1645v2Lan3PPPoEEntry OBJECT-TYPE
   SYNTAX      Pr1645v2Lan3PPPoEEntry
   MAX-ACCESS  not-accessible
   STATUS      current
   DESCRIPTION
      ""
   INDEX      { pr1645v2Lan3PPPoETableIx }
   ::= {pr1645v2Lan3PPPoESSCTable 1}

Pr1645v2Lan3PPPoEEntry ::=
   SEQUENCE
      {
      pr1645v2Lan3PPPoETableIx
         TableIndex,
      pr1645v2Lan3PPPoEName
         DisplayString,
      pr1645v2Lan3PPPoEMCInOctets
         Counter64,
      pr1645v2Lan3PPPoEMCInUcast
         Counter64,
      pr1645v2Lan3PPPoEMCInNUcastPkts
         Counter64,
      pr1645v2Lan3PPPoEMCInBcastPkts
         Counter64,
      pr1645v2Lan3PPPoEMCInMcastPkts
         Counter64,
      pr1645v2Lan3PPPoEMCInDiscards
         Counter64,
      pr1645v2Lan3PPPoEMCInErrors
         Counter64,
      pr1645v2Lan3PPPoEMCInUnknownProtos
         Counter64,
      pr1645v2Lan3PPPoEMCInDropEx
         Counter64,
      pr1645v2Lan3PPPoEMCInDropNoMac
         Counter64,
      pr1645v2Lan3PPPoEMCInDropNUCast
         Counter64,
      pr1645v2Lan3PPPoEMCInDropFilter
         Counter64,
      pr1645v2Lan3PPPoEMCInBandwidth15sec
         Integer32,
      pr1645v2Lan3PPPoEMCInBandwidth30sec
         Integer32,
      pr1645v2Lan3PPPoEMCInBandwidth1min
         Integer32,
      pr1645v2Lan3PPPoEMCInBandwidth2min
         Integer32,
      pr1645v2Lan3PPPoEMCInBandwidth5min
         Integer32,
      pr1645v2Lan3PPPoEMCOutOctets
         Counter64,
      pr1645v2Lan3PPPoEMCOutUcastPkts
         Counter64,
      pr1645v2Lan3PPPoEMCOutNUcastPkts
         Counter64,
      pr1645v2Lan3PPPoEMCOutBcastPkts
         Counter64,
      pr1645v2Lan3PPPoEMCOutMcastPkts
         Counter64,
      pr1645v2Lan3PPPoEMCOutDiscards
         Counter64,
      pr1645v2Lan3PPPoEMCOutErrors
         Counter64,
      pr1645v2Lan3PPPoEMCOutQLen
         Counter32,
      pr1645v2Lan3PPPoEMCOutDropEx
         Counter64,
      pr1645v2Lan3PPPoEMCOutDropNoArp
         Counter64,
      pr1645v2Lan3PPPoEMCOutDropFilter
         Counter64,
      pr1645v2Lan3PPPoEMCOutBandwidth15sec
         Integer32,
      pr1645v2Lan3PPPoEMCOutBandwidth30sec
         Integer32,
      pr1645v2Lan3PPPoEMCOutBandwidth1min
         Integer32,
      pr1645v2Lan3PPPoEMCOutBandwidth2min
         Integer32,
      pr1645v2Lan3PPPoEMCOutBandwidth5min
         Integer32,
      pr1645v2Lan3PPPoEPppLinkMonitoringRequestsSent
         Gauge32,
      pr1645v2Lan3PPPoEPppLinkMonitoringRepliesRcvd
         Gauge32,
      pr1645v2Lan3PPPoEPppLinkMonitoringRequestsRcvd
         Gauge32,
      pr1645v2Lan3PPPoEPppLinkMonitoringRepliesSent
         Gauge32
      }

pr1645v2Lan3PPPoETableIx OBJECT-TYPE
   SYNTAX      TableIndex
   MAX-ACCESS  not-accessible
   STATUS      current
   DESCRIPTION
      ""
   ::= {pr1645v2Lan3PPPoEEntry 11}

pr1645v2Lan3PPPoEName OBJECT-TYPE
   SYNTAX      DisplayString
   MAX-ACCESS  read-only
   STATUS      current
   DESCRIPTION
      "Path: ethernet3.performance.pppoEClient.name"
   ::= {pr1645v2Lan3PPPoEEntry 16777216}

pr1645v2Lan3PPPoEMCInOctets OBJECT-TYPE
   SYNTAX      Counter64
   MAX-ACCESS  read-only
   STATUS      current
   DESCRIPTION
      "Path: ethernet3.performance.pppoEClient.mibCounters.ifInOctets

       64 bit unsigned wrappable counter."
   ::= {pr1645v2Lan3PPPoEEntry 40697856}

pr1645v2Lan3PPPoEMCInUcast OBJECT-TYPE
   SYNTAX      Counter64
   MAX-ACCESS  read-only
   STATUS      current
   DESCRIPTION
      "Path: ethernet3.performance.pppoEClient.mibCounters.ifInUcastPkts

       64 bit unsigned wrappable counter."
   ::= {pr1645v2Lan3PPPoEEntry 40763392}

pr1645v2Lan3PPPoEMCInNUcastPkts OBJECT-TYPE
   SYNTAX      Counter64
   MAX-ACCESS  read-only
   STATUS      current
   DESCRIPTION
      "Path: ethernet3.performance.pppoEClient.mibCounters.ifInNUcastPkts

       64 bit unsigned wrappable counter."
   ::= {pr1645v2Lan3PPPoEEntry 40828928}

pr1645v2Lan3PPPoEMCInBcastPkts OBJECT-TYPE
   SYNTAX      Counter64
   MAX-ACCESS  read-only
   STATUS      current
   DESCRIPTION
      "Path: ethernet3.performance.pppoEClient.mibCounters.ifInBcastPkts

       64 bit unsigned wrappable counter."
   ::= {pr1645v2Lan3PPPoEEntry 47382528}

pr1645v2Lan3PPPoEMCInMcastPkts OBJECT-TYPE
   SYNTAX      Counter64
   MAX-ACCESS  read-only
   STATUS      current
   DESCRIPTION
      "Path: ethernet3.performance.pppoEClient.mibCounters.ifInMcastPkts

       64 bit unsigned wrappable counter."
   ::= {pr1645v2Lan3PPPoEEntry 48037888}

pr1645v2Lan3PPPoEMCInDiscards OBJECT-TYPE
   SYNTAX      Counter64
   MAX-ACCESS  read-only
   STATUS      current
   DESCRIPTION
      "Path: ethernet3.performance.pppoEClient.mibCounters.ifInDiscards

       64 bit unsigned wrappable counter."
   ::= {pr1645v2Lan3PPPoEEntry 40894464}

pr1645v2Lan3PPPoEMCInErrors OBJECT-TYPE
   SYNTAX      Counter64
   MAX-ACCESS  read-only
   STATUS      current
   DESCRIPTION
      "Path: ethernet3.performance.pppoEClient.mibCounters.ifInErrors

       64 bit unsigned wrappable counter."
   ::= {pr1645v2Lan3PPPoEEntry 40960000}

pr1645v2Lan3PPPoEMCInUnknownProtos OBJECT-TYPE
   SYNTAX      Counter64
   MAX-ACCESS  read-only
   STATUS      current
   DESCRIPTION
      "Path: ethernet3.performance.pppoEClient.mibCounters.ifInUnknownProtos

       64 bit unsigned wrappable counter."
   ::= {pr1645v2Lan3PPPoEEntry 41025536}

pr1645v2Lan3PPPoEMCInDropEx OBJECT-TYPE
   SYNTAX      Counter64
   MAX-ACCESS  read-only
   STATUS      current
   DESCRIPTION
      "Path: ethernet3.performance.pppoEClient.mibCounters.ifInDropLevelExceeded

       64 bit unsigned wrappable counter."
   ::= {pr1645v2Lan3PPPoEEntry 42074112}

pr1645v2Lan3PPPoEMCInDropNoMac OBJECT-TYPE
   SYNTAX      Counter64
   MAX-ACCESS  read-only
   STATUS      current
   DESCRIPTION
      "Path: ethernet3.performance.pppoEClient.mibCounters.ifInDiscardsNoMacFit

       64 bit unsigned wrappable counter."
   ::= {pr1645v2Lan3PPPoEEntry 42270720}

pr1645v2Lan3PPPoEMCInDropNUCast OBJECT-TYPE
   SYNTAX      Counter64
   MAX-ACCESS  read-only
   STATUS      current
   DESCRIPTION
      "Path: ethernet3.performance.pppoEClient.mibCounters.ifInDiscardsNUCast

       64 bit unsigned wrappable counter."
   ::= {pr1645v2Lan3PPPoEEntry 42467328}

pr1645v2Lan3PPPoEMCInDropFilter OBJECT-TYPE
   SYNTAX      Counter64
   MAX-ACCESS  read-only
   STATUS      current
   DESCRIPTION
      "Path: ethernet3.performance.pppoEClient.mibCounters.ifInDiscardsFilter

       64 bit unsigned wrappable counter."
   ::= {pr1645v2Lan3PPPoEEntry 42532864}

pr1645v2Lan3PPPoEMCInBandwidth15sec OBJECT-TYPE
   SYNTAX      Integer32
   MAX-ACCESS  read-only
   STATUS      current
   DESCRIPTION
      "Path: ethernet3.performance.pppoEClient.mibCounters.ifInBandwidth.15sec

       unit name = bps
       formula = 8 * ; 8 /"
   ::= {pr1645v2Lan3PPPoEEntry 45417728}

pr1645v2Lan3PPPoEMCInBandwidth30sec OBJECT-TYPE
   SYNTAX      Integer32
   MAX-ACCESS  read-only
   STATUS      current
   DESCRIPTION
      "Path: ethernet3.performance.pppoEClient.mibCounters.ifInBandwidth.30sec

       unit name = bps
       formula = 8 * ; 8 /"
   ::= {pr1645v2Lan3PPPoEEntry 45419008}

pr1645v2Lan3PPPoEMCInBandwidth1min OBJECT-TYPE
   SYNTAX      Integer32
   MAX-ACCESS  read-only
   STATUS      current
   DESCRIPTION
      "Path: ethernet3.performance.pppoEClient.mibCounters.ifInBandwidth.1min

       unit name = bps
       formula = 8 * ; 8 /"
   ::= {pr1645v2Lan3PPPoEEntry 45421568}

pr1645v2Lan3PPPoEMCInBandwidth2min OBJECT-TYPE
   SYNTAX      Integer32
   MAX-ACCESS  read-only
   STATUS      current
   DESCRIPTION
      "Path: ethernet3.performance.pppoEClient.mibCounters.ifInBandwidth.2min

       unit name = bps
       formula = 8 * ; 8 /"
   ::= {pr1645v2Lan3PPPoEEntry 45426688}

pr1645v2Lan3PPPoEMCInBandwidth5min OBJECT-TYPE
   SYNTAX      Integer32
   MAX-ACCESS  read-only
   STATUS      current
   DESCRIPTION
      "Path: ethernet3.performance.pppoEClient.mibCounters.ifInBandwidth.5min

       unit name = bps
       formula = 8 * ; 8 /"
   ::= {pr1645v2Lan3PPPoEEntry 45442048}

pr1645v2Lan3PPPoEMCOutOctets OBJECT-TYPE
   SYNTAX      Counter64
   MAX-ACCESS  read-only
   STATUS      current
   DESCRIPTION
      "Path: ethernet3.performance.pppoEClient.mibCounters.ifOutOctets

       64 bit unsigned wrappable counter."
   ::= {pr1645v2Lan3PPPoEEntry 41091072}

pr1645v2Lan3PPPoEMCOutUcastPkts OBJECT-TYPE
   SYNTAX      Counter64
   MAX-ACCESS  read-only
   STATUS      current
   DESCRIPTION
      "Path: ethernet3.performance.pppoEClient.mibCounters.ifOutUcastPkts

       64 bit unsigned wrappable counter."
   ::= {pr1645v2Lan3PPPoEEntry 41156608}

pr1645v2Lan3PPPoEMCOutNUcastPkts OBJECT-TYPE
   SYNTAX      Counter64
   MAX-ACCESS  read-only
   STATUS      current
   DESCRIPTION
      "Path: ethernet3.performance.pppoEClient.mibCounters.ifOutNUcastPkts

       64 bit unsigned wrappable counter."
   ::= {pr1645v2Lan3PPPoEEntry 41222144}

pr1645v2Lan3PPPoEMCOutBcastPkts OBJECT-TYPE
   SYNTAX      Counter64
   MAX-ACCESS  read-only
   STATUS      current
   DESCRIPTION
      "Path: ethernet3.performance.pppoEClient.mibCounters.ifOutBcastPkts

       64 bit unsigned wrappable counter."
   ::= {pr1645v2Lan3PPPoEEntry 47775744}

pr1645v2Lan3PPPoEMCOutMcastPkts OBJECT-TYPE
   SYNTAX      Counter64
   MAX-ACCESS  read-only
   STATUS      current
   DESCRIPTION
      "Path: ethernet3.performance.pppoEClient.mibCounters.ifOutMcastPkts

       64 bit unsigned wrappable counter."
   ::= {pr1645v2Lan3PPPoEEntry 48431104}

pr1645v2Lan3PPPoEMCOutDiscards OBJECT-TYPE
   SYNTAX      Counter64
   MAX-ACCESS  read-only
   STATUS      current
   DESCRIPTION
      "Path: ethernet3.performance.pppoEClient.mibCounters.ifOutDiscards

       64 bit unsigned wrappable counter."
   ::= {pr1645v2Lan3PPPoEEntry 41287680}

pr1645v2Lan3PPPoEMCOutErrors OBJECT-TYPE
   SYNTAX      Counter64
   MAX-ACCESS  read-only
   STATUS      current
   DESCRIPTION
      "Path: ethernet3.performance.pppoEClient.mibCounters.ifOutErrors

       64 bit unsigned wrappable counter."
   ::= {pr1645v2Lan3PPPoEEntry 41353216}

pr1645v2Lan3PPPoEMCOutQLen OBJECT-TYPE
   SYNTAX      Counter32
   MAX-ACCESS  read-only
   STATUS      current
   DESCRIPTION
      "Path: ethernet3.performance.pppoEClient.mibCounters.ifOutQLen

       32 bit unsigned wrappable counter."
   ::= {pr1645v2Lan3PPPoEEntry 41418752}

pr1645v2Lan3PPPoEMCOutDropEx OBJECT-TYPE
   SYNTAX      Counter64
   MAX-ACCESS  read-only
   STATUS      current
   DESCRIPTION
      "Path: ethernet3.performance.pppoEClient.mibCounters.ifOutDropLevelExceeded

       64 bit unsigned wrappable counter."
   ::= {pr1645v2Lan3PPPoEEntry 41484288}

pr1645v2Lan3PPPoEMCOutDropNoArp OBJECT-TYPE
   SYNTAX      Counter64
   MAX-ACCESS  read-only
   STATUS      current
   DESCRIPTION
      "Path: ethernet3.performance.pppoEClient.mibCounters.ifOutDiscardsNoArp

       64 bit unsigned wrappable counter."
   ::= {pr1645v2Lan3PPPoEEntry 42336256}

pr1645v2Lan3PPPoEMCOutDropFilter OBJECT-TYPE
   SYNTAX      Counter64
   MAX-ACCESS  read-only
   STATUS      current
   DESCRIPTION
      "Path: ethernet3.performance.pppoEClient.mibCounters.ifOutDiscardsFilter

       64 bit unsigned wrappable counter."
   ::= {pr1645v2Lan3PPPoEEntry 42598400}

pr1645v2Lan3PPPoEMCOutBandwidth15sec OBJECT-TYPE
   SYNTAX      Integer32
   MAX-ACCESS  read-only
   STATUS      current
   DESCRIPTION
      "Path: ethernet3.performance.pppoEClient.mibCounters.ifOutBandwidth.15sec

       unit name = bps
       formula = 8 * ; 8 /"
   ::= {pr1645v2Lan3PPPoEEntry 45483264}

pr1645v2Lan3PPPoEMCOutBandwidth30sec OBJECT-TYPE
   SYNTAX      Integer32
   MAX-ACCESS  read-only
   STATUS      current
   DESCRIPTION
      "Path: ethernet3.performance.pppoEClient.mibCounters.ifOutBandwidth.30sec

       unit name = bps
       formula = 8 * ; 8 /"
   ::= {pr1645v2Lan3PPPoEEntry 45484544}

pr1645v2Lan3PPPoEMCOutBandwidth1min OBJECT-TYPE
   SYNTAX      Integer32
   MAX-ACCESS  read-only
   STATUS      current
   DESCRIPTION
      "Path: ethernet3.performance.pppoEClient.mibCounters.ifOutBandwidth.1min

       unit name = bps
       formula = 8 * ; 8 /"
   ::= {pr1645v2Lan3PPPoEEntry 45487104}

pr1645v2Lan3PPPoEMCOutBandwidth2min OBJECT-TYPE
   SYNTAX      Integer32
   MAX-ACCESS  read-only
   STATUS      current
   DESCRIPTION
      "Path: ethernet3.performance.pppoEClient.mibCounters.ifOutBandwidth.2min

       unit name = bps
       formula = 8 * ; 8 /"
   ::= {pr1645v2Lan3PPPoEEntry 45492224}

pr1645v2Lan3PPPoEMCOutBandwidth5min OBJECT-TYPE
   SYNTAX      Integer32
   MAX-ACCESS  read-only
   STATUS      current
   DESCRIPTION
      "Path: ethernet3.performance.pppoEClient.mibCounters.ifOutBandwidth.5min

       unit name = bps
       formula = 8 * ; 8 /"
   ::= {pr1645v2Lan3PPPoEEntry 45507584}

pr1645v2Lan3PPPoEPppLinkMonitoringRequestsSent OBJECT-TYPE
   SYNTAX      Gauge32
   MAX-ACCESS  read-only
   STATUS      current
   DESCRIPTION
      "Path: ethernet3.performance.pppoEClient.ppp.linkMonitoring.requestsSent

       32 bit unsigned gauge value."
   ::= {pr1645v2Lan3PPPoEEntry 50397440}

pr1645v2Lan3PPPoEPppLinkMonitoringRepliesRcvd OBJECT-TYPE
   SYNTAX      Gauge32
   MAX-ACCESS  read-only
   STATUS      current
   DESCRIPTION
      "Path: ethernet3.performance.pppoEClient.ppp.linkMonitoring.repliesRcvd

       32 bit unsigned gauge value."
   ::= {pr1645v2Lan3PPPoEEntry 50397696}

pr1645v2Lan3PPPoEPppLinkMonitoringRequestsRcvd OBJECT-TYPE
   SYNTAX      Gauge32
   MAX-ACCESS  read-only
   STATUS      current
   DESCRIPTION
      "Path: ethernet3.performance.pppoEClient.ppp.linkMonitoring.requestsRcvd

       32 bit unsigned gauge value."
   ::= {pr1645v2Lan3PPPoEEntry 50397952}

pr1645v2Lan3PPPoEPppLinkMonitoringRepliesSent OBJECT-TYPE
   SYNTAX      Gauge32
   MAX-ACCESS  read-only
   STATUS      current
   DESCRIPTION
      "Path: ethernet3.performance.pppoEClient.ppp.linkMonitoring.repliesSent

       32 bit unsigned gauge value."
   ::= {pr1645v2Lan3PPPoEEntry 50398208}

pr1645v2Lan3PPPoEMCH2P OBJECT-TYPE
   SYNTAX      SEQUENCE OF Pr1645v2Lan3PPPoEMCH2PEntry
   MAX-ACCESS  not-accessible
   STATUS      current
   DESCRIPTION
      ""
   ::= {pr1645v2Lan3PPPoE 41549824}

pr1645v2Lan3PPPoEMCH2PEntry OBJECT-TYPE
   SYNTAX      Pr1645v2Lan3PPPoEMCH2PEntry
   MAX-ACCESS  not-accessible
   STATUS      current
   DESCRIPTION
      ""
   INDEX      { pr1645v2Lan3PPPoETableIx,
                pr1645v2Lan3PPPoEMCH2PTableIx }
   ::= {pr1645v2Lan3PPPoEMCH2P 1}

Pr1645v2Lan3PPPoEMCH2PEntry ::=
   SEQUENCE
      {
      pr1645v2Lan3PPPoEMCH2PTableIx
         TableIndex,
      pr1645v2Lan3PPPoEMCH2PSysUpTime
         TimeTicks,
      pr1645v2Lan3PPPoEMCH2PIfUpTime
         TimeTicks,
      pr1645v2Lan3PPPoEMCH2PIfStatChanges
         Counter32,
      pr1645v2Lan3PPPoEMCH2PIfInOctets
         Counter64,
      pr1645v2Lan3PPPoEMCH2PIfInUCPkts
         Counter64,
      pr1645v2Lan3PPPoEMCH2PIfInNUCPkts
         Counter64,
      pr1645v2Lan3PPPoEMCH2PIfInBCPkts
         Counter64,
      pr1645v2Lan3PPPoEMCH2PIfInMCPkts
         Counter64,
      pr1645v2Lan3PPPoEMCH2PIfInDiscards
         Counter64,
      pr1645v2Lan3PPPoEMCH2PIfInErrors
         Counter64,
      pr1645v2Lan3PPPoEMCH2PIfInUnkwn
         Counter64,
      pr1645v2Lan3PPPoEMCH2PInDropEx
         Counter64,
      pr1645v2Lan3PPPoEMCH2PInDropNoMac
         Counter64,
      pr1645v2Lan3PPPoEMCH2PInDropNUCast
         Counter64,
      pr1645v2Lan3PPPoEMCH2PInDropFilter
         Counter64,
      pr1645v2Lan3PPPoEMCH2PIfInBandwidth
         Integer32,
      pr1645v2Lan3PPPoEMCH2PIfOutOctets
         Counter64,
      pr1645v2Lan3PPPoEMCH2PIfOutUCPkts
         Counter64,
      pr1645v2Lan3PPPoEMCH2PIfOutNUCPkts
         Counter64,
      pr1645v2Lan3PPPoEMCH2PIfOutBCPkts
         Counter64,
      pr1645v2Lan3PPPoEMCH2PIfOutMCPkts
         Counter64,
      pr1645v2Lan3PPPoEMCH2PIfOutDiscards
         Counter64,
      pr1645v2Lan3PPPoEMCH2PIfOutErrors
         Counter64,
      pr1645v2Lan3PPPoEMCH2POutDropEx
         Counter64,
      pr1645v2Lan3PPPoEMCH2POutDropNoArp
         Counter64,
      pr1645v2Lan3PPPoEMCH2POutDropFilter
         Counter64,
      pr1645v2Lan3PPPoEMCH2PIfOutBandwidth
         Integer32,
      pr1645v2Lan3PPPoEMCH2PIfErrSec
         Counter32
      }

pr1645v2Lan3PPPoEMCH2PTableIx OBJECT-TYPE
   SYNTAX      TableIndex
   MAX-ACCESS  not-accessible
   STATUS      current
   DESCRIPTION
      ""
   ::= {pr1645v2Lan3PPPoEMCH2PEntry 11}

pr1645v2Lan3PPPoEMCH2PSysUpTime OBJECT-TYPE
   SYNTAX      TimeTicks
   MAX-ACCESS  read-only
   STATUS      current
   DESCRIPTION
      "Path: ethernet3.performance.pppoEClient.mibCounters.h2Performance.sysUpTime

       Time in centi-second."
   ::= {pr1645v2Lan3PPPoEMCH2PEntry 16777216}

pr1645v2Lan3PPPoEMCH2PIfUpTime OBJECT-TYPE
   SYNTAX      TimeTicks
   MAX-ACCESS  read-only
   STATUS      current
   DESCRIPTION
      "Path: ethernet3.performance.pppoEClient.mibCounters.h2Performance.ifUpTime

       Time in centi-second."
   ::= {pr1645v2Lan3PPPoEMCH2PEntry 33554432}

pr1645v2Lan3PPPoEMCH2PIfStatChanges OBJECT-TYPE
   SYNTAX      Counter32
   MAX-ACCESS  read-only
   STATUS      current
   DESCRIPTION
      "Path: ethernet3.performance.pppoEClient.mibCounters.h2Performance.ifStatusChanges

       32 bit unsigned wrappable counter."
   ::= {pr1645v2Lan3PPPoEMCH2PEntry 50331648}

pr1645v2Lan3PPPoEMCH2PIfInOctets OBJECT-TYPE
   SYNTAX      Counter64
   MAX-ACCESS  read-only
   STATUS      current
   DESCRIPTION
      "Path: ethernet3.performance.pppoEClient.mibCounters.h2Performance.ifInOctets

       64 bit unsigned wrappable counter."
   ::= {pr1645v2Lan3PPPoEMCH2PEntry 67108864}

pr1645v2Lan3PPPoEMCH2PIfInUCPkts OBJECT-TYPE
   SYNTAX      Counter64
   MAX-ACCESS  read-only
   STATUS      current
   DESCRIPTION
      "Path: ethernet3.performance.pppoEClient.mibCounters.h2Performance.ifInUcastPkts

       64 bit unsigned wrappable counter."
   ::= {pr1645v2Lan3PPPoEMCH2PEntry 83886080}

pr1645v2Lan3PPPoEMCH2PIfInNUCPkts OBJECT-TYPE
   SYNTAX      Counter64
   MAX-ACCESS  read-only
   STATUS      current
   DESCRIPTION
      "Path: ethernet3.performance.pppoEClient.mibCounters.h2Performance.ifInNUcastPkts

       64 bit unsigned wrappable counter."
   ::= {pr1645v2Lan3PPPoEMCH2PEntry 100663296}

pr1645v2Lan3PPPoEMCH2PIfInBCPkts OBJECT-TYPE
   SYNTAX      Counter64
   MAX-ACCESS  read-only
   STATUS      current
   DESCRIPTION
      "Path: ethernet3.performance.pppoEClient.mibCounters.h2Performance.ifInBcastPkts

       64 bit unsigned wrappable counter."
   ::= {pr1645v2Lan3PPPoEMCH2PEntry 419430400}

pr1645v2Lan3PPPoEMCH2PIfInMCPkts OBJECT-TYPE
   SYNTAX      Counter64
   MAX-ACCESS  read-only
   STATUS      current
   DESCRIPTION
      "Path: ethernet3.performance.pppoEClient.mibCounters.h2Performance.ifInMcastPkts

       64 bit unsigned wrappable counter."
   ::= {pr1645v2Lan3PPPoEMCH2PEntry 436207616}

pr1645v2Lan3PPPoEMCH2PIfInDiscards OBJECT-TYPE
   SYNTAX      Counter64
   MAX-ACCESS  read-only
   STATUS      current
   DESCRIPTION
      "Path: ethernet3.performance.pppoEClient.mibCounters.h2Performance.ifInDiscards

       64 bit unsigned wrappable counter."
   ::= {pr1645v2Lan3PPPoEMCH2PEntry 117440512}

pr1645v2Lan3PPPoEMCH2PIfInErrors OBJECT-TYPE
   SYNTAX      Counter64
   MAX-ACCESS  read-only
   STATUS      current
   DESCRIPTION
      "Path: ethernet3.performance.pppoEClient.mibCounters.h2Performance.ifInErrors

       64 bit unsigned wrappable counter."
   ::= {pr1645v2Lan3PPPoEMCH2PEntry 134217728}

pr1645v2Lan3PPPoEMCH2PIfInUnkwn OBJECT-TYPE
   SYNTAX      Counter64
   MAX-ACCESS  read-only
   STATUS      current
   DESCRIPTION
      "Path: ethernet3.performance.pppoEClient.mibCounters.h2Performance.ifInUnknownProtos

       64 bit unsigned wrappable counter."
   ::= {pr1645v2Lan3PPPoEMCH2PEntry 150994944}

pr1645v2Lan3PPPoEMCH2PInDropEx OBJECT-TYPE
   SYNTAX      Counter64
   MAX-ACCESS  read-only
   STATUS      current
   DESCRIPTION
      "Path: ethernet3.performance.pppoEClient.mibCounters.h2Performance.ifInDropLevelExceeded

       64 bit unsigned wrappable counter."
   ::= {pr1645v2Lan3PPPoEMCH2PEntry 335544320}

pr1645v2Lan3PPPoEMCH2PInDropNoMac OBJECT-TYPE
   SYNTAX      Counter64
   MAX-ACCESS  read-only
   STATUS      current
   DESCRIPTION
      "Path: ethernet3.performance.pppoEClient.mibCounters.h2Performance.fInDiscardsNoMacFit

       64 bit unsigned wrappable counter."
   ::= {pr1645v2Lan3PPPoEMCH2PEntry 301989888}

pr1645v2Lan3PPPoEMCH2PInDropNUCast OBJECT-TYPE
   SYNTAX      Counter64
   MAX-ACCESS  read-only
   STATUS      current
   DESCRIPTION
      "Path: ethernet3.performance.pppoEClient.mibCounters.h2Performance.fInDiscardsNUCast

       64 bit unsigned wrappable counter."
   ::= {pr1645v2Lan3PPPoEMCH2PEntry 318767104}

pr1645v2Lan3PPPoEMCH2PInDropFilter OBJECT-TYPE
   SYNTAX      Counter64
   MAX-ACCESS  read-only
   STATUS      current
   DESCRIPTION
      "Path: ethernet3.performance.pppoEClient.mibCounters.h2Performance.fInDiscardsFilter

       64 bit unsigned wrappable counter."
   ::= {pr1645v2Lan3PPPoEMCH2PEntry 385875968}

pr1645v2Lan3PPPoEMCH2PIfInBandwidth OBJECT-TYPE
   SYNTAX      Integer32
   MAX-ACCESS  read-only
   STATUS      current
   DESCRIPTION
      "Path: ethernet3.performance.pppoEClient.mibCounters.h2Performance.ifInBandwidth

       unit name = bps
       formula = 8 * ; 8 /"
   ::= {pr1645v2Lan3PPPoEMCH2PEntry 268435456}

pr1645v2Lan3PPPoEMCH2PIfOutOctets OBJECT-TYPE
   SYNTAX      Counter64
   MAX-ACCESS  read-only
   STATUS      current
   DESCRIPTION
      "Path: ethernet3.performance.pppoEClient.mibCounters.h2Performance.ifOutOctets

       64 bit unsigned wrappable counter."
   ::= {pr1645v2Lan3PPPoEMCH2PEntry 167772160}

pr1645v2Lan3PPPoEMCH2PIfOutUCPkts OBJECT-TYPE
   SYNTAX      Counter64
   MAX-ACCESS  read-only
   STATUS      current
   DESCRIPTION
      "Path: ethernet3.performance.pppoEClient.mibCounters.h2Performance.ifOutUcastPkts

       64 bit unsigned wrappable counter."
   ::= {pr1645v2Lan3PPPoEMCH2PEntry 184549376}

pr1645v2Lan3PPPoEMCH2PIfOutNUCPkts OBJECT-TYPE
   SYNTAX      Counter64
   MAX-ACCESS  read-only
   STATUS      current
   DESCRIPTION
      "Path: ethernet3.performance.pppoEClient.mibCounters.h2Performance.ifOutNUcastPkts

       64 bit unsigned wrappable counter."
   ::= {pr1645v2Lan3PPPoEMCH2PEntry 201326592}

pr1645v2Lan3PPPoEMCH2PIfOutBCPkts OBJECT-TYPE
   SYNTAX      Counter64
   MAX-ACCESS  read-only
   STATUS      current
   DESCRIPTION
      "Path: ethernet3.performance.pppoEClient.mibCounters.h2Performance.ifOutBcastPkts

       64 bit unsigned wrappable counter."
   ::= {pr1645v2Lan3PPPoEMCH2PEntry 452984832}

pr1645v2Lan3PPPoEMCH2PIfOutMCPkts OBJECT-TYPE
   SYNTAX      Counter64
   MAX-ACCESS  read-only
   STATUS      current
   DESCRIPTION
      "Path: ethernet3.performance.pppoEClient.mibCounters.h2Performance.ifOutMcastPkts

       64 bit unsigned wrappable counter."
   ::= {pr1645v2Lan3PPPoEMCH2PEntry 469762048}

pr1645v2Lan3PPPoEMCH2PIfOutDiscards OBJECT-TYPE
   SYNTAX      Counter64
   MAX-ACCESS  read-only
   STATUS      current
   DESCRIPTION
      "Path: ethernet3.performance.pppoEClient.mibCounters.h2Performance.ifOutDiscards

       64 bit unsigned wrappable counter."
   ::= {pr1645v2Lan3PPPoEMCH2PEntry 218103808}

pr1645v2Lan3PPPoEMCH2PIfOutErrors OBJECT-TYPE
   SYNTAX      Counter64
   MAX-ACCESS  read-only
   STATUS      current
   DESCRIPTION
      "Path: ethernet3.performance.pppoEClient.mibCounters.h2Performance.ifOutErrors

       64 bit unsigned wrappable counter."
   ::= {pr1645v2Lan3PPPoEMCH2PEntry 234881024}

pr1645v2Lan3PPPoEMCH2POutDropEx OBJECT-TYPE
   SYNTAX      Counter64
   MAX-ACCESS  read-only
   STATUS      current
   DESCRIPTION
      "Path: ethernet3.performance.pppoEClient.mibCounters.h2Performance.ifOutDropLevelExceeded

       64 bit unsigned wrappable counter."
   ::= {pr1645v2Lan3PPPoEMCH2PEntry 352321536}

pr1645v2Lan3PPPoEMCH2POutDropNoArp OBJECT-TYPE
   SYNTAX      Counter64
   MAX-ACCESS  read-only
   STATUS      current
   DESCRIPTION
      "Path: ethernet3.performance.pppoEClient.mibCounters.h2Performance.ifOutDiscardsNoArp

       64 bit unsigned wrappable counter."
   ::= {pr1645v2Lan3PPPoEMCH2PEntry 369098752}

pr1645v2Lan3PPPoEMCH2POutDropFilter OBJECT-TYPE
   SYNTAX      Counter64
   MAX-ACCESS  read-only
   STATUS      current
   DESCRIPTION
      "Path: ethernet3.performance.pppoEClient.mibCounters.h2Performance.ifOutDiscardsFilter

       64 bit unsigned wrappable counter."
   ::= {pr1645v2Lan3PPPoEMCH2PEntry 402653184}

pr1645v2Lan3PPPoEMCH2PIfOutBandwidth OBJECT-TYPE
   SYNTAX      Integer32
   MAX-ACCESS  read-only
   STATUS      current
   DESCRIPTION
      "Path: ethernet3.performance.pppoEClient.mibCounters.h2Performance.ifOutBandwidth

       unit name = bps
       formula = 8 * ; 8 /"
   ::= {pr1645v2Lan3PPPoEMCH2PEntry 285212672}

pr1645v2Lan3PPPoEMCH2PIfErrSec OBJECT-TYPE
   SYNTAX      Counter32
   MAX-ACCESS  read-only
   STATUS      current
   DESCRIPTION
      "Path: ethernet3.performance.pppoEClient.mibCounters.h2Performance.ifErrSec

       32 bit unsigned wrappable counter."
   ::= {pr1645v2Lan3PPPoEMCH2PEntry 251658240}

pr1645v2Lan3PPPoEMCH24P OBJECT-TYPE
   SYNTAX      SEQUENCE OF Pr1645v2Lan3PPPoEMCH24PEntry
   MAX-ACCESS  not-accessible
   STATUS      current
   DESCRIPTION
      ""
   ::= {pr1645v2Lan3PPPoE 41615360}

pr1645v2Lan3PPPoEMCH24PEntry OBJECT-TYPE
   SYNTAX      Pr1645v2Lan3PPPoEMCH24PEntry
   MAX-ACCESS  not-accessible
   STATUS      current
   DESCRIPTION
      ""
   INDEX      { pr1645v2Lan3PPPoETableIx,
                pr1645v2Lan3PPPoEMCH24PTableIx }
   ::= {pr1645v2Lan3PPPoEMCH24P 1}

Pr1645v2Lan3PPPoEMCH24PEntry ::=
   SEQUENCE
      {
      pr1645v2Lan3PPPoEMCH24PTableIx
         TableIndex,
      pr1645v2Lan3PPPoEMCH24PSysUpTime
         TimeTicks,
      pr1645v2Lan3PPPoEMCH24PIfUpTime
         TimeTicks,
      pr1645v2Lan3PPPoEMCH24PIfStatChanges
         Counter32,
      pr1645v2Lan3PPPoEMCH24PIfInOctets
         Counter64,
      pr1645v2Lan3PPPoEMCH24PIfInUCPkts
         Counter64,
      pr1645v2Lan3PPPoEMCH24PIfInNUCPkts
         Counter64,
      pr1645v2Lan3PPPoEMCH24PIfInBCPkts
         Counter64,
      pr1645v2Lan3PPPoEMCH24PIfInMCPkts
         Counter64,
      pr1645v2Lan3PPPoEMCH24PIfInDiscards
         Counter64,
      pr1645v2Lan3PPPoEMCH24PIfInErrors
         Counter64,
      pr1645v2Lan3PPPoEMCH24PIfInUnkwn
         Counter64,
      pr1645v2Lan3PPPoEMCH24PInDropEx
         Counter64,
      pr1645v2Lan3PPPoEMCH24PInDropNoMac
         Counter64,
      pr1645v2Lan3PPPoEMCH24PInDropNUCast
         Counter64,
      pr1645v2Lan3PPPoEMCH24PInDropFilter
         Counter64,
      pr1645v2Lan3PPPoEMCH24PIfInBandwidth
         Integer32,
      pr1645v2Lan3PPPoEMCH24PIfOutOctets
         Counter64,
      pr1645v2Lan3PPPoEMCH24PIfOutUCPkts
         Counter64,
      pr1645v2Lan3PPPoEMCH24PIfOutNUCPkts
         Counter64,
      pr1645v2Lan3PPPoEMCH24PIfOutBCPkts
         Counter64,
      pr1645v2Lan3PPPoEMCH24PIfOutMCPkts
         Counter64,
      pr1645v2Lan3PPPoEMCH24PIfOutDiscards
         Counter64,
      pr1645v2Lan3PPPoEMCH24PIfOutErrors
         Counter64,
      pr1645v2Lan3PPPoEMCH24POutDropEx
         Counter64,
      pr1645v2Lan3PPPoEMCH24POutDropNoArp
         Counter64,
      pr1645v2Lan3PPPoEMCH24POutDropFilter
         Counter64,
      pr1645v2Lan3PPPoEMCH24PIfOutBandwidth
         Integer32,
      pr1645v2Lan3PPPoEMCH24PIfErrSec
         Counter32
      }

pr1645v2Lan3PPPoEMCH24PTableIx OBJECT-TYPE
   SYNTAX      TableIndex
   MAX-ACCESS  not-accessible
   STATUS      current
   DESCRIPTION
      ""
   ::= {pr1645v2Lan3PPPoEMCH24PEntry 11}

pr1645v2Lan3PPPoEMCH24PSysUpTime OBJECT-TYPE
   SYNTAX      TimeTicks
   MAX-ACCESS  read-only
   STATUS      current
   DESCRIPTION
      "Path: ethernet3.performance.pppoEClient.mibCounters.h24Performance.sysUpTime

       Time in centi-second."
   ::= {pr1645v2Lan3PPPoEMCH24PEntry 16777216}

pr1645v2Lan3PPPoEMCH24PIfUpTime OBJECT-TYPE
   SYNTAX      TimeTicks
   MAX-ACCESS  read-only
   STATUS      current
   DESCRIPTION
      "Path: ethernet3.performance.pppoEClient.mibCounters.h24Performance.ifUpTime

       Time in centi-second."
   ::= {pr1645v2Lan3PPPoEMCH24PEntry 33554432}

pr1645v2Lan3PPPoEMCH24PIfStatChanges OBJECT-TYPE
   SYNTAX      Counter32
   MAX-ACCESS  read-only
   STATUS      current
   DESCRIPTION
      "Path: ethernet3.performance.pppoEClient.mibCounters.h24Performance.ifStatusChanges

       32 bit unsigned wrappable counter."
   ::= {pr1645v2Lan3PPPoEMCH24PEntry 50331648}

pr1645v2Lan3PPPoEMCH24PIfInOctets OBJECT-TYPE
   SYNTAX      Counter64
   MAX-ACCESS  read-only
   STATUS      current
   DESCRIPTION
      "Path: ethernet3.performance.pppoEClient.mibCounters.h24Performance.ifInOctets

       64 bit unsigned wrappable counter."
   ::= {pr1645v2Lan3PPPoEMCH24PEntry 67108864}

pr1645v2Lan3PPPoEMCH24PIfInUCPkts OBJECT-TYPE
   SYNTAX      Counter64
   MAX-ACCESS  read-only
   STATUS      current
   DESCRIPTION
      "Path: ethernet3.performance.pppoEClient.mibCounters.h24Performance.ifInUcastPkts

       64 bit unsigned wrappable counter."
   ::= {pr1645v2Lan3PPPoEMCH24PEntry 83886080}

pr1645v2Lan3PPPoEMCH24PIfInNUCPkts OBJECT-TYPE
   SYNTAX      Counter64
   MAX-ACCESS  read-only
   STATUS      current
   DESCRIPTION
      "Path: ethernet3.performance.pppoEClient.mibCounters.h24Performance.ifInNUcastPkts

       64 bit unsigned wrappable counter."
   ::= {pr1645v2Lan3PPPoEMCH24PEntry 100663296}

pr1645v2Lan3PPPoEMCH24PIfInBCPkts OBJECT-TYPE
   SYNTAX      Counter64
   MAX-ACCESS  read-only
   STATUS      current
   DESCRIPTION
      "Path: ethernet3.performance.pppoEClient.mibCounters.h24Performance.ifInBcastPkts

       64 bit unsigned wrappable counter."
   ::= {pr1645v2Lan3PPPoEMCH24PEntry 419430400}

pr1645v2Lan3PPPoEMCH24PIfInMCPkts OBJECT-TYPE
   SYNTAX      Counter64
   MAX-ACCESS  read-only
   STATUS      current
   DESCRIPTION
      "Path: ethernet3.performance.pppoEClient.mibCounters.h24Performance.ifInMcastPkts

       64 bit unsigned wrappable counter."
   ::= {pr1645v2Lan3PPPoEMCH24PEntry 436207616}

pr1645v2Lan3PPPoEMCH24PIfInDiscards OBJECT-TYPE
   SYNTAX      Counter64
   MAX-ACCESS  read-only
   STATUS      current
   DESCRIPTION
      "Path: ethernet3.performance.pppoEClient.mibCounters.h24Performance.ifInDiscards

       64 bit unsigned wrappable counter."
   ::= {pr1645v2Lan3PPPoEMCH24PEntry 117440512}

pr1645v2Lan3PPPoEMCH24PIfInErrors OBJECT-TYPE
   SYNTAX      Counter64
   MAX-ACCESS  read-only
   STATUS      current
   DESCRIPTION
      "Path: ethernet3.performance.pppoEClient.mibCounters.h24Performance.ifInErrors

       64 bit unsigned wrappable counter."
   ::= {pr1645v2Lan3PPPoEMCH24PEntry 134217728}

pr1645v2Lan3PPPoEMCH24PIfInUnkwn OBJECT-TYPE
   SYNTAX      Counter64
   MAX-ACCESS  read-only
   STATUS      current
   DESCRIPTION
      "Path: ethernet3.performance.pppoEClient.mibCounters.h24Performance.ifInUnknownProtos

       64 bit unsigned wrappable counter."
   ::= {pr1645v2Lan3PPPoEMCH24PEntry 150994944}

pr1645v2Lan3PPPoEMCH24PInDropEx OBJECT-TYPE
   SYNTAX      Counter64
   MAX-ACCESS  read-only
   STATUS      current
   DESCRIPTION
      "Path: ethernet3.performance.pppoEClient.mibCounters.h24Performance.ifInDropLevelExceeded

       64 bit unsigned wrappable counter."
   ::= {pr1645v2Lan3PPPoEMCH24PEntry 335544320}

pr1645v2Lan3PPPoEMCH24PInDropNoMac OBJECT-TYPE
   SYNTAX      Counter64
   MAX-ACCESS  read-only
   STATUS      current
   DESCRIPTION
      "Path: ethernet3.performance.pppoEClient.mibCounters.h24Performance.fInDiscardsNoMacFit

       64 bit unsigned wrappable counter."
   ::= {pr1645v2Lan3PPPoEMCH24PEntry 301989888}

pr1645v2Lan3PPPoEMCH24PInDropNUCast OBJECT-TYPE
   SYNTAX      Counter64
   MAX-ACCESS  read-only
   STATUS      current
   DESCRIPTION
      "Path: ethernet3.performance.pppoEClient.mibCounters.h24Performance.fInDiscardsNUCast

       64 bit unsigned wrappable counter."
   ::= {pr1645v2Lan3PPPoEMCH24PEntry 318767104}

pr1645v2Lan3PPPoEMCH24PInDropFilter OBJECT-TYPE
   SYNTAX      Counter64
   MAX-ACCESS  read-only
   STATUS      current
   DESCRIPTION
      "Path: ethernet3.performance.pppoEClient.mibCounters.h24Performance.fInDiscardsFilter

       64 bit unsigned wrappable counter."
   ::= {pr1645v2Lan3PPPoEMCH24PEntry 385875968}

pr1645v2Lan3PPPoEMCH24PIfInBandwidth OBJECT-TYPE
   SYNTAX      Integer32
   MAX-ACCESS  read-only
   STATUS      current
   DESCRIPTION
      "Path: ethernet3.performance.pppoEClient.mibCounters.h24Performance.ifInBandwidth

       unit name = bps
       formula = 8 * ; 8 /"
   ::= {pr1645v2Lan3PPPoEMCH24PEntry 268435456}

pr1645v2Lan3PPPoEMCH24PIfOutOctets OBJECT-TYPE
   SYNTAX      Counter64
   MAX-ACCESS  read-only
   STATUS      current
   DESCRIPTION
      "Path: ethernet3.performance.pppoEClient.mibCounters.h24Performance.ifOutOctets

       64 bit unsigned wrappable counter."
   ::= {pr1645v2Lan3PPPoEMCH24PEntry 167772160}

pr1645v2Lan3PPPoEMCH24PIfOutUCPkts OBJECT-TYPE
   SYNTAX      Counter64
   MAX-ACCESS  read-only
   STATUS      current
   DESCRIPTION
      "Path: ethernet3.performance.pppoEClient.mibCounters.h24Performance.ifOutUcastPkts

       64 bit unsigned wrappable counter."
   ::= {pr1645v2Lan3PPPoEMCH24PEntry 184549376}

pr1645v2Lan3PPPoEMCH24PIfOutNUCPkts OBJECT-TYPE
   SYNTAX      Counter64
   MAX-ACCESS  read-only
   STATUS      current
   DESCRIPTION
      "Path: ethernet3.performance.pppoEClient.mibCounters.h24Performance.ifOutNUcastPkts

       64 bit unsigned wrappable counter."
   ::= {pr1645v2Lan3PPPoEMCH24PEntry 201326592}

pr1645v2Lan3PPPoEMCH24PIfOutBCPkts OBJECT-TYPE
   SYNTAX      Counter64
   MAX-ACCESS  read-only
   STATUS      current
   DESCRIPTION
      "Path: ethernet3.performance.pppoEClient.mibCounters.h24Performance.ifOutBcastPkts

       64 bit unsigned wrappable counter."
   ::= {pr1645v2Lan3PPPoEMCH24PEntry 452984832}

pr1645v2Lan3PPPoEMCH24PIfOutMCPkts OBJECT-TYPE
   SYNTAX      Counter64
   MAX-ACCESS  read-only
   STATUS      current
   DESCRIPTION
      "Path: ethernet3.performance.pppoEClient.mibCounters.h24Performance.ifOutMcastPkts

       64 bit unsigned wrappable counter."
   ::= {pr1645v2Lan3PPPoEMCH24PEntry 469762048}

pr1645v2Lan3PPPoEMCH24PIfOutDiscards OBJECT-TYPE
   SYNTAX      Counter64
   MAX-ACCESS  read-only
   STATUS      current
   DESCRIPTION
      "Path: ethernet3.performance.pppoEClient.mibCounters.h24Performance.ifOutDiscards

       64 bit unsigned wrappable counter."
   ::= {pr1645v2Lan3PPPoEMCH24PEntry 218103808}

pr1645v2Lan3PPPoEMCH24PIfOutErrors OBJECT-TYPE
   SYNTAX      Counter64
   MAX-ACCESS  read-only
   STATUS      current
   DESCRIPTION
      "Path: ethernet3.performance.pppoEClient.mibCounters.h24Performance.ifOutErrors

       64 bit unsigned wrappable counter."
   ::= {pr1645v2Lan3PPPoEMCH24PEntry 234881024}

pr1645v2Lan3PPPoEMCH24POutDropEx OBJECT-TYPE
   SYNTAX      Counter64
   MAX-ACCESS  read-only
   STATUS      current
   DESCRIPTION
      "Path: ethernet3.performance.pppoEClient.mibCounters.h24Performance.ifOutDropLevelExceeded

       64 bit unsigned wrappable counter."
   ::= {pr1645v2Lan3PPPoEMCH24PEntry 352321536}

pr1645v2Lan3PPPoEMCH24POutDropNoArp OBJECT-TYPE
   SYNTAX      Counter64
   MAX-ACCESS  read-only
   STATUS      current
   DESCRIPTION
      "Path: ethernet3.performance.pppoEClient.mibCounters.h24Performance.ifOutDiscardsNoArp

       64 bit unsigned wrappable counter."
   ::= {pr1645v2Lan3PPPoEMCH24PEntry 369098752}

pr1645v2Lan3PPPoEMCH24POutDropFilter OBJECT-TYPE
   SYNTAX      Counter64
   MAX-ACCESS  read-only
   STATUS      current
   DESCRIPTION
      "Path: ethernet3.performance.pppoEClient.mibCounters.h24Performance.ifOutDiscardsFilter

       64 bit unsigned wrappable counter."
   ::= {pr1645v2Lan3PPPoEMCH24PEntry 402653184}

pr1645v2Lan3PPPoEMCH24PIfOutBandwidth OBJECT-TYPE
   SYNTAX      Integer32
   MAX-ACCESS  read-only
   STATUS      current
   DESCRIPTION
      "Path: ethernet3.performance.pppoEClient.mibCounters.h24Performance.ifOutBandwidth

       unit name = bps
       formula = 8 * ; 8 /"
   ::= {pr1645v2Lan3PPPoEMCH24PEntry 285212672}

pr1645v2Lan3PPPoEMCH24PIfErrSec OBJECT-TYPE
   SYNTAX      Counter32
   MAX-ACCESS  read-only
   STATUS      current
   DESCRIPTION
      "Path: ethernet3.performance.pppoEClient.mibCounters.h24Performance.ifErrSec

       32 bit unsigned wrappable counter."
   ::= {pr1645v2Lan3PPPoEMCH24PEntry 251658240}

pr1645v2Lan3PPPoEMCD7P OBJECT-TYPE
   SYNTAX      SEQUENCE OF Pr1645v2Lan3PPPoEMCD7PEntry
   MAX-ACCESS  not-accessible
   STATUS      current
   DESCRIPTION
      ""
   ::= {pr1645v2Lan3PPPoE 41680896}

pr1645v2Lan3PPPoEMCD7PEntry OBJECT-TYPE
   SYNTAX      Pr1645v2Lan3PPPoEMCD7PEntry
   MAX-ACCESS  not-accessible
   STATUS      current
   DESCRIPTION
      ""
   INDEX      { pr1645v2Lan3PPPoETableIx,
                pr1645v2Lan3PPPoEMCD7PTableIx }
   ::= {pr1645v2Lan3PPPoEMCD7P 1}

Pr1645v2Lan3PPPoEMCD7PEntry ::=
   SEQUENCE
      {
      pr1645v2Lan3PPPoEMCD7PTableIx
         TableIndex,
      pr1645v2Lan3PPPoEMCD7PSysUpTime
         TimeTicks,
      pr1645v2Lan3PPPoEMCD7PIfUpTime
         TimeTicks,
      pr1645v2Lan3PPPoEMCD7PIfStatChanges
         Counter32,
      pr1645v2Lan3PPPoEMCD7PIfInOctets
         Counter64,
      pr1645v2Lan3PPPoEMCD7PIfInUCPkts
         Counter64,
      pr1645v2Lan3PPPoEMCD7PIfInNUCPkts
         Counter64,
      pr1645v2Lan3PPPoEMCD7PIfInBCPkts
         Counter64,
      pr1645v2Lan3PPPoEMCD7PIfInMCPkts
         Counter64,
      pr1645v2Lan3PPPoEMCD7PIfInDiscards
         Counter64,
      pr1645v2Lan3PPPoEMCD7PIfInErrors
         Counter64,
      pr1645v2Lan3PPPoEMCD7PIfInUnkwn
         Counter64,
      pr1645v2Lan3PPPoEMCD7PInDropEx
         Counter64,
      pr1645v2Lan3PPPoEMCD7PInDropNoMac
         Counter64,
      pr1645v2Lan3PPPoEMCD7PInDropNUCast
         Counter64,
      pr1645v2Lan3PPPoEMCD7PInDropFilter
         Counter64,
      pr1645v2Lan3PPPoEMCD7PIfInBandwidth
         Integer32,
      pr1645v2Lan3PPPoEMCD7PIfOutOctets
         Counter64,
      pr1645v2Lan3PPPoEMCD7PIfOutUCPkts
         Counter64,
      pr1645v2Lan3PPPoEMCD7PIfOutNUCPkts
         Counter64,
      pr1645v2Lan3PPPoEMCD7PIfOutBCPkts
         Counter64,
      pr1645v2Lan3PPPoEMCD7PIfOutMCPkts
         Counter64,
      pr1645v2Lan3PPPoEMCD7PIfOutDiscards
         Counter64,
      pr1645v2Lan3PPPoEMCD7PIfOutErrors
         Counter64,
      pr1645v2Lan3PPPoEMCD7POutDropEx
         Counter64,
      pr1645v2Lan3PPPoEMCD7POutDropNoArp
         Counter64,
      pr1645v2Lan3PPPoEMCD7POutDropFilter
         Counter64,
      pr1645v2Lan3PPPoEMCD7PIfOutBandwidth
         Integer32,
      pr1645v2Lan3PPPoEMCD7PIfErrSec
         Counter32
      }

pr1645v2Lan3PPPoEMCD7PTableIx OBJECT-TYPE
   SYNTAX      TableIndex
   MAX-ACCESS  not-accessible
   STATUS      current
   DESCRIPTION
      ""
   ::= {pr1645v2Lan3PPPoEMCD7PEntry 11}

pr1645v2Lan3PPPoEMCD7PSysUpTime OBJECT-TYPE
   SYNTAX      TimeTicks
   MAX-ACCESS  read-only
   STATUS      current
   DESCRIPTION
      "Path: ethernet3.performance.pppoEClient.mibCounters.d7Performance.sysUpTime

       Time in centi-second."
   ::= {pr1645v2Lan3PPPoEMCD7PEntry 16777216}

pr1645v2Lan3PPPoEMCD7PIfUpTime OBJECT-TYPE
   SYNTAX      TimeTicks
   MAX-ACCESS  read-only
   STATUS      current
   DESCRIPTION
      "Path: ethernet3.performance.pppoEClient.mibCounters.d7Performance.ifUpTime

       Time in centi-second."
   ::= {pr1645v2Lan3PPPoEMCD7PEntry 33554432}

pr1645v2Lan3PPPoEMCD7PIfStatChanges OBJECT-TYPE
   SYNTAX      Counter32
   MAX-ACCESS  read-only
   STATUS      current
   DESCRIPTION
      "Path: ethernet3.performance.pppoEClient.mibCounters.d7Performance.ifStatusChanges

       32 bit unsigned wrappable counter."
   ::= {pr1645v2Lan3PPPoEMCD7PEntry 50331648}

pr1645v2Lan3PPPoEMCD7PIfInOctets OBJECT-TYPE
   SYNTAX      Counter64
   MAX-ACCESS  read-only
   STATUS      current
   DESCRIPTION
      "Path: ethernet3.performance.pppoEClient.mibCounters.d7Performance.ifInOctets

       64 bit unsigned wrappable counter."
   ::= {pr1645v2Lan3PPPoEMCD7PEntry 67108864}

pr1645v2Lan3PPPoEMCD7PIfInUCPkts OBJECT-TYPE
   SYNTAX      Counter64
   MAX-ACCESS  read-only
   STATUS      current
   DESCRIPTION
      "Path: ethernet3.performance.pppoEClient.mibCounters.d7Performance.ifInUcastPkts

       64 bit unsigned wrappable counter."
   ::= {pr1645v2Lan3PPPoEMCD7PEntry 83886080}

pr1645v2Lan3PPPoEMCD7PIfInNUCPkts OBJECT-TYPE
   SYNTAX      Counter64
   MAX-ACCESS  read-only
   STATUS      current
   DESCRIPTION
      "Path: ethernet3.performance.pppoEClient.mibCounters.d7Performance.ifInNUcastPkts

       64 bit unsigned wrappable counter."
   ::= {pr1645v2Lan3PPPoEMCD7PEntry 100663296}

pr1645v2Lan3PPPoEMCD7PIfInBCPkts OBJECT-TYPE
   SYNTAX      Counter64
   MAX-ACCESS  read-only
   STATUS      current
   DESCRIPTION
      "Path: ethernet3.performance.pppoEClient.mibCounters.d7Performance.ifInBcastPkts

       64 bit unsigned wrappable counter."
   ::= {pr1645v2Lan3PPPoEMCD7PEntry 419430400}

pr1645v2Lan3PPPoEMCD7PIfInMCPkts OBJECT-TYPE
   SYNTAX      Counter64
   MAX-ACCESS  read-only
   STATUS      current
   DESCRIPTION
      "Path: ethernet3.performance.pppoEClient.mibCounters.d7Performance.ifInMcastPkts

       64 bit unsigned wrappable counter."
   ::= {pr1645v2Lan3PPPoEMCD7PEntry 436207616}

pr1645v2Lan3PPPoEMCD7PIfInDiscards OBJECT-TYPE
   SYNTAX      Counter64
   MAX-ACCESS  read-only
   STATUS      current
   DESCRIPTION
      "Path: ethernet3.performance.pppoEClient.mibCounters.d7Performance.ifInDiscards

       64 bit unsigned wrappable counter."
   ::= {pr1645v2Lan3PPPoEMCD7PEntry 117440512}

pr1645v2Lan3PPPoEMCD7PIfInErrors OBJECT-TYPE
   SYNTAX      Counter64
   MAX-ACCESS  read-only
   STATUS      current
   DESCRIPTION
      "Path: ethernet3.performance.pppoEClient.mibCounters.d7Performance.ifInErrors

       64 bit unsigned wrappable counter."
   ::= {pr1645v2Lan3PPPoEMCD7PEntry 134217728}

pr1645v2Lan3PPPoEMCD7PIfInUnkwn OBJECT-TYPE
   SYNTAX      Counter64
   MAX-ACCESS  read-only
   STATUS      current
   DESCRIPTION
      "Path: ethernet3.performance.pppoEClient.mibCounters.d7Performance.ifInUnknownProtos

       64 bit unsigned wrappable counter."
   ::= {pr1645v2Lan3PPPoEMCD7PEntry 150994944}

pr1645v2Lan3PPPoEMCD7PInDropEx OBJECT-TYPE
   SYNTAX      Counter64
   MAX-ACCESS  read-only
   STATUS      current
   DESCRIPTION
      "Path: ethernet3.performance.pppoEClient.mibCounters.d7Performance.ifInDropLevelExceeded

       64 bit unsigned wrappable counter."
   ::= {pr1645v2Lan3PPPoEMCD7PEntry 335544320}

pr1645v2Lan3PPPoEMCD7PInDropNoMac OBJECT-TYPE
   SYNTAX      Counter64
   MAX-ACCESS  read-only
   STATUS      current
   DESCRIPTION
      "Path: ethernet3.performance.pppoEClient.mibCounters.d7Performance.fInDiscardsNoMacFit

       64 bit unsigned wrappable counter."
   ::= {pr1645v2Lan3PPPoEMCD7PEntry 301989888}

pr1645v2Lan3PPPoEMCD7PInDropNUCast OBJECT-TYPE
   SYNTAX      Counter64
   MAX-ACCESS  read-only
   STATUS      current
   DESCRIPTION
      "Path: ethernet3.performance.pppoEClient.mibCounters.d7Performance.fInDiscardsNUCast

       64 bit unsigned wrappable counter."
   ::= {pr1645v2Lan3PPPoEMCD7PEntry 318767104}

pr1645v2Lan3PPPoEMCD7PInDropFilter OBJECT-TYPE
   SYNTAX      Counter64
   MAX-ACCESS  read-only
   STATUS      current
   DESCRIPTION
      "Path: ethernet3.performance.pppoEClient.mibCounters.d7Performance.fInDiscardsFilter

       64 bit unsigned wrappable counter."
   ::= {pr1645v2Lan3PPPoEMCD7PEntry 385875968}

pr1645v2Lan3PPPoEMCD7PIfInBandwidth OBJECT-TYPE
   SYNTAX      Integer32
   MAX-ACCESS  read-only
   STATUS      current
   DESCRIPTION
      "Path: ethernet3.performance.pppoEClient.mibCounters.d7Performance.ifInBandwidth

       unit name = bps
       formula = 8 * ; 8 /"
   ::= {pr1645v2Lan3PPPoEMCD7PEntry 268435456}

pr1645v2Lan3PPPoEMCD7PIfOutOctets OBJECT-TYPE
   SYNTAX      Counter64
   MAX-ACCESS  read-only
   STATUS      current
   DESCRIPTION
      "Path: ethernet3.performance.pppoEClient.mibCounters.d7Performance.ifOutOctets

       64 bit unsigned wrappable counter."
   ::= {pr1645v2Lan3PPPoEMCD7PEntry 167772160}

pr1645v2Lan3PPPoEMCD7PIfOutUCPkts OBJECT-TYPE
   SYNTAX      Counter64
   MAX-ACCESS  read-only
   STATUS      current
   DESCRIPTION
      "Path: ethernet3.performance.pppoEClient.mibCounters.d7Performance.ifOutUcastPkts

       64 bit unsigned wrappable counter."
   ::= {pr1645v2Lan3PPPoEMCD7PEntry 184549376}

pr1645v2Lan3PPPoEMCD7PIfOutNUCPkts OBJECT-TYPE
   SYNTAX      Counter64
   MAX-ACCESS  read-only
   STATUS      current
   DESCRIPTION
      "Path: ethernet3.performance.pppoEClient.mibCounters.d7Performance.ifOutNUcastPkts

       64 bit unsigned wrappable counter."
   ::= {pr1645v2Lan3PPPoEMCD7PEntry 201326592}

pr1645v2Lan3PPPoEMCD7PIfOutBCPkts OBJECT-TYPE
   SYNTAX      Counter64
   MAX-ACCESS  read-only
   STATUS      current
   DESCRIPTION
      "Path: ethernet3.performance.pppoEClient.mibCounters.d7Performance.ifOutBcastPkts

       64 bit unsigned wrappable counter."
   ::= {pr1645v2Lan3PPPoEMCD7PEntry 452984832}

pr1645v2Lan3PPPoEMCD7PIfOutMCPkts OBJECT-TYPE
   SYNTAX      Counter64
   MAX-ACCESS  read-only
   STATUS      current
   DESCRIPTION
      "Path: ethernet3.performance.pppoEClient.mibCounters.d7Performance.ifOutMcastPkts

       64 bit unsigned wrappable counter."
   ::= {pr1645v2Lan3PPPoEMCD7PEntry 469762048}

pr1645v2Lan3PPPoEMCD7PIfOutDiscards OBJECT-TYPE
   SYNTAX      Counter64
   MAX-ACCESS  read-only
   STATUS      current
   DESCRIPTION
      "Path: ethernet3.performance.pppoEClient.mibCounters.d7Performance.ifOutDiscards

       64 bit unsigned wrappable counter."
   ::= {pr1645v2Lan3PPPoEMCD7PEntry 218103808}

pr1645v2Lan3PPPoEMCD7PIfOutErrors OBJECT-TYPE
   SYNTAX      Counter64
   MAX-ACCESS  read-only
   STATUS      current
   DESCRIPTION
      "Path: ethernet3.performance.pppoEClient.mibCounters.d7Performance.ifOutErrors

       64 bit unsigned wrappable counter."
   ::= {pr1645v2Lan3PPPoEMCD7PEntry 234881024}

pr1645v2Lan3PPPoEMCD7POutDropEx OBJECT-TYPE
   SYNTAX      Counter64
   MAX-ACCESS  read-only
   STATUS      current
   DESCRIPTION
      "Path: ethernet3.performance.pppoEClient.mibCounters.d7Performance.ifOutDropLevelExceeded

       64 bit unsigned wrappable counter."
   ::= {pr1645v2Lan3PPPoEMCD7PEntry 352321536}

pr1645v2Lan3PPPoEMCD7POutDropNoArp OBJECT-TYPE
   SYNTAX      Counter64
   MAX-ACCESS  read-only
   STATUS      current
   DESCRIPTION
      "Path: ethernet3.performance.pppoEClient.mibCounters.d7Performance.ifOutDiscardsNoArp

       64 bit unsigned wrappable counter."
   ::= {pr1645v2Lan3PPPoEMCD7PEntry 369098752}

pr1645v2Lan3PPPoEMCD7POutDropFilter OBJECT-TYPE
   SYNTAX      Counter64
   MAX-ACCESS  read-only
   STATUS      current
   DESCRIPTION
      "Path: ethernet3.performance.pppoEClient.mibCounters.d7Performance.ifOutDiscardsFilter

       64 bit unsigned wrappable counter."
   ::= {pr1645v2Lan3PPPoEMCD7PEntry 402653184}

pr1645v2Lan3PPPoEMCD7PIfOutBandwidth OBJECT-TYPE
   SYNTAX      Integer32
   MAX-ACCESS  read-only
   STATUS      current
   DESCRIPTION
      "Path: ethernet3.performance.pppoEClient.mibCounters.d7Performance.ifOutBandwidth

       unit name = bps
       formula = 8 * ; 8 /"
   ::= {pr1645v2Lan3PPPoEMCD7PEntry 285212672}

pr1645v2Lan3PPPoEMCD7PIfErrSec OBJECT-TYPE
   SYNTAX      Counter32
   MAX-ACCESS  read-only
   STATUS      current
   DESCRIPTION
      "Path: ethernet3.performance.pppoEClient.mibCounters.d7Performance.ifErrSec

       32 bit unsigned wrappable counter."
   ::= {pr1645v2Lan3PPPoEMCD7PEntry 251658240}


pr1645v2Lan3IfInHwPriorityQueues OBJECT IDENTIFIER ::= {pr1645v2Lan3 132}

pr1645v2Lan3IfInHwPriorityQueuesSSCTable OBJECT-TYPE
   SYNTAX      SEQUENCE OF Pr1645v2Lan3IfInHwPriorityQueuesEntry
   MAX-ACCESS  not-accessible
   STATUS      current
   DESCRIPTION
      "hwPriorityQueues"
   ::= {pr1645v2Lan3IfInHwPriorityQueues 1}

pr1645v2Lan3IfInHwPriorityQueuesEntry OBJECT-TYPE
   SYNTAX      Pr1645v2Lan3IfInHwPriorityQueuesEntry
   MAX-ACCESS  not-accessible
   STATUS      current
   DESCRIPTION
      ""
   INDEX      { pr1645v2Lan3IfInHwPriorityQueuesTableIx }
   ::= {pr1645v2Lan3IfInHwPriorityQueuesSSCTable 1}

Pr1645v2Lan3IfInHwPriorityQueuesEntry ::=
   SEQUENCE
      {
      pr1645v2Lan3IfInHwPriorityQueuesTableIx
         TableIndex,
      pr1645v2Lan3IfInHwPriorityQueuesName
         INTEGER,
      pr1645v2Lan3IfInHwPriorityQueuesLength
         Integer32,
      pr1645v2Lan3IfInHwPriorityQueuesPacketsTotal
         Counter64,
      pr1645v2Lan3IfInHwPriorityQueuesOctetsTotal
         Counter64,
      pr1645v2Lan3IfInHwPriorityQueuesOctetsBandwidth15sec
         Integer32,
      pr1645v2Lan3IfInHwPriorityQueuesOctetsBandwidth30sec
         Integer32,
      pr1645v2Lan3IfInHwPriorityQueuesOctetsBandwidth1min
         Integer32,
      pr1645v2Lan3IfInHwPriorityQueuesOctetsBandwidth2min
         Integer32,
      pr1645v2Lan3IfInHwPriorityQueuesOctetsBandwidth5min
         Integer32
      }

pr1645v2Lan3IfInHwPriorityQueuesTableIx OBJECT-TYPE
   SYNTAX      TableIndex
   MAX-ACCESS  not-accessible
   STATUS      current
   DESCRIPTION
      ""
   ::= {pr1645v2Lan3IfInHwPriorityQueuesEntry 11}

pr1645v2Lan3IfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3IfInHwPriorityQueuesEntry 16777216}

pr1645v2Lan3IfInHwPriorityQueuesLength OBJECT-TYPE
   SYNTAX      Integer32
   MAX-ACCESS  read-only
   STATUS      current
   DESCRIPTION
      "Path: ethernet3.performance.ifInHwPriorityQueues.length"
   ::= {pr1645v2Lan3IfInHwPriorityQueuesEntry 33554432}

pr1645v2Lan3IfInHwPriorityQueuesPacketsTotal OBJECT-TYPE
   SYNTAX      Counter64
   MAX-ACCESS  read-only
   STATUS      current
   DESCRIPTION
      "Path: ethernet3.performance.ifInHwPriorityQueues.packets.total

       64 bit unsigned wrappable counter."
   ::= {pr1645v2Lan3IfInHwPriorityQueuesEntry 50790400}

pr1645v2Lan3IfInHwPriorityQueuesOctetsTotal OBJECT-TYPE
   SYNTAX      Counter64
   MAX-ACCESS  read-only
   STATUS      current
   DESCRIPTION
      "Path: ethernet3.performance.ifInHwPriorityQueues.octets.total

       64 bit unsigned wrappable counter."
   ::= {pr1645v2Lan3IfInHwPriorityQueuesEntry 67567616}

pr1645v2Lan3IfInHwPriorityQueuesOctetsBandwidth15sec OBJECT-TYPE
   SYNTAX      Integer32
   MAX-ACCESS  read-only
   STATUS      current
   DESCRIPTION
      "Path: ethernet3.performance.ifInHwPriorityQueues.octets.bandwidth.15sec

       unit name = bps
       formula = 8 * ; 8 /"
   ::= {pr1645v2Lan3IfInHwPriorityQueuesEntry 70386944}

pr1645v2Lan3IfInHwPriorityQueuesOctetsBandwidth30sec OBJECT-TYPE
   SYNTAX      Integer32
   MAX-ACCESS  read-only
   STATUS      current
   DESCRIPTION
      "Path: ethernet3.performance.ifInHwPriorityQueues.octets.bandwidth.30sec

       unit name = bps
       formula = 8 * ; 8 /"
   ::= {pr1645v2Lan3IfInHwPriorityQueuesEntry 70388224}

pr1645v2Lan3IfInHwPriorityQueuesOctetsBandwidth1min OBJECT-TYPE
   SYNTAX      Integer32
   MAX-ACCESS  read-only
   STATUS      current
   DESCRIPTION
      "Path: ethernet3.performance.ifInHwPriorityQueues.octets.bandwidth.1min

       unit name = bps
       formula = 8 * ; 8 /"
   ::= {pr1645v2Lan3IfInHwPriorityQueuesEntry 70390784}

pr1645v2Lan3IfInHwPriorityQueuesOctetsBandwidth2min OBJECT-TYPE
   SYNTAX      Integer32
   MAX-ACCESS  read-only
   STATUS      current
   DESCRIPTION
      "Path: ethernet3.performance.ifInHwPriorityQueues.octets.bandwidth.2min

       unit name = bps
       formula = 8 * ; 8 /"
   ::= {pr1645v2Lan3IfInHwPriorityQueuesEntry 70395904}

pr1645v2Lan3IfInHwPriorityQueuesOctetsBandwidth5min OBJECT-TYPE
   SYNTAX      Integer32
   MAX-ACCESS  read-only
   STATUS      current
   DESCRIPTION
      "Path: ethernet3.performance.ifInHwPriorityQueues.octets.bandwidth.5min

       unit name = bps
       formula = 8 * ; 8 /"
   ::= {pr1645v2Lan3IfInHwPriorityQueuesEntry 70411264}

pr1645v2Lan3IfInHwPriorityQueuesH2Performance OBJECT-TYPE
   SYNTAX      SEQUENCE OF Pr1645v2Lan3IfInHwPriorityQueuesH2PerformanceEntry
   MAX-ACCESS  not-accessible
   STATUS      current
   DESCRIPTION
      ""
   ::= {pr1645v2Lan3IfInHwPriorityQueues 83886080}

pr1645v2Lan3IfInHwPriorityQueuesH2PerformanceEntry OBJECT-TYPE
   SYNTAX      Pr1645v2Lan3IfInHwPriorityQueuesH2PerformanceEntry
   MAX-ACCESS  not-accessible
   STATUS      current
   DESCRIPTION
      ""
   INDEX      { pr1645v2Lan3IfInHwPriorityQueuesTableIx,
                pr1645v2Lan3IfInHwPriorityQueuesH2PerformanceTableIx }
   ::= {pr1645v2Lan3IfInHwPriorityQueuesH2Performance 1}

Pr1645v2Lan3IfInHwPriorityQueuesH2PerformanceEntry ::=
   SEQUENCE
      {
      pr1645v2Lan3IfInHwPriorityQueuesH2PerformanceTableIx
         TableIndex,
      pr1645v2Lan3IfInHwPriorityQueuesH2PerformanceSysUpTime
         TimeTicks,
      pr1645v2Lan3IfInHwPriorityQueuesH2PerformanceTotPkts
         Counter64,
      pr1645v2Lan3IfInHwPriorityQueuesH2PerformanceTotOcts
         Counter64,
      pr1645v2Lan3IfInHwPriorityQueuesH2PerformanceBandwidth
         Integer32
      }

pr1645v2Lan3IfInHwPriorityQueuesH2PerformanceTableIx OBJECT-TYPE
   SYNTAX      TableIndex
   MAX-ACCESS  not-accessible
   STATUS      current
   DESCRIPTION
      ""
   ::= {pr1645v2Lan3IfInHwPriorityQueuesH2PerformanceEntry 11}

pr1645v2Lan3IfInHwPriorityQueuesH2PerformanceSysUpTime OBJECT-TYPE
   SYNTAX      TimeTicks
   MAX-ACCESS  read-only
   STATUS      current
   DESCRIPTION
      "Path: ethernet3.performance.ifInHwPriorityQueues.h2Performance.sysUpTime

       Time in centi-second."
   ::= {pr1645v2Lan3IfInHwPriorityQueuesH2PerformanceEntry 16777216}

pr1645v2Lan3IfInHwPriorityQueuesH2PerformanceTotPkts OBJECT-TYPE
   SYNTAX      Counter64
   MAX-ACCESS  read-only
   STATUS      current
   DESCRIPTION
      "Path: ethernet3.performance.ifInHwPriorityQueues.h2Performance.totalPkts

       64 bit unsigned wrappable counter."
   ::= {pr1645v2Lan3IfInHwPriorityQueuesH2PerformanceEntry 234881024}

pr1645v2Lan3IfInHwPriorityQueuesH2PerformanceTotOcts OBJECT-TYPE
   SYNTAX      Counter64
   MAX-ACCESS  read-only
   STATUS      current
   DESCRIPTION
      "Path: ethernet3.performance.ifInHwPriorityQueues.h2Performance.totalOctets

       64 bit unsigned wrappable counter."
   ::= {pr1645v2Lan3IfInHwPriorityQueuesH2PerformanceEntry 251658240}

pr1645v2Lan3IfInHwPriorityQueuesH2PerformanceBandwidth OBJECT-TYPE
   SYNTAX      Integer32
   MAX-ACCESS  read-only
   STATUS      current
   DESCRIPTION
      "Path: ethernet3.performance.ifInHwPriorityQueues.h2Performance.bandwidth

       unit name = bps
       formula = 8 * ; 8 /"
   ::= {pr1645v2Lan3IfInHwPriorityQueuesH2PerformanceEntry 268435456}

pr1645v2Lan3IfInHwPriorityQueuesH24Performance OBJECT-TYPE
   SYNTAX      SEQUENCE OF Pr1645v2Lan3IfInHwPriorityQueuesH24PerformanceEntry
   MAX-ACCESS  not-accessible
   STATUS      current
   DESCRIPTION
      ""
   ::= {pr1645v2Lan3IfInHwPriorityQueues 100663296}

pr1645v2Lan3IfInHwPriorityQueuesH24PerformanceEntry OBJECT-TYPE
   SYNTAX      Pr1645v2Lan3IfInHwPriorityQueuesH24PerformanceEntry
   MAX-ACCESS  not-accessible
   STATUS      current
   DESCRIPTION
      ""
   INDEX      { pr1645v2Lan3IfInHwPriorityQueuesTableIx,
                pr1645v2Lan3IfInHwPriorityQueuesH24PerformanceTableIx }
   ::= {pr1645v2Lan3IfInHwPriorityQueuesH24Performance 1}

Pr1645v2Lan3IfInHwPriorityQueuesH24PerformanceEntry ::=
   SEQUENCE
      {
      pr1645v2Lan3IfInHwPriorityQueuesH24PerformanceTableIx
         TableIndex,
      pr1645v2Lan3IfInHwPriorityQueuesH24PerformanceSysUpTime
         TimeTicks,
      pr1645v2Lan3IfInHwPriorityQueuesH24PerformanceTotPkts
         Counter64,
      pr1645v2Lan3IfInHwPriorityQueuesH24PerformanceTotOcts
         Counter64,
      pr1645v2Lan3IfInHwPriorityQueuesH24PerformanceBandwidth
         Integer32
      }

pr1645v2Lan3IfInHwPriorityQueuesH24PerformanceTableIx OBJECT-TYPE
   SYNTAX      TableIndex
   MAX-ACCESS  not-accessible
   STATUS      current
   DESCRIPTION
      ""
   ::= {pr1645v2Lan3IfInHwPriorityQueuesH24PerformanceEntry 11}

pr1645v2Lan3IfInHwPriorityQueuesH24PerformanceSysUpTime OBJECT-TYPE
   SYNTAX      TimeTicks
   MAX-ACCESS  read-only
   STATUS      current
   DESCRIPTION
      "Path: ethernet3.performance.ifInHwPriorityQueues.h24Performance.sysUpTime

       Time in centi-second."
   ::= {pr1645v2Lan3IfInHwPriorityQueuesH24PerformanceEntry 16777216}

pr1645v2Lan3IfInHwPriorityQueuesH24PerformanceTotPkts OBJECT-TYPE
   SYNTAX      Counter64
   MAX-ACCESS  read-only
   STATUS      current
   DESCRIPTION
      "Path: ethernet3.performance.ifInHwPriorityQueues.h24Performance.totalPkts

       64 bit unsigned wrappable counter."
   ::= {pr1645v2Lan3IfInHwPriorityQueuesH24PerformanceEntry 234881024}

pr1645v2Lan3IfInHwPriorityQueuesH24PerformanceTotOcts OBJECT-TYPE
   SYNTAX      Counter64
   MAX-ACCESS  read-only
   STATUS      current
   DESCRIPTION
      "Path: ethernet3.performance.ifInHwPriorityQueues.h24Performance.totalOctets

       64 bit unsigned wrappable counter."
   ::= {pr1645v2Lan3IfInHwPriorityQueuesH24PerformanceEntry 251658240}

pr1645v2Lan3IfInHwPriorityQueuesH24PerformanceBandwidth OBJECT-TYPE
   SYNTAX      Integer32
   MAX-ACCESS  read-only
   STATUS      current
   DESCRIPTION
      "Path: ethernet3.performance.ifInHwPriorityQueues.h24Performance.bandwidth

       unit name = bps
       formula = 8 * ; 8 /"
   ::= {pr1645v2Lan3IfInHwPriorityQueuesH24PerformanceEntry 268435456}

pr1645v2Lan3IfInHwPriorityQueuesD7Performance OBJECT-TYPE
   SYNTAX      SEQUENCE OF Pr1645v2Lan3IfInHwPriorityQueuesD7PerformanceEntry
   MAX-ACCESS  not-accessible
   STATUS      current
   DESCRIPTION
      ""
   ::= {pr1645v2Lan3IfInHwPriorityQueues 117440512}

pr1645v2Lan3IfInHwPriorityQueuesD7PerformanceEntry OBJECT-TYPE
   SYNTAX      Pr1645v2Lan3IfInHwPriorityQueuesD7PerformanceEntry
   MAX-ACCESS  not-accessible
   STATUS      current
   DESCRIPTION
      ""
   INDEX      { pr1645v2Lan3IfInHwPriorityQueuesTableIx,
                pr1645v2Lan3IfInHwPriorityQueuesD7PerformanceTableIx }
   ::= {pr1645v2Lan3IfInHwPriorityQueuesD7Performance 1}

Pr1645v2Lan3IfInHwPriorityQueuesD7PerformanceEntry ::=
   SEQUENCE
      {
      pr1645v2Lan3IfInHwPriorityQueuesD7PerformanceTableIx
         TableIndex,
      pr1645v2Lan3IfInHwPriorityQueuesD7PerformanceSysUpTime
         TimeTicks,
      pr1645v2Lan3IfInHwPriorityQueuesD7PerformanceTotPkts
         Counter64,
      pr1645v2Lan3IfInHwPriorityQueuesD7PerformanceTotOcts
         Counter64,
      pr1645v2Lan3IfInHwPriorityQueuesD7PerformanceBandwidth
         Integer32
      }

pr1645v2Lan3IfInHwPriorityQueuesD7PerformanceTableIx OBJECT-TYPE
   SYNTAX      TableIndex
   MAX-ACCESS  not-accessible
   STATUS      current
   DESCRIPTION
      ""
   ::= {pr1645v2Lan3IfInHwPriorityQueuesD7PerformanceEntry 11}

pr1645v2Lan3IfInHwPriorityQueuesD7PerformanceSysUpTime OBJECT-TYPE
   SYNTAX      TimeTicks
   MAX-ACCESS  read-only
   STATUS      current
   DESCRIPTION
      "Path: ethernet3.performance.ifInHwPriorityQueues.d7Performance.sysUpTime

       Time in centi-second."
   ::= {pr1645v2Lan3IfInHwPriorityQueuesD7PerformanceEntry 16777216}

pr1645v2Lan3IfInHwPriorityQueuesD7PerformanceTotPkts OBJECT-TYPE
   SYNTAX      Counter64
   MAX-ACCESS  read-only
   STATUS      current
   DESCRIPTION
      "Path: ethernet3.performance.ifInHwPriorityQueues.d7Performance.totalPkts

       64 bit unsigned wrappable counter."
   ::= {pr1645v2Lan3IfInHwPriorityQueuesD7PerformanceEntry 234881024}

pr1645v2Lan3IfInHwPriorityQueuesD7PerformanceTotOcts OBJECT-TYPE
   SYNTAX      Counter64
   MAX-ACCESS  read-only
   STATUS      current
   DESCRIPTION
      "Path: ethernet3.performance.ifInHwPriorityQueues.d7Performance.totalOctets

       64 bit unsigned wrappable counter."
   ::= {pr1645v2Lan3IfInHwPriorityQueuesD7PerformanceEntry 251658240}

pr1645v2Lan3IfInHwPriorityQueuesD7PerformanceBandwidth OBJECT-TYPE
   SYNTAX      Integer32
   MAX-ACCESS  read-only
   STATUS      current
   DESCRIPTION
      "Path: ethernet3.performance.ifInHwPriorityQueues.d7Performance.bandwidth

       unit name = bps
       formula = 8 * ; 8 /"
   ::= {pr1645v2Lan3IfInHwPriorityQueuesD7PerformanceEntry 268435456}



ar1645v2Lan3 OBJECT IDENTIFIER ::= {r1645v2Lan3 16}


ar1645v2Lan3ClearCounters OBJECT-TYPE
   SYNTAX      Integer32
   MAX-ACCESS  read-write
   STATUS      current
   DESCRIPTION
      "Path: ethernet3.actions.clearCounters
       Info: reset counters"
   ::= {ar1645v2Lan3 263}


ar1645v2Lan3PowerToggle OBJECT-TYPE
   SYNTAX      Integer32
   MAX-ACCESS  read-write
   STATUS      current
   DESCRIPTION
      "Path: ethernet3.actions.powerToggle
       Info: action in the debug group"
   ::= {ar1645v2Lan3 68}


ar1645v2Lan3RestartIntf OBJECT-TYPE
   SYNTAX      Integer32
   MAX-ACCESS  read-write
   STATUS      current
   DESCRIPTION
      "Path: ethernet3.actions.restartIntf
       Info: action in the debug group"
   ::= {ar1645v2Lan3 67}


ar1645v2Lan3ClearOamEventLog OBJECT-TYPE
   SYNTAX      Integer32
   MAX-ACCESS  read-write
   STATUS      current
   DESCRIPTION
      "Path: ethernet3.actions.clearOamEventLog
       Info: clear the OAM event log"
   ::= {ar1645v2Lan3 916}


ar1645v2Lan3Loopback OBJECT-TYPE
   SYNTAX      Integer32
   MAX-ACCESS  read-write
   STATUS      current
   DESCRIPTION
      "Path: ethernet3.actions.loopback
       Info: ethernet loopback"
   ::= {ar1645v2Lan3 914}


ar1645v2Lan3Loop OBJECT IDENTIFIER ::= {ar1645v2Lan3 915}

ar1645v2Lan3LoopSSC OBJECT IDENTIFIER ::= {ar1645v2Lan3Loop 1}

ar1645v2Lan3LoopEntry OBJECT IDENTIFIER ::= {ar1645v2Lan3LoopSSC 1}

ar1645v2Lan3LoopAction OBJECT-TYPE
   SYNTAX      INTEGER
               {
               start (1),
               stop (2)
               }
   MAX-ACCESS  read-write
   STATUS      current
   DESCRIPTION
      "Path: ethernet3.actions.loop.action

       Possibilities:
               start   (1)
               stop   (2)"
   ::= {ar1645v2Lan3LoopEntry 16777216}

ar1645v2Lan3LoopTime OBJECT-TYPE
   SYNTAX      TimeTicks
   MAX-ACCESS  read-write
   STATUS      current
   DESCRIPTION
      "Path: ethernet3.actions.loop.time

       Time in centi-second."
   ::= {ar1645v2Lan3LoopEntry 50331648}

ar1645v2Lan3LoopIntfName OBJECT-TYPE
   SYNTAX      DisplayString
   MAX-ACCESS  read-write
   STATUS      current
   DESCRIPTION
      "Path: ethernet3.actions.loop.intfName"
   ::= {ar1645v2Lan3LoopEntry 67108864}


ar1645v2Lan3OamRemLoopback OBJECT-TYPE
   SYNTAX      Integer32
   MAX-ACCESS  read-write
   STATUS      current
   DESCRIPTION
      "Path: ethernet3.actions.oamRemLoopback
       Info: OAM Remote Loopback"
   ::= {ar1645v2Lan3 912}


ar1645v2Lan3Type OBJECT-TYPE
   SYNTAX      INTEGER
               {
               start (0),
               stop (1)
               }
   MAX-ACCESS  read-write
   STATUS      current
   DESCRIPTION
      "Path: ethernet3.actions.type
       Info: OAM Remote Loopback type

       Possibilities:
               start   (0)
               stop   (1)"
   ::= {ar1645v2Lan3 913}


ar1645v2Lan3SendWOL OBJECT-TYPE
   SYNTAX      Integer32
   MAX-ACCESS  read-write
   STATUS      current
   DESCRIPTION
      "Path: ethernet3.actions.sendWOL
       Info: send a WakeOnLan message on this interface"
   ::= {ar1645v2Lan3 333}


ar1645v2Lan3WolInfo OBJECT IDENTIFIER ::= {ar1645v2Lan3 332}

ar1645v2Lan3WolInfoSSC OBJECT IDENTIFIER ::= {ar1645v2Lan3WolInfo 1}

ar1645v2Lan3WolInfoEntry OBJECT IDENTIFIER ::= {ar1645v2Lan3WolInfoSSC 1}

ar1645v2Lan3WolInfoTargetMAC OBJECT-TYPE
   SYNTAX      OCTET STRING
   MAX-ACCESS  read-write
   STATUS      current
   DESCRIPTION
      "Path: ethernet3.actions.wolInfo.targetMAC

       MAC address."
   ::= {ar1645v2Lan3WolInfoEntry 16777216}

ar1645v2Lan3WolInfoPassword OBJECT-TYPE
   SYNTAX      OCTET STRING
   MAX-ACCESS  read-write
   STATUS      current
   DESCRIPTION
      "Path: ethernet3.actions.wolInfo.password"
   ::= {ar1645v2Lan3WolInfoEntry 33554432}


ar1645v2Lan3ClearArpCache OBJECT-TYPE
   SYNTAX      Integer32
   MAX-ACCESS  read-write
   STATUS      current
   DESCRIPTION
      "Path: ethernet3.actions.clearArpCache
       Info: clear all dynamic enties in ARP cache table"
   ::= {ar1645v2Lan3 25}


ar1645v2Lan3ClearDebugCounters OBJECT-TYPE
   SYNTAX      Integer32
   MAX-ACCESS  read-write
   STATUS      current
   DESCRIPTION
      "Path: ethernet3.actions.clearDebugCounters
       Info: action in the debug group"
   ::= {ar1645v2Lan3 76}


ar1645v2Lan3EnableRds OBJECT-TYPE
   SYNTAX      Integer32
   MAX-ACCESS  read-write
   STATUS      current
   DESCRIPTION
      "Path: ethernet3.actions.enableRds
       Info: action in the debug group"
   ::= {ar1645v2Lan3 367}


ar1645v2Lan3DisableRds OBJECT-TYPE
   SYNTAX      Integer32
   MAX-ACCESS  read-write
   STATUS      current
   DESCRIPTION
      "Path: ethernet3.actions.disableRds
       Info: action in the debug group"
   ::= {ar1645v2Lan3 366}


ar1645v2Lan3EnableTds OBJECT-TYPE
   SYNTAX      Integer32
   MAX-ACCESS  read-write
   STATUS      current
   DESCRIPTION
      "Path: ethernet3.actions.enableTds
       Info: action in the debug group"
   ::= {ar1645v2Lan3 365}


ar1645v2Lan3DisableTds OBJECT-TYPE
   SYNTAX      Integer32
   MAX-ACCESS  read-write
   STATUS      current
   DESCRIPTION
      "Path: ethernet3.actions.disableTds
       Info: action in the debug group"
   ::= {ar1645v2Lan3 364}


ar1645v2Lan3ClearTsecStats OBJECT-TYPE
   SYNTAX      Integer32
   MAX-ACCESS  read-write
   STATUS      current
   DESCRIPTION
      "Path: ethernet3.actions.clearTsecStats
       Info: action in the debug group"
   ::= {ar1645v2Lan3 363}


ar1645v2Lan3StopTsecStats OBJECT-TYPE
   SYNTAX      Integer32
   MAX-ACCESS  read-write
   STATUS      current
   DESCRIPTION
      "Path: ethernet3.actions.stopTsecStats
       Info: action in the debug group"
   ::= {ar1645v2Lan3 362}


ar1645v2Lan3StartTsecStats OBJECT-TYPE
   SYNTAX      Integer32
   MAX-ACCESS  read-write
   STATUS      current
   DESCRIPTION
      "Path: ethernet3.actions.startTsecStats
       Info: action in the debug group"
   ::= {ar1645v2Lan3 361}


ar1645v2Lan3PhyAction OBJECT-TYPE
   SYNTAX      Integer32
   MAX-ACCESS  read-write
   STATUS      current
   DESCRIPTION
      "Path: ethernet3.actions.phyAction
       Info: action in the debug group"
   ::= {ar1645v2Lan3 90}



fr1645v2Lan3 OBJECT IDENTIFIER ::= {r1645v2Lan3 13}


fr1645v2Lan3Alarm OBJECT IDENTIFIER ::= {fr1645v2Lan3 207}

fr1645v2Lan3AlarmSSC OBJECT IDENTIFIER ::= {fr1645v2Lan3Alarm 1}

fr1645v2Lan3AlarmEntry OBJECT IDENTIFIER ::= {fr1645v2Lan3AlarmSSC 1}

fr1645v2Lan3AlarmDiscriminator OBJECT-TYPE
   SYNTAX      Integer32
   MAX-ACCESS  read-only
   STATUS      current
   DESCRIPTION
      "Path: ethernet3.alarms.alarmInfo.discriminator"
   ::= {fr1645v2Lan3AlarmEntry 16777216}

fr1645v2Lan3AlarmCurrent OBJECT-TYPE
   SYNTAX      Integer32
   MAX-ACCESS  read-only
   STATUS      current
   DESCRIPTION
      "Path: ethernet3.alarms.alarmInfo.currentAlarms

       Bit meanings:
               bit 0 = linkDown,
               bit 9 = pppoEDown"
   ::= {fr1645v2Lan3AlarmEntry 33554432}

fr1645v2Lan3AlarmPrevious OBJECT-TYPE
   SYNTAX      Integer32
   MAX-ACCESS  read-only
   STATUS      current
   DESCRIPTION
      "Path: ethernet3.alarms.alarmInfo.previousAlarms

       Bit meanings:
               bit 0 = linkDown,
               bit 9 = pppoEDown"
   ::= {fr1645v2Lan3AlarmEntry 50331648}

fr1645v2Lan3AlarmMask OBJECT-TYPE
   SYNTAX      Integer32
   MAX-ACCESS  read-only
   STATUS      current
   DESCRIPTION
      "Path: ethernet3.alarms.alarmInfo.alarmMask

       Bit meanings:
               bit 0 = linkDown,
               bit 9 = pppoEDown"
   ::= {fr1645v2Lan3AlarmEntry 67108864}

fr1645v2Lan3AlarmLevLinkDown OBJECT-TYPE
   SYNTAX      Integer32
   MAX-ACCESS  read-only
   STATUS      current
   DESCRIPTION
      "Path: ethernet3.alarms.alarmInfo.alarmLevel.linkDown"
   ::= {fr1645v2Lan3AlarmEntry 83951616}

fr1645v2Lan3AlarmLevPppoEDown OBJECT-TYPE
   SYNTAX      Integer32
   MAX-ACCESS  read-only
   STATUS      current
   DESCRIPTION
      "Path: ethernet3.alarms.alarmInfo.alarmLevel.pppoEDown"
   ::= {fr1645v2Lan3AlarmEntry 84541440}


fr1645v2Lan3AlarmE2 OBJECT IDENTIFIER ::= {fr1645v2Lan3Alarm 2}

fr1645v2Lan3AlarmE2Entry OBJECT IDENTIFIER ::= {fr1645v2Lan3AlarmE2 1}

fr1645v2Lan3AlarmE2LinkDown OBJECT IDENTIFIER ::= {fr1645v2Lan3AlarmE2Entry 10}

fr1645v2Lan3AlarmE2LinkDownPfx OBJECT IDENTIFIER ::= {fr1645v2Lan3AlarmE2LinkDown 0}

fr1645v2Lan3AlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lan3Giga'
                (root='router1645') has changed from the ON to the OFF state."
   ::= {fr1645v2Lan3AlarmE2LinkDownPfx 1}

fr1645v2Lan3AlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lan3Giga'
                (root='router1645') has changed from the OFF to the ON state."
   ::= {fr1645v2Lan3AlarmE2LinkDownPfx 2}

fr1645v2Lan3AlarmE2PppoEDown OBJECT IDENTIFIER ::= {fr1645v2Lan3AlarmE2Entry 19}

fr1645v2Lan3AlarmE2PppoEDownPfx OBJECT IDENTIFIER ::= {fr1645v2Lan3AlarmE2PppoEDown 0}

fr1645v2Lan3AlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lan3Giga'
                (root='router1645') has changed from the ON to the OFF state."
   ::= {fr1645v2Lan3AlarmE2PppoEDownPfx 1}

fr1645v2Lan3AlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lan3Giga'
                (root='router1645') has changed from the OFF to the ON state."
   ::= {fr1645v2Lan3AlarmE2PppoEDownPfx 2}



END
