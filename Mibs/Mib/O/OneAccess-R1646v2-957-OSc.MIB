OneAccess-R1646v2-957-OSc DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2OSc OBJECT IDENTIFIER ::= {r1646Rootv2 957}

r1646v2OScMOProp OBJECT IDENTIFIER ::= {r1646v2OSc 1}

r1646v2OScMOPropEntry OBJECT IDENTIFIER ::= {r1646v2OScMOProp 1}

r1646v2OScMOPropPath OBJECT-TYPE
   SYNTAX      ContainmentPath
   MAX-ACCESS  read-only
   STATUS      current
   DESCRIPTION
      "Textual description of the containment tree from the instance of
       the root object down to the instance of the current object."
   ::= {r1646v2OScMOPropEntry 3}

r1646v2OScMOPropRev OBJECT-TYPE
   SYNTAX      ObjectRevision
   MAX-ACCESS  read-only
   STATUS      current
   DESCRIPTION
      "This value corresponds with the revision of the MANAGED OBJECT."
   ::= {r1646v2OScMOPropEntry 4}



pr1646v2OSc OBJECT IDENTIFIER ::= {r1646v2OSc 12}


pr1646v2OScProcPower OBJECT IDENTIFIER ::= {pr1646v2OSc 1}

pr1646v2OScProcPowerSSC OBJECT IDENTIFIER ::= {pr1646v2OScProcPower 1}

pr1646v2OScProcPowerEntry OBJECT IDENTIFIER ::= {pr1646v2OScProcPowerSSC 1}

pr1646v2OScProcPowerCore0 OBJECT-TYPE
   SYNTAX      Integer32
   UNITS       "%"
   MAX-ACCESS  read-only
   STATUS      current
   DESCRIPTION
      "Path: operatingSystem.performance.procPower.core0

       unit name = %"
   ::= {pr1646v2OScProcPowerEntry 16777216}

pr1646v2OScProcPowerCore1 OBJECT-TYPE
   SYNTAX      Integer32
   MAX-ACCESS  read-only
   STATUS      current
   DESCRIPTION
      "Path: operatingSystem.performance.procPower.core1

       unit name = %
       formula = 10 / ; 10 *"
   ::= {pr1646v2OScProcPowerEntry 33554432}



END
