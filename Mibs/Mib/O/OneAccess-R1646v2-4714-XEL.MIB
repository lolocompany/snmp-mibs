OneAccess-R1646v2-4714-XEL DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2XEL OBJECT IDENTIFIER ::= {r1646Rootv2 4714}

r1646v2XELMOProp OBJECT IDENTIFIER ::= {r1646v2XEL 1}

r1646v2XELMOPropEntry OBJECT IDENTIFIER ::= {r1646v2XELMOProp 1}

r1646v2XELMOPropPath OBJECT-TYPE
   SYNTAX      ContainmentPath
   MAX-ACCESS  read-only
   STATUS      current
   DESCRIPTION
      "Textual description of the containment tree from the instance of
       the root object down to the instance of the current object."
   ::= {r1646v2XELMOPropEntry 3}

r1646v2XELMOPropRev OBJECT-TYPE
   SYNTAX      ObjectRevision
   MAX-ACCESS  read-only
   STATUS      current
   DESCRIPTION
      "This value corresponds with the revision of the MANAGED OBJECT."
   ::= {r1646v2XELMOPropEntry 4}



sr1646v2XEL OBJECT IDENTIFIER ::= {r1646v2XEL 14}


sr1646v2XELEocInfo OBJECT IDENTIFIER ::= {sr1646v2XEL 132}

sr1646v2XELEocInfoSSC OBJECT IDENTIFIER ::= {sr1646v2XELEocInfo 1}

sr1646v2XELEocInfoEntry OBJECT IDENTIFIER ::= {sr1646v2XELEocInfoSSC 1}

sr1646v2XELEocInfoVendorID OBJECT-TYPE
   SYNTAX      OCTET STRING
   MAX-ACCESS  read-only
   STATUS      current
   DESCRIPTION
      "Path: end.status.eocInfo.vendorID"
   ::= {sr1646v2XELEocInfoEntry 16777216}

sr1646v2XELEocInfoVendorVersionNumber OBJECT-TYPE
   SYNTAX      OCTET STRING
   MAX-ACCESS  read-only
   STATUS      current
   DESCRIPTION
      "Path: end.status.eocInfo.vendorVersionNumber"
   ::= {sr1646v2XELEocInfoEntry 33554432}

sr1646v2XELEocInfoVendorSerialNumber OBJECT-TYPE
   SYNTAX      OCTET STRING
   MAX-ACCESS  read-only
   STATUS      current
   DESCRIPTION
      "Path: end.status.eocInfo.vendorSerialNumber"
   ::= {sr1646v2XELEocInfoEntry 50331648}


sr1646v2XELG994VendorID OBJECT-TYPE
   SYNTAX      OCTET STRING
   MAX-ACCESS  read-only
   STATUS      current
   DESCRIPTION
      "Path: end.status.g994VendorID
       Info: G994 vendor id"
   ::= {sr1646v2XEL 133}


sr1646v2XELG997Capabilities OBJECT-TYPE
   SYNTAX      OCTET STRING
   MAX-ACCESS  read-only
   STATUS      current
   DESCRIPTION
      "Path: end.status.g997Capabilities
       Info: G997 XTSE Capabilities"
   ::= {sr1646v2XEL 134}



END
