OneAccess-R1645v2-4838-ElinePair DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2ElinePair OBJECT IDENTIFIER ::= {r1645Rootv2 4838}

r1645v2ElinePairMOProp OBJECT-TYPE
   SYNTAX      SEQUENCE OF R1645v2ElinePairMOPropEntry
   MAX-ACCESS  not-accessible
   STATUS      current
   DESCRIPTION
      ""
   ::= {r1645v2ElinePair 1}

r1645v2ElinePairMOPropEntry OBJECT-TYPE
   SYNTAX      R1645v2ElinePairMOPropEntry
   MAX-ACCESS  not-accessible
   STATUS      current
   DESCRIPTION
      ""
   INDEX      { r1645v2ElinePairMOPropGlobalIx }
   ::= {r1645v2ElinePairMOProp 1}

R1645v2ElinePairMOPropEntry ::=
   SEQUENCE
      {
      r1645v2ElinePairMOPropPath
         ContainmentPath,
      r1645v2ElinePairMOPropRev
         ObjectRevision,
      r1645v2ElinePairMOPropGlobalIx
         GlobalIndex
      }

r1645v2ElinePairMOPropPath OBJECT-TYPE
   SYNTAX      ContainmentPath
   MAX-ACCESS  read-only
   STATUS      current
   DESCRIPTION
      "Textual description of the containment tree from the instance of
       the root object down to the instance of the current object."
   ::= {r1645v2ElinePairMOPropEntry 3}

r1645v2ElinePairMOPropRev OBJECT-TYPE
   SYNTAX      ObjectRevision
   MAX-ACCESS  read-only
   STATUS      current
   DESCRIPTION
      "This value corresponds with the revision of the MANAGED OBJECT."
   ::= {r1645v2ElinePairMOPropEntry 4}

r1645v2ElinePairMOPropGlobalIx OBJECT-TYPE
   SYNTAX      GlobalIndex
   MAX-ACCESS  read-only
   STATUS      current
   DESCRIPTION
      "The value of the tlsCntTreeGlobalIndex of the MANAGED OBJECT."
   ::= {r1645v2ElinePairMOPropEntry 10}



sr1645v2ElinePair OBJECT IDENTIFIER ::= {r1645v2ElinePair 14}


sr1645v2ElinePairDsTransmitPower OBJECT IDENTIFIER ::= {sr1645v2ElinePair 15}

sr1645v2ElinePairDsTransmitPowerTable OBJECT-TYPE
   SYNTAX      SEQUENCE OF Sr1645v2ElinePairDsTransmitPowerEntry
   MAX-ACCESS  not-accessible
   STATUS      current
   DESCRIPTION
      "Tx power"
   ::= {sr1645v2ElinePairDsTransmitPower 1}

sr1645v2ElinePairDsTransmitPowerEntry OBJECT-TYPE
   SYNTAX      Sr1645v2ElinePairDsTransmitPowerEntry
   MAX-ACCESS  not-accessible
   STATUS      current
   DESCRIPTION
      ""
   INDEX      { sr1645v2ElinePairDsTransmitPowerGlobalIx }
   ::= {sr1645v2ElinePairDsTransmitPowerTable 1}

Sr1645v2ElinePairDsTransmitPowerEntry ::=
   SEQUENCE
      {
      sr1645v2ElinePairDsTransmitPowerGlobalIx
         GlobalIndex,
      sr1645v2ElinePairDsTransmitPowerValue
         INTEGER
      }

sr1645v2ElinePairDsTransmitPowerGlobalIx OBJECT-TYPE
   SYNTAX      GlobalIndex
   MAX-ACCESS  not-accessible
   STATUS      current
   DESCRIPTION
      "The value of the tlsCntTreeGlobalIndex of the MANAGED OBJECT."
   ::= {sr1645v2ElinePairDsTransmitPowerEntry 10}

sr1645v2ElinePairDsTransmitPowerValue OBJECT-TYPE
   SYNTAX      INTEGER
               {
               notAvailable (32767)
               }
   MAX-ACCESS  read-only
   STATUS      current
   DESCRIPTION
      "Path: linePair.status.dsTransmitPower

       unit name = dBm
       formula = 10 /; 10 *

       Possibilities:
               notAvailable   (32767)"
   ::= {sr1645v2ElinePairDsTransmitPowerEntry 2147483648}


sr1645v2ElinePairFeLossOfSignal OBJECT IDENTIFIER ::= {sr1645v2ElinePair 20}

sr1645v2ElinePairFeLossOfSignalTable OBJECT-TYPE
   SYNTAX      SEQUENCE OF Sr1645v2ElinePairFeLossOfSignalEntry
   MAX-ACCESS  not-accessible
   STATUS      current
   DESCRIPTION
      "Loss of ..."
   ::= {sr1645v2ElinePairFeLossOfSignal 1}

sr1645v2ElinePairFeLossOfSignalEntry OBJECT-TYPE
   SYNTAX      Sr1645v2ElinePairFeLossOfSignalEntry
   MAX-ACCESS  not-accessible
   STATUS      current
   DESCRIPTION
      ""
   INDEX      { sr1645v2ElinePairFeLossOfSignalGlobalIx }
   ::= {sr1645v2ElinePairFeLossOfSignalTable 1}

Sr1645v2ElinePairFeLossOfSignalEntry ::=
   SEQUENCE
      {
      sr1645v2ElinePairFeLossOfSignalGlobalIx
         GlobalIndex,
      sr1645v2ElinePairFeLossOfSignalValue
         INTEGER
      }

sr1645v2ElinePairFeLossOfSignalGlobalIx OBJECT-TYPE
   SYNTAX      GlobalIndex
   MAX-ACCESS  not-accessible
   STATUS      current
   DESCRIPTION
      "The value of the tlsCntTreeGlobalIndex of the MANAGED OBJECT."
   ::= {sr1645v2ElinePairFeLossOfSignalEntry 10}

sr1645v2ElinePairFeLossOfSignalValue OBJECT-TYPE
   SYNTAX      INTEGER
               {
               off (0),
               on (1)
               }
   MAX-ACCESS  read-only
   STATUS      current
   DESCRIPTION
      "Path: linePair.status.feLossOfSignal

       Possibilities:
               off   (0)
               on   (1)"
   ::= {sr1645v2ElinePairFeLossOfSignalEntry 2147483648}


sr1645v2ElinePairFeLossOfMargin OBJECT IDENTIFIER ::= {sr1645v2ElinePair 22}

sr1645v2ElinePairFeLossOfMarginTable OBJECT-TYPE
   SYNTAX      SEQUENCE OF Sr1645v2ElinePairFeLossOfMarginEntry
   MAX-ACCESS  not-accessible
   STATUS      current
   DESCRIPTION
      "Loss of ..."
   ::= {sr1645v2ElinePairFeLossOfMargin 1}

sr1645v2ElinePairFeLossOfMarginEntry OBJECT-TYPE
   SYNTAX      Sr1645v2ElinePairFeLossOfMarginEntry
   MAX-ACCESS  not-accessible
   STATUS      current
   DESCRIPTION
      ""
   INDEX      { sr1645v2ElinePairFeLossOfMarginGlobalIx }
   ::= {sr1645v2ElinePairFeLossOfMarginTable 1}

Sr1645v2ElinePairFeLossOfMarginEntry ::=
   SEQUENCE
      {
      sr1645v2ElinePairFeLossOfMarginGlobalIx
         GlobalIndex,
      sr1645v2ElinePairFeLossOfMarginValue
         INTEGER
      }

sr1645v2ElinePairFeLossOfMarginGlobalIx OBJECT-TYPE
   SYNTAX      GlobalIndex
   MAX-ACCESS  not-accessible
   STATUS      current
   DESCRIPTION
      "The value of the tlsCntTreeGlobalIndex of the MANAGED OBJECT."
   ::= {sr1645v2ElinePairFeLossOfMarginEntry 10}

sr1645v2ElinePairFeLossOfMarginValue OBJECT-TYPE
   SYNTAX      INTEGER
               {
               off (0),
               on (1)
               }
   MAX-ACCESS  read-only
   STATUS      current
   DESCRIPTION
      "Path: linePair.status.feLossOfMargin

       Possibilities:
               off   (0)
               on   (1)"
   ::= {sr1645v2ElinePairFeLossOfMarginEntry 2147483648}


sr1645v2ElinePairFeLossOfPower OBJECT IDENTIFIER ::= {sr1645v2ElinePair 24}

sr1645v2ElinePairFeLossOfPowerTable OBJECT-TYPE
   SYNTAX      SEQUENCE OF Sr1645v2ElinePairFeLossOfPowerEntry
   MAX-ACCESS  not-accessible
   STATUS      current
   DESCRIPTION
      "Loss of ..."
   ::= {sr1645v2ElinePairFeLossOfPower 1}

sr1645v2ElinePairFeLossOfPowerEntry OBJECT-TYPE
   SYNTAX      Sr1645v2ElinePairFeLossOfPowerEntry
   MAX-ACCESS  not-accessible
   STATUS      current
   DESCRIPTION
      ""
   INDEX      { sr1645v2ElinePairFeLossOfPowerGlobalIx }
   ::= {sr1645v2ElinePairFeLossOfPowerTable 1}

Sr1645v2ElinePairFeLossOfPowerEntry ::=
   SEQUENCE
      {
      sr1645v2ElinePairFeLossOfPowerGlobalIx
         GlobalIndex,
      sr1645v2ElinePairFeLossOfPowerValue
         INTEGER
      }

sr1645v2ElinePairFeLossOfPowerGlobalIx OBJECT-TYPE
   SYNTAX      GlobalIndex
   MAX-ACCESS  not-accessible
   STATUS      current
   DESCRIPTION
      "The value of the tlsCntTreeGlobalIndex of the MANAGED OBJECT."
   ::= {sr1645v2ElinePairFeLossOfPowerEntry 10}

sr1645v2ElinePairFeLossOfPowerValue OBJECT-TYPE
   SYNTAX      INTEGER
               {
               off (0),
               on (1)
               }
   MAX-ACCESS  read-only
   STATUS      current
   DESCRIPTION
      "Path: linePair.status.feLossOfPower

       Possibilities:
               off   (0)
               on   (1)"
   ::= {sr1645v2ElinePairFeLossOfPowerEntry 2147483648}


sr1645v2ElinePairUsSignalNoiseMargin OBJECT IDENTIFIER ::= {sr1645v2ElinePair 26}

sr1645v2ElinePairUsSignalNoiseMarginTable OBJECT-TYPE
   SYNTAX      SEQUENCE OF Sr1645v2ElinePairUsSignalNoiseMarginEntry
   MAX-ACCESS  not-accessible
   STATUS      current
   DESCRIPTION
      "signalNoiseMargin -51dB to +51dB"
   ::= {sr1645v2ElinePairUsSignalNoiseMargin 1}

sr1645v2ElinePairUsSignalNoiseMarginEntry OBJECT-TYPE
   SYNTAX      Sr1645v2ElinePairUsSignalNoiseMarginEntry
   MAX-ACCESS  not-accessible
   STATUS      current
   DESCRIPTION
      ""
   INDEX      { sr1645v2ElinePairUsSignalNoiseMarginGlobalIx }
   ::= {sr1645v2ElinePairUsSignalNoiseMarginTable 1}

Sr1645v2ElinePairUsSignalNoiseMarginEntry ::=
   SEQUENCE
      {
      sr1645v2ElinePairUsSignalNoiseMarginGlobalIx
         GlobalIndex,
      sr1645v2ElinePairUsSignalNoiseMarginValue
         INTEGER
      }

sr1645v2ElinePairUsSignalNoiseMarginGlobalIx OBJECT-TYPE
   SYNTAX      GlobalIndex
   MAX-ACCESS  not-accessible
   STATUS      current
   DESCRIPTION
      "The value of the tlsCntTreeGlobalIndex of the MANAGED OBJECT."
   ::= {sr1645v2ElinePairUsSignalNoiseMarginEntry 10}

sr1645v2ElinePairUsSignalNoiseMarginValue OBJECT-TYPE
   SYNTAX      INTEGER
               {
               notAvailable (32767),
               undetermined (-512),
               lowerThanMargin (-511),
               higherThanMargin (511)
               }
   MAX-ACCESS  read-only
   STATUS      current
   DESCRIPTION
      "Path: linePair.status.usSignalNoiseMargin

       unit name = dB
       formula = 10 /; 10 *

       Possibilities:
               notAvailable   (32767)
               undetermined   (-512)
               lowerThanMargin   (-511)
               higherThanMargin   (511)"
   ::= {sr1645v2ElinePairUsSignalNoiseMarginEntry 2147483648}


sr1645v2ElinePairDsDTUFecCodewordSize OBJECT IDENTIFIER ::= {sr1645v2ElinePair 31}

sr1645v2ElinePairDsDTUFecCodewordSizeTable OBJECT-TYPE
   SYNTAX      SEQUENCE OF Sr1645v2ElinePairDsDTUFecCodewordSizeEntry
   MAX-ACCESS  not-accessible
   STATUS      current
   DESCRIPTION
      "Codeword Size"
   ::= {sr1645v2ElinePairDsDTUFecCodewordSize 1}

sr1645v2ElinePairDsDTUFecCodewordSizeEntry OBJECT-TYPE
   SYNTAX      Sr1645v2ElinePairDsDTUFecCodewordSizeEntry
   MAX-ACCESS  not-accessible
   STATUS      current
   DESCRIPTION
      ""
   INDEX      { sr1645v2ElinePairDsDTUFecCodewordSizeGlobalIx }
   ::= {sr1645v2ElinePairDsDTUFecCodewordSizeTable 1}

Sr1645v2ElinePairDsDTUFecCodewordSizeEntry ::=
   SEQUENCE
      {
      sr1645v2ElinePairDsDTUFecCodewordSizeGlobalIx
         GlobalIndex,
      sr1645v2ElinePairDsDTUFecCodewordSizeValue
         INTEGER
      }

sr1645v2ElinePairDsDTUFecCodewordSizeGlobalIx OBJECT-TYPE
   SYNTAX      GlobalIndex
   MAX-ACCESS  not-accessible
   STATUS      current
   DESCRIPTION
      "The value of the tlsCntTreeGlobalIndex of the MANAGED OBJECT."
   ::= {sr1645v2ElinePairDsDTUFecCodewordSizeEntry 10}

sr1645v2ElinePairDsDTUFecCodewordSizeValue OBJECT-TYPE
   SYNTAX      INTEGER
               {
               notAvailable (32767)
               }
   MAX-ACCESS  read-only
   STATUS      current
   DESCRIPTION
      "Path: linePair.status.dsDTUFecCodewordSize

       Possibilities:
               notAvailable   (32767)"
   ::= {sr1645v2ElinePairDsDTUFecCodewordSizeEntry 2147483648}


sr1645v2ElinePairSnmpIndex OBJECT IDENTIFIER ::= {sr1645v2ElinePair 269}

sr1645v2ElinePairSnmpIndexTable OBJECT-TYPE
   SYNTAX      SEQUENCE OF Sr1645v2ElinePairSnmpIndexEntry
   MAX-ACCESS  not-accessible
   STATUS      current
   DESCRIPTION
      "SNMP index assigned to this object"
   ::= {sr1645v2ElinePairSnmpIndex 1}

sr1645v2ElinePairSnmpIndexEntry OBJECT-TYPE
   SYNTAX      Sr1645v2ElinePairSnmpIndexEntry
   MAX-ACCESS  not-accessible
   STATUS      current
   DESCRIPTION
      ""
   INDEX      { sr1645v2ElinePairSnmpIndexGlobalIx }
   ::= {sr1645v2ElinePairSnmpIndexTable 1}

Sr1645v2ElinePairSnmpIndexEntry ::=
   SEQUENCE
      {
      sr1645v2ElinePairSnmpIndexGlobalIx
         GlobalIndex,
      sr1645v2ElinePairSnmpIndexValue
         Integer32
      }

sr1645v2ElinePairSnmpIndexGlobalIx OBJECT-TYPE
   SYNTAX      GlobalIndex
   MAX-ACCESS  not-accessible
   STATUS      current
   DESCRIPTION
      "The value of the tlsCntTreeGlobalIndex of the MANAGED OBJECT."
   ::= {sr1645v2ElinePairSnmpIndexEntry 10}

sr1645v2ElinePairSnmpIndexValue OBJECT-TYPE
   SYNTAX      Integer32
   MAX-ACCESS  read-only
   STATUS      current
   DESCRIPTION
      "Path: linePair.status.snmpIndex"
   ::= {sr1645v2ElinePairSnmpIndexEntry 2147483648}



pr1645v2ElinePair OBJECT IDENTIFIER ::= {r1645v2ElinePair 12}


pr1645v2ElinePairH2Params OBJECT IDENTIFIER ::= {pr1645v2ElinePair 40}

pr1645v2ElinePairH2ParamsSSCTable OBJECT-TYPE
   SYNTAX      SEQUENCE OF Pr1645v2ElinePairH2ParamsEntry
   MAX-ACCESS  not-accessible
   STATUS      current
   DESCRIPTION
      "h2LineParameters"
   ::= {pr1645v2ElinePairH2Params 1}

pr1645v2ElinePairH2ParamsEntry OBJECT-TYPE
   SYNTAX      Pr1645v2ElinePairH2ParamsEntry
   MAX-ACCESS  not-accessible
   STATUS      current
   DESCRIPTION
      ""
   INDEX      { pr1645v2ElinePairH2ParamsGlobalIx,
                pr1645v2ElinePairH2ParamsTableIx }
   ::= {pr1645v2ElinePairH2ParamsSSCTable 1}

Pr1645v2ElinePairH2ParamsEntry ::=
   SEQUENCE
      {
      pr1645v2ElinePairH2ParamsGlobalIx
         GlobalIndex,
      pr1645v2ElinePairH2ParamsTableIx
         TableIndex,
      pr1645v2ElinePairH2ParamsSysUpTime
         TimeTicks,
      pr1645v2ElinePairH2ParamsSnrMin
         Integer32,
      pr1645v2ElinePairH2ParamsSnrAvrg
         Integer32,
      pr1645v2ElinePairH2ParamsSnrMax
         Integer32
      }

pr1645v2ElinePairH2ParamsGlobalIx OBJECT-TYPE
   SYNTAX      GlobalIndex
   MAX-ACCESS  not-accessible
   STATUS      current
   DESCRIPTION
      "The value of the tlsCntTreeGlobalIndex of the MANAGED OBJECT."
   ::= {pr1645v2ElinePairH2ParamsEntry 10}

pr1645v2ElinePairH2ParamsTableIx OBJECT-TYPE
   SYNTAX      TableIndex
   MAX-ACCESS  not-accessible
   STATUS      current
   DESCRIPTION
      ""
   ::= {pr1645v2ElinePairH2ParamsEntry 11}

pr1645v2ElinePairH2ParamsSysUpTime OBJECT-TYPE
   SYNTAX      TimeTicks
   MAX-ACCESS  read-only
   STATUS      current
   DESCRIPTION
      "Path: linePair.performance.h2LineParameters.sysUpTime

       Time in centi-second."
   ::= {pr1645v2ElinePairH2ParamsEntry 16777216}

pr1645v2ElinePairH2ParamsSnrMin OBJECT-TYPE
   SYNTAX      Integer32
   MAX-ACCESS  read-only
   STATUS      current
   DESCRIPTION
      "Path: linePair.performance.h2LineParameters.noiseMarginMin

       unit name = dB
       formula = 10 / ; 10 *"
   ::= {pr1645v2ElinePairH2ParamsEntry 83886080}

pr1645v2ElinePairH2ParamsSnrAvrg OBJECT-TYPE
   SYNTAX      Integer32
   MAX-ACCESS  read-only
   STATUS      current
   DESCRIPTION
      "Path: linePair.performance.h2LineParameters.noiseMarginAvrg

       unit name = dB
       formula = 10 / ; 10 *"
   ::= {pr1645v2ElinePairH2ParamsEntry 100663296}

pr1645v2ElinePairH2ParamsSnrMax OBJECT-TYPE
   SYNTAX      Integer32
   MAX-ACCESS  read-only
   STATUS      current
   DESCRIPTION
      "Path: linePair.performance.h2LineParameters.noiseMarginMax

       unit name = dB
       formula = 10 / ; 10 *"
   ::= {pr1645v2ElinePairH2ParamsEntry 117440512}


pr1645v2ElinePairH2Perf OBJECT IDENTIFIER ::= {pr1645v2ElinePair 41}

pr1645v2ElinePairH2PerfSSCTable OBJECT-TYPE
   SYNTAX      SEQUENCE OF Pr1645v2ElinePairH2PerfEntry
   MAX-ACCESS  not-accessible
   STATUS      current
   DESCRIPTION
      "h2Performance"
   ::= {pr1645v2ElinePairH2Perf 1}

pr1645v2ElinePairH2PerfEntry OBJECT-TYPE
   SYNTAX      Pr1645v2ElinePairH2PerfEntry
   MAX-ACCESS  not-accessible
   STATUS      current
   DESCRIPTION
      ""
   INDEX      { pr1645v2ElinePairH2PerfGlobalIx,
                pr1645v2ElinePairH2PerfTableIx }
   ::= {pr1645v2ElinePairH2PerfSSCTable 1}

Pr1645v2ElinePairH2PerfEntry ::=
   SEQUENCE
      {
      pr1645v2ElinePairH2PerfGlobalIx
         GlobalIndex,
      pr1645v2ElinePairH2PerfTableIx
         TableIndex,
      pr1645v2ElinePairH2PerfSysUpTime
         TimeTicks,
      pr1645v2ElinePairH2PerfCViol
         Counter32,
      pr1645v2ElinePairH2PerfErrSec
         TimeTicks,
      pr1645v2ElinePairH2PerfSevErrSec
         TimeTicks,
      pr1645v2ElinePairH2PerfUnavSec
         TimeTicks,
      pr1645v2ElinePairH2PerfLosSec
         TimeTicks,
      pr1645v2ElinePairH2PerfLorSec
         TimeTicks,
      pr1645v2ElinePairH2PerfLossOfSignal
         Counter32,
      pr1645v2ElinePairH2PerfLossOfRmc
         Counter32,
      pr1645v2ElinePairH2PerfLossOfMargin
         Counter32,
      pr1645v2ElinePairH2PerfLossOfPower
         Counter32,
      pr1645v2ElinePairH2PerfUncorrDtu
         Counter32,
      pr1645v2ElinePairH2PerfRetransDtu
         Counter32,
      pr1645v2ElinePairH2PerfMSec
         TimeTicks
      }

pr1645v2ElinePairH2PerfGlobalIx OBJECT-TYPE
   SYNTAX      GlobalIndex
   MAX-ACCESS  not-accessible
   STATUS      current
   DESCRIPTION
      "The value of the tlsCntTreeGlobalIndex of the MANAGED OBJECT."
   ::= {pr1645v2ElinePairH2PerfEntry 10}

pr1645v2ElinePairH2PerfTableIx OBJECT-TYPE
   SYNTAX      TableIndex
   MAX-ACCESS  not-accessible
   STATUS      current
   DESCRIPTION
      ""
   ::= {pr1645v2ElinePairH2PerfEntry 11}

pr1645v2ElinePairH2PerfSysUpTime OBJECT-TYPE
   SYNTAX      TimeTicks
   MAX-ACCESS  read-only
   STATUS      current
   DESCRIPTION
      "Path: linePair.performance.h2Performance.sysUpTime

       Time in centi-second."
   ::= {pr1645v2ElinePairH2PerfEntry 16777216}

pr1645v2ElinePairH2PerfCViol OBJECT-TYPE
   SYNTAX      Counter32
   MAX-ACCESS  read-only
   STATUS      current
   DESCRIPTION
      "Path: linePair.performance.h2Performance.codeViolations

       32 bit unsigned wrappable counter."
   ::= {pr1645v2ElinePairH2PerfEntry 33554432}

pr1645v2ElinePairH2PerfErrSec OBJECT-TYPE
   SYNTAX      TimeTicks
   MAX-ACCESS  read-only
   STATUS      current
   DESCRIPTION
      "Path: linePair.performance.h2Performance.errSec

       Time in centi-second."
   ::= {pr1645v2ElinePairH2PerfEntry 50331648}

pr1645v2ElinePairH2PerfSevErrSec OBJECT-TYPE
   SYNTAX      TimeTicks
   MAX-ACCESS  read-only
   STATUS      current
   DESCRIPTION
      "Path: linePair.performance.h2Performance.sevErrSec

       Time in centi-second."
   ::= {pr1645v2ElinePairH2PerfEntry 67108864}

pr1645v2ElinePairH2PerfUnavSec OBJECT-TYPE
   SYNTAX      TimeTicks
   MAX-ACCESS  read-only
   STATUS      current
   DESCRIPTION
      "Path: linePair.performance.h2Performance.unavailSec

       Time in centi-second."
   ::= {pr1645v2ElinePairH2PerfEntry 83886080}

pr1645v2ElinePairH2PerfLosSec OBJECT-TYPE
   SYNTAX      TimeTicks
   MAX-ACCESS  read-only
   STATUS      current
   DESCRIPTION
      "Path: linePair.performance.h2Performance.losSec

       Time in centi-second."
   ::= {pr1645v2ElinePairH2PerfEntry 100663296}

pr1645v2ElinePairH2PerfLorSec OBJECT-TYPE
   SYNTAX      TimeTicks
   MAX-ACCESS  read-only
   STATUS      current
   DESCRIPTION
      "Path: linePair.performance.h2Performance.lorSec

       Time in centi-second."
   ::= {pr1645v2ElinePairH2PerfEntry 251658240}

pr1645v2ElinePairH2PerfLossOfSignal OBJECT-TYPE
   SYNTAX      Counter32
   MAX-ACCESS  read-only
   STATUS      current
   DESCRIPTION
      "Path: linePair.performance.h2Performance.lossOfSignal

       32 bit unsigned wrappable counter."
   ::= {pr1645v2ElinePairH2PerfEntry 268435456}

pr1645v2ElinePairH2PerfLossOfRmc OBJECT-TYPE
   SYNTAX      Counter32
   MAX-ACCESS  read-only
   STATUS      current
   DESCRIPTION
      "Path: linePair.performance.h2Performance.lossOfRmc

       32 bit unsigned wrappable counter."
   ::= {pr1645v2ElinePairH2PerfEntry 285212672}

pr1645v2ElinePairH2PerfLossOfMargin OBJECT-TYPE
   SYNTAX      Counter32
   MAX-ACCESS  read-only
   STATUS      current
   DESCRIPTION
      "Path: linePair.performance.h2Performance.lossOfMargin

       32 bit unsigned wrappable counter."
   ::= {pr1645v2ElinePairH2PerfEntry 301989888}

pr1645v2ElinePairH2PerfLossOfPower OBJECT-TYPE
   SYNTAX      Counter32
   MAX-ACCESS  read-only
   STATUS      current
   DESCRIPTION
      "Path: linePair.performance.h2Performance.lossOfPower

       32 bit unsigned wrappable counter."
   ::= {pr1645v2ElinePairH2PerfEntry 318767104}

pr1645v2ElinePairH2PerfUncorrDtu OBJECT-TYPE
   SYNTAX      Counter32
   MAX-ACCESS  read-only
   STATUS      current
   DESCRIPTION
      "Path: linePair.performance.h2Performance.uncorrDtu

       32 bit unsigned wrappable counter."
   ::= {pr1645v2ElinePairH2PerfEntry 335544320}

pr1645v2ElinePairH2PerfRetransDtu OBJECT-TYPE
   SYNTAX      Counter32
   MAX-ACCESS  read-only
   STATUS      current
   DESCRIPTION
      "Path: linePair.performance.h2Performance.retransDtu

       32 bit unsigned wrappable counter."
   ::= {pr1645v2ElinePairH2PerfEntry 352321536}

pr1645v2ElinePairH2PerfMSec OBJECT-TYPE
   SYNTAX      TimeTicks
   MAX-ACCESS  read-only
   STATUS      current
   DESCRIPTION
      "Path: linePair.performance.h2Performance.moniSec

       Time in centi-second."
   ::= {pr1645v2ElinePairH2PerfEntry 134217728}


pr1645v2ElinePairH24Params OBJECT IDENTIFIER ::= {pr1645v2ElinePair 42}

pr1645v2ElinePairH24ParamsSSCTable OBJECT-TYPE
   SYNTAX      SEQUENCE OF Pr1645v2ElinePairH24ParamsEntry
   MAX-ACCESS  not-accessible
   STATUS      current
   DESCRIPTION
      "h24LineParameters"
   ::= {pr1645v2ElinePairH24Params 1}

pr1645v2ElinePairH24ParamsEntry OBJECT-TYPE
   SYNTAX      Pr1645v2ElinePairH24ParamsEntry
   MAX-ACCESS  not-accessible
   STATUS      current
   DESCRIPTION
      ""
   INDEX      { pr1645v2ElinePairH24ParamsGlobalIx,
                pr1645v2ElinePairH24ParamsTableIx }
   ::= {pr1645v2ElinePairH24ParamsSSCTable 1}

Pr1645v2ElinePairH24ParamsEntry ::=
   SEQUENCE
      {
      pr1645v2ElinePairH24ParamsGlobalIx
         GlobalIndex,
      pr1645v2ElinePairH24ParamsTableIx
         TableIndex,
      pr1645v2ElinePairH24ParamsSysUpTime
         TimeTicks,
      pr1645v2ElinePairH24ParamsSnrMin
         Integer32,
      pr1645v2ElinePairH24ParamsSnrAvrg
         Integer32,
      pr1645v2ElinePairH24ParamsSnrMax
         Integer32
      }

pr1645v2ElinePairH24ParamsGlobalIx OBJECT-TYPE
   SYNTAX      GlobalIndex
   MAX-ACCESS  not-accessible
   STATUS      current
   DESCRIPTION
      "The value of the tlsCntTreeGlobalIndex of the MANAGED OBJECT."
   ::= {pr1645v2ElinePairH24ParamsEntry 10}

pr1645v2ElinePairH24ParamsTableIx OBJECT-TYPE
   SYNTAX      TableIndex
   MAX-ACCESS  not-accessible
   STATUS      current
   DESCRIPTION
      ""
   ::= {pr1645v2ElinePairH24ParamsEntry 11}

pr1645v2ElinePairH24ParamsSysUpTime OBJECT-TYPE
   SYNTAX      TimeTicks
   MAX-ACCESS  read-only
   STATUS      current
   DESCRIPTION
      "Path: linePair.performance.h24LineParameters.sysUpTime

       Time in centi-second."
   ::= {pr1645v2ElinePairH24ParamsEntry 16777216}

pr1645v2ElinePairH24ParamsSnrMin OBJECT-TYPE
   SYNTAX      Integer32
   MAX-ACCESS  read-only
   STATUS      current
   DESCRIPTION
      "Path: linePair.performance.h24LineParameters.noiseMarginMin

       unit name = dB
       formula = 10 / ; 10 *"
   ::= {pr1645v2ElinePairH24ParamsEntry 83886080}

pr1645v2ElinePairH24ParamsSnrAvrg OBJECT-TYPE
   SYNTAX      Integer32
   MAX-ACCESS  read-only
   STATUS      current
   DESCRIPTION
      "Path: linePair.performance.h24LineParameters.noiseMarginAvrg

       unit name = dB
       formula = 10 / ; 10 *"
   ::= {pr1645v2ElinePairH24ParamsEntry 100663296}

pr1645v2ElinePairH24ParamsSnrMax OBJECT-TYPE
   SYNTAX      Integer32
   MAX-ACCESS  read-only
   STATUS      current
   DESCRIPTION
      "Path: linePair.performance.h24LineParameters.noiseMarginMax

       unit name = dB
       formula = 10 / ; 10 *"
   ::= {pr1645v2ElinePairH24ParamsEntry 117440512}


pr1645v2ElinePairH24Perf OBJECT IDENTIFIER ::= {pr1645v2ElinePair 43}

pr1645v2ElinePairH24PerfSSCTable OBJECT-TYPE
   SYNTAX      SEQUENCE OF Pr1645v2ElinePairH24PerfEntry
   MAX-ACCESS  not-accessible
   STATUS      current
   DESCRIPTION
      "h24Performance"
   ::= {pr1645v2ElinePairH24Perf 1}

pr1645v2ElinePairH24PerfEntry OBJECT-TYPE
   SYNTAX      Pr1645v2ElinePairH24PerfEntry
   MAX-ACCESS  not-accessible
   STATUS      current
   DESCRIPTION
      ""
   INDEX      { pr1645v2ElinePairH24PerfGlobalIx,
                pr1645v2ElinePairH24PerfTableIx }
   ::= {pr1645v2ElinePairH24PerfSSCTable 1}

Pr1645v2ElinePairH24PerfEntry ::=
   SEQUENCE
      {
      pr1645v2ElinePairH24PerfGlobalIx
         GlobalIndex,
      pr1645v2ElinePairH24PerfTableIx
         TableIndex,
      pr1645v2ElinePairH24PerfSysUpTime
         TimeTicks,
      pr1645v2ElinePairH24PerfCViol
         Counter32,
      pr1645v2ElinePairH24PerfErrSec
         TimeTicks,
      pr1645v2ElinePairH24PerfSevErrSec
         TimeTicks,
      pr1645v2ElinePairH24PerfUnavSec
         TimeTicks,
      pr1645v2ElinePairH24PerfLosSec
         TimeTicks,
      pr1645v2ElinePairH24PerfLorSec
         TimeTicks,
      pr1645v2ElinePairH24PerfLossOfSignal
         Counter32,
      pr1645v2ElinePairH24PerfLossOfRmc
         Counter32,
      pr1645v2ElinePairH24PerfLossOfMargin
         Counter32,
      pr1645v2ElinePairH24PerfLossOfPower
         Counter32,
      pr1645v2ElinePairH24PerfUncorrDtu
         Counter32,
      pr1645v2ElinePairH24PerfRetransDtu
         Counter32,
      pr1645v2ElinePairH24PerfMSec
         TimeTicks
      }

pr1645v2ElinePairH24PerfGlobalIx OBJECT-TYPE
   SYNTAX      GlobalIndex
   MAX-ACCESS  not-accessible
   STATUS      current
   DESCRIPTION
      "The value of the tlsCntTreeGlobalIndex of the MANAGED OBJECT."
   ::= {pr1645v2ElinePairH24PerfEntry 10}

pr1645v2ElinePairH24PerfTableIx OBJECT-TYPE
   SYNTAX      TableIndex
   MAX-ACCESS  not-accessible
   STATUS      current
   DESCRIPTION
      ""
   ::= {pr1645v2ElinePairH24PerfEntry 11}

pr1645v2ElinePairH24PerfSysUpTime OBJECT-TYPE
   SYNTAX      TimeTicks
   MAX-ACCESS  read-only
   STATUS      current
   DESCRIPTION
      "Path: linePair.performance.h24Performance.sysUpTime

       Time in centi-second."
   ::= {pr1645v2ElinePairH24PerfEntry 16777216}

pr1645v2ElinePairH24PerfCViol OBJECT-TYPE
   SYNTAX      Counter32
   MAX-ACCESS  read-only
   STATUS      current
   DESCRIPTION
      "Path: linePair.performance.h24Performance.codeViolations

       32 bit unsigned wrappable counter."
   ::= {pr1645v2ElinePairH24PerfEntry 33554432}

pr1645v2ElinePairH24PerfErrSec OBJECT-TYPE
   SYNTAX      TimeTicks
   MAX-ACCESS  read-only
   STATUS      current
   DESCRIPTION
      "Path: linePair.performance.h24Performance.errSec

       Time in centi-second."
   ::= {pr1645v2ElinePairH24PerfEntry 50331648}

pr1645v2ElinePairH24PerfSevErrSec OBJECT-TYPE
   SYNTAX      TimeTicks
   MAX-ACCESS  read-only
   STATUS      current
   DESCRIPTION
      "Path: linePair.performance.h24Performance.sevErrSec

       Time in centi-second."
   ::= {pr1645v2ElinePairH24PerfEntry 67108864}

pr1645v2ElinePairH24PerfUnavSec OBJECT-TYPE
   SYNTAX      TimeTicks
   MAX-ACCESS  read-only
   STATUS      current
   DESCRIPTION
      "Path: linePair.performance.h24Performance.unavailSec

       Time in centi-second."
   ::= {pr1645v2ElinePairH24PerfEntry 83886080}

pr1645v2ElinePairH24PerfLosSec OBJECT-TYPE
   SYNTAX      TimeTicks
   MAX-ACCESS  read-only
   STATUS      current
   DESCRIPTION
      "Path: linePair.performance.h24Performance.losSec

       Time in centi-second."
   ::= {pr1645v2ElinePairH24PerfEntry 100663296}

pr1645v2ElinePairH24PerfLorSec OBJECT-TYPE
   SYNTAX      TimeTicks
   MAX-ACCESS  read-only
   STATUS      current
   DESCRIPTION
      "Path: linePair.performance.h24Performance.lorSec

       Time in centi-second."
   ::= {pr1645v2ElinePairH24PerfEntry 251658240}

pr1645v2ElinePairH24PerfLossOfSignal OBJECT-TYPE
   SYNTAX      Counter32
   MAX-ACCESS  read-only
   STATUS      current
   DESCRIPTION
      "Path: linePair.performance.h24Performance.lossOfSignal

       32 bit unsigned wrappable counter."
   ::= {pr1645v2ElinePairH24PerfEntry 268435456}

pr1645v2ElinePairH24PerfLossOfRmc OBJECT-TYPE
   SYNTAX      Counter32
   MAX-ACCESS  read-only
   STATUS      current
   DESCRIPTION
      "Path: linePair.performance.h24Performance.lossOfRmc

       32 bit unsigned wrappable counter."
   ::= {pr1645v2ElinePairH24PerfEntry 285212672}

pr1645v2ElinePairH24PerfLossOfMargin OBJECT-TYPE
   SYNTAX      Counter32
   MAX-ACCESS  read-only
   STATUS      current
   DESCRIPTION
      "Path: linePair.performance.h24Performance.lossOfMargin

       32 bit unsigned wrappable counter."
   ::= {pr1645v2ElinePairH24PerfEntry 301989888}

pr1645v2ElinePairH24PerfLossOfPower OBJECT-TYPE
   SYNTAX      Counter32
   MAX-ACCESS  read-only
   STATUS      current
   DESCRIPTION
      "Path: linePair.performance.h24Performance.lossOfPower

       32 bit unsigned wrappable counter."
   ::= {pr1645v2ElinePairH24PerfEntry 318767104}

pr1645v2ElinePairH24PerfUncorrDtu OBJECT-TYPE
   SYNTAX      Counter32
   MAX-ACCESS  read-only
   STATUS      current
   DESCRIPTION
      "Path: linePair.performance.h24Performance.uncorrDtu

       32 bit unsigned wrappable counter."
   ::= {pr1645v2ElinePairH24PerfEntry 335544320}

pr1645v2ElinePairH24PerfRetransDtu OBJECT-TYPE
   SYNTAX      Counter32
   MAX-ACCESS  read-only
   STATUS      current
   DESCRIPTION
      "Path: linePair.performance.h24Performance.retransDtu

       32 bit unsigned wrappable counter."
   ::= {pr1645v2ElinePairH24PerfEntry 352321536}

pr1645v2ElinePairH24PerfMSec OBJECT-TYPE
   SYNTAX      TimeTicks
   MAX-ACCESS  read-only
   STATUS      current
   DESCRIPTION
      "Path: linePair.performance.h24Performance.moniSec

       Time in centi-second."
   ::= {pr1645v2ElinePairH24PerfEntry 134217728}


pr1645v2ElinePairD7Params OBJECT IDENTIFIER ::= {pr1645v2ElinePair 44}

pr1645v2ElinePairD7ParamsSSCTable OBJECT-TYPE
   SYNTAX      SEQUENCE OF Pr1645v2ElinePairD7ParamsEntry
   MAX-ACCESS  not-accessible
   STATUS      current
   DESCRIPTION
      "d7LineParameters"
   ::= {pr1645v2ElinePairD7Params 1}

pr1645v2ElinePairD7ParamsEntry OBJECT-TYPE
   SYNTAX      Pr1645v2ElinePairD7ParamsEntry
   MAX-ACCESS  not-accessible
   STATUS      current
   DESCRIPTION
      ""
   INDEX      { pr1645v2ElinePairD7ParamsGlobalIx,
                pr1645v2ElinePairD7ParamsTableIx }
   ::= {pr1645v2ElinePairD7ParamsSSCTable 1}

Pr1645v2ElinePairD7ParamsEntry ::=
   SEQUENCE
      {
      pr1645v2ElinePairD7ParamsGlobalIx
         GlobalIndex,
      pr1645v2ElinePairD7ParamsTableIx
         TableIndex,
      pr1645v2ElinePairD7ParamsSysUpTime
         TimeTicks,
      pr1645v2ElinePairD7ParamsSnrMin
         Integer32,
      pr1645v2ElinePairD7ParamsSnrAvrg
         Integer32,
      pr1645v2ElinePairD7ParamsSnrMax
         Integer32
      }

pr1645v2ElinePairD7ParamsGlobalIx OBJECT-TYPE
   SYNTAX      GlobalIndex
   MAX-ACCESS  not-accessible
   STATUS      current
   DESCRIPTION
      "The value of the tlsCntTreeGlobalIndex of the MANAGED OBJECT."
   ::= {pr1645v2ElinePairD7ParamsEntry 10}

pr1645v2ElinePairD7ParamsTableIx OBJECT-TYPE
   SYNTAX      TableIndex
   MAX-ACCESS  not-accessible
   STATUS      current
   DESCRIPTION
      ""
   ::= {pr1645v2ElinePairD7ParamsEntry 11}

pr1645v2ElinePairD7ParamsSysUpTime OBJECT-TYPE
   SYNTAX      TimeTicks
   MAX-ACCESS  read-only
   STATUS      current
   DESCRIPTION
      "Path: linePair.performance.d7LineParameters.sysUpTime

       Time in centi-second."
   ::= {pr1645v2ElinePairD7ParamsEntry 16777216}

pr1645v2ElinePairD7ParamsSnrMin OBJECT-TYPE
   SYNTAX      Integer32
   MAX-ACCESS  read-only
   STATUS      current
   DESCRIPTION
      "Path: linePair.performance.d7LineParameters.noiseMarginMin

       unit name = dB
       formula = 10 / ; 10 *"
   ::= {pr1645v2ElinePairD7ParamsEntry 83886080}

pr1645v2ElinePairD7ParamsSnrAvrg OBJECT-TYPE
   SYNTAX      Integer32
   MAX-ACCESS  read-only
   STATUS      current
   DESCRIPTION
      "Path: linePair.performance.d7LineParameters.noiseMarginAvrg

       unit name = dB
       formula = 10 / ; 10 *"
   ::= {pr1645v2ElinePairD7ParamsEntry 100663296}

pr1645v2ElinePairD7ParamsSnrMax OBJECT-TYPE
   SYNTAX      Integer32
   MAX-ACCESS  read-only
   STATUS      current
   DESCRIPTION
      "Path: linePair.performance.d7LineParameters.noiseMarginMax

       unit name = dB
       formula = 10 / ; 10 *"
   ::= {pr1645v2ElinePairD7ParamsEntry 117440512}


pr1645v2ElinePairD7Perf OBJECT IDENTIFIER ::= {pr1645v2ElinePair 45}

pr1645v2ElinePairD7PerfSSCTable OBJECT-TYPE
   SYNTAX      SEQUENCE OF Pr1645v2ElinePairD7PerfEntry
   MAX-ACCESS  not-accessible
   STATUS      current
   DESCRIPTION
      "d7Performance"
   ::= {pr1645v2ElinePairD7Perf 1}

pr1645v2ElinePairD7PerfEntry OBJECT-TYPE
   SYNTAX      Pr1645v2ElinePairD7PerfEntry
   MAX-ACCESS  not-accessible
   STATUS      current
   DESCRIPTION
      ""
   INDEX      { pr1645v2ElinePairD7PerfGlobalIx,
                pr1645v2ElinePairD7PerfTableIx }
   ::= {pr1645v2ElinePairD7PerfSSCTable 1}

Pr1645v2ElinePairD7PerfEntry ::=
   SEQUENCE
      {
      pr1645v2ElinePairD7PerfGlobalIx
         GlobalIndex,
      pr1645v2ElinePairD7PerfTableIx
         TableIndex,
      pr1645v2ElinePairD7PerfSysUpTime
         TimeTicks,
      pr1645v2ElinePairD7PerfCViol
         Counter32,
      pr1645v2ElinePairD7PerfErrSec
         TimeTicks,
      pr1645v2ElinePairD7PerfSevErrSec
         TimeTicks,
      pr1645v2ElinePairD7PerfUnavSec
         TimeTicks,
      pr1645v2ElinePairD7PerfLosSec
         TimeTicks,
      pr1645v2ElinePairD7PerfLorSec
         TimeTicks,
      pr1645v2ElinePairD7PerfLossOfSignal
         Counter32,
      pr1645v2ElinePairD7PerfLossOfRmc
         Counter32,
      pr1645v2ElinePairD7PerfLossOfMargin
         Counter32,
      pr1645v2ElinePairD7PerfLossOfPower
         Counter32,
      pr1645v2ElinePairD7PerfUncorrDtu
         Counter32,
      pr1645v2ElinePairD7PerfRetransDtu
         Counter32,
      pr1645v2ElinePairD7PerfMSec
         TimeTicks
      }

pr1645v2ElinePairD7PerfGlobalIx OBJECT-TYPE
   SYNTAX      GlobalIndex
   MAX-ACCESS  not-accessible
   STATUS      current
   DESCRIPTION
      "The value of the tlsCntTreeGlobalIndex of the MANAGED OBJECT."
   ::= {pr1645v2ElinePairD7PerfEntry 10}

pr1645v2ElinePairD7PerfTableIx OBJECT-TYPE
   SYNTAX      TableIndex
   MAX-ACCESS  not-accessible
   STATUS      current
   DESCRIPTION
      ""
   ::= {pr1645v2ElinePairD7PerfEntry 11}

pr1645v2ElinePairD7PerfSysUpTime OBJECT-TYPE
   SYNTAX      TimeTicks
   MAX-ACCESS  read-only
   STATUS      current
   DESCRIPTION
      "Path: linePair.performance.d7Performance.sysUpTime

       Time in centi-second."
   ::= {pr1645v2ElinePairD7PerfEntry 16777216}

pr1645v2ElinePairD7PerfCViol OBJECT-TYPE
   SYNTAX      Counter32
   MAX-ACCESS  read-only
   STATUS      current
   DESCRIPTION
      "Path: linePair.performance.d7Performance.codeViolations

       32 bit unsigned wrappable counter."
   ::= {pr1645v2ElinePairD7PerfEntry 33554432}

pr1645v2ElinePairD7PerfErrSec OBJECT-TYPE
   SYNTAX      TimeTicks
   MAX-ACCESS  read-only
   STATUS      current
   DESCRIPTION
      "Path: linePair.performance.d7Performance.errSec

       Time in centi-second."
   ::= {pr1645v2ElinePairD7PerfEntry 50331648}

pr1645v2ElinePairD7PerfSevErrSec OBJECT-TYPE
   SYNTAX      TimeTicks
   MAX-ACCESS  read-only
   STATUS      current
   DESCRIPTION
      "Path: linePair.performance.d7Performance.sevErrSec

       Time in centi-second."
   ::= {pr1645v2ElinePairD7PerfEntry 67108864}

pr1645v2ElinePairD7PerfUnavSec OBJECT-TYPE
   SYNTAX      TimeTicks
   MAX-ACCESS  read-only
   STATUS      current
   DESCRIPTION
      "Path: linePair.performance.d7Performance.unavailSec

       Time in centi-second."
   ::= {pr1645v2ElinePairD7PerfEntry 83886080}

pr1645v2ElinePairD7PerfLosSec OBJECT-TYPE
   SYNTAX      TimeTicks
   MAX-ACCESS  read-only
   STATUS      current
   DESCRIPTION
      "Path: linePair.performance.d7Performance.losSec

       Time in centi-second."
   ::= {pr1645v2ElinePairD7PerfEntry 100663296}

pr1645v2ElinePairD7PerfLorSec OBJECT-TYPE
   SYNTAX      TimeTicks
   MAX-ACCESS  read-only
   STATUS      current
   DESCRIPTION
      "Path: linePair.performance.d7Performance.lorSec

       Time in centi-second."
   ::= {pr1645v2ElinePairD7PerfEntry 251658240}

pr1645v2ElinePairD7PerfLossOfSignal OBJECT-TYPE
   SYNTAX      Counter32
   MAX-ACCESS  read-only
   STATUS      current
   DESCRIPTION
      "Path: linePair.performance.d7Performance.lossOfSignal

       32 bit unsigned wrappable counter."
   ::= {pr1645v2ElinePairD7PerfEntry 268435456}

pr1645v2ElinePairD7PerfLossOfRmc OBJECT-TYPE
   SYNTAX      Counter32
   MAX-ACCESS  read-only
   STATUS      current
   DESCRIPTION
      "Path: linePair.performance.d7Performance.lossOfRmc

       32 bit unsigned wrappable counter."
   ::= {pr1645v2ElinePairD7PerfEntry 285212672}

pr1645v2ElinePairD7PerfLossOfMargin OBJECT-TYPE
   SYNTAX      Counter32
   MAX-ACCESS  read-only
   STATUS      current
   DESCRIPTION
      "Path: linePair.performance.d7Performance.lossOfMargin

       32 bit unsigned wrappable counter."
   ::= {pr1645v2ElinePairD7PerfEntry 301989888}

pr1645v2ElinePairD7PerfLossOfPower OBJECT-TYPE
   SYNTAX      Counter32
   MAX-ACCESS  read-only
   STATUS      current
   DESCRIPTION
      "Path: linePair.performance.d7Performance.lossOfPower

       32 bit unsigned wrappable counter."
   ::= {pr1645v2ElinePairD7PerfEntry 318767104}

pr1645v2ElinePairD7PerfUncorrDtu OBJECT-TYPE
   SYNTAX      Counter32
   MAX-ACCESS  read-only
   STATUS      current
   DESCRIPTION
      "Path: linePair.performance.d7Performance.uncorrDtu

       32 bit unsigned wrappable counter."
   ::= {pr1645v2ElinePairD7PerfEntry 335544320}

pr1645v2ElinePairD7PerfRetransDtu OBJECT-TYPE
   SYNTAX      Counter32
   MAX-ACCESS  read-only
   STATUS      current
   DESCRIPTION
      "Path: linePair.performance.d7Performance.retransDtu

       32 bit unsigned wrappable counter."
   ::= {pr1645v2ElinePairD7PerfEntry 352321536}

pr1645v2ElinePairD7PerfMSec OBJECT-TYPE
   SYNTAX      TimeTicks
   MAX-ACCESS  read-only
   STATUS      current
   DESCRIPTION
      "Path: linePair.performance.d7Performance.moniSec

       Time in centi-second."
   ::= {pr1645v2ElinePairD7PerfEntry 134217728}


pr1645v2ElinePairParams OBJECT IDENTIFIER ::= {pr1645v2ElinePair 46}

pr1645v2ElinePairParamsSSCTable OBJECT-TYPE
   SYNTAX      SEQUENCE OF Pr1645v2ElinePairParamsEntry
   MAX-ACCESS  not-accessible
   STATUS      current
   DESCRIPTION
      "elineParameters"
   ::= {pr1645v2ElinePairParams 1}

pr1645v2ElinePairParamsEntry OBJECT-TYPE
   SYNTAX      Pr1645v2ElinePairParamsEntry
   MAX-ACCESS  not-accessible
   STATUS      current
   DESCRIPTION
      ""
   INDEX      { pr1645v2ElinePairParamsGlobalIx }
   ::= {pr1645v2ElinePairParamsSSCTable 1}

Pr1645v2ElinePairParamsEntry ::=
   SEQUENCE
      {
      pr1645v2ElinePairParamsGlobalIx
         GlobalIndex,
      pr1645v2ElinePairParamsSnr
         Integer32
      }

pr1645v2ElinePairParamsGlobalIx OBJECT-TYPE
   SYNTAX      GlobalIndex
   MAX-ACCESS  not-accessible
   STATUS      current
   DESCRIPTION
      "The value of the tlsCntTreeGlobalIndex of the MANAGED OBJECT."
   ::= {pr1645v2ElinePairParamsEntry 10}

pr1645v2ElinePairParamsSnr OBJECT-TYPE
   SYNTAX      Integer32
   MAX-ACCESS  read-only
   STATUS      current
   DESCRIPTION
      "Path: linePair.performance.lineParameters.noiseMargin

       unit name = dB
       formula = 10 / ; 10 *"
   ::= {pr1645v2ElinePairParamsEntry 33554432}


pr1645v2ElinePairPerf OBJECT IDENTIFIER ::= {pr1645v2ElinePair 47}

pr1645v2ElinePairPerfSSCTable OBJECT-TYPE
   SYNTAX      SEQUENCE OF Pr1645v2ElinePairPerfEntry
   MAX-ACCESS  not-accessible
   STATUS      current
   DESCRIPTION
      "linePerformance"
   ::= {pr1645v2ElinePairPerf 1}

pr1645v2ElinePairPerfEntry OBJECT-TYPE
   SYNTAX      Pr1645v2ElinePairPerfEntry
   MAX-ACCESS  not-accessible
   STATUS      current
   DESCRIPTION
      ""
   INDEX      { pr1645v2ElinePairPerfGlobalIx }
   ::= {pr1645v2ElinePairPerfSSCTable 1}

Pr1645v2ElinePairPerfEntry ::=
   SEQUENCE
      {
      pr1645v2ElinePairPerfGlobalIx
         GlobalIndex,
      pr1645v2ElinePairPerfCViol
         Counter32,
      pr1645v2ElinePairPerfErrSec
         TimeTicks,
      pr1645v2ElinePairPerfSevErrSec
         TimeTicks,
      pr1645v2ElinePairPerfUnavSec
         TimeTicks,
      pr1645v2ElinePairPerfLosSec
         TimeTicks,
      pr1645v2ElinePairPerfLorSec
         TimeTicks,
      pr1645v2ElinePairPerfLossOfSignal
         Counter32,
      pr1645v2ElinePairPerfLossOfRmc
         Counter32,
      pr1645v2ElinePairPerfLossOfMargin
         Counter32,
      pr1645v2ElinePairPerfLossOfPower
         Counter32,
      pr1645v2ElinePairPerfUncorrDtu
         Counter32,
      pr1645v2ElinePairPerfRetransDtu
         Counter32
      }

pr1645v2ElinePairPerfGlobalIx OBJECT-TYPE
   SYNTAX      GlobalIndex
   MAX-ACCESS  not-accessible
   STATUS      current
   DESCRIPTION
      "The value of the tlsCntTreeGlobalIndex of the MANAGED OBJECT."
   ::= {pr1645v2ElinePairPerfEntry 10}

pr1645v2ElinePairPerfCViol OBJECT-TYPE
   SYNTAX      Counter32
   MAX-ACCESS  read-only
   STATUS      current
   DESCRIPTION
      "Path: linePair.performance.performance.codeViolations

       32 bit unsigned wrappable counter."
   ::= {pr1645v2ElinePairPerfEntry 16777216}

pr1645v2ElinePairPerfErrSec OBJECT-TYPE
   SYNTAX      TimeTicks
   MAX-ACCESS  read-only
   STATUS      current
   DESCRIPTION
      "Path: linePair.performance.performance.errSec

       Time in centi-second."
   ::= {pr1645v2ElinePairPerfEntry 33554432}

pr1645v2ElinePairPerfSevErrSec OBJECT-TYPE
   SYNTAX      TimeTicks
   MAX-ACCESS  read-only
   STATUS      current
   DESCRIPTION
      "Path: linePair.performance.performance.sevErrSec

       Time in centi-second."
   ::= {pr1645v2ElinePairPerfEntry 50331648}

pr1645v2ElinePairPerfUnavSec OBJECT-TYPE
   SYNTAX      TimeTicks
   MAX-ACCESS  read-only
   STATUS      current
   DESCRIPTION
      "Path: linePair.performance.performance.unavailSec

       Time in centi-second."
   ::= {pr1645v2ElinePairPerfEntry 67108864}

pr1645v2ElinePairPerfLosSec OBJECT-TYPE
   SYNTAX      TimeTicks
   MAX-ACCESS  read-only
   STATUS      current
   DESCRIPTION
      "Path: linePair.performance.performance.losSec

       Time in centi-second."
   ::= {pr1645v2ElinePairPerfEntry 83886080}

pr1645v2ElinePairPerfLorSec OBJECT-TYPE
   SYNTAX      TimeTicks
   MAX-ACCESS  read-only
   STATUS      current
   DESCRIPTION
      "Path: linePair.performance.performance.lorSec

       Time in centi-second."
   ::= {pr1645v2ElinePairPerfEntry 251658240}

pr1645v2ElinePairPerfLossOfSignal OBJECT-TYPE
   SYNTAX      Counter32
   MAX-ACCESS  read-only
   STATUS      current
   DESCRIPTION
      "Path: linePair.performance.performance.lossOfSignal

       32 bit unsigned wrappable counter."
   ::= {pr1645v2ElinePairPerfEntry 268435456}

pr1645v2ElinePairPerfLossOfRmc OBJECT-TYPE
   SYNTAX      Counter32
   MAX-ACCESS  read-only
   STATUS      current
   DESCRIPTION
      "Path: linePair.performance.performance.lossOfRmc

       32 bit unsigned wrappable counter."
   ::= {pr1645v2ElinePairPerfEntry 285212672}

pr1645v2ElinePairPerfLossOfMargin OBJECT-TYPE
   SYNTAX      Counter32
   MAX-ACCESS  read-only
   STATUS      current
   DESCRIPTION
      "Path: linePair.performance.performance.lossOfMargin

       32 bit unsigned wrappable counter."
   ::= {pr1645v2ElinePairPerfEntry 301989888}

pr1645v2ElinePairPerfLossOfPower OBJECT-TYPE
   SYNTAX      Counter32
   MAX-ACCESS  read-only
   STATUS      current
   DESCRIPTION
      "Path: linePair.performance.performance.lossOfPower

       32 bit unsigned wrappable counter."
   ::= {pr1645v2ElinePairPerfEntry 318767104}

pr1645v2ElinePairPerfUncorrDtu OBJECT-TYPE
   SYNTAX      Counter32
   MAX-ACCESS  read-only
   STATUS      current
   DESCRIPTION
      "Path: linePair.performance.performance.uncorrDtu

       32 bit unsigned wrappable counter."
   ::= {pr1645v2ElinePairPerfEntry 335544320}

pr1645v2ElinePairPerfRetransDtu OBJECT-TYPE
   SYNTAX      Counter32
   MAX-ACCESS  read-only
   STATUS      current
   DESCRIPTION
      "Path: linePair.performance.performance.retransDtu

       32 bit unsigned wrappable counter."
   ::= {pr1645v2ElinePairPerfEntry 352321536}



ar1645v2ElinePair OBJECT IDENTIFIER ::= {r1645v2ElinePair 16}


ar1645v2ElinePairClearCounters OBJECT IDENTIFIER ::= {ar1645v2ElinePair 263}

ar1645v2ElinePairClearCountersTable OBJECT-TYPE
   SYNTAX      SEQUENCE OF Ar1645v2ElinePairClearCountersEntry
   MAX-ACCESS  not-accessible
   STATUS      current
   DESCRIPTION
      "reset counters"
   ::= {ar1645v2ElinePairClearCounters 1}

ar1645v2ElinePairClearCountersEntry OBJECT-TYPE
   SYNTAX      Ar1645v2ElinePairClearCountersEntry
   MAX-ACCESS  not-accessible
   STATUS      current
   DESCRIPTION
      ""
   INDEX      { ar1645v2ElinePairClearCountersGlobalIx }
   ::= {ar1645v2ElinePairClearCountersTable 1}

Ar1645v2ElinePairClearCountersEntry ::=
   SEQUENCE
      {
      ar1645v2ElinePairClearCountersGlobalIx
         GlobalIndex,
      ar1645v2ElinePairClearCountersValue
         Integer32
      }

ar1645v2ElinePairClearCountersGlobalIx OBJECT-TYPE
   SYNTAX      GlobalIndex
   MAX-ACCESS  not-accessible
   STATUS      current
   DESCRIPTION
      "The value of the tlsCntTreeGlobalIndex of the MANAGED OBJECT."
   ::= {ar1645v2ElinePairClearCountersEntry 10}

ar1645v2ElinePairClearCountersValue OBJECT-TYPE
   SYNTAX      Integer32
   MAX-ACCESS  read-write
   STATUS      current
   DESCRIPTION
      "Path: linePair.actions.clearCounters"
   ::= {ar1645v2ElinePairClearCountersEntry 2147483648}

END
