OneAccess-R1645v2-4677-ApsB DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2ApsB OBJECT IDENTIFIER ::= {r1645Rootv2 4677}

r1645v2ApsBMOProp OBJECT-TYPE
   SYNTAX      SEQUENCE OF R1645v2ApsBMOPropEntry
   MAX-ACCESS  not-accessible
   STATUS      current
   DESCRIPTION
      ""
   ::= {r1645v2ApsB 1}

r1645v2ApsBMOPropEntry OBJECT-TYPE
   SYNTAX      R1645v2ApsBMOPropEntry
   MAX-ACCESS  not-accessible
   STATUS      current
   DESCRIPTION
      ""
   INDEX      { r1645v2ApsBMOPropGlobalIx }
   ::= {r1645v2ApsBMOProp 1}

R1645v2ApsBMOPropEntry ::=
   SEQUENCE
      {
      r1645v2ApsBMOPropPath
         ContainmentPath,
      r1645v2ApsBMOPropRev
         ObjectRevision,
      r1645v2ApsBMOPropGlobalIx
         GlobalIndex
      }

r1645v2ApsBMOPropPath OBJECT-TYPE
   SYNTAX      ContainmentPath
   MAX-ACCESS  read-only
   STATUS      current
   DESCRIPTION
      "Textual description of the containment tree from the instance of
       the root object down to the instance of the current object."
   ::= {r1645v2ApsBMOPropEntry 3}

r1645v2ApsBMOPropRev OBJECT-TYPE
   SYNTAX      ObjectRevision
   MAX-ACCESS  read-only
   STATUS      current
   DESCRIPTION
      "This value corresponds with the revision of the MANAGED OBJECT."
   ::= {r1645v2ApsBMOPropEntry 4}

r1645v2ApsBMOPropGlobalIx OBJECT-TYPE
   SYNTAX      GlobalIndex
   MAX-ACCESS  read-only
   STATUS      current
   DESCRIPTION
      "The value of the tlsCntTreeGlobalIndex of the MANAGED OBJECT."
   ::= {r1645v2ApsBMOPropEntry 10}



sr1645v2ApsB OBJECT IDENTIFIER ::= {r1645v2ApsB 14}


sr1645v2ApsBDescr OBJECT IDENTIFIER ::= {sr1645v2ApsB 101}

sr1645v2ApsBDescrTable OBJECT-TYPE
   SYNTAX      SEQUENCE OF Sr1645v2ApsBDescrEntry
   MAX-ACCESS  not-accessible
   STATUS      current
   DESCRIPTION
      "ifDescr"
   ::= {sr1645v2ApsBDescr 1}

sr1645v2ApsBDescrEntry OBJECT-TYPE
   SYNTAX      Sr1645v2ApsBDescrEntry
   MAX-ACCESS  not-accessible
   STATUS      current
   DESCRIPTION
      ""
   INDEX      { sr1645v2ApsBDescrGlobalIx }
   ::= {sr1645v2ApsBDescrTable 1}

Sr1645v2ApsBDescrEntry ::=
   SEQUENCE
      {
      sr1645v2ApsBDescrGlobalIx
         GlobalIndex,
      sr1645v2ApsBDescrValue
         DisplayString
      }

sr1645v2ApsBDescrGlobalIx OBJECT-TYPE
   SYNTAX      GlobalIndex
   MAX-ACCESS  not-accessible
   STATUS      current
   DESCRIPTION
      "The value of the tlsCntTreeGlobalIndex of the MANAGED OBJECT."
   ::= {sr1645v2ApsBDescrEntry 10}

sr1645v2ApsBDescrValue OBJECT-TYPE
   SYNTAX      DisplayString
   MAX-ACCESS  read-only
   STATUS      current
   DESCRIPTION
      "Path: apsBundle.status.ifDescr"
   ::= {sr1645v2ApsBDescrEntry 2147483648}


sr1645v2ApsBType OBJECT IDENTIFIER ::= {sr1645v2ApsB 102}

sr1645v2ApsBTypeTable OBJECT-TYPE
   SYNTAX      SEQUENCE OF Sr1645v2ApsBTypeEntry
   MAX-ACCESS  not-accessible
   STATUS      current
   DESCRIPTION
      "ifType"
   ::= {sr1645v2ApsBType 1}

sr1645v2ApsBTypeEntry OBJECT-TYPE
   SYNTAX      Sr1645v2ApsBTypeEntry
   MAX-ACCESS  not-accessible
   STATUS      current
   DESCRIPTION
      ""
   INDEX      { sr1645v2ApsBTypeGlobalIx }
   ::= {sr1645v2ApsBTypeTable 1}

Sr1645v2ApsBTypeEntry ::=
   SEQUENCE
      {
      sr1645v2ApsBTypeGlobalIx
         GlobalIndex,
      sr1645v2ApsBTypeValue
         INTEGER
      }

sr1645v2ApsBTypeGlobalIx OBJECT-TYPE
   SYNTAX      GlobalIndex
   MAX-ACCESS  not-accessible
   STATUS      current
   DESCRIPTION
      "The value of the tlsCntTreeGlobalIndex of the MANAGED OBJECT."
   ::= {sr1645v2ApsBTypeEntry 10}

sr1645v2ApsBTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: apsBundle.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2ApsBTypeEntry 2147483648}


sr1645v2ApsBMtu OBJECT IDENTIFIER ::= {sr1645v2ApsB 103}

sr1645v2ApsBMtuTable OBJECT-TYPE
   SYNTAX      SEQUENCE OF Sr1645v2ApsBMtuEntry
   MAX-ACCESS  not-accessible
   STATUS      current
   DESCRIPTION
      "ifMtu"
   ::= {sr1645v2ApsBMtu 1}

sr1645v2ApsBMtuEntry OBJECT-TYPE
   SYNTAX      Sr1645v2ApsBMtuEntry
   MAX-ACCESS  not-accessible
   STATUS      current
   DESCRIPTION
      ""
   INDEX      { sr1645v2ApsBMtuGlobalIx }
   ::= {sr1645v2ApsBMtuTable 1}

Sr1645v2ApsBMtuEntry ::=
   SEQUENCE
      {
      sr1645v2ApsBMtuGlobalIx
         GlobalIndex,
      sr1645v2ApsBMtuValue
         Integer32
      }

sr1645v2ApsBMtuGlobalIx OBJECT-TYPE
   SYNTAX      GlobalIndex
   MAX-ACCESS  not-accessible
   STATUS      current
   DESCRIPTION
      "The value of the tlsCntTreeGlobalIndex of the MANAGED OBJECT."
   ::= {sr1645v2ApsBMtuEntry 10}

sr1645v2ApsBMtuValue OBJECT-TYPE
   SYNTAX      Integer32
   MAX-ACCESS  read-only
   STATUS      current
   DESCRIPTION
      "Path: apsBundle.status.ifMtu"
   ::= {sr1645v2ApsBMtuEntry 2147483648}


sr1645v2ApsBOperStatus OBJECT IDENTIFIER ::= {sr1645v2ApsB 107}

sr1645v2ApsBOperStatusTable OBJECT-TYPE
   SYNTAX      SEQUENCE OF Sr1645v2ApsBOperStatusEntry
   MAX-ACCESS  not-accessible
   STATUS      current
   DESCRIPTION
      "ifOperStatus"
   ::= {sr1645v2ApsBOperStatus 1}

sr1645v2ApsBOperStatusEntry OBJECT-TYPE
   SYNTAX      Sr1645v2ApsBOperStatusEntry
   MAX-ACCESS  not-accessible
   STATUS      current
   DESCRIPTION
      ""
   INDEX      { sr1645v2ApsBOperStatusGlobalIx }
   ::= {sr1645v2ApsBOperStatusTable 1}

Sr1645v2ApsBOperStatusEntry ::=
   SEQUENCE
      {
      sr1645v2ApsBOperStatusGlobalIx
         GlobalIndex,
      sr1645v2ApsBOperStatusValue
         INTEGER
      }

sr1645v2ApsBOperStatusGlobalIx OBJECT-TYPE
   SYNTAX      GlobalIndex
   MAX-ACCESS  not-accessible
   STATUS      current
   DESCRIPTION
      "The value of the tlsCntTreeGlobalIndex of the MANAGED OBJECT."
   ::= {sr1645v2ApsBOperStatusEntry 10}

sr1645v2ApsBOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: apsBundle.status.ifOperStatus

       Possibilities:
               up   (1)
               down   (2)
               testing   (3)
               unknown   (4)
               dormant   (5)
               notPresent   (6)
               lowerLayerDown   (7)"
   ::= {sr1645v2ApsBOperStatusEntry 2147483648}


sr1645v2ApsBLastChange OBJECT IDENTIFIER ::= {sr1645v2ApsB 108}

sr1645v2ApsBLastChangeTable OBJECT-TYPE
   SYNTAX      SEQUENCE OF Sr1645v2ApsBLastChangeEntry
   MAX-ACCESS  not-accessible
   STATUS      current
   DESCRIPTION
      "ifLastChange"
   ::= {sr1645v2ApsBLastChange 1}

sr1645v2ApsBLastChangeEntry OBJECT-TYPE
   SYNTAX      Sr1645v2ApsBLastChangeEntry
   MAX-ACCESS  not-accessible
   STATUS      current
   DESCRIPTION
      ""
   INDEX      { sr1645v2ApsBLastChangeGlobalIx }
   ::= {sr1645v2ApsBLastChangeTable 1}

Sr1645v2ApsBLastChangeEntry ::=
   SEQUENCE
      {
      sr1645v2ApsBLastChangeGlobalIx
         GlobalIndex,
      sr1645v2ApsBLastChangeValue
         TimeTicks
      }

sr1645v2ApsBLastChangeGlobalIx OBJECT-TYPE
   SYNTAX      GlobalIndex
   MAX-ACCESS  not-accessible
   STATUS      current
   DESCRIPTION
      "The value of the tlsCntTreeGlobalIndex of the MANAGED OBJECT."
   ::= {sr1645v2ApsBLastChangeEntry 10}

sr1645v2ApsBLastChangeValue OBJECT-TYPE
   SYNTAX      TimeTicks
   MAX-ACCESS  read-only
   STATUS      current
   DESCRIPTION
      "Path: apsBundle.status.ifLastChange

       Time in centi-second."
   ::= {sr1645v2ApsBLastChangeEntry 2147483648}


sr1645v2ApsBLastChangeD OBJECT IDENTIFIER ::= {sr1645v2ApsB 183}

sr1645v2ApsBLastChangeDTable OBJECT-TYPE
   SYNTAX      SEQUENCE OF Sr1645v2ApsBLastChangeDEntry
   MAX-ACCESS  not-accessible
   STATUS      current
   DESCRIPTION
      "ifLastChangeDate"
   ::= {sr1645v2ApsBLastChangeD 1}

sr1645v2ApsBLastChangeDEntry OBJECT-TYPE
   SYNTAX      Sr1645v2ApsBLastChangeDEntry
   MAX-ACCESS  not-accessible
   STATUS      current
   DESCRIPTION
      ""
   INDEX      { sr1645v2ApsBLastChangeDGlobalIx }
   ::= {sr1645v2ApsBLastChangeDTable 1}

Sr1645v2ApsBLastChangeDEntry ::=
   SEQUENCE
      {
      sr1645v2ApsBLastChangeDGlobalIx
         GlobalIndex,
      sr1645v2ApsBLastChangeDValue
         DisplayString
      }

sr1645v2ApsBLastChangeDGlobalIx OBJECT-TYPE
   SYNTAX      GlobalIndex
   MAX-ACCESS  not-accessible
   STATUS      current
   DESCRIPTION
      "The value of the tlsCntTreeGlobalIndex of the MANAGED OBJECT."
   ::= {sr1645v2ApsBLastChangeDEntry 10}

sr1645v2ApsBLastChangeDValue OBJECT-TYPE
   SYNTAX      DisplayString
   MAX-ACCESS  read-only
   STATUS      current
   DESCRIPTION
      "Path: apsBundle.status.ifLastChangeDate"
   ::= {sr1645v2ApsBLastChangeDEntry 2147483648}


sr1645v2ApsBSpeed OBJECT IDENTIFIER ::= {sr1645v2ApsB 104}

sr1645v2ApsBSpeedTable OBJECT-TYPE
   SYNTAX      SEQUENCE OF Sr1645v2ApsBSpeedEntry
   MAX-ACCESS  not-accessible
   STATUS      current
   DESCRIPTION
      "ifSpeed"
   ::= {sr1645v2ApsBSpeed 1}

sr1645v2ApsBSpeedEntry OBJECT-TYPE
   SYNTAX      Sr1645v2ApsBSpeedEntry
   MAX-ACCESS  not-accessible
   STATUS      current
   DESCRIPTION
      ""
   INDEX      { sr1645v2ApsBSpeedGlobalIx }
   ::= {sr1645v2ApsBSpeedTable 1}

Sr1645v2ApsBSpeedEntry ::=
   SEQUENCE
      {
      sr1645v2ApsBSpeedGlobalIx
         GlobalIndex,
      sr1645v2ApsBSpeedValue
         Gauge32
      }

sr1645v2ApsBSpeedGlobalIx OBJECT-TYPE
   SYNTAX      GlobalIndex
   MAX-ACCESS  not-accessible
   STATUS      current
   DESCRIPTION
      "The value of the tlsCntTreeGlobalIndex of the MANAGED OBJECT."
   ::= {sr1645v2ApsBSpeedEntry 10}

sr1645v2ApsBSpeedValue OBJECT-TYPE
   SYNTAX      Gauge32
   MAX-ACCESS  read-only
   STATUS      current
   DESCRIPTION
      "Path: apsBundle.status.ifSpeed

       32 bit unsigned gauge value."
   ::= {sr1645v2ApsBSpeedEntry 2147483648}


sr1645v2ApsBSnmpIndex OBJECT IDENTIFIER ::= {sr1645v2ApsB 269}

sr1645v2ApsBSnmpIndexTable OBJECT-TYPE
   SYNTAX      SEQUENCE OF Sr1645v2ApsBSnmpIndexEntry
   MAX-ACCESS  not-accessible
   STATUS      current
   DESCRIPTION
      "SNMP index assigned to this object"
   ::= {sr1645v2ApsBSnmpIndex 1}

sr1645v2ApsBSnmpIndexEntry OBJECT-TYPE
   SYNTAX      Sr1645v2ApsBSnmpIndexEntry
   MAX-ACCESS  not-accessible
   STATUS      current
   DESCRIPTION
      ""
   INDEX      { sr1645v2ApsBSnmpIndexGlobalIx }
   ::= {sr1645v2ApsBSnmpIndexTable 1}

Sr1645v2ApsBSnmpIndexEntry ::=
   SEQUENCE
      {
      sr1645v2ApsBSnmpIndexGlobalIx
         GlobalIndex,
      sr1645v2ApsBSnmpIndexValue
         Integer32
      }

sr1645v2ApsBSnmpIndexGlobalIx OBJECT-TYPE
   SYNTAX      GlobalIndex
   MAX-ACCESS  not-accessible
   STATUS      current
   DESCRIPTION
      "The value of the tlsCntTreeGlobalIndex of the MANAGED OBJECT."
   ::= {sr1645v2ApsBSnmpIndexEntry 10}

sr1645v2ApsBSnmpIndexValue OBJECT-TYPE
   SYNTAX      Integer32
   MAX-ACCESS  read-only
   STATUS      current
   DESCRIPTION
      "Path: apsBundle.status.snmpIndex"
   ::= {sr1645v2ApsBSnmpIndexEntry 2147483648}


sr1645v2ApsBMode OBJECT IDENTIFIER ::= {sr1645v2ApsB 150}

sr1645v2ApsBModeTable OBJECT-TYPE
   SYNTAX      SEQUENCE OF Sr1645v2ApsBModeEntry
   MAX-ACCESS  not-accessible
   STATUS      current
   DESCRIPTION
      "APS running mode"
   ::= {sr1645v2ApsBMode 1}

sr1645v2ApsBModeEntry OBJECT-TYPE
   SYNTAX      Sr1645v2ApsBModeEntry
   MAX-ACCESS  not-accessible
   STATUS      current
   DESCRIPTION
      ""
   INDEX      { sr1645v2ApsBModeGlobalIx }
   ::= {sr1645v2ApsBModeTable 1}

Sr1645v2ApsBModeEntry ::=
   SEQUENCE
      {
      sr1645v2ApsBModeGlobalIx
         GlobalIndex,
      sr1645v2ApsBModeValue
         INTEGER
      }

sr1645v2ApsBModeGlobalIx OBJECT-TYPE
   SYNTAX      GlobalIndex
   MAX-ACCESS  not-accessible
   STATUS      current
   DESCRIPTION
      "The value of the tlsCntTreeGlobalIndex of the MANAGED OBJECT."
   ::= {sr1645v2ApsBModeEntry 10}

sr1645v2ApsBModeValue OBJECT-TYPE
   SYNTAX      INTEGER
               {
               unknown (0),
               s1p1sunidirectional (1),
               s1p1sbidirectional (2),
               s11sbidirectional (3)
               }
   MAX-ACCESS  read-only
   STATUS      current
   DESCRIPTION
      "Path: apsBundle.status.mode

       Possibilities:
               unknown   (0)
               1+1 unidirectional   (1)
               1+1 bidirectional   (2)
               1:1 bidirectional   (3)"
   ::= {sr1645v2ApsBModeEntry 2147483648}


sr1645v2ApsBRevertive OBJECT IDENTIFIER ::= {sr1645v2ApsB 160}

sr1645v2ApsBRevertiveTable OBJECT-TYPE
   SYNTAX      SEQUENCE OF Sr1645v2ApsBRevertiveEntry
   MAX-ACCESS  not-accessible
   STATUS      current
   DESCRIPTION
      "APS revertive"
   ::= {sr1645v2ApsBRevertive 1}

sr1645v2ApsBRevertiveEntry OBJECT-TYPE
   SYNTAX      Sr1645v2ApsBRevertiveEntry
   MAX-ACCESS  not-accessible
   STATUS      current
   DESCRIPTION
      ""
   INDEX      { sr1645v2ApsBRevertiveGlobalIx }
   ::= {sr1645v2ApsBRevertiveTable 1}

Sr1645v2ApsBRevertiveEntry ::=
   SEQUENCE
      {
      sr1645v2ApsBRevertiveGlobalIx
         GlobalIndex,
      sr1645v2ApsBRevertiveValue
         INTEGER
      }

sr1645v2ApsBRevertiveGlobalIx OBJECT-TYPE
   SYNTAX      GlobalIndex
   MAX-ACCESS  not-accessible
   STATUS      current
   DESCRIPTION
      "The value of the tlsCntTreeGlobalIndex of the MANAGED OBJECT."
   ::= {sr1645v2ApsBRevertiveEntry 10}

sr1645v2ApsBRevertiveValue OBJECT-TYPE
   SYNTAX      INTEGER
               {
               unknown (0),
               yes (1),
               no (2)
               }
   MAX-ACCESS  read-only
   STATUS      current
   DESCRIPTION
      "Path: apsBundle.status.revertive

       Possibilities:
               unknown   (0)
               yes   (1)
               no   (2)"
   ::= {sr1645v2ApsBRevertiveEntry 2147483648}


sr1645v2ApsBTimeToRestore OBJECT IDENTIFIER ::= {sr1645v2ApsB 157}

sr1645v2ApsBTimeToRestoreTable OBJECT-TYPE
   SYNTAX      SEQUENCE OF Sr1645v2ApsBTimeToRestoreEntry
   MAX-ACCESS  not-accessible
   STATUS      current
   DESCRIPTION
      "APS time to restore in state I"
   ::= {sr1645v2ApsBTimeToRestore 1}

sr1645v2ApsBTimeToRestoreEntry OBJECT-TYPE
   SYNTAX      Sr1645v2ApsBTimeToRestoreEntry
   MAX-ACCESS  not-accessible
   STATUS      current
   DESCRIPTION
      ""
   INDEX      { sr1645v2ApsBTimeToRestoreGlobalIx }
   ::= {sr1645v2ApsBTimeToRestoreTable 1}

Sr1645v2ApsBTimeToRestoreEntry ::=
   SEQUENCE
      {
      sr1645v2ApsBTimeToRestoreGlobalIx
         GlobalIndex,
      sr1645v2ApsBTimeToRestoreValue
         TimeTicks
      }

sr1645v2ApsBTimeToRestoreGlobalIx OBJECT-TYPE
   SYNTAX      GlobalIndex
   MAX-ACCESS  not-accessible
   STATUS      current
   DESCRIPTION
      "The value of the tlsCntTreeGlobalIndex of the MANAGED OBJECT."
   ::= {sr1645v2ApsBTimeToRestoreEntry 10}

sr1645v2ApsBTimeToRestoreValue OBJECT-TYPE
   SYNTAX      TimeTicks
   MAX-ACCESS  read-only
   STATUS      current
   DESCRIPTION
      "Path: apsBundle.status.timeToRestore

       Time in centi-second."
   ::= {sr1645v2ApsBTimeToRestoreEntry 2147483648}


sr1645v2ApsBApsCommunication OBJECT IDENTIFIER ::= {sr1645v2ApsB 161}

sr1645v2ApsBApsCommunicationTable OBJECT-TYPE
   SYNTAX      SEQUENCE OF Sr1645v2ApsBApsCommunicationEntry
   MAX-ACCESS  not-accessible
   STATUS      current
   DESCRIPTION
      "APS communication"
   ::= {sr1645v2ApsBApsCommunication 1}

sr1645v2ApsBApsCommunicationEntry OBJECT-TYPE
   SYNTAX      Sr1645v2ApsBApsCommunicationEntry
   MAX-ACCESS  not-accessible
   STATUS      current
   DESCRIPTION
      ""
   INDEX      { sr1645v2ApsBApsCommunicationGlobalIx }
   ::= {sr1645v2ApsBApsCommunicationTable 1}

Sr1645v2ApsBApsCommunicationEntry ::=
   SEQUENCE
      {
      sr1645v2ApsBApsCommunicationGlobalIx
         GlobalIndex,
      sr1645v2ApsBApsCommunicationValue
         INTEGER
      }

sr1645v2ApsBApsCommunicationGlobalIx OBJECT-TYPE
   SYNTAX      GlobalIndex
   MAX-ACCESS  not-accessible
   STATUS      current
   DESCRIPTION
      "The value of the tlsCntTreeGlobalIndex of the MANAGED OBJECT."
   ::= {sr1645v2ApsBApsCommunicationEntry 10}

sr1645v2ApsBApsCommunicationValue OBJECT-TYPE
   SYNTAX      INTEGER
               {
               unknown (0),
               yes (1),
               no (2)
               }
   MAX-ACCESS  read-only
   STATUS      current
   DESCRIPTION
      "Path: apsBundle.status.apsCommunication

       Possibilities:
               unknown   (0)
               yes   (1)
               no   (2)"
   ::= {sr1645v2ApsBApsCommunicationEntry 2147483648}


sr1645v2ApsBState OBJECT IDENTIFIER ::= {sr1645v2ApsB 151}

sr1645v2ApsBStateTable OBJECT-TYPE
   SYNTAX      SEQUENCE OF Sr1645v2ApsBStateEntry
   MAX-ACCESS  not-accessible
   STATUS      current
   DESCRIPTION
      "APS current state"
   ::= {sr1645v2ApsBState 1}

sr1645v2ApsBStateEntry OBJECT-TYPE
   SYNTAX      Sr1645v2ApsBStateEntry
   MAX-ACCESS  not-accessible
   STATUS      current
   DESCRIPTION
      ""
   INDEX      { sr1645v2ApsBStateGlobalIx }
   ::= {sr1645v2ApsBStateTable 1}

Sr1645v2ApsBStateEntry ::=
   SEQUENCE
      {
      sr1645v2ApsBStateGlobalIx
         GlobalIndex,
      sr1645v2ApsBStateValue
         INTEGER
      }

sr1645v2ApsBStateGlobalIx OBJECT-TYPE
   SYNTAX      GlobalIndex
   MAX-ACCESS  not-accessible
   STATUS      current
   DESCRIPTION
      "The value of the tlsCntTreeGlobalIndex of the MANAGED OBJECT."
   ::= {sr1645v2ApsBStateEntry 10}

sr1645v2ApsBStateValue OBJECT-TYPE
   SYNTAX      INTEGER
               {
               unknown (0),
               auNoRequest (1),
               buNoRequest (2),
               cuLockout (3),
               duForcedSwitch (4),
               euSignalFailuW (5),
               fuSignalFailuP (6),
               puSignalDegradeuW (7),
               quSignalDegradeuP (8),
               guManualSwitch (9),
               huManualSwitch (10),
               iuWaitToRestore (11),
               juDoNotRevert (12),
               kuExercise (13),
               luExercise (14),
               muReverseRequest (15),
               nuReverseRequest (16)
               }
   MAX-ACCESS  read-only
   STATUS      current
   DESCRIPTION
      "Path: apsBundle.status.state

       Possibilities:
               unknown   (0)
               a_NoRequest   (1)
               b_NoRequest   (2)
               c_Lockout   (3)
               d_ForcedSwitch   (4)
               e_SignalFail_W   (5)
               f_SignalFail_P   (6)
               p_SignalDegrade_W   (7)
               q_SignalDegrade_P   (8)
               g_ManualSwitch   (9)
               h_ManualSwitch   (10)
               i_WaitToRestore   (11)
               j_DoNotRevert   (12)
               k_Exercise   (13)
               l_Exercise   (14)
               m_ReverseRequest   (15)
               n_ReverseRequest   (16)"
   ::= {sr1645v2ApsBStateEntry 2147483648}


sr1645v2ApsBActiveLink OBJECT IDENTIFIER ::= {sr1645v2ApsB 152}

sr1645v2ApsBActiveLinkTable OBJECT-TYPE
   SYNTAX      SEQUENCE OF Sr1645v2ApsBActiveLinkEntry
   MAX-ACCESS  not-accessible
   STATUS      current
   DESCRIPTION
      "APS active link"
   ::= {sr1645v2ApsBActiveLink 1}

sr1645v2ApsBActiveLinkEntry OBJECT-TYPE
   SYNTAX      Sr1645v2ApsBActiveLinkEntry
   MAX-ACCESS  not-accessible
   STATUS      current
   DESCRIPTION
      ""
   INDEX      { sr1645v2ApsBActiveLinkGlobalIx }
   ::= {sr1645v2ApsBActiveLinkTable 1}

Sr1645v2ApsBActiveLinkEntry ::=
   SEQUENCE
      {
      sr1645v2ApsBActiveLinkGlobalIx
         GlobalIndex,
      sr1645v2ApsBActiveLinkValue
         INTEGER
      }

sr1645v2ApsBActiveLinkGlobalIx OBJECT-TYPE
   SYNTAX      GlobalIndex
   MAX-ACCESS  not-accessible
   STATUS      current
   DESCRIPTION
      "The value of the tlsCntTreeGlobalIndex of the MANAGED OBJECT."
   ::= {sr1645v2ApsBActiveLinkEntry 10}

sr1645v2ApsBActiveLinkValue OBJECT-TYPE
   SYNTAX      INTEGER
               {
               unknown (0),
               working (1),
               protection (2)
               }
   MAX-ACCESS  read-only
   STATUS      current
   DESCRIPTION
      "Path: apsBundle.status.activeLink

       Possibilities:
               unknown   (0)
               working   (1)
               protection   (2)"
   ::= {sr1645v2ApsBActiveLinkEntry 2147483648}


sr1645v2ApsBWorkingEntity OBJECT IDENTIFIER ::= {sr1645v2ApsB 153}

sr1645v2ApsBWorkingEntitySSCTable OBJECT-TYPE
   SYNTAX      SEQUENCE OF Sr1645v2ApsBWorkingEntityEntry
   MAX-ACCESS  not-accessible
   STATUS      current
   DESCRIPTION
      "APS working entity info"
   ::= {sr1645v2ApsBWorkingEntity 1}

sr1645v2ApsBWorkingEntityEntry OBJECT-TYPE
   SYNTAX      Sr1645v2ApsBWorkingEntityEntry
   MAX-ACCESS  not-accessible
   STATUS      current
   DESCRIPTION
      ""
   INDEX      { sr1645v2ApsBWorkingEntityGlobalIx }
   ::= {sr1645v2ApsBWorkingEntitySSCTable 1}

Sr1645v2ApsBWorkingEntityEntry ::=
   SEQUENCE
      {
      sr1645v2ApsBWorkingEntityGlobalIx
         GlobalIndex,
      sr1645v2ApsBWorkingEntityIf
         DisplayString,
      sr1645v2ApsBWorkingEntityIfStatus
         INTEGER,
      sr1645v2ApsBWorkingEntityMepName
         DisplayString,
      sr1645v2ApsBWorkingEntityMepDefect
         INTEGER,
      sr1645v2ApsBWorkingEntityQualityDegrade
         Integer32
      }

sr1645v2ApsBWorkingEntityGlobalIx OBJECT-TYPE
   SYNTAX      GlobalIndex
   MAX-ACCESS  not-accessible
   STATUS      current
   DESCRIPTION
      "The value of the tlsCntTreeGlobalIndex of the MANAGED OBJECT."
   ::= {sr1645v2ApsBWorkingEntityEntry 10}

sr1645v2ApsBWorkingEntityIf OBJECT-TYPE
   SYNTAX      DisplayString
   MAX-ACCESS  read-only
   STATUS      current
   DESCRIPTION
      "Path: apsBundle.status.workingEntity.interface"
   ::= {sr1645v2ApsBWorkingEntityEntry 16777216}

sr1645v2ApsBWorkingEntityIfStatus OBJECT-TYPE
   SYNTAX      INTEGER
               {
               notFound (0),
               up (1),
               down (2)
               }
   MAX-ACCESS  read-only
   STATUS      current
   DESCRIPTION
      "Path: apsBundle.status.workingEntity.ifStatus

       Possibilities:
               notFound   (0)
               up   (1)
               down   (2)"
   ::= {sr1645v2ApsBWorkingEntityEntry 67108864}

sr1645v2ApsBWorkingEntityMepName OBJECT-TYPE
   SYNTAX      DisplayString
   MAX-ACCESS  read-only
   STATUS      current
   DESCRIPTION
      "Path: apsBundle.status.workingEntity.mepName"
   ::= {sr1645v2ApsBWorkingEntityEntry 33554432}

sr1645v2ApsBWorkingEntityMepDefect OBJECT-TYPE
   SYNTAX      INTEGER
               {
               noManagedMep (0),
               none (1),
               lossOfContinuity (2),
               s (3)
               }
   MAX-ACCESS  read-only
   STATUS      current
   DESCRIPTION
      "Path: apsBundle.status.workingEntity.mepDefect

       Possibilities:
               noManagedMep   (0)
               none   (1)
               lossOfContinuity   (2)
                  (3)"
   ::= {sr1645v2ApsBWorkingEntityEntry 50331648}

sr1645v2ApsBWorkingEntityQualityDegrade OBJECT-TYPE
   SYNTAX      Integer32
   MAX-ACCESS  read-only
   STATUS      current
   DESCRIPTION
      "Path: apsBundle.status.workingEntity.qualityDegrade

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {sr1645v2ApsBWorkingEntityEntry 83886080}


sr1645v2ApsBProtectionEntity OBJECT IDENTIFIER ::= {sr1645v2ApsB 154}

sr1645v2ApsBProtectionEntitySSCTable OBJECT-TYPE
   SYNTAX      SEQUENCE OF Sr1645v2ApsBProtectionEntityEntry
   MAX-ACCESS  not-accessible
   STATUS      current
   DESCRIPTION
      "APS protection entity info"
   ::= {sr1645v2ApsBProtectionEntity 1}

sr1645v2ApsBProtectionEntityEntry OBJECT-TYPE
   SYNTAX      Sr1645v2ApsBProtectionEntityEntry
   MAX-ACCESS  not-accessible
   STATUS      current
   DESCRIPTION
      ""
   INDEX      { sr1645v2ApsBProtectionEntityGlobalIx }
   ::= {sr1645v2ApsBProtectionEntitySSCTable 1}

Sr1645v2ApsBProtectionEntityEntry ::=
   SEQUENCE
      {
      sr1645v2ApsBProtectionEntityGlobalIx
         GlobalIndex,
      sr1645v2ApsBProtectionEntityIf
         DisplayString,
      sr1645v2ApsBProtectionEntityIfStatus
         INTEGER,
      sr1645v2ApsBProtectionEntityMepName
         DisplayString,
      sr1645v2ApsBProtectionEntityMepDefect
         INTEGER,
      sr1645v2ApsBProtectionEntityQualityDegrade
         Integer32
      }

sr1645v2ApsBProtectionEntityGlobalIx OBJECT-TYPE
   SYNTAX      GlobalIndex
   MAX-ACCESS  not-accessible
   STATUS      current
   DESCRIPTION
      "The value of the tlsCntTreeGlobalIndex of the MANAGED OBJECT."
   ::= {sr1645v2ApsBProtectionEntityEntry 10}

sr1645v2ApsBProtectionEntityIf OBJECT-TYPE
   SYNTAX      DisplayString
   MAX-ACCESS  read-only
   STATUS      current
   DESCRIPTION
      "Path: apsBundle.status.protectionEntity.interface"
   ::= {sr1645v2ApsBProtectionEntityEntry 16777216}

sr1645v2ApsBProtectionEntityIfStatus OBJECT-TYPE
   SYNTAX      INTEGER
               {
               notFound (0),
               up (1),
               down (2)
               }
   MAX-ACCESS  read-only
   STATUS      current
   DESCRIPTION
      "Path: apsBundle.status.protectionEntity.ifStatus

       Possibilities:
               notFound   (0)
               up   (1)
               down   (2)"
   ::= {sr1645v2ApsBProtectionEntityEntry 67108864}

sr1645v2ApsBProtectionEntityMepName OBJECT-TYPE
   SYNTAX      DisplayString
   MAX-ACCESS  read-only
   STATUS      current
   DESCRIPTION
      "Path: apsBundle.status.protectionEntity.mepName"
   ::= {sr1645v2ApsBProtectionEntityEntry 33554432}

sr1645v2ApsBProtectionEntityMepDefect OBJECT-TYPE
   SYNTAX      INTEGER
               {
               noManagedMep (0),
               none (1),
               lossOfContinuity (2),
               s (3)
               }
   MAX-ACCESS  read-only
   STATUS      current
   DESCRIPTION
      "Path: apsBundle.status.protectionEntity.mepDefect

       Possibilities:
               noManagedMep   (0)
               none   (1)
               lossOfContinuity   (2)
                  (3)"
   ::= {sr1645v2ApsBProtectionEntityEntry 50331648}

sr1645v2ApsBProtectionEntityQualityDegrade OBJECT-TYPE
   SYNTAX      Integer32
   MAX-ACCESS  read-only
   STATUS      current
   DESCRIPTION
      "Path: apsBundle.status.protectionEntity.qualityDegrade

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {sr1645v2ApsBProtectionEntityEntry 83886080}


sr1645v2ApsBMismatches OBJECT IDENTIFIER ::= {sr1645v2ApsB 159}

sr1645v2ApsBMismatchesSSCTable OBJECT-TYPE
   SYNTAX      SEQUENCE OF Sr1645v2ApsBMismatchesEntry
   MAX-ACCESS  not-accessible
   STATUS      current
   DESCRIPTION
      "APS mismatches"
   ::= {sr1645v2ApsBMismatches 1}

sr1645v2ApsBMismatchesEntry OBJECT-TYPE
   SYNTAX      Sr1645v2ApsBMismatchesEntry
   MAX-ACCESS  not-accessible
   STATUS      current
   DESCRIPTION
      ""
   INDEX      { sr1645v2ApsBMismatchesGlobalIx }
   ::= {sr1645v2ApsBMismatchesSSCTable 1}

Sr1645v2ApsBMismatchesEntry ::=
   SEQUENCE
      {
      sr1645v2ApsBMismatchesGlobalIx
         GlobalIndex,
      sr1645v2ApsBMismatchesApsCommunication
         INTEGER,
      sr1645v2ApsBMismatchesBridgeType
         INTEGER,
      sr1645v2ApsBMismatchesDirection
         INTEGER,
      sr1645v2ApsBMismatchesRevertive
         INTEGER,
      sr1645v2ApsBMismatchesFwdBridgeSelector
         INTEGER,
      sr1645v2ApsBMismatchesBwdBridgeSelector
         INTEGER
      }

sr1645v2ApsBMismatchesGlobalIx OBJECT-TYPE
   SYNTAX      GlobalIndex
   MAX-ACCESS  not-accessible
   STATUS      current
   DESCRIPTION
      "The value of the tlsCntTreeGlobalIndex of the MANAGED OBJECT."
   ::= {sr1645v2ApsBMismatchesEntry 10}

sr1645v2ApsBMismatchesApsCommunication OBJECT-TYPE
   SYNTAX      INTEGER
               {
               no (0),
               yes (1)
               }
   MAX-ACCESS  read-only
   STATUS      current
   DESCRIPTION
      "Path: apsBundle.status.mismatches.apsCommunication

       Possibilities:
               no   (0)
               yes   (1)"
   ::= {sr1645v2ApsBMismatchesEntry 16777216}

sr1645v2ApsBMismatchesBridgeType OBJECT-TYPE
   SYNTAX      INTEGER
               {
               no (0),
               yes (1)
               }
   MAX-ACCESS  read-only
   STATUS      current
   DESCRIPTION
      "Path: apsBundle.status.mismatches.bridgeType

       Possibilities:
               no   (0)
               yes   (1)"
   ::= {sr1645v2ApsBMismatchesEntry 33554432}

sr1645v2ApsBMismatchesDirection OBJECT-TYPE
   SYNTAX      INTEGER
               {
               no (0),
               yes (1)
               }
   MAX-ACCESS  read-only
   STATUS      current
   DESCRIPTION
      "Path: apsBundle.status.mismatches.direction

       Possibilities:
               no   (0)
               yes   (1)"
   ::= {sr1645v2ApsBMismatchesEntry 50331648}

sr1645v2ApsBMismatchesRevertive OBJECT-TYPE
   SYNTAX      INTEGER
               {
               no (0),
               yes (1)
               }
   MAX-ACCESS  read-only
   STATUS      current
   DESCRIPTION
      "Path: apsBundle.status.mismatches.revertive

       Possibilities:
               no   (0)
               yes   (1)"
   ::= {sr1645v2ApsBMismatchesEntry 67108864}

sr1645v2ApsBMismatchesFwdBridgeSelector OBJECT-TYPE
   SYNTAX      INTEGER
               {
               no (0),
               yes (1)
               }
   MAX-ACCESS  read-only
   STATUS      current
   DESCRIPTION
      "Path: apsBundle.status.mismatches.fwdBridgeSelector

       Possibilities:
               no   (0)
               yes   (1)"
   ::= {sr1645v2ApsBMismatchesEntry 83886080}

sr1645v2ApsBMismatchesBwdBridgeSelector OBJECT-TYPE
   SYNTAX      INTEGER
               {
               no (0),
               yes (1)
               }
   MAX-ACCESS  read-only
   STATUS      current
   DESCRIPTION
      "Path: apsBundle.status.mismatches.bwdBridgeSelector

       Possibilities:
               no   (0)
               yes   (1)"
   ::= {sr1645v2ApsBMismatchesEntry 100663296}


sr1645v2ApsBMacAddress OBJECT IDENTIFIER ::= {sr1645v2ApsB 105}

sr1645v2ApsBMacAddressTable OBJECT-TYPE
   SYNTAX      SEQUENCE OF Sr1645v2ApsBMacAddressEntry
   MAX-ACCESS  not-accessible
   STATUS      current
   DESCRIPTION
      "ifPhysAddress"
   ::= {sr1645v2ApsBMacAddress 1}

sr1645v2ApsBMacAddressEntry OBJECT-TYPE
   SYNTAX      Sr1645v2ApsBMacAddressEntry
   MAX-ACCESS  not-accessible
   STATUS      current
   DESCRIPTION
      ""
   INDEX      { sr1645v2ApsBMacAddressGlobalIx }
   ::= {sr1645v2ApsBMacAddressTable 1}

Sr1645v2ApsBMacAddressEntry ::=
   SEQUENCE
      {
      sr1645v2ApsBMacAddressGlobalIx
         GlobalIndex,
      sr1645v2ApsBMacAddressValue
         OCTET STRING
      }

sr1645v2ApsBMacAddressGlobalIx OBJECT-TYPE
   SYNTAX      GlobalIndex
   MAX-ACCESS  not-accessible
   STATUS      current
   DESCRIPTION
      "The value of the tlsCntTreeGlobalIndex of the MANAGED OBJECT."
   ::= {sr1645v2ApsBMacAddressEntry 10}

sr1645v2ApsBMacAddressValue OBJECT-TYPE
   SYNTAX      OCTET STRING
   MAX-ACCESS  read-only
   STATUS      current
   DESCRIPTION
      "Path: apsBundle.status.macAddress

       MAC address."
   ::= {sr1645v2ApsBMacAddressEntry 2147483648}



er1645v2ApsB OBJECT IDENTIFIER ::= {r1645v2ApsB 11}


er1645v2ApsBRemark OBJECT IDENTIFIER ::= {er1645v2ApsB 321}

er1645v2ApsBRemarkTable OBJECT-TYPE
   SYNTAX      SEQUENCE OF Er1645v2ApsBRemarkEntry
   MAX-ACCESS  not-accessible
   STATUS      current
   DESCRIPTION
      "intfRemark"
   ::= {er1645v2ApsBRemark 1}

er1645v2ApsBRemarkEntry OBJECT-TYPE
   SYNTAX      Er1645v2ApsBRemarkEntry
   MAX-ACCESS  not-accessible
   STATUS      current
   DESCRIPTION
      ""
   INDEX      { er1645v2ApsBRemarkGlobalIx }
   ::= {er1645v2ApsBRemarkTable 1}

Er1645v2ApsBRemarkEntry ::=
   SEQUENCE
      {
      er1645v2ApsBRemarkGlobalIx
         GlobalIndex,
      er1645v2ApsBRemarkValue
         DisplayString
      }

er1645v2ApsBRemarkGlobalIx OBJECT-TYPE
   SYNTAX      GlobalIndex
   MAX-ACCESS  not-accessible
   STATUS      current
   DESCRIPTION
      "The value of the tlsCntTreeGlobalIndex of the MANAGED OBJECT."
   ::= {er1645v2ApsBRemarkEntry 10}

er1645v2ApsBRemarkValue OBJECT-TYPE
   SYNTAX      DisplayString
   MAX-ACCESS  read-write
   STATUS      current
   DESCRIPTION
      "Path: apsBundle.editConf.remark"
   ::= {er1645v2ApsBRemarkEntry 2147483648}


er1645v2ApsBAdminStatus OBJECT IDENTIFIER ::= {er1645v2ApsB 106}

er1645v2ApsBAdminStatusTable OBJECT-TYPE
   SYNTAX      SEQUENCE OF Er1645v2ApsBAdminStatusEntry
   MAX-ACCESS  not-accessible
   STATUS      current
   DESCRIPTION
      "ifAdminStatus"
   ::= {er1645v2ApsBAdminStatus 1}

er1645v2ApsBAdminStatusEntry OBJECT-TYPE
   SYNTAX      Er1645v2ApsBAdminStatusEntry
   MAX-ACCESS  not-accessible
   STATUS      current
   DESCRIPTION
      ""
   INDEX      { er1645v2ApsBAdminStatusGlobalIx }
   ::= {er1645v2ApsBAdminStatusTable 1}

Er1645v2ApsBAdminStatusEntry ::=
   SEQUENCE
      {
      er1645v2ApsBAdminStatusGlobalIx
         GlobalIndex,
      er1645v2ApsBAdminStatusValue
         INTEGER
      }

er1645v2ApsBAdminStatusGlobalIx OBJECT-TYPE
   SYNTAX      GlobalIndex
   MAX-ACCESS  not-accessible
   STATUS      current
   DESCRIPTION
      "The value of the tlsCntTreeGlobalIndex of the MANAGED OBJECT."
   ::= {er1645v2ApsBAdminStatusEntry 10}

er1645v2ApsBAdminStatusValue OBJECT-TYPE
   SYNTAX      INTEGER
               {
               up (1),
               down (2)
               }
   MAX-ACCESS  read-write
   STATUS      current
   DESCRIPTION
      "Path: apsBundle.editConf.adminStatus

       Possibilities:
               up   (1)
               down   (2)"
   ::= {er1645v2ApsBAdminStatusEntry 2147483648}


er1645v2ApsBAlarmMask OBJECT IDENTIFIER ::= {er1645v2ApsB 135}

er1645v2ApsBAlarmMaskTable OBJECT-TYPE
   SYNTAX      SEQUENCE OF Er1645v2ApsBAlarmMaskEntry
   MAX-ACCESS  not-accessible
   STATUS      current
   DESCRIPTION
      "ifAlarmMask"
   ::= {er1645v2ApsBAlarmMask 1}

er1645v2ApsBAlarmMaskEntry OBJECT-TYPE
   SYNTAX      Er1645v2ApsBAlarmMaskEntry
   MAX-ACCESS  not-accessible
   STATUS      current
   DESCRIPTION
      ""
   INDEX      { er1645v2ApsBAlarmMaskGlobalIx }
   ::= {er1645v2ApsBAlarmMaskTable 1}

Er1645v2ApsBAlarmMaskEntry ::=
   SEQUENCE
      {
      er1645v2ApsBAlarmMaskGlobalIx
         GlobalIndex,
      er1645v2ApsBAlarmMaskValue
         Integer32
      }

er1645v2ApsBAlarmMaskGlobalIx OBJECT-TYPE
   SYNTAX      GlobalIndex
   MAX-ACCESS  not-accessible
   STATUS      current
   DESCRIPTION
      "The value of the tlsCntTreeGlobalIndex of the MANAGED OBJECT."
   ::= {er1645v2ApsBAlarmMaskEntry 10}

er1645v2ApsBAlarmMaskValue OBJECT-TYPE
   SYNTAX      Integer32
   MAX-ACCESS  read-write
   STATUS      current
   DESCRIPTION
      "Path: apsBundle.editConf.alarmMask

       Bit meanings:
               bit 0 = linkDown"
   ::= {er1645v2ApsBAlarmMaskEntry 2147483648}


er1645v2ApsBAlarmLev OBJECT IDENTIFIER ::= {er1645v2ApsB 170}

er1645v2ApsBAlarmLevSSCTable OBJECT-TYPE
   SYNTAX      SEQUENCE OF Er1645v2ApsBAlarmLevEntry
   MAX-ACCESS  not-accessible
   STATUS      current
   DESCRIPTION
      "IfAlarmLevels"
   ::= {er1645v2ApsBAlarmLev 1}

er1645v2ApsBAlarmLevEntry OBJECT-TYPE
   SYNTAX      Er1645v2ApsBAlarmLevEntry
   MAX-ACCESS  not-accessible
   STATUS      current
   DESCRIPTION
      ""
   INDEX      { er1645v2ApsBAlarmLevGlobalIx }
   ::= {er1645v2ApsBAlarmLevSSCTable 1}

Er1645v2ApsBAlarmLevEntry ::=
   SEQUENCE
      {
      er1645v2ApsBAlarmLevGlobalIx
         GlobalIndex,
      er1645v2ApsBAlarmLevLinkDown
         Integer32
      }

er1645v2ApsBAlarmLevGlobalIx OBJECT-TYPE
   SYNTAX      GlobalIndex
   MAX-ACCESS  not-accessible
   STATUS      current
   DESCRIPTION
      "The value of the tlsCntTreeGlobalIndex of the MANAGED OBJECT."
   ::= {er1645v2ApsBAlarmLevEntry 10}

er1645v2ApsBAlarmLevLinkDown OBJECT-TYPE
   SYNTAX      Integer32
   MAX-ACCESS  read-write
   STATUS      current
   DESCRIPTION
      "Path: apsBundle.editConf.alarmLevel.linkDown"
   ::= {er1645v2ApsBAlarmLevEntry 16777216}


er1645v2ApsBBw OBJECT IDENTIFIER ::= {er1645v2ApsB 5}

er1645v2ApsBBwSSCTable OBJECT-TYPE
   SYNTAX      SEQUENCE OF Er1645v2ApsBBwEntry
   MAX-ACCESS  not-accessible
   STATUS      current
   DESCRIPTION
      ""
   ::= {er1645v2ApsBBw 1}

er1645v2ApsBBwEntry OBJECT-TYPE
   SYNTAX      Er1645v2ApsBBwEntry
   MAX-ACCESS  not-accessible
   STATUS      current
   DESCRIPTION
      ""
   INDEX      { er1645v2ApsBBwGlobalIx }
   ::= {er1645v2ApsBBwSSCTable 1}

Er1645v2ApsBBwEntry ::=
   SEQUENCE
      {
      er1645v2ApsBBwGlobalIx
         GlobalIndex,
      er1645v2ApsBBwMode
         INTEGER,
      er1645v2ApsBBwCir
         Integer32,
      er1645v2ApsBBwEir
         Integer32,
      er1645v2ApsBBwUnit
         INTEGER,
      er1645v2ApsBBwTc
         INTEGER,
      er1645v2ApsBBwTcFactor
         INTEGER,
      er1645v2ApsBBwCorrType
         INTEGER,
      er1645v2ApsBBwCorrPredefEncapsFrameRelay
         DisplayString,
      er1645v2ApsBBwCorrPredefEncapsPpp
         DisplayString,
      er1645v2ApsBBwCorrPredefEncapsAtmHl
         INTEGER,
      er1645v2ApsBBwCorrPredefEncapsAtmMp
         INTEGER,
      er1645v2ApsBBwCorrPredefEncapsHdlc
         DisplayString,
      er1645v2ApsBBwCorrPredefEncapsEfmFs
         Integer32,
      er1645v2ApsBBwCorrPredefEncapsEfmIb
         Integer32,
      er1645v2ApsBBwCorrPredefMode
         INTEGER,
      er1645v2ApsBBwCorrManualOverhead
         Integer32,
      er1645v2ApsBBwCorrManualFrameData
         Counter32,
      er1645v2ApsBBwCorrManualFrameHeader
         Counter32,
      er1645v2ApsBBwMaxFifoQLen
         Integer32,
      er1645v2ApsBBwDeFlagCir
         INTEGER,
      er1645v2ApsBBwDeFlagEir
         INTEGER,
      er1645v2ApsBBwDeFlagViolate
         INTEGER,
      er1645v2ApsBBwActCirActNone
         OCTET STRING,
      er1645v2ApsBBwActCirActEthCos1
         INTEGER,
      er1645v2ApsBBwActCirActEthDei1
         INTEGER,
      er1645v2ApsBBwActCirActEthCos2
         INTEGER,
      er1645v2ApsBBwActCirActEthDei2
         INTEGER,
      er1645v2ApsBBwActCirActEthCos3
         INTEGER,
      er1645v2ApsBBwActCirActEthDei3
         INTEGER,
      er1645v2ApsBBwActCirActEthCos4
         INTEGER,
      er1645v2ApsBBwActCirActEthDei4
         INTEGER,
      er1645v2ApsBBwActCirActEthCos5
         INTEGER,
      er1645v2ApsBBwActCirActEthDei5
         INTEGER,
      er1645v2ApsBBwActCirActEthCos6
         INTEGER,
      er1645v2ApsBBwActCirActEthDei6
         INTEGER,
      er1645v2ApsBBwActCirActEthCos7
         INTEGER,
      er1645v2ApsBBwActCirActEthDei7
         INTEGER,
      er1645v2ApsBBwActCirActEthCos8
         INTEGER,
      er1645v2ApsBBwActCirActEthDei8
         INTEGER,
      er1645v2ApsBBwActCirActEthTos
         INTEGER,
      er1645v2ApsBBwActCirActEthQueue
         INTEGER,
      er1645v2ApsBBwActCirActEthDrpLev
         INTEGER,
      er1645v2ApsBBwActCirActEthDeFlag
         INTEGER,
      er1645v2ApsBBwActCirActIpTos
         INTEGER,
      er1645v2ApsBBwActCirActIpQueue
         INTEGER,
      er1645v2ApsBBwActCirActIpDrpLev
         INTEGER,
      er1645v2ApsBBwActCirActIpDeFlag
         INTEGER,
      er1645v2ApsBBwActEirActNone
         OCTET STRING,
      er1645v2ApsBBwActEirActEthCos1
         INTEGER,
      er1645v2ApsBBwActEirActEthDei1
         INTEGER,
      er1645v2ApsBBwActEirActEthCos2
         INTEGER,
      er1645v2ApsBBwActEirActEthDei2
         INTEGER,
      er1645v2ApsBBwActEirActEthCos3
         INTEGER,
      er1645v2ApsBBwActEirActEthDei3
         INTEGER,
      er1645v2ApsBBwActEirActEthCos4
         INTEGER,
      er1645v2ApsBBwActEirActEthDei4
         INTEGER,
      er1645v2ApsBBwActEirActEthCos5
         INTEGER,
      er1645v2ApsBBwActEirActEthDei5
         INTEGER,
      er1645v2ApsBBwActEirActEthCos6
         INTEGER,
      er1645v2ApsBBwActEirActEthDei6
         INTEGER,
      er1645v2ApsBBwActEirActEthCos7
         INTEGER,
      er1645v2ApsBBwActEirActEthDei7
         INTEGER,
      er1645v2ApsBBwActEirActEthCos8
         INTEGER,
      er1645v2ApsBBwActEirActEthDei8
         INTEGER,
      er1645v2ApsBBwActEirActEthTos
         INTEGER,
      er1645v2ApsBBwActEirActEthQueue
         INTEGER,
      er1645v2ApsBBwActEirActEthDrpLev
         INTEGER,
      er1645v2ApsBBwActEirActEthDeFlag
         INTEGER,
      er1645v2ApsBBwActEirActIpTos
         INTEGER,
      er1645v2ApsBBwActEirActIpQueue
         INTEGER,
      er1645v2ApsBBwActEirActIpDrpLev
         INTEGER,
      er1645v2ApsBBwActEirActIpDeFlag
         INTEGER,
      er1645v2ApsBBwActViolActNone
         OCTET STRING,
      er1645v2ApsBBwActViolActDrop
         OCTET STRING,
      er1645v2ApsBBwActViolActEthCos1
         INTEGER,
      er1645v2ApsBBwActViolActEthDei1
         INTEGER,
      er1645v2ApsBBwActViolActEthCos2
         INTEGER,
      er1645v2ApsBBwActViolActEthDei2
         INTEGER,
      er1645v2ApsBBwActViolActEthCos3
         INTEGER,
      er1645v2ApsBBwActViolActEthDei3
         INTEGER,
      er1645v2ApsBBwActViolActEthCos4
         INTEGER,
      er1645v2ApsBBwActViolActEthDei4
         INTEGER,
      er1645v2ApsBBwActViolActEthCos5
         INTEGER,
      er1645v2ApsBBwActViolActEthDei5
         INTEGER,
      er1645v2ApsBBwActViolActEthCos6
         INTEGER,
      er1645v2ApsBBwActViolActEthDei6
         INTEGER,
      er1645v2ApsBBwActViolActEthCos7
         INTEGER,
      er1645v2ApsBBwActViolActEthDei7
         INTEGER,
      er1645v2ApsBBwActViolActEthCos8
         INTEGER,
      er1645v2ApsBBwActViolActEthDei8
         INTEGER,
      er1645v2ApsBBwActViolActEthTos
         INTEGER,
      er1645v2ApsBBwActViolActEthQueue
         INTEGER,
      er1645v2ApsBBwActViolActEthDrpLev
         INTEGER,
      er1645v2ApsBBwActViolActEthDeFlag
         INTEGER,
      er1645v2ApsBBwActViolActIpTos
         INTEGER,
      er1645v2ApsBBwActViolActIpQueue
         INTEGER,
      er1645v2ApsBBwActViolActIpDrpLev
         INTEGER,
      er1645v2ApsBBwActViolActIpDeFlag
         INTEGER
      }

er1645v2ApsBBwGlobalIx OBJECT-TYPE
   SYNTAX      GlobalIndex
   MAX-ACCESS  not-accessible
   STATUS      current
   DESCRIPTION
      "The value of the tlsCntTreeGlobalIndex of the MANAGED OBJECT."
   ::= {er1645v2ApsBBwEntry 10}

er1645v2ApsBBwMode OBJECT-TYPE
   SYNTAX      INTEGER
               {
               reshaping (1),
               policing (2),
               policingReshape (3)
               }
   MAX-ACCESS  read-write
   STATUS      current
   DESCRIPTION
      "Path: apsBundle.editConf.bandwidth.mode

       Possibilities:
               reshaping   (1)
               policing   (2)
               policingReshape   (3)"
   ::= {er1645v2ApsBBwEntry 3758096384}

er1645v2ApsBBwCir OBJECT-TYPE
   SYNTAX      Integer32
   MAX-ACCESS  read-write
   STATUS      current
   DESCRIPTION
      "Path: apsBundle.editConf.bandwidth.cir"
   ::= {er1645v2ApsBBwEntry 268435456}

er1645v2ApsBBwEir OBJECT-TYPE
   SYNTAX      Integer32
   MAX-ACCESS  read-write
   STATUS      current
   DESCRIPTION
      "Path: apsBundle.editConf.bandwidth.eir"
   ::= {er1645v2ApsBBwEntry 1879048192}

er1645v2ApsBBwUnit OBJECT-TYPE
   SYNTAX      INTEGER
               {
               bitssec (1),
               percent (2)
               }
   MAX-ACCESS  read-write
   STATUS      current
   DESCRIPTION
      "Path: apsBundle.editConf.bandwidth.unit

       Possibilities:
               bits/sec   (1)
               percent   (2)"
   ::= {er1645v2ApsBBwEntry 1342177280}

er1645v2ApsBBwTc OBJECT-TYPE
   SYNTAX      INTEGER
               {
               auto (0)
               }
   MAX-ACCESS  read-write
   STATUS      current
   DESCRIPTION
      "Path: apsBundle.editConf.bandwidth.tc

       Possibilities:
               auto   (0)"
   ::= {er1645v2ApsBBwEntry 1610612736}

er1645v2ApsBBwTcFactor OBJECT-TYPE
   SYNTAX      INTEGER
               {
               ms (10),
               s100us (1)
               }
   MAX-ACCESS  read-write
   STATUS      current
   DESCRIPTION
      "Path: apsBundle.editConf.bandwidth.tcFactor

       Possibilities:
               ms   (10)
               *100us   (1)"
   ::= {er1645v2ApsBBwEntry 2147483648}

er1645v2ApsBBwCorrType OBJECT-TYPE
   SYNTAX      INTEGER
               {
               noCorrection (0),
               predefined (1),
               manual (2)
               }
   MAX-ACCESS  read-write
   STATUS      current
   DESCRIPTION
      "Path: apsBundle.editConf.bandwidth.correction.type

       Possibilities:
               noCorrection   (0)
               predefined   (1)
               manual   (2)"
   ::= {er1645v2ApsBBwEntry 570425344}

er1645v2ApsBBwCorrPredefEncapsFrameRelay OBJECT-TYPE
   SYNTAX      DisplayString
   MAX-ACCESS  read-write
   STATUS      current
   DESCRIPTION
      "Path: apsBundle.editConf.bandwidth.correction.predefined.encapsulation.frameRelay"
   ::= {er1645v2ApsBBwEntry 608436224}

er1645v2ApsBBwCorrPredefEncapsPpp OBJECT-TYPE
   SYNTAX      DisplayString
   MAX-ACCESS  read-write
   STATUS      current
   DESCRIPTION
      "Path: apsBundle.editConf.bandwidth.correction.predefined.encapsulation.ppp"
   ::= {er1645v2ApsBBwEntry 608698368}

er1645v2ApsBBwCorrPredefEncapsAtmHl OBJECT-TYPE
   SYNTAX      INTEGER
               {
               rfc2684 (0),
               ppp (1),
               pppOverEthernet (2)
               }
   MAX-ACCESS  read-write
   STATUS      current
   DESCRIPTION
      "Path: apsBundle.editConf.bandwidth.correction.predefined.encapsulation.atm.higherLayer

       Possibilities:
               rfc2684   (0)
               ppp   (1)
               pppOverEthernet   (2)"
   ::= {er1645v2ApsBBwEntry 608993280}

er1645v2ApsBBwCorrPredefEncapsAtmMp OBJECT-TYPE
   SYNTAX      INTEGER
               {
               llcEncapsulation (0),
               vcMultiplexing (1)
               }
   MAX-ACCESS  read-write
   STATUS      current
   DESCRIPTION
      "Path: apsBundle.editConf.bandwidth.correction.predefined.encapsulation.atm.multiProtocol

       Possibilities:
               llcEncapsulation   (0)
               vcMultiplexing   (1)"
   ::= {er1645v2ApsBBwEntry 609026048}

er1645v2ApsBBwCorrPredefEncapsHdlc OBJECT-TYPE
   SYNTAX      DisplayString
   MAX-ACCESS  read-write
   STATUS      current
   DESCRIPTION
      "Path: apsBundle.editConf.bandwidth.correction.predefined.encapsulation.hdlc"
   ::= {er1645v2ApsBBwEntry 609222656}

er1645v2ApsBBwCorrPredefEncapsEfmFs OBJECT-TYPE
   SYNTAX      Integer32
   MAX-ACCESS  read-write
   STATUS      current
   DESCRIPTION
      "Path: apsBundle.editConf.bandwidth.correction.predefined.encapsulation.efm.fragmentSize"
   ::= {er1645v2ApsBBwEntry 609517568}

er1645v2ApsBBwCorrPredefEncapsEfmIb OBJECT-TYPE
   SYNTAX      Integer32
   MAX-ACCESS  read-write
   STATUS      current
   DESCRIPTION
      "Path: apsBundle.editConf.bandwidth.correction.predefined.encapsulation.efm.idleBytes"
   ::= {er1645v2ApsBBwEntry 609550336}

er1645v2ApsBBwCorrPredefMode OBJECT-TYPE
   SYNTAX      INTEGER
               {
               routing (0),
               bridging (1)
               }
   MAX-ACCESS  read-write
   STATUS      current
   DESCRIPTION
      "Path: apsBundle.editConf.bandwidth.correction.predefined.mode

       Possibilities:
               routing   (0)
               bridging   (1)"
   ::= {er1645v2ApsBBwEntry 612368384}

er1645v2ApsBBwCorrManualOverhead OBJECT-TYPE
   SYNTAX      Integer32
   MAX-ACCESS  read-write
   STATUS      current
   DESCRIPTION
      "Path: apsBundle.editConf.bandwidth.correction.manual.overhead"
   ::= {er1645v2ApsBBwEntry 637665280}

er1645v2ApsBBwCorrManualFrameData OBJECT-TYPE
   SYNTAX      Counter32
   MAX-ACCESS  read-write
   STATUS      current
   DESCRIPTION
      "Path: apsBundle.editConf.bandwidth.correction.manual.frameData

       32 bit unsigned wrappable counter."
   ::= {er1645v2ApsBBwEntry 637796352}

er1645v2ApsBBwCorrManualFrameHeader OBJECT-TYPE
   SYNTAX      Counter32
   MAX-ACCESS  read-write
   STATUS      current
   DESCRIPTION
      "Path: apsBundle.editConf.bandwidth.correction.manual.frameHeader

       32 bit unsigned wrappable counter."
   ::= {er1645v2ApsBBwEntry 637927424}

er1645v2ApsBBwMaxFifoQLen OBJECT-TYPE
   SYNTAX      Integer32
   MAX-ACCESS  read-write
   STATUS      current
   DESCRIPTION
      "Path: apsBundle.editConf.bandwidth.maxFifoQLen"
   ::= {er1645v2ApsBBwEntry 805306368}

er1645v2ApsBBwDeFlagCir OBJECT-TYPE
   SYNTAX      INTEGER
               {
               allowed (1),
               notAllowed (2)
               }
   MAX-ACCESS  read-write
   STATUS      current
   DESCRIPTION
      "Path: apsBundle.editConf.bandwidth.deFlag.cir

       Possibilities:
               allowed   (1)
               notAllowed   (2)"
   ::= {er1645v2ApsBBwEntry 3490709504}

er1645v2ApsBBwDeFlagEir OBJECT-TYPE
   SYNTAX      INTEGER
               {
               allowed (1),
               notAllowed (2)
               }
   MAX-ACCESS  read-write
   STATUS      current
   DESCRIPTION
      "Path: apsBundle.editConf.bandwidth.deFlag.eir

       Possibilities:
               allowed   (1)
               notAllowed   (2)"
   ::= {er1645v2ApsBBwEntry 3491758080}

er1645v2ApsBBwDeFlagViolate OBJECT-TYPE
   SYNTAX      INTEGER
               {
               allowed (1),
               notAllowed (2)
               }
   MAX-ACCESS  read-write
   STATUS      current
   DESCRIPTION
      "Path: apsBundle.editConf.bandwidth.deFlag.violate

       Possibilities:
               allowed   (1)
               notAllowed   (2)"
   ::= {er1645v2ApsBBwEntry 3492806656}

er1645v2ApsBBwActCirActNone OBJECT-TYPE
   SYNTAX      OCTET STRING
   MAX-ACCESS  read-write
   STATUS      current
   DESCRIPTION
      "Path: apsBundle.editConf.bandwidth.action.cirAction.none"
   ::= {er1645v2ApsBBwEntry 4062183424}

er1645v2ApsBBwActCirActEthCos1 OBJECT-TYPE
   SYNTAX      INTEGER
               {
               unchanged (256)
               }
   MAX-ACCESS  read-write
   STATUS      current
   DESCRIPTION
      "Path: apsBundle.editConf.bandwidth.action.cirAction.ethernet.cosDepth1

       Possibilities:
               unchanged   (256)"
   ::= {er1645v2ApsBBwEntry 4064346112}

er1645v2ApsBBwActCirActEthDei1 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth1

       Possibilities:
               unchanged   (255)
               clear   (0)
               set   (1)"
   ::= {er1645v2ApsBBwEntry 4065656832}

er1645v2ApsBBwActCirActEthCos2 OBJECT-TYPE
   SYNTAX      INTEGER
               {
               unchanged (256)
               }
   MAX-ACCESS  read-write
   STATUS      current
   DESCRIPTION
      "Path: apsBundle.editConf.bandwidth.action.cirAction.ethernet.cosDepth2

       Possibilities:
               unchanged   (256)"
   ::= {er1645v2ApsBBwEntry 4064411648}

er1645v2ApsBBwActCirActEthDei2 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth2

       Possibilities:
               unchanged   (255)
               clear   (0)
               set   (1)"
   ::= {er1645v2ApsBBwEntry 4065722368}

er1645v2ApsBBwActCirActEthCos3 OBJECT-TYPE
   SYNTAX      INTEGER
               {
               unchanged (256)
               }
   MAX-ACCESS  read-write
   STATUS      current
   DESCRIPTION
      "Path: apsBundle.editConf.bandwidth.action.cirAction.ethernet.cosDepth3

       Possibilities:
               unchanged   (256)"
   ::= {er1645v2ApsBBwEntry 4064477184}

er1645v2ApsBBwActCirActEthDei3 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth3

       Possibilities:
               unchanged   (255)
               clear   (0)
               set   (1)"
   ::= {er1645v2ApsBBwEntry 4065787904}

er1645v2ApsBBwActCirActEthCos4 OBJECT-TYPE
   SYNTAX      INTEGER
               {
               unchanged (256)
               }
   MAX-ACCESS  read-write
   STATUS      current
   DESCRIPTION
      "Path: apsBundle.editConf.bandwidth.action.cirAction.ethernet.cosDepth4

       Possibilities:
               unchanged   (256)"
   ::= {er1645v2ApsBBwEntry 4064542720}

er1645v2ApsBBwActCirActEthDei4 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth4

       Possibilities:
               unchanged   (255)
               clear   (0)
               set   (1)"
   ::= {er1645v2ApsBBwEntry 4065853440}

er1645v2ApsBBwActCirActEthCos5 OBJECT-TYPE
   SYNTAX      INTEGER
               {
               unchanged (256)
               }
   MAX-ACCESS  read-write
   STATUS      current
   DESCRIPTION
      "Path: apsBundle.editConf.bandwidth.action.cirAction.ethernet.cosDepth5

       Possibilities:
               unchanged   (256)"
   ::= {er1645v2ApsBBwEntry 4064608256}

er1645v2ApsBBwActCirActEthDei5 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth5

       Possibilities:
               unchanged   (255)
               clear   (0)
               set   (1)"
   ::= {er1645v2ApsBBwEntry 4065918976}

er1645v2ApsBBwActCirActEthCos6 OBJECT-TYPE
   SYNTAX      INTEGER
               {
               unchanged (256)
               }
   MAX-ACCESS  read-write
   STATUS      current
   DESCRIPTION
      "Path: apsBundle.editConf.bandwidth.action.cirAction.ethernet.cosDepth6

       Possibilities:
               unchanged   (256)"
   ::= {er1645v2ApsBBwEntry 4064673792}

er1645v2ApsBBwActCirActEthDei6 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth6

       Possibilities:
               unchanged   (255)
               clear   (0)
               set   (1)"
   ::= {er1645v2ApsBBwEntry 4065984512}

er1645v2ApsBBwActCirActEthCos7 OBJECT-TYPE
   SYNTAX      INTEGER
               {
               unchanged (256)
               }
   MAX-ACCESS  read-write
   STATUS      current
   DESCRIPTION
      "Path: apsBundle.editConf.bandwidth.action.cirAction.ethernet.cosDepth7

       Possibilities:
               unchanged   (256)"
   ::= {er1645v2ApsBBwEntry 4064739328}

er1645v2ApsBBwActCirActEthDei7 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth7

       Possibilities:
               unchanged   (255)
               clear   (0)
               set   (1)"
   ::= {er1645v2ApsBBwEntry 4066050048}

er1645v2ApsBBwActCirActEthCos8 OBJECT-TYPE
   SYNTAX      INTEGER
               {
               unchanged (256)
               }
   MAX-ACCESS  read-write
   STATUS      current
   DESCRIPTION
      "Path: apsBundle.editConf.bandwidth.action.cirAction.ethernet.cosDepth8

       Possibilities:
               unchanged   (256)"
   ::= {er1645v2ApsBBwEntry 4064804864}

er1645v2ApsBBwActCirActEthDei8 OBJECT-TYPE
   SYNTAX      INTEGER
               {
               unchanged (255),
               clear (0),
               set (1)
               }
   MAX-ACCESS  read-write
   STATUS      current
   DESCRIPTION
      "Path: apsBundle.editConf.bandwidth.action.cirAction.ethernet.deiDepth8

       Possibilities:
               unchanged   (255)
               clear   (0)
               set   (1)"
   ::= {er1645v2ApsBBwEntry 4066115584}

er1645v2ApsBBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4064870400}

er1645v2ApsBBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4064935936}

er1645v2ApsBBwActCirActEthDrpLev OBJECT-TYPE
   SYNTAX      INTEGER
               {
               unchanged (0)
               }
   MAX-ACCESS  read-write
   STATUS      current
   DESCRIPTION
      "Path: apsBundle.editConf.bandwidth.action.cirAction.ethernet.dropLevel

       Possibilities:
               unchanged   (0)"
   ::= {er1645v2ApsBBwEntry 4065001472}

er1645v2ApsBBwActCirActEthDeFlag OBJECT-TYPE
   SYNTAX      INTEGER
               {
               unchanged (255),
               clear (0),
               set (1)
               }
   MAX-ACCESS  read-write
   STATUS      current
   DESCRIPTION
      "Path: apsBundle.editConf.bandwidth.action.cirAction.ethernet.deFlag

       Possibilities:
               unchanged   (255)
               clear   (0)
               set   (1)"
   ::= {er1645v2ApsBBwEntry 4065198080}

er1645v2ApsBBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4071161856}

er1645v2ApsBBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4071227392}

er1645v2ApsBBwActCirActIpDrpLev OBJECT-TYPE
   SYNTAX      INTEGER
               {
               unchanged (0)
               }
   MAX-ACCESS  read-write
   STATUS      current
   DESCRIPTION
      "Path: apsBundle.editConf.bandwidth.action.cirAction.ip.dropLevel

       Possibilities:
               unchanged   (0)"
   ::= {er1645v2ApsBBwEntry 4071292928}

er1645v2ApsBBwActCirActIpDeFlag OBJECT-TYPE
   SYNTAX      INTEGER
               {
               unchanged (255),
               clear (0),
               set (1)
               }
   MAX-ACCESS  read-write
   STATUS      current
   DESCRIPTION
      "Path: apsBundle.editConf.bandwidth.action.cirAction.ip.deFlag

       Possibilities:
               unchanged   (255)
               clear   (0)
               set   (1)"
   ::= {er1645v2ApsBBwEntry 4071489536}

er1645v2ApsBBwActEirActNone OBJECT-TYPE
   SYNTAX      OCTET STRING
   MAX-ACCESS  read-write
   STATUS      current
   DESCRIPTION
      "Path: apsBundle.editConf.bandwidth.action.eirAction.none"
   ::= {er1645v2ApsBBwEntry 4095737856}

er1645v2ApsBBwActEirActEthCos1 OBJECT-TYPE
   SYNTAX      INTEGER
               {
               unchanged (256)
               }
   MAX-ACCESS  read-write
   STATUS      current
   DESCRIPTION
      "Path: apsBundle.editConf.bandwidth.action.eirAction.ethernet.cosDepth1

       Possibilities:
               unchanged   (256)"
   ::= {er1645v2ApsBBwEntry 4097900544}

er1645v2ApsBBwActEirActEthDei1 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth1

       Possibilities:
               unchanged   (255)
               clear   (0)
               set   (1)"
   ::= {er1645v2ApsBBwEntry 4099211264}

er1645v2ApsBBwActEirActEthCos2 OBJECT-TYPE
   SYNTAX      INTEGER
               {
               unchanged (256)
               }
   MAX-ACCESS  read-write
   STATUS      current
   DESCRIPTION
      "Path: apsBundle.editConf.bandwidth.action.eirAction.ethernet.cosDepth2

       Possibilities:
               unchanged   (256)"
   ::= {er1645v2ApsBBwEntry 4097966080}

er1645v2ApsBBwActEirActEthDei2 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth2

       Possibilities:
               unchanged   (255)
               clear   (0)
               set   (1)"
   ::= {er1645v2ApsBBwEntry 4099276800}

er1645v2ApsBBwActEirActEthCos3 OBJECT-TYPE
   SYNTAX      INTEGER
               {
               unchanged (256)
               }
   MAX-ACCESS  read-write
   STATUS      current
   DESCRIPTION
      "Path: apsBundle.editConf.bandwidth.action.eirAction.ethernet.cosDepth3

       Possibilities:
               unchanged   (256)"
   ::= {er1645v2ApsBBwEntry 4098031616}

er1645v2ApsBBwActEirActEthDei3 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth3

       Possibilities:
               unchanged   (255)
               clear   (0)
               set   (1)"
   ::= {er1645v2ApsBBwEntry 4099342336}

er1645v2ApsBBwActEirActEthCos4 OBJECT-TYPE
   SYNTAX      INTEGER
               {
               unchanged (256)
               }
   MAX-ACCESS  read-write
   STATUS      current
   DESCRIPTION
      "Path: apsBundle.editConf.bandwidth.action.eirAction.ethernet.cosDepth4

       Possibilities:
               unchanged   (256)"
   ::= {er1645v2ApsBBwEntry 4098097152}

er1645v2ApsBBwActEirActEthDei4 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth4

       Possibilities:
               unchanged   (255)
               clear   (0)
               set   (1)"
   ::= {er1645v2ApsBBwEntry 4099407872}

er1645v2ApsBBwActEirActEthCos5 OBJECT-TYPE
   SYNTAX      INTEGER
               {
               unchanged (256)
               }
   MAX-ACCESS  read-write
   STATUS      current
   DESCRIPTION
      "Path: apsBundle.editConf.bandwidth.action.eirAction.ethernet.cosDepth5

       Possibilities:
               unchanged   (256)"
   ::= {er1645v2ApsBBwEntry 4098162688}

er1645v2ApsBBwActEirActEthDei5 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth5

       Possibilities:
               unchanged   (255)
               clear   (0)
               set   (1)"
   ::= {er1645v2ApsBBwEntry 4099473408}

er1645v2ApsBBwActEirActEthCos6 OBJECT-TYPE
   SYNTAX      INTEGER
               {
               unchanged (256)
               }
   MAX-ACCESS  read-write
   STATUS      current
   DESCRIPTION
      "Path: apsBundle.editConf.bandwidth.action.eirAction.ethernet.cosDepth6

       Possibilities:
               unchanged   (256)"
   ::= {er1645v2ApsBBwEntry 4098228224}

er1645v2ApsBBwActEirActEthDei6 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth6

       Possibilities:
               unchanged   (255)
               clear   (0)
               set   (1)"
   ::= {er1645v2ApsBBwEntry 4099538944}

er1645v2ApsBBwActEirActEthCos7 OBJECT-TYPE
   SYNTAX      INTEGER
               {
               unchanged (256)
               }
   MAX-ACCESS  read-write
   STATUS      current
   DESCRIPTION
      "Path: apsBundle.editConf.bandwidth.action.eirAction.ethernet.cosDepth7

       Possibilities:
               unchanged   (256)"
   ::= {er1645v2ApsBBwEntry 4098293760}

er1645v2ApsBBwActEirActEthDei7 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth7

       Possibilities:
               unchanged   (255)
               clear   (0)
               set   (1)"
   ::= {er1645v2ApsBBwEntry 4099604480}

er1645v2ApsBBwActEirActEthCos8 OBJECT-TYPE
   SYNTAX      INTEGER
               {
               unchanged (256)
               }
   MAX-ACCESS  read-write
   STATUS      current
   DESCRIPTION
      "Path: apsBundle.editConf.bandwidth.action.eirAction.ethernet.cosDepth8

       Possibilities:
               unchanged   (256)"
   ::= {er1645v2ApsBBwEntry 4098359296}

er1645v2ApsBBwActEirActEthDei8 OBJECT-TYPE
   SYNTAX      INTEGER
               {
               unchanged (255),
               clear (0),
               set (1)
               }
   MAX-ACCESS  read-write
   STATUS      current
   DESCRIPTION
      "Path: apsBundle.editConf.bandwidth.action.eirAction.ethernet.deiDepth8

       Possibilities:
               unchanged   (255)
               clear   (0)
               set   (1)"
   ::= {er1645v2ApsBBwEntry 4099670016}

er1645v2ApsBBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4098424832}

er1645v2ApsBBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4098490368}

er1645v2ApsBBwActEirActEthDrpLev OBJECT-TYPE
   SYNTAX      INTEGER
               {
               unchanged (0)
               }
   MAX-ACCESS  read-write
   STATUS      current
   DESCRIPTION
      "Path: apsBundle.editConf.bandwidth.action.eirAction.ethernet.dropLevel

       Possibilities:
               unchanged   (0)"
   ::= {er1645v2ApsBBwEntry 4098555904}

er1645v2ApsBBwActEirActEthDeFlag OBJECT-TYPE
   SYNTAX      INTEGER
               {
               unchanged (255),
               clear (0),
               set (1)
               }
   MAX-ACCESS  read-write
   STATUS      current
   DESCRIPTION
      "Path: apsBundle.editConf.bandwidth.action.eirAction.ethernet.deFlag

       Possibilities:
               unchanged   (255)
               clear   (0)
               set   (1)"
   ::= {er1645v2ApsBBwEntry 4098752512}

er1645v2ApsBBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4104716288}

er1645v2ApsBBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4104781824}

er1645v2ApsBBwActEirActIpDrpLev OBJECT-TYPE
   SYNTAX      INTEGER
               {
               unchanged (0)
               }
   MAX-ACCESS  read-write
   STATUS      current
   DESCRIPTION
      "Path: apsBundle.editConf.bandwidth.action.eirAction.ip.dropLevel

       Possibilities:
               unchanged   (0)"
   ::= {er1645v2ApsBBwEntry 4104847360}

er1645v2ApsBBwActEirActIpDeFlag OBJECT-TYPE
   SYNTAX      INTEGER
               {
               unchanged (255),
               clear (0),
               set (1)
               }
   MAX-ACCESS  read-write
   STATUS      current
   DESCRIPTION
      "Path: apsBundle.editConf.bandwidth.action.eirAction.ip.deFlag

       Possibilities:
               unchanged   (255)
               clear   (0)
               set   (1)"
   ::= {er1645v2ApsBBwEntry 4105043968}

er1645v2ApsBBwActViolActNone OBJECT-TYPE
   SYNTAX      OCTET STRING
   MAX-ACCESS  read-write
   STATUS      current
   DESCRIPTION
      "Path: apsBundle.editConf.bandwidth.action.violateAction.none"
   ::= {er1645v2ApsBBwEntry 4129292288}

er1645v2ApsBBwActViolActDrop OBJECT-TYPE
   SYNTAX      OCTET STRING
   MAX-ACCESS  read-write
   STATUS      current
   DESCRIPTION
      "Path: apsBundle.editConf.bandwidth.action.violateAction.drop"
   ::= {er1645v2ApsBBwEntry 4133486592}

er1645v2ApsBBwActViolActEthCos1 OBJECT-TYPE
   SYNTAX      INTEGER
               {
               unchanged (256)
               }
   MAX-ACCESS  read-write
   STATUS      current
   DESCRIPTION
      "Path: apsBundle.editConf.bandwidth.action.violateAction.ethernet.cosDepth1

       Possibilities:
               unchanged   (256)"
   ::= {er1645v2ApsBBwEntry 4131454976}

er1645v2ApsBBwActViolActEthDei1 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth1

       Possibilities:
               unchanged   (255)
               clear   (0)
               set   (1)"
   ::= {er1645v2ApsBBwEntry 4132765696}

er1645v2ApsBBwActViolActEthCos2 OBJECT-TYPE
   SYNTAX      INTEGER
               {
               unchanged (256)
               }
   MAX-ACCESS  read-write
   STATUS      current
   DESCRIPTION
      "Path: apsBundle.editConf.bandwidth.action.violateAction.ethernet.cosDepth2

       Possibilities:
               unchanged   (256)"
   ::= {er1645v2ApsBBwEntry 4131520512}

er1645v2ApsBBwActViolActEthDei2 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth2

       Possibilities:
               unchanged   (255)
               clear   (0)
               set   (1)"
   ::= {er1645v2ApsBBwEntry 4132831232}

er1645v2ApsBBwActViolActEthCos3 OBJECT-TYPE
   SYNTAX      INTEGER
               {
               unchanged (256)
               }
   MAX-ACCESS  read-write
   STATUS      current
   DESCRIPTION
      "Path: apsBundle.editConf.bandwidth.action.violateAction.ethernet.cosDepth3

       Possibilities:
               unchanged   (256)"
   ::= {er1645v2ApsBBwEntry 4131586048}

er1645v2ApsBBwActViolActEthDei3 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth3

       Possibilities:
               unchanged   (255)
               clear   (0)
               set   (1)"
   ::= {er1645v2ApsBBwEntry 4132896768}

er1645v2ApsBBwActViolActEthCos4 OBJECT-TYPE
   SYNTAX      INTEGER
               {
               unchanged (256)
               }
   MAX-ACCESS  read-write
   STATUS      current
   DESCRIPTION
      "Path: apsBundle.editConf.bandwidth.action.violateAction.ethernet.cosDepth4

       Possibilities:
               unchanged   (256)"
   ::= {er1645v2ApsBBwEntry 4131651584}

er1645v2ApsBBwActViolActEthDei4 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth4

       Possibilities:
               unchanged   (255)
               clear   (0)
               set   (1)"
   ::= {er1645v2ApsBBwEntry 4132962304}

er1645v2ApsBBwActViolActEthCos5 OBJECT-TYPE
   SYNTAX      INTEGER
               {
               unchanged (256)
               }
   MAX-ACCESS  read-write
   STATUS      current
   DESCRIPTION
      "Path: apsBundle.editConf.bandwidth.action.violateAction.ethernet.cosDepth5

       Possibilities:
               unchanged   (256)"
   ::= {er1645v2ApsBBwEntry 4131717120}

er1645v2ApsBBwActViolActEthDei5 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth5

       Possibilities:
               unchanged   (255)
               clear   (0)
               set   (1)"
   ::= {er1645v2ApsBBwEntry 4133027840}

er1645v2ApsBBwActViolActEthCos6 OBJECT-TYPE
   SYNTAX      INTEGER
               {
               unchanged (256)
               }
   MAX-ACCESS  read-write
   STATUS      current
   DESCRIPTION
      "Path: apsBundle.editConf.bandwidth.action.violateAction.ethernet.cosDepth6

       Possibilities:
               unchanged   (256)"
   ::= {er1645v2ApsBBwEntry 4131782656}

er1645v2ApsBBwActViolActEthDei6 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth6

       Possibilities:
               unchanged   (255)
               clear   (0)
               set   (1)"
   ::= {er1645v2ApsBBwEntry 4133093376}

er1645v2ApsBBwActViolActEthCos7 OBJECT-TYPE
   SYNTAX      INTEGER
               {
               unchanged (256)
               }
   MAX-ACCESS  read-write
   STATUS      current
   DESCRIPTION
      "Path: apsBundle.editConf.bandwidth.action.violateAction.ethernet.cosDepth7

       Possibilities:
               unchanged   (256)"
   ::= {er1645v2ApsBBwEntry 4131848192}

er1645v2ApsBBwActViolActEthDei7 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth7

       Possibilities:
               unchanged   (255)
               clear   (0)
               set   (1)"
   ::= {er1645v2ApsBBwEntry 4133158912}

er1645v2ApsBBwActViolActEthCos8 OBJECT-TYPE
   SYNTAX      INTEGER
               {
               unchanged (256)
               }
   MAX-ACCESS  read-write
   STATUS      current
   DESCRIPTION
      "Path: apsBundle.editConf.bandwidth.action.violateAction.ethernet.cosDepth8

       Possibilities:
               unchanged   (256)"
   ::= {er1645v2ApsBBwEntry 4131913728}

er1645v2ApsBBwActViolActEthDei8 OBJECT-TYPE
   SYNTAX      INTEGER
               {
               unchanged (255),
               clear (0),
               set (1)
               }
   MAX-ACCESS  read-write
   STATUS      current
   DESCRIPTION
      "Path: apsBundle.editConf.bandwidth.action.violateAction.ethernet.deiDepth8

       Possibilities:
               unchanged   (255)
               clear   (0)
               set   (1)"
   ::= {er1645v2ApsBBwEntry 4133224448}

er1645v2ApsBBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4131979264}

er1645v2ApsBBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4132044800}

er1645v2ApsBBwActViolActEthDrpLev OBJECT-TYPE
   SYNTAX      INTEGER
               {
               unchanged (0)
               }
   MAX-ACCESS  read-write
   STATUS      current
   DESCRIPTION
      "Path: apsBundle.editConf.bandwidth.action.violateAction.ethernet.dropLevel

       Possibilities:
               unchanged   (0)"
   ::= {er1645v2ApsBBwEntry 4132110336}

er1645v2ApsBBwActViolActEthDeFlag OBJECT-TYPE
   SYNTAX      INTEGER
               {
               unchanged (255),
               clear (0),
               set (1)
               }
   MAX-ACCESS  read-write
   STATUS      current
   DESCRIPTION
      "Path: apsBundle.editConf.bandwidth.action.violateAction.ethernet.deFlag

       Possibilities:
               unchanged   (255)
               clear   (0)
               set   (1)"
   ::= {er1645v2ApsBBwEntry 4132306944}

er1645v2ApsBBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBBwEntry 4138270720}

er1645v2ApsBBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBBwEntry 4138336256}

er1645v2ApsBBwActViolActIpDrpLev OBJECT-TYPE
   SYNTAX      INTEGER
               {
               unchanged (0)
               }
   MAX-ACCESS  read-write
   STATUS      current
   DESCRIPTION
      "Path: apsBundle.editConf.bandwidth.action.violateAction.ip.dropLevel

       Possibilities:
               unchanged   (0)"
   ::= {er1645v2ApsBBwEntry 4138401792}

er1645v2ApsBBwActViolActIpDeFlag OBJECT-TYPE
   SYNTAX      INTEGER
               {
               unchanged (255),
               clear (0),
               set (1)
               }
   MAX-ACCESS  read-write
   STATUS      current
   DESCRIPTION
      "Path: apsBundle.editConf.bandwidth.action.violateAction.ip.deFlag

       Possibilities:
               unchanged   (255)
               clear   (0)
               set   (1)"
   ::= {er1645v2ApsBBwEntry 4138598400}


er1645v2ApsBIbw OBJECT IDENTIFIER ::= {er1645v2ApsB 13}

er1645v2ApsBIbwSSCTable OBJECT-TYPE
   SYNTAX      SEQUENCE OF Er1645v2ApsBIbwEntry
   MAX-ACCESS  not-accessible
   STATUS      current
   DESCRIPTION
      ""
   ::= {er1645v2ApsBIbw 1}

er1645v2ApsBIbwEntry OBJECT-TYPE
   SYNTAX      Er1645v2ApsBIbwEntry
   MAX-ACCESS  not-accessible
   STATUS      current
   DESCRIPTION
      ""
   INDEX      { er1645v2ApsBIbwGlobalIx }
   ::= {er1645v2ApsBIbwSSCTable 1}

Er1645v2ApsBIbwEntry ::=
   SEQUENCE
      {
      er1645v2ApsBIbwGlobalIx
         GlobalIndex,
      er1645v2ApsBIbwMode
         INTEGER,
      er1645v2ApsBIbwCir
         Integer32,
      er1645v2ApsBIbwEir
         Integer32,
      er1645v2ApsBIbwUnit
         INTEGER,
      er1645v2ApsBIbwTc
         INTEGER,
      er1645v2ApsBIbwTcFactor
         INTEGER,
      er1645v2ApsBIbwCorrType
         INTEGER,
      er1645v2ApsBIbwCorrPredefEncapsFrameRelay
         DisplayString,
      er1645v2ApsBIbwCorrPredefEncapsPpp
         DisplayString,
      er1645v2ApsBIbwCorrPredefEncapsAtmHl
         INTEGER,
      er1645v2ApsBIbwCorrPredefEncapsAtmMp
         INTEGER,
      er1645v2ApsBIbwCorrPredefEncapsHdlc
         DisplayString,
      er1645v2ApsBIbwCorrPredefEncapsEfmFs
         Integer32,
      er1645v2ApsBIbwCorrPredefEncapsEfmIb
         Integer32,
      er1645v2ApsBIbwCorrPredefMode
         INTEGER,
      er1645v2ApsBIbwCorrManualOverhead
         Integer32,
      er1645v2ApsBIbwCorrManualFrameData
         Counter32,
      er1645v2ApsBIbwCorrManualFrameHeader
         Counter32,
      er1645v2ApsBIbwMaxFifoQLen
         Integer32,
      er1645v2ApsBIbwPriorityPolicy
         DisplayString,
      er1645v2ApsBIbwDeFlagCir
         INTEGER,
      er1645v2ApsBIbwDeFlagEir
         INTEGER,
      er1645v2ApsBIbwDeFlagViolate
         INTEGER,
      er1645v2ApsBIbwActCirActNone
         OCTET STRING,
      er1645v2ApsBIbwActCirActEthCos1
         INTEGER,
      er1645v2ApsBIbwActCirActEthDei1
         INTEGER,
      er1645v2ApsBIbwActCirActEthCos2
         INTEGER,
      er1645v2ApsBIbwActCirActEthDei2
         INTEGER,
      er1645v2ApsBIbwActCirActEthCos3
         INTEGER,
      er1645v2ApsBIbwActCirActEthDei3
         INTEGER,
      er1645v2ApsBIbwActCirActEthCos4
         INTEGER,
      er1645v2ApsBIbwActCirActEthDei4
         INTEGER,
      er1645v2ApsBIbwActCirActEthCos5
         INTEGER,
      er1645v2ApsBIbwActCirActEthDei5
         INTEGER,
      er1645v2ApsBIbwActCirActEthCos6
         INTEGER,
      er1645v2ApsBIbwActCirActEthDei6
         INTEGER,
      er1645v2ApsBIbwActCirActEthCos7
         INTEGER,
      er1645v2ApsBIbwActCirActEthDei7
         INTEGER,
      er1645v2ApsBIbwActCirActEthCos8
         INTEGER,
      er1645v2ApsBIbwActCirActEthDei8
         INTEGER,
      er1645v2ApsBIbwActCirActEthTos
         INTEGER,
      er1645v2ApsBIbwActCirActEthQueue
         INTEGER,
      er1645v2ApsBIbwActCirActEthDrpLev
         INTEGER,
      er1645v2ApsBIbwActCirActEthDeFlag
         INTEGER,
      er1645v2ApsBIbwActCirActIpTos
         INTEGER,
      er1645v2ApsBIbwActCirActIpQueue
         INTEGER,
      er1645v2ApsBIbwActCirActIpDrpLev
         INTEGER,
      er1645v2ApsBIbwActCirActIpDeFlag
         INTEGER,
      er1645v2ApsBIbwActEirActNone
         OCTET STRING,
      er1645v2ApsBIbwActEirActEthCos1
         INTEGER,
      er1645v2ApsBIbwActEirActEthDei1
         INTEGER,
      er1645v2ApsBIbwActEirActEthCos2
         INTEGER,
      er1645v2ApsBIbwActEirActEthDei2
         INTEGER,
      er1645v2ApsBIbwActEirActEthCos3
         INTEGER,
      er1645v2ApsBIbwActEirActEthDei3
         INTEGER,
      er1645v2ApsBIbwActEirActEthCos4
         INTEGER,
      er1645v2ApsBIbwActEirActEthDei4
         INTEGER,
      er1645v2ApsBIbwActEirActEthCos5
         INTEGER,
      er1645v2ApsBIbwActEirActEthDei5
         INTEGER,
      er1645v2ApsBIbwActEirActEthCos6
         INTEGER,
      er1645v2ApsBIbwActEirActEthDei6
         INTEGER,
      er1645v2ApsBIbwActEirActEthCos7
         INTEGER,
      er1645v2ApsBIbwActEirActEthDei7
         INTEGER,
      er1645v2ApsBIbwActEirActEthCos8
         INTEGER,
      er1645v2ApsBIbwActEirActEthDei8
         INTEGER,
      er1645v2ApsBIbwActEirActEthTos
         INTEGER,
      er1645v2ApsBIbwActEirActEthQueue
         INTEGER,
      er1645v2ApsBIbwActEirActEthDrpLev
         INTEGER,
      er1645v2ApsBIbwActEirActEthDeFlag
         INTEGER,
      er1645v2ApsBIbwActEirActIpTos
         INTEGER,
      er1645v2ApsBIbwActEirActIpQueue
         INTEGER,
      er1645v2ApsBIbwActEirActIpDrpLev
         INTEGER,
      er1645v2ApsBIbwActEirActIpDeFlag
         INTEGER,
      er1645v2ApsBIbwActViolActNone
         OCTET STRING,
      er1645v2ApsBIbwActViolActDrop
         OCTET STRING,
      er1645v2ApsBIbwActViolActEthCos1
         INTEGER,
      er1645v2ApsBIbwActViolActEthDei1
         INTEGER,
      er1645v2ApsBIbwActViolActEthCos2
         INTEGER,
      er1645v2ApsBIbwActViolActEthDei2
         INTEGER,
      er1645v2ApsBIbwActViolActEthCos3
         INTEGER,
      er1645v2ApsBIbwActViolActEthDei3
         INTEGER,
      er1645v2ApsBIbwActViolActEthCos4
         INTEGER,
      er1645v2ApsBIbwActViolActEthDei4
         INTEGER,
      er1645v2ApsBIbwActViolActEthCos5
         INTEGER,
      er1645v2ApsBIbwActViolActEthDei5
         INTEGER,
      er1645v2ApsBIbwActViolActEthCos6
         INTEGER,
      er1645v2ApsBIbwActViolActEthDei6
         INTEGER,
      er1645v2ApsBIbwActViolActEthCos7
         INTEGER,
      er1645v2ApsBIbwActViolActEthDei7
         INTEGER,
      er1645v2ApsBIbwActViolActEthCos8
         INTEGER,
      er1645v2ApsBIbwActViolActEthDei8
         INTEGER,
      er1645v2ApsBIbwActViolActEthTos
         INTEGER,
      er1645v2ApsBIbwActViolActEthQueue
         INTEGER,
      er1645v2ApsBIbwActViolActEthDrpLev
         INTEGER,
      er1645v2ApsBIbwActViolActEthDeFlag
         INTEGER,
      er1645v2ApsBIbwActViolActIpTos
         INTEGER,
      er1645v2ApsBIbwActViolActIpQueue
         INTEGER,
      er1645v2ApsBIbwActViolActIpDrpLev
         INTEGER,
      er1645v2ApsBIbwActViolActIpDeFlag
         INTEGER,
      er1645v2ApsBIbwSubInterfacesExcluded
         INTEGER,
      er1645v2ApsBIbwSubInterfacesIncludedInAccessList
         DisplayString
      }

er1645v2ApsBIbwGlobalIx OBJECT-TYPE
   SYNTAX      GlobalIndex
   MAX-ACCESS  not-accessible
   STATUS      current
   DESCRIPTION
      "The value of the tlsCntTreeGlobalIndex of the MANAGED OBJECT."
   ::= {er1645v2ApsBIbwEntry 10}

er1645v2ApsBIbwMode OBJECT-TYPE
   SYNTAX      INTEGER
               {
               reshaping (1),
               policing (2)
               }
   MAX-ACCESS  read-write
   STATUS      current
   DESCRIPTION
      "Path: apsBundle.editConf.inboundBandwidth.mode

       Possibilities:
               reshaping   (1)
               policing   (2)"
   ::= {er1645v2ApsBIbwEntry 3758096384}

er1645v2ApsBIbwCir OBJECT-TYPE
   SYNTAX      Integer32
   MAX-ACCESS  read-write
   STATUS      current
   DESCRIPTION
      "Path: apsBundle.editConf.inboundBandwidth.cir"
   ::= {er1645v2ApsBIbwEntry 268435456}

er1645v2ApsBIbwEir OBJECT-TYPE
   SYNTAX      Integer32
   MAX-ACCESS  read-write
   STATUS      current
   DESCRIPTION
      "Path: apsBundle.editConf.inboundBandwidth.eir"
   ::= {er1645v2ApsBIbwEntry 1879048192}

er1645v2ApsBIbwUnit OBJECT-TYPE
   SYNTAX      INTEGER
               {
               bitssec (1),
               percent (2)
               }
   MAX-ACCESS  read-write
   STATUS      current
   DESCRIPTION
      "Path: apsBundle.editConf.inboundBandwidth.unit

       Possibilities:
               bits/sec   (1)
               percent   (2)"
   ::= {er1645v2ApsBIbwEntry 1342177280}

er1645v2ApsBIbwTc OBJECT-TYPE
   SYNTAX      INTEGER
               {
               auto (0)
               }
   MAX-ACCESS  read-write
   STATUS      current
   DESCRIPTION
      "Path: apsBundle.editConf.inboundBandwidth.tc

       Possibilities:
               auto   (0)"
   ::= {er1645v2ApsBIbwEntry 1610612736}

er1645v2ApsBIbwTcFactor OBJECT-TYPE
   SYNTAX      INTEGER
               {
               ms (10),
               s100us (1)
               }
   MAX-ACCESS  read-write
   STATUS      current
   DESCRIPTION
      "Path: apsBundle.editConf.inboundBandwidth.tcFactor

       Possibilities:
               ms   (10)
               *100us   (1)"
   ::= {er1645v2ApsBIbwEntry 2147483648}

er1645v2ApsBIbwCorrType OBJECT-TYPE
   SYNTAX      INTEGER
               {
               noCorrection (0),
               predefined (1),
               manual (2)
               }
   MAX-ACCESS  read-write
   STATUS      current
   DESCRIPTION
      "Path: apsBundle.editConf.inboundBandwidth.correction.type

       Possibilities:
               noCorrection   (0)
               predefined   (1)
               manual   (2)"
   ::= {er1645v2ApsBIbwEntry 570425344}

er1645v2ApsBIbwCorrPredefEncapsFrameRelay OBJECT-TYPE
   SYNTAX      DisplayString
   MAX-ACCESS  read-write
   STATUS      current
   DESCRIPTION
      "Path: apsBundle.editConf.inboundBandwidth.correction.predefined.encapsulation.frameRelay"
   ::= {er1645v2ApsBIbwEntry 608436224}

er1645v2ApsBIbwCorrPredefEncapsPpp OBJECT-TYPE
   SYNTAX      DisplayString
   MAX-ACCESS  read-write
   STATUS      current
   DESCRIPTION
      "Path: apsBundle.editConf.inboundBandwidth.correction.predefined.encapsulation.ppp"
   ::= {er1645v2ApsBIbwEntry 608698368}

er1645v2ApsBIbwCorrPredefEncapsAtmHl OBJECT-TYPE
   SYNTAX      INTEGER
               {
               rfc2684 (0),
               ppp (1),
               pppOverEthernet (2)
               }
   MAX-ACCESS  read-write
   STATUS      current
   DESCRIPTION
      "Path: apsBundle.editConf.inboundBandwidth.correction.predefined.encapsulation.atm.higherLayer

       Possibilities:
               rfc2684   (0)
               ppp   (1)
               pppOverEthernet   (2)"
   ::= {er1645v2ApsBIbwEntry 608993280}

er1645v2ApsBIbwCorrPredefEncapsAtmMp OBJECT-TYPE
   SYNTAX      INTEGER
               {
               llcEncapsulation (0),
               vcMultiplexing (1)
               }
   MAX-ACCESS  read-write
   STATUS      current
   DESCRIPTION
      "Path: apsBundle.editConf.inboundBandwidth.correction.predefined.encapsulation.atm.multiProtocol

       Possibilities:
               llcEncapsulation   (0)
               vcMultiplexing   (1)"
   ::= {er1645v2ApsBIbwEntry 609026048}

er1645v2ApsBIbwCorrPredefEncapsHdlc OBJECT-TYPE
   SYNTAX      DisplayString
   MAX-ACCESS  read-write
   STATUS      current
   DESCRIPTION
      "Path: apsBundle.editConf.inboundBandwidth.correction.predefined.encapsulation.hdlc"
   ::= {er1645v2ApsBIbwEntry 609222656}

er1645v2ApsBIbwCorrPredefEncapsEfmFs OBJECT-TYPE
   SYNTAX      Integer32
   MAX-ACCESS  read-write
   STATUS      current
   DESCRIPTION
      "Path: apsBundle.editConf.inboundBandwidth.correction.predefined.encapsulation.efm.fragmentSize"
   ::= {er1645v2ApsBIbwEntry 609517568}

er1645v2ApsBIbwCorrPredefEncapsEfmIb OBJECT-TYPE
   SYNTAX      Integer32
   MAX-ACCESS  read-write
   STATUS      current
   DESCRIPTION
      "Path: apsBundle.editConf.inboundBandwidth.correction.predefined.encapsulation.efm.idleBytes"
   ::= {er1645v2ApsBIbwEntry 609550336}

er1645v2ApsBIbwCorrPredefMode OBJECT-TYPE
   SYNTAX      INTEGER
               {
               routing (0),
               bridging (1)
               }
   MAX-ACCESS  read-write
   STATUS      current
   DESCRIPTION
      "Path: apsBundle.editConf.inboundBandwidth.correction.predefined.mode

       Possibilities:
               routing   (0)
               bridging   (1)"
   ::= {er1645v2ApsBIbwEntry 612368384}

er1645v2ApsBIbwCorrManualOverhead OBJECT-TYPE
   SYNTAX      Integer32
   MAX-ACCESS  read-write
   STATUS      current
   DESCRIPTION
      "Path: apsBundle.editConf.inboundBandwidth.correction.manual.overhead"
   ::= {er1645v2ApsBIbwEntry 637665280}

er1645v2ApsBIbwCorrManualFrameData OBJECT-TYPE
   SYNTAX      Counter32
   MAX-ACCESS  read-write
   STATUS      current
   DESCRIPTION
      "Path: apsBundle.editConf.inboundBandwidth.correction.manual.frameData

       32 bit unsigned wrappable counter."
   ::= {er1645v2ApsBIbwEntry 637796352}

er1645v2ApsBIbwCorrManualFrameHeader OBJECT-TYPE
   SYNTAX      Counter32
   MAX-ACCESS  read-write
   STATUS      current
   DESCRIPTION
      "Path: apsBundle.editConf.inboundBandwidth.correction.manual.frameHeader

       32 bit unsigned wrappable counter."
   ::= {er1645v2ApsBIbwEntry 637927424}

er1645v2ApsBIbwMaxFifoQLen OBJECT-TYPE
   SYNTAX      Integer32
   MAX-ACCESS  read-write
   STATUS      current
   DESCRIPTION
      "Path: apsBundle.editConf.inboundBandwidth.maxFifoQLen"
   ::= {er1645v2ApsBIbwEntry 805306368}

er1645v2ApsBIbwPriorityPolicy OBJECT-TYPE
   SYNTAX      DisplayString
   MAX-ACCESS  read-write
   STATUS      current
   DESCRIPTION
      "Path: apsBundle.editConf.inboundBandwidth.priorityPolicy"
   ::= {er1645v2ApsBIbwEntry 1073741824}

er1645v2ApsBIbwDeFlagCir OBJECT-TYPE
   SYNTAX      INTEGER
               {
               allowed (1),
               notAllowed (2)
               }
   MAX-ACCESS  read-write
   STATUS      current
   DESCRIPTION
      "Path: apsBundle.editConf.inboundBandwidth.deFlag.cir

       Possibilities:
               allowed   (1)
               notAllowed   (2)"
   ::= {er1645v2ApsBIbwEntry 3490709504}

er1645v2ApsBIbwDeFlagEir OBJECT-TYPE
   SYNTAX      INTEGER
               {
               allowed (1),
               notAllowed (2)
               }
   MAX-ACCESS  read-write
   STATUS      current
   DESCRIPTION
      "Path: apsBundle.editConf.inboundBandwidth.deFlag.eir

       Possibilities:
               allowed   (1)
               notAllowed   (2)"
   ::= {er1645v2ApsBIbwEntry 3491758080}

er1645v2ApsBIbwDeFlagViolate OBJECT-TYPE
   SYNTAX      INTEGER
               {
               allowed (1),
               notAllowed (2)
               }
   MAX-ACCESS  read-write
   STATUS      current
   DESCRIPTION
      "Path: apsBundle.editConf.inboundBandwidth.deFlag.violate

       Possibilities:
               allowed   (1)
               notAllowed   (2)"
   ::= {er1645v2ApsBIbwEntry 3492806656}

er1645v2ApsBIbwActCirActNone OBJECT-TYPE
   SYNTAX      OCTET STRING
   MAX-ACCESS  read-write
   STATUS      current
   DESCRIPTION
      "Path: apsBundle.editConf.inboundBandwidth.action.cirAction.none"
   ::= {er1645v2ApsBIbwEntry 4062183424}

er1645v2ApsBIbwActCirActEthCos1 OBJECT-TYPE
   SYNTAX      INTEGER
               {
               unchanged (256)
               }
   MAX-ACCESS  read-write
   STATUS      current
   DESCRIPTION
      "Path: apsBundle.editConf.inboundBandwidth.action.cirAction.ethernet.cosDepth1

       Possibilities:
               unchanged   (256)"
   ::= {er1645v2ApsBIbwEntry 4064346112}

er1645v2ApsBIbwActCirActEthDei1 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth1

       Possibilities:
               unchanged   (255)
               clear   (0)
               set   (1)"
   ::= {er1645v2ApsBIbwEntry 4065656832}

er1645v2ApsBIbwActCirActEthCos2 OBJECT-TYPE
   SYNTAX      INTEGER
               {
               unchanged (256)
               }
   MAX-ACCESS  read-write
   STATUS      current
   DESCRIPTION
      "Path: apsBundle.editConf.inboundBandwidth.action.cirAction.ethernet.cosDepth2

       Possibilities:
               unchanged   (256)"
   ::= {er1645v2ApsBIbwEntry 4064411648}

er1645v2ApsBIbwActCirActEthDei2 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth2

       Possibilities:
               unchanged   (255)
               clear   (0)
               set   (1)"
   ::= {er1645v2ApsBIbwEntry 4065722368}

er1645v2ApsBIbwActCirActEthCos3 OBJECT-TYPE
   SYNTAX      INTEGER
               {
               unchanged (256)
               }
   MAX-ACCESS  read-write
   STATUS      current
   DESCRIPTION
      "Path: apsBundle.editConf.inboundBandwidth.action.cirAction.ethernet.cosDepth3

       Possibilities:
               unchanged   (256)"
   ::= {er1645v2ApsBIbwEntry 4064477184}

er1645v2ApsBIbwActCirActEthDei3 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth3

       Possibilities:
               unchanged   (255)
               clear   (0)
               set   (1)"
   ::= {er1645v2ApsBIbwEntry 4065787904}

er1645v2ApsBIbwActCirActEthCos4 OBJECT-TYPE
   SYNTAX      INTEGER
               {
               unchanged (256)
               }
   MAX-ACCESS  read-write
   STATUS      current
   DESCRIPTION
      "Path: apsBundle.editConf.inboundBandwidth.action.cirAction.ethernet.cosDepth4

       Possibilities:
               unchanged   (256)"
   ::= {er1645v2ApsBIbwEntry 4064542720}

er1645v2ApsBIbwActCirActEthDei4 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth4

       Possibilities:
               unchanged   (255)
               clear   (0)
               set   (1)"
   ::= {er1645v2ApsBIbwEntry 4065853440}

er1645v2ApsBIbwActCirActEthCos5 OBJECT-TYPE
   SYNTAX      INTEGER
               {
               unchanged (256)
               }
   MAX-ACCESS  read-write
   STATUS      current
   DESCRIPTION
      "Path: apsBundle.editConf.inboundBandwidth.action.cirAction.ethernet.cosDepth5

       Possibilities:
               unchanged   (256)"
   ::= {er1645v2ApsBIbwEntry 4064608256}

er1645v2ApsBIbwActCirActEthDei5 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth5

       Possibilities:
               unchanged   (255)
               clear   (0)
               set   (1)"
   ::= {er1645v2ApsBIbwEntry 4065918976}

er1645v2ApsBIbwActCirActEthCos6 OBJECT-TYPE
   SYNTAX      INTEGER
               {
               unchanged (256)
               }
   MAX-ACCESS  read-write
   STATUS      current
   DESCRIPTION
      "Path: apsBundle.editConf.inboundBandwidth.action.cirAction.ethernet.cosDepth6

       Possibilities:
               unchanged   (256)"
   ::= {er1645v2ApsBIbwEntry 4064673792}

er1645v2ApsBIbwActCirActEthDei6 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth6

       Possibilities:
               unchanged   (255)
               clear   (0)
               set   (1)"
   ::= {er1645v2ApsBIbwEntry 4065984512}

er1645v2ApsBIbwActCirActEthCos7 OBJECT-TYPE
   SYNTAX      INTEGER
               {
               unchanged (256)
               }
   MAX-ACCESS  read-write
   STATUS      current
   DESCRIPTION
      "Path: apsBundle.editConf.inboundBandwidth.action.cirAction.ethernet.cosDepth7

       Possibilities:
               unchanged   (256)"
   ::= {er1645v2ApsBIbwEntry 4064739328}

er1645v2ApsBIbwActCirActEthDei7 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth7

       Possibilities:
               unchanged   (255)
               clear   (0)
               set   (1)"
   ::= {er1645v2ApsBIbwEntry 4066050048}

er1645v2ApsBIbwActCirActEthCos8 OBJECT-TYPE
   SYNTAX      INTEGER
               {
               unchanged (256)
               }
   MAX-ACCESS  read-write
   STATUS      current
   DESCRIPTION
      "Path: apsBundle.editConf.inboundBandwidth.action.cirAction.ethernet.cosDepth8

       Possibilities:
               unchanged   (256)"
   ::= {er1645v2ApsBIbwEntry 4064804864}

er1645v2ApsBIbwActCirActEthDei8 OBJECT-TYPE
   SYNTAX      INTEGER
               {
               unchanged (255),
               clear (0),
               set (1)
               }
   MAX-ACCESS  read-write
   STATUS      current
   DESCRIPTION
      "Path: apsBundle.editConf.inboundBandwidth.action.cirAction.ethernet.deiDepth8

       Possibilities:
               unchanged   (255)
               clear   (0)
               set   (1)"
   ::= {er1645v2ApsBIbwEntry 4066115584}

er1645v2ApsBIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4064870400}

er1645v2ApsBIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4064935936}

er1645v2ApsBIbwActCirActEthDrpLev OBJECT-TYPE
   SYNTAX      INTEGER
               {
               unchanged (0)
               }
   MAX-ACCESS  read-write
   STATUS      current
   DESCRIPTION
      "Path: apsBundle.editConf.inboundBandwidth.action.cirAction.ethernet.dropLevel

       Possibilities:
               unchanged   (0)"
   ::= {er1645v2ApsBIbwEntry 4065001472}

er1645v2ApsBIbwActCirActEthDeFlag OBJECT-TYPE
   SYNTAX      INTEGER
               {
               unchanged (255),
               clear (0),
               set (1)
               }
   MAX-ACCESS  read-write
   STATUS      current
   DESCRIPTION
      "Path: apsBundle.editConf.inboundBandwidth.action.cirAction.ethernet.deFlag

       Possibilities:
               unchanged   (255)
               clear   (0)
               set   (1)"
   ::= {er1645v2ApsBIbwEntry 4065198080}

er1645v2ApsBIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4071161856}

er1645v2ApsBIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4071227392}

er1645v2ApsBIbwActCirActIpDrpLev OBJECT-TYPE
   SYNTAX      INTEGER
               {
               unchanged (0)
               }
   MAX-ACCESS  read-write
   STATUS      current
   DESCRIPTION
      "Path: apsBundle.editConf.inboundBandwidth.action.cirAction.ip.dropLevel

       Possibilities:
               unchanged   (0)"
   ::= {er1645v2ApsBIbwEntry 4071292928}

er1645v2ApsBIbwActCirActIpDeFlag OBJECT-TYPE
   SYNTAX      INTEGER
               {
               unchanged (255),
               clear (0),
               set (1)
               }
   MAX-ACCESS  read-write
   STATUS      current
   DESCRIPTION
      "Path: apsBundle.editConf.inboundBandwidth.action.cirAction.ip.deFlag

       Possibilities:
               unchanged   (255)
               clear   (0)
               set   (1)"
   ::= {er1645v2ApsBIbwEntry 4071489536}

er1645v2ApsBIbwActEirActNone OBJECT-TYPE
   SYNTAX      OCTET STRING
   MAX-ACCESS  read-write
   STATUS      current
   DESCRIPTION
      "Path: apsBundle.editConf.inboundBandwidth.action.eirAction.none"
   ::= {er1645v2ApsBIbwEntry 4095737856}

er1645v2ApsBIbwActEirActEthCos1 OBJECT-TYPE
   SYNTAX      INTEGER
               {
               unchanged (256)
               }
   MAX-ACCESS  read-write
   STATUS      current
   DESCRIPTION
      "Path: apsBundle.editConf.inboundBandwidth.action.eirAction.ethernet.cosDepth1

       Possibilities:
               unchanged   (256)"
   ::= {er1645v2ApsBIbwEntry 4097900544}

er1645v2ApsBIbwActEirActEthDei1 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth1

       Possibilities:
               unchanged   (255)
               clear   (0)
               set   (1)"
   ::= {er1645v2ApsBIbwEntry 4099211264}

er1645v2ApsBIbwActEirActEthCos2 OBJECT-TYPE
   SYNTAX      INTEGER
               {
               unchanged (256)
               }
   MAX-ACCESS  read-write
   STATUS      current
   DESCRIPTION
      "Path: apsBundle.editConf.inboundBandwidth.action.eirAction.ethernet.cosDepth2

       Possibilities:
               unchanged   (256)"
   ::= {er1645v2ApsBIbwEntry 4097966080}

er1645v2ApsBIbwActEirActEthDei2 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth2

       Possibilities:
               unchanged   (255)
               clear   (0)
               set   (1)"
   ::= {er1645v2ApsBIbwEntry 4099276800}

er1645v2ApsBIbwActEirActEthCos3 OBJECT-TYPE
   SYNTAX      INTEGER
               {
               unchanged (256)
               }
   MAX-ACCESS  read-write
   STATUS      current
   DESCRIPTION
      "Path: apsBundle.editConf.inboundBandwidth.action.eirAction.ethernet.cosDepth3

       Possibilities:
               unchanged   (256)"
   ::= {er1645v2ApsBIbwEntry 4098031616}

er1645v2ApsBIbwActEirActEthDei3 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth3

       Possibilities:
               unchanged   (255)
               clear   (0)
               set   (1)"
   ::= {er1645v2ApsBIbwEntry 4099342336}

er1645v2ApsBIbwActEirActEthCos4 OBJECT-TYPE
   SYNTAX      INTEGER
               {
               unchanged (256)
               }
   MAX-ACCESS  read-write
   STATUS      current
   DESCRIPTION
      "Path: apsBundle.editConf.inboundBandwidth.action.eirAction.ethernet.cosDepth4

       Possibilities:
               unchanged   (256)"
   ::= {er1645v2ApsBIbwEntry 4098097152}

er1645v2ApsBIbwActEirActEthDei4 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth4

       Possibilities:
               unchanged   (255)
               clear   (0)
               set   (1)"
   ::= {er1645v2ApsBIbwEntry 4099407872}

er1645v2ApsBIbwActEirActEthCos5 OBJECT-TYPE
   SYNTAX      INTEGER
               {
               unchanged (256)
               }
   MAX-ACCESS  read-write
   STATUS      current
   DESCRIPTION
      "Path: apsBundle.editConf.inboundBandwidth.action.eirAction.ethernet.cosDepth5

       Possibilities:
               unchanged   (256)"
   ::= {er1645v2ApsBIbwEntry 4098162688}

er1645v2ApsBIbwActEirActEthDei5 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth5

       Possibilities:
               unchanged   (255)
               clear   (0)
               set   (1)"
   ::= {er1645v2ApsBIbwEntry 4099473408}

er1645v2ApsBIbwActEirActEthCos6 OBJECT-TYPE
   SYNTAX      INTEGER
               {
               unchanged (256)
               }
   MAX-ACCESS  read-write
   STATUS      current
   DESCRIPTION
      "Path: apsBundle.editConf.inboundBandwidth.action.eirAction.ethernet.cosDepth6

       Possibilities:
               unchanged   (256)"
   ::= {er1645v2ApsBIbwEntry 4098228224}

er1645v2ApsBIbwActEirActEthDei6 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth6

       Possibilities:
               unchanged   (255)
               clear   (0)
               set   (1)"
   ::= {er1645v2ApsBIbwEntry 4099538944}

er1645v2ApsBIbwActEirActEthCos7 OBJECT-TYPE
   SYNTAX      INTEGER
               {
               unchanged (256)
               }
   MAX-ACCESS  read-write
   STATUS      current
   DESCRIPTION
      "Path: apsBundle.editConf.inboundBandwidth.action.eirAction.ethernet.cosDepth7

       Possibilities:
               unchanged   (256)"
   ::= {er1645v2ApsBIbwEntry 4098293760}

er1645v2ApsBIbwActEirActEthDei7 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth7

       Possibilities:
               unchanged   (255)
               clear   (0)
               set   (1)"
   ::= {er1645v2ApsBIbwEntry 4099604480}

er1645v2ApsBIbwActEirActEthCos8 OBJECT-TYPE
   SYNTAX      INTEGER
               {
               unchanged (256)
               }
   MAX-ACCESS  read-write
   STATUS      current
   DESCRIPTION
      "Path: apsBundle.editConf.inboundBandwidth.action.eirAction.ethernet.cosDepth8

       Possibilities:
               unchanged   (256)"
   ::= {er1645v2ApsBIbwEntry 4098359296}

er1645v2ApsBIbwActEirActEthDei8 OBJECT-TYPE
   SYNTAX      INTEGER
               {
               unchanged (255),
               clear (0),
               set (1)
               }
   MAX-ACCESS  read-write
   STATUS      current
   DESCRIPTION
      "Path: apsBundle.editConf.inboundBandwidth.action.eirAction.ethernet.deiDepth8

       Possibilities:
               unchanged   (255)
               clear   (0)
               set   (1)"
   ::= {er1645v2ApsBIbwEntry 4099670016}

er1645v2ApsBIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4098424832}

er1645v2ApsBIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4098490368}

er1645v2ApsBIbwActEirActEthDrpLev OBJECT-TYPE
   SYNTAX      INTEGER
               {
               unchanged (0)
               }
   MAX-ACCESS  read-write
   STATUS      current
   DESCRIPTION
      "Path: apsBundle.editConf.inboundBandwidth.action.eirAction.ethernet.dropLevel

       Possibilities:
               unchanged   (0)"
   ::= {er1645v2ApsBIbwEntry 4098555904}

er1645v2ApsBIbwActEirActEthDeFlag OBJECT-TYPE
   SYNTAX      INTEGER
               {
               unchanged (255),
               clear (0),
               set (1)
               }
   MAX-ACCESS  read-write
   STATUS      current
   DESCRIPTION
      "Path: apsBundle.editConf.inboundBandwidth.action.eirAction.ethernet.deFlag

       Possibilities:
               unchanged   (255)
               clear   (0)
               set   (1)"
   ::= {er1645v2ApsBIbwEntry 4098752512}

er1645v2ApsBIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4104716288}

er1645v2ApsBIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4104781824}

er1645v2ApsBIbwActEirActIpDrpLev OBJECT-TYPE
   SYNTAX      INTEGER
               {
               unchanged (0)
               }
   MAX-ACCESS  read-write
   STATUS      current
   DESCRIPTION
      "Path: apsBundle.editConf.inboundBandwidth.action.eirAction.ip.dropLevel

       Possibilities:
               unchanged   (0)"
   ::= {er1645v2ApsBIbwEntry 4104847360}

er1645v2ApsBIbwActEirActIpDeFlag OBJECT-TYPE
   SYNTAX      INTEGER
               {
               unchanged (255),
               clear (0),
               set (1)
               }
   MAX-ACCESS  read-write
   STATUS      current
   DESCRIPTION
      "Path: apsBundle.editConf.inboundBandwidth.action.eirAction.ip.deFlag

       Possibilities:
               unchanged   (255)
               clear   (0)
               set   (1)"
   ::= {er1645v2ApsBIbwEntry 4105043968}

er1645v2ApsBIbwActViolActNone OBJECT-TYPE
   SYNTAX      OCTET STRING
   MAX-ACCESS  read-write
   STATUS      current
   DESCRIPTION
      "Path: apsBundle.editConf.inboundBandwidth.action.violateAction.none"
   ::= {er1645v2ApsBIbwEntry 4129292288}

er1645v2ApsBIbwActViolActDrop OBJECT-TYPE
   SYNTAX      OCTET STRING
   MAX-ACCESS  read-write
   STATUS      current
   DESCRIPTION
      "Path: apsBundle.editConf.inboundBandwidth.action.violateAction.drop"
   ::= {er1645v2ApsBIbwEntry 4133486592}

er1645v2ApsBIbwActViolActEthCos1 OBJECT-TYPE
   SYNTAX      INTEGER
               {
               unchanged (256)
               }
   MAX-ACCESS  read-write
   STATUS      current
   DESCRIPTION
      "Path: apsBundle.editConf.inboundBandwidth.action.violateAction.ethernet.cosDepth1

       Possibilities:
               unchanged   (256)"
   ::= {er1645v2ApsBIbwEntry 4131454976}

er1645v2ApsBIbwActViolActEthDei1 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth1

       Possibilities:
               unchanged   (255)
               clear   (0)
               set   (1)"
   ::= {er1645v2ApsBIbwEntry 4132765696}

er1645v2ApsBIbwActViolActEthCos2 OBJECT-TYPE
   SYNTAX      INTEGER
               {
               unchanged (256)
               }
   MAX-ACCESS  read-write
   STATUS      current
   DESCRIPTION
      "Path: apsBundle.editConf.inboundBandwidth.action.violateAction.ethernet.cosDepth2

       Possibilities:
               unchanged   (256)"
   ::= {er1645v2ApsBIbwEntry 4131520512}

er1645v2ApsBIbwActViolActEthDei2 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth2

       Possibilities:
               unchanged   (255)
               clear   (0)
               set   (1)"
   ::= {er1645v2ApsBIbwEntry 4132831232}

er1645v2ApsBIbwActViolActEthCos3 OBJECT-TYPE
   SYNTAX      INTEGER
               {
               unchanged (256)
               }
   MAX-ACCESS  read-write
   STATUS      current
   DESCRIPTION
      "Path: apsBundle.editConf.inboundBandwidth.action.violateAction.ethernet.cosDepth3

       Possibilities:
               unchanged   (256)"
   ::= {er1645v2ApsBIbwEntry 4131586048}

er1645v2ApsBIbwActViolActEthDei3 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth3

       Possibilities:
               unchanged   (255)
               clear   (0)
               set   (1)"
   ::= {er1645v2ApsBIbwEntry 4132896768}

er1645v2ApsBIbwActViolActEthCos4 OBJECT-TYPE
   SYNTAX      INTEGER
               {
               unchanged (256)
               }
   MAX-ACCESS  read-write
   STATUS      current
   DESCRIPTION
      "Path: apsBundle.editConf.inboundBandwidth.action.violateAction.ethernet.cosDepth4

       Possibilities:
               unchanged   (256)"
   ::= {er1645v2ApsBIbwEntry 4131651584}

er1645v2ApsBIbwActViolActEthDei4 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth4

       Possibilities:
               unchanged   (255)
               clear   (0)
               set   (1)"
   ::= {er1645v2ApsBIbwEntry 4132962304}

er1645v2ApsBIbwActViolActEthCos5 OBJECT-TYPE
   SYNTAX      INTEGER
               {
               unchanged (256)
               }
   MAX-ACCESS  read-write
   STATUS      current
   DESCRIPTION
      "Path: apsBundle.editConf.inboundBandwidth.action.violateAction.ethernet.cosDepth5

       Possibilities:
               unchanged   (256)"
   ::= {er1645v2ApsBIbwEntry 4131717120}

er1645v2ApsBIbwActViolActEthDei5 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth5

       Possibilities:
               unchanged   (255)
               clear   (0)
               set   (1)"
   ::= {er1645v2ApsBIbwEntry 4133027840}

er1645v2ApsBIbwActViolActEthCos6 OBJECT-TYPE
   SYNTAX      INTEGER
               {
               unchanged (256)
               }
   MAX-ACCESS  read-write
   STATUS      current
   DESCRIPTION
      "Path: apsBundle.editConf.inboundBandwidth.action.violateAction.ethernet.cosDepth6

       Possibilities:
               unchanged   (256)"
   ::= {er1645v2ApsBIbwEntry 4131782656}

er1645v2ApsBIbwActViolActEthDei6 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth6

       Possibilities:
               unchanged   (255)
               clear   (0)
               set   (1)"
   ::= {er1645v2ApsBIbwEntry 4133093376}

er1645v2ApsBIbwActViolActEthCos7 OBJECT-TYPE
   SYNTAX      INTEGER
               {
               unchanged (256)
               }
   MAX-ACCESS  read-write
   STATUS      current
   DESCRIPTION
      "Path: apsBundle.editConf.inboundBandwidth.action.violateAction.ethernet.cosDepth7

       Possibilities:
               unchanged   (256)"
   ::= {er1645v2ApsBIbwEntry 4131848192}

er1645v2ApsBIbwActViolActEthDei7 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth7

       Possibilities:
               unchanged   (255)
               clear   (0)
               set   (1)"
   ::= {er1645v2ApsBIbwEntry 4133158912}

er1645v2ApsBIbwActViolActEthCos8 OBJECT-TYPE
   SYNTAX      INTEGER
               {
               unchanged (256)
               }
   MAX-ACCESS  read-write
   STATUS      current
   DESCRIPTION
      "Path: apsBundle.editConf.inboundBandwidth.action.violateAction.ethernet.cosDepth8

       Possibilities:
               unchanged   (256)"
   ::= {er1645v2ApsBIbwEntry 4131913728}

er1645v2ApsBIbwActViolActEthDei8 OBJECT-TYPE
   SYNTAX      INTEGER
               {
               unchanged (255),
               clear (0),
               set (1)
               }
   MAX-ACCESS  read-write
   STATUS      current
   DESCRIPTION
      "Path: apsBundle.editConf.inboundBandwidth.action.violateAction.ethernet.deiDepth8

       Possibilities:
               unchanged   (255)
               clear   (0)
               set   (1)"
   ::= {er1645v2ApsBIbwEntry 4133224448}

er1645v2ApsBIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4131979264}

er1645v2ApsBIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4132044800}

er1645v2ApsBIbwActViolActEthDrpLev OBJECT-TYPE
   SYNTAX      INTEGER
               {
               unchanged (0)
               }
   MAX-ACCESS  read-write
   STATUS      current
   DESCRIPTION
      "Path: apsBundle.editConf.inboundBandwidth.action.violateAction.ethernet.dropLevel

       Possibilities:
               unchanged   (0)"
   ::= {er1645v2ApsBIbwEntry 4132110336}

er1645v2ApsBIbwActViolActEthDeFlag OBJECT-TYPE
   SYNTAX      INTEGER
               {
               unchanged (255),
               clear (0),
               set (1)
               }
   MAX-ACCESS  read-write
   STATUS      current
   DESCRIPTION
      "Path: apsBundle.editConf.inboundBandwidth.action.violateAction.ethernet.deFlag

       Possibilities:
               unchanged   (255)
               clear   (0)
               set   (1)"
   ::= {er1645v2ApsBIbwEntry 4132306944}

er1645v2ApsBIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: apsBundle.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2ApsBIbwEntry 4138270720}

er1645v2ApsBIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: apsBundle.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2ApsBIbwEntry 4138336256}

er1645v2ApsBIbwActViolActIpDrpLev OBJECT-TYPE
   SYNTAX      INTEGER
               {
               unchanged (0)
               }
   MAX-ACCESS  read-write
   STATUS      current
   DESCRIPTION
      "Path: apsBundle.editConf.inboundBandwidth.action.violateAction.ip.dropLevel

       Possibilities:
               unchanged   (0)"
   ::= {er1645v2ApsBIbwEntry 4138401792}

er1645v2ApsBIbwActViolActIpDeFlag OBJECT-TYPE
   SYNTAX      INTEGER
               {
               unchanged (255),
               clear (0),
               set (1)
               }
   MAX-ACCESS  read-write
   STATUS      current
   DESCRIPTION
      "Path: apsBundle.editConf.inboundBandwidth.action.violateAction.ip.deFlag

       Possibilities:
               unchanged   (255)
               clear   (0)
               set   (1)"
   ::= {er1645v2ApsBIbwEntry 4138598400}

er1645v2ApsBIbwSubInterfacesExcluded OBJECT-TYPE
   SYNTAX      INTEGER
               {
               s (1)
               }
   MAX-ACCESS  read-write
   STATUS      current
   DESCRIPTION
      "Path: apsBundle.editConf.inboundBandwidth.subInterfaces.excluded

       Possibilities:
                  (1)"
   ::= {er1645v2ApsBIbwEntry 2416967680}

er1645v2ApsBIbwSubInterfacesIncludedInAccessList OBJECT-TYPE
   SYNTAX      DisplayString
   MAX-ACCESS  read-write
   STATUS      current
   DESCRIPTION
      "Path: apsBundle.editConf.inboundBandwidth.subInterfaces.included.inAccessList"
   ::= {er1645v2ApsBIbwEntry 2418020352}


er1645v2ApsBPriorityPolicy OBJECT IDENTIFIER ::= {er1645v2ApsB 39}

er1645v2ApsBPriorityPolicyTable OBJECT-TYPE
   SYNTAX      SEQUENCE OF Er1645v2ApsBPriorityPolicyEntry
   MAX-ACCESS  not-accessible
   STATUS      current
   DESCRIPTION
      "Preferred Policy"
   ::= {er1645v2ApsBPriorityPolicy 1}

er1645v2ApsBPriorityPolicyEntry OBJECT-TYPE
   SYNTAX      Er1645v2ApsBPriorityPolicyEntry
   MAX-ACCESS  not-accessible
   STATUS      current
   DESCRIPTION
      ""
   INDEX      { er1645v2ApsBPriorityPolicyGlobalIx }
   ::= {er1645v2ApsBPriorityPolicyTable 1}

Er1645v2ApsBPriorityPolicyEntry ::=
   SEQUENCE
      {
      er1645v2ApsBPriorityPolicyGlobalIx
         GlobalIndex,
      er1645v2ApsBPriorityPolicyValue
         DisplayString
      }

er1645v2ApsBPriorityPolicyGlobalIx OBJECT-TYPE
   SYNTAX      GlobalIndex
   MAX-ACCESS  not-accessible
   STATUS      current
   DESCRIPTION
      "The value of the tlsCntTreeGlobalIndex of the MANAGED OBJECT."
   ::= {er1645v2ApsBPriorityPolicyEntry 10}

er1645v2ApsBPriorityPolicyValue OBJECT-TYPE
   SYNTAX      DisplayString
   MAX-ACCESS  read-write
   STATUS      current
   DESCRIPTION
      "Path: apsBundle.editConf.priorityPolicy"
   ::= {er1645v2ApsBPriorityPolicyEntry 2147483648}


er1645v2ApsBSnmpIndexOffset OBJECT IDENTIFIER ::= {er1645v2ApsB 268}

er1645v2ApsBSnmpIndexOffsetTable OBJECT-TYPE
   SYNTAX      SEQUENCE OF Er1645v2ApsBSnmpIndexOffsetEntry
   MAX-ACCESS  not-accessible
   STATUS      current
   DESCRIPTION
      "Preferred offset in the range of SNMP indices for this SWinst, 0 means automatic"
   ::= {er1645v2ApsBSnmpIndexOffset 1}

er1645v2ApsBSnmpIndexOffsetEntry OBJECT-TYPE
   SYNTAX      Er1645v2ApsBSnmpIndexOffsetEntry
   MAX-ACCESS  not-accessible
   STATUS      current
   DESCRIPTION
      ""
   INDEX      { er1645v2ApsBSnmpIndexOffsetGlobalIx }
   ::= {er1645v2ApsBSnmpIndexOffsetTable 1}

Er1645v2ApsBSnmpIndexOffsetEntry ::=
   SEQUENCE
      {
      er1645v2ApsBSnmpIndexOffsetGlobalIx
         GlobalIndex,
      er1645v2ApsBSnmpIndexOffsetValue
         Integer32
      }

er1645v2ApsBSnmpIndexOffsetGlobalIx OBJECT-TYPE
   SYNTAX      GlobalIndex
   MAX-ACCESS  not-accessible
   STATUS      current
   DESCRIPTION
      "The value of the tlsCntTreeGlobalIndex of the MANAGED OBJECT."
   ::= {er1645v2ApsBSnmpIndexOffsetEntry 10}

er1645v2ApsBSnmpIndexOffsetValue OBJECT-TYPE
   SYNTAX      Integer32
   MAX-ACCESS  read-write
   STATUS      current
   DESCRIPTION
      "Path: apsBundle.editConf.snmpIndexOffset"
   ::= {er1645v2ApsBSnmpIndexOffsetEntry 2147483648}


er1645v2ApsBAps OBJECT IDENTIFIER ::= {er1645v2ApsB 90}

er1645v2ApsBApsSSCTable OBJECT-TYPE
   SYNTAX      SEQUENCE OF Er1645v2ApsBApsEntry
   MAX-ACCESS  not-accessible
   STATUS      current
   DESCRIPTION
      "APS configuration parameters"
   ::= {er1645v2ApsBAps 1}

er1645v2ApsBApsEntry OBJECT-TYPE
   SYNTAX      Er1645v2ApsBApsEntry
   MAX-ACCESS  not-accessible
   STATUS      current
   DESCRIPTION
      ""
   INDEX      { er1645v2ApsBApsGlobalIx }
   ::= {er1645v2ApsBApsSSCTable 1}

Er1645v2ApsBApsEntry ::=
   SEQUENCE
      {
      er1645v2ApsBApsGlobalIx
         GlobalIndex,
      er1645v2ApsBApsMode
         INTEGER,
      er1645v2ApsBApsRevertive
         INTEGER,
      er1645v2ApsBApsWaitToRestorePeriod
         TimeTicks,
      er1645v2ApsBApsHoldOffTime
         Integer32,
      er1645v2ApsBApsBridgeType
         INTEGER
      }

er1645v2ApsBApsGlobalIx OBJECT-TYPE
   SYNTAX      GlobalIndex
   MAX-ACCESS  not-accessible
   STATUS      current
   DESCRIPTION
      "The value of the tlsCntTreeGlobalIndex of the MANAGED OBJECT."
   ::= {er1645v2ApsBApsEntry 10}

er1645v2ApsBApsMode OBJECT-TYPE
   SYNTAX      INTEGER
               {
               s1p1sbidirectional (0),
               s1p1sunidirectional (1),
               s11sbidirectional (2)
               }
   MAX-ACCESS  read-write
   STATUS      current
   DESCRIPTION
      "Path: apsBundle.editConf.aps.mode

       Possibilities:
               1+1 bidirectional   (0)
               1+1 unidirectional   (1)
               1:1 bidirectional   (2)"
   ::= {er1645v2ApsBApsEntry 16777216}

er1645v2ApsBApsRevertive OBJECT-TYPE
   SYNTAX      INTEGER
               {
               no (0),
               yes (1)
               }
   MAX-ACCESS  read-write
   STATUS      current
   DESCRIPTION
      "Path: apsBundle.editConf.aps.revertive

       Possibilities:
               no   (0)
               yes   (1)"
   ::= {er1645v2ApsBApsEntry 33554432}

er1645v2ApsBApsWaitToRestorePeriod OBJECT-TYPE
   SYNTAX      TimeTicks
   MAX-ACCESS  read-write
   STATUS      current
   DESCRIPTION
      "Path: apsBundle.editConf.aps.waitToRestorePeriod

       Time in centi-second."
   ::= {er1645v2ApsBApsEntry 50331648}

er1645v2ApsBApsHoldOffTime OBJECT-TYPE
   SYNTAX      Integer32
   UNITS       "100msec"
   MAX-ACCESS  read-write
   STATUS      current
   DESCRIPTION
      "Path: apsBundle.editConf.aps.holdOffTime

       unit name = 100msec"
   ::= {er1645v2ApsBApsEntry 67108864}

er1645v2ApsBApsBridgeType OBJECT-TYPE
   SYNTAX      INTEGER
               {
               selector (0),
               broadcast (1)
               }
   MAX-ACCESS  read-write
   STATUS      current
   DESCRIPTION
      "Path: apsBundle.editConf.aps.bridgeType

       Possibilities:
               selector   (0)
               broadcast   (1)"
   ::= {er1645v2ApsBApsEntry 83886080}


er1645v2ApsBMembers OBJECT IDENTIFIER ::= {er1645v2ApsB 91}

er1645v2ApsBMembersSSCTable OBJECT-TYPE
   SYNTAX      SEQUENCE OF Er1645v2ApsBMembersEntry
   MAX-ACCESS  not-accessible
   STATUS      current
   DESCRIPTION
      "APS member list"
   ::= {er1645v2ApsBMembers 1}

er1645v2ApsBMembersEntry OBJECT-TYPE
   SYNTAX      Er1645v2ApsBMembersEntry
   MAX-ACCESS  not-accessible
   STATUS      current
   DESCRIPTION
      ""
   INDEX      { er1645v2ApsBMembersGlobalIx }
   ::= {er1645v2ApsBMembersSSCTable 1}

Er1645v2ApsBMembersEntry ::=
   SEQUENCE
      {
      er1645v2ApsBMembersGlobalIx
         GlobalIndex,
      er1645v2ApsBMembersWorkingInterface
         DisplayString,
      er1645v2ApsBMembersProtectionInterface
         DisplayString
      }

er1645v2ApsBMembersGlobalIx OBJECT-TYPE
   SYNTAX      GlobalIndex
   MAX-ACCESS  not-accessible
   STATUS      current
   DESCRIPTION
      "The value of the tlsCntTreeGlobalIndex of the MANAGED OBJECT."
   ::= {er1645v2ApsBMembersEntry 10}

er1645v2ApsBMembersWorkingInterface OBJECT-TYPE
   SYNTAX      DisplayString
   MAX-ACCESS  read-write
   STATUS      current
   DESCRIPTION
      "Path: apsBundle.editConf.members.workingInterface"
   ::= {er1645v2ApsBMembersEntry 16777216}

er1645v2ApsBMembersProtectionInterface OBJECT-TYPE
   SYNTAX      DisplayString
   MAX-ACCESS  read-write
   STATUS      current
   DESCRIPTION
      "Path: apsBundle.editConf.members.protectionInterface"
   ::= {er1645v2ApsBMembersEntry 33554432}


er1645v2ApsBBrC OBJECT IDENTIFIER ::= {er1645v2ApsB 27}

er1645v2ApsBBrCSSCTable OBJECT-TYPE
   SYNTAX      SEQUENCE OF Er1645v2ApsBBrCEntry
   MAX-ACCESS  not-accessible
   STATUS      current
   DESCRIPTION
      "Set bridging parameters"
   ::= {er1645v2ApsBBrC 1}

er1645v2ApsBBrCEntry OBJECT-TYPE
   SYNTAX      Er1645v2ApsBBrCEntry
   MAX-ACCESS  not-accessible
   STATUS      current
   DESCRIPTION
      ""
   INDEX      { er1645v2ApsBBrCGlobalIx }
   ::= {er1645v2ApsBBrCSSCTable 1}

Er1645v2ApsBBrCEntry ::=
   SEQUENCE
      {
      er1645v2ApsBBrCGlobalIx
         GlobalIndex,
      er1645v2ApsBBrCAccessList
         DisplayString,
      er1645v2ApsBBrCInAccessList
         DisplayString,
      er1645v2ApsBBrCTp
         DisplayString,
      er1645v2ApsBBrCBridgeGroup
         DisplayString,
      er1645v2ApsBBrCLimBC
         INTEGER,
      er1645v2ApsBBrCPrivateMode
         INTEGER,
      er1645v2ApsBBrCLearning
         INTEGER,
      er1645v2ApsBBrCMaxCacheSize
         INTEGER,
      er1645v2ApsBBrCRelearnDropOnRelearn
         INTEGER,
      er1645v2ApsBBrCRelearnShutdownThreshold
         Integer32,
      er1645v2ApsBBrCRelearnShutdownTime
         TimeTicks,
      er1645v2ApsBBrCRelearnLoopDetection
         INTEGER,
      er1645v2ApsBBrCRelearnLoopDetectionInterval
         TimeTicks,
      er1645v2ApsBBrCVlanMemberShip
         INTEGER,
      er1645v2ApsBBrCDot1adType
         INTEGER,
      er1645v2ApsBBrCPriority
         Integer32,
      er1645v2ApsBBrCPathCost
         Integer32,
      er1645v2ApsBBrCInternalPathCost
         Integer32,
      er1645v2ApsBBrCTCD
         INTEGER,
      er1645v2ApsBBrCRestrictedRole
         INTEGER,
      er1645v2ApsBBrCAdminEdge
         INTEGER,
      er1645v2ApsBBrCMgmtInline
         INTEGER,
      er1645v2ApsBBrCL2ptMode
         INTEGER,
      er1645v2ApsBBrCL2ptProtocols
         Integer32,
      er1645v2ApsBBrCL2ptDestMac
         OCTET STRING,
      er1645v2ApsBBrCL2ptCos
         INTEGER,
      er1645v2ApsBBrCL2ptDropThrStp
         INTEGER,
      er1645v2ApsBBrCL2ptDropThrLldp
         INTEGER,
      er1645v2ApsBBrCL2ptDropThrOam
         INTEGER,
      er1645v2ApsBBrCL2ptDropThrCdp
         INTEGER,
      er1645v2ApsBBrCL2ptDropThrVtp
         INTEGER,
      er1645v2ApsBBrCL2ptDropThrLacp
         INTEGER,
      er1645v2ApsBBrCL2ptDropThrEfmOam
         INTEGER,
      er1645v2ApsBBrCL2ptDropThrPvst
         INTEGER,
      er1645v2ApsBBrCL2ptDropThrMmrp
         INTEGER,
      er1645v2ApsBBrCL2ptDropThrMvrp
         INTEGER,
      er1645v2ApsBBrCL2ptDropThrGvrp
         INTEGER,
      er1645v2ApsBBrCL2ptDropThrGmrp
         INTEGER,
      er1645v2ApsBBrCL2ptDropThrDtp
         INTEGER,
      er1645v2ApsBBrCL2ptDropThrPagp
         INTEGER,
      er1645v2ApsBBrCL2ptDropThrUdld
         INTEGER
      }

er1645v2ApsBBrCGlobalIx OBJECT-TYPE
   SYNTAX      GlobalIndex
   MAX-ACCESS  not-accessible
   STATUS      current
   DESCRIPTION
      "The value of the tlsCntTreeGlobalIndex of the MANAGED OBJECT."
   ::= {er1645v2ApsBBrCEntry 10}

er1645v2ApsBBrCAccessList OBJECT-TYPE
   SYNTAX      DisplayString
   MAX-ACCESS  read-write
   STATUS      current
   DESCRIPTION
      "Path: apsBundle.editConf.bridging.accessList"
   ::= {er1645v2ApsBBrCEntry 83886080}

er1645v2ApsBBrCInAccessList OBJECT-TYPE
   SYNTAX      DisplayString
   MAX-ACCESS  read-write
   STATUS      current
   DESCRIPTION
      "Path: apsBundle.editConf.bridging.inAccessList"
   ::= {er1645v2ApsBBrCEntry 251658240}

er1645v2ApsBBrCTp OBJECT-TYPE
   SYNTAX      DisplayString
   MAX-ACCESS  read-write
   STATUS      current
   DESCRIPTION
      "Path: apsBundle.editConf.bridging.trafficPolicy"
   ::= {er1645v2ApsBBrCEntry 100663296}

er1645v2ApsBBrCBridgeGroup OBJECT-TYPE
   SYNTAX      DisplayString
   MAX-ACCESS  read-write
   STATUS      current
   DESCRIPTION
      "Path: apsBundle.editConf.bridging.bridgeGroup"
   ::= {er1645v2ApsBBrCEntry 117440512}

er1645v2ApsBBrCLimBC OBJECT-TYPE
   SYNTAX      INTEGER
               {
               disabled (0),
               enabled (1)
               }
   MAX-ACCESS  read-write
   STATUS      current
   DESCRIPTION
      "Path: apsBundle.editConf.bridging.limitBroadcasts

       Possibilities:
               disabled   (0)
               enabled   (1)"
   ::= {er1645v2ApsBBrCEntry 134217728}

er1645v2ApsBBrCPrivateMode OBJECT-TYPE
   SYNTAX      INTEGER
               {
               disabled (0),
               enabled (1)
               }
   MAX-ACCESS  read-write
   STATUS      current
   DESCRIPTION
      "Path: apsBundle.editConf.bridging.privateMode

       Possibilities:
               disabled   (0)
               enabled   (1)"
   ::= {er1645v2ApsBBrCEntry 419430400}

er1645v2ApsBBrCLearning OBJECT-TYPE
   SYNTAX      INTEGER
               {
               disabled (0),
               enabled (1)
               }
   MAX-ACCESS  read-write
   STATUS      current
   DESCRIPTION
      "Path: apsBundle.editConf.bridging.learning

       Possibilities:
               disabled   (0)
               enabled   (1)"
   ::= {er1645v2ApsBBrCEntry 201326592}

er1645v2ApsBBrCMaxCacheSize OBJECT-TYPE
   SYNTAX      INTEGER
               {
               unlimited (0)
               }
   MAX-ACCESS  read-write
   STATUS      current
   DESCRIPTION
      "Path: apsBundle.editConf.bridging.maxCacheSize

       Possibilities:
               unlimited   (0)"
   ::= {er1645v2ApsBBrCEntry 218103808}

er1645v2ApsBBrCRelearnDropOnRelearn OBJECT-TYPE
   SYNTAX      INTEGER
               {
               disabled (0),
               enabled (1)
               }
   MAX-ACCESS  read-write
   STATUS      current
   DESCRIPTION
      "Path: apsBundle.editConf.bridging.relearn.dropOnRelearn

       Possibilities:
               disabled   (0)
               enabled   (1)"
   ::= {er1645v2ApsBBrCEntry 234946560}

er1645v2ApsBBrCRelearnShutdownThreshold OBJECT-TYPE
   SYNTAX      Integer32
   MAX-ACCESS  read-write
   STATUS      current
   DESCRIPTION
      "Path: apsBundle.editConf.bridging.relearn.shutdownThreshold"
   ::= {er1645v2ApsBBrCEntry 235012096}

er1645v2ApsBBrCRelearnShutdownTime OBJECT-TYPE
   SYNTAX      TimeTicks
   MAX-ACCESS  read-write
   STATUS      current
   DESCRIPTION
      "Path: apsBundle.editConf.bridging.relearn.shutdownTime

       Time in centi-second."
   ::= {er1645v2ApsBBrCEntry 235077632}

er1645v2ApsBBrCRelearnLoopDetection OBJECT-TYPE
   SYNTAX      INTEGER
               {
               disabled (0),
               passive (1),
               active (2)
               }
   MAX-ACCESS  read-write
   STATUS      current
   DESCRIPTION
      "Path: apsBundle.editConf.bridging.relearn.loopDetection

       Possibilities:
               disabled   (0)
               passive   (1)
               active   (2)"
   ::= {er1645v2ApsBBrCEntry 235143168}

er1645v2ApsBBrCRelearnLoopDetectionInterval OBJECT-TYPE
   SYNTAX      TimeTicks
   MAX-ACCESS  read-write
   STATUS      current
   DESCRIPTION
      "Path: apsBundle.editConf.bridging.relearn.loopDetectionInterval

       Time in centi-second."
   ::= {er1645v2ApsBBrCEntry 235208704}

er1645v2ApsBBrCVlanMemberShip OBJECT-TYPE
   SYNTAX      INTEGER
               {
               all (0),
               none (1),
               grouped (2)
               }
   MAX-ACCESS  read-write
   STATUS      current
   DESCRIPTION
      "Path: apsBundle.editConf.bridging.vlanMemberShip

       Possibilities:
               all   (0)
               none   (1)
               grouped   (2)"
   ::= {er1645v2ApsBBrCEntry 318767104}

er1645v2ApsBBrCDot1adType OBJECT-TYPE
   SYNTAX      INTEGER
               {
               slOPTg (0),
               cPort (4),
               sPort (1),
               nni (2)
               }
   MAX-ACCESS  read-write
   STATUS      current
   DESCRIPTION
      "Path: apsBundle.editConf.bridging.dot1ad.type

       Possibilities:
               <OPT>   (0)
               cPort   (4)
               sPort   (1)
               nni   (2)"
   ::= {er1645v2ApsBBrCEntry 503382016}

er1645v2ApsBBrCPriority OBJECT-TYPE
   SYNTAX      Integer32
   MAX-ACCESS  read-write
   STATUS      current
   DESCRIPTION
      "Path: apsBundle.editConf.bridging.priority"
   ::= {er1645v2ApsBBrCEntry 33554432}

er1645v2ApsBBrCPathCost OBJECT-TYPE
   SYNTAX      Integer32
   MAX-ACCESS  read-write
   STATUS      current
   DESCRIPTION
      "Path: apsBundle.editConf.bridging.pathCost"
   ::= {er1645v2ApsBBrCEntry 50331648}

er1645v2ApsBBrCInternalPathCost OBJECT-TYPE
   SYNTAX      Integer32
   MAX-ACCESS  read-write
   STATUS      current
   DESCRIPTION
      "Path: apsBundle.editConf.bridging.internalPathCost"
   ::= {er1645v2ApsBBrCEntry 301989888}

er1645v2ApsBBrCTCD OBJECT-TYPE
   SYNTAX      INTEGER
               {
               disabled (0),
               enabled (1)
               }
   MAX-ACCESS  read-write
   STATUS      current
   DESCRIPTION
      "Path: apsBundle.editConf.bridging.topologyChangeDetection

       Possibilities:
               disabled   (0)
               enabled   (1)"
   ::= {er1645v2ApsBBrCEntry 67108864}

er1645v2ApsBBrCRestrictedRole OBJECT-TYPE
   SYNTAX      INTEGER
               {
               disabled (0),
               enabled (1)
               }
   MAX-ACCESS  read-write
   STATUS      current
   DESCRIPTION
      "Path: apsBundle.editConf.bridging.restrictedRole

       Possibilities:
               disabled   (0)
               enabled   (1)"
   ::= {er1645v2ApsBBrCEntry 335544320}

er1645v2ApsBBrCAdminEdge OBJECT-TYPE
   SYNTAX      INTEGER
               {
               disabled (0),
               enabled (1)
               }
   MAX-ACCESS  read-write
   STATUS      current
   DESCRIPTION
      "Path: apsBundle.editConf.bridging.adminEdge

       Possibilities:
               disabled   (0)
               enabled   (1)"
   ::= {er1645v2ApsBBrCEntry 268435456}

er1645v2ApsBBrCMgmtInline OBJECT-TYPE
   SYNTAX      INTEGER
               {
               disabled (0),
               enabled (1)
               }
   MAX-ACCESS  read-write
   STATUS      current
   DESCRIPTION
      "Path: apsBundle.editConf.bridging.mgmtInline

       Possibilities:
               disabled   (0)
               enabled   (1)"
   ::= {er1645v2ApsBBrCEntry 369098752}

er1645v2ApsBBrCL2ptMode OBJECT-TYPE
   SYNTAX      INTEGER
               {
               disabled (0),
               enabled (1)
               }
   MAX-ACCESS  read-write
   STATUS      current
   DESCRIPTION
      "Path: apsBundle.editConf.bridging.l2ProtTunnel.mode

       Possibilities:
               disabled   (0)
               enabled   (1)"
   ::= {er1645v2ApsBBrCEntry 403701760}

er1645v2ApsBBrCL2ptProtocols OBJECT-TYPE
   SYNTAX      Integer32
   MAX-ACCESS  read-write
   STATUS      current
   DESCRIPTION
      "Path: apsBundle.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2ApsBBrCEntry 404750336}

er1645v2ApsBBrCL2ptDestMac OBJECT-TYPE
   SYNTAX      OCTET STRING
   MAX-ACCESS  read-write
   STATUS      current
   DESCRIPTION
      "Path: apsBundle.editConf.bridging.l2ProtTunnel.destinationMac

       MAC address."
   ::= {er1645v2ApsBBrCEntry 405798912}

er1645v2ApsBBrCL2ptCos OBJECT-TYPE
   SYNTAX      INTEGER
               {
               unchanged (255)
               }
   MAX-ACCESS  read-write
   STATUS      current
   DESCRIPTION
      "Path: apsBundle.editConf.bridging.l2ProtTunnel.cos

       Possibilities:
               unchanged   (255)"
   ::= {er1645v2ApsBBrCEntry 406847488}

er1645v2ApsBBrCL2ptDropThrStp OBJECT-TYPE
   SYNTAX      INTEGER
               {
               unlimited (0)
               }
   UNITS       "packets/sec"
   MAX-ACCESS  read-write
   STATUS      current
   DESCRIPTION
      "Path: apsBundle.editConf.bridging.l2ProtTunnel.dropThresholds.stp

       unit name = packets/sec

       Possibilities:
               unlimited   (0)"
   ::= {er1645v2ApsBBrCEntry 407900160}

er1645v2ApsBBrCL2ptDropThrLldp OBJECT-TYPE
   SYNTAX      INTEGER
               {
               unlimited (0)
               }
   UNITS       "packets/sec"
   MAX-ACCESS  read-write
   STATUS      current
   DESCRIPTION
      "Path: apsBundle.editConf.bridging.l2ProtTunnel.dropThresholds.lldp

       unit name = packets/sec

       Possibilities:
               unlimited   (0)"
   ::= {er1645v2ApsBBrCEntry 407904256}

er1645v2ApsBBrCL2ptDropThrOam OBJECT-TYPE
   SYNTAX      INTEGER
               {
               unlimited (0)
               }
   UNITS       "packets/sec"
   MAX-ACCESS  read-write
   STATUS      current
   DESCRIPTION
      "Path: apsBundle.editConf.bridging.l2ProtTunnel.dropThresholds.oam

       unit name = packets/sec

       Possibilities:
               unlimited   (0)"
   ::= {er1645v2ApsBBrCEntry 407908352}

er1645v2ApsBBrCL2ptDropThrCdp OBJECT-TYPE
   SYNTAX      INTEGER
               {
               unlimited (0)
               }
   UNITS       "packets/sec"
   MAX-ACCESS  read-write
   STATUS      current
   DESCRIPTION
      "Path: apsBundle.editConf.bridging.l2ProtTunnel.dropThresholds.cdp

       unit name = packets/sec

       Possibilities:
               unlimited   (0)"
   ::= {er1645v2ApsBBrCEntry 407912448}

er1645v2ApsBBrCL2ptDropThrVtp OBJECT-TYPE
   SYNTAX      INTEGER
               {
               unlimited (0)
               }
   UNITS       "packets/sec"
   MAX-ACCESS  read-write
   STATUS      current
   DESCRIPTION
      "Path: apsBundle.editConf.bridging.l2ProtTunnel.dropThresholds.vtp

       unit name = packets/sec

       Possibilities:
               unlimited   (0)"
   ::= {er1645v2ApsBBrCEntry 407916544}

er1645v2ApsBBrCL2ptDropThrLacp OBJECT-TYPE
   SYNTAX      INTEGER
               {
               unlimited (0)
               }
   UNITS       "packets/sec"
   MAX-ACCESS  read-write
   STATUS      current
   DESCRIPTION
      "Path: apsBundle.editConf.bridging.l2ProtTunnel.dropThresholds.lacp

       unit name = packets/sec

       Possibilities:
               unlimited   (0)"
   ::= {er1645v2ApsBBrCEntry 407920640}

er1645v2ApsBBrCL2ptDropThrEfmOam OBJECT-TYPE
   SYNTAX      INTEGER
               {
               unlimited (0)
               }
   UNITS       "packets/sec"
   MAX-ACCESS  read-write
   STATUS      current
   DESCRIPTION
      "Path: apsBundle.editConf.bridging.l2ProtTunnel.dropThresholds.efmOam

       unit name = packets/sec

       Possibilities:
               unlimited   (0)"
   ::= {er1645v2ApsBBrCEntry 407924736}

er1645v2ApsBBrCL2ptDropThrPvst OBJECT-TYPE
   SYNTAX      INTEGER
               {
               unlimited (0)
               }
   UNITS       "packets/sec"
   MAX-ACCESS  read-write
   STATUS      current
   DESCRIPTION
      "Path: apsBundle.editConf.bridging.l2ProtTunnel.dropThresholds.pvst

       unit name = packets/sec

       Possibilities:
               unlimited   (0)"
   ::= {er1645v2ApsBBrCEntry 407928832}

er1645v2ApsBBrCL2ptDropThrMmrp OBJECT-TYPE
   SYNTAX      INTEGER
               {
               unlimited (0)
               }
   UNITS       "packets/sec"
   MAX-ACCESS  read-write
   STATUS      current
   DESCRIPTION
      "Path: apsBundle.editConf.bridging.l2ProtTunnel.dropThresholds.mmrp

       unit name = packets/sec

       Possibilities:
               unlimited   (0)"
   ::= {er1645v2ApsBBrCEntry 407932928}

er1645v2ApsBBrCL2ptDropThrMvrp OBJECT-TYPE
   SYNTAX      INTEGER
               {
               unlimited (0)
               }
   UNITS       "packets/sec"
   MAX-ACCESS  read-write
   STATUS      current
   DESCRIPTION
      "Path: apsBundle.editConf.bridging.l2ProtTunnel.dropThresholds.mvrp

       unit name = packets/sec

       Possibilities:
               unlimited   (0)"
   ::= {er1645v2ApsBBrCEntry 407937024}

er1645v2ApsBBrCL2ptDropThrGvrp OBJECT-TYPE
   SYNTAX      INTEGER
               {
               unlimited (0)
               }
   UNITS       "packets/sec"
   MAX-ACCESS  read-write
   STATUS      current
   DESCRIPTION
      "Path: apsBundle.editConf.bridging.l2ProtTunnel.dropThresholds.gvrp

       unit name = packets/sec

       Possibilities:
               unlimited   (0)"
   ::= {er1645v2ApsBBrCEntry 407941120}

er1645v2ApsBBrCL2ptDropThrGmrp OBJECT-TYPE
   SYNTAX      INTEGER
               {
               unlimited (0)
               }
   UNITS       "packets/sec"
   MAX-ACCESS  read-write
   STATUS      current
   DESCRIPTION
      "Path: apsBundle.editConf.bridging.l2ProtTunnel.dropThresholds.gmrp

       unit name = packets/sec

       Possibilities:
               unlimited   (0)"
   ::= {er1645v2ApsBBrCEntry 407945216}

er1645v2ApsBBrCL2ptDropThrDtp OBJECT-TYPE
   SYNTAX      INTEGER
               {
               unlimited (0)
               }
   UNITS       "packets/sec"
   MAX-ACCESS  read-write
   STATUS      current
   DESCRIPTION
      "Path: apsBundle.editConf.bridging.l2ProtTunnel.dropThresholds.dtp

       unit name = packets/sec

       Possibilities:
               unlimited   (0)"
   ::= {er1645v2ApsBBrCEntry 407949312}

er1645v2ApsBBrCL2ptDropThrPagp OBJECT-TYPE
   SYNTAX      INTEGER
               {
               unlimited (0)
               }
   UNITS       "packets/sec"
   MAX-ACCESS  read-write
   STATUS      current
   DESCRIPTION
      "Path: apsBundle.editConf.bridging.l2ProtTunnel.dropThresholds.pagp

       unit name = packets/sec

       Possibilities:
               unlimited   (0)"
   ::= {er1645v2ApsBBrCEntry 407953408}

er1645v2ApsBBrCL2ptDropThrUdld OBJECT-TYPE
   SYNTAX      INTEGER
               {
               unlimited (0)
               }
   UNITS       "packets/sec"
   MAX-ACCESS  read-write
   STATUS      current
   DESCRIPTION
      "Path: apsBundle.editConf.bridging.l2ProtTunnel.dropThresholds.udld

       unit name = packets/sec

       Possibilities:
               unlimited   (0)"
   ::= {er1645v2ApsBBrCEntry 407957504}


er1645v2ApsBVlanTagging OBJECT IDENTIFIER ::= {er1645v2ApsB 14}

er1645v2ApsBVlanTaggingSSCTable OBJECT-TYPE
   SYNTAX      SEQUENCE OF Er1645v2ApsBVlanTaggingEntry
   MAX-ACCESS  not-accessible
   STATUS      current
   DESCRIPTION
      "vlan tagging config"
   ::= {er1645v2ApsBVlanTagging 1}

er1645v2ApsBVlanTaggingEntry OBJECT-TYPE
   SYNTAX      Er1645v2ApsBVlanTaggingEntry
   MAX-ACCESS  not-accessible
   STATUS      current
   DESCRIPTION
      ""
   INDEX      { er1645v2ApsBVlanTaggingGlobalIx }
   ::= {er1645v2ApsBVlanTaggingSSCTable 1}

Er1645v2ApsBVlanTaggingEntry ::=
   SEQUENCE
      {
      er1645v2ApsBVlanTaggingGlobalIx
         GlobalIndex,
      er1645v2ApsBVlanTaggingUntaggedAction
         INTEGER,
      er1645v2ApsBVlanTaggingUntaggedTagInfoTpid
         INTEGER,
      er1645v2ApsBVlanTaggingUntaggedTagInfoVid
         Integer32,
      er1645v2ApsBVlanTaggingUnknownVlansAction
         INTEGER,
      er1645v2ApsBVlanTaggingUnknownVlansTagInfoTpid
         INTEGER,
      er1645v2ApsBVlanTaggingUnknownVlansTagInfoVid
         Integer32
      }

er1645v2ApsBVlanTaggingGlobalIx OBJECT-TYPE
   SYNTAX      GlobalIndex
   MAX-ACCESS  not-accessible
   STATUS      current
   DESCRIPTION
      "The value of the tlsCntTreeGlobalIndex of the MANAGED OBJECT."
   ::= {er1645v2ApsBVlanTaggingEntry 10}

er1645v2ApsBVlanTaggingUntaggedAction OBJECT-TYPE
   SYNTAX      INTEGER
               {
               discard (0),
               accept (1),
               tag (2)
               }
   MAX-ACCESS  read-write
   STATUS      current
   DESCRIPTION
      "Path: apsBundle.editConf.vlanTagging.untagged.action

       Possibilities:
               discard   (0)
               accept   (1)
               tag   (2)"
   ::= {er1645v2ApsBVlanTaggingEntry 671088640}

er1645v2ApsBVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: apsBundle.editConf.vlanTagging.untagged.tagInfo.tpid

       Possibilities:
               dot1Q   (33024)
               dot1ad   (34984)
               0x9100   (37120)
               0x9200   (37376)
               0x9300   (37632)"
   ::= {er1645v2ApsBVlanTaggingEntry 746586112}

er1645v2ApsBVlanTaggingUntaggedTagInfoVid OBJECT-TYPE
   SYNTAX      Integer32
   MAX-ACCESS  read-write
   STATUS      current
   DESCRIPTION
      "Path: apsBundle.editConf.vlanTagging.untagged.tagInfo.vid"
   ::= {er1645v2ApsBVlanTaggingEntry 754974720}

er1645v2ApsBVlanTaggingUnknownVlansAction OBJECT-TYPE
   SYNTAX      INTEGER
               {
               discard (0),
               accept (1),
               tag (2)
               }
   MAX-ACCESS  read-write
   STATUS      current
   DESCRIPTION
      "Path: apsBundle.editConf.vlanTagging.unknownVlans.action

       Possibilities:
               discard   (0)
               accept   (1)
               tag   (2)"
   ::= {er1645v2ApsBVlanTaggingEntry 1744830464}

er1645v2ApsBVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: apsBundle.editConf.vlanTagging.unknownVlans.tagInfo.tpid

       Possibilities:
               dot1Q   (33024)
               dot1ad   (34984)
               0x9100   (37120)
               0x9200   (37376)
               0x9300   (37632)"
   ::= {er1645v2ApsBVlanTaggingEntry 1820327936}

er1645v2ApsBVlanTaggingUnknownVlansTagInfoVid OBJECT-TYPE
   SYNTAX      Integer32
   MAX-ACCESS  read-write
   STATUS      current
   DESCRIPTION
      "Path: apsBundle.editConf.vlanTagging.unknownVlans.tagInfo.vid"
   ::= {er1645v2ApsBVlanTaggingEntry 1828716544}

er1645v2ApsBVlanTaggingVlans OBJECT-TYPE
   SYNTAX      SEQUENCE OF Er1645v2ApsBVlanTaggingVlansEntry
   MAX-ACCESS  not-accessible
   STATUS      current
   DESCRIPTION
      ""
   ::= {er1645v2ApsBVlanTagging 1073741824}

er1645v2ApsBVlanTaggingVlansEntry OBJECT-TYPE
   SYNTAX      Er1645v2ApsBVlanTaggingVlansEntry
   MAX-ACCESS  not-accessible
   STATUS      current
   DESCRIPTION
      ""
   INDEX      { er1645v2ApsBVlanTaggingVlansGlobalIx,
                er1645v2ApsBVlanTaggingVlansTableIx }
   ::= {er1645v2ApsBVlanTaggingVlans 1}

Er1645v2ApsBVlanTaggingVlansEntry ::=
   SEQUENCE
      {
      er1645v2ApsBVlanTaggingVlansActions
         VariableLengthTableActions,
      er1645v2ApsBVlanTaggingVlansGlobalIx
         GlobalIndex,
      er1645v2ApsBVlanTaggingVlansTableIx
         TableIndex,
      er1645v2ApsBVlanTaggingVlansVid
         Integer32,
      er1645v2ApsBVlanTaggingVlansEndVid
         Integer32,
      er1645v2ApsBVlanTaggingVlansAction
         INTEGER,
      er1645v2ApsBVlanTaggingVlansTagInfoTpid
         INTEGER,
      er1645v2ApsBVlanTaggingVlansTagInfoVid
         Integer32
      }

er1645v2ApsBVlanTaggingVlansActions OBJECT-TYPE
   SYNTAX      VariableLengthTableActions
   MAX-ACCESS  read-write
   STATUS      current
   DESCRIPTION
      "By way of this field, some manipulations
       on this table may be performed."
   ::= {er1645v2ApsBVlanTaggingVlansEntry 2}

er1645v2ApsBVlanTaggingVlansGlobalIx OBJECT-TYPE
   SYNTAX      GlobalIndex
   MAX-ACCESS  not-accessible
   STATUS      current
   DESCRIPTION
      "The value of the tlsCntTreeGlobalIndex of the MANAGED OBJECT."
   ::= {er1645v2ApsBVlanTaggingVlansEntry 10}

er1645v2ApsBVlanTaggingVlansTableIx OBJECT-TYPE
   SYNTAX      TableIndex
   MAX-ACCESS  not-accessible
   STATUS      current
   DESCRIPTION
      ""
   ::= {er1645v2ApsBVlanTaggingVlansEntry 11}

er1645v2ApsBVlanTaggingVlansVid OBJECT-TYPE
   SYNTAX      Integer32
   MAX-ACCESS  read-write
   STATUS      current
   DESCRIPTION
      "Path: apsBundle.editConf.vlanTagging.vlans.vid"
   ::= {er1645v2ApsBVlanTaggingVlansEntry 536870912}

er1645v2ApsBVlanTaggingVlansEndVid OBJECT-TYPE
   SYNTAX      Integer32
   MAX-ACCESS  read-write
   STATUS      current
   DESCRIPTION
      "Path: apsBundle.editConf.vlanTagging.vlans.endVid"
   ::= {er1645v2ApsBVlanTaggingVlansEntry 2147483648}

er1645v2ApsBVlanTaggingVlansAction OBJECT-TYPE
   SYNTAX      INTEGER
               {
               discard (0),
               accept (1),
               tag (2)
               }
   MAX-ACCESS  read-write
   STATUS      current
   DESCRIPTION
      "Path: apsBundle.editConf.vlanTagging.vlans.action

       Possibilities:
               discard   (0)
               accept   (1)
               tag   (2)"
   ::= {er1645v2ApsBVlanTaggingVlansEntry 1073741824}

er1645v2ApsBVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: apsBundle.editConf.vlanTagging.vlans.tagInfo.tpid

       Possibilities:
               dot1Q   (33024)
               dot1ad   (34984)
               0x9100   (37120)
               0x9200   (37376)
               0x9300   (37632)"
   ::= {er1645v2ApsBVlanTaggingVlansEntry 1677721600}

er1645v2ApsBVlanTaggingVlansTagInfoVid OBJECT-TYPE
   SYNTAX      Integer32
   MAX-ACCESS  read-write
   STATUS      current
   DESCRIPTION
      "Path: apsBundle.editConf.vlanTagging.vlans.tagInfo.vid"
   ::= {er1645v2ApsBVlanTaggingVlansEntry 1744830464}


er1645v2ApsBMacAddress OBJECT IDENTIFIER ::= {er1645v2ApsB 201}

er1645v2ApsBMacAddressSSCTable OBJECT-TYPE
   SYNTAX      SEQUENCE OF Er1645v2ApsBMacAddressEntry
   MAX-ACCESS  not-accessible
   STATUS      current
   DESCRIPTION
      "Configurable MAC address of APS bundle"
   ::= {er1645v2ApsBMacAddress 1}

er1645v2ApsBMacAddressEntry OBJECT-TYPE
   SYNTAX      Er1645v2ApsBMacAddressEntry
   MAX-ACCESS  not-accessible
   STATUS      current
   DESCRIPTION
      ""
   INDEX      { er1645v2ApsBMacAddressGlobalIx }
   ::= {er1645v2ApsBMacAddressSSCTable 1}

Er1645v2ApsBMacAddressEntry ::=
   SEQUENCE
      {
      er1645v2ApsBMacAddressGlobalIx
         GlobalIndex,
      er1645v2ApsBMacAddressWorkingIntf
         DisplayString,
      er1645v2ApsBMacAddressProtectionIntf
         DisplayString,
      er1645v2ApsBMacAddressDeviceMac
         DisplayString,
      er1645v2ApsBMacAddressUserMac
         OCTET STRING,
      er1645v2ApsBMacAddressRandomMac
         Integer32
      }

er1645v2ApsBMacAddressGlobalIx OBJECT-TYPE
   SYNTAX      GlobalIndex
   MAX-ACCESS  not-accessible
   STATUS      current
   DESCRIPTION
      "The value of the tlsCntTreeGlobalIndex of the MANAGED OBJECT."
   ::= {er1645v2ApsBMacAddressEntry 10}

er1645v2ApsBMacAddressWorkingIntf OBJECT-TYPE
   SYNTAX      DisplayString
   MAX-ACCESS  read-write
   STATUS      current
   DESCRIPTION
      "Path: apsBundle.editConf.macAddress.workingIntf"
   ::= {er1645v2ApsBMacAddressEntry 100663296}

er1645v2ApsBMacAddressProtectionIntf OBJECT-TYPE
   SYNTAX      DisplayString
   MAX-ACCESS  read-write
   STATUS      current
   DESCRIPTION
      "Path: apsBundle.editConf.macAddress.protectionIntf"
   ::= {er1645v2ApsBMacAddressEntry 117440512}

er1645v2ApsBMacAddressDeviceMac OBJECT-TYPE
   SYNTAX      DisplayString
   MAX-ACCESS  read-write
   STATUS      current
   DESCRIPTION
      "Path: apsBundle.editConf.macAddress.deviceMac"
   ::= {er1645v2ApsBMacAddressEntry 50331648}

er1645v2ApsBMacAddressUserMac OBJECT-TYPE
   SYNTAX      OCTET STRING
   MAX-ACCESS  read-write
   STATUS      current
   DESCRIPTION
      "Path: apsBundle.editConf.macAddress.userMac

       MAC address."
   ::= {er1645v2ApsBMacAddressEntry 33554432}

er1645v2ApsBMacAddressRandomMac OBJECT-TYPE
   SYNTAX      Integer32
   MAX-ACCESS  read-write
   STATUS      current
   DESCRIPTION
      "Path: apsBundle.editConf.macAddress.randomMac"
   ::= {er1645v2ApsBMacAddressEntry 67108864}


er1645v2ApsBBridgeCacheDistribution OBJECT IDENTIFIER ::= {er1645v2ApsB 92}

er1645v2ApsBBridgeCacheDistributionSSCTable OBJECT-TYPE
   SYNTAX      SEQUENCE OF Er1645v2ApsBBridgeCacheDistributionEntry
   MAX-ACCESS  not-accessible
   STATUS      current
   DESCRIPTION
      "APS bridge cache distribution table"
   ::= {er1645v2ApsBBridgeCacheDistribution 1}

er1645v2ApsBBridgeCacheDistributionEntry OBJECT-TYPE
   SYNTAX      Er1645v2ApsBBridgeCacheDistributionEntry
   MAX-ACCESS  not-accessible
   STATUS      current
   DESCRIPTION
      ""
   INDEX      { er1645v2ApsBBridgeCacheDistributionGlobalIx,
                er1645v2ApsBBridgeCacheDistributionTableIx }
   ::= {er1645v2ApsBBridgeCacheDistributionSSCTable 1}

Er1645v2ApsBBridgeCacheDistributionEntry ::=
   SEQUENCE
      {
      er1645v2ApsBBridgeCacheDistributionActions
         VariableLengthTableActions,
      er1645v2ApsBBridgeCacheDistributionGlobalIx
         GlobalIndex,
      er1645v2ApsBBridgeCacheDistributionTableIx
         TableIndex,
      er1645v2ApsBBridgeCacheDistributionDestinationMac
         OCTET STRING,
      er1645v2ApsBBridgeCacheDistributionType
         INTEGER
      }

er1645v2ApsBBridgeCacheDistributionActions OBJECT-TYPE
   SYNTAX      VariableLengthTableActions
   MAX-ACCESS  read-write
   STATUS      current
   DESCRIPTION
      "By way of this field, some manipulations
       on this table may be performed."
   ::= {er1645v2ApsBBridgeCacheDistributionEntry 2}

er1645v2ApsBBridgeCacheDistributionGlobalIx OBJECT-TYPE
   SYNTAX      GlobalIndex
   MAX-ACCESS  not-accessible
   STATUS      current
   DESCRIPTION
      "The value of the tlsCntTreeGlobalIndex of the MANAGED OBJECT."
   ::= {er1645v2ApsBBridgeCacheDistributionEntry 10}

er1645v2ApsBBridgeCacheDistributionTableIx OBJECT-TYPE
   SYNTAX      TableIndex
   MAX-ACCESS  not-accessible
   STATUS      current
   DESCRIPTION
      ""
   ::= {er1645v2ApsBBridgeCacheDistributionEntry 11}

er1645v2ApsBBridgeCacheDistributionDestinationMac OBJECT-TYPE
   SYNTAX      OCTET STRING
   MAX-ACCESS  read-write
   STATUS      current
   DESCRIPTION
      "Path: apsBundle.editConf.bridgeCacheDistribution.destinationMac

       MAC address."
   ::= {er1645v2ApsBBridgeCacheDistributionEntry 16777216}

er1645v2ApsBBridgeCacheDistributionType OBJECT-TYPE
   SYNTAX      INTEGER
               {
               arp (2054)
               }
   MAX-ACCESS  read-write
   STATUS      current
   DESCRIPTION
      "Path: apsBundle.editConf.bridgeCacheDistribution.type

       Possibilities:
               arp   (2054)"
   ::= {er1645v2ApsBBridgeCacheDistributionEntry 33554432}



pr1645v2ApsB OBJECT IDENTIFIER ::= {r1645v2ApsB 12}


pr1645v2ApsBInOctets OBJECT IDENTIFIER ::= {pr1645v2ApsB 109}

pr1645v2ApsBInOctetsTable OBJECT-TYPE
   SYNTAX      SEQUENCE OF Pr1645v2ApsBInOctetsEntry
   MAX-ACCESS  not-accessible
   STATUS      current
   DESCRIPTION
      "ifInOctets"
   ::= {pr1645v2ApsBInOctets 1}

pr1645v2ApsBInOctetsEntry OBJECT-TYPE
   SYNTAX      Pr1645v2ApsBInOctetsEntry
   MAX-ACCESS  not-accessible
   STATUS      current
   DESCRIPTION
      ""
   INDEX      { pr1645v2ApsBInOctetsGlobalIx }
   ::= {pr1645v2ApsBInOctetsTable 1}

Pr1645v2ApsBInOctetsEntry ::=
   SEQUENCE
      {
      pr1645v2ApsBInOctetsGlobalIx
         GlobalIndex,
      pr1645v2ApsBInOctetsValue
         Counter64
      }

pr1645v2ApsBInOctetsGlobalIx OBJECT-TYPE
   SYNTAX      GlobalIndex
   MAX-ACCESS  not-accessible
   STATUS      current
   DESCRIPTION
      "The value of the tlsCntTreeGlobalIndex of the MANAGED OBJECT."
   ::= {pr1645v2ApsBInOctetsEntry 10}

pr1645v2ApsBInOctetsValue OBJECT-TYPE
   SYNTAX      Counter64
   MAX-ACCESS  read-only
   STATUS      current
   DESCRIPTION
      "Path: apsBundle.performance.ifInOctets

       64 bit unsigned wrappable counter."
   ::= {pr1645v2ApsBInOctetsEntry 2147483648}


pr1645v2ApsBInUcast OBJECT IDENTIFIER ::= {pr1645v2ApsB 110}

pr1645v2ApsBInUcastTable OBJECT-TYPE
   SYNTAX      SEQUENCE OF Pr1645v2ApsBInUcastEntry
   MAX-ACCESS  not-accessible
   STATUS      current
   DESCRIPTION
      "ifInUcastPkts"
   ::= {pr1645v2ApsBInUcast 1}

pr1645v2ApsBInUcastEntry OBJECT-TYPE
   SYNTAX      Pr1645v2ApsBInUcastEntry
   MAX-ACCESS  not-accessible
   STATUS      current
   DESCRIPTION
      ""
   INDEX      { pr1645v2ApsBInUcastGlobalIx }
   ::= {pr1645v2ApsBInUcastTable 1}

Pr1645v2ApsBInUcastEntry ::=
   SEQUENCE
      {
      pr1645v2ApsBInUcastGlobalIx
         GlobalIndex,
      pr1645v2ApsBInUcastValue
         Counter64
      }

pr1645v2ApsBInUcastGlobalIx OBJECT-TYPE
   SYNTAX      GlobalIndex
   MAX-ACCESS  not-accessible
   STATUS      current
   DESCRIPTION
      "The value of the tlsCntTreeGlobalIndex of the MANAGED OBJECT."
   ::= {pr1645v2ApsBInUcastEntry 10}

pr1645v2ApsBInUcastValue OBJECT-TYPE
   SYNTAX      Counter64
   MAX-ACCESS  read-only
   STATUS      current
   DESCRIPTION
      "Path: apsBundle.performance.ifInUcastPkts

       64 bit unsigned wrappable counter."
   ::= {pr1645v2ApsBInUcastEntry 2147483648}


pr1645v2ApsBInNUcastPkts OBJECT IDENTIFIER ::= {pr1645v2ApsB 111}

pr1645v2ApsBInNUcastPktsTable OBJECT-TYPE
   SYNTAX      SEQUENCE OF Pr1645v2ApsBInNUcastPktsEntry
   MAX-ACCESS  not-accessible
   STATUS      current
   DESCRIPTION
      "ifInNUcastPkts"
   ::= {pr1645v2ApsBInNUcastPkts 1}

pr1645v2ApsBInNUcastPktsEntry OBJECT-TYPE
   SYNTAX      Pr1645v2ApsBInNUcastPktsEntry
   MAX-ACCESS  not-accessible
   STATUS      current
   DESCRIPTION
      ""
   INDEX      { pr1645v2ApsBInNUcastPktsGlobalIx }
   ::= {pr1645v2ApsBInNUcastPktsTable 1}

Pr1645v2ApsBInNUcastPktsEntry ::=
   SEQUENCE
      {
      pr1645v2ApsBInNUcastPktsGlobalIx
         GlobalIndex,
      pr1645v2ApsBInNUcastPktsValue
         Counter64
      }

pr1645v2ApsBInNUcastPktsGlobalIx OBJECT-TYPE
   SYNTAX      GlobalIndex
   MAX-ACCESS  not-accessible
   STATUS      current
   DESCRIPTION
      "The value of the tlsCntTreeGlobalIndex of the MANAGED OBJECT."
   ::= {pr1645v2ApsBInNUcastPktsEntry 10}

pr1645v2ApsBInNUcastPktsValue OBJECT-TYPE
   SYNTAX      Counter64
   MAX-ACCESS  read-only
   STATUS      current
   DESCRIPTION
      "Path: apsBundle.performance.ifInNUcastPkts

       64 bit unsigned wrappable counter."
   ::= {pr1645v2ApsBInNUcastPktsEntry 2147483648}


pr1645v2ApsBInBcastPkts OBJECT IDENTIFIER ::= {pr1645v2ApsB 211}

pr1645v2ApsBInBcastPktsTable OBJECT-TYPE
   SYNTAX      SEQUENCE OF Pr1645v2ApsBInBcastPktsEntry
   MAX-ACCESS  not-accessible
   STATUS      current
   DESCRIPTION
      "ifInBcastPkts"
   ::= {pr1645v2ApsBInBcastPkts 1}

pr1645v2ApsBInBcastPktsEntry OBJECT-TYPE
   SYNTAX      Pr1645v2ApsBInBcastPktsEntry
   MAX-ACCESS  not-accessible
   STATUS      current
   DESCRIPTION
      ""
   INDEX      { pr1645v2ApsBInBcastPktsGlobalIx }
   ::= {pr1645v2ApsBInBcastPktsTable 1}

Pr1645v2ApsBInBcastPktsEntry ::=
   SEQUENCE
      {
      pr1645v2ApsBInBcastPktsGlobalIx
         GlobalIndex,
      pr1645v2ApsBInBcastPktsValue
         Counter64
      }

pr1645v2ApsBInBcastPktsGlobalIx OBJECT-TYPE
   SYNTAX      GlobalIndex
   MAX-ACCESS  not-accessible
   STATUS      current
   DESCRIPTION
      "The value of the tlsCntTreeGlobalIndex of the MANAGED OBJECT."
   ::= {pr1645v2ApsBInBcastPktsEntry 10}

pr1645v2ApsBInBcastPktsValue OBJECT-TYPE
   SYNTAX      Counter64
   MAX-ACCESS  read-only
   STATUS      current
   DESCRIPTION
      "Path: apsBundle.performance.ifInBcastPkts

       64 bit unsigned wrappable counter."
   ::= {pr1645v2ApsBInBcastPktsEntry 2147483648}


pr1645v2ApsBInMcastPkts OBJECT IDENTIFIER ::= {pr1645v2ApsB 221}

pr1645v2ApsBInMcastPktsTable OBJECT-TYPE
   SYNTAX      SEQUENCE OF Pr1645v2ApsBInMcastPktsEntry
   MAX-ACCESS  not-accessible
   STATUS      current
   DESCRIPTION
      "ifInNUcastPkts"
   ::= {pr1645v2ApsBInMcastPkts 1}

pr1645v2ApsBInMcastPktsEntry OBJECT-TYPE
   SYNTAX      Pr1645v2ApsBInMcastPktsEntry
   MAX-ACCESS  not-accessible
   STATUS      current
   DESCRIPTION
      ""
   INDEX      { pr1645v2ApsBInMcastPktsGlobalIx }
   ::= {pr1645v2ApsBInMcastPktsTable 1}

Pr1645v2ApsBInMcastPktsEntry ::=
   SEQUENCE
      {
      pr1645v2ApsBInMcastPktsGlobalIx
         GlobalIndex,
      pr1645v2ApsBInMcastPktsValue
         Counter64
      }

pr1645v2ApsBInMcastPktsGlobalIx OBJECT-TYPE
   SYNTAX      GlobalIndex
   MAX-ACCESS  not-accessible
   STATUS      current
   DESCRIPTION
      "The value of the tlsCntTreeGlobalIndex of the MANAGED OBJECT."
   ::= {pr1645v2ApsBInMcastPktsEntry 10}

pr1645v2ApsBInMcastPktsValue OBJECT-TYPE
   SYNTAX      Counter64
   MAX-ACCESS  read-only
   STATUS      current
   DESCRIPTION
      "Path: apsBundle.performance.ifInMcastPkts

       64 bit unsigned wrappable counter."
   ::= {pr1645v2ApsBInMcastPktsEntry 2147483648}


pr1645v2ApsBInDiscards OBJECT IDENTIFIER ::= {pr1645v2ApsB 112}

pr1645v2ApsBInDiscardsTable OBJECT-TYPE
   SYNTAX      SEQUENCE OF Pr1645v2ApsBInDiscardsEntry
   MAX-ACCESS  not-accessible
   STATUS      current
   DESCRIPTION
      "ifInDiscards"
   ::= {pr1645v2ApsBInDiscards 1}

pr1645v2ApsBInDiscardsEntry OBJECT-TYPE
   SYNTAX      Pr1645v2ApsBInDiscardsEntry
   MAX-ACCESS  not-accessible
   STATUS      current
   DESCRIPTION
      ""
   INDEX      { pr1645v2ApsBInDiscardsGlobalIx }
   ::= {pr1645v2ApsBInDiscardsTable 1}

Pr1645v2ApsBInDiscardsEntry ::=
   SEQUENCE
      {
      pr1645v2ApsBInDiscardsGlobalIx
         GlobalIndex,
      pr1645v2ApsBInDiscardsValue
         Counter64
      }

pr1645v2ApsBInDiscardsGlobalIx OBJECT-TYPE
   SYNTAX      GlobalIndex
   MAX-ACCESS  not-accessible
   STATUS      current
   DESCRIPTION
      "The value of the tlsCntTreeGlobalIndex of the MANAGED OBJECT."
   ::= {pr1645v2ApsBInDiscardsEntry 10}

pr1645v2ApsBInDiscardsValue OBJECT-TYPE
   SYNTAX      Counter64
   MAX-ACCESS  read-only
   STATUS      current
   DESCRIPTION
      "Path: apsBundle.performance.ifInDiscards

       64 bit unsigned wrappable counter."
   ::= {pr1645v2ApsBInDiscardsEntry 2147483648}


pr1645v2ApsBInErrors OBJECT IDENTIFIER ::= {pr1645v2ApsB 113}

pr1645v2ApsBInErrorsTable OBJECT-TYPE
   SYNTAX      SEQUENCE OF Pr1645v2ApsBInErrorsEntry
   MAX-ACCESS  not-accessible
   STATUS      current
   DESCRIPTION
      "ifInErrors"
   ::= {pr1645v2ApsBInErrors 1}

pr1645v2ApsBInErrorsEntry OBJECT-TYPE
   SYNTAX      Pr1645v2ApsBInErrorsEntry
   MAX-ACCESS  not-accessible
   STATUS      current
   DESCRIPTION
      ""
   INDEX      { pr1645v2ApsBInErrorsGlobalIx }
   ::= {pr1645v2ApsBInErrorsTable 1}

Pr1645v2ApsBInErrorsEntry ::=
   SEQUENCE
      {
      pr1645v2ApsBInErrorsGlobalIx
         GlobalIndex,
      pr1645v2ApsBInErrorsValue
         Counter64
      }

pr1645v2ApsBInErrorsGlobalIx OBJECT-TYPE
   SYNTAX      GlobalIndex
   MAX-ACCESS  not-accessible
   STATUS      current
   DESCRIPTION
      "The value of the tlsCntTreeGlobalIndex of the MANAGED OBJECT."
   ::= {pr1645v2ApsBInErrorsEntry 10}

pr1645v2ApsBInErrorsValue OBJECT-TYPE
   SYNTAX      Counter64
   MAX-ACCESS  read-only
   STATUS      current
   DESCRIPTION
      "Path: apsBundle.performance.ifInErrors

       64 bit unsigned wrappable counter."
   ::= {pr1645v2ApsBInErrorsEntry 2147483648}


pr1645v2ApsBInUnknownProtos OBJECT IDENTIFIER ::= {pr1645v2ApsB 114}

pr1645v2ApsBInUnknownProtosTable OBJECT-TYPE
   SYNTAX      SEQUENCE OF Pr1645v2ApsBInUnknownProtosEntry
   MAX-ACCESS  not-accessible
   STATUS      current
   DESCRIPTION
      "ifInUnknownprotos"
   ::= {pr1645v2ApsBInUnknownProtos 1}

pr1645v2ApsBInUnknownProtosEntry OBJECT-TYPE
   SYNTAX      Pr1645v2ApsBInUnknownProtosEntry
   MAX-ACCESS  not-accessible
   STATUS      current
   DESCRIPTION
      ""
   INDEX      { pr1645v2ApsBInUnknownProtosGlobalIx }
   ::= {pr1645v2ApsBInUnknownProtosTable 1}

Pr1645v2ApsBInUnknownProtosEntry ::=
   SEQUENCE
      {
      pr1645v2ApsBInUnknownProtosGlobalIx
         GlobalIndex,
      pr1645v2ApsBInUnknownProtosValue
         Counter64
      }

pr1645v2ApsBInUnknownProtosGlobalIx OBJECT-TYPE
   SYNTAX      GlobalIndex
   MAX-ACCESS  not-accessible
   STATUS      current
   DESCRIPTION
      "The value of the tlsCntTreeGlobalIndex of the MANAGED OBJECT."
   ::= {pr1645v2ApsBInUnknownProtosEntry 10}

pr1645v2ApsBInUnknownProtosValue OBJECT-TYPE
   SYNTAX      Counter64
   MAX-ACCESS  read-only
   STATUS      current
   DESCRIPTION
      "Path: apsBundle.performance.ifInUnknownProtos

       64 bit unsigned wrappable counter."
   ::= {pr1645v2ApsBInUnknownProtosEntry 2147483648}


pr1645v2ApsBInQLen OBJECT IDENTIFIER ::= {pr1645v2ApsB 128}

pr1645v2ApsBInQLenTable OBJECT-TYPE
   SYNTAX      SEQUENCE OF Pr1645v2ApsBInQLenEntry
   MAX-ACCESS  not-accessible
   STATUS      current
   DESCRIPTION
      "ifInQLen"
   ::= {pr1645v2ApsBInQLen 1}

pr1645v2ApsBInQLenEntry OBJECT-TYPE
   SYNTAX      Pr1645v2ApsBInQLenEntry
   MAX-ACCESS  not-accessible
   STATUS      current
   DESCRIPTION
      ""
   INDEX      { pr1645v2ApsBInQLenGlobalIx }
   ::= {pr1645v2ApsBInQLenTable 1}

Pr1645v2ApsBInQLenEntry ::=
   SEQUENCE
      {
      pr1645v2ApsBInQLenGlobalIx
         GlobalIndex,
      pr1645v2ApsBInQLenValue
         Gauge32
      }

pr1645v2ApsBInQLenGlobalIx OBJECT-TYPE
   SYNTAX      GlobalIndex
   MAX-ACCESS  not-accessible
   STATUS      current
   DESCRIPTION
      "The value of the tlsCntTreeGlobalIndex of the MANAGED OBJECT."
   ::= {pr1645v2ApsBInQLenEntry 10}

pr1645v2ApsBInQLenValue OBJECT-TYPE
   SYNTAX      Gauge32
   MAX-ACCESS  read-only
   STATUS      current
   DESCRIPTION
      "Path: apsBundle.performance.ifInQLen

       32 bit unsigned gauge value."
   ::= {pr1645v2ApsBInQLenEntry 2147483648}


pr1645v2ApsBInDropEx OBJECT IDENTIFIER ::= {pr1645v2ApsB 130}

pr1645v2ApsBInDropExTable OBJECT-TYPE
   SYNTAX      SEQUENCE OF Pr1645v2ApsBInDropExEntry
   MAX-ACCESS  not-accessible
   STATUS      current
   DESCRIPTION
      "ifInDiscards"
   ::= {pr1645v2ApsBInDropEx 1}

pr1645v2ApsBInDropExEntry OBJECT-TYPE
   SYNTAX      Pr1645v2ApsBInDropExEntry
   MAX-ACCESS  not-accessible
   STATUS      current
   DESCRIPTION
      ""
   INDEX      { pr1645v2ApsBInDropExGlobalIx }
   ::= {pr1645v2ApsBInDropExTable 1}

Pr1645v2ApsBInDropExEntry ::=
   SEQUENCE
      {
      pr1645v2ApsBInDropExGlobalIx
         GlobalIndex,
      pr1645v2ApsBInDropExValue
         Counter64
      }

pr1645v2ApsBInDropExGlobalIx OBJECT-TYPE
   SYNTAX      GlobalIndex
   MAX-ACCESS  not-accessible
   STATUS      current
   DESCRIPTION
      "The value of the tlsCntTreeGlobalIndex of the MANAGED OBJECT."
   ::= {pr1645v2ApsBInDropExEntry 10}

pr1645v2ApsBInDropExValue OBJECT-TYPE
   SYNTAX      Counter64
   MAX-ACCESS  read-only
   STATUS      current
   DESCRIPTION
      "Path: apsBundle.performance.ifInDropLevelExceeded

       64 bit unsigned wrappable counter."
   ::= {pr1645v2ApsBInDropExEntry 2147483648}


pr1645v2ApsBInDropNoMac OBJECT IDENTIFIER ::= {pr1645v2ApsB 133}

pr1645v2ApsBInDropNoMacTable OBJECT-TYPE
   SYNTAX      SEQUENCE OF Pr1645v2ApsBInDropNoMacEntry
   MAX-ACCESS  not-accessible
   STATUS      current
   DESCRIPTION
      "ifInDiscards"
   ::= {pr1645v2ApsBInDropNoMac 1}

pr1645v2ApsBInDropNoMacEntry OBJECT-TYPE
   SYNTAX      Pr1645v2ApsBInDropNoMacEntry
   MAX-ACCESS  not-accessible
   STATUS      current
   DESCRIPTION
      ""
   INDEX      { pr1645v2ApsBInDropNoMacGlobalIx }
   ::= {pr1645v2ApsBInDropNoMacTable 1}

Pr1645v2ApsBInDropNoMacEntry ::=
   SEQUENCE
      {
      pr1645v2ApsBInDropNoMacGlobalIx
         GlobalIndex,
      pr1645v2ApsBInDropNoMacValue
         Counter64
      }

pr1645v2ApsBInDropNoMacGlobalIx OBJECT-TYPE
   SYNTAX      GlobalIndex
   MAX-ACCESS  not-accessible
   STATUS      current
   DESCRIPTION
      "The value of the tlsCntTreeGlobalIndex of the MANAGED OBJECT."
   ::= {pr1645v2ApsBInDropNoMacEntry 10}

pr1645v2ApsBInDropNoMacValue OBJECT-TYPE
   SYNTAX      Counter64
   MAX-ACCESS  read-only
   STATUS      current
   DESCRIPTION
      "Path: apsBundle.performance.ifInDiscardsNoMacFit

       64 bit unsigned wrappable counter."
   ::= {pr1645v2ApsBInDropNoMacEntry 2147483648}


pr1645v2ApsBInDropNUCast OBJECT IDENTIFIER ::= {pr1645v2ApsB 136}

pr1645v2ApsBInDropNUCastTable OBJECT-TYPE
   SYNTAX      SEQUENCE OF Pr1645v2ApsBInDropNUCastEntry
   MAX-ACCESS  not-accessible
   STATUS      current
   DESCRIPTION
      "ifInDiscards"
   ::= {pr1645v2ApsBInDropNUCast 1}

pr1645v2ApsBInDropNUCastEntry OBJECT-TYPE
   SYNTAX      Pr1645v2ApsBInDropNUCastEntry
   MAX-ACCESS  not-accessible
   STATUS      current
   DESCRIPTION
      ""
   INDEX      { pr1645v2ApsBInDropNUCastGlobalIx }
   ::= {pr1645v2ApsBInDropNUCastTable 1}

Pr1645v2ApsBInDropNUCastEntry ::=
   SEQUENCE
      {
      pr1645v2ApsBInDropNUCastGlobalIx
         GlobalIndex,
      pr1645v2ApsBInDropNUCastValue
         Counter64
      }

pr1645v2ApsBInDropNUCastGlobalIx OBJECT-TYPE
   SYNTAX      GlobalIndex
   MAX-ACCESS  not-accessible
   STATUS      current
   DESCRIPTION
      "The value of the tlsCntTreeGlobalIndex of the MANAGED OBJECT."
   ::= {pr1645v2ApsBInDropNUCastEntry 10}

pr1645v2ApsBInDropNUCastValue OBJECT-TYPE
   SYNTAX      Counter64
   MAX-ACCESS  read-only
   STATUS      current
   DESCRIPTION
      "Path: apsBundle.performance.ifInDiscardsNUCast

       64 bit unsigned wrappable counter."
   ::= {pr1645v2ApsBInDropNUCastEntry 2147483648}


pr1645v2ApsBInDropFilter OBJECT IDENTIFIER ::= {pr1645v2ApsB 137}

pr1645v2ApsBInDropFilterTable OBJECT-TYPE
   SYNTAX      SEQUENCE OF Pr1645v2ApsBInDropFilterEntry
   MAX-ACCESS  not-accessible
   STATUS      current
   DESCRIPTION
      "ifInDiscards"
   ::= {pr1645v2ApsBInDropFilter 1}

pr1645v2ApsBInDropFilterEntry OBJECT-TYPE
   SYNTAX      Pr1645v2ApsBInDropFilterEntry
   MAX-ACCESS  not-accessible
   STATUS      current
   DESCRIPTION
      ""
   INDEX      { pr1645v2ApsBInDropFilterGlobalIx }
   ::= {pr1645v2ApsBInDropFilterTable 1}

Pr1645v2ApsBInDropFilterEntry ::=
   SEQUENCE
      {
      pr1645v2ApsBInDropFilterGlobalIx
         GlobalIndex,
      pr1645v2ApsBInDropFilterValue
         Counter64
      }

pr1645v2ApsBInDropFilterGlobalIx OBJECT-TYPE
   SYNTAX      GlobalIndex
   MAX-ACCESS  not-accessible
   STATUS      current
   DESCRIPTION
      "The value of the tlsCntTreeGlobalIndex of the MANAGED OBJECT."
   ::= {pr1645v2ApsBInDropFilterEntry 10}

pr1645v2ApsBInDropFilterValue OBJECT-TYPE
   SYNTAX      Counter64
   MAX-ACCESS  read-only
   STATUS      current
   DESCRIPTION
      "Path: apsBundle.performance.ifInDiscardsFilter

       64 bit unsigned wrappable counter."
   ::= {pr1645v2ApsBInDropFilterEntry 2147483648}


pr1645v2ApsBInQueues OBJECT IDENTIFIER ::= {pr1645v2ApsB 131}

pr1645v2ApsBInQueuesSSCTable OBJECT-TYPE
   SYNTAX      SEQUENCE OF Pr1645v2ApsBInQueuesEntry
   MAX-ACCESS  not-accessible
   STATUS      current
   DESCRIPTION
      "Queue Lengths"
   ::= {pr1645v2ApsBInQueues 1}

pr1645v2ApsBInQueuesEntry OBJECT-TYPE
   SYNTAX      Pr1645v2ApsBInQueuesEntry
   MAX-ACCESS  not-accessible
   STATUS      current
   DESCRIPTION
      ""
   INDEX      { pr1645v2ApsBInQueuesGlobalIx,
                pr1645v2ApsBInQueuesTableIx }
   ::= {pr1645v2ApsBInQueuesSSCTable 1}

Pr1645v2ApsBInQueuesEntry ::=
   SEQUENCE
      {
      pr1645v2ApsBInQueuesGlobalIx
         GlobalIndex,
      pr1645v2ApsBInQueuesTableIx
         TableIndex,
      pr1645v2ApsBInQueuesName
         INTEGER,
      pr1645v2ApsBInQueuesLength
         Integer32,
      pr1645v2ApsBInQueuesOctetLength
         Integer32,
      pr1645v2ApsBInQueuesRedLength
         Integer32,
      pr1645v2ApsBInQueuesPacketsTotal
         Counter64,
      pr1645v2ApsBInQueuesPacketsDirectTx
         Counter64,
      pr1645v2ApsBInQueuesPacketsQueued
         Counter64,
      pr1645v2ApsBInQueuesPacketsDropped
         Counter64,
      pr1645v2ApsBInQueuesPacketsRedDropped
         Counter64,
      pr1645v2ApsBInQueuesPacketsCirTx
         Counter64,
      pr1645v2ApsBInQueuesPacketsEirTx
         Counter64,
      pr1645v2ApsBInQueuesPacketsViolateTx
         Counter64,
      pr1645v2ApsBInQueuesOctetsTotal
         Counter64,
      pr1645v2ApsBInQueuesOctetsDirectTx
         Counter64,
      pr1645v2ApsBInQueuesOctetsQueued
         Counter64,
      pr1645v2ApsBInQueuesOctetsDropped
         Counter64,
      pr1645v2ApsBInQueuesOctetsRedDropped
         Counter64,
      pr1645v2ApsBInQueuesOctetsCirTx
         Counter64,
      pr1645v2ApsBInQueuesOctetsEirTx
         Counter64,
      pr1645v2ApsBInQueuesOctetsViolateTx
         Counter64,
      pr1645v2ApsBInQueuesOctetsBandwidth15sec
         Integer32,
      pr1645v2ApsBInQueuesOctetsBandwidth30sec
         Integer32,
      pr1645v2ApsBInQueuesOctetsBandwidth1min
         Integer32,
      pr1645v2ApsBInQueuesOctetsBandwidth2min
         Integer32,
      pr1645v2ApsBInQueuesOctetsBandwidth5min
         Integer32
      }

pr1645v2ApsBInQueuesGlobalIx OBJECT-TYPE
   SYNTAX      GlobalIndex
   MAX-ACCESS  not-accessible
   STATUS      current
   DESCRIPTION
      "The value of the tlsCntTreeGlobalIndex of the MANAGED OBJECT."
   ::= {pr1645v2ApsBInQueuesEntry 10}

pr1645v2ApsBInQueuesTableIx OBJECT-TYPE
   SYNTAX      TableIndex
   MAX-ACCESS  not-accessible
   STATUS      current
   DESCRIPTION
      ""
   ::= {pr1645v2ApsBInQueuesEntry 11}

pr1645v2ApsBInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: apsBundle.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2ApsBInQueuesEntry 16777216}

pr1645v2ApsBInQueuesLength OBJECT-TYPE
   SYNTAX      Integer32
   MAX-ACCESS  read-only
   STATUS      current
   DESCRIPTION
      "Path: apsBundle.performance.ifInPriorityQueues.length"
   ::= {pr1645v2ApsBInQueuesEntry 33554432}

pr1645v2ApsBInQueuesOctetLength OBJECT-TYPE
   SYNTAX      Integer32
   MAX-ACCESS  read-only
   STATUS      current
   DESCRIPTION
      "Path: apsBundle.performance.ifInPriorityQueues.octetLength"
   ::= {pr1645v2ApsBInQueuesEntry 150994944}

pr1645v2ApsBInQueuesRedLength OBJECT-TYPE
   SYNTAX      Integer32
   MAX-ACCESS  read-only
   STATUS      current
   DESCRIPTION
      "Path: apsBundle.performance.ifInPriorityQueues.redLength"
   ::= {pr1645v2ApsBInQueuesEntry 134217728}

pr1645v2ApsBInQueuesPacketsTotal OBJECT-TYPE
   SYNTAX      Counter64
   MAX-ACCESS  read-only
   STATUS      current
   DESCRIPTION
      "Path: apsBundle.performance.ifInPriorityQueues.packets.total

       64 bit unsigned wrappable counter."
   ::= {pr1645v2ApsBInQueuesEntry 50790400}

pr1645v2ApsBInQueuesPacketsDirectTx OBJECT-TYPE
   SYNTAX      Counter64
   MAX-ACCESS  read-only
   STATUS      current
   DESCRIPTION
      "Path: apsBundle.performance.ifInPriorityQueues.packets.directTx

       64 bit unsigned wrappable counter."
   ::= {pr1645v2ApsBInQueuesEntry 50397184}

pr1645v2ApsBInQueuesPacketsQueued OBJECT-TYPE
   SYNTAX      Counter64
   MAX-ACCESS  read-only
   STATUS      current
   DESCRIPTION
      "Path: apsBundle.performance.ifInPriorityQueues.packets.queued

       64 bit unsigned wrappable counter."
   ::= {pr1645v2ApsBInQueuesEntry 50462720}

pr1645v2ApsBInQueuesPacketsDropped OBJECT-TYPE
   SYNTAX      Counter64
   MAX-ACCESS  read-only
   STATUS      current
   DESCRIPTION
      "Path: apsBundle.performance.ifInPriorityQueues.packets.dropped

       64 bit unsigned wrappable counter."
   ::= {pr1645v2ApsBInQueuesEntry 50528256}

pr1645v2ApsBInQueuesPacketsRedDropped OBJECT-TYPE
   SYNTAX      Counter64
   MAX-ACCESS  read-only
   STATUS      current
   DESCRIPTION
      "Path: apsBundle.performance.ifInPriorityQueues.packets.redDropped

       64 bit unsigned wrappable counter."
   ::= {pr1645v2ApsBInQueuesEntry 50724864}

pr1645v2ApsBInQueuesPacketsCirTx OBJECT-TYPE
   SYNTAX      Counter64
   MAX-ACCESS  read-only
   STATUS      current
   DESCRIPTION
      "Path: apsBundle.performance.ifInPriorityQueues.packets.cirTx

       64 bit unsigned wrappable counter."
   ::= {pr1645v2ApsBInQueuesEntry 50593792}

pr1645v2ApsBInQueuesPacketsEirTx OBJECT-TYPE
   SYNTAX      Counter64
   MAX-ACCESS  read-only
   STATUS      current
   DESCRIPTION
      "Path: apsBundle.performance.ifInPriorityQueues.packets.eirTx

       64 bit unsigned wrappable counter."
   ::= {pr1645v2ApsBInQueuesEntry 50659328}

pr1645v2ApsBInQueuesPacketsViolateTx OBJECT-TYPE
   SYNTAX      Counter64
   MAX-ACCESS  read-only
   STATUS      current
   DESCRIPTION
      "Path: apsBundle.performance.ifInPriorityQueues.packets.violateTx

       64 bit unsigned wrappable counter."
   ::= {pr1645v2ApsBInQueuesEntry 50855936}

pr1645v2ApsBInQueuesOctetsTotal OBJECT-TYPE
   SYNTAX      Counter64
   MAX-ACCESS  read-only
   STATUS      current
   DESCRIPTION
      "Path: apsBundle.performance.ifInPriorityQueues.octets.total

       64 bit unsigned wrappable counter."
   ::= {pr1645v2ApsBInQueuesEntry 67567616}

pr1645v2ApsBInQueuesOctetsDirectTx OBJECT-TYPE
   SYNTAX      Counter64
   MAX-ACCESS  read-only
   STATUS      current
   DESCRIPTION
      "Path: apsBundle.performance.ifInPriorityQueues.octets.directTx

       64 bit unsigned wrappable counter."
   ::= {pr1645v2ApsBInQueuesEntry 67174400}

pr1645v2ApsBInQueuesOctetsQueued OBJECT-TYPE
   SYNTAX      Counter64
   MAX-ACCESS  read-only
   STATUS      current
   DESCRIPTION
      "Path: apsBundle.performance.ifInPriorityQueues.octets.queued

       64 bit unsigned wrappable counter."
   ::= {pr1645v2ApsBInQueuesEntry 67239936}

pr1645v2ApsBInQueuesOctetsDropped OBJECT-TYPE
   SYNTAX      Counter64
   MAX-ACCESS  read-only
   STATUS      current
   DESCRIPTION
      "Path: apsBundle.performance.ifInPriorityQueues.octets.dropped

       64 bit unsigned wrappable counter."
   ::= {pr1645v2ApsBInQueuesEntry 67305472}

pr1645v2ApsBInQueuesOctetsRedDropped OBJECT-TYPE
   SYNTAX      Counter64
   MAX-ACCESS  read-only
   STATUS      current
   DESCRIPTION
      "Path: apsBundle.performance.ifInPriorityQueues.octets.redDropped

       64 bit unsigned wrappable counter."
   ::= {pr1645v2ApsBInQueuesEntry 67502080}

pr1645v2ApsBInQueuesOctetsCirTx OBJECT-TYPE
   SYNTAX      Counter64
   MAX-ACCESS  read-only
   STATUS      current
   DESCRIPTION
      "Path: apsBundle.performance.ifInPriorityQueues.octets.cirTx

       64 bit unsigned wrappable counter."
   ::= {pr1645v2ApsBInQueuesEntry 67371008}

pr1645v2ApsBInQueuesOctetsEirTx OBJECT-TYPE
   SYNTAX      Counter64
   MAX-ACCESS  read-only
   STATUS      current
   DESCRIPTION
      "Path: apsBundle.performance.ifInPriorityQueues.octets.eirTx

       64 bit unsigned wrappable counter."
   ::= {pr1645v2ApsBInQueuesEntry 67436544}

pr1645v2ApsBInQueuesOctetsViolateTx OBJECT-TYPE
   SYNTAX      Counter64
   MAX-ACCESS  read-only
   STATUS      current
   DESCRIPTION
      "Path: apsBundle.performance.ifInPriorityQueues.octets.violateTx

       64 bit unsigned wrappable counter."
   ::= {pr1645v2ApsBInQueuesEntry 67633152}

pr1645v2ApsBInQueuesOctetsBandwidth15sec OBJECT-TYPE
   SYNTAX      Integer32
   MAX-ACCESS  read-only
   STATUS      current
   DESCRIPTION
      "Path: apsBundle.performance.ifInPriorityQueues.octets.bandwidth.15sec

       unit name = bps
       formula = 8 * ; 8 /"
   ::= {pr1645v2ApsBInQueuesEntry 70386944}

pr1645v2ApsBInQueuesOctetsBandwidth30sec OBJECT-TYPE
   SYNTAX      Integer32
   MAX-ACCESS  read-only
   STATUS      current
   DESCRIPTION
      "Path: apsBundle.performance.ifInPriorityQueues.octets.bandwidth.30sec

       unit name = bps
       formula = 8 * ; 8 /"
   ::= {pr1645v2ApsBInQueuesEntry 70388224}

pr1645v2ApsBInQueuesOctetsBandwidth1min OBJECT-TYPE
   SYNTAX      Integer32
   MAX-ACCESS  read-only
   STATUS      current
   DESCRIPTION
      "Path: apsBundle.performance.ifInPriorityQueues.octets.bandwidth.1min

       unit name = bps
       formula = 8 * ; 8 /"
   ::= {pr1645v2ApsBInQueuesEntry 70390784}

pr1645v2ApsBInQueuesOctetsBandwidth2min OBJECT-TYPE
   SYNTAX      Integer32
   MAX-ACCESS  read-only
   STATUS      current
   DESCRIPTION
      "Path: apsBundle.performance.ifInPriorityQueues.octets.bandwidth.2min

       unit name = bps
       formula = 8 * ; 8 /"
   ::= {pr1645v2ApsBInQueuesEntry 70395904}

pr1645v2ApsBInQueuesOctetsBandwidth5min OBJECT-TYPE
   SYNTAX      Integer32
   MAX-ACCESS  read-only
   STATUS      current
   DESCRIPTION
      "Path: apsBundle.performance.ifInPriorityQueues.octets.bandwidth.5min

       unit name = bps
       formula = 8 * ; 8 /"
   ::= {pr1645v2ApsBInQueuesEntry 70411264}

pr1645v2ApsBInQueuesH2Performance OBJECT-TYPE
   SYNTAX      SEQUENCE OF Pr1645v2ApsBInQueuesH2PerformanceEntry
   MAX-ACCESS  not-accessible
   STATUS      current
   DESCRIPTION
      ""
   ::= {pr1645v2ApsBInQueues 83886080}

pr1645v2ApsBInQueuesH2PerformanceEntry OBJECT-TYPE
   SYNTAX      Pr1645v2ApsBInQueuesH2PerformanceEntry
   MAX-ACCESS  not-accessible
   STATUS      current
   DESCRIPTION
      ""
   INDEX      { pr1645v2ApsBInQueuesH2PerformanceGlobalIx,
                pr1645v2ApsBInQueuesTableIx,
                pr1645v2ApsBInQueuesH2PerformanceTableIx }
   ::= {pr1645v2ApsBInQueuesH2Performance 1}

Pr1645v2ApsBInQueuesH2PerformanceEntry ::=
   SEQUENCE
      {
      pr1645v2ApsBInQueuesH2PerformanceGlobalIx
         GlobalIndex,
      pr1645v2ApsBInQueuesH2PerformanceTableIx
         TableIndex,
      pr1645v2ApsBInQueuesH2PerformanceSysUpTime
         TimeTicks,
      pr1645v2ApsBInQueuesH2PerformanceTotPkts
         Counter64,
      pr1645v2ApsBInQueuesH2PerformanceDirTxPkts
         Counter64,
      pr1645v2ApsBInQueuesH2PerformanceQdPkts
         Counter64,
      pr1645v2ApsBInQueuesH2PerformanceDropPkts
         Counter64,
      pr1645v2ApsBInQueuesH2PerformanceRDropPkts
         Counter64,
      pr1645v2ApsBInQueuesH2PerformanceCirTxPkts
         Counter64,
      pr1645v2ApsBInQueuesH2PerformanceEirTxPkts
         Counter64,
      pr1645v2ApsBInQueuesH2PerformanceViolTxPkts
         Counter64,
      pr1645v2ApsBInQueuesH2PerformanceTotOcts
         Counter64,
      pr1645v2ApsBInQueuesH2PerformanceDirTxOcts
         Counter64,
      pr1645v2ApsBInQueuesH2PerformanceQdOcts
         Counter64,
      pr1645v2ApsBInQueuesH2PerformanceDropOcts
         Counter64,
      pr1645v2ApsBInQueuesH2PerformanceRDropOcts
         Counter64,
      pr1645v2ApsBInQueuesH2PerformanceCirTxOcts
         Counter64,
      pr1645v2ApsBInQueuesH2PerformanceEirTxOcts
         Counter64,
      pr1645v2ApsBInQueuesH2PerformanceViolTxOcts
         Counter64,
      pr1645v2ApsBInQueuesH2PerformanceBandwidth
         Integer32
      }

pr1645v2ApsBInQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2ApsBInQueuesH2PerformanceEntry 10}

pr1645v2ApsBInQueuesH2PerformanceTableIx OBJECT-TYPE
   SYNTAX      TableIndex
   MAX-ACCESS  not-accessible
   STATUS      current
   DESCRIPTION
      ""
   ::= {pr1645v2ApsBInQueuesH2PerformanceEntry 11}

pr1645v2ApsBInQueuesH2PerformanceSysUpTime OBJECT-TYPE
   SYNTAX      TimeTicks
   MAX-ACCESS  read-only
   STATUS      current
   DESCRIPTION
      "Path: apsBundle.performance.ifInPriorityQueues.h2Performance.sysUpTime

       Time in centi-second."
   ::= {pr1645v2ApsBInQueuesH2PerformanceEntry 16777216}

pr1645v2ApsBInQueuesH2PerformanceTotPkts OBJECT-TYPE
   SYNTAX      Counter64
   MAX-ACCESS  read-only
   STATUS      current
   DESCRIPTION
      "Path: apsBundle.performance.ifInPriorityQueues.h2Performance.totalPkts

       64 bit unsigned wrappable counter."
   ::= {pr1645v2ApsBInQueuesH2PerformanceEntry 234881024}

pr1645v2ApsBInQueuesH2PerformanceDirTxPkts OBJECT-TYPE
   SYNTAX      Counter64
   MAX-ACCESS  read-only
   STATUS      current
   DESCRIPTION
      "Path: apsBundle.performance.ifInPriorityQueues.h2Performance.directTxPkts

       64 bit unsigned wrappable counter."
   ::= {pr1645v2ApsBInQueuesH2PerformanceEntry 33554432}

pr1645v2ApsBInQueuesH2PerformanceQdPkts OBJECT-TYPE
   SYNTAX      Counter64
   MAX-ACCESS  read-only
   STATUS      current
   DESCRIPTION
      "Path: apsBundle.performance.ifInPriorityQueues.h2Performance.queuedPkts

       64 bit unsigned wrappable counter."
   ::= {pr1645v2ApsBInQueuesH2PerformanceEntry 50331648}

pr1645v2ApsBInQueuesH2PerformanceDropPkts OBJECT-TYPE
   SYNTAX      Counter64
   MAX-ACCESS  read-only
   STATUS      current
   DESCRIPTION
      "Path: apsBundle.performance.ifInPriorityQueues.h2Performance.droppedPkts

       64 bit unsigned wrappable counter."
   ::= {pr1645v2ApsBInQueuesH2PerformanceEntry 67108864}

pr1645v2ApsBInQueuesH2PerformanceRDropPkts OBJECT-TYPE
   SYNTAX      Counter64
   MAX-ACCESS  read-only
   STATUS      current
   DESCRIPTION
      "Path: apsBundle.performance.ifInPriorityQueues.h2Performance.redDroppedPkts

       64 bit unsigned wrappable counter."
   ::= {pr1645v2ApsBInQueuesH2PerformanceEntry 201326592}

pr1645v2ApsBInQueuesH2PerformanceCirTxPkts OBJECT-TYPE
   SYNTAX      Counter64
   MAX-ACCESS  read-only
   STATUS      current
   DESCRIPTION
      "Path: apsBundle.performance.ifInPriorityQueues.h2Performance.cirTxPkts

       64 bit unsigned wrappable counter."
   ::= {pr1645v2ApsBInQueuesH2PerformanceEntry 83886080}

pr1645v2ApsBInQueuesH2PerformanceEirTxPkts OBJECT-TYPE
   SYNTAX      Counter64
   MAX-ACCESS  read-only
   STATUS      current
   DESCRIPTION
      "Path: apsBundle.performance.ifInPriorityQueues.h2Performance.eirTxPkts

       64 bit unsigned wrappable counter."
   ::= {pr1645v2ApsBInQueuesH2PerformanceEntry 100663296}

pr1645v2ApsBInQueuesH2PerformanceViolTxPkts OBJECT-TYPE
   SYNTAX      Counter64
   MAX-ACCESS  read-only
   STATUS      current
   DESCRIPTION
      "Path: apsBundle.performance.ifInPriorityQueues.h2Performance.violateTxPkts

       64 bit unsigned wrappable counter."
   ::= {pr1645v2ApsBInQueuesH2PerformanceEntry 301989888}

pr1645v2ApsBInQueuesH2PerformanceTotOcts OBJECT-TYPE
   SYNTAX      Counter64
   MAX-ACCESS  read-only
   STATUS      current
   DESCRIPTION
      "Path: apsBundle.performance.ifInPriorityQueues.h2Performance.totalOctets

       64 bit unsigned wrappable counter."
   ::= {pr1645v2ApsBInQueuesH2PerformanceEntry 251658240}

pr1645v2ApsBInQueuesH2PerformanceDirTxOcts OBJECT-TYPE
   SYNTAX      Counter64
   MAX-ACCESS  read-only
   STATUS      current
   DESCRIPTION
      "Path: apsBundle.performance.ifInPriorityQueues.h2Performance.directTxOctets

       64 bit unsigned wrappable counter."
   ::= {pr1645v2ApsBInQueuesH2PerformanceEntry 117440512}

pr1645v2ApsBInQueuesH2PerformanceQdOcts OBJECT-TYPE
   SYNTAX      Counter64
   MAX-ACCESS  read-only
   STATUS      current
   DESCRIPTION
      "Path: apsBundle.performance.ifInPriorityQueues.h2Performance.queuedOctets

       64 bit unsigned wrappable counter."
   ::= {pr1645v2ApsBInQueuesH2PerformanceEntry 134217728}

pr1645v2ApsBInQueuesH2PerformanceDropOcts OBJECT-TYPE
   SYNTAX      Counter64
   MAX-ACCESS  read-only
   STATUS      current
   DESCRIPTION
      "Path: apsBundle.performance.ifInPriorityQueues.h2Performance.droppedOctets

       64 bit unsigned wrappable counter."
   ::= {pr1645v2ApsBInQueuesH2PerformanceEntry 150994944}

pr1645v2ApsBInQueuesH2PerformanceRDropOcts OBJECT-TYPE
   SYNTAX      Counter64
   MAX-ACCESS  read-only
   STATUS      current
   DESCRIPTION
      "Path: apsBundle.performance.ifInPriorityQueues.h2Performance.redDroppedOctets

       64 bit unsigned wrappable counter."
   ::= {pr1645v2ApsBInQueuesH2PerformanceEntry 218103808}

pr1645v2ApsBInQueuesH2PerformanceCirTxOcts OBJECT-TYPE
   SYNTAX      Counter64
   MAX-ACCESS  read-only
   STATUS      current
   DESCRIPTION
      "Path: apsBundle.performance.ifInPriorityQueues.h2Performance.cirTxOctets

       64 bit unsigned wrappable counter."
   ::= {pr1645v2ApsBInQueuesH2PerformanceEntry 167772160}

pr1645v2ApsBInQueuesH2PerformanceEirTxOcts OBJECT-TYPE
   SYNTAX      Counter64
   MAX-ACCESS  read-only
   STATUS      current
   DESCRIPTION
      "Path: apsBundle.performance.ifInPriorityQueues.h2Performance.eirTxOctets

       64 bit unsigned wrappable counter."
   ::= {pr1645v2ApsBInQueuesH2PerformanceEntry 184549376}

pr1645v2ApsBInQueuesH2PerformanceViolTxOcts OBJECT-TYPE
   SYNTAX      Counter64
   MAX-ACCESS  read-only
   STATUS      current
   DESCRIPTION
      "Path: apsBundle.performance.ifInPriorityQueues.h2Performance.violateTxOctets

       64 bit unsigned wrappable counter."
   ::= {pr1645v2ApsBInQueuesH2PerformanceEntry 318767104}

pr1645v2ApsBInQueuesH2PerformanceBandwidth OBJECT-TYPE
   SYNTAX      Integer32
   MAX-ACCESS  read-only
   STATUS      current
   DESCRIPTION
      "Path: apsBundle.performance.ifInPriorityQueues.h2Performance.bandwidth

       unit name = bps
       formula = 8 * ; 8 /"
   ::= {pr1645v2ApsBInQueuesH2PerformanceEntry 268435456}

pr1645v2ApsBInQueuesH24Performance OBJECT-TYPE
   SYNTAX      SEQUENCE OF Pr1645v2ApsBInQueuesH24PerformanceEntry
   MAX-ACCESS  not-accessible
   STATUS      current
   DESCRIPTION
      ""
   ::= {pr1645v2ApsBInQueues 100663296}

pr1645v2ApsBInQueuesH24PerformanceEntry OBJECT-TYPE
   SYNTAX      Pr1645v2ApsBInQueuesH24PerformanceEntry
   MAX-ACCESS  not-accessible
   STATUS      current
   DESCRIPTION
      ""
   INDEX      { pr1645v2ApsBInQueuesH24PerformanceGlobalIx,
                pr1645v2ApsBInQueuesTableIx,
                pr1645v2ApsBInQueuesH24PerformanceTableIx }
   ::= {pr1645v2ApsBInQueuesH24Performance 1}

Pr1645v2ApsBInQueuesH24PerformanceEntry ::=
   SEQUENCE
      {
      pr1645v2ApsBInQueuesH24PerformanceGlobalIx
         GlobalIndex,
      pr1645v2ApsBInQueuesH24PerformanceTableIx
         TableIndex,
      pr1645v2ApsBInQueuesH24PerformanceSysUpTime
         TimeTicks,
      pr1645v2ApsBInQueuesH24PerformanceTotPkts
         Counter64,
      pr1645v2ApsBInQueuesH24PerformanceDirTxPkts
         Counter64,
      pr1645v2ApsBInQueuesH24PerformanceQdPkts
         Counter64,
      pr1645v2ApsBInQueuesH24PerformanceDropPkts
         Counter64,
      pr1645v2ApsBInQueuesH24PerformanceRDropPkts
         Counter64,
      pr1645v2ApsBInQueuesH24PerformanceCirTxPkts
         Counter64,
      pr1645v2ApsBInQueuesH24PerformanceEirTxPkts
         Counter64,
      pr1645v2ApsBInQueuesH24PerformanceViolTxPkts
         Counter64,
      pr1645v2ApsBInQueuesH24PerformanceTotOcts
         Counter64,
      pr1645v2ApsBInQueuesH24PerformanceDirTxOcts
         Counter64,
      pr1645v2ApsBInQueuesH24PerformanceQdOcts
         Counter64,
      pr1645v2ApsBInQueuesH24PerformanceDropOcts
         Counter64,
      pr1645v2ApsBInQueuesH24PerformanceRDropOcts
         Counter64,
      pr1645v2ApsBInQueuesH24PerformanceCirTxOcts
         Counter64,
      pr1645v2ApsBInQueuesH24PerformanceEirTxOcts
         Counter64,
      pr1645v2ApsBInQueuesH24PerformanceViolTxOcts
         Counter64,
      pr1645v2ApsBInQueuesH24PerformanceBandwidth
         Integer32
      }

pr1645v2ApsBInQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2ApsBInQueuesH24PerformanceEntry 10}

pr1645v2ApsBInQueuesH24PerformanceTableIx OBJECT-TYPE
   SYNTAX      TableIndex
   MAX-ACCESS  not-accessible
   STATUS      current
   DESCRIPTION
      ""
   ::= {pr1645v2ApsBInQueuesH24PerformanceEntry 11}

pr1645v2ApsBInQueuesH24PerformanceSysUpTime OBJECT-TYPE
   SYNTAX      TimeTicks
   MAX-ACCESS  read-only
   STATUS      current
   DESCRIPTION
      "Path: apsBundle.performance.ifInPriorityQueues.h24Performance.sysUpTime

       Time in centi-second."
   ::= {pr1645v2ApsBInQueuesH24PerformanceEntry 16777216}

pr1645v2ApsBInQueuesH24PerformanceTotPkts OBJECT-TYPE
   SYNTAX      Counter64
   MAX-ACCESS  read-only
   STATUS      current
   DESCRIPTION
      "Path: apsBundle.performance.ifInPriorityQueues.h24Performance.totalPkts

       64 bit unsigned wrappable counter."
   ::= {pr1645v2ApsBInQueuesH24PerformanceEntry 234881024}

pr1645v2ApsBInQueuesH24PerformanceDirTxPkts OBJECT-TYPE
   SYNTAX      Counter64
   MAX-ACCESS  read-only
   STATUS      current
   DESCRIPTION
      "Path: apsBundle.performance.ifInPriorityQueues.h24Performance.directTxPkts

       64 bit unsigned wrappable counter."
   ::= {pr1645v2ApsBInQueuesH24PerformanceEntry 33554432}

pr1645v2ApsBInQueuesH24PerformanceQdPkts OBJECT-TYPE
   SYNTAX      Counter64
   MAX-ACCESS  read-only
   STATUS      current
   DESCRIPTION
      "Path: apsBundle.performance.ifInPriorityQueues.h24Performance.queuedPkts

       64 bit unsigned wrappable counter."
   ::= {pr1645v2ApsBInQueuesH24PerformanceEntry 50331648}

pr1645v2ApsBInQueuesH24PerformanceDropPkts OBJECT-TYPE
   SYNTAX      Counter64
   MAX-ACCESS  read-only
   STATUS      current
   DESCRIPTION
      "Path: apsBundle.performance.ifInPriorityQueues.h24Performance.droppedPkts

       64 bit unsigned wrappable counter."
   ::= {pr1645v2ApsBInQueuesH24PerformanceEntry 67108864}

pr1645v2ApsBInQueuesH24PerformanceRDropPkts OBJECT-TYPE
   SYNTAX      Counter64
   MAX-ACCESS  read-only
   STATUS      current
   DESCRIPTION
      "Path: apsBundle.performance.ifInPriorityQueues.h24Performance.redDroppedPkts

       64 bit unsigned wrappable counter."
   ::= {pr1645v2ApsBInQueuesH24PerformanceEntry 201326592}

pr1645v2ApsBInQueuesH24PerformanceCirTxPkts OBJECT-TYPE
   SYNTAX      Counter64
   MAX-ACCESS  read-only
   STATUS      current
   DESCRIPTION
      "Path: apsBundle.performance.ifInPriorityQueues.h24Performance.cirTxPkts

       64 bit unsigned wrappable counter."
   ::= {pr1645v2ApsBInQueuesH24PerformanceEntry 83886080}

pr1645v2ApsBInQueuesH24PerformanceEirTxPkts OBJECT-TYPE
   SYNTAX      Counter64
   MAX-ACCESS  read-only
   STATUS      current
   DESCRIPTION
      "Path: apsBundle.performance.ifInPriorityQueues.h24Performance.eirTxPkts

       64 bit unsigned wrappable counter."
   ::= {pr1645v2ApsBInQueuesH24PerformanceEntry 100663296}

pr1645v2ApsBInQueuesH24PerformanceViolTxPkts OBJECT-TYPE
   SYNTAX      Counter64
   MAX-ACCESS  read-only
   STATUS      current
   DESCRIPTION
      "Path: apsBundle.performance.ifInPriorityQueues.h24Performance.violateTxPkts

       64 bit unsigned wrappable counter."
   ::= {pr1645v2ApsBInQueuesH24PerformanceEntry 301989888}

pr1645v2ApsBInQueuesH24PerformanceTotOcts OBJECT-TYPE
   SYNTAX      Counter64
   MAX-ACCESS  read-only
   STATUS      current
   DESCRIPTION
      "Path: apsBundle.performance.ifInPriorityQueues.h24Performance.totalOctets

       64 bit unsigned wrappable counter."
   ::= {pr1645v2ApsBInQueuesH24PerformanceEntry 251658240}

pr1645v2ApsBInQueuesH24PerformanceDirTxOcts OBJECT-TYPE
   SYNTAX      Counter64
   MAX-ACCESS  read-only
   STATUS      current
   DESCRIPTION
      "Path: apsBundle.performance.ifInPriorityQueues.h24Performance.directTxOctets

       64 bit unsigned wrappable counter."
   ::= {pr1645v2ApsBInQueuesH24PerformanceEntry 117440512}

pr1645v2ApsBInQueuesH24PerformanceQdOcts OBJECT-TYPE
   SYNTAX      Counter64
   MAX-ACCESS  read-only
   STATUS      current
   DESCRIPTION
      "Path: apsBundle.performance.ifInPriorityQueues.h24Performance.queuedOctets

       64 bit unsigned wrappable counter."
   ::= {pr1645v2ApsBInQueuesH24PerformanceEntry 134217728}

pr1645v2ApsBInQueuesH24PerformanceDropOcts OBJECT-TYPE
   SYNTAX      Counter64
   MAX-ACCESS  read-only
   STATUS      current
   DESCRIPTION
      "Path: apsBundle.performance.ifInPriorityQueues.h24Performance.droppedOctets

       64 bit unsigned wrappable counter."
   ::= {pr1645v2ApsBInQueuesH24PerformanceEntry 150994944}

pr1645v2ApsBInQueuesH24PerformanceRDropOcts OBJECT-TYPE
   SYNTAX      Counter64
   MAX-ACCESS  read-only
   STATUS      current
   DESCRIPTION
      "Path: apsBundle.performance.ifInPriorityQueues.h24Performance.redDroppedOctets

       64 bit unsigned wrappable counter."
   ::= {pr1645v2ApsBInQueuesH24PerformanceEntry 218103808}

pr1645v2ApsBInQueuesH24PerformanceCirTxOcts OBJECT-TYPE
   SYNTAX      Counter64
   MAX-ACCESS  read-only
   STATUS      current
   DESCRIPTION
      "Path: apsBundle.performance.ifInPriorityQueues.h24Performance.cirTxOctets

       64 bit unsigned wrappable counter."
   ::= {pr1645v2ApsBInQueuesH24PerformanceEntry 167772160}

pr1645v2ApsBInQueuesH24PerformanceEirTxOcts OBJECT-TYPE
   SYNTAX      Counter64
   MAX-ACCESS  read-only
   STATUS      current
   DESCRIPTION
      "Path: apsBundle.performance.ifInPriorityQueues.h24Performance.eirTxOctets

       64 bit unsigned wrappable counter."
   ::= {pr1645v2ApsBInQueuesH24PerformanceEntry 184549376}

pr1645v2ApsBInQueuesH24PerformanceViolTxOcts OBJECT-TYPE
   SYNTAX      Counter64
   MAX-ACCESS  read-only
   STATUS      current
   DESCRIPTION
      "Path: apsBundle.performance.ifInPriorityQueues.h24Performance.violateTxOctets

       64 bit unsigned wrappable counter."
   ::= {pr1645v2ApsBInQueuesH24PerformanceEntry 318767104}

pr1645v2ApsBInQueuesH24PerformanceBandwidth OBJECT-TYPE
   SYNTAX      Integer32
   MAX-ACCESS  read-only
   STATUS      current
   DESCRIPTION
      "Path: apsBundle.performance.ifInPriorityQueues.h24Performance.bandwidth

       unit name = bps
       formula = 8 * ; 8 /"
   ::= {pr1645v2ApsBInQueuesH24PerformanceEntry 268435456}

pr1645v2ApsBInQueuesD7Performance OBJECT-TYPE
   SYNTAX      SEQUENCE OF Pr1645v2ApsBInQueuesD7PerformanceEntry
   MAX-ACCESS  not-accessible
   STATUS      current
   DESCRIPTION
      ""
   ::= {pr1645v2ApsBInQueues 117440512}

pr1645v2ApsBInQueuesD7PerformanceEntry OBJECT-TYPE
   SYNTAX      Pr1645v2ApsBInQueuesD7PerformanceEntry
   MAX-ACCESS  not-accessible
   STATUS      current
   DESCRIPTION
      ""
   INDEX      { pr1645v2ApsBInQueuesD7PerformanceGlobalIx,
                pr1645v2ApsBInQueuesTableIx,
                pr1645v2ApsBInQueuesD7PerformanceTableIx }
   ::= {pr1645v2ApsBInQueuesD7Performance 1}

Pr1645v2ApsBInQueuesD7PerformanceEntry ::=
   SEQUENCE
      {
      pr1645v2ApsBInQueuesD7PerformanceGlobalIx
         GlobalIndex,
      pr1645v2ApsBInQueuesD7PerformanceTableIx
         TableIndex,
      pr1645v2ApsBInQueuesD7PerformanceSysUpTime
         TimeTicks,
      pr1645v2ApsBInQueuesD7PerformanceTotPkts
         Counter64,
      pr1645v2ApsBInQueuesD7PerformanceDirTxPkts
         Counter64,
      pr1645v2ApsBInQueuesD7PerformanceQdPkts
         Counter64,
      pr1645v2ApsBInQueuesD7PerformanceDropPkts
         Counter64,
      pr1645v2ApsBInQueuesD7PerformanceRDropPkts
         Counter64,
      pr1645v2ApsBInQueuesD7PerformanceCirTxPkts
         Counter64,
      pr1645v2ApsBInQueuesD7PerformanceEirTxPkts
         Counter64,
      pr1645v2ApsBInQueuesD7PerformanceViolTxPkts
         Counter64,
      pr1645v2ApsBInQueuesD7PerformanceTotOcts
         Counter64,
      pr1645v2ApsBInQueuesD7PerformanceDirTxOcts
         Counter64,
      pr1645v2ApsBInQueuesD7PerformanceQdOcts
         Counter64,
      pr1645v2ApsBInQueuesD7PerformanceDropOcts
         Counter64,
      pr1645v2ApsBInQueuesD7PerformanceRDropOcts
         Counter64,
      pr1645v2ApsBInQueuesD7PerformanceCirTxOcts
         Counter64,
      pr1645v2ApsBInQueuesD7PerformanceEirTxOcts
         Counter64,
      pr1645v2ApsBInQueuesD7PerformanceViolTxOcts
         Counter64,
      pr1645v2ApsBInQueuesD7PerformanceBandwidth
         Integer32
      }

pr1645v2ApsBInQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2ApsBInQueuesD7PerformanceEntry 10}

pr1645v2ApsBInQueuesD7PerformanceTableIx OBJECT-TYPE
   SYNTAX      TableIndex
   MAX-ACCESS  not-accessible
   STATUS      current
   DESCRIPTION
      ""
   ::= {pr1645v2ApsBInQueuesD7PerformanceEntry 11}

pr1645v2ApsBInQueuesD7PerformanceSysUpTime OBJECT-TYPE
   SYNTAX      TimeTicks
   MAX-ACCESS  read-only
   STATUS      current
   DESCRIPTION
      "Path: apsBundle.performance.ifInPriorityQueues.d7Performance.sysUpTime

       Time in centi-second."
   ::= {pr1645v2ApsBInQueuesD7PerformanceEntry 16777216}

pr1645v2ApsBInQueuesD7PerformanceTotPkts OBJECT-TYPE
   SYNTAX      Counter64
   MAX-ACCESS  read-only
   STATUS      current
   DESCRIPTION
      "Path: apsBundle.performance.ifInPriorityQueues.d7Performance.totalPkts

       64 bit unsigned wrappable counter."
   ::= {pr1645v2ApsBInQueuesD7PerformanceEntry 234881024}

pr1645v2ApsBInQueuesD7PerformanceDirTxPkts OBJECT-TYPE
   SYNTAX      Counter64
   MAX-ACCESS  read-only
   STATUS      current
   DESCRIPTION
      "Path: apsBundle.performance.ifInPriorityQueues.d7Performance.directTxPkts

       64 bit unsigned wrappable counter."
   ::= {pr1645v2ApsBInQueuesD7PerformanceEntry 33554432}

pr1645v2ApsBInQueuesD7PerformanceQdPkts OBJECT-TYPE
   SYNTAX      Counter64
   MAX-ACCESS  read-only
   STATUS      current
   DESCRIPTION
      "Path: apsBundle.performance.ifInPriorityQueues.d7Performance.queuedPkts

       64 bit unsigned wrappable counter."
   ::= {pr1645v2ApsBInQueuesD7PerformanceEntry 50331648}

pr1645v2ApsBInQueuesD7PerformanceDropPkts OBJECT-TYPE
   SYNTAX      Counter64
   MAX-ACCESS  read-only
   STATUS      current
   DESCRIPTION
      "Path: apsBundle.performance.ifInPriorityQueues.d7Performance.droppedPkts

       64 bit unsigned wrappable counter."
   ::= {pr1645v2ApsBInQueuesD7PerformanceEntry 67108864}

pr1645v2ApsBInQueuesD7PerformanceRDropPkts OBJECT-TYPE
   SYNTAX      Counter64
   MAX-ACCESS  read-only
   STATUS      current
   DESCRIPTION
      "Path: apsBundle.performance.ifInPriorityQueues.d7Performance.redDroppedPkts

       64 bit unsigned wrappable counter."
   ::= {pr1645v2ApsBInQueuesD7PerformanceEntry 201326592}

pr1645v2ApsBInQueuesD7PerformanceCirTxPkts OBJECT-TYPE
   SYNTAX      Counter64
   MAX-ACCESS  read-only
   STATUS      current
   DESCRIPTION
      "Path: apsBundle.performance.ifInPriorityQueues.d7Performance.cirTxPkts

       64 bit unsigned wrappable counter."
   ::= {pr1645v2ApsBInQueuesD7PerformanceEntry 83886080}

pr1645v2ApsBInQueuesD7PerformanceEirTxPkts OBJECT-TYPE
   SYNTAX      Counter64
   MAX-ACCESS  read-only
   STATUS      current
   DESCRIPTION
      "Path: apsBundle.performance.ifInPriorityQueues.d7Performance.eirTxPkts

       64 bit unsigned wrappable counter."
   ::= {pr1645v2ApsBInQueuesD7PerformanceEntry 100663296}

pr1645v2ApsBInQueuesD7PerformanceViolTxPkts OBJECT-TYPE
   SYNTAX      Counter64
   MAX-ACCESS  read-only
   STATUS      current
   DESCRIPTION
      "Path: apsBundle.performance.ifInPriorityQueues.d7Performance.violateTxPkts

       64 bit unsigned wrappable counter."
   ::= {pr1645v2ApsBInQueuesD7PerformanceEntry 301989888}

pr1645v2ApsBInQueuesD7PerformanceTotOcts OBJECT-TYPE
   SYNTAX      Counter64
   MAX-ACCESS  read-only
   STATUS      current
   DESCRIPTION
      "Path: apsBundle.performance.ifInPriorityQueues.d7Performance.totalOctets

       64 bit unsigned wrappable counter."
   ::= {pr1645v2ApsBInQueuesD7PerformanceEntry 251658240}

pr1645v2ApsBInQueuesD7PerformanceDirTxOcts OBJECT-TYPE
   SYNTAX      Counter64
   MAX-ACCESS  read-only
   STATUS      current
   DESCRIPTION
      "Path: apsBundle.performance.ifInPriorityQueues.d7Performance.directTxOctets

       64 bit unsigned wrappable counter."
   ::= {pr1645v2ApsBInQueuesD7PerformanceEntry 117440512}

pr1645v2ApsBInQueuesD7PerformanceQdOcts OBJECT-TYPE
   SYNTAX      Counter64
   MAX-ACCESS  read-only
   STATUS      current
   DESCRIPTION
      "Path: apsBundle.performance.ifInPriorityQueues.d7Performance.queuedOctets

       64 bit unsigned wrappable counter."
   ::= {pr1645v2ApsBInQueuesD7PerformanceEntry 134217728}

pr1645v2ApsBInQueuesD7PerformanceDropOcts OBJECT-TYPE
   SYNTAX      Counter64
   MAX-ACCESS  read-only
   STATUS      current
   DESCRIPTION
      "Path: apsBundle.performance.ifInPriorityQueues.d7Performance.droppedOctets

       64 bit unsigned wrappable counter."
   ::= {pr1645v2ApsBInQueuesD7PerformanceEntry 150994944}

pr1645v2ApsBInQueuesD7PerformanceRDropOcts OBJECT-TYPE
   SYNTAX      Counter64
   MAX-ACCESS  read-only
   STATUS      current
   DESCRIPTION
      "Path: apsBundle.performance.ifInPriorityQueues.d7Performance.redDroppedOctets

       64 bit unsigned wrappable counter."
   ::= {pr1645v2ApsBInQueuesD7PerformanceEntry 218103808}

pr1645v2ApsBInQueuesD7PerformanceCirTxOcts OBJECT-TYPE
   SYNTAX      Counter64
   MAX-ACCESS  read-only
   STATUS      current
   DESCRIPTION
      "Path: apsBundle.performance.ifInPriorityQueues.d7Performance.cirTxOctets

       64 bit unsigned wrappable counter."
   ::= {pr1645v2ApsBInQueuesD7PerformanceEntry 167772160}

pr1645v2ApsBInQueuesD7PerformanceEirTxOcts OBJECT-TYPE
   SYNTAX      Counter64
   MAX-ACCESS  read-only
   STATUS      current
   DESCRIPTION
      "Path: apsBundle.performance.ifInPriorityQueues.d7Performance.eirTxOctets

       64 bit unsigned wrappable counter."
   ::= {pr1645v2ApsBInQueuesD7PerformanceEntry 184549376}

pr1645v2ApsBInQueuesD7PerformanceViolTxOcts OBJECT-TYPE
   SYNTAX      Counter64
   MAX-ACCESS  read-only
   STATUS      current
   DESCRIPTION
      "Path: apsBundle.performance.ifInPriorityQueues.d7Performance.violateTxOctets

       64 bit unsigned wrappable counter."
   ::= {pr1645v2ApsBInQueuesD7PerformanceEntry 318767104}

pr1645v2ApsBInQueuesD7PerformanceBandwidth OBJECT-TYPE
   SYNTAX      Integer32
   MAX-ACCESS  read-only
   STATUS      current
   DESCRIPTION
      "Path: apsBundle.performance.ifInPriorityQueues.d7Performance.bandwidth

       unit name = bps
       formula = 8 * ; 8 /"
   ::= {pr1645v2ApsBInQueuesD7PerformanceEntry 268435456}


pr1645v2ApsBInBandwidth OBJECT IDENTIFIER ::= {pr1645v2ApsB 181}

pr1645v2ApsBInBandwidthSSCTable OBJECT-TYPE
   SYNTAX      SEQUENCE OF Pr1645v2ApsBInBandwidthEntry
   MAX-ACCESS  not-accessible
   STATUS      current
   DESCRIPTION
      "bandwidth"
   ::= {pr1645v2ApsBInBandwidth 1}

pr1645v2ApsBInBandwidthEntry OBJECT-TYPE
   SYNTAX      Pr1645v2ApsBInBandwidthEntry
   MAX-ACCESS  not-accessible
   STATUS      current
   DESCRIPTION
      ""
   INDEX      { pr1645v2ApsBInBandwidthGlobalIx }
   ::= {pr1645v2ApsBInBandwidthSSCTable 1}

Pr1645v2ApsBInBandwidthEntry ::=
   SEQUENCE
      {
      pr1645v2ApsBInBandwidthGlobalIx
         GlobalIndex,
      pr1645v2ApsBInBandwidth15sec
         Integer32,
      pr1645v2ApsBInBandwidth30sec
         Integer32,
      pr1645v2ApsBInBandwidth1min
         Integer32,
      pr1645v2ApsBInBandwidth2min
         Integer32,
      pr1645v2ApsBInBandwidth5min
         Integer32
      }

pr1645v2ApsBInBandwidthGlobalIx OBJECT-TYPE
   SYNTAX      GlobalIndex
   MAX-ACCESS  not-accessible
   STATUS      current
   DESCRIPTION
      "The value of the tlsCntTreeGlobalIndex of the MANAGED OBJECT."
   ::= {pr1645v2ApsBInBandwidthEntry 10}

pr1645v2ApsBInBandwidth15sec OBJECT-TYPE
   SYNTAX      Integer32
   MAX-ACCESS  read-only
   STATUS      current
   DESCRIPTION
      "Path: apsBundle.performance.ifInBandwidth.15sec

       unit name = bps
       formula = 8 * ; 8 /"
   ::= {pr1645v2ApsBInBandwidthEntry 83886080}

pr1645v2ApsBInBandwidth30sec OBJECT-TYPE
   SYNTAX      Integer32
   MAX-ACCESS  read-only
   STATUS      current
   DESCRIPTION
      "Path: apsBundle.performance.ifInBandwidth.30sec

       unit name = bps
       formula = 8 * ; 8 /"
   ::= {pr1645v2ApsBInBandwidthEntry 167772160}

pr1645v2ApsBInBandwidth1min OBJECT-TYPE
   SYNTAX      Integer32
   MAX-ACCESS  read-only
   STATUS      current
   DESCRIPTION
      "Path: apsBundle.performance.ifInBandwidth.1min

       unit name = bps
       formula = 8 * ; 8 /"
   ::= {pr1645v2ApsBInBandwidthEntry 335544320}

pr1645v2ApsBInBandwidth2min OBJECT-TYPE
   SYNTAX      Integer32
   MAX-ACCESS  read-only
   STATUS      current
   DESCRIPTION
      "Path: apsBundle.performance.ifInBandwidth.2min

       unit name = bps
       formula = 8 * ; 8 /"
   ::= {pr1645v2ApsBInBandwidthEntry 671088640}

pr1645v2ApsBInBandwidth5min OBJECT-TYPE
   SYNTAX      Integer32
   MAX-ACCESS  read-only
   STATUS      current
   DESCRIPTION
      "Path: apsBundle.performance.ifInBandwidth.5min

       unit name = bps
       formula = 8 * ; 8 /"
   ::= {pr1645v2ApsBInBandwidthEntry 1677721600}


pr1645v2ApsBOutOctets OBJECT IDENTIFIER ::= {pr1645v2ApsB 115}

pr1645v2ApsBOutOctetsTable OBJECT-TYPE
   SYNTAX      SEQUENCE OF Pr1645v2ApsBOutOctetsEntry
   MAX-ACCESS  not-accessible
   STATUS      current
   DESCRIPTION
      "ifOutOctets"
   ::= {pr1645v2ApsBOutOctets 1}

pr1645v2ApsBOutOctetsEntry OBJECT-TYPE
   SYNTAX      Pr1645v2ApsBOutOctetsEntry
   MAX-ACCESS  not-accessible
   STATUS      current
   DESCRIPTION
      ""
   INDEX      { pr1645v2ApsBOutOctetsGlobalIx }
   ::= {pr1645v2ApsBOutOctetsTable 1}

Pr1645v2ApsBOutOctetsEntry ::=
   SEQUENCE
      {
      pr1645v2ApsBOutOctetsGlobalIx
         GlobalIndex,
      pr1645v2ApsBOutOctetsValue
         Counter64
      }

pr1645v2ApsBOutOctetsGlobalIx OBJECT-TYPE
   SYNTAX      GlobalIndex
   MAX-ACCESS  not-accessible
   STATUS      current
   DESCRIPTION
      "The value of the tlsCntTreeGlobalIndex of the MANAGED OBJECT."
   ::= {pr1645v2ApsBOutOctetsEntry 10}

pr1645v2ApsBOutOctetsValue OBJECT-TYPE
   SYNTAX      Counter64
   MAX-ACCESS  read-only
   STATUS      current
   DESCRIPTION
      "Path: apsBundle.performance.ifOutOctets

       64 bit unsigned wrappable counter."
   ::= {pr1645v2ApsBOutOctetsEntry 2147483648}


pr1645v2ApsBOutUcastPkts OBJECT IDENTIFIER ::= {pr1645v2ApsB 116}

pr1645v2ApsBOutUcastPktsTable OBJECT-TYPE
   SYNTAX      SEQUENCE OF Pr1645v2ApsBOutUcastPktsEntry
   MAX-ACCESS  not-accessible
   STATUS      current
   DESCRIPTION
      "ifOutUcastPkts"
   ::= {pr1645v2ApsBOutUcastPkts 1}

pr1645v2ApsBOutUcastPktsEntry OBJECT-TYPE
   SYNTAX      Pr1645v2ApsBOutUcastPktsEntry
   MAX-ACCESS  not-accessible
   STATUS      current
   DESCRIPTION
      ""
   INDEX      { pr1645v2ApsBOutUcastPktsGlobalIx }
   ::= {pr1645v2ApsBOutUcastPktsTable 1}

Pr1645v2ApsBOutUcastPktsEntry ::=
   SEQUENCE
      {
      pr1645v2ApsBOutUcastPktsGlobalIx
         GlobalIndex,
      pr1645v2ApsBOutUcastPktsValue
         Counter64
      }

pr1645v2ApsBOutUcastPktsGlobalIx OBJECT-TYPE
   SYNTAX      GlobalIndex
   MAX-ACCESS  not-accessible
   STATUS      current
   DESCRIPTION
      "The value of the tlsCntTreeGlobalIndex of the MANAGED OBJECT."
   ::= {pr1645v2ApsBOutUcastPktsEntry 10}

pr1645v2ApsBOutUcastPktsValue OBJECT-TYPE
   SYNTAX      Counter64
   MAX-ACCESS  read-only
   STATUS      current
   DESCRIPTION
      "Path: apsBundle.performance.ifOutUcastPkts

       64 bit unsigned wrappable counter."
   ::= {pr1645v2ApsBOutUcastPktsEntry 2147483648}


pr1645v2ApsBOutNUcastPkts OBJECT IDENTIFIER ::= {pr1645v2ApsB 117}

pr1645v2ApsBOutNUcastPktsTable OBJECT-TYPE
   SYNTAX      SEQUENCE OF Pr1645v2ApsBOutNUcastPktsEntry
   MAX-ACCESS  not-accessible
   STATUS      current
   DESCRIPTION
      "ifOutNUcastPkts"
   ::= {pr1645v2ApsBOutNUcastPkts 1}

pr1645v2ApsBOutNUcastPktsEntry OBJECT-TYPE
   SYNTAX      Pr1645v2ApsBOutNUcastPktsEntry
   MAX-ACCESS  not-accessible
   STATUS      current
   DESCRIPTION
      ""
   INDEX      { pr1645v2ApsBOutNUcastPktsGlobalIx }
   ::= {pr1645v2ApsBOutNUcastPktsTable 1}

Pr1645v2ApsBOutNUcastPktsEntry ::=
   SEQUENCE
      {
      pr1645v2ApsBOutNUcastPktsGlobalIx
         GlobalIndex,
      pr1645v2ApsBOutNUcastPktsValue
         Counter64
      }

pr1645v2ApsBOutNUcastPktsGlobalIx OBJECT-TYPE
   SYNTAX      GlobalIndex
   MAX-ACCESS  not-accessible
   STATUS      current
   DESCRIPTION
      "The value of the tlsCntTreeGlobalIndex of the MANAGED OBJECT."
   ::= {pr1645v2ApsBOutNUcastPktsEntry 10}

pr1645v2ApsBOutNUcastPktsValue OBJECT-TYPE
   SYNTAX      Counter64
   MAX-ACCESS  read-only
   STATUS      current
   DESCRIPTION
      "Path: apsBundle.performance.ifOutNUcastPkts

       64 bit unsigned wrappable counter."
   ::= {pr1645v2ApsBOutNUcastPktsEntry 2147483648}


pr1645v2ApsBOutBcastPkts OBJECT IDENTIFIER ::= {pr1645v2ApsB 217}

pr1645v2ApsBOutBcastPktsTable OBJECT-TYPE
   SYNTAX      SEQUENCE OF Pr1645v2ApsBOutBcastPktsEntry
   MAX-ACCESS  not-accessible
   STATUS      current
   DESCRIPTION
      "ifOutBcastPkts"
   ::= {pr1645v2ApsBOutBcastPkts 1}

pr1645v2ApsBOutBcastPktsEntry OBJECT-TYPE
   SYNTAX      Pr1645v2ApsBOutBcastPktsEntry
   MAX-ACCESS  not-accessible
   STATUS      current
   DESCRIPTION
      ""
   INDEX      { pr1645v2ApsBOutBcastPktsGlobalIx }
   ::= {pr1645v2ApsBOutBcastPktsTable 1}

Pr1645v2ApsBOutBcastPktsEntry ::=
   SEQUENCE
      {
      pr1645v2ApsBOutBcastPktsGlobalIx
         GlobalIndex,
      pr1645v2ApsBOutBcastPktsValue
         Counter64
      }

pr1645v2ApsBOutBcastPktsGlobalIx OBJECT-TYPE
   SYNTAX      GlobalIndex
   MAX-ACCESS  not-accessible
   STATUS      current
   DESCRIPTION
      "The value of the tlsCntTreeGlobalIndex of the MANAGED OBJECT."
   ::= {pr1645v2ApsBOutBcastPktsEntry 10}

pr1645v2ApsBOutBcastPktsValue OBJECT-TYPE
   SYNTAX      Counter64
   MAX-ACCESS  read-only
   STATUS      current
   DESCRIPTION
      "Path: apsBundle.performance.ifOutBcastPkts

       64 bit unsigned wrappable counter."
   ::= {pr1645v2ApsBOutBcastPktsEntry 2147483648}


pr1645v2ApsBOutMcastPkts OBJECT IDENTIFIER ::= {pr1645v2ApsB 227}

pr1645v2ApsBOutMcastPktsTable OBJECT-TYPE
   SYNTAX      SEQUENCE OF Pr1645v2ApsBOutMcastPktsEntry
   MAX-ACCESS  not-accessible
   STATUS      current
   DESCRIPTION
      "ifOutMcastPkts"
   ::= {pr1645v2ApsBOutMcastPkts 1}

pr1645v2ApsBOutMcastPktsEntry OBJECT-TYPE
   SYNTAX      Pr1645v2ApsBOutMcastPktsEntry
   MAX-ACCESS  not-accessible
   STATUS      current
   DESCRIPTION
      ""
   INDEX      { pr1645v2ApsBOutMcastPktsGlobalIx }
   ::= {pr1645v2ApsBOutMcastPktsTable 1}

Pr1645v2ApsBOutMcastPktsEntry ::=
   SEQUENCE
      {
      pr1645v2ApsBOutMcastPktsGlobalIx
         GlobalIndex,
      pr1645v2ApsBOutMcastPktsValue
         Counter64
      }

pr1645v2ApsBOutMcastPktsGlobalIx OBJECT-TYPE
   SYNTAX      GlobalIndex
   MAX-ACCESS  not-accessible
   STATUS      current
   DESCRIPTION
      "The value of the tlsCntTreeGlobalIndex of the MANAGED OBJECT."
   ::= {pr1645v2ApsBOutMcastPktsEntry 10}

pr1645v2ApsBOutMcastPktsValue OBJECT-TYPE
   SYNTAX      Counter64
   MAX-ACCESS  read-only
   STATUS      current
   DESCRIPTION
      "Path: apsBundle.performance.ifOutMcastPkts

       64 bit unsigned wrappable counter."
   ::= {pr1645v2ApsBOutMcastPktsEntry 2147483648}


pr1645v2ApsBOutDiscards OBJECT IDENTIFIER ::= {pr1645v2ApsB 118}

pr1645v2ApsBOutDiscardsTable OBJECT-TYPE
   SYNTAX      SEQUENCE OF Pr1645v2ApsBOutDiscardsEntry
   MAX-ACCESS  not-accessible
   STATUS      current
   DESCRIPTION
      "ifOutDiscards"
   ::= {pr1645v2ApsBOutDiscards 1}

pr1645v2ApsBOutDiscardsEntry OBJECT-TYPE
   SYNTAX      Pr1645v2ApsBOutDiscardsEntry
   MAX-ACCESS  not-accessible
   STATUS      current
   DESCRIPTION
      ""
   INDEX      { pr1645v2ApsBOutDiscardsGlobalIx }
   ::= {pr1645v2ApsBOutDiscardsTable 1}

Pr1645v2ApsBOutDiscardsEntry ::=
   SEQUENCE
      {
      pr1645v2ApsBOutDiscardsGlobalIx
         GlobalIndex,
      pr1645v2ApsBOutDiscardsValue
         Counter64
      }

pr1645v2ApsBOutDiscardsGlobalIx OBJECT-TYPE
   SYNTAX      GlobalIndex
   MAX-ACCESS  not-accessible
   STATUS      current
   DESCRIPTION
      "The value of the tlsCntTreeGlobalIndex of the MANAGED OBJECT."
   ::= {pr1645v2ApsBOutDiscardsEntry 10}

pr1645v2ApsBOutDiscardsValue OBJECT-TYPE
   SYNTAX      Counter64
   MAX-ACCESS  read-only
   STATUS      current
   DESCRIPTION
      "Path: apsBundle.performance.ifOutDiscards

       64 bit unsigned wrappable counter."
   ::= {pr1645v2ApsBOutDiscardsEntry 2147483648}


pr1645v2ApsBOutErrors OBJECT IDENTIFIER ::= {pr1645v2ApsB 119}

pr1645v2ApsBOutErrorsTable OBJECT-TYPE
   SYNTAX      SEQUENCE OF Pr1645v2ApsBOutErrorsEntry
   MAX-ACCESS  not-accessible
   STATUS      current
   DESCRIPTION
      "ifOutErrors"
   ::= {pr1645v2ApsBOutErrors 1}

pr1645v2ApsBOutErrorsEntry OBJECT-TYPE
   SYNTAX      Pr1645v2ApsBOutErrorsEntry
   MAX-ACCESS  not-accessible
   STATUS      current
   DESCRIPTION
      ""
   INDEX      { pr1645v2ApsBOutErrorsGlobalIx }
   ::= {pr1645v2ApsBOutErrorsTable 1}

Pr1645v2ApsBOutErrorsEntry ::=
   SEQUENCE
      {
      pr1645v2ApsBOutErrorsGlobalIx
         GlobalIndex,
      pr1645v2ApsBOutErrorsValue
         Counter64
      }

pr1645v2ApsBOutErrorsGlobalIx OBJECT-TYPE
   SYNTAX      GlobalIndex
   MAX-ACCESS  not-accessible
   STATUS      current
   DESCRIPTION
      "The value of the tlsCntTreeGlobalIndex of the MANAGED OBJECT."
   ::= {pr1645v2ApsBOutErrorsEntry 10}

pr1645v2ApsBOutErrorsValue OBJECT-TYPE
   SYNTAX      Counter64
   MAX-ACCESS  read-only
   STATUS      current
   DESCRIPTION
      "Path: apsBundle.performance.ifOutErrors

       64 bit unsigned wrappable counter."
   ::= {pr1645v2ApsBOutErrorsEntry 2147483648}


pr1645v2ApsBOutQLen OBJECT IDENTIFIER ::= {pr1645v2ApsB 120}

pr1645v2ApsBOutQLenTable OBJECT-TYPE
   SYNTAX      SEQUENCE OF Pr1645v2ApsBOutQLenEntry
   MAX-ACCESS  not-accessible
   STATUS      current
   DESCRIPTION
      "ifOutQLen"
   ::= {pr1645v2ApsBOutQLen 1}

pr1645v2ApsBOutQLenEntry OBJECT-TYPE
   SYNTAX      Pr1645v2ApsBOutQLenEntry
   MAX-ACCESS  not-accessible
   STATUS      current
   DESCRIPTION
      ""
   INDEX      { pr1645v2ApsBOutQLenGlobalIx }
   ::= {pr1645v2ApsBOutQLenTable 1}

Pr1645v2ApsBOutQLenEntry ::=
   SEQUENCE
      {
      pr1645v2ApsBOutQLenGlobalIx
         GlobalIndex,
      pr1645v2ApsBOutQLenValue
         Gauge32
      }

pr1645v2ApsBOutQLenGlobalIx OBJECT-TYPE
   SYNTAX      GlobalIndex
   MAX-ACCESS  not-accessible
   STATUS      current
   DESCRIPTION
      "The value of the tlsCntTreeGlobalIndex of the MANAGED OBJECT."
   ::= {pr1645v2ApsBOutQLenEntry 10}

pr1645v2ApsBOutQLenValue OBJECT-TYPE
   SYNTAX      Gauge32
   MAX-ACCESS  read-only
   STATUS      current
   DESCRIPTION
      "Path: apsBundle.performance.ifOutQLen

       32 bit unsigned gauge value."
   ::= {pr1645v2ApsBOutQLenEntry 2147483648}


pr1645v2ApsBOutDropEx OBJECT IDENTIFIER ::= {pr1645v2ApsB 127}

pr1645v2ApsBOutDropExTable OBJECT-TYPE
   SYNTAX      SEQUENCE OF Pr1645v2ApsBOutDropExEntry
   MAX-ACCESS  not-accessible
   STATUS      current
   DESCRIPTION
      "ifOutDiscards"
   ::= {pr1645v2ApsBOutDropEx 1}

pr1645v2ApsBOutDropExEntry OBJECT-TYPE
   SYNTAX      Pr1645v2ApsBOutDropExEntry
   MAX-ACCESS  not-accessible
   STATUS      current
   DESCRIPTION
      ""
   INDEX      { pr1645v2ApsBOutDropExGlobalIx }
   ::= {pr1645v2ApsBOutDropExTable 1}

Pr1645v2ApsBOutDropExEntry ::=
   SEQUENCE
      {
      pr1645v2ApsBOutDropExGlobalIx
         GlobalIndex,
      pr1645v2ApsBOutDropExValue
         Counter64
      }

pr1645v2ApsBOutDropExGlobalIx OBJECT-TYPE
   SYNTAX      GlobalIndex
   MAX-ACCESS  not-accessible
   STATUS      current
   DESCRIPTION
      "The value of the tlsCntTreeGlobalIndex of the MANAGED OBJECT."
   ::= {pr1645v2ApsBOutDropExEntry 10}

pr1645v2ApsBOutDropExValue OBJECT-TYPE
   SYNTAX      Counter64
   MAX-ACCESS  read-only
   STATUS      current
   DESCRIPTION
      "Path: apsBundle.performance.ifOutDropLevelExceeded

       64 bit unsigned wrappable counter."
   ::= {pr1645v2ApsBOutDropExEntry 2147483648}


pr1645v2ApsBOutDropNoArp OBJECT IDENTIFIER ::= {pr1645v2ApsB 134}

pr1645v2ApsBOutDropNoArpTable OBJECT-TYPE
   SYNTAX      SEQUENCE OF Pr1645v2ApsBOutDropNoArpEntry
   MAX-ACCESS  not-accessible
   STATUS      current
   DESCRIPTION
      "ifOutDiscards"
   ::= {pr1645v2ApsBOutDropNoArp 1}

pr1645v2ApsBOutDropNoArpEntry OBJECT-TYPE
   SYNTAX      Pr1645v2ApsBOutDropNoArpEntry
   MAX-ACCESS  not-accessible
   STATUS      current
   DESCRIPTION
      ""
   INDEX      { pr1645v2ApsBOutDropNoArpGlobalIx }
   ::= {pr1645v2ApsBOutDropNoArpTable 1}

Pr1645v2ApsBOutDropNoArpEntry ::=
   SEQUENCE
      {
      pr1645v2ApsBOutDropNoArpGlobalIx
         GlobalIndex,
      pr1645v2ApsBOutDropNoArpValue
         Counter64
      }

pr1645v2ApsBOutDropNoArpGlobalIx OBJECT-TYPE
   SYNTAX      GlobalIndex
   MAX-ACCESS  not-accessible
   STATUS      current
   DESCRIPTION
      "The value of the tlsCntTreeGlobalIndex of the MANAGED OBJECT."
   ::= {pr1645v2ApsBOutDropNoArpEntry 10}

pr1645v2ApsBOutDropNoArpValue OBJECT-TYPE
   SYNTAX      Counter64
   MAX-ACCESS  read-only
   STATUS      current
   DESCRIPTION
      "Path: apsBundle.performance.ifOutDiscardsNoArp

       64 bit unsigned wrappable counter."
   ::= {pr1645v2ApsBOutDropNoArpEntry 2147483648}


pr1645v2ApsBOutDropFilter OBJECT IDENTIFIER ::= {pr1645v2ApsB 138}

pr1645v2ApsBOutDropFilterTable OBJECT-TYPE
   SYNTAX      SEQUENCE OF Pr1645v2ApsBOutDropFilterEntry
   MAX-ACCESS  not-accessible
   STATUS      current
   DESCRIPTION
      "ifOutDiscards"
   ::= {pr1645v2ApsBOutDropFilter 1}

pr1645v2ApsBOutDropFilterEntry OBJECT-TYPE
   SYNTAX      Pr1645v2ApsBOutDropFilterEntry
   MAX-ACCESS  not-accessible
   STATUS      current
   DESCRIPTION
      ""
   INDEX      { pr1645v2ApsBOutDropFilterGlobalIx }
   ::= {pr1645v2ApsBOutDropFilterTable 1}

Pr1645v2ApsBOutDropFilterEntry ::=
   SEQUENCE
      {
      pr1645v2ApsBOutDropFilterGlobalIx
         GlobalIndex,
      pr1645v2ApsBOutDropFilterValue
         Counter64
      }

pr1645v2ApsBOutDropFilterGlobalIx OBJECT-TYPE
   SYNTAX      GlobalIndex
   MAX-ACCESS  not-accessible
   STATUS      current
   DESCRIPTION
      "The value of the tlsCntTreeGlobalIndex of the MANAGED OBJECT."
   ::= {pr1645v2ApsBOutDropFilterEntry 10}

pr1645v2ApsBOutDropFilterValue OBJECT-TYPE
   SYNTAX      Counter64
   MAX-ACCESS  read-only
   STATUS      current
   DESCRIPTION
      "Path: apsBundle.performance.ifOutDiscardsFilter

       64 bit unsigned wrappable counter."
   ::= {pr1645v2ApsBOutDropFilterEntry 2147483648}


pr1645v2ApsBOutQueues OBJECT IDENTIFIER ::= {pr1645v2ApsB 129}

pr1645v2ApsBOutQueuesSSCTable OBJECT-TYPE
   SYNTAX      SEQUENCE OF Pr1645v2ApsBOutQueuesEntry
   MAX-ACCESS  not-accessible
   STATUS      current
   DESCRIPTION
      "Queue Lengths"
   ::= {pr1645v2ApsBOutQueues 1}

pr1645v2ApsBOutQueuesEntry OBJECT-TYPE
   SYNTAX      Pr1645v2ApsBOutQueuesEntry
   MAX-ACCESS  not-accessible
   STATUS      current
   DESCRIPTION
      ""
   INDEX      { pr1645v2ApsBOutQueuesGlobalIx,
                pr1645v2ApsBOutQueuesTableIx }
   ::= {pr1645v2ApsBOutQueuesSSCTable 1}

Pr1645v2ApsBOutQueuesEntry ::=
   SEQUENCE
      {
      pr1645v2ApsBOutQueuesGlobalIx
         GlobalIndex,
      pr1645v2ApsBOutQueuesTableIx
         TableIndex,
      pr1645v2ApsBOutQueuesName
         INTEGER,
      pr1645v2ApsBOutQueuesLength
         Integer32,
      pr1645v2ApsBOutQueuesOctetLength
         Integer32,
      pr1645v2ApsBOutQueuesRedLength
         Integer32,
      pr1645v2ApsBOutQueuesPacketsTotal
         Counter64,
      pr1645v2ApsBOutQueuesPacketsDirectTx
         Counter64,
      pr1645v2ApsBOutQueuesPacketsQueued
         Counter64,
      pr1645v2ApsBOutQueuesPacketsDropped
         Counter64,
      pr1645v2ApsBOutQueuesPacketsRedDropped
         Counter64,
      pr1645v2ApsBOutQueuesPacketsCirTx
         Counter64,
      pr1645v2ApsBOutQueuesPacketsEirTx
         Counter64,
      pr1645v2ApsBOutQueuesPacketsViolateTx
         Counter64,
      pr1645v2ApsBOutQueuesOctetsTotal
         Counter64,
      pr1645v2ApsBOutQueuesOctetsDirectTx
         Counter64,
      pr1645v2ApsBOutQueuesOctetsQueued
         Counter64,
      pr1645v2ApsBOutQueuesOctetsDropped
         Counter64,
      pr1645v2ApsBOutQueuesOctetsRedDropped
         Counter64,
      pr1645v2ApsBOutQueuesOctetsCirTx
         Counter64,
      pr1645v2ApsBOutQueuesOctetsEirTx
         Counter64,
      pr1645v2ApsBOutQueuesOctetsViolateTx
         Counter64,
      pr1645v2ApsBOutQueuesOctetsBandwidth15sec
         Integer32,
      pr1645v2ApsBOutQueuesOctetsBandwidth30sec
         Integer32,
      pr1645v2ApsBOutQueuesOctetsBandwidth1min
         Integer32,
      pr1645v2ApsBOutQueuesOctetsBandwidth2min
         Integer32,
      pr1645v2ApsBOutQueuesOctetsBandwidth5min
         Integer32
      }

pr1645v2ApsBOutQueuesGlobalIx OBJECT-TYPE
   SYNTAX      GlobalIndex
   MAX-ACCESS  not-accessible
   STATUS      current
   DESCRIPTION
      "The value of the tlsCntTreeGlobalIndex of the MANAGED OBJECT."
   ::= {pr1645v2ApsBOutQueuesEntry 10}

pr1645v2ApsBOutQueuesTableIx OBJECT-TYPE
   SYNTAX      TableIndex
   MAX-ACCESS  not-accessible
   STATUS      current
   DESCRIPTION
      ""
   ::= {pr1645v2ApsBOutQueuesEntry 11}

pr1645v2ApsBOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: apsBundle.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2ApsBOutQueuesEntry 16777216}

pr1645v2ApsBOutQueuesLength OBJECT-TYPE
   SYNTAX      Integer32
   MAX-ACCESS  read-only
   STATUS      current
   DESCRIPTION
      "Path: apsBundle.performance.ifOutPriorityQueues.length"
   ::= {pr1645v2ApsBOutQueuesEntry 33554432}

pr1645v2ApsBOutQueuesOctetLength OBJECT-TYPE
   SYNTAX      Integer32
   MAX-ACCESS  read-only
   STATUS      current
   DESCRIPTION
      "Path: apsBundle.performance.ifOutPriorityQueues.octetLength"
   ::= {pr1645v2ApsBOutQueuesEntry 150994944}

pr1645v2ApsBOutQueuesRedLength OBJECT-TYPE
   SYNTAX      Integer32
   MAX-ACCESS  read-only
   STATUS      current
   DESCRIPTION
      "Path: apsBundle.performance.ifOutPriorityQueues.redLength"
   ::= {pr1645v2ApsBOutQueuesEntry 134217728}

pr1645v2ApsBOutQueuesPacketsTotal OBJECT-TYPE
   SYNTAX      Counter64
   MAX-ACCESS  read-only
   STATUS      current
   DESCRIPTION
      "Path: apsBundle.performance.ifOutPriorityQueues.packets.total

       64 bit unsigned wrappable counter."
   ::= {pr1645v2ApsBOutQueuesEntry 50790400}

pr1645v2ApsBOutQueuesPacketsDirectTx OBJECT-TYPE
   SYNTAX      Counter64
   MAX-ACCESS  read-only
   STATUS      current
   DESCRIPTION
      "Path: apsBundle.performance.ifOutPriorityQueues.packets.directTx

       64 bit unsigned wrappable counter."
   ::= {pr1645v2ApsBOutQueuesEntry 50397184}

pr1645v2ApsBOutQueuesPacketsQueued OBJECT-TYPE
   SYNTAX      Counter64
   MAX-ACCESS  read-only
   STATUS      current
   DESCRIPTION
      "Path: apsBundle.performance.ifOutPriorityQueues.packets.queued

       64 bit unsigned wrappable counter."
   ::= {pr1645v2ApsBOutQueuesEntry 50462720}

pr1645v2ApsBOutQueuesPacketsDropped OBJECT-TYPE
   SYNTAX      Counter64
   MAX-ACCESS  read-only
   STATUS      current
   DESCRIPTION
      "Path: apsBundle.performance.ifOutPriorityQueues.packets.dropped

       64 bit unsigned wrappable counter."
   ::= {pr1645v2ApsBOutQueuesEntry 50528256}

pr1645v2ApsBOutQueuesPacketsRedDropped OBJECT-TYPE
   SYNTAX      Counter64
   MAX-ACCESS  read-only
   STATUS      current
   DESCRIPTION
      "Path: apsBundle.performance.ifOutPriorityQueues.packets.redDropped

       64 bit unsigned wrappable counter."
   ::= {pr1645v2ApsBOutQueuesEntry 50724864}

pr1645v2ApsBOutQueuesPacketsCirTx OBJECT-TYPE
   SYNTAX      Counter64
   MAX-ACCESS  read-only
   STATUS      current
   DESCRIPTION
      "Path: apsBundle.performance.ifOutPriorityQueues.packets.cirTx

       64 bit unsigned wrappable counter."
   ::= {pr1645v2ApsBOutQueuesEntry 50593792}

pr1645v2ApsBOutQueuesPacketsEirTx OBJECT-TYPE
   SYNTAX      Counter64
   MAX-ACCESS  read-only
   STATUS      current
   DESCRIPTION
      "Path: apsBundle.performance.ifOutPriorityQueues.packets.eirTx

       64 bit unsigned wrappable counter."
   ::= {pr1645v2ApsBOutQueuesEntry 50659328}

pr1645v2ApsBOutQueuesPacketsViolateTx OBJECT-TYPE
   SYNTAX      Counter64
   MAX-ACCESS  read-only
   STATUS      current
   DESCRIPTION
      "Path: apsBundle.performance.ifOutPriorityQueues.packets.violateTx

       64 bit unsigned wrappable counter."
   ::= {pr1645v2ApsBOutQueuesEntry 50855936}

pr1645v2ApsBOutQueuesOctetsTotal OBJECT-TYPE
   SYNTAX      Counter64
   MAX-ACCESS  read-only
   STATUS      current
   DESCRIPTION
      "Path: apsBundle.performance.ifOutPriorityQueues.octets.total

       64 bit unsigned wrappable counter."
   ::= {pr1645v2ApsBOutQueuesEntry 67567616}

pr1645v2ApsBOutQueuesOctetsDirectTx OBJECT-TYPE
   SYNTAX      Counter64
   MAX-ACCESS  read-only
   STATUS      current
   DESCRIPTION
      "Path: apsBundle.performance.ifOutPriorityQueues.octets.directTx

       64 bit unsigned wrappable counter."
   ::= {pr1645v2ApsBOutQueuesEntry 67174400}

pr1645v2ApsBOutQueuesOctetsQueued OBJECT-TYPE
   SYNTAX      Counter64
   MAX-ACCESS  read-only
   STATUS      current
   DESCRIPTION
      "Path: apsBundle.performance.ifOutPriorityQueues.octets.queued

       64 bit unsigned wrappable counter."
   ::= {pr1645v2ApsBOutQueuesEntry 67239936}

pr1645v2ApsBOutQueuesOctetsDropped OBJECT-TYPE
   SYNTAX      Counter64
   MAX-ACCESS  read-only
   STATUS      current
   DESCRIPTION
      "Path: apsBundle.performance.ifOutPriorityQueues.octets.dropped

       64 bit unsigned wrappable counter."
   ::= {pr1645v2ApsBOutQueuesEntry 67305472}

pr1645v2ApsBOutQueuesOctetsRedDropped OBJECT-TYPE
   SYNTAX      Counter64
   MAX-ACCESS  read-only
   STATUS      current
   DESCRIPTION
      "Path: apsBundle.performance.ifOutPriorityQueues.octets.redDropped

       64 bit unsigned wrappable counter."
   ::= {pr1645v2ApsBOutQueuesEntry 67502080}

pr1645v2ApsBOutQueuesOctetsCirTx OBJECT-TYPE
   SYNTAX      Counter64
   MAX-ACCESS  read-only
   STATUS      current
   DESCRIPTION
      "Path: apsBundle.performance.ifOutPriorityQueues.octets.cirTx

       64 bit unsigned wrappable counter."
   ::= {pr1645v2ApsBOutQueuesEntry 67371008}

pr1645v2ApsBOutQueuesOctetsEirTx OBJECT-TYPE
   SYNTAX      Counter64
   MAX-ACCESS  read-only
   STATUS      current
   DESCRIPTION
      "Path: apsBundle.performance.ifOutPriorityQueues.octets.eirTx

       64 bit unsigned wrappable counter."
   ::= {pr1645v2ApsBOutQueuesEntry 67436544}

pr1645v2ApsBOutQueuesOctetsViolateTx OBJECT-TYPE
   SYNTAX      Counter64
   MAX-ACCESS  read-only
   STATUS      current
   DESCRIPTION
      "Path: apsBundle.performance.ifOutPriorityQueues.octets.violateTx

       64 bit unsigned wrappable counter."
   ::= {pr1645v2ApsBOutQueuesEntry 67633152}

pr1645v2ApsBOutQueuesOctetsBandwidth15sec OBJECT-TYPE
   SYNTAX      Integer32
   MAX-ACCESS  read-only
   STATUS      current
   DESCRIPTION
      "Path: apsBundle.performance.ifOutPriorityQueues.octets.bandwidth.15sec

       unit name = bps
       formula = 8 * ; 8 /"
   ::= {pr1645v2ApsBOutQueuesEntry 70386944}

pr1645v2ApsBOutQueuesOctetsBandwidth30sec OBJECT-TYPE
   SYNTAX      Integer32
   MAX-ACCESS  read-only
   STATUS      current
   DESCRIPTION
      "Path: apsBundle.performance.ifOutPriorityQueues.octets.bandwidth.30sec

       unit name = bps
       formula = 8 * ; 8 /"
   ::= {pr1645v2ApsBOutQueuesEntry 70388224}

pr1645v2ApsBOutQueuesOctetsBandwidth1min OBJECT-TYPE
   SYNTAX      Integer32
   MAX-ACCESS  read-only
   STATUS      current
   DESCRIPTION
      "Path: apsBundle.performance.ifOutPriorityQueues.octets.bandwidth.1min

       unit name = bps
       formula = 8 * ; 8 /"
   ::= {pr1645v2ApsBOutQueuesEntry 70390784}

pr1645v2ApsBOutQueuesOctetsBandwidth2min OBJECT-TYPE
   SYNTAX      Integer32
   MAX-ACCESS  read-only
   STATUS      current
   DESCRIPTION
      "Path: apsBundle.performance.ifOutPriorityQueues.octets.bandwidth.2min

       unit name = bps
       formula = 8 * ; 8 /"
   ::= {pr1645v2ApsBOutQueuesEntry 70395904}

pr1645v2ApsBOutQueuesOctetsBandwidth5min OBJECT-TYPE
   SYNTAX      Integer32
   MAX-ACCESS  read-only
   STATUS      current
   DESCRIPTION
      "Path: apsBundle.performance.ifOutPriorityQueues.octets.bandwidth.5min

       unit name = bps
       formula = 8 * ; 8 /"
   ::= {pr1645v2ApsBOutQueuesEntry 70411264}

pr1645v2ApsBOutQueuesH2Performance OBJECT-TYPE
   SYNTAX      SEQUENCE OF Pr1645v2ApsBOutQueuesH2PerformanceEntry
   MAX-ACCESS  not-accessible
   STATUS      current
   DESCRIPTION
      ""
   ::= {pr1645v2ApsBOutQueues 83886080}

pr1645v2ApsBOutQueuesH2PerformanceEntry OBJECT-TYPE
   SYNTAX      Pr1645v2ApsBOutQueuesH2PerformanceEntry
   MAX-ACCESS  not-accessible
   STATUS      current
   DESCRIPTION
      ""
   INDEX      { pr1645v2ApsBOutQueuesH2PerformanceGlobalIx,
                pr1645v2ApsBOutQueuesTableIx,
                pr1645v2ApsBOutQueuesH2PerformanceTableIx }
   ::= {pr1645v2ApsBOutQueuesH2Performance 1}

Pr1645v2ApsBOutQueuesH2PerformanceEntry ::=
   SEQUENCE
      {
      pr1645v2ApsBOutQueuesH2PerformanceGlobalIx
         GlobalIndex,
      pr1645v2ApsBOutQueuesH2PerformanceTableIx
         TableIndex,
      pr1645v2ApsBOutQueuesH2PerformanceSysUpTime
         TimeTicks,
      pr1645v2ApsBOutQueuesH2PerformanceTotPkts
         Counter64,
      pr1645v2ApsBOutQueuesH2PerformanceDirTxPkts
         Counter64,
      pr1645v2ApsBOutQueuesH2PerformanceQdPkts
         Counter64,
      pr1645v2ApsBOutQueuesH2PerformanceDropPkts
         Counter64,
      pr1645v2ApsBOutQueuesH2PerformanceRDropPkts
         Counter64,
      pr1645v2ApsBOutQueuesH2PerformanceCirTxPkts
         Counter64,
      pr1645v2ApsBOutQueuesH2PerformanceEirTxPkts
         Counter64,
      pr1645v2ApsBOutQueuesH2PerformanceViolTxPkts
         Counter64,
      pr1645v2ApsBOutQueuesH2PerformanceTotOcts
         Counter64,
      pr1645v2ApsBOutQueuesH2PerformanceDirTxOcts
         Counter64,
      pr1645v2ApsBOutQueuesH2PerformanceQdOcts
         Counter64,
      pr1645v2ApsBOutQueuesH2PerformanceDropOcts
         Counter64,
      pr1645v2ApsBOutQueuesH2PerformanceRDropOcts
         Counter64,
      pr1645v2ApsBOutQueuesH2PerformanceCirTxOcts
         Counter64,
      pr1645v2ApsBOutQueuesH2PerformanceEirTxOcts
         Counter64,
      pr1645v2ApsBOutQueuesH2PerformanceViolTxOcts
         Counter64,
      pr1645v2ApsBOutQueuesH2PerformanceBandwidth
         Integer32
      }

pr1645v2ApsBOutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2ApsBOutQueuesH2PerformanceEntry 10}

pr1645v2ApsBOutQueuesH2PerformanceTableIx OBJECT-TYPE
   SYNTAX      TableIndex
   MAX-ACCESS  not-accessible
   STATUS      current
   DESCRIPTION
      ""
   ::= {pr1645v2ApsBOutQueuesH2PerformanceEntry 11}

pr1645v2ApsBOutQueuesH2PerformanceSysUpTime OBJECT-TYPE
   SYNTAX      TimeTicks
   MAX-ACCESS  read-only
   STATUS      current
   DESCRIPTION
      "Path: apsBundle.performance.ifOutPriorityQueues.h2Performance.sysUpTime

       Time in centi-second."
   ::= {pr1645v2ApsBOutQueuesH2PerformanceEntry 16777216}

pr1645v2ApsBOutQueuesH2PerformanceTotPkts OBJECT-TYPE
   SYNTAX      Counter64
   MAX-ACCESS  read-only
   STATUS      current
   DESCRIPTION
      "Path: apsBundle.performance.ifOutPriorityQueues.h2Performance.totalPkts

       64 bit unsigned wrappable counter."
   ::= {pr1645v2ApsBOutQueuesH2PerformanceEntry 234881024}

pr1645v2ApsBOutQueuesH2PerformanceDirTxPkts OBJECT-TYPE
   SYNTAX      Counter64
   MAX-ACCESS  read-only
   STATUS      current
   DESCRIPTION
      "Path: apsBundle.performance.ifOutPriorityQueues.h2Performance.directTxPkts

       64 bit unsigned wrappable counter."
   ::= {pr1645v2ApsBOutQueuesH2PerformanceEntry 33554432}

pr1645v2ApsBOutQueuesH2PerformanceQdPkts OBJECT-TYPE
   SYNTAX      Counter64
   MAX-ACCESS  read-only
   STATUS      current
   DESCRIPTION
      "Path: apsBundle.performance.ifOutPriorityQueues.h2Performance.queuedPkts

       64 bit unsigned wrappable counter."
   ::= {pr1645v2ApsBOutQueuesH2PerformanceEntry 50331648}

pr1645v2ApsBOutQueuesH2PerformanceDropPkts OBJECT-TYPE
   SYNTAX      Counter64
   MAX-ACCESS  read-only
   STATUS      current
   DESCRIPTION
      "Path: apsBundle.performance.ifOutPriorityQueues.h2Performance.droppedPkts

       64 bit unsigned wrappable counter."
   ::= {pr1645v2ApsBOutQueuesH2PerformanceEntry 67108864}

pr1645v2ApsBOutQueuesH2PerformanceRDropPkts OBJECT-TYPE
   SYNTAX      Counter64
   MAX-ACCESS  read-only
   STATUS      current
   DESCRIPTION
      "Path: apsBundle.performance.ifOutPriorityQueues.h2Performance.redDroppedPkts

       64 bit unsigned wrappable counter."
   ::= {pr1645v2ApsBOutQueuesH2PerformanceEntry 201326592}

pr1645v2ApsBOutQueuesH2PerformanceCirTxPkts OBJECT-TYPE
   SYNTAX      Counter64
   MAX-ACCESS  read-only
   STATUS      current
   DESCRIPTION
      "Path: apsBundle.performance.ifOutPriorityQueues.h2Performance.cirTxPkts

       64 bit unsigned wrappable counter."
   ::= {pr1645v2ApsBOutQueuesH2PerformanceEntry 83886080}

pr1645v2ApsBOutQueuesH2PerformanceEirTxPkts OBJECT-TYPE
   SYNTAX      Counter64
   MAX-ACCESS  read-only
   STATUS      current
   DESCRIPTION
      "Path: apsBundle.performance.ifOutPriorityQueues.h2Performance.eirTxPkts

       64 bit unsigned wrappable counter."
   ::= {pr1645v2ApsBOutQueuesH2PerformanceEntry 100663296}

pr1645v2ApsBOutQueuesH2PerformanceViolTxPkts OBJECT-TYPE
   SYNTAX      Counter64
   MAX-ACCESS  read-only
   STATUS      current
   DESCRIPTION
      "Path: apsBundle.performance.ifOutPriorityQueues.h2Performance.violateTxPkts

       64 bit unsigned wrappable counter."
   ::= {pr1645v2ApsBOutQueuesH2PerformanceEntry 301989888}

pr1645v2ApsBOutQueuesH2PerformanceTotOcts OBJECT-TYPE
   SYNTAX      Counter64
   MAX-ACCESS  read-only
   STATUS      current
   DESCRIPTION
      "Path: apsBundle.performance.ifOutPriorityQueues.h2Performance.totalOctets

       64 bit unsigned wrappable counter."
   ::= {pr1645v2ApsBOutQueuesH2PerformanceEntry 251658240}

pr1645v2ApsBOutQueuesH2PerformanceDirTxOcts OBJECT-TYPE
   SYNTAX      Counter64
   MAX-ACCESS  read-only
   STATUS      current
   DESCRIPTION
      "Path: apsBundle.performance.ifOutPriorityQueues.h2Performance.directTxOctets

       64 bit unsigned wrappable counter."
   ::= {pr1645v2ApsBOutQueuesH2PerformanceEntry 117440512}

pr1645v2ApsBOutQueuesH2PerformanceQdOcts OBJECT-TYPE
   SYNTAX      Counter64
   MAX-ACCESS  read-only
   STATUS      current
   DESCRIPTION
      "Path: apsBundle.performance.ifOutPriorityQueues.h2Performance.queuedOctets

       64 bit unsigned wrappable counter."
   ::= {pr1645v2ApsBOutQueuesH2PerformanceEntry 134217728}

pr1645v2ApsBOutQueuesH2PerformanceDropOcts OBJECT-TYPE
   SYNTAX      Counter64
   MAX-ACCESS  read-only
   STATUS      current
   DESCRIPTION
      "Path: apsBundle.performance.ifOutPriorityQueues.h2Performance.droppedOctets

       64 bit unsigned wrappable counter."
   ::= {pr1645v2ApsBOutQueuesH2PerformanceEntry 150994944}

pr1645v2ApsBOutQueuesH2PerformanceRDropOcts OBJECT-TYPE
   SYNTAX      Counter64
   MAX-ACCESS  read-only
   STATUS      current
   DESCRIPTION
      "Path: apsBundle.performance.ifOutPriorityQueues.h2Performance.redDroppedOctets

       64 bit unsigned wrappable counter."
   ::= {pr1645v2ApsBOutQueuesH2PerformanceEntry 218103808}

pr1645v2ApsBOutQueuesH2PerformanceCirTxOcts OBJECT-TYPE
   SYNTAX      Counter64
   MAX-ACCESS  read-only
   STATUS      current
   DESCRIPTION
      "Path: apsBundle.performance.ifOutPriorityQueues.h2Performance.cirTxOctets

       64 bit unsigned wrappable counter."
   ::= {pr1645v2ApsBOutQueuesH2PerformanceEntry 167772160}

pr1645v2ApsBOutQueuesH2PerformanceEirTxOcts OBJECT-TYPE
   SYNTAX      Counter64
   MAX-ACCESS  read-only
   STATUS      current
   DESCRIPTION
      "Path: apsBundle.performance.ifOutPriorityQueues.h2Performance.eirTxOctets

       64 bit unsigned wrappable counter."
   ::= {pr1645v2ApsBOutQueuesH2PerformanceEntry 184549376}

pr1645v2ApsBOutQueuesH2PerformanceViolTxOcts OBJECT-TYPE
   SYNTAX      Counter64
   MAX-ACCESS  read-only
   STATUS      current
   DESCRIPTION
      "Path: apsBundle.performance.ifOutPriorityQueues.h2Performance.violateTxOctets

       64 bit unsigned wrappable counter."
   ::= {pr1645v2ApsBOutQueuesH2PerformanceEntry 318767104}

pr1645v2ApsBOutQueuesH2PerformanceBandwidth OBJECT-TYPE
   SYNTAX      Integer32
   MAX-ACCESS  read-only
   STATUS      current
   DESCRIPTION
      "Path: apsBundle.performance.ifOutPriorityQueues.h2Performance.bandwidth

       unit name = bps
       formula = 8 * ; 8 /"
   ::= {pr1645v2ApsBOutQueuesH2PerformanceEntry 268435456}

pr1645v2ApsBOutQueuesH24Performance OBJECT-TYPE
   SYNTAX      SEQUENCE OF Pr1645v2ApsBOutQueuesH24PerformanceEntry
   MAX-ACCESS  not-accessible
   STATUS      current
   DESCRIPTION
      ""
   ::= {pr1645v2ApsBOutQueues 100663296}

pr1645v2ApsBOutQueuesH24PerformanceEntry OBJECT-TYPE
   SYNTAX      Pr1645v2ApsBOutQueuesH24PerformanceEntry
   MAX-ACCESS  not-accessible
   STATUS      current
   DESCRIPTION
      ""
   INDEX      { pr1645v2ApsBOutQueuesH24PerformanceGlobalIx,
                pr1645v2ApsBOutQueuesTableIx,
                pr1645v2ApsBOutQueuesH24PerformanceTableIx }
   ::= {pr1645v2ApsBOutQueuesH24Performance 1}

Pr1645v2ApsBOutQueuesH24PerformanceEntry ::=
   SEQUENCE
      {
      pr1645v2ApsBOutQueuesH24PerformanceGlobalIx
         GlobalIndex,
      pr1645v2ApsBOutQueuesH24PerformanceTableIx
         TableIndex,
      pr1645v2ApsBOutQueuesH24PerformanceSysUpTime
         TimeTicks,
      pr1645v2ApsBOutQueuesH24PerformanceTotPkts
         Counter64,
      pr1645v2ApsBOutQueuesH24PerformanceDirTxPkts
         Counter64,
      pr1645v2ApsBOutQueuesH24PerformanceQdPkts
         Counter64,
      pr1645v2ApsBOutQueuesH24PerformanceDropPkts
         Counter64,
      pr1645v2ApsBOutQueuesH24PerformanceRDropPkts
         Counter64,
      pr1645v2ApsBOutQueuesH24PerformanceCirTxPkts
         Counter64,
      pr1645v2ApsBOutQueuesH24PerformanceEirTxPkts
         Counter64,
      pr1645v2ApsBOutQueuesH24PerformanceViolTxPkts
         Counter64,
      pr1645v2ApsBOutQueuesH24PerformanceTotOcts
         Counter64,
      pr1645v2ApsBOutQueuesH24PerformanceDirTxOcts
         Counter64,
      pr1645v2ApsBOutQueuesH24PerformanceQdOcts
         Counter64,
      pr1645v2ApsBOutQueuesH24PerformanceDropOcts
         Counter64,
      pr1645v2ApsBOutQueuesH24PerformanceRDropOcts
         Counter64,
      pr1645v2ApsBOutQueuesH24PerformanceCirTxOcts
         Counter64,
      pr1645v2ApsBOutQueuesH24PerformanceEirTxOcts
         Counter64,
      pr1645v2ApsBOutQueuesH24PerformanceViolTxOcts
         Counter64,
      pr1645v2ApsBOutQueuesH24PerformanceBandwidth
         Integer32
      }

pr1645v2ApsBOutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2ApsBOutQueuesH24PerformanceEntry 10}

pr1645v2ApsBOutQueuesH24PerformanceTableIx OBJECT-TYPE
   SYNTAX      TableIndex
   MAX-ACCESS  not-accessible
   STATUS      current
   DESCRIPTION
      ""
   ::= {pr1645v2ApsBOutQueuesH24PerformanceEntry 11}

pr1645v2ApsBOutQueuesH24PerformanceSysUpTime OBJECT-TYPE
   SYNTAX      TimeTicks
   MAX-ACCESS  read-only
   STATUS      current
   DESCRIPTION
      "Path: apsBundle.performance.ifOutPriorityQueues.h24Performance.sysUpTime

       Time in centi-second."
   ::= {pr1645v2ApsBOutQueuesH24PerformanceEntry 16777216}

pr1645v2ApsBOutQueuesH24PerformanceTotPkts OBJECT-TYPE
   SYNTAX      Counter64
   MAX-ACCESS  read-only
   STATUS      current
   DESCRIPTION
      "Path: apsBundle.performance.ifOutPriorityQueues.h24Performance.totalPkts

       64 bit unsigned wrappable counter."
   ::= {pr1645v2ApsBOutQueuesH24PerformanceEntry 234881024}

pr1645v2ApsBOutQueuesH24PerformanceDirTxPkts OBJECT-TYPE
   SYNTAX      Counter64
   MAX-ACCESS  read-only
   STATUS      current
   DESCRIPTION
      "Path: apsBundle.performance.ifOutPriorityQueues.h24Performance.directTxPkts

       64 bit unsigned wrappable counter."
   ::= {pr1645v2ApsBOutQueuesH24PerformanceEntry 33554432}

pr1645v2ApsBOutQueuesH24PerformanceQdPkts OBJECT-TYPE
   SYNTAX      Counter64
   MAX-ACCESS  read-only
   STATUS      current
   DESCRIPTION
      "Path: apsBundle.performance.ifOutPriorityQueues.h24Performance.queuedPkts

       64 bit unsigned wrappable counter."
   ::= {pr1645v2ApsBOutQueuesH24PerformanceEntry 50331648}

pr1645v2ApsBOutQueuesH24PerformanceDropPkts OBJECT-TYPE
   SYNTAX      Counter64
   MAX-ACCESS  read-only
   STATUS      current
   DESCRIPTION
      "Path: apsBundle.performance.ifOutPriorityQueues.h24Performance.droppedPkts

       64 bit unsigned wrappable counter."
   ::= {pr1645v2ApsBOutQueuesH24PerformanceEntry 67108864}

pr1645v2ApsBOutQueuesH24PerformanceRDropPkts OBJECT-TYPE
   SYNTAX      Counter64
   MAX-ACCESS  read-only
   STATUS      current
   DESCRIPTION
      "Path: apsBundle.performance.ifOutPriorityQueues.h24Performance.redDroppedPkts

       64 bit unsigned wrappable counter."
   ::= {pr1645v2ApsBOutQueuesH24PerformanceEntry 201326592}

pr1645v2ApsBOutQueuesH24PerformanceCirTxPkts OBJECT-TYPE
   SYNTAX      Counter64
   MAX-ACCESS  read-only
   STATUS      current
   DESCRIPTION
      "Path: apsBundle.performance.ifOutPriorityQueues.h24Performance.cirTxPkts

       64 bit unsigned wrappable counter."
   ::= {pr1645v2ApsBOutQueuesH24PerformanceEntry 83886080}

pr1645v2ApsBOutQueuesH24PerformanceEirTxPkts OBJECT-TYPE
   SYNTAX      Counter64
   MAX-ACCESS  read-only
   STATUS      current
   DESCRIPTION
      "Path: apsBundle.performance.ifOutPriorityQueues.h24Performance.eirTxPkts

       64 bit unsigned wrappable counter."
   ::= {pr1645v2ApsBOutQueuesH24PerformanceEntry 100663296}

pr1645v2ApsBOutQueuesH24PerformanceViolTxPkts OBJECT-TYPE
   SYNTAX      Counter64
   MAX-ACCESS  read-only
   STATUS      current
   DESCRIPTION
      "Path: apsBundle.performance.ifOutPriorityQueues.h24Performance.violateTxPkts

       64 bit unsigned wrappable counter."
   ::= {pr1645v2ApsBOutQueuesH24PerformanceEntry 301989888}

pr1645v2ApsBOutQueuesH24PerformanceTotOcts OBJECT-TYPE
   SYNTAX      Counter64
   MAX-ACCESS  read-only
   STATUS      current
   DESCRIPTION
      "Path: apsBundle.performance.ifOutPriorityQueues.h24Performance.totalOctets

       64 bit unsigned wrappable counter."
   ::= {pr1645v2ApsBOutQueuesH24PerformanceEntry 251658240}

pr1645v2ApsBOutQueuesH24PerformanceDirTxOcts OBJECT-TYPE
   SYNTAX      Counter64
   MAX-ACCESS  read-only
   STATUS      current
   DESCRIPTION
      "Path: apsBundle.performance.ifOutPriorityQueues.h24Performance.directTxOctets

       64 bit unsigned wrappable counter."
   ::= {pr1645v2ApsBOutQueuesH24PerformanceEntry 117440512}

pr1645v2ApsBOutQueuesH24PerformanceQdOcts OBJECT-TYPE
   SYNTAX      Counter64
   MAX-ACCESS  read-only
   STATUS      current
   DESCRIPTION
      "Path: apsBundle.performance.ifOutPriorityQueues.h24Performance.queuedOctets

       64 bit unsigned wrappable counter."
   ::= {pr1645v2ApsBOutQueuesH24PerformanceEntry 134217728}

pr1645v2ApsBOutQueuesH24PerformanceDropOcts OBJECT-TYPE
   SYNTAX      Counter64
   MAX-ACCESS  read-only
   STATUS      current
   DESCRIPTION
      "Path: apsBundle.performance.ifOutPriorityQueues.h24Performance.droppedOctets

       64 bit unsigned wrappable counter."
   ::= {pr1645v2ApsBOutQueuesH24PerformanceEntry 150994944}

pr1645v2ApsBOutQueuesH24PerformanceRDropOcts OBJECT-TYPE
   SYNTAX      Counter64
   MAX-ACCESS  read-only
   STATUS      current
   DESCRIPTION
      "Path: apsBundle.performance.ifOutPriorityQueues.h24Performance.redDroppedOctets

       64 bit unsigned wrappable counter."
   ::= {pr1645v2ApsBOutQueuesH24PerformanceEntry 218103808}

pr1645v2ApsBOutQueuesH24PerformanceCirTxOcts OBJECT-TYPE
   SYNTAX      Counter64
   MAX-ACCESS  read-only
   STATUS      current
   DESCRIPTION
      "Path: apsBundle.performance.ifOutPriorityQueues.h24Performance.cirTxOctets

       64 bit unsigned wrappable counter."
   ::= {pr1645v2ApsBOutQueuesH24PerformanceEntry 167772160}

pr1645v2ApsBOutQueuesH24PerformanceEirTxOcts OBJECT-TYPE
   SYNTAX      Counter64
   MAX-ACCESS  read-only
   STATUS      current
   DESCRIPTION
      "Path: apsBundle.performance.ifOutPriorityQueues.h24Performance.eirTxOctets

       64 bit unsigned wrappable counter."
   ::= {pr1645v2ApsBOutQueuesH24PerformanceEntry 184549376}

pr1645v2ApsBOutQueuesH24PerformanceViolTxOcts OBJECT-TYPE
   SYNTAX      Counter64
   MAX-ACCESS  read-only
   STATUS      current
   DESCRIPTION
      "Path: apsBundle.performance.ifOutPriorityQueues.h24Performance.violateTxOctets

       64 bit unsigned wrappable counter."
   ::= {pr1645v2ApsBOutQueuesH24PerformanceEntry 318767104}

pr1645v2ApsBOutQueuesH24PerformanceBandwidth OBJECT-TYPE
   SYNTAX      Integer32
   MAX-ACCESS  read-only
   STATUS      current
   DESCRIPTION
      "Path: apsBundle.performance.ifOutPriorityQueues.h24Performance.bandwidth

       unit name = bps
       formula = 8 * ; 8 /"
   ::= {pr1645v2ApsBOutQueuesH24PerformanceEntry 268435456}

pr1645v2ApsBOutQueuesD7Performance OBJECT-TYPE
   SYNTAX      SEQUENCE OF Pr1645v2ApsBOutQueuesD7PerformanceEntry
   MAX-ACCESS  not-accessible
   STATUS      current
   DESCRIPTION
      ""
   ::= {pr1645v2ApsBOutQueues 117440512}

pr1645v2ApsBOutQueuesD7PerformanceEntry OBJECT-TYPE
   SYNTAX      Pr1645v2ApsBOutQueuesD7PerformanceEntry
   MAX-ACCESS  not-accessible
   STATUS      current
   DESCRIPTION
      ""
   INDEX      { pr1645v2ApsBOutQueuesD7PerformanceGlobalIx,
                pr1645v2ApsBOutQueuesTableIx,
                pr1645v2ApsBOutQueuesD7PerformanceTableIx }
   ::= {pr1645v2ApsBOutQueuesD7Performance 1}

Pr1645v2ApsBOutQueuesD7PerformanceEntry ::=
   SEQUENCE
      {
      pr1645v2ApsBOutQueuesD7PerformanceGlobalIx
         GlobalIndex,
      pr1645v2ApsBOutQueuesD7PerformanceTableIx
         TableIndex,
      pr1645v2ApsBOutQueuesD7PerformanceSysUpTime
         TimeTicks,
      pr1645v2ApsBOutQueuesD7PerformanceTotPkts
         Counter64,
      pr1645v2ApsBOutQueuesD7PerformanceDirTxPkts
         Counter64,
      pr1645v2ApsBOutQueuesD7PerformanceQdPkts
         Counter64,
      pr1645v2ApsBOutQueuesD7PerformanceDropPkts
         Counter64,
      pr1645v2ApsBOutQueuesD7PerformanceRDropPkts
         Counter64,
      pr1645v2ApsBOutQueuesD7PerformanceCirTxPkts
         Counter64,
      pr1645v2ApsBOutQueuesD7PerformanceEirTxPkts
         Counter64,
      pr1645v2ApsBOutQueuesD7PerformanceViolTxPkts
         Counter64,
      pr1645v2ApsBOutQueuesD7PerformanceTotOcts
         Counter64,
      pr1645v2ApsBOutQueuesD7PerformanceDirTxOcts
         Counter64,
      pr1645v2ApsBOutQueuesD7PerformanceQdOcts
         Counter64,
      pr1645v2ApsBOutQueuesD7PerformanceDropOcts
         Counter64,
      pr1645v2ApsBOutQueuesD7PerformanceRDropOcts
         Counter64,
      pr1645v2ApsBOutQueuesD7PerformanceCirTxOcts
         Counter64,
      pr1645v2ApsBOutQueuesD7PerformanceEirTxOcts
         Counter64,
      pr1645v2ApsBOutQueuesD7PerformanceViolTxOcts
         Counter64,
      pr1645v2ApsBOutQueuesD7PerformanceBandwidth
         Integer32
      }

pr1645v2ApsBOutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2ApsBOutQueuesD7PerformanceEntry 10}

pr1645v2ApsBOutQueuesD7PerformanceTableIx OBJECT-TYPE
   SYNTAX      TableIndex
   MAX-ACCESS  not-accessible
   STATUS      current
   DESCRIPTION
      ""
   ::= {pr1645v2ApsBOutQueuesD7PerformanceEntry 11}

pr1645v2ApsBOutQueuesD7PerformanceSysUpTime OBJECT-TYPE
   SYNTAX      TimeTicks
   MAX-ACCESS  read-only
   STATUS      current
   DESCRIPTION
      "Path: apsBundle.performance.ifOutPriorityQueues.d7Performance.sysUpTime

       Time in centi-second."
   ::= {pr1645v2ApsBOutQueuesD7PerformanceEntry 16777216}

pr1645v2ApsBOutQueuesD7PerformanceTotPkts OBJECT-TYPE
   SYNTAX      Counter64
   MAX-ACCESS  read-only
   STATUS      current
   DESCRIPTION
      "Path: apsBundle.performance.ifOutPriorityQueues.d7Performance.totalPkts

       64 bit unsigned wrappable counter."
   ::= {pr1645v2ApsBOutQueuesD7PerformanceEntry 234881024}

pr1645v2ApsBOutQueuesD7PerformanceDirTxPkts OBJECT-TYPE
   SYNTAX      Counter64
   MAX-ACCESS  read-only
   STATUS      current
   DESCRIPTION
      "Path: apsBundle.performance.ifOutPriorityQueues.d7Performance.directTxPkts

       64 bit unsigned wrappable counter."
   ::= {pr1645v2ApsBOutQueuesD7PerformanceEntry 33554432}

pr1645v2ApsBOutQueuesD7PerformanceQdPkts OBJECT-TYPE
   SYNTAX      Counter64
   MAX-ACCESS  read-only
   STATUS      current
   DESCRIPTION
      "Path: apsBundle.performance.ifOutPriorityQueues.d7Performance.queuedPkts

       64 bit unsigned wrappable counter."
   ::= {pr1645v2ApsBOutQueuesD7PerformanceEntry 50331648}

pr1645v2ApsBOutQueuesD7PerformanceDropPkts OBJECT-TYPE
   SYNTAX      Counter64
   MAX-ACCESS  read-only
   STATUS      current
   DESCRIPTION
      "Path: apsBundle.performance.ifOutPriorityQueues.d7Performance.droppedPkts

       64 bit unsigned wrappable counter."
   ::= {pr1645v2ApsBOutQueuesD7PerformanceEntry 67108864}

pr1645v2ApsBOutQueuesD7PerformanceRDropPkts OBJECT-TYPE
   SYNTAX      Counter64
   MAX-ACCESS  read-only
   STATUS      current
   DESCRIPTION
      "Path: apsBundle.performance.ifOutPriorityQueues.d7Performance.redDroppedPkts

       64 bit unsigned wrappable counter."
   ::= {pr1645v2ApsBOutQueuesD7PerformanceEntry 201326592}

pr1645v2ApsBOutQueuesD7PerformanceCirTxPkts OBJECT-TYPE
   SYNTAX      Counter64
   MAX-ACCESS  read-only
   STATUS      current
   DESCRIPTION
      "Path: apsBundle.performance.ifOutPriorityQueues.d7Performance.cirTxPkts

       64 bit unsigned wrappable counter."
   ::= {pr1645v2ApsBOutQueuesD7PerformanceEntry 83886080}

pr1645v2ApsBOutQueuesD7PerformanceEirTxPkts OBJECT-TYPE
   SYNTAX      Counter64
   MAX-ACCESS  read-only
   STATUS      current
   DESCRIPTION
      "Path: apsBundle.performance.ifOutPriorityQueues.d7Performance.eirTxPkts

       64 bit unsigned wrappable counter."
   ::= {pr1645v2ApsBOutQueuesD7PerformanceEntry 100663296}

pr1645v2ApsBOutQueuesD7PerformanceViolTxPkts OBJECT-TYPE
   SYNTAX      Counter64
   MAX-ACCESS  read-only
   STATUS      current
   DESCRIPTION
      "Path: apsBundle.performance.ifOutPriorityQueues.d7Performance.violateTxPkts

       64 bit unsigned wrappable counter."
   ::= {pr1645v2ApsBOutQueuesD7PerformanceEntry 301989888}

pr1645v2ApsBOutQueuesD7PerformanceTotOcts OBJECT-TYPE
   SYNTAX      Counter64
   MAX-ACCESS  read-only
   STATUS      current
   DESCRIPTION
      "Path: apsBundle.performance.ifOutPriorityQueues.d7Performance.totalOctets

       64 bit unsigned wrappable counter."
   ::= {pr1645v2ApsBOutQueuesD7PerformanceEntry 251658240}

pr1645v2ApsBOutQueuesD7PerformanceDirTxOcts OBJECT-TYPE
   SYNTAX      Counter64
   MAX-ACCESS  read-only
   STATUS      current
   DESCRIPTION
      "Path: apsBundle.performance.ifOutPriorityQueues.d7Performance.directTxOctets

       64 bit unsigned wrappable counter."
   ::= {pr1645v2ApsBOutQueuesD7PerformanceEntry 117440512}

pr1645v2ApsBOutQueuesD7PerformanceQdOcts OBJECT-TYPE
   SYNTAX      Counter64
   MAX-ACCESS  read-only
   STATUS      current
   DESCRIPTION
      "Path: apsBundle.performance.ifOutPriorityQueues.d7Performance.queuedOctets

       64 bit unsigned wrappable counter."
   ::= {pr1645v2ApsBOutQueuesD7PerformanceEntry 134217728}

pr1645v2ApsBOutQueuesD7PerformanceDropOcts OBJECT-TYPE
   SYNTAX      Counter64
   MAX-ACCESS  read-only
   STATUS      current
   DESCRIPTION
      "Path: apsBundle.performance.ifOutPriorityQueues.d7Performance.droppedOctets

       64 bit unsigned wrappable counter."
   ::= {pr1645v2ApsBOutQueuesD7PerformanceEntry 150994944}

pr1645v2ApsBOutQueuesD7PerformanceRDropOcts OBJECT-TYPE
   SYNTAX      Counter64
   MAX-ACCESS  read-only
   STATUS      current
   DESCRIPTION
      "Path: apsBundle.performance.ifOutPriorityQueues.d7Performance.redDroppedOctets

       64 bit unsigned wrappable counter."
   ::= {pr1645v2ApsBOutQueuesD7PerformanceEntry 218103808}

pr1645v2ApsBOutQueuesD7PerformanceCirTxOcts OBJECT-TYPE
   SYNTAX      Counter64
   MAX-ACCESS  read-only
   STATUS      current
   DESCRIPTION
      "Path: apsBundle.performance.ifOutPriorityQueues.d7Performance.cirTxOctets

       64 bit unsigned wrappable counter."
   ::= {pr1645v2ApsBOutQueuesD7PerformanceEntry 167772160}

pr1645v2ApsBOutQueuesD7PerformanceEirTxOcts OBJECT-TYPE
   SYNTAX      Counter64
   MAX-ACCESS  read-only
   STATUS      current
   DESCRIPTION
      "Path: apsBundle.performance.ifOutPriorityQueues.d7Performance.eirTxOctets

       64 bit unsigned wrappable counter."
   ::= {pr1645v2ApsBOutQueuesD7PerformanceEntry 184549376}

pr1645v2ApsBOutQueuesD7PerformanceViolTxOcts OBJECT-TYPE
   SYNTAX      Counter64
   MAX-ACCESS  read-only
   STATUS      current
   DESCRIPTION
      "Path: apsBundle.performance.ifOutPriorityQueues.d7Performance.violateTxOctets

       64 bit unsigned wrappable counter."
   ::= {pr1645v2ApsBOutQueuesD7PerformanceEntry 318767104}

pr1645v2ApsBOutQueuesD7PerformanceBandwidth OBJECT-TYPE
   SYNTAX      Integer32
   MAX-ACCESS  read-only
   STATUS      current
   DESCRIPTION
      "Path: apsBundle.performance.ifOutPriorityQueues.d7Performance.bandwidth

       unit name = bps
       formula = 8 * ; 8 /"
   ::= {pr1645v2ApsBOutQueuesD7PerformanceEntry 268435456}


pr1645v2ApsBOutBandwidth OBJECT IDENTIFIER ::= {pr1645v2ApsB 182}

pr1645v2ApsBOutBandwidthSSCTable OBJECT-TYPE
   SYNTAX      SEQUENCE OF Pr1645v2ApsBOutBandwidthEntry
   MAX-ACCESS  not-accessible
   STATUS      current
   DESCRIPTION
      "bandwidth"
   ::= {pr1645v2ApsBOutBandwidth 1}

pr1645v2ApsBOutBandwidthEntry OBJECT-TYPE
   SYNTAX      Pr1645v2ApsBOutBandwidthEntry
   MAX-ACCESS  not-accessible
   STATUS      current
   DESCRIPTION
      ""
   INDEX      { pr1645v2ApsBOutBandwidthGlobalIx }
   ::= {pr1645v2ApsBOutBandwidthSSCTable 1}

Pr1645v2ApsBOutBandwidthEntry ::=
   SEQUENCE
      {
      pr1645v2ApsBOutBandwidthGlobalIx
         GlobalIndex,
      pr1645v2ApsBOutBandwidth15sec
         Integer32,
      pr1645v2ApsBOutBandwidth30sec
         Integer32,
      pr1645v2ApsBOutBandwidth1min
         Integer32,
      pr1645v2ApsBOutBandwidth2min
         Integer32,
      pr1645v2ApsBOutBandwidth5min
         Integer32
      }

pr1645v2ApsBOutBandwidthGlobalIx OBJECT-TYPE
   SYNTAX      GlobalIndex
   MAX-ACCESS  not-accessible
   STATUS      current
   DESCRIPTION
      "The value of the tlsCntTreeGlobalIndex of the MANAGED OBJECT."
   ::= {pr1645v2ApsBOutBandwidthEntry 10}

pr1645v2ApsBOutBandwidth15sec OBJECT-TYPE
   SYNTAX      Integer32
   MAX-ACCESS  read-only
   STATUS      current
   DESCRIPTION
      "Path: apsBundle.performance.ifOutBandwidth.15sec

       unit name = bps
       formula = 8 * ; 8 /"
   ::= {pr1645v2ApsBOutBandwidthEntry 83886080}

pr1645v2ApsBOutBandwidth30sec OBJECT-TYPE
   SYNTAX      Integer32
   MAX-ACCESS  read-only
   STATUS      current
   DESCRIPTION
      "Path: apsBundle.performance.ifOutBandwidth.30sec

       unit name = bps
       formula = 8 * ; 8 /"
   ::= {pr1645v2ApsBOutBandwidthEntry 167772160}

pr1645v2ApsBOutBandwidth1min OBJECT-TYPE
   SYNTAX      Integer32
   MAX-ACCESS  read-only
   STATUS      current
   DESCRIPTION
      "Path: apsBundle.performance.ifOutBandwidth.1min

       unit name = bps
       formula = 8 * ; 8 /"
   ::= {pr1645v2ApsBOutBandwidthEntry 335544320}

pr1645v2ApsBOutBandwidth2min OBJECT-TYPE
   SYNTAX      Integer32
   MAX-ACCESS  read-only
   STATUS      current
   DESCRIPTION
      "Path: apsBundle.performance.ifOutBandwidth.2min

       unit name = bps
       formula = 8 * ; 8 /"
   ::= {pr1645v2ApsBOutBandwidthEntry 671088640}

pr1645v2ApsBOutBandwidth5min OBJECT-TYPE
   SYNTAX      Integer32
   MAX-ACCESS  read-only
   STATUS      current
   DESCRIPTION
      "Path: apsBundle.performance.ifOutBandwidth.5min

       unit name = bps
       formula = 8 * ; 8 /"
   ::= {pr1645v2ApsBOutBandwidthEntry 1677721600}


pr1645v2ApsBInP OBJECT IDENTIFIER ::= {pr1645v2ApsB 307}

pr1645v2ApsBInPSSCTable OBJECT-TYPE
   SYNTAX      SEQUENCE OF Pr1645v2ApsBInPEntry
   MAX-ACCESS  not-accessible
   STATUS      current
   DESCRIPTION
      "h2IfInPerformance"
   ::= {pr1645v2ApsBInP 1}

pr1645v2ApsBInPEntry OBJECT-TYPE
   SYNTAX      Pr1645v2ApsBInPEntry
   MAX-ACCESS  not-accessible
   STATUS      current
   DESCRIPTION
      ""
   INDEX      { pr1645v2ApsBInPGlobalIx,
                pr1645v2ApsBInPTableIx }
   ::= {pr1645v2ApsBInPSSCTable 1}

Pr1645v2ApsBInPEntry ::=
   SEQUENCE
      {
      pr1645v2ApsBInPGlobalIx
         GlobalIndex,
      pr1645v2ApsBInPTableIx
         TableIndex,
      pr1645v2ApsBInPSysUpTime
         TimeTicks,
      pr1645v2ApsBInPIfUpTime
         TimeTicks,
      pr1645v2ApsBInPIfStatChanges
         Counter32,
      pr1645v2ApsBInPIfInOctets
         Counter64,
      pr1645v2ApsBInPIfInUCPkts
         Counter64,
      pr1645v2ApsBInPIfInNUCPkts
         Counter64,
      pr1645v2ApsBInPIfInBCPkts
         Counter64,
      pr1645v2ApsBInPIfInMCPkts
         Counter64,
      pr1645v2ApsBInPIfInDiscards
         Counter64,
      pr1645v2ApsBInPIfInErrors
         Counter64,
      pr1645v2ApsBInPIfInUnkwn
         Counter64,
      pr1645v2ApsBInPInDropEx
         Counter64,
      pr1645v2ApsBInPInDropNoMac
         Counter64,
      pr1645v2ApsBInPInDropNUCast
         Counter64,
      pr1645v2ApsBInPInDropFilter
         Counter64,
      pr1645v2ApsBInPIfInBandwidth
         Integer32,
      pr1645v2ApsBInPIfOutOctets
         Counter64,
      pr1645v2ApsBInPIfOutUCPkts
         Counter64,
      pr1645v2ApsBInPIfOutNUCPkts
         Counter64,
      pr1645v2ApsBInPIfOutBCPkts
         Counter64,
      pr1645v2ApsBInPIfOutMCPkts
         Counter64,
      pr1645v2ApsBInPIfOutDiscards
         Counter64,
      pr1645v2ApsBInPIfOutErrors
         Counter64,
      pr1645v2ApsBInPOutDropEx
         Counter64,
      pr1645v2ApsBInPOutDropNoArp
         Counter64,
      pr1645v2ApsBInPOutDropFilter
         Counter64,
      pr1645v2ApsBInPIfOutBandwidth
         Integer32,
      pr1645v2ApsBInPIfErrSec
         Counter32
      }

pr1645v2ApsBInPGlobalIx OBJECT-TYPE
   SYNTAX      GlobalIndex
   MAX-ACCESS  not-accessible
   STATUS      current
   DESCRIPTION
      "The value of the tlsCntTreeGlobalIndex of the MANAGED OBJECT."
   ::= {pr1645v2ApsBInPEntry 10}

pr1645v2ApsBInPTableIx OBJECT-TYPE
   SYNTAX      TableIndex
   MAX-ACCESS  not-accessible
   STATUS      current
   DESCRIPTION
      ""
   ::= {pr1645v2ApsBInPEntry 11}

pr1645v2ApsBInPSysUpTime OBJECT-TYPE
   SYNTAX      TimeTicks
   MAX-ACCESS  read-only
   STATUS      current
   DESCRIPTION
      "Path: apsBundle.performance.h2Performance.sysUpTime

       Time in centi-second."
   ::= {pr1645v2ApsBInPEntry 16777216}

pr1645v2ApsBInPIfUpTime OBJECT-TYPE
   SYNTAX      TimeTicks
   MAX-ACCESS  read-only
   STATUS      current
   DESCRIPTION
      "Path: apsBundle.performance.h2Performance.ifUpTime

       Time in centi-second."
   ::= {pr1645v2ApsBInPEntry 33554432}

pr1645v2ApsBInPIfStatChanges OBJECT-TYPE
   SYNTAX      Counter32
   MAX-ACCESS  read-only
   STATUS      current
   DESCRIPTION
      "Path: apsBundle.performance.h2Performance.ifStatusChanges

       32 bit unsigned wrappable counter."
   ::= {pr1645v2ApsBInPEntry 50331648}

pr1645v2ApsBInPIfInOctets OBJECT-TYPE
   SYNTAX      Counter64
   MAX-ACCESS  read-only
   STATUS      current
   DESCRIPTION
      "Path: apsBundle.performance.h2Performance.ifInOctets

       64 bit unsigned wrappable counter."
   ::= {pr1645v2ApsBInPEntry 67108864}

pr1645v2ApsBInPIfInUCPkts OBJECT-TYPE
   SYNTAX      Counter64
   MAX-ACCESS  read-only
   STATUS      current
   DESCRIPTION
      "Path: apsBundle.performance.h2Performance.ifInUcastPkts

       64 bit unsigned wrappable counter."
   ::= {pr1645v2ApsBInPEntry 83886080}

pr1645v2ApsBInPIfInNUCPkts OBJECT-TYPE
   SYNTAX      Counter64
   MAX-ACCESS  read-only
   STATUS      current
   DESCRIPTION
      "Path: apsBundle.performance.h2Performance.ifInNUcastPkts

       64 bit unsigned wrappable counter."
   ::= {pr1645v2ApsBInPEntry 100663296}

pr1645v2ApsBInPIfInBCPkts OBJECT-TYPE
   SYNTAX      Counter64
   MAX-ACCESS  read-only
   STATUS      current
   DESCRIPTION
      "Path: apsBundle.performance.h2Performance.ifInBcastPkts

       64 bit unsigned wrappable counter."
   ::= {pr1645v2ApsBInPEntry 419430400}

pr1645v2ApsBInPIfInMCPkts OBJECT-TYPE
   SYNTAX      Counter64
   MAX-ACCESS  read-only
   STATUS      current
   DESCRIPTION
      "Path: apsBundle.performance.h2Performance.ifInMcastPkts

       64 bit unsigned wrappable counter."
   ::= {pr1645v2ApsBInPEntry 436207616}

pr1645v2ApsBInPIfInDiscards OBJECT-TYPE
   SYNTAX      Counter64
   MAX-ACCESS  read-only
   STATUS      current
   DESCRIPTION
      "Path: apsBundle.performance.h2Performance.ifInDiscards

       64 bit unsigned wrappable counter."
   ::= {pr1645v2ApsBInPEntry 117440512}

pr1645v2ApsBInPIfInErrors OBJECT-TYPE
   SYNTAX      Counter64
   MAX-ACCESS  read-only
   STATUS      current
   DESCRIPTION
      "Path: apsBundle.performance.h2Performance.ifInErrors

       64 bit unsigned wrappable counter."
   ::= {pr1645v2ApsBInPEntry 134217728}

pr1645v2ApsBInPIfInUnkwn OBJECT-TYPE
   SYNTAX      Counter64
   MAX-ACCESS  read-only
   STATUS      current
   DESCRIPTION
      "Path: apsBundle.performance.h2Performance.ifInUnknownProtos

       64 bit unsigned wrappable counter."
   ::= {pr1645v2ApsBInPEntry 150994944}

pr1645v2ApsBInPInDropEx OBJECT-TYPE
   SYNTAX      Counter64
   MAX-ACCESS  read-only
   STATUS      current
   DESCRIPTION
      "Path: apsBundle.performance.h2Performance.ifInDropLevelExceeded

       64 bit unsigned wrappable counter."
   ::= {pr1645v2ApsBInPEntry 335544320}

pr1645v2ApsBInPInDropNoMac OBJECT-TYPE
   SYNTAX      Counter64
   MAX-ACCESS  read-only
   STATUS      current
   DESCRIPTION
      "Path: apsBundle.performance.h2Performance.fInDiscardsNoMacFit

       64 bit unsigned wrappable counter."
   ::= {pr1645v2ApsBInPEntry 301989888}

pr1645v2ApsBInPInDropNUCast OBJECT-TYPE
   SYNTAX      Counter64
   MAX-ACCESS  read-only
   STATUS      current
   DESCRIPTION
      "Path: apsBundle.performance.h2Performance.fInDiscardsNUCast

       64 bit unsigned wrappable counter."
   ::= {pr1645v2ApsBInPEntry 318767104}

pr1645v2ApsBInPInDropFilter OBJECT-TYPE
   SYNTAX      Counter64
   MAX-ACCESS  read-only
   STATUS      current
   DESCRIPTION
      "Path: apsBundle.performance.h2Performance.fInDiscardsFilter

       64 bit unsigned wrappable counter."
   ::= {pr1645v2ApsBInPEntry 385875968}

pr1645v2ApsBInPIfInBandwidth OBJECT-TYPE
   SYNTAX      Integer32
   MAX-ACCESS  read-only
   STATUS      current
   DESCRIPTION
      "Path: apsBundle.performance.h2Performance.ifInBandwidth

       unit name = bps
       formula = 8 * ; 8 /"
   ::= {pr1645v2ApsBInPEntry 268435456}

pr1645v2ApsBInPIfOutOctets OBJECT-TYPE
   SYNTAX      Counter64
   MAX-ACCESS  read-only
   STATUS      current
   DESCRIPTION
      "Path: apsBundle.performance.h2Performance.ifOutOctets

       64 bit unsigned wrappable counter."
   ::= {pr1645v2ApsBInPEntry 167772160}

pr1645v2ApsBInPIfOutUCPkts OBJECT-TYPE
   SYNTAX      Counter64
   MAX-ACCESS  read-only
   STATUS      current
   DESCRIPTION
      "Path: apsBundle.performance.h2Performance.ifOutUcastPkts

       64 bit unsigned wrappable counter."
   ::= {pr1645v2ApsBInPEntry 184549376}

pr1645v2ApsBInPIfOutNUCPkts OBJECT-TYPE
   SYNTAX      Counter64
   MAX-ACCESS  read-only
   STATUS      current
   DESCRIPTION
      "Path: apsBundle.performance.h2Performance.ifOutNUcastPkts

       64 bit unsigned wrappable counter."
   ::= {pr1645v2ApsBInPEntry 201326592}

pr1645v2ApsBInPIfOutBCPkts OBJECT-TYPE
   SYNTAX      Counter64
   MAX-ACCESS  read-only
   STATUS      current
   DESCRIPTION
      "Path: apsBundle.performance.h2Performance.ifOutBcastPkts

       64 bit unsigned wrappable counter."
   ::= {pr1645v2ApsBInPEntry 452984832}

pr1645v2ApsBInPIfOutMCPkts OBJECT-TYPE
   SYNTAX      Counter64
   MAX-ACCESS  read-only
   STATUS      current
   DESCRIPTION
      "Path: apsBundle.performance.h2Performance.ifOutMcastPkts

       64 bit unsigned wrappable counter."
   ::= {pr1645v2ApsBInPEntry 469762048}

pr1645v2ApsBInPIfOutDiscards OBJECT-TYPE
   SYNTAX      Counter64
   MAX-ACCESS  read-only
   STATUS      current
   DESCRIPTION
      "Path: apsBundle.performance.h2Performance.ifOutDiscards

       64 bit unsigned wrappable counter."
   ::= {pr1645v2ApsBInPEntry 218103808}

pr1645v2ApsBInPIfOutErrors OBJECT-TYPE
   SYNTAX      Counter64
   MAX-ACCESS  read-only
   STATUS      current
   DESCRIPTION
      "Path: apsBundle.performance.h2Performance.ifOutErrors

       64 bit unsigned wrappable counter."
   ::= {pr1645v2ApsBInPEntry 234881024}

pr1645v2ApsBInPOutDropEx OBJECT-TYPE
   SYNTAX      Counter64
   MAX-ACCESS  read-only
   STATUS      current
   DESCRIPTION
      "Path: apsBundle.performance.h2Performance.ifOutDropLevelExceeded

       64 bit unsigned wrappable counter."
   ::= {pr1645v2ApsBInPEntry 352321536}

pr1645v2ApsBInPOutDropNoArp OBJECT-TYPE
   SYNTAX      Counter64
   MAX-ACCESS  read-only
   STATUS      current
   DESCRIPTION
      "Path: apsBundle.performance.h2Performance.ifOutDiscardsNoArp

       64 bit unsigned wrappable counter."
   ::= {pr1645v2ApsBInPEntry 369098752}

pr1645v2ApsBInPOutDropFilter OBJECT-TYPE
   SYNTAX      Counter64
   MAX-ACCESS  read-only
   STATUS      current
   DESCRIPTION
      "Path: apsBundle.performance.h2Performance.ifOutDiscardsFilter

       64 bit unsigned wrappable counter."
   ::= {pr1645v2ApsBInPEntry 402653184}

pr1645v2ApsBInPIfOutBandwidth OBJECT-TYPE
   SYNTAX      Integer32
   MAX-ACCESS  read-only
   STATUS      current
   DESCRIPTION
      "Path: apsBundle.performance.h2Performance.ifOutBandwidth

       unit name = bps
       formula = 8 * ; 8 /"
   ::= {pr1645v2ApsBInPEntry 285212672}

pr1645v2ApsBInPIfErrSec OBJECT-TYPE
   SYNTAX      Counter32
   MAX-ACCESS  read-only
   STATUS      current
   DESCRIPTION
      "Path: apsBundle.performance.h2Performance.ifErrSec

       32 bit unsigned wrappable counter."
   ::= {pr1645v2ApsBInPEntry 251658240}


pr1645v2ApsBH24InP OBJECT IDENTIFIER ::= {pr1645v2ApsB 308}

pr1645v2ApsBH24InPSSCTable OBJECT-TYPE
   SYNTAX      SEQUENCE OF Pr1645v2ApsBH24InPEntry
   MAX-ACCESS  not-accessible
   STATUS      current
   DESCRIPTION
      "h24IfInPerformance"
   ::= {pr1645v2ApsBH24InP 1}

pr1645v2ApsBH24InPEntry OBJECT-TYPE
   SYNTAX      Pr1645v2ApsBH24InPEntry
   MAX-ACCESS  not-accessible
   STATUS      current
   DESCRIPTION
      ""
   INDEX      { pr1645v2ApsBH24InPGlobalIx,
                pr1645v2ApsBH24InPTableIx }
   ::= {pr1645v2ApsBH24InPSSCTable 1}

Pr1645v2ApsBH24InPEntry ::=
   SEQUENCE
      {
      pr1645v2ApsBH24InPGlobalIx
         GlobalIndex,
      pr1645v2ApsBH24InPTableIx
         TableIndex,
      pr1645v2ApsBH24InPSysUpTime
         TimeTicks,
      pr1645v2ApsBH24InPIfUpTime
         TimeTicks,
      pr1645v2ApsBH24InPIfStatChanges
         Counter32,
      pr1645v2ApsBH24InPIfInOctets
         Counter64,
      pr1645v2ApsBH24InPIfInUCPkts
         Counter64,
      pr1645v2ApsBH24InPIfInNUCPkts
         Counter64,
      pr1645v2ApsBH24InPIfInBCPkts
         Counter64,
      pr1645v2ApsBH24InPIfInMCPkts
         Counter64,
      pr1645v2ApsBH24InPIfInDiscards
         Counter64,
      pr1645v2ApsBH24InPIfInErrors
         Counter64,
      pr1645v2ApsBH24InPIfInUnkwn
         Counter64,
      pr1645v2ApsBH24InPInDropEx
         Counter64,
      pr1645v2ApsBH24InPInDropNoMac
         Counter64,
      pr1645v2ApsBH24InPInDropNUCast
         Counter64,
      pr1645v2ApsBH24InPInDropFilter
         Counter64,
      pr1645v2ApsBH24InPIfInBandwidth
         Integer32,
      pr1645v2ApsBH24InPIfOutOctets
         Counter64,
      pr1645v2ApsBH24InPIfOutUCPkts
         Counter64,
      pr1645v2ApsBH24InPIfOutNUCPkts
         Counter64,
      pr1645v2ApsBH24InPIfOutBCPkts
         Counter64,
      pr1645v2ApsBH24InPIfOutMCPkts
         Counter64,
      pr1645v2ApsBH24InPIfOutDiscards
         Counter64,
      pr1645v2ApsBH24InPIfOutErrors
         Counter64,
      pr1645v2ApsBH24InPOutDropEx
         Counter64,
      pr1645v2ApsBH24InPOutDropNoArp
         Counter64,
      pr1645v2ApsBH24InPOutDropFilter
         Counter64,
      pr1645v2ApsBH24InPIfOutBandwidth
         Integer32,
      pr1645v2ApsBH24InPIfErrSec
         Counter32
      }

pr1645v2ApsBH24InPGlobalIx OBJECT-TYPE
   SYNTAX      GlobalIndex
   MAX-ACCESS  not-accessible
   STATUS      current
   DESCRIPTION
      "The value of the tlsCntTreeGlobalIndex of the MANAGED OBJECT."
   ::= {pr1645v2ApsBH24InPEntry 10}

pr1645v2ApsBH24InPTableIx OBJECT-TYPE
   SYNTAX      TableIndex
   MAX-ACCESS  not-accessible
   STATUS      current
   DESCRIPTION
      ""
   ::= {pr1645v2ApsBH24InPEntry 11}

pr1645v2ApsBH24InPSysUpTime OBJECT-TYPE
   SYNTAX      TimeTicks
   MAX-ACCESS  read-only
   STATUS      current
   DESCRIPTION
      "Path: apsBundle.performance.h24Performance.sysUpTime

       Time in centi-second."
   ::= {pr1645v2ApsBH24InPEntry 16777216}

pr1645v2ApsBH24InPIfUpTime OBJECT-TYPE
   SYNTAX      TimeTicks
   MAX-ACCESS  read-only
   STATUS      current
   DESCRIPTION
      "Path: apsBundle.performance.h24Performance.ifUpTime

       Time in centi-second."
   ::= {pr1645v2ApsBH24InPEntry 33554432}

pr1645v2ApsBH24InPIfStatChanges OBJECT-TYPE
   SYNTAX      Counter32
   MAX-ACCESS  read-only
   STATUS      current
   DESCRIPTION
      "Path: apsBundle.performance.h24Performance.ifStatusChanges

       32 bit unsigned wrappable counter."
   ::= {pr1645v2ApsBH24InPEntry 50331648}

pr1645v2ApsBH24InPIfInOctets OBJECT-TYPE
   SYNTAX      Counter64
   MAX-ACCESS  read-only
   STATUS      current
   DESCRIPTION
      "Path: apsBundle.performance.h24Performance.ifInOctets

       64 bit unsigned wrappable counter."
   ::= {pr1645v2ApsBH24InPEntry 67108864}

pr1645v2ApsBH24InPIfInUCPkts OBJECT-TYPE
   SYNTAX      Counter64
   MAX-ACCESS  read-only
   STATUS      current
   DESCRIPTION
      "Path: apsBundle.performance.h24Performance.ifInUcastPkts

       64 bit unsigned wrappable counter."
   ::= {pr1645v2ApsBH24InPEntry 83886080}

pr1645v2ApsBH24InPIfInNUCPkts OBJECT-TYPE
   SYNTAX      Counter64
   MAX-ACCESS  read-only
   STATUS      current
   DESCRIPTION
      "Path: apsBundle.performance.h24Performance.ifInNUcastPkts

       64 bit unsigned wrappable counter."
   ::= {pr1645v2ApsBH24InPEntry 100663296}

pr1645v2ApsBH24InPIfInBCPkts OBJECT-TYPE
   SYNTAX      Counter64
   MAX-ACCESS  read-only
   STATUS      current
   DESCRIPTION
      "Path: apsBundle.performance.h24Performance.ifInBcastPkts

       64 bit unsigned wrappable counter."
   ::= {pr1645v2ApsBH24InPEntry 419430400}

pr1645v2ApsBH24InPIfInMCPkts OBJECT-TYPE
   SYNTAX      Counter64
   MAX-ACCESS  read-only
   STATUS      current
   DESCRIPTION
      "Path: apsBundle.performance.h24Performance.ifInMcastPkts

       64 bit unsigned wrappable counter."
   ::= {pr1645v2ApsBH24InPEntry 436207616}

pr1645v2ApsBH24InPIfInDiscards OBJECT-TYPE
   SYNTAX      Counter64
   MAX-ACCESS  read-only
   STATUS      current
   DESCRIPTION
      "Path: apsBundle.performance.h24Performance.ifInDiscards

       64 bit unsigned wrappable counter."
   ::= {pr1645v2ApsBH24InPEntry 117440512}

pr1645v2ApsBH24InPIfInErrors OBJECT-TYPE
   SYNTAX      Counter64
   MAX-ACCESS  read-only
   STATUS      current
   DESCRIPTION
      "Path: apsBundle.performance.h24Performance.ifInErrors

       64 bit unsigned wrappable counter."
   ::= {pr1645v2ApsBH24InPEntry 134217728}

pr1645v2ApsBH24InPIfInUnkwn OBJECT-TYPE
   SYNTAX      Counter64
   MAX-ACCESS  read-only
   STATUS      current
   DESCRIPTION
      "Path: apsBundle.performance.h24Performance.ifInUnknownProtos

       64 bit unsigned wrappable counter."
   ::= {pr1645v2ApsBH24InPEntry 150994944}

pr1645v2ApsBH24InPInDropEx OBJECT-TYPE
   SYNTAX      Counter64
   MAX-ACCESS  read-only
   STATUS      current
   DESCRIPTION
      "Path: apsBundle.performance.h24Performance.ifInDropLevelExceeded

       64 bit unsigned wrappable counter."
   ::= {pr1645v2ApsBH24InPEntry 335544320}

pr1645v2ApsBH24InPInDropNoMac OBJECT-TYPE
   SYNTAX      Counter64
   MAX-ACCESS  read-only
   STATUS      current
   DESCRIPTION
      "Path: apsBundle.performance.h24Performance.fInDiscardsNoMacFit

       64 bit unsigned wrappable counter."
   ::= {pr1645v2ApsBH24InPEntry 301989888}

pr1645v2ApsBH24InPInDropNUCast OBJECT-TYPE
   SYNTAX      Counter64
   MAX-ACCESS  read-only
   STATUS      current
   DESCRIPTION
      "Path: apsBundle.performance.h24Performance.fInDiscardsNUCast

       64 bit unsigned wrappable counter."
   ::= {pr1645v2ApsBH24InPEntry 318767104}

pr1645v2ApsBH24InPInDropFilter OBJECT-TYPE
   SYNTAX      Counter64
   MAX-ACCESS  read-only
   STATUS      current
   DESCRIPTION
      "Path: apsBundle.performance.h24Performance.fInDiscardsFilter

       64 bit unsigned wrappable counter."
   ::= {pr1645v2ApsBH24InPEntry 385875968}

pr1645v2ApsBH24InPIfInBandwidth OBJECT-TYPE
   SYNTAX      Integer32
   MAX-ACCESS  read-only
   STATUS      current
   DESCRIPTION
      "Path: apsBundle.performance.h24Performance.ifInBandwidth

       unit name = bps
       formula = 8 * ; 8 /"
   ::= {pr1645v2ApsBH24InPEntry 268435456}

pr1645v2ApsBH24InPIfOutOctets OBJECT-TYPE
   SYNTAX      Counter64
   MAX-ACCESS  read-only
   STATUS      current
   DESCRIPTION
      "Path: apsBundle.performance.h24Performance.ifOutOctets

       64 bit unsigned wrappable counter."
   ::= {pr1645v2ApsBH24InPEntry 167772160}

pr1645v2ApsBH24InPIfOutUCPkts OBJECT-TYPE
   SYNTAX      Counter64
   MAX-ACCESS  read-only
   STATUS      current
   DESCRIPTION
      "Path: apsBundle.performance.h24Performance.ifOutUcastPkts

       64 bit unsigned wrappable counter."
   ::= {pr1645v2ApsBH24InPEntry 184549376}

pr1645v2ApsBH24InPIfOutNUCPkts OBJECT-TYPE
   SYNTAX      Counter64
   MAX-ACCESS  read-only
   STATUS      current
   DESCRIPTION
      "Path: apsBundle.performance.h24Performance.ifOutNUcastPkts

       64 bit unsigned wrappable counter."
   ::= {pr1645v2ApsBH24InPEntry 201326592}

pr1645v2ApsBH24InPIfOutBCPkts OBJECT-TYPE
   SYNTAX      Counter64
   MAX-ACCESS  read-only
   STATUS      current
   DESCRIPTION
      "Path: apsBundle.performance.h24Performance.ifOutBcastPkts

       64 bit unsigned wrappable counter."
   ::= {pr1645v2ApsBH24InPEntry 452984832}

pr1645v2ApsBH24InPIfOutMCPkts OBJECT-TYPE
   SYNTAX      Counter64
   MAX-ACCESS  read-only
   STATUS      current
   DESCRIPTION
      "Path: apsBundle.performance.h24Performance.ifOutMcastPkts

       64 bit unsigned wrappable counter."
   ::= {pr1645v2ApsBH24InPEntry 469762048}

pr1645v2ApsBH24InPIfOutDiscards OBJECT-TYPE
   SYNTAX      Counter64
   MAX-ACCESS  read-only
   STATUS      current
   DESCRIPTION
      "Path: apsBundle.performance.h24Performance.ifOutDiscards

       64 bit unsigned wrappable counter."
   ::= {pr1645v2ApsBH24InPEntry 218103808}

pr1645v2ApsBH24InPIfOutErrors OBJECT-TYPE
   SYNTAX      Counter64
   MAX-ACCESS  read-only
   STATUS      current
   DESCRIPTION
      "Path: apsBundle.performance.h24Performance.ifOutErrors

       64 bit unsigned wrappable counter."
   ::= {pr1645v2ApsBH24InPEntry 234881024}

pr1645v2ApsBH24InPOutDropEx OBJECT-TYPE
   SYNTAX      Counter64
   MAX-ACCESS  read-only
   STATUS      current
   DESCRIPTION
      "Path: apsBundle.performance.h24Performance.ifOutDropLevelExceeded

       64 bit unsigned wrappable counter."
   ::= {pr1645v2ApsBH24InPEntry 352321536}

pr1645v2ApsBH24InPOutDropNoArp OBJECT-TYPE
   SYNTAX      Counter64
   MAX-ACCESS  read-only
   STATUS      current
   DESCRIPTION
      "Path: apsBundle.performance.h24Performance.ifOutDiscardsNoArp

       64 bit unsigned wrappable counter."
   ::= {pr1645v2ApsBH24InPEntry 369098752}

pr1645v2ApsBH24InPOutDropFilter OBJECT-TYPE
   SYNTAX      Counter64
   MAX-ACCESS  read-only
   STATUS      current
   DESCRIPTION
      "Path: apsBundle.performance.h24Performance.ifOutDiscardsFilter

       64 bit unsigned wrappable counter."
   ::= {pr1645v2ApsBH24InPEntry 402653184}

pr1645v2ApsBH24InPIfOutBandwidth OBJECT-TYPE
   SYNTAX      Integer32
   MAX-ACCESS  read-only
   STATUS      current
   DESCRIPTION
      "Path: apsBundle.performance.h24Performance.ifOutBandwidth

       unit name = bps
       formula = 8 * ; 8 /"
   ::= {pr1645v2ApsBH24InPEntry 285212672}

pr1645v2ApsBH24InPIfErrSec OBJECT-TYPE
   SYNTAX      Counter32
   MAX-ACCESS  read-only
   STATUS      current
   DESCRIPTION
      "Path: apsBundle.performance.h24Performance.ifErrSec

       32 bit unsigned wrappable counter."
   ::= {pr1645v2ApsBH24InPEntry 251658240}


pr1645v2ApsBD7InP OBJECT IDENTIFIER ::= {pr1645v2ApsB 309}

pr1645v2ApsBD7InPSSCTable OBJECT-TYPE
   SYNTAX      SEQUENCE OF Pr1645v2ApsBD7InPEntry
   MAX-ACCESS  not-accessible
   STATUS      current
   DESCRIPTION
      "d7IfInPerformance"
   ::= {pr1645v2ApsBD7InP 1}

pr1645v2ApsBD7InPEntry OBJECT-TYPE
   SYNTAX      Pr1645v2ApsBD7InPEntry
   MAX-ACCESS  not-accessible
   STATUS      current
   DESCRIPTION
      ""
   INDEX      { pr1645v2ApsBD7InPGlobalIx,
                pr1645v2ApsBD7InPTableIx }
   ::= {pr1645v2ApsBD7InPSSCTable 1}

Pr1645v2ApsBD7InPEntry ::=
   SEQUENCE
      {
      pr1645v2ApsBD7InPGlobalIx
         GlobalIndex,
      pr1645v2ApsBD7InPTableIx
         TableIndex,
      pr1645v2ApsBD7InPSysUpTime
         TimeTicks,
      pr1645v2ApsBD7InPIfUpTime
         TimeTicks,
      pr1645v2ApsBD7InPIfStatChanges
         Counter32,
      pr1645v2ApsBD7InPIfInOctets
         Counter64,
      pr1645v2ApsBD7InPIfInUCPkts
         Counter64,
      pr1645v2ApsBD7InPIfInNUCPkts
         Counter64,
      pr1645v2ApsBD7InPIfInBCPkts
         Counter64,
      pr1645v2ApsBD7InPIfInMCPkts
         Counter64,
      pr1645v2ApsBD7InPIfInDiscards
         Counter64,
      pr1645v2ApsBD7InPIfInErrors
         Counter64,
      pr1645v2ApsBD7InPIfInUnkwn
         Counter64,
      pr1645v2ApsBD7InPInDropEx
         Counter64,
      pr1645v2ApsBD7InPInDropNoMac
         Counter64,
      pr1645v2ApsBD7InPInDropNUCast
         Counter64,
      pr1645v2ApsBD7InPInDropFilter
         Counter64,
      pr1645v2ApsBD7InPIfInBandwidth
         Integer32,
      pr1645v2ApsBD7InPIfOutOctets
         Counter64,
      pr1645v2ApsBD7InPIfOutUCPkts
         Counter64,
      pr1645v2ApsBD7InPIfOutNUCPkts
         Counter64,
      pr1645v2ApsBD7InPIfOutBCPkts
         Counter64,
      pr1645v2ApsBD7InPIfOutMCPkts
         Counter64,
      pr1645v2ApsBD7InPIfOutDiscards
         Counter64,
      pr1645v2ApsBD7InPIfOutErrors
         Counter64,
      pr1645v2ApsBD7InPOutDropEx
         Counter64,
      pr1645v2ApsBD7InPOutDropNoArp
         Counter64,
      pr1645v2ApsBD7InPOutDropFilter
         Counter64,
      pr1645v2ApsBD7InPIfOutBandwidth
         Integer32,
      pr1645v2ApsBD7InPIfErrSec
         Counter32
      }

pr1645v2ApsBD7InPGlobalIx OBJECT-TYPE
   SYNTAX      GlobalIndex
   MAX-ACCESS  not-accessible
   STATUS      current
   DESCRIPTION
      "The value of the tlsCntTreeGlobalIndex of the MANAGED OBJECT."
   ::= {pr1645v2ApsBD7InPEntry 10}

pr1645v2ApsBD7InPTableIx OBJECT-TYPE
   SYNTAX      TableIndex
   MAX-ACCESS  not-accessible
   STATUS      current
   DESCRIPTION
      ""
   ::= {pr1645v2ApsBD7InPEntry 11}

pr1645v2ApsBD7InPSysUpTime OBJECT-TYPE
   SYNTAX      TimeTicks
   MAX-ACCESS  read-only
   STATUS      current
   DESCRIPTION
      "Path: apsBundle.performance.d7Performance.sysUpTime

       Time in centi-second."
   ::= {pr1645v2ApsBD7InPEntry 16777216}

pr1645v2ApsBD7InPIfUpTime OBJECT-TYPE
   SYNTAX      TimeTicks
   MAX-ACCESS  read-only
   STATUS      current
   DESCRIPTION
      "Path: apsBundle.performance.d7Performance.ifUpTime

       Time in centi-second."
   ::= {pr1645v2ApsBD7InPEntry 33554432}

pr1645v2ApsBD7InPIfStatChanges OBJECT-TYPE
   SYNTAX      Counter32
   MAX-ACCESS  read-only
   STATUS      current
   DESCRIPTION
      "Path: apsBundle.performance.d7Performance.ifStatusChanges

       32 bit unsigned wrappable counter."
   ::= {pr1645v2ApsBD7InPEntry 50331648}

pr1645v2ApsBD7InPIfInOctets OBJECT-TYPE
   SYNTAX      Counter64
   MAX-ACCESS  read-only
   STATUS      current
   DESCRIPTION
      "Path: apsBundle.performance.d7Performance.ifInOctets

       64 bit unsigned wrappable counter."
   ::= {pr1645v2ApsBD7InPEntry 67108864}

pr1645v2ApsBD7InPIfInUCPkts OBJECT-TYPE
   SYNTAX      Counter64
   MAX-ACCESS  read-only
   STATUS      current
   DESCRIPTION
      "Path: apsBundle.performance.d7Performance.ifInUcastPkts

       64 bit unsigned wrappable counter."
   ::= {pr1645v2ApsBD7InPEntry 83886080}

pr1645v2ApsBD7InPIfInNUCPkts OBJECT-TYPE
   SYNTAX      Counter64
   MAX-ACCESS  read-only
   STATUS      current
   DESCRIPTION
      "Path: apsBundle.performance.d7Performance.ifInNUcastPkts

       64 bit unsigned wrappable counter."
   ::= {pr1645v2ApsBD7InPEntry 100663296}

pr1645v2ApsBD7InPIfInBCPkts OBJECT-TYPE
   SYNTAX      Counter64
   MAX-ACCESS  read-only
   STATUS      current
   DESCRIPTION
      "Path: apsBundle.performance.d7Performance.ifInBcastPkts

       64 bit unsigned wrappable counter."
   ::= {pr1645v2ApsBD7InPEntry 419430400}

pr1645v2ApsBD7InPIfInMCPkts OBJECT-TYPE
   SYNTAX      Counter64
   MAX-ACCESS  read-only
   STATUS      current
   DESCRIPTION
      "Path: apsBundle.performance.d7Performance.ifInMcastPkts

       64 bit unsigned wrappable counter."
   ::= {pr1645v2ApsBD7InPEntry 436207616}

pr1645v2ApsBD7InPIfInDiscards OBJECT-TYPE
   SYNTAX      Counter64
   MAX-ACCESS  read-only
   STATUS      current
   DESCRIPTION
      "Path: apsBundle.performance.d7Performance.ifInDiscards

       64 bit unsigned wrappable counter."
   ::= {pr1645v2ApsBD7InPEntry 117440512}

pr1645v2ApsBD7InPIfInErrors OBJECT-TYPE
   SYNTAX      Counter64
   MAX-ACCESS  read-only
   STATUS      current
   DESCRIPTION
      "Path: apsBundle.performance.d7Performance.ifInErrors

       64 bit unsigned wrappable counter."
   ::= {pr1645v2ApsBD7InPEntry 134217728}

pr1645v2ApsBD7InPIfInUnkwn OBJECT-TYPE
   SYNTAX      Counter64
   MAX-ACCESS  read-only
   STATUS      current
   DESCRIPTION
      "Path: apsBundle.performance.d7Performance.ifInUnknownProtos

       64 bit unsigned wrappable counter."
   ::= {pr1645v2ApsBD7InPEntry 150994944}

pr1645v2ApsBD7InPInDropEx OBJECT-TYPE
   SYNTAX      Counter64
   MAX-ACCESS  read-only
   STATUS      current
   DESCRIPTION
      "Path: apsBundle.performance.d7Performance.ifInDropLevelExceeded

       64 bit unsigned wrappable counter."
   ::= {pr1645v2ApsBD7InPEntry 335544320}

pr1645v2ApsBD7InPInDropNoMac OBJECT-TYPE
   SYNTAX      Counter64
   MAX-ACCESS  read-only
   STATUS      current
   DESCRIPTION
      "Path: apsBundle.performance.d7Performance.fInDiscardsNoMacFit

       64 bit unsigned wrappable counter."
   ::= {pr1645v2ApsBD7InPEntry 301989888}

pr1645v2ApsBD7InPInDropNUCast OBJECT-TYPE
   SYNTAX      Counter64
   MAX-ACCESS  read-only
   STATUS      current
   DESCRIPTION
      "Path: apsBundle.performance.d7Performance.fInDiscardsNUCast

       64 bit unsigned wrappable counter."
   ::= {pr1645v2ApsBD7InPEntry 318767104}

pr1645v2ApsBD7InPInDropFilter OBJECT-TYPE
   SYNTAX      Counter64
   MAX-ACCESS  read-only
   STATUS      current
   DESCRIPTION
      "Path: apsBundle.performance.d7Performance.fInDiscardsFilter

       64 bit unsigned wrappable counter."
   ::= {pr1645v2ApsBD7InPEntry 385875968}

pr1645v2ApsBD7InPIfInBandwidth OBJECT-TYPE
   SYNTAX      Integer32
   MAX-ACCESS  read-only
   STATUS      current
   DESCRIPTION
      "Path: apsBundle.performance.d7Performance.ifInBandwidth

       unit name = bps
       formula = 8 * ; 8 /"
   ::= {pr1645v2ApsBD7InPEntry 268435456}

pr1645v2ApsBD7InPIfOutOctets OBJECT-TYPE
   SYNTAX      Counter64
   MAX-ACCESS  read-only
   STATUS      current
   DESCRIPTION
      "Path: apsBundle.performance.d7Performance.ifOutOctets

       64 bit unsigned wrappable counter."
   ::= {pr1645v2ApsBD7InPEntry 167772160}

pr1645v2ApsBD7InPIfOutUCPkts OBJECT-TYPE
   SYNTAX      Counter64
   MAX-ACCESS  read-only
   STATUS      current
   DESCRIPTION
      "Path: apsBundle.performance.d7Performance.ifOutUcastPkts

       64 bit unsigned wrappable counter."
   ::= {pr1645v2ApsBD7InPEntry 184549376}

pr1645v2ApsBD7InPIfOutNUCPkts OBJECT-TYPE
   SYNTAX      Counter64
   MAX-ACCESS  read-only
   STATUS      current
   DESCRIPTION
      "Path: apsBundle.performance.d7Performance.ifOutNUcastPkts

       64 bit unsigned wrappable counter."
   ::= {pr1645v2ApsBD7InPEntry 201326592}

pr1645v2ApsBD7InPIfOutBCPkts OBJECT-TYPE
   SYNTAX      Counter64
   MAX-ACCESS  read-only
   STATUS      current
   DESCRIPTION
      "Path: apsBundle.performance.d7Performance.ifOutBcastPkts

       64 bit unsigned wrappable counter."
   ::= {pr1645v2ApsBD7InPEntry 452984832}

pr1645v2ApsBD7InPIfOutMCPkts OBJECT-TYPE
   SYNTAX      Counter64
   MAX-ACCESS  read-only
   STATUS      current
   DESCRIPTION
      "Path: apsBundle.performance.d7Performance.ifOutMcastPkts

       64 bit unsigned wrappable counter."
   ::= {pr1645v2ApsBD7InPEntry 469762048}

pr1645v2ApsBD7InPIfOutDiscards OBJECT-TYPE
   SYNTAX      Counter64
   MAX-ACCESS  read-only
   STATUS      current
   DESCRIPTION
      "Path: apsBundle.performance.d7Performance.ifOutDiscards

       64 bit unsigned wrappable counter."
   ::= {pr1645v2ApsBD7InPEntry 218103808}

pr1645v2ApsBD7InPIfOutErrors OBJECT-TYPE
   SYNTAX      Counter64
   MAX-ACCESS  read-only
   STATUS      current
   DESCRIPTION
      "Path: apsBundle.performance.d7Performance.ifOutErrors

       64 bit unsigned wrappable counter."
   ::= {pr1645v2ApsBD7InPEntry 234881024}

pr1645v2ApsBD7InPOutDropEx OBJECT-TYPE
   SYNTAX      Counter64
   MAX-ACCESS  read-only
   STATUS      current
   DESCRIPTION
      "Path: apsBundle.performance.d7Performance.ifOutDropLevelExceeded

       64 bit unsigned wrappable counter."
   ::= {pr1645v2ApsBD7InPEntry 352321536}

pr1645v2ApsBD7InPOutDropNoArp OBJECT-TYPE
   SYNTAX      Counter64
   MAX-ACCESS  read-only
   STATUS      current
   DESCRIPTION
      "Path: apsBundle.performance.d7Performance.ifOutDiscardsNoArp

       64 bit unsigned wrappable counter."
   ::= {pr1645v2ApsBD7InPEntry 369098752}

pr1645v2ApsBD7InPOutDropFilter OBJECT-TYPE
   SYNTAX      Counter64
   MAX-ACCESS  read-only
   STATUS      current
   DESCRIPTION
      "Path: apsBundle.performance.d7Performance.ifOutDiscardsFilter

       64 bit unsigned wrappable counter."
   ::= {pr1645v2ApsBD7InPEntry 402653184}

pr1645v2ApsBD7InPIfOutBandwidth OBJECT-TYPE
   SYNTAX      Integer32
   MAX-ACCESS  read-only
   STATUS      current
   DESCRIPTION
      "Path: apsBundle.performance.d7Performance.ifOutBandwidth

       unit name = bps
       formula = 8 * ; 8 /"
   ::= {pr1645v2ApsBD7InPEntry 285212672}

pr1645v2ApsBD7InPIfErrSec OBJECT-TYPE
   SYNTAX      Counter32
   MAX-ACCESS  read-only
   STATUS      current
   DESCRIPTION
      "Path: apsBundle.performance.d7Performance.ifErrSec

       32 bit unsigned wrappable counter."
   ::= {pr1645v2ApsBD7InPEntry 251658240}


pr1645v2ApsBApsPdu OBJECT IDENTIFIER ::= {pr1645v2ApsB 155}

pr1645v2ApsBApsPduSSCTable OBJECT-TYPE
   SYNTAX      SEQUENCE OF Pr1645v2ApsBApsPduEntry
   MAX-ACCESS  not-accessible
   STATUS      current
   DESCRIPTION
      "statistics of the APS bundle"
   ::= {pr1645v2ApsBApsPdu 1}

pr1645v2ApsBApsPduEntry OBJECT-TYPE
   SYNTAX      Pr1645v2ApsBApsPduEntry
   MAX-ACCESS  not-accessible
   STATUS      current
   DESCRIPTION
      ""
   INDEX      { pr1645v2ApsBApsPduGlobalIx }
   ::= {pr1645v2ApsBApsPduSSCTable 1}

Pr1645v2ApsBApsPduEntry ::=
   SEQUENCE
      {
      pr1645v2ApsBApsPduGlobalIx
         GlobalIndex,
      pr1645v2ApsBApsPduTx
         Counter32,
      pr1645v2ApsBApsPduRxValid
         Counter32,
      pr1645v2ApsBApsPduRxInvalid
         Counter32,
      pr1645v2ApsBApsPduRxUnsupported
         Counter32
      }

pr1645v2ApsBApsPduGlobalIx OBJECT-TYPE
   SYNTAX      GlobalIndex
   MAX-ACCESS  not-accessible
   STATUS      current
   DESCRIPTION
      "The value of the tlsCntTreeGlobalIndex of the MANAGED OBJECT."
   ::= {pr1645v2ApsBApsPduEntry 10}

pr1645v2ApsBApsPduTx OBJECT-TYPE
   SYNTAX      Counter32
   MAX-ACCESS  read-only
   STATUS      current
   DESCRIPTION
      "Path: apsBundle.performance.apsPdu.tx

       32 bit unsigned wrappable counter."
   ::= {pr1645v2ApsBApsPduEntry 16777216}

pr1645v2ApsBApsPduRxValid OBJECT-TYPE
   SYNTAX      Counter32
   MAX-ACCESS  read-only
   STATUS      current
   DESCRIPTION
      "Path: apsBundle.performance.apsPdu.rxValid

       32 bit unsigned wrappable counter."
   ::= {pr1645v2ApsBApsPduEntry 33554432}

pr1645v2ApsBApsPduRxInvalid OBJECT-TYPE
   SYNTAX      Counter32
   MAX-ACCESS  read-only
   STATUS      current
   DESCRIPTION
      "Path: apsBundle.performance.apsPdu.rxInvalid

       32 bit unsigned wrappable counter."
   ::= {pr1645v2ApsBApsPduEntry 50331648}

pr1645v2ApsBApsPduRxUnsupported OBJECT-TYPE
   SYNTAX      Counter32
   MAX-ACCESS  read-only
   STATUS      current
   DESCRIPTION
      "Path: apsBundle.performance.apsPdu.rxUnsupported

       32 bit unsigned wrappable counter."
   ::= {pr1645v2ApsBApsPduEntry 67108864}


pr1645v2ApsBBridgeCacheDistribution OBJECT IDENTIFIER ::= {pr1645v2ApsB 162}

pr1645v2ApsBBridgeCacheDistributionSSCTable OBJECT-TYPE
   SYNTAX      SEQUENCE OF Pr1645v2ApsBBridgeCacheDistributionEntry
   MAX-ACCESS  not-accessible
   STATUS      current
   DESCRIPTION
      "statistics of the APS bridge cache distribution"
   ::= {pr1645v2ApsBBridgeCacheDistribution 1}

pr1645v2ApsBBridgeCacheDistributionEntry OBJECT-TYPE
   SYNTAX      Pr1645v2ApsBBridgeCacheDistributionEntry
   MAX-ACCESS  not-accessible
   STATUS      current
   DESCRIPTION
      ""
   INDEX      { pr1645v2ApsBBridgeCacheDistributionGlobalIx }
   ::= {pr1645v2ApsBBridgeCacheDistributionSSCTable 1}

Pr1645v2ApsBBridgeCacheDistributionEntry ::=
   SEQUENCE
      {
      pr1645v2ApsBBridgeCacheDistributionGlobalIx
         GlobalIndex,
      pr1645v2ApsBBridgeCacheDistributionDiscriminator
         Counter32,
      pr1645v2ApsBBridgeCacheDistributionDistributeCount
         Counter32,
      pr1645v2ApsBBridgeCacheDistributionLastDistribution
         DisplayString
      }

pr1645v2ApsBBridgeCacheDistributionGlobalIx OBJECT-TYPE
   SYNTAX      GlobalIndex
   MAX-ACCESS  not-accessible
   STATUS      current
   DESCRIPTION
      "The value of the tlsCntTreeGlobalIndex of the MANAGED OBJECT."
   ::= {pr1645v2ApsBBridgeCacheDistributionEntry 10}

pr1645v2ApsBBridgeCacheDistributionDiscriminator OBJECT-TYPE
   SYNTAX      Counter32
   MAX-ACCESS  read-only
   STATUS      current
   DESCRIPTION
      "Path: apsBundle.performance.bridgeCacheDistribution.discriminator

       32 bit unsigned wrappable counter."
   ::= {pr1645v2ApsBBridgeCacheDistributionEntry 16777216}

pr1645v2ApsBBridgeCacheDistributionDistributeCount OBJECT-TYPE
   SYNTAX      Counter32
   MAX-ACCESS  read-only
   STATUS      current
   DESCRIPTION
      "Path: apsBundle.performance.bridgeCacheDistribution.distributeCount

       32 bit unsigned wrappable counter."
   ::= {pr1645v2ApsBBridgeCacheDistributionEntry 33554432}

pr1645v2ApsBBridgeCacheDistributionLastDistribution OBJECT-TYPE
   SYNTAX      DisplayString
   MAX-ACCESS  read-only
   STATUS      current
   DESCRIPTION
      "Path: apsBundle.performance.bridgeCacheDistribution.lastDistribution"
   ::= {pr1645v2ApsBBridgeCacheDistributionEntry 50331648}



fr1645v2ApsB OBJECT IDENTIFIER ::= {r1645v2ApsB 13}


fr1645v2ApsBAlarm OBJECT IDENTIFIER ::= {fr1645v2ApsB 207}

fr1645v2ApsBAlarmSSCTable OBJECT-TYPE
   SYNTAX      SEQUENCE OF Fr1645v2ApsBAlarmEntry
   MAX-ACCESS  not-accessible
   STATUS      current
   DESCRIPTION
      "IfAlarmInfo"
   ::= {fr1645v2ApsBAlarm 1}

fr1645v2ApsBAlarmEntry OBJECT-TYPE
   SYNTAX      Fr1645v2ApsBAlarmEntry
   MAX-ACCESS  not-accessible
   STATUS      current
   DESCRIPTION
      ""
   INDEX      { fr1645v2ApsBAlarmGlobalIx }
   ::= {fr1645v2ApsBAlarmSSCTable 1}

Fr1645v2ApsBAlarmEntry ::=
   SEQUENCE
      {
      fr1645v2ApsBAlarmGlobalIx
         GlobalIndex,
      fr1645v2ApsBAlarmDiscriminator
         Integer32,
      fr1645v2ApsBAlarmCurrent
         Integer32,
      fr1645v2ApsBAlarmPrevious
         Integer32,
      fr1645v2ApsBAlarmMask
         Integer32,
      fr1645v2ApsBAlarmLevLinkDown
         Integer32
      }

fr1645v2ApsBAlarmGlobalIx OBJECT-TYPE
   SYNTAX      GlobalIndex
   MAX-ACCESS  not-accessible
   STATUS      current
   DESCRIPTION
      "The value of the tlsCntTreeGlobalIndex of the MANAGED OBJECT."
   ::= {fr1645v2ApsBAlarmEntry 10}

fr1645v2ApsBAlarmDiscriminator OBJECT-TYPE
   SYNTAX      Integer32
   MAX-ACCESS  read-only
   STATUS      current
   DESCRIPTION
      "Path: apsBundle.alarms.alarmInfo.discriminator"
   ::= {fr1645v2ApsBAlarmEntry 16777216}

fr1645v2ApsBAlarmCurrent OBJECT-TYPE
   SYNTAX      Integer32
   MAX-ACCESS  read-only
   STATUS      current
   DESCRIPTION
      "Path: apsBundle.alarms.alarmInfo.currentAlarms

       Bit meanings:
               bit 0 = linkDown"
   ::= {fr1645v2ApsBAlarmEntry 33554432}

fr1645v2ApsBAlarmPrevious OBJECT-TYPE
   SYNTAX      Integer32
   MAX-ACCESS  read-only
   STATUS      current
   DESCRIPTION
      "Path: apsBundle.alarms.alarmInfo.previousAlarms

       Bit meanings:
               bit 0 = linkDown"
   ::= {fr1645v2ApsBAlarmEntry 50331648}

fr1645v2ApsBAlarmMask OBJECT-TYPE
   SYNTAX      Integer32
   MAX-ACCESS  read-only
   STATUS      current
   DESCRIPTION
      "Path: apsBundle.alarms.alarmInfo.alarmMask

       Bit meanings:
               bit 0 = linkDown"
   ::= {fr1645v2ApsBAlarmEntry 67108864}

fr1645v2ApsBAlarmLevLinkDown OBJECT-TYPE
   SYNTAX      Integer32
   MAX-ACCESS  read-only
   STATUS      current
   DESCRIPTION
      "Path: apsBundle.alarms.alarmInfo.alarmLevel.linkDown"
   ::= {fr1645v2ApsBAlarmEntry 83951616}


fr1645v2ApsBAlarmE2 OBJECT IDENTIFIER ::= {fr1645v2ApsBAlarm 2}

fr1645v2ApsBAlarmE2Entry OBJECT IDENTIFIER ::= {fr1645v2ApsBAlarmE2 1}

fr1645v2ApsBAlarmE2LinkDown OBJECT IDENTIFIER ::= {fr1645v2ApsBAlarmE2Entry 10}

fr1645v2ApsBAlarmE2LinkDownPfx OBJECT IDENTIFIER ::= {fr1645v2ApsBAlarmE2LinkDown 0}

fr1645v2ApsBAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'apsBundle'
                (root='router1645') has changed from the ON to the OFF state."
   ::= {fr1645v2ApsBAlarmE2LinkDownPfx 1}

fr1645v2ApsBAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'apsBundle'
                (root='router1645') has changed from the OFF to the ON state."
   ::= {fr1645v2ApsBAlarmE2LinkDownPfx 2}



ar1645v2ApsB OBJECT IDENTIFIER ::= {r1645v2ApsB 16}


ar1645v2ApsBClearCounters OBJECT IDENTIFIER ::= {ar1645v2ApsB 263}

ar1645v2ApsBClearCountersTable OBJECT-TYPE
   SYNTAX      SEQUENCE OF Ar1645v2ApsBClearCountersEntry
   MAX-ACCESS  not-accessible
   STATUS      current
   DESCRIPTION
      "reset counters"
   ::= {ar1645v2ApsBClearCounters 1}

ar1645v2ApsBClearCountersEntry OBJECT-TYPE
   SYNTAX      Ar1645v2ApsBClearCountersEntry
   MAX-ACCESS  not-accessible
   STATUS      current
   DESCRIPTION
      ""
   INDEX      { ar1645v2ApsBClearCountersGlobalIx }
   ::= {ar1645v2ApsBClearCountersTable 1}

Ar1645v2ApsBClearCountersEntry ::=
   SEQUENCE
      {
      ar1645v2ApsBClearCountersGlobalIx
         GlobalIndex,
      ar1645v2ApsBClearCountersValue
         Integer32
      }

ar1645v2ApsBClearCountersGlobalIx OBJECT-TYPE
   SYNTAX      GlobalIndex
   MAX-ACCESS  not-accessible
   STATUS      current
   DESCRIPTION
      "The value of the tlsCntTreeGlobalIndex of the MANAGED OBJECT."
   ::= {ar1645v2ApsBClearCountersEntry 10}

ar1645v2ApsBClearCountersValue OBJECT-TYPE
   SYNTAX      Integer32
   MAX-ACCESS  read-write
   STATUS      current
   DESCRIPTION
      "Path: apsBundle.actions.clearCounters"
   ::= {ar1645v2ApsBClearCountersEntry 2147483648}


ar1645v2ApsBApsCommand OBJECT IDENTIFIER ::= {ar1645v2ApsB 250}

ar1645v2ApsBApsCommandTable OBJECT-TYPE
   SYNTAX      SEQUENCE OF Ar1645v2ApsBApsCommandEntry
   MAX-ACCESS  not-accessible
   STATUS      current
   DESCRIPTION
      "ETH-APS command action"
   ::= {ar1645v2ApsBApsCommand 1}

ar1645v2ApsBApsCommandEntry OBJECT-TYPE
   SYNTAX      Ar1645v2ApsBApsCommandEntry
   MAX-ACCESS  not-accessible
   STATUS      current
   DESCRIPTION
      ""
   INDEX      { ar1645v2ApsBApsCommandGlobalIx }
   ::= {ar1645v2ApsBApsCommandTable 1}

Ar1645v2ApsBApsCommandEntry ::=
   SEQUENCE
      {
      ar1645v2ApsBApsCommandGlobalIx
         GlobalIndex,
      ar1645v2ApsBApsCommandValue
         Integer32
      }

ar1645v2ApsBApsCommandGlobalIx OBJECT-TYPE
   SYNTAX      GlobalIndex
   MAX-ACCESS  not-accessible
   STATUS      current
   DESCRIPTION
      "The value of the tlsCntTreeGlobalIndex of the MANAGED OBJECT."
   ::= {ar1645v2ApsBApsCommandEntry 10}

ar1645v2ApsBApsCommandValue OBJECT-TYPE
   SYNTAX      Integer32
   MAX-ACCESS  read-write
   STATUS      current
   DESCRIPTION
      "Path: apsBundle.actions.apsCommand"
   ::= {ar1645v2ApsBApsCommandEntry 2147483648}


ar1645v2ApsBType OBJECT IDENTIFIER ::= {ar1645v2ApsB 251}

ar1645v2ApsBTypeTable OBJECT-TYPE
   SYNTAX      SEQUENCE OF Ar1645v2ApsBTypeEntry
   MAX-ACCESS  not-accessible
   STATUS      current
   DESCRIPTION
      "ETH-APS command type for the action"
   ::= {ar1645v2ApsBType 1}

ar1645v2ApsBTypeEntry OBJECT-TYPE
   SYNTAX      Ar1645v2ApsBTypeEntry
   MAX-ACCESS  not-accessible
   STATUS      current
   DESCRIPTION
      ""
   INDEX      { ar1645v2ApsBTypeGlobalIx }
   ::= {ar1645v2ApsBTypeTable 1}

Ar1645v2ApsBTypeEntry ::=
   SEQUENCE
      {
      ar1645v2ApsBTypeGlobalIx
         GlobalIndex,
      ar1645v2ApsBTypeValue
         INTEGER
      }

ar1645v2ApsBTypeGlobalIx OBJECT-TYPE
   SYNTAX      GlobalIndex
   MAX-ACCESS  not-accessible
   STATUS      current
   DESCRIPTION
      "The value of the tlsCntTreeGlobalIndex of the MANAGED OBJECT."
   ::= {ar1645v2ApsBTypeEntry 10}

ar1645v2ApsBTypeValue OBJECT-TYPE
   SYNTAX      INTEGER
               {
               clear (13),
               exercise (14),
               lockOut (1),
               forcedSwitch (2),
               manualSwitchToWorking (12),
               manualSwitchToProtection (11)
               }
   MAX-ACCESS  read-write
   STATUS      current
   DESCRIPTION
      "Path: apsBundle.actions.type

       Possibilities:
               clear   (13)
               exercise   (14)
               lockOut   (1)
               forcedSwitch   (2)
               manualSwitchToWorking   (12)
               manualSwitchToProtection   (11)"
   ::= {ar1645v2ApsBTypeEntry 2147483648}



END
