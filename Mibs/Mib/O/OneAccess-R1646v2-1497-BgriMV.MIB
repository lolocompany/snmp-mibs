OneAccess-R1646v2-1497-BgriMV DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2BgriMV OBJECT IDENTIFIER ::= {r1646Rootv2 1497}

r1646v2BgriMVMOProp OBJECT-TYPE
   SYNTAX      SEQUENCE OF R1646v2BgriMVMOPropEntry
   MAX-ACCESS  not-accessible
   STATUS      current
   DESCRIPTION
      ""
   ::= {r1646v2BgriMV 1}

r1646v2BgriMVMOPropEntry OBJECT-TYPE
   SYNTAX      R1646v2BgriMVMOPropEntry
   MAX-ACCESS  not-accessible
   STATUS      current
   DESCRIPTION
      ""
   INDEX      { r1646v2BgriMVMOPropGlobalIx }
   ::= {r1646v2BgriMVMOProp 1}

R1646v2BgriMVMOPropEntry ::=
   SEQUENCE
      {
      r1646v2BgriMVMOPropPath
         ContainmentPath,
      r1646v2BgriMVMOPropRev
         ObjectRevision,
      r1646v2BgriMVMOPropGlobalIx
         GlobalIndex
      }

r1646v2BgriMVMOPropPath OBJECT-TYPE
   SYNTAX      ContainmentPath
   MAX-ACCESS  read-only
   STATUS      current
   DESCRIPTION
      "Textual description of the containment tree from the instance of
       the root object down to the instance of the current object."
   ::= {r1646v2BgriMVMOPropEntry 3}

r1646v2BgriMVMOPropRev OBJECT-TYPE
   SYNTAX      ObjectRevision
   MAX-ACCESS  read-only
   STATUS      current
   DESCRIPTION
      "This value corresponds with the revision of the MANAGED OBJECT."
   ::= {r1646v2BgriMVMOPropEntry 4}

r1646v2BgriMVMOPropGlobalIx OBJECT-TYPE
   SYNTAX      GlobalIndex
   MAX-ACCESS  read-only
   STATUS      current
   DESCRIPTION
      "The value of the tlsCntTreeGlobalIndex of the MANAGED OBJECT."
   ::= {r1646v2BgriMVMOPropEntry 10}



er1646v2BgriMV OBJECT IDENTIFIER ::= {r1646v2BgriMV 11}


er1646v2BgriMVBridgeCache OBJECT IDENTIFIER ::= {er1646v2BgriMV 10}

er1646v2BgriMVBridgeCacheTable OBJECT-TYPE
   SYNTAX      SEQUENCE OF Er1646v2BgriMVBridgeCacheEntry
   MAX-ACCESS  not-accessible
   STATUS      current
   DESCRIPTION
      "used for bridgeCache"
   ::= {er1646v2BgriMVBridgeCache 1}

er1646v2BgriMVBridgeCacheEntry OBJECT-TYPE
   SYNTAX      Er1646v2BgriMVBridgeCacheEntry
   MAX-ACCESS  not-accessible
   STATUS      current
   DESCRIPTION
      ""
   INDEX      { er1646v2BgriMVBridgeCacheGlobalIx }
   ::= {er1646v2BgriMVBridgeCacheTable 1}

Er1646v2BgriMVBridgeCacheEntry ::=
   SEQUENCE
      {
      er1646v2BgriMVBridgeCacheGlobalIx
         GlobalIndex,
      er1646v2BgriMVBridgeCacheValue
         INTEGER
      }

er1646v2BgriMVBridgeCacheGlobalIx OBJECT-TYPE
   SYNTAX      GlobalIndex
   MAX-ACCESS  not-accessible
   STATUS      current
   DESCRIPTION
      "The value of the tlsCntTreeGlobalIndex of the MANAGED OBJECT."
   ::= {er1646v2BgriMVBridgeCacheEntry 10}

er1646v2BgriMVBridgeCacheValue OBJECT-TYPE
   SYNTAX      INTEGER
               {
               disabled (0),
               learning (1),
               switching (2)
               }
   MAX-ACCESS  read-write
   STATUS      current
   DESCRIPTION
      "Path: vpnBridgeGroup.editConf.bridgeCache

       Possibilities:
               disabled   (0)
               learning   (1)
               switching   (2)"
   ::= {er1646v2BgriMVBridgeCacheEntry 2147483648}


er1646v2BgriMVMaxCacheSize OBJECT IDENTIFIER ::= {er1646v2BgriMV 38}

er1646v2BgriMVMaxCacheSizeTable OBJECT-TYPE
   SYNTAX      SEQUENCE OF Er1646v2BgriMVMaxCacheSizeEntry
   MAX-ACCESS  not-accessible
   STATUS      current
   DESCRIPTION
      "used for size of bridgeCache"
   ::= {er1646v2BgriMVMaxCacheSize 1}

er1646v2BgriMVMaxCacheSizeEntry OBJECT-TYPE
   SYNTAX      Er1646v2BgriMVMaxCacheSizeEntry
   MAX-ACCESS  not-accessible
   STATUS      current
   DESCRIPTION
      ""
   INDEX      { er1646v2BgriMVMaxCacheSizeGlobalIx }
   ::= {er1646v2BgriMVMaxCacheSizeTable 1}

Er1646v2BgriMVMaxCacheSizeEntry ::=
   SEQUENCE
      {
      er1646v2BgriMVMaxCacheSizeGlobalIx
         GlobalIndex,
      er1646v2BgriMVMaxCacheSizeValue
         INTEGER
      }

er1646v2BgriMVMaxCacheSizeGlobalIx OBJECT-TYPE
   SYNTAX      GlobalIndex
   MAX-ACCESS  not-accessible
   STATUS      current
   DESCRIPTION
      "The value of the tlsCntTreeGlobalIndex of the MANAGED OBJECT."
   ::= {er1646v2BgriMVMaxCacheSizeEntry 10}

er1646v2BgriMVMaxCacheSizeValue OBJECT-TYPE
   SYNTAX      INTEGER
               {
               unlimited (0)
               }
   MAX-ACCESS  read-write
   STATUS      current
   DESCRIPTION
      "Path: vpnBridgeGroup.editConf.maxCacheSize

       Possibilities:
               unlimited   (0)"
   ::= {er1646v2BgriMVMaxCacheSizeEntry 2147483648}


er1646v2BgriMVStaticBridgeCache OBJECT IDENTIFIER ::= {er1646v2BgriMV 36}

er1646v2BgriMVStaticBridgeCacheSSCTable OBJECT-TYPE
   SYNTAX      SEQUENCE OF Er1646v2BgriMVStaticBridgeCacheEntry
   MAX-ACCESS  not-accessible
   STATUS      current
   DESCRIPTION
      "bridge cache"
   ::= {er1646v2BgriMVStaticBridgeCache 1}

er1646v2BgriMVStaticBridgeCacheEntry OBJECT-TYPE
   SYNTAX      Er1646v2BgriMVStaticBridgeCacheEntry
   MAX-ACCESS  not-accessible
   STATUS      current
   DESCRIPTION
      ""
   INDEX      { er1646v2BgriMVStaticBridgeCacheGlobalIx,
                er1646v2BgriMVStaticBridgeCacheTableIx }
   ::= {er1646v2BgriMVStaticBridgeCacheSSCTable 1}

Er1646v2BgriMVStaticBridgeCacheEntry ::=
   SEQUENCE
      {
      er1646v2BgriMVStaticBridgeCacheActions
         VariableLengthTableActions,
      er1646v2BgriMVStaticBridgeCacheGlobalIx
         GlobalIndex,
      er1646v2BgriMVStaticBridgeCacheTableIx
         TableIndex,
      er1646v2BgriMVStaticBridgeCacheIf
         DisplayString,
      er1646v2BgriMVStaticBridgeCacheMacAddress
         OCTET STRING,
      er1646v2BgriMVStaticBridgeCacheVlanId
         Integer32
      }

er1646v2BgriMVStaticBridgeCacheActions OBJECT-TYPE
   SYNTAX      VariableLengthTableActions
   MAX-ACCESS  read-write
   STATUS      current
   DESCRIPTION
      "By way of this field, some manipulations
       on this table may be performed."
   ::= {er1646v2BgriMVStaticBridgeCacheEntry 2}

er1646v2BgriMVStaticBridgeCacheGlobalIx OBJECT-TYPE
   SYNTAX      GlobalIndex
   MAX-ACCESS  not-accessible
   STATUS      current
   DESCRIPTION
      "The value of the tlsCntTreeGlobalIndex of the MANAGED OBJECT."
   ::= {er1646v2BgriMVStaticBridgeCacheEntry 10}

er1646v2BgriMVStaticBridgeCacheTableIx OBJECT-TYPE
   SYNTAX      TableIndex
   MAX-ACCESS  not-accessible
   STATUS      current
   DESCRIPTION
      ""
   ::= {er1646v2BgriMVStaticBridgeCacheEntry 11}

er1646v2BgriMVStaticBridgeCacheIf OBJECT-TYPE
   SYNTAX      DisplayString
   MAX-ACCESS  read-write
   STATUS      current
   DESCRIPTION
      "Path: vpnBridgeGroup.editConf.staticBridgeCache.interface"
   ::= {er1646v2BgriMVStaticBridgeCacheEntry 16777216}

er1646v2BgriMVStaticBridgeCacheMacAddress OBJECT-TYPE
   SYNTAX      OCTET STRING
   MAX-ACCESS  read-write
   STATUS      current
   DESCRIPTION
      "Path: vpnBridgeGroup.editConf.staticBridgeCache.macAddress

       MAC address."
   ::= {er1646v2BgriMVStaticBridgeCacheEntry 33554432}

er1646v2BgriMVStaticBridgeCacheVlanId OBJECT-TYPE
   SYNTAX      Integer32
   MAX-ACCESS  read-write
   STATUS      current
   DESCRIPTION
      "Path: vpnBridgeGroup.editConf.staticBridgeCache.vlanId"
   ::= {er1646v2BgriMVStaticBridgeCacheEntry 50331648}


er1646v2BgriMVForwardMulticast OBJECT IDENTIFIER ::= {er1646v2BgriMV 35}

er1646v2BgriMVForwardMulticastTable OBJECT-TYPE
   SYNTAX      SEQUENCE OF Er1646v2BgriMVForwardMulticastEntry
   MAX-ACCESS  not-accessible
   STATUS      current
   DESCRIPTION
      "used for size of bridgeCache"
   ::= {er1646v2BgriMVForwardMulticast 1}

er1646v2BgriMVForwardMulticastEntry OBJECT-TYPE
   SYNTAX      Er1646v2BgriMVForwardMulticastEntry
   MAX-ACCESS  not-accessible
   STATUS      current
   DESCRIPTION
      ""
   INDEX      { er1646v2BgriMVForwardMulticastGlobalIx }
   ::= {er1646v2BgriMVForwardMulticastTable 1}

Er1646v2BgriMVForwardMulticastEntry ::=
   SEQUENCE
      {
      er1646v2BgriMVForwardMulticastGlobalIx
         GlobalIndex,
      er1646v2BgriMVForwardMulticastValue
         INTEGER
      }

er1646v2BgriMVForwardMulticastGlobalIx OBJECT-TYPE
   SYNTAX      GlobalIndex
   MAX-ACCESS  not-accessible
   STATUS      current
   DESCRIPTION
      "The value of the tlsCntTreeGlobalIndex of the MANAGED OBJECT."
   ::= {er1646v2BgriMVForwardMulticastEntry 10}

er1646v2BgriMVForwardMulticastValue OBJECT-TYPE
   SYNTAX      INTEGER
               {
               noSpanningTree (0),
               all (1),
               noLinkConstrainedProtos (2),
               dot1ad (3)
               }
   MAX-ACCESS  read-write
   STATUS      current
   DESCRIPTION
      "Path: vpnBridgeGroup.editConf.forwardMulticast

       Possibilities:
               noSpanningTree   (0)
               all   (1)
               noLinkConstrainedProtos   (2)
               dot1ad   (3)"
   ::= {er1646v2BgriMVForwardMulticastEntry 2147483648}


er1646v2BgriMVVlanLearningMode OBJECT IDENTIFIER ::= {er1646v2BgriMV 17}

er1646v2BgriMVVlanLearningModeTable OBJECT-TYPE
   SYNTAX      SEQUENCE OF Er1646v2BgriMVVlanLearningModeEntry
   MAX-ACCESS  not-accessible
   STATUS      current
   DESCRIPTION
      ""
   ::= {er1646v2BgriMVVlanLearningMode 1}

er1646v2BgriMVVlanLearningModeEntry OBJECT-TYPE
   SYNTAX      Er1646v2BgriMVVlanLearningModeEntry
   MAX-ACCESS  not-accessible
   STATUS      current
   DESCRIPTION
      ""
   INDEX      { er1646v2BgriMVVlanLearningModeGlobalIx }
   ::= {er1646v2BgriMVVlanLearningModeTable 1}

Er1646v2BgriMVVlanLearningModeEntry ::=
   SEQUENCE
      {
      er1646v2BgriMVVlanLearningModeGlobalIx
         GlobalIndex,
      er1646v2BgriMVVlanLearningModeValue
         INTEGER
      }

er1646v2BgriMVVlanLearningModeGlobalIx OBJECT-TYPE
   SYNTAX      GlobalIndex
   MAX-ACCESS  not-accessible
   STATUS      current
   DESCRIPTION
      "The value of the tlsCntTreeGlobalIndex of the MANAGED OBJECT."
   ::= {er1646v2BgriMVVlanLearningModeEntry 10}

er1646v2BgriMVVlanLearningModeValue OBJECT-TYPE
   SYNTAX      INTEGER
               {
               shared (0),
               independent (1),
               grouped (2)
               }
   MAX-ACCESS  read-write
   STATUS      current
   DESCRIPTION
      "Path: vpnBridgeGroup.editConf.vlanLearningMode

       Possibilities:
               shared   (0)
               independent   (1)
               grouped   (2)"
   ::= {er1646v2BgriMVVlanLearningModeEntry 2147483648}


er1646v2BgriMVVlanSwitching OBJECT IDENTIFIER ::= {er1646v2BgriMV 15}

er1646v2BgriMVVlanSwitchingSSCTable OBJECT-TYPE
   SYNTAX      SEQUENCE OF Er1646v2BgriMVVlanSwitchingEntry
   MAX-ACCESS  not-accessible
   STATUS      current
   DESCRIPTION
      "used for bridgeCache"
   ::= {er1646v2BgriMVVlanSwitching 1}

er1646v2BgriMVVlanSwitchingEntry OBJECT-TYPE
   SYNTAX      Er1646v2BgriMVVlanSwitchingEntry
   MAX-ACCESS  not-accessible
   STATUS      current
   DESCRIPTION
      ""
   INDEX      { er1646v2BgriMVVlanSwitchingGlobalIx,
                er1646v2BgriMVVlanSwitchingTableIx }
   ::= {er1646v2BgriMVVlanSwitchingSSCTable 1}

Er1646v2BgriMVVlanSwitchingEntry ::=
   SEQUENCE
      {
      er1646v2BgriMVVlanSwitchingActions
         VariableLengthTableActions,
      er1646v2BgriMVVlanSwitchingGlobalIx
         GlobalIndex,
      er1646v2BgriMVVlanSwitchingTableIx
         TableIndex,
      er1646v2BgriMVVlanSwitchingSi
         DisplayString,
      er1646v2BgriMVVlanSwitchingSv
         INTEGER,
      er1646v2BgriMVVlanSwitchingSp
         INTEGER,
      er1646v2BgriMVVlanSwitchingSmP0
         Integer32,
      er1646v2BgriMVVlanSwitchingSmP1
         Integer32,
      er1646v2BgriMVVlanSwitchingSmP2
         Integer32,
      er1646v2BgriMVVlanSwitchingSmP3
         Integer32,
      er1646v2BgriMVVlanSwitchingSmP4
         Integer32,
      er1646v2BgriMVVlanSwitchingSmP5
         Integer32,
      er1646v2BgriMVVlanSwitchingSmP6
         Integer32,
      er1646v2BgriMVVlanSwitchingSmP7
         Integer32,
      er1646v2BgriMVVlanSwitchingDi
         DisplayString,
      er1646v2BgriMVVlanSwitchingDv
         INTEGER,
      er1646v2BgriMVVlanSwitchingDp
         INTEGER,
      er1646v2BgriMVVlanSwitchingDmP0
         Integer32,
      er1646v2BgriMVVlanSwitchingDmP1
         Integer32,
      er1646v2BgriMVVlanSwitchingDmP2
         Integer32,
      er1646v2BgriMVVlanSwitchingDmP3
         Integer32,
      er1646v2BgriMVVlanSwitchingDmP4
         Integer32,
      er1646v2BgriMVVlanSwitchingDmP5
         Integer32,
      er1646v2BgriMVVlanSwitchingDmP6
         Integer32,
      er1646v2BgriMVVlanSwitchingDmP7
         Integer32,
      er1646v2BgriMVVlanSwitchingTunnel
         INTEGER,
      er1646v2BgriMVVlanSwitchingBidir
         INTEGER
      }

er1646v2BgriMVVlanSwitchingActions OBJECT-TYPE
   SYNTAX      VariableLengthTableActions
   MAX-ACCESS  read-write
   STATUS      current
   DESCRIPTION
      "By way of this field, some manipulations
       on this table may be performed."
   ::= {er1646v2BgriMVVlanSwitchingEntry 2}

er1646v2BgriMVVlanSwitchingGlobalIx OBJECT-TYPE
   SYNTAX      GlobalIndex
   MAX-ACCESS  not-accessible
   STATUS      current
   DESCRIPTION
      "The value of the tlsCntTreeGlobalIndex of the MANAGED OBJECT."
   ::= {er1646v2BgriMVVlanSwitchingEntry 10}

er1646v2BgriMVVlanSwitchingTableIx OBJECT-TYPE
   SYNTAX      TableIndex
   MAX-ACCESS  not-accessible
   STATUS      current
   DESCRIPTION
      ""
   ::= {er1646v2BgriMVVlanSwitchingEntry 11}

er1646v2BgriMVVlanSwitchingSi OBJECT-TYPE
   SYNTAX      DisplayString
   MAX-ACCESS  read-write
   STATUS      current
   DESCRIPTION
      "Path: vpnBridgeGroup.editConf.vlanSwitching.sourceIntf"
   ::= {er1646v2BgriMVVlanSwitchingEntry 16777216}

er1646v2BgriMVVlanSwitchingSv OBJECT-TYPE
   SYNTAX      INTEGER
               {
               any (-1)
               }
   MAX-ACCESS  read-write
   STATUS      current
   DESCRIPTION
      "Path: vpnBridgeGroup.editConf.vlanSwitching.sourceVlan

       Possibilities:
               any   (-1)"
   ::= {er1646v2BgriMVVlanSwitchingEntry 33554432}

er1646v2BgriMVVlanSwitchingSp OBJECT-TYPE
   SYNTAX      INTEGER
               {
               any (-1)
               }
   MAX-ACCESS  read-write
   STATUS      current
   DESCRIPTION
      "Path: vpnBridgeGroup.editConf.vlanSwitching.sourcePFilter

       Possibilities:
               any   (-1)"
   ::= {er1646v2BgriMVVlanSwitchingEntry 134217728}

er1646v2BgriMVVlanSwitchingSmP0 OBJECT-TYPE
   SYNTAX      Integer32
   MAX-ACCESS  read-write
   STATUS      current
   DESCRIPTION
      "Path: vpnBridgeGroup.editConf.vlanSwitching.sourcePMap.p0"
   ::= {er1646v2BgriMVVlanSwitchingEntry 50397184}

er1646v2BgriMVVlanSwitchingSmP1 OBJECT-TYPE
   SYNTAX      Integer32
   MAX-ACCESS  read-write
   STATUS      current
   DESCRIPTION
      "Path: vpnBridgeGroup.editConf.vlanSwitching.sourcePMap.p1"
   ::= {er1646v2BgriMVVlanSwitchingEntry 50462720}

er1646v2BgriMVVlanSwitchingSmP2 OBJECT-TYPE
   SYNTAX      Integer32
   MAX-ACCESS  read-write
   STATUS      current
   DESCRIPTION
      "Path: vpnBridgeGroup.editConf.vlanSwitching.sourcePMap.p2"
   ::= {er1646v2BgriMVVlanSwitchingEntry 50528256}

er1646v2BgriMVVlanSwitchingSmP3 OBJECT-TYPE
   SYNTAX      Integer32
   MAX-ACCESS  read-write
   STATUS      current
   DESCRIPTION
      "Path: vpnBridgeGroup.editConf.vlanSwitching.sourcePMap.p3"
   ::= {er1646v2BgriMVVlanSwitchingEntry 50593792}

er1646v2BgriMVVlanSwitchingSmP4 OBJECT-TYPE
   SYNTAX      Integer32
   MAX-ACCESS  read-write
   STATUS      current
   DESCRIPTION
      "Path: vpnBridgeGroup.editConf.vlanSwitching.sourcePMap.p4"
   ::= {er1646v2BgriMVVlanSwitchingEntry 50659328}

er1646v2BgriMVVlanSwitchingSmP5 OBJECT-TYPE
   SYNTAX      Integer32
   MAX-ACCESS  read-write
   STATUS      current
   DESCRIPTION
      "Path: vpnBridgeGroup.editConf.vlanSwitching.sourcePMap.p5"
   ::= {er1646v2BgriMVVlanSwitchingEntry 50724864}

er1646v2BgriMVVlanSwitchingSmP6 OBJECT-TYPE
   SYNTAX      Integer32
   MAX-ACCESS  read-write
   STATUS      current
   DESCRIPTION
      "Path: vpnBridgeGroup.editConf.vlanSwitching.sourcePMap.p6"
   ::= {er1646v2BgriMVVlanSwitchingEntry 50790400}

er1646v2BgriMVVlanSwitchingSmP7 OBJECT-TYPE
   SYNTAX      Integer32
   MAX-ACCESS  read-write
   STATUS      current
   DESCRIPTION
      "Path: vpnBridgeGroup.editConf.vlanSwitching.sourcePMap.p7"
   ::= {er1646v2BgriMVVlanSwitchingEntry 50855936}

er1646v2BgriMVVlanSwitchingDi OBJECT-TYPE
   SYNTAX      DisplayString
   MAX-ACCESS  read-write
   STATUS      current
   DESCRIPTION
      "Path: vpnBridgeGroup.editConf.vlanSwitching.destinationIntf"
   ::= {er1646v2BgriMVVlanSwitchingEntry 67108864}

er1646v2BgriMVVlanSwitchingDv OBJECT-TYPE
   SYNTAX      INTEGER
               {
               unchanged (-1)
               }
   MAX-ACCESS  read-write
   STATUS      current
   DESCRIPTION
      "Path: vpnBridgeGroup.editConf.vlanSwitching.destinationVlan

       Possibilities:
               unchanged   (-1)"
   ::= {er1646v2BgriMVVlanSwitchingEntry 83886080}

er1646v2BgriMVVlanSwitchingDp OBJECT-TYPE
   SYNTAX      INTEGER
               {
               any (-1)
               }
   MAX-ACCESS  read-write
   STATUS      current
   DESCRIPTION
      "Path: vpnBridgeGroup.editConf.vlanSwitching.destinationPFilter

       Possibilities:
               any   (-1)"
   ::= {er1646v2BgriMVVlanSwitchingEntry 167772160}

er1646v2BgriMVVlanSwitchingDmP0 OBJECT-TYPE
   SYNTAX      Integer32
   MAX-ACCESS  read-write
   STATUS      current
   DESCRIPTION
      "Path: vpnBridgeGroup.editConf.vlanSwitching.destinationPMap.p0"
   ::= {er1646v2BgriMVVlanSwitchingEntry 100728832}

er1646v2BgriMVVlanSwitchingDmP1 OBJECT-TYPE
   SYNTAX      Integer32
   MAX-ACCESS  read-write
   STATUS      current
   DESCRIPTION
      "Path: vpnBridgeGroup.editConf.vlanSwitching.destinationPMap.p1"
   ::= {er1646v2BgriMVVlanSwitchingEntry 100794368}

er1646v2BgriMVVlanSwitchingDmP2 OBJECT-TYPE
   SYNTAX      Integer32
   MAX-ACCESS  read-write
   STATUS      current
   DESCRIPTION
      "Path: vpnBridgeGroup.editConf.vlanSwitching.destinationPMap.p2"
   ::= {er1646v2BgriMVVlanSwitchingEntry 100859904}

er1646v2BgriMVVlanSwitchingDmP3 OBJECT-TYPE
   SYNTAX      Integer32
   MAX-ACCESS  read-write
   STATUS      current
   DESCRIPTION
      "Path: vpnBridgeGroup.editConf.vlanSwitching.destinationPMap.p3"
   ::= {er1646v2BgriMVVlanSwitchingEntry 100925440}

er1646v2BgriMVVlanSwitchingDmP4 OBJECT-TYPE
   SYNTAX      Integer32
   MAX-ACCESS  read-write
   STATUS      current
   DESCRIPTION
      "Path: vpnBridgeGroup.editConf.vlanSwitching.destinationPMap.p4"
   ::= {er1646v2BgriMVVlanSwitchingEntry 100990976}

er1646v2BgriMVVlanSwitchingDmP5 OBJECT-TYPE
   SYNTAX      Integer32
   MAX-ACCESS  read-write
   STATUS      current
   DESCRIPTION
      "Path: vpnBridgeGroup.editConf.vlanSwitching.destinationPMap.p5"
   ::= {er1646v2BgriMVVlanSwitchingEntry 101056512}

er1646v2BgriMVVlanSwitchingDmP6 OBJECT-TYPE
   SYNTAX      Integer32
   MAX-ACCESS  read-write
   STATUS      current
   DESCRIPTION
      "Path: vpnBridgeGroup.editConf.vlanSwitching.destinationPMap.p6"
   ::= {er1646v2BgriMVVlanSwitchingEntry 101122048}

er1646v2BgriMVVlanSwitchingDmP7 OBJECT-TYPE
   SYNTAX      Integer32
   MAX-ACCESS  read-write
   STATUS      current
   DESCRIPTION
      "Path: vpnBridgeGroup.editConf.vlanSwitching.destinationPMap.p7"
   ::= {er1646v2BgriMVVlanSwitchingEntry 101187584}

er1646v2BgriMVVlanSwitchingTunnel OBJECT-TYPE
   SYNTAX      INTEGER
               {
               disabled (0),
               enabled (1),
               sVlan (3)
               }
   MAX-ACCESS  read-write
   STATUS      current
   DESCRIPTION
      "Path: vpnBridgeGroup.editConf.vlanSwitching.tunnel

       Possibilities:
               disabled   (0)
               enabled   (1)
               sVlan   (3)"
   ::= {er1646v2BgriMVVlanSwitchingEntry 117440512}

er1646v2BgriMVVlanSwitchingBidir OBJECT-TYPE
   SYNTAX      INTEGER
               {
               no (0),
               yes (1)
               }
   MAX-ACCESS  read-write
   STATUS      current
   DESCRIPTION
      "Path: vpnBridgeGroup.editConf.vlanSwitching.bidirectional

       Possibilities:
               no   (0)
               yes   (1)"
   ::= {er1646v2BgriMVVlanSwitchingEntry 150994944}


er1646v2BgriMVPktCounters OBJECT IDENTIFIER ::= {er1646v2BgriMV 31}

er1646v2BgriMVPktCountersTable OBJECT-TYPE
   SYNTAX      SEQUENCE OF Er1646v2BgriMVPktCountersEntry
   MAX-ACCESS  not-accessible
   STATUS      current
   DESCRIPTION
      ""
   ::= {er1646v2BgriMVPktCounters 1}

er1646v2BgriMVPktCountersEntry OBJECT-TYPE
   SYNTAX      Er1646v2BgriMVPktCountersEntry
   MAX-ACCESS  not-accessible
   STATUS      current
   DESCRIPTION
      ""
   INDEX      { er1646v2BgriMVPktCountersGlobalIx }
   ::= {er1646v2BgriMVPktCountersTable 1}

Er1646v2BgriMVPktCountersEntry ::=
   SEQUENCE
      {
      er1646v2BgriMVPktCountersGlobalIx
         GlobalIndex,
      er1646v2BgriMVPktCountersValue
         INTEGER
      }

er1646v2BgriMVPktCountersGlobalIx OBJECT-TYPE
   SYNTAX      GlobalIndex
   MAX-ACCESS  not-accessible
   STATUS      current
   DESCRIPTION
      "The value of the tlsCntTreeGlobalIndex of the MANAGED OBJECT."
   ::= {er1646v2BgriMVPktCountersEntry 10}

er1646v2BgriMVPktCountersValue OBJECT-TYPE
   SYNTAX      INTEGER
               {
               disabled (1),
               enabled (2)
               }
   MAX-ACCESS  read-write
   STATUS      current
   DESCRIPTION
      "Path: vpnBridgeGroup.editConf.pktCounters

       Possibilities:
               disabled   (1)
               enabled   (2)"
   ::= {er1646v2BgriMVPktCountersEntry 2147483648}


er1646v2BgriMVBackup OBJECT IDENTIFIER ::= {er1646v2BgriMV 32}

er1646v2BgriMVBackupSSCTable OBJECT-TYPE
   SYNTAX      SEQUENCE OF Er1646v2BgriMVBackupEntry
   MAX-ACCESS  not-accessible
   STATUS      current
   DESCRIPTION
      ""
   ::= {er1646v2BgriMVBackup 1}

er1646v2BgriMVBackupEntry OBJECT-TYPE
   SYNTAX      Er1646v2BgriMVBackupEntry
   MAX-ACCESS  not-accessible
   STATUS      current
   DESCRIPTION
      ""
   INDEX      { er1646v2BgriMVBackupGlobalIx }
   ::= {er1646v2BgriMVBackupSSCTable 1}

Er1646v2BgriMVBackupEntry ::=
   SEQUENCE
      {
      er1646v2BgriMVBackupGlobalIx
         GlobalIndex,
      er1646v2BgriMVBackupDisabled
         OCTET STRING,
      er1646v2BgriMVBackupSimpleInterface1
         DisplayString,
      er1646v2BgriMVBackupSimpleInterface1MepName
         DisplayString,
      er1646v2BgriMVBackupSimpleInterface2
         DisplayString,
      er1646v2BgriMVBackupSimpleInterface2MepName
         DisplayString,
      er1646v2BgriMVBackupSimpleBackup
         DisplayString,
      er1646v2BgriMVBackupSimpleBackupMepName
         DisplayString,
      er1646v2BgriMVBackupSimpleType
         INTEGER
      }

er1646v2BgriMVBackupGlobalIx OBJECT-TYPE
   SYNTAX      GlobalIndex
   MAX-ACCESS  not-accessible
   STATUS      current
   DESCRIPTION
      "The value of the tlsCntTreeGlobalIndex of the MANAGED OBJECT."
   ::= {er1646v2BgriMVBackupEntry 10}

er1646v2BgriMVBackupDisabled OBJECT-TYPE
   SYNTAX      OCTET STRING
   MAX-ACCESS  read-write
   STATUS      current
   DESCRIPTION
      "Path: vpnBridgeGroup.editConf.backup.disabled"
   ::= {er1646v2BgriMVBackupEntry 16777216}

er1646v2BgriMVBackupSimpleInterface1 OBJECT-TYPE
   SYNTAX      DisplayString
   MAX-ACCESS  read-write
   STATUS      current
   DESCRIPTION
      "Path: vpnBridgeGroup.editConf.backup.simple.interface1"
   ::= {er1646v2BgriMVBackupEntry 33619968}

er1646v2BgriMVBackupSimpleInterface1MepName OBJECT-TYPE
   SYNTAX      DisplayString
   MAX-ACCESS  read-write
   STATUS      current
   DESCRIPTION
      "Path: vpnBridgeGroup.editConf.backup.simple.interface1MepName"
   ::= {er1646v2BgriMVBackupEntry 33947648}

er1646v2BgriMVBackupSimpleInterface2 OBJECT-TYPE
   SYNTAX      DisplayString
   MAX-ACCESS  read-write
   STATUS      current
   DESCRIPTION
      "Path: vpnBridgeGroup.editConf.backup.simple.interface2"
   ::= {er1646v2BgriMVBackupEntry 33685504}

er1646v2BgriMVBackupSimpleInterface2MepName OBJECT-TYPE
   SYNTAX      DisplayString
   MAX-ACCESS  read-write
   STATUS      current
   DESCRIPTION
      "Path: vpnBridgeGroup.editConf.backup.simple.interface2MepName"
   ::= {er1646v2BgriMVBackupEntry 34013184}

er1646v2BgriMVBackupSimpleBackup OBJECT-TYPE
   SYNTAX      DisplayString
   MAX-ACCESS  read-write
   STATUS      current
   DESCRIPTION
      "Path: vpnBridgeGroup.editConf.backup.simple.backup"
   ::= {er1646v2BgriMVBackupEntry 33751040}

er1646v2BgriMVBackupSimpleBackupMepName OBJECT-TYPE
   SYNTAX      DisplayString
   MAX-ACCESS  read-write
   STATUS      current
   DESCRIPTION
      "Path: vpnBridgeGroup.editConf.backup.simple.backupMepName"
   ::= {er1646v2BgriMVBackupEntry 33816576}

er1646v2BgriMVBackupSimpleType OBJECT-TYPE
   SYNTAX      INTEGER
               {
               master (1),
               slave (2)
               }
   MAX-ACCESS  read-write
   STATUS      current
   DESCRIPTION
      "Path: vpnBridgeGroup.editConf.backup.simple.type

       Possibilities:
               master   (1)
               slave   (2)"
   ::= {er1646v2BgriMVBackupEntry 33882112}

er1646v2BgriMVBackupSimpleCacheDistribution OBJECT-TYPE
   SYNTAX      SEQUENCE OF Er1646v2BgriMVBackupSimpleCacheDistributionEntry
   MAX-ACCESS  not-accessible
   STATUS      current
   DESCRIPTION
      ""
   ::= {er1646v2BgriMVBackup 34078720}

er1646v2BgriMVBackupSimpleCacheDistributionEntry OBJECT-TYPE
   SYNTAX      Er1646v2BgriMVBackupSimpleCacheDistributionEntry
   MAX-ACCESS  not-accessible
   STATUS      current
   DESCRIPTION
      ""
   INDEX      { er1646v2BgriMVBackupSimpleCacheDistributionGlobalIx,
                er1646v2BgriMVBackupSimpleCacheDistributionTableIx }
   ::= {er1646v2BgriMVBackupSimpleCacheDistribution 1}

Er1646v2BgriMVBackupSimpleCacheDistributionEntry ::=
   SEQUENCE
      {
      er1646v2BgriMVBackupSimpleCacheDistributionActions
         VariableLengthTableActions,
      er1646v2BgriMVBackupSimpleCacheDistributionGlobalIx
         GlobalIndex,
      er1646v2BgriMVBackupSimpleCacheDistributionTableIx
         TableIndex,
      er1646v2BgriMVBackupSimpleCacheDistributionDestinationMac
         OCTET STRING,
      er1646v2BgriMVBackupSimpleCacheDistributionType
         INTEGER
      }

er1646v2BgriMVBackupSimpleCacheDistributionActions OBJECT-TYPE
   SYNTAX      VariableLengthTableActions
   MAX-ACCESS  read-write
   STATUS      current
   DESCRIPTION
      "By way of this field, some manipulations
       on this table may be performed."
   ::= {er1646v2BgriMVBackupSimpleCacheDistributionEntry 2}

er1646v2BgriMVBackupSimpleCacheDistributionGlobalIx OBJECT-TYPE
   SYNTAX      GlobalIndex
   MAX-ACCESS  not-accessible
   STATUS      current
   DESCRIPTION
      "The value of the tlsCntTreeGlobalIndex of the MANAGED OBJECT."
   ::= {er1646v2BgriMVBackupSimpleCacheDistributionEntry 10}

er1646v2BgriMVBackupSimpleCacheDistributionTableIx OBJECT-TYPE
   SYNTAX      TableIndex
   MAX-ACCESS  not-accessible
   STATUS      current
   DESCRIPTION
      ""
   ::= {er1646v2BgriMVBackupSimpleCacheDistributionEntry 11}

er1646v2BgriMVBackupSimpleCacheDistributionDestinationMac OBJECT-TYPE
   SYNTAX      OCTET STRING
   MAX-ACCESS  read-write
   STATUS      current
   DESCRIPTION
      "Path: vpnBridgeGroup.editConf.backup.simple.cacheDistribution.destinationMac

       MAC address."
   ::= {er1646v2BgriMVBackupSimpleCacheDistributionEntry 16777216}

er1646v2BgriMVBackupSimpleCacheDistributionType OBJECT-TYPE
   SYNTAX      INTEGER
               {
               arp (2054)
               }
   MAX-ACCESS  read-write
   STATUS      current
   DESCRIPTION
      "Path: vpnBridgeGroup.editConf.backup.simple.cacheDistribution.type

       Possibilities:
               arp   (2054)"
   ::= {er1646v2BgriMVBackupSimpleCacheDistributionEntry 33554432}


er1646v2BgriMVAlarmMask OBJECT IDENTIFIER ::= {er1646v2BgriMV 50}

er1646v2BgriMVAlarmMaskTable OBJECT-TYPE
   SYNTAX      SEQUENCE OF Er1646v2BgriMVAlarmMaskEntry
   MAX-ACCESS  not-accessible
   STATUS      current
   DESCRIPTION
      "bridge group alarmMask"
   ::= {er1646v2BgriMVAlarmMask 1}

er1646v2BgriMVAlarmMaskEntry OBJECT-TYPE
   SYNTAX      Er1646v2BgriMVAlarmMaskEntry
   MAX-ACCESS  not-accessible
   STATUS      current
   DESCRIPTION
      ""
   INDEX      { er1646v2BgriMVAlarmMaskGlobalIx }
   ::= {er1646v2BgriMVAlarmMaskTable 1}

Er1646v2BgriMVAlarmMaskEntry ::=
   SEQUENCE
      {
      er1646v2BgriMVAlarmMaskGlobalIx
         GlobalIndex,
      er1646v2BgriMVAlarmMaskValue
         Integer32
      }

er1646v2BgriMVAlarmMaskGlobalIx OBJECT-TYPE
   SYNTAX      GlobalIndex
   MAX-ACCESS  not-accessible
   STATUS      current
   DESCRIPTION
      "The value of the tlsCntTreeGlobalIndex of the MANAGED OBJECT."
   ::= {er1646v2BgriMVAlarmMaskEntry 10}

er1646v2BgriMVAlarmMaskValue OBJECT-TYPE
   SYNTAX      Integer32
   MAX-ACCESS  read-write
   STATUS      current
   DESCRIPTION
      "Path: vpnBridgeGroup.editConf.alarmMask

       Bit meanings:
               bit 0 = linkDown,
               bit 1 = linkShutdown"
   ::= {er1646v2BgriMVAlarmMaskEntry 2147483648}


er1646v2BgriMVAlarmLev OBJECT IDENTIFIER ::= {er1646v2BgriMV 51}

er1646v2BgriMVAlarmLevSSCTable OBJECT-TYPE
   SYNTAX      SEQUENCE OF Er1646v2BgriMVAlarmLevEntry
   MAX-ACCESS  not-accessible
   STATUS      current
   DESCRIPTION
      "bridge group alarmLevels"
   ::= {er1646v2BgriMVAlarmLev 1}

er1646v2BgriMVAlarmLevEntry OBJECT-TYPE
   SYNTAX      Er1646v2BgriMVAlarmLevEntry
   MAX-ACCESS  not-accessible
   STATUS      current
   DESCRIPTION
      ""
   INDEX      { er1646v2BgriMVAlarmLevGlobalIx }
   ::= {er1646v2BgriMVAlarmLevSSCTable 1}

Er1646v2BgriMVAlarmLevEntry ::=
   SEQUENCE
      {
      er1646v2BgriMVAlarmLevGlobalIx
         GlobalIndex,
      er1646v2BgriMVAlarmLevLinkDown
         Integer32,
      er1646v2BgriMVAlarmLevLinkShutdown
         Integer32
      }

er1646v2BgriMVAlarmLevGlobalIx OBJECT-TYPE
   SYNTAX      GlobalIndex
   MAX-ACCESS  not-accessible
   STATUS      current
   DESCRIPTION
      "The value of the tlsCntTreeGlobalIndex of the MANAGED OBJECT."
   ::= {er1646v2BgriMVAlarmLevEntry 10}

er1646v2BgriMVAlarmLevLinkDown OBJECT-TYPE
   SYNTAX      Integer32
   MAX-ACCESS  read-write
   STATUS      current
   DESCRIPTION
      "Path: vpnBridgeGroup.editConf.alarmLevel.linkDown"
   ::= {er1646v2BgriMVAlarmLevEntry 16777216}

er1646v2BgriMVAlarmLevLinkShutdown OBJECT-TYPE
   SYNTAX      Integer32
   MAX-ACCESS  read-write
   STATUS      current
   DESCRIPTION
      "Path: vpnBridgeGroup.editConf.alarmLevel.linkShutdown"
   ::= {er1646v2BgriMVAlarmLevEntry 33554432}


er1646v2BgriMVBridgeTimeOut OBJECT IDENTIFIER ::= {er1646v2BgriMV 21}

er1646v2BgriMVBridgeTimeOutTable OBJECT-TYPE
   SYNTAX      SEQUENCE OF Er1646v2BgriMVBridgeTimeOutEntry
   MAX-ACCESS  not-accessible
   STATUS      current
   DESCRIPTION
      "timeout of bridge cache entries"
   ::= {er1646v2BgriMVBridgeTimeOut 1}

er1646v2BgriMVBridgeTimeOutEntry OBJECT-TYPE
   SYNTAX      Er1646v2BgriMVBridgeTimeOutEntry
   MAX-ACCESS  not-accessible
   STATUS      current
   DESCRIPTION
      ""
   INDEX      { er1646v2BgriMVBridgeTimeOutGlobalIx }
   ::= {er1646v2BgriMVBridgeTimeOutTable 1}

Er1646v2BgriMVBridgeTimeOutEntry ::=
   SEQUENCE
      {
      er1646v2BgriMVBridgeTimeOutGlobalIx
         GlobalIndex,
      er1646v2BgriMVBridgeTimeOutValue
         TimeTicks
      }

er1646v2BgriMVBridgeTimeOutGlobalIx OBJECT-TYPE
   SYNTAX      GlobalIndex
   MAX-ACCESS  not-accessible
   STATUS      current
   DESCRIPTION
      "The value of the tlsCntTreeGlobalIndex of the MANAGED OBJECT."
   ::= {er1646v2BgriMVBridgeTimeOutEntry 10}

er1646v2BgriMVBridgeTimeOutValue OBJECT-TYPE
   SYNTAX      TimeTicks
   MAX-ACCESS  read-write
   STATUS      current
   DESCRIPTION
      "Path: vpnBridgeGroup.editConf.bridgeTimeOut

       Time in centi-second."
   ::= {er1646v2BgriMVBridgeTimeOutEntry 2147483648}


er1646v2BgriMVRemark OBJECT IDENTIFIER ::= {er1646v2BgriMV 321}

er1646v2BgriMVRemarkTable OBJECT-TYPE
   SYNTAX      SEQUENCE OF Er1646v2BgriMVRemarkEntry
   MAX-ACCESS  not-accessible
   STATUS      current
   DESCRIPTION
      "intfRemark"
   ::= {er1646v2BgriMVRemark 1}

er1646v2BgriMVRemarkEntry OBJECT-TYPE
   SYNTAX      Er1646v2BgriMVRemarkEntry
   MAX-ACCESS  not-accessible
   STATUS      current
   DESCRIPTION
      ""
   INDEX      { er1646v2BgriMVRemarkGlobalIx }
   ::= {er1646v2BgriMVRemarkTable 1}

Er1646v2BgriMVRemarkEntry ::=
   SEQUENCE
      {
      er1646v2BgriMVRemarkGlobalIx
         GlobalIndex,
      er1646v2BgriMVRemarkValue
         DisplayString
      }

er1646v2BgriMVRemarkGlobalIx OBJECT-TYPE
   SYNTAX      GlobalIndex
   MAX-ACCESS  not-accessible
   STATUS      current
   DESCRIPTION
      "The value of the tlsCntTreeGlobalIndex of the MANAGED OBJECT."
   ::= {er1646v2BgriMVRemarkEntry 10}

er1646v2BgriMVRemarkValue OBJECT-TYPE
   SYNTAX      DisplayString
   MAX-ACCESS  read-write
   STATUS      current
   DESCRIPTION
      "Path: vpnBridgeGroup.editConf.remark"
   ::= {er1646v2BgriMVRemarkEntry 2147483648}


er1646v2BgriMVMode OBJECT IDENTIFIER ::= {er1646v2BgriMV 4}

er1646v2BgriMVModeTable OBJECT-TYPE
   SYNTAX      SEQUENCE OF Er1646v2BgriMVModeEntry
   MAX-ACCESS  not-accessible
   STATUS      current
   DESCRIPTION
      "routing and/or ipV6 selection"
   ::= {er1646v2BgriMVMode 1}

er1646v2BgriMVModeEntry OBJECT-TYPE
   SYNTAX      Er1646v2BgriMVModeEntry
   MAX-ACCESS  not-accessible
   STATUS      current
   DESCRIPTION
      ""
   INDEX      { er1646v2BgriMVModeGlobalIx }
   ::= {er1646v2BgriMVModeTable 1}

Er1646v2BgriMVModeEntry ::=
   SEQUENCE
      {
      er1646v2BgriMVModeGlobalIx
         GlobalIndex,
      er1646v2BgriMVModeValue
         INTEGER
      }

er1646v2BgriMVModeGlobalIx OBJECT-TYPE
   SYNTAX      GlobalIndex
   MAX-ACCESS  not-accessible
   STATUS      current
   DESCRIPTION
      "The value of the tlsCntTreeGlobalIndex of the MANAGED OBJECT."
   ::= {er1646v2BgriMVModeEntry 10}

er1646v2BgriMVModeValue OBJECT-TYPE
   SYNTAX      INTEGER
               {
               routing (1),
               ipV6 (3),
               ipV6ipV4 (4),
               disabled (100)
               }
   MAX-ACCESS  read-write
   STATUS      current
   DESCRIPTION
      "Path: vpnBridgeGroup.editConf.mode

       Possibilities:
               routing   (1)
               ipV6   (3)
               ipV6/ipV4   (4)
               disabled   (100)"
   ::= {er1646v2BgriMVModeEntry 2147483648}


er1646v2BgriMVIpV6 OBJECT IDENTIFIER ::= {er1646v2BgriMV 16}

er1646v2BgriMVIpV6SSCTable OBJECT-TYPE
   SYNTAX      SEQUENCE OF Er1646v2BgriMVIpV6Entry
   MAX-ACCESS  not-accessible
   STATUS      current
   DESCRIPTION
      "IPv6 interface config parameters"
   ::= {er1646v2BgriMVIpV6 1}

er1646v2BgriMVIpV6Entry OBJECT-TYPE
   SYNTAX      Er1646v2BgriMVIpV6Entry
   MAX-ACCESS  not-accessible
   STATUS      current
   DESCRIPTION
      ""
   INDEX      { er1646v2BgriMVIpV6GlobalIx }
   ::= {er1646v2BgriMVIpV6SSCTable 1}

Er1646v2BgriMVIpV6Entry ::=
   SEQUENCE
      {
      er1646v2BgriMVIpV6GlobalIx
         GlobalIndex,
      er1646v2BgriMVIpV6VrfRouter
         DisplayString,
      er1646v2BgriMVIpV6AddrAutoConfigNrDupAddrDetects
         Integer32,
      er1646v2BgriMVIpV6AddrAutoConfigAcceptRa
         INTEGER,
      er1646v2BgriMVIpV6AddrAutoConfigAcceptRaRdnss
         INTEGER,
      er1646v2BgriMVIpV6AddrAutoConfigAcceptRaDnssl
         INTEGER,
      er1646v2BgriMVIpV6DefaultRoute
         INTEGER,
      er1646v2BgriMVIpV6RaSend
         INTEGER,
      er1646v2BgriMVIpV6RaMinInterval
         TimeTicks,
      er1646v2BgriMVIpV6RaMaxInterval
         TimeTicks,
      er1646v2BgriMVIpV6RaManagedFlag
         INTEGER,
      er1646v2BgriMVIpV6RaOtherConfFlag
         INTEGER,
      er1646v2BgriMVIpV6RaLinkMtu
         Integer32,
      er1646v2BgriMVIpV6RaReachableTime
         TimeTicks,
      er1646v2BgriMVIpV6RaRetransmitTime
         TimeTicks,
      er1646v2BgriMVIpV6RaHopLimit
         Integer32,
      er1646v2BgriMVIpV6RaDefaultLifeTime
         TimeTicks,
      er1646v2BgriMVIpV6RaDnsOptionsRdnssLifeTime
         TimeTicks,
      er1646v2BgriMVIpV6RaDnsOptionsRdnssImportServers
         INTEGER,
      er1646v2BgriMVIpV6RaDnsOptionsDnsslLifeTime
         TimeTicks,
      er1646v2BgriMVIpV6RaDnsOptionsDnsslImportDomains
         INTEGER,
      er1646v2BgriMVIpV6RsSend
         INTEGER,
      er1646v2BgriMVIpV6RsMaxRandomDelay
         TimeTicks,
      er1646v2BgriMVIpV6RsInterval
         TimeTicks,
      er1646v2BgriMVIpV6RsMaxSolicitations
         Integer32,
      er1646v2BgriMVIpV6TrafficPolicyInbound
         DisplayString,
      er1646v2BgriMVIpV6TrafficPolicyOutbound
         DisplayString,
      er1646v2BgriMVIpV6FirewallZone
         DisplayString,
      er1646v2BgriMVIpV6DhcpClientAddrAC
         INTEGER,
      er1646v2BgriMVIpV6DhcpClientPrDelMode
         INTEGER,
      er1646v2BgriMVIpV6DhcpClientPrDelPool
         DisplayString,
      er1646v2BgriMVIpV6DhcpClientPrDelPdExclOpt
         INTEGER,
      er1646v2BgriMVIpV6DhcpClientDnsServerPref
         Integer32,
      er1646v2BgriMVIpV6DhcpClientRapidCommit
         INTEGER,
      er1646v2BgriMVIpV6DhcpClientTimersSolTimeOut
         TimeTicks,
      er1646v2BgriMVIpV6DhcpClientTimersSolMaxRt
         TimeTicks,
      er1646v2BgriMVIpV6DhcpClientTimersInfoRefresh
         TimeTicks,
      er1646v2BgriMVIpV6DhcpServerMode
         INTEGER,
      er1646v2BgriMVIpV6DhcpServerPreference
         Integer32,
      er1646v2BgriMVIpV6DhcpServerPool
         DisplayString,
      er1646v2BgriMVIpV6DhcpServerRapidCommit
         INTEGER,
      er1646v2BgriMVIpV6DhcpServerTimersInfoRefresh
         TimeTicks,
      er1646v2BgriMVIpV6DhcpRelayMode
         INTEGER,
      er1646v2BgriMVIpV6SendRedirect
         INTEGER,
      er1646v2BgriMVIpV6LinkMtu
         Integer32,
      er1646v2BgriMVIpV6InterfaceId
         OCTET STRING,
      er1646v2BgriMVIpV6MF
         Integer32,
      er1646v2BgriMVIpV6IcmpMessagesNoRoute
         INTEGER,
      er1646v2BgriMVIpV6IcmpMessagesBeyondScope
         INTEGER,
      er1646v2BgriMVIpV6IcmpMessagesAddressUnreachable
         INTEGER,
      er1646v2BgriMVIpV6IcmpMessagesPortUnreachable
         INTEGER,
      er1646v2BgriMVIpV6IcmpMessagesPacketTooBig
         INTEGER,
      er1646v2BgriMVIpV6IcmpMessagesHopLimitExceeded
         INTEGER,
      er1646v2BgriMVIpV6IcmpMessagesFragTimeExceeded
         INTEGER,
      er1646v2BgriMVIpV6IcmpMessagesHeaderFieldErr
         INTEGER,
      er1646v2BgriMVIpV6IcmpMessagesOptionUnrecognized
         INTEGER,
      er1646v2BgriMVIpV6IcmpMessagesRedirect
         INTEGER
      }

er1646v2BgriMVIpV6GlobalIx OBJECT-TYPE
   SYNTAX      GlobalIndex
   MAX-ACCESS  not-accessible
   STATUS      current
   DESCRIPTION
      "The value of the tlsCntTreeGlobalIndex of the MANAGED OBJECT."
   ::= {er1646v2BgriMVIpV6Entry 10}

er1646v2BgriMVIpV6VrfRouter OBJECT-TYPE
   SYNTAX      DisplayString
   MAX-ACCESS  read-write
   STATUS      current
   DESCRIPTION
      "Path: vpnBridgeGroup.editConf.ipV6.vrfRouter"
   ::= {er1646v2BgriMVIpV6Entry 16777216}

er1646v2BgriMVIpV6AddrAutoConfigNrDupAddrDetects OBJECT-TYPE
   SYNTAX      Integer32
   MAX-ACCESS  read-write
   STATUS      current
   DESCRIPTION
      "Path: vpnBridgeGroup.editConf.ipV6.addrAutoConfig.nrDupAddrDetects"
   ::= {er1646v2BgriMVIpV6Entry 67174400}

er1646v2BgriMVIpV6AddrAutoConfigAcceptRa OBJECT-TYPE
   SYNTAX      INTEGER
               {
               disabled (0),
               enabled (1)
               }
   MAX-ACCESS  read-write
   STATUS      current
   DESCRIPTION
      "Path: vpnBridgeGroup.editConf.ipV6.addrAutoConfig.acceptRa

       Possibilities:
               disabled   (0)
               enabled   (1)"
   ::= {er1646v2BgriMVIpV6Entry 67239936}

er1646v2BgriMVIpV6AddrAutoConfigAcceptRaRdnss OBJECT-TYPE
   SYNTAX      INTEGER
               {
               disabled (0),
               enabled (1)
               }
   MAX-ACCESS  read-write
   STATUS      current
   DESCRIPTION
      "Path: vpnBridgeGroup.editConf.ipV6.addrAutoConfig.acceptRaRdnss

       Possibilities:
               disabled   (0)
               enabled   (1)"
   ::= {er1646v2BgriMVIpV6Entry 67305472}

er1646v2BgriMVIpV6AddrAutoConfigAcceptRaDnssl OBJECT-TYPE
   SYNTAX      INTEGER
               {
               disabled (0),
               enabled (1)
               }
   MAX-ACCESS  read-write
   STATUS      current
   DESCRIPTION
      "Path: vpnBridgeGroup.editConf.ipV6.addrAutoConfig.acceptRaDnssl

       Possibilities:
               disabled   (0)
               enabled   (1)"
   ::= {er1646v2BgriMVIpV6Entry 67371008}

er1646v2BgriMVIpV6DefaultRoute OBJECT-TYPE
   SYNTAX      INTEGER
               {
               disabled (0),
               enabled (1)
               }
   MAX-ACCESS  read-write
   STATUS      current
   DESCRIPTION
      "Path: vpnBridgeGroup.editConf.ipV6.defaultRoute

       Possibilities:
               disabled   (0)
               enabled   (1)"
   ::= {er1646v2BgriMVIpV6Entry 83886080}

er1646v2BgriMVIpV6RaSend OBJECT-TYPE
   SYNTAX      INTEGER
               {
               disabled (0),
               enabled (1)
               }
   MAX-ACCESS  read-write
   STATUS      current
   DESCRIPTION
      "Path: vpnBridgeGroup.editConf.ipV6.ra.send

       Possibilities:
               disabled   (0)
               enabled   (1)"
   ::= {er1646v2BgriMVIpV6Entry 100728832}

er1646v2BgriMVIpV6RaMinInterval OBJECT-TYPE
   SYNTAX      TimeTicks
   MAX-ACCESS  read-write
   STATUS      current
   DESCRIPTION
      "Path: vpnBridgeGroup.editConf.ipV6.ra.minInterval

       Time in centi-second."
   ::= {er1646v2BgriMVIpV6Entry 100794368}

er1646v2BgriMVIpV6RaMaxInterval OBJECT-TYPE
   SYNTAX      TimeTicks
   MAX-ACCESS  read-write
   STATUS      current
   DESCRIPTION
      "Path: vpnBridgeGroup.editConf.ipV6.ra.maxInterval

       Time in centi-second."
   ::= {er1646v2BgriMVIpV6Entry 100859904}

er1646v2BgriMVIpV6RaManagedFlag OBJECT-TYPE
   SYNTAX      INTEGER
               {
               disabled (0),
               enabled (1)
               }
   MAX-ACCESS  read-write
   STATUS      current
   DESCRIPTION
      "Path: vpnBridgeGroup.editConf.ipV6.ra.managedFlag

       Possibilities:
               disabled   (0)
               enabled   (1)"
   ::= {er1646v2BgriMVIpV6Entry 100925440}

er1646v2BgriMVIpV6RaOtherConfFlag OBJECT-TYPE
   SYNTAX      INTEGER
               {
               disabled (0),
               enabled (1)
               }
   MAX-ACCESS  read-write
   STATUS      current
   DESCRIPTION
      "Path: vpnBridgeGroup.editConf.ipV6.ra.otherConfFlag

       Possibilities:
               disabled   (0)
               enabled   (1)"
   ::= {er1646v2BgriMVIpV6Entry 100990976}

er1646v2BgriMVIpV6RaLinkMtu OBJECT-TYPE
   SYNTAX      Integer32
   MAX-ACCESS  read-write
   STATUS      current
   DESCRIPTION
      "Path: vpnBridgeGroup.editConf.ipV6.ra.linkMtu"
   ::= {er1646v2BgriMVIpV6Entry 101056512}

er1646v2BgriMVIpV6RaReachableTime OBJECT-TYPE
   SYNTAX      TimeTicks
   MAX-ACCESS  read-write
   STATUS      current
   DESCRIPTION
      "Path: vpnBridgeGroup.editConf.ipV6.ra.reachableTime

       Time in centi-second."
   ::= {er1646v2BgriMVIpV6Entry 101122048}

er1646v2BgriMVIpV6RaRetransmitTime OBJECT-TYPE
   SYNTAX      TimeTicks
   MAX-ACCESS  read-write
   STATUS      current
   DESCRIPTION
      "Path: vpnBridgeGroup.editConf.ipV6.ra.retransmitTime

       Time in centi-second."
   ::= {er1646v2BgriMVIpV6Entry 101187584}

er1646v2BgriMVIpV6RaHopLimit OBJECT-TYPE
   SYNTAX      Integer32
   MAX-ACCESS  read-write
   STATUS      current
   DESCRIPTION
      "Path: vpnBridgeGroup.editConf.ipV6.ra.hopLimit"
   ::= {er1646v2BgriMVIpV6Entry 101253120}

er1646v2BgriMVIpV6RaDefaultLifeTime OBJECT-TYPE
   SYNTAX      TimeTicks
   MAX-ACCESS  read-write
   STATUS      current
   DESCRIPTION
      "Path: vpnBridgeGroup.editConf.ipV6.ra.defaultLifeTime

       Time in centi-second."
   ::= {er1646v2BgriMVIpV6Entry 101318656}

er1646v2BgriMVIpV6RaDnsOptionsRdnssLifeTime OBJECT-TYPE
   SYNTAX      TimeTicks
   MAX-ACCESS  read-write
   STATUS      current
   DESCRIPTION
      "Path: vpnBridgeGroup.editConf.ipV6.ra.dnsOptions.rdnss.lifeTime

       Time in centi-second."
   ::= {er1646v2BgriMVIpV6Entry 101393408}

er1646v2BgriMVIpV6RaDnsOptionsRdnssImportServers OBJECT-TYPE
   SYNTAX      INTEGER
               {
               disabled (0),
               enabled (1)
               }
   MAX-ACCESS  read-write
   STATUS      current
   DESCRIPTION
      "Path: vpnBridgeGroup.editConf.ipV6.ra.dnsOptions.rdnss.importServers

       Possibilities:
               disabled   (0)
               enabled   (1)"
   ::= {er1646v2BgriMVIpV6Entry 101395456}

er1646v2BgriMVIpV6RaDnsOptionsDnsslLifeTime OBJECT-TYPE
   SYNTAX      TimeTicks
   MAX-ACCESS  read-write
   STATUS      current
   DESCRIPTION
      "Path: vpnBridgeGroup.editConf.ipV6.ra.dnsOptions.dnssl.lifeTime

       Time in centi-second."
   ::= {er1646v2BgriMVIpV6Entry 101401600}

er1646v2BgriMVIpV6RaDnsOptionsDnsslImportDomains OBJECT-TYPE
   SYNTAX      INTEGER
               {
               disabled (0),
               enabled (1)
               }
   MAX-ACCESS  read-write
   STATUS      current
   DESCRIPTION
      "Path: vpnBridgeGroup.editConf.ipV6.ra.dnsOptions.dnssl.importDomains

       Possibilities:
               disabled   (0)
               enabled   (1)"
   ::= {er1646v2BgriMVIpV6Entry 101403648}

er1646v2BgriMVIpV6RsSend OBJECT-TYPE
   SYNTAX      INTEGER
               {
               disabled (0),
               enabled (1)
               }
   MAX-ACCESS  read-write
   STATUS      current
   DESCRIPTION
      "Path: vpnBridgeGroup.editConf.ipV6.rs.send

       Possibilities:
               disabled   (0)
               enabled   (1)"
   ::= {er1646v2BgriMVIpV6Entry 335609856}

er1646v2BgriMVIpV6RsMaxRandomDelay OBJECT-TYPE
   SYNTAX      TimeTicks
   MAX-ACCESS  read-write
   STATUS      current
   DESCRIPTION
      "Path: vpnBridgeGroup.editConf.ipV6.rs.maxRandomDelay

       Time in centi-second."
   ::= {er1646v2BgriMVIpV6Entry 335675392}

er1646v2BgriMVIpV6RsInterval OBJECT-TYPE
   SYNTAX      TimeTicks
   MAX-ACCESS  read-write
   STATUS      current
   DESCRIPTION
      "Path: vpnBridgeGroup.editConf.ipV6.rs.interval

       Time in centi-second."
   ::= {er1646v2BgriMVIpV6Entry 335740928}

er1646v2BgriMVIpV6RsMaxSolicitations OBJECT-TYPE
   SYNTAX      Integer32
   MAX-ACCESS  read-write
   STATUS      current
   DESCRIPTION
      "Path: vpnBridgeGroup.editConf.ipV6.rs.maxSolicitations"
   ::= {er1646v2BgriMVIpV6Entry 335806464}

er1646v2BgriMVIpV6TrafficPolicyInbound OBJECT-TYPE
   SYNTAX      DisplayString
   MAX-ACCESS  read-write
   STATUS      current
   DESCRIPTION
      "Path: vpnBridgeGroup.editConf.ipV6.trafficPolicy.inbound"
   ::= {er1646v2BgriMVIpV6Entry 184614912}

er1646v2BgriMVIpV6TrafficPolicyOutbound OBJECT-TYPE
   SYNTAX      DisplayString
   MAX-ACCESS  read-write
   STATUS      current
   DESCRIPTION
      "Path: vpnBridgeGroup.editConf.ipV6.trafficPolicy.outbound"
   ::= {er1646v2BgriMVIpV6Entry 184680448}

er1646v2BgriMVIpV6FirewallZone OBJECT-TYPE
   SYNTAX      DisplayString
   MAX-ACCESS  read-write
   STATUS      current
   DESCRIPTION
      "Path: vpnBridgeGroup.editConf.ipV6.firewall.zone"
   ::= {er1646v2BgriMVIpV6Entry 201392128}

er1646v2BgriMVIpV6DhcpClientAddrAC OBJECT-TYPE
   SYNTAX      INTEGER
               {
               disabled (0),
               enabled (1)
               }
   MAX-ACCESS  read-write
   STATUS      current
   DESCRIPTION
      "Path: vpnBridgeGroup.editConf.ipV6.dhcp.client.addrAutoConfig

       Possibilities:
               disabled   (0)
               enabled   (1)"
   ::= {er1646v2BgriMVIpV6Entry 170131456}

er1646v2BgriMVIpV6DhcpClientPrDelMode OBJECT-TYPE
   SYNTAX      INTEGER
               {
               disabled (0),
               enabled (1)
               }
   MAX-ACCESS  read-write
   STATUS      current
   DESCRIPTION
      "Path: vpnBridgeGroup.editConf.ipV6.dhcp.client.pd.mode

       Possibilities:
               disabled   (0)
               enabled   (1)"
   ::= {er1646v2BgriMVIpV6Entry 170394624}

er1646v2BgriMVIpV6DhcpClientPrDelPool OBJECT-TYPE
   SYNTAX      DisplayString
   MAX-ACCESS  read-write
   STATUS      current
   DESCRIPTION
      "Path: vpnBridgeGroup.editConf.ipV6.dhcp.client.pd.pool"
   ::= {er1646v2BgriMVIpV6Entry 170395648}

er1646v2BgriMVIpV6DhcpClientPrDelPdExclOpt OBJECT-TYPE
   SYNTAX      INTEGER
               {
               disabled (0),
               enabled (1)
               }
   MAX-ACCESS  read-write
   STATUS      current
   DESCRIPTION
      "Path: vpnBridgeGroup.editConf.ipV6.dhcp.client.pd.pdExclOpt

       Possibilities:
               disabled   (0)
               enabled   (1)"
   ::= {er1646v2BgriMVIpV6Entry 170396672}

er1646v2BgriMVIpV6DhcpClientDnsServerPref OBJECT-TYPE
   SYNTAX      Integer32
   MAX-ACCESS  read-write
   STATUS      current
   DESCRIPTION
      "Path: vpnBridgeGroup.editConf.ipV6.dhcp.client.dns.serverPref"
   ::= {er1646v2BgriMVIpV6Entry 170918912}

er1646v2BgriMVIpV6DhcpClientRapidCommit OBJECT-TYPE
   SYNTAX      INTEGER
               {
               disabled (0),
               enabled (1)
               }
   MAX-ACCESS  read-write
   STATUS      current
   DESCRIPTION
      "Path: vpnBridgeGroup.editConf.ipV6.dhcp.client.rapidCommit

       Possibilities:
               disabled   (0)
               enabled   (1)"
   ::= {er1646v2BgriMVIpV6Entry 170655744}

er1646v2BgriMVIpV6DhcpClientTimersSolTimeOut OBJECT-TYPE
   SYNTAX      TimeTicks
   MAX-ACCESS  read-write
   STATUS      current
   DESCRIPTION
      "Path: vpnBridgeGroup.editConf.ipV6.dhcp.client.timers.solTimeOut

       Time in centi-second."
   ::= {er1646v2BgriMVIpV6Entry 171181056}

er1646v2BgriMVIpV6DhcpClientTimersSolMaxRt OBJECT-TYPE
   SYNTAX      TimeTicks
   MAX-ACCESS  read-write
   STATUS      current
   DESCRIPTION
      "Path: vpnBridgeGroup.editConf.ipV6.dhcp.client.timers.solMaxRt

       Time in centi-second."
   ::= {er1646v2BgriMVIpV6Entry 171182080}

er1646v2BgriMVIpV6DhcpClientTimersInfoRefresh OBJECT-TYPE
   SYNTAX      TimeTicks
   MAX-ACCESS  read-write
   STATUS      current
   DESCRIPTION
      "Path: vpnBridgeGroup.editConf.ipV6.dhcp.client.timers.infoRefresh

       Time in centi-second."
   ::= {er1646v2BgriMVIpV6Entry 171183104}

er1646v2BgriMVIpV6DhcpServerMode OBJECT-TYPE
   SYNTAX      INTEGER
               {
               disabled (0),
               enabled (1)
               }
   MAX-ACCESS  read-write
   STATUS      current
   DESCRIPTION
      "Path: vpnBridgeGroup.editConf.ipV6.dhcp.server.mode

       Possibilities:
               disabled   (0)
               enabled   (1)"
   ::= {er1646v2BgriMVIpV6Entry 172228608}

er1646v2BgriMVIpV6DhcpServerPreference OBJECT-TYPE
   SYNTAX      Integer32
   MAX-ACCESS  read-write
   STATUS      current
   DESCRIPTION
      "Path: vpnBridgeGroup.editConf.ipV6.dhcp.server.preference"
   ::= {er1646v2BgriMVIpV6Entry 172490752}

er1646v2BgriMVIpV6DhcpServerPool OBJECT-TYPE
   SYNTAX      DisplayString
   MAX-ACCESS  read-write
   STATUS      current
   DESCRIPTION
      "Path: vpnBridgeGroup.editConf.ipV6.dhcp.server.pool"
   ::= {er1646v2BgriMVIpV6Entry 172752896}

er1646v2BgriMVIpV6DhcpServerRapidCommit OBJECT-TYPE
   SYNTAX      INTEGER
               {
               disabled (0),
               enabled (1)
               }
   MAX-ACCESS  read-write
   STATUS      current
   DESCRIPTION
      "Path: vpnBridgeGroup.editConf.ipV6.dhcp.server.rapidCommit

       Possibilities:
               disabled   (0)
               enabled   (1)"
   ::= {er1646v2BgriMVIpV6Entry 173015040}

er1646v2BgriMVIpV6DhcpServerTimersInfoRefresh OBJECT-TYPE
   SYNTAX      TimeTicks
   MAX-ACCESS  read-write
   STATUS      current
   DESCRIPTION
      "Path: vpnBridgeGroup.editConf.ipV6.dhcp.server.timers.infoRefresh

       Time in centi-second."
   ::= {er1646v2BgriMVIpV6Entry 173278208}

er1646v2BgriMVIpV6DhcpRelayMode OBJECT-TYPE
   SYNTAX      INTEGER
               {
               disabled (0),
               enabled (1)
               }
   MAX-ACCESS  read-write
   STATUS      current
   DESCRIPTION
      "Path: vpnBridgeGroup.editConf.ipV6.dhcp.relay.mode

       Possibilities:
               disabled   (0)
               enabled   (1)"
   ::= {er1646v2BgriMVIpV6Entry 174071808}

er1646v2BgriMVIpV6SendRedirect OBJECT-TYPE
   SYNTAX      INTEGER
               {
               disabled (0),
               enabled (1)
               }
   MAX-ACCESS  read-write
   STATUS      current
   DESCRIPTION
      "Path: vpnBridgeGroup.editConf.ipV6.sendRedirect

       Possibilities:
               disabled   (0)
               enabled   (1)"
   ::= {er1646v2BgriMVIpV6Entry 117440512}

er1646v2BgriMVIpV6LinkMtu OBJECT-TYPE
   SYNTAX      Integer32
   MAX-ACCESS  read-write
   STATUS      current
   DESCRIPTION
      "Path: vpnBridgeGroup.editConf.ipV6.linkMtu"
   ::= {er1646v2BgriMVIpV6Entry 134217728}

er1646v2BgriMVIpV6InterfaceId OBJECT-TYPE
   SYNTAX      OCTET STRING
   MAX-ACCESS  read-write
   STATUS      current
   DESCRIPTION
      "Path: vpnBridgeGroup.editConf.ipV6.interfaceId"
   ::= {er1646v2BgriMVIpV6Entry 150994944}

er1646v2BgriMVIpV6MF OBJECT-TYPE
   SYNTAX      Integer32
   MAX-ACCESS  read-write
   STATUS      current
   DESCRIPTION
      "Path: vpnBridgeGroup.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2BgriMVIpV6Entry 285212672}

er1646v2BgriMVIpV6IcmpMessagesNoRoute OBJECT-TYPE
   SYNTAX      INTEGER
               {
               disabled (0),
               enabled (1)
               }
   MAX-ACCESS  read-write
   STATUS      current
   DESCRIPTION
      "Path: vpnBridgeGroup.editConf.ipV6.icmpMessages.noRoute

       Possibilities:
               disabled   (0)
               enabled   (1)"
   ::= {er1646v2BgriMVIpV6Entry 302055424}

er1646v2BgriMVIpV6IcmpMessagesBeyondScope OBJECT-TYPE
   SYNTAX      INTEGER
               {
               disabled (0),
               enabled (1)
               }
   MAX-ACCESS  read-write
   STATUS      current
   DESCRIPTION
      "Path: vpnBridgeGroup.editConf.ipV6.icmpMessages.beyondScope

       Possibilities:
               disabled   (0)
               enabled   (1)"
   ::= {er1646v2BgriMVIpV6Entry 302186496}

er1646v2BgriMVIpV6IcmpMessagesAddressUnreachable OBJECT-TYPE
   SYNTAX      INTEGER
               {
               disabled (0),
               enabled (1)
               }
   MAX-ACCESS  read-write
   STATUS      current
   DESCRIPTION
      "Path: vpnBridgeGroup.editConf.ipV6.icmpMessages.addressUnreachable

       Possibilities:
               disabled   (0)
               enabled   (1)"
   ::= {er1646v2BgriMVIpV6Entry 302252032}

er1646v2BgriMVIpV6IcmpMessagesPortUnreachable OBJECT-TYPE
   SYNTAX      INTEGER
               {
               disabled (0),
               enabled (1)
               }
   MAX-ACCESS  read-write
   STATUS      current
   DESCRIPTION
      "Path: vpnBridgeGroup.editConf.ipV6.icmpMessages.portUnreachable

       Possibilities:
               disabled   (0)
               enabled   (1)"
   ::= {er1646v2BgriMVIpV6Entry 302317568}

er1646v2BgriMVIpV6IcmpMessagesPacketTooBig OBJECT-TYPE
   SYNTAX      INTEGER
               {
               disabled (0),
               enabled (1)
               }
   MAX-ACCESS  read-write
   STATUS      current
   DESCRIPTION
      "Path: vpnBridgeGroup.editConf.ipV6.icmpMessages.packetTooBig

       Possibilities:
               disabled   (0)
               enabled   (1)"
   ::= {er1646v2BgriMVIpV6Entry 302645248}

er1646v2BgriMVIpV6IcmpMessagesHopLimitExceeded OBJECT-TYPE
   SYNTAX      INTEGER
               {
               disabled (0),
               enabled (1)
               }
   MAX-ACCESS  read-write
   STATUS      current
   DESCRIPTION
      "Path: vpnBridgeGroup.editConf.ipV6.icmpMessages.hopLimitExceeded

       Possibilities:
               disabled   (0)
               enabled   (1)"
   ::= {er1646v2BgriMVIpV6Entry 303300608}

er1646v2BgriMVIpV6IcmpMessagesFragTimeExceeded OBJECT-TYPE
   SYNTAX      INTEGER
               {
               disabled (0),
               enabled (1)
               }
   MAX-ACCESS  read-write
   STATUS      current
   DESCRIPTION
      "Path: vpnBridgeGroup.editConf.ipV6.icmpMessages.fragTimeExceeded

       Possibilities:
               disabled   (0)
               enabled   (1)"
   ::= {er1646v2BgriMVIpV6Entry 303366144}

er1646v2BgriMVIpV6IcmpMessagesHeaderFieldErr OBJECT-TYPE
   SYNTAX      INTEGER
               {
               disabled (0),
               enabled (1)
               }
   MAX-ACCESS  read-write
   STATUS      current
   DESCRIPTION
      "Path: vpnBridgeGroup.editConf.ipV6.icmpMessages.headerFieldErr

       Possibilities:
               disabled   (0)
               enabled   (1)"
   ::= {er1646v2BgriMVIpV6Entry 303955968}

er1646v2BgriMVIpV6IcmpMessagesOptionUnrecognized OBJECT-TYPE
   SYNTAX      INTEGER
               {
               disabled (0),
               enabled (1)
               }
   MAX-ACCESS  read-write
   STATUS      current
   DESCRIPTION
      "Path: vpnBridgeGroup.editConf.ipV6.icmpMessages.optionUnrecognized

       Possibilities:
               disabled   (0)
               enabled   (1)"
   ::= {er1646v2BgriMVIpV6Entry 304087040}

er1646v2BgriMVIpV6IcmpMessagesRedirect OBJECT-TYPE
   SYNTAX      INTEGER
               {
               disabled (0),
               enabled (1)
               }
   MAX-ACCESS  read-write
   STATUS      current
   DESCRIPTION
      "Path: vpnBridgeGroup.editConf.ipV6.icmpMessages.redirect

       Possibilities:
               disabled   (0)
               enabled   (1)"
   ::= {er1646v2BgriMVIpV6Entry 304611328}

er1646v2BgriMVIpV6Addresses OBJECT-TYPE
   SYNTAX      SEQUENCE OF Er1646v2BgriMVIpV6AddressesEntry
   MAX-ACCESS  not-accessible
   STATUS      current
   DESCRIPTION
      ""
   ::= {er1646v2BgriMVIpV6 50331648}

er1646v2BgriMVIpV6AddressesEntry OBJECT-TYPE
   SYNTAX      Er1646v2BgriMVIpV6AddressesEntry
   MAX-ACCESS  not-accessible
   STATUS      current
   DESCRIPTION
      ""
   INDEX      { er1646v2BgriMVIpV6AddressesGlobalIx,
                er1646v2BgriMVIpV6AddressesTableIx }
   ::= {er1646v2BgriMVIpV6Addresses 1}

Er1646v2BgriMVIpV6AddressesEntry ::=
   SEQUENCE
      {
      er1646v2BgriMVIpV6AddressesActions
         VariableLengthTableActions,
      er1646v2BgriMVIpV6AddressesGlobalIx
         GlobalIndex,
      er1646v2BgriMVIpV6AddressesTableIx
         TableIndex,
      er1646v2BgriMVIpV6AddressesType
         INTEGER,
      er1646v2BgriMVIpV6AddressesAddress
         Ipv6Address,
      er1646v2BgriMVIpV6AddressesPrefixLength
         Integer32,
      er1646v2BgriMVIpV6AddressesGeneralPrefix
         DisplayString,
      er1646v2BgriMVIpV6AddressesRaSend
         INTEGER,
      er1646v2BgriMVIpV6AddressesRaOnLinkFlag
         INTEGER,
      er1646v2BgriMVIpV6AddressesRaAutoFlag
         INTEGER,
      er1646v2BgriMVIpV6AddressesRaValidLifeTime
         TimeTicks,
      er1646v2BgriMVIpV6AddressesRaValidLTMode
         INTEGER,
      er1646v2BgriMVIpV6AddressesRaPrefLifeTime
         TimeTicks,
      er1646v2BgriMVIpV6AddressesRaPrefLTMode
         INTEGER
      }

er1646v2BgriMVIpV6AddressesActions OBJECT-TYPE
   SYNTAX      VariableLengthTableActions
   MAX-ACCESS  read-write
   STATUS      current
   DESCRIPTION
      "By way of this field, some manipulations
       on this table may be performed."
   ::= {er1646v2BgriMVIpV6AddressesEntry 2}

er1646v2BgriMVIpV6AddressesGlobalIx OBJECT-TYPE
   SYNTAX      GlobalIndex
   MAX-ACCESS  not-accessible
   STATUS      current
   DESCRIPTION
      "The value of the tlsCntTreeGlobalIndex of the MANAGED OBJECT."
   ::= {er1646v2BgriMVIpV6AddressesEntry 10}

er1646v2BgriMVIpV6AddressesTableIx OBJECT-TYPE
   SYNTAX      TableIndex
   MAX-ACCESS  not-accessible
   STATUS      current
   DESCRIPTION
      ""
   ::= {er1646v2BgriMVIpV6AddressesEntry 11}

er1646v2BgriMVIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vpnBridgeGroup.editConf.ipV6.addresses.type

       Possibilities:
               unicast   (0)
               eui64   (1)
               anycast   (2)
               linkLocal   (3)
               generalPrefix   (4)"
   ::= {er1646v2BgriMVIpV6AddressesEntry 50331648}

er1646v2BgriMVIpV6AddressesAddress OBJECT-TYPE
   SYNTAX      Ipv6Address
   MAX-ACCESS  read-write
   STATUS      current
   DESCRIPTION
      "Path: vpnBridgeGroup.editConf.ipV6.addresses.address

       ipv6 address"
   ::= {er1646v2BgriMVIpV6AddressesEntry 16777216}

er1646v2BgriMVIpV6AddressesPrefixLength OBJECT-TYPE
   SYNTAX      Integer32
   MAX-ACCESS  read-write
   STATUS      current
   DESCRIPTION
      "Path: vpnBridgeGroup.editConf.ipV6.addresses.prefixLength"
   ::= {er1646v2BgriMVIpV6AddressesEntry 33554432}

er1646v2BgriMVIpV6AddressesGeneralPrefix OBJECT-TYPE
   SYNTAX      DisplayString
   MAX-ACCESS  read-write
   STATUS      current
   DESCRIPTION
      "Path: vpnBridgeGroup.editConf.ipV6.addresses.generalPrefix"
   ::= {er1646v2BgriMVIpV6AddressesEntry 83886080}

er1646v2BgriMVIpV6AddressesRaSend OBJECT-TYPE
   SYNTAX      INTEGER
               {
               disabled (0),
               enabled (1)
               }
   MAX-ACCESS  read-write
   STATUS      current
   DESCRIPTION
      "Path: vpnBridgeGroup.editConf.ipV6.addresses.ra.send

       Possibilities:
               disabled   (0)
               enabled   (1)"
   ::= {er1646v2BgriMVIpV6AddressesEntry 67174400}

er1646v2BgriMVIpV6AddressesRaOnLinkFlag OBJECT-TYPE
   SYNTAX      INTEGER
               {
               disabled (0),
               enabled (1)
               }
   MAX-ACCESS  read-write
   STATUS      current
   DESCRIPTION
      "Path: vpnBridgeGroup.editConf.ipV6.addresses.ra.onLinkFlag

       Possibilities:
               disabled   (0)
               enabled   (1)"
   ::= {er1646v2BgriMVIpV6AddressesEntry 67371008}

er1646v2BgriMVIpV6AddressesRaAutoFlag OBJECT-TYPE
   SYNTAX      INTEGER
               {
               disabled (0),
               enabled (1)
               }
   MAX-ACCESS  read-write
   STATUS      current
   DESCRIPTION
      "Path: vpnBridgeGroup.editConf.ipV6.addresses.ra.autonomousFlag

       Possibilities:
               disabled   (0)
               enabled   (1)"
   ::= {er1646v2BgriMVIpV6AddressesEntry 67567616}

er1646v2BgriMVIpV6AddressesRaValidLifeTime OBJECT-TYPE
   SYNTAX      TimeTicks
   MAX-ACCESS  read-write
   STATUS      current
   DESCRIPTION
      "Path: vpnBridgeGroup.editConf.ipV6.addresses.ra.validLifeTime

       Time in centi-second."
   ::= {er1646v2BgriMVIpV6AddressesEntry 67239936}

er1646v2BgriMVIpV6AddressesRaValidLTMode OBJECT-TYPE
   SYNTAX      INTEGER
               {
               fixed (0),
               infinite (2)
               }
   MAX-ACCESS  read-write
   STATUS      current
   DESCRIPTION
      "Path: vpnBridgeGroup.editConf.ipV6.addresses.ra.validLifeTimeMode

       Possibilities:
               fixed   (0)
               infinite   (2)"
   ::= {er1646v2BgriMVIpV6AddressesEntry 67305472}

er1646v2BgriMVIpV6AddressesRaPrefLifeTime OBJECT-TYPE
   SYNTAX      TimeTicks
   MAX-ACCESS  read-write
   STATUS      current
   DESCRIPTION
      "Path: vpnBridgeGroup.editConf.ipV6.addresses.ra.prefLifeTime

       Time in centi-second."
   ::= {er1646v2BgriMVIpV6AddressesEntry 67436544}

er1646v2BgriMVIpV6AddressesRaPrefLTMode OBJECT-TYPE
   SYNTAX      INTEGER
               {
               fixed (0),
               infinite (2)
               }
   MAX-ACCESS  read-write
   STATUS      current
   DESCRIPTION
      "Path: vpnBridgeGroup.editConf.ipV6.addresses.ra.prefLifeTimeMode

       Possibilities:
               fixed   (0)
               infinite   (2)"
   ::= {er1646v2BgriMVIpV6AddressesEntry 67502080}

er1646v2BgriMVIpV6RaDnsOptionsRdnssServers OBJECT-TYPE
   SYNTAX      SEQUENCE OF Er1646v2BgriMVIpV6RaDnsOptionsRdnssServersEntry
   MAX-ACCESS  not-accessible
   STATUS      current
   DESCRIPTION
      ""
   ::= {er1646v2BgriMVIpV6 101394432}

er1646v2BgriMVIpV6RaDnsOptionsRdnssServersEntry OBJECT-TYPE
   SYNTAX      Er1646v2BgriMVIpV6RaDnsOptionsRdnssServersEntry
   MAX-ACCESS  not-accessible
   STATUS      current
   DESCRIPTION
      ""
   INDEX      { er1646v2BgriMVIpV6RaDnsOptionsRdnssServersGlobalIx,
                er1646v2BgriMVIpV6RaDnsOptionsRdnssServersTableIx }
   ::= {er1646v2BgriMVIpV6RaDnsOptionsRdnssServers 1}

Er1646v2BgriMVIpV6RaDnsOptionsRdnssServersEntry ::=
   SEQUENCE
      {
      er1646v2BgriMVIpV6RaDnsOptionsRdnssServersActions
         VariableLengthTableActions,
      er1646v2BgriMVIpV6RaDnsOptionsRdnssServersGlobalIx
         GlobalIndex,
      er1646v2BgriMVIpV6RaDnsOptionsRdnssServersTableIx
         TableIndex,
      er1646v2BgriMVIpV6RaDnsOptionsRdnssServersAddress
         Ipv6Address
      }

er1646v2BgriMVIpV6RaDnsOptionsRdnssServersActions OBJECT-TYPE
   SYNTAX      VariableLengthTableActions
   MAX-ACCESS  read-write
   STATUS      current
   DESCRIPTION
      "By way of this field, some manipulations
       on this table may be performed."
   ::= {er1646v2BgriMVIpV6RaDnsOptionsRdnssServersEntry 2}

er1646v2BgriMVIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2BgriMVIpV6RaDnsOptionsRdnssServersEntry 10}

er1646v2BgriMVIpV6RaDnsOptionsRdnssServersTableIx OBJECT-TYPE
   SYNTAX      TableIndex
   MAX-ACCESS  not-accessible
   STATUS      current
   DESCRIPTION
      ""
   ::= {er1646v2BgriMVIpV6RaDnsOptionsRdnssServersEntry 11}

er1646v2BgriMVIpV6RaDnsOptionsRdnssServersAddress OBJECT-TYPE
   SYNTAX      Ipv6Address
   MAX-ACCESS  read-write
   STATUS      current
   DESCRIPTION
      "Path: vpnBridgeGroup.editConf.ipV6.ra.dnsOptions.rdnss.servers.address

       ipv6 address"
   ::= {er1646v2BgriMVIpV6RaDnsOptionsRdnssServersEntry 16777216}

er1646v2BgriMVIpV6RaDnsOptionsDnsslDomains OBJECT-TYPE
   SYNTAX      SEQUENCE OF Er1646v2BgriMVIpV6RaDnsOptionsDnsslDomainsEntry
   MAX-ACCESS  not-accessible
   STATUS      current
   DESCRIPTION
      ""
   ::= {er1646v2BgriMVIpV6 101402624}

er1646v2BgriMVIpV6RaDnsOptionsDnsslDomainsEntry OBJECT-TYPE
   SYNTAX      Er1646v2BgriMVIpV6RaDnsOptionsDnsslDomainsEntry
   MAX-ACCESS  not-accessible
   STATUS      current
   DESCRIPTION
      ""
   INDEX      { er1646v2BgriMVIpV6RaDnsOptionsDnsslDomainsGlobalIx,
                er1646v2BgriMVIpV6RaDnsOptionsDnsslDomainsTableIx }
   ::= {er1646v2BgriMVIpV6RaDnsOptionsDnsslDomains 1}

Er1646v2BgriMVIpV6RaDnsOptionsDnsslDomainsEntry ::=
   SEQUENCE
      {
      er1646v2BgriMVIpV6RaDnsOptionsDnsslDomainsActions
         VariableLengthTableActions,
      er1646v2BgriMVIpV6RaDnsOptionsDnsslDomainsGlobalIx
         GlobalIndex,
      er1646v2BgriMVIpV6RaDnsOptionsDnsslDomainsTableIx
         TableIndex,
      er1646v2BgriMVIpV6RaDnsOptionsDnsslDomainsName
         DisplayString
      }

er1646v2BgriMVIpV6RaDnsOptionsDnsslDomainsActions OBJECT-TYPE
   SYNTAX      VariableLengthTableActions
   MAX-ACCESS  read-write
   STATUS      current
   DESCRIPTION
      "By way of this field, some manipulations
       on this table may be performed."
   ::= {er1646v2BgriMVIpV6RaDnsOptionsDnsslDomainsEntry 2}

er1646v2BgriMVIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2BgriMVIpV6RaDnsOptionsDnsslDomainsEntry 10}

er1646v2BgriMVIpV6RaDnsOptionsDnsslDomainsTableIx OBJECT-TYPE
   SYNTAX      TableIndex
   MAX-ACCESS  not-accessible
   STATUS      current
   DESCRIPTION
      ""
   ::= {er1646v2BgriMVIpV6RaDnsOptionsDnsslDomainsEntry 11}

er1646v2BgriMVIpV6RaDnsOptionsDnsslDomainsName OBJECT-TYPE
   SYNTAX      DisplayString
   MAX-ACCESS  read-write
   STATUS      current
   DESCRIPTION
      "Path: vpnBridgeGroup.editConf.ipV6.ra.dnsOptions.dnssl.domains.name"
   ::= {er1646v2BgriMVIpV6RaDnsOptionsDnsslDomainsEntry 16777216}

er1646v2BgriMVIpV6DhcpClientUserClassOpt OBJECT-TYPE
   SYNTAX      SEQUENCE OF Er1646v2BgriMVIpV6DhcpClientUserClassOptEntry
   MAX-ACCESS  not-accessible
   STATUS      current
   DESCRIPTION
      ""
   ::= {er1646v2BgriMVIpV6 171442176}

er1646v2BgriMVIpV6DhcpClientUserClassOptEntry OBJECT-TYPE
   SYNTAX      Er1646v2BgriMVIpV6DhcpClientUserClassOptEntry
   MAX-ACCESS  not-accessible
   STATUS      current
   DESCRIPTION
      ""
   INDEX      { er1646v2BgriMVIpV6DhcpClientUserClassOptGlobalIx,
                er1646v2BgriMVIpV6DhcpClientUserClassOptTableIx }
   ::= {er1646v2BgriMVIpV6DhcpClientUserClassOpt 1}

Er1646v2BgriMVIpV6DhcpClientUserClassOptEntry ::=
   SEQUENCE
      {
      er1646v2BgriMVIpV6DhcpClientUserClassOptActions
         VariableLengthTableActions,
      er1646v2BgriMVIpV6DhcpClientUserClassOptGlobalIx
         GlobalIndex,
      er1646v2BgriMVIpV6DhcpClientUserClassOptTableIx
         TableIndex,
      er1646v2BgriMVIpV6DhcpClientUserClassOptValueAscii
         DisplayString,
      er1646v2BgriMVIpV6DhcpClientUserClassOptValueDecimal
         Integer32,
      er1646v2BgriMVIpV6DhcpClientUserClassOptValueHexData
         OCTET STRING
      }

er1646v2BgriMVIpV6DhcpClientUserClassOptActions OBJECT-TYPE
   SYNTAX      VariableLengthTableActions
   MAX-ACCESS  read-write
   STATUS      current
   DESCRIPTION
      "By way of this field, some manipulations
       on this table may be performed."
   ::= {er1646v2BgriMVIpV6DhcpClientUserClassOptEntry 2}

er1646v2BgriMVIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2BgriMVIpV6DhcpClientUserClassOptEntry 10}

er1646v2BgriMVIpV6DhcpClientUserClassOptTableIx OBJECT-TYPE
   SYNTAX      TableIndex
   MAX-ACCESS  not-accessible
   STATUS      current
   DESCRIPTION
      ""
   ::= {er1646v2BgriMVIpV6DhcpClientUserClassOptEntry 11}

er1646v2BgriMVIpV6DhcpClientUserClassOptValueAscii OBJECT-TYPE
   SYNTAX      DisplayString
   MAX-ACCESS  read-write
   STATUS      current
   DESCRIPTION
      "Path: vpnBridgeGroup.editConf.ipV6.dhcp.client.userClassOpt.value.ascii"
   ::= {er1646v2BgriMVIpV6DhcpClientUserClassOptEntry 16842752}

er1646v2BgriMVIpV6DhcpClientUserClassOptValueDecimal OBJECT-TYPE
   SYNTAX      Integer32
   MAX-ACCESS  read-write
   STATUS      current
   DESCRIPTION
      "Path: vpnBridgeGroup.editConf.ipV6.dhcp.client.userClassOpt.value.decimal"
   ::= {er1646v2BgriMVIpV6DhcpClientUserClassOptEntry 16908288}

er1646v2BgriMVIpV6DhcpClientUserClassOptValueHexData OBJECT-TYPE
   SYNTAX      OCTET STRING
   MAX-ACCESS  read-write
   STATUS      current
   DESCRIPTION
      "Path: vpnBridgeGroup.editConf.ipV6.dhcp.client.userClassOpt.value.hexData"
   ::= {er1646v2BgriMVIpV6DhcpClientUserClassOptEntry 16973824}

er1646v2BgriMVIpV6DhcpClientVendorCl OBJECT-TYPE
   SYNTAX      SEQUENCE OF Er1646v2BgriMVIpV6DhcpClientVendorClEntry
   MAX-ACCESS  not-accessible
   STATUS      current
   DESCRIPTION
      ""
   ::= {er1646v2BgriMVIpV6 171704320}

er1646v2BgriMVIpV6DhcpClientVendorClEntry OBJECT-TYPE
   SYNTAX      Er1646v2BgriMVIpV6DhcpClientVendorClEntry
   MAX-ACCESS  not-accessible
   STATUS      current
   DESCRIPTION
      ""
   INDEX      { er1646v2BgriMVIpV6DhcpClientVendorClGlobalIx,
                er1646v2BgriMVIpV6DhcpClientVendorClTableIx }
   ::= {er1646v2BgriMVIpV6DhcpClientVendorCl 1}

Er1646v2BgriMVIpV6DhcpClientVendorClEntry ::=
   SEQUENCE
      {
      er1646v2BgriMVIpV6DhcpClientVendorClActions
         VariableLengthTableActions,
      er1646v2BgriMVIpV6DhcpClientVendorClGlobalIx
         GlobalIndex,
      er1646v2BgriMVIpV6DhcpClientVendorClTableIx
         TableIndex,
      er1646v2BgriMVIpV6DhcpClientVendorClValueAscii
         DisplayString,
      er1646v2BgriMVIpV6DhcpClientVendorClValueDecimal
         Integer32,
      er1646v2BgriMVIpV6DhcpClientVendorClValueHexData
         OCTET STRING
      }

er1646v2BgriMVIpV6DhcpClientVendorClActions OBJECT-TYPE
   SYNTAX      VariableLengthTableActions
   MAX-ACCESS  read-write
   STATUS      current
   DESCRIPTION
      "By way of this field, some manipulations
       on this table may be performed."
   ::= {er1646v2BgriMVIpV6DhcpClientVendorClEntry 2}

er1646v2BgriMVIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2BgriMVIpV6DhcpClientVendorClEntry 10}

er1646v2BgriMVIpV6DhcpClientVendorClTableIx OBJECT-TYPE
   SYNTAX      TableIndex
   MAX-ACCESS  not-accessible
   STATUS      current
   DESCRIPTION
      ""
   ::= {er1646v2BgriMVIpV6DhcpClientVendorClEntry 11}

er1646v2BgriMVIpV6DhcpClientVendorClValueAscii OBJECT-TYPE
   SYNTAX      DisplayString
   MAX-ACCESS  read-write
   STATUS      current
   DESCRIPTION
      "Path: vpnBridgeGroup.editConf.ipV6.dhcp.client.vendorClassOpt.value.ascii"
   ::= {er1646v2BgriMVIpV6DhcpClientVendorClEntry 16842752}

er1646v2BgriMVIpV6DhcpClientVendorClValueDecimal OBJECT-TYPE
   SYNTAX      Integer32
   MAX-ACCESS  read-write
   STATUS      current
   DESCRIPTION
      "Path: vpnBridgeGroup.editConf.ipV6.dhcp.client.vendorClassOpt.value.decimal"
   ::= {er1646v2BgriMVIpV6DhcpClientVendorClEntry 16908288}

er1646v2BgriMVIpV6DhcpClientVendorClValueHexData OBJECT-TYPE
   SYNTAX      OCTET STRING
   MAX-ACCESS  read-write
   STATUS      current
   DESCRIPTION
      "Path: vpnBridgeGroup.editConf.ipV6.dhcp.client.vendorClassOpt.value.hexData"
   ::= {er1646v2BgriMVIpV6DhcpClientVendorClEntry 16973824}

er1646v2BgriMVIpV6DhcpRelayDestinations OBJECT-TYPE
   SYNTAX      SEQUENCE OF Er1646v2BgriMVIpV6DhcpRelayDestinationsEntry
   MAX-ACCESS  not-accessible
   STATUS      current
   DESCRIPTION
      ""
   ::= {er1646v2BgriMVIpV6 174080000}

er1646v2BgriMVIpV6DhcpRelayDestinationsEntry OBJECT-TYPE
   SYNTAX      Er1646v2BgriMVIpV6DhcpRelayDestinationsEntry
   MAX-ACCESS  not-accessible
   STATUS      current
   DESCRIPTION
      ""
   INDEX      { er1646v2BgriMVIpV6DhcpRelayDestinationsGlobalIx,
                er1646v2BgriMVIpV6DhcpRelayDestinationsTableIx }
   ::= {er1646v2BgriMVIpV6DhcpRelayDestinations 1}

Er1646v2BgriMVIpV6DhcpRelayDestinationsEntry ::=
   SEQUENCE
      {
      er1646v2BgriMVIpV6DhcpRelayDestinationsActions
         VariableLengthTableActions,
      er1646v2BgriMVIpV6DhcpRelayDestinationsGlobalIx
         GlobalIndex,
      er1646v2BgriMVIpV6DhcpRelayDestinationsTableIx
         TableIndex,
      er1646v2BgriMVIpV6DhcpRelayDestinationsAddress
         Ipv6Address,
      er1646v2BgriMVIpV6DhcpRelayDestinationsInterface
         DisplayString
      }

er1646v2BgriMVIpV6DhcpRelayDestinationsActions OBJECT-TYPE
   SYNTAX      VariableLengthTableActions
   MAX-ACCESS  read-write
   STATUS      current
   DESCRIPTION
      "By way of this field, some manipulations
       on this table may be performed."
   ::= {er1646v2BgriMVIpV6DhcpRelayDestinationsEntry 2}

er1646v2BgriMVIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2BgriMVIpV6DhcpRelayDestinationsEntry 10}

er1646v2BgriMVIpV6DhcpRelayDestinationsTableIx OBJECT-TYPE
   SYNTAX      TableIndex
   MAX-ACCESS  not-accessible
   STATUS      current
   DESCRIPTION
      ""
   ::= {er1646v2BgriMVIpV6DhcpRelayDestinationsEntry 11}

er1646v2BgriMVIpV6DhcpRelayDestinationsAddress OBJECT-TYPE
   SYNTAX      Ipv6Address
   MAX-ACCESS  read-write
   STATUS      current
   DESCRIPTION
      "Path: vpnBridgeGroup.editConf.ipV6.dhcp.relay.destinations.address

       ipv6 address"
   ::= {er1646v2BgriMVIpV6DhcpRelayDestinationsEntry 16777216}

er1646v2BgriMVIpV6DhcpRelayDestinationsInterface OBJECT-TYPE
   SYNTAX      DisplayString
   MAX-ACCESS  read-write
   STATUS      current
   DESCRIPTION
      "Path: vpnBridgeGroup.editConf.ipV6.dhcp.relay.destinations.interface"
   ::= {er1646v2BgriMVIpV6DhcpRelayDestinationsEntry 33554432}


er1646v2BgriMVArp OBJECT IDENTIFIER ::= {er1646v2BgriMV 19}

er1646v2BgriMVArpSSCTable OBJECT-TYPE
   SYNTAX      SEQUENCE OF Er1646v2BgriMVArpEntry
   MAX-ACCESS  not-accessible
   STATUS      current
   DESCRIPTION
      "ethernet related config parameters"
   ::= {er1646v2BgriMVArp 1}

er1646v2BgriMVArpEntry OBJECT-TYPE
   SYNTAX      Er1646v2BgriMVArpEntry
   MAX-ACCESS  not-accessible
   STATUS      current
   DESCRIPTION
      ""
   INDEX      { er1646v2BgriMVArpGlobalIx }
   ::= {er1646v2BgriMVArpSSCTable 1}

Er1646v2BgriMVArpEntry ::=
   SEQUENCE
      {
      er1646v2BgriMVArpGlobalIx
         GlobalIndex,
      er1646v2BgriMVArpTimeOut
         TimeTicks,
      er1646v2BgriMVArpProxyArp
         INTEGER
      }

er1646v2BgriMVArpGlobalIx OBJECT-TYPE
   SYNTAX      GlobalIndex
   MAX-ACCESS  not-accessible
   STATUS      current
   DESCRIPTION
      "The value of the tlsCntTreeGlobalIndex of the MANAGED OBJECT."
   ::= {er1646v2BgriMVArpEntry 10}

er1646v2BgriMVArpTimeOut OBJECT-TYPE
   SYNTAX      TimeTicks
   MAX-ACCESS  read-write
   STATUS      current
   DESCRIPTION
      "Path: vpnBridgeGroup.editConf.arp.timeOut

       Time in centi-second."
   ::= {er1646v2BgriMVArpEntry 201326592}

er1646v2BgriMVArpProxyArp OBJECT-TYPE
   SYNTAX      INTEGER
               {
               disabled (0),
               enabled (1)
               }
   MAX-ACCESS  read-write
   STATUS      current
   DESCRIPTION
      "Path: vpnBridgeGroup.editConf.arp.proxyArp

       Possibilities:
               disabled   (0)
               enabled   (1)"
   ::= {er1646v2BgriMVArpEntry 838860800}

er1646v2BgriMVArpStaticArp OBJECT-TYPE
   SYNTAX      SEQUENCE OF Er1646v2BgriMVArpStaticArpEntry
   MAX-ACCESS  not-accessible
   STATUS      current
   DESCRIPTION
      ""
   ::= {er1646v2BgriMVArp 50331648}

er1646v2BgriMVArpStaticArpEntry OBJECT-TYPE
   SYNTAX      Er1646v2BgriMVArpStaticArpEntry
   MAX-ACCESS  not-accessible
   STATUS      current
   DESCRIPTION
      ""
   INDEX      { er1646v2BgriMVArpStaticArpGlobalIx,
                er1646v2BgriMVArpStaticArpTableIx }
   ::= {er1646v2BgriMVArpStaticArp 1}

Er1646v2BgriMVArpStaticArpEntry ::=
   SEQUENCE
      {
      er1646v2BgriMVArpStaticArpActions
         VariableLengthTableActions,
      er1646v2BgriMVArpStaticArpGlobalIx
         GlobalIndex,
      er1646v2BgriMVArpStaticArpTableIx
         TableIndex,
      er1646v2BgriMVArpStaticArpMacAddress
         OCTET STRING,
      er1646v2BgriMVArpStaticArpIpAddress
         IpAddress
      }

er1646v2BgriMVArpStaticArpActions OBJECT-TYPE
   SYNTAX      VariableLengthTableActions
   MAX-ACCESS  read-write
   STATUS      current
   DESCRIPTION
      "By way of this field, some manipulations
       on this table may be performed."
   ::= {er1646v2BgriMVArpStaticArpEntry 2}

er1646v2BgriMVArpStaticArpGlobalIx OBJECT-TYPE
   SYNTAX      GlobalIndex
   MAX-ACCESS  not-accessible
   STATUS      current
   DESCRIPTION
      "The value of the tlsCntTreeGlobalIndex of the MANAGED OBJECT."
   ::= {er1646v2BgriMVArpStaticArpEntry 10}

er1646v2BgriMVArpStaticArpTableIx OBJECT-TYPE
   SYNTAX      TableIndex
   MAX-ACCESS  not-accessible
   STATUS      current
   DESCRIPTION
      ""
   ::= {er1646v2BgriMVArpStaticArpEntry 11}

er1646v2BgriMVArpStaticArpMacAddress OBJECT-TYPE
   SYNTAX      OCTET STRING
   MAX-ACCESS  read-write
   STATUS      current
   DESCRIPTION
      "Path: vpnBridgeGroup.editConf.arp.staticArp.macAddress

       MAC address."
   ::= {er1646v2BgriMVArpStaticArpEntry 16777216}

er1646v2BgriMVArpStaticArpIpAddress OBJECT-TYPE
   SYNTAX      IpAddress
   MAX-ACCESS  read-write
   STATUS      current
   DESCRIPTION
      "Path: vpnBridgeGroup.editConf.arp.staticArp.ipAddress"
   ::= {er1646v2BgriMVArpStaticArpEntry 33554432}


er1646v2BgriMVSpanningTree OBJECT IDENTIFIER ::= {er1646v2BgriMV 5}

er1646v2BgriMVSpanningTreeSSCTable OBJECT-TYPE
   SYNTAX      SEQUENCE OF Er1646v2BgriMVSpanningTreeEntry
   MAX-ACCESS  not-accessible
   STATUS      current
   DESCRIPTION
      "Enable spanning tree algorithm"
   ::= {er1646v2BgriMVSpanningTree 1}

er1646v2BgriMVSpanningTreeEntry OBJECT-TYPE
   SYNTAX      Er1646v2BgriMVSpanningTreeEntry
   MAX-ACCESS  not-accessible
   STATUS      current
   DESCRIPTION
      ""
   INDEX      { er1646v2BgriMVSpanningTreeGlobalIx }
   ::= {er1646v2BgriMVSpanningTreeSSCTable 1}

Er1646v2BgriMVSpanningTreeEntry ::=
   SEQUENCE
      {
      er1646v2BgriMVSpanningTreeGlobalIx
         GlobalIndex,
      er1646v2BgriMVSpanningTreeSpTProt
         INTEGER,
      er1646v2BgriMVSpanningTreeBrPrio
         Integer32,
      er1646v2BgriMVSpanningTreeBrMAge
         TimeTicks,
      er1646v2BgriMVSpanningTreeBrHTim
         TimeTicks,
      er1646v2BgriMVSpanningTreeBrFDel
         TimeTicks,
      er1646v2BgriMVSpanningTreeTxHoldCnt
         Integer32,
      er1646v2BgriMVSpanningTreeMstConfigIdName
         DisplayString,
      er1646v2BgriMVSpanningTreeMstConfigIdRevisionLevel
         Integer32,
      er1646v2BgriMVSpanningTreeMaxHops
         Integer32
      }

er1646v2BgriMVSpanningTreeGlobalIx OBJECT-TYPE
   SYNTAX      GlobalIndex
   MAX-ACCESS  not-accessible
   STATUS      current
   DESCRIPTION
      "The value of the tlsCntTreeGlobalIndex of the MANAGED OBJECT."
   ::= {er1646v2BgriMVSpanningTreeEntry 10}

er1646v2BgriMVSpanningTreeSpTProt OBJECT-TYPE
   SYNTAX      INTEGER
               {
               none (0),
               p802d1DsmsSTPsCompatibility (2),
               p802d1D (1),
               p802d1Q (3)
               }
   MAX-ACCESS  read-write
   STATUS      current
   DESCRIPTION
      "Path: vpnBridgeGroup.editConf.spanningTree.protocol

       Possibilities:
               none   (0)
               p802.1D - STP Compatibility   (2)
               p802.1D   (1)
               p802.1Q   (3)"
   ::= {er1646v2BgriMVSpanningTreeEntry 16777216}

er1646v2BgriMVSpanningTreeBrPrio OBJECT-TYPE
   SYNTAX      Integer32
   MAX-ACCESS  read-write
   STATUS      current
   DESCRIPTION
      "Path: vpnBridgeGroup.editConf.spanningTree.bridgePriority"
   ::= {er1646v2BgriMVSpanningTreeEntry 33554432}

er1646v2BgriMVSpanningTreeBrMAge OBJECT-TYPE
   SYNTAX      TimeTicks
   MAX-ACCESS  read-write
   STATUS      current
   DESCRIPTION
      "Path: vpnBridgeGroup.editConf.spanningTree.bridgeMaxAge

       Time in centi-second."
   ::= {er1646v2BgriMVSpanningTreeEntry 50331648}

er1646v2BgriMVSpanningTreeBrHTim OBJECT-TYPE
   SYNTAX      TimeTicks
   MAX-ACCESS  read-write
   STATUS      current
   DESCRIPTION
      "Path: vpnBridgeGroup.editConf.spanningTree.bridgeHelloTime

       Time in centi-second."
   ::= {er1646v2BgriMVSpanningTreeEntry 67108864}

er1646v2BgriMVSpanningTreeBrFDel OBJECT-TYPE
   SYNTAX      TimeTicks
   MAX-ACCESS  read-write
   STATUS      current
   DESCRIPTION
      "Path: vpnBridgeGroup.editConf.spanningTree.bridgeForwardDelay

       Time in centi-second."
   ::= {er1646v2BgriMVSpanningTreeEntry 83886080}

er1646v2BgriMVSpanningTreeTxHoldCnt OBJECT-TYPE
   SYNTAX      Integer32
   MAX-ACCESS  read-write
   STATUS      current
   DESCRIPTION
      "Path: vpnBridgeGroup.editConf.spanningTree.transmitHoldCount"
   ::= {er1646v2BgriMVSpanningTreeEntry 100663296}

er1646v2BgriMVSpanningTreeMstConfigIdName OBJECT-TYPE
   SYNTAX      DisplayString
   MAX-ACCESS  read-write
   STATUS      current
   DESCRIPTION
      "Path: vpnBridgeGroup.editConf.spanningTree.mstConfigId.name"
   ::= {er1646v2BgriMVSpanningTreeEntry 117506048}

er1646v2BgriMVSpanningTreeMstConfigIdRevisionLevel OBJECT-TYPE
   SYNTAX      Integer32
   MAX-ACCESS  read-write
   STATUS      current
   DESCRIPTION
      "Path: vpnBridgeGroup.editConf.spanningTree.mstConfigId.revisionLevel"
   ::= {er1646v2BgriMVSpanningTreeEntry 117571584}

er1646v2BgriMVSpanningTreeMaxHops OBJECT-TYPE
   SYNTAX      Integer32
   MAX-ACCESS  read-write
   STATUS      current
   DESCRIPTION
      "Path: vpnBridgeGroup.editConf.spanningTree.maxHops"
   ::= {er1646v2BgriMVSpanningTreeEntry 134217728}


er1646v2BgriMVLocalAccess OBJECT IDENTIFIER ::= {er1646v2BgriMV 28}

er1646v2BgriMVLocalAccessTable OBJECT-TYPE
   SYNTAX      SEQUENCE OF Er1646v2BgriMVLocalAccessEntry
   MAX-ACCESS  not-accessible
   STATUS      current
   DESCRIPTION
      "restricts access to protocolstack via bridgegroup"
   ::= {er1646v2BgriMVLocalAccess 1}

er1646v2BgriMVLocalAccessEntry OBJECT-TYPE
   SYNTAX      Er1646v2BgriMVLocalAccessEntry
   MAX-ACCESS  not-accessible
   STATUS      current
   DESCRIPTION
      ""
   INDEX      { er1646v2BgriMVLocalAccessGlobalIx }
   ::= {er1646v2BgriMVLocalAccessTable 1}

Er1646v2BgriMVLocalAccessEntry ::=
   SEQUENCE
      {
      er1646v2BgriMVLocalAccessGlobalIx
         GlobalIndex,
      er1646v2BgriMVLocalAccessValue
         INTEGER
      }

er1646v2BgriMVLocalAccessGlobalIx OBJECT-TYPE
   SYNTAX      GlobalIndex
   MAX-ACCESS  not-accessible
   STATUS      current
   DESCRIPTION
      "The value of the tlsCntTreeGlobalIndex of the MANAGED OBJECT."
   ::= {er1646v2BgriMVLocalAccessEntry 10}

er1646v2BgriMVLocalAccessValue OBJECT-TYPE
   SYNTAX      INTEGER
               {
               permitted (0),
               restricted (1)
               }
   MAX-ACCESS  read-write
   STATUS      current
   DESCRIPTION
      "Path: vpnBridgeGroup.editConf.localAccess

       Possibilities:
               permitted   (0)
               restricted   (1)"
   ::= {er1646v2BgriMVLocalAccessEntry 2147483648}


er1646v2BgriMVAccessControl OBJECT IDENTIFIER ::= {er1646v2BgriMV 29}

er1646v2BgriMVAccessControlSSCTable OBJECT-TYPE
   SYNTAX      SEQUENCE OF Er1646v2BgriMVAccessControlEntry
   MAX-ACCESS  not-accessible
   STATUS      current
   DESCRIPTION
      "access control on bridgegroups"
   ::= {er1646v2BgriMVAccessControl 1}

er1646v2BgriMVAccessControlEntry OBJECT-TYPE
   SYNTAX      Er1646v2BgriMVAccessControlEntry
   MAX-ACCESS  not-accessible
   STATUS      current
   DESCRIPTION
      ""
   INDEX      { er1646v2BgriMVAccessControlGlobalIx }
   ::= {er1646v2BgriMVAccessControlSSCTable 1}

Er1646v2BgriMVAccessControlEntry ::=
   SEQUENCE
      {
      er1646v2BgriMVAccessControlGlobalIx
         GlobalIndex,
      er1646v2BgriMVAccessControlInAccessList
         DisplayString,
      er1646v2BgriMVAccessControlLimBC
         INTEGER
      }

er1646v2BgriMVAccessControlGlobalIx OBJECT-TYPE
   SYNTAX      GlobalIndex
   MAX-ACCESS  not-accessible
   STATUS      current
   DESCRIPTION
      "The value of the tlsCntTreeGlobalIndex of the MANAGED OBJECT."
   ::= {er1646v2BgriMVAccessControlEntry 10}

er1646v2BgriMVAccessControlInAccessList OBJECT-TYPE
   SYNTAX      DisplayString
   MAX-ACCESS  read-write
   STATUS      current
   DESCRIPTION
      "Path: vpnBridgeGroup.editConf.accessControl.inAccessList"
   ::= {er1646v2BgriMVAccessControlEntry 83886080}

er1646v2BgriMVAccessControlLimBC OBJECT-TYPE
   SYNTAX      INTEGER
               {
               disabled (0),
               enabled (1)
               }
   MAX-ACCESS  read-write
   STATUS      current
   DESCRIPTION
      "Path: vpnBridgeGroup.editConf.accessControl.limitBroadcasts

       Possibilities:
               disabled   (0)
               enabled   (1)"
   ::= {er1646v2BgriMVAccessControlEntry 134217728}


er1646v2BgriMVIp OBJECT IDENTIFIER ::= {er1646v2BgriMV 18}

er1646v2BgriMVIpSSCTable OBJECT-TYPE
   SYNTAX      SEQUENCE OF Er1646v2BgriMVIpEntry
   MAX-ACCESS  not-accessible
   STATUS      current
   DESCRIPTION
      "ip interface config parameters"
   ::= {er1646v2BgriMVIp 1}

er1646v2BgriMVIpEntry OBJECT-TYPE
   SYNTAX      Er1646v2BgriMVIpEntry
   MAX-ACCESS  not-accessible
   STATUS      current
   DESCRIPTION
      ""
   INDEX      { er1646v2BgriMVIpGlobalIx }
   ::= {er1646v2BgriMVIpSSCTable 1}

Er1646v2BgriMVIpEntry ::=
   SEQUENCE
      {
      er1646v2BgriMVIpGlobalIx
         GlobalIndex,
      er1646v2BgriMVIpVrfRouter
         DisplayString,
      er1646v2BgriMVIpAdr
         IpAddress,
      er1646v2BgriMVIpNetm
         IpAddress,
      er1646v2BgriMVIpSNetName
         INTEGER,
      er1646v2BgriMVIpSNetCust
         DisplayString,
      er1646v2BgriMVIpDhcpC
         INTEGER,
      er1646v2BgriMVIpDhcpGatewayPreference
         Integer32,
      er1646v2BgriMVIpDhcpRoutePreference
         Integer32,
      er1646v2BgriMVIpDhcpDnsPreference
         Integer32,
      er1646v2BgriMVIpMtu
         Integer32,
      er1646v2BgriMVIpMssAdjust
         INTEGER,
      er1646v2BgriMVIpRipMetric
         Integer32,
      er1646v2BgriMVIpRipMetricOut
         Integer32,
      er1646v2BgriMVIpRipMode
         INTEGER,
      er1646v2BgriMVIpRipTxVer
         INTEGER,
      er1646v2BgriMVIpRipRxVer
         INTEGER,
      er1646v2BgriMVIpRipSplitH
         INTEGER,
      er1646v2BgriMVIpRipAuth
         INTEGER,
      er1646v2BgriMVIpRipFilter
         DisplayString,
      er1646v2BgriMVIpRipFilterIn
         DisplayString,
      er1646v2BgriMVIpRipClearNextHop
         INTEGER,
      er1646v2BgriMVIpAccPol
         DisplayString,
      er1646v2BgriMVIpAB
         DisplayString,
      er1646v2BgriMVIpMA
         INTEGER,
      er1646v2BgriMVIpMF
         Integer32,
      er1646v2BgriMVIpDB
         INTEGER,
      er1646v2BgriMVIpIR
         INTEGER,
      er1646v2BgriMVIpIgmp
         INTEGER,
      er1646v2BgriMVIpNN
         DisplayString,
      er1646v2BgriMVIpVrrp
         INTEGER,
      er1646v2BgriMVIpPimMode
         INTEGER,
      er1646v2BgriMVIpPimDrPriority
         Counter32,
      er1646v2BgriMVIpPimHelloTime
         TimeTicks,
      er1646v2BgriMVIpPimPropagationDelay
         TimeTicks,
      er1646v2BgriMVIpPimOverrideInterval
         TimeTicks,
      er1646v2BgriMVIpPimBsrBorder
         INTEGER,
      er1646v2BgriMVIpPimTtlThreshold
         Integer32,
      er1646v2BgriMVIpIMNetworkUnreachable
         INTEGER,
      er1646v2BgriMVIpIMHostUnreachable
         INTEGER,
      er1646v2BgriMVIpIMProtocolUnreachable
         INTEGER,
      er1646v2BgriMVIpIMPortUnreachable
         INTEGER,
      er1646v2BgriMVIpIMMtuExceeded
         INTEGER,
      er1646v2BgriMVIpIMAdminProhibited
         INTEGER,
      er1646v2BgriMVIpIMTtlExceeded
         INTEGER,
      er1646v2BgriMVIpIMRedirect
         INTEGER
      }

er1646v2BgriMVIpGlobalIx OBJECT-TYPE
   SYNTAX      GlobalIndex
   MAX-ACCESS  not-accessible
   STATUS      current
   DESCRIPTION
      "The value of the tlsCntTreeGlobalIndex of the MANAGED OBJECT."
   ::= {er1646v2BgriMVIpEntry 10}

er1646v2BgriMVIpVrfRouter OBJECT-TYPE
   SYNTAX      DisplayString
   MAX-ACCESS  read-write
   STATUS      current
   DESCRIPTION
      "Path: vpnBridgeGroup.editConf.ip.vrfRouter"
   ::= {er1646v2BgriMVIpEntry 738197504}

er1646v2BgriMVIpAdr OBJECT-TYPE
   SYNTAX      IpAddress
   MAX-ACCESS  read-write
   STATUS      current
   DESCRIPTION
      "Path: vpnBridgeGroup.editConf.ip.address"
   ::= {er1646v2BgriMVIpEntry 2030043136}

er1646v2BgriMVIpNetm OBJECT-TYPE
   SYNTAX      IpAddress
   MAX-ACCESS  read-write
   STATUS      current
   DESCRIPTION
      "Path: vpnBridgeGroup.editConf.ip.netMask"
   ::= {er1646v2BgriMVIpEntry 2063597568}

er1646v2BgriMVIpSNetName OBJECT-TYPE
   SYNTAX      INTEGER
               {
               slOPTg (0),
               corp (2),
               dmz (3),
               internet (1)
               }
   MAX-ACCESS  read-write
   STATUS      current
   DESCRIPTION
      "Path: vpnBridgeGroup.editConf.ip.sNet.name

       Possibilities:
               <OPT>   (0)
               corp   (2)
               dmz   (3)
               internet   (1)"
   ::= {er1646v2BgriMVIpEntry 855703552}

er1646v2BgriMVIpSNetCust OBJECT-TYPE
   SYNTAX      DisplayString
   MAX-ACCESS  read-write
   STATUS      current
   DESCRIPTION
      "Path: vpnBridgeGroup.editConf.ip.sNet.custom"
   ::= {er1646v2BgriMVIpEntry 855769088}

er1646v2BgriMVIpDhcpC OBJECT-TYPE
   SYNTAX      INTEGER
               {
               disabled (0),
               enabled (1)
               }
   MAX-ACCESS  read-write
   STATUS      current
   DESCRIPTION
      "Path: vpnBridgeGroup.editConf.ip.dhcpClient

       Possibilities:
               disabled   (0)
               enabled   (1)"
   ::= {er1646v2BgriMVIpEntry 838860800}

er1646v2BgriMVIpDhcpGatewayPreference OBJECT-TYPE
   SYNTAX      Integer32
   MAX-ACCESS  read-write
   STATUS      current
   DESCRIPTION
      "Path: vpnBridgeGroup.editConf.ip.dhcp.gatewayPreference"
   ::= {er1646v2BgriMVIpEntry 872480768}

er1646v2BgriMVIpDhcpRoutePreference OBJECT-TYPE
   SYNTAX      Integer32
   MAX-ACCESS  read-write
   STATUS      current
   DESCRIPTION
      "Path: vpnBridgeGroup.editConf.ip.dhcp.routePreference"
   ::= {er1646v2BgriMVIpEntry 872546304}

er1646v2BgriMVIpDhcpDnsPreference OBJECT-TYPE
   SYNTAX      Integer32
   MAX-ACCESS  read-write
   STATUS      current
   DESCRIPTION
      "Path: vpnBridgeGroup.editConf.ip.dhcp.dnsPreference"
   ::= {er1646v2BgriMVIpEntry 872611840}

er1646v2BgriMVIpMtu OBJECT-TYPE
   SYNTAX      Integer32
   MAX-ACCESS  read-write
   STATUS      current
   DESCRIPTION
      "Path: vpnBridgeGroup.editConf.ip.mtu"
   ::= {er1646v2BgriMVIpEntry 671088640}

er1646v2BgriMVIpMssAdjust OBJECT-TYPE
   SYNTAX      INTEGER
               {
               disabled (0),
               auto (65536)
               }
   MAX-ACCESS  read-write
   STATUS      current
   DESCRIPTION
      "Path: vpnBridgeGroup.editConf.ip.mssAdjust

       Possibilities:
               disabled   (0)
               auto   (65536)"
   ::= {er1646v2BgriMVIpEntry 754974720}

er1646v2BgriMVIpRipMetric OBJECT-TYPE
   SYNTAX      Integer32
   MAX-ACCESS  read-write
   STATUS      current
   DESCRIPTION
      "Path: vpnBridgeGroup.editConf.ip.rip.metric"
   ::= {er1646v2BgriMVIpEntry 353566720}

er1646v2BgriMVIpRipMetricOut OBJECT-TYPE
   SYNTAX      Integer32
   MAX-ACCESS  read-write
   STATUS      current
   DESCRIPTION
      "Path: vpnBridgeGroup.editConf.ip.rip.metricOut"
   ::= {er1646v2BgriMVIpEntry 353632256}

er1646v2BgriMVIpRipMode OBJECT-TYPE
   SYNTAX      INTEGER
               {
               disabled (0),
               passive (1),
               active (2)
               }
   MAX-ACCESS  read-write
   STATUS      current
   DESCRIPTION
      "Path: vpnBridgeGroup.editConf.ip.rip.mode

       Possibilities:
               disabled   (0)
               passive   (1)
               active   (2)"
   ::= {er1646v2BgriMVIpEntry 353697792}

er1646v2BgriMVIpRipTxVer OBJECT-TYPE
   SYNTAX      INTEGER
               {
               rip1 (0),
               rip2 (1),
               rip1mcompatible (2)
               }
   MAX-ACCESS  read-write
   STATUS      current
   DESCRIPTION
      "Path: vpnBridgeGroup.editConf.ip.rip.txVersion

       Possibilities:
               rip1   (0)
               rip2   (1)
               rip1-compatible   (2)"
   ::= {er1646v2BgriMVIpEntry 354615296}

er1646v2BgriMVIpRipRxVer OBJECT-TYPE
   SYNTAX      INTEGER
               {
               rip1only (0),
               rip2only (1),
               rip12 (2)
               }
   MAX-ACCESS  read-write
   STATUS      current
   DESCRIPTION
      "Path: vpnBridgeGroup.editConf.ip.rip.rxVersion

       Possibilities:
               rip1only   (0)
               rip2only   (1)
               rip1&2   (2)"
   ::= {er1646v2BgriMVIpEntry 354680832}

er1646v2BgriMVIpRipSplitH OBJECT-TYPE
   SYNTAX      INTEGER
               {
               disabled (0),
               enabled (1),
               poisonedReverse (2)
               }
   MAX-ACCESS  read-write
   STATUS      current
   DESCRIPTION
      "Path: vpnBridgeGroup.editConf.ip.rip.splitHorizon

       Possibilities:
               disabled   (0)
               enabled   (1)
               poisonedReverse   (2)"
   ::= {er1646v2BgriMVIpEntry 353828864}

er1646v2BgriMVIpRipAuth OBJECT-TYPE
   SYNTAX      INTEGER
               {
               disabled (0),
               texts (1),
               md5 (2)
               }
   MAX-ACCESS  read-write
   STATUS      current
   DESCRIPTION
      "Path: vpnBridgeGroup.editConf.ip.rip.authentication

       Possibilities:
               disabled   (0)
               text    (1)
               md5   (2)"
   ::= {er1646v2BgriMVIpEntry 353501184}

er1646v2BgriMVIpRipFilter OBJECT-TYPE
   SYNTAX      DisplayString
   MAX-ACCESS  read-write
   STATUS      current
   DESCRIPTION
      "Path: vpnBridgeGroup.editConf.ip.rip.filter"
   ::= {er1646v2BgriMVIpEntry 354418688}

er1646v2BgriMVIpRipFilterIn OBJECT-TYPE
   SYNTAX      DisplayString
   MAX-ACCESS  read-write
   STATUS      current
   DESCRIPTION
      "Path: vpnBridgeGroup.editConf.ip.rip.filterIn"
   ::= {er1646v2BgriMVIpEntry 354484224}

er1646v2BgriMVIpRipClearNextHop OBJECT-TYPE
   SYNTAX      INTEGER
               {
               disabled (0),
               enabled (1)
               }
   MAX-ACCESS  read-write
   STATUS      current
   DESCRIPTION
      "Path: vpnBridgeGroup.editConf.ip.rip.clearNextHop

       Possibilities:
               disabled   (0)
               enabled   (1)"
   ::= {er1646v2BgriMVIpEntry 352452608}

er1646v2BgriMVIpAccPol OBJECT-TYPE
   SYNTAX      DisplayString
   MAX-ACCESS  read-write
   STATUS      current
   DESCRIPTION
      "Path: vpnBridgeGroup.editConf.ip.accessPolicy"
   ::= {er1646v2BgriMVIpEntry 704643072}

er1646v2BgriMVIpAB OBJECT-TYPE
   SYNTAX      DisplayString
   MAX-ACCESS  read-write
   STATUS      current
   DESCRIPTION
      "Path: vpnBridgeGroup.editConf.ip.trafficPolicy"
   ::= {er1646v2BgriMVIpEntry 234881024}

er1646v2BgriMVIpMA OBJECT-TYPE
   SYNTAX      INTEGER
               {
               disabled (0),
               enabled (1)
               }
   MAX-ACCESS  read-write
   STATUS      current
   DESCRIPTION
      "Path: vpnBridgeGroup.editConf.ip.mgmtAccess

       Possibilities:
               disabled   (0)
               enabled   (1)"
   ::= {er1646v2BgriMVIpEntry 268435456}

er1646v2BgriMVIpMF OBJECT-TYPE
   SYNTAX      Integer32
   MAX-ACCESS  read-write
   STATUS      current
   DESCRIPTION
      "Path: vpnBridgeGroup.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2BgriMVIpEntry 285212672}

er1646v2BgriMVIpDB OBJECT-TYPE
   SYNTAX      INTEGER
               {
               disabled (0),
               enabled (1)
               }
   MAX-ACCESS  read-write
   STATUS      current
   DESCRIPTION
      "Path: vpnBridgeGroup.editConf.ip.directedBroadcasts

       Possibilities:
               disabled   (0)
               enabled   (1)"
   ::= {er1646v2BgriMVIpEntry 369098752}

er1646v2BgriMVIpIR OBJECT-TYPE
   SYNTAX      INTEGER
               {
               disabled (0),
               enabled (1)
               }
   MAX-ACCESS  read-write
   STATUS      current
   DESCRIPTION
      "Path: vpnBridgeGroup.editConf.ip.icmpRedirects

       Possibilities:
               disabled   (0)
               enabled   (1)"
   ::= {er1646v2BgriMVIpEntry 436207616}

er1646v2BgriMVIpIgmp OBJECT-TYPE
   SYNTAX      INTEGER
               {
               disabled (0),
               proxy (1),
               router (2),
               v3Router (5)
               }
   MAX-ACCESS  read-write
   STATUS      current
   DESCRIPTION
      "Path: vpnBridgeGroup.editConf.ip.igmp

       Possibilities:
               disabled   (0)
               proxy   (1)
               router   (2)
               v3Router   (5)"
   ::= {er1646v2BgriMVIpEntry 536870912}

er1646v2BgriMVIpNN OBJECT-TYPE
   SYNTAX      DisplayString
   MAX-ACCESS  read-write
   STATUS      current
   DESCRIPTION
      "Path: vpnBridgeGroup.editConf.ip.nat"
   ::= {er1646v2BgriMVIpEntry 452984832}

er1646v2BgriMVIpVrrp OBJECT-TYPE
   SYNTAX      INTEGER
               {
               disabled (0),
               enabled (1)
               }
   MAX-ACCESS  read-write
   STATUS      current
   DESCRIPTION
      "Path: vpnBridgeGroup.editConf.ip.vrrp

       Possibilities:
               disabled   (0)
               enabled   (1)"
   ::= {er1646v2BgriMVIpEntry 721420288}

er1646v2BgriMVIpPimMode OBJECT-TYPE
   SYNTAX      INTEGER
               {
               disabled (0),
               sparse (1),
               passive (2)
               }
   MAX-ACCESS  read-write
   STATUS      current
   DESCRIPTION
      "Path: vpnBridgeGroup.editConf.ip.pim.mode

       Possibilities:
               disabled   (0)
               sparse   (1)
               passive   (2)"
   ::= {er1646v2BgriMVIpEntry 771817472}

er1646v2BgriMVIpPimDrPriority OBJECT-TYPE
   SYNTAX      Counter32
   MAX-ACCESS  read-write
   STATUS      current
   DESCRIPTION
      "Path: vpnBridgeGroup.editConf.ip.pim.drPriority

       32 bit unsigned wrappable counter."
   ::= {er1646v2BgriMVIpEntry 771883008}

er1646v2BgriMVIpPimHelloTime OBJECT-TYPE
   SYNTAX      TimeTicks
   MAX-ACCESS  read-write
   STATUS      current
   DESCRIPTION
      "Path: vpnBridgeGroup.editConf.ip.pim.helloTime

       Time in centi-second."
   ::= {er1646v2BgriMVIpEntry 771948544}

er1646v2BgriMVIpPimPropagationDelay OBJECT-TYPE
   SYNTAX      TimeTicks
   MAX-ACCESS  read-write
   STATUS      current
   DESCRIPTION
      "Path: vpnBridgeGroup.editConf.ip.pim.propagationDelay

       Time in centi-second."
   ::= {er1646v2BgriMVIpEntry 772014080}

er1646v2BgriMVIpPimOverrideInterval OBJECT-TYPE
   SYNTAX      TimeTicks
   MAX-ACCESS  read-write
   STATUS      current
   DESCRIPTION
      "Path: vpnBridgeGroup.editConf.ip.pim.overrideInterval

       Time in centi-second."
   ::= {er1646v2BgriMVIpEntry 772079616}

er1646v2BgriMVIpPimBsrBorder OBJECT-TYPE
   SYNTAX      INTEGER
               {
               disabled (0),
               enabled (1)
               }
   MAX-ACCESS  read-write
   STATUS      current
   DESCRIPTION
      "Path: vpnBridgeGroup.editConf.ip.pim.bsrBorder

       Possibilities:
               disabled   (0)
               enabled   (1)"
   ::= {er1646v2BgriMVIpEntry 772145152}

er1646v2BgriMVIpPimTtlThreshold OBJECT-TYPE
   SYNTAX      Integer32
   MAX-ACCESS  read-write
   STATUS      current
   DESCRIPTION
      "Path: vpnBridgeGroup.editConf.ip.pim.ttlThreshold"
   ::= {er1646v2BgriMVIpEntry 772210688}

er1646v2BgriMVIpIMNetworkUnreachable OBJECT-TYPE
   SYNTAX      INTEGER
               {
               disabled (0),
               enabled (1)
               }
   MAX-ACCESS  read-write
   STATUS      current
   DESCRIPTION
      "Path: vpnBridgeGroup.editConf.ip.icmpMessages.networkUnreachable

       Possibilities:
               disabled   (0)
               enabled   (1)"
   ::= {er1646v2BgriMVIpEntry 788594688}

er1646v2BgriMVIpIMHostUnreachable OBJECT-TYPE
   SYNTAX      INTEGER
               {
               disabled (0),
               enabled (1)
               }
   MAX-ACCESS  read-write
   STATUS      current
   DESCRIPTION
      "Path: vpnBridgeGroup.editConf.ip.icmpMessages.hostUnreachable

       Possibilities:
               disabled   (0)
               enabled   (1)"
   ::= {er1646v2BgriMVIpEntry 788660224}

er1646v2BgriMVIpIMProtocolUnreachable OBJECT-TYPE
   SYNTAX      INTEGER
               {
               disabled (0),
               enabled (1)
               }
   MAX-ACCESS  read-write
   STATUS      current
   DESCRIPTION
      "Path: vpnBridgeGroup.editConf.ip.icmpMessages.protocolUnreachable

       Possibilities:
               disabled   (0)
               enabled   (1)"
   ::= {er1646v2BgriMVIpEntry 788725760}

er1646v2BgriMVIpIMPortUnreachable OBJECT-TYPE
   SYNTAX      INTEGER
               {
               disabled (0),
               enabled (1)
               }
   MAX-ACCESS  read-write
   STATUS      current
   DESCRIPTION
      "Path: vpnBridgeGroup.editConf.ip.icmpMessages.portUnreachable

       Possibilities:
               disabled   (0)
               enabled   (1)"
   ::= {er1646v2BgriMVIpEntry 788791296}

er1646v2BgriMVIpIMMtuExceeded OBJECT-TYPE
   SYNTAX      INTEGER
               {
               disabled (0),
               enabled (1)
               }
   MAX-ACCESS  read-write
   STATUS      current
   DESCRIPTION
      "Path: vpnBridgeGroup.editConf.ip.icmpMessages.mtuExceeded

       Possibilities:
               disabled   (0)
               enabled   (1)"
   ::= {er1646v2BgriMVIpEntry 788856832}

er1646v2BgriMVIpIMAdminProhibited OBJECT-TYPE
   SYNTAX      INTEGER
               {
               disabled (0),
               enabled (1)
               }
   MAX-ACCESS  read-write
   STATUS      current
   DESCRIPTION
      "Path: vpnBridgeGroup.editConf.ip.icmpMessages.adminProhibited

       Possibilities:
               disabled   (0)
               enabled   (1)"
   ::= {er1646v2BgriMVIpEntry 788922368}

er1646v2BgriMVIpIMTtlExceeded OBJECT-TYPE
   SYNTAX      INTEGER
               {
               disabled (0),
               enabled (1)
               }
   MAX-ACCESS  read-write
   STATUS      current
   DESCRIPTION
      "Path: vpnBridgeGroup.editConf.ip.icmpMessages.ttlExceeded

       Possibilities:
               disabled   (0)
               enabled   (1)"
   ::= {er1646v2BgriMVIpEntry 788987904}

er1646v2BgriMVIpIMRedirect OBJECT-TYPE
   SYNTAX      INTEGER
               {
               disabled (0),
               enabled (1)
               }
   MAX-ACCESS  read-write
   STATUS      current
   DESCRIPTION
      "Path: vpnBridgeGroup.editConf.ip.icmpMessages.redirect

       Possibilities:
               disabled   (0)
               enabled   (1)"
   ::= {er1646v2BgriMVIpEntry 789053440}

er1646v2BgriMVIpSaddr OBJECT-TYPE
   SYNTAX      SEQUENCE OF Er1646v2BgriMVIpSaddrEntry
   MAX-ACCESS  not-accessible
   STATUS      current
   DESCRIPTION
      ""
   ::= {er1646v2BgriMVIp 385875968}

er1646v2BgriMVIpSaddrEntry OBJECT-TYPE
   SYNTAX      Er1646v2BgriMVIpSaddrEntry
   MAX-ACCESS  not-accessible
   STATUS      current
   DESCRIPTION
      ""
   INDEX      { er1646v2BgriMVIpSaddrGlobalIx,
                er1646v2BgriMVIpSaddrTableIx }
   ::= {er1646v2BgriMVIpSaddr 1}

Er1646v2BgriMVIpSaddrEntry ::=
   SEQUENCE
      {
      er1646v2BgriMVIpSaddrActions
         VariableLengthTableActions,
      er1646v2BgriMVIpSaddrGlobalIx
         GlobalIndex,
      er1646v2BgriMVIpSaddrTableIx
         TableIndex,
      er1646v2BgriMVIpSaddrAddress
         IpAddress,
      er1646v2BgriMVIpSaddrNetMask
         IpAddress
      }

er1646v2BgriMVIpSaddrActions OBJECT-TYPE
   SYNTAX      VariableLengthTableActions
   MAX-ACCESS  read-write
   STATUS      current
   DESCRIPTION
      "By way of this field, some manipulations
       on this table may be performed."
   ::= {er1646v2BgriMVIpSaddrEntry 2}

er1646v2BgriMVIpSaddrGlobalIx OBJECT-TYPE
   SYNTAX      GlobalIndex
   MAX-ACCESS  not-accessible
   STATUS      current
   DESCRIPTION
      "The value of the tlsCntTreeGlobalIndex of the MANAGED OBJECT."
   ::= {er1646v2BgriMVIpSaddrEntry 10}

er1646v2BgriMVIpSaddrTableIx OBJECT-TYPE
   SYNTAX      TableIndex
   MAX-ACCESS  not-accessible
   STATUS      current
   DESCRIPTION
      ""
   ::= {er1646v2BgriMVIpSaddrEntry 11}

er1646v2BgriMVIpSaddrAddress OBJECT-TYPE
   SYNTAX      IpAddress
   MAX-ACCESS  read-write
   STATUS      current
   DESCRIPTION
      "Path: vpnBridgeGroup.editConf.ip.secondaryIp.address"
   ::= {er1646v2BgriMVIpSaddrEntry 2030043136}

er1646v2BgriMVIpSaddrNetMask OBJECT-TYPE
   SYNTAX      IpAddress
   MAX-ACCESS  read-write
   STATUS      current
   DESCRIPTION
      "Path: vpnBridgeGroup.editConf.ip.secondaryIp.netMask"
   ::= {er1646v2BgriMVIpSaddrEntry 2063597568}

er1646v2BgriMVIpH OBJECT-TYPE
   SYNTAX      SEQUENCE OF Er1646v2BgriMVIpHEntry
   MAX-ACCESS  not-accessible
   STATUS      current
   DESCRIPTION
      ""
   ::= {er1646v2BgriMVIp 251658240}

er1646v2BgriMVIpHEntry OBJECT-TYPE
   SYNTAX      Er1646v2BgriMVIpHEntry
   MAX-ACCESS  not-accessible
   STATUS      current
   DESCRIPTION
      ""
   INDEX      { er1646v2BgriMVIpHGlobalIx,
                er1646v2BgriMVIpHTableIx }
   ::= {er1646v2BgriMVIpH 1}

Er1646v2BgriMVIpHEntry ::=
   SEQUENCE
      {
      er1646v2BgriMVIpHActions
         VariableLengthTableActions,
      er1646v2BgriMVIpHGlobalIx
         GlobalIndex,
      er1646v2BgriMVIpHTableIx
         TableIndex,
      er1646v2BgriMVIpHAddress
         IpAddress,
      er1646v2BgriMVIpHDhcpRelayOptionSubscriberId
         DisplayString
      }

er1646v2BgriMVIpHActions OBJECT-TYPE
   SYNTAX      VariableLengthTableActions
   MAX-ACCESS  read-write
   STATUS      current
   DESCRIPTION
      "By way of this field, some manipulations
       on this table may be performed."
   ::= {er1646v2BgriMVIpHEntry 2}

er1646v2BgriMVIpHGlobalIx OBJECT-TYPE
   SYNTAX      GlobalIndex
   MAX-ACCESS  not-accessible
   STATUS      current
   DESCRIPTION
      "The value of the tlsCntTreeGlobalIndex of the MANAGED OBJECT."
   ::= {er1646v2BgriMVIpHEntry 10}

er1646v2BgriMVIpHTableIx OBJECT-TYPE
   SYNTAX      TableIndex
   MAX-ACCESS  not-accessible
   STATUS      current
   DESCRIPTION
      ""
   ::= {er1646v2BgriMVIpHEntry 11}

er1646v2BgriMVIpHAddress OBJECT-TYPE
   SYNTAX      IpAddress
   MAX-ACCESS  read-write
   STATUS      current
   DESCRIPTION
      "Path: vpnBridgeGroup.editConf.ip.helpers.address"
   ::= {er1646v2BgriMVIpHEntry 16777216}

er1646v2BgriMVIpHDhcpRelayOptionSubscriberId OBJECT-TYPE
   SYNTAX      DisplayString
   MAX-ACCESS  read-write
   STATUS      current
   DESCRIPTION
      "Path: vpnBridgeGroup.editConf.ip.helpers.dhcpRelayOption.subscriberId"
   ::= {er1646v2BgriMVIpHEntry 33947648}


er1646v2BgriMVVlan OBJECT IDENTIFIER ::= {er1646v2BgriMV 33}

er1646v2BgriMVVlanSSCTable OBJECT-TYPE
   SYNTAX      SEQUENCE OF Er1646v2BgriMVVlanEntry
   MAX-ACCESS  not-accessible
   STATUS      current
   DESCRIPTION
      ""
   ::= {er1646v2BgriMVVlan 1}

er1646v2BgriMVVlanEntry OBJECT-TYPE
   SYNTAX      Er1646v2BgriMVVlanEntry
   MAX-ACCESS  not-accessible
   STATUS      current
   DESCRIPTION
      ""
   INDEX      { er1646v2BgriMVVlanGlobalIx,
                er1646v2BgriMVVlanTableIx }
   ::= {er1646v2BgriMVVlanSSCTable 1}

Er1646v2BgriMVVlanEntry ::=
   SEQUENCE
      {
      er1646v2BgriMVVlanActions
         VariableLengthTableActions,
      er1646v2BgriMVVlanGlobalIx
         GlobalIndex,
      er1646v2BgriMVVlanTableIx
         TableIndex,
      er1646v2BgriMVVlanName
         DisplayString,
      er1646v2BgriMVVlanRemark
         DisplayString,
      er1646v2BgriMVVlanAdminStatus
         INTEGER,
      er1646v2BgriMVVlanMode
         INTEGER,
      er1646v2BgriMVVlanIpVrfRouter
         DisplayString,
      er1646v2BgriMVVlanIpAdr
         IpAddress,
      er1646v2BgriMVVlanIpNetm
         IpAddress,
      er1646v2BgriMVVlanIpSNetName
         INTEGER,
      er1646v2BgriMVVlanIpSNetCust
         DisplayString,
      er1646v2BgriMVVlanIpDhcpC
         INTEGER,
      er1646v2BgriMVVlanIpDhcpGatewayPreference
         Integer32,
      er1646v2BgriMVVlanIpDhcpRoutePreference
         Integer32,
      er1646v2BgriMVVlanIpDhcpDnsPreference
         Integer32,
      er1646v2BgriMVVlanIpMtu
         Integer32,
      er1646v2BgriMVVlanIpMssAdjust
         INTEGER,
      er1646v2BgriMVVlanIpRipMetric
         Integer32,
      er1646v2BgriMVVlanIpRipMetricOut
         Integer32,
      er1646v2BgriMVVlanIpRipMode
         INTEGER,
      er1646v2BgriMVVlanIpRipTxVer
         INTEGER,
      er1646v2BgriMVVlanIpRipRxVer
         INTEGER,
      er1646v2BgriMVVlanIpRipSplitH
         INTEGER,
      er1646v2BgriMVVlanIpRipAuth
         INTEGER,
      er1646v2BgriMVVlanIpRipFilter
         DisplayString,
      er1646v2BgriMVVlanIpRipFilterIn
         DisplayString,
      er1646v2BgriMVVlanIpRipClearNextHop
         INTEGER,
      er1646v2BgriMVVlanIpAccPol
         DisplayString,
      er1646v2BgriMVVlanIpAB
         DisplayString,
      er1646v2BgriMVVlanIpMA
         INTEGER,
      er1646v2BgriMVVlanIpMF
         Integer32,
      er1646v2BgriMVVlanIpDB
         INTEGER,
      er1646v2BgriMVVlanIpIR
         INTEGER,
      er1646v2BgriMVVlanIpIgmp
         INTEGER,
      er1646v2BgriMVVlanIpNN
         DisplayString,
      er1646v2BgriMVVlanIpVrrp
         INTEGER,
      er1646v2BgriMVVlanIpPimMode
         INTEGER,
      er1646v2BgriMVVlanIpPimDrPriority
         Counter32,
      er1646v2BgriMVVlanIpPimHelloTime
         TimeTicks,
      er1646v2BgriMVVlanIpPimPropagationDelay
         TimeTicks,
      er1646v2BgriMVVlanIpPimOverrideInterval
         TimeTicks,
      er1646v2BgriMVVlanIpPimBsrBorder
         INTEGER,
      er1646v2BgriMVVlanIpPimTtlThreshold
         Integer32,
      er1646v2BgriMVVlanIpIMNetworkUnreachable
         INTEGER,
      er1646v2BgriMVVlanIpIMHostUnreachable
         INTEGER,
      er1646v2BgriMVVlanIpIMProtocolUnreachable
         INTEGER,
      er1646v2BgriMVVlanIpIMPortUnreachable
         INTEGER,
      er1646v2BgriMVVlanIpIMMtuExceeded
         INTEGER,
      er1646v2BgriMVVlanIpIMAdminProhibited
         INTEGER,
      er1646v2BgriMVVlanIpIMTtlExceeded
         INTEGER,
      er1646v2BgriMVVlanIpIMRedirect
         INTEGER,
      er1646v2BgriMVVlanIpV6VrfRouter
         DisplayString,
      er1646v2BgriMVVlanIpV6AddrAutoConfigNrDupAddrDetects
         Integer32,
      er1646v2BgriMVVlanIpV6AddrAutoConfigAcceptRa
         INTEGER,
      er1646v2BgriMVVlanIpV6AddrAutoConfigAcceptRaRdnss
         INTEGER,
      er1646v2BgriMVVlanIpV6AddrAutoConfigAcceptRaDnssl
         INTEGER,
      er1646v2BgriMVVlanIpV6DefaultRoute
         INTEGER,
      er1646v2BgriMVVlanIpV6RaSend
         INTEGER,
      er1646v2BgriMVVlanIpV6RaMinInterval
         TimeTicks,
      er1646v2BgriMVVlanIpV6RaMaxInterval
         TimeTicks,
      er1646v2BgriMVVlanIpV6RaManagedFlag
         INTEGER,
      er1646v2BgriMVVlanIpV6RaOtherConfFlag
         INTEGER,
      er1646v2BgriMVVlanIpV6RaLinkMtu
         Integer32,
      er1646v2BgriMVVlanIpV6RaReachableTime
         TimeTicks,
      er1646v2BgriMVVlanIpV6RaRetransmitTime
         TimeTicks,
      er1646v2BgriMVVlanIpV6RaHopLimit
         Integer32,
      er1646v2BgriMVVlanIpV6RaDefaultLifeTime
         TimeTicks,
      er1646v2BgriMVVlanIpV6RaDnsOptionsRdnssLifeTime
         TimeTicks,
      er1646v2BgriMVVlanIpV6RaDnsOptionsRdnssImportServers
         INTEGER,
      er1646v2BgriMVVlanIpV6RaDnsOptionsDnsslLifeTime
         TimeTicks,
      er1646v2BgriMVVlanIpV6RaDnsOptionsDnsslImportDomains
         INTEGER,
      er1646v2BgriMVVlanIpV6RsSend
         INTEGER,
      er1646v2BgriMVVlanIpV6RsMaxRandomDelay
         TimeTicks,
      er1646v2BgriMVVlanIpV6RsInterval
         TimeTicks,
      er1646v2BgriMVVlanIpV6RsMaxSolicitations
         Integer32,
      er1646v2BgriMVVlanIpV6TrafficPolicyInbound
         DisplayString,
      er1646v2BgriMVVlanIpV6TrafficPolicyOutbound
         DisplayString,
      er1646v2BgriMVVlanIpV6FirewallZone
         DisplayString,
      er1646v2BgriMVVlanIpV6DhcpClientAddrAC
         INTEGER,
      er1646v2BgriMVVlanIpV6DhcpClientPrDelMode
         INTEGER,
      er1646v2BgriMVVlanIpV6DhcpClientPrDelPool
         DisplayString,
      er1646v2BgriMVVlanIpV6DhcpClientPrDelPdExclOpt
         INTEGER,
      er1646v2BgriMVVlanIpV6DhcpClientDnsServerPref
         Integer32,
      er1646v2BgriMVVlanIpV6DhcpClientRapidCommit
         INTEGER,
      er1646v2BgriMVVlanIpV6DhcpClientTimersSolTimeOut
         TimeTicks,
      er1646v2BgriMVVlanIpV6DhcpClientTimersSolMaxRt
         TimeTicks,
      er1646v2BgriMVVlanIpV6DhcpClientTimersInfoRefresh
         TimeTicks,
      er1646v2BgriMVVlanIpV6DhcpServerMode
         INTEGER,
      er1646v2BgriMVVlanIpV6DhcpServerPreference
         Integer32,
      er1646v2BgriMVVlanIpV6DhcpServerPool
         DisplayString,
      er1646v2BgriMVVlanIpV6DhcpServerRapidCommit
         INTEGER,
      er1646v2BgriMVVlanIpV6DhcpServerTimersInfoRefresh
         TimeTicks,
      er1646v2BgriMVVlanIpV6DhcpRelayMode
         INTEGER,
      er1646v2BgriMVVlanIpV6SendRedirect
         INTEGER,
      er1646v2BgriMVVlanIpV6LinkMtu
         Integer32,
      er1646v2BgriMVVlanIpV6InterfaceId
         OCTET STRING,
      er1646v2BgriMVVlanIpV6MF
         Integer32,
      er1646v2BgriMVVlanIpV6IcmpMessagesNoRoute
         INTEGER,
      er1646v2BgriMVVlanIpV6IcmpMessagesBeyondScope
         INTEGER,
      er1646v2BgriMVVlanIpV6IcmpMessagesAddressUnreachable
         INTEGER,
      er1646v2BgriMVVlanIpV6IcmpMessagesPortUnreachable
         INTEGER,
      er1646v2BgriMVVlanIpV6IcmpMessagesPacketTooBig
         INTEGER,
      er1646v2BgriMVVlanIpV6IcmpMessagesHopLimitExceeded
         INTEGER,
      er1646v2BgriMVVlanIpV6IcmpMessagesFragTimeExceeded
         INTEGER,
      er1646v2BgriMVVlanIpV6IcmpMessagesHeaderFieldErr
         INTEGER,
      er1646v2BgriMVVlanIpV6IcmpMessagesOptionUnrecognized
         INTEGER,
      er1646v2BgriMVVlanIpV6IcmpMessagesRedirect
         INTEGER,
      er1646v2BgriMVVlanVlanVid
         INTEGER,
      er1646v2BgriMVVlanVlanTpid
         INTEGER,
      er1646v2BgriMVVlanVlanTxCos
         INTEGER,
      er1646v2BgriMVVlanVlanChTos
         INTEGER,
      er1646v2BgriMVVlanVlanCTMapP0
         INTEGER,
      er1646v2BgriMVVlanVlanCTMapP1
         INTEGER,
      er1646v2BgriMVVlanVlanCTMapP2
         INTEGER,
      er1646v2BgriMVVlanVlanCTMapP3
         INTEGER,
      er1646v2BgriMVVlanVlanCTMapP4
         INTEGER,
      er1646v2BgriMVVlanVlanCTMapP5
         INTEGER,
      er1646v2BgriMVVlanVlanCTMapP6
         INTEGER,
      er1646v2BgriMVVlanVlanCTMapP7
         INTEGER,
      er1646v2BgriMVVlanVlanQCMapQueue1
         Integer32,
      er1646v2BgriMVVlanVlanQCMapQueue2
         Integer32,
      er1646v2BgriMVVlanVlanQCMapQueue3
         Integer32,
      er1646v2BgriMVVlanVlanQCMapQueue4
         Integer32,
      er1646v2BgriMVVlanVlanQCMapQueue5
         Integer32,
      er1646v2BgriMVVlanVlanQCMapLowDelayQueue
         Integer32,
      er1646v2BgriMVVlanVlanQCMapLowDelay2Queue
         Integer32,
      er1646v2BgriMVVlanVlanQCMapSystemQueue
         Integer32,
      er1646v2BgriMVVlanVlanArpTimeOut
         TimeTicks,
      er1646v2BgriMVVlanVlanArpProxyArp
         INTEGER
      }

er1646v2BgriMVVlanActions OBJECT-TYPE
   SYNTAX      VariableLengthTableActions
   MAX-ACCESS  read-write
   STATUS      current
   DESCRIPTION
      "By way of this field, some manipulations
       on this table may be performed."
   ::= {er1646v2BgriMVVlanEntry 2}

er1646v2BgriMVVlanGlobalIx OBJECT-TYPE
   SYNTAX      GlobalIndex
   MAX-ACCESS  not-accessible
   STATUS      current
   DESCRIPTION
      "The value of the tlsCntTreeGlobalIndex of the MANAGED OBJECT."
   ::= {er1646v2BgriMVVlanEntry 10}

er1646v2BgriMVVlanTableIx OBJECT-TYPE
   SYNTAX      TableIndex
   MAX-ACCESS  not-accessible
   STATUS      current
   DESCRIPTION
      ""
   ::= {er1646v2BgriMVVlanEntry 11}

er1646v2BgriMVVlanName OBJECT-TYPE
   SYNTAX      DisplayString
   MAX-ACCESS  read-write
   STATUS      current
   DESCRIPTION
      "Path: vpnBridgeGroup.editConf.vlan.name"
   ::= {er1646v2BgriMVVlanEntry 16777216}

er1646v2BgriMVVlanRemark OBJECT-TYPE
   SYNTAX      DisplayString
   MAX-ACCESS  read-write
   STATUS      current
   DESCRIPTION
      "Path: vpnBridgeGroup.editConf.vlan.remark"
   ::= {er1646v2BgriMVVlanEntry 1157627904}

er1646v2BgriMVVlanAdminStatus OBJECT-TYPE
   SYNTAX      INTEGER
               {
               up (1),
               down (2)
               }
   MAX-ACCESS  read-write
   STATUS      current
   DESCRIPTION
      "Path: vpnBridgeGroup.editConf.vlan.adminStatus

       Possibilities:
               up   (1)
               down   (2)"
   ::= {er1646v2BgriMVVlanEntry 33554432}

er1646v2BgriMVVlanMode OBJECT-TYPE
   SYNTAX      INTEGER
               {
               routing (1),
               ipV6 (16),
               ipV6ipV4 (17)
               }
   MAX-ACCESS  read-write
   STATUS      current
   DESCRIPTION
      "Path: vpnBridgeGroup.editConf.vlan.mode

       Possibilities:
               routing   (1)
               ipV6   (16)
               ipV6/ipV4   (17)"
   ::= {er1646v2BgriMVVlanEntry 67108864}

er1646v2BgriMVVlanIpVrfRouter OBJECT-TYPE
   SYNTAX      DisplayString
   MAX-ACCESS  read-write
   STATUS      current
   DESCRIPTION
      "Path: vpnBridgeGroup.editConf.vlan.ip.vrfRouter"
   ::= {er1646v2BgriMVVlanEntry 53215232}

er1646v2BgriMVVlanIpAdr OBJECT-TYPE
   SYNTAX      IpAddress
   MAX-ACCESS  read-write
   STATUS      current
   DESCRIPTION
      "Path: vpnBridgeGroup.editConf.vlan.ip.address"
   ::= {er1646v2BgriMVVlanEntry 58261504}

er1646v2BgriMVVlanIpNetm OBJECT-TYPE
   SYNTAX      IpAddress
   MAX-ACCESS  read-write
   STATUS      current
   DESCRIPTION
      "Path: vpnBridgeGroup.editConf.vlan.ip.netMask"
   ::= {er1646v2BgriMVVlanEntry 58392576}

er1646v2BgriMVVlanIpSNetName OBJECT-TYPE
   SYNTAX      INTEGER
               {
               slOPTg (0),
               corp (2),
               dmz (3),
               internet (1)
               }
   MAX-ACCESS  read-write
   STATUS      current
   DESCRIPTION
      "Path: vpnBridgeGroup.editConf.vlan.ip.sNet.name

       Possibilities:
               <OPT>   (0)
               corp   (2)
               dmz   (3)
               internet   (1)"
   ::= {er1646v2BgriMVVlanEntry 53674240}

er1646v2BgriMVVlanIpSNetCust OBJECT-TYPE
   SYNTAX      DisplayString
   MAX-ACCESS  read-write
   STATUS      current
   DESCRIPTION
      "Path: vpnBridgeGroup.editConf.vlan.ip.sNet.custom"
   ::= {er1646v2BgriMVVlanEntry 53674496}

er1646v2BgriMVVlanIpDhcpC OBJECT-TYPE
   SYNTAX      INTEGER
               {
               disabled (0),
               enabled (1)
               }
   MAX-ACCESS  read-write
   STATUS      current
   DESCRIPTION
      "Path: vpnBridgeGroup.editConf.vlan.ip.dhcpClient

       Possibilities:
               disabled   (0)
               enabled   (1)"
   ::= {er1646v2BgriMVVlanEntry 53608448}

er1646v2BgriMVVlanIpDhcpGatewayPreference OBJECT-TYPE
   SYNTAX      Integer32
   MAX-ACCESS  read-write
   STATUS      current
   DESCRIPTION
      "Path: vpnBridgeGroup.editConf.vlan.ip.dhcp.gatewayPreference"
   ::= {er1646v2BgriMVVlanEntry 53739776}

er1646v2BgriMVVlanIpDhcpRoutePreference OBJECT-TYPE
   SYNTAX      Integer32
   MAX-ACCESS  read-write
   STATUS      current
   DESCRIPTION
      "Path: vpnBridgeGroup.editConf.vlan.ip.dhcp.routePreference"
   ::= {er1646v2BgriMVVlanEntry 53740032}

er1646v2BgriMVVlanIpDhcpDnsPreference OBJECT-TYPE
   SYNTAX      Integer32
   MAX-ACCESS  read-write
   STATUS      current
   DESCRIPTION
      "Path: vpnBridgeGroup.editConf.vlan.ip.dhcp.dnsPreference"
   ::= {er1646v2BgriMVVlanEntry 53740288}

er1646v2BgriMVVlanIpMtu OBJECT-TYPE
   SYNTAX      Integer32
   MAX-ACCESS  read-write
   STATUS      current
   DESCRIPTION
      "Path: vpnBridgeGroup.editConf.vlan.ip.mtu"
   ::= {er1646v2BgriMVVlanEntry 52953088}

er1646v2BgriMVVlanIpMssAdjust OBJECT-TYPE
   SYNTAX      INTEGER
               {
               disabled (0),
               auto (65536)
               }
   MAX-ACCESS  read-write
   STATUS      current
   DESCRIPTION
      "Path: vpnBridgeGroup.editConf.vlan.ip.mssAdjust

       Possibilities:
               disabled   (0)
               auto   (65536)"
   ::= {er1646v2BgriMVVlanEntry 53280768}

er1646v2BgriMVVlanIpRipMetric OBJECT-TYPE
   SYNTAX      Integer32
   MAX-ACCESS  read-write
   STATUS      current
   DESCRIPTION
      "Path: vpnBridgeGroup.editConf.vlan.ip.rip.metric"
   ::= {er1646v2BgriMVVlanEntry 51712768}

er1646v2BgriMVVlanIpRipMetricOut OBJECT-TYPE
   SYNTAX      Integer32
   MAX-ACCESS  read-write
   STATUS      current
   DESCRIPTION
      "Path: vpnBridgeGroup.editConf.vlan.ip.rip.metricOut"
   ::= {er1646v2BgriMVVlanEntry 51713024}

er1646v2BgriMVVlanIpRipMode OBJECT-TYPE
   SYNTAX      INTEGER
               {
               disabled (0),
               passive (1),
               active (2)
               }
   MAX-ACCESS  read-write
   STATUS      current
   DESCRIPTION
      "Path: vpnBridgeGroup.editConf.vlan.ip.rip.mode

       Possibilities:
               disabled   (0)
               passive   (1)
               active   (2)"
   ::= {er1646v2BgriMVVlanEntry 51713280}

er1646v2BgriMVVlanIpRipTxVer OBJECT-TYPE
   SYNTAX      INTEGER
               {
               rip1 (0),
               rip2 (1),
               rip1mcompatible (2)
               }
   MAX-ACCESS  read-write
   STATUS      current
   DESCRIPTION
      "Path: vpnBridgeGroup.editConf.vlan.ip.rip.txVersion

       Possibilities:
               rip1   (0)
               rip2   (1)
               rip1-compatible   (2)"
   ::= {er1646v2BgriMVVlanEntry 51716864}

er1646v2BgriMVVlanIpRipRxVer OBJECT-TYPE
   SYNTAX      INTEGER
               {
               rip1only (0),
               rip2only (1),
               rip12 (2)
               }
   MAX-ACCESS  read-write
   STATUS      current
   DESCRIPTION
      "Path: vpnBridgeGroup.editConf.vlan.ip.rip.rxVersion

       Possibilities:
               rip1only   (0)
               rip2only   (1)
               rip1&2   (2)"
   ::= {er1646v2BgriMVVlanEntry 51717120}

er1646v2BgriMVVlanIpRipSplitH OBJECT-TYPE
   SYNTAX      INTEGER
               {
               disabled (0),
               enabled (1),
               poisonedReverse (2)
               }
   MAX-ACCESS  read-write
   STATUS      current
   DESCRIPTION
      "Path: vpnBridgeGroup.editConf.vlan.ip.rip.splitHorizon

       Possibilities:
               disabled   (0)
               enabled   (1)
               poisonedReverse   (2)"
   ::= {er1646v2BgriMVVlanEntry 51713792}

er1646v2BgriMVVlanIpRipAuth OBJECT-TYPE
   SYNTAX      INTEGER
               {
               disabled (0),
               texts (1),
               md5 (2)
               }
   MAX-ACCESS  read-write
   STATUS      current
   DESCRIPTION
      "Path: vpnBridgeGroup.editConf.vlan.ip.rip.authentication

       Possibilities:
               disabled   (0)
               text    (1)
               md5   (2)"
   ::= {er1646v2BgriMVVlanEntry 51712512}

er1646v2BgriMVVlanIpRipFilter OBJECT-TYPE
   SYNTAX      DisplayString
   MAX-ACCESS  read-write
   STATUS      current
   DESCRIPTION
      "Path: vpnBridgeGroup.editConf.vlan.ip.rip.filter"
   ::= {er1646v2BgriMVVlanEntry 51716096}

er1646v2BgriMVVlanIpRipFilterIn OBJECT-TYPE
   SYNTAX      DisplayString
   MAX-ACCESS  read-write
   STATUS      current
   DESCRIPTION
      "Path: vpnBridgeGroup.editConf.vlan.ip.rip.filterIn"
   ::= {er1646v2BgriMVVlanEntry 51716352}

er1646v2BgriMVVlanIpRipClearNextHop OBJECT-TYPE
   SYNTAX      INTEGER
               {
               disabled (0),
               enabled (1)
               }
   MAX-ACCESS  read-write
   STATUS      current
   DESCRIPTION
      "Path: vpnBridgeGroup.editConf.vlan.ip.rip.clearNextHop

       Possibilities:
               disabled   (0)
               enabled   (1)"
   ::= {er1646v2BgriMVVlanEntry 51708416}

er1646v2BgriMVVlanIpAccPol OBJECT-TYPE
   SYNTAX      DisplayString
   MAX-ACCESS  read-write
   STATUS      current
   DESCRIPTION
      "Path: vpnBridgeGroup.editConf.vlan.ip.accessPolicy"
   ::= {er1646v2BgriMVVlanEntry 53084160}

er1646v2BgriMVVlanIpAB OBJECT-TYPE
   SYNTAX      DisplayString
   MAX-ACCESS  read-write
   STATUS      current
   DESCRIPTION
      "Path: vpnBridgeGroup.editConf.vlan.ip.trafficPolicy"
   ::= {er1646v2BgriMVVlanEntry 51249152}

er1646v2BgriMVVlanIpMA OBJECT-TYPE
   SYNTAX      INTEGER
               {
               disabled (0),
               enabled (1)
               }
   MAX-ACCESS  read-write
   STATUS      current
   DESCRIPTION
      "Path: vpnBridgeGroup.editConf.vlan.ip.mgmtAccess

       Possibilities:
               disabled   (0)
               enabled   (1)"
   ::= {er1646v2BgriMVVlanEntry 51380224}

er1646v2BgriMVVlanIpMF OBJECT-TYPE
   SYNTAX      Integer32
   MAX-ACCESS  read-write
   STATUS      current
   DESCRIPTION
      "Path: vpnBridgeGroup.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2BgriMVVlanEntry 51445760}

er1646v2BgriMVVlanIpDB OBJECT-TYPE
   SYNTAX      INTEGER
               {
               disabled (0),
               enabled (1)
               }
   MAX-ACCESS  read-write
   STATUS      current
   DESCRIPTION
      "Path: vpnBridgeGroup.editConf.vlan.ip.directedBroadcasts

       Possibilities:
               disabled   (0)
               enabled   (1)"
   ::= {er1646v2BgriMVVlanEntry 51773440}

er1646v2BgriMVVlanIpIR OBJECT-TYPE
   SYNTAX      INTEGER
               {
               disabled (0),
               enabled (1)
               }
   MAX-ACCESS  read-write
   STATUS      current
   DESCRIPTION
      "Path: vpnBridgeGroup.editConf.vlan.ip.icmpRedirects

       Possibilities:
               disabled   (0)
               enabled   (1)"
   ::= {er1646v2BgriMVVlanEntry 52035584}

er1646v2BgriMVVlanIpIgmp OBJECT-TYPE
   SYNTAX      INTEGER
               {
               disabled (0),
               proxy (1),
               router (2),
               v3Router (5)
               }
   MAX-ACCESS  read-write
   STATUS      current
   DESCRIPTION
      "Path: vpnBridgeGroup.editConf.vlan.ip.igmp

       Possibilities:
               disabled   (0)
               proxy   (1)
               router   (2)
               v3Router   (5)"
   ::= {er1646v2BgriMVVlanEntry 52428800}

er1646v2BgriMVVlanIpNN OBJECT-TYPE
   SYNTAX      DisplayString
   MAX-ACCESS  read-write
   STATUS      current
   DESCRIPTION
      "Path: vpnBridgeGroup.editConf.vlan.ip.nat"
   ::= {er1646v2BgriMVVlanEntry 52101120}

er1646v2BgriMVVlanIpVrrp OBJECT-TYPE
   SYNTAX      INTEGER
               {
               disabled (0),
               enabled (1)
               }
   MAX-ACCESS  read-write
   STATUS      current
   DESCRIPTION
      "Path: vpnBridgeGroup.editConf.vlan.ip.vrrp

       Possibilities:
               disabled   (0)
               enabled   (1)"
   ::= {er1646v2BgriMVVlanEntry 53149696}

er1646v2BgriMVVlanIpPimMode OBJECT-TYPE
   SYNTAX      INTEGER
               {
               disabled (0),
               sparse (1),
               passive (2)
               }
   MAX-ACCESS  read-write
   STATUS      current
   DESCRIPTION
      "Path: vpnBridgeGroup.editConf.vlan.ip.pim.mode

       Possibilities:
               disabled   (0)
               sparse   (1)
               passive   (2)"
   ::= {er1646v2BgriMVVlanEntry 53346560}

er1646v2BgriMVVlanIpPimDrPriority OBJECT-TYPE
   SYNTAX      Counter32
   MAX-ACCESS  read-write
   STATUS      current
   DESCRIPTION
      "Path: vpnBridgeGroup.editConf.vlan.ip.pim.drPriority

       32 bit unsigned wrappable counter."
   ::= {er1646v2BgriMVVlanEntry 53346816}

er1646v2BgriMVVlanIpPimHelloTime OBJECT-TYPE
   SYNTAX      TimeTicks
   MAX-ACCESS  read-write
   STATUS      current
   DESCRIPTION
      "Path: vpnBridgeGroup.editConf.vlan.ip.pim.helloTime

       Time in centi-second."
   ::= {er1646v2BgriMVVlanEntry 53347072}

er1646v2BgriMVVlanIpPimPropagationDelay OBJECT-TYPE
   SYNTAX      TimeTicks
   MAX-ACCESS  read-write
   STATUS      current
   DESCRIPTION
      "Path: vpnBridgeGroup.editConf.vlan.ip.pim.propagationDelay

       Time in centi-second."
   ::= {er1646v2BgriMVVlanEntry 53347328}

er1646v2BgriMVVlanIpPimOverrideInterval OBJECT-TYPE
   SYNTAX      TimeTicks
   MAX-ACCESS  read-write
   STATUS      current
   DESCRIPTION
      "Path: vpnBridgeGroup.editConf.vlan.ip.pim.overrideInterval

       Time in centi-second."
   ::= {er1646v2BgriMVVlanEntry 53347584}

er1646v2BgriMVVlanIpPimBsrBorder OBJECT-TYPE
   SYNTAX      INTEGER
               {
               disabled (0),
               enabled (1)
               }
   MAX-ACCESS  read-write
   STATUS      current
   DESCRIPTION
      "Path: vpnBridgeGroup.editConf.vlan.ip.pim.bsrBorder

       Possibilities:
               disabled   (0)
               enabled   (1)"
   ::= {er1646v2BgriMVVlanEntry 53347840}

er1646v2BgriMVVlanIpPimTtlThreshold OBJECT-TYPE
   SYNTAX      Integer32
   MAX-ACCESS  read-write
   STATUS      current
   DESCRIPTION
      "Path: vpnBridgeGroup.editConf.vlan.ip.pim.ttlThreshold"
   ::= {er1646v2BgriMVVlanEntry 53348096}

er1646v2BgriMVVlanIpIMNetworkUnreachable OBJECT-TYPE
   SYNTAX      INTEGER
               {
               disabled (0),
               enabled (1)
               }
   MAX-ACCESS  read-write
   STATUS      current
   DESCRIPTION
      "Path: vpnBridgeGroup.editConf.vlan.ip.icmpMessages.networkUnreachable

       Possibilities:
               disabled   (0)
               enabled   (1)"
   ::= {er1646v2BgriMVVlanEntry 53412096}

er1646v2BgriMVVlanIpIMHostUnreachable OBJECT-TYPE
   SYNTAX      INTEGER
               {
               disabled (0),
               enabled (1)
               }
   MAX-ACCESS  read-write
   STATUS      current
   DESCRIPTION
      "Path: vpnBridgeGroup.editConf.vlan.ip.icmpMessages.hostUnreachable

       Possibilities:
               disabled   (0)
               enabled   (1)"
   ::= {er1646v2BgriMVVlanEntry 53412352}

er1646v2BgriMVVlanIpIMProtocolUnreachable OBJECT-TYPE
   SYNTAX      INTEGER
               {
               disabled (0),
               enabled (1)
               }
   MAX-ACCESS  read-write
   STATUS      current
   DESCRIPTION
      "Path: vpnBridgeGroup.editConf.vlan.ip.icmpMessages.protocolUnreachable

       Possibilities:
               disabled   (0)
               enabled   (1)"
   ::= {er1646v2BgriMVVlanEntry 53412608}

er1646v2BgriMVVlanIpIMPortUnreachable OBJECT-TYPE
   SYNTAX      INTEGER
               {
               disabled (0),
               enabled (1)
               }
   MAX-ACCESS  read-write
   STATUS      current
   DESCRIPTION
      "Path: vpnBridgeGroup.editConf.vlan.ip.icmpMessages.portUnreachable

       Possibilities:
               disabled   (0)
               enabled   (1)"
   ::= {er1646v2BgriMVVlanEntry 53412864}

er1646v2BgriMVVlanIpIMMtuExceeded OBJECT-TYPE
   SYNTAX      INTEGER
               {
               disabled (0),
               enabled (1)
               }
   MAX-ACCESS  read-write
   STATUS      current
   DESCRIPTION
      "Path: vpnBridgeGroup.editConf.vlan.ip.icmpMessages.mtuExceeded

       Possibilities:
               disabled   (0)
               enabled   (1)"
   ::= {er1646v2BgriMVVlanEntry 53413120}

er1646v2BgriMVVlanIpIMAdminProhibited OBJECT-TYPE
   SYNTAX      INTEGER
               {
               disabled (0),
               enabled (1)
               }
   MAX-ACCESS  read-write
   STATUS      current
   DESCRIPTION
      "Path: vpnBridgeGroup.editConf.vlan.ip.icmpMessages.adminProhibited

       Possibilities:
               disabled   (0)
               enabled   (1)"
   ::= {er1646v2BgriMVVlanEntry 53413376}

er1646v2BgriMVVlanIpIMTtlExceeded OBJECT-TYPE
   SYNTAX      INTEGER
               {
               disabled (0),
               enabled (1)
               }
   MAX-ACCESS  read-write
   STATUS      current
   DESCRIPTION
      "Path: vpnBridgeGroup.editConf.vlan.ip.icmpMessages.ttlExceeded

       Possibilities:
               disabled   (0)
               enabled   (1)"
   ::= {er1646v2BgriMVVlanEntry 53413632}

er1646v2BgriMVVlanIpIMRedirect OBJECT-TYPE
   SYNTAX      INTEGER
               {
               disabled (0),
               enabled (1)
               }
   MAX-ACCESS  read-write
   STATUS      current
   DESCRIPTION
      "Path: vpnBridgeGroup.editConf.vlan.ip.icmpMessages.redirect

       Possibilities:
               disabled   (0)
               enabled   (1)"
   ::= {er1646v2BgriMVVlanEntry 53413888}

er1646v2BgriMVVlanIpV6VrfRouter OBJECT-TYPE
   SYNTAX      DisplayString
   MAX-ACCESS  read-write
   STATUS      current
   DESCRIPTION
      "Path: vpnBridgeGroup.editConf.vlan.ipV6.vrfRouter"
   ::= {er1646v2BgriMVVlanEntry 704708608}

er1646v2BgriMVVlanIpV6AddrAutoConfigNrDupAddrDetects OBJECT-TYPE
   SYNTAX      Integer32
   MAX-ACCESS  read-write
   STATUS      current
   DESCRIPTION
      "Path: vpnBridgeGroup.editConf.vlan.ipV6.addrAutoConfig.nrDupAddrDetects"
   ::= {er1646v2BgriMVVlanEntry 704905472}

er1646v2BgriMVVlanIpV6AddrAutoConfigAcceptRa OBJECT-TYPE
   SYNTAX      INTEGER
               {
               disabled (0),
               enabled (1)
               }
   MAX-ACCESS  read-write
   STATUS      current
   DESCRIPTION
      "Path: vpnBridgeGroup.editConf.vlan.ipV6.addrAutoConfig.acceptRa

       Possibilities:
               disabled   (0)
               enabled   (1)"
   ::= {er1646v2BgriMVVlanEntry 704905728}

er1646v2BgriMVVlanIpV6AddrAutoConfigAcceptRaRdnss OBJECT-TYPE
   SYNTAX      INTEGER
               {
               disabled (0),
               enabled (1)
               }
   MAX-ACCESS  read-write
   STATUS      current
   DESCRIPTION
      "Path: vpnBridgeGroup.editConf.vlan.ipV6.addrAutoConfig.acceptRaRdnss

       Possibilities:
               disabled   (0)
               enabled   (1)"
   ::= {er1646v2BgriMVVlanEntry 704905984}

er1646v2BgriMVVlanIpV6AddrAutoConfigAcceptRaDnssl OBJECT-TYPE
   SYNTAX      INTEGER
               {
               disabled (0),
               enabled (1)
               }
   MAX-ACCESS  read-write
   STATUS      current
   DESCRIPTION
      "Path: vpnBridgeGroup.editConf.vlan.ipV6.addrAutoConfig.acceptRaDnssl

       Possibilities:
               disabled   (0)
               enabled   (1)"
   ::= {er1646v2BgriMVVlanEntry 704906240}

er1646v2BgriMVVlanIpV6DefaultRoute OBJECT-TYPE
   SYNTAX      INTEGER
               {
               disabled (0),
               enabled (1)
               }
   MAX-ACCESS  read-write
   STATUS      current
   DESCRIPTION
      "Path: vpnBridgeGroup.editConf.vlan.ipV6.defaultRoute

       Possibilities:
               disabled   (0)
               enabled   (1)"
   ::= {er1646v2BgriMVVlanEntry 704970752}

er1646v2BgriMVVlanIpV6RaSend OBJECT-TYPE
   SYNTAX      INTEGER
               {
               disabled (0),
               enabled (1)
               }
   MAX-ACCESS  read-write
   STATUS      current
   DESCRIPTION
      "Path: vpnBridgeGroup.editConf.vlan.ipV6.ra.send

       Possibilities:
               disabled   (0)
               enabled   (1)"
   ::= {er1646v2BgriMVVlanEntry 705036544}

er1646v2BgriMVVlanIpV6RaMinInterval OBJECT-TYPE
   SYNTAX      TimeTicks
   MAX-ACCESS  read-write
   STATUS      current
   DESCRIPTION
      "Path: vpnBridgeGroup.editConf.vlan.ipV6.ra.minInterval

       Time in centi-second."
   ::= {er1646v2BgriMVVlanEntry 705036800}

er1646v2BgriMVVlanIpV6RaMaxInterval OBJECT-TYPE
   SYNTAX      TimeTicks
   MAX-ACCESS  read-write
   STATUS      current
   DESCRIPTION
      "Path: vpnBridgeGroup.editConf.vlan.ipV6.ra.maxInterval

       Time in centi-second."
   ::= {er1646v2BgriMVVlanEntry 705037056}

er1646v2BgriMVVlanIpV6RaManagedFlag OBJECT-TYPE
   SYNTAX      INTEGER
               {
               disabled (0),
               enabled (1)
               }
   MAX-ACCESS  read-write
   STATUS      current
   DESCRIPTION
      "Path: vpnBridgeGroup.editConf.vlan.ipV6.ra.managedFlag

       Possibilities:
               disabled   (0)
               enabled   (1)"
   ::= {er1646v2BgriMVVlanEntry 705037312}

er1646v2BgriMVVlanIpV6RaOtherConfFlag OBJECT-TYPE
   SYNTAX      INTEGER
               {
               disabled (0),
               enabled (1)
               }
   MAX-ACCESS  read-write
   STATUS      current
   DESCRIPTION
      "Path: vpnBridgeGroup.editConf.vlan.ipV6.ra.otherConfFlag

       Possibilities:
               disabled   (0)
               enabled   (1)"
   ::= {er1646v2BgriMVVlanEntry 705037568}

er1646v2BgriMVVlanIpV6RaLinkMtu OBJECT-TYPE
   SYNTAX      Integer32
   MAX-ACCESS  read-write
   STATUS      current
   DESCRIPTION
      "Path: vpnBridgeGroup.editConf.vlan.ipV6.ra.linkMtu"
   ::= {er1646v2BgriMVVlanEntry 705037824}

er1646v2BgriMVVlanIpV6RaReachableTime OBJECT-TYPE
   SYNTAX      TimeTicks
   MAX-ACCESS  read-write
   STATUS      current
   DESCRIPTION
      "Path: vpnBridgeGroup.editConf.vlan.ipV6.ra.reachableTime

       Time in centi-second."
   ::= {er1646v2BgriMVVlanEntry 705038080}

er1646v2BgriMVVlanIpV6RaRetransmitTime OBJECT-TYPE
   SYNTAX      TimeTicks
   MAX-ACCESS  read-write
   STATUS      current
   DESCRIPTION
      "Path: vpnBridgeGroup.editConf.vlan.ipV6.ra.retransmitTime

       Time in centi-second."
   ::= {er1646v2BgriMVVlanEntry 705038336}

er1646v2BgriMVVlanIpV6RaHopLimit OBJECT-TYPE
   SYNTAX      Integer32
   MAX-ACCESS  read-write
   STATUS      current
   DESCRIPTION
      "Path: vpnBridgeGroup.editConf.vlan.ipV6.ra.hopLimit"
   ::= {er1646v2BgriMVVlanEntry 705038592}

er1646v2BgriMVVlanIpV6RaDefaultLifeTime OBJECT-TYPE
   SYNTAX      TimeTicks
   MAX-ACCESS  read-write
   STATUS      current
   DESCRIPTION
      "Path: vpnBridgeGroup.editConf.vlan.ipV6.ra.defaultLifeTime

       Time in centi-second."
   ::= {er1646v2BgriMVVlanEntry 705038848}

er1646v2BgriMVVlanIpV6RaDnsOptionsRdnssLifeTime OBJECT-TYPE
   SYNTAX      TimeTicks
   MAX-ACCESS  read-write
   STATUS      current
   DESCRIPTION
      "Path: vpnBridgeGroup.editConf.vlan.ipV6.ra.dnsOptions.rdnss.lifeTime

       Time in centi-second."
   ::= {er1646v2BgriMVVlanEntry 705039140}

er1646v2BgriMVVlanIpV6RaDnsOptionsRdnssImportServers OBJECT-TYPE
   SYNTAX      INTEGER
               {
               disabled (0),
               enabled (1)
               }
   MAX-ACCESS  read-write
   STATUS      current
   DESCRIPTION
      "Path: vpnBridgeGroup.editConf.vlan.ipV6.ra.dnsOptions.rdnss.importServers

       Possibilities:
               disabled   (0)
               enabled   (1)"
   ::= {er1646v2BgriMVVlanEntry 705039148}

er1646v2BgriMVVlanIpV6RaDnsOptionsDnsslLifeTime OBJECT-TYPE
   SYNTAX      TimeTicks
   MAX-ACCESS  read-write
   STATUS      current
   DESCRIPTION
      "Path: vpnBridgeGroup.editConf.vlan.ipV6.ra.dnsOptions.dnssl.lifeTime

       Time in centi-second."
   ::= {er1646v2BgriMVVlanEntry 705039172}

er1646v2BgriMVVlanIpV6RaDnsOptionsDnsslImportDomains OBJECT-TYPE
   SYNTAX      INTEGER
               {
               disabled (0),
               enabled (1)
               }
   MAX-ACCESS  read-write
   STATUS      current
   DESCRIPTION
      "Path: vpnBridgeGroup.editConf.vlan.ipV6.ra.dnsOptions.dnssl.importDomains

       Possibilities:
               disabled   (0)
               enabled   (1)"
   ::= {er1646v2BgriMVVlanEntry 705039180}

er1646v2BgriMVVlanIpV6RsSend OBJECT-TYPE
   SYNTAX      INTEGER
               {
               disabled (0),
               enabled (1)
               }
   MAX-ACCESS  read-write
   STATUS      current
   DESCRIPTION
      "Path: vpnBridgeGroup.editConf.vlan.ipV6.rs.send

       Possibilities:
               disabled   (0)
               enabled   (1)"
   ::= {er1646v2BgriMVVlanEntry 705954048}

er1646v2BgriMVVlanIpV6RsMaxRandomDelay OBJECT-TYPE
   SYNTAX      TimeTicks
   MAX-ACCESS  read-write
   STATUS      current
   DESCRIPTION
      "Path: vpnBridgeGroup.editConf.vlan.ipV6.rs.maxRandomDelay

       Time in centi-second."
   ::= {er1646v2BgriMVVlanEntry 705954304}

er1646v2BgriMVVlanIpV6RsInterval OBJECT-TYPE
   SYNTAX      TimeTicks
   MAX-ACCESS  read-write
   STATUS      current
   DESCRIPTION
      "Path: vpnBridgeGroup.editConf.vlan.ipV6.rs.interval

       Time in centi-second."
   ::= {er1646v2BgriMVVlanEntry 705954560}

er1646v2BgriMVVlanIpV6RsMaxSolicitations OBJECT-TYPE
   SYNTAX      Integer32
   MAX-ACCESS  read-write
   STATUS      current
   DESCRIPTION
      "Path: vpnBridgeGroup.editConf.vlan.ipV6.rs.maxSolicitations"
   ::= {er1646v2BgriMVVlanEntry 705954816}

er1646v2BgriMVVlanIpV6TrafficPolicyInbound OBJECT-TYPE
   SYNTAX      DisplayString
   MAX-ACCESS  read-write
   STATUS      current
   DESCRIPTION
      "Path: vpnBridgeGroup.editConf.vlan.ipV6.trafficPolicy.inbound"
   ::= {er1646v2BgriMVVlanEntry 705364224}

er1646v2BgriMVVlanIpV6TrafficPolicyOutbound OBJECT-TYPE
   SYNTAX      DisplayString
   MAX-ACCESS  read-write
   STATUS      current
   DESCRIPTION
      "Path: vpnBridgeGroup.editConf.vlan.ipV6.trafficPolicy.outbound"
   ::= {er1646v2BgriMVVlanEntry 705364480}

er1646v2BgriMVVlanIpV6FirewallZone OBJECT-TYPE
   SYNTAX      DisplayString
   MAX-ACCESS  read-write
   STATUS      current
   DESCRIPTION
      "Path: vpnBridgeGroup.editConf.vlan.ipV6.firewall.zone"
   ::= {er1646v2BgriMVVlanEntry 705429760}

er1646v2BgriMVVlanIpV6DhcpClientAddrAC OBJECT-TYPE
   SYNTAX      INTEGER
               {
               disabled (0),
               enabled (1)
               }
   MAX-ACCESS  read-write
   STATUS      current
   DESCRIPTION
      "Path: vpnBridgeGroup.editConf.vlan.ipV6.dhcp.client.addrAutoConfig

       Possibilities:
               disabled   (0)
               enabled   (1)"
   ::= {er1646v2BgriMVVlanEntry 705307648}

er1646v2BgriMVVlanIpV6DhcpClientPrDelMode OBJECT-TYPE
   SYNTAX      INTEGER
               {
               disabled (0),
               enabled (1)
               }
   MAX-ACCESS  read-write
   STATUS      current
   DESCRIPTION
      "Path: vpnBridgeGroup.editConf.vlan.ipV6.dhcp.client.pd.mode

       Possibilities:
               disabled   (0)
               enabled   (1)"
   ::= {er1646v2BgriMVVlanEntry 705308676}

er1646v2BgriMVVlanIpV6DhcpClientPrDelPool OBJECT-TYPE
   SYNTAX      DisplayString
   MAX-ACCESS  read-write
   STATUS      current
   DESCRIPTION
      "Path: vpnBridgeGroup.editConf.vlan.ipV6.dhcp.client.pd.pool"
   ::= {er1646v2BgriMVVlanEntry 705308680}

er1646v2BgriMVVlanIpV6DhcpClientPrDelPdExclOpt OBJECT-TYPE
   SYNTAX      INTEGER
               {
               disabled (0),
               enabled (1)
               }
   MAX-ACCESS  read-write
   STATUS      current
   DESCRIPTION
      "Path: vpnBridgeGroup.editConf.vlan.ipV6.dhcp.client.pd.pdExclOpt

       Possibilities:
               disabled   (0)
               enabled   (1)"
   ::= {er1646v2BgriMVVlanEntry 705308684}

er1646v2BgriMVVlanIpV6DhcpClientDnsServerPref OBJECT-TYPE
   SYNTAX      Integer32
   MAX-ACCESS  read-write
   STATUS      current
   DESCRIPTION
      "Path: vpnBridgeGroup.editConf.vlan.ipV6.dhcp.client.dns.serverPref"
   ::= {er1646v2BgriMVVlanEntry 705310724}

er1646v2BgriMVVlanIpV6DhcpClientRapidCommit OBJECT-TYPE
   SYNTAX      INTEGER
               {
               disabled (0),
               enabled (1)
               }
   MAX-ACCESS  read-write
   STATUS      current
   DESCRIPTION
      "Path: vpnBridgeGroup.editConf.vlan.ipV6.dhcp.client.rapidCommit

       Possibilities:
               disabled   (0)
               enabled   (1)"
   ::= {er1646v2BgriMVVlanEntry 705309696}

er1646v2BgriMVVlanIpV6DhcpClientTimersSolTimeOut OBJECT-TYPE
   SYNTAX      TimeTicks
   MAX-ACCESS  read-write
   STATUS      current
   DESCRIPTION
      "Path: vpnBridgeGroup.editConf.vlan.ipV6.dhcp.client.timers.solTimeOut

       Time in centi-second."
   ::= {er1646v2BgriMVVlanEntry 705311748}

er1646v2BgriMVVlanIpV6DhcpClientTimersSolMaxRt OBJECT-TYPE
   SYNTAX      TimeTicks
   MAX-ACCESS  read-write
   STATUS      current
   DESCRIPTION
      "Path: vpnBridgeGroup.editConf.vlan.ipV6.dhcp.client.timers.solMaxRt

       Time in centi-second."
   ::= {er1646v2BgriMVVlanEntry 705311752}

er1646v2BgriMVVlanIpV6DhcpClientTimersInfoRefresh OBJECT-TYPE
   SYNTAX      TimeTicks
   MAX-ACCESS  read-write
   STATUS      current
   DESCRIPTION
      "Path: vpnBridgeGroup.editConf.vlan.ipV6.dhcp.client.timers.infoRefresh

       Time in centi-second."
   ::= {er1646v2BgriMVVlanEntry 705311756}

er1646v2BgriMVVlanIpV6DhcpServerMode OBJECT-TYPE
   SYNTAX      INTEGER
               {
               disabled (0),
               enabled (1)
               }
   MAX-ACCESS  read-write
   STATUS      current
   DESCRIPTION
      "Path: vpnBridgeGroup.editConf.vlan.ipV6.dhcp.server.mode

       Possibilities:
               disabled   (0)
               enabled   (1)"
   ::= {er1646v2BgriMVVlanEntry 705315840}

er1646v2BgriMVVlanIpV6DhcpServerPreference OBJECT-TYPE
   SYNTAX      Integer32
   MAX-ACCESS  read-write
   STATUS      current
   DESCRIPTION
      "Path: vpnBridgeGroup.editConf.vlan.ipV6.dhcp.server.preference"
   ::= {er1646v2BgriMVVlanEntry 705316864}

er1646v2BgriMVVlanIpV6DhcpServerPool OBJECT-TYPE
   SYNTAX      DisplayString
   MAX-ACCESS  read-write
   STATUS      current
   DESCRIPTION
      "Path: vpnBridgeGroup.editConf.vlan.ipV6.dhcp.server.pool"
   ::= {er1646v2BgriMVVlanEntry 705317888}

er1646v2BgriMVVlanIpV6DhcpServerRapidCommit OBJECT-TYPE
   SYNTAX      INTEGER
               {
               disabled (0),
               enabled (1)
               }
   MAX-ACCESS  read-write
   STATUS      current
   DESCRIPTION
      "Path: vpnBridgeGroup.editConf.vlan.ipV6.dhcp.server.rapidCommit

       Possibilities:
               disabled   (0)
               enabled   (1)"
   ::= {er1646v2BgriMVVlanEntry 705318912}

er1646v2BgriMVVlanIpV6DhcpServerTimersInfoRefresh OBJECT-TYPE
   SYNTAX      TimeTicks
   MAX-ACCESS  read-write
   STATUS      current
   DESCRIPTION
      "Path: vpnBridgeGroup.editConf.vlan.ipV6.dhcp.server.timers.infoRefresh

       Time in centi-second."
   ::= {er1646v2BgriMVVlanEntry 705319940}

er1646v2BgriMVVlanIpV6DhcpRelayMode OBJECT-TYPE
   SYNTAX      INTEGER
               {
               disabled (0),
               enabled (1)
               }
   MAX-ACCESS  read-write
   STATUS      current
   DESCRIPTION
      "Path: vpnBridgeGroup.editConf.vlan.ipV6.dhcp.relay.mode

       Possibilities:
               disabled   (0)
               enabled   (1)"
   ::= {er1646v2BgriMVVlanEntry 705323040}

er1646v2BgriMVVlanIpV6SendRedirect OBJECT-TYPE
   SYNTAX      INTEGER
               {
               disabled (0),
               enabled (1)
               }
   MAX-ACCESS  read-write
   STATUS      current
   DESCRIPTION
      "Path: vpnBridgeGroup.editConf.vlan.ipV6.sendRedirect

       Possibilities:
               disabled   (0)
               enabled   (1)"
   ::= {er1646v2BgriMVVlanEntry 705101824}

er1646v2BgriMVVlanIpV6LinkMtu OBJECT-TYPE
   SYNTAX      Integer32
   MAX-ACCESS  read-write
   STATUS      current
   DESCRIPTION
      "Path: vpnBridgeGroup.editConf.vlan.ipV6.linkMtu"
   ::= {er1646v2BgriMVVlanEntry 705167360}

er1646v2BgriMVVlanIpV6InterfaceId OBJECT-TYPE
   SYNTAX      OCTET STRING
   MAX-ACCESS  read-write
   STATUS      current
   DESCRIPTION
      "Path: vpnBridgeGroup.editConf.vlan.ipV6.interfaceId"
   ::= {er1646v2BgriMVVlanEntry 705232896}

er1646v2BgriMVVlanIpV6MF OBJECT-TYPE
   SYNTAX      Integer32
   MAX-ACCESS  read-write
   STATUS      current
   DESCRIPTION
      "Path: vpnBridgeGroup.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2BgriMVVlanEntry 705757184}

er1646v2BgriMVVlanIpV6IcmpMessagesNoRoute OBJECT-TYPE
   SYNTAX      INTEGER
               {
               disabled (0),
               enabled (1)
               }
   MAX-ACCESS  read-write
   STATUS      current
   DESCRIPTION
      "Path: vpnBridgeGroup.editConf.vlan.ipV6.icmpMessages.noRoute

       Possibilities:
               disabled   (0)
               enabled   (1)"
   ::= {er1646v2BgriMVVlanEntry 705822976}

er1646v2BgriMVVlanIpV6IcmpMessagesBeyondScope OBJECT-TYPE
   SYNTAX      INTEGER
               {
               disabled (0),
               enabled (1)
               }
   MAX-ACCESS  read-write
   STATUS      current
   DESCRIPTION
      "Path: vpnBridgeGroup.editConf.vlan.ipV6.icmpMessages.beyondScope

       Possibilities:
               disabled   (0)
               enabled   (1)"
   ::= {er1646v2BgriMVVlanEntry 705823488}

er1646v2BgriMVVlanIpV6IcmpMessagesAddressUnreachable OBJECT-TYPE
   SYNTAX      INTEGER
               {
               disabled (0),
               enabled (1)
               }
   MAX-ACCESS  read-write
   STATUS      current
   DESCRIPTION
      "Path: vpnBridgeGroup.editConf.vlan.ipV6.icmpMessages.addressUnreachable

       Possibilities:
               disabled   (0)
               enabled   (1)"
   ::= {er1646v2BgriMVVlanEntry 705823744}

er1646v2BgriMVVlanIpV6IcmpMessagesPortUnreachable OBJECT-TYPE
   SYNTAX      INTEGER
               {
               disabled (0),
               enabled (1)
               }
   MAX-ACCESS  read-write
   STATUS      current
   DESCRIPTION
      "Path: vpnBridgeGroup.editConf.vlan.ipV6.icmpMessages.portUnreachable

       Possibilities:
               disabled   (0)
               enabled   (1)"
   ::= {er1646v2BgriMVVlanEntry 705824000}

er1646v2BgriMVVlanIpV6IcmpMessagesPacketTooBig OBJECT-TYPE
   SYNTAX      INTEGER
               {
               disabled (0),
               enabled (1)
               }
   MAX-ACCESS  read-write
   STATUS      current
   DESCRIPTION
      "Path: vpnBridgeGroup.editConf.vlan.ipV6.icmpMessages.packetTooBig

       Possibilities:
               disabled   (0)
               enabled   (1)"
   ::= {er1646v2BgriMVVlanEntry 705825280}

er1646v2BgriMVVlanIpV6IcmpMessagesHopLimitExceeded OBJECT-TYPE
   SYNTAX      INTEGER
               {
               disabled (0),
               enabled (1)
               }
   MAX-ACCESS  read-write
   STATUS      current
   DESCRIPTION
      "Path: vpnBridgeGroup.editConf.vlan.ipV6.icmpMessages.hopLimitExceeded

       Possibilities:
               disabled   (0)
               enabled   (1)"
   ::= {er1646v2BgriMVVlanEntry 705827840}

er1646v2BgriMVVlanIpV6IcmpMessagesFragTimeExceeded OBJECT-TYPE
   SYNTAX      INTEGER
               {
               disabled (0),
               enabled (1)
               }
   MAX-ACCESS  read-write
   STATUS      current
   DESCRIPTION
      "Path: vpnBridgeGroup.editConf.vlan.ipV6.icmpMessages.fragTimeExceeded

       Possibilities:
               disabled   (0)
               enabled   (1)"
   ::= {er1646v2BgriMVVlanEntry 705828096}

er1646v2BgriMVVlanIpV6IcmpMessagesHeaderFieldErr OBJECT-TYPE
   SYNTAX      INTEGER
               {
               disabled (0),
               enabled (1)
               }
   MAX-ACCESS  read-write
   STATUS      current
   DESCRIPTION
      "Path: vpnBridgeGroup.editConf.vlan.ipV6.icmpMessages.headerFieldErr

       Possibilities:
               disabled   (0)
               enabled   (1)"
   ::= {er1646v2BgriMVVlanEntry 705830400}

er1646v2BgriMVVlanIpV6IcmpMessagesOptionUnrecognized OBJECT-TYPE
   SYNTAX      INTEGER
               {
               disabled (0),
               enabled (1)
               }
   MAX-ACCESS  read-write
   STATUS      current
   DESCRIPTION
      "Path: vpnBridgeGroup.editConf.vlan.ipV6.icmpMessages.optionUnrecognized

       Possibilities:
               disabled   (0)
               enabled   (1)"
   ::= {er1646v2BgriMVVlanEntry 705830912}

er1646v2BgriMVVlanIpV6IcmpMessagesRedirect OBJECT-TYPE
   SYNTAX      INTEGER
               {
               disabled (0),
               enabled (1)
               }
   MAX-ACCESS  read-write
   STATUS      current
   DESCRIPTION
      "Path: vpnBridgeGroup.editConf.vlan.ipV6.icmpMessages.redirect

       Possibilities:
               disabled   (0)
               enabled   (1)"
   ::= {er1646v2BgriMVVlanEntry 705832960}

er1646v2BgriMVVlanVlanVid OBJECT-TYPE
   SYNTAX      INTEGER
               {
               prioTagged (4096)
               }
   MAX-ACCESS  read-write
   STATUS      current
   DESCRIPTION
      "Path: vpnBridgeGroup.editConf.vlan.vlan.vid

       Possibilities:
               prioTagged   (4096)"
   ::= {er1646v2BgriMVVlanEntry 234946560}

er1646v2BgriMVVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: vpnBridgeGroup.editConf.vlan.vlan.tpid

       Possibilities:
               dot1Q   (33024)
               dot1ad   (34984)
               0x9100   (37120)
               0x9200   (37376)
               0x9300   (37632)"
   ::= {er1646v2BgriMVVlanEntry 241238016}

er1646v2BgriMVVlanVlanTxCos OBJECT-TYPE
   SYNTAX      INTEGER
               {
               tosCosMap (8),
               queueCosMap (16)
               }
   MAX-ACCESS  read-write
   STATUS      current
   DESCRIPTION
      "Path: vpnBridgeGroup.editConf.vlan.vlan.txCos

       Possibilities:
               tosCosMap   (8)
               queueCosMap   (16)"
   ::= {er1646v2BgriMVVlanEntry 235077632}

er1646v2BgriMVVlanVlanChTos OBJECT-TYPE
   SYNTAX      INTEGER
               {
               disabled (0),
               enabled (1)
               }
   MAX-ACCESS  read-write
   STATUS      current
   DESCRIPTION
      "Path: vpnBridgeGroup.editConf.vlan.vlan.changeTos

       Possibilities:
               disabled   (0)
               enabled   (1)"
   ::= {er1646v2BgriMVVlanEntry 235208704}

er1646v2BgriMVVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235143424}

er1646v2BgriMVVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235143680}

er1646v2BgriMVVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235143936}

er1646v2BgriMVVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235144192}

er1646v2BgriMVVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235144448}

er1646v2BgriMVVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235144704}

er1646v2BgriMVVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235144960}

er1646v2BgriMVVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vpnBridgeGroup.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2BgriMVVlanEntry 235145216}

er1646v2BgriMVVlanVlanQCMapQueue1 OBJECT-TYPE
   SYNTAX      Integer32
   MAX-ACCESS  read-write
   STATUS      current
   DESCRIPTION
      "Path: vpnBridgeGroup.editConf.vlan.vlan.queueCosMap.queue1"
   ::= {er1646v2BgriMVVlanEntry 241434880}

er1646v2BgriMVVlanVlanQCMapQueue2 OBJECT-TYPE
   SYNTAX      Integer32
   MAX-ACCESS  read-write
   STATUS      current
   DESCRIPTION
      "Path: vpnBridgeGroup.editConf.vlan.vlan.queueCosMap.queue2"
   ::= {er1646v2BgriMVVlanEntry 241435136}

er1646v2BgriMVVlanVlanQCMapQueue3 OBJECT-TYPE
   SYNTAX      Integer32
   MAX-ACCESS  read-write
   STATUS      current
   DESCRIPTION
      "Path: vpnBridgeGroup.editConf.vlan.vlan.queueCosMap.queue3"
   ::= {er1646v2BgriMVVlanEntry 241435392}

er1646v2BgriMVVlanVlanQCMapQueue4 OBJECT-TYPE
   SYNTAX      Integer32
   MAX-ACCESS  read-write
   STATUS      current
   DESCRIPTION
      "Path: vpnBridgeGroup.editConf.vlan.vlan.queueCosMap.queue4"
   ::= {er1646v2BgriMVVlanEntry 241435648}

er1646v2BgriMVVlanVlanQCMapQueue5 OBJECT-TYPE
   SYNTAX      Integer32
   MAX-ACCESS  read-write
   STATUS      current
   DESCRIPTION
      "Path: vpnBridgeGroup.editConf.vlan.vlan.queueCosMap.queue5"
   ::= {er1646v2BgriMVVlanEntry 241435904}

er1646v2BgriMVVlanVlanQCMapLowDelayQueue OBJECT-TYPE
   SYNTAX      Integer32
   MAX-ACCESS  read-write
   STATUS      current
   DESCRIPTION
      "Path: vpnBridgeGroup.editConf.vlan.vlan.queueCosMap.lowDelayQueue"
   ::= {er1646v2BgriMVVlanEntry 241436160}

er1646v2BgriMVVlanVlanQCMapLowDelay2Queue OBJECT-TYPE
   SYNTAX      Integer32
   MAX-ACCESS  read-write
   STATUS      current
   DESCRIPTION
      "Path: vpnBridgeGroup.editConf.vlan.vlan.queueCosMap.lowDelay2Queue"
   ::= {er1646v2BgriMVVlanEntry 241436416}

er1646v2BgriMVVlanVlanQCMapSystemQueue OBJECT-TYPE
   SYNTAX      Integer32
   MAX-ACCESS  read-write
   STATUS      current
   DESCRIPTION
      "Path: vpnBridgeGroup.editConf.vlan.vlan.queueCosMap.systemQueue"
   ::= {er1646v2BgriMVVlanEntry 241436672}

er1646v2BgriMVVlanVlanArpTimeOut OBJECT-TYPE
   SYNTAX      TimeTicks
   MAX-ACCESS  read-write
   STATUS      current
   DESCRIPTION
      "Path: vpnBridgeGroup.editConf.vlan.vlan.arp.timeOut

       Time in centi-second."
   ::= {er1646v2BgriMVVlanEntry 235277312}

er1646v2BgriMVVlanVlanArpProxyArp OBJECT-TYPE
   SYNTAX      INTEGER
               {
               disabled (0),
               enabled (1)
               }
   MAX-ACCESS  read-write
   STATUS      current
   DESCRIPTION
      "Path: vpnBridgeGroup.editConf.vlan.vlan.arp.proxyArp

       Possibilities:
               disabled   (0)
               enabled   (1)"
   ::= {er1646v2BgriMVVlanEntry 235287040}

er1646v2BgriMVVlanIpSaddr OBJECT-TYPE
   SYNTAX      SEQUENCE OF Er1646v2BgriMVVlanIpSaddrEntry
   MAX-ACCESS  not-accessible
   STATUS      current
   DESCRIPTION
      ""
   ::= {er1646v2BgriMVVlan 51838976}

er1646v2BgriMVVlanIpSaddrEntry OBJECT-TYPE
   SYNTAX      Er1646v2BgriMVVlanIpSaddrEntry
   MAX-ACCESS  not-accessible
   STATUS      current
   DESCRIPTION
      ""
   INDEX      { er1646v2BgriMVVlanIpSaddrGlobalIx,
                er1646v2BgriMVVlanTableIx,
                er1646v2BgriMVVlanIpSaddrTableIx }
   ::= {er1646v2BgriMVVlanIpSaddr 1}

Er1646v2BgriMVVlanIpSaddrEntry ::=
   SEQUENCE
      {
      er1646v2BgriMVVlanIpSaddrActions
         VariableLengthTableActions,
      er1646v2BgriMVVlanIpSaddrGlobalIx
         GlobalIndex,
      er1646v2BgriMVVlanIpSaddrTableIx
         TableIndex,
      er1646v2BgriMVVlanIpSaddrAddress
         IpAddress,
      er1646v2BgriMVVlanIpSaddrNetMask
         IpAddress
      }

er1646v2BgriMVVlanIpSaddrActions OBJECT-TYPE
   SYNTAX      VariableLengthTableActions
   MAX-ACCESS  read-write
   STATUS      current
   DESCRIPTION
      "By way of this field, some manipulations
       on this table may be performed."
   ::= {er1646v2BgriMVVlanIpSaddrEntry 2}

er1646v2BgriMVVlanIpSaddrGlobalIx OBJECT-TYPE
   SYNTAX      GlobalIndex
   MAX-ACCESS  not-accessible
   STATUS      current
   DESCRIPTION
      "The value of the tlsCntTreeGlobalIndex of the MANAGED OBJECT."
   ::= {er1646v2BgriMVVlanIpSaddrEntry 10}

er1646v2BgriMVVlanIpSaddrTableIx OBJECT-TYPE
   SYNTAX      TableIndex
   MAX-ACCESS  not-accessible
   STATUS      current
   DESCRIPTION
      ""
   ::= {er1646v2BgriMVVlanIpSaddrEntry 11}

er1646v2BgriMVVlanIpSaddrAddress OBJECT-TYPE
   SYNTAX      IpAddress
   MAX-ACCESS  read-write
   STATUS      current
   DESCRIPTION
      "Path: vpnBridgeGroup.editConf.vlan.ip.secondaryIp.address"
   ::= {er1646v2BgriMVVlanIpSaddrEntry 2030043136}

er1646v2BgriMVVlanIpSaddrNetMask OBJECT-TYPE
   SYNTAX      IpAddress
   MAX-ACCESS  read-write
   STATUS      current
   DESCRIPTION
      "Path: vpnBridgeGroup.editConf.vlan.ip.secondaryIp.netMask"
   ::= {er1646v2BgriMVVlanIpSaddrEntry 2063597568}

er1646v2BgriMVVlanIpH OBJECT-TYPE
   SYNTAX      SEQUENCE OF Er1646v2BgriMVVlanIpHEntry
   MAX-ACCESS  not-accessible
   STATUS      current
   DESCRIPTION
      ""
   ::= {er1646v2BgriMVVlan 51314688}

er1646v2BgriMVVlanIpHEntry OBJECT-TYPE
   SYNTAX      Er1646v2BgriMVVlanIpHEntry
   MAX-ACCESS  not-accessible
   STATUS      current
   DESCRIPTION
      ""
   INDEX      { er1646v2BgriMVVlanIpHGlobalIx,
                er1646v2BgriMVVlanTableIx,
                er1646v2BgriMVVlanIpHTableIx }
   ::= {er1646v2BgriMVVlanIpH 1}

Er1646v2BgriMVVlanIpHEntry ::=
   SEQUENCE
      {
      er1646v2BgriMVVlanIpHActions
         VariableLengthTableActions,
      er1646v2BgriMVVlanIpHGlobalIx
         GlobalIndex,
      er1646v2BgriMVVlanIpHTableIx
         TableIndex,
      er1646v2BgriMVVlanIpHAddress
         IpAddress,
      er1646v2BgriMVVlanIpHDhcpRelayOptionSubscriberId
         DisplayString
      }

er1646v2BgriMVVlanIpHActions OBJECT-TYPE
   SYNTAX      VariableLengthTableActions
   MAX-ACCESS  read-write
   STATUS      current
   DESCRIPTION
      "By way of this field, some manipulations
       on this table may be performed."
   ::= {er1646v2BgriMVVlanIpHEntry 2}

er1646v2BgriMVVlanIpHGlobalIx OBJECT-TYPE
   SYNTAX      GlobalIndex
   MAX-ACCESS  not-accessible
   STATUS      current
   DESCRIPTION
      "The value of the tlsCntTreeGlobalIndex of the MANAGED OBJECT."
   ::= {er1646v2BgriMVVlanIpHEntry 10}

er1646v2BgriMVVlanIpHTableIx OBJECT-TYPE
   SYNTAX      TableIndex
   MAX-ACCESS  not-accessible
   STATUS      current
   DESCRIPTION
      ""
   ::= {er1646v2BgriMVVlanIpHEntry 11}

er1646v2BgriMVVlanIpHAddress OBJECT-TYPE
   SYNTAX      IpAddress
   MAX-ACCESS  read-write
   STATUS      current
   DESCRIPTION
      "Path: vpnBridgeGroup.editConf.vlan.ip.helpers.address"
   ::= {er1646v2BgriMVVlanIpHEntry 16777216}

er1646v2BgriMVVlanIpHDhcpRelayOptionSubscriberId OBJECT-TYPE
   SYNTAX      DisplayString
   MAX-ACCESS  read-write
   STATUS      current
   DESCRIPTION
      "Path: vpnBridgeGroup.editConf.vlan.ip.helpers.dhcpRelayOption.subscriberId"
   ::= {er1646v2BgriMVVlanIpHEntry 33947648}

er1646v2BgriMVVlanIpV6Addresses OBJECT-TYPE
   SYNTAX      SEQUENCE OF Er1646v2BgriMVVlanIpV6AddressesEntry
   MAX-ACCESS  not-accessible
   STATUS      current
   DESCRIPTION
      ""
   ::= {er1646v2BgriMVVlan 704839680}

er1646v2BgriMVVlanIpV6AddressesEntry OBJECT-TYPE
   SYNTAX      Er1646v2BgriMVVlanIpV6AddressesEntry
   MAX-ACCESS  not-accessible
   STATUS      current
   DESCRIPTION
      ""
   INDEX      { er1646v2BgriMVVlanIpV6AddressesGlobalIx,
                er1646v2BgriMVVlanTableIx,
                er1646v2BgriMVVlanIpV6AddressesTableIx }
   ::= {er1646v2BgriMVVlanIpV6Addresses 1}

Er1646v2BgriMVVlanIpV6AddressesEntry ::=
   SEQUENCE
      {
      er1646v2BgriMVVlanIpV6AddressesActions
         VariableLengthTableActions,
      er1646v2BgriMVVlanIpV6AddressesGlobalIx
         GlobalIndex,
      er1646v2BgriMVVlanIpV6AddressesTableIx
         TableIndex,
      er1646v2BgriMVVlanIpV6AddressesType
         INTEGER,
      er1646v2BgriMVVlanIpV6AddressesAddress
         Ipv6Address,
      er1646v2BgriMVVlanIpV6AddressesPrefixLength
         Integer32,
      er1646v2BgriMVVlanIpV6AddressesGeneralPrefix
         DisplayString,
      er1646v2BgriMVVlanIpV6AddressesRaSend
         INTEGER,
      er1646v2BgriMVVlanIpV6AddressesRaOnLinkFlag
         INTEGER,
      er1646v2BgriMVVlanIpV6AddressesRaAutoFlag
         INTEGER,
      er1646v2BgriMVVlanIpV6AddressesRaValidLifeTime
         TimeTicks,
      er1646v2BgriMVVlanIpV6AddressesRaValidLTMode
         INTEGER,
      er1646v2BgriMVVlanIpV6AddressesRaPrefLifeTime
         TimeTicks,
      er1646v2BgriMVVlanIpV6AddressesRaPrefLTMode
         INTEGER
      }

er1646v2BgriMVVlanIpV6AddressesActions OBJECT-TYPE
   SYNTAX      VariableLengthTableActions
   MAX-ACCESS  read-write
   STATUS      current
   DESCRIPTION
      "By way of this field, some manipulations
       on this table may be performed."
   ::= {er1646v2BgriMVVlanIpV6AddressesEntry 2}

er1646v2BgriMVVlanIpV6AddressesGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6AddressesEntry 10}

er1646v2BgriMVVlanIpV6AddressesTableIx OBJECT-TYPE
   SYNTAX      TableIndex
   MAX-ACCESS  not-accessible
   STATUS      current
   DESCRIPTION
      ""
   ::= {er1646v2BgriMVVlanIpV6AddressesEntry 11}

er1646v2BgriMVVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vpnBridgeGroup.editConf.vlan.ipV6.addresses.type

       Possibilities:
               unicast   (0)
               eui64   (1)
               anycast   (2)
               linkLocal   (3)
               generalPrefix   (4)"
   ::= {er1646v2BgriMVVlanIpV6AddressesEntry 50331648}

er1646v2BgriMVVlanIpV6AddressesAddress OBJECT-TYPE
   SYNTAX      Ipv6Address
   MAX-ACCESS  read-write
   STATUS      current
   DESCRIPTION
      "Path: vpnBridgeGroup.editConf.vlan.ipV6.addresses.address

       ipv6 address"
   ::= {er1646v2BgriMVVlanIpV6AddressesEntry 16777216}

er1646v2BgriMVVlanIpV6AddressesPrefixLength OBJECT-TYPE
   SYNTAX      Integer32
   MAX-ACCESS  read-write
   STATUS      current
   DESCRIPTION
      "Path: vpnBridgeGroup.editConf.vlan.ipV6.addresses.prefixLength"
   ::= {er1646v2BgriMVVlanIpV6AddressesEntry 33554432}

er1646v2BgriMVVlanIpV6AddressesGeneralPrefix OBJECT-TYPE
   SYNTAX      DisplayString
   MAX-ACCESS  read-write
   STATUS      current
   DESCRIPTION
      "Path: vpnBridgeGroup.editConf.vlan.ipV6.addresses.generalPrefix"
   ::= {er1646v2BgriMVVlanIpV6AddressesEntry 83886080}

er1646v2BgriMVVlanIpV6AddressesRaSend OBJECT-TYPE
   SYNTAX      INTEGER
               {
               disabled (0),
               enabled (1)
               }
   MAX-ACCESS  read-write
   STATUS      current
   DESCRIPTION
      "Path: vpnBridgeGroup.editConf.vlan.ipV6.addresses.ra.send

       Possibilities:
               disabled   (0)
               enabled   (1)"
   ::= {er1646v2BgriMVVlanIpV6AddressesEntry 67174400}

er1646v2BgriMVVlanIpV6AddressesRaOnLinkFlag OBJECT-TYPE
   SYNTAX      INTEGER
               {
               disabled (0),
               enabled (1)
               }
   MAX-ACCESS  read-write
   STATUS      current
   DESCRIPTION
      "Path: vpnBridgeGroup.editConf.vlan.ipV6.addresses.ra.onLinkFlag

       Possibilities:
               disabled   (0)
               enabled   (1)"
   ::= {er1646v2BgriMVVlanIpV6AddressesEntry 67371008}

er1646v2BgriMVVlanIpV6AddressesRaAutoFlag OBJECT-TYPE
   SYNTAX      INTEGER
               {
               disabled (0),
               enabled (1)
               }
   MAX-ACCESS  read-write
   STATUS      current
   DESCRIPTION
      "Path: vpnBridgeGroup.editConf.vlan.ipV6.addresses.ra.autonomousFlag

       Possibilities:
               disabled   (0)
               enabled   (1)"
   ::= {er1646v2BgriMVVlanIpV6AddressesEntry 67567616}

er1646v2BgriMVVlanIpV6AddressesRaValidLifeTime OBJECT-TYPE
   SYNTAX      TimeTicks
   MAX-ACCESS  read-write
   STATUS      current
   DESCRIPTION
      "Path: vpnBridgeGroup.editConf.vlan.ipV6.addresses.ra.validLifeTime

       Time in centi-second."
   ::= {er1646v2BgriMVVlanIpV6AddressesEntry 67239936}

er1646v2BgriMVVlanIpV6AddressesRaValidLTMode OBJECT-TYPE
   SYNTAX      INTEGER
               {
               fixed (0),
               infinite (2)
               }
   MAX-ACCESS  read-write
   STATUS      current
   DESCRIPTION
      "Path: vpnBridgeGroup.editConf.vlan.ipV6.addresses.ra.validLifeTimeMode

       Possibilities:
               fixed   (0)
               infinite   (2)"
   ::= {er1646v2BgriMVVlanIpV6AddressesEntry 67305472}

er1646v2BgriMVVlanIpV6AddressesRaPrefLifeTime OBJECT-TYPE
   SYNTAX      TimeTicks
   MAX-ACCESS  read-write
   STATUS      current
   DESCRIPTION
      "Path: vpnBridgeGroup.editConf.vlan.ipV6.addresses.ra.prefLifeTime

       Time in centi-second."
   ::= {er1646v2BgriMVVlanIpV6AddressesEntry 67436544}

er1646v2BgriMVVlanIpV6AddressesRaPrefLTMode OBJECT-TYPE
   SYNTAX      INTEGER
               {
               fixed (0),
               infinite (2)
               }
   MAX-ACCESS  read-write
   STATUS      current
   DESCRIPTION
      "Path: vpnBridgeGroup.editConf.vlan.ipV6.addresses.ra.prefLifeTimeMode

       Possibilities:
               fixed   (0)
               infinite   (2)"
   ::= {er1646v2BgriMVVlanIpV6AddressesEntry 67502080}

er1646v2BgriMVVlanIpV6RaDnsOptionsRdnssServers OBJECT-TYPE
   SYNTAX      SEQUENCE OF Er1646v2BgriMVVlanIpV6RaDnsOptionsRdnssServersEntry
   MAX-ACCESS  not-accessible
   STATUS      current
   DESCRIPTION
      ""
   ::= {er1646v2BgriMVVlan 705039144}

er1646v2BgriMVVlanIpV6RaDnsOptionsRdnssServersEntry OBJECT-TYPE
   SYNTAX      Er1646v2BgriMVVlanIpV6RaDnsOptionsRdnssServersEntry
   MAX-ACCESS  not-accessible
   STATUS      current
   DESCRIPTION
      ""
   INDEX      { er1646v2BgriMVVlanIpV6RaDnsOptionsRdnssServersGlobalIx,
                er1646v2BgriMVVlanTableIx,
                er1646v2BgriMVVlanIpV6RaDnsOptionsRdnssServersTableIx }
   ::= {er1646v2BgriMVVlanIpV6RaDnsOptionsRdnssServers 1}

Er1646v2BgriMVVlanIpV6RaDnsOptionsRdnssServersEntry ::=
   SEQUENCE
      {
      er1646v2BgriMVVlanIpV6RaDnsOptionsRdnssServersActions
         VariableLengthTableActions,
      er1646v2BgriMVVlanIpV6RaDnsOptionsRdnssServersGlobalIx
         GlobalIndex,
      er1646v2BgriMVVlanIpV6RaDnsOptionsRdnssServersTableIx
         TableIndex,
      er1646v2BgriMVVlanIpV6RaDnsOptionsRdnssServersAddress
         Ipv6Address
      }

er1646v2BgriMVVlanIpV6RaDnsOptionsRdnssServersActions OBJECT-TYPE
   SYNTAX      VariableLengthTableActions
   MAX-ACCESS  read-write
   STATUS      current
   DESCRIPTION
      "By way of this field, some manipulations
       on this table may be performed."
   ::= {er1646v2BgriMVVlanIpV6RaDnsOptionsRdnssServersEntry 2}

er1646v2BgriMVVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6RaDnsOptionsRdnssServersEntry 10}

er1646v2BgriMVVlanIpV6RaDnsOptionsRdnssServersTableIx OBJECT-TYPE
   SYNTAX      TableIndex
   MAX-ACCESS  not-accessible
   STATUS      current
   DESCRIPTION
      ""
   ::= {er1646v2BgriMVVlanIpV6RaDnsOptionsRdnssServersEntry 11}

er1646v2BgriMVVlanIpV6RaDnsOptionsRdnssServersAddress OBJECT-TYPE
   SYNTAX      Ipv6Address
   MAX-ACCESS  read-write
   STATUS      current
   DESCRIPTION
      "Path: vpnBridgeGroup.editConf.vlan.ipV6.ra.dnsOptions.rdnss.servers.address

       ipv6 address"
   ::= {er1646v2BgriMVVlanIpV6RaDnsOptionsRdnssServersEntry 16777216}

er1646v2BgriMVVlanIpV6RaDnsOptionsDnsslDomains OBJECT-TYPE
   SYNTAX      SEQUENCE OF Er1646v2BgriMVVlanIpV6RaDnsOptionsDnsslDomainsEntry
   MAX-ACCESS  not-accessible
   STATUS      current
   DESCRIPTION
      ""
   ::= {er1646v2BgriMVVlan 705039176}

er1646v2BgriMVVlanIpV6RaDnsOptionsDnsslDomainsEntry OBJECT-TYPE
   SYNTAX      Er1646v2BgriMVVlanIpV6RaDnsOptionsDnsslDomainsEntry
   MAX-ACCESS  not-accessible
   STATUS      current
   DESCRIPTION
      ""
   INDEX      { er1646v2BgriMVVlanIpV6RaDnsOptionsDnsslDomainsGlobalIx,
                er1646v2BgriMVVlanTableIx,
                er1646v2BgriMVVlanIpV6RaDnsOptionsDnsslDomainsTableIx }
   ::= {er1646v2BgriMVVlanIpV6RaDnsOptionsDnsslDomains 1}

Er1646v2BgriMVVlanIpV6RaDnsOptionsDnsslDomainsEntry ::=
   SEQUENCE
      {
      er1646v2BgriMVVlanIpV6RaDnsOptionsDnsslDomainsActions
         VariableLengthTableActions,
      er1646v2BgriMVVlanIpV6RaDnsOptionsDnsslDomainsGlobalIx
         GlobalIndex,
      er1646v2BgriMVVlanIpV6RaDnsOptionsDnsslDomainsTableIx
         TableIndex,
      er1646v2BgriMVVlanIpV6RaDnsOptionsDnsslDomainsName
         DisplayString
      }

er1646v2BgriMVVlanIpV6RaDnsOptionsDnsslDomainsActions OBJECT-TYPE
   SYNTAX      VariableLengthTableActions
   MAX-ACCESS  read-write
   STATUS      current
   DESCRIPTION
      "By way of this field, some manipulations
       on this table may be performed."
   ::= {er1646v2BgriMVVlanIpV6RaDnsOptionsDnsslDomainsEntry 2}

er1646v2BgriMVVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6RaDnsOptionsDnsslDomainsEntry 10}

er1646v2BgriMVVlanIpV6RaDnsOptionsDnsslDomainsTableIx OBJECT-TYPE
   SYNTAX      TableIndex
   MAX-ACCESS  not-accessible
   STATUS      current
   DESCRIPTION
      ""
   ::= {er1646v2BgriMVVlanIpV6RaDnsOptionsDnsslDomainsEntry 11}

er1646v2BgriMVVlanIpV6RaDnsOptionsDnsslDomainsName OBJECT-TYPE
   SYNTAX      DisplayString
   MAX-ACCESS  read-write
   STATUS      current
   DESCRIPTION
      "Path: vpnBridgeGroup.editConf.vlan.ipV6.ra.dnsOptions.dnssl.domains.name"
   ::= {er1646v2BgriMVVlanIpV6RaDnsOptionsDnsslDomainsEntry 16777216}

er1646v2BgriMVVlanIpV6DhcpClientUserClassOpt OBJECT-TYPE
   SYNTAX      SEQUENCE OF Er1646v2BgriMVVlanIpV6DhcpClientUserClassOptEntry
   MAX-ACCESS  not-accessible
   STATUS      current
   DESCRIPTION
      ""
   ::= {er1646v2BgriMVVlan 705312768}

er1646v2BgriMVVlanIpV6DhcpClientUserClassOptEntry OBJECT-TYPE
   SYNTAX      Er1646v2BgriMVVlanIpV6DhcpClientUserClassOptEntry
   MAX-ACCESS  not-accessible
   STATUS      current
   DESCRIPTION
      ""
   INDEX      { er1646v2BgriMVVlanIpV6DhcpClientUserClassOptGlobalIx,
                er1646v2BgriMVVlanTableIx,
                er1646v2BgriMVVlanIpV6DhcpClientUserClassOptTableIx }
   ::= {er1646v2BgriMVVlanIpV6DhcpClientUserClassOpt 1}

Er1646v2BgriMVVlanIpV6DhcpClientUserClassOptEntry ::=
   SEQUENCE
      {
      er1646v2BgriMVVlanIpV6DhcpClientUserClassOptActions
         VariableLengthTableActions,
      er1646v2BgriMVVlanIpV6DhcpClientUserClassOptGlobalIx
         GlobalIndex,
      er1646v2BgriMVVlanIpV6DhcpClientUserClassOptTableIx
         TableIndex,
      er1646v2BgriMVVlanIpV6DhcpClientUserClassOptValueAscii
         DisplayString,
      er1646v2BgriMVVlanIpV6DhcpClientUserClassOptValueDecimal
         Integer32,
      er1646v2BgriMVVlanIpV6DhcpClientUserClassOptValueHexData
         OCTET STRING
      }

er1646v2BgriMVVlanIpV6DhcpClientUserClassOptActions OBJECT-TYPE
   SYNTAX      VariableLengthTableActions
   MAX-ACCESS  read-write
   STATUS      current
   DESCRIPTION
      "By way of this field, some manipulations
       on this table may be performed."
   ::= {er1646v2BgriMVVlanIpV6DhcpClientUserClassOptEntry 2}

er1646v2BgriMVVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6DhcpClientUserClassOptEntry 10}

er1646v2BgriMVVlanIpV6DhcpClientUserClassOptTableIx OBJECT-TYPE
   SYNTAX      TableIndex
   MAX-ACCESS  not-accessible
   STATUS      current
   DESCRIPTION
      ""
   ::= {er1646v2BgriMVVlanIpV6DhcpClientUserClassOptEntry 11}

er1646v2BgriMVVlanIpV6DhcpClientUserClassOptValueAscii OBJECT-TYPE
   SYNTAX      DisplayString
   MAX-ACCESS  read-write
   STATUS      current
   DESCRIPTION
      "Path: vpnBridgeGroup.editConf.vlan.ipV6.dhcp.client.userClassOpt.value.ascii"
   ::= {er1646v2BgriMVVlanIpV6DhcpClientUserClassOptEntry 16842752}

er1646v2BgriMVVlanIpV6DhcpClientUserClassOptValueDecimal OBJECT-TYPE
   SYNTAX      Integer32
   MAX-ACCESS  read-write
   STATUS      current
   DESCRIPTION
      "Path: vpnBridgeGroup.editConf.vlan.ipV6.dhcp.client.userClassOpt.value.decimal"
   ::= {er1646v2BgriMVVlanIpV6DhcpClientUserClassOptEntry 16908288}

er1646v2BgriMVVlanIpV6DhcpClientUserClassOptValueHexData OBJECT-TYPE
   SYNTAX      OCTET STRING
   MAX-ACCESS  read-write
   STATUS      current
   DESCRIPTION
      "Path: vpnBridgeGroup.editConf.vlan.ipV6.dhcp.client.userClassOpt.value.hexData"
   ::= {er1646v2BgriMVVlanIpV6DhcpClientUserClassOptEntry 16973824}

er1646v2BgriMVVlanIpV6DhcpClientVendorCl OBJECT-TYPE
   SYNTAX      SEQUENCE OF Er1646v2BgriMVVlanIpV6DhcpClientVendorClEntry
   MAX-ACCESS  not-accessible
   STATUS      current
   DESCRIPTION
      ""
   ::= {er1646v2BgriMVVlan 705313792}

er1646v2BgriMVVlanIpV6DhcpClientVendorClEntry OBJECT-TYPE
   SYNTAX      Er1646v2BgriMVVlanIpV6DhcpClientVendorClEntry
   MAX-ACCESS  not-accessible
   STATUS      current
   DESCRIPTION
      ""
   INDEX      { er1646v2BgriMVVlanIpV6DhcpClientVendorClGlobalIx,
                er1646v2BgriMVVlanTableIx,
                er1646v2BgriMVVlanIpV6DhcpClientVendorClTableIx }
   ::= {er1646v2BgriMVVlanIpV6DhcpClientVendorCl 1}

Er1646v2BgriMVVlanIpV6DhcpClientVendorClEntry ::=
   SEQUENCE
      {
      er1646v2BgriMVVlanIpV6DhcpClientVendorClActions
         VariableLengthTableActions,
      er1646v2BgriMVVlanIpV6DhcpClientVendorClGlobalIx
         GlobalIndex,
      er1646v2BgriMVVlanIpV6DhcpClientVendorClTableIx
         TableIndex,
      er1646v2BgriMVVlanIpV6DhcpClientVendorClValueAscii
         DisplayString,
      er1646v2BgriMVVlanIpV6DhcpClientVendorClValueDecimal
         Integer32,
      er1646v2BgriMVVlanIpV6DhcpClientVendorClValueHexData
         OCTET STRING
      }

er1646v2BgriMVVlanIpV6DhcpClientVendorClActions OBJECT-TYPE
   SYNTAX      VariableLengthTableActions
   MAX-ACCESS  read-write
   STATUS      current
   DESCRIPTION
      "By way of this field, some manipulations
       on this table may be performed."
   ::= {er1646v2BgriMVVlanIpV6DhcpClientVendorClEntry 2}

er1646v2BgriMVVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6DhcpClientVendorClEntry 10}

er1646v2BgriMVVlanIpV6DhcpClientVendorClTableIx OBJECT-TYPE
   SYNTAX      TableIndex
   MAX-ACCESS  not-accessible
   STATUS      current
   DESCRIPTION
      ""
   ::= {er1646v2BgriMVVlanIpV6DhcpClientVendorClEntry 11}

er1646v2BgriMVVlanIpV6DhcpClientVendorClValueAscii OBJECT-TYPE
   SYNTAX      DisplayString
   MAX-ACCESS  read-write
   STATUS      current
   DESCRIPTION
      "Path: vpnBridgeGroup.editConf.vlan.ipV6.dhcp.client.vendorClassOpt.value.ascii"
   ::= {er1646v2BgriMVVlanIpV6DhcpClientVendorClEntry 16842752}

er1646v2BgriMVVlanIpV6DhcpClientVendorClValueDecimal OBJECT-TYPE
   SYNTAX      Integer32
   MAX-ACCESS  read-write
   STATUS      current
   DESCRIPTION
      "Path: vpnBridgeGroup.editConf.vlan.ipV6.dhcp.client.vendorClassOpt.value.decimal"
   ::= {er1646v2BgriMVVlanIpV6DhcpClientVendorClEntry 16908288}

er1646v2BgriMVVlanIpV6DhcpClientVendorClValueHexData OBJECT-TYPE
   SYNTAX      OCTET STRING
   MAX-ACCESS  read-write
   STATUS      current
   DESCRIPTION
      "Path: vpnBridgeGroup.editConf.vlan.ipV6.dhcp.client.vendorClassOpt.value.hexData"
   ::= {er1646v2BgriMVVlanIpV6DhcpClientVendorClEntry 16973824}

er1646v2BgriMVVlanIpV6DhcpRelayDestinations OBJECT-TYPE
   SYNTAX      SEQUENCE OF Er1646v2BgriMVVlanIpV6DhcpRelayDestinationsEntry
   MAX-ACCESS  not-accessible
   STATUS      current
   DESCRIPTION
      ""
   ::= {er1646v2BgriMVVlan 705323072}

er1646v2BgriMVVlanIpV6DhcpRelayDestinationsEntry OBJECT-TYPE
   SYNTAX      Er1646v2BgriMVVlanIpV6DhcpRelayDestinationsEntry
   MAX-ACCESS  not-accessible
   STATUS      current
   DESCRIPTION
      ""
   INDEX      { er1646v2BgriMVVlanIpV6DhcpRelayDestinationsGlobalIx,
                er1646v2BgriMVVlanTableIx,
                er1646v2BgriMVVlanIpV6DhcpRelayDestinationsTableIx }
   ::= {er1646v2BgriMVVlanIpV6DhcpRelayDestinations 1}

Er1646v2BgriMVVlanIpV6DhcpRelayDestinationsEntry ::=
   SEQUENCE
      {
      er1646v2BgriMVVlanIpV6DhcpRelayDestinationsActions
         VariableLengthTableActions,
      er1646v2BgriMVVlanIpV6DhcpRelayDestinationsGlobalIx
         GlobalIndex,
      er1646v2BgriMVVlanIpV6DhcpRelayDestinationsTableIx
         TableIndex,
      er1646v2BgriMVVlanIpV6DhcpRelayDestinationsAddress
         Ipv6Address,
      er1646v2BgriMVVlanIpV6DhcpRelayDestinationsInterface
         DisplayString
      }

er1646v2BgriMVVlanIpV6DhcpRelayDestinationsActions OBJECT-TYPE
   SYNTAX      VariableLengthTableActions
   MAX-ACCESS  read-write
   STATUS      current
   DESCRIPTION
      "By way of this field, some manipulations
       on this table may be performed."
   ::= {er1646v2BgriMVVlanIpV6DhcpRelayDestinationsEntry 2}

er1646v2BgriMVVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2BgriMVVlanIpV6DhcpRelayDestinationsEntry 10}

er1646v2BgriMVVlanIpV6DhcpRelayDestinationsTableIx OBJECT-TYPE
   SYNTAX      TableIndex
   MAX-ACCESS  not-accessible
   STATUS      current
   DESCRIPTION
      ""
   ::= {er1646v2BgriMVVlanIpV6DhcpRelayDestinationsEntry 11}

er1646v2BgriMVVlanIpV6DhcpRelayDestinationsAddress OBJECT-TYPE
   SYNTAX      Ipv6Address
   MAX-ACCESS  read-write
   STATUS      current
   DESCRIPTION
      "Path: vpnBridgeGroup.editConf.vlan.ipV6.dhcp.relay.destinations.address

       ipv6 address"
   ::= {er1646v2BgriMVVlanIpV6DhcpRelayDestinationsEntry 16777216}

er1646v2BgriMVVlanIpV6DhcpRelayDestinationsInterface OBJECT-TYPE
   SYNTAX      DisplayString
   MAX-ACCESS  read-write
   STATUS      current
   DESCRIPTION
      "Path: vpnBridgeGroup.editConf.vlan.ipV6.dhcp.relay.destinations.interface"
   ::= {er1646v2BgriMVVlanIpV6DhcpRelayDestinationsEntry 33554432}

er1646v2BgriMVVlanVlanTCMap OBJECT-TYPE
   SYNTAX      SEQUENCE OF Er1646v2BgriMVVlanVlanTCMapEntry
   MAX-ACCESS  not-accessible
   STATUS      current
   DESCRIPTION
      ""
   ::= {er1646v2BgriMVVlan 241369088}

er1646v2BgriMVVlanVlanTCMapEntry OBJECT-TYPE
   SYNTAX      Er1646v2BgriMVVlanVlanTCMapEntry
   MAX-ACCESS  not-accessible
   STATUS      current
   DESCRIPTION
      ""
   INDEX      { er1646v2BgriMVVlanVlanTCMapGlobalIx,
                er1646v2BgriMVVlanTableIx,
                er1646v2BgriMVVlanVlanTCMapTableIx }
   ::= {er1646v2BgriMVVlanVlanTCMap 1}

Er1646v2BgriMVVlanVlanTCMapEntry ::=
   SEQUENCE
      {
      er1646v2BgriMVVlanVlanTCMapActions
         VariableLengthTableActions,
      er1646v2BgriMVVlanVlanTCMapGlobalIx
         GlobalIndex,
      er1646v2BgriMVVlanVlanTCMapTableIx
         TableIndex,
      er1646v2BgriMVVlanVlanTCMapStartTos
         INTEGER,
      er1646v2BgriMVVlanVlanTCMapEndTos
         INTEGER,
      er1646v2BgriMVVlanVlanTCMapCos
         INTEGER
      }

er1646v2BgriMVVlanVlanTCMapActions OBJECT-TYPE
   SYNTAX      VariableLengthTableActions
   MAX-ACCESS  read-write
   STATUS      current
   DESCRIPTION
      "By way of this field, some manipulations
       on this table may be performed."
   ::= {er1646v2BgriMVVlanVlanTCMapEntry 2}

er1646v2BgriMVVlanVlanTCMapGlobalIx OBJECT-TYPE
   SYNTAX      GlobalIndex
   MAX-ACCESS  not-accessible
   STATUS      current
   DESCRIPTION
      "The value of the tlsCntTreeGlobalIndex of the MANAGED OBJECT."
   ::= {er1646v2BgriMVVlanVlanTCMapEntry 10}

er1646v2BgriMVVlanVlanTCMapTableIx OBJECT-TYPE
   SYNTAX      TableIndex
   MAX-ACCESS  not-accessible
   STATUS      current
   DESCRIPTION
      ""
   ::= {er1646v2BgriMVVlanVlanTCMapEntry 11}

er1646v2BgriMVVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: vpnBridgeGroup.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2BgriMVVlanVlanTCMapEntry 16777216}

er1646v2BgriMVVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: vpnBridgeGroup.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2BgriMVVlanVlanTCMapEntry 33554432}

er1646v2BgriMVVlanVlanTCMapCos OBJECT-TYPE
   SYNTAX      INTEGER
               {
               queueCosMap (8)
               }
   MAX-ACCESS  read-write
   STATUS      current
   DESCRIPTION
      "Path: vpnBridgeGroup.editConf.vlan.vlan.tosCosMap.cos

       Possibilities:
               queueCosMap   (8)"
   ::= {er1646v2BgriMVVlanVlanTCMapEntry 50331648}

er1646v2BgriMVVlanVlanArpStaticArp OBJECT-TYPE
   SYNTAX      SEQUENCE OF Er1646v2BgriMVVlanVlanArpStaticArpEntry
   MAX-ACCESS  not-accessible
   STATUS      current
   DESCRIPTION
      ""
   ::= {er1646v2BgriMVVlan 235275008}

er1646v2BgriMVVlanVlanArpStaticArpEntry OBJECT-TYPE
   SYNTAX      Er1646v2BgriMVVlanVlanArpStaticArpEntry
   MAX-ACCESS  not-accessible
   STATUS      current
   DESCRIPTION
      ""
   INDEX      { er1646v2BgriMVVlanVlanArpStaticArpGlobalIx,
                er1646v2BgriMVVlanTableIx,
                er1646v2BgriMVVlanVlanArpStaticArpTableIx }
   ::= {er1646v2BgriMVVlanVlanArpStaticArp 1}

Er1646v2BgriMVVlanVlanArpStaticArpEntry ::=
   SEQUENCE
      {
      er1646v2BgriMVVlanVlanArpStaticArpActions
         VariableLengthTableActions,
      er1646v2BgriMVVlanVlanArpStaticArpGlobalIx
         GlobalIndex,
      er1646v2BgriMVVlanVlanArpStaticArpTableIx
         TableIndex,
      er1646v2BgriMVVlanVlanArpStaticArpMacAddress
         OCTET STRING,
      er1646v2BgriMVVlanVlanArpStaticArpIpAddress
         IpAddress
      }

er1646v2BgriMVVlanVlanArpStaticArpActions OBJECT-TYPE
   SYNTAX      VariableLengthTableActions
   MAX-ACCESS  read-write
   STATUS      current
   DESCRIPTION
      "By way of this field, some manipulations
       on this table may be performed."
   ::= {er1646v2BgriMVVlanVlanArpStaticArpEntry 2}

er1646v2BgriMVVlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2BgriMVVlanVlanArpStaticArpEntry 10}

er1646v2BgriMVVlanVlanArpStaticArpTableIx OBJECT-TYPE
   SYNTAX      TableIndex
   MAX-ACCESS  not-accessible
   STATUS      current
   DESCRIPTION
      ""
   ::= {er1646v2BgriMVVlanVlanArpStaticArpEntry 11}

er1646v2BgriMVVlanVlanArpStaticArpMacAddress OBJECT-TYPE
   SYNTAX      OCTET STRING
   MAX-ACCESS  read-write
   STATUS      current
   DESCRIPTION
      "Path: vpnBridgeGroup.editConf.vlan.vlan.arp.staticArp.macAddress

       MAC address."
   ::= {er1646v2BgriMVVlanVlanArpStaticArpEntry 16777216}

er1646v2BgriMVVlanVlanArpStaticArpIpAddress OBJECT-TYPE
   SYNTAX      IpAddress
   MAX-ACCESS  read-write
   STATUS      current
   DESCRIPTION
      "Path: vpnBridgeGroup.editConf.vlan.vlan.arp.staticArp.ipAddress"
   ::= {er1646v2BgriMVVlanVlanArpStaticArpEntry 33554432}


er1646v2BgriMVPppOE OBJECT IDENTIFIER ::= {er1646v2BgriMV 80}

er1646v2BgriMVPppOESSCTable OBJECT-TYPE
   SYNTAX      SEQUENCE OF Er1646v2BgriMVPppOEEntry
   MAX-ACCESS  not-accessible
   STATUS      current
   DESCRIPTION
      ""
   ::= {er1646v2BgriMVPppOE 1}

er1646v2BgriMVPppOEEntry OBJECT-TYPE
   SYNTAX      Er1646v2BgriMVPppOEEntry
   MAX-ACCESS  not-accessible
   STATUS      current
   DESCRIPTION
      ""
   INDEX      { er1646v2BgriMVPppOEGlobalIx,
                er1646v2BgriMVPppOETableIx }
   ::= {er1646v2BgriMVPppOESSCTable 1}

Er1646v2BgriMVPppOEEntry ::=
   SEQUENCE
      {
      er1646v2BgriMVPppOEActions
         VariableLengthTableActions,
      er1646v2BgriMVPppOEGlobalIx
         GlobalIndex,
      er1646v2BgriMVPppOETableIx
         TableIndex,
      er1646v2BgriMVPppOEName
         DisplayString,
      er1646v2BgriMVPppOERemark
         DisplayString,
      er1646v2BgriMVPppOEAdminStatus
         INTEGER,
      er1646v2BgriMVPppOEMode
         INTEGER,
      er1646v2BgriMVPppOEIpVrfRouter
         DisplayString,
      er1646v2BgriMVPppOEIpAdr
         IpAddress,
      er1646v2BgriMVPppOEIpNetm
         IpAddress,
      er1646v2BgriMVPppOEIpSNetName
         INTEGER,
      er1646v2BgriMVPppOEIpSNetCust
         DisplayString,
      er1646v2BgriMVPppOEIpRem
         IpAddress,
      er1646v2BgriMVPppOEIpUnnumbered
         DisplayString,
      er1646v2BgriMVPppOEIpGwPref
         Integer32,
      er1646v2BgriMVPppOEIpRsn
         INTEGER,
      er1646v2BgriMVPppOEIpMtu
         Integer32,
      er1646v2BgriMVPppOEIpMssAdjust
         INTEGER,
      er1646v2BgriMVPppOEIpRipMetric
         Integer32,
      er1646v2BgriMVPppOEIpRipMetricOut
         Integer32,
      er1646v2BgriMVPppOEIpRipMode
         INTEGER,
      er1646v2BgriMVPppOEIpRipTxVer
         INTEGER,
      er1646v2BgriMVPppOEIpRipRxVer
         INTEGER,
      er1646v2BgriMVPppOEIpRipSplitH
         INTEGER,
      er1646v2BgriMVPppOEIpRipAuth
         INTEGER,
      er1646v2BgriMVPppOEIpRipFilter
         DisplayString,
      er1646v2BgriMVPppOEIpRipFilterIn
         DisplayString,
      er1646v2BgriMVPppOEIpRipClearNextHop
         INTEGER,
      er1646v2BgriMVPppOEIpAccPol
         DisplayString,
      er1646v2BgriMVPppOEIpAB
         DisplayString,
      er1646v2BgriMVPppOEIpMA
         INTEGER,
      er1646v2BgriMVPppOEIpMF
         Integer32,
      er1646v2BgriMVPppOEIpDB
         INTEGER,
      er1646v2BgriMVPppOEIpIR
         INTEGER,
      er1646v2BgriMVPppOEIpIgmp
         INTEGER,
      er1646v2BgriMVPppOEIpNN
         DisplayString,
      er1646v2BgriMVPppOEIpPimMode
         INTEGER,
      er1646v2BgriMVPppOEIpPimDrPriority
         Counter32,
      er1646v2BgriMVPppOEIpPimHelloTime
         TimeTicks,
      er1646v2BgriMVPppOEIpPimPropagationDelay
         TimeTicks,
      er1646v2BgriMVPppOEIpPimOverrideInterval
         TimeTicks,
      er1646v2BgriMVPppOEIpPimBsrBorder
         INTEGER,
      er1646v2BgriMVPppOEIpPimTtlThreshold
         Integer32,
      er1646v2BgriMVPppOEIpIMNetworkUnreachable
         INTEGER,
      er1646v2BgriMVPppOEIpIMHostUnreachable
         INTEGER,
      er1646v2BgriMVPppOEIpIMProtocolUnreachable
         INTEGER,
      er1646v2BgriMVPppOEIpIMPortUnreachable
         INTEGER,
      er1646v2BgriMVPppOEIpIMMtuExceeded
         INTEGER,
      er1646v2BgriMVPppOEIpIMAdminProhibited
         INTEGER,
      er1646v2BgriMVPppOEIpIMTtlExceeded
         INTEGER,
      er1646v2BgriMVPppOEIpIMRedirect
         INTEGER,
      er1646v2BgriMVPppOEIpV6VrfRouter
         DisplayString,
      er1646v2BgriMVPppOEIpV6AddrAutoConfigNrDupAddrDetects
         Integer32,
      er1646v2BgriMVPppOEIpV6AddrAutoConfigAcceptRa
         INTEGER,
      er1646v2BgriMVPppOEIpV6AddrAutoConfigAcceptRaRdnss
         INTEGER,
      er1646v2BgriMVPppOEIpV6AddrAutoConfigAcceptRaDnssl
         INTEGER,
      er1646v2BgriMVPppOEIpV6DefaultRoute
         INTEGER,
      er1646v2BgriMVPppOEIpV6RaSend
         INTEGER,
      er1646v2BgriMVPppOEIpV6RaMinInterval
         TimeTicks,
      er1646v2BgriMVPppOEIpV6RaMaxInterval
         TimeTicks,
      er1646v2BgriMVPppOEIpV6RaManagedFlag
         INTEGER,
      er1646v2BgriMVPppOEIpV6RaOtherConfFlag
         INTEGER,
      er1646v2BgriMVPppOEIpV6RaLinkMtu
         Integer32,
      er1646v2BgriMVPppOEIpV6RaReachableTime
         TimeTicks,
      er1646v2BgriMVPppOEIpV6RaRetransmitTime
         TimeTicks,
      er1646v2BgriMVPppOEIpV6RaHopLimit
         Integer32,
      er1646v2BgriMVPppOEIpV6RaDefaultLifeTime
         TimeTicks,
      er1646v2BgriMVPppOEIpV6RaDnsOptionsRdnssLifeTime
         TimeTicks,
      er1646v2BgriMVPppOEIpV6RaDnsOptionsRdnssImportServers
         INTEGER,
      er1646v2BgriMVPppOEIpV6RaDnsOptionsDnsslLifeTime
         TimeTicks,
      er1646v2BgriMVPppOEIpV6RaDnsOptionsDnsslImportDomains
         INTEGER,
      er1646v2BgriMVPppOEIpV6RsSend
         INTEGER,
      er1646v2BgriMVPppOEIpV6RsMaxRandomDelay
         TimeTicks,
      er1646v2BgriMVPppOEIpV6RsInterval
         TimeTicks,
      er1646v2BgriMVPppOEIpV6RsMaxSolicitations
         Integer32,
      er1646v2BgriMVPppOEIpV6TrafficPolicyInbound
         DisplayString,
      er1646v2BgriMVPppOEIpV6TrafficPolicyOutbound
         DisplayString,
      er1646v2BgriMVPppOEIpV6FirewallZone
         DisplayString,
      er1646v2BgriMVPppOEIpV6DhcpClientAddrAC
         INTEGER,
      er1646v2BgriMVPppOEIpV6DhcpClientPrDelMode
         INTEGER,
      er1646v2BgriMVPppOEIpV6DhcpClientPrDelPool
         DisplayString,
      er1646v2BgriMVPppOEIpV6DhcpClientPrDelPdExclOpt
         INTEGER,
      er1646v2BgriMVPppOEIpV6DhcpClientDnsServerPref
         Integer32,
      er1646v2BgriMVPppOEIpV6DhcpClientRapidCommit
         INTEGER,
      er1646v2BgriMVPppOEIpV6DhcpClientTimersSolTimeOut
         TimeTicks,
      er1646v2BgriMVPppOEIpV6DhcpClientTimersSolMaxRt
         TimeTicks,
      er1646v2BgriMVPppOEIpV6DhcpClientTimersInfoRefresh
         TimeTicks,
      er1646v2BgriMVPppOEIpV6DhcpServerMode
         INTEGER,
      er1646v2BgriMVPppOEIpV6DhcpServerPreference
         Integer32,
      er1646v2BgriMVPppOEIpV6DhcpServerPool
         DisplayString,
      er1646v2BgriMVPppOEIpV6DhcpServerRapidCommit
         INTEGER,
      er1646v2BgriMVPppOEIpV6DhcpServerTimersInfoRefresh
         TimeTicks,
      er1646v2BgriMVPppOEIpV6DhcpRelayMode
         INTEGER,
      er1646v2BgriMVPppOEIpV6SendRedirect
         INTEGER,
      er1646v2BgriMVPppOEIpV6LinkMtu
         Integer32,
      er1646v2BgriMVPppOEIpV6InterfaceId
         OCTET STRING,
      er1646v2BgriMVPppOEIpV6MF
         Integer32,
      er1646v2BgriMVPppOEIpV6IcmpMessagesNoRoute
         INTEGER,
      er1646v2BgriMVPppOEIpV6IcmpMessagesBeyondScope
         INTEGER,
      er1646v2BgriMVPppOEIpV6IcmpMessagesAddressUnreachable
         INTEGER,
      er1646v2BgriMVPppOEIpV6IcmpMessagesPortUnreachable
         INTEGER,
      er1646v2BgriMVPppOEIpV6IcmpMessagesPacketTooBig
         INTEGER,
      er1646v2BgriMVPppOEIpV6IcmpMessagesHopLimitExceeded
         INTEGER,
      er1646v2BgriMVPppOEIpV6IcmpMessagesFragTimeExceeded
         INTEGER,
      er1646v2BgriMVPppOEIpV6IcmpMessagesHeaderFieldErr
         INTEGER,
      er1646v2BgriMVPppOEIpV6IcmpMessagesOptionUnrecognized
         INTEGER,
      er1646v2BgriMVPppOEIpV6IcmpMessagesRedirect
         INTEGER,
      er1646v2BgriMVPppOEPppLnkMOperation
         INTEGER,
      er1646v2BgriMVPppOEPppLnkMInterval
         TimeTicks,
      er1646v2BgriMVPppOEPppLnkMRepTimeOut
         TimeTicks,
      er1646v2BgriMVPppOEPppLnkMFailsPrmt
         Integer32,
      er1646v2BgriMVPppOEPppAuthentication
         INTEGER,
      er1646v2BgriMVPppOEPppAuthenPeriod
         TimeTicks,
      er1646v2BgriMVPppOEPppSessionName
         DisplayString,
      er1646v2BgriMVPppOEPppSessionSecret
         DisplayString,
      er1646v2BgriMVPppOEPppEncModeSessionSecret
         INTEGER,
      er1646v2BgriMVPppOEPppEncSessionSecret
         DisplayString,
      er1646v2BgriMVPppOEPppServiceName
         DisplayString
      }

er1646v2BgriMVPppOEActions OBJECT-TYPE
   SYNTAX      VariableLengthTableActions
   MAX-ACCESS  read-write
   STATUS      current
   DESCRIPTION
      "By way of this field, some manipulations
       on this table may be performed."
   ::= {er1646v2BgriMVPppOEEntry 2}

er1646v2BgriMVPppOEGlobalIx OBJECT-TYPE
   SYNTAX      GlobalIndex
   MAX-ACCESS  not-accessible
   STATUS      current
   DESCRIPTION
      "The value of the tlsCntTreeGlobalIndex of the MANAGED OBJECT."
   ::= {er1646v2BgriMVPppOEEntry 10}

er1646v2BgriMVPppOETableIx OBJECT-TYPE
   SYNTAX      TableIndex
   MAX-ACCESS  not-accessible
   STATUS      current
   DESCRIPTION
      ""
   ::= {er1646v2BgriMVPppOEEntry 11}

er1646v2BgriMVPppOEName OBJECT-TYPE
   SYNTAX      DisplayString
   MAX-ACCESS  read-write
   STATUS      current
   DESCRIPTION
      "Path: vpnBridgeGroup.editConf.pppoEClient.name"
   ::= {er1646v2BgriMVPppOEEntry 16777216}

er1646v2BgriMVPppOERemark OBJECT-TYPE
   SYNTAX      DisplayString
   MAX-ACCESS  read-write
   STATUS      current
   DESCRIPTION
      "Path: vpnBridgeGroup.editConf.pppoEClient.remark"
   ::= {er1646v2BgriMVPppOEEntry 1157627904}

er1646v2BgriMVPppOEAdminStatus OBJECT-TYPE
   SYNTAX      INTEGER
               {
               up (1),
               down (2)
               }
   MAX-ACCESS  read-write
   STATUS      current
   DESCRIPTION
      "Path: vpnBridgeGroup.editConf.pppoEClient.adminStatus

       Possibilities:
               up   (1)
               down   (2)"
   ::= {er1646v2BgriMVPppOEEntry 33554432}

er1646v2BgriMVPppOEMode OBJECT-TYPE
   SYNTAX      INTEGER
               {
               routing (1),
               multilink (8),
               ipV6 (16),
               ipV6ipV4 (17)
               }
   MAX-ACCESS  read-write
   STATUS      current
   DESCRIPTION
      "Path: vpnBridgeGroup.editConf.pppoEClient.mode

       Possibilities:
               routing   (1)
               multilink   (8)
               ipV6   (16)
               ipV6/ipV4   (17)"
   ::= {er1646v2BgriMVPppOEEntry 67108864}

er1646v2BgriMVPppOEIpVrfRouter OBJECT-TYPE
   SYNTAX      DisplayString
   MAX-ACCESS  read-write
   STATUS      current
   DESCRIPTION
      "Path: vpnBridgeGroup.editConf.pppoEClient.ip.vrfRouter"
   ::= {er1646v2BgriMVPppOEEntry 53215232}

er1646v2BgriMVPppOEIpAdr OBJECT-TYPE
   SYNTAX      IpAddress
   MAX-ACCESS  read-write
   STATUS      current
   DESCRIPTION
      "Path: vpnBridgeGroup.editConf.pppoEClient.ip.address"
   ::= {er1646v2BgriMVPppOEEntry 58261504}

er1646v2BgriMVPppOEIpNetm OBJECT-TYPE
   SYNTAX      IpAddress
   MAX-ACCESS  read-write
   STATUS      current
   DESCRIPTION
      "Path: vpnBridgeGroup.editConf.pppoEClient.ip.netMask"
   ::= {er1646v2BgriMVPppOEEntry 58392576}

er1646v2BgriMVPppOEIpSNetName OBJECT-TYPE
   SYNTAX      INTEGER
               {
               slOPTg (0),
               corp (2),
               dmz (3),
               internet (1)
               }
   MAX-ACCESS  read-write
   STATUS      current
   DESCRIPTION
      "Path: vpnBridgeGroup.editConf.pppoEClient.ip.sNet.name

       Possibilities:
               <OPT>   (0)
               corp   (2)
               dmz   (3)
               internet   (1)"
   ::= {er1646v2BgriMVPppOEEntry 53674240}

er1646v2BgriMVPppOEIpSNetCust OBJECT-TYPE
   SYNTAX      DisplayString
   MAX-ACCESS  read-write
   STATUS      current
   DESCRIPTION
      "Path: vpnBridgeGroup.editConf.pppoEClient.ip.sNet.custom"
   ::= {er1646v2BgriMVPppOEEntry 53674496}

er1646v2BgriMVPppOEIpRem OBJECT-TYPE
   SYNTAX      IpAddress
   MAX-ACCESS  read-write
   STATUS      current
   DESCRIPTION
      "Path: vpnBridgeGroup.editConf.pppoEClient.ip.remote"
   ::= {er1646v2BgriMVPppOEEntry 58458112}

er1646v2BgriMVPppOEIpUnnumbered OBJECT-TYPE
   SYNTAX      DisplayString
   MAX-ACCESS  read-write
   STATUS      current
   DESCRIPTION
      "Path: vpnBridgeGroup.editConf.pppoEClient.ip.unnumbered"
   ::= {er1646v2BgriMVPppOEEntry 52625408}

er1646v2BgriMVPppOEIpGwPref OBJECT-TYPE
   SYNTAX      Integer32
   MAX-ACCESS  read-write
   STATUS      current
   DESCRIPTION
      "Path: vpnBridgeGroup.editConf.pppoEClient.ip.gatewayPreference"
   ::= {er1646v2BgriMVPppOEEntry 52690944}

er1646v2BgriMVPppOEIpRsn OBJECT-TYPE
   SYNTAX      INTEGER
               {
               disabled (0),
               enabled (1)
               }
   MAX-ACCESS  read-write
   STATUS      current
   DESCRIPTION
      "Path: vpnBridgeGroup.editConf.pppoEClient.ip.requestSubnet

       Possibilities:
               disabled   (0)
               enabled   (1)"
   ::= {er1646v2BgriMVPppOEEntry 56688640}

er1646v2BgriMVPppOEIpMtu OBJECT-TYPE
   SYNTAX      Integer32
   MAX-ACCESS  read-write
   STATUS      current
   DESCRIPTION
      "Path: vpnBridgeGroup.editConf.pppoEClient.ip.mtu"
   ::= {er1646v2BgriMVPppOEEntry 52953088}

er1646v2BgriMVPppOEIpMssAdjust OBJECT-TYPE
   SYNTAX      INTEGER
               {
               disabled (0),
               auto (65536)
               }
   MAX-ACCESS  read-write
   STATUS      current
   DESCRIPTION
      "Path: vpnBridgeGroup.editConf.pppoEClient.ip.mssAdjust

       Possibilities:
               disabled   (0)
               auto   (65536)"
   ::= {er1646v2BgriMVPppOEEntry 53280768}

er1646v2BgriMVPppOEIpRipMetric OBJECT-TYPE
   SYNTAX      Integer32
   MAX-ACCESS  read-write
   STATUS      current
   DESCRIPTION
      "Path: vpnBridgeGroup.editConf.pppoEClient.ip.rip.metric"
   ::= {er1646v2BgriMVPppOEEntry 51712768}

er1646v2BgriMVPppOEIpRipMetricOut OBJECT-TYPE
   SYNTAX      Integer32
   MAX-ACCESS  read-write
   STATUS      current
   DESCRIPTION
      "Path: vpnBridgeGroup.editConf.pppoEClient.ip.rip.metricOut"
   ::= {er1646v2BgriMVPppOEEntry 51713024}

er1646v2BgriMVPppOEIpRipMode OBJECT-TYPE
   SYNTAX      INTEGER
               {
               disabled (0),
               passive (1),
               active (2)
               }
   MAX-ACCESS  read-write
   STATUS      current
   DESCRIPTION
      "Path: vpnBridgeGroup.editConf.pppoEClient.ip.rip.mode

       Possibilities:
               disabled   (0)
               passive   (1)
               active   (2)"
   ::= {er1646v2BgriMVPppOEEntry 51713280}

er1646v2BgriMVPppOEIpRipTxVer OBJECT-TYPE
   SYNTAX      INTEGER
               {
               rip1 (0),
               rip2 (1),
               rip1mcompatible (2)
               }
   MAX-ACCESS  read-write
   STATUS      current
   DESCRIPTION
      "Path: vpnBridgeGroup.editConf.pppoEClient.ip.rip.txVersion

       Possibilities:
               rip1   (0)
               rip2   (1)
               rip1-compatible   (2)"
   ::= {er1646v2BgriMVPppOEEntry 51716864}

er1646v2BgriMVPppOEIpRipRxVer OBJECT-TYPE
   SYNTAX      INTEGER
               {
               rip1only (0),
               rip2only (1),
               rip12 (2)
               }
   MAX-ACCESS  read-write
   STATUS      current
   DESCRIPTION
      "Path: vpnBridgeGroup.editConf.pppoEClient.ip.rip.rxVersion

       Possibilities:
               rip1only   (0)
               rip2only   (1)
               rip1&2   (2)"
   ::= {er1646v2BgriMVPppOEEntry 51717120}

er1646v2BgriMVPppOEIpRipSplitH OBJECT-TYPE
   SYNTAX      INTEGER
               {
               disabled (0),
               enabled (1),
               poisonedReverse (2)
               }
   MAX-ACCESS  read-write
   STATUS      current
   DESCRIPTION
      "Path: vpnBridgeGroup.editConf.pppoEClient.ip.rip.splitHorizon

       Possibilities:
               disabled   (0)
               enabled   (1)
               poisonedReverse   (2)"
   ::= {er1646v2BgriMVPppOEEntry 51713792}

er1646v2BgriMVPppOEIpRipAuth OBJECT-TYPE
   SYNTAX      INTEGER
               {
               disabled (0),
               texts (1),
               md5 (2)
               }
   MAX-ACCESS  read-write
   STATUS      current
   DESCRIPTION
      "Path: vpnBridgeGroup.editConf.pppoEClient.ip.rip.authentication

       Possibilities:
               disabled   (0)
               text    (1)
               md5   (2)"
   ::= {er1646v2BgriMVPppOEEntry 51712512}

er1646v2BgriMVPppOEIpRipFilter OBJECT-TYPE
   SYNTAX      DisplayString
   MAX-ACCESS  read-write
   STATUS      current
   DESCRIPTION
      "Path: vpnBridgeGroup.editConf.pppoEClient.ip.rip.filter"
   ::= {er1646v2BgriMVPppOEEntry 51716096}

er1646v2BgriMVPppOEIpRipFilterIn OBJECT-TYPE
   SYNTAX      DisplayString
   MAX-ACCESS  read-write
   STATUS      current
   DESCRIPTION
      "Path: vpnBridgeGroup.editConf.pppoEClient.ip.rip.filterIn"
   ::= {er1646v2BgriMVPppOEEntry 51716352}

er1646v2BgriMVPppOEIpRipClearNextHop OBJECT-TYPE
   SYNTAX      INTEGER
               {
               disabled (0),
               enabled (1)
               }
   MAX-ACCESS  read-write
   STATUS      current
   DESCRIPTION
      "Path: vpnBridgeGroup.editConf.pppoEClient.ip.rip.clearNextHop

       Possibilities:
               disabled   (0)
               enabled   (1)"
   ::= {er1646v2BgriMVPppOEEntry 51708416}

er1646v2BgriMVPppOEIpAccPol OBJECT-TYPE
   SYNTAX      DisplayString
   MAX-ACCESS  read-write
   STATUS      current
   DESCRIPTION
      "Path: vpnBridgeGroup.editConf.pppoEClient.ip.accessPolicy"
   ::= {er1646v2BgriMVPppOEEntry 53084160}

er1646v2BgriMVPppOEIpAB OBJECT-TYPE
   SYNTAX      DisplayString
   MAX-ACCESS  read-write
   STATUS      current
   DESCRIPTION
      "Path: vpnBridgeGroup.editConf.pppoEClient.ip.trafficPolicy"
   ::= {er1646v2BgriMVPppOEEntry 51249152}

er1646v2BgriMVPppOEIpMA OBJECT-TYPE
   SYNTAX      INTEGER
               {
               disabled (0),
               enabled (1)
               }
   MAX-ACCESS  read-write
   STATUS      current
   DESCRIPTION
      "Path: vpnBridgeGroup.editConf.pppoEClient.ip.mgmtAccess

       Possibilities:
               disabled   (0)
               enabled   (1)"
   ::= {er1646v2BgriMVPppOEEntry 51380224}

er1646v2BgriMVPppOEIpMF OBJECT-TYPE
   SYNTAX      Integer32
   MAX-ACCESS  read-write
   STATUS      current
   DESCRIPTION
      "Path: vpnBridgeGroup.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2BgriMVPppOEEntry 51445760}

er1646v2BgriMVPppOEIpDB OBJECT-TYPE
   SYNTAX      INTEGER
               {
               disabled (0),
               enabled (1)
               }
   MAX-ACCESS  read-write
   STATUS      current
   DESCRIPTION
      "Path: vpnBridgeGroup.editConf.pppoEClient.ip.directedBroadcasts

       Possibilities:
               disabled   (0)
               enabled   (1)"
   ::= {er1646v2BgriMVPppOEEntry 51773440}

er1646v2BgriMVPppOEIpIR OBJECT-TYPE
   SYNTAX      INTEGER
               {
               disabled (0),
               enabled (1)
               }
   MAX-ACCESS  read-write
   STATUS      current
   DESCRIPTION
      "Path: vpnBridgeGroup.editConf.pppoEClient.ip.icmpRedirects

       Possibilities:
               disabled   (0)
               enabled   (1)"
   ::= {er1646v2BgriMVPppOEEntry 52035584}

er1646v2BgriMVPppOEIpIgmp OBJECT-TYPE
   SYNTAX      INTEGER
               {
               disabled (0),
               proxy (1),
               router (2),
               v3Router (5)
               }
   MAX-ACCESS  read-write
   STATUS      current
   DESCRIPTION
      "Path: vpnBridgeGroup.editConf.pppoEClient.ip.igmp

       Possibilities:
               disabled   (0)
               proxy   (1)
               router   (2)
               v3Router   (5)"
   ::= {er1646v2BgriMVPppOEEntry 52428800}

er1646v2BgriMVPppOEIpNN OBJECT-TYPE
   SYNTAX      DisplayString
   MAX-ACCESS  read-write
   STATUS      current
   DESCRIPTION
      "Path: vpnBridgeGroup.editConf.pppoEClient.ip.nat"
   ::= {er1646v2BgriMVPppOEEntry 52101120}

er1646v2BgriMVPppOEIpPimMode OBJECT-TYPE
   SYNTAX      INTEGER
               {
               disabled (0),
               sparse (1),
               passive (2)
               }
   MAX-ACCESS  read-write
   STATUS      current
   DESCRIPTION
      "Path: vpnBridgeGroup.editConf.pppoEClient.ip.pim.mode

       Possibilities:
               disabled   (0)
               sparse   (1)
               passive   (2)"
   ::= {er1646v2BgriMVPppOEEntry 53346560}

er1646v2BgriMVPppOEIpPimDrPriority OBJECT-TYPE
   SYNTAX      Counter32
   MAX-ACCESS  read-write
   STATUS      current
   DESCRIPTION
      "Path: vpnBridgeGroup.editConf.pppoEClient.ip.pim.drPriority

       32 bit unsigned wrappable counter."
   ::= {er1646v2BgriMVPppOEEntry 53346816}

er1646v2BgriMVPppOEIpPimHelloTime OBJECT-TYPE
   SYNTAX      TimeTicks
   MAX-ACCESS  read-write
   STATUS      current
   DESCRIPTION
      "Path: vpnBridgeGroup.editConf.pppoEClient.ip.pim.helloTime

       Time in centi-second."
   ::= {er1646v2BgriMVPppOEEntry 53347072}

er1646v2BgriMVPppOEIpPimPropagationDelay OBJECT-TYPE
   SYNTAX      TimeTicks
   MAX-ACCESS  read-write
   STATUS      current
   DESCRIPTION
      "Path: vpnBridgeGroup.editConf.pppoEClient.ip.pim.propagationDelay

       Time in centi-second."
   ::= {er1646v2BgriMVPppOEEntry 53347328}

er1646v2BgriMVPppOEIpPimOverrideInterval OBJECT-TYPE
   SYNTAX      TimeTicks
   MAX-ACCESS  read-write
   STATUS      current
   DESCRIPTION
      "Path: vpnBridgeGroup.editConf.pppoEClient.ip.pim.overrideInterval

       Time in centi-second."
   ::= {er1646v2BgriMVPppOEEntry 53347584}

er1646v2BgriMVPppOEIpPimBsrBorder OBJECT-TYPE
   SYNTAX      INTEGER
               {
               disabled (0),
               enabled (1)
               }
   MAX-ACCESS  read-write
   STATUS      current
   DESCRIPTION
      "Path: vpnBridgeGroup.editConf.pppoEClient.ip.pim.bsrBorder

       Possibilities:
               disabled   (0)
               enabled   (1)"
   ::= {er1646v2BgriMVPppOEEntry 53347840}

er1646v2BgriMVPppOEIpPimTtlThreshold OBJECT-TYPE
   SYNTAX      Integer32
   MAX-ACCESS  read-write
   STATUS      current
   DESCRIPTION
      "Path: vpnBridgeGroup.editConf.pppoEClient.ip.pim.ttlThreshold"
   ::= {er1646v2BgriMVPppOEEntry 53348096}

er1646v2BgriMVPppOEIpIMNetworkUnreachable OBJECT-TYPE
   SYNTAX      INTEGER
               {
               disabled (0),
               enabled (1)
               }
   MAX-ACCESS  read-write
   STATUS      current
   DESCRIPTION
      "Path: vpnBridgeGroup.editConf.pppoEClient.ip.icmpMessages.networkUnreachable

       Possibilities:
               disabled   (0)
               enabled   (1)"
   ::= {er1646v2BgriMVPppOEEntry 53412096}

er1646v2BgriMVPppOEIpIMHostUnreachable OBJECT-TYPE
   SYNTAX      INTEGER
               {
               disabled (0),
               enabled (1)
               }
   MAX-ACCESS  read-write
   STATUS      current
   DESCRIPTION
      "Path: vpnBridgeGroup.editConf.pppoEClient.ip.icmpMessages.hostUnreachable

       Possibilities:
               disabled   (0)
               enabled   (1)"
   ::= {er1646v2BgriMVPppOEEntry 53412352}

er1646v2BgriMVPppOEIpIMProtocolUnreachable OBJECT-TYPE
   SYNTAX      INTEGER
               {
               disabled (0),
               enabled (1)
               }
   MAX-ACCESS  read-write
   STATUS      current
   DESCRIPTION
      "Path: vpnBridgeGroup.editConf.pppoEClient.ip.icmpMessages.protocolUnreachable

       Possibilities:
               disabled   (0)
               enabled   (1)"
   ::= {er1646v2BgriMVPppOEEntry 53412608}

er1646v2BgriMVPppOEIpIMPortUnreachable OBJECT-TYPE
   SYNTAX      INTEGER
               {
               disabled (0),
               enabled (1)
               }
   MAX-ACCESS  read-write
   STATUS      current
   DESCRIPTION
      "Path: vpnBridgeGroup.editConf.pppoEClient.ip.icmpMessages.portUnreachable

       Possibilities:
               disabled   (0)
               enabled   (1)"
   ::= {er1646v2BgriMVPppOEEntry 53412864}

er1646v2BgriMVPppOEIpIMMtuExceeded OBJECT-TYPE
   SYNTAX      INTEGER
               {
               disabled (0),
               enabled (1)
               }
   MAX-ACCESS  read-write
   STATUS      current
   DESCRIPTION
      "Path: vpnBridgeGroup.editConf.pppoEClient.ip.icmpMessages.mtuExceeded

       Possibilities:
               disabled   (0)
               enabled   (1)"
   ::= {er1646v2BgriMVPppOEEntry 53413120}

er1646v2BgriMVPppOEIpIMAdminProhibited OBJECT-TYPE
   SYNTAX      INTEGER
               {
               disabled (0),
               enabled (1)
               }
   MAX-ACCESS  read-write
   STATUS      current
   DESCRIPTION
      "Path: vpnBridgeGroup.editConf.pppoEClient.ip.icmpMessages.adminProhibited

       Possibilities:
               disabled   (0)
               enabled   (1)"
   ::= {er1646v2BgriMVPppOEEntry 53413376}

er1646v2BgriMVPppOEIpIMTtlExceeded OBJECT-TYPE
   SYNTAX      INTEGER
               {
               disabled (0),
               enabled (1)
               }
   MAX-ACCESS  read-write
   STATUS      current
   DESCRIPTION
      "Path: vpnBridgeGroup.editConf.pppoEClient.ip.icmpMessages.ttlExceeded

       Possibilities:
               disabled   (0)
               enabled   (1)"
   ::= {er1646v2BgriMVPppOEEntry 53413632}

er1646v2BgriMVPppOEIpIMRedirect OBJECT-TYPE
   SYNTAX      INTEGER
               {
               disabled (0),
               enabled (1)
               }
   MAX-ACCESS  read-write
   STATUS      current
   DESCRIPTION
      "Path: vpnBridgeGroup.editConf.pppoEClient.ip.icmpMessages.redirect

       Possibilities:
               disabled   (0)
               enabled   (1)"
   ::= {er1646v2BgriMVPppOEEntry 53413888}

er1646v2BgriMVPppOEIpV6VrfRouter OBJECT-TYPE
   SYNTAX      DisplayString
   MAX-ACCESS  read-write
   STATUS      current
   DESCRIPTION
      "Path: vpnBridgeGroup.editConf.pppoEClient.ipV6.vrfRouter"
   ::= {er1646v2BgriMVPppOEEntry 704708608}

er1646v2BgriMVPppOEIpV6AddrAutoConfigNrDupAddrDetects OBJECT-TYPE
   SYNTAX      Integer32
   MAX-ACCESS  read-write
   STATUS      current
   DESCRIPTION
      "Path: vpnBridgeGroup.editConf.pppoEClient.ipV6.addrAutoConfig.nrDupAddrDetects"
   ::= {er1646v2BgriMVPppOEEntry 704905472}

er1646v2BgriMVPppOEIpV6AddrAutoConfigAcceptRa OBJECT-TYPE
   SYNTAX      INTEGER
               {
               disabled (0),
               enabled (1)
               }
   MAX-ACCESS  read-write
   STATUS      current
   DESCRIPTION
      "Path: vpnBridgeGroup.editConf.pppoEClient.ipV6.addrAutoConfig.acceptRa

       Possibilities:
               disabled   (0)
               enabled   (1)"
   ::= {er1646v2BgriMVPppOEEntry 704905728}

er1646v2BgriMVPppOEIpV6AddrAutoConfigAcceptRaRdnss OBJECT-TYPE
   SYNTAX      INTEGER
               {
               disabled (0),
               enabled (1)
               }
   MAX-ACCESS  read-write
   STATUS      current
   DESCRIPTION
      "Path: vpnBridgeGroup.editConf.pppoEClient.ipV6.addrAutoConfig.acceptRaRdnss

       Possibilities:
               disabled   (0)
               enabled   (1)"
   ::= {er1646v2BgriMVPppOEEntry 704905984}

er1646v2BgriMVPppOEIpV6AddrAutoConfigAcceptRaDnssl OBJECT-TYPE
   SYNTAX      INTEGER
               {
               disabled (0),
               enabled (1)
               }
   MAX-ACCESS  read-write
   STATUS      current
   DESCRIPTION
      "Path: vpnBridgeGroup.editConf.pppoEClient.ipV6.addrAutoConfig.acceptRaDnssl

       Possibilities:
               disabled   (0)
               enabled   (1)"
   ::= {er1646v2BgriMVPppOEEntry 704906240}

er1646v2BgriMVPppOEIpV6DefaultRoute OBJECT-TYPE
   SYNTAX      INTEGER
               {
               disabled (0),
               enabled (1)
               }
   MAX-ACCESS  read-write
   STATUS      current
   DESCRIPTION
      "Path: vpnBridgeGroup.editConf.pppoEClient.ipV6.defaultRoute

       Possibilities:
               disabled   (0)
               enabled   (1)"
   ::= {er1646v2BgriMVPppOEEntry 704970752}

er1646v2BgriMVPppOEIpV6RaSend OBJECT-TYPE
   SYNTAX      INTEGER
               {
               disabled (0),
               enabled (1)
               }
   MAX-ACCESS  read-write
   STATUS      current
   DESCRIPTION
      "Path: vpnBridgeGroup.editConf.pppoEClient.ipV6.ra.send

       Possibilities:
               disabled   (0)
               enabled   (1)"
   ::= {er1646v2BgriMVPppOEEntry 705036544}

er1646v2BgriMVPppOEIpV6RaMinInterval OBJECT-TYPE
   SYNTAX      TimeTicks
   MAX-ACCESS  read-write
   STATUS      current
   DESCRIPTION
      "Path: vpnBridgeGroup.editConf.pppoEClient.ipV6.ra.minInterval

       Time in centi-second."
   ::= {er1646v2BgriMVPppOEEntry 705036800}

er1646v2BgriMVPppOEIpV6RaMaxInterval OBJECT-TYPE
   SYNTAX      TimeTicks
   MAX-ACCESS  read-write
   STATUS      current
   DESCRIPTION
      "Path: vpnBridgeGroup.editConf.pppoEClient.ipV6.ra.maxInterval

       Time in centi-second."
   ::= {er1646v2BgriMVPppOEEntry 705037056}

er1646v2BgriMVPppOEIpV6RaManagedFlag OBJECT-TYPE
   SYNTAX      INTEGER
               {
               disabled (0),
               enabled (1)
               }
   MAX-ACCESS  read-write
   STATUS      current
   DESCRIPTION
      "Path: vpnBridgeGroup.editConf.pppoEClient.ipV6.ra.managedFlag

       Possibilities:
               disabled   (0)
               enabled   (1)"
   ::= {er1646v2BgriMVPppOEEntry 705037312}

er1646v2BgriMVPppOEIpV6RaOtherConfFlag OBJECT-TYPE
   SYNTAX      INTEGER
               {
               disabled (0),
               enabled (1)
               }
   MAX-ACCESS  read-write
   STATUS      current
   DESCRIPTION
      "Path: vpnBridgeGroup.editConf.pppoEClient.ipV6.ra.otherConfFlag

       Possibilities:
               disabled   (0)
               enabled   (1)"
   ::= {er1646v2BgriMVPppOEEntry 705037568}

er1646v2BgriMVPppOEIpV6RaLinkMtu OBJECT-TYPE
   SYNTAX      Integer32
   MAX-ACCESS  read-write
   STATUS      current
   DESCRIPTION
      "Path: vpnBridgeGroup.editConf.pppoEClient.ipV6.ra.linkMtu"
   ::= {er1646v2BgriMVPppOEEntry 705037824}

er1646v2BgriMVPppOEIpV6RaReachableTime OBJECT-TYPE
   SYNTAX      TimeTicks
   MAX-ACCESS  read-write
   STATUS      current
   DESCRIPTION
      "Path: vpnBridgeGroup.editConf.pppoEClient.ipV6.ra.reachableTime

       Time in centi-second."
   ::= {er1646v2BgriMVPppOEEntry 705038080}

er1646v2BgriMVPppOEIpV6RaRetransmitTime OBJECT-TYPE
   SYNTAX      TimeTicks
   MAX-ACCESS  read-write
   STATUS      current
   DESCRIPTION
      "Path: vpnBridgeGroup.editConf.pppoEClient.ipV6.ra.retransmitTime

       Time in centi-second."
   ::= {er1646v2BgriMVPppOEEntry 705038336}

er1646v2BgriMVPppOEIpV6RaHopLimit OBJECT-TYPE
   SYNTAX      Integer32
   MAX-ACCESS  read-write
   STATUS      current
   DESCRIPTION
      "Path: vpnBridgeGroup.editConf.pppoEClient.ipV6.ra.hopLimit"
   ::= {er1646v2BgriMVPppOEEntry 705038592}

er1646v2BgriMVPppOEIpV6RaDefaultLifeTime OBJECT-TYPE
   SYNTAX      TimeTicks
   MAX-ACCESS  read-write
   STATUS      current
   DESCRIPTION
      "Path: vpnBridgeGroup.editConf.pppoEClient.ipV6.ra.defaultLifeTime

       Time in centi-second."
   ::= {er1646v2BgriMVPppOEEntry 705038848}

er1646v2BgriMVPppOEIpV6RaDnsOptionsRdnssLifeTime OBJECT-TYPE
   SYNTAX      TimeTicks
   MAX-ACCESS  read-write
   STATUS      current
   DESCRIPTION
      "Path: vpnBridgeGroup.editConf.pppoEClient.ipV6.ra.dnsOptions.rdnss.lifeTime

       Time in centi-second."
   ::= {er1646v2BgriMVPppOEEntry 705039140}

er1646v2BgriMVPppOEIpV6RaDnsOptionsRdnssImportServers OBJECT-TYPE
   SYNTAX      INTEGER
               {
               disabled (0),
               enabled (1)
               }
   MAX-ACCESS  read-write
   STATUS      current
   DESCRIPTION
      "Path: vpnBridgeGroup.editConf.pppoEClient.ipV6.ra.dnsOptions.rdnss.importServers

       Possibilities:
               disabled   (0)
               enabled   (1)"
   ::= {er1646v2BgriMVPppOEEntry 705039148}

er1646v2BgriMVPppOEIpV6RaDnsOptionsDnsslLifeTime OBJECT-TYPE
   SYNTAX      TimeTicks
   MAX-ACCESS  read-write
   STATUS      current
   DESCRIPTION
      "Path: vpnBridgeGroup.editConf.pppoEClient.ipV6.ra.dnsOptions.dnssl.lifeTime

       Time in centi-second."
   ::= {er1646v2BgriMVPppOEEntry 705039172}

er1646v2BgriMVPppOEIpV6RaDnsOptionsDnsslImportDomains OBJECT-TYPE
   SYNTAX      INTEGER
               {
               disabled (0),
               enabled (1)
               }
   MAX-ACCESS  read-write
   STATUS      current
   DESCRIPTION
      "Path: vpnBridgeGroup.editConf.pppoEClient.ipV6.ra.dnsOptions.dnssl.importDomains

       Possibilities:
               disabled   (0)
               enabled   (1)"
   ::= {er1646v2BgriMVPppOEEntry 705039180}

er1646v2BgriMVPppOEIpV6RsSend OBJECT-TYPE
   SYNTAX      INTEGER
               {
               disabled (0),
               enabled (1)
               }
   MAX-ACCESS  read-write
   STATUS      current
   DESCRIPTION
      "Path: vpnBridgeGroup.editConf.pppoEClient.ipV6.rs.send

       Possibilities:
               disabled   (0)
               enabled   (1)"
   ::= {er1646v2BgriMVPppOEEntry 705954048}

er1646v2BgriMVPppOEIpV6RsMaxRandomDelay OBJECT-TYPE
   SYNTAX      TimeTicks
   MAX-ACCESS  read-write
   STATUS      current
   DESCRIPTION
      "Path: vpnBridgeGroup.editConf.pppoEClient.ipV6.rs.maxRandomDelay

       Time in centi-second."
   ::= {er1646v2BgriMVPppOEEntry 705954304}

er1646v2BgriMVPppOEIpV6RsInterval OBJECT-TYPE
   SYNTAX      TimeTicks
   MAX-ACCESS  read-write
   STATUS      current
   DESCRIPTION
      "Path: vpnBridgeGroup.editConf.pppoEClient.ipV6.rs.interval

       Time in centi-second."
   ::= {er1646v2BgriMVPppOEEntry 705954560}

er1646v2BgriMVPppOEIpV6RsMaxSolicitations OBJECT-TYPE
   SYNTAX      Integer32
   MAX-ACCESS  read-write
   STATUS      current
   DESCRIPTION
      "Path: vpnBridgeGroup.editConf.pppoEClient.ipV6.rs.maxSolicitations"
   ::= {er1646v2BgriMVPppOEEntry 705954816}

er1646v2BgriMVPppOEIpV6TrafficPolicyInbound OBJECT-TYPE
   SYNTAX      DisplayString
   MAX-ACCESS  read-write
   STATUS      current
   DESCRIPTION
      "Path: vpnBridgeGroup.editConf.pppoEClient.ipV6.trafficPolicy.inbound"
   ::= {er1646v2BgriMVPppOEEntry 705364224}

er1646v2BgriMVPppOEIpV6TrafficPolicyOutbound OBJECT-TYPE
   SYNTAX      DisplayString
   MAX-ACCESS  read-write
   STATUS      current
   DESCRIPTION
      "Path: vpnBridgeGroup.editConf.pppoEClient.ipV6.trafficPolicy.outbound"
   ::= {er1646v2BgriMVPppOEEntry 705364480}

er1646v2BgriMVPppOEIpV6FirewallZone OBJECT-TYPE
   SYNTAX      DisplayString
   MAX-ACCESS  read-write
   STATUS      current
   DESCRIPTION
      "Path: vpnBridgeGroup.editConf.pppoEClient.ipV6.firewall.zone"
   ::= {er1646v2BgriMVPppOEEntry 705429760}

er1646v2BgriMVPppOEIpV6DhcpClientAddrAC OBJECT-TYPE
   SYNTAX      INTEGER
               {
               disabled (0),
               enabled (1)
               }
   MAX-ACCESS  read-write
   STATUS      current
   DESCRIPTION
      "Path: vpnBridgeGroup.editConf.pppoEClient.ipV6.dhcp.client.addrAutoConfig

       Possibilities:
               disabled   (0)
               enabled   (1)"
   ::= {er1646v2BgriMVPppOEEntry 705307648}

er1646v2BgriMVPppOEIpV6DhcpClientPrDelMode OBJECT-TYPE
   SYNTAX      INTEGER
               {
               disabled (0),
               enabled (1)
               }
   MAX-ACCESS  read-write
   STATUS      current
   DESCRIPTION
      "Path: vpnBridgeGroup.editConf.pppoEClient.ipV6.dhcp.client.pd.mode

       Possibilities:
               disabled   (0)
               enabled   (1)"
   ::= {er1646v2BgriMVPppOEEntry 705308676}

er1646v2BgriMVPppOEIpV6DhcpClientPrDelPool OBJECT-TYPE
   SYNTAX      DisplayString
   MAX-ACCESS  read-write
   STATUS      current
   DESCRIPTION
      "Path: vpnBridgeGroup.editConf.pppoEClient.ipV6.dhcp.client.pd.pool"
   ::= {er1646v2BgriMVPppOEEntry 705308680}

er1646v2BgriMVPppOEIpV6DhcpClientPrDelPdExclOpt OBJECT-TYPE
   SYNTAX      INTEGER
               {
               disabled (0),
               enabled (1)
               }
   MAX-ACCESS  read-write
   STATUS      current
   DESCRIPTION
      "Path: vpnBridgeGroup.editConf.pppoEClient.ipV6.dhcp.client.pd.pdExclOpt

       Possibilities:
               disabled   (0)
               enabled   (1)"
   ::= {er1646v2BgriMVPppOEEntry 705308684}

er1646v2BgriMVPppOEIpV6DhcpClientDnsServerPref OBJECT-TYPE
   SYNTAX      Integer32
   MAX-ACCESS  read-write
   STATUS      current
   DESCRIPTION
      "Path: vpnBridgeGroup.editConf.pppoEClient.ipV6.dhcp.client.dns.serverPref"
   ::= {er1646v2BgriMVPppOEEntry 705310724}

er1646v2BgriMVPppOEIpV6DhcpClientRapidCommit OBJECT-TYPE
   SYNTAX      INTEGER
               {
               disabled (0),
               enabled (1)
               }
   MAX-ACCESS  read-write
   STATUS      current
   DESCRIPTION
      "Path: vpnBridgeGroup.editConf.pppoEClient.ipV6.dhcp.client.rapidCommit

       Possibilities:
               disabled   (0)
               enabled   (1)"
   ::= {er1646v2BgriMVPppOEEntry 705309696}

er1646v2BgriMVPppOEIpV6DhcpClientTimersSolTimeOut OBJECT-TYPE
   SYNTAX      TimeTicks
   MAX-ACCESS  read-write
   STATUS      current
   DESCRIPTION
      "Path: vpnBridgeGroup.editConf.pppoEClient.ipV6.dhcp.client.timers.solTimeOut

       Time in centi-second."
   ::= {er1646v2BgriMVPppOEEntry 705311748}

er1646v2BgriMVPppOEIpV6DhcpClientTimersSolMaxRt OBJECT-TYPE
   SYNTAX      TimeTicks
   MAX-ACCESS  read-write
   STATUS      current
   DESCRIPTION
      "Path: vpnBridgeGroup.editConf.pppoEClient.ipV6.dhcp.client.timers.solMaxRt

       Time in centi-second."
   ::= {er1646v2BgriMVPppOEEntry 705311752}

er1646v2BgriMVPppOEIpV6DhcpClientTimersInfoRefresh OBJECT-TYPE
   SYNTAX      TimeTicks
   MAX-ACCESS  read-write
   STATUS      current
   DESCRIPTION
      "Path: vpnBridgeGroup.editConf.pppoEClient.ipV6.dhcp.client.timers.infoRefresh

       Time in centi-second."
   ::= {er1646v2BgriMVPppOEEntry 705311756}

er1646v2BgriMVPppOEIpV6DhcpServerMode OBJECT-TYPE
   SYNTAX      INTEGER
               {
               disabled (0),
               enabled (1)
               }
   MAX-ACCESS  read-write
   STATUS      current
   DESCRIPTION
      "Path: vpnBridgeGroup.editConf.pppoEClient.ipV6.dhcp.server.mode

       Possibilities:
               disabled   (0)
               enabled   (1)"
   ::= {er1646v2BgriMVPppOEEntry 705315840}

er1646v2BgriMVPppOEIpV6DhcpServerPreference OBJECT-TYPE
   SYNTAX      Integer32
   MAX-ACCESS  read-write
   STATUS      current
   DESCRIPTION
      "Path: vpnBridgeGroup.editConf.pppoEClient.ipV6.dhcp.server.preference"
   ::= {er1646v2BgriMVPppOEEntry 705316864}

er1646v2BgriMVPppOEIpV6DhcpServerPool OBJECT-TYPE
   SYNTAX      DisplayString
   MAX-ACCESS  read-write
   STATUS      current
   DESCRIPTION
      "Path: vpnBridgeGroup.editConf.pppoEClient.ipV6.dhcp.server.pool"
   ::= {er1646v2BgriMVPppOEEntry 705317888}

er1646v2BgriMVPppOEIpV6DhcpServerRapidCommit OBJECT-TYPE
   SYNTAX      INTEGER
               {
               disabled (0),
               enabled (1)
               }
   MAX-ACCESS  read-write
   STATUS      current
   DESCRIPTION
      "Path: vpnBridgeGroup.editConf.pppoEClient.ipV6.dhcp.server.rapidCommit

       Possibilities:
               disabled   (0)
               enabled   (1)"
   ::= {er1646v2BgriMVPppOEEntry 705318912}

er1646v2BgriMVPppOEIpV6DhcpServerTimersInfoRefresh OBJECT-TYPE
   SYNTAX      TimeTicks
   MAX-ACCESS  read-write
   STATUS      current
   DESCRIPTION
      "Path: vpnBridgeGroup.editConf.pppoEClient.ipV6.dhcp.server.timers.infoRefresh

       Time in centi-second."
   ::= {er1646v2BgriMVPppOEEntry 705319940}

er1646v2BgriMVPppOEIpV6DhcpRelayMode OBJECT-TYPE
   SYNTAX      INTEGER
               {
               disabled (0),
               enabled (1)
               }
   MAX-ACCESS  read-write
   STATUS      current
   DESCRIPTION
      "Path: vpnBridgeGroup.editConf.pppoEClient.ipV6.dhcp.relay.mode

       Possibilities:
               disabled   (0)
               enabled   (1)"
   ::= {er1646v2BgriMVPppOEEntry 705323040}

er1646v2BgriMVPppOEIpV6SendRedirect OBJECT-TYPE
   SYNTAX      INTEGER
               {
               disabled (0),
               enabled (1)
               }
   MAX-ACCESS  read-write
   STATUS      current
   DESCRIPTION
      "Path: vpnBridgeGroup.editConf.pppoEClient.ipV6.sendRedirect

       Possibilities:
               disabled   (0)
               enabled   (1)"
   ::= {er1646v2BgriMVPppOEEntry 705101824}

er1646v2BgriMVPppOEIpV6LinkMtu OBJECT-TYPE
   SYNTAX      Integer32
   MAX-ACCESS  read-write
   STATUS      current
   DESCRIPTION
      "Path: vpnBridgeGroup.editConf.pppoEClient.ipV6.linkMtu"
   ::= {er1646v2BgriMVPppOEEntry 705167360}

er1646v2BgriMVPppOEIpV6InterfaceId OBJECT-TYPE
   SYNTAX      OCTET STRING
   MAX-ACCESS  read-write
   STATUS      current
   DESCRIPTION
      "Path: vpnBridgeGroup.editConf.pppoEClient.ipV6.interfaceId"
   ::= {er1646v2BgriMVPppOEEntry 705232896}

er1646v2BgriMVPppOEIpV6MF OBJECT-TYPE
   SYNTAX      Integer32
   MAX-ACCESS  read-write
   STATUS      current
   DESCRIPTION
      "Path: vpnBridgeGroup.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2BgriMVPppOEEntry 705757184}

er1646v2BgriMVPppOEIpV6IcmpMessagesNoRoute OBJECT-TYPE
   SYNTAX      INTEGER
               {
               disabled (0),
               enabled (1)
               }
   MAX-ACCESS  read-write
   STATUS      current
   DESCRIPTION
      "Path: vpnBridgeGroup.editConf.pppoEClient.ipV6.icmpMessages.noRoute

       Possibilities:
               disabled   (0)
               enabled   (1)"
   ::= {er1646v2BgriMVPppOEEntry 705822976}

er1646v2BgriMVPppOEIpV6IcmpMessagesBeyondScope OBJECT-TYPE
   SYNTAX      INTEGER
               {
               disabled (0),
               enabled (1)
               }
   MAX-ACCESS  read-write
   STATUS      current
   DESCRIPTION
      "Path: vpnBridgeGroup.editConf.pppoEClient.ipV6.icmpMessages.beyondScope

       Possibilities:
               disabled   (0)
               enabled   (1)"
   ::= {er1646v2BgriMVPppOEEntry 705823488}

er1646v2BgriMVPppOEIpV6IcmpMessagesAddressUnreachable OBJECT-TYPE
   SYNTAX      INTEGER
               {
               disabled (0),
               enabled (1)
               }
   MAX-ACCESS  read-write
   STATUS      current
   DESCRIPTION
      "Path: vpnBridgeGroup.editConf.pppoEClient.ipV6.icmpMessages.addressUnreachable

       Possibilities:
               disabled   (0)
               enabled   (1)"
   ::= {er1646v2BgriMVPppOEEntry 705823744}

er1646v2BgriMVPppOEIpV6IcmpMessagesPortUnreachable OBJECT-TYPE
   SYNTAX      INTEGER
               {
               disabled (0),
               enabled (1)
               }
   MAX-ACCESS  read-write
   STATUS      current
   DESCRIPTION
      "Path: vpnBridgeGroup.editConf.pppoEClient.ipV6.icmpMessages.portUnreachable

       Possibilities:
               disabled   (0)
               enabled   (1)"
   ::= {er1646v2BgriMVPppOEEntry 705824000}

er1646v2BgriMVPppOEIpV6IcmpMessagesPacketTooBig OBJECT-TYPE
   SYNTAX      INTEGER
               {
               disabled (0),
               enabled (1)
               }
   MAX-ACCESS  read-write
   STATUS      current
   DESCRIPTION
      "Path: vpnBridgeGroup.editConf.pppoEClient.ipV6.icmpMessages.packetTooBig

       Possibilities:
               disabled   (0)
               enabled   (1)"
   ::= {er1646v2BgriMVPppOEEntry 705825280}

er1646v2BgriMVPppOEIpV6IcmpMessagesHopLimitExceeded OBJECT-TYPE
   SYNTAX      INTEGER
               {
               disabled (0),
               enabled (1)
               }
   MAX-ACCESS  read-write
   STATUS      current
   DESCRIPTION
      "Path: vpnBridgeGroup.editConf.pppoEClient.ipV6.icmpMessages.hopLimitExceeded

       Possibilities:
               disabled   (0)
               enabled   (1)"
   ::= {er1646v2BgriMVPppOEEntry 705827840}

er1646v2BgriMVPppOEIpV6IcmpMessagesFragTimeExceeded OBJECT-TYPE
   SYNTAX      INTEGER
               {
               disabled (0),
               enabled (1)
               }
   MAX-ACCESS  read-write
   STATUS      current
   DESCRIPTION
      "Path: vpnBridgeGroup.editConf.pppoEClient.ipV6.icmpMessages.fragTimeExceeded

       Possibilities:
               disabled   (0)
               enabled   (1)"
   ::= {er1646v2BgriMVPppOEEntry 705828096}

er1646v2BgriMVPppOEIpV6IcmpMessagesHeaderFieldErr OBJECT-TYPE
   SYNTAX      INTEGER
               {
               disabled (0),
               enabled (1)
               }
   MAX-ACCESS  read-write
   STATUS      current
   DESCRIPTION
      "Path: vpnBridgeGroup.editConf.pppoEClient.ipV6.icmpMessages.headerFieldErr

       Possibilities:
               disabled   (0)
               enabled   (1)"
   ::= {er1646v2BgriMVPppOEEntry 705830400}

er1646v2BgriMVPppOEIpV6IcmpMessagesOptionUnrecognized OBJECT-TYPE
   SYNTAX      INTEGER
               {
               disabled (0),
               enabled (1)
               }
   MAX-ACCESS  read-write
   STATUS      current
   DESCRIPTION
      "Path: vpnBridgeGroup.editConf.pppoEClient.ipV6.icmpMessages.optionUnrecognized

       Possibilities:
               disabled   (0)
               enabled   (1)"
   ::= {er1646v2BgriMVPppOEEntry 705830912}

er1646v2BgriMVPppOEIpV6IcmpMessagesRedirect OBJECT-TYPE
   SYNTAX      INTEGER
               {
               disabled (0),
               enabled (1)
               }
   MAX-ACCESS  read-write
   STATUS      current
   DESCRIPTION
      "Path: vpnBridgeGroup.editConf.pppoEClient.ipV6.icmpMessages.redirect

       Possibilities:
               disabled   (0)
               enabled   (1)"
   ::= {er1646v2BgriMVPppOEEntry 705832960}

er1646v2BgriMVPppOEPppLnkMOperation OBJECT-TYPE
   SYNTAX      INTEGER
               {
               disabled (0),
               enabled (1)
               }
   MAX-ACCESS  read-write
   STATUS      current
   DESCRIPTION
      "Path: vpnBridgeGroup.editConf.pppoEClient.ppp.linkMonitoring.operation

       Possibilities:
               disabled   (0)
               enabled   (1)"
   ::= {er1646v2BgriMVPppOEEntry 251724032}

er1646v2BgriMVPppOEPppLnkMInterval OBJECT-TYPE
   SYNTAX      TimeTicks
   MAX-ACCESS  read-write
   STATUS      current
   DESCRIPTION
      "Path: vpnBridgeGroup.editConf.pppoEClient.ppp.linkMonitoring.interval

       Time in centi-second."
   ::= {er1646v2BgriMVPppOEEntry 251724288}

er1646v2BgriMVPppOEPppLnkMRepTimeOut OBJECT-TYPE
   SYNTAX      TimeTicks
   MAX-ACCESS  read-write
   STATUS      current
   DESCRIPTION
      "Path: vpnBridgeGroup.editConf.pppoEClient.ppp.linkMonitoring.replyTimeOut

       Time in centi-second."
   ::= {er1646v2BgriMVPppOEEntry 251724544}

er1646v2BgriMVPppOEPppLnkMFailsPrmt OBJECT-TYPE
   SYNTAX      Integer32
   MAX-ACCESS  read-write
   STATUS      current
   DESCRIPTION
      "Path: vpnBridgeGroup.editConf.pppoEClient.ppp.linkMonitoring.failsPermitted"
   ::= {er1646v2BgriMVPppOEEntry 251724800}

er1646v2BgriMVPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: vpnBridgeGroup.editConf.pppoEClient.ppp.authentication

       Possibilities:
               disabled   (0)
               chap   (1)
               pap   (2)
               chapOrPap   (3)
               msChap   (4)
               msChapV2   (5)"
   ::= {er1646v2BgriMVPppOEEntry 251789312}

er1646v2BgriMVPppOEPppAuthenPeriod OBJECT-TYPE
   SYNTAX      TimeTicks
   MAX-ACCESS  read-write
   STATUS      current
   DESCRIPTION
      "Path: vpnBridgeGroup.editConf.pppoEClient.ppp.authenPeriod

       Time in centi-second."
   ::= {er1646v2BgriMVPppOEEntry 251854848}

er1646v2BgriMVPppOEPppSessionName OBJECT-TYPE
   SYNTAX      DisplayString
   MAX-ACCESS  read-write
   STATUS      current
   DESCRIPTION
      "Path: vpnBridgeGroup.editConf.pppoEClient.ppp.sessionName"
   ::= {er1646v2BgriMVPppOEEntry 251985920}

er1646v2BgriMVPppOEPppSessionSecret OBJECT-TYPE
   SYNTAX      DisplayString
   MAX-ACCESS  read-write
   STATUS      current
   DESCRIPTION
      "Path: vpnBridgeGroup.editConf.pppoEClient.ppp.sessionSecret"
   ::= {er1646v2BgriMVPppOEEntry 252051456}

er1646v2BgriMVPppOEPppEncModeSessionSecret OBJECT-TYPE
   SYNTAX      INTEGER
               {
               none (1),
               encrypt (2),
               encType1 (3),
               invalid (128)
               }
   MAX-ACCESS  read-write
   STATUS      current
   DESCRIPTION
      "Path: vpnBridgeGroup.editConf.pppoEClient.ppp.encModeSessionSecret

       Possibilities:
               none   (1)
               encrypt   (2)
               encType1   (3)
               invalid   (128)"
   ::= {er1646v2BgriMVPppOEEntry 252182528}

er1646v2BgriMVPppOEPppEncSessionSecret OBJECT-TYPE
   SYNTAX      DisplayString
   MAX-ACCESS  read-write
   STATUS      current
   DESCRIPTION
      "Path: vpnBridgeGroup.editConf.pppoEClient.ppp.encSessionSecret"
   ::= {er1646v2BgriMVPppOEEntry 252248064}

er1646v2BgriMVPppOEPppServiceName OBJECT-TYPE
   SYNTAX      DisplayString
   MAX-ACCESS  read-write
   STATUS      current
   DESCRIPTION
      "Path: vpnBridgeGroup.editConf.pppoEClient.ppp.serviceName"
   ::= {er1646v2BgriMVPppOEEntry 252116992}

er1646v2BgriMVPppOEIpH OBJECT-TYPE
   SYNTAX      SEQUENCE OF Er1646v2BgriMVPppOEIpHEntry
   MAX-ACCESS  not-accessible
   STATUS      current
   DESCRIPTION
      ""
   ::= {er1646v2BgriMVPppOE 51314688}

er1646v2BgriMVPppOEIpHEntry OBJECT-TYPE
   SYNTAX      Er1646v2BgriMVPppOEIpHEntry
   MAX-ACCESS  not-accessible
   STATUS      current
   DESCRIPTION
      ""
   INDEX      { er1646v2BgriMVPppOEIpHGlobalIx,
                er1646v2BgriMVPppOETableIx,
                er1646v2BgriMVPppOEIpHTableIx }
   ::= {er1646v2BgriMVPppOEIpH 1}

Er1646v2BgriMVPppOEIpHEntry ::=
   SEQUENCE
      {
      er1646v2BgriMVPppOEIpHActions
         VariableLengthTableActions,
      er1646v2BgriMVPppOEIpHGlobalIx
         GlobalIndex,
      er1646v2BgriMVPppOEIpHTableIx
         TableIndex,
      er1646v2BgriMVPppOEIpHAddress
         IpAddress,
      er1646v2BgriMVPppOEIpHDhcpRelayOptionSubscriberId
         DisplayString
      }

er1646v2BgriMVPppOEIpHActions OBJECT-TYPE
   SYNTAX      VariableLengthTableActions
   MAX-ACCESS  read-write
   STATUS      current
   DESCRIPTION
      "By way of this field, some manipulations
       on this table may be performed."
   ::= {er1646v2BgriMVPppOEIpHEntry 2}

er1646v2BgriMVPppOEIpHGlobalIx OBJECT-TYPE
   SYNTAX      GlobalIndex
   MAX-ACCESS  not-accessible
   STATUS      current
   DESCRIPTION
      "The value of the tlsCntTreeGlobalIndex of the MANAGED OBJECT."
   ::= {er1646v2BgriMVPppOEIpHEntry 10}

er1646v2BgriMVPppOEIpHTableIx OBJECT-TYPE
   SYNTAX      TableIndex
   MAX-ACCESS  not-accessible
   STATUS      current
   DESCRIPTION
      ""
   ::= {er1646v2BgriMVPppOEIpHEntry 11}

er1646v2BgriMVPppOEIpHAddress OBJECT-TYPE
   SYNTAX      IpAddress
   MAX-ACCESS  read-write
   STATUS      current
   DESCRIPTION
      "Path: vpnBridgeGroup.editConf.pppoEClient.ip.helpers.address"
   ::= {er1646v2BgriMVPppOEIpHEntry 16777216}

er1646v2BgriMVPppOEIpHDhcpRelayOptionSubscriberId OBJECT-TYPE
   SYNTAX      DisplayString
   MAX-ACCESS  read-write
   STATUS      current
   DESCRIPTION
      "Path: vpnBridgeGroup.editConf.pppoEClient.ip.helpers.dhcpRelayOption.subscriberId"
   ::= {er1646v2BgriMVPppOEIpHEntry 33947648}

er1646v2BgriMVPppOEIpV6Addresses OBJECT-TYPE
   SYNTAX      SEQUENCE OF Er1646v2BgriMVPppOEIpV6AddressesEntry
   MAX-ACCESS  not-accessible
   STATUS      current
   DESCRIPTION
      ""
   ::= {er1646v2BgriMVPppOE 704839680}

er1646v2BgriMVPppOEIpV6AddressesEntry OBJECT-TYPE
   SYNTAX      Er1646v2BgriMVPppOEIpV6AddressesEntry
   MAX-ACCESS  not-accessible
   STATUS      current
   DESCRIPTION
      ""
   INDEX      { er1646v2BgriMVPppOEIpV6AddressesGlobalIx,
                er1646v2BgriMVPppOETableIx,
                er1646v2BgriMVPppOEIpV6AddressesTableIx }
   ::= {er1646v2BgriMVPppOEIpV6Addresses 1}

Er1646v2BgriMVPppOEIpV6AddressesEntry ::=
   SEQUENCE
      {
      er1646v2BgriMVPppOEIpV6AddressesActions
         VariableLengthTableActions,
      er1646v2BgriMVPppOEIpV6AddressesGlobalIx
         GlobalIndex,
      er1646v2BgriMVPppOEIpV6AddressesTableIx
         TableIndex,
      er1646v2BgriMVPppOEIpV6AddressesType
         INTEGER,
      er1646v2BgriMVPppOEIpV6AddressesAddress
         Ipv6Address,
      er1646v2BgriMVPppOEIpV6AddressesPrefixLength
         Integer32,
      er1646v2BgriMVPppOEIpV6AddressesGeneralPrefix
         DisplayString,
      er1646v2BgriMVPppOEIpV6AddressesRaSend
         INTEGER,
      er1646v2BgriMVPppOEIpV6AddressesRaOnLinkFlag
         INTEGER,
      er1646v2BgriMVPppOEIpV6AddressesRaAutoFlag
         INTEGER,
      er1646v2BgriMVPppOEIpV6AddressesRaValidLifeTime
         TimeTicks,
      er1646v2BgriMVPppOEIpV6AddressesRaValidLTMode
         INTEGER,
      er1646v2BgriMVPppOEIpV6AddressesRaPrefLifeTime
         TimeTicks,
      er1646v2BgriMVPppOEIpV6AddressesRaPrefLTMode
         INTEGER
      }

er1646v2BgriMVPppOEIpV6AddressesActions OBJECT-TYPE
   SYNTAX      VariableLengthTableActions
   MAX-ACCESS  read-write
   STATUS      current
   DESCRIPTION
      "By way of this field, some manipulations
       on this table may be performed."
   ::= {er1646v2BgriMVPppOEIpV6AddressesEntry 2}

er1646v2BgriMVPppOEIpV6AddressesGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6AddressesEntry 10}

er1646v2BgriMVPppOEIpV6AddressesTableIx OBJECT-TYPE
   SYNTAX      TableIndex
   MAX-ACCESS  not-accessible
   STATUS      current
   DESCRIPTION
      ""
   ::= {er1646v2BgriMVPppOEIpV6AddressesEntry 11}

er1646v2BgriMVPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vpnBridgeGroup.editConf.pppoEClient.ipV6.addresses.type

       Possibilities:
               unicast   (0)
               eui64   (1)
               anycast   (2)
               linkLocal   (3)
               generalPrefix   (4)"
   ::= {er1646v2BgriMVPppOEIpV6AddressesEntry 50331648}

er1646v2BgriMVPppOEIpV6AddressesAddress OBJECT-TYPE
   SYNTAX      Ipv6Address
   MAX-ACCESS  read-write
   STATUS      current
   DESCRIPTION
      "Path: vpnBridgeGroup.editConf.pppoEClient.ipV6.addresses.address

       ipv6 address"
   ::= {er1646v2BgriMVPppOEIpV6AddressesEntry 16777216}

er1646v2BgriMVPppOEIpV6AddressesPrefixLength OBJECT-TYPE
   SYNTAX      Integer32
   MAX-ACCESS  read-write
   STATUS      current
   DESCRIPTION
      "Path: vpnBridgeGroup.editConf.pppoEClient.ipV6.addresses.prefixLength"
   ::= {er1646v2BgriMVPppOEIpV6AddressesEntry 33554432}

er1646v2BgriMVPppOEIpV6AddressesGeneralPrefix OBJECT-TYPE
   SYNTAX      DisplayString
   MAX-ACCESS  read-write
   STATUS      current
   DESCRIPTION
      "Path: vpnBridgeGroup.editConf.pppoEClient.ipV6.addresses.generalPrefix"
   ::= {er1646v2BgriMVPppOEIpV6AddressesEntry 83886080}

er1646v2BgriMVPppOEIpV6AddressesRaSend OBJECT-TYPE
   SYNTAX      INTEGER
               {
               disabled (0),
               enabled (1)
               }
   MAX-ACCESS  read-write
   STATUS      current
   DESCRIPTION
      "Path: vpnBridgeGroup.editConf.pppoEClient.ipV6.addresses.ra.send

       Possibilities:
               disabled   (0)
               enabled   (1)"
   ::= {er1646v2BgriMVPppOEIpV6AddressesEntry 67174400}

er1646v2BgriMVPppOEIpV6AddressesRaOnLinkFlag OBJECT-TYPE
   SYNTAX      INTEGER
               {
               disabled (0),
               enabled (1)
               }
   MAX-ACCESS  read-write
   STATUS      current
   DESCRIPTION
      "Path: vpnBridgeGroup.editConf.pppoEClient.ipV6.addresses.ra.onLinkFlag

       Possibilities:
               disabled   (0)
               enabled   (1)"
   ::= {er1646v2BgriMVPppOEIpV6AddressesEntry 67371008}

er1646v2BgriMVPppOEIpV6AddressesRaAutoFlag OBJECT-TYPE
   SYNTAX      INTEGER
               {
               disabled (0),
               enabled (1)
               }
   MAX-ACCESS  read-write
   STATUS      current
   DESCRIPTION
      "Path: vpnBridgeGroup.editConf.pppoEClient.ipV6.addresses.ra.autonomousFlag

       Possibilities:
               disabled   (0)
               enabled   (1)"
   ::= {er1646v2BgriMVPppOEIpV6AddressesEntry 67567616}

er1646v2BgriMVPppOEIpV6AddressesRaValidLifeTime OBJECT-TYPE
   SYNTAX      TimeTicks
   MAX-ACCESS  read-write
   STATUS      current
   DESCRIPTION
      "Path: vpnBridgeGroup.editConf.pppoEClient.ipV6.addresses.ra.validLifeTime

       Time in centi-second."
   ::= {er1646v2BgriMVPppOEIpV6AddressesEntry 67239936}

er1646v2BgriMVPppOEIpV6AddressesRaValidLTMode OBJECT-TYPE
   SYNTAX      INTEGER
               {
               fixed (0),
               infinite (2)
               }
   MAX-ACCESS  read-write
   STATUS      current
   DESCRIPTION
      "Path: vpnBridgeGroup.editConf.pppoEClient.ipV6.addresses.ra.validLifeTimeMode

       Possibilities:
               fixed   (0)
               infinite   (2)"
   ::= {er1646v2BgriMVPppOEIpV6AddressesEntry 67305472}

er1646v2BgriMVPppOEIpV6AddressesRaPrefLifeTime OBJECT-TYPE
   SYNTAX      TimeTicks
   MAX-ACCESS  read-write
   STATUS      current
   DESCRIPTION
      "Path: vpnBridgeGroup.editConf.pppoEClient.ipV6.addresses.ra.prefLifeTime

       Time in centi-second."
   ::= {er1646v2BgriMVPppOEIpV6AddressesEntry 67436544}

er1646v2BgriMVPppOEIpV6AddressesRaPrefLTMode OBJECT-TYPE
   SYNTAX      INTEGER
               {
               fixed (0),
               infinite (2)
               }
   MAX-ACCESS  read-write
   STATUS      current
   DESCRIPTION
      "Path: vpnBridgeGroup.editConf.pppoEClient.ipV6.addresses.ra.prefLifeTimeMode

       Possibilities:
               fixed   (0)
               infinite   (2)"
   ::= {er1646v2BgriMVPppOEIpV6AddressesEntry 67502080}

er1646v2BgriMVPppOEIpV6RaDnsOptionsRdnssServers OBJECT-TYPE
   SYNTAX      SEQUENCE OF Er1646v2BgriMVPppOEIpV6RaDnsOptionsRdnssServersEntry
   MAX-ACCESS  not-accessible
   STATUS      current
   DESCRIPTION
      ""
   ::= {er1646v2BgriMVPppOE 705039144}

er1646v2BgriMVPppOEIpV6RaDnsOptionsRdnssServersEntry OBJECT-TYPE
   SYNTAX      Er1646v2BgriMVPppOEIpV6RaDnsOptionsRdnssServersEntry
   MAX-ACCESS  not-accessible
   STATUS      current
   DESCRIPTION
      ""
   INDEX      { er1646v2BgriMVPppOEIpV6RaDnsOptionsRdnssServersGlobalIx,
                er1646v2BgriMVPppOETableIx,
                er1646v2BgriMVPppOEIpV6RaDnsOptionsRdnssServersTableIx }
   ::= {er1646v2BgriMVPppOEIpV6RaDnsOptionsRdnssServers 1}

Er1646v2BgriMVPppOEIpV6RaDnsOptionsRdnssServersEntry ::=
   SEQUENCE
      {
      er1646v2BgriMVPppOEIpV6RaDnsOptionsRdnssServersActions
         VariableLengthTableActions,
      er1646v2BgriMVPppOEIpV6RaDnsOptionsRdnssServersGlobalIx
         GlobalIndex,
      er1646v2BgriMVPppOEIpV6RaDnsOptionsRdnssServersTableIx
         TableIndex,
      er1646v2BgriMVPppOEIpV6RaDnsOptionsRdnssServersAddress
         Ipv6Address
      }

er1646v2BgriMVPppOEIpV6RaDnsOptionsRdnssServersActions OBJECT-TYPE
   SYNTAX      VariableLengthTableActions
   MAX-ACCESS  read-write
   STATUS      current
   DESCRIPTION
      "By way of this field, some manipulations
       on this table may be performed."
   ::= {er1646v2BgriMVPppOEIpV6RaDnsOptionsRdnssServersEntry 2}

er1646v2BgriMVPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6RaDnsOptionsRdnssServersEntry 10}

er1646v2BgriMVPppOEIpV6RaDnsOptionsRdnssServersTableIx OBJECT-TYPE
   SYNTAX      TableIndex
   MAX-ACCESS  not-accessible
   STATUS      current
   DESCRIPTION
      ""
   ::= {er1646v2BgriMVPppOEIpV6RaDnsOptionsRdnssServersEntry 11}

er1646v2BgriMVPppOEIpV6RaDnsOptionsRdnssServersAddress OBJECT-TYPE
   SYNTAX      Ipv6Address
   MAX-ACCESS  read-write
   STATUS      current
   DESCRIPTION
      "Path: vpnBridgeGroup.editConf.pppoEClient.ipV6.ra.dnsOptions.rdnss.servers.address

       ipv6 address"
   ::= {er1646v2BgriMVPppOEIpV6RaDnsOptionsRdnssServersEntry 16777216}

er1646v2BgriMVPppOEIpV6RaDnsOptionsDnsslDomains OBJECT-TYPE
   SYNTAX      SEQUENCE OF Er1646v2BgriMVPppOEIpV6RaDnsOptionsDnsslDomainsEntry
   MAX-ACCESS  not-accessible
   STATUS      current
   DESCRIPTION
      ""
   ::= {er1646v2BgriMVPppOE 705039176}

er1646v2BgriMVPppOEIpV6RaDnsOptionsDnsslDomainsEntry OBJECT-TYPE
   SYNTAX      Er1646v2BgriMVPppOEIpV6RaDnsOptionsDnsslDomainsEntry
   MAX-ACCESS  not-accessible
   STATUS      current
   DESCRIPTION
      ""
   INDEX      { er1646v2BgriMVPppOEIpV6RaDnsOptionsDnsslDomainsGlobalIx,
                er1646v2BgriMVPppOETableIx,
                er1646v2BgriMVPppOEIpV6RaDnsOptionsDnsslDomainsTableIx }
   ::= {er1646v2BgriMVPppOEIpV6RaDnsOptionsDnsslDomains 1}

Er1646v2BgriMVPppOEIpV6RaDnsOptionsDnsslDomainsEntry ::=
   SEQUENCE
      {
      er1646v2BgriMVPppOEIpV6RaDnsOptionsDnsslDomainsActions
         VariableLengthTableActions,
      er1646v2BgriMVPppOEIpV6RaDnsOptionsDnsslDomainsGlobalIx
         GlobalIndex,
      er1646v2BgriMVPppOEIpV6RaDnsOptionsDnsslDomainsTableIx
         TableIndex,
      er1646v2BgriMVPppOEIpV6RaDnsOptionsDnsslDomainsName
         DisplayString
      }

er1646v2BgriMVPppOEIpV6RaDnsOptionsDnsslDomainsActions OBJECT-TYPE
   SYNTAX      VariableLengthTableActions
   MAX-ACCESS  read-write
   STATUS      current
   DESCRIPTION
      "By way of this field, some manipulations
       on this table may be performed."
   ::= {er1646v2BgriMVPppOEIpV6RaDnsOptionsDnsslDomainsEntry 2}

er1646v2BgriMVPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6RaDnsOptionsDnsslDomainsEntry 10}

er1646v2BgriMVPppOEIpV6RaDnsOptionsDnsslDomainsTableIx OBJECT-TYPE
   SYNTAX      TableIndex
   MAX-ACCESS  not-accessible
   STATUS      current
   DESCRIPTION
      ""
   ::= {er1646v2BgriMVPppOEIpV6RaDnsOptionsDnsslDomainsEntry 11}

er1646v2BgriMVPppOEIpV6RaDnsOptionsDnsslDomainsName OBJECT-TYPE
   SYNTAX      DisplayString
   MAX-ACCESS  read-write
   STATUS      current
   DESCRIPTION
      "Path: vpnBridgeGroup.editConf.pppoEClient.ipV6.ra.dnsOptions.dnssl.domains.name"
   ::= {er1646v2BgriMVPppOEIpV6RaDnsOptionsDnsslDomainsEntry 16777216}

er1646v2BgriMVPppOEIpV6DhcpClientUserClassOpt OBJECT-TYPE
   SYNTAX      SEQUENCE OF Er1646v2BgriMVPppOEIpV6DhcpClientUserClassOptEntry
   MAX-ACCESS  not-accessible
   STATUS      current
   DESCRIPTION
      ""
   ::= {er1646v2BgriMVPppOE 705312768}

er1646v2BgriMVPppOEIpV6DhcpClientUserClassOptEntry OBJECT-TYPE
   SYNTAX      Er1646v2BgriMVPppOEIpV6DhcpClientUserClassOptEntry
   MAX-ACCESS  not-accessible
   STATUS      current
   DESCRIPTION
      ""
   INDEX      { er1646v2BgriMVPppOEIpV6DhcpClientUserClassOptGlobalIx,
                er1646v2BgriMVPppOETableIx,
                er1646v2BgriMVPppOEIpV6DhcpClientUserClassOptTableIx }
   ::= {er1646v2BgriMVPppOEIpV6DhcpClientUserClassOpt 1}

Er1646v2BgriMVPppOEIpV6DhcpClientUserClassOptEntry ::=
   SEQUENCE
      {
      er1646v2BgriMVPppOEIpV6DhcpClientUserClassOptActions
         VariableLengthTableActions,
      er1646v2BgriMVPppOEIpV6DhcpClientUserClassOptGlobalIx
         GlobalIndex,
      er1646v2BgriMVPppOEIpV6DhcpClientUserClassOptTableIx
         TableIndex,
      er1646v2BgriMVPppOEIpV6DhcpClientUserClassOptValueAscii
         DisplayString,
      er1646v2BgriMVPppOEIpV6DhcpClientUserClassOptValueDecimal
         Integer32,
      er1646v2BgriMVPppOEIpV6DhcpClientUserClassOptValueHexData
         OCTET STRING
      }

er1646v2BgriMVPppOEIpV6DhcpClientUserClassOptActions OBJECT-TYPE
   SYNTAX      VariableLengthTableActions
   MAX-ACCESS  read-write
   STATUS      current
   DESCRIPTION
      "By way of this field, some manipulations
       on this table may be performed."
   ::= {er1646v2BgriMVPppOEIpV6DhcpClientUserClassOptEntry 2}

er1646v2BgriMVPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6DhcpClientUserClassOptEntry 10}

er1646v2BgriMVPppOEIpV6DhcpClientUserClassOptTableIx OBJECT-TYPE
   SYNTAX      TableIndex
   MAX-ACCESS  not-accessible
   STATUS      current
   DESCRIPTION
      ""
   ::= {er1646v2BgriMVPppOEIpV6DhcpClientUserClassOptEntry 11}

er1646v2BgriMVPppOEIpV6DhcpClientUserClassOptValueAscii OBJECT-TYPE
   SYNTAX      DisplayString
   MAX-ACCESS  read-write
   STATUS      current
   DESCRIPTION
      "Path: vpnBridgeGroup.editConf.pppoEClient.ipV6.dhcp.client.userClassOpt.value.ascii"
   ::= {er1646v2BgriMVPppOEIpV6DhcpClientUserClassOptEntry 16842752}

er1646v2BgriMVPppOEIpV6DhcpClientUserClassOptValueDecimal OBJECT-TYPE
   SYNTAX      Integer32
   MAX-ACCESS  read-write
   STATUS      current
   DESCRIPTION
      "Path: vpnBridgeGroup.editConf.pppoEClient.ipV6.dhcp.client.userClassOpt.value.decimal"
   ::= {er1646v2BgriMVPppOEIpV6DhcpClientUserClassOptEntry 16908288}

er1646v2BgriMVPppOEIpV6DhcpClientUserClassOptValueHexData OBJECT-TYPE
   SYNTAX      OCTET STRING
   MAX-ACCESS  read-write
   STATUS      current
   DESCRIPTION
      "Path: vpnBridgeGroup.editConf.pppoEClient.ipV6.dhcp.client.userClassOpt.value.hexData"
   ::= {er1646v2BgriMVPppOEIpV6DhcpClientUserClassOptEntry 16973824}

er1646v2BgriMVPppOEIpV6DhcpClientVendorCl OBJECT-TYPE
   SYNTAX      SEQUENCE OF Er1646v2BgriMVPppOEIpV6DhcpClientVendorClEntry
   MAX-ACCESS  not-accessible
   STATUS      current
   DESCRIPTION
      ""
   ::= {er1646v2BgriMVPppOE 705313792}

er1646v2BgriMVPppOEIpV6DhcpClientVendorClEntry OBJECT-TYPE
   SYNTAX      Er1646v2BgriMVPppOEIpV6DhcpClientVendorClEntry
   MAX-ACCESS  not-accessible
   STATUS      current
   DESCRIPTION
      ""
   INDEX      { er1646v2BgriMVPppOEIpV6DhcpClientVendorClGlobalIx,
                er1646v2BgriMVPppOETableIx,
                er1646v2BgriMVPppOEIpV6DhcpClientVendorClTableIx }
   ::= {er1646v2BgriMVPppOEIpV6DhcpClientVendorCl 1}

Er1646v2BgriMVPppOEIpV6DhcpClientVendorClEntry ::=
   SEQUENCE
      {
      er1646v2BgriMVPppOEIpV6DhcpClientVendorClActions
         VariableLengthTableActions,
      er1646v2BgriMVPppOEIpV6DhcpClientVendorClGlobalIx
         GlobalIndex,
      er1646v2BgriMVPppOEIpV6DhcpClientVendorClTableIx
         TableIndex,
      er1646v2BgriMVPppOEIpV6DhcpClientVendorClValueAscii
         DisplayString,
      er1646v2BgriMVPppOEIpV6DhcpClientVendorClValueDecimal
         Integer32,
      er1646v2BgriMVPppOEIpV6DhcpClientVendorClValueHexData
         OCTET STRING
      }

er1646v2BgriMVPppOEIpV6DhcpClientVendorClActions OBJECT-TYPE
   SYNTAX      VariableLengthTableActions
   MAX-ACCESS  read-write
   STATUS      current
   DESCRIPTION
      "By way of this field, some manipulations
       on this table may be performed."
   ::= {er1646v2BgriMVPppOEIpV6DhcpClientVendorClEntry 2}

er1646v2BgriMVPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6DhcpClientVendorClEntry 10}

er1646v2BgriMVPppOEIpV6DhcpClientVendorClTableIx OBJECT-TYPE
   SYNTAX      TableIndex
   MAX-ACCESS  not-accessible
   STATUS      current
   DESCRIPTION
      ""
   ::= {er1646v2BgriMVPppOEIpV6DhcpClientVendorClEntry 11}

er1646v2BgriMVPppOEIpV6DhcpClientVendorClValueAscii OBJECT-TYPE
   SYNTAX      DisplayString
   MAX-ACCESS  read-write
   STATUS      current
   DESCRIPTION
      "Path: vpnBridgeGroup.editConf.pppoEClient.ipV6.dhcp.client.vendorClassOpt.value.ascii"
   ::= {er1646v2BgriMVPppOEIpV6DhcpClientVendorClEntry 16842752}

er1646v2BgriMVPppOEIpV6DhcpClientVendorClValueDecimal OBJECT-TYPE
   SYNTAX      Integer32
   MAX-ACCESS  read-write
   STATUS      current
   DESCRIPTION
      "Path: vpnBridgeGroup.editConf.pppoEClient.ipV6.dhcp.client.vendorClassOpt.value.decimal"
   ::= {er1646v2BgriMVPppOEIpV6DhcpClientVendorClEntry 16908288}

er1646v2BgriMVPppOEIpV6DhcpClientVendorClValueHexData OBJECT-TYPE
   SYNTAX      OCTET STRING
   MAX-ACCESS  read-write
   STATUS      current
   DESCRIPTION
      "Path: vpnBridgeGroup.editConf.pppoEClient.ipV6.dhcp.client.vendorClassOpt.value.hexData"
   ::= {er1646v2BgriMVPppOEIpV6DhcpClientVendorClEntry 16973824}

er1646v2BgriMVPppOEIpV6DhcpRelayDestinations OBJECT-TYPE
   SYNTAX      SEQUENCE OF Er1646v2BgriMVPppOEIpV6DhcpRelayDestinationsEntry
   MAX-ACCESS  not-accessible
   STATUS      current
   DESCRIPTION
      ""
   ::= {er1646v2BgriMVPppOE 705323072}

er1646v2BgriMVPppOEIpV6DhcpRelayDestinationsEntry OBJECT-TYPE
   SYNTAX      Er1646v2BgriMVPppOEIpV6DhcpRelayDestinationsEntry
   MAX-ACCESS  not-accessible
   STATUS      current
   DESCRIPTION
      ""
   INDEX      { er1646v2BgriMVPppOEIpV6DhcpRelayDestinationsGlobalIx,
                er1646v2BgriMVPppOETableIx,
                er1646v2BgriMVPppOEIpV6DhcpRelayDestinationsTableIx }
   ::= {er1646v2BgriMVPppOEIpV6DhcpRelayDestinations 1}

Er1646v2BgriMVPppOEIpV6DhcpRelayDestinationsEntry ::=
   SEQUENCE
      {
      er1646v2BgriMVPppOEIpV6DhcpRelayDestinationsActions
         VariableLengthTableActions,
      er1646v2BgriMVPppOEIpV6DhcpRelayDestinationsGlobalIx
         GlobalIndex,
      er1646v2BgriMVPppOEIpV6DhcpRelayDestinationsTableIx
         TableIndex,
      er1646v2BgriMVPppOEIpV6DhcpRelayDestinationsAddress
         Ipv6Address,
      er1646v2BgriMVPppOEIpV6DhcpRelayDestinationsInterface
         DisplayString
      }

er1646v2BgriMVPppOEIpV6DhcpRelayDestinationsActions OBJECT-TYPE
   SYNTAX      VariableLengthTableActions
   MAX-ACCESS  read-write
   STATUS      current
   DESCRIPTION
      "By way of this field, some manipulations
       on this table may be performed."
   ::= {er1646v2BgriMVPppOEIpV6DhcpRelayDestinationsEntry 2}

er1646v2BgriMVPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2BgriMVPppOEIpV6DhcpRelayDestinationsEntry 10}

er1646v2BgriMVPppOEIpV6DhcpRelayDestinationsTableIx OBJECT-TYPE
   SYNTAX      TableIndex
   MAX-ACCESS  not-accessible
   STATUS      current
   DESCRIPTION
      ""
   ::= {er1646v2BgriMVPppOEIpV6DhcpRelayDestinationsEntry 11}

er1646v2BgriMVPppOEIpV6DhcpRelayDestinationsAddress OBJECT-TYPE
   SYNTAX      Ipv6Address
   MAX-ACCESS  read-write
   STATUS      current
   DESCRIPTION
      "Path: vpnBridgeGroup.editConf.pppoEClient.ipV6.dhcp.relay.destinations.address

       ipv6 address"
   ::= {er1646v2BgriMVPppOEIpV6DhcpRelayDestinationsEntry 16777216}

er1646v2BgriMVPppOEIpV6DhcpRelayDestinationsInterface OBJECT-TYPE
   SYNTAX      DisplayString
   MAX-ACCESS  read-write
   STATUS      current
   DESCRIPTION
      "Path: vpnBridgeGroup.editConf.pppoEClient.ipV6.dhcp.relay.destinations.interface"
   ::= {er1646v2BgriMVPppOEIpV6DhcpRelayDestinationsEntry 33554432}


er1646v2BgriMVSnmpIndexOffset OBJECT IDENTIFIER ::= {er1646v2BgriMV 268}

er1646v2BgriMVSnmpIndexOffsetTable OBJECT-TYPE
   SYNTAX      SEQUENCE OF Er1646v2BgriMVSnmpIndexOffsetEntry
   MAX-ACCESS  not-accessible
   STATUS      current
   DESCRIPTION
      "Preferred offset in the range of SNMP indices for this SWinst, 0 means automatic"
   ::= {er1646v2BgriMVSnmpIndexOffset 1}

er1646v2BgriMVSnmpIndexOffsetEntry OBJECT-TYPE
   SYNTAX      Er1646v2BgriMVSnmpIndexOffsetEntry
   MAX-ACCESS  not-accessible
   STATUS      current
   DESCRIPTION
      ""
   INDEX      { er1646v2BgriMVSnmpIndexOffsetGlobalIx }
   ::= {er1646v2BgriMVSnmpIndexOffsetTable 1}

Er1646v2BgriMVSnmpIndexOffsetEntry ::=
   SEQUENCE
      {
      er1646v2BgriMVSnmpIndexOffsetGlobalIx
         GlobalIndex,
      er1646v2BgriMVSnmpIndexOffsetValue
         Integer32
      }

er1646v2BgriMVSnmpIndexOffsetGlobalIx OBJECT-TYPE
   SYNTAX      GlobalIndex
   MAX-ACCESS  not-accessible
   STATUS      current
   DESCRIPTION
      "The value of the tlsCntTreeGlobalIndex of the MANAGED OBJECT."
   ::= {er1646v2BgriMVSnmpIndexOffsetEntry 10}

er1646v2BgriMVSnmpIndexOffsetValue OBJECT-TYPE
   SYNTAX      Integer32
   MAX-ACCESS  read-write
   STATUS      current
   DESCRIPTION
      "Path: vpnBridgeGroup.editConf.snmpIndexOffset"
   ::= {er1646v2BgriMVSnmpIndexOffsetEntry 2147483648}


er1646v2BgriMVMacAddress OBJECT IDENTIFIER ::= {er1646v2BgriMV 27}

er1646v2BgriMVMacAddressSSCTable OBJECT-TYPE
   SYNTAX      SEQUENCE OF Er1646v2BgriMVMacAddressEntry
   MAX-ACCESS  not-accessible
   STATUS      current
   DESCRIPTION
      "Configurable MAC address of Bridge group"
   ::= {er1646v2BgriMVMacAddress 1}

er1646v2BgriMVMacAddressEntry OBJECT-TYPE
   SYNTAX      Er1646v2BgriMVMacAddressEntry
   MAX-ACCESS  not-accessible
   STATUS      current
   DESCRIPTION
      ""
   INDEX      { er1646v2BgriMVMacAddressGlobalIx }
   ::= {er1646v2BgriMVMacAddressSSCTable 1}

Er1646v2BgriMVMacAddressEntry ::=
   SEQUENCE
      {
      er1646v2BgriMVMacAddressGlobalIx
         GlobalIndex,
      er1646v2BgriMVMacAddressDeviceMac
         DisplayString,
      er1646v2BgriMVMacAddressUserMac
         OCTET STRING,
      er1646v2BgriMVMacAddressRandomMac
         Integer32
      }

er1646v2BgriMVMacAddressGlobalIx OBJECT-TYPE
   SYNTAX      GlobalIndex
   MAX-ACCESS  not-accessible
   STATUS      current
   DESCRIPTION
      "The value of the tlsCntTreeGlobalIndex of the MANAGED OBJECT."
   ::= {er1646v2BgriMVMacAddressEntry 10}

er1646v2BgriMVMacAddressDeviceMac OBJECT-TYPE
   SYNTAX      DisplayString
   MAX-ACCESS  read-write
   STATUS      current
   DESCRIPTION
      "Path: vpnBridgeGroup.editConf.macAddress.deviceMac"
   ::= {er1646v2BgriMVMacAddressEntry 50331648}

er1646v2BgriMVMacAddressUserMac OBJECT-TYPE
   SYNTAX      OCTET STRING
   MAX-ACCESS  read-write
   STATUS      current
   DESCRIPTION
      "Path: vpnBridgeGroup.editConf.macAddress.userMac

       MAC address."
   ::= {er1646v2BgriMVMacAddressEntry 33554432}

er1646v2BgriMVMacAddressRandomMac OBJECT-TYPE
   SYNTAX      Integer32
   MAX-ACCESS  read-write
   STATUS      current
   DESCRIPTION
      "Path: vpnBridgeGroup.editConf.macAddress.randomMac"
   ::= {er1646v2BgriMVMacAddressEntry 67108864}


er1646v2BgriMVPppoEServer OBJECT IDENTIFIER ::= {er1646v2BgriMV 37}

er1646v2BgriMVPppoEServerTable OBJECT-TYPE
   SYNTAX      SEQUENCE OF Er1646v2BgriMVPppoEServerEntry
   MAX-ACCESS  not-accessible
   STATUS      current
   DESCRIPTION
      "ppp server name on interface"
   ::= {er1646v2BgriMVPppoEServer 1}

er1646v2BgriMVPppoEServerEntry OBJECT-TYPE
   SYNTAX      Er1646v2BgriMVPppoEServerEntry
   MAX-ACCESS  not-accessible
   STATUS      current
   DESCRIPTION
      ""
   INDEX      { er1646v2BgriMVPppoEServerGlobalIx }
   ::= {er1646v2BgriMVPppoEServerTable 1}

Er1646v2BgriMVPppoEServerEntry ::=
   SEQUENCE
      {
      er1646v2BgriMVPppoEServerGlobalIx
         GlobalIndex,
      er1646v2BgriMVPppoEServerValue
         DisplayString
      }

er1646v2BgriMVPppoEServerGlobalIx OBJECT-TYPE
   SYNTAX      GlobalIndex
   MAX-ACCESS  not-accessible
   STATUS      current
   DESCRIPTION
      "The value of the tlsCntTreeGlobalIndex of the MANAGED OBJECT."
   ::= {er1646v2BgriMVPppoEServerEntry 10}

er1646v2BgriMVPppoEServerValue OBJECT-TYPE
   SYNTAX      DisplayString
   MAX-ACCESS  read-write
   STATUS      current
   DESCRIPTION
      "Path: vpnBridgeGroup.editConf.pppoEServer"
   ::= {er1646v2BgriMVPppoEServerEntry 2147483648}



sr1646v2BgriMV OBJECT IDENTIFIER ::= {r1646v2BgriMV 14}


sr1646v2BgriMVBdgCache OBJECT IDENTIFIER ::= {sr1646v2BgriMV 3}

sr1646v2BgriMVBdgCacheSSCTable OBJECT-TYPE
   SYNTAX      SEQUENCE OF Sr1646v2BgriMVBdgCacheEntry
   MAX-ACCESS  not-accessible
   STATUS      current
   DESCRIPTION
      "bridge cache"
   ::= {sr1646v2BgriMVBdgCache 1}

sr1646v2BgriMVBdgCacheEntry OBJECT-TYPE
   SYNTAX      Sr1646v2BgriMVBdgCacheEntry
   MAX-ACCESS  not-accessible
   STATUS      current
   DESCRIPTION
      ""
   INDEX      { sr1646v2BgriMVBdgCacheGlobalIx,
                sr1646v2BgriMVBdgCacheTableIx }
   ::= {sr1646v2BgriMVBdgCacheSSCTable 1}

Sr1646v2BgriMVBdgCacheEntry ::=
   SEQUENCE
      {
      sr1646v2BgriMVBdgCacheGlobalIx
         GlobalIndex,
      sr1646v2BgriMVBdgCacheTableIx
         TableIndex,
      sr1646v2BgriMVBdgCacheIf
         DisplayString,
      sr1646v2BgriMVBdgCacheMacAddress
         OCTET STRING,
      sr1646v2BgriMVBdgCacheTpid
         INTEGER,
      sr1646v2BgriMVBdgCacheVlanId
         INTEGER,
      sr1646v2BgriMVBdgCacheTpid2
         INTEGER,
      sr1646v2BgriMVBdgCacheVlanId2
         INTEGER,
      sr1646v2BgriMVBdgCacheType
         INTEGER,
      sr1646v2BgriMVBdgCacheAge
         TimeTicks
      }

sr1646v2BgriMVBdgCacheGlobalIx OBJECT-TYPE
   SYNTAX      GlobalIndex
   MAX-ACCESS  not-accessible
   STATUS      current
   DESCRIPTION
      "The value of the tlsCntTreeGlobalIndex of the MANAGED OBJECT."
   ::= {sr1646v2BgriMVBdgCacheEntry 10}

sr1646v2BgriMVBdgCacheTableIx OBJECT-TYPE
   SYNTAX      TableIndex
   MAX-ACCESS  not-accessible
   STATUS      current
   DESCRIPTION
      ""
   ::= {sr1646v2BgriMVBdgCacheEntry 11}

sr1646v2BgriMVBdgCacheIf OBJECT-TYPE
   SYNTAX      DisplayString
   MAX-ACCESS  read-only
   STATUS      current
   DESCRIPTION
      "Path: vpnBridgeGroup.status.bridgeCache.interface"
   ::= {sr1646v2BgriMVBdgCacheEntry 16777216}

sr1646v2BgriMVBdgCacheMacAddress OBJECT-TYPE
   SYNTAX      OCTET STRING
   MAX-ACCESS  read-only
   STATUS      current
   DESCRIPTION
      "Path: vpnBridgeGroup.status.bridgeCache.macAddress

       MAC address."
   ::= {sr1646v2BgriMVBdgCacheEntry 33554432}

sr1646v2BgriMVBdgCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vpnBridgeGroup.status.bridgeCache.tpid

       Possibilities:
               untagged   (0)
               dot1q   (33024)
               dot1ad   (34984)
               group   (65534)
               notUsed   (65535)
               dot1qOrDot1ad   (65536)"
   ::= {sr1646v2BgriMVBdgCacheEntry 150994944}

sr1646v2BgriMVBdgCacheVlanId OBJECT-TYPE
   SYNTAX      INTEGER
               {
               undefined (-1)
               }
   MAX-ACCESS  read-only
   STATUS      current
   DESCRIPTION
      "Path: vpnBridgeGroup.status.bridgeCache.vlanId

       Possibilities:
               undefined   (-1)"
   ::= {sr1646v2BgriMVBdgCacheEntry 83886080}

sr1646v2BgriMVBdgCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vpnBridgeGroup.status.bridgeCache.tpid2

       Possibilities:
               untagged   (0)
               dot1q   (33024)
               dot1ad   (34984)
               group   (65534)
               notUsed   (65535)
               dot1qOrDot1ad   (65536)"
   ::= {sr1646v2BgriMVBdgCacheEntry 369098752}

sr1646v2BgriMVBdgCacheVlanId2 OBJECT-TYPE
   SYNTAX      INTEGER
               {
               undefined (-1)
               }
   MAX-ACCESS  read-only
   STATUS      current
   DESCRIPTION
      "Path: vpnBridgeGroup.status.bridgeCache.vlanId2

       Possibilities:
               undefined   (-1)"
   ::= {sr1646v2BgriMVBdgCacheEntry 385875968}

sr1646v2BgriMVBdgCacheType OBJECT-TYPE
   SYNTAX      INTEGER
               {
               static (0),
               dynamic (1),
               tester (2),
               fastFlood (3)
               }
   MAX-ACCESS  read-only
   STATUS      current
   DESCRIPTION
      "Path: vpnBridgeGroup.status.bridgeCache.type

       Possibilities:
               static   (0)
               dynamic   (1)
               tester   (2)
               fastFlood   (3)"
   ::= {sr1646v2BgriMVBdgCacheEntry 50331648}

sr1646v2BgriMVBdgCacheAge OBJECT-TYPE
   SYNTAX      TimeTicks
   MAX-ACCESS  read-only
   STATUS      current
   DESCRIPTION
      "Path: vpnBridgeGroup.status.bridgeCache.age

       Time in centi-second."
   ::= {sr1646v2BgriMVBdgCacheEntry 67108864}


sr1646v2BgriMVBridgeCacheSize OBJECT IDENTIFIER ::= {sr1646v2BgriMV 39}

sr1646v2BgriMVBridgeCacheSizeSSCTable OBJECT-TYPE
   SYNTAX      SEQUENCE OF Sr1646v2BgriMVBridgeCacheSizeEntry
   MAX-ACCESS  not-accessible
   STATUS      current
   DESCRIPTION
      "bridge cache size info"
   ::= {sr1646v2BgriMVBridgeCacheSize 1}

sr1646v2BgriMVBridgeCacheSizeEntry OBJECT-TYPE
   SYNTAX      Sr1646v2BgriMVBridgeCacheSizeEntry
   MAX-ACCESS  not-accessible
   STATUS      current
   DESCRIPTION
      ""
   INDEX      { sr1646v2BgriMVBridgeCacheSizeGlobalIx }
   ::= {sr1646v2BgriMVBridgeCacheSizeSSCTable 1}

Sr1646v2BgriMVBridgeCacheSizeEntry ::=
   SEQUENCE
      {
      sr1646v2BgriMVBridgeCacheSizeGlobalIx
         GlobalIndex,
      sr1646v2BgriMVBridgeCacheSizeSize
         Counter32,
      sr1646v2BgriMVBridgeCacheSizeMaxSize
         INTEGER
      }

sr1646v2BgriMVBridgeCacheSizeGlobalIx OBJECT-TYPE
   SYNTAX      GlobalIndex
   MAX-ACCESS  not-accessible
   STATUS      current
   DESCRIPTION
      "The value of the tlsCntTreeGlobalIndex of the MANAGED OBJECT."
   ::= {sr1646v2BgriMVBridgeCacheSizeEntry 10}

sr1646v2BgriMVBridgeCacheSizeSize OBJECT-TYPE
   SYNTAX      Counter32
   MAX-ACCESS  read-only
   STATUS      current
   DESCRIPTION
      "Path: vpnBridgeGroup.status.bridgeCacheSize.size

       32 bit unsigned wrappable counter."
   ::= {sr1646v2BgriMVBridgeCacheSizeEntry 16777216}

sr1646v2BgriMVBridgeCacheSizeMaxSize OBJECT-TYPE
   SYNTAX      INTEGER
               {
               unlimited (0)
               }
   MAX-ACCESS  read-only
   STATUS      current
   DESCRIPTION
      "Path: vpnBridgeGroup.status.bridgeCacheSize.maxSize

       Possibilities:
               unlimited   (0)"
   ::= {sr1646v2BgriMVBridgeCacheSizeEntry 33554432}


sr1646v2BgriMVMacAddress OBJECT IDENTIFIER ::= {sr1646v2BgriMV 105}

sr1646v2BgriMVMacAddressTable OBJECT-TYPE
   SYNTAX      SEQUENCE OF Sr1646v2BgriMVMacAddressEntry
   MAX-ACCESS  not-accessible
   STATUS      current
   DESCRIPTION
      "ifPhysAddress"
   ::= {sr1646v2BgriMVMacAddress 1}

sr1646v2BgriMVMacAddressEntry OBJECT-TYPE
   SYNTAX      Sr1646v2BgriMVMacAddressEntry
   MAX-ACCESS  not-accessible
   STATUS      current
   DESCRIPTION
      ""
   INDEX      { sr1646v2BgriMVMacAddressGlobalIx }
   ::= {sr1646v2BgriMVMacAddressTable 1}

Sr1646v2BgriMVMacAddressEntry ::=
   SEQUENCE
      {
      sr1646v2BgriMVMacAddressGlobalIx
         GlobalIndex,
      sr1646v2BgriMVMacAddressValue
         OCTET STRING
      }

sr1646v2BgriMVMacAddressGlobalIx OBJECT-TYPE
   SYNTAX      GlobalIndex
   MAX-ACCESS  not-accessible
   STATUS      current
   DESCRIPTION
      "The value of the tlsCntTreeGlobalIndex of the MANAGED OBJECT."
   ::= {sr1646v2BgriMVMacAddressEntry 10}

sr1646v2BgriMVMacAddressValue OBJECT-TYPE
   SYNTAX      OCTET STRING
   MAX-ACCESS  read-only
   STATUS      current
   DESCRIPTION
      "Path: vpnBridgeGroup.status.macAddress

       MAC address."
   ::= {sr1646v2BgriMVMacAddressEntry 2147483648}


sr1646v2BgriMVDescr OBJECT IDENTIFIER ::= {sr1646v2BgriMV 101}

sr1646v2BgriMVDescrTable OBJECT-TYPE
   SYNTAX      SEQUENCE OF Sr1646v2BgriMVDescrEntry
   MAX-ACCESS  not-accessible
   STATUS      current
   DESCRIPTION
      "ifDescr"
   ::= {sr1646v2BgriMVDescr 1}

sr1646v2BgriMVDescrEntry OBJECT-TYPE
   SYNTAX      Sr1646v2BgriMVDescrEntry
   MAX-ACCESS  not-accessible
   STATUS      current
   DESCRIPTION
      ""
   INDEX      { sr1646v2BgriMVDescrGlobalIx }
   ::= {sr1646v2BgriMVDescrTable 1}

Sr1646v2BgriMVDescrEntry ::=
   SEQUENCE
      {
      sr1646v2BgriMVDescrGlobalIx
         GlobalIndex,
      sr1646v2BgriMVDescrValue
         DisplayString
      }

sr1646v2BgriMVDescrGlobalIx OBJECT-TYPE
   SYNTAX      GlobalIndex
   MAX-ACCESS  not-accessible
   STATUS      current
   DESCRIPTION
      "The value of the tlsCntTreeGlobalIndex of the MANAGED OBJECT."
   ::= {sr1646v2BgriMVDescrEntry 10}

sr1646v2BgriMVDescrValue OBJECT-TYPE
   SYNTAX      DisplayString
   MAX-ACCESS  read-only
   STATUS      current
   DESCRIPTION
      "Path: vpnBridgeGroup.status.ifDescr"
   ::= {sr1646v2BgriMVDescrEntry 2147483648}


sr1646v2BgriMVType OBJECT IDENTIFIER ::= {sr1646v2BgriMV 102}

sr1646v2BgriMVTypeTable OBJECT-TYPE
   SYNTAX      SEQUENCE OF Sr1646v2BgriMVTypeEntry
   MAX-ACCESS  not-accessible
   STATUS      current
   DESCRIPTION
      "ifType"
   ::= {sr1646v2BgriMVType 1}

sr1646v2BgriMVTypeEntry OBJECT-TYPE
   SYNTAX      Sr1646v2BgriMVTypeEntry
   MAX-ACCESS  not-accessible
   STATUS      current
   DESCRIPTION
      ""
   INDEX      { sr1646v2BgriMVTypeGlobalIx }
   ::= {sr1646v2BgriMVTypeTable 1}

Sr1646v2BgriMVTypeEntry ::=
   SEQUENCE
      {
      sr1646v2BgriMVTypeGlobalIx
         GlobalIndex,
      sr1646v2BgriMVTypeValue
         INTEGER
      }

sr1646v2BgriMVTypeGlobalIx OBJECT-TYPE
   SYNTAX      GlobalIndex
   MAX-ACCESS  not-accessible
   STATUS      current
   DESCRIPTION
      "The value of the tlsCntTreeGlobalIndex of the MANAGED OBJECT."
   ::= {sr1646v2BgriMVTypeEntry 10}

sr1646v2BgriMVTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: vpnBridgeGroup.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2BgriMVTypeEntry 2147483648}


sr1646v2BgriMVMtu OBJECT IDENTIFIER ::= {sr1646v2BgriMV 103}

sr1646v2BgriMVMtuTable OBJECT-TYPE
   SYNTAX      SEQUENCE OF Sr1646v2BgriMVMtuEntry
   MAX-ACCESS  not-accessible
   STATUS      current
   DESCRIPTION
      "ifMtu"
   ::= {sr1646v2BgriMVMtu 1}

sr1646v2BgriMVMtuEntry OBJECT-TYPE
   SYNTAX      Sr1646v2BgriMVMtuEntry
   MAX-ACCESS  not-accessible
   STATUS      current
   DESCRIPTION
      ""
   INDEX      { sr1646v2BgriMVMtuGlobalIx }
   ::= {sr1646v2BgriMVMtuTable 1}

Sr1646v2BgriMVMtuEntry ::=
   SEQUENCE
      {
      sr1646v2BgriMVMtuGlobalIx
         GlobalIndex,
      sr1646v2BgriMVMtuValue
         Integer32
      }

sr1646v2BgriMVMtuGlobalIx OBJECT-TYPE
   SYNTAX      GlobalIndex
   MAX-ACCESS  not-accessible
   STATUS      current
   DESCRIPTION
      "The value of the tlsCntTreeGlobalIndex of the MANAGED OBJECT."
   ::= {sr1646v2BgriMVMtuEntry 10}

sr1646v2BgriMVMtuValue OBJECT-TYPE
   SYNTAX      Integer32
   MAX-ACCESS  read-only
   STATUS      current
   DESCRIPTION
      "Path: vpnBridgeGroup.status.ifMtu"
   ::= {sr1646v2BgriMVMtuEntry 2147483648}


sr1646v2BgriMVOperStatus OBJECT IDENTIFIER ::= {sr1646v2BgriMV 107}

sr1646v2BgriMVOperStatusTable OBJECT-TYPE
   SYNTAX      SEQUENCE OF Sr1646v2BgriMVOperStatusEntry
   MAX-ACCESS  not-accessible
   STATUS      current
   DESCRIPTION
      "ifOperStatus"
   ::= {sr1646v2BgriMVOperStatus 1}

sr1646v2BgriMVOperStatusEntry OBJECT-TYPE
   SYNTAX      Sr1646v2BgriMVOperStatusEntry
   MAX-ACCESS  not-accessible
   STATUS      current
   DESCRIPTION
      ""
   INDEX      { sr1646v2BgriMVOperStatusGlobalIx }
   ::= {sr1646v2BgriMVOperStatusTable 1}

Sr1646v2BgriMVOperStatusEntry ::=
   SEQUENCE
      {
      sr1646v2BgriMVOperStatusGlobalIx
         GlobalIndex,
      sr1646v2BgriMVOperStatusValue
         INTEGER
      }

sr1646v2BgriMVOperStatusGlobalIx OBJECT-TYPE
   SYNTAX      GlobalIndex
   MAX-ACCESS  not-accessible
   STATUS      current
   DESCRIPTION
      "The value of the tlsCntTreeGlobalIndex of the MANAGED OBJECT."
   ::= {sr1646v2BgriMVOperStatusEntry 10}

sr1646v2BgriMVOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vpnBridgeGroup.status.ifOperStatus

       Possibilities:
               up   (1)
               down   (2)
               testing   (3)
               unknown   (4)
               dormant   (5)
               notPresent   (6)
               lowerLayerDown   (7)"
   ::= {sr1646v2BgriMVOperStatusEntry 2147483648}


sr1646v2BgriMVIp OBJECT IDENTIFIER ::= {sr1646v2BgriMV 11}

sr1646v2BgriMVIpSSCTable OBJECT-TYPE
   SYNTAX      SEQUENCE OF Sr1646v2BgriMVIpEntry
   MAX-ACCESS  not-accessible
   STATUS      current
   DESCRIPTION
      "Ip status parameters of a bridge gateway"
   ::= {sr1646v2BgriMVIp 1}

sr1646v2BgriMVIpEntry OBJECT-TYPE
   SYNTAX      Sr1646v2BgriMVIpEntry
   MAX-ACCESS  not-accessible
   STATUS      current
   DESCRIPTION
      ""
   INDEX      { sr1646v2BgriMVIpGlobalIx }
   ::= {sr1646v2BgriMVIpSSCTable 1}

Sr1646v2BgriMVIpEntry ::=
   SEQUENCE
      {
      sr1646v2BgriMVIpGlobalIx
         GlobalIndex,
      sr1646v2BgriMVIpAddress
         IpAddress,
      sr1646v2BgriMVIpNetMask
         IpAddress,
      sr1646v2BgriMVIpDhcpStatus
         INTEGER,
      sr1646v2BgriMVIpDhcpLeaseTime
         TimeTicks
      }

sr1646v2BgriMVIpGlobalIx OBJECT-TYPE
   SYNTAX      GlobalIndex
   MAX-ACCESS  not-accessible
   STATUS      current
   DESCRIPTION
      "The value of the tlsCntTreeGlobalIndex of the MANAGED OBJECT."
   ::= {sr1646v2BgriMVIpEntry 10}

sr1646v2BgriMVIpAddress OBJECT-TYPE
   SYNTAX      IpAddress
   MAX-ACCESS  read-only
   STATUS      current
   DESCRIPTION
      "Path: vpnBridgeGroup.status.ip.address"
   ::= {sr1646v2BgriMVIpEntry 268435456}

sr1646v2BgriMVIpNetMask OBJECT-TYPE
   SYNTAX      IpAddress
   MAX-ACCESS  read-only
   STATUS      current
   DESCRIPTION
      "Path: vpnBridgeGroup.status.ip.netMask"
   ::= {sr1646v2BgriMVIpEntry 285212672}

sr1646v2BgriMVIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: vpnBridgeGroup.status.ip.dhcp.status

       Possibilities:
               none   (0)
               selecting   (1)
               requesting   (2)
               rebinding   (3)
               bound   (4)
               renewing   (5)
               rebooting   (6)
               initreboot   (7)"
   ::= {sr1646v2BgriMVIpEntry 402718720}

sr1646v2BgriMVIpDhcpLeaseTime OBJECT-TYPE
   SYNTAX      TimeTicks
   MAX-ACCESS  read-only
   STATUS      current
   DESCRIPTION
      "Path: vpnBridgeGroup.status.ip.dhcp.leaseTime

       Time in centi-second."
   ::= {sr1646v2BgriMVIpEntry 402784256}

sr1646v2BgriMVIpSecondaryIp OBJECT-TYPE
   SYNTAX      SEQUENCE OF Sr1646v2BgriMVIpSecondaryIpEntry
   MAX-ACCESS  not-accessible
   STATUS      current
   DESCRIPTION
      ""
   ::= {sr1646v2BgriMVIp 385875968}

sr1646v2BgriMVIpSecondaryIpEntry OBJECT-TYPE
   SYNTAX      Sr1646v2BgriMVIpSecondaryIpEntry
   MAX-ACCESS  not-accessible
   STATUS      current
   DESCRIPTION
      ""
   INDEX      { sr1646v2BgriMVIpSecondaryIpGlobalIx,
                sr1646v2BgriMVIpSecondaryIpTableIx }
   ::= {sr1646v2BgriMVIpSecondaryIp 1}

Sr1646v2BgriMVIpSecondaryIpEntry ::=
   SEQUENCE
      {
      sr1646v2BgriMVIpSecondaryIpGlobalIx
         GlobalIndex,
      sr1646v2BgriMVIpSecondaryIpTableIx
         TableIndex,
      sr1646v2BgriMVIpSecondaryIpAddress
         IpAddress,
      sr1646v2BgriMVIpSecondaryIpNetMask
         IpAddress
      }

sr1646v2BgriMVIpSecondaryIpGlobalIx OBJECT-TYPE
   SYNTAX      GlobalIndex
   MAX-ACCESS  not-accessible
   STATUS      current
   DESCRIPTION
      "The value of the tlsCntTreeGlobalIndex of the MANAGED OBJECT."
   ::= {sr1646v2BgriMVIpSecondaryIpEntry 10}

sr1646v2BgriMVIpSecondaryIpTableIx OBJECT-TYPE
   SYNTAX      TableIndex
   MAX-ACCESS  not-accessible
   STATUS      current
   DESCRIPTION
      ""
   ::= {sr1646v2BgriMVIpSecondaryIpEntry 11}

sr1646v2BgriMVIpSecondaryIpAddress OBJECT-TYPE
   SYNTAX      IpAddress
   MAX-ACCESS  read-only
   STATUS      current
   DESCRIPTION
      "Path: vpnBridgeGroup.status.ip.secondaryIp.address"
   ::= {sr1646v2BgriMVIpSecondaryIpEntry 2030043136}

sr1646v2BgriMVIpSecondaryIpNetMask OBJECT-TYPE
   SYNTAX      IpAddress
   MAX-ACCESS  read-only
   STATUS      current
   DESCRIPTION
      "Path: vpnBridgeGroup.status.ip.secondaryIp.netMask"
   ::= {sr1646v2BgriMVIpSecondaryIpEntry 2063597568}


sr1646v2BgriMVIpV6 OBJECT IDENTIFIER ::= {sr1646v2BgriMV 22}

sr1646v2BgriMVIpV6SSCTable OBJECT-TYPE
   SYNTAX      SEQUENCE OF Sr1646v2BgriMVIpV6Entry
   MAX-ACCESS  not-accessible
   STATUS      current
   DESCRIPTION
      "IPv6 interface config parameters"
   ::= {sr1646v2BgriMVIpV6 1}

sr1646v2BgriMVIpV6Entry OBJECT-TYPE
   SYNTAX      Sr1646v2BgriMVIpV6Entry
   MAX-ACCESS  not-accessible
   STATUS      current
   DESCRIPTION
      ""
   INDEX      { sr1646v2BgriMVIpV6GlobalIx }
   ::= {sr1646v2BgriMVIpV6SSCTable 1}

Sr1646v2BgriMVIpV6Entry ::=
   SEQUENCE
      {
      sr1646v2BgriMVIpV6GlobalIx
         GlobalIndex,
      sr1646v2BgriMVIpV6State
         INTEGER,
      sr1646v2BgriMVIpV6InterfaceId
         OCTET STRING,
      sr1646v2BgriMVIpV6LinkMtu
         Integer32,
      sr1646v2BgriMVIpV6HopLimit
         Integer32,
      sr1646v2BgriMVIpV6DhcpIaid
         Counter32,
      sr1646v2BgriMVIpV6RaRcvOption
         Integer32
      }

sr1646v2BgriMVIpV6GlobalIx OBJECT-TYPE
   SYNTAX      GlobalIndex
   MAX-ACCESS  not-accessible
   STATUS      current
   DESCRIPTION
      "The value of the tlsCntTreeGlobalIndex of the MANAGED OBJECT."
   ::= {sr1646v2BgriMVIpV6Entry 10}

sr1646v2BgriMVIpV6State OBJECT-TYPE
   SYNTAX      INTEGER
               {
               disabled (0),
               enabled (1)
               }
   MAX-ACCESS  read-only
   STATUS      current
   DESCRIPTION
      "Path: vpnBridgeGroup.status.ipV6.state

       Possibilities:
               disabled   (0)
               enabled   (1)"
   ::= {sr1646v2BgriMVIpV6Entry 16777216}

sr1646v2BgriMVIpV6InterfaceId OBJECT-TYPE
   SYNTAX      OCTET STRING
   MAX-ACCESS  read-only
   STATUS      current
   DESCRIPTION
      "Path: vpnBridgeGroup.status.ipV6.interfaceId"
   ::= {sr1646v2BgriMVIpV6Entry 33554432}

sr1646v2BgriMVIpV6LinkMtu OBJECT-TYPE
   SYNTAX      Integer32
   MAX-ACCESS  read-only
   STATUS      current
   DESCRIPTION
      "Path: vpnBridgeGroup.status.ipV6.linkMtu"
   ::= {sr1646v2BgriMVIpV6Entry 67108864}

sr1646v2BgriMVIpV6HopLimit OBJECT-TYPE
   SYNTAX      Integer32
   MAX-ACCESS  read-only
   STATUS      current
   DESCRIPTION
      "Path: vpnBridgeGroup.status.ipV6.hopLimit"
   ::= {sr1646v2BgriMVIpV6Entry 83886080}

sr1646v2BgriMVIpV6DhcpIaid OBJECT-TYPE
   SYNTAX      Counter32
   MAX-ACCESS  read-only
   STATUS      current
   DESCRIPTION
      "Path: vpnBridgeGroup.status.ipV6.dhcp.iaid

       32 bit unsigned wrappable counter."
   ::= {sr1646v2BgriMVIpV6Entry 100728832}

sr1646v2BgriMVIpV6RaRcvOption OBJECT-TYPE
   SYNTAX      Integer32
   MAX-ACCESS  read-only
   STATUS      current
   DESCRIPTION
      "Path: vpnBridgeGroup.status.ipV6.raRcvOption

       Bit meanings:
               bit 0 = linkMtu,
               bit 1 = srcLinkLayer,
               bit 2 = prefixInfo,
               bit 3 = rdnss,
               bit 4 = dnssl"
   ::= {sr1646v2BgriMVIpV6Entry 117440512}

sr1646v2BgriMVIpV6Addresses OBJECT-TYPE
   SYNTAX      SEQUENCE OF Sr1646v2BgriMVIpV6AddressesEntry
   MAX-ACCESS  not-accessible
   STATUS      current
   DESCRIPTION
      ""
   ::= {sr1646v2BgriMVIpV6 50331648}

sr1646v2BgriMVIpV6AddressesEntry OBJECT-TYPE
   SYNTAX      Sr1646v2BgriMVIpV6AddressesEntry
   MAX-ACCESS  not-accessible
   STATUS      current
   DESCRIPTION
      ""
   INDEX      { sr1646v2BgriMVIpV6AddressesGlobalIx,
                sr1646v2BgriMVIpV6AddressesTableIx }
   ::= {sr1646v2BgriMVIpV6Addresses 1}

Sr1646v2BgriMVIpV6AddressesEntry ::=
   SEQUENCE
      {
      sr1646v2BgriMVIpV6AddressesGlobalIx
         GlobalIndex,
      sr1646v2BgriMVIpV6AddressesTableIx
         TableIndex,
      sr1646v2BgriMVIpV6AddressesAddress
         Ipv6Address,
      sr1646v2BgriMVIpV6AddressesPrefixLength
         Integer32,
      sr1646v2BgriMVIpV6AddressesStatus
         INTEGER,
      sr1646v2BgriMVIpV6AddressesOrigin
         INTEGER,
      sr1646v2BgriMVIpV6AddressesFlagsInterfaceId
         INTEGER,
      sr1646v2BgriMVIpV6AddressesFlagsAnycast
         INTEGER,
      sr1646v2BgriMVIpV6AddressesTimersValidLifeTime
         TimeTicks,
      sr1646v2BgriMVIpV6AddressesTimersPrefLifeTime
         TimeTicks
      }

sr1646v2BgriMVIpV6AddressesGlobalIx OBJECT-TYPE
   SYNTAX      GlobalIndex
   MAX-ACCESS  not-accessible
   STATUS      current
   DESCRIPTION
      "The value of the tlsCntTreeGlobalIndex of the MANAGED OBJECT."
   ::= {sr1646v2BgriMVIpV6AddressesEntry 10}

sr1646v2BgriMVIpV6AddressesTableIx OBJECT-TYPE
   SYNTAX      TableIndex
   MAX-ACCESS  not-accessible
   STATUS      current
   DESCRIPTION
      ""
   ::= {sr1646v2BgriMVIpV6AddressesEntry 11}

sr1646v2BgriMVIpV6AddressesAddress OBJECT-TYPE
   SYNTAX      Ipv6Address
   MAX-ACCESS  read-only
   STATUS      current
   DESCRIPTION
      "Path: vpnBridgeGroup.status.ipV6.addresses.address

       ipv6 address"
   ::= {sr1646v2BgriMVIpV6AddressesEntry 16777216}

sr1646v2BgriMVIpV6AddressesPrefixLength OBJECT-TYPE
   SYNTAX      Integer32
   MAX-ACCESS  read-only
   STATUS      current
   DESCRIPTION
      "Path: vpnBridgeGroup.status.ipV6.addresses.prefixLength"
   ::= {sr1646v2BgriMVIpV6AddressesEntry 33554432}

sr1646v2BgriMVIpV6AddressesStatus OBJECT-TYPE
   SYNTAX      INTEGER
               {
               invalid (0),
               tentative (1),
               deprecated (2),
               preferred (3)
               }
   MAX-ACCESS  read-only
   STATUS      current
   DESCRIPTION
      "Path: vpnBridgeGroup.status.ipV6.addresses.status

       Possibilities:
               invalid   (0)
               tentative   (1)
               deprecated   (2)
               preferred   (3)"
   ::= {sr1646v2BgriMVIpV6AddressesEntry 50331648}

sr1646v2BgriMVIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vpnBridgeGroup.status.ipV6.addresses.origin

       Possibilities:
               unknown   (0)
               manual   (1)
               generalPrefix   (2)
               statelessAuto   (3)
               statefullAuto   (4)"
   ::= {sr1646v2BgriMVIpV6AddressesEntry 67108864}

sr1646v2BgriMVIpV6AddressesFlagsInterfaceId OBJECT-TYPE
   SYNTAX      INTEGER
               {
               no (0),
               yes (1)
               }
   MAX-ACCESS  read-only
   STATUS      current
   DESCRIPTION
      "Path: vpnBridgeGroup.status.ipV6.addresses.flags.interfaceId

       Possibilities:
               no   (0)
               yes   (1)"
   ::= {sr1646v2BgriMVIpV6AddressesEntry 83951616}

sr1646v2BgriMVIpV6AddressesFlagsAnycast OBJECT-TYPE
   SYNTAX      INTEGER
               {
               no (0),
               yes (1)
               }
   MAX-ACCESS  read-only
   STATUS      current
   DESCRIPTION
      "Path: vpnBridgeGroup.status.ipV6.addresses.flags.anycast

       Possibilities:
               no   (0)
               yes   (1)"
   ::= {sr1646v2BgriMVIpV6AddressesEntry 84017152}

sr1646v2BgriMVIpV6AddressesTimersValidLifeTime OBJECT-TYPE
   SYNTAX      TimeTicks
   MAX-ACCESS  read-only
   STATUS      current
   DESCRIPTION
      "Path: vpnBridgeGroup.status.ipV6.addresses.timers.validLifeTime

       Time in centi-second."
   ::= {sr1646v2BgriMVIpV6AddressesEntry 100794368}

sr1646v2BgriMVIpV6AddressesTimersPrefLifeTime OBJECT-TYPE
   SYNTAX      TimeTicks
   MAX-ACCESS  read-only
   STATUS      current
   DESCRIPTION
      "Path: vpnBridgeGroup.status.ipV6.addresses.timers.prefLifeTime

       Time in centi-second."
   ::= {sr1646v2BgriMVIpV6AddressesEntry 100728832}


sr1646v2BgriMVStp OBJECT IDENTIFIER ::= {sr1646v2BgriMV 9}

sr1646v2BgriMVStpSSCTable OBJECT-TYPE
   SYNTAX      SEQUENCE OF Sr1646v2BgriMVStpEntry
   MAX-ACCESS  not-accessible
   STATUS      current
   DESCRIPTION
      "spanning tree info on bridge group"
   ::= {sr1646v2BgriMVStp 1}

sr1646v2BgriMVStpEntry OBJECT-TYPE
   SYNTAX      Sr1646v2BgriMVStpEntry
   MAX-ACCESS  not-accessible
   STATUS      current
   DESCRIPTION
      ""
   INDEX      { sr1646v2BgriMVStpGlobalIx }
   ::= {sr1646v2BgriMVStpSSCTable 1}

Sr1646v2BgriMVStpEntry ::=
   SEQUENCE
      {
      sr1646v2BgriMVStpGlobalIx
         GlobalIndex,
      sr1646v2BgriMVStpBridgePriority
         Integer32,
      sr1646v2BgriMVStpBridgeMacAddress
         OCTET STRING,
      sr1646v2BgriMVStpBridgeTimesMessageAge
         TimeTicks,
      sr1646v2BgriMVStpBridgeTimesMaxAge
         TimeTicks,
      sr1646v2BgriMVStpBridgeTimesForwardDelay
         TimeTicks,
      sr1646v2BgriMVStpBridgeTimesNrHops
         Integer32,
      sr1646v2BgriMVStpRootBridgeIdPriority
         Integer32,
      sr1646v2BgriMVStpRootBridgeIdMacAddress
         OCTET STRING,
      sr1646v2BgriMVStpRootPortId
         Integer32,
      sr1646v2BgriMVStpExtRootPathCost
         Integer32,
      sr1646v2BgriMVStpIntRootPathCost
         Integer32,
      sr1646v2BgriMVStpMstConfigIdFormatSelector
         Integer32,
      sr1646v2BgriMVStpMstConfigIdName
         DisplayString,
      sr1646v2BgriMVStpMstConfigIdRevisionLevel
         Integer32,
      sr1646v2BgriMVStpMstConfigIdDigest
         OCTET STRING
      }

sr1646v2BgriMVStpGlobalIx OBJECT-TYPE
   SYNTAX      GlobalIndex
   MAX-ACCESS  not-accessible
   STATUS      current
   DESCRIPTION
      "The value of the tlsCntTreeGlobalIndex of the MANAGED OBJECT."
   ::= {sr1646v2BgriMVStpEntry 10}

sr1646v2BgriMVStpBridgePriority OBJECT-TYPE
   SYNTAX      Integer32
   MAX-ACCESS  read-only
   STATUS      current
   DESCRIPTION
      "Path: vpnBridgeGroup.status.spanningTree.bridgePriority"
   ::= {sr1646v2BgriMVStpEntry 16777216}

sr1646v2BgriMVStpBridgeMacAddress OBJECT-TYPE
   SYNTAX      OCTET STRING
   MAX-ACCESS  read-only
   STATUS      current
   DESCRIPTION
      "Path: vpnBridgeGroup.status.spanningTree.bridgeMacAddress

       MAC address."
   ::= {sr1646v2BgriMVStpEntry 33554432}

sr1646v2BgriMVStpBridgeTimesMessageAge OBJECT-TYPE
   SYNTAX      TimeTicks
   MAX-ACCESS  read-only
   STATUS      current
   DESCRIPTION
      "Path: vpnBridgeGroup.status.spanningTree.bridgeTimes.messageAge

       Time in centi-second."
   ::= {sr1646v2BgriMVStpEntry 50397184}

sr1646v2BgriMVStpBridgeTimesMaxAge OBJECT-TYPE
   SYNTAX      TimeTicks
   MAX-ACCESS  read-only
   STATUS      current
   DESCRIPTION
      "Path: vpnBridgeGroup.status.spanningTree.bridgeTimes.maxAge

       Time in centi-second."
   ::= {sr1646v2BgriMVStpEntry 50462720}

sr1646v2BgriMVStpBridgeTimesForwardDelay OBJECT-TYPE
   SYNTAX      TimeTicks
   MAX-ACCESS  read-only
   STATUS      current
   DESCRIPTION
      "Path: vpnBridgeGroup.status.spanningTree.bridgeTimes.forwardDelay

       Time in centi-second."
   ::= {sr1646v2BgriMVStpEntry 50528256}

sr1646v2BgriMVStpBridgeTimesNrHops OBJECT-TYPE
   SYNTAX      Integer32
   MAX-ACCESS  read-only
   STATUS      current
   DESCRIPTION
      "Path: vpnBridgeGroup.status.spanningTree.bridgeTimes.nrHops"
   ::= {sr1646v2BgriMVStpEntry 50593792}

sr1646v2BgriMVStpRootBridgeIdPriority OBJECT-TYPE
   SYNTAX      Integer32
   MAX-ACCESS  read-only
   STATUS      current
   DESCRIPTION
      "Path: vpnBridgeGroup.status.spanningTree.rootBridgeId.priority"
   ::= {sr1646v2BgriMVStpEntry 67174400}

sr1646v2BgriMVStpRootBridgeIdMacAddress OBJECT-TYPE
   SYNTAX      OCTET STRING
   MAX-ACCESS  read-only
   STATUS      current
   DESCRIPTION
      "Path: vpnBridgeGroup.status.spanningTree.rootBridgeId.macAddress

       MAC address."
   ::= {sr1646v2BgriMVStpEntry 67239936}

sr1646v2BgriMVStpRootPortId OBJECT-TYPE
   SYNTAX      Integer32
   MAX-ACCESS  read-only
   STATUS      current
   DESCRIPTION
      "Path: vpnBridgeGroup.status.spanningTree.rootPortId"
   ::= {sr1646v2BgriMVStpEntry 83886080}

sr1646v2BgriMVStpExtRootPathCost OBJECT-TYPE
   SYNTAX      Integer32
   MAX-ACCESS  read-only
   STATUS      current
   DESCRIPTION
      "Path: vpnBridgeGroup.status.spanningTree.extRootPathCost"
   ::= {sr1646v2BgriMVStpEntry 100663296}

sr1646v2BgriMVStpIntRootPathCost OBJECT-TYPE
   SYNTAX      Integer32
   MAX-ACCESS  read-only
   STATUS      current
   DESCRIPTION
      "Path: vpnBridgeGroup.status.spanningTree.intRootPathCost"
   ::= {sr1646v2BgriMVStpEntry 117440512}

sr1646v2BgriMVStpMstConfigIdFormatSelector OBJECT-TYPE
   SYNTAX      Integer32
   MAX-ACCESS  read-only
   STATUS      current
   DESCRIPTION
      "Path: vpnBridgeGroup.status.spanningTree.mstConfigId.formatSelector"
   ::= {sr1646v2BgriMVStpEntry 134283264}

sr1646v2BgriMVStpMstConfigIdName OBJECT-TYPE
   SYNTAX      DisplayString
   MAX-ACCESS  read-only
   STATUS      current
   DESCRIPTION
      "Path: vpnBridgeGroup.status.spanningTree.mstConfigId.name"
   ::= {sr1646v2BgriMVStpEntry 134348800}

sr1646v2BgriMVStpMstConfigIdRevisionLevel OBJECT-TYPE
   SYNTAX      Integer32
   MAX-ACCESS  read-only
   STATUS      current
   DESCRIPTION
      "Path: vpnBridgeGroup.status.spanningTree.mstConfigId.revisionLevel"
   ::= {sr1646v2BgriMVStpEntry 134414336}

sr1646v2BgriMVStpMstConfigIdDigest OBJECT-TYPE
   SYNTAX      OCTET STRING
   MAX-ACCESS  read-only
   STATUS      current
   DESCRIPTION
      "Path: vpnBridgeGroup.status.spanningTree.mstConfigId.digest"
   ::= {sr1646v2BgriMVStpEntry 134479872}


sr1646v2BgriMVBridging OBJECT IDENTIFIER ::= {sr1646v2BgriMV 12}

sr1646v2BgriMVBridgingSSCTable OBJECT-TYPE
   SYNTAX      SEQUENCE OF Sr1646v2BgriMVBridgingEntry
   MAX-ACCESS  not-accessible
   STATUS      current
   DESCRIPTION
      " bridge-port status"
   ::= {sr1646v2BgriMVBridging 1}

sr1646v2BgriMVBridgingEntry OBJECT-TYPE
   SYNTAX      Sr1646v2BgriMVBridgingEntry
   MAX-ACCESS  not-accessible
   STATUS      current
   DESCRIPTION
      ""
   INDEX      { sr1646v2BgriMVBridgingGlobalIx,
                sr1646v2BgriMVBridgingTableIx }
   ::= {sr1646v2BgriMVBridgingSSCTable 1}

Sr1646v2BgriMVBridgingEntry ::=
   SEQUENCE
      {
      sr1646v2BgriMVBridgingGlobalIx
         GlobalIndex,
      sr1646v2BgriMVBridgingTableIx
         TableIndex,
      sr1646v2BgriMVBridgingName
         DisplayString,
      sr1646v2BgriMVBridgingState
         INTEGER,
      sr1646v2BgriMVBridgingCacheSize
         Counter32,
      sr1646v2BgriMVBridgingMaxCacheSize
         INTEGER,
      sr1646v2BgriMVBridgingVlMmbAll
         DisplayString,
      sr1646v2BgriMVBridgingVlMmbNone
         DisplayString,
      sr1646v2BgriMVBridgingStPortRole
         INTEGER,
      sr1646v2BgriMVBridgingStPortId
         Integer32,
      sr1646v2BgriMVBridgingStPpCostExtPathCost
         Integer32,
      sr1646v2BgriMVBridgingStPpCostIntPathCost
         Integer32,
      sr1646v2BgriMVBridgingStExtRpCost
         Integer32,
      sr1646v2BgriMVBridgingStIntRpCost
         Integer32,
      sr1646v2BgriMVBridgingStDesBrIdPriority
         Integer32,
      sr1646v2BgriMVBridgingStDesBrIdMacAddress
         OCTET STRING,
      sr1646v2BgriMVBridgingStDesPrtId
         Integer32,
      sr1646v2BgriMVBridgingStDesInt
         INTEGER,
      sr1646v2BgriMVBridgingStEdgeDetection
         INTEGER
      }

sr1646v2BgriMVBridgingGlobalIx OBJECT-TYPE
   SYNTAX      GlobalIndex
   MAX-ACCESS  not-accessible
   STATUS      current
   DESCRIPTION
      "The value of the tlsCntTreeGlobalIndex of the MANAGED OBJECT."
   ::= {sr1646v2BgriMVBridgingEntry 10}

sr1646v2BgriMVBridgingTableIx OBJECT-TYPE
   SYNTAX      TableIndex
   MAX-ACCESS  not-accessible
   STATUS      current
   DESCRIPTION
      ""
   ::= {sr1646v2BgriMVBridgingEntry 11}

sr1646v2BgriMVBridgingName OBJECT-TYPE
   SYNTAX      DisplayString
   MAX-ACCESS  read-only
   STATUS      current
   DESCRIPTION
      "Path: vpnBridgeGroup.status.bridging.name"
   ::= {sr1646v2BgriMVBridgingEntry 16777216}

sr1646v2BgriMVBridgingState OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: vpnBridgeGroup.status.bridging.state

       Possibilities:
               disabled   (0)
               discarding   (1)
               learning   (2)
               forwarding   (3)
               backupBlockedIntfDown   (256)
               backupBlockedIntfUp   (259)
               shutdown   (255)"
   ::= {sr1646v2BgriMVBridgingEntry 33554432}

sr1646v2BgriMVBridgingCacheSize OBJECT-TYPE
   SYNTAX      Counter32
   MAX-ACCESS  read-only
   STATUS      current
   DESCRIPTION
      "Path: vpnBridgeGroup.status.bridging.cacheSize

       32 bit unsigned wrappable counter."
   ::= {sr1646v2BgriMVBridgingEntry 50331648}

sr1646v2BgriMVBridgingMaxCacheSize OBJECT-TYPE
   SYNTAX      INTEGER
               {
               unlimited (0)
               }
   MAX-ACCESS  read-only
   STATUS      current
   DESCRIPTION
      "Path: vpnBridgeGroup.status.bridging.maxCacheSize

       Possibilities:
               unlimited   (0)"
   ::= {sr1646v2BgriMVBridgingEntry 67108864}

sr1646v2BgriMVBridgingVlMmbAll OBJECT-TYPE
   SYNTAX      DisplayString
   MAX-ACCESS  read-only
   STATUS      current
   DESCRIPTION
      "Path: vpnBridgeGroup.status.bridging.vlanMemberShip.all"
   ::= {sr1646v2BgriMVBridgingEntry 100728832}

sr1646v2BgriMVBridgingVlMmbNone OBJECT-TYPE
   SYNTAX      DisplayString
   MAX-ACCESS  read-only
   STATUS      current
   DESCRIPTION
      "Path: vpnBridgeGroup.status.bridging.vlanMemberShip.none"
   ::= {sr1646v2BgriMVBridgingEntry 100794368}

sr1646v2BgriMVBridgingStPortRole OBJECT-TYPE
   SYNTAX      INTEGER
               {
               none (0),
               root (1),
               designated (2),
               alternate (3),
               backup (4),
               disabled (5),
               master (6)
               }
   MAX-ACCESS  read-only
   STATUS      current
   DESCRIPTION
      "Path: vpnBridgeGroup.status.bridging.spanningTree.portRole

       Possibilities:
               none   (0)
               root   (1)
               designated   (2)
               alternate   (3)
               backup   (4)
               disabled   (5)
               master   (6)"
   ::= {sr1646v2BgriMVBridgingEntry 83951616}

sr1646v2BgriMVBridgingStPortId OBJECT-TYPE
   SYNTAX      Integer32
   MAX-ACCESS  read-only
   STATUS      current
   DESCRIPTION
      "Path: vpnBridgeGroup.status.bridging.spanningTree.portId"
   ::= {sr1646v2BgriMVBridgingEntry 84017152}

sr1646v2BgriMVBridgingStPpCostExtPathCost OBJECT-TYPE
   SYNTAX      Integer32
   MAX-ACCESS  read-only
   STATUS      current
   DESCRIPTION
      "Path: vpnBridgeGroup.status.bridging.spanningTree.portPathCosts.extPathCost"
   ::= {sr1646v2BgriMVBridgingEntry 84082944}

sr1646v2BgriMVBridgingStPpCostIntPathCost OBJECT-TYPE
   SYNTAX      Integer32
   MAX-ACCESS  read-only
   STATUS      current
   DESCRIPTION
      "Path: vpnBridgeGroup.status.bridging.spanningTree.portPathCosts.intPathCost"
   ::= {sr1646v2BgriMVBridgingEntry 84083200}

sr1646v2BgriMVBridgingStExtRpCost OBJECT-TYPE
   SYNTAX      Integer32
   MAX-ACCESS  read-only
   STATUS      current
   DESCRIPTION
      "Path: vpnBridgeGroup.status.bridging.spanningTree.extRootPathCost"
   ::= {sr1646v2BgriMVBridgingEntry 84148224}

sr1646v2BgriMVBridgingStIntRpCost OBJECT-TYPE
   SYNTAX      Integer32
   MAX-ACCESS  read-only
   STATUS      current
   DESCRIPTION
      "Path: vpnBridgeGroup.status.bridging.spanningTree.intRootPathCost"
   ::= {sr1646v2BgriMVBridgingEntry 84213760}

sr1646v2BgriMVBridgingStDesBrIdPriority OBJECT-TYPE
   SYNTAX      Integer32
   MAX-ACCESS  read-only
   STATUS      current
   DESCRIPTION
      "Path: vpnBridgeGroup.status.bridging.spanningTree.designatedBridgeId.priority"
   ::= {sr1646v2BgriMVBridgingEntry 84279552}

sr1646v2BgriMVBridgingStDesBrIdMacAddress OBJECT-TYPE
   SYNTAX      OCTET STRING
   MAX-ACCESS  read-only
   STATUS      current
   DESCRIPTION
      "Path: vpnBridgeGroup.status.bridging.spanningTree.designatedBridgeId.macAddress

       MAC address."
   ::= {sr1646v2BgriMVBridgingEntry 84279808}

sr1646v2BgriMVBridgingStDesPrtId OBJECT-TYPE
   SYNTAX      Integer32
   MAX-ACCESS  read-only
   STATUS      current
   DESCRIPTION
      "Path: vpnBridgeGroup.status.bridging.spanningTree.designatedPortId"
   ::= {sr1646v2BgriMVBridgingEntry 84344832}

sr1646v2BgriMVBridgingStDesInt OBJECT-TYPE
   SYNTAX      INTEGER
               {
               no (0),
               yes (1)
               }
   MAX-ACCESS  read-only
   STATUS      current
   DESCRIPTION
      "Path: vpnBridgeGroup.status.bridging.spanningTree.designatedOrInternal

       Possibilities:
               no   (0)
               yes   (1)"
   ::= {sr1646v2BgriMVBridgingEntry 84410368}

sr1646v2BgriMVBridgingStEdgeDetection OBJECT-TYPE
   SYNTAX      INTEGER
               {
               none (0),
               edge (1),
               notEdge (2)
               }
   MAX-ACCESS  read-only
   STATUS      current
   DESCRIPTION
      "Path: vpnBridgeGroup.status.bridging.spanningTree.edgeDetection

       Possibilities:
               none   (0)
               edge   (1)
               notEdge   (2)"
   ::= {sr1646v2BgriMVBridgingEntry 84475904}

sr1646v2BgriMVBridgingVlMmbGrouped OBJECT-TYPE
   SYNTAX      SEQUENCE OF Sr1646v2BgriMVBridgingVlMmbGroupedEntry
   MAX-ACCESS  not-accessible
   STATUS      current
   DESCRIPTION
      ""
   ::= {sr1646v2BgriMVBridging 100859904}

sr1646v2BgriMVBridgingVlMmbGroupedEntry OBJECT-TYPE
   SYNTAX      Sr1646v2BgriMVBridgingVlMmbGroupedEntry
   MAX-ACCESS  not-accessible
   STATUS      current
   DESCRIPTION
      ""
   INDEX      { sr1646v2BgriMVBridgingVlMmbGroupedGlobalIx,
                sr1646v2BgriMVBridgingTableIx,
                sr1646v2BgriMVBridgingVlMmbGroupedTableIx }
   ::= {sr1646v2BgriMVBridgingVlMmbGrouped 1}

Sr1646v2BgriMVBridgingVlMmbGroupedEntry ::=
   SEQUENCE
      {
      sr1646v2BgriMVBridgingVlMmbGroupedGlobalIx
         GlobalIndex,
      sr1646v2BgriMVBridgingVlMmbGroupedTableIx
         TableIndex,
      sr1646v2BgriMVBridgingVlMmbGroupedVlanId
         Integer32
      }

sr1646v2BgriMVBridgingVlMmbGroupedGlobalIx OBJECT-TYPE
   SYNTAX      GlobalIndex
   MAX-ACCESS  not-accessible
   STATUS      current
   DESCRIPTION
      "The value of the tlsCntTreeGlobalIndex of the MANAGED OBJECT."
   ::= {sr1646v2BgriMVBridgingVlMmbGroupedEntry 10}

sr1646v2BgriMVBridgingVlMmbGroupedTableIx OBJECT-TYPE
   SYNTAX      TableIndex
   MAX-ACCESS  not-accessible
   STATUS      current
   DESCRIPTION
      ""
   ::= {sr1646v2BgriMVBridgingVlMmbGroupedEntry 11}

sr1646v2BgriMVBridgingVlMmbGroupedVlanId OBJECT-TYPE
   SYNTAX      Integer32
   MAX-ACCESS  read-only
   STATUS      current
   DESCRIPTION
      "Path: vpnBridgeGroup.status.bridging.vlanMemberShip.grouped.vlanId"
   ::= {sr1646v2BgriMVBridgingVlMmbGroupedEntry 16777216}


sr1646v2BgriMVArpCache OBJECT IDENTIFIER ::= {sr1646v2BgriMV 13}

sr1646v2BgriMVArpCacheSSCTable OBJECT-TYPE
   SYNTAX      SEQUENCE OF Sr1646v2BgriMVArpCacheEntry
   MAX-ACCESS  not-accessible
   STATUS      current
   DESCRIPTION
      "arp cache of ethernet interface"
   ::= {sr1646v2BgriMVArpCache 1}

sr1646v2BgriMVArpCacheEntry OBJECT-TYPE
   SYNTAX      Sr1646v2BgriMVArpCacheEntry
   MAX-ACCESS  not-accessible
   STATUS      current
   DESCRIPTION
      ""
   INDEX      { sr1646v2BgriMVArpCacheGlobalIx,
                sr1646v2BgriMVArpCacheTableIx }
   ::= {sr1646v2BgriMVArpCacheSSCTable 1}

Sr1646v2BgriMVArpCacheEntry ::=
   SEQUENCE
      {
      sr1646v2BgriMVArpCacheGlobalIx
         GlobalIndex,
      sr1646v2BgriMVArpCacheTableIx
         TableIndex,
      sr1646v2BgriMVArpCacheMacAddress
         OCTET STRING,
      sr1646v2BgriMVArpCacheIpAddress
         IpAddress,
      sr1646v2BgriMVArpCacheType
         INTEGER,
      sr1646v2BgriMVArpCacheTimeOut
         TimeTicks
      }

sr1646v2BgriMVArpCacheGlobalIx OBJECT-TYPE
   SYNTAX      GlobalIndex
   MAX-ACCESS  not-accessible
   STATUS      current
   DESCRIPTION
      "The value of the tlsCntTreeGlobalIndex of the MANAGED OBJECT."
   ::= {sr1646v2BgriMVArpCacheEntry 10}

sr1646v2BgriMVArpCacheTableIx OBJECT-TYPE
   SYNTAX      TableIndex
   MAX-ACCESS  not-accessible
   STATUS      current
   DESCRIPTION
      ""
   ::= {sr1646v2BgriMVArpCacheEntry 11}

sr1646v2BgriMVArpCacheMacAddress OBJECT-TYPE
   SYNTAX      OCTET STRING
   MAX-ACCESS  read-only
   STATUS      current
   DESCRIPTION
      "Path: vpnBridgeGroup.status.arpCache.macAddress

       MAC address."
   ::= {sr1646v2BgriMVArpCacheEntry 16777216}

sr1646v2BgriMVArpCacheIpAddress OBJECT-TYPE
   SYNTAX      IpAddress
   MAX-ACCESS  read-only
   STATUS      current
   DESCRIPTION
      "Path: vpnBridgeGroup.status.arpCache.ipAddress"
   ::= {sr1646v2BgriMVArpCacheEntry 33554432}

sr1646v2BgriMVArpCacheType OBJECT-TYPE
   SYNTAX      INTEGER
               {
               static (0),
               dynamic (1)
               }
   MAX-ACCESS  read-only
   STATUS      current
   DESCRIPTION
      "Path: vpnBridgeGroup.status.arpCache.type

       Possibilities:
               static   (0)
               dynamic   (1)"
   ::= {sr1646v2BgriMVArpCacheEntry 50331648}

sr1646v2BgriMVArpCacheTimeOut OBJECT-TYPE
   SYNTAX      TimeTicks
   MAX-ACCESS  read-only
   STATUS      current
   DESCRIPTION
      "Path: vpnBridgeGroup.status.arpCache.timeOut

       Time in centi-second."
   ::= {sr1646v2BgriMVArpCacheEntry 67108864}


sr1646v2BgriMVVlan OBJECT IDENTIFIER ::= {sr1646v2BgriMV 34}

sr1646v2BgriMVVlanSSCTable OBJECT-TYPE
   SYNTAX      SEQUENCE OF Sr1646v2BgriMVVlanEntry
   MAX-ACCESS  not-accessible
   STATUS      current
   DESCRIPTION
      ""
   ::= {sr1646v2BgriMVVlan 1}

sr1646v2BgriMVVlanEntry OBJECT-TYPE
   SYNTAX      Sr1646v2BgriMVVlanEntry
   MAX-ACCESS  not-accessible
   STATUS      current
   DESCRIPTION
      ""
   INDEX      { sr1646v2BgriMVVlanGlobalIx,
                sr1646v2BgriMVVlanTableIx }
   ::= {sr1646v2BgriMVVlanSSCTable 1}

Sr1646v2BgriMVVlanEntry ::=
   SEQUENCE
      {
      sr1646v2BgriMVVlanGlobalIx
         GlobalIndex,
      sr1646v2BgriMVVlanTableIx
         TableIndex,
      sr1646v2BgriMVVlanName
         DisplayString,
      sr1646v2BgriMVVlanMode
         INTEGER,
      sr1646v2BgriMVVlanIfOperStatus
         INTEGER,
      sr1646v2BgriMVVlanIfLastChange
         TimeTicks,
      sr1646v2BgriMVVlanIfLastChangeDate
         DisplayString,
      sr1646v2BgriMVVlanIpAddress
         IpAddress,
      sr1646v2BgriMVVlanIpNetMask
         IpAddress,
      sr1646v2BgriMVVlanIpDhcpStatus
         INTEGER,
      sr1646v2BgriMVVlanIpDhcpLeaseTime
         TimeTicks,
      sr1646v2BgriMVVlanIpV6State
         INTEGER,
      sr1646v2BgriMVVlanIpV6InterfaceId
         OCTET STRING,
      sr1646v2BgriMVVlanIpV6LinkMtu
         Integer32,
      sr1646v2BgriMVVlanIpV6HopLimit
         Integer32,
      sr1646v2BgriMVVlanIpV6DhcpIaid
         Counter32,
      sr1646v2BgriMVVlanIpV6RaRcvOption
         Integer32,
      sr1646v2BgriMVVlanVlanVid
         Integer32
      }

sr1646v2BgriMVVlanGlobalIx OBJECT-TYPE
   SYNTAX      GlobalIndex
   MAX-ACCESS  not-accessible
   STATUS      current
   DESCRIPTION
      "The value of the tlsCntTreeGlobalIndex of the MANAGED OBJECT."
   ::= {sr1646v2BgriMVVlanEntry 10}

sr1646v2BgriMVVlanTableIx OBJECT-TYPE
   SYNTAX      TableIndex
   MAX-ACCESS  not-accessible
   STATUS      current
   DESCRIPTION
      ""
   ::= {sr1646v2BgriMVVlanEntry 11}

sr1646v2BgriMVVlanName OBJECT-TYPE
   SYNTAX      DisplayString
   MAX-ACCESS  read-only
   STATUS      current
   DESCRIPTION
      "Path: vpnBridgeGroup.status.vlan.name"
   ::= {sr1646v2BgriMVVlanEntry 16777216}

sr1646v2BgriMVVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: vpnBridgeGroup.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2BgriMVVlanEntry 335544320}

sr1646v2BgriMVVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vpnBridgeGroup.status.vlan.ifOperStatus

       Possibilities:
               up   (1)
               down   (2)
               testing   (3)
               unknown   (4)
               dormant   (5)
               notPresent   (6)
               lowerLayerDown   (7)"
   ::= {sr1646v2BgriMVVlanEntry 1795162112}

sr1646v2BgriMVVlanIfLastChange OBJECT-TYPE
   SYNTAX      TimeTicks
   MAX-ACCESS  read-only
   STATUS      current
   DESCRIPTION
      "Path: vpnBridgeGroup.status.vlan.ifLastChange

       Time in centi-second."
   ::= {sr1646v2BgriMVVlanEntry 1811939328}

sr1646v2BgriMVVlanIfLastChangeDate OBJECT-TYPE
   SYNTAX      DisplayString
   MAX-ACCESS  read-only
   STATUS      current
   DESCRIPTION
      "Path: vpnBridgeGroup.status.vlan.ifLastChangeDate"
   ::= {sr1646v2BgriMVVlanEntry 3070230528}

sr1646v2BgriMVVlanIpAddress OBJECT-TYPE
   SYNTAX      IpAddress
   MAX-ACCESS  read-only
   STATUS      current
   DESCRIPTION
      "Path: vpnBridgeGroup.status.vlan.ip.address"
   ::= {sr1646v2BgriMVVlanEntry 51380224}

sr1646v2BgriMVVlanIpNetMask OBJECT-TYPE
   SYNTAX      IpAddress
   MAX-ACCESS  read-only
   STATUS      current
   DESCRIPTION
      "Path: vpnBridgeGroup.status.vlan.ip.netMask"
   ::= {sr1646v2BgriMVVlanEntry 51445760}

sr1646v2BgriMVVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: vpnBridgeGroup.status.vlan.ip.dhcp.status

       Possibilities:
               none   (0)
               selecting   (1)
               requesting   (2)
               rebinding   (3)
               bound   (4)
               renewing   (5)
               rebooting   (6)
               initreboot   (7)"
   ::= {sr1646v2BgriMVVlanEntry 51904768}

sr1646v2BgriMVVlanIpDhcpLeaseTime OBJECT-TYPE
   SYNTAX      TimeTicks
   MAX-ACCESS  read-only
   STATUS      current
   DESCRIPTION
      "Path: vpnBridgeGroup.status.vlan.ip.dhcp.leaseTime

       Time in centi-second."
   ::= {sr1646v2BgriMVVlanEntry 51905024}

sr1646v2BgriMVVlanIpV6State OBJECT-TYPE
   SYNTAX      INTEGER
               {
               disabled (0),
               enabled (1)
               }
   MAX-ACCESS  read-only
   STATUS      current
   DESCRIPTION
      "Path: vpnBridgeGroup.status.vlan.ipV6.state

       Possibilities:
               disabled   (0)
               enabled   (1)"
   ::= {sr1646v2BgriMVVlanEntry 100728832}

sr1646v2BgriMVVlanIpV6InterfaceId OBJECT-TYPE
   SYNTAX      OCTET STRING
   MAX-ACCESS  read-only
   STATUS      current
   DESCRIPTION
      "Path: vpnBridgeGroup.status.vlan.ipV6.interfaceId"
   ::= {sr1646v2BgriMVVlanEntry 100794368}

sr1646v2BgriMVVlanIpV6LinkMtu OBJECT-TYPE
   SYNTAX      Integer32
   MAX-ACCESS  read-only
   STATUS      current
   DESCRIPTION
      "Path: vpnBridgeGroup.status.vlan.ipV6.linkMtu"
   ::= {sr1646v2BgriMVVlanEntry 100925440}

sr1646v2BgriMVVlanIpV6HopLimit OBJECT-TYPE
   SYNTAX      Integer32
   MAX-ACCESS  read-only
   STATUS      current
   DESCRIPTION
      "Path: vpnBridgeGroup.status.vlan.ipV6.hopLimit"
   ::= {sr1646v2BgriMVVlanEntry 100990976}

sr1646v2BgriMVVlanIpV6DhcpIaid OBJECT-TYPE
   SYNTAX      Counter32
   MAX-ACCESS  read-only
   STATUS      current
   DESCRIPTION
      "Path: vpnBridgeGroup.status.vlan.ipV6.dhcp.iaid

       32 bit unsigned wrappable counter."
   ::= {sr1646v2BgriMVVlanEntry 101056768}

sr1646v2BgriMVVlanIpV6RaRcvOption OBJECT-TYPE
   SYNTAX      Integer32
   MAX-ACCESS  read-only
   STATUS      current
   DESCRIPTION
      "Path: vpnBridgeGroup.status.vlan.ipV6.raRcvOption

       Bit meanings:
               bit 0 = linkMtu,
               bit 1 = srcLinkLayer,
               bit 2 = prefixInfo,
               bit 3 = rdnss,
               bit 4 = dnssl"
   ::= {sr1646v2BgriMVVlanEntry 101122048}

sr1646v2BgriMVVlanVlanVid OBJECT-TYPE
   SYNTAX      Integer32
   MAX-ACCESS  read-only
   STATUS      current
   DESCRIPTION
      "Path: vpnBridgeGroup.status.vlan.vlan.vid"
   ::= {sr1646v2BgriMVVlanEntry 234946560}

sr1646v2BgriMVVlanIpSecondaryIp OBJECT-TYPE
   SYNTAX      SEQUENCE OF Sr1646v2BgriMVVlanIpSecondaryIpEntry
   MAX-ACCESS  not-accessible
   STATUS      current
   DESCRIPTION
      ""
   ::= {sr1646v2BgriMVVlan 51838976}

sr1646v2BgriMVVlanIpSecondaryIpEntry OBJECT-TYPE
   SYNTAX      Sr1646v2BgriMVVlanIpSecondaryIpEntry
   MAX-ACCESS  not-accessible
   STATUS      current
   DESCRIPTION
      ""
   INDEX      { sr1646v2BgriMVVlanIpSecondaryIpGlobalIx,
                sr1646v2BgriMVVlanTableIx,
                sr1646v2BgriMVVlanIpSecondaryIpTableIx }
   ::= {sr1646v2BgriMVVlanIpSecondaryIp 1}

Sr1646v2BgriMVVlanIpSecondaryIpEntry ::=
   SEQUENCE
      {
      sr1646v2BgriMVVlanIpSecondaryIpGlobalIx
         GlobalIndex,
      sr1646v2BgriMVVlanIpSecondaryIpTableIx
         TableIndex,
      sr1646v2BgriMVVlanIpSecondaryIpAddress
         IpAddress,
      sr1646v2BgriMVVlanIpSecondaryIpNetMask
         IpAddress
      }

sr1646v2BgriMVVlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2BgriMVVlanIpSecondaryIpEntry 10}

sr1646v2BgriMVVlanIpSecondaryIpTableIx OBJECT-TYPE
   SYNTAX      TableIndex
   MAX-ACCESS  not-accessible
   STATUS      current
   DESCRIPTION
      ""
   ::= {sr1646v2BgriMVVlanIpSecondaryIpEntry 11}

sr1646v2BgriMVVlanIpSecondaryIpAddress OBJECT-TYPE
   SYNTAX      IpAddress
   MAX-ACCESS  read-only
   STATUS      current
   DESCRIPTION
      "Path: vpnBridgeGroup.status.vlan.ip.secondaryIp.address"
   ::= {sr1646v2BgriMVVlanIpSecondaryIpEntry 2030043136}

sr1646v2BgriMVVlanIpSecondaryIpNetMask OBJECT-TYPE
   SYNTAX      IpAddress
   MAX-ACCESS  read-only
   STATUS      current
   DESCRIPTION
      "Path: vpnBridgeGroup.status.vlan.ip.secondaryIp.netMask"
   ::= {sr1646v2BgriMVVlanIpSecondaryIpEntry 2063597568}

sr1646v2BgriMVVlanIpV6Addresses OBJECT-TYPE
   SYNTAX      SEQUENCE OF Sr1646v2BgriMVVlanIpV6AddressesEntry
   MAX-ACCESS  not-accessible
   STATUS      current
   DESCRIPTION
      ""
   ::= {sr1646v2BgriMVVlan 100859904}

sr1646v2BgriMVVlanIpV6AddressesEntry OBJECT-TYPE
   SYNTAX      Sr1646v2BgriMVVlanIpV6AddressesEntry
   MAX-ACCESS  not-accessible
   STATUS      current
   DESCRIPTION
      ""
   INDEX      { sr1646v2BgriMVVlanIpV6AddressesGlobalIx,
                sr1646v2BgriMVVlanTableIx,
                sr1646v2BgriMVVlanIpV6AddressesTableIx }
   ::= {sr1646v2BgriMVVlanIpV6Addresses 1}

Sr1646v2BgriMVVlanIpV6AddressesEntry ::=
   SEQUENCE
      {
      sr1646v2BgriMVVlanIpV6AddressesGlobalIx
         GlobalIndex,
      sr1646v2BgriMVVlanIpV6AddressesTableIx
         TableIndex,
      sr1646v2BgriMVVlanIpV6AddressesAddress
         Ipv6Address,
      sr1646v2BgriMVVlanIpV6AddressesPrefixLength
         Integer32,
      sr1646v2BgriMVVlanIpV6AddressesStatus
         INTEGER,
      sr1646v2BgriMVVlanIpV6AddressesOrigin
         INTEGER,
      sr1646v2BgriMVVlanIpV6AddressesFlagsInterfaceId
         INTEGER,
      sr1646v2BgriMVVlanIpV6AddressesFlagsAnycast
         INTEGER,
      sr1646v2BgriMVVlanIpV6AddressesTimersValidLifeTime
         TimeTicks,
      sr1646v2BgriMVVlanIpV6AddressesTimersPrefLifeTime
         TimeTicks
      }

sr1646v2BgriMVVlanIpV6AddressesGlobalIx OBJECT-TYPE
   SYNTAX      GlobalIndex
   MAX-ACCESS  not-accessible
   STATUS      current
   DESCRIPTION
      "The value of the tlsCntTreeGlobalIndex of the MANAGED OBJECT."
   ::= {sr1646v2BgriMVVlanIpV6AddressesEntry 10}

sr1646v2BgriMVVlanIpV6AddressesTableIx OBJECT-TYPE
   SYNTAX      TableIndex
   MAX-ACCESS  not-accessible
   STATUS      current
   DESCRIPTION
      ""
   ::= {sr1646v2BgriMVVlanIpV6AddressesEntry 11}

sr1646v2BgriMVVlanIpV6AddressesAddress OBJECT-TYPE
   SYNTAX      Ipv6Address
   MAX-ACCESS  read-only
   STATUS      current
   DESCRIPTION
      "Path: vpnBridgeGroup.status.vlan.ipV6.addresses.address

       ipv6 address"
   ::= {sr1646v2BgriMVVlanIpV6AddressesEntry 16777216}

sr1646v2BgriMVVlanIpV6AddressesPrefixLength OBJECT-TYPE
   SYNTAX      Integer32
   MAX-ACCESS  read-only
   STATUS      current
   DESCRIPTION
      "Path: vpnBridgeGroup.status.vlan.ipV6.addresses.prefixLength"
   ::= {sr1646v2BgriMVVlanIpV6AddressesEntry 33554432}

sr1646v2BgriMVVlanIpV6AddressesStatus OBJECT-TYPE
   SYNTAX      INTEGER
               {
               invalid (0),
               tentative (1),
               deprecated (2),
               preferred (3)
               }
   MAX-ACCESS  read-only
   STATUS      current
   DESCRIPTION
      "Path: vpnBridgeGroup.status.vlan.ipV6.addresses.status

       Possibilities:
               invalid   (0)
               tentative   (1)
               deprecated   (2)
               preferred   (3)"
   ::= {sr1646v2BgriMVVlanIpV6AddressesEntry 50331648}

sr1646v2BgriMVVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vpnBridgeGroup.status.vlan.ipV6.addresses.origin

       Possibilities:
               unknown   (0)
               manual   (1)
               generalPrefix   (2)
               statelessAuto   (3)
               statefullAuto   (4)"
   ::= {sr1646v2BgriMVVlanIpV6AddressesEntry 67108864}

sr1646v2BgriMVVlanIpV6AddressesFlagsInterfaceId OBJECT-TYPE
   SYNTAX      INTEGER
               {
               no (0),
               yes (1)
               }
   MAX-ACCESS  read-only
   STATUS      current
   DESCRIPTION
      "Path: vpnBridgeGroup.status.vlan.ipV6.addresses.flags.interfaceId

       Possibilities:
               no   (0)
               yes   (1)"
   ::= {sr1646v2BgriMVVlanIpV6AddressesEntry 83951616}

sr1646v2BgriMVVlanIpV6AddressesFlagsAnycast OBJECT-TYPE
   SYNTAX      INTEGER
               {
               no (0),
               yes (1)
               }
   MAX-ACCESS  read-only
   STATUS      current
   DESCRIPTION
      "Path: vpnBridgeGroup.status.vlan.ipV6.addresses.flags.anycast

       Possibilities:
               no   (0)
               yes   (1)"
   ::= {sr1646v2BgriMVVlanIpV6AddressesEntry 84017152}

sr1646v2BgriMVVlanIpV6AddressesTimersValidLifeTime OBJECT-TYPE
   SYNTAX      TimeTicks
   MAX-ACCESS  read-only
   STATUS      current
   DESCRIPTION
      "Path: vpnBridgeGroup.status.vlan.ipV6.addresses.timers.validLifeTime

       Time in centi-second."
   ::= {sr1646v2BgriMVVlanIpV6AddressesEntry 100794368}

sr1646v2BgriMVVlanIpV6AddressesTimersPrefLifeTime OBJECT-TYPE
   SYNTAX      TimeTicks
   MAX-ACCESS  read-only
   STATUS      current
   DESCRIPTION
      "Path: vpnBridgeGroup.status.vlan.ipV6.addresses.timers.prefLifeTime

       Time in centi-second."
   ::= {sr1646v2BgriMVVlanIpV6AddressesEntry 100728832}

sr1646v2BgriMVVlanVlanArpCache OBJECT-TYPE
   SYNTAX      SEQUENCE OF Sr1646v2BgriMVVlanVlanArpCacheEntry
   MAX-ACCESS  not-accessible
   STATUS      current
   DESCRIPTION
      ""
   ::= {sr1646v2BgriMVVlan 235601920}

sr1646v2BgriMVVlanVlanArpCacheEntry OBJECT-TYPE
   SYNTAX      Sr1646v2BgriMVVlanVlanArpCacheEntry
   MAX-ACCESS  not-accessible
   STATUS      current
   DESCRIPTION
      ""
   INDEX      { sr1646v2BgriMVVlanVlanArpCacheGlobalIx,
                sr1646v2BgriMVVlanTableIx,
                sr1646v2BgriMVVlanVlanArpCacheTableIx }
   ::= {sr1646v2BgriMVVlanVlanArpCache 1}

Sr1646v2BgriMVVlanVlanArpCacheEntry ::=
   SEQUENCE
      {
      sr1646v2BgriMVVlanVlanArpCacheGlobalIx
         GlobalIndex,
      sr1646v2BgriMVVlanVlanArpCacheTableIx
         TableIndex,
      sr1646v2BgriMVVlanVlanArpCacheMacAddress
         OCTET STRING,
      sr1646v2BgriMVVlanVlanArpCacheIpAddress
         IpAddress,
      sr1646v2BgriMVVlanVlanArpCacheType
         INTEGER,
      sr1646v2BgriMVVlanVlanArpCacheTimeOut
         TimeTicks
      }

sr1646v2BgriMVVlanVlanArpCacheGlobalIx OBJECT-TYPE
   SYNTAX      GlobalIndex
   MAX-ACCESS  not-accessible
   STATUS      current
   DESCRIPTION
      "The value of the tlsCntTreeGlobalIndex of the MANAGED OBJECT."
   ::= {sr1646v2BgriMVVlanVlanArpCacheEntry 10}

sr1646v2BgriMVVlanVlanArpCacheTableIx OBJECT-TYPE
   SYNTAX      TableIndex
   MAX-ACCESS  not-accessible
   STATUS      current
   DESCRIPTION
      ""
   ::= {sr1646v2BgriMVVlanVlanArpCacheEntry 11}

sr1646v2BgriMVVlanVlanArpCacheMacAddress OBJECT-TYPE
   SYNTAX      OCTET STRING
   MAX-ACCESS  read-only
   STATUS      current
   DESCRIPTION
      "Path: vpnBridgeGroup.status.vlan.vlan.arpCache.macAddress

       MAC address."
   ::= {sr1646v2BgriMVVlanVlanArpCacheEntry 16777216}

sr1646v2BgriMVVlanVlanArpCacheIpAddress OBJECT-TYPE
   SYNTAX      IpAddress
   MAX-ACCESS  read-only
   STATUS      current
   DESCRIPTION
      "Path: vpnBridgeGroup.status.vlan.vlan.arpCache.ipAddress"
   ::= {sr1646v2BgriMVVlanVlanArpCacheEntry 33554432}

sr1646v2BgriMVVlanVlanArpCacheType OBJECT-TYPE
   SYNTAX      INTEGER
               {
               static (0),
               dynamic (1)
               }
   MAX-ACCESS  read-only
   STATUS      current
   DESCRIPTION
      "Path: vpnBridgeGroup.status.vlan.vlan.arpCache.type

       Possibilities:
               static   (0)
               dynamic   (1)"
   ::= {sr1646v2BgriMVVlanVlanArpCacheEntry 50331648}

sr1646v2BgriMVVlanVlanArpCacheTimeOut OBJECT-TYPE
   SYNTAX      TimeTicks
   MAX-ACCESS  read-only
   STATUS      current
   DESCRIPTION
      "Path: vpnBridgeGroup.status.vlan.vlan.arpCache.timeOut

       Time in centi-second."
   ::= {sr1646v2BgriMVVlanVlanArpCacheEntry 67108864}


sr1646v2BgriMVPppOE OBJECT IDENTIFIER ::= {sr1646v2BgriMV 81}

sr1646v2BgriMVPppOESSCTable OBJECT-TYPE
   SYNTAX      SEQUENCE OF Sr1646v2BgriMVPppOEEntry
   MAX-ACCESS  not-accessible
   STATUS      current
   DESCRIPTION
      ""
   ::= {sr1646v2BgriMVPppOE 1}

sr1646v2BgriMVPppOEEntry OBJECT-TYPE
   SYNTAX      Sr1646v2BgriMVPppOEEntry
   MAX-ACCESS  not-accessible
   STATUS      current
   DESCRIPTION
      ""
   INDEX      { sr1646v2BgriMVPppOEGlobalIx,
                sr1646v2BgriMVPppOETableIx }
   ::= {sr1646v2BgriMVPppOESSCTable 1}

Sr1646v2BgriMVPppOEEntry ::=
   SEQUENCE
      {
      sr1646v2BgriMVPppOEGlobalIx
         GlobalIndex,
      sr1646v2BgriMVPppOETableIx
         TableIndex,
      sr1646v2BgriMVPppOEName
         DisplayString,
      sr1646v2BgriMVPppOEMode
         INTEGER,
      sr1646v2BgriMVPppOEIfOperStatus
         INTEGER,
      sr1646v2BgriMVPppOEIfLastChange
         TimeTicks,
      sr1646v2BgriMVPppOEIfLastChangeDate
         DisplayString,
      sr1646v2BgriMVPppOEIpAddress
         IpAddress,
      sr1646v2BgriMVPppOEIpNetMask
         IpAddress,
      sr1646v2BgriMVPppOEIpRemote
         IpAddress,
      sr1646v2BgriMVPppOEPppOEthDiscState
         INTEGER,
      sr1646v2BgriMVPppOEPppOEthPeerMac
         OCTET STRING,
      sr1646v2BgriMVPppOEPppOEthServiceName
         DisplayString,
      sr1646v2BgriMVPppOEPppLcpState
         INTEGER,
      sr1646v2BgriMVPppOEPppIpcpState
         INTEGER,
      sr1646v2BgriMVPppOEPppIp6cpState
         INTEGER,
      sr1646v2BgriMVPppOEPppMyAutSt
         INTEGER,
      sr1646v2BgriMVPppOEPppHisAutSt
         INTEGER,
      sr1646v2BgriMVPppOEPppMru
         Integer32,
      sr1646v2BgriMVPppOEIpV6State
         INTEGER,
      sr1646v2BgriMVPppOEIpV6InterfaceId
         OCTET STRING,
      sr1646v2BgriMVPppOEIpV6LinkMtu
         Integer32,
      sr1646v2BgriMVPppOEIpV6HopLimit
         Integer32,
      sr1646v2BgriMVPppOEIpV6DhcpIaid
         Counter32,
      sr1646v2BgriMVPppOEIpV6RaRcvOption
         Integer32
      }

sr1646v2BgriMVPppOEGlobalIx OBJECT-TYPE
   SYNTAX      GlobalIndex
   MAX-ACCESS  not-accessible
   STATUS      current
   DESCRIPTION
      "The value of the tlsCntTreeGlobalIndex of the MANAGED OBJECT."
   ::= {sr1646v2BgriMVPppOEEntry 10}

sr1646v2BgriMVPppOETableIx OBJECT-TYPE
   SYNTAX      TableIndex
   MAX-ACCESS  not-accessible
   STATUS      current
   DESCRIPTION
      ""
   ::= {sr1646v2BgriMVPppOEEntry 11}

sr1646v2BgriMVPppOEName OBJECT-TYPE
   SYNTAX      DisplayString
   MAX-ACCESS  read-only
   STATUS      current
   DESCRIPTION
      "Path: vpnBridgeGroup.status.pppoEClient.name"
   ::= {sr1646v2BgriMVPppOEEntry 16777216}

sr1646v2BgriMVPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: vpnBridgeGroup.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2BgriMVPppOEEntry 335544320}

sr1646v2BgriMVPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vpnBridgeGroup.status.pppoEClient.ifOperStatus

       Possibilities:
               up   (1)
               down   (2)
               testing   (3)
               unknown   (4)
               dormant   (5)
               notPresent   (6)
               lowerLayerDown   (7)"
   ::= {sr1646v2BgriMVPppOEEntry 1795162112}

sr1646v2BgriMVPppOEIfLastChange OBJECT-TYPE
   SYNTAX      TimeTicks
   MAX-ACCESS  read-only
   STATUS      current
   DESCRIPTION
      "Path: vpnBridgeGroup.status.pppoEClient.ifLastChange

       Time in centi-second."
   ::= {sr1646v2BgriMVPppOEEntry 1811939328}

sr1646v2BgriMVPppOEIfLastChangeDate OBJECT-TYPE
   SYNTAX      DisplayString
   MAX-ACCESS  read-only
   STATUS      current
   DESCRIPTION
      "Path: vpnBridgeGroup.status.pppoEClient.ifLastChangeDate"
   ::= {sr1646v2BgriMVPppOEEntry 3070230528}

sr1646v2BgriMVPppOEIpAddress OBJECT-TYPE
   SYNTAX      IpAddress
   MAX-ACCESS  read-only
   STATUS      current
   DESCRIPTION
      "Path: vpnBridgeGroup.status.pppoEClient.ip.address"
   ::= {sr1646v2BgriMVPppOEEntry 51380224}

sr1646v2BgriMVPppOEIpNetMask OBJECT-TYPE
   SYNTAX      IpAddress
   MAX-ACCESS  read-only
   STATUS      current
   DESCRIPTION
      "Path: vpnBridgeGroup.status.pppoEClient.ip.netMask"
   ::= {sr1646v2BgriMVPppOEEntry 51445760}

sr1646v2BgriMVPppOEIpRemote OBJECT-TYPE
   SYNTAX      IpAddress
   MAX-ACCESS  read-only
   STATUS      current
   DESCRIPTION
      "Path: vpnBridgeGroup.status.pppoEClient.ip.remote"
   ::= {sr1646v2BgriMVPppOEEntry 51511296}

sr1646v2BgriMVPppOEPppOEthDiscState OBJECT-TYPE
   SYNTAX      INTEGER
               {
               idle (0),
               waitForPADO (1),
               waitForPADS (2),
               established (3)
               }
   MAX-ACCESS  read-only
   STATUS      current
   DESCRIPTION
      "Path: vpnBridgeGroup.status.pppoEClient.pppOverEth.discState

       Possibilities:
               idle   (0)
               waitForPADO   (1)
               waitForPADS   (2)
               established   (3)"
   ::= {sr1646v2BgriMVPppOEEntry 67174400}

sr1646v2BgriMVPppOEPppOEthPeerMac OBJECT-TYPE
   SYNTAX      OCTET STRING
   MAX-ACCESS  read-only
   STATUS      current
   DESCRIPTION
      "Path: vpnBridgeGroup.status.pppoEClient.pppOverEth.remoteMacAddress

       MAC address."
   ::= {sr1646v2BgriMVPppOEEntry 67239936}

sr1646v2BgriMVPppOEPppOEthServiceName OBJECT-TYPE
   SYNTAX      DisplayString
   MAX-ACCESS  read-only
   STATUS      current
   DESCRIPTION
      "Path: vpnBridgeGroup.status.pppoEClient.pppOverEth.serviceName"
   ::= {sr1646v2BgriMVPppOEEntry 67305472}

sr1646v2BgriMVPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vpnBridgeGroup.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2BgriMVPppOEEntry 83951616}

sr1646v2BgriMVPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vpnBridgeGroup.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2BgriMVPppOEEntry 84017152}

sr1646v2BgriMVPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vpnBridgeGroup.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2BgriMVPppOEEntry 84869120}

sr1646v2BgriMVPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: vpnBridgeGroup.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2BgriMVPppOEEntry 84541440}

sr1646v2BgriMVPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: vpnBridgeGroup.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2BgriMVPppOEEntry 84606976}

sr1646v2BgriMVPppOEPppMru OBJECT-TYPE
   SYNTAX      Integer32
   MAX-ACCESS  read-only
   STATUS      current
   DESCRIPTION
      "Path: vpnBridgeGroup.status.pppoEClient.ppp.mru"
   ::= {sr1646v2BgriMVPppOEEntry 84934656}

sr1646v2BgriMVPppOEIpV6State OBJECT-TYPE
   SYNTAX      INTEGER
               {
               disabled (0),
               enabled (1)
               }
   MAX-ACCESS  read-only
   STATUS      current
   DESCRIPTION
      "Path: vpnBridgeGroup.status.pppoEClient.ipV6.state

       Possibilities:
               disabled   (0)
               enabled   (1)"
   ::= {sr1646v2BgriMVPppOEEntry 100728832}

sr1646v2BgriMVPppOEIpV6InterfaceId OBJECT-TYPE
   SYNTAX      OCTET STRING
   MAX-ACCESS  read-only
   STATUS      current
   DESCRIPTION
      "Path: vpnBridgeGroup.status.pppoEClient.ipV6.interfaceId"
   ::= {sr1646v2BgriMVPppOEEntry 100794368}

sr1646v2BgriMVPppOEIpV6LinkMtu OBJECT-TYPE
   SYNTAX      Integer32
   MAX-ACCESS  read-only
   STATUS      current
   DESCRIPTION
      "Path: vpnBridgeGroup.status.pppoEClient.ipV6.linkMtu"
   ::= {sr1646v2BgriMVPppOEEntry 100925440}

sr1646v2BgriMVPppOEIpV6HopLimit OBJECT-TYPE
   SYNTAX      Integer32
   MAX-ACCESS  read-only
   STATUS      current
   DESCRIPTION
      "Path: vpnBridgeGroup.status.pppoEClient.ipV6.hopLimit"
   ::= {sr1646v2BgriMVPppOEEntry 100990976}

sr1646v2BgriMVPppOEIpV6DhcpIaid OBJECT-TYPE
   SYNTAX      Counter32
   MAX-ACCESS  read-only
   STATUS      current
   DESCRIPTION
      "Path: vpnBridgeGroup.status.pppoEClient.ipV6.dhcp.iaid

       32 bit unsigned wrappable counter."
   ::= {sr1646v2BgriMVPppOEEntry 101056768}

sr1646v2BgriMVPppOEIpV6RaRcvOption OBJECT-TYPE
   SYNTAX      Integer32
   MAX-ACCESS  read-only
   STATUS      current
   DESCRIPTION
      "Path: vpnBridgeGroup.status.pppoEClient.ipV6.raRcvOption

       Bit meanings:
               bit 0 = linkMtu,
               bit 1 = srcLinkLayer,
               bit 2 = prefixInfo,
               bit 3 = rdnss,
               bit 4 = dnssl"
   ::= {sr1646v2BgriMVPppOEEntry 101122048}

sr1646v2BgriMVPppOEIpV6Addresses OBJECT-TYPE
   SYNTAX      SEQUENCE OF Sr1646v2BgriMVPppOEIpV6AddressesEntry
   MAX-ACCESS  not-accessible
   STATUS      current
   DESCRIPTION
      ""
   ::= {sr1646v2BgriMVPppOE 100859904}

sr1646v2BgriMVPppOEIpV6AddressesEntry OBJECT-TYPE
   SYNTAX      Sr1646v2BgriMVPppOEIpV6AddressesEntry
   MAX-ACCESS  not-accessible
   STATUS      current
   DESCRIPTION
      ""
   INDEX      { sr1646v2BgriMVPppOEIpV6AddressesGlobalIx,
                sr1646v2BgriMVPppOETableIx,
                sr1646v2BgriMVPppOEIpV6AddressesTableIx }
   ::= {sr1646v2BgriMVPppOEIpV6Addresses 1}

Sr1646v2BgriMVPppOEIpV6AddressesEntry ::=
   SEQUENCE
      {
      sr1646v2BgriMVPppOEIpV6AddressesGlobalIx
         GlobalIndex,
      sr1646v2BgriMVPppOEIpV6AddressesTableIx
         TableIndex,
      sr1646v2BgriMVPppOEIpV6AddressesAddress
         Ipv6Address,
      sr1646v2BgriMVPppOEIpV6AddressesPrefixLength
         Integer32,
      sr1646v2BgriMVPppOEIpV6AddressesStatus
         INTEGER,
      sr1646v2BgriMVPppOEIpV6AddressesOrigin
         INTEGER,
      sr1646v2BgriMVPppOEIpV6AddressesFlagsInterfaceId
         INTEGER,
      sr1646v2BgriMVPppOEIpV6AddressesFlagsAnycast
         INTEGER,
      sr1646v2BgriMVPppOEIpV6AddressesTimersValidLifeTime
         TimeTicks,
      sr1646v2BgriMVPppOEIpV6AddressesTimersPrefLifeTime
         TimeTicks
      }

sr1646v2BgriMVPppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2BgriMVPppOEIpV6AddressesEntry 10}

sr1646v2BgriMVPppOEIpV6AddressesTableIx OBJECT-TYPE
   SYNTAX      TableIndex
   MAX-ACCESS  not-accessible
   STATUS      current
   DESCRIPTION
      ""
   ::= {sr1646v2BgriMVPppOEIpV6AddressesEntry 11}

sr1646v2BgriMVPppOEIpV6AddressesAddress OBJECT-TYPE
   SYNTAX      Ipv6Address
   MAX-ACCESS  read-only
   STATUS      current
   DESCRIPTION
      "Path: vpnBridgeGroup.status.pppoEClient.ipV6.addresses.address

       ipv6 address"
   ::= {sr1646v2BgriMVPppOEIpV6AddressesEntry 16777216}

sr1646v2BgriMVPppOEIpV6AddressesPrefixLength OBJECT-TYPE
   SYNTAX      Integer32
   MAX-ACCESS  read-only
   STATUS      current
   DESCRIPTION
      "Path: vpnBridgeGroup.status.pppoEClient.ipV6.addresses.prefixLength"
   ::= {sr1646v2BgriMVPppOEIpV6AddressesEntry 33554432}

sr1646v2BgriMVPppOEIpV6AddressesStatus OBJECT-TYPE
   SYNTAX      INTEGER
               {
               invalid (0),
               tentative (1),
               deprecated (2),
               preferred (3)
               }
   MAX-ACCESS  read-only
   STATUS      current
   DESCRIPTION
      "Path: vpnBridgeGroup.status.pppoEClient.ipV6.addresses.status

       Possibilities:
               invalid   (0)
               tentative   (1)
               deprecated   (2)
               preferred   (3)"
   ::= {sr1646v2BgriMVPppOEIpV6AddressesEntry 50331648}

sr1646v2BgriMVPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vpnBridgeGroup.status.pppoEClient.ipV6.addresses.origin

       Possibilities:
               unknown   (0)
               manual   (1)
               generalPrefix   (2)
               statelessAuto   (3)
               statefullAuto   (4)"
   ::= {sr1646v2BgriMVPppOEIpV6AddressesEntry 67108864}

sr1646v2BgriMVPppOEIpV6AddressesFlagsInterfaceId OBJECT-TYPE
   SYNTAX      INTEGER
               {
               no (0),
               yes (1)
               }
   MAX-ACCESS  read-only
   STATUS      current
   DESCRIPTION
      "Path: vpnBridgeGroup.status.pppoEClient.ipV6.addresses.flags.interfaceId

       Possibilities:
               no   (0)
               yes   (1)"
   ::= {sr1646v2BgriMVPppOEIpV6AddressesEntry 83951616}

sr1646v2BgriMVPppOEIpV6AddressesFlagsAnycast OBJECT-TYPE
   SYNTAX      INTEGER
               {
               no (0),
               yes (1)
               }
   MAX-ACCESS  read-only
   STATUS      current
   DESCRIPTION
      "Path: vpnBridgeGroup.status.pppoEClient.ipV6.addresses.flags.anycast

       Possibilities:
               no   (0)
               yes   (1)"
   ::= {sr1646v2BgriMVPppOEIpV6AddressesEntry 84017152}

sr1646v2BgriMVPppOEIpV6AddressesTimersValidLifeTime OBJECT-TYPE
   SYNTAX      TimeTicks
   MAX-ACCESS  read-only
   STATUS      current
   DESCRIPTION
      "Path: vpnBridgeGroup.status.pppoEClient.ipV6.addresses.timers.validLifeTime

       Time in centi-second."
   ::= {sr1646v2BgriMVPppOEIpV6AddressesEntry 100794368}

sr1646v2BgriMVPppOEIpV6AddressesTimersPrefLifeTime OBJECT-TYPE
   SYNTAX      TimeTicks
   MAX-ACCESS  read-only
   STATUS      current
   DESCRIPTION
      "Path: vpnBridgeGroup.status.pppoEClient.ipV6.addresses.timers.prefLifeTime

       Time in centi-second."
   ::= {sr1646v2BgriMVPppOEIpV6AddressesEntry 100728832}


sr1646v2BgriMVSnmpIndex OBJECT IDENTIFIER ::= {sr1646v2BgriMV 269}

sr1646v2BgriMVSnmpIndexTable OBJECT-TYPE
   SYNTAX      SEQUENCE OF Sr1646v2BgriMVSnmpIndexEntry
   MAX-ACCESS  not-accessible
   STATUS      current
   DESCRIPTION
      "SNMP index assigned to this object"
   ::= {sr1646v2BgriMVSnmpIndex 1}

sr1646v2BgriMVSnmpIndexEntry OBJECT-TYPE
   SYNTAX      Sr1646v2BgriMVSnmpIndexEntry
   MAX-ACCESS  not-accessible
   STATUS      current
   DESCRIPTION
      ""
   INDEX      { sr1646v2BgriMVSnmpIndexGlobalIx }
   ::= {sr1646v2BgriMVSnmpIndexTable 1}

Sr1646v2BgriMVSnmpIndexEntry ::=
   SEQUENCE
      {
      sr1646v2BgriMVSnmpIndexGlobalIx
         GlobalIndex,
      sr1646v2BgriMVSnmpIndexValue
         Integer32
      }

sr1646v2BgriMVSnmpIndexGlobalIx OBJECT-TYPE
   SYNTAX      GlobalIndex
   MAX-ACCESS  not-accessible
   STATUS      current
   DESCRIPTION
      "The value of the tlsCntTreeGlobalIndex of the MANAGED OBJECT."
   ::= {sr1646v2BgriMVSnmpIndexEntry 10}

sr1646v2BgriMVSnmpIndexValue OBJECT-TYPE
   SYNTAX      Integer32
   MAX-ACCESS  read-only
   STATUS      current
   DESCRIPTION
      "Path: vpnBridgeGroup.status.snmpIndex"
   ::= {sr1646v2BgriMVSnmpIndexEntry 2147483648}



pr1646v2BgriMV OBJECT IDENTIFIER ::= {r1646v2BgriMV 12}


pr1646v2BgriMVCachePerf OBJECT IDENTIFIER ::= {pr1646v2BgriMV 6}

pr1646v2BgriMVCachePerfSSCTable OBJECT-TYPE
   SYNTAX      SEQUENCE OF Pr1646v2BgriMVCachePerfEntry
   MAX-ACCESS  not-accessible
   STATUS      current
   DESCRIPTION
      "cache entry performance"
   ::= {pr1646v2BgriMVCachePerf 1}

pr1646v2BgriMVCachePerfEntry OBJECT-TYPE
   SYNTAX      Pr1646v2BgriMVCachePerfEntry
   MAX-ACCESS  not-accessible
   STATUS      current
   DESCRIPTION
      ""
   INDEX      { pr1646v2BgriMVCachePerfGlobalIx,
                pr1646v2BgriMVCachePerfTableIx }
   ::= {pr1646v2BgriMVCachePerfSSCTable 1}

Pr1646v2BgriMVCachePerfEntry ::=
   SEQUENCE
      {
      pr1646v2BgriMVCachePerfGlobalIx
         GlobalIndex,
      pr1646v2BgriMVCachePerfTableIx
         TableIndex,
      pr1646v2BgriMVCachePerfIf
         DisplayString,
      pr1646v2BgriMVCachePerfMacAddress
         OCTET STRING,
      pr1646v2BgriMVCachePerfTpid
         INTEGER,
      pr1646v2BgriMVCachePerfVlanId
         INTEGER,
      pr1646v2BgriMVCachePerfTpid2
         INTEGER,
      pr1646v2BgriMVCachePerfVlanId2
         INTEGER,
      pr1646v2BgriMVCachePerfType
         INTEGER,
      pr1646v2BgriMVCachePerfRxPkts
         Counter32,
      pr1646v2BgriMVCachePerfTxPkts
         Counter32,
      pr1646v2BgriMVCachePerfStatViols
         Counter32,
      pr1646v2BgriMVCachePerfRelearns
         Counter32,
      pr1646v2BgriMVCachePerfRelearnDrops
         Counter32
      }

pr1646v2BgriMVCachePerfGlobalIx OBJECT-TYPE
   SYNTAX      GlobalIndex
   MAX-ACCESS  not-accessible
   STATUS      current
   DESCRIPTION
      "The value of the tlsCntTreeGlobalIndex of the MANAGED OBJECT."
   ::= {pr1646v2BgriMVCachePerfEntry 10}

pr1646v2BgriMVCachePerfTableIx OBJECT-TYPE
   SYNTAX      TableIndex
   MAX-ACCESS  not-accessible
   STATUS      current
   DESCRIPTION
      ""
   ::= {pr1646v2BgriMVCachePerfEntry 11}

pr1646v2BgriMVCachePerfIf OBJECT-TYPE
   SYNTAX      DisplayString
   MAX-ACCESS  read-only
   STATUS      current
   DESCRIPTION
      "Path: vpnBridgeGroup.performance.bridgeCache.interface"
   ::= {pr1646v2BgriMVCachePerfEntry 16777216}

pr1646v2BgriMVCachePerfMacAddress OBJECT-TYPE
   SYNTAX      OCTET STRING
   MAX-ACCESS  read-only
   STATUS      current
   DESCRIPTION
      "Path: vpnBridgeGroup.performance.bridgeCache.macAddress

       MAC address."
   ::= {pr1646v2BgriMVCachePerfEntry 33554432}

pr1646v2BgriMVCachePerfTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vpnBridgeGroup.performance.bridgeCache.tpid

       Possibilities:
               untagged   (0)
               dot1q   (33024)
               dot1ad   (34984)
               group   (65534)
               notUsed   (65535)
               dot1qOrDot1ad   (65536)"
   ::= {pr1646v2BgriMVCachePerfEntry 335544320}

pr1646v2BgriMVCachePerfVlanId OBJECT-TYPE
   SYNTAX      INTEGER
               {
               undefined (-1)
               }
   MAX-ACCESS  read-only
   STATUS      current
   DESCRIPTION
      "Path: vpnBridgeGroup.performance.bridgeCache.vlanId

       Possibilities:
               undefined   (-1)"
   ::= {pr1646v2BgriMVCachePerfEntry 50331648}

pr1646v2BgriMVCachePerfTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vpnBridgeGroup.performance.bridgeCache.tpid2

       Possibilities:
               untagged   (0)
               dot1q   (33024)
               dot1ad   (34984)
               group   (65534)
               notUsed   (65535)
               dot1qOrDot1ad   (65536)"
   ::= {pr1646v2BgriMVCachePerfEntry 369098752}

pr1646v2BgriMVCachePerfVlanId2 OBJECT-TYPE
   SYNTAX      INTEGER
               {
               undefined (-1)
               }
   MAX-ACCESS  read-only
   STATUS      current
   DESCRIPTION
      "Path: vpnBridgeGroup.performance.bridgeCache.vlanId2

       Possibilities:
               undefined   (-1)"
   ::= {pr1646v2BgriMVCachePerfEntry 385875968}

pr1646v2BgriMVCachePerfType OBJECT-TYPE
   SYNTAX      INTEGER
               {
               static (0),
               dynamic (1),
               tester (2),
               fastFlood (3)
               }
   MAX-ACCESS  read-only
   STATUS      current
   DESCRIPTION
      "Path: vpnBridgeGroup.performance.bridgeCache.type

       Possibilities:
               static   (0)
               dynamic   (1)
               tester   (2)
               fastFlood   (3)"
   ::= {pr1646v2BgriMVCachePerfEntry 352321536}

pr1646v2BgriMVCachePerfRxPkts OBJECT-TYPE
   SYNTAX      Counter32
   MAX-ACCESS  read-only
   STATUS      current
   DESCRIPTION
      "Path: vpnBridgeGroup.performance.bridgeCache.rxPkts

       32 bit unsigned wrappable counter."
   ::= {pr1646v2BgriMVCachePerfEntry 83886080}

pr1646v2BgriMVCachePerfTxPkts OBJECT-TYPE
   SYNTAX      Counter32
   MAX-ACCESS  read-only
   STATUS      current
   DESCRIPTION
      "Path: vpnBridgeGroup.performance.bridgeCache.txPkts

       32 bit unsigned wrappable counter."
   ::= {pr1646v2BgriMVCachePerfEntry 100663296}

pr1646v2BgriMVCachePerfStatViols OBJECT-TYPE
   SYNTAX      Counter32
   MAX-ACCESS  read-only
   STATUS      current
   DESCRIPTION
      "Path: vpnBridgeGroup.performance.bridgeCache.staticViolations

       32 bit unsigned wrappable counter."
   ::= {pr1646v2BgriMVCachePerfEntry 117440512}

pr1646v2BgriMVCachePerfRelearns OBJECT-TYPE
   SYNTAX      Counter32
   MAX-ACCESS  read-only
   STATUS      current
   DESCRIPTION
      "Path: vpnBridgeGroup.performance.bridgeCache.relearns

       32 bit unsigned wrappable counter."
   ::= {pr1646v2BgriMVCachePerfEntry 134217728}

pr1646v2BgriMVCachePerfRelearnDrops OBJECT-TYPE
   SYNTAX      Counter32
   MAX-ACCESS  read-only
   STATUS      current
   DESCRIPTION
      "Path: vpnBridgeGroup.performance.bridgeCache.relearnDrops

       32 bit unsigned wrappable counter."
   ::= {pr1646v2BgriMVCachePerfEntry 150994944}


pr1646v2BgriMVResCachePerf OBJECT IDENTIFIER ::= {pr1646v2BgriMV 45}

pr1646v2BgriMVResCachePerfSSCTable OBJECT-TYPE
   SYNTAX      SEQUENCE OF Pr1646v2BgriMVResCachePerfEntry
   MAX-ACCESS  not-accessible
   STATUS      current
   DESCRIPTION
      "cache of reserved Ethernet addresses"
   ::= {pr1646v2BgriMVResCachePerf 1}

pr1646v2BgriMVResCachePerfEntry OBJECT-TYPE
   SYNTAX      Pr1646v2BgriMVResCachePerfEntry
   MAX-ACCESS  not-accessible
   STATUS      current
   DESCRIPTION
      ""
   INDEX      { pr1646v2BgriMVResCachePerfGlobalIx,
                pr1646v2BgriMVResCachePerfTableIx }
   ::= {pr1646v2BgriMVResCachePerfSSCTable 1}

Pr1646v2BgriMVResCachePerfEntry ::=
   SEQUENCE
      {
      pr1646v2BgriMVResCachePerfGlobalIx
         GlobalIndex,
      pr1646v2BgriMVResCachePerfTableIx
         TableIndex,
      pr1646v2BgriMVResCachePerfMacAddress
         OCTET STRING,
      pr1646v2BgriMVResCachePerfRxPkts
         Counter32
      }

pr1646v2BgriMVResCachePerfGlobalIx OBJECT-TYPE
   SYNTAX      GlobalIndex
   MAX-ACCESS  not-accessible
   STATUS      current
   DESCRIPTION
      "The value of the tlsCntTreeGlobalIndex of the MANAGED OBJECT."
   ::= {pr1646v2BgriMVResCachePerfEntry 10}

pr1646v2BgriMVResCachePerfTableIx OBJECT-TYPE
   SYNTAX      TableIndex
   MAX-ACCESS  not-accessible
   STATUS      current
   DESCRIPTION
      ""
   ::= {pr1646v2BgriMVResCachePerfEntry 11}

pr1646v2BgriMVResCachePerfMacAddress OBJECT-TYPE
   SYNTAX      OCTET STRING
   MAX-ACCESS  read-only
   STATUS      current
   DESCRIPTION
      "Path: vpnBridgeGroup.performance.reservedAddressCache.macAddress

       MAC address."
   ::= {pr1646v2BgriMVResCachePerfEntry 16777216}

pr1646v2BgriMVResCachePerfRxPkts OBJECT-TYPE
   SYNTAX      Counter32
   MAX-ACCESS  read-only
   STATUS      current
   DESCRIPTION
      "Path: vpnBridgeGroup.performance.reservedAddressCache.rxPkts

       32 bit unsigned wrappable counter."
   ::= {pr1646v2BgriMVResCachePerfEntry 33554432}


pr1646v2BgriMVCacheEvents OBJECT IDENTIFIER ::= {pr1646v2BgriMV 44}

pr1646v2BgriMVCacheEventsSSCTable OBJECT-TYPE
   SYNTAX      SEQUENCE OF Pr1646v2BgriMVCacheEventsEntry
   MAX-ACCESS  not-accessible
   STATUS      current
   DESCRIPTION
      "bridge performances"
   ::= {pr1646v2BgriMVCacheEvents 1}

pr1646v2BgriMVCacheEventsEntry OBJECT-TYPE
   SYNTAX      Pr1646v2BgriMVCacheEventsEntry
   MAX-ACCESS  not-accessible
   STATUS      current
   DESCRIPTION
      ""
   INDEX      { pr1646v2BgriMVCacheEventsGlobalIx }
   ::= {pr1646v2BgriMVCacheEventsSSCTable 1}

Pr1646v2BgriMVCacheEventsEntry ::=
   SEQUENCE
      {
      pr1646v2BgriMVCacheEventsGlobalIx
         GlobalIndex,
      pr1646v2BgriMVCacheEventsSizeOverflows
         Counter32,
      pr1646v2BgriMVCacheEventsStaticViolations
         Counter32,
      pr1646v2BgriMVCacheEventsRelearns
         Counter32,
      pr1646v2BgriMVCacheEventsRelearnDrops
         Counter32,
      pr1646v2BgriMVCacheEventsLoopsDetected
         Counter32
      }

pr1646v2BgriMVCacheEventsGlobalIx OBJECT-TYPE
   SYNTAX      GlobalIndex
   MAX-ACCESS  not-accessible
   STATUS      current
   DESCRIPTION
      "The value of the tlsCntTreeGlobalIndex of the MANAGED OBJECT."
   ::= {pr1646v2BgriMVCacheEventsEntry 10}

pr1646v2BgriMVCacheEventsSizeOverflows OBJECT-TYPE
   SYNTAX      Counter32
   MAX-ACCESS  read-only
   STATUS      current
   DESCRIPTION
      "Path: vpnBridgeGroup.performance.cacheEvents.sizeOverflows

       32 bit unsigned wrappable counter."
   ::= {pr1646v2BgriMVCacheEventsEntry 16777216}

pr1646v2BgriMVCacheEventsStaticViolations OBJECT-TYPE
   SYNTAX      Counter32
   MAX-ACCESS  read-only
   STATUS      current
   DESCRIPTION
      "Path: vpnBridgeGroup.performance.cacheEvents.staticViolations

       32 bit unsigned wrappable counter."
   ::= {pr1646v2BgriMVCacheEventsEntry 33554432}

pr1646v2BgriMVCacheEventsRelearns OBJECT-TYPE
   SYNTAX      Counter32
   MAX-ACCESS  read-only
   STATUS      current
   DESCRIPTION
      "Path: vpnBridgeGroup.performance.cacheEvents.relearns

       32 bit unsigned wrappable counter."
   ::= {pr1646v2BgriMVCacheEventsEntry 50331648}

pr1646v2BgriMVCacheEventsRelearnDrops OBJECT-TYPE
   SYNTAX      Counter32
   MAX-ACCESS  read-only
   STATUS      current
   DESCRIPTION
      "Path: vpnBridgeGroup.performance.cacheEvents.relearnDrops

       32 bit unsigned wrappable counter."
   ::= {pr1646v2BgriMVCacheEventsEntry 67108864}

pr1646v2BgriMVCacheEventsLoopsDetected OBJECT-TYPE
   SYNTAX      Counter32
   MAX-ACCESS  read-only
   STATUS      current
   DESCRIPTION
      "Path: vpnBridgeGroup.performance.cacheEvents.loopsDetected

       32 bit unsigned wrappable counter."
   ::= {pr1646v2BgriMVCacheEventsEntry 117440512}


pr1646v2BgriMVBridgeRxPkts OBJECT IDENTIFIER ::= {pr1646v2BgriMV 42}

pr1646v2BgriMVBridgeRxPktsTable OBJECT-TYPE
   SYNTAX      SEQUENCE OF Pr1646v2BgriMVBridgeRxPktsEntry
   MAX-ACCESS  not-accessible
   STATUS      current
   DESCRIPTION
      "counter (floods or discards) of bridge"
   ::= {pr1646v2BgriMVBridgeRxPkts 1}

pr1646v2BgriMVBridgeRxPktsEntry OBJECT-TYPE
   SYNTAX      Pr1646v2BgriMVBridgeRxPktsEntry
   MAX-ACCESS  not-accessible
   STATUS      current
   DESCRIPTION
      ""
   INDEX      { pr1646v2BgriMVBridgeRxPktsGlobalIx }
   ::= {pr1646v2BgriMVBridgeRxPktsTable 1}

Pr1646v2BgriMVBridgeRxPktsEntry ::=
   SEQUENCE
      {
      pr1646v2BgriMVBridgeRxPktsGlobalIx
         GlobalIndex,
      pr1646v2BgriMVBridgeRxPktsValue
         Counter32
      }

pr1646v2BgriMVBridgeRxPktsGlobalIx OBJECT-TYPE
   SYNTAX      GlobalIndex
   MAX-ACCESS  not-accessible
   STATUS      current
   DESCRIPTION
      "The value of the tlsCntTreeGlobalIndex of the MANAGED OBJECT."
   ::= {pr1646v2BgriMVBridgeRxPktsEntry 10}

pr1646v2BgriMVBridgeRxPktsValue OBJECT-TYPE
   SYNTAX      Counter32
   MAX-ACCESS  read-only
   STATUS      current
   DESCRIPTION
      "Path: vpnBridgeGroup.performance.bridgeRxPkts

       32 bit unsigned wrappable counter."
   ::= {pr1646v2BgriMVBridgeRxPktsEntry 2147483648}


pr1646v2BgriMVBridgeTxPkts OBJECT IDENTIFIER ::= {pr1646v2BgriMV 43}

pr1646v2BgriMVBridgeTxPktsTable OBJECT-TYPE
   SYNTAX      SEQUENCE OF Pr1646v2BgriMVBridgeTxPktsEntry
   MAX-ACCESS  not-accessible
   STATUS      current
   DESCRIPTION
      "counter (floods or discards) of bridge"
   ::= {pr1646v2BgriMVBridgeTxPkts 1}

pr1646v2BgriMVBridgeTxPktsEntry OBJECT-TYPE
   SYNTAX      Pr1646v2BgriMVBridgeTxPktsEntry
   MAX-ACCESS  not-accessible
   STATUS      current
   DESCRIPTION
      ""
   INDEX      { pr1646v2BgriMVBridgeTxPktsGlobalIx }
   ::= {pr1646v2BgriMVBridgeTxPktsTable 1}

Pr1646v2BgriMVBridgeTxPktsEntry ::=
   SEQUENCE
      {
      pr1646v2BgriMVBridgeTxPktsGlobalIx
         GlobalIndex,
      pr1646v2BgriMVBridgeTxPktsValue
         Counter32
      }

pr1646v2BgriMVBridgeTxPktsGlobalIx OBJECT-TYPE
   SYNTAX      GlobalIndex
   MAX-ACCESS  not-accessible
   STATUS      current
   DESCRIPTION
      "The value of the tlsCntTreeGlobalIndex of the MANAGED OBJECT."
   ::= {pr1646v2BgriMVBridgeTxPktsEntry 10}

pr1646v2BgriMVBridgeTxPktsValue OBJECT-TYPE
   SYNTAX      Counter32
   MAX-ACCESS  read-only
   STATUS      current
   DESCRIPTION
      "Path: vpnBridgeGroup.performance.bridgeTxPkts

       32 bit unsigned wrappable counter."
   ::= {pr1646v2BgriMVBridgeTxPktsEntry 2147483648}


pr1646v2BgriMVBridgeDiscards OBJECT IDENTIFIER ::= {pr1646v2BgriMV 7}

pr1646v2BgriMVBridgeDiscardsTable OBJECT-TYPE
   SYNTAX      SEQUENCE OF Pr1646v2BgriMVBridgeDiscardsEntry
   MAX-ACCESS  not-accessible
   STATUS      current
   DESCRIPTION
      "counter (floods or discards) of bridge"
   ::= {pr1646v2BgriMVBridgeDiscards 1}

pr1646v2BgriMVBridgeDiscardsEntry OBJECT-TYPE
   SYNTAX      Pr1646v2BgriMVBridgeDiscardsEntry
   MAX-ACCESS  not-accessible
   STATUS      current
   DESCRIPTION
      ""
   INDEX      { pr1646v2BgriMVBridgeDiscardsGlobalIx }
   ::= {pr1646v2BgriMVBridgeDiscardsTable 1}

Pr1646v2BgriMVBridgeDiscardsEntry ::=
   SEQUENCE
      {
      pr1646v2BgriMVBridgeDiscardsGlobalIx
         GlobalIndex,
      pr1646v2BgriMVBridgeDiscardsValue
         Counter32
      }

pr1646v2BgriMVBridgeDiscardsGlobalIx OBJECT-TYPE
   SYNTAX      GlobalIndex
   MAX-ACCESS  not-accessible
   STATUS      current
   DESCRIPTION
      "The value of the tlsCntTreeGlobalIndex of the MANAGED OBJECT."
   ::= {pr1646v2BgriMVBridgeDiscardsEntry 10}

pr1646v2BgriMVBridgeDiscardsValue OBJECT-TYPE
   SYNTAX      Counter32
   MAX-ACCESS  read-only
   STATUS      current
   DESCRIPTION
      "Path: vpnBridgeGroup.performance.bridgeDiscards

       32 bit unsigned wrappable counter."
   ::= {pr1646v2BgriMVBridgeDiscardsEntry 2147483648}


pr1646v2BgriMVBridgeFloods OBJECT IDENTIFIER ::= {pr1646v2BgriMV 8}

pr1646v2BgriMVBridgeFloodsTable OBJECT-TYPE
   SYNTAX      SEQUENCE OF Pr1646v2BgriMVBridgeFloodsEntry
   MAX-ACCESS  not-accessible
   STATUS      current
   DESCRIPTION
      "counter (floods or discards) of bridge"
   ::= {pr1646v2BgriMVBridgeFloods 1}

pr1646v2BgriMVBridgeFloodsEntry OBJECT-TYPE
   SYNTAX      Pr1646v2BgriMVBridgeFloodsEntry
   MAX-ACCESS  not-accessible
   STATUS      current
   DESCRIPTION
      ""
   INDEX      { pr1646v2BgriMVBridgeFloodsGlobalIx }
   ::= {pr1646v2BgriMVBridgeFloodsTable 1}

Pr1646v2BgriMVBridgeFloodsEntry ::=
   SEQUENCE
      {
      pr1646v2BgriMVBridgeFloodsGlobalIx
         GlobalIndex,
      pr1646v2BgriMVBridgeFloodsValue
         Counter32
      }

pr1646v2BgriMVBridgeFloodsGlobalIx OBJECT-TYPE
   SYNTAX      GlobalIndex
   MAX-ACCESS  not-accessible
   STATUS      current
   DESCRIPTION
      "The value of the tlsCntTreeGlobalIndex of the MANAGED OBJECT."
   ::= {pr1646v2BgriMVBridgeFloodsEntry 10}

pr1646v2BgriMVBridgeFloodsValue OBJECT-TYPE
   SYNTAX      Counter32
   MAX-ACCESS  read-only
   STATUS      current
   DESCRIPTION
      "Path: vpnBridgeGroup.performance.bridgeFloods

       32 bit unsigned wrappable counter."
   ::= {pr1646v2BgriMVBridgeFloodsEntry 2147483648}


pr1646v2BgriMVBridgeBroadcasts OBJECT IDENTIFIER ::= {pr1646v2BgriMV 40}

pr1646v2BgriMVBridgeBroadcastsTable OBJECT-TYPE
   SYNTAX      SEQUENCE OF Pr1646v2BgriMVBridgeBroadcastsEntry
   MAX-ACCESS  not-accessible
   STATUS      current
   DESCRIPTION
      "counter (floods or discards) of bridge"
   ::= {pr1646v2BgriMVBridgeBroadcasts 1}

pr1646v2BgriMVBridgeBroadcastsEntry OBJECT-TYPE
   SYNTAX      Pr1646v2BgriMVBridgeBroadcastsEntry
   MAX-ACCESS  not-accessible
   STATUS      current
   DESCRIPTION
      ""
   INDEX      { pr1646v2BgriMVBridgeBroadcastsGlobalIx }
   ::= {pr1646v2BgriMVBridgeBroadcastsTable 1}

Pr1646v2BgriMVBridgeBroadcastsEntry ::=
   SEQUENCE
      {
      pr1646v2BgriMVBridgeBroadcastsGlobalIx
         GlobalIndex,
      pr1646v2BgriMVBridgeBroadcastsValue
         Counter32
      }

pr1646v2BgriMVBridgeBroadcastsGlobalIx OBJECT-TYPE
   SYNTAX      GlobalIndex
   MAX-ACCESS  not-accessible
   STATUS      current
   DESCRIPTION
      "The value of the tlsCntTreeGlobalIndex of the MANAGED OBJECT."
   ::= {pr1646v2BgriMVBridgeBroadcastsEntry 10}

pr1646v2BgriMVBridgeBroadcastsValue OBJECT-TYPE
   SYNTAX      Counter32
   MAX-ACCESS  read-only
   STATUS      current
   DESCRIPTION
      "Path: vpnBridgeGroup.performance.bridgeBroadcasts

       32 bit unsigned wrappable counter."
   ::= {pr1646v2BgriMVBridgeBroadcastsEntry 2147483648}


pr1646v2BgriMVBridgeMulticasts OBJECT IDENTIFIER ::= {pr1646v2BgriMV 41}

pr1646v2BgriMVBridgeMulticastsTable OBJECT-TYPE
   SYNTAX      SEQUENCE OF Pr1646v2BgriMVBridgeMulticastsEntry
   MAX-ACCESS  not-accessible
   STATUS      current
   DESCRIPTION
      "counter (floods or discards) of bridge"
   ::= {pr1646v2BgriMVBridgeMulticasts 1}

pr1646v2BgriMVBridgeMulticastsEntry OBJECT-TYPE
   SYNTAX      Pr1646v2BgriMVBridgeMulticastsEntry
   MAX-ACCESS  not-accessible
   STATUS      current
   DESCRIPTION
      ""
   INDEX      { pr1646v2BgriMVBridgeMulticastsGlobalIx }
   ::= {pr1646v2BgriMVBridgeMulticastsTable 1}

Pr1646v2BgriMVBridgeMulticastsEntry ::=
   SEQUENCE
      {
      pr1646v2BgriMVBridgeMulticastsGlobalIx
         GlobalIndex,
      pr1646v2BgriMVBridgeMulticastsValue
         Counter32
      }

pr1646v2BgriMVBridgeMulticastsGlobalIx OBJECT-TYPE
   SYNTAX      GlobalIndex
   MAX-ACCESS  not-accessible
   STATUS      current
   DESCRIPTION
      "The value of the tlsCntTreeGlobalIndex of the MANAGED OBJECT."
   ::= {pr1646v2BgriMVBridgeMulticastsEntry 10}

pr1646v2BgriMVBridgeMulticastsValue OBJECT-TYPE
   SYNTAX      Counter32
   MAX-ACCESS  read-only
   STATUS      current
   DESCRIPTION
      "Path: vpnBridgeGroup.performance.bridgeMulticasts

       32 bit unsigned wrappable counter."
   ::= {pr1646v2BgriMVBridgeMulticastsEntry 2147483648}


pr1646v2BgriMVVlanSwitching OBJECT IDENTIFIER ::= {pr1646v2BgriMV 30}

pr1646v2BgriMVVlanSwitchingSSCTable OBJECT-TYPE
   SYNTAX      SEQUENCE OF Pr1646v2BgriMVVlanSwitchingEntry
   MAX-ACCESS  not-accessible
   STATUS      current
   DESCRIPTION
      "ospf area summary lsa overview"
   ::= {pr1646v2BgriMVVlanSwitching 1}

pr1646v2BgriMVVlanSwitchingEntry OBJECT-TYPE
   SYNTAX      Pr1646v2BgriMVVlanSwitchingEntry
   MAX-ACCESS  not-accessible
   STATUS      current
   DESCRIPTION
      ""
   INDEX      { pr1646v2BgriMVVlanSwitchingGlobalIx,
                pr1646v2BgriMVVlanSwitchingTableIx }
   ::= {pr1646v2BgriMVVlanSwitchingSSCTable 1}

Pr1646v2BgriMVVlanSwitchingEntry ::=
   SEQUENCE
      {
      pr1646v2BgriMVVlanSwitchingGlobalIx
         GlobalIndex,
      pr1646v2BgriMVVlanSwitchingTableIx
         TableIndex,
      pr1646v2BgriMVVlanSwitchingSrcIntf
         DisplayString,
      pr1646v2BgriMVVlanSwitchingSrcVlan
         INTEGER,
      pr1646v2BgriMVVlanSwitchingSrcPFlt
         INTEGER,
      pr1646v2BgriMVVlanSwitchingDestIntf
         DisplayString,
      pr1646v2BgriMVVlanSwitchingDestVlan
         INTEGER,
      pr1646v2BgriMVVlanSwitchingTunnelMode
         INTEGER,
      pr1646v2BgriMVVlanSwitchingUses
         Counter32
      }

pr1646v2BgriMVVlanSwitchingGlobalIx OBJECT-TYPE
   SYNTAX      GlobalIndex
   MAX-ACCESS  not-accessible
   STATUS      current
   DESCRIPTION
      "The value of the tlsCntTreeGlobalIndex of the MANAGED OBJECT."
   ::= {pr1646v2BgriMVVlanSwitchingEntry 10}

pr1646v2BgriMVVlanSwitchingTableIx OBJECT-TYPE
   SYNTAX      TableIndex
   MAX-ACCESS  not-accessible
   STATUS      current
   DESCRIPTION
      ""
   ::= {pr1646v2BgriMVVlanSwitchingEntry 11}

pr1646v2BgriMVVlanSwitchingSrcIntf OBJECT-TYPE
   SYNTAX      DisplayString
   MAX-ACCESS  read-only
   STATUS      current
   DESCRIPTION
      "Path: vpnBridgeGroup.performance.vlanSwitching.sourceIntf"
   ::= {pr1646v2BgriMVVlanSwitchingEntry 16777216}

pr1646v2BgriMVVlanSwitchingSrcVlan OBJECT-TYPE
   SYNTAX      INTEGER
               {
               any (-1)
               }
   MAX-ACCESS  read-only
   STATUS      current
   DESCRIPTION
      "Path: vpnBridgeGroup.performance.vlanSwitching.sourceVlan

       Possibilities:
               any   (-1)"
   ::= {pr1646v2BgriMVVlanSwitchingEntry 33554432}

pr1646v2BgriMVVlanSwitchingSrcPFlt OBJECT-TYPE
   SYNTAX      INTEGER
               {
               any (-1)
               }
   MAX-ACCESS  read-only
   STATUS      current
   DESCRIPTION
      "Path: vpnBridgeGroup.performance.vlanSwitching.sourcePFilter

       Possibilities:
               any   (-1)"
   ::= {pr1646v2BgriMVVlanSwitchingEntry 100663296}

pr1646v2BgriMVVlanSwitchingDestIntf OBJECT-TYPE
   SYNTAX      DisplayString
   MAX-ACCESS  read-only
   STATUS      current
   DESCRIPTION
      "Path: vpnBridgeGroup.performance.vlanSwitching.destinationIntf"
   ::= {pr1646v2BgriMVVlanSwitchingEntry 50331648}

pr1646v2BgriMVVlanSwitchingDestVlan OBJECT-TYPE
   SYNTAX      INTEGER
               {
               unchanged (-1)
               }
   MAX-ACCESS  read-only
   STATUS      current
   DESCRIPTION
      "Path: vpnBridgeGroup.performance.vlanSwitching.destinationVlan

       Possibilities:
               unchanged   (-1)"
   ::= {pr1646v2BgriMVVlanSwitchingEntry 67108864}

pr1646v2BgriMVVlanSwitchingTunnelMode OBJECT-TYPE
   SYNTAX      INTEGER
               {
               none (0),
               toTunnel (1),
               fromTunnel (2),
               toSVlanTunnel (3),
               fromSVlanTunnel (4)
               }
   MAX-ACCESS  read-only
   STATUS      current
   DESCRIPTION
      "Path: vpnBridgeGroup.performance.vlanSwitching.tunnelMode

       Possibilities:
               none   (0)
               toTunnel   (1)
               fromTunnel   (2)
               toSVlanTunnel   (3)
               fromSVlanTunnel   (4)"
   ::= {pr1646v2BgriMVVlanSwitchingEntry 117440512}

pr1646v2BgriMVVlanSwitchingUses OBJECT-TYPE
   SYNTAX      Counter32
   MAX-ACCESS  read-only
   STATUS      current
   DESCRIPTION
      "Path: vpnBridgeGroup.performance.vlanSwitching.uses

       32 bit unsigned wrappable counter."
   ::= {pr1646v2BgriMVVlanSwitchingEntry 83886080}


pr1646v2BgriMVMibCounters OBJECT IDENTIFIER ::= {pr1646v2BgriMV 100}

pr1646v2BgriMVMibCountersSSCTable OBJECT-TYPE
   SYNTAX      SEQUENCE OF Pr1646v2BgriMVMibCountersEntry
   MAX-ACCESS  not-accessible
   STATUS      current
   DESCRIPTION
      "mibCounter"
   ::= {pr1646v2BgriMVMibCounters 1}

pr1646v2BgriMVMibCountersEntry OBJECT-TYPE
   SYNTAX      Pr1646v2BgriMVMibCountersEntry
   MAX-ACCESS  not-accessible
   STATUS      current
   DESCRIPTION
      ""
   INDEX      { pr1646v2BgriMVMibCountersGlobalIx }
   ::= {pr1646v2BgriMVMibCountersSSCTable 1}

Pr1646v2BgriMVMibCountersEntry ::=
   SEQUENCE
      {
      pr1646v2BgriMVMibCountersGlobalIx
         GlobalIndex,
      pr1646v2BgriMVMibCountersInOctets
         Counter64,
      pr1646v2BgriMVMibCountersInUcast
         Counter64,
      pr1646v2BgriMVMibCountersInNUcastPkts
         Counter64,
      pr1646v2BgriMVMibCountersInBcastPkts
         Counter64,
      pr1646v2BgriMVMibCountersInMcastPkts
         Counter64,
      pr1646v2BgriMVMibCountersInDiscards
         Counter64,
      pr1646v2BgriMVMibCountersInErrors
         Counter64,
      pr1646v2BgriMVMibCountersInUnknownProtos
         Counter64,
      pr1646v2BgriMVMibCountersInDropEx
         Counter64,
      pr1646v2BgriMVMibCountersInDropNoMac
         Counter64,
      pr1646v2BgriMVMibCountersInDropNUCast
         Counter64,
      pr1646v2BgriMVMibCountersInDropFilter
         Counter64,
      pr1646v2BgriMVMibCountersInBandwidth15sec
         Integer32,
      pr1646v2BgriMVMibCountersInBandwidth30sec
         Integer32,
      pr1646v2BgriMVMibCountersInBandwidth1min
         Integer32,
      pr1646v2BgriMVMibCountersInBandwidth2min
         Integer32,
      pr1646v2BgriMVMibCountersInBandwidth5min
         Integer32,
      pr1646v2BgriMVMibCountersOutOctets
         Counter64,
      pr1646v2BgriMVMibCountersOutUcastPkts
         Counter64,
      pr1646v2BgriMVMibCountersOutNUcastPkts
         Counter64,
      pr1646v2BgriMVMibCountersOutBcastPkts
         Counter64,
      pr1646v2BgriMVMibCountersOutMcastPkts
         Counter64,
      pr1646v2BgriMVMibCountersOutDiscards
         Counter64,
      pr1646v2BgriMVMibCountersOutErrors
         Counter64,
      pr1646v2BgriMVMibCountersOutQLen
         Counter32,
      pr1646v2BgriMVMibCountersOutDropEx
         Counter64,
      pr1646v2BgriMVMibCountersOutDropNoArp
         Counter64,
      pr1646v2BgriMVMibCountersOutDropFilter
         Counter64,
      pr1646v2BgriMVMibCountersOutBandwidth15sec
         Integer32,
      pr1646v2BgriMVMibCountersOutBandwidth30sec
         Integer32,
      pr1646v2BgriMVMibCountersOutBandwidth1min
         Integer32,
      pr1646v2BgriMVMibCountersOutBandwidth2min
         Integer32,
      pr1646v2BgriMVMibCountersOutBandwidth5min
         Integer32
      }

pr1646v2BgriMVMibCountersGlobalIx OBJECT-TYPE
   SYNTAX      GlobalIndex
   MAX-ACCESS  not-accessible
   STATUS      current
   DESCRIPTION
      "The value of the tlsCntTreeGlobalIndex of the MANAGED OBJECT."
   ::= {pr1646v2BgriMVMibCountersEntry 10}

pr1646v2BgriMVMibCountersInOctets OBJECT-TYPE
   SYNTAX      Counter64
   MAX-ACCESS  read-only
   STATUS      current
   DESCRIPTION
      "Path: vpnBridgeGroup.performance.mibCounters.ifInOctets

       64 bit unsigned wrappable counter."
   ::= {pr1646v2BgriMVMibCountersEntry 1828716544}

pr1646v2BgriMVMibCountersInUcast OBJECT-TYPE
   SYNTAX      Counter64
   MAX-ACCESS  read-only
   STATUS      current
   DESCRIPTION
      "Path: vpnBridgeGroup.performance.mibCounters.ifInUcastPkts

       64 bit unsigned wrappable counter."
   ::= {pr1646v2BgriMVMibCountersEntry 1845493760}

pr1646v2BgriMVMibCountersInNUcastPkts OBJECT-TYPE
   SYNTAX      Counter64
   MAX-ACCESS  read-only
   STATUS      current
   DESCRIPTION
      "Path: vpnBridgeGroup.performance.mibCounters.ifInNUcastPkts

       64 bit unsigned wrappable counter."
   ::= {pr1646v2BgriMVMibCountersEntry 1862270976}

pr1646v2BgriMVMibCountersInBcastPkts OBJECT-TYPE
   SYNTAX      Counter64
   MAX-ACCESS  read-only
   STATUS      current
   DESCRIPTION
      "Path: vpnBridgeGroup.performance.mibCounters.ifInBcastPkts

       64 bit unsigned wrappable counter."
   ::= {pr1646v2BgriMVMibCountersEntry 3539992576}

pr1646v2BgriMVMibCountersInMcastPkts OBJECT-TYPE
   SYNTAX      Counter64
   MAX-ACCESS  read-only
   STATUS      current
   DESCRIPTION
      "Path: vpnBridgeGroup.performance.mibCounters.ifInMcastPkts

       64 bit unsigned wrappable counter."
   ::= {pr1646v2BgriMVMibCountersEntry 3707764736}

pr1646v2BgriMVMibCountersInDiscards OBJECT-TYPE
   SYNTAX      Counter64
   MAX-ACCESS  read-only
   STATUS      current
   DESCRIPTION
      "Path: vpnBridgeGroup.performance.mibCounters.ifInDiscards

       64 bit unsigned wrappable counter."
   ::= {pr1646v2BgriMVMibCountersEntry 1879048192}

pr1646v2BgriMVMibCountersInErrors OBJECT-TYPE
   SYNTAX      Counter64
   MAX-ACCESS  read-only
   STATUS      current
   DESCRIPTION
      "Path: vpnBridgeGroup.performance.mibCounters.ifInErrors

       64 bit unsigned wrappable counter."
   ::= {pr1646v2BgriMVMibCountersEntry 1895825408}

pr1646v2BgriMVMibCountersInUnknownProtos OBJECT-TYPE
   SYNTAX      Counter64
   MAX-ACCESS  read-only
   STATUS      current
   DESCRIPTION
      "Path: vpnBridgeGroup.performance.mibCounters.ifInUnknownProtos

       64 bit unsigned wrappable counter."
   ::= {pr1646v2BgriMVMibCountersEntry 1912602624}

pr1646v2BgriMVMibCountersInDropEx OBJECT-TYPE
   SYNTAX      Counter64
   MAX-ACCESS  read-only
   STATUS      current
   DESCRIPTION
      "Path: vpnBridgeGroup.performance.mibCounters.ifInDropLevelExceeded

       64 bit unsigned wrappable counter."
   ::= {pr1646v2BgriMVMibCountersEntry 2181038080}

pr1646v2BgriMVMibCountersInDropNoMac OBJECT-TYPE
   SYNTAX      Counter64
   MAX-ACCESS  read-only
   STATUS      current
   DESCRIPTION
      "Path: vpnBridgeGroup.performance.mibCounters.ifInDiscardsNoMacFit

       64 bit unsigned wrappable counter."
   ::= {pr1646v2BgriMVMibCountersEntry 2231369728}

pr1646v2BgriMVMibCountersInDropNUCast OBJECT-TYPE
   SYNTAX      Counter64
   MAX-ACCESS  read-only
   STATUS      current
   DESCRIPTION
      "Path: vpnBridgeGroup.performance.mibCounters.ifInDiscardsNUCast

       64 bit unsigned wrappable counter."
   ::= {pr1646v2BgriMVMibCountersEntry 2281701376}

pr1646v2BgriMVMibCountersInDropFilter OBJECT-TYPE
   SYNTAX      Counter64
   MAX-ACCESS  read-only
   STATUS      current
   DESCRIPTION
      "Path: vpnBridgeGroup.performance.mibCounters.ifInDiscardsFilter

       64 bit unsigned wrappable counter."
   ::= {pr1646v2BgriMVMibCountersEntry 2298478592}

pr1646v2BgriMVMibCountersInBandwidth15sec OBJECT-TYPE
   SYNTAX      Integer32
   MAX-ACCESS  read-only
   STATUS      current
   DESCRIPTION
      "Path: vpnBridgeGroup.performance.mibCounters.ifInBandwidth.15sec

       unit name = bps
       formula = 8 * ; 8 /"
   ::= {pr1646v2BgriMVMibCountersEntry 3037003776}

pr1646v2BgriMVMibCountersInBandwidth30sec OBJECT-TYPE
   SYNTAX      Integer32
   MAX-ACCESS  read-only
   STATUS      current
   DESCRIPTION
      "Path: vpnBridgeGroup.performance.mibCounters.ifInBandwidth.30sec

       unit name = bps
       formula = 8 * ; 8 /"
   ::= {pr1646v2BgriMVMibCountersEntry 3037331456}

pr1646v2BgriMVMibCountersInBandwidth1min OBJECT-TYPE
   SYNTAX      Integer32
   MAX-ACCESS  read-only
   STATUS      current
   DESCRIPTION
      "Path: vpnBridgeGroup.performance.mibCounters.ifInBandwidth.1min

       unit name = bps
       formula = 8 * ; 8 /"
   ::= {pr1646v2BgriMVMibCountersEntry 3037986816}

pr1646v2BgriMVMibCountersInBandwidth2min OBJECT-TYPE
   SYNTAX      Integer32
   MAX-ACCESS  read-only
   STATUS      current
   DESCRIPTION
      "Path: vpnBridgeGroup.performance.mibCounters.ifInBandwidth.2min

       unit name = bps
       formula = 8 * ; 8 /"
   ::= {pr1646v2BgriMVMibCountersEntry 3039297536}

pr1646v2BgriMVMibCountersInBandwidth5min OBJECT-TYPE
   SYNTAX      Integer32
   MAX-ACCESS  read-only
   STATUS      current
   DESCRIPTION
      "Path: vpnBridgeGroup.performance.mibCounters.ifInBandwidth.5min

       unit name = bps
       formula = 8 * ; 8 /"
   ::= {pr1646v2BgriMVMibCountersEntry 3043229696}

pr1646v2BgriMVMibCountersOutOctets OBJECT-TYPE
   SYNTAX      Counter64
   MAX-ACCESS  read-only
   STATUS      current
   DESCRIPTION
      "Path: vpnBridgeGroup.performance.mibCounters.ifOutOctets

       64 bit unsigned wrappable counter."
   ::= {pr1646v2BgriMVMibCountersEntry 1929379840}

pr1646v2BgriMVMibCountersOutUcastPkts OBJECT-TYPE
   SYNTAX      Counter64
   MAX-ACCESS  read-only
   STATUS      current
   DESCRIPTION
      "Path: vpnBridgeGroup.performance.mibCounters.ifOutUcastPkts

       64 bit unsigned wrappable counter."
   ::= {pr1646v2BgriMVMibCountersEntry 1946157056}

pr1646v2BgriMVMibCountersOutNUcastPkts OBJECT-TYPE
   SYNTAX      Counter64
   MAX-ACCESS  read-only
   STATUS      current
   DESCRIPTION
      "Path: vpnBridgeGroup.performance.mibCounters.ifOutNUcastPkts

       64 bit unsigned wrappable counter."
   ::= {pr1646v2BgriMVMibCountersEntry 1962934272}

pr1646v2BgriMVMibCountersOutBcastPkts OBJECT-TYPE
   SYNTAX      Counter64
   MAX-ACCESS  read-only
   STATUS      current
   DESCRIPTION
      "Path: vpnBridgeGroup.performance.mibCounters.ifOutBcastPkts

       64 bit unsigned wrappable counter."
   ::= {pr1646v2BgriMVMibCountersEntry 3640655872}

pr1646v2BgriMVMibCountersOutMcastPkts OBJECT-TYPE
   SYNTAX      Counter64
   MAX-ACCESS  read-only
   STATUS      current
   DESCRIPTION
      "Path: vpnBridgeGroup.performance.mibCounters.ifOutMcastPkts

       64 bit unsigned wrappable counter."
   ::= {pr1646v2BgriMVMibCountersEntry 3808428032}

pr1646v2BgriMVMibCountersOutDiscards OBJECT-TYPE
   SYNTAX      Counter64
   MAX-ACCESS  read-only
   STATUS      current
   DESCRIPTION
      "Path: vpnBridgeGroup.performance.mibCounters.ifOutDiscards

       64 bit unsigned wrappable counter."
   ::= {pr1646v2BgriMVMibCountersEntry 1979711488}

pr1646v2BgriMVMibCountersOutErrors OBJECT-TYPE
   SYNTAX      Counter64
   MAX-ACCESS  read-only
   STATUS      current
   DESCRIPTION
      "Path: vpnBridgeGroup.performance.mibCounters.ifOutErrors

       64 bit unsigned wrappable counter."
   ::= {pr1646v2BgriMVMibCountersEntry 1996488704}

pr1646v2BgriMVMibCountersOutQLen OBJECT-TYPE
   SYNTAX      Counter32
   MAX-ACCESS  read-only
   STATUS      current
   DESCRIPTION
      "Path: vpnBridgeGroup.performance.mibCounters.ifOutQLen

       32 bit unsigned wrappable counter."
   ::= {pr1646v2BgriMVMibCountersEntry 2013265920}

pr1646v2BgriMVMibCountersOutDropEx OBJECT-TYPE
   SYNTAX      Counter64
   MAX-ACCESS  read-only
   STATUS      current
   DESCRIPTION
      "Path: vpnBridgeGroup.performance.mibCounters.ifOutDropLevelExceeded

       64 bit unsigned wrappable counter."
   ::= {pr1646v2BgriMVMibCountersEntry 2030043136}

pr1646v2BgriMVMibCountersOutDropNoArp OBJECT-TYPE
   SYNTAX      Counter64
   MAX-ACCESS  read-only
   STATUS      current
   DESCRIPTION
      "Path: vpnBridgeGroup.performance.mibCounters.ifOutDiscardsNoArp

       64 bit unsigned wrappable counter."
   ::= {pr1646v2BgriMVMibCountersEntry 2248146944}

pr1646v2BgriMVMibCountersOutDropFilter OBJECT-TYPE
   SYNTAX      Counter64
   MAX-ACCESS  read-only
   STATUS      current
   DESCRIPTION
      "Path: vpnBridgeGroup.performance.mibCounters.ifOutDiscardsFilter

       64 bit unsigned wrappable counter."
   ::= {pr1646v2BgriMVMibCountersEntry 2315255808}

pr1646v2BgriMVMibCountersOutBandwidth15sec OBJECT-TYPE
   SYNTAX      Integer32
   MAX-ACCESS  read-only
   STATUS      current
   DESCRIPTION
      "Path: vpnBridgeGroup.performance.mibCounters.ifOutBandwidth.15sec

       unit name = bps
       formula = 8 * ; 8 /"
   ::= {pr1646v2BgriMVMibCountersEntry 3053780992}

pr1646v2BgriMVMibCountersOutBandwidth30sec OBJECT-TYPE
   SYNTAX      Integer32
   MAX-ACCESS  read-only
   STATUS      current
   DESCRIPTION
      "Path: vpnBridgeGroup.performance.mibCounters.ifOutBandwidth.30sec

       unit name = bps
       formula = 8 * ; 8 /"
   ::= {pr1646v2BgriMVMibCountersEntry 3054108672}

pr1646v2BgriMVMibCountersOutBandwidth1min OBJECT-TYPE
   SYNTAX      Integer32
   MAX-ACCESS  read-only
   STATUS      current
   DESCRIPTION
      "Path: vpnBridgeGroup.performance.mibCounters.ifOutBandwidth.1min

       unit name = bps
       formula = 8 * ; 8 /"
   ::= {pr1646v2BgriMVMibCountersEntry 3054764032}

pr1646v2BgriMVMibCountersOutBandwidth2min OBJECT-TYPE
   SYNTAX      Integer32
   MAX-ACCESS  read-only
   STATUS      current
   DESCRIPTION
      "Path: vpnBridgeGroup.performance.mibCounters.ifOutBandwidth.2min

       unit name = bps
       formula = 8 * ; 8 /"
   ::= {pr1646v2BgriMVMibCountersEntry 3056074752}

pr1646v2BgriMVMibCountersOutBandwidth5min OBJECT-TYPE
   SYNTAX      Integer32
   MAX-ACCESS  read-only
   STATUS      current
   DESCRIPTION
      "Path: vpnBridgeGroup.performance.mibCounters.ifOutBandwidth.5min

       unit name = bps
       formula = 8 * ; 8 /"
   ::= {pr1646v2BgriMVMibCountersEntry 3060006912}

pr1646v2BgriMVMibCountersH2P OBJECT-TYPE
   SYNTAX      SEQUENCE OF Pr1646v2BgriMVMibCountersH2PEntry
   MAX-ACCESS  not-accessible
   STATUS      current
   DESCRIPTION
      ""
   ::= {pr1646v2BgriMVMibCounters 2046820352}

pr1646v2BgriMVMibCountersH2PEntry OBJECT-TYPE
   SYNTAX      Pr1646v2BgriMVMibCountersH2PEntry
   MAX-ACCESS  not-accessible
   STATUS      current
   DESCRIPTION
      ""
   INDEX      { pr1646v2BgriMVMibCountersH2PGlobalIx,
                pr1646v2BgriMVMibCountersH2PTableIx }
   ::= {pr1646v2BgriMVMibCountersH2P 1}

Pr1646v2BgriMVMibCountersH2PEntry ::=
   SEQUENCE
      {
      pr1646v2BgriMVMibCountersH2PGlobalIx
         GlobalIndex,
      pr1646v2BgriMVMibCountersH2PTableIx
         TableIndex,
      pr1646v2BgriMVMibCountersH2PSysUpTime
         TimeTicks,
      pr1646v2BgriMVMibCountersH2PIfUpTime
         TimeTicks,
      pr1646v2BgriMVMibCountersH2PIfStatChanges
         Counter32,
      pr1646v2BgriMVMibCountersH2PIfInOctets
         Counter64,
      pr1646v2BgriMVMibCountersH2PIfInUCPkts
         Counter64,
      pr1646v2BgriMVMibCountersH2PIfInNUCPkts
         Counter64,
      pr1646v2BgriMVMibCountersH2PIfInBCPkts
         Counter64,
      pr1646v2BgriMVMibCountersH2PIfInMCPkts
         Counter64,
      pr1646v2BgriMVMibCountersH2PIfInDiscards
         Counter64,
      pr1646v2BgriMVMibCountersH2PIfInErrors
         Counter64,
      pr1646v2BgriMVMibCountersH2PIfInUnkwn
         Counter64,
      pr1646v2BgriMVMibCountersH2PInDropEx
         Counter64,
      pr1646v2BgriMVMibCountersH2PInDropNoMac
         Counter64,
      pr1646v2BgriMVMibCountersH2PInDropNUCast
         Counter64,
      pr1646v2BgriMVMibCountersH2PInDropFilter
         Counter64,
      pr1646v2BgriMVMibCountersH2PIfInBandwidth
         Integer32,
      pr1646v2BgriMVMibCountersH2PIfOutOctets
         Counter64,
      pr1646v2BgriMVMibCountersH2PIfOutUCPkts
         Counter64,
      pr1646v2BgriMVMibCountersH2PIfOutNUCPkts
         Counter64,
      pr1646v2BgriMVMibCountersH2PIfOutBCPkts
         Counter64,
      pr1646v2BgriMVMibCountersH2PIfOutMCPkts
         Counter64,
      pr1646v2BgriMVMibCountersH2PIfOutDiscards
         Counter64,
      pr1646v2BgriMVMibCountersH2PIfOutErrors
         Counter64,
      pr1646v2BgriMVMibCountersH2POutDropEx
         Counter64,
      pr1646v2BgriMVMibCountersH2POutDropNoArp
         Counter64,
      pr1646v2BgriMVMibCountersH2POutDropFilter
         Counter64,
      pr1646v2BgriMVMibCountersH2PIfOutBandwidth
         Integer32,
      pr1646v2BgriMVMibCountersH2PIfErrSec
         Counter32
      }

pr1646v2BgriMVMibCountersH2PGlobalIx OBJECT-TYPE
   SYNTAX      GlobalIndex
   MAX-ACCESS  not-accessible
   STATUS      current
   DESCRIPTION
      "The value of the tlsCntTreeGlobalIndex of the MANAGED OBJECT."
   ::= {pr1646v2BgriMVMibCountersH2PEntry 10}

pr1646v2BgriMVMibCountersH2PTableIx OBJECT-TYPE
   SYNTAX      TableIndex
   MAX-ACCESS  not-accessible
   STATUS      current
   DESCRIPTION
      ""
   ::= {pr1646v2BgriMVMibCountersH2PEntry 11}

pr1646v2BgriMVMibCountersH2PSysUpTime OBJECT-TYPE
   SYNTAX      TimeTicks
   MAX-ACCESS  read-only
   STATUS      current
   DESCRIPTION
      "Path: vpnBridgeGroup.performance.mibCounters.h2Performance.sysUpTime

       Time in centi-second."
   ::= {pr1646v2BgriMVMibCountersH2PEntry 16777216}

pr1646v2BgriMVMibCountersH2PIfUpTime OBJECT-TYPE
   SYNTAX      TimeTicks
   MAX-ACCESS  read-only
   STATUS      current
   DESCRIPTION
      "Path: vpnBridgeGroup.performance.mibCounters.h2Performance.ifUpTime

       Time in centi-second."
   ::= {pr1646v2BgriMVMibCountersH2PEntry 33554432}

pr1646v2BgriMVMibCountersH2PIfStatChanges OBJECT-TYPE
   SYNTAX      Counter32
   MAX-ACCESS  read-only
   STATUS      current
   DESCRIPTION
      "Path: vpnBridgeGroup.performance.mibCounters.h2Performance.ifStatusChanges

       32 bit unsigned wrappable counter."
   ::= {pr1646v2BgriMVMibCountersH2PEntry 50331648}

pr1646v2BgriMVMibCountersH2PIfInOctets OBJECT-TYPE
   SYNTAX      Counter64
   MAX-ACCESS  read-only
   STATUS      current
   DESCRIPTION
      "Path: vpnBridgeGroup.performance.mibCounters.h2Performance.ifInOctets

       64 bit unsigned wrappable counter."
   ::= {pr1646v2BgriMVMibCountersH2PEntry 67108864}

pr1646v2BgriMVMibCountersH2PIfInUCPkts OBJECT-TYPE
   SYNTAX      Counter64
   MAX-ACCESS  read-only
   STATUS      current
   DESCRIPTION
      "Path: vpnBridgeGroup.performance.mibCounters.h2Performance.ifInUcastPkts

       64 bit unsigned wrappable counter."
   ::= {pr1646v2BgriMVMibCountersH2PEntry 83886080}

pr1646v2BgriMVMibCountersH2PIfInNUCPkts OBJECT-TYPE
   SYNTAX      Counter64
   MAX-ACCESS  read-only
   STATUS      current
   DESCRIPTION
      "Path: vpnBridgeGroup.performance.mibCounters.h2Performance.ifInNUcastPkts

       64 bit unsigned wrappable counter."
   ::= {pr1646v2BgriMVMibCountersH2PEntry 100663296}

pr1646v2BgriMVMibCountersH2PIfInBCPkts OBJECT-TYPE
   SYNTAX      Counter64
   MAX-ACCESS  read-only
   STATUS      current
   DESCRIPTION
      "Path: vpnBridgeGroup.performance.mibCounters.h2Performance.ifInBcastPkts

       64 bit unsigned wrappable counter."
   ::= {pr1646v2BgriMVMibCountersH2PEntry 419430400}

pr1646v2BgriMVMibCountersH2PIfInMCPkts OBJECT-TYPE
   SYNTAX      Counter64
   MAX-ACCESS  read-only
   STATUS      current
   DESCRIPTION
      "Path: vpnBridgeGroup.performance.mibCounters.h2Performance.ifInMcastPkts

       64 bit unsigned wrappable counter."
   ::= {pr1646v2BgriMVMibCountersH2PEntry 436207616}

pr1646v2BgriMVMibCountersH2PIfInDiscards OBJECT-TYPE
   SYNTAX      Counter64
   MAX-ACCESS  read-only
   STATUS      current
   DESCRIPTION
      "Path: vpnBridgeGroup.performance.mibCounters.h2Performance.ifInDiscards

       64 bit unsigned wrappable counter."
   ::= {pr1646v2BgriMVMibCountersH2PEntry 117440512}

pr1646v2BgriMVMibCountersH2PIfInErrors OBJECT-TYPE
   SYNTAX      Counter64
   MAX-ACCESS  read-only
   STATUS      current
   DESCRIPTION
      "Path: vpnBridgeGroup.performance.mibCounters.h2Performance.ifInErrors

       64 bit unsigned wrappable counter."
   ::= {pr1646v2BgriMVMibCountersH2PEntry 134217728}

pr1646v2BgriMVMibCountersH2PIfInUnkwn OBJECT-TYPE
   SYNTAX      Counter64
   MAX-ACCESS  read-only
   STATUS      current
   DESCRIPTION
      "Path: vpnBridgeGroup.performance.mibCounters.h2Performance.ifInUnknownProtos

       64 bit unsigned wrappable counter."
   ::= {pr1646v2BgriMVMibCountersH2PEntry 150994944}

pr1646v2BgriMVMibCountersH2PInDropEx OBJECT-TYPE
   SYNTAX      Counter64
   MAX-ACCESS  read-only
   STATUS      current
   DESCRIPTION
      "Path: vpnBridgeGroup.performance.mibCounters.h2Performance.ifInDropLevelExceeded

       64 bit unsigned wrappable counter."
   ::= {pr1646v2BgriMVMibCountersH2PEntry 335544320}

pr1646v2BgriMVMibCountersH2PInDropNoMac OBJECT-TYPE
   SYNTAX      Counter64
   MAX-ACCESS  read-only
   STATUS      current
   DESCRIPTION
      "Path: vpnBridgeGroup.performance.mibCounters.h2Performance.fInDiscardsNoMacFit

       64 bit unsigned wrappable counter."
   ::= {pr1646v2BgriMVMibCountersH2PEntry 301989888}

pr1646v2BgriMVMibCountersH2PInDropNUCast OBJECT-TYPE
   SYNTAX      Counter64
   MAX-ACCESS  read-only
   STATUS      current
   DESCRIPTION
      "Path: vpnBridgeGroup.performance.mibCounters.h2Performance.fInDiscardsNUCast

       64 bit unsigned wrappable counter."
   ::= {pr1646v2BgriMVMibCountersH2PEntry 318767104}

pr1646v2BgriMVMibCountersH2PInDropFilter OBJECT-TYPE
   SYNTAX      Counter64
   MAX-ACCESS  read-only
   STATUS      current
   DESCRIPTION
      "Path: vpnBridgeGroup.performance.mibCounters.h2Performance.fInDiscardsFilter

       64 bit unsigned wrappable counter."
   ::= {pr1646v2BgriMVMibCountersH2PEntry 385875968}

pr1646v2BgriMVMibCountersH2PIfInBandwidth OBJECT-TYPE
   SYNTAX      Integer32
   MAX-ACCESS  read-only
   STATUS      current
   DESCRIPTION
      "Path: vpnBridgeGroup.performance.mibCounters.h2Performance.ifInBandwidth

       unit name = bps
       formula = 8 * ; 8 /"
   ::= {pr1646v2BgriMVMibCountersH2PEntry 268435456}

pr1646v2BgriMVMibCountersH2PIfOutOctets OBJECT-TYPE
   SYNTAX      Counter64
   MAX-ACCESS  read-only
   STATUS      current
   DESCRIPTION
      "Path: vpnBridgeGroup.performance.mibCounters.h2Performance.ifOutOctets

       64 bit unsigned wrappable counter."
   ::= {pr1646v2BgriMVMibCountersH2PEntry 167772160}

pr1646v2BgriMVMibCountersH2PIfOutUCPkts OBJECT-TYPE
   SYNTAX      Counter64
   MAX-ACCESS  read-only
   STATUS      current
   DESCRIPTION
      "Path: vpnBridgeGroup.performance.mibCounters.h2Performance.ifOutUcastPkts

       64 bit unsigned wrappable counter."
   ::= {pr1646v2BgriMVMibCountersH2PEntry 184549376}

pr1646v2BgriMVMibCountersH2PIfOutNUCPkts OBJECT-TYPE
   SYNTAX      Counter64
   MAX-ACCESS  read-only
   STATUS      current
   DESCRIPTION
      "Path: vpnBridgeGroup.performance.mibCounters.h2Performance.ifOutNUcastPkts

       64 bit unsigned wrappable counter."
   ::= {pr1646v2BgriMVMibCountersH2PEntry 201326592}

pr1646v2BgriMVMibCountersH2PIfOutBCPkts OBJECT-TYPE
   SYNTAX      Counter64
   MAX-ACCESS  read-only
   STATUS      current
   DESCRIPTION
      "Path: vpnBridgeGroup.performance.mibCounters.h2Performance.ifOutBcastPkts

       64 bit unsigned wrappable counter."
   ::= {pr1646v2BgriMVMibCountersH2PEntry 452984832}

pr1646v2BgriMVMibCountersH2PIfOutMCPkts OBJECT-TYPE
   SYNTAX      Counter64
   MAX-ACCESS  read-only
   STATUS      current
   DESCRIPTION
      "Path: vpnBridgeGroup.performance.mibCounters.h2Performance.ifOutMcastPkts

       64 bit unsigned wrappable counter."
   ::= {pr1646v2BgriMVMibCountersH2PEntry 469762048}

pr1646v2BgriMVMibCountersH2PIfOutDiscards OBJECT-TYPE
   SYNTAX      Counter64
   MAX-ACCESS  read-only
   STATUS      current
   DESCRIPTION
      "Path: vpnBridgeGroup.performance.mibCounters.h2Performance.ifOutDiscards

       64 bit unsigned wrappable counter."
   ::= {pr1646v2BgriMVMibCountersH2PEntry 218103808}

pr1646v2BgriMVMibCountersH2PIfOutErrors OBJECT-TYPE
   SYNTAX      Counter64
   MAX-ACCESS  read-only
   STATUS      current
   DESCRIPTION
      "Path: vpnBridgeGroup.performance.mibCounters.h2Performance.ifOutErrors

       64 bit unsigned wrappable counter."
   ::= {pr1646v2BgriMVMibCountersH2PEntry 234881024}

pr1646v2BgriMVMibCountersH2POutDropEx OBJECT-TYPE
   SYNTAX      Counter64
   MAX-ACCESS  read-only
   STATUS      current
   DESCRIPTION
      "Path: vpnBridgeGroup.performance.mibCounters.h2Performance.ifOutDropLevelExceeded

       64 bit unsigned wrappable counter."
   ::= {pr1646v2BgriMVMibCountersH2PEntry 352321536}

pr1646v2BgriMVMibCountersH2POutDropNoArp OBJECT-TYPE
   SYNTAX      Counter64
   MAX-ACCESS  read-only
   STATUS      current
   DESCRIPTION
      "Path: vpnBridgeGroup.performance.mibCounters.h2Performance.ifOutDiscardsNoArp

       64 bit unsigned wrappable counter."
   ::= {pr1646v2BgriMVMibCountersH2PEntry 369098752}

pr1646v2BgriMVMibCountersH2POutDropFilter OBJECT-TYPE
   SYNTAX      Counter64
   MAX-ACCESS  read-only
   STATUS      current
   DESCRIPTION
      "Path: vpnBridgeGroup.performance.mibCounters.h2Performance.ifOutDiscardsFilter

       64 bit unsigned wrappable counter."
   ::= {pr1646v2BgriMVMibCountersH2PEntry 402653184}

pr1646v2BgriMVMibCountersH2PIfOutBandwidth OBJECT-TYPE
   SYNTAX      Integer32
   MAX-ACCESS  read-only
   STATUS      current
   DESCRIPTION
      "Path: vpnBridgeGroup.performance.mibCounters.h2Performance.ifOutBandwidth

       unit name = bps
       formula = 8 * ; 8 /"
   ::= {pr1646v2BgriMVMibCountersH2PEntry 285212672}

pr1646v2BgriMVMibCountersH2PIfErrSec OBJECT-TYPE
   SYNTAX      Counter32
   MAX-ACCESS  read-only
   STATUS      current
   DESCRIPTION
      "Path: vpnBridgeGroup.performance.mibCounters.h2Performance.ifErrSec

       32 bit unsigned wrappable counter."
   ::= {pr1646v2BgriMVMibCountersH2PEntry 251658240}

pr1646v2BgriMVMibCountersH24P OBJECT-TYPE
   SYNTAX      SEQUENCE OF Pr1646v2BgriMVMibCountersH24PEntry
   MAX-ACCESS  not-accessible
   STATUS      current
   DESCRIPTION
      ""
   ::= {pr1646v2BgriMVMibCounters 2063597568}

pr1646v2BgriMVMibCountersH24PEntry OBJECT-TYPE
   SYNTAX      Pr1646v2BgriMVMibCountersH24PEntry
   MAX-ACCESS  not-accessible
   STATUS      current
   DESCRIPTION
      ""
   INDEX      { pr1646v2BgriMVMibCountersH24PGlobalIx,
                pr1646v2BgriMVMibCountersH24PTableIx }
   ::= {pr1646v2BgriMVMibCountersH24P 1}

Pr1646v2BgriMVMibCountersH24PEntry ::=
   SEQUENCE
      {
      pr1646v2BgriMVMibCountersH24PGlobalIx
         GlobalIndex,
      pr1646v2BgriMVMibCountersH24PTableIx
         TableIndex,
      pr1646v2BgriMVMibCountersH24PSysUpTime
         TimeTicks,
      pr1646v2BgriMVMibCountersH24PIfUpTime
         TimeTicks,
      pr1646v2BgriMVMibCountersH24PIfStatChanges
         Counter32,
      pr1646v2BgriMVMibCountersH24PIfInOctets
         Counter64,
      pr1646v2BgriMVMibCountersH24PIfInUCPkts
         Counter64,
      pr1646v2BgriMVMibCountersH24PIfInNUCPkts
         Counter64,
      pr1646v2BgriMVMibCountersH24PIfInBCPkts
         Counter64,
      pr1646v2BgriMVMibCountersH24PIfInMCPkts
         Counter64,
      pr1646v2BgriMVMibCountersH24PIfInDiscards
         Counter64,
      pr1646v2BgriMVMibCountersH24PIfInErrors
         Counter64,
      pr1646v2BgriMVMibCountersH24PIfInUnkwn
         Counter64,
      pr1646v2BgriMVMibCountersH24PInDropEx
         Counter64,
      pr1646v2BgriMVMibCountersH24PInDropNoMac
         Counter64,
      pr1646v2BgriMVMibCountersH24PInDropNUCast
         Counter64,
      pr1646v2BgriMVMibCountersH24PInDropFilter
         Counter64,
      pr1646v2BgriMVMibCountersH24PIfInBandwidth
         Integer32,
      pr1646v2BgriMVMibCountersH24PIfOutOctets
         Counter64,
      pr1646v2BgriMVMibCountersH24PIfOutUCPkts
         Counter64,
      pr1646v2BgriMVMibCountersH24PIfOutNUCPkts
         Counter64,
      pr1646v2BgriMVMibCountersH24PIfOutBCPkts
         Counter64,
      pr1646v2BgriMVMibCountersH24PIfOutMCPkts
         Counter64,
      pr1646v2BgriMVMibCountersH24PIfOutDiscards
         Counter64,
      pr1646v2BgriMVMibCountersH24PIfOutErrors
         Counter64,
      pr1646v2BgriMVMibCountersH24POutDropEx
         Counter64,
      pr1646v2BgriMVMibCountersH24POutDropNoArp
         Counter64,
      pr1646v2BgriMVMibCountersH24POutDropFilter
         Counter64,
      pr1646v2BgriMVMibCountersH24PIfOutBandwidth
         Integer32,
      pr1646v2BgriMVMibCountersH24PIfErrSec
         Counter32
      }

pr1646v2BgriMVMibCountersH24PGlobalIx OBJECT-TYPE
   SYNTAX      GlobalIndex
   MAX-ACCESS  not-accessible
   STATUS      current
   DESCRIPTION
      "The value of the tlsCntTreeGlobalIndex of the MANAGED OBJECT."
   ::= {pr1646v2BgriMVMibCountersH24PEntry 10}

pr1646v2BgriMVMibCountersH24PTableIx OBJECT-TYPE
   SYNTAX      TableIndex
   MAX-ACCESS  not-accessible
   STATUS      current
   DESCRIPTION
      ""
   ::= {pr1646v2BgriMVMibCountersH24PEntry 11}

pr1646v2BgriMVMibCountersH24PSysUpTime OBJECT-TYPE
   SYNTAX      TimeTicks
   MAX-ACCESS  read-only
   STATUS      current
   DESCRIPTION
      "Path: vpnBridgeGroup.performance.mibCounters.h24Performance.sysUpTime

       Time in centi-second."
   ::= {pr1646v2BgriMVMibCountersH24PEntry 16777216}

pr1646v2BgriMVMibCountersH24PIfUpTime OBJECT-TYPE
   SYNTAX      TimeTicks
   MAX-ACCESS  read-only
   STATUS      current
   DESCRIPTION
      "Path: vpnBridgeGroup.performance.mibCounters.h24Performance.ifUpTime

       Time in centi-second."
   ::= {pr1646v2BgriMVMibCountersH24PEntry 33554432}

pr1646v2BgriMVMibCountersH24PIfStatChanges OBJECT-TYPE
   SYNTAX      Counter32
   MAX-ACCESS  read-only
   STATUS      current
   DESCRIPTION
      "Path: vpnBridgeGroup.performance.mibCounters.h24Performance.ifStatusChanges

       32 bit unsigned wrappable counter."
   ::= {pr1646v2BgriMVMibCountersH24PEntry 50331648}

pr1646v2BgriMVMibCountersH24PIfInOctets OBJECT-TYPE
   SYNTAX      Counter64
   MAX-ACCESS  read-only
   STATUS      current
   DESCRIPTION
      "Path: vpnBridgeGroup.performance.mibCounters.h24Performance.ifInOctets

       64 bit unsigned wrappable counter."
   ::= {pr1646v2BgriMVMibCountersH24PEntry 67108864}

pr1646v2BgriMVMibCountersH24PIfInUCPkts OBJECT-TYPE
   SYNTAX      Counter64
   MAX-ACCESS  read-only
   STATUS      current
   DESCRIPTION
      "Path: vpnBridgeGroup.performance.mibCounters.h24Performance.ifInUcastPkts

       64 bit unsigned wrappable counter."
   ::= {pr1646v2BgriMVMibCountersH24PEntry 83886080}

pr1646v2BgriMVMibCountersH24PIfInNUCPkts OBJECT-TYPE
   SYNTAX      Counter64
   MAX-ACCESS  read-only
   STATUS      current
   DESCRIPTION
      "Path: vpnBridgeGroup.performance.mibCounters.h24Performance.ifInNUcastPkts

       64 bit unsigned wrappable counter."
   ::= {pr1646v2BgriMVMibCountersH24PEntry 100663296}

pr1646v2BgriMVMibCountersH24PIfInBCPkts OBJECT-TYPE
   SYNTAX      Counter64
   MAX-ACCESS  read-only
   STATUS      current
   DESCRIPTION
      "Path: vpnBridgeGroup.performance.mibCounters.h24Performance.ifInBcastPkts

       64 bit unsigned wrappable counter."
   ::= {pr1646v2BgriMVMibCountersH24PEntry 419430400}

pr1646v2BgriMVMibCountersH24PIfInMCPkts OBJECT-TYPE
   SYNTAX      Counter64
   MAX-ACCESS  read-only
   STATUS      current
   DESCRIPTION
      "Path: vpnBridgeGroup.performance.mibCounters.h24Performance.ifInMcastPkts

       64 bit unsigned wrappable counter."
   ::= {pr1646v2BgriMVMibCountersH24PEntry 436207616}

pr1646v2BgriMVMibCountersH24PIfInDiscards OBJECT-TYPE
   SYNTAX      Counter64
   MAX-ACCESS  read-only
   STATUS      current
   DESCRIPTION
      "Path: vpnBridgeGroup.performance.mibCounters.h24Performance.ifInDiscards

       64 bit unsigned wrappable counter."
   ::= {pr1646v2BgriMVMibCountersH24PEntry 117440512}

pr1646v2BgriMVMibCountersH24PIfInErrors OBJECT-TYPE
   SYNTAX      Counter64
   MAX-ACCESS  read-only
   STATUS      current
   DESCRIPTION
      "Path: vpnBridgeGroup.performance.mibCounters.h24Performance.ifInErrors

       64 bit unsigned wrappable counter."
   ::= {pr1646v2BgriMVMibCountersH24PEntry 134217728}

pr1646v2BgriMVMibCountersH24PIfInUnkwn OBJECT-TYPE
   SYNTAX      Counter64
   MAX-ACCESS  read-only
   STATUS      current
   DESCRIPTION
      "Path: vpnBridgeGroup.performance.mibCounters.h24Performance.ifInUnknownProtos

       64 bit unsigned wrappable counter."
   ::= {pr1646v2BgriMVMibCountersH24PEntry 150994944}

pr1646v2BgriMVMibCountersH24PInDropEx OBJECT-TYPE
   SYNTAX      Counter64
   MAX-ACCESS  read-only
   STATUS      current
   DESCRIPTION
      "Path: vpnBridgeGroup.performance.mibCounters.h24Performance.ifInDropLevelExceeded

       64 bit unsigned wrappable counter."
   ::= {pr1646v2BgriMVMibCountersH24PEntry 335544320}

pr1646v2BgriMVMibCountersH24PInDropNoMac OBJECT-TYPE
   SYNTAX      Counter64
   MAX-ACCESS  read-only
   STATUS      current
   DESCRIPTION
      "Path: vpnBridgeGroup.performance.mibCounters.h24Performance.fInDiscardsNoMacFit

       64 bit unsigned wrappable counter."
   ::= {pr1646v2BgriMVMibCountersH24PEntry 301989888}

pr1646v2BgriMVMibCountersH24PInDropNUCast OBJECT-TYPE
   SYNTAX      Counter64
   MAX-ACCESS  read-only
   STATUS      current
   DESCRIPTION
      "Path: vpnBridgeGroup.performance.mibCounters.h24Performance.fInDiscardsNUCast

       64 bit unsigned wrappable counter."
   ::= {pr1646v2BgriMVMibCountersH24PEntry 318767104}

pr1646v2BgriMVMibCountersH24PInDropFilter OBJECT-TYPE
   SYNTAX      Counter64
   MAX-ACCESS  read-only
   STATUS      current
   DESCRIPTION
      "Path: vpnBridgeGroup.performance.mibCounters.h24Performance.fInDiscardsFilter

       64 bit unsigned wrappable counter."
   ::= {pr1646v2BgriMVMibCountersH24PEntry 385875968}

pr1646v2BgriMVMibCountersH24PIfInBandwidth OBJECT-TYPE
   SYNTAX      Integer32
   MAX-ACCESS  read-only
   STATUS      current
   DESCRIPTION
      "Path: vpnBridgeGroup.performance.mibCounters.h24Performance.ifInBandwidth

       unit name = bps
       formula = 8 * ; 8 /"
   ::= {pr1646v2BgriMVMibCountersH24PEntry 268435456}

pr1646v2BgriMVMibCountersH24PIfOutOctets OBJECT-TYPE
   SYNTAX      Counter64
   MAX-ACCESS  read-only
   STATUS      current
   DESCRIPTION
      "Path: vpnBridgeGroup.performance.mibCounters.h24Performance.ifOutOctets

       64 bit unsigned wrappable counter."
   ::= {pr1646v2BgriMVMibCountersH24PEntry 167772160}

pr1646v2BgriMVMibCountersH24PIfOutUCPkts OBJECT-TYPE
   SYNTAX      Counter64
   MAX-ACCESS  read-only
   STATUS      current
   DESCRIPTION
      "Path: vpnBridgeGroup.performance.mibCounters.h24Performance.ifOutUcastPkts

       64 bit unsigned wrappable counter."
   ::= {pr1646v2BgriMVMibCountersH24PEntry 184549376}

pr1646v2BgriMVMibCountersH24PIfOutNUCPkts OBJECT-TYPE
   SYNTAX      Counter64
   MAX-ACCESS  read-only
   STATUS      current
   DESCRIPTION
      "Path: vpnBridgeGroup.performance.mibCounters.h24Performance.ifOutNUcastPkts

       64 bit unsigned wrappable counter."
   ::= {pr1646v2BgriMVMibCountersH24PEntry 201326592}

pr1646v2BgriMVMibCountersH24PIfOutBCPkts OBJECT-TYPE
   SYNTAX      Counter64
   MAX-ACCESS  read-only
   STATUS      current
   DESCRIPTION
      "Path: vpnBridgeGroup.performance.mibCounters.h24Performance.ifOutBcastPkts

       64 bit unsigned wrappable counter."
   ::= {pr1646v2BgriMVMibCountersH24PEntry 452984832}

pr1646v2BgriMVMibCountersH24PIfOutMCPkts OBJECT-TYPE
   SYNTAX      Counter64
   MAX-ACCESS  read-only
   STATUS      current
   DESCRIPTION
      "Path: vpnBridgeGroup.performance.mibCounters.h24Performance.ifOutMcastPkts

       64 bit unsigned wrappable counter."
   ::= {pr1646v2BgriMVMibCountersH24PEntry 469762048}

pr1646v2BgriMVMibCountersH24PIfOutDiscards OBJECT-TYPE
   SYNTAX      Counter64
   MAX-ACCESS  read-only
   STATUS      current
   DESCRIPTION
      "Path: vpnBridgeGroup.performance.mibCounters.h24Performance.ifOutDiscards

       64 bit unsigned wrappable counter."
   ::= {pr1646v2BgriMVMibCountersH24PEntry 218103808}

pr1646v2BgriMVMibCountersH24PIfOutErrors OBJECT-TYPE
   SYNTAX      Counter64
   MAX-ACCESS  read-only
   STATUS      current
   DESCRIPTION
      "Path: vpnBridgeGroup.performance.mibCounters.h24Performance.ifOutErrors

       64 bit unsigned wrappable counter."
   ::= {pr1646v2BgriMVMibCountersH24PEntry 234881024}

pr1646v2BgriMVMibCountersH24POutDropEx OBJECT-TYPE
   SYNTAX      Counter64
   MAX-ACCESS  read-only
   STATUS      current
   DESCRIPTION
      "Path: vpnBridgeGroup.performance.mibCounters.h24Performance.ifOutDropLevelExceeded

       64 bit unsigned wrappable counter."
   ::= {pr1646v2BgriMVMibCountersH24PEntry 352321536}

pr1646v2BgriMVMibCountersH24POutDropNoArp OBJECT-TYPE
   SYNTAX      Counter64
   MAX-ACCESS  read-only
   STATUS      current
   DESCRIPTION
      "Path: vpnBridgeGroup.performance.mibCounters.h24Performance.ifOutDiscardsNoArp

       64 bit unsigned wrappable counter."
   ::= {pr1646v2BgriMVMibCountersH24PEntry 369098752}

pr1646v2BgriMVMibCountersH24POutDropFilter OBJECT-TYPE
   SYNTAX      Counter64
   MAX-ACCESS  read-only
   STATUS      current
   DESCRIPTION
      "Path: vpnBridgeGroup.performance.mibCounters.h24Performance.ifOutDiscardsFilter

       64 bit unsigned wrappable counter."
   ::= {pr1646v2BgriMVMibCountersH24PEntry 402653184}

pr1646v2BgriMVMibCountersH24PIfOutBandwidth OBJECT-TYPE
   SYNTAX      Integer32
   MAX-ACCESS  read-only
   STATUS      current
   DESCRIPTION
      "Path: vpnBridgeGroup.performance.mibCounters.h24Performance.ifOutBandwidth

       unit name = bps
       formula = 8 * ; 8 /"
   ::= {pr1646v2BgriMVMibCountersH24PEntry 285212672}

pr1646v2BgriMVMibCountersH24PIfErrSec OBJECT-TYPE
   SYNTAX      Counter32
   MAX-ACCESS  read-only
   STATUS      current
   DESCRIPTION
      "Path: vpnBridgeGroup.performance.mibCounters.h24Performance.ifErrSec

       32 bit unsigned wrappable counter."
   ::= {pr1646v2BgriMVMibCountersH24PEntry 251658240}

pr1646v2BgriMVMibCountersD7P OBJECT-TYPE
   SYNTAX      SEQUENCE OF Pr1646v2BgriMVMibCountersD7PEntry
   MAX-ACCESS  not-accessible
   STATUS      current
   DESCRIPTION
      ""
   ::= {pr1646v2BgriMVMibCounters 2080374784}

pr1646v2BgriMVMibCountersD7PEntry OBJECT-TYPE
   SYNTAX      Pr1646v2BgriMVMibCountersD7PEntry
   MAX-ACCESS  not-accessible
   STATUS      current
   DESCRIPTION
      ""
   INDEX      { pr1646v2BgriMVMibCountersD7PGlobalIx,
                pr1646v2BgriMVMibCountersD7PTableIx }
   ::= {pr1646v2BgriMVMibCountersD7P 1}

Pr1646v2BgriMVMibCountersD7PEntry ::=
   SEQUENCE
      {
      pr1646v2BgriMVMibCountersD7PGlobalIx
         GlobalIndex,
      pr1646v2BgriMVMibCountersD7PTableIx
         TableIndex,
      pr1646v2BgriMVMibCountersD7PSysUpTime
         TimeTicks,
      pr1646v2BgriMVMibCountersD7PIfUpTime
         TimeTicks,
      pr1646v2BgriMVMibCountersD7PIfStatChanges
         Counter32,
      pr1646v2BgriMVMibCountersD7PIfInOctets
         Counter64,
      pr1646v2BgriMVMibCountersD7PIfInUCPkts
         Counter64,
      pr1646v2BgriMVMibCountersD7PIfInNUCPkts
         Counter64,
      pr1646v2BgriMVMibCountersD7PIfInBCPkts
         Counter64,
      pr1646v2BgriMVMibCountersD7PIfInMCPkts
         Counter64,
      pr1646v2BgriMVMibCountersD7PIfInDiscards
         Counter64,
      pr1646v2BgriMVMibCountersD7PIfInErrors
         Counter64,
      pr1646v2BgriMVMibCountersD7PIfInUnkwn
         Counter64,
      pr1646v2BgriMVMibCountersD7PInDropEx
         Counter64,
      pr1646v2BgriMVMibCountersD7PInDropNoMac
         Counter64,
      pr1646v2BgriMVMibCountersD7PInDropNUCast
         Counter64,
      pr1646v2BgriMVMibCountersD7PInDropFilter
         Counter64,
      pr1646v2BgriMVMibCountersD7PIfInBandwidth
         Integer32,
      pr1646v2BgriMVMibCountersD7PIfOutOctets
         Counter64,
      pr1646v2BgriMVMibCountersD7PIfOutUCPkts
         Counter64,
      pr1646v2BgriMVMibCountersD7PIfOutNUCPkts
         Counter64,
      pr1646v2BgriMVMibCountersD7PIfOutBCPkts
         Counter64,
      pr1646v2BgriMVMibCountersD7PIfOutMCPkts
         Counter64,
      pr1646v2BgriMVMibCountersD7PIfOutDiscards
         Counter64,
      pr1646v2BgriMVMibCountersD7PIfOutErrors
         Counter64,
      pr1646v2BgriMVMibCountersD7POutDropEx
         Counter64,
      pr1646v2BgriMVMibCountersD7POutDropNoArp
         Counter64,
      pr1646v2BgriMVMibCountersD7POutDropFilter
         Counter64,
      pr1646v2BgriMVMibCountersD7PIfOutBandwidth
         Integer32,
      pr1646v2BgriMVMibCountersD7PIfErrSec
         Counter32
      }

pr1646v2BgriMVMibCountersD7PGlobalIx OBJECT-TYPE
   SYNTAX      GlobalIndex
   MAX-ACCESS  not-accessible
   STATUS      current
   DESCRIPTION
      "The value of the tlsCntTreeGlobalIndex of the MANAGED OBJECT."
   ::= {pr1646v2BgriMVMibCountersD7PEntry 10}

pr1646v2BgriMVMibCountersD7PTableIx OBJECT-TYPE
   SYNTAX      TableIndex
   MAX-ACCESS  not-accessible
   STATUS      current
   DESCRIPTION
      ""
   ::= {pr1646v2BgriMVMibCountersD7PEntry 11}

pr1646v2BgriMVMibCountersD7PSysUpTime OBJECT-TYPE
   SYNTAX      TimeTicks
   MAX-ACCESS  read-only
   STATUS      current
   DESCRIPTION
      "Path: vpnBridgeGroup.performance.mibCounters.d7Performance.sysUpTime

       Time in centi-second."
   ::= {pr1646v2BgriMVMibCountersD7PEntry 16777216}

pr1646v2BgriMVMibCountersD7PIfUpTime OBJECT-TYPE
   SYNTAX      TimeTicks
   MAX-ACCESS  read-only
   STATUS      current
   DESCRIPTION
      "Path: vpnBridgeGroup.performance.mibCounters.d7Performance.ifUpTime

       Time in centi-second."
   ::= {pr1646v2BgriMVMibCountersD7PEntry 33554432}

pr1646v2BgriMVMibCountersD7PIfStatChanges OBJECT-TYPE
   SYNTAX      Counter32
   MAX-ACCESS  read-only
   STATUS      current
   DESCRIPTION
      "Path: vpnBridgeGroup.performance.mibCounters.d7Performance.ifStatusChanges

       32 bit unsigned wrappable counter."
   ::= {pr1646v2BgriMVMibCountersD7PEntry 50331648}

pr1646v2BgriMVMibCountersD7PIfInOctets OBJECT-TYPE
   SYNTAX      Counter64
   MAX-ACCESS  read-only
   STATUS      current
   DESCRIPTION
      "Path: vpnBridgeGroup.performance.mibCounters.d7Performance.ifInOctets

       64 bit unsigned wrappable counter."
   ::= {pr1646v2BgriMVMibCountersD7PEntry 67108864}

pr1646v2BgriMVMibCountersD7PIfInUCPkts OBJECT-TYPE
   SYNTAX      Counter64
   MAX-ACCESS  read-only
   STATUS      current
   DESCRIPTION
      "Path: vpnBridgeGroup.performance.mibCounters.d7Performance.ifInUcastPkts

       64 bit unsigned wrappable counter."
   ::= {pr1646v2BgriMVMibCountersD7PEntry 83886080}

pr1646v2BgriMVMibCountersD7PIfInNUCPkts OBJECT-TYPE
   SYNTAX      Counter64
   MAX-ACCESS  read-only
   STATUS      current
   DESCRIPTION
      "Path: vpnBridgeGroup.performance.mibCounters.d7Performance.ifInNUcastPkts

       64 bit unsigned wrappable counter."
   ::= {pr1646v2BgriMVMibCountersD7PEntry 100663296}

pr1646v2BgriMVMibCountersD7PIfInBCPkts OBJECT-TYPE
   SYNTAX      Counter64
   MAX-ACCESS  read-only
   STATUS      current
   DESCRIPTION
      "Path: vpnBridgeGroup.performance.mibCounters.d7Performance.ifInBcastPkts

       64 bit unsigned wrappable counter."
   ::= {pr1646v2BgriMVMibCountersD7PEntry 419430400}

pr1646v2BgriMVMibCountersD7PIfInMCPkts OBJECT-TYPE
   SYNTAX      Counter64
   MAX-ACCESS  read-only
   STATUS      current
   DESCRIPTION
      "Path: vpnBridgeGroup.performance.mibCounters.d7Performance.ifInMcastPkts

       64 bit unsigned wrappable counter."
   ::= {pr1646v2BgriMVMibCountersD7PEntry 436207616}

pr1646v2BgriMVMibCountersD7PIfInDiscards OBJECT-TYPE
   SYNTAX      Counter64
   MAX-ACCESS  read-only
   STATUS      current
   DESCRIPTION
      "Path: vpnBridgeGroup.performance.mibCounters.d7Performance.ifInDiscards

       64 bit unsigned wrappable counter."
   ::= {pr1646v2BgriMVMibCountersD7PEntry 117440512}

pr1646v2BgriMVMibCountersD7PIfInErrors OBJECT-TYPE
   SYNTAX      Counter64
   MAX-ACCESS  read-only
   STATUS      current
   DESCRIPTION
      "Path: vpnBridgeGroup.performance.mibCounters.d7Performance.ifInErrors

       64 bit unsigned wrappable counter."
   ::= {pr1646v2BgriMVMibCountersD7PEntry 134217728}

pr1646v2BgriMVMibCountersD7PIfInUnkwn OBJECT-TYPE
   SYNTAX      Counter64
   MAX-ACCESS  read-only
   STATUS      current
   DESCRIPTION
      "Path: vpnBridgeGroup.performance.mibCounters.d7Performance.ifInUnknownProtos

       64 bit unsigned wrappable counter."
   ::= {pr1646v2BgriMVMibCountersD7PEntry 150994944}

pr1646v2BgriMVMibCountersD7PInDropEx OBJECT-TYPE
   SYNTAX      Counter64
   MAX-ACCESS  read-only
   STATUS      current
   DESCRIPTION
      "Path: vpnBridgeGroup.performance.mibCounters.d7Performance.ifInDropLevelExceeded

       64 bit unsigned wrappable counter."
   ::= {pr1646v2BgriMVMibCountersD7PEntry 335544320}

pr1646v2BgriMVMibCountersD7PInDropNoMac OBJECT-TYPE
   SYNTAX      Counter64
   MAX-ACCESS  read-only
   STATUS      current
   DESCRIPTION
      "Path: vpnBridgeGroup.performance.mibCounters.d7Performance.fInDiscardsNoMacFit

       64 bit unsigned wrappable counter."
   ::= {pr1646v2BgriMVMibCountersD7PEntry 301989888}

pr1646v2BgriMVMibCountersD7PInDropNUCast OBJECT-TYPE
   SYNTAX      Counter64
   MAX-ACCESS  read-only
   STATUS      current
   DESCRIPTION
      "Path: vpnBridgeGroup.performance.mibCounters.d7Performance.fInDiscardsNUCast

       64 bit unsigned wrappable counter."
   ::= {pr1646v2BgriMVMibCountersD7PEntry 318767104}

pr1646v2BgriMVMibCountersD7PInDropFilter OBJECT-TYPE
   SYNTAX      Counter64
   MAX-ACCESS  read-only
   STATUS      current
   DESCRIPTION
      "Path: vpnBridgeGroup.performance.mibCounters.d7Performance.fInDiscardsFilter

       64 bit unsigned wrappable counter."
   ::= {pr1646v2BgriMVMibCountersD7PEntry 385875968}

pr1646v2BgriMVMibCountersD7PIfInBandwidth OBJECT-TYPE
   SYNTAX      Integer32
   MAX-ACCESS  read-only
   STATUS      current
   DESCRIPTION
      "Path: vpnBridgeGroup.performance.mibCounters.d7Performance.ifInBandwidth

       unit name = bps
       formula = 8 * ; 8 /"
   ::= {pr1646v2BgriMVMibCountersD7PEntry 268435456}

pr1646v2BgriMVMibCountersD7PIfOutOctets OBJECT-TYPE
   SYNTAX      Counter64
   MAX-ACCESS  read-only
   STATUS      current
   DESCRIPTION
      "Path: vpnBridgeGroup.performance.mibCounters.d7Performance.ifOutOctets

       64 bit unsigned wrappable counter."
   ::= {pr1646v2BgriMVMibCountersD7PEntry 167772160}

pr1646v2BgriMVMibCountersD7PIfOutUCPkts OBJECT-TYPE
   SYNTAX      Counter64
   MAX-ACCESS  read-only
   STATUS      current
   DESCRIPTION
      "Path: vpnBridgeGroup.performance.mibCounters.d7Performance.ifOutUcastPkts

       64 bit unsigned wrappable counter."
   ::= {pr1646v2BgriMVMibCountersD7PEntry 184549376}

pr1646v2BgriMVMibCountersD7PIfOutNUCPkts OBJECT-TYPE
   SYNTAX      Counter64
   MAX-ACCESS  read-only
   STATUS      current
   DESCRIPTION
      "Path: vpnBridgeGroup.performance.mibCounters.d7Performance.ifOutNUcastPkts

       64 bit unsigned wrappable counter."
   ::= {pr1646v2BgriMVMibCountersD7PEntry 201326592}

pr1646v2BgriMVMibCountersD7PIfOutBCPkts OBJECT-TYPE
   SYNTAX      Counter64
   MAX-ACCESS  read-only
   STATUS      current
   DESCRIPTION
      "Path: vpnBridgeGroup.performance.mibCounters.d7Performance.ifOutBcastPkts

       64 bit unsigned wrappable counter."
   ::= {pr1646v2BgriMVMibCountersD7PEntry 452984832}

pr1646v2BgriMVMibCountersD7PIfOutMCPkts OBJECT-TYPE
   SYNTAX      Counter64
   MAX-ACCESS  read-only
   STATUS      current
   DESCRIPTION
      "Path: vpnBridgeGroup.performance.mibCounters.d7Performance.ifOutMcastPkts

       64 bit unsigned wrappable counter."
   ::= {pr1646v2BgriMVMibCountersD7PEntry 469762048}

pr1646v2BgriMVMibCountersD7PIfOutDiscards OBJECT-TYPE
   SYNTAX      Counter64
   MAX-ACCESS  read-only
   STATUS      current
   DESCRIPTION
      "Path: vpnBridgeGroup.performance.mibCounters.d7Performance.ifOutDiscards

       64 bit unsigned wrappable counter."
   ::= {pr1646v2BgriMVMibCountersD7PEntry 218103808}

pr1646v2BgriMVMibCountersD7PIfOutErrors OBJECT-TYPE
   SYNTAX      Counter64
   MAX-ACCESS  read-only
   STATUS      current
   DESCRIPTION
      "Path: vpnBridgeGroup.performance.mibCounters.d7Performance.ifOutErrors

       64 bit unsigned wrappable counter."
   ::= {pr1646v2BgriMVMibCountersD7PEntry 234881024}

pr1646v2BgriMVMibCountersD7POutDropEx OBJECT-TYPE
   SYNTAX      Counter64
   MAX-ACCESS  read-only
   STATUS      current
   DESCRIPTION
      "Path: vpnBridgeGroup.performance.mibCounters.d7Performance.ifOutDropLevelExceeded

       64 bit unsigned wrappable counter."
   ::= {pr1646v2BgriMVMibCountersD7PEntry 352321536}

pr1646v2BgriMVMibCountersD7POutDropNoArp OBJECT-TYPE
   SYNTAX      Counter64
   MAX-ACCESS  read-only
   STATUS      current
   DESCRIPTION
      "Path: vpnBridgeGroup.performance.mibCounters.d7Performance.ifOutDiscardsNoArp

       64 bit unsigned wrappable counter."
   ::= {pr1646v2BgriMVMibCountersD7PEntry 369098752}

pr1646v2BgriMVMibCountersD7POutDropFilter OBJECT-TYPE
   SYNTAX      Counter64
   MAX-ACCESS  read-only
   STATUS      current
   DESCRIPTION
      "Path: vpnBridgeGroup.performance.mibCounters.d7Performance.ifOutDiscardsFilter

       64 bit unsigned wrappable counter."
   ::= {pr1646v2BgriMVMibCountersD7PEntry 402653184}

pr1646v2BgriMVMibCountersD7PIfOutBandwidth OBJECT-TYPE
   SYNTAX      Integer32
   MAX-ACCESS  read-only
   STATUS      current
   DESCRIPTION
      "Path: vpnBridgeGroup.performance.mibCounters.d7Performance.ifOutBandwidth

       unit name = bps
       formula = 8 * ; 8 /"
   ::= {pr1646v2BgriMVMibCountersD7PEntry 285212672}

pr1646v2BgriMVMibCountersD7PIfErrSec OBJECT-TYPE
   SYNTAX      Counter32
   MAX-ACCESS  read-only
   STATUS      current
   DESCRIPTION
      "Path: vpnBridgeGroup.performance.mibCounters.d7Performance.ifErrSec

       32 bit unsigned wrappable counter."
   ::= {pr1646v2BgriMVMibCountersD7PEntry 251658240}


pr1646v2BgriMVBridging OBJECT IDENTIFIER ::= {pr1646v2BgriMV 90}

pr1646v2BgriMVBridgingSSCTable OBJECT-TYPE
   SYNTAX      SEQUENCE OF Pr1646v2BgriMVBridgingEntry
   MAX-ACCESS  not-accessible
   STATUS      current
   DESCRIPTION
      " bridge-port performance"
   ::= {pr1646v2BgriMVBridging 1}

pr1646v2BgriMVBridgingEntry OBJECT-TYPE
   SYNTAX      Pr1646v2BgriMVBridgingEntry
   MAX-ACCESS  not-accessible
   STATUS      current
   DESCRIPTION
      ""
   INDEX      { pr1646v2BgriMVBridgingGlobalIx,
                pr1646v2BgriMVBridgingTableIx }
   ::= {pr1646v2BgriMVBridgingSSCTable 1}

Pr1646v2BgriMVBridgingEntry ::=
   SEQUENCE
      {
      pr1646v2BgriMVBridgingGlobalIx
         GlobalIndex,
      pr1646v2BgriMVBridgingTableIx
         TableIndex,
      pr1646v2BgriMVBridgingName
         DisplayString,
      pr1646v2BgriMVBridgingRxPkts
         Counter32,
      pr1646v2BgriMVBridgingTxPkts
         Counter32,
      pr1646v2BgriMVBridgingRxDiscards
         Counter32,
      pr1646v2BgriMVBridgingRxFloods
         Counter32,
      pr1646v2BgriMVBridgingRxBroadcasts
         Counter32,
      pr1646v2BgriMVBridgingRxMulticasts
         Counter32,
      pr1646v2BgriMVBridgingCacheSizeOverflows
         Counter32,
      pr1646v2BgriMVBridgingCacheStaticViolations
         Counter32,
      pr1646v2BgriMVBridgingCacheRelearns
         Counter32,
      pr1646v2BgriMVBridgingCacheRelearnDrops
         Counter32,
      pr1646v2BgriMVBridgingCacheLoopsDetected
         Counter32,
      pr1646v2BgriMVBridgingVlanMemberShipRxDiscards
         Counter32,
      pr1646v2BgriMVBridgingVlanMemberShipTxDiscards
         Counter32,
      pr1646v2BgriMVBridgingSpanningTreeRxMstp
         Integer32,
      pr1646v2BgriMVBridgingSpanningTreeRxRstp
         Integer32,
      pr1646v2BgriMVBridgingSpanningTreeRxConfig
         Integer32,
      pr1646v2BgriMVBridgingSpanningTreeRxTcn
         Integer32,
      pr1646v2BgriMVBridgingSpanningTreeRxDiscards
         Integer32,
      pr1646v2BgriMVBridgingSpanningTreeTxMstp
         Integer32,
      pr1646v2BgriMVBridgingSpanningTreeTxRstp
         Integer32,
      pr1646v2BgriMVBridgingSpanningTreeTxConfig
         Integer32,
      pr1646v2BgriMVBridgingSpanningTreeTxTcn
         Integer32
      }

pr1646v2BgriMVBridgingGlobalIx OBJECT-TYPE
   SYNTAX      GlobalIndex
   MAX-ACCESS  not-accessible
   STATUS      current
   DESCRIPTION
      "The value of the tlsCntTreeGlobalIndex of the MANAGED OBJECT."
   ::= {pr1646v2BgriMVBridgingEntry 10}

pr1646v2BgriMVBridgingTableIx OBJECT-TYPE
   SYNTAX      TableIndex
   MAX-ACCESS  not-accessible
   STATUS      current
   DESCRIPTION
      ""
   ::= {pr1646v2BgriMVBridgingEntry 11}

pr1646v2BgriMVBridgingName OBJECT-TYPE
   SYNTAX      DisplayString
   MAX-ACCESS  read-only
   STATUS      current
   DESCRIPTION
      "Path: vpnBridgeGroup.performance.bridging.name"
   ::= {pr1646v2BgriMVBridgingEntry 16777216}

pr1646v2BgriMVBridgingRxPkts OBJECT-TYPE
   SYNTAX      Counter32
   MAX-ACCESS  read-only
   STATUS      current
   DESCRIPTION
      "Path: vpnBridgeGroup.performance.bridging.rxPkts

       32 bit unsigned wrappable counter."
   ::= {pr1646v2BgriMVBridgingEntry 33554432}

pr1646v2BgriMVBridgingTxPkts OBJECT-TYPE
   SYNTAX      Counter32
   MAX-ACCESS  read-only
   STATUS      current
   DESCRIPTION
      "Path: vpnBridgeGroup.performance.bridging.txPkts

       32 bit unsigned wrappable counter."
   ::= {pr1646v2BgriMVBridgingEntry 50331648}

pr1646v2BgriMVBridgingRxDiscards OBJECT-TYPE
   SYNTAX      Counter32
   MAX-ACCESS  read-only
   STATUS      current
   DESCRIPTION
      "Path: vpnBridgeGroup.performance.bridging.rxDiscards

       32 bit unsigned wrappable counter."
   ::= {pr1646v2BgriMVBridgingEntry 67108864}

pr1646v2BgriMVBridgingRxFloods OBJECT-TYPE
   SYNTAX      Counter32
   MAX-ACCESS  read-only
   STATUS      current
   DESCRIPTION
      "Path: vpnBridgeGroup.performance.bridging.rxFloods

       32 bit unsigned wrappable counter."
   ::= {pr1646v2BgriMVBridgingEntry 83886080}

pr1646v2BgriMVBridgingRxBroadcasts OBJECT-TYPE
   SYNTAX      Counter32
   MAX-ACCESS  read-only
   STATUS      current
   DESCRIPTION
      "Path: vpnBridgeGroup.performance.bridging.rxBroadcasts

       32 bit unsigned wrappable counter."
   ::= {pr1646v2BgriMVBridgingEntry 100663296}

pr1646v2BgriMVBridgingRxMulticasts OBJECT-TYPE
   SYNTAX      Counter32
   MAX-ACCESS  read-only
   STATUS      current
   DESCRIPTION
      "Path: vpnBridgeGroup.performance.bridging.rxMulticasts

       32 bit unsigned wrappable counter."
   ::= {pr1646v2BgriMVBridgingEntry 117440512}

pr1646v2BgriMVBridgingCacheSizeOverflows OBJECT-TYPE
   SYNTAX      Counter32
   MAX-ACCESS  read-only
   STATUS      current
   DESCRIPTION
      "Path: vpnBridgeGroup.performance.bridging.cache.sizeOverflows

       32 bit unsigned wrappable counter."
   ::= {pr1646v2BgriMVBridgingEntry 134283264}

pr1646v2BgriMVBridgingCacheStaticViolations OBJECT-TYPE
   SYNTAX      Counter32
   MAX-ACCESS  read-only
   STATUS      current
   DESCRIPTION
      "Path: vpnBridgeGroup.performance.bridging.cache.staticViolations

       32 bit unsigned wrappable counter."
   ::= {pr1646v2BgriMVBridgingEntry 134348800}

pr1646v2BgriMVBridgingCacheRelearns OBJECT-TYPE
   SYNTAX      Counter32
   MAX-ACCESS  read-only
   STATUS      current
   DESCRIPTION
      "Path: vpnBridgeGroup.performance.bridging.cache.relearns

       32 bit unsigned wrappable counter."
   ::= {pr1646v2BgriMVBridgingEntry 134414336}

pr1646v2BgriMVBridgingCacheRelearnDrops OBJECT-TYPE
   SYNTAX      Counter32
   MAX-ACCESS  read-only
   STATUS      current
   DESCRIPTION
      "Path: vpnBridgeGroup.performance.bridging.cache.relearnDrops

       32 bit unsigned wrappable counter."
   ::= {pr1646v2BgriMVBridgingEntry 134479872}

pr1646v2BgriMVBridgingCacheLoopsDetected OBJECT-TYPE
   SYNTAX      Counter32
   MAX-ACCESS  read-only
   STATUS      current
   DESCRIPTION
      "Path: vpnBridgeGroup.performance.bridging.cache.loopsDetected

       32 bit unsigned wrappable counter."
   ::= {pr1646v2BgriMVBridgingEntry 134676480}

pr1646v2BgriMVBridgingVlanMemberShipRxDiscards OBJECT-TYPE
   SYNTAX      Counter32
   MAX-ACCESS  read-only
   STATUS      current
   DESCRIPTION
      "Path: vpnBridgeGroup.performance.bridging.vlanMemberShip.rxDiscards

       32 bit unsigned wrappable counter."
   ::= {pr1646v2BgriMVBridgingEntry 218169344}

pr1646v2BgriMVBridgingVlanMemberShipTxDiscards OBJECT-TYPE
   SYNTAX      Counter32
   MAX-ACCESS  read-only
   STATUS      current
   DESCRIPTION
      "Path: vpnBridgeGroup.performance.bridging.vlanMemberShip.txDiscards

       32 bit unsigned wrappable counter."
   ::= {pr1646v2BgriMVBridgingEntry 218234880}

pr1646v2BgriMVBridgingSpanningTreeRxMstp OBJECT-TYPE
   SYNTAX      Integer32
   MAX-ACCESS  read-only
   STATUS      current
   DESCRIPTION
      "Path: vpnBridgeGroup.performance.bridging.spanningTree.rxMstp"
   ::= {pr1646v2BgriMVBridgingEntry 201392128}

pr1646v2BgriMVBridgingSpanningTreeRxRstp OBJECT-TYPE
   SYNTAX      Integer32
   MAX-ACCESS  read-only
   STATUS      current
   DESCRIPTION
      "Path: vpnBridgeGroup.performance.bridging.spanningTree.rxRstp"
   ::= {pr1646v2BgriMVBridgingEntry 201457664}

pr1646v2BgriMVBridgingSpanningTreeRxConfig OBJECT-TYPE
   SYNTAX      Integer32
   MAX-ACCESS  read-only
   STATUS      current
   DESCRIPTION
      "Path: vpnBridgeGroup.performance.bridging.spanningTree.rxConfig"
   ::= {pr1646v2BgriMVBridgingEntry 201523200}

pr1646v2BgriMVBridgingSpanningTreeRxTcn OBJECT-TYPE
   SYNTAX      Integer32
   MAX-ACCESS  read-only
   STATUS      current
   DESCRIPTION
      "Path: vpnBridgeGroup.performance.bridging.spanningTree.rxTcn"
   ::= {pr1646v2BgriMVBridgingEntry 201588736}

pr1646v2BgriMVBridgingSpanningTreeRxDiscards OBJECT-TYPE
   SYNTAX      Integer32
   MAX-ACCESS  read-only
   STATUS      current
   DESCRIPTION
      "Path: vpnBridgeGroup.performance.bridging.spanningTree.rxDiscards"
   ::= {pr1646v2BgriMVBridgingEntry 201654272}

pr1646v2BgriMVBridgingSpanningTreeTxMstp OBJECT-TYPE
   SYNTAX      Integer32
   MAX-ACCESS  read-only
   STATUS      current
   DESCRIPTION
      "Path: vpnBridgeGroup.performance.bridging.spanningTree.txMstp"
   ::= {pr1646v2BgriMVBridgingEntry 201719808}

pr1646v2BgriMVBridgingSpanningTreeTxRstp OBJECT-TYPE
   SYNTAX      Integer32
   MAX-ACCESS  read-only
   STATUS      current
   DESCRIPTION
      "Path: vpnBridgeGroup.performance.bridging.spanningTree.txRstp"
   ::= {pr1646v2BgriMVBridgingEntry 201785344}

pr1646v2BgriMVBridgingSpanningTreeTxConfig OBJECT-TYPE
   SYNTAX      Integer32
   MAX-ACCESS  read-only
   STATUS      current
   DESCRIPTION
      "Path: vpnBridgeGroup.performance.bridging.spanningTree.txConfig"
   ::= {pr1646v2BgriMVBridgingEntry 201850880}

pr1646v2BgriMVBridgingSpanningTreeTxTcn OBJECT-TYPE
   SYNTAX      Integer32
   MAX-ACCESS  read-only
   STATUS      current
   DESCRIPTION
      "Path: vpnBridgeGroup.performance.bridging.spanningTree.txTcn"
   ::= {pr1646v2BgriMVBridgingEntry 201916416}

pr1646v2BgriMVBridgingH2Performance OBJECT-TYPE
   SYNTAX      SEQUENCE OF Pr1646v2BgriMVBridgingH2PerformanceEntry
   MAX-ACCESS  not-accessible
   STATUS      current
   DESCRIPTION
      ""
   ::= {pr1646v2BgriMVBridging 150994944}

pr1646v2BgriMVBridgingH2PerformanceEntry OBJECT-TYPE
   SYNTAX      Pr1646v2BgriMVBridgingH2PerformanceEntry
   MAX-ACCESS  not-accessible
   STATUS      current
   DESCRIPTION
      ""
   INDEX      { pr1646v2BgriMVBridgingH2PerformanceGlobalIx,
                pr1646v2BgriMVBridgingTableIx,
                pr1646v2BgriMVBridgingH2PerformanceTableIx }
   ::= {pr1646v2BgriMVBridgingH2Performance 1}

Pr1646v2BgriMVBridgingH2PerformanceEntry ::=
   SEQUENCE
      {
      pr1646v2BgriMVBridgingH2PerformanceGlobalIx
         GlobalIndex,
      pr1646v2BgriMVBridgingH2PerformanceTableIx
         TableIndex,
      pr1646v2BgriMVBridgingH2PerformanceSysUpTime
         TimeTicks,
      pr1646v2BgriMVBridgingH2PerformanceRxPkts
         Counter32,
      pr1646v2BgriMVBridgingH2PerformanceTxPkts
         Counter32,
      pr1646v2BgriMVBridgingH2PerformanceRxDiscards
         Counter32,
      pr1646v2BgriMVBridgingH2PerformanceRxFloods
         Counter32,
      pr1646v2BgriMVBridgingH2PerformanceRxBroadcasts
         Counter32,
      pr1646v2BgriMVBridgingH2PerformanceRxMulticasts
         Counter32,
      pr1646v2BgriMVBridgingH2PerformanceCacheSizeOverflows
         Counter32,
      pr1646v2BgriMVBridgingH2PerformanceStaticCacheViolations
         Counter32,
      pr1646v2BgriMVBridgingH2PerformanceCacheRelearns
         Counter32,
      pr1646v2BgriMVBridgingH2PerformanceCacheRelearnDrops
         Counter32,
      pr1646v2BgriMVBridgingH2PerformanceLoopsDetected
         Counter32
      }

pr1646v2BgriMVBridgingH2PerformanceGlobalIx OBJECT-TYPE
   SYNTAX      GlobalIndex
   MAX-ACCESS  not-accessible
   STATUS      current
   DESCRIPTION
      "The value of the tlsCntTreeGlobalIndex of the MANAGED OBJECT."
   ::= {pr1646v2BgriMVBridgingH2PerformanceEntry 10}

pr1646v2BgriMVBridgingH2PerformanceTableIx OBJECT-TYPE
   SYNTAX      TableIndex
   MAX-ACCESS  not-accessible
   STATUS      current
   DESCRIPTION
      ""
   ::= {pr1646v2BgriMVBridgingH2PerformanceEntry 11}

pr1646v2BgriMVBridgingH2PerformanceSysUpTime OBJECT-TYPE
   SYNTAX      TimeTicks
   MAX-ACCESS  read-only
   STATUS      current
   DESCRIPTION
      "Path: vpnBridgeGroup.performance.bridging.h2Performance.sysUpTime

       Time in centi-second."
   ::= {pr1646v2BgriMVBridgingH2PerformanceEntry 16777216}

pr1646v2BgriMVBridgingH2PerformanceRxPkts OBJECT-TYPE
   SYNTAX      Counter32
   MAX-ACCESS  read-only
   STATUS      current
   DESCRIPTION
      "Path: vpnBridgeGroup.performance.bridging.h2Performance.rxPkts

       32 bit unsigned wrappable counter."
   ::= {pr1646v2BgriMVBridgingH2PerformanceEntry 33554432}

pr1646v2BgriMVBridgingH2PerformanceTxPkts OBJECT-TYPE
   SYNTAX      Counter32
   MAX-ACCESS  read-only
   STATUS      current
   DESCRIPTION
      "Path: vpnBridgeGroup.performance.bridging.h2Performance.txPkts

       32 bit unsigned wrappable counter."
   ::= {pr1646v2BgriMVBridgingH2PerformanceEntry 50331648}

pr1646v2BgriMVBridgingH2PerformanceRxDiscards OBJECT-TYPE
   SYNTAX      Counter32
   MAX-ACCESS  read-only
   STATUS      current
   DESCRIPTION
      "Path: vpnBridgeGroup.performance.bridging.h2Performance.rxDiscards

       32 bit unsigned wrappable counter."
   ::= {pr1646v2BgriMVBridgingH2PerformanceEntry 67108864}

pr1646v2BgriMVBridgingH2PerformanceRxFloods OBJECT-TYPE
   SYNTAX      Counter32
   MAX-ACCESS  read-only
   STATUS      current
   DESCRIPTION
      "Path: vpnBridgeGroup.performance.bridging.h2Performance.rxFloods

       32 bit unsigned wrappable counter."
   ::= {pr1646v2BgriMVBridgingH2PerformanceEntry 83886080}

pr1646v2BgriMVBridgingH2PerformanceRxBroadcasts OBJECT-TYPE
   SYNTAX      Counter32
   MAX-ACCESS  read-only
   STATUS      current
   DESCRIPTION
      "Path: vpnBridgeGroup.performance.bridging.h2Performance.rxBroadcasts

       32 bit unsigned wrappable counter."
   ::= {pr1646v2BgriMVBridgingH2PerformanceEntry 100663296}

pr1646v2BgriMVBridgingH2PerformanceRxMulticasts OBJECT-TYPE
   SYNTAX      Counter32
   MAX-ACCESS  read-only
   STATUS      current
   DESCRIPTION
      "Path: vpnBridgeGroup.performance.bridging.h2Performance.rxMulticasts

       32 bit unsigned wrappable counter."
   ::= {pr1646v2BgriMVBridgingH2PerformanceEntry 117440512}

pr1646v2BgriMVBridgingH2PerformanceCacheSizeOverflows OBJECT-TYPE
   SYNTAX      Counter32
   MAX-ACCESS  read-only
   STATUS      current
   DESCRIPTION
      "Path: vpnBridgeGroup.performance.bridging.h2Performance.cacheSizeOverflows

       32 bit unsigned wrappable counter."
   ::= {pr1646v2BgriMVBridgingH2PerformanceEntry 134217728}

pr1646v2BgriMVBridgingH2PerformanceStaticCacheViolations OBJECT-TYPE
   SYNTAX      Counter32
   MAX-ACCESS  read-only
   STATUS      current
   DESCRIPTION
      "Path: vpnBridgeGroup.performance.bridging.h2Performance.staticCacheViolations

       32 bit unsigned wrappable counter."
   ::= {pr1646v2BgriMVBridgingH2PerformanceEntry 150994944}

pr1646v2BgriMVBridgingH2PerformanceCacheRelearns OBJECT-TYPE
   SYNTAX      Counter32
   MAX-ACCESS  read-only
   STATUS      current
   DESCRIPTION
      "Path: vpnBridgeGroup.performance.bridging.h2Performance.cacheRelearns

       32 bit unsigned wrappable counter."
   ::= {pr1646v2BgriMVBridgingH2PerformanceEntry 167772160}

pr1646v2BgriMVBridgingH2PerformanceCacheRelearnDrops OBJECT-TYPE
   SYNTAX      Counter32
   MAX-ACCESS  read-only
   STATUS      current
   DESCRIPTION
      "Path: vpnBridgeGroup.performance.bridging.h2Performance.cacheRelearnDrops

       32 bit unsigned wrappable counter."
   ::= {pr1646v2BgriMVBridgingH2PerformanceEntry 184549376}

pr1646v2BgriMVBridgingH2PerformanceLoopsDetected OBJECT-TYPE
   SYNTAX      Counter32
   MAX-ACCESS  read-only
   STATUS      current
   DESCRIPTION
      "Path: vpnBridgeGroup.performance.bridging.h2Performance.loopsDetected

       32 bit unsigned wrappable counter."
   ::= {pr1646v2BgriMVBridgingH2PerformanceEntry 234881024}

pr1646v2BgriMVBridgingH24Performance OBJECT-TYPE
   SYNTAX      SEQUENCE OF Pr1646v2BgriMVBridgingH24PerformanceEntry
   MAX-ACCESS  not-accessible
   STATUS      current
   DESCRIPTION
      ""
   ::= {pr1646v2BgriMVBridging 167772160}

pr1646v2BgriMVBridgingH24PerformanceEntry OBJECT-TYPE
   SYNTAX      Pr1646v2BgriMVBridgingH24PerformanceEntry
   MAX-ACCESS  not-accessible
   STATUS      current
   DESCRIPTION
      ""
   INDEX      { pr1646v2BgriMVBridgingH24PerformanceGlobalIx,
                pr1646v2BgriMVBridgingTableIx,
                pr1646v2BgriMVBridgingH24PerformanceTableIx }
   ::= {pr1646v2BgriMVBridgingH24Performance 1}

Pr1646v2BgriMVBridgingH24PerformanceEntry ::=
   SEQUENCE
      {
      pr1646v2BgriMVBridgingH24PerformanceGlobalIx
         GlobalIndex,
      pr1646v2BgriMVBridgingH24PerformanceTableIx
         TableIndex,
      pr1646v2BgriMVBridgingH24PerformanceSysUpTime
         TimeTicks,
      pr1646v2BgriMVBridgingH24PerformanceRxPkts
         Counter32,
      pr1646v2BgriMVBridgingH24PerformanceTxPkts
         Counter32,
      pr1646v2BgriMVBridgingH24PerformanceRxDiscards
         Counter32,
      pr1646v2BgriMVBridgingH24PerformanceRxFloods
         Counter32,
      pr1646v2BgriMVBridgingH24PerformanceRxBroadcasts
         Counter32,
      pr1646v2BgriMVBridgingH24PerformanceRxMulticasts
         Counter32,
      pr1646v2BgriMVBridgingH24PerformanceCacheSizeOverflows
         Counter32,
      pr1646v2BgriMVBridgingH24PerformanceStaticCacheViolations
         Counter32,
      pr1646v2BgriMVBridgingH24PerformanceCacheRelearns
         Counter32,
      pr1646v2BgriMVBridgingH24PerformanceCacheRelearnDrops
         Counter32,
      pr1646v2BgriMVBridgingH24PerformanceLoopsDetected
         Counter32
      }

pr1646v2BgriMVBridgingH24PerformanceGlobalIx OBJECT-TYPE
   SYNTAX      GlobalIndex
   MAX-ACCESS  not-accessible
   STATUS      current
   DESCRIPTION
      "The value of the tlsCntTreeGlobalIndex of the MANAGED OBJECT."
   ::= {pr1646v2BgriMVBridgingH24PerformanceEntry 10}

pr1646v2BgriMVBridgingH24PerformanceTableIx OBJECT-TYPE
   SYNTAX      TableIndex
   MAX-ACCESS  not-accessible
   STATUS      current
   DESCRIPTION
      ""
   ::= {pr1646v2BgriMVBridgingH24PerformanceEntry 11}

pr1646v2BgriMVBridgingH24PerformanceSysUpTime OBJECT-TYPE
   SYNTAX      TimeTicks
   MAX-ACCESS  read-only
   STATUS      current
   DESCRIPTION
      "Path: vpnBridgeGroup.performance.bridging.h24Performance.sysUpTime

       Time in centi-second."
   ::= {pr1646v2BgriMVBridgingH24PerformanceEntry 16777216}

pr1646v2BgriMVBridgingH24PerformanceRxPkts OBJECT-TYPE
   SYNTAX      Counter32
   MAX-ACCESS  read-only
   STATUS      current
   DESCRIPTION
      "Path: vpnBridgeGroup.performance.bridging.h24Performance.rxPkts

       32 bit unsigned wrappable counter."
   ::= {pr1646v2BgriMVBridgingH24PerformanceEntry 33554432}

pr1646v2BgriMVBridgingH24PerformanceTxPkts OBJECT-TYPE
   SYNTAX      Counter32
   MAX-ACCESS  read-only
   STATUS      current
   DESCRIPTION
      "Path: vpnBridgeGroup.performance.bridging.h24Performance.txPkts

       32 bit unsigned wrappable counter."
   ::= {pr1646v2BgriMVBridgingH24PerformanceEntry 50331648}

pr1646v2BgriMVBridgingH24PerformanceRxDiscards OBJECT-TYPE
   SYNTAX      Counter32
   MAX-ACCESS  read-only
   STATUS      current
   DESCRIPTION
      "Path: vpnBridgeGroup.performance.bridging.h24Performance.rxDiscards

       32 bit unsigned wrappable counter."
   ::= {pr1646v2BgriMVBridgingH24PerformanceEntry 67108864}

pr1646v2BgriMVBridgingH24PerformanceRxFloods OBJECT-TYPE
   SYNTAX      Counter32
   MAX-ACCESS  read-only
   STATUS      current
   DESCRIPTION
      "Path: vpnBridgeGroup.performance.bridging.h24Performance.rxFloods

       32 bit unsigned wrappable counter."
   ::= {pr1646v2BgriMVBridgingH24PerformanceEntry 83886080}

pr1646v2BgriMVBridgingH24PerformanceRxBroadcasts OBJECT-TYPE
   SYNTAX      Counter32
   MAX-ACCESS  read-only
   STATUS      current
   DESCRIPTION
      "Path: vpnBridgeGroup.performance.bridging.h24Performance.rxBroadcasts

       32 bit unsigned wrappable counter."
   ::= {pr1646v2BgriMVBridgingH24PerformanceEntry 100663296}

pr1646v2BgriMVBridgingH24PerformanceRxMulticasts OBJECT-TYPE
   SYNTAX      Counter32
   MAX-ACCESS  read-only
   STATUS      current
   DESCRIPTION
      "Path: vpnBridgeGroup.performance.bridging.h24Performance.rxMulticasts

       32 bit unsigned wrappable counter."
   ::= {pr1646v2BgriMVBridgingH24PerformanceEntry 117440512}

pr1646v2BgriMVBridgingH24PerformanceCacheSizeOverflows OBJECT-TYPE
   SYNTAX      Counter32
   MAX-ACCESS  read-only
   STATUS      current
   DESCRIPTION
      "Path: vpnBridgeGroup.performance.bridging.h24Performance.cacheSizeOverflows

       32 bit unsigned wrappable counter."
   ::= {pr1646v2BgriMVBridgingH24PerformanceEntry 134217728}

pr1646v2BgriMVBridgingH24PerformanceStaticCacheViolations OBJECT-TYPE
   SYNTAX      Counter32
   MAX-ACCESS  read-only
   STATUS      current
   DESCRIPTION
      "Path: vpnBridgeGroup.performance.bridging.h24Performance.staticCacheViolations

       32 bit unsigned wrappable counter."
   ::= {pr1646v2BgriMVBridgingH24PerformanceEntry 150994944}

pr1646v2BgriMVBridgingH24PerformanceCacheRelearns OBJECT-TYPE
   SYNTAX      Counter32
   MAX-ACCESS  read-only
   STATUS      current
   DESCRIPTION
      "Path: vpnBridgeGroup.performance.bridging.h24Performance.cacheRelearns

       32 bit unsigned wrappable counter."
   ::= {pr1646v2BgriMVBridgingH24PerformanceEntry 167772160}

pr1646v2BgriMVBridgingH24PerformanceCacheRelearnDrops OBJECT-TYPE
   SYNTAX      Counter32
   MAX-ACCESS  read-only
   STATUS      current
   DESCRIPTION
      "Path: vpnBridgeGroup.performance.bridging.h24Performance.cacheRelearnDrops

       32 bit unsigned wrappable counter."
   ::= {pr1646v2BgriMVBridgingH24PerformanceEntry 184549376}

pr1646v2BgriMVBridgingH24PerformanceLoopsDetected OBJECT-TYPE
   SYNTAX      Counter32
   MAX-ACCESS  read-only
   STATUS      current
   DESCRIPTION
      "Path: vpnBridgeGroup.performance.bridging.h24Performance.loopsDetected

       32 bit unsigned wrappable counter."
   ::= {pr1646v2BgriMVBridgingH24PerformanceEntry 234881024}

pr1646v2BgriMVBridgingD7Performance OBJECT-TYPE
   SYNTAX      SEQUENCE OF Pr1646v2BgriMVBridgingD7PerformanceEntry
   MAX-ACCESS  not-accessible
   STATUS      current
   DESCRIPTION
      ""
   ::= {pr1646v2BgriMVBridging 184549376}

pr1646v2BgriMVBridgingD7PerformanceEntry OBJECT-TYPE
   SYNTAX      Pr1646v2BgriMVBridgingD7PerformanceEntry
   MAX-ACCESS  not-accessible
   STATUS      current
   DESCRIPTION
      ""
   INDEX      { pr1646v2BgriMVBridgingD7PerformanceGlobalIx,
                pr1646v2BgriMVBridgingTableIx,
                pr1646v2BgriMVBridgingD7PerformanceTableIx }
   ::= {pr1646v2BgriMVBridgingD7Performance 1}

Pr1646v2BgriMVBridgingD7PerformanceEntry ::=
   SEQUENCE
      {
      pr1646v2BgriMVBridgingD7PerformanceGlobalIx
         GlobalIndex,
      pr1646v2BgriMVBridgingD7PerformanceTableIx
         TableIndex,
      pr1646v2BgriMVBridgingD7PerformanceSysUpTime
         TimeTicks,
      pr1646v2BgriMVBridgingD7PerformanceRxPkts
         Counter32,
      pr1646v2BgriMVBridgingD7PerformanceTxPkts
         Counter32,
      pr1646v2BgriMVBridgingD7PerformanceRxDiscards
         Counter32,
      pr1646v2BgriMVBridgingD7PerformanceRxFloods
         Counter32,
      pr1646v2BgriMVBridgingD7PerformanceRxBroadcasts
         Counter32,
      pr1646v2BgriMVBridgingD7PerformanceRxMulticasts
         Counter32,
      pr1646v2BgriMVBridgingD7PerformanceCacheSizeOverflows
         Counter32,
      pr1646v2BgriMVBridgingD7PerformanceStaticCacheViolations
         Counter32,
      pr1646v2BgriMVBridgingD7PerformanceCacheRelearns
         Counter32,
      pr1646v2BgriMVBridgingD7PerformanceCacheRelearnDrops
         Counter32,
      pr1646v2BgriMVBridgingD7PerformanceLoopsDetected
         Counter32
      }

pr1646v2BgriMVBridgingD7PerformanceGlobalIx OBJECT-TYPE
   SYNTAX      GlobalIndex
   MAX-ACCESS  not-accessible
   STATUS      current
   DESCRIPTION
      "The value of the tlsCntTreeGlobalIndex of the MANAGED OBJECT."
   ::= {pr1646v2BgriMVBridgingD7PerformanceEntry 10}

pr1646v2BgriMVBridgingD7PerformanceTableIx OBJECT-TYPE
   SYNTAX      TableIndex
   MAX-ACCESS  not-accessible
   STATUS      current
   DESCRIPTION
      ""
   ::= {pr1646v2BgriMVBridgingD7PerformanceEntry 11}

pr1646v2BgriMVBridgingD7PerformanceSysUpTime OBJECT-TYPE
   SYNTAX      TimeTicks
   MAX-ACCESS  read-only
   STATUS      current
   DESCRIPTION
      "Path: vpnBridgeGroup.performance.bridging.d7Performance.sysUpTime

       Time in centi-second."
   ::= {pr1646v2BgriMVBridgingD7PerformanceEntry 16777216}

pr1646v2BgriMVBridgingD7PerformanceRxPkts OBJECT-TYPE
   SYNTAX      Counter32
   MAX-ACCESS  read-only
   STATUS      current
   DESCRIPTION
      "Path: vpnBridgeGroup.performance.bridging.d7Performance.rxPkts

       32 bit unsigned wrappable counter."
   ::= {pr1646v2BgriMVBridgingD7PerformanceEntry 33554432}

pr1646v2BgriMVBridgingD7PerformanceTxPkts OBJECT-TYPE
   SYNTAX      Counter32
   MAX-ACCESS  read-only
   STATUS      current
   DESCRIPTION
      "Path: vpnBridgeGroup.performance.bridging.d7Performance.txPkts

       32 bit unsigned wrappable counter."
   ::= {pr1646v2BgriMVBridgingD7PerformanceEntry 50331648}

pr1646v2BgriMVBridgingD7PerformanceRxDiscards OBJECT-TYPE
   SYNTAX      Counter32
   MAX-ACCESS  read-only
   STATUS      current
   DESCRIPTION
      "Path: vpnBridgeGroup.performance.bridging.d7Performance.rxDiscards

       32 bit unsigned wrappable counter."
   ::= {pr1646v2BgriMVBridgingD7PerformanceEntry 67108864}

pr1646v2BgriMVBridgingD7PerformanceRxFloods OBJECT-TYPE
   SYNTAX      Counter32
   MAX-ACCESS  read-only
   STATUS      current
   DESCRIPTION
      "Path: vpnBridgeGroup.performance.bridging.d7Performance.rxFloods

       32 bit unsigned wrappable counter."
   ::= {pr1646v2BgriMVBridgingD7PerformanceEntry 83886080}

pr1646v2BgriMVBridgingD7PerformanceRxBroadcasts OBJECT-TYPE
   SYNTAX      Counter32
   MAX-ACCESS  read-only
   STATUS      current
   DESCRIPTION
      "Path: vpnBridgeGroup.performance.bridging.d7Performance.rxBroadcasts

       32 bit unsigned wrappable counter."
   ::= {pr1646v2BgriMVBridgingD7PerformanceEntry 100663296}

pr1646v2BgriMVBridgingD7PerformanceRxMulticasts OBJECT-TYPE
   SYNTAX      Counter32
   MAX-ACCESS  read-only
   STATUS      current
   DESCRIPTION
      "Path: vpnBridgeGroup.performance.bridging.d7Performance.rxMulticasts

       32 bit unsigned wrappable counter."
   ::= {pr1646v2BgriMVBridgingD7PerformanceEntry 117440512}

pr1646v2BgriMVBridgingD7PerformanceCacheSizeOverflows OBJECT-TYPE
   SYNTAX      Counter32
   MAX-ACCESS  read-only
   STATUS      current
   DESCRIPTION
      "Path: vpnBridgeGroup.performance.bridging.d7Performance.cacheSizeOverflows

       32 bit unsigned wrappable counter."
   ::= {pr1646v2BgriMVBridgingD7PerformanceEntry 134217728}

pr1646v2BgriMVBridgingD7PerformanceStaticCacheViolations OBJECT-TYPE
   SYNTAX      Counter32
   MAX-ACCESS  read-only
   STATUS      current
   DESCRIPTION
      "Path: vpnBridgeGroup.performance.bridging.d7Performance.staticCacheViolations

       32 bit unsigned wrappable counter."
   ::= {pr1646v2BgriMVBridgingD7PerformanceEntry 150994944}

pr1646v2BgriMVBridgingD7PerformanceCacheRelearns OBJECT-TYPE
   SYNTAX      Counter32
   MAX-ACCESS  read-only
   STATUS      current
   DESCRIPTION
      "Path: vpnBridgeGroup.performance.bridging.d7Performance.cacheRelearns

       32 bit unsigned wrappable counter."
   ::= {pr1646v2BgriMVBridgingD7PerformanceEntry 167772160}

pr1646v2BgriMVBridgingD7PerformanceCacheRelearnDrops OBJECT-TYPE
   SYNTAX      Counter32
   MAX-ACCESS  read-only
   STATUS      current
   DESCRIPTION
      "Path: vpnBridgeGroup.performance.bridging.d7Performance.cacheRelearnDrops

       32 bit unsigned wrappable counter."
   ::= {pr1646v2BgriMVBridgingD7PerformanceEntry 184549376}

pr1646v2BgriMVBridgingD7PerformanceLoopsDetected OBJECT-TYPE
   SYNTAX      Counter32
   MAX-ACCESS  read-only
   STATUS      current
   DESCRIPTION
      "Path: vpnBridgeGroup.performance.bridging.d7Performance.loopsDetected

       32 bit unsigned wrappable counter."
   ::= {pr1646v2BgriMVBridgingD7PerformanceEntry 234881024}


pr1646v2BgriMVL2ProtTunnel OBJECT IDENTIFIER ::= {pr1646v2BgriMV 46}

pr1646v2BgriMVL2ProtTunnelSSCTable OBJECT-TYPE
   SYNTAX      SEQUENCE OF Pr1646v2BgriMVL2ProtTunnelEntry
   MAX-ACCESS  not-accessible
   STATUS      current
   DESCRIPTION
      "l2 protocol tunnel performance"
   ::= {pr1646v2BgriMVL2ProtTunnel 1}

pr1646v2BgriMVL2ProtTunnelEntry OBJECT-TYPE
   SYNTAX      Pr1646v2BgriMVL2ProtTunnelEntry
   MAX-ACCESS  not-accessible
   STATUS      current
   DESCRIPTION
      ""
   INDEX      { pr1646v2BgriMVL2ProtTunnelGlobalIx,
                pr1646v2BgriMVL2ProtTunnelTableIx }
   ::= {pr1646v2BgriMVL2ProtTunnelSSCTable 1}

Pr1646v2BgriMVL2ProtTunnelEntry ::=
   SEQUENCE
      {
      pr1646v2BgriMVL2ProtTunnelGlobalIx
         GlobalIndex,
      pr1646v2BgriMVL2ProtTunnelTableIx
         TableIndex,
      pr1646v2BgriMVL2ProtTunnelName
         DisplayString,
      pr1646v2BgriMVL2ProtTunnelEncapsPktsStp
         Counter32,
      pr1646v2BgriMVL2ProtTunnelEncapsPktsLldp
         Counter32,
      pr1646v2BgriMVL2ProtTunnelEncapsPktsOam
         Counter32,
      pr1646v2BgriMVL2ProtTunnelEncapsPktsCdp
         Counter32,
      pr1646v2BgriMVL2ProtTunnelEncapsPktsVtp
         Counter32,
      pr1646v2BgriMVL2ProtTunnelEncapsPktsLacp
         Counter32,
      pr1646v2BgriMVL2ProtTunnelEncapsPktsEfmOam
         Counter32,
      pr1646v2BgriMVL2ProtTunnelEncapsPktsPvst
         Counter32,
      pr1646v2BgriMVL2ProtTunnelEncapsPktsMmrp
         Counter32,
      pr1646v2BgriMVL2ProtTunnelEncapsPktsMvrp
         Counter32,
      pr1646v2BgriMVL2ProtTunnelEncapsPktsGvrp
         Counter32,
      pr1646v2BgriMVL2ProtTunnelEncapsPktsGmrp
         Counter32,
      pr1646v2BgriMVL2ProtTunnelEncapsPktsDtp
         Counter32,
      pr1646v2BgriMVL2ProtTunnelEncapsPktsPagp
         Counter32,
      pr1646v2BgriMVL2ProtTunnelEncapsPktsUdld
         Counter32,
      pr1646v2BgriMVL2ProtTunnelDecapsPktsStp
         Counter32,
      pr1646v2BgriMVL2ProtTunnelDecapsPktsLldp
         Counter32,
      pr1646v2BgriMVL2ProtTunnelDecapsPktsOam
         Counter32,
      pr1646v2BgriMVL2ProtTunnelDecapsPktsCdp
         Counter32,
      pr1646v2BgriMVL2ProtTunnelDecapsPktsVtp
         Counter32,
      pr1646v2BgriMVL2ProtTunnelDecapsPktsLacp
         Counter32,
      pr1646v2BgriMVL2ProtTunnelDecapsPktsEfmOam
         Counter32,
      pr1646v2BgriMVL2ProtTunnelDecapsPktsPvst
         Counter32,
      pr1646v2BgriMVL2ProtTunnelDecapsPktsMmrp
         Counter32,
      pr1646v2BgriMVL2ProtTunnelDecapsPktsMvrp
         Counter32,
      pr1646v2BgriMVL2ProtTunnelDecapsPktsGvrp
         Counter32,
      pr1646v2BgriMVL2ProtTunnelDecapsPktsGmrp
         Counter32,
      pr1646v2BgriMVL2ProtTunnelDecapsPktsDtp
         Counter32,
      pr1646v2BgriMVL2ProtTunnelDecapsPktsPagp
         Counter32,
      pr1646v2BgriMVL2ProtTunnelDecapsPktsUdld
         Counter32,
      pr1646v2BgriMVL2ProtTunnelDroppedStp
         Counter32,
      pr1646v2BgriMVL2ProtTunnelDroppedLldp
         Counter32,
      pr1646v2BgriMVL2ProtTunnelDroppedOam
         Counter32,
      pr1646v2BgriMVL2ProtTunnelDroppedCdp
         Counter32,
      pr1646v2BgriMVL2ProtTunnelDroppedVtp
         Counter32,
      pr1646v2BgriMVL2ProtTunnelDroppedLacp
         Counter32,
      pr1646v2BgriMVL2ProtTunnelDroppedEfmOam
         Counter32,
      pr1646v2BgriMVL2ProtTunnelDroppedPvst
         Counter32,
      pr1646v2BgriMVL2ProtTunnelDroppedMmrp
         Counter32,
      pr1646v2BgriMVL2ProtTunnelDroppedMvrp
         Counter32,
      pr1646v2BgriMVL2ProtTunnelDroppedGvrp
         Counter32,
      pr1646v2BgriMVL2ProtTunnelDroppedGmrp
         Counter32,
      pr1646v2BgriMVL2ProtTunnelDroppedDtp
         Counter32,
      pr1646v2BgriMVL2ProtTunnelDroppedPagp
         Counter32,
      pr1646v2BgriMVL2ProtTunnelDroppedUdld
         Counter32
      }

pr1646v2BgriMVL2ProtTunnelGlobalIx OBJECT-TYPE
   SYNTAX      GlobalIndex
   MAX-ACCESS  not-accessible
   STATUS      current
   DESCRIPTION
      "The value of the tlsCntTreeGlobalIndex of the MANAGED OBJECT."
   ::= {pr1646v2BgriMVL2ProtTunnelEntry 10}

pr1646v2BgriMVL2ProtTunnelTableIx OBJECT-TYPE
   SYNTAX      TableIndex
   MAX-ACCESS  not-accessible
   STATUS      current
   DESCRIPTION
      ""
   ::= {pr1646v2BgriMVL2ProtTunnelEntry 11}

pr1646v2BgriMVL2ProtTunnelName OBJECT-TYPE
   SYNTAX      DisplayString
   MAX-ACCESS  read-only
   STATUS      current
   DESCRIPTION
      "Path: vpnBridgeGroup.performance.l2ProtTunnel.name"
   ::= {pr1646v2BgriMVL2ProtTunnelEntry 16777216}

pr1646v2BgriMVL2ProtTunnelEncapsPktsStp OBJECT-TYPE
   SYNTAX      Counter32
   MAX-ACCESS  read-only
   STATUS      current
   DESCRIPTION
      "Path: vpnBridgeGroup.performance.l2ProtTunnel.encapsPkts.stp

       32 bit unsigned wrappable counter."
   ::= {pr1646v2BgriMVL2ProtTunnelEntry 33619968}

pr1646v2BgriMVL2ProtTunnelEncapsPktsLldp OBJECT-TYPE
   SYNTAX      Counter32
   MAX-ACCESS  read-only
   STATUS      current
   DESCRIPTION
      "Path: vpnBridgeGroup.performance.l2ProtTunnel.encapsPkts.lldp

       32 bit unsigned wrappable counter."
   ::= {pr1646v2BgriMVL2ProtTunnelEntry 33685504}

pr1646v2BgriMVL2ProtTunnelEncapsPktsOam OBJECT-TYPE
   SYNTAX      Counter32
   MAX-ACCESS  read-only
   STATUS      current
   DESCRIPTION
      "Path: vpnBridgeGroup.performance.l2ProtTunnel.encapsPkts.oam

       32 bit unsigned wrappable counter."
   ::= {pr1646v2BgriMVL2ProtTunnelEntry 33751040}

pr1646v2BgriMVL2ProtTunnelEncapsPktsCdp OBJECT-TYPE
   SYNTAX      Counter32
   MAX-ACCESS  read-only
   STATUS      current
   DESCRIPTION
      "Path: vpnBridgeGroup.performance.l2ProtTunnel.encapsPkts.cdp

       32 bit unsigned wrappable counter."
   ::= {pr1646v2BgriMVL2ProtTunnelEntry 33816576}

pr1646v2BgriMVL2ProtTunnelEncapsPktsVtp OBJECT-TYPE
   SYNTAX      Counter32
   MAX-ACCESS  read-only
   STATUS      current
   DESCRIPTION
      "Path: vpnBridgeGroup.performance.l2ProtTunnel.encapsPkts.vtp

       32 bit unsigned wrappable counter."
   ::= {pr1646v2BgriMVL2ProtTunnelEntry 33882112}

pr1646v2BgriMVL2ProtTunnelEncapsPktsLacp OBJECT-TYPE
   SYNTAX      Counter32
   MAX-ACCESS  read-only
   STATUS      current
   DESCRIPTION
      "Path: vpnBridgeGroup.performance.l2ProtTunnel.encapsPkts.lacp

       32 bit unsigned wrappable counter."
   ::= {pr1646v2BgriMVL2ProtTunnelEntry 33947648}

pr1646v2BgriMVL2ProtTunnelEncapsPktsEfmOam OBJECT-TYPE
   SYNTAX      Counter32
   MAX-ACCESS  read-only
   STATUS      current
   DESCRIPTION
      "Path: vpnBridgeGroup.performance.l2ProtTunnel.encapsPkts.efmOam

       32 bit unsigned wrappable counter."
   ::= {pr1646v2BgriMVL2ProtTunnelEntry 34013184}

pr1646v2BgriMVL2ProtTunnelEncapsPktsPvst OBJECT-TYPE
   SYNTAX      Counter32
   MAX-ACCESS  read-only
   STATUS      current
   DESCRIPTION
      "Path: vpnBridgeGroup.performance.l2ProtTunnel.encapsPkts.pvst

       32 bit unsigned wrappable counter."
   ::= {pr1646v2BgriMVL2ProtTunnelEntry 34078720}

pr1646v2BgriMVL2ProtTunnelEncapsPktsMmrp OBJECT-TYPE
   SYNTAX      Counter32
   MAX-ACCESS  read-only
   STATUS      current
   DESCRIPTION
      "Path: vpnBridgeGroup.performance.l2ProtTunnel.encapsPkts.mmrp

       32 bit unsigned wrappable counter."
   ::= {pr1646v2BgriMVL2ProtTunnelEntry 34144256}

pr1646v2BgriMVL2ProtTunnelEncapsPktsMvrp OBJECT-TYPE
   SYNTAX      Counter32
   MAX-ACCESS  read-only
   STATUS      current
   DESCRIPTION
      "Path: vpnBridgeGroup.performance.l2ProtTunnel.encapsPkts.mvrp

       32 bit unsigned wrappable counter."
   ::= {pr1646v2BgriMVL2ProtTunnelEntry 34209792}

pr1646v2BgriMVL2ProtTunnelEncapsPktsGvrp OBJECT-TYPE
   SYNTAX      Counter32
   MAX-ACCESS  read-only
   STATUS      current
   DESCRIPTION
      "Path: vpnBridgeGroup.performance.l2ProtTunnel.encapsPkts.gvrp

       32 bit unsigned wrappable counter."
   ::= {pr1646v2BgriMVL2ProtTunnelEntry 34275328}

pr1646v2BgriMVL2ProtTunnelEncapsPktsGmrp OBJECT-TYPE
   SYNTAX      Counter32
   MAX-ACCESS  read-only
   STATUS      current
   DESCRIPTION
      "Path: vpnBridgeGroup.performance.l2ProtTunnel.encapsPkts.gmrp

       32 bit unsigned wrappable counter."
   ::= {pr1646v2BgriMVL2ProtTunnelEntry 34340864}

pr1646v2BgriMVL2ProtTunnelEncapsPktsDtp OBJECT-TYPE
   SYNTAX      Counter32
   MAX-ACCESS  read-only
   STATUS      current
   DESCRIPTION
      "Path: vpnBridgeGroup.performance.l2ProtTunnel.encapsPkts.dtp

       32 bit unsigned wrappable counter."
   ::= {pr1646v2BgriMVL2ProtTunnelEntry 34406400}

pr1646v2BgriMVL2ProtTunnelEncapsPktsPagp OBJECT-TYPE
   SYNTAX      Counter32
   MAX-ACCESS  read-only
   STATUS      current
   DESCRIPTION
      "Path: vpnBridgeGroup.performance.l2ProtTunnel.encapsPkts.pagp

       32 bit unsigned wrappable counter."
   ::= {pr1646v2BgriMVL2ProtTunnelEntry 34471936}

pr1646v2BgriMVL2ProtTunnelEncapsPktsUdld OBJECT-TYPE
   SYNTAX      Counter32
   MAX-ACCESS  read-only
   STATUS      current
   DESCRIPTION
      "Path: vpnBridgeGroup.performance.l2ProtTunnel.encapsPkts.udld

       32 bit unsigned wrappable counter."
   ::= {pr1646v2BgriMVL2ProtTunnelEntry 34537472}

pr1646v2BgriMVL2ProtTunnelDecapsPktsStp OBJECT-TYPE
   SYNTAX      Counter32
   MAX-ACCESS  read-only
   STATUS      current
   DESCRIPTION
      "Path: vpnBridgeGroup.performance.l2ProtTunnel.decapsPkts.stp

       32 bit unsigned wrappable counter."
   ::= {pr1646v2BgriMVL2ProtTunnelEntry 50397184}

pr1646v2BgriMVL2ProtTunnelDecapsPktsLldp OBJECT-TYPE
   SYNTAX      Counter32
   MAX-ACCESS  read-only
   STATUS      current
   DESCRIPTION
      "Path: vpnBridgeGroup.performance.l2ProtTunnel.decapsPkts.lldp

       32 bit unsigned wrappable counter."
   ::= {pr1646v2BgriMVL2ProtTunnelEntry 50462720}

pr1646v2BgriMVL2ProtTunnelDecapsPktsOam OBJECT-TYPE
   SYNTAX      Counter32
   MAX-ACCESS  read-only
   STATUS      current
   DESCRIPTION
      "Path: vpnBridgeGroup.performance.l2ProtTunnel.decapsPkts.oam

       32 bit unsigned wrappable counter."
   ::= {pr1646v2BgriMVL2ProtTunnelEntry 50528256}

pr1646v2BgriMVL2ProtTunnelDecapsPktsCdp OBJECT-TYPE
   SYNTAX      Counter32
   MAX-ACCESS  read-only
   STATUS      current
   DESCRIPTION
      "Path: vpnBridgeGroup.performance.l2ProtTunnel.decapsPkts.cdp

       32 bit unsigned wrappable counter."
   ::= {pr1646v2BgriMVL2ProtTunnelEntry 50593792}

pr1646v2BgriMVL2ProtTunnelDecapsPktsVtp OBJECT-TYPE
   SYNTAX      Counter32
   MAX-ACCESS  read-only
   STATUS      current
   DESCRIPTION
      "Path: vpnBridgeGroup.performance.l2ProtTunnel.decapsPkts.vtp

       32 bit unsigned wrappable counter."
   ::= {pr1646v2BgriMVL2ProtTunnelEntry 50659328}

pr1646v2BgriMVL2ProtTunnelDecapsPktsLacp OBJECT-TYPE
   SYNTAX      Counter32
   MAX-ACCESS  read-only
   STATUS      current
   DESCRIPTION
      "Path: vpnBridgeGroup.performance.l2ProtTunnel.decapsPkts.lacp

       32 bit unsigned wrappable counter."
   ::= {pr1646v2BgriMVL2ProtTunnelEntry 50724864}

pr1646v2BgriMVL2ProtTunnelDecapsPktsEfmOam OBJECT-TYPE
   SYNTAX      Counter32
   MAX-ACCESS  read-only
   STATUS      current
   DESCRIPTION
      "Path: vpnBridgeGroup.performance.l2ProtTunnel.decapsPkts.efmOam

       32 bit unsigned wrappable counter."
   ::= {pr1646v2BgriMVL2ProtTunnelEntry 50790400}

pr1646v2BgriMVL2ProtTunnelDecapsPktsPvst OBJECT-TYPE
   SYNTAX      Counter32
   MAX-ACCESS  read-only
   STATUS      current
   DESCRIPTION
      "Path: vpnBridgeGroup.performance.l2ProtTunnel.decapsPkts.pvst

       32 bit unsigned wrappable counter."
   ::= {pr1646v2BgriMVL2ProtTunnelEntry 50855936}

pr1646v2BgriMVL2ProtTunnelDecapsPktsMmrp OBJECT-TYPE
   SYNTAX      Counter32
   MAX-ACCESS  read-only
   STATUS      current
   DESCRIPTION
      "Path: vpnBridgeGroup.performance.l2ProtTunnel.decapsPkts.mmrp

       32 bit unsigned wrappable counter."
   ::= {pr1646v2BgriMVL2ProtTunnelEntry 50921472}

pr1646v2BgriMVL2ProtTunnelDecapsPktsMvrp OBJECT-TYPE
   SYNTAX      Counter32
   MAX-ACCESS  read-only
   STATUS      current
   DESCRIPTION
      "Path: vpnBridgeGroup.performance.l2ProtTunnel.decapsPkts.mvrp

       32 bit unsigned wrappable counter."
   ::= {pr1646v2BgriMVL2ProtTunnelEntry 50987008}

pr1646v2BgriMVL2ProtTunnelDecapsPktsGvrp OBJECT-TYPE
   SYNTAX      Counter32
   MAX-ACCESS  read-only
   STATUS      current
   DESCRIPTION
      "Path: vpnBridgeGroup.performance.l2ProtTunnel.decapsPkts.gvrp

       32 bit unsigned wrappable counter."
   ::= {pr1646v2BgriMVL2ProtTunnelEntry 51052544}

pr1646v2BgriMVL2ProtTunnelDecapsPktsGmrp OBJECT-TYPE
   SYNTAX      Counter32
   MAX-ACCESS  read-only
   STATUS      current
   DESCRIPTION
      "Path: vpnBridgeGroup.performance.l2ProtTunnel.decapsPkts.gmrp

       32 bit unsigned wrappable counter."
   ::= {pr1646v2BgriMVL2ProtTunnelEntry 51118080}

pr1646v2BgriMVL2ProtTunnelDecapsPktsDtp OBJECT-TYPE
   SYNTAX      Counter32
   MAX-ACCESS  read-only
   STATUS      current
   DESCRIPTION
      "Path: vpnBridgeGroup.performance.l2ProtTunnel.decapsPkts.dtp

       32 bit unsigned wrappable counter."
   ::= {pr1646v2BgriMVL2ProtTunnelEntry 51183616}

pr1646v2BgriMVL2ProtTunnelDecapsPktsPagp OBJECT-TYPE
   SYNTAX      Counter32
   MAX-ACCESS  read-only
   STATUS      current
   DESCRIPTION
      "Path: vpnBridgeGroup.performance.l2ProtTunnel.decapsPkts.pagp

       32 bit unsigned wrappable counter."
   ::= {pr1646v2BgriMVL2ProtTunnelEntry 51249152}

pr1646v2BgriMVL2ProtTunnelDecapsPktsUdld OBJECT-TYPE
   SYNTAX      Counter32
   MAX-ACCESS  read-only
   STATUS      current
   DESCRIPTION
      "Path: vpnBridgeGroup.performance.l2ProtTunnel.decapsPkts.udld

       32 bit unsigned wrappable counter."
   ::= {pr1646v2BgriMVL2ProtTunnelEntry 51314688}

pr1646v2BgriMVL2ProtTunnelDroppedStp OBJECT-TYPE
   SYNTAX      Counter32
   MAX-ACCESS  read-only
   STATUS      current
   DESCRIPTION
      "Path: vpnBridgeGroup.performance.l2ProtTunnel.dropped.stp

       32 bit unsigned wrappable counter."
   ::= {pr1646v2BgriMVL2ProtTunnelEntry 67174400}

pr1646v2BgriMVL2ProtTunnelDroppedLldp OBJECT-TYPE
   SYNTAX      Counter32
   MAX-ACCESS  read-only
   STATUS      current
   DESCRIPTION
      "Path: vpnBridgeGroup.performance.l2ProtTunnel.dropped.lldp

       32 bit unsigned wrappable counter."
   ::= {pr1646v2BgriMVL2ProtTunnelEntry 67239936}

pr1646v2BgriMVL2ProtTunnelDroppedOam OBJECT-TYPE
   SYNTAX      Counter32
   MAX-ACCESS  read-only
   STATUS      current
   DESCRIPTION
      "Path: vpnBridgeGroup.performance.l2ProtTunnel.dropped.oam

       32 bit unsigned wrappable counter."
   ::= {pr1646v2BgriMVL2ProtTunnelEntry 67305472}

pr1646v2BgriMVL2ProtTunnelDroppedCdp OBJECT-TYPE
   SYNTAX      Counter32
   MAX-ACCESS  read-only
   STATUS      current
   DESCRIPTION
      "Path: vpnBridgeGroup.performance.l2ProtTunnel.dropped.cdp

       32 bit unsigned wrappable counter."
   ::= {pr1646v2BgriMVL2ProtTunnelEntry 67371008}

pr1646v2BgriMVL2ProtTunnelDroppedVtp OBJECT-TYPE
   SYNTAX      Counter32
   MAX-ACCESS  read-only
   STATUS      current
   DESCRIPTION
      "Path: vpnBridgeGroup.performance.l2ProtTunnel.dropped.vtp

       32 bit unsigned wrappable counter."
   ::= {pr1646v2BgriMVL2ProtTunnelEntry 67436544}

pr1646v2BgriMVL2ProtTunnelDroppedLacp OBJECT-TYPE
   SYNTAX      Counter32
   MAX-ACCESS  read-only
   STATUS      current
   DESCRIPTION
      "Path: vpnBridgeGroup.performance.l2ProtTunnel.dropped.lacp

       32 bit unsigned wrappable counter."
   ::= {pr1646v2BgriMVL2ProtTunnelEntry 67502080}

pr1646v2BgriMVL2ProtTunnelDroppedEfmOam OBJECT-TYPE
   SYNTAX      Counter32
   MAX-ACCESS  read-only
   STATUS      current
   DESCRIPTION
      "Path: vpnBridgeGroup.performance.l2ProtTunnel.dropped.efmOam

       32 bit unsigned wrappable counter."
   ::= {pr1646v2BgriMVL2ProtTunnelEntry 67567616}

pr1646v2BgriMVL2ProtTunnelDroppedPvst OBJECT-TYPE
   SYNTAX      Counter32
   MAX-ACCESS  read-only
   STATUS      current
   DESCRIPTION
      "Path: vpnBridgeGroup.performance.l2ProtTunnel.dropped.pvst

       32 bit unsigned wrappable counter."
   ::= {pr1646v2BgriMVL2ProtTunnelEntry 67633152}

pr1646v2BgriMVL2ProtTunnelDroppedMmrp OBJECT-TYPE
   SYNTAX      Counter32
   MAX-ACCESS  read-only
   STATUS      current
   DESCRIPTION
      "Path: vpnBridgeGroup.performance.l2ProtTunnel.dropped.mmrp

       32 bit unsigned wrappable counter."
   ::= {pr1646v2BgriMVL2ProtTunnelEntry 67698688}

pr1646v2BgriMVL2ProtTunnelDroppedMvrp OBJECT-TYPE
   SYNTAX      Counter32
   MAX-ACCESS  read-only
   STATUS      current
   DESCRIPTION
      "Path: vpnBridgeGroup.performance.l2ProtTunnel.dropped.mvrp

       32 bit unsigned wrappable counter."
   ::= {pr1646v2BgriMVL2ProtTunnelEntry 67764224}

pr1646v2BgriMVL2ProtTunnelDroppedGvrp OBJECT-TYPE
   SYNTAX      Counter32
   MAX-ACCESS  read-only
   STATUS      current
   DESCRIPTION
      "Path: vpnBridgeGroup.performance.l2ProtTunnel.dropped.gvrp

       32 bit unsigned wrappable counter."
   ::= {pr1646v2BgriMVL2ProtTunnelEntry 67829760}

pr1646v2BgriMVL2ProtTunnelDroppedGmrp OBJECT-TYPE
   SYNTAX      Counter32
   MAX-ACCESS  read-only
   STATUS      current
   DESCRIPTION
      "Path: vpnBridgeGroup.performance.l2ProtTunnel.dropped.gmrp

       32 bit unsigned wrappable counter."
   ::= {pr1646v2BgriMVL2ProtTunnelEntry 67895296}

pr1646v2BgriMVL2ProtTunnelDroppedDtp OBJECT-TYPE
   SYNTAX      Counter32
   MAX-ACCESS  read-only
   STATUS      current
   DESCRIPTION
      "Path: vpnBridgeGroup.performance.l2ProtTunnel.dropped.dtp

       32 bit unsigned wrappable counter."
   ::= {pr1646v2BgriMVL2ProtTunnelEntry 67960832}

pr1646v2BgriMVL2ProtTunnelDroppedPagp OBJECT-TYPE
   SYNTAX      Counter32
   MAX-ACCESS  read-only
   STATUS      current
   DESCRIPTION
      "Path: vpnBridgeGroup.performance.l2ProtTunnel.dropped.pagp

       32 bit unsigned wrappable counter."
   ::= {pr1646v2BgriMVL2ProtTunnelEntry 68026368}

pr1646v2BgriMVL2ProtTunnelDroppedUdld OBJECT-TYPE
   SYNTAX      Counter32
   MAX-ACCESS  read-only
   STATUS      current
   DESCRIPTION
      "Path: vpnBridgeGroup.performance.l2ProtTunnel.dropped.udld

       32 bit unsigned wrappable counter."
   ::= {pr1646v2BgriMVL2ProtTunnelEntry 68091904}


pr1646v2BgriMVH2Perf OBJECT IDENTIFIER ::= {pr1646v2BgriMV 91}

pr1646v2BgriMVH2PerfSSCTable OBJECT-TYPE
   SYNTAX      SEQUENCE OF Pr1646v2BgriMVH2PerfEntry
   MAX-ACCESS  not-accessible
   STATUS      current
   DESCRIPTION
      "2 hour bridge stats"
   ::= {pr1646v2BgriMVH2Perf 1}

pr1646v2BgriMVH2PerfEntry OBJECT-TYPE
   SYNTAX      Pr1646v2BgriMVH2PerfEntry
   MAX-ACCESS  not-accessible
   STATUS      current
   DESCRIPTION
      ""
   INDEX      { pr1646v2BgriMVH2PerfGlobalIx,
                pr1646v2BgriMVH2PerfTableIx }
   ::= {pr1646v2BgriMVH2PerfSSCTable 1}

Pr1646v2BgriMVH2PerfEntry ::=
   SEQUENCE
      {
      pr1646v2BgriMVH2PerfGlobalIx
         GlobalIndex,
      pr1646v2BgriMVH2PerfTableIx
         TableIndex,
      pr1646v2BgriMVH2PerfSysUpTime
         TimeTicks,
      pr1646v2BgriMVH2PerfRxPkts
         Counter32,
      pr1646v2BgriMVH2PerfTxPkts
         Counter32,
      pr1646v2BgriMVH2PerfDiscards
         Counter32,
      pr1646v2BgriMVH2PerfFloods
         Counter32,
      pr1646v2BgriMVH2PerfBroadcasts
         Counter32,
      pr1646v2BgriMVH2PerfMulticasts
         Counter32,
      pr1646v2BgriMVH2PerfCacheSizeOverflows
         Counter32,
      pr1646v2BgriMVH2PerfStaticCacheViolations
         Counter32,
      pr1646v2BgriMVH2PerfCacheRelearns
         Counter32,
      pr1646v2BgriMVH2PerfCacheRelearnDrops
         Counter32,
      pr1646v2BgriMVH2PerfLoopsDetected
         Counter32
      }

pr1646v2BgriMVH2PerfGlobalIx OBJECT-TYPE
   SYNTAX      GlobalIndex
   MAX-ACCESS  not-accessible
   STATUS      current
   DESCRIPTION
      "The value of the tlsCntTreeGlobalIndex of the MANAGED OBJECT."
   ::= {pr1646v2BgriMVH2PerfEntry 10}

pr1646v2BgriMVH2PerfTableIx OBJECT-TYPE
   SYNTAX      TableIndex
   MAX-ACCESS  not-accessible
   STATUS      current
   DESCRIPTION
      ""
   ::= {pr1646v2BgriMVH2PerfEntry 11}

pr1646v2BgriMVH2PerfSysUpTime OBJECT-TYPE
   SYNTAX      TimeTicks
   MAX-ACCESS  read-only
   STATUS      current
   DESCRIPTION
      "Path: vpnBridgeGroup.performance.h2Performance.sysUpTime

       Time in centi-second."
   ::= {pr1646v2BgriMVH2PerfEntry 16777216}

pr1646v2BgriMVH2PerfRxPkts OBJECT-TYPE
   SYNTAX      Counter32
   MAX-ACCESS  read-only
   STATUS      current
   DESCRIPTION
      "Path: vpnBridgeGroup.performance.h2Performance.rxPkts

       32 bit unsigned wrappable counter."
   ::= {pr1646v2BgriMVH2PerfEntry 33554432}

pr1646v2BgriMVH2PerfTxPkts OBJECT-TYPE
   SYNTAX      Counter32
   MAX-ACCESS  read-only
   STATUS      current
   DESCRIPTION
      "Path: vpnBridgeGroup.performance.h2Performance.txPkts

       32 bit unsigned wrappable counter."
   ::= {pr1646v2BgriMVH2PerfEntry 50331648}

pr1646v2BgriMVH2PerfDiscards OBJECT-TYPE
   SYNTAX      Counter32
   MAX-ACCESS  read-only
   STATUS      current
   DESCRIPTION
      "Path: vpnBridgeGroup.performance.h2Performance.discards

       32 bit unsigned wrappable counter."
   ::= {pr1646v2BgriMVH2PerfEntry 67108864}

pr1646v2BgriMVH2PerfFloods OBJECT-TYPE
   SYNTAX      Counter32
   MAX-ACCESS  read-only
   STATUS      current
   DESCRIPTION
      "Path: vpnBridgeGroup.performance.h2Performance.floods

       32 bit unsigned wrappable counter."
   ::= {pr1646v2BgriMVH2PerfEntry 83886080}

pr1646v2BgriMVH2PerfBroadcasts OBJECT-TYPE
   SYNTAX      Counter32
   MAX-ACCESS  read-only
   STATUS      current
   DESCRIPTION
      "Path: vpnBridgeGroup.performance.h2Performance.broadcasts

       32 bit unsigned wrappable counter."
   ::= {pr1646v2BgriMVH2PerfEntry 100663296}

pr1646v2BgriMVH2PerfMulticasts OBJECT-TYPE
   SYNTAX      Counter32
   MAX-ACCESS  read-only
   STATUS      current
   DESCRIPTION
      "Path: vpnBridgeGroup.performance.h2Performance.multicasts

       32 bit unsigned wrappable counter."
   ::= {pr1646v2BgriMVH2PerfEntry 117440512}

pr1646v2BgriMVH2PerfCacheSizeOverflows OBJECT-TYPE
   SYNTAX      Counter32
   MAX-ACCESS  read-only
   STATUS      current
   DESCRIPTION
      "Path: vpnBridgeGroup.performance.h2Performance.cacheSizeOverflows

       32 bit unsigned wrappable counter."
   ::= {pr1646v2BgriMVH2PerfEntry 134217728}

pr1646v2BgriMVH2PerfStaticCacheViolations OBJECT-TYPE
   SYNTAX      Counter32
   MAX-ACCESS  read-only
   STATUS      current
   DESCRIPTION
      "Path: vpnBridgeGroup.performance.h2Performance.staticCacheViolations

       32 bit unsigned wrappable counter."
   ::= {pr1646v2BgriMVH2PerfEntry 150994944}

pr1646v2BgriMVH2PerfCacheRelearns OBJECT-TYPE
   SYNTAX      Counter32
   MAX-ACCESS  read-only
   STATUS      current
   DESCRIPTION
      "Path: vpnBridgeGroup.performance.h2Performance.cacheRelearns

       32 bit unsigned wrappable counter."
   ::= {pr1646v2BgriMVH2PerfEntry 167772160}

pr1646v2BgriMVH2PerfCacheRelearnDrops OBJECT-TYPE
   SYNTAX      Counter32
   MAX-ACCESS  read-only
   STATUS      current
   DESCRIPTION
      "Path: vpnBridgeGroup.performance.h2Performance.cacheRelearnDrops

       32 bit unsigned wrappable counter."
   ::= {pr1646v2BgriMVH2PerfEntry 184549376}

pr1646v2BgriMVH2PerfLoopsDetected OBJECT-TYPE
   SYNTAX      Counter32
   MAX-ACCESS  read-only
   STATUS      current
   DESCRIPTION
      "Path: vpnBridgeGroup.performance.h2Performance.loopsDetected

       32 bit unsigned wrappable counter."
   ::= {pr1646v2BgriMVH2PerfEntry 234881024}


pr1646v2BgriMVH24Perf OBJECT IDENTIFIER ::= {pr1646v2BgriMV 92}

pr1646v2BgriMVH24PerfSSCTable OBJECT-TYPE
   SYNTAX      SEQUENCE OF Pr1646v2BgriMVH24PerfEntry
   MAX-ACCESS  not-accessible
   STATUS      current
   DESCRIPTION
      "24 hour bridge stats"
   ::= {pr1646v2BgriMVH24Perf 1}

pr1646v2BgriMVH24PerfEntry OBJECT-TYPE
   SYNTAX      Pr1646v2BgriMVH24PerfEntry
   MAX-ACCESS  not-accessible
   STATUS      current
   DESCRIPTION
      ""
   INDEX      { pr1646v2BgriMVH24PerfGlobalIx,
                pr1646v2BgriMVH24PerfTableIx }
   ::= {pr1646v2BgriMVH24PerfSSCTable 1}

Pr1646v2BgriMVH24PerfEntry ::=
   SEQUENCE
      {
      pr1646v2BgriMVH24PerfGlobalIx
         GlobalIndex,
      pr1646v2BgriMVH24PerfTableIx
         TableIndex,
      pr1646v2BgriMVH24PerfSysUpTime
         TimeTicks,
      pr1646v2BgriMVH24PerfRxPkts
         Counter32,
      pr1646v2BgriMVH24PerfTxPkts
         Counter32,
      pr1646v2BgriMVH24PerfDiscards
         Counter32,
      pr1646v2BgriMVH24PerfFloods
         Counter32,
      pr1646v2BgriMVH24PerfBroadcasts
         Counter32,
      pr1646v2BgriMVH24PerfMulticasts
         Counter32,
      pr1646v2BgriMVH24PerfCacheSizeOverflows
         Counter32,
      pr1646v2BgriMVH24PerfStaticCacheViolations
         Counter32,
      pr1646v2BgriMVH24PerfCacheRelearns
         Counter32,
      pr1646v2BgriMVH24PerfCacheRelearnDrops
         Counter32,
      pr1646v2BgriMVH24PerfLoopsDetected
         Counter32
      }

pr1646v2BgriMVH24PerfGlobalIx OBJECT-TYPE
   SYNTAX      GlobalIndex
   MAX-ACCESS  not-accessible
   STATUS      current
   DESCRIPTION
      "The value of the tlsCntTreeGlobalIndex of the MANAGED OBJECT."
   ::= {pr1646v2BgriMVH24PerfEntry 10}

pr1646v2BgriMVH24PerfTableIx OBJECT-TYPE
   SYNTAX      TableIndex
   MAX-ACCESS  not-accessible
   STATUS      current
   DESCRIPTION
      ""
   ::= {pr1646v2BgriMVH24PerfEntry 11}

pr1646v2BgriMVH24PerfSysUpTime OBJECT-TYPE
   SYNTAX      TimeTicks
   MAX-ACCESS  read-only
   STATUS      current
   DESCRIPTION
      "Path: vpnBridgeGroup.performance.h24Performance.sysUpTime

       Time in centi-second."
   ::= {pr1646v2BgriMVH24PerfEntry 16777216}

pr1646v2BgriMVH24PerfRxPkts OBJECT-TYPE
   SYNTAX      Counter32
   MAX-ACCESS  read-only
   STATUS      current
   DESCRIPTION
      "Path: vpnBridgeGroup.performance.h24Performance.rxPkts

       32 bit unsigned wrappable counter."
   ::= {pr1646v2BgriMVH24PerfEntry 33554432}

pr1646v2BgriMVH24PerfTxPkts OBJECT-TYPE
   SYNTAX      Counter32
   MAX-ACCESS  read-only
   STATUS      current
   DESCRIPTION
      "Path: vpnBridgeGroup.performance.h24Performance.txPkts

       32 bit unsigned wrappable counter."
   ::= {pr1646v2BgriMVH24PerfEntry 50331648}

pr1646v2BgriMVH24PerfDiscards OBJECT-TYPE
   SYNTAX      Counter32
   MAX-ACCESS  read-only
   STATUS      current
   DESCRIPTION
      "Path: vpnBridgeGroup.performance.h24Performance.discards

       32 bit unsigned wrappable counter."
   ::= {pr1646v2BgriMVH24PerfEntry 67108864}

pr1646v2BgriMVH24PerfFloods OBJECT-TYPE
   SYNTAX      Counter32
   MAX-ACCESS  read-only
   STATUS      current
   DESCRIPTION
      "Path: vpnBridgeGroup.performance.h24Performance.floods

       32 bit unsigned wrappable counter."
   ::= {pr1646v2BgriMVH24PerfEntry 83886080}

pr1646v2BgriMVH24PerfBroadcasts OBJECT-TYPE
   SYNTAX      Counter32
   MAX-ACCESS  read-only
   STATUS      current
   DESCRIPTION
      "Path: vpnBridgeGroup.performance.h24Performance.broadcasts

       32 bit unsigned wrappable counter."
   ::= {pr1646v2BgriMVH24PerfEntry 100663296}

pr1646v2BgriMVH24PerfMulticasts OBJECT-TYPE
   SYNTAX      Counter32
   MAX-ACCESS  read-only
   STATUS      current
   DESCRIPTION
      "Path: vpnBridgeGroup.performance.h24Performance.multicasts

       32 bit unsigned wrappable counter."
   ::= {pr1646v2BgriMVH24PerfEntry 117440512}

pr1646v2BgriMVH24PerfCacheSizeOverflows OBJECT-TYPE
   SYNTAX      Counter32
   MAX-ACCESS  read-only
   STATUS      current
   DESCRIPTION
      "Path: vpnBridgeGroup.performance.h24Performance.cacheSizeOverflows

       32 bit unsigned wrappable counter."
   ::= {pr1646v2BgriMVH24PerfEntry 134217728}

pr1646v2BgriMVH24PerfStaticCacheViolations OBJECT-TYPE
   SYNTAX      Counter32
   MAX-ACCESS  read-only
   STATUS      current
   DESCRIPTION
      "Path: vpnBridgeGroup.performance.h24Performance.staticCacheViolations

       32 bit unsigned wrappable counter."
   ::= {pr1646v2BgriMVH24PerfEntry 150994944}

pr1646v2BgriMVH24PerfCacheRelearns OBJECT-TYPE
   SYNTAX      Counter32
   MAX-ACCESS  read-only
   STATUS      current
   DESCRIPTION
      "Path: vpnBridgeGroup.performance.h24Performance.cacheRelearns

       32 bit unsigned wrappable counter."
   ::= {pr1646v2BgriMVH24PerfEntry 167772160}

pr1646v2BgriMVH24PerfCacheRelearnDrops OBJECT-TYPE
   SYNTAX      Counter32
   MAX-ACCESS  read-only
   STATUS      current
   DESCRIPTION
      "Path: vpnBridgeGroup.performance.h24Performance.cacheRelearnDrops

       32 bit unsigned wrappable counter."
   ::= {pr1646v2BgriMVH24PerfEntry 184549376}

pr1646v2BgriMVH24PerfLoopsDetected OBJECT-TYPE
   SYNTAX      Counter32
   MAX-ACCESS  read-only
   STATUS      current
   DESCRIPTION
      "Path: vpnBridgeGroup.performance.h24Performance.loopsDetected

       32 bit unsigned wrappable counter."
   ::= {pr1646v2BgriMVH24PerfEntry 234881024}


pr1646v2BgriMVD7Perf OBJECT IDENTIFIER ::= {pr1646v2BgriMV 93}

pr1646v2BgriMVD7PerfSSCTable OBJECT-TYPE
   SYNTAX      SEQUENCE OF Pr1646v2BgriMVD7PerfEntry
   MAX-ACCESS  not-accessible
   STATUS      current
   DESCRIPTION
      "7 days bridge stats"
   ::= {pr1646v2BgriMVD7Perf 1}

pr1646v2BgriMVD7PerfEntry OBJECT-TYPE
   SYNTAX      Pr1646v2BgriMVD7PerfEntry
   MAX-ACCESS  not-accessible
   STATUS      current
   DESCRIPTION
      ""
   INDEX      { pr1646v2BgriMVD7PerfGlobalIx,
                pr1646v2BgriMVD7PerfTableIx }
   ::= {pr1646v2BgriMVD7PerfSSCTable 1}

Pr1646v2BgriMVD7PerfEntry ::=
   SEQUENCE
      {
      pr1646v2BgriMVD7PerfGlobalIx
         GlobalIndex,
      pr1646v2BgriMVD7PerfTableIx
         TableIndex,
      pr1646v2BgriMVD7PerfSysUpTime
         TimeTicks,
      pr1646v2BgriMVD7PerfRxPkts
         Counter32,
      pr1646v2BgriMVD7PerfTxPkts
         Counter32,
      pr1646v2BgriMVD7PerfDiscards
         Counter32,
      pr1646v2BgriMVD7PerfFloods
         Counter32,
      pr1646v2BgriMVD7PerfBroadcasts
         Counter32,
      pr1646v2BgriMVD7PerfMulticasts
         Counter32,
      pr1646v2BgriMVD7PerfCacheSizeOverflows
         Counter32,
      pr1646v2BgriMVD7PerfStaticCacheViolations
         Counter32,
      pr1646v2BgriMVD7PerfCacheRelearns
         Counter32,
      pr1646v2BgriMVD7PerfCacheRelearnDrops
         Counter32,
      pr1646v2BgriMVD7PerfLoopsDetected
         Counter32
      }

pr1646v2BgriMVD7PerfGlobalIx OBJECT-TYPE
   SYNTAX      GlobalIndex
   MAX-ACCESS  not-accessible
   STATUS      current
   DESCRIPTION
      "The value of the tlsCntTreeGlobalIndex of the MANAGED OBJECT."
   ::= {pr1646v2BgriMVD7PerfEntry 10}

pr1646v2BgriMVD7PerfTableIx OBJECT-TYPE
   SYNTAX      TableIndex
   MAX-ACCESS  not-accessible
   STATUS      current
   DESCRIPTION
      ""
   ::= {pr1646v2BgriMVD7PerfEntry 11}

pr1646v2BgriMVD7PerfSysUpTime OBJECT-TYPE
   SYNTAX      TimeTicks
   MAX-ACCESS  read-only
   STATUS      current
   DESCRIPTION
      "Path: vpnBridgeGroup.performance.d7Performance.sysUpTime

       Time in centi-second."
   ::= {pr1646v2BgriMVD7PerfEntry 16777216}

pr1646v2BgriMVD7PerfRxPkts OBJECT-TYPE
   SYNTAX      Counter32
   MAX-ACCESS  read-only
   STATUS      current
   DESCRIPTION
      "Path: vpnBridgeGroup.performance.d7Performance.rxPkts

       32 bit unsigned wrappable counter."
   ::= {pr1646v2BgriMVD7PerfEntry 33554432}

pr1646v2BgriMVD7PerfTxPkts OBJECT-TYPE
   SYNTAX      Counter32
   MAX-ACCESS  read-only
   STATUS      current
   DESCRIPTION
      "Path: vpnBridgeGroup.performance.d7Performance.txPkts

       32 bit unsigned wrappable counter."
   ::= {pr1646v2BgriMVD7PerfEntry 50331648}

pr1646v2BgriMVD7PerfDiscards OBJECT-TYPE
   SYNTAX      Counter32
   MAX-ACCESS  read-only
   STATUS      current
   DESCRIPTION
      "Path: vpnBridgeGroup.performance.d7Performance.discards

       32 bit unsigned wrappable counter."
   ::= {pr1646v2BgriMVD7PerfEntry 67108864}

pr1646v2BgriMVD7PerfFloods OBJECT-TYPE
   SYNTAX      Counter32
   MAX-ACCESS  read-only
   STATUS      current
   DESCRIPTION
      "Path: vpnBridgeGroup.performance.d7Performance.floods

       32 bit unsigned wrappable counter."
   ::= {pr1646v2BgriMVD7PerfEntry 83886080}

pr1646v2BgriMVD7PerfBroadcasts OBJECT-TYPE
   SYNTAX      Counter32
   MAX-ACCESS  read-only
   STATUS      current
   DESCRIPTION
      "Path: vpnBridgeGroup.performance.d7Performance.broadcasts

       32 bit unsigned wrappable counter."
   ::= {pr1646v2BgriMVD7PerfEntry 100663296}

pr1646v2BgriMVD7PerfMulticasts OBJECT-TYPE
   SYNTAX      Counter32
   MAX-ACCESS  read-only
   STATUS      current
   DESCRIPTION
      "Path: vpnBridgeGroup.performance.d7Performance.multicasts

       32 bit unsigned wrappable counter."
   ::= {pr1646v2BgriMVD7PerfEntry 117440512}

pr1646v2BgriMVD7PerfCacheSizeOverflows OBJECT-TYPE
   SYNTAX      Counter32
   MAX-ACCESS  read-only
   STATUS      current
   DESCRIPTION
      "Path: vpnBridgeGroup.performance.d7Performance.cacheSizeOverflows

       32 bit unsigned wrappable counter."
   ::= {pr1646v2BgriMVD7PerfEntry 134217728}

pr1646v2BgriMVD7PerfStaticCacheViolations OBJECT-TYPE
   SYNTAX      Counter32
   MAX-ACCESS  read-only
   STATUS      current
   DESCRIPTION
      "Path: vpnBridgeGroup.performance.d7Performance.staticCacheViolations

       32 bit unsigned wrappable counter."
   ::= {pr1646v2BgriMVD7PerfEntry 150994944}

pr1646v2BgriMVD7PerfCacheRelearns OBJECT-TYPE
   SYNTAX      Counter32
   MAX-ACCESS  read-only
   STATUS      current
   DESCRIPTION
      "Path: vpnBridgeGroup.performance.d7Performance.cacheRelearns

       32 bit unsigned wrappable counter."
   ::= {pr1646v2BgriMVD7PerfEntry 167772160}

pr1646v2BgriMVD7PerfCacheRelearnDrops OBJECT-TYPE
   SYNTAX      Counter32
   MAX-ACCESS  read-only
   STATUS      current
   DESCRIPTION
      "Path: vpnBridgeGroup.performance.d7Performance.cacheRelearnDrops

       32 bit unsigned wrappable counter."
   ::= {pr1646v2BgriMVD7PerfEntry 184549376}

pr1646v2BgriMVD7PerfLoopsDetected OBJECT-TYPE
   SYNTAX      Counter32
   MAX-ACCESS  read-only
   STATUS      current
   DESCRIPTION
      "Path: vpnBridgeGroup.performance.d7Performance.loopsDetected

       32 bit unsigned wrappable counter."
   ::= {pr1646v2BgriMVD7PerfEntry 234881024}


pr1646v2BgriMVVlan OBJECT IDENTIFIER ::= {pr1646v2BgriMV 310}

pr1646v2BgriMVVlanSSCTable OBJECT-TYPE
   SYNTAX      SEQUENCE OF Pr1646v2BgriMVVlanEntry
   MAX-ACCESS  not-accessible
   STATUS      current
   DESCRIPTION
      ""
   ::= {pr1646v2BgriMVVlan 1}

pr1646v2BgriMVVlanEntry OBJECT-TYPE
   SYNTAX      Pr1646v2BgriMVVlanEntry
   MAX-ACCESS  not-accessible
   STATUS      current
   DESCRIPTION
      ""
   INDEX      { pr1646v2BgriMVVlanGlobalIx,
                pr1646v2BgriMVVlanTableIx }
   ::= {pr1646v2BgriMVVlanSSCTable 1}

Pr1646v2BgriMVVlanEntry ::=
   SEQUENCE
      {
      pr1646v2BgriMVVlanGlobalIx
         GlobalIndex,
      pr1646v2BgriMVVlanTableIx
         TableIndex,
      pr1646v2BgriMVVlanName
         DisplayString,
      pr1646v2BgriMVVlanMCInOctets
         Counter64,
      pr1646v2BgriMVVlanMCInUcast
         Counter64,
      pr1646v2BgriMVVlanMCInNUcastPkts
         Counter64,
      pr1646v2BgriMVVlanMCInBcastPkts
         Counter64,
      pr1646v2BgriMVVlanMCInMcastPkts
         Counter64,
      pr1646v2BgriMVVlanMCInDiscards
         Counter64,
      pr1646v2BgriMVVlanMCInErrors
         Counter64,
      pr1646v2BgriMVVlanMCInUnknownProtos
         Counter64,
      pr1646v2BgriMVVlanMCInDropEx
         Counter64,
      pr1646v2BgriMVVlanMCInDropNoMac
         Counter64,
      pr1646v2BgriMVVlanMCInDropNUCast
         Counter64,
      pr1646v2BgriMVVlanMCInDropFilter
         Counter64,
      pr1646v2BgriMVVlanMCInBandwidth15sec
         Integer32,
      pr1646v2BgriMVVlanMCInBandwidth30sec
         Integer32,
      pr1646v2BgriMVVlanMCInBandwidth1min
         Integer32,
      pr1646v2BgriMVVlanMCInBandwidth2min
         Integer32,
      pr1646v2BgriMVVlanMCInBandwidth5min
         Integer32,
      pr1646v2BgriMVVlanMCOutOctets
         Counter64,
      pr1646v2BgriMVVlanMCOutUcastPkts
         Counter64,
      pr1646v2BgriMVVlanMCOutNUcastPkts
         Counter64,
      pr1646v2BgriMVVlanMCOutBcastPkts
         Counter64,
      pr1646v2BgriMVVlanMCOutMcastPkts
         Counter64,
      pr1646v2BgriMVVlanMCOutDiscards
         Counter64,
      pr1646v2BgriMVVlanMCOutErrors
         Counter64,
      pr1646v2BgriMVVlanMCOutQLen
         Counter32,
      pr1646v2BgriMVVlanMCOutDropEx
         Counter64,
      pr1646v2BgriMVVlanMCOutDropNoArp
         Counter64,
      pr1646v2BgriMVVlanMCOutDropFilter
         Counter64,
      pr1646v2BgriMVVlanMCOutBandwidth15sec
         Integer32,
      pr1646v2BgriMVVlanMCOutBandwidth30sec
         Integer32,
      pr1646v2BgriMVVlanMCOutBandwidth1min
         Integer32,
      pr1646v2BgriMVVlanMCOutBandwidth2min
         Integer32,
      pr1646v2BgriMVVlanMCOutBandwidth5min
         Integer32,
      pr1646v2BgriMVVlanVlanVid
         Integer32
      }

pr1646v2BgriMVVlanGlobalIx OBJECT-TYPE
   SYNTAX      GlobalIndex
   MAX-ACCESS  not-accessible
   STATUS      current
   DESCRIPTION
      "The value of the tlsCntTreeGlobalIndex of the MANAGED OBJECT."
   ::= {pr1646v2BgriMVVlanEntry 10}

pr1646v2BgriMVVlanTableIx OBJECT-TYPE
   SYNTAX      TableIndex
   MAX-ACCESS  not-accessible
   STATUS      current
   DESCRIPTION
      ""
   ::= {pr1646v2BgriMVVlanEntry 11}

pr1646v2BgriMVVlanName OBJECT-TYPE
   SYNTAX      DisplayString
   MAX-ACCESS  read-only
   STATUS      current
   DESCRIPTION
      "Path: vpnBridgeGroup.performance.vlan.name"
   ::= {pr1646v2BgriMVVlanEntry 16777216}

pr1646v2BgriMVVlanMCInOctets OBJECT-TYPE
   SYNTAX      Counter64
   MAX-ACCESS  read-only
   STATUS      current
   DESCRIPTION
      "Path: vpnBridgeGroup.performance.vlan.mibCounters.ifInOctets

       64 bit unsigned wrappable counter."
   ::= {pr1646v2BgriMVVlanEntry 40697856}

pr1646v2BgriMVVlanMCInUcast OBJECT-TYPE
   SYNTAX      Counter64
   MAX-ACCESS  read-only
   STATUS      current
   DESCRIPTION
      "Path: vpnBridgeGroup.performance.vlan.mibCounters.ifInUcastPkts

       64 bit unsigned wrappable counter."
   ::= {pr1646v2BgriMVVlanEntry 40763392}

pr1646v2BgriMVVlanMCInNUcastPkts OBJECT-TYPE
   SYNTAX      Counter64
   MAX-ACCESS  read-only
   STATUS      current
   DESCRIPTION
      "Path: vpnBridgeGroup.performance.vlan.mibCounters.ifInNUcastPkts

       64 bit unsigned wrappable counter."
   ::= {pr1646v2BgriMVVlanEntry 40828928}

pr1646v2BgriMVVlanMCInBcastPkts OBJECT-TYPE
   SYNTAX      Counter64
   MAX-ACCESS  read-only
   STATUS      current
   DESCRIPTION
      "Path: vpnBridgeGroup.performance.vlan.mibCounters.ifInBcastPkts

       64 bit unsigned wrappable counter."
   ::= {pr1646v2BgriMVVlanEntry 47382528}

pr1646v2BgriMVVlanMCInMcastPkts OBJECT-TYPE
   SYNTAX      Counter64
   MAX-ACCESS  read-only
   STATUS      current
   DESCRIPTION
      "Path: vpnBridgeGroup.performance.vlan.mibCounters.ifInMcastPkts

       64 bit unsigned wrappable counter."
   ::= {pr1646v2BgriMVVlanEntry 48037888}

pr1646v2BgriMVVlanMCInDiscards OBJECT-TYPE
   SYNTAX      Counter64
   MAX-ACCESS  read-only
   STATUS      current
   DESCRIPTION
      "Path: vpnBridgeGroup.performance.vlan.mibCounters.ifInDiscards

       64 bit unsigned wrappable counter."
   ::= {pr1646v2BgriMVVlanEntry 40894464}

pr1646v2BgriMVVlanMCInErrors OBJECT-TYPE
   SYNTAX      Counter64
   MAX-ACCESS  read-only
   STATUS      current
   DESCRIPTION
      "Path: vpnBridgeGroup.performance.vlan.mibCounters.ifInErrors

       64 bit unsigned wrappable counter."
   ::= {pr1646v2BgriMVVlanEntry 40960000}

pr1646v2BgriMVVlanMCInUnknownProtos OBJECT-TYPE
   SYNTAX      Counter64
   MAX-ACCESS  read-only
   STATUS      current
   DESCRIPTION
      "Path: vpnBridgeGroup.performance.vlan.mibCounters.ifInUnknownProtos

       64 bit unsigned wrappable counter."
   ::= {pr1646v2BgriMVVlanEntry 41025536}

pr1646v2BgriMVVlanMCInDropEx OBJECT-TYPE
   SYNTAX      Counter64
   MAX-ACCESS  read-only
   STATUS      current
   DESCRIPTION
      "Path: vpnBridgeGroup.performance.vlan.mibCounters.ifInDropLevelExceeded

       64 bit unsigned wrappable counter."
   ::= {pr1646v2BgriMVVlanEntry 42074112}

pr1646v2BgriMVVlanMCInDropNoMac OBJECT-TYPE
   SYNTAX      Counter64
   MAX-ACCESS  read-only
   STATUS      current
   DESCRIPTION
      "Path: vpnBridgeGroup.performance.vlan.mibCounters.ifInDiscardsNoMacFit

       64 bit unsigned wrappable counter."
   ::= {pr1646v2BgriMVVlanEntry 42270720}

pr1646v2BgriMVVlanMCInDropNUCast OBJECT-TYPE
   SYNTAX      Counter64
   MAX-ACCESS  read-only
   STATUS      current
   DESCRIPTION
      "Path: vpnBridgeGroup.performance.vlan.mibCounters.ifInDiscardsNUCast

       64 bit unsigned wrappable counter."
   ::= {pr1646v2BgriMVVlanEntry 42467328}

pr1646v2BgriMVVlanMCInDropFilter OBJECT-TYPE
   SYNTAX      Counter64
   MAX-ACCESS  read-only
   STATUS      current
   DESCRIPTION
      "Path: vpnBridgeGroup.performance.vlan.mibCounters.ifInDiscardsFilter

       64 bit unsigned wrappable counter."
   ::= {pr1646v2BgriMVVlanEntry 42532864}

pr1646v2BgriMVVlanMCInBandwidth15sec OBJECT-TYPE
   SYNTAX      Integer32
   MAX-ACCESS  read-only
   STATUS      current
   DESCRIPTION
      "Path: vpnBridgeGroup.performance.vlan.mibCounters.ifInBandwidth.15sec

       unit name = bps
       formula = 8 * ; 8 /"
   ::= {pr1646v2BgriMVVlanEntry 45417728}

pr1646v2BgriMVVlanMCInBandwidth30sec OBJECT-TYPE
   SYNTAX      Integer32
   MAX-ACCESS  read-only
   STATUS      current
   DESCRIPTION
      "Path: vpnBridgeGroup.performance.vlan.mibCounters.ifInBandwidth.30sec

       unit name = bps
       formula = 8 * ; 8 /"
   ::= {pr1646v2BgriMVVlanEntry 45419008}

pr1646v2BgriMVVlanMCInBandwidth1min OBJECT-TYPE
   SYNTAX      Integer32
   MAX-ACCESS  read-only
   STATUS      current
   DESCRIPTION
      "Path: vpnBridgeGroup.performance.vlan.mibCounters.ifInBandwidth.1min

       unit name = bps
       formula = 8 * ; 8 /"
   ::= {pr1646v2BgriMVVlanEntry 45421568}

pr1646v2BgriMVVlanMCInBandwidth2min OBJECT-TYPE
   SYNTAX      Integer32
   MAX-ACCESS  read-only
   STATUS      current
   DESCRIPTION
      "Path: vpnBridgeGroup.performance.vlan.mibCounters.ifInBandwidth.2min

       unit name = bps
       formula = 8 * ; 8 /"
   ::= {pr1646v2BgriMVVlanEntry 45426688}

pr1646v2BgriMVVlanMCInBandwidth5min OBJECT-TYPE
   SYNTAX      Integer32
   MAX-ACCESS  read-only
   STATUS      current
   DESCRIPTION
      "Path: vpnBridgeGroup.performance.vlan.mibCounters.ifInBandwidth.5min

       unit name = bps
       formula = 8 * ; 8 /"
   ::= {pr1646v2BgriMVVlanEntry 45442048}

pr1646v2BgriMVVlanMCOutOctets OBJECT-TYPE
   SYNTAX      Counter64
   MAX-ACCESS  read-only
   STATUS      current
   DESCRIPTION
      "Path: vpnBridgeGroup.performance.vlan.mibCounters.ifOutOctets

       64 bit unsigned wrappable counter."
   ::= {pr1646v2BgriMVVlanEntry 41091072}

pr1646v2BgriMVVlanMCOutUcastPkts OBJECT-TYPE
   SYNTAX      Counter64
   MAX-ACCESS  read-only
   STATUS      current
   DESCRIPTION
      "Path: vpnBridgeGroup.performance.vlan.mibCounters.ifOutUcastPkts

       64 bit unsigned wrappable counter."
   ::= {pr1646v2BgriMVVlanEntry 41156608}

pr1646v2BgriMVVlanMCOutNUcastPkts OBJECT-TYPE
   SYNTAX      Counter64
   MAX-ACCESS  read-only
   STATUS      current
   DESCRIPTION
      "Path: vpnBridgeGroup.performance.vlan.mibCounters.ifOutNUcastPkts

       64 bit unsigned wrappable counter."
   ::= {pr1646v2BgriMVVlanEntry 41222144}

pr1646v2BgriMVVlanMCOutBcastPkts OBJECT-TYPE
   SYNTAX      Counter64
   MAX-ACCESS  read-only
   STATUS      current
   DESCRIPTION
      "Path: vpnBridgeGroup.performance.vlan.mibCounters.ifOutBcastPkts

       64 bit unsigned wrappable counter."
   ::= {pr1646v2BgriMVVlanEntry 47775744}

pr1646v2BgriMVVlanMCOutMcastPkts OBJECT-TYPE
   SYNTAX      Counter64
   MAX-ACCESS  read-only
   STATUS      current
   DESCRIPTION
      "Path: vpnBridgeGroup.performance.vlan.mibCounters.ifOutMcastPkts

       64 bit unsigned wrappable counter."
   ::= {pr1646v2BgriMVVlanEntry 48431104}

pr1646v2BgriMVVlanMCOutDiscards OBJECT-TYPE
   SYNTAX      Counter64
   MAX-ACCESS  read-only
   STATUS      current
   DESCRIPTION
      "Path: vpnBridgeGroup.performance.vlan.mibCounters.ifOutDiscards

       64 bit unsigned wrappable counter."
   ::= {pr1646v2BgriMVVlanEntry 41287680}

pr1646v2BgriMVVlanMCOutErrors OBJECT-TYPE
   SYNTAX      Counter64
   MAX-ACCESS  read-only
   STATUS      current
   DESCRIPTION
      "Path: vpnBridgeGroup.performance.vlan.mibCounters.ifOutErrors

       64 bit unsigned wrappable counter."
   ::= {pr1646v2BgriMVVlanEntry 41353216}

pr1646v2BgriMVVlanMCOutQLen OBJECT-TYPE
   SYNTAX      Counter32
   MAX-ACCESS  read-only
   STATUS      current
   DESCRIPTION
      "Path: vpnBridgeGroup.performance.vlan.mibCounters.ifOutQLen

       32 bit unsigned wrappable counter."
   ::= {pr1646v2BgriMVVlanEntry 41418752}

pr1646v2BgriMVVlanMCOutDropEx OBJECT-TYPE
   SYNTAX      Counter64
   MAX-ACCESS  read-only
   STATUS      current
   DESCRIPTION
      "Path: vpnBridgeGroup.performance.vlan.mibCounters.ifOutDropLevelExceeded

       64 bit unsigned wrappable counter."
   ::= {pr1646v2BgriMVVlanEntry 41484288}

pr1646v2BgriMVVlanMCOutDropNoArp OBJECT-TYPE
   SYNTAX      Counter64
   MAX-ACCESS  read-only
   STATUS      current
   DESCRIPTION
      "Path: vpnBridgeGroup.performance.vlan.mibCounters.ifOutDiscardsNoArp

       64 bit unsigned wrappable counter."
   ::= {pr1646v2BgriMVVlanEntry 42336256}

pr1646v2BgriMVVlanMCOutDropFilter OBJECT-TYPE
   SYNTAX      Counter64
   MAX-ACCESS  read-only
   STATUS      current
   DESCRIPTION
      "Path: vpnBridgeGroup.performance.vlan.mibCounters.ifOutDiscardsFilter

       64 bit unsigned wrappable counter."
   ::= {pr1646v2BgriMVVlanEntry 42598400}

pr1646v2BgriMVVlanMCOutBandwidth15sec OBJECT-TYPE
   SYNTAX      Integer32
   MAX-ACCESS  read-only
   STATUS      current
   DESCRIPTION
      "Path: vpnBridgeGroup.performance.vlan.mibCounters.ifOutBandwidth.15sec

       unit name = bps
       formula = 8 * ; 8 /"
   ::= {pr1646v2BgriMVVlanEntry 45483264}

pr1646v2BgriMVVlanMCOutBandwidth30sec OBJECT-TYPE
   SYNTAX      Integer32
   MAX-ACCESS  read-only
   STATUS      current
   DESCRIPTION
      "Path: vpnBridgeGroup.performance.vlan.mibCounters.ifOutBandwidth.30sec

       unit name = bps
       formula = 8 * ; 8 /"
   ::= {pr1646v2BgriMVVlanEntry 45484544}

pr1646v2BgriMVVlanMCOutBandwidth1min OBJECT-TYPE
   SYNTAX      Integer32
   MAX-ACCESS  read-only
   STATUS      current
   DESCRIPTION
      "Path: vpnBridgeGroup.performance.vlan.mibCounters.ifOutBandwidth.1min

       unit name = bps
       formula = 8 * ; 8 /"
   ::= {pr1646v2BgriMVVlanEntry 45487104}

pr1646v2BgriMVVlanMCOutBandwidth2min OBJECT-TYPE
   SYNTAX      Integer32
   MAX-ACCESS  read-only
   STATUS      current
   DESCRIPTION
      "Path: vpnBridgeGroup.performance.vlan.mibCounters.ifOutBandwidth.2min

       unit name = bps
       formula = 8 * ; 8 /"
   ::= {pr1646v2BgriMVVlanEntry 45492224}

pr1646v2BgriMVVlanMCOutBandwidth5min OBJECT-TYPE
   SYNTAX      Integer32
   MAX-ACCESS  read-only
   STATUS      current
   DESCRIPTION
      "Path: vpnBridgeGroup.performance.vlan.mibCounters.ifOutBandwidth.5min

       unit name = bps
       formula = 8 * ; 8 /"
   ::= {pr1646v2BgriMVVlanEntry 45507584}

pr1646v2BgriMVVlanVlanVid OBJECT-TYPE
   SYNTAX      Integer32
   MAX-ACCESS  read-only
   STATUS      current
   DESCRIPTION
      "Path: vpnBridgeGroup.performance.vlan.vlan.vid"
   ::= {pr1646v2BgriMVVlanEntry 234946560}

pr1646v2BgriMVVlanMCH2P OBJECT-TYPE
   SYNTAX      SEQUENCE OF Pr1646v2BgriMVVlanMCH2PEntry
   MAX-ACCESS  not-accessible
   STATUS      current
   DESCRIPTION
      ""
   ::= {pr1646v2BgriMVVlan 41549824}

pr1646v2BgriMVVlanMCH2PEntry OBJECT-TYPE
   SYNTAX      Pr1646v2BgriMVVlanMCH2PEntry
   MAX-ACCESS  not-accessible
   STATUS      current
   DESCRIPTION
      ""
   INDEX      { pr1646v2BgriMVVlanMCH2PGlobalIx,
                pr1646v2BgriMVVlanTableIx,
                pr1646v2BgriMVVlanMCH2PTableIx }
   ::= {pr1646v2BgriMVVlanMCH2P 1}

Pr1646v2BgriMVVlanMCH2PEntry ::=
   SEQUENCE
      {
      pr1646v2BgriMVVlanMCH2PGlobalIx
         GlobalIndex,
      pr1646v2BgriMVVlanMCH2PTableIx
         TableIndex,
      pr1646v2BgriMVVlanMCH2PSysUpTime
         TimeTicks,
      pr1646v2BgriMVVlanMCH2PIfUpTime
         TimeTicks,
      pr1646v2BgriMVVlanMCH2PIfStatChanges
         Counter32,
      pr1646v2BgriMVVlanMCH2PIfInOctets
         Counter64,
      pr1646v2BgriMVVlanMCH2PIfInUCPkts
         Counter64,
      pr1646v2BgriMVVlanMCH2PIfInNUCPkts
         Counter64,
      pr1646v2BgriMVVlanMCH2PIfInBCPkts
         Counter64,
      pr1646v2BgriMVVlanMCH2PIfInMCPkts
         Counter64,
      pr1646v2BgriMVVlanMCH2PIfInDiscards
         Counter64,
      pr1646v2BgriMVVlanMCH2PIfInErrors
         Counter64,
      pr1646v2BgriMVVlanMCH2PIfInUnkwn
         Counter64,
      pr1646v2BgriMVVlanMCH2PInDropEx
         Counter64,
      pr1646v2BgriMVVlanMCH2PInDropNoMac
         Counter64,
      pr1646v2BgriMVVlanMCH2PInDropNUCast
         Counter64,
      pr1646v2BgriMVVlanMCH2PInDropFilter
         Counter64,
      pr1646v2BgriMVVlanMCH2PIfInBandwidth
         Integer32,
      pr1646v2BgriMVVlanMCH2PIfOutOctets
         Counter64,
      pr1646v2BgriMVVlanMCH2PIfOutUCPkts
         Counter64,
      pr1646v2BgriMVVlanMCH2PIfOutNUCPkts
         Counter64,
      pr1646v2BgriMVVlanMCH2PIfOutBCPkts
         Counter64,
      pr1646v2BgriMVVlanMCH2PIfOutMCPkts
         Counter64,
      pr1646v2BgriMVVlanMCH2PIfOutDiscards
         Counter64,
      pr1646v2BgriMVVlanMCH2PIfOutErrors
         Counter64,
      pr1646v2BgriMVVlanMCH2POutDropEx
         Counter64,
      pr1646v2BgriMVVlanMCH2POutDropNoArp
         Counter64,
      pr1646v2BgriMVVlanMCH2POutDropFilter
         Counter64,
      pr1646v2BgriMVVlanMCH2PIfOutBandwidth
         Integer32,
      pr1646v2BgriMVVlanMCH2PIfErrSec
         Counter32
      }

pr1646v2BgriMVVlanMCH2PGlobalIx OBJECT-TYPE
   SYNTAX      GlobalIndex
   MAX-ACCESS  not-accessible
   STATUS      current
   DESCRIPTION
      "The value of the tlsCntTreeGlobalIndex of the MANAGED OBJECT."
   ::= {pr1646v2BgriMVVlanMCH2PEntry 10}

pr1646v2BgriMVVlanMCH2PTableIx OBJECT-TYPE
   SYNTAX      TableIndex
   MAX-ACCESS  not-accessible
   STATUS      current
   DESCRIPTION
      ""
   ::= {pr1646v2BgriMVVlanMCH2PEntry 11}

pr1646v2BgriMVVlanMCH2PSysUpTime OBJECT-TYPE
   SYNTAX      TimeTicks
   MAX-ACCESS  read-only
   STATUS      current
   DESCRIPTION
      "Path: vpnBridgeGroup.performance.vlan.mibCounters.h2Performance.sysUpTime

       Time in centi-second."
   ::= {pr1646v2BgriMVVlanMCH2PEntry 16777216}

pr1646v2BgriMVVlanMCH2PIfUpTime OBJECT-TYPE
   SYNTAX      TimeTicks
   MAX-ACCESS  read-only
   STATUS      current
   DESCRIPTION
      "Path: vpnBridgeGroup.performance.vlan.mibCounters.h2Performance.ifUpTime

       Time in centi-second."
   ::= {pr1646v2BgriMVVlanMCH2PEntry 33554432}

pr1646v2BgriMVVlanMCH2PIfStatChanges OBJECT-TYPE
   SYNTAX      Counter32
   MAX-ACCESS  read-only
   STATUS      current
   DESCRIPTION
      "Path: vpnBridgeGroup.performance.vlan.mibCounters.h2Performance.ifStatusChanges

       32 bit unsigned wrappable counter."
   ::= {pr1646v2BgriMVVlanMCH2PEntry 50331648}

pr1646v2BgriMVVlanMCH2PIfInOctets OBJECT-TYPE
   SYNTAX      Counter64
   MAX-ACCESS  read-only
   STATUS      current
   DESCRIPTION
      "Path: vpnBridgeGroup.performance.vlan.mibCounters.h2Performance.ifInOctets

       64 bit unsigned wrappable counter."
   ::= {pr1646v2BgriMVVlanMCH2PEntry 67108864}

pr1646v2BgriMVVlanMCH2PIfInUCPkts OBJECT-TYPE
   SYNTAX      Counter64
   MAX-ACCESS  read-only
   STATUS      current
   DESCRIPTION
      "Path: vpnBridgeGroup.performance.vlan.mibCounters.h2Performance.ifInUcastPkts

       64 bit unsigned wrappable counter."
   ::= {pr1646v2BgriMVVlanMCH2PEntry 83886080}

pr1646v2BgriMVVlanMCH2PIfInNUCPkts OBJECT-TYPE
   SYNTAX      Counter64
   MAX-ACCESS  read-only
   STATUS      current
   DESCRIPTION
      "Path: vpnBridgeGroup.performance.vlan.mibCounters.h2Performance.ifInNUcastPkts

       64 bit unsigned wrappable counter."
   ::= {pr1646v2BgriMVVlanMCH2PEntry 100663296}

pr1646v2BgriMVVlanMCH2PIfInBCPkts OBJECT-TYPE
   SYNTAX      Counter64
   MAX-ACCESS  read-only
   STATUS      current
   DESCRIPTION
      "Path: vpnBridgeGroup.performance.vlan.mibCounters.h2Performance.ifInBcastPkts

       64 bit unsigned wrappable counter."
   ::= {pr1646v2BgriMVVlanMCH2PEntry 419430400}

pr1646v2BgriMVVlanMCH2PIfInMCPkts OBJECT-TYPE
   SYNTAX      Counter64
   MAX-ACCESS  read-only
   STATUS      current
   DESCRIPTION
      "Path: vpnBridgeGroup.performance.vlan.mibCounters.h2Performance.ifInMcastPkts

       64 bit unsigned wrappable counter."
   ::= {pr1646v2BgriMVVlanMCH2PEntry 436207616}

pr1646v2BgriMVVlanMCH2PIfInDiscards OBJECT-TYPE
   SYNTAX      Counter64
   MAX-ACCESS  read-only
   STATUS      current
   DESCRIPTION
      "Path: vpnBridgeGroup.performance.vlan.mibCounters.h2Performance.ifInDiscards

       64 bit unsigned wrappable counter."
   ::= {pr1646v2BgriMVVlanMCH2PEntry 117440512}

pr1646v2BgriMVVlanMCH2PIfInErrors OBJECT-TYPE
   SYNTAX      Counter64
   MAX-ACCESS  read-only
   STATUS      current
   DESCRIPTION
      "Path: vpnBridgeGroup.performance.vlan.mibCounters.h2Performance.ifInErrors

       64 bit unsigned wrappable counter."
   ::= {pr1646v2BgriMVVlanMCH2PEntry 134217728}

pr1646v2BgriMVVlanMCH2PIfInUnkwn OBJECT-TYPE
   SYNTAX      Counter64
   MAX-ACCESS  read-only
   STATUS      current
   DESCRIPTION
      "Path: vpnBridgeGroup.performance.vlan.mibCounters.h2Performance.ifInUnknownProtos

       64 bit unsigned wrappable counter."
   ::= {pr1646v2BgriMVVlanMCH2PEntry 150994944}

pr1646v2BgriMVVlanMCH2PInDropEx OBJECT-TYPE
   SYNTAX      Counter64
   MAX-ACCESS  read-only
   STATUS      current
   DESCRIPTION
      "Path: vpnBridgeGroup.performance.vlan.mibCounters.h2Performance.ifInDropLevelExceeded

       64 bit unsigned wrappable counter."
   ::= {pr1646v2BgriMVVlanMCH2PEntry 335544320}

pr1646v2BgriMVVlanMCH2PInDropNoMac OBJECT-TYPE
   SYNTAX      Counter64
   MAX-ACCESS  read-only
   STATUS      current
   DESCRIPTION
      "Path: vpnBridgeGroup.performance.vlan.mibCounters.h2Performance.fInDiscardsNoMacFit

       64 bit unsigned wrappable counter."
   ::= {pr1646v2BgriMVVlanMCH2PEntry 301989888}

pr1646v2BgriMVVlanMCH2PInDropNUCast OBJECT-TYPE
   SYNTAX      Counter64
   MAX-ACCESS  read-only
   STATUS      current
   DESCRIPTION
      "Path: vpnBridgeGroup.performance.vlan.mibCounters.h2Performance.fInDiscardsNUCast

       64 bit unsigned wrappable counter."
   ::= {pr1646v2BgriMVVlanMCH2PEntry 318767104}

pr1646v2BgriMVVlanMCH2PInDropFilter OBJECT-TYPE
   SYNTAX      Counter64
   MAX-ACCESS  read-only
   STATUS      current
   DESCRIPTION
      "Path: vpnBridgeGroup.performance.vlan.mibCounters.h2Performance.fInDiscardsFilter

       64 bit unsigned wrappable counter."
   ::= {pr1646v2BgriMVVlanMCH2PEntry 385875968}

pr1646v2BgriMVVlanMCH2PIfInBandwidth OBJECT-TYPE
   SYNTAX      Integer32
   MAX-ACCESS  read-only
   STATUS      current
   DESCRIPTION
      "Path: vpnBridgeGroup.performance.vlan.mibCounters.h2Performance.ifInBandwidth

       unit name = bps
       formula = 8 * ; 8 /"
   ::= {pr1646v2BgriMVVlanMCH2PEntry 268435456}

pr1646v2BgriMVVlanMCH2PIfOutOctets OBJECT-TYPE
   SYNTAX      Counter64
   MAX-ACCESS  read-only
   STATUS      current
   DESCRIPTION
      "Path: vpnBridgeGroup.performance.vlan.mibCounters.h2Performance.ifOutOctets

       64 bit unsigned wrappable counter."
   ::= {pr1646v2BgriMVVlanMCH2PEntry 167772160}

pr1646v2BgriMVVlanMCH2PIfOutUCPkts OBJECT-TYPE
   SYNTAX      Counter64
   MAX-ACCESS  read-only
   STATUS      current
   DESCRIPTION
      "Path: vpnBridgeGroup.performance.vlan.mibCounters.h2Performance.ifOutUcastPkts

       64 bit unsigned wrappable counter."
   ::= {pr1646v2BgriMVVlanMCH2PEntry 184549376}

pr1646v2BgriMVVlanMCH2PIfOutNUCPkts OBJECT-TYPE
   SYNTAX      Counter64
   MAX-ACCESS  read-only
   STATUS      current
   DESCRIPTION
      "Path: vpnBridgeGroup.performance.vlan.mibCounters.h2Performance.ifOutNUcastPkts

       64 bit unsigned wrappable counter."
   ::= {pr1646v2BgriMVVlanMCH2PEntry 201326592}

pr1646v2BgriMVVlanMCH2PIfOutBCPkts OBJECT-TYPE
   SYNTAX      Counter64
   MAX-ACCESS  read-only
   STATUS      current
   DESCRIPTION
      "Path: vpnBridgeGroup.performance.vlan.mibCounters.h2Performance.ifOutBcastPkts

       64 bit unsigned wrappable counter."
   ::= {pr1646v2BgriMVVlanMCH2PEntry 452984832}

pr1646v2BgriMVVlanMCH2PIfOutMCPkts OBJECT-TYPE
   SYNTAX      Counter64
   MAX-ACCESS  read-only
   STATUS      current
   DESCRIPTION
      "Path: vpnBridgeGroup.performance.vlan.mibCounters.h2Performance.ifOutMcastPkts

       64 bit unsigned wrappable counter."
   ::= {pr1646v2BgriMVVlanMCH2PEntry 469762048}

pr1646v2BgriMVVlanMCH2PIfOutDiscards OBJECT-TYPE
   SYNTAX      Counter64
   MAX-ACCESS  read-only
   STATUS      current
   DESCRIPTION
      "Path: vpnBridgeGroup.performance.vlan.mibCounters.h2Performance.ifOutDiscards

       64 bit unsigned wrappable counter."
   ::= {pr1646v2BgriMVVlanMCH2PEntry 218103808}

pr1646v2BgriMVVlanMCH2PIfOutErrors OBJECT-TYPE
   SYNTAX      Counter64
   MAX-ACCESS  read-only
   STATUS      current
   DESCRIPTION
      "Path: vpnBridgeGroup.performance.vlan.mibCounters.h2Performance.ifOutErrors

       64 bit unsigned wrappable counter."
   ::= {pr1646v2BgriMVVlanMCH2PEntry 234881024}

pr1646v2BgriMVVlanMCH2POutDropEx OBJECT-TYPE
   SYNTAX      Counter64
   MAX-ACCESS  read-only
   STATUS      current
   DESCRIPTION
      "Path: vpnBridgeGroup.performance.vlan.mibCounters.h2Performance.ifOutDropLevelExceeded

       64 bit unsigned wrappable counter."
   ::= {pr1646v2BgriMVVlanMCH2PEntry 352321536}

pr1646v2BgriMVVlanMCH2POutDropNoArp OBJECT-TYPE
   SYNTAX      Counter64
   MAX-ACCESS  read-only
   STATUS      current
   DESCRIPTION
      "Path: vpnBridgeGroup.performance.vlan.mibCounters.h2Performance.ifOutDiscardsNoArp

       64 bit unsigned wrappable counter."
   ::= {pr1646v2BgriMVVlanMCH2PEntry 369098752}

pr1646v2BgriMVVlanMCH2POutDropFilter OBJECT-TYPE
   SYNTAX      Counter64
   MAX-ACCESS  read-only
   STATUS      current
   DESCRIPTION
      "Path: vpnBridgeGroup.performance.vlan.mibCounters.h2Performance.ifOutDiscardsFilter

       64 bit unsigned wrappable counter."
   ::= {pr1646v2BgriMVVlanMCH2PEntry 402653184}

pr1646v2BgriMVVlanMCH2PIfOutBandwidth OBJECT-TYPE
   SYNTAX      Integer32
   MAX-ACCESS  read-only
   STATUS      current
   DESCRIPTION
      "Path: vpnBridgeGroup.performance.vlan.mibCounters.h2Performance.ifOutBandwidth

       unit name = bps
       formula = 8 * ; 8 /"
   ::= {pr1646v2BgriMVVlanMCH2PEntry 285212672}

pr1646v2BgriMVVlanMCH2PIfErrSec OBJECT-TYPE
   SYNTAX      Counter32
   MAX-ACCESS  read-only
   STATUS      current
   DESCRIPTION
      "Path: vpnBridgeGroup.performance.vlan.mibCounters.h2Performance.ifErrSec

       32 bit unsigned wrappable counter."
   ::= {pr1646v2BgriMVVlanMCH2PEntry 251658240}

pr1646v2BgriMVVlanMCH24P OBJECT-TYPE
   SYNTAX      SEQUENCE OF Pr1646v2BgriMVVlanMCH24PEntry
   MAX-ACCESS  not-accessible
   STATUS      current
   DESCRIPTION
      ""
   ::= {pr1646v2BgriMVVlan 41615360}

pr1646v2BgriMVVlanMCH24PEntry OBJECT-TYPE
   SYNTAX      Pr1646v2BgriMVVlanMCH24PEntry
   MAX-ACCESS  not-accessible
   STATUS      current
   DESCRIPTION
      ""
   INDEX      { pr1646v2BgriMVVlanMCH24PGlobalIx,
                pr1646v2BgriMVVlanTableIx,
                pr1646v2BgriMVVlanMCH24PTableIx }
   ::= {pr1646v2BgriMVVlanMCH24P 1}

Pr1646v2BgriMVVlanMCH24PEntry ::=
   SEQUENCE
      {
      pr1646v2BgriMVVlanMCH24PGlobalIx
         GlobalIndex,
      pr1646v2BgriMVVlanMCH24PTableIx
         TableIndex,
      pr1646v2BgriMVVlanMCH24PSysUpTime
         TimeTicks,
      pr1646v2BgriMVVlanMCH24PIfUpTime
         TimeTicks,
      pr1646v2BgriMVVlanMCH24PIfStatChanges
         Counter32,
      pr1646v2BgriMVVlanMCH24PIfInOctets
         Counter64,
      pr1646v2BgriMVVlanMCH24PIfInUCPkts
         Counter64,
      pr1646v2BgriMVVlanMCH24PIfInNUCPkts
         Counter64,
      pr1646v2BgriMVVlanMCH24PIfInBCPkts
         Counter64,
      pr1646v2BgriMVVlanMCH24PIfInMCPkts
         Counter64,
      pr1646v2BgriMVVlanMCH24PIfInDiscards
         Counter64,
      pr1646v2BgriMVVlanMCH24PIfInErrors
         Counter64,
      pr1646v2BgriMVVlanMCH24PIfInUnkwn
         Counter64,
      pr1646v2BgriMVVlanMCH24PInDropEx
         Counter64,
      pr1646v2BgriMVVlanMCH24PInDropNoMac
         Counter64,
      pr1646v2BgriMVVlanMCH24PInDropNUCast
         Counter64,
      pr1646v2BgriMVVlanMCH24PInDropFilter
         Counter64,
      pr1646v2BgriMVVlanMCH24PIfInBandwidth
         Integer32,
      pr1646v2BgriMVVlanMCH24PIfOutOctets
         Counter64,
      pr1646v2BgriMVVlanMCH24PIfOutUCPkts
         Counter64,
      pr1646v2BgriMVVlanMCH24PIfOutNUCPkts
         Counter64,
      pr1646v2BgriMVVlanMCH24PIfOutBCPkts
         Counter64,
      pr1646v2BgriMVVlanMCH24PIfOutMCPkts
         Counter64,
      pr1646v2BgriMVVlanMCH24PIfOutDiscards
         Counter64,
      pr1646v2BgriMVVlanMCH24PIfOutErrors
         Counter64,
      pr1646v2BgriMVVlanMCH24POutDropEx
         Counter64,
      pr1646v2BgriMVVlanMCH24POutDropNoArp
         Counter64,
      pr1646v2BgriMVVlanMCH24POutDropFilter
         Counter64,
      pr1646v2BgriMVVlanMCH24PIfOutBandwidth
         Integer32,
      pr1646v2BgriMVVlanMCH24PIfErrSec
         Counter32
      }

pr1646v2BgriMVVlanMCH24PGlobalIx OBJECT-TYPE
   SYNTAX      GlobalIndex
   MAX-ACCESS  not-accessible
   STATUS      current
   DESCRIPTION
      "The value of the tlsCntTreeGlobalIndex of the MANAGED OBJECT."
   ::= {pr1646v2BgriMVVlanMCH24PEntry 10}

pr1646v2BgriMVVlanMCH24PTableIx OBJECT-TYPE
   SYNTAX      TableIndex
   MAX-ACCESS  not-accessible
   STATUS      current
   DESCRIPTION
      ""
   ::= {pr1646v2BgriMVVlanMCH24PEntry 11}

pr1646v2BgriMVVlanMCH24PSysUpTime OBJECT-TYPE
   SYNTAX      TimeTicks
   MAX-ACCESS  read-only
   STATUS      current
   DESCRIPTION
      "Path: vpnBridgeGroup.performance.vlan.mibCounters.h24Performance.sysUpTime

       Time in centi-second."
   ::= {pr1646v2BgriMVVlanMCH24PEntry 16777216}

pr1646v2BgriMVVlanMCH24PIfUpTime OBJECT-TYPE
   SYNTAX      TimeTicks
   MAX-ACCESS  read-only
   STATUS      current
   DESCRIPTION
      "Path: vpnBridgeGroup.performance.vlan.mibCounters.h24Performance.ifUpTime

       Time in centi-second."
   ::= {pr1646v2BgriMVVlanMCH24PEntry 33554432}

pr1646v2BgriMVVlanMCH24PIfStatChanges OBJECT-TYPE
   SYNTAX      Counter32
   MAX-ACCESS  read-only
   STATUS      current
   DESCRIPTION
      "Path: vpnBridgeGroup.performance.vlan.mibCounters.h24Performance.ifStatusChanges

       32 bit unsigned wrappable counter."
   ::= {pr1646v2BgriMVVlanMCH24PEntry 50331648}

pr1646v2BgriMVVlanMCH24PIfInOctets OBJECT-TYPE
   SYNTAX      Counter64
   MAX-ACCESS  read-only
   STATUS      current
   DESCRIPTION
      "Path: vpnBridgeGroup.performance.vlan.mibCounters.h24Performance.ifInOctets

       64 bit unsigned wrappable counter."
   ::= {pr1646v2BgriMVVlanMCH24PEntry 67108864}

pr1646v2BgriMVVlanMCH24PIfInUCPkts OBJECT-TYPE
   SYNTAX      Counter64
   MAX-ACCESS  read-only
   STATUS      current
   DESCRIPTION
      "Path: vpnBridgeGroup.performance.vlan.mibCounters.h24Performance.ifInUcastPkts

       64 bit unsigned wrappable counter."
   ::= {pr1646v2BgriMVVlanMCH24PEntry 83886080}

pr1646v2BgriMVVlanMCH24PIfInNUCPkts OBJECT-TYPE
   SYNTAX      Counter64
   MAX-ACCESS  read-only
   STATUS      current
   DESCRIPTION
      "Path: vpnBridgeGroup.performance.vlan.mibCounters.h24Performance.ifInNUcastPkts

       64 bit unsigned wrappable counter."
   ::= {pr1646v2BgriMVVlanMCH24PEntry 100663296}

pr1646v2BgriMVVlanMCH24PIfInBCPkts OBJECT-TYPE
   SYNTAX      Counter64
   MAX-ACCESS  read-only
   STATUS      current
   DESCRIPTION
      "Path: vpnBridgeGroup.performance.vlan.mibCounters.h24Performance.ifInBcastPkts

       64 bit unsigned wrappable counter."
   ::= {pr1646v2BgriMVVlanMCH24PEntry 419430400}

pr1646v2BgriMVVlanMCH24PIfInMCPkts OBJECT-TYPE
   SYNTAX      Counter64
   MAX-ACCESS  read-only
   STATUS      current
   DESCRIPTION
      "Path: vpnBridgeGroup.performance.vlan.mibCounters.h24Performance.ifInMcastPkts

       64 bit unsigned wrappable counter."
   ::= {pr1646v2BgriMVVlanMCH24PEntry 436207616}

pr1646v2BgriMVVlanMCH24PIfInDiscards OBJECT-TYPE
   SYNTAX      Counter64
   MAX-ACCESS  read-only
   STATUS      current
   DESCRIPTION
      "Path: vpnBridgeGroup.performance.vlan.mibCounters.h24Performance.ifInDiscards

       64 bit unsigned wrappable counter."
   ::= {pr1646v2BgriMVVlanMCH24PEntry 117440512}

pr1646v2BgriMVVlanMCH24PIfInErrors OBJECT-TYPE
   SYNTAX      Counter64
   MAX-ACCESS  read-only
   STATUS      current
   DESCRIPTION
      "Path: vpnBridgeGroup.performance.vlan.mibCounters.h24Performance.ifInErrors

       64 bit unsigned wrappable counter."
   ::= {pr1646v2BgriMVVlanMCH24PEntry 134217728}

pr1646v2BgriMVVlanMCH24PIfInUnkwn OBJECT-TYPE
   SYNTAX      Counter64
   MAX-ACCESS  read-only
   STATUS      current
   DESCRIPTION
      "Path: vpnBridgeGroup.performance.vlan.mibCounters.h24Performance.ifInUnknownProtos

       64 bit unsigned wrappable counter."
   ::= {pr1646v2BgriMVVlanMCH24PEntry 150994944}

pr1646v2BgriMVVlanMCH24PInDropEx OBJECT-TYPE
   SYNTAX      Counter64
   MAX-ACCESS  read-only
   STATUS      current
   DESCRIPTION
      "Path: vpnBridgeGroup.performance.vlan.mibCounters.h24Performance.ifInDropLevelExceeded

       64 bit unsigned wrappable counter."
   ::= {pr1646v2BgriMVVlanMCH24PEntry 335544320}

pr1646v2BgriMVVlanMCH24PInDropNoMac OBJECT-TYPE
   SYNTAX      Counter64
   MAX-ACCESS  read-only
   STATUS      current
   DESCRIPTION
      "Path: vpnBridgeGroup.performance.vlan.mibCounters.h24Performance.fInDiscardsNoMacFit

       64 bit unsigned wrappable counter."
   ::= {pr1646v2BgriMVVlanMCH24PEntry 301989888}

pr1646v2BgriMVVlanMCH24PInDropNUCast OBJECT-TYPE
   SYNTAX      Counter64
   MAX-ACCESS  read-only
   STATUS      current
   DESCRIPTION
      "Path: vpnBridgeGroup.performance.vlan.mibCounters.h24Performance.fInDiscardsNUCast

       64 bit unsigned wrappable counter."
   ::= {pr1646v2BgriMVVlanMCH24PEntry 318767104}

pr1646v2BgriMVVlanMCH24PInDropFilter OBJECT-TYPE
   SYNTAX      Counter64
   MAX-ACCESS  read-only
   STATUS      current
   DESCRIPTION
      "Path: vpnBridgeGroup.performance.vlan.mibCounters.h24Performance.fInDiscardsFilter

       64 bit unsigned wrappable counter."
   ::= {pr1646v2BgriMVVlanMCH24PEntry 385875968}

pr1646v2BgriMVVlanMCH24PIfInBandwidth OBJECT-TYPE
   SYNTAX      Integer32
   MAX-ACCESS  read-only
   STATUS      current
   DESCRIPTION
      "Path: vpnBridgeGroup.performance.vlan.mibCounters.h24Performance.ifInBandwidth

       unit name = bps
       formula = 8 * ; 8 /"
   ::= {pr1646v2BgriMVVlanMCH24PEntry 268435456}

pr1646v2BgriMVVlanMCH24PIfOutOctets OBJECT-TYPE
   SYNTAX      Counter64
   MAX-ACCESS  read-only
   STATUS      current
   DESCRIPTION
      "Path: vpnBridgeGroup.performance.vlan.mibCounters.h24Performance.ifOutOctets

       64 bit unsigned wrappable counter."
   ::= {pr1646v2BgriMVVlanMCH24PEntry 167772160}

pr1646v2BgriMVVlanMCH24PIfOutUCPkts OBJECT-TYPE
   SYNTAX      Counter64
   MAX-ACCESS  read-only
   STATUS      current
   DESCRIPTION
      "Path: vpnBridgeGroup.performance.vlan.mibCounters.h24Performance.ifOutUcastPkts

       64 bit unsigned wrappable counter."
   ::= {pr1646v2BgriMVVlanMCH24PEntry 184549376}

pr1646v2BgriMVVlanMCH24PIfOutNUCPkts OBJECT-TYPE
   SYNTAX      Counter64
   MAX-ACCESS  read-only
   STATUS      current
   DESCRIPTION
      "Path: vpnBridgeGroup.performance.vlan.mibCounters.h24Performance.ifOutNUcastPkts

       64 bit unsigned wrappable counter."
   ::= {pr1646v2BgriMVVlanMCH24PEntry 201326592}

pr1646v2BgriMVVlanMCH24PIfOutBCPkts OBJECT-TYPE
   SYNTAX      Counter64
   MAX-ACCESS  read-only
   STATUS      current
   DESCRIPTION
      "Path: vpnBridgeGroup.performance.vlan.mibCounters.h24Performance.ifOutBcastPkts

       64 bit unsigned wrappable counter."
   ::= {pr1646v2BgriMVVlanMCH24PEntry 452984832}

pr1646v2BgriMVVlanMCH24PIfOutMCPkts OBJECT-TYPE
   SYNTAX      Counter64
   MAX-ACCESS  read-only
   STATUS      current
   DESCRIPTION
      "Path: vpnBridgeGroup.performance.vlan.mibCounters.h24Performance.ifOutMcastPkts

       64 bit unsigned wrappable counter."
   ::= {pr1646v2BgriMVVlanMCH24PEntry 469762048}

pr1646v2BgriMVVlanMCH24PIfOutDiscards OBJECT-TYPE
   SYNTAX      Counter64
   MAX-ACCESS  read-only
   STATUS      current
   DESCRIPTION
      "Path: vpnBridgeGroup.performance.vlan.mibCounters.h24Performance.ifOutDiscards

       64 bit unsigned wrappable counter."
   ::= {pr1646v2BgriMVVlanMCH24PEntry 218103808}

pr1646v2BgriMVVlanMCH24PIfOutErrors OBJECT-TYPE
   SYNTAX      Counter64
   MAX-ACCESS  read-only
   STATUS      current
   DESCRIPTION
      "Path: vpnBridgeGroup.performance.vlan.mibCounters.h24Performance.ifOutErrors

       64 bit unsigned wrappable counter."
   ::= {pr1646v2BgriMVVlanMCH24PEntry 234881024}

pr1646v2BgriMVVlanMCH24POutDropEx OBJECT-TYPE
   SYNTAX      Counter64
   MAX-ACCESS  read-only
   STATUS      current
   DESCRIPTION
      "Path: vpnBridgeGroup.performance.vlan.mibCounters.h24Performance.ifOutDropLevelExceeded

       64 bit unsigned wrappable counter."
   ::= {pr1646v2BgriMVVlanMCH24PEntry 352321536}

pr1646v2BgriMVVlanMCH24POutDropNoArp OBJECT-TYPE
   SYNTAX      Counter64
   MAX-ACCESS  read-only
   STATUS      current
   DESCRIPTION
      "Path: vpnBridgeGroup.performance.vlan.mibCounters.h24Performance.ifOutDiscardsNoArp

       64 bit unsigned wrappable counter."
   ::= {pr1646v2BgriMVVlanMCH24PEntry 369098752}

pr1646v2BgriMVVlanMCH24POutDropFilter OBJECT-TYPE
   SYNTAX      Counter64
   MAX-ACCESS  read-only
   STATUS      current
   DESCRIPTION
      "Path: vpnBridgeGroup.performance.vlan.mibCounters.h24Performance.ifOutDiscardsFilter

       64 bit unsigned wrappable counter."
   ::= {pr1646v2BgriMVVlanMCH24PEntry 402653184}

pr1646v2BgriMVVlanMCH24PIfOutBandwidth OBJECT-TYPE
   SYNTAX      Integer32
   MAX-ACCESS  read-only
   STATUS      current
   DESCRIPTION
      "Path: vpnBridgeGroup.performance.vlan.mibCounters.h24Performance.ifOutBandwidth

       unit name = bps
       formula = 8 * ; 8 /"
   ::= {pr1646v2BgriMVVlanMCH24PEntry 285212672}

pr1646v2BgriMVVlanMCH24PIfErrSec OBJECT-TYPE
   SYNTAX      Counter32
   MAX-ACCESS  read-only
   STATUS      current
   DESCRIPTION
      "Path: vpnBridgeGroup.performance.vlan.mibCounters.h24Performance.ifErrSec

       32 bit unsigned wrappable counter."
   ::= {pr1646v2BgriMVVlanMCH24PEntry 251658240}

pr1646v2BgriMVVlanMCD7P OBJECT-TYPE
   SYNTAX      SEQUENCE OF Pr1646v2BgriMVVlanMCD7PEntry
   MAX-ACCESS  not-accessible
   STATUS      current
   DESCRIPTION
      ""
   ::= {pr1646v2BgriMVVlan 41680896}

pr1646v2BgriMVVlanMCD7PEntry OBJECT-TYPE
   SYNTAX      Pr1646v2BgriMVVlanMCD7PEntry
   MAX-ACCESS  not-accessible
   STATUS      current
   DESCRIPTION
      ""
   INDEX      { pr1646v2BgriMVVlanMCD7PGlobalIx,
                pr1646v2BgriMVVlanTableIx,
                pr1646v2BgriMVVlanMCD7PTableIx }
   ::= {pr1646v2BgriMVVlanMCD7P 1}

Pr1646v2BgriMVVlanMCD7PEntry ::=
   SEQUENCE
      {
      pr1646v2BgriMVVlanMCD7PGlobalIx
         GlobalIndex,
      pr1646v2BgriMVVlanMCD7PTableIx
         TableIndex,
      pr1646v2BgriMVVlanMCD7PSysUpTime
         TimeTicks,
      pr1646v2BgriMVVlanMCD7PIfUpTime
         TimeTicks,
      pr1646v2BgriMVVlanMCD7PIfStatChanges
         Counter32,
      pr1646v2BgriMVVlanMCD7PIfInOctets
         Counter64,
      pr1646v2BgriMVVlanMCD7PIfInUCPkts
         Counter64,
      pr1646v2BgriMVVlanMCD7PIfInNUCPkts
         Counter64,
      pr1646v2BgriMVVlanMCD7PIfInBCPkts
         Counter64,
      pr1646v2BgriMVVlanMCD7PIfInMCPkts
         Counter64,
      pr1646v2BgriMVVlanMCD7PIfInDiscards
         Counter64,
      pr1646v2BgriMVVlanMCD7PIfInErrors
         Counter64,
      pr1646v2BgriMVVlanMCD7PIfInUnkwn
         Counter64,
      pr1646v2BgriMVVlanMCD7PInDropEx
         Counter64,
      pr1646v2BgriMVVlanMCD7PInDropNoMac
         Counter64,
      pr1646v2BgriMVVlanMCD7PInDropNUCast
         Counter64,
      pr1646v2BgriMVVlanMCD7PInDropFilter
         Counter64,
      pr1646v2BgriMVVlanMCD7PIfInBandwidth
         Integer32,
      pr1646v2BgriMVVlanMCD7PIfOutOctets
         Counter64,
      pr1646v2BgriMVVlanMCD7PIfOutUCPkts
         Counter64,
      pr1646v2BgriMVVlanMCD7PIfOutNUCPkts
         Counter64,
      pr1646v2BgriMVVlanMCD7PIfOutBCPkts
         Counter64,
      pr1646v2BgriMVVlanMCD7PIfOutMCPkts
         Counter64,
      pr1646v2BgriMVVlanMCD7PIfOutDiscards
         Counter64,
      pr1646v2BgriMVVlanMCD7PIfOutErrors
         Counter64,
      pr1646v2BgriMVVlanMCD7POutDropEx
         Counter64,
      pr1646v2BgriMVVlanMCD7POutDropNoArp
         Counter64,
      pr1646v2BgriMVVlanMCD7POutDropFilter
         Counter64,
      pr1646v2BgriMVVlanMCD7PIfOutBandwidth
         Integer32,
      pr1646v2BgriMVVlanMCD7PIfErrSec
         Counter32
      }

pr1646v2BgriMVVlanMCD7PGlobalIx OBJECT-TYPE
   SYNTAX      GlobalIndex
   MAX-ACCESS  not-accessible
   STATUS      current
   DESCRIPTION
      "The value of the tlsCntTreeGlobalIndex of the MANAGED OBJECT."
   ::= {pr1646v2BgriMVVlanMCD7PEntry 10}

pr1646v2BgriMVVlanMCD7PTableIx OBJECT-TYPE
   SYNTAX      TableIndex
   MAX-ACCESS  not-accessible
   STATUS      current
   DESCRIPTION
      ""
   ::= {pr1646v2BgriMVVlanMCD7PEntry 11}

pr1646v2BgriMVVlanMCD7PSysUpTime OBJECT-TYPE
   SYNTAX      TimeTicks
   MAX-ACCESS  read-only
   STATUS      current
   DESCRIPTION
      "Path: vpnBridgeGroup.performance.vlan.mibCounters.d7Performance.sysUpTime

       Time in centi-second."
   ::= {pr1646v2BgriMVVlanMCD7PEntry 16777216}

pr1646v2BgriMVVlanMCD7PIfUpTime OBJECT-TYPE
   SYNTAX      TimeTicks
   MAX-ACCESS  read-only
   STATUS      current
   DESCRIPTION
      "Path: vpnBridgeGroup.performance.vlan.mibCounters.d7Performance.ifUpTime

       Time in centi-second."
   ::= {pr1646v2BgriMVVlanMCD7PEntry 33554432}

pr1646v2BgriMVVlanMCD7PIfStatChanges OBJECT-TYPE
   SYNTAX      Counter32
   MAX-ACCESS  read-only
   STATUS      current
   DESCRIPTION
      "Path: vpnBridgeGroup.performance.vlan.mibCounters.d7Performance.ifStatusChanges

       32 bit unsigned wrappable counter."
   ::= {pr1646v2BgriMVVlanMCD7PEntry 50331648}

pr1646v2BgriMVVlanMCD7PIfInOctets OBJECT-TYPE
   SYNTAX      Counter64
   MAX-ACCESS  read-only
   STATUS      current
   DESCRIPTION
      "Path: vpnBridgeGroup.performance.vlan.mibCounters.d7Performance.ifInOctets

       64 bit unsigned wrappable counter."
   ::= {pr1646v2BgriMVVlanMCD7PEntry 67108864}

pr1646v2BgriMVVlanMCD7PIfInUCPkts OBJECT-TYPE
   SYNTAX      Counter64
   MAX-ACCESS  read-only
   STATUS      current
   DESCRIPTION
      "Path: vpnBridgeGroup.performance.vlan.mibCounters.d7Performance.ifInUcastPkts

       64 bit unsigned wrappable counter."
   ::= {pr1646v2BgriMVVlanMCD7PEntry 83886080}

pr1646v2BgriMVVlanMCD7PIfInNUCPkts OBJECT-TYPE
   SYNTAX      Counter64
   MAX-ACCESS  read-only
   STATUS      current
   DESCRIPTION
      "Path: vpnBridgeGroup.performance.vlan.mibCounters.d7Performance.ifInNUcastPkts

       64 bit unsigned wrappable counter."
   ::= {pr1646v2BgriMVVlanMCD7PEntry 100663296}

pr1646v2BgriMVVlanMCD7PIfInBCPkts OBJECT-TYPE
   SYNTAX      Counter64
   MAX-ACCESS  read-only
   STATUS      current
   DESCRIPTION
      "Path: vpnBridgeGroup.performance.vlan.mibCounters.d7Performance.ifInBcastPkts

       64 bit unsigned wrappable counter."
   ::= {pr1646v2BgriMVVlanMCD7PEntry 419430400}

pr1646v2BgriMVVlanMCD7PIfInMCPkts OBJECT-TYPE
   SYNTAX      Counter64
   MAX-ACCESS  read-only
   STATUS      current
   DESCRIPTION
      "Path: vpnBridgeGroup.performance.vlan.mibCounters.d7Performance.ifInMcastPkts

       64 bit unsigned wrappable counter."
   ::= {pr1646v2BgriMVVlanMCD7PEntry 436207616}

pr1646v2BgriMVVlanMCD7PIfInDiscards OBJECT-TYPE
   SYNTAX      Counter64
   MAX-ACCESS  read-only
   STATUS      current
   DESCRIPTION
      "Path: vpnBridgeGroup.performance.vlan.mibCounters.d7Performance.ifInDiscards

       64 bit unsigned wrappable counter."
   ::= {pr1646v2BgriMVVlanMCD7PEntry 117440512}

pr1646v2BgriMVVlanMCD7PIfInErrors OBJECT-TYPE
   SYNTAX      Counter64
   MAX-ACCESS  read-only
   STATUS      current
   DESCRIPTION
      "Path: vpnBridgeGroup.performance.vlan.mibCounters.d7Performance.ifInErrors

       64 bit unsigned wrappable counter."
   ::= {pr1646v2BgriMVVlanMCD7PEntry 134217728}

pr1646v2BgriMVVlanMCD7PIfInUnkwn OBJECT-TYPE
   SYNTAX      Counter64
   MAX-ACCESS  read-only
   STATUS      current
   DESCRIPTION
      "Path: vpnBridgeGroup.performance.vlan.mibCounters.d7Performance.ifInUnknownProtos

       64 bit unsigned wrappable counter."
   ::= {pr1646v2BgriMVVlanMCD7PEntry 150994944}

pr1646v2BgriMVVlanMCD7PInDropEx OBJECT-TYPE
   SYNTAX      Counter64
   MAX-ACCESS  read-only
   STATUS      current
   DESCRIPTION
      "Path: vpnBridgeGroup.performance.vlan.mibCounters.d7Performance.ifInDropLevelExceeded

       64 bit unsigned wrappable counter."
   ::= {pr1646v2BgriMVVlanMCD7PEntry 335544320}

pr1646v2BgriMVVlanMCD7PInDropNoMac OBJECT-TYPE
   SYNTAX      Counter64
   MAX-ACCESS  read-only
   STATUS      current
   DESCRIPTION
      "Path: vpnBridgeGroup.performance.vlan.mibCounters.d7Performance.fInDiscardsNoMacFit

       64 bit unsigned wrappable counter."
   ::= {pr1646v2BgriMVVlanMCD7PEntry 301989888}

pr1646v2BgriMVVlanMCD7PInDropNUCast OBJECT-TYPE
   SYNTAX      Counter64
   MAX-ACCESS  read-only
   STATUS      current
   DESCRIPTION
      "Path: vpnBridgeGroup.performance.vlan.mibCounters.d7Performance.fInDiscardsNUCast

       64 bit unsigned wrappable counter."
   ::= {pr1646v2BgriMVVlanMCD7PEntry 318767104}

pr1646v2BgriMVVlanMCD7PInDropFilter OBJECT-TYPE
   SYNTAX      Counter64
   MAX-ACCESS  read-only
   STATUS      current
   DESCRIPTION
      "Path: vpnBridgeGroup.performance.vlan.mibCounters.d7Performance.fInDiscardsFilter

       64 bit unsigned wrappable counter."
   ::= {pr1646v2BgriMVVlanMCD7PEntry 385875968}

pr1646v2BgriMVVlanMCD7PIfInBandwidth OBJECT-TYPE
   SYNTAX      Integer32
   MAX-ACCESS  read-only
   STATUS      current
   DESCRIPTION
      "Path: vpnBridgeGroup.performance.vlan.mibCounters.d7Performance.ifInBandwidth

       unit name = bps
       formula = 8 * ; 8 /"
   ::= {pr1646v2BgriMVVlanMCD7PEntry 268435456}

pr1646v2BgriMVVlanMCD7PIfOutOctets OBJECT-TYPE
   SYNTAX      Counter64
   MAX-ACCESS  read-only
   STATUS      current
   DESCRIPTION
      "Path: vpnBridgeGroup.performance.vlan.mibCounters.d7Performance.ifOutOctets

       64 bit unsigned wrappable counter."
   ::= {pr1646v2BgriMVVlanMCD7PEntry 167772160}

pr1646v2BgriMVVlanMCD7PIfOutUCPkts OBJECT-TYPE
   SYNTAX      Counter64
   MAX-ACCESS  read-only
   STATUS      current
   DESCRIPTION
      "Path: vpnBridgeGroup.performance.vlan.mibCounters.d7Performance.ifOutUcastPkts

       64 bit unsigned wrappable counter."
   ::= {pr1646v2BgriMVVlanMCD7PEntry 184549376}

pr1646v2BgriMVVlanMCD7PIfOutNUCPkts OBJECT-TYPE
   SYNTAX      Counter64
   MAX-ACCESS  read-only
   STATUS      current
   DESCRIPTION
      "Path: vpnBridgeGroup.performance.vlan.mibCounters.d7Performance.ifOutNUcastPkts

       64 bit unsigned wrappable counter."
   ::= {pr1646v2BgriMVVlanMCD7PEntry 201326592}

pr1646v2BgriMVVlanMCD7PIfOutBCPkts OBJECT-TYPE
   SYNTAX      Counter64
   MAX-ACCESS  read-only
   STATUS      current
   DESCRIPTION
      "Path: vpnBridgeGroup.performance.vlan.mibCounters.d7Performance.ifOutBcastPkts

       64 bit unsigned wrappable counter."
   ::= {pr1646v2BgriMVVlanMCD7PEntry 452984832}

pr1646v2BgriMVVlanMCD7PIfOutMCPkts OBJECT-TYPE
   SYNTAX      Counter64
   MAX-ACCESS  read-only
   STATUS      current
   DESCRIPTION
      "Path: vpnBridgeGroup.performance.vlan.mibCounters.d7Performance.ifOutMcastPkts

       64 bit unsigned wrappable counter."
   ::= {pr1646v2BgriMVVlanMCD7PEntry 469762048}

pr1646v2BgriMVVlanMCD7PIfOutDiscards OBJECT-TYPE
   SYNTAX      Counter64
   MAX-ACCESS  read-only
   STATUS      current
   DESCRIPTION
      "Path: vpnBridgeGroup.performance.vlan.mibCounters.d7Performance.ifOutDiscards

       64 bit unsigned wrappable counter."
   ::= {pr1646v2BgriMVVlanMCD7PEntry 218103808}

pr1646v2BgriMVVlanMCD7PIfOutErrors OBJECT-TYPE
   SYNTAX      Counter64
   MAX-ACCESS  read-only
   STATUS      current
   DESCRIPTION
      "Path: vpnBridgeGroup.performance.vlan.mibCounters.d7Performance.ifOutErrors

       64 bit unsigned wrappable counter."
   ::= {pr1646v2BgriMVVlanMCD7PEntry 234881024}

pr1646v2BgriMVVlanMCD7POutDropEx OBJECT-TYPE
   SYNTAX      Counter64
   MAX-ACCESS  read-only
   STATUS      current
   DESCRIPTION
      "Path: vpnBridgeGroup.performance.vlan.mibCounters.d7Performance.ifOutDropLevelExceeded

       64 bit unsigned wrappable counter."
   ::= {pr1646v2BgriMVVlanMCD7PEntry 352321536}

pr1646v2BgriMVVlanMCD7POutDropNoArp OBJECT-TYPE
   SYNTAX      Counter64
   MAX-ACCESS  read-only
   STATUS      current
   DESCRIPTION
      "Path: vpnBridgeGroup.performance.vlan.mibCounters.d7Performance.ifOutDiscardsNoArp

       64 bit unsigned wrappable counter."
   ::= {pr1646v2BgriMVVlanMCD7PEntry 369098752}

pr1646v2BgriMVVlanMCD7POutDropFilter OBJECT-TYPE
   SYNTAX      Counter64
   MAX-ACCESS  read-only
   STATUS      current
   DESCRIPTION
      "Path: vpnBridgeGroup.performance.vlan.mibCounters.d7Performance.ifOutDiscardsFilter

       64 bit unsigned wrappable counter."
   ::= {pr1646v2BgriMVVlanMCD7PEntry 402653184}

pr1646v2BgriMVVlanMCD7PIfOutBandwidth OBJECT-TYPE
   SYNTAX      Integer32
   MAX-ACCESS  read-only
   STATUS      current
   DESCRIPTION
      "Path: vpnBridgeGroup.performance.vlan.mibCounters.d7Performance.ifOutBandwidth

       unit name = bps
       formula = 8 * ; 8 /"
   ::= {pr1646v2BgriMVVlanMCD7PEntry 285212672}

pr1646v2BgriMVVlanMCD7PIfErrSec OBJECT-TYPE
   SYNTAX      Counter32
   MAX-ACCESS  read-only
   STATUS      current
   DESCRIPTION
      "Path: vpnBridgeGroup.performance.vlan.mibCounters.d7Performance.ifErrSec

       32 bit unsigned wrappable counter."
   ::= {pr1646v2BgriMVVlanMCD7PEntry 251658240}


pr1646v2BgriMVPPPoE OBJECT IDENTIFIER ::= {pr1646v2BgriMV 82}

pr1646v2BgriMVPPPoESSCTable OBJECT-TYPE
   SYNTAX      SEQUENCE OF Pr1646v2BgriMVPPPoEEntry
   MAX-ACCESS  not-accessible
   STATUS      current
   DESCRIPTION
      ""
   ::= {pr1646v2BgriMVPPPoE 1}

pr1646v2BgriMVPPPoEEntry OBJECT-TYPE
   SYNTAX      Pr1646v2BgriMVPPPoEEntry
   MAX-ACCESS  not-accessible
   STATUS      current
   DESCRIPTION
      ""
   INDEX      { pr1646v2BgriMVPPPoEGlobalIx,
                pr1646v2BgriMVPPPoETableIx }
   ::= {pr1646v2BgriMVPPPoESSCTable 1}

Pr1646v2BgriMVPPPoEEntry ::=
   SEQUENCE
      {
      pr1646v2BgriMVPPPoEGlobalIx
         GlobalIndex,
      pr1646v2BgriMVPPPoETableIx
         TableIndex,
      pr1646v2BgriMVPPPoEName
         DisplayString,
      pr1646v2BgriMVPPPoEMCInOctets
         Counter64,
      pr1646v2BgriMVPPPoEMCInUcast
         Counter64,
      pr1646v2BgriMVPPPoEMCInNUcastPkts
         Counter64,
      pr1646v2BgriMVPPPoEMCInBcastPkts
         Counter64,
      pr1646v2BgriMVPPPoEMCInMcastPkts
         Counter64,
      pr1646v2BgriMVPPPoEMCInDiscards
         Counter64,
      pr1646v2BgriMVPPPoEMCInErrors
         Counter64,
      pr1646v2BgriMVPPPoEMCInUnknownProtos
         Counter64,
      pr1646v2BgriMVPPPoEMCInDropEx
         Counter64,
      pr1646v2BgriMVPPPoEMCInDropNoMac
         Counter64,
      pr1646v2BgriMVPPPoEMCInDropNUCast
         Counter64,
      pr1646v2BgriMVPPPoEMCInDropFilter
         Counter64,
      pr1646v2BgriMVPPPoEMCInBandwidth15sec
         Integer32,
      pr1646v2BgriMVPPPoEMCInBandwidth30sec
         Integer32,
      pr1646v2BgriMVPPPoEMCInBandwidth1min
         Integer32,
      pr1646v2BgriMVPPPoEMCInBandwidth2min
         Integer32,
      pr1646v2BgriMVPPPoEMCInBandwidth5min
         Integer32,
      pr1646v2BgriMVPPPoEMCOutOctets
         Counter64,
      pr1646v2BgriMVPPPoEMCOutUcastPkts
         Counter64,
      pr1646v2BgriMVPPPoEMCOutNUcastPkts
         Counter64,
      pr1646v2BgriMVPPPoEMCOutBcastPkts
         Counter64,
      pr1646v2BgriMVPPPoEMCOutMcastPkts
         Counter64,
      pr1646v2BgriMVPPPoEMCOutDiscards
         Counter64,
      pr1646v2BgriMVPPPoEMCOutErrors
         Counter64,
      pr1646v2BgriMVPPPoEMCOutQLen
         Counter32,
      pr1646v2BgriMVPPPoEMCOutDropEx
         Counter64,
      pr1646v2BgriMVPPPoEMCOutDropNoArp
         Counter64,
      pr1646v2BgriMVPPPoEMCOutDropFilter
         Counter64,
      pr1646v2BgriMVPPPoEMCOutBandwidth15sec
         Integer32,
      pr1646v2BgriMVPPPoEMCOutBandwidth30sec
         Integer32,
      pr1646v2BgriMVPPPoEMCOutBandwidth1min
         Integer32,
      pr1646v2BgriMVPPPoEMCOutBandwidth2min
         Integer32,
      pr1646v2BgriMVPPPoEMCOutBandwidth5min
         Integer32,
      pr1646v2BgriMVPPPoEPppLinkMonitoringRequestsSent
         Gauge32,
      pr1646v2BgriMVPPPoEPppLinkMonitoringRepliesRcvd
         Gauge32,
      pr1646v2BgriMVPPPoEPppLinkMonitoringRequestsRcvd
         Gauge32,
      pr1646v2BgriMVPPPoEPppLinkMonitoringRepliesSent
         Gauge32
      }

pr1646v2BgriMVPPPoEGlobalIx OBJECT-TYPE
   SYNTAX      GlobalIndex
   MAX-ACCESS  not-accessible
   STATUS      current
   DESCRIPTION
      "The value of the tlsCntTreeGlobalIndex of the MANAGED OBJECT."
   ::= {pr1646v2BgriMVPPPoEEntry 10}

pr1646v2BgriMVPPPoETableIx OBJECT-TYPE
   SYNTAX      TableIndex
   MAX-ACCESS  not-accessible
   STATUS      current
   DESCRIPTION
      ""
   ::= {pr1646v2BgriMVPPPoEEntry 11}

pr1646v2BgriMVPPPoEName OBJECT-TYPE
   SYNTAX      DisplayString
   MAX-ACCESS  read-only
   STATUS      current
   DESCRIPTION
      "Path: vpnBridgeGroup.performance.pppoEClient.name"
   ::= {pr1646v2BgriMVPPPoEEntry 16777216}

pr1646v2BgriMVPPPoEMCInOctets OBJECT-TYPE
   SYNTAX      Counter64
   MAX-ACCESS  read-only
   STATUS      current
   DESCRIPTION
      "Path: vpnBridgeGroup.performance.pppoEClient.mibCounters.ifInOctets

       64 bit unsigned wrappable counter."
   ::= {pr1646v2BgriMVPPPoEEntry 40697856}

pr1646v2BgriMVPPPoEMCInUcast OBJECT-TYPE
   SYNTAX      Counter64
   MAX-ACCESS  read-only
   STATUS      current
   DESCRIPTION
      "Path: vpnBridgeGroup.performance.pppoEClient.mibCounters.ifInUcastPkts

       64 bit unsigned wrappable counter."
   ::= {pr1646v2BgriMVPPPoEEntry 40763392}

pr1646v2BgriMVPPPoEMCInNUcastPkts OBJECT-TYPE
   SYNTAX      Counter64
   MAX-ACCESS  read-only
   STATUS      current
   DESCRIPTION
      "Path: vpnBridgeGroup.performance.pppoEClient.mibCounters.ifInNUcastPkts

       64 bit unsigned wrappable counter."
   ::= {pr1646v2BgriMVPPPoEEntry 40828928}

pr1646v2BgriMVPPPoEMCInBcastPkts OBJECT-TYPE
   SYNTAX      Counter64
   MAX-ACCESS  read-only
   STATUS      current
   DESCRIPTION
      "Path: vpnBridgeGroup.performance.pppoEClient.mibCounters.ifInBcastPkts

       64 bit unsigned wrappable counter."
   ::= {pr1646v2BgriMVPPPoEEntry 47382528}

pr1646v2BgriMVPPPoEMCInMcastPkts OBJECT-TYPE
   SYNTAX      Counter64
   MAX-ACCESS  read-only
   STATUS      current
   DESCRIPTION
      "Path: vpnBridgeGroup.performance.pppoEClient.mibCounters.ifInMcastPkts

       64 bit unsigned wrappable counter."
   ::= {pr1646v2BgriMVPPPoEEntry 48037888}

pr1646v2BgriMVPPPoEMCInDiscards OBJECT-TYPE
   SYNTAX      Counter64
   MAX-ACCESS  read-only
   STATUS      current
   DESCRIPTION
      "Path: vpnBridgeGroup.performance.pppoEClient.mibCounters.ifInDiscards

       64 bit unsigned wrappable counter."
   ::= {pr1646v2BgriMVPPPoEEntry 40894464}

pr1646v2BgriMVPPPoEMCInErrors OBJECT-TYPE
   SYNTAX      Counter64
   MAX-ACCESS  read-only
   STATUS      current
   DESCRIPTION
      "Path: vpnBridgeGroup.performance.pppoEClient.mibCounters.ifInErrors

       64 bit unsigned wrappable counter."
   ::= {pr1646v2BgriMVPPPoEEntry 40960000}

pr1646v2BgriMVPPPoEMCInUnknownProtos OBJECT-TYPE
   SYNTAX      Counter64
   MAX-ACCESS  read-only
   STATUS      current
   DESCRIPTION
      "Path: vpnBridgeGroup.performance.pppoEClient.mibCounters.ifInUnknownProtos

       64 bit unsigned wrappable counter."
   ::= {pr1646v2BgriMVPPPoEEntry 41025536}

pr1646v2BgriMVPPPoEMCInDropEx OBJECT-TYPE
   SYNTAX      Counter64
   MAX-ACCESS  read-only
   STATUS      current
   DESCRIPTION
      "Path: vpnBridgeGroup.performance.pppoEClient.mibCounters.ifInDropLevelExceeded

       64 bit unsigned wrappable counter."
   ::= {pr1646v2BgriMVPPPoEEntry 42074112}

pr1646v2BgriMVPPPoEMCInDropNoMac OBJECT-TYPE
   SYNTAX      Counter64
   MAX-ACCESS  read-only
   STATUS      current
   DESCRIPTION
      "Path: vpnBridgeGroup.performance.pppoEClient.mibCounters.ifInDiscardsNoMacFit

       64 bit unsigned wrappable counter."
   ::= {pr1646v2BgriMVPPPoEEntry 42270720}

pr1646v2BgriMVPPPoEMCInDropNUCast OBJECT-TYPE
   SYNTAX      Counter64
   MAX-ACCESS  read-only
   STATUS      current
   DESCRIPTION
      "Path: vpnBridgeGroup.performance.pppoEClient.mibCounters.ifInDiscardsNUCast

       64 bit unsigned wrappable counter."
   ::= {pr1646v2BgriMVPPPoEEntry 42467328}

pr1646v2BgriMVPPPoEMCInDropFilter OBJECT-TYPE
   SYNTAX      Counter64
   MAX-ACCESS  read-only
   STATUS      current
   DESCRIPTION
      "Path: vpnBridgeGroup.performance.pppoEClient.mibCounters.ifInDiscardsFilter

       64 bit unsigned wrappable counter."
   ::= {pr1646v2BgriMVPPPoEEntry 42532864}

pr1646v2BgriMVPPPoEMCInBandwidth15sec OBJECT-TYPE
   SYNTAX      Integer32
   MAX-ACCESS  read-only
   STATUS      current
   DESCRIPTION
      "Path: vpnBridgeGroup.performance.pppoEClient.mibCounters.ifInBandwidth.15sec

       unit name = bps
       formula = 8 * ; 8 /"
   ::= {pr1646v2BgriMVPPPoEEntry 45417728}

pr1646v2BgriMVPPPoEMCInBandwidth30sec OBJECT-TYPE
   SYNTAX      Integer32
   MAX-ACCESS  read-only
   STATUS      current
   DESCRIPTION
      "Path: vpnBridgeGroup.performance.pppoEClient.mibCounters.ifInBandwidth.30sec

       unit name = bps
       formula = 8 * ; 8 /"
   ::= {pr1646v2BgriMVPPPoEEntry 45419008}

pr1646v2BgriMVPPPoEMCInBandwidth1min OBJECT-TYPE
   SYNTAX      Integer32
   MAX-ACCESS  read-only
   STATUS      current
   DESCRIPTION
      "Path: vpnBridgeGroup.performance.pppoEClient.mibCounters.ifInBandwidth.1min

       unit name = bps
       formula = 8 * ; 8 /"
   ::= {pr1646v2BgriMVPPPoEEntry 45421568}

pr1646v2BgriMVPPPoEMCInBandwidth2min OBJECT-TYPE
   SYNTAX      Integer32
   MAX-ACCESS  read-only
   STATUS      current
   DESCRIPTION
      "Path: vpnBridgeGroup.performance.pppoEClient.mibCounters.ifInBandwidth.2min

       unit name = bps
       formula = 8 * ; 8 /"
   ::= {pr1646v2BgriMVPPPoEEntry 45426688}

pr1646v2BgriMVPPPoEMCInBandwidth5min OBJECT-TYPE
   SYNTAX      Integer32
   MAX-ACCESS  read-only
   STATUS      current
   DESCRIPTION
      "Path: vpnBridgeGroup.performance.pppoEClient.mibCounters.ifInBandwidth.5min

       unit name = bps
       formula = 8 * ; 8 /"
   ::= {pr1646v2BgriMVPPPoEEntry 45442048}

pr1646v2BgriMVPPPoEMCOutOctets OBJECT-TYPE
   SYNTAX      Counter64
   MAX-ACCESS  read-only
   STATUS      current
   DESCRIPTION
      "Path: vpnBridgeGroup.performance.pppoEClient.mibCounters.ifOutOctets

       64 bit unsigned wrappable counter."
   ::= {pr1646v2BgriMVPPPoEEntry 41091072}

pr1646v2BgriMVPPPoEMCOutUcastPkts OBJECT-TYPE
   SYNTAX      Counter64
   MAX-ACCESS  read-only
   STATUS      current
   DESCRIPTION
      "Path: vpnBridgeGroup.performance.pppoEClient.mibCounters.ifOutUcastPkts

       64 bit unsigned wrappable counter."
   ::= {pr1646v2BgriMVPPPoEEntry 41156608}

pr1646v2BgriMVPPPoEMCOutNUcastPkts OBJECT-TYPE
   SYNTAX      Counter64
   MAX-ACCESS  read-only
   STATUS      current
   DESCRIPTION
      "Path: vpnBridgeGroup.performance.pppoEClient.mibCounters.ifOutNUcastPkts

       64 bit unsigned wrappable counter."
   ::= {pr1646v2BgriMVPPPoEEntry 41222144}

pr1646v2BgriMVPPPoEMCOutBcastPkts OBJECT-TYPE
   SYNTAX      Counter64
   MAX-ACCESS  read-only
   STATUS      current
   DESCRIPTION
      "Path: vpnBridgeGroup.performance.pppoEClient.mibCounters.ifOutBcastPkts

       64 bit unsigned wrappable counter."
   ::= {pr1646v2BgriMVPPPoEEntry 47775744}

pr1646v2BgriMVPPPoEMCOutMcastPkts OBJECT-TYPE
   SYNTAX      Counter64
   MAX-ACCESS  read-only
   STATUS      current
   DESCRIPTION
      "Path: vpnBridgeGroup.performance.pppoEClient.mibCounters.ifOutMcastPkts

       64 bit unsigned wrappable counter."
   ::= {pr1646v2BgriMVPPPoEEntry 48431104}

pr1646v2BgriMVPPPoEMCOutDiscards OBJECT-TYPE
   SYNTAX      Counter64
   MAX-ACCESS  read-only
   STATUS      current
   DESCRIPTION
      "Path: vpnBridgeGroup.performance.pppoEClient.mibCounters.ifOutDiscards

       64 bit unsigned wrappable counter."
   ::= {pr1646v2BgriMVPPPoEEntry 41287680}

pr1646v2BgriMVPPPoEMCOutErrors OBJECT-TYPE
   SYNTAX      Counter64
   MAX-ACCESS  read-only
   STATUS      current
   DESCRIPTION
      "Path: vpnBridgeGroup.performance.pppoEClient.mibCounters.ifOutErrors

       64 bit unsigned wrappable counter."
   ::= {pr1646v2BgriMVPPPoEEntry 41353216}

pr1646v2BgriMVPPPoEMCOutQLen OBJECT-TYPE
   SYNTAX      Counter32
   MAX-ACCESS  read-only
   STATUS      current
   DESCRIPTION
      "Path: vpnBridgeGroup.performance.pppoEClient.mibCounters.ifOutQLen

       32 bit unsigned wrappable counter."
   ::= {pr1646v2BgriMVPPPoEEntry 41418752}

pr1646v2BgriMVPPPoEMCOutDropEx OBJECT-TYPE
   SYNTAX      Counter64
   MAX-ACCESS  read-only
   STATUS      current
   DESCRIPTION
      "Path: vpnBridgeGroup.performance.pppoEClient.mibCounters.ifOutDropLevelExceeded

       64 bit unsigned wrappable counter."
   ::= {pr1646v2BgriMVPPPoEEntry 41484288}

pr1646v2BgriMVPPPoEMCOutDropNoArp OBJECT-TYPE
   SYNTAX      Counter64
   MAX-ACCESS  read-only
   STATUS      current
   DESCRIPTION
      "Path: vpnBridgeGroup.performance.pppoEClient.mibCounters.ifOutDiscardsNoArp

       64 bit unsigned wrappable counter."
   ::= {pr1646v2BgriMVPPPoEEntry 42336256}

pr1646v2BgriMVPPPoEMCOutDropFilter OBJECT-TYPE
   SYNTAX      Counter64
   MAX-ACCESS  read-only
   STATUS      current
   DESCRIPTION
      "Path: vpnBridgeGroup.performance.pppoEClient.mibCounters.ifOutDiscardsFilter

       64 bit unsigned wrappable counter."
   ::= {pr1646v2BgriMVPPPoEEntry 42598400}

pr1646v2BgriMVPPPoEMCOutBandwidth15sec OBJECT-TYPE
   SYNTAX      Integer32
   MAX-ACCESS  read-only
   STATUS      current
   DESCRIPTION
      "Path: vpnBridgeGroup.performance.pppoEClient.mibCounters.ifOutBandwidth.15sec

       unit name = bps
       formula = 8 * ; 8 /"
   ::= {pr1646v2BgriMVPPPoEEntry 45483264}

pr1646v2BgriMVPPPoEMCOutBandwidth30sec OBJECT-TYPE
   SYNTAX      Integer32
   MAX-ACCESS  read-only
   STATUS      current
   DESCRIPTION
      "Path: vpnBridgeGroup.performance.pppoEClient.mibCounters.ifOutBandwidth.30sec

       unit name = bps
       formula = 8 * ; 8 /"
   ::= {pr1646v2BgriMVPPPoEEntry 45484544}

pr1646v2BgriMVPPPoEMCOutBandwidth1min OBJECT-TYPE
   SYNTAX      Integer32
   MAX-ACCESS  read-only
   STATUS      current
   DESCRIPTION
      "Path: vpnBridgeGroup.performance.pppoEClient.mibCounters.ifOutBandwidth.1min

       unit name = bps
       formula = 8 * ; 8 /"
   ::= {pr1646v2BgriMVPPPoEEntry 45487104}

pr1646v2BgriMVPPPoEMCOutBandwidth2min OBJECT-TYPE
   SYNTAX      Integer32
   MAX-ACCESS  read-only
   STATUS      current
   DESCRIPTION
      "Path: vpnBridgeGroup.performance.pppoEClient.mibCounters.ifOutBandwidth.2min

       unit name = bps
       formula = 8 * ; 8 /"
   ::= {pr1646v2BgriMVPPPoEEntry 45492224}

pr1646v2BgriMVPPPoEMCOutBandwidth5min OBJECT-TYPE
   SYNTAX      Integer32
   MAX-ACCESS  read-only
   STATUS      current
   DESCRIPTION
      "Path: vpnBridgeGroup.performance.pppoEClient.mibCounters.ifOutBandwidth.5min

       unit name = bps
       formula = 8 * ; 8 /"
   ::= {pr1646v2BgriMVPPPoEEntry 45507584}

pr1646v2BgriMVPPPoEPppLinkMonitoringRequestsSent OBJECT-TYPE
   SYNTAX      Gauge32
   MAX-ACCESS  read-only
   STATUS      current
   DESCRIPTION
      "Path: vpnBridgeGroup.performance.pppoEClient.ppp.linkMonitoring.requestsSent

       32 bit unsigned gauge value."
   ::= {pr1646v2BgriMVPPPoEEntry 50397440}

pr1646v2BgriMVPPPoEPppLinkMonitoringRepliesRcvd OBJECT-TYPE
   SYNTAX      Gauge32
   MAX-ACCESS  read-only
   STATUS      current
   DESCRIPTION
      "Path: vpnBridgeGroup.performance.pppoEClient.ppp.linkMonitoring.repliesRcvd

       32 bit unsigned gauge value."
   ::= {pr1646v2BgriMVPPPoEEntry 50397696}

pr1646v2BgriMVPPPoEPppLinkMonitoringRequestsRcvd OBJECT-TYPE
   SYNTAX      Gauge32
   MAX-ACCESS  read-only
   STATUS      current
   DESCRIPTION
      "Path: vpnBridgeGroup.performance.pppoEClient.ppp.linkMonitoring.requestsRcvd

       32 bit unsigned gauge value."
   ::= {pr1646v2BgriMVPPPoEEntry 50397952}

pr1646v2BgriMVPPPoEPppLinkMonitoringRepliesSent OBJECT-TYPE
   SYNTAX      Gauge32
   MAX-ACCESS  read-only
   STATUS      current
   DESCRIPTION
      "Path: vpnBridgeGroup.performance.pppoEClient.ppp.linkMonitoring.repliesSent

       32 bit unsigned gauge value."
   ::= {pr1646v2BgriMVPPPoEEntry 50398208}

pr1646v2BgriMVPPPoEMCH2P OBJECT-TYPE
   SYNTAX      SEQUENCE OF Pr1646v2BgriMVPPPoEMCH2PEntry
   MAX-ACCESS  not-accessible
   STATUS      current
   DESCRIPTION
      ""
   ::= {pr1646v2BgriMVPPPoE 41549824}

pr1646v2BgriMVPPPoEMCH2PEntry OBJECT-TYPE
   SYNTAX      Pr1646v2BgriMVPPPoEMCH2PEntry
   MAX-ACCESS  not-accessible
   STATUS      current
   DESCRIPTION
      ""
   INDEX      { pr1646v2BgriMVPPPoEMCH2PGlobalIx,
                pr1646v2BgriMVPPPoETableIx,
                pr1646v2BgriMVPPPoEMCH2PTableIx }
   ::= {pr1646v2BgriMVPPPoEMCH2P 1}

Pr1646v2BgriMVPPPoEMCH2PEntry ::=
   SEQUENCE
      {
      pr1646v2BgriMVPPPoEMCH2PGlobalIx
         GlobalIndex,
      pr1646v2BgriMVPPPoEMCH2PTableIx
         TableIndex,
      pr1646v2BgriMVPPPoEMCH2PSysUpTime
         TimeTicks,
      pr1646v2BgriMVPPPoEMCH2PIfUpTime
         TimeTicks,
      pr1646v2BgriMVPPPoEMCH2PIfStatChanges
         Counter32,
      pr1646v2BgriMVPPPoEMCH2PIfInOctets
         Counter64,
      pr1646v2BgriMVPPPoEMCH2PIfInUCPkts
         Counter64,
      pr1646v2BgriMVPPPoEMCH2PIfInNUCPkts
         Counter64,
      pr1646v2BgriMVPPPoEMCH2PIfInBCPkts
         Counter64,
      pr1646v2BgriMVPPPoEMCH2PIfInMCPkts
         Counter64,
      pr1646v2BgriMVPPPoEMCH2PIfInDiscards
         Counter64,
      pr1646v2BgriMVPPPoEMCH2PIfInErrors
         Counter64,
      pr1646v2BgriMVPPPoEMCH2PIfInUnkwn
         Counter64,
      pr1646v2BgriMVPPPoEMCH2PInDropEx
         Counter64,
      pr1646v2BgriMVPPPoEMCH2PInDropNoMac
         Counter64,
      pr1646v2BgriMVPPPoEMCH2PInDropNUCast
         Counter64,
      pr1646v2BgriMVPPPoEMCH2PInDropFilter
         Counter64,
      pr1646v2BgriMVPPPoEMCH2PIfInBandwidth
         Integer32,
      pr1646v2BgriMVPPPoEMCH2PIfOutOctets
         Counter64,
      pr1646v2BgriMVPPPoEMCH2PIfOutUCPkts
         Counter64,
      pr1646v2BgriMVPPPoEMCH2PIfOutNUCPkts
         Counter64,
      pr1646v2BgriMVPPPoEMCH2PIfOutBCPkts
         Counter64,
      pr1646v2BgriMVPPPoEMCH2PIfOutMCPkts
         Counter64,
      pr1646v2BgriMVPPPoEMCH2PIfOutDiscards
         Counter64,
      pr1646v2BgriMVPPPoEMCH2PIfOutErrors
         Counter64,
      pr1646v2BgriMVPPPoEMCH2POutDropEx
         Counter64,
      pr1646v2BgriMVPPPoEMCH2POutDropNoArp
         Counter64,
      pr1646v2BgriMVPPPoEMCH2POutDropFilter
         Counter64,
      pr1646v2BgriMVPPPoEMCH2PIfOutBandwidth
         Integer32,
      pr1646v2BgriMVPPPoEMCH2PIfErrSec
         Counter32
      }

pr1646v2BgriMVPPPoEMCH2PGlobalIx OBJECT-TYPE
   SYNTAX      GlobalIndex
   MAX-ACCESS  not-accessible
   STATUS      current
   DESCRIPTION
      "The value of the tlsCntTreeGlobalIndex of the MANAGED OBJECT."
   ::= {pr1646v2BgriMVPPPoEMCH2PEntry 10}

pr1646v2BgriMVPPPoEMCH2PTableIx OBJECT-TYPE
   SYNTAX      TableIndex
   MAX-ACCESS  not-accessible
   STATUS      current
   DESCRIPTION
      ""
   ::= {pr1646v2BgriMVPPPoEMCH2PEntry 11}

pr1646v2BgriMVPPPoEMCH2PSysUpTime OBJECT-TYPE
   SYNTAX      TimeTicks
   MAX-ACCESS  read-only
   STATUS      current
   DESCRIPTION
      "Path: vpnBridgeGroup.performance.pppoEClient.mibCounters.h2Performance.sysUpTime

       Time in centi-second."
   ::= {pr1646v2BgriMVPPPoEMCH2PEntry 16777216}

pr1646v2BgriMVPPPoEMCH2PIfUpTime OBJECT-TYPE
   SYNTAX      TimeTicks
   MAX-ACCESS  read-only
   STATUS      current
   DESCRIPTION
      "Path: vpnBridgeGroup.performance.pppoEClient.mibCounters.h2Performance.ifUpTime

       Time in centi-second."
   ::= {pr1646v2BgriMVPPPoEMCH2PEntry 33554432}

pr1646v2BgriMVPPPoEMCH2PIfStatChanges OBJECT-TYPE
   SYNTAX      Counter32
   MAX-ACCESS  read-only
   STATUS      current
   DESCRIPTION
      "Path: vpnBridgeGroup.performance.pppoEClient.mibCounters.h2Performance.ifStatusChanges

       32 bit unsigned wrappable counter."
   ::= {pr1646v2BgriMVPPPoEMCH2PEntry 50331648}

pr1646v2BgriMVPPPoEMCH2PIfInOctets OBJECT-TYPE
   SYNTAX      Counter64
   MAX-ACCESS  read-only
   STATUS      current
   DESCRIPTION
      "Path: vpnBridgeGroup.performance.pppoEClient.mibCounters.h2Performance.ifInOctets

       64 bit unsigned wrappable counter."
   ::= {pr1646v2BgriMVPPPoEMCH2PEntry 67108864}

pr1646v2BgriMVPPPoEMCH2PIfInUCPkts OBJECT-TYPE
   SYNTAX      Counter64
   MAX-ACCESS  read-only
   STATUS      current
   DESCRIPTION
      "Path: vpnBridgeGroup.performance.pppoEClient.mibCounters.h2Performance.ifInUcastPkts

       64 bit unsigned wrappable counter."
   ::= {pr1646v2BgriMVPPPoEMCH2PEntry 83886080}

pr1646v2BgriMVPPPoEMCH2PIfInNUCPkts OBJECT-TYPE
   SYNTAX      Counter64
   MAX-ACCESS  read-only
   STATUS      current
   DESCRIPTION
      "Path: vpnBridgeGroup.performance.pppoEClient.mibCounters.h2Performance.ifInNUcastPkts

       64 bit unsigned wrappable counter."
   ::= {pr1646v2BgriMVPPPoEMCH2PEntry 100663296}

pr1646v2BgriMVPPPoEMCH2PIfInBCPkts OBJECT-TYPE
   SYNTAX      Counter64
   MAX-ACCESS  read-only
   STATUS      current
   DESCRIPTION
      "Path: vpnBridgeGroup.performance.pppoEClient.mibCounters.h2Performance.ifInBcastPkts

       64 bit unsigned wrappable counter."
   ::= {pr1646v2BgriMVPPPoEMCH2PEntry 419430400}

pr1646v2BgriMVPPPoEMCH2PIfInMCPkts OBJECT-TYPE
   SYNTAX      Counter64
   MAX-ACCESS  read-only
   STATUS      current
   DESCRIPTION
      "Path: vpnBridgeGroup.performance.pppoEClient.mibCounters.h2Performance.ifInMcastPkts

       64 bit unsigned wrappable counter."
   ::= {pr1646v2BgriMVPPPoEMCH2PEntry 436207616}

pr1646v2BgriMVPPPoEMCH2PIfInDiscards OBJECT-TYPE
   SYNTAX      Counter64
   MAX-ACCESS  read-only
   STATUS      current
   DESCRIPTION
      "Path: vpnBridgeGroup.performance.pppoEClient.mibCounters.h2Performance.ifInDiscards

       64 bit unsigned wrappable counter."
   ::= {pr1646v2BgriMVPPPoEMCH2PEntry 117440512}

pr1646v2BgriMVPPPoEMCH2PIfInErrors OBJECT-TYPE
   SYNTAX      Counter64
   MAX-ACCESS  read-only
   STATUS      current
   DESCRIPTION
      "Path: vpnBridgeGroup.performance.pppoEClient.mibCounters.h2Performance.ifInErrors

       64 bit unsigned wrappable counter."
   ::= {pr1646v2BgriMVPPPoEMCH2PEntry 134217728}

pr1646v2BgriMVPPPoEMCH2PIfInUnkwn OBJECT-TYPE
   SYNTAX      Counter64
   MAX-ACCESS  read-only
   STATUS      current
   DESCRIPTION
      "Path: vpnBridgeGroup.performance.pppoEClient.mibCounters.h2Performance.ifInUnknownProtos

       64 bit unsigned wrappable counter."
   ::= {pr1646v2BgriMVPPPoEMCH2PEntry 150994944}

pr1646v2BgriMVPPPoEMCH2PInDropEx OBJECT-TYPE
   SYNTAX      Counter64
   MAX-ACCESS  read-only
   STATUS      current
   DESCRIPTION
      "Path: vpnBridgeGroup.performance.pppoEClient.mibCounters.h2Performance.ifInDropLevelExceeded

       64 bit unsigned wrappable counter."
   ::= {pr1646v2BgriMVPPPoEMCH2PEntry 335544320}

pr1646v2BgriMVPPPoEMCH2PInDropNoMac OBJECT-TYPE
   SYNTAX      Counter64
   MAX-ACCESS  read-only
   STATUS      current
   DESCRIPTION
      "Path: vpnBridgeGroup.performance.pppoEClient.mibCounters.h2Performance.fInDiscardsNoMacFit

       64 bit unsigned wrappable counter."
   ::= {pr1646v2BgriMVPPPoEMCH2PEntry 301989888}

pr1646v2BgriMVPPPoEMCH2PInDropNUCast OBJECT-TYPE
   SYNTAX      Counter64
   MAX-ACCESS  read-only
   STATUS      current
   DESCRIPTION
      "Path: vpnBridgeGroup.performance.pppoEClient.mibCounters.h2Performance.fInDiscardsNUCast

       64 bit unsigned wrappable counter."
   ::= {pr1646v2BgriMVPPPoEMCH2PEntry 318767104}

pr1646v2BgriMVPPPoEMCH2PInDropFilter OBJECT-TYPE
   SYNTAX      Counter64
   MAX-ACCESS  read-only
   STATUS      current
   DESCRIPTION
      "Path: vpnBridgeGroup.performance.pppoEClient.mibCounters.h2Performance.fInDiscardsFilter

       64 bit unsigned wrappable counter."
   ::= {pr1646v2BgriMVPPPoEMCH2PEntry 385875968}

pr1646v2BgriMVPPPoEMCH2PIfInBandwidth OBJECT-TYPE
   SYNTAX      Integer32
   MAX-ACCESS  read-only
   STATUS      current
   DESCRIPTION
      "Path: vpnBridgeGroup.performance.pppoEClient.mibCounters.h2Performance.ifInBandwidth

       unit name = bps
       formula = 8 * ; 8 /"
   ::= {pr1646v2BgriMVPPPoEMCH2PEntry 268435456}

pr1646v2BgriMVPPPoEMCH2PIfOutOctets OBJECT-TYPE
   SYNTAX      Counter64
   MAX-ACCESS  read-only
   STATUS      current
   DESCRIPTION
      "Path: vpnBridgeGroup.performance.pppoEClient.mibCounters.h2Performance.ifOutOctets

       64 bit unsigned wrappable counter."
   ::= {pr1646v2BgriMVPPPoEMCH2PEntry 167772160}

pr1646v2BgriMVPPPoEMCH2PIfOutUCPkts OBJECT-TYPE
   SYNTAX      Counter64
   MAX-ACCESS  read-only
   STATUS      current
   DESCRIPTION
      "Path: vpnBridgeGroup.performance.pppoEClient.mibCounters.h2Performance.ifOutUcastPkts

       64 bit unsigned wrappable counter."
   ::= {pr1646v2BgriMVPPPoEMCH2PEntry 184549376}

pr1646v2BgriMVPPPoEMCH2PIfOutNUCPkts OBJECT-TYPE
   SYNTAX      Counter64
   MAX-ACCESS  read-only
   STATUS      current
   DESCRIPTION
      "Path: vpnBridgeGroup.performance.pppoEClient.mibCounters.h2Performance.ifOutNUcastPkts

       64 bit unsigned wrappable counter."
   ::= {pr1646v2BgriMVPPPoEMCH2PEntry 201326592}

pr1646v2BgriMVPPPoEMCH2PIfOutBCPkts OBJECT-TYPE
   SYNTAX      Counter64
   MAX-ACCESS  read-only
   STATUS      current
   DESCRIPTION
      "Path: vpnBridgeGroup.performance.pppoEClient.mibCounters.h2Performance.ifOutBcastPkts

       64 bit unsigned wrappable counter."
   ::= {pr1646v2BgriMVPPPoEMCH2PEntry 452984832}

pr1646v2BgriMVPPPoEMCH2PIfOutMCPkts OBJECT-TYPE
   SYNTAX      Counter64
   MAX-ACCESS  read-only
   STATUS      current
   DESCRIPTION
      "Path: vpnBridgeGroup.performance.pppoEClient.mibCounters.h2Performance.ifOutMcastPkts

       64 bit unsigned wrappable counter."
   ::= {pr1646v2BgriMVPPPoEMCH2PEntry 469762048}

pr1646v2BgriMVPPPoEMCH2PIfOutDiscards OBJECT-TYPE
   SYNTAX      Counter64
   MAX-ACCESS  read-only
   STATUS      current
   DESCRIPTION
      "Path: vpnBridgeGroup.performance.pppoEClient.mibCounters.h2Performance.ifOutDiscards

       64 bit unsigned wrappable counter."
   ::= {pr1646v2BgriMVPPPoEMCH2PEntry 218103808}

pr1646v2BgriMVPPPoEMCH2PIfOutErrors OBJECT-TYPE
   SYNTAX      Counter64
   MAX-ACCESS  read-only
   STATUS      current
   DESCRIPTION
      "Path: vpnBridgeGroup.performance.pppoEClient.mibCounters.h2Performance.ifOutErrors

       64 bit unsigned wrappable counter."
   ::= {pr1646v2BgriMVPPPoEMCH2PEntry 234881024}

pr1646v2BgriMVPPPoEMCH2POutDropEx OBJECT-TYPE
   SYNTAX      Counter64
   MAX-ACCESS  read-only
   STATUS      current
   DESCRIPTION
      "Path: vpnBridgeGroup.performance.pppoEClient.mibCounters.h2Performance.ifOutDropLevelExceeded

       64 bit unsigned wrappable counter."
   ::= {pr1646v2BgriMVPPPoEMCH2PEntry 352321536}

pr1646v2BgriMVPPPoEMCH2POutDropNoArp OBJECT-TYPE
   SYNTAX      Counter64
   MAX-ACCESS  read-only
   STATUS      current
   DESCRIPTION
      "Path: vpnBridgeGroup.performance.pppoEClient.mibCounters.h2Performance.ifOutDiscardsNoArp

       64 bit unsigned wrappable counter."
   ::= {pr1646v2BgriMVPPPoEMCH2PEntry 369098752}

pr1646v2BgriMVPPPoEMCH2POutDropFilter OBJECT-TYPE
   SYNTAX      Counter64
   MAX-ACCESS  read-only
   STATUS      current
   DESCRIPTION
      "Path: vpnBridgeGroup.performance.pppoEClient.mibCounters.h2Performance.ifOutDiscardsFilter

       64 bit unsigned wrappable counter."
   ::= {pr1646v2BgriMVPPPoEMCH2PEntry 402653184}

pr1646v2BgriMVPPPoEMCH2PIfOutBandwidth OBJECT-TYPE
   SYNTAX      Integer32
   MAX-ACCESS  read-only
   STATUS      current
   DESCRIPTION
      "Path: vpnBridgeGroup.performance.pppoEClient.mibCounters.h2Performance.ifOutBandwidth

       unit name = bps
       formula = 8 * ; 8 /"
   ::= {pr1646v2BgriMVPPPoEMCH2PEntry 285212672}

pr1646v2BgriMVPPPoEMCH2PIfErrSec OBJECT-TYPE
   SYNTAX      Counter32
   MAX-ACCESS  read-only
   STATUS      current
   DESCRIPTION
      "Path: vpnBridgeGroup.performance.pppoEClient.mibCounters.h2Performance.ifErrSec

       32 bit unsigned wrappable counter."
   ::= {pr1646v2BgriMVPPPoEMCH2PEntry 251658240}

pr1646v2BgriMVPPPoEMCH24P OBJECT-TYPE
   SYNTAX      SEQUENCE OF Pr1646v2BgriMVPPPoEMCH24PEntry
   MAX-ACCESS  not-accessible
   STATUS      current
   DESCRIPTION
      ""
   ::= {pr1646v2BgriMVPPPoE 41615360}

pr1646v2BgriMVPPPoEMCH24PEntry OBJECT-TYPE
   SYNTAX      Pr1646v2BgriMVPPPoEMCH24PEntry
   MAX-ACCESS  not-accessible
   STATUS      current
   DESCRIPTION
      ""
   INDEX      { pr1646v2BgriMVPPPoEMCH24PGlobalIx,
                pr1646v2BgriMVPPPoETableIx,
                pr1646v2BgriMVPPPoEMCH24PTableIx }
   ::= {pr1646v2BgriMVPPPoEMCH24P 1}

Pr1646v2BgriMVPPPoEMCH24PEntry ::=
   SEQUENCE
      {
      pr1646v2BgriMVPPPoEMCH24PGlobalIx
         GlobalIndex,
      pr1646v2BgriMVPPPoEMCH24PTableIx
         TableIndex,
      pr1646v2BgriMVPPPoEMCH24PSysUpTime
         TimeTicks,
      pr1646v2BgriMVPPPoEMCH24PIfUpTime
         TimeTicks,
      pr1646v2BgriMVPPPoEMCH24PIfStatChanges
         Counter32,
      pr1646v2BgriMVPPPoEMCH24PIfInOctets
         Counter64,
      pr1646v2BgriMVPPPoEMCH24PIfInUCPkts
         Counter64,
      pr1646v2BgriMVPPPoEMCH24PIfInNUCPkts
         Counter64,
      pr1646v2BgriMVPPPoEMCH24PIfInBCPkts
         Counter64,
      pr1646v2BgriMVPPPoEMCH24PIfInMCPkts
         Counter64,
      pr1646v2BgriMVPPPoEMCH24PIfInDiscards
         Counter64,
      pr1646v2BgriMVPPPoEMCH24PIfInErrors
         Counter64,
      pr1646v2BgriMVPPPoEMCH24PIfInUnkwn
         Counter64,
      pr1646v2BgriMVPPPoEMCH24PInDropEx
         Counter64,
      pr1646v2BgriMVPPPoEMCH24PInDropNoMac
         Counter64,
      pr1646v2BgriMVPPPoEMCH24PInDropNUCast
         Counter64,
      pr1646v2BgriMVPPPoEMCH24PInDropFilter
         Counter64,
      pr1646v2BgriMVPPPoEMCH24PIfInBandwidth
         Integer32,
      pr1646v2BgriMVPPPoEMCH24PIfOutOctets
         Counter64,
      pr1646v2BgriMVPPPoEMCH24PIfOutUCPkts
         Counter64,
      pr1646v2BgriMVPPPoEMCH24PIfOutNUCPkts
         Counter64,
      pr1646v2BgriMVPPPoEMCH24PIfOutBCPkts
         Counter64,
      pr1646v2BgriMVPPPoEMCH24PIfOutMCPkts
         Counter64,
      pr1646v2BgriMVPPPoEMCH24PIfOutDiscards
         Counter64,
      pr1646v2BgriMVPPPoEMCH24PIfOutErrors
         Counter64,
      pr1646v2BgriMVPPPoEMCH24POutDropEx
         Counter64,
      pr1646v2BgriMVPPPoEMCH24POutDropNoArp
         Counter64,
      pr1646v2BgriMVPPPoEMCH24POutDropFilter
         Counter64,
      pr1646v2BgriMVPPPoEMCH24PIfOutBandwidth
         Integer32,
      pr1646v2BgriMVPPPoEMCH24PIfErrSec
         Counter32
      }

pr1646v2BgriMVPPPoEMCH24PGlobalIx OBJECT-TYPE
   SYNTAX      GlobalIndex
   MAX-ACCESS  not-accessible
   STATUS      current
   DESCRIPTION
      "The value of the tlsCntTreeGlobalIndex of the MANAGED OBJECT."
   ::= {pr1646v2BgriMVPPPoEMCH24PEntry 10}

pr1646v2BgriMVPPPoEMCH24PTableIx OBJECT-TYPE
   SYNTAX      TableIndex
   MAX-ACCESS  not-accessible
   STATUS      current
   DESCRIPTION
      ""
   ::= {pr1646v2BgriMVPPPoEMCH24PEntry 11}

pr1646v2BgriMVPPPoEMCH24PSysUpTime OBJECT-TYPE
   SYNTAX      TimeTicks
   MAX-ACCESS  read-only
   STATUS      current
   DESCRIPTION
      "Path: vpnBridgeGroup.performance.pppoEClient.mibCounters.h24Performance.sysUpTime

       Time in centi-second."
   ::= {pr1646v2BgriMVPPPoEMCH24PEntry 16777216}

pr1646v2BgriMVPPPoEMCH24PIfUpTime OBJECT-TYPE
   SYNTAX      TimeTicks
   MAX-ACCESS  read-only
   STATUS      current
   DESCRIPTION
      "Path: vpnBridgeGroup.performance.pppoEClient.mibCounters.h24Performance.ifUpTime

       Time in centi-second."
   ::= {pr1646v2BgriMVPPPoEMCH24PEntry 33554432}

pr1646v2BgriMVPPPoEMCH24PIfStatChanges OBJECT-TYPE
   SYNTAX      Counter32
   MAX-ACCESS  read-only
   STATUS      current
   DESCRIPTION
      "Path: vpnBridgeGroup.performance.pppoEClient.mibCounters.h24Performance.ifStatusChanges

       32 bit unsigned wrappable counter."
   ::= {pr1646v2BgriMVPPPoEMCH24PEntry 50331648}

pr1646v2BgriMVPPPoEMCH24PIfInOctets OBJECT-TYPE
   SYNTAX      Counter64
   MAX-ACCESS  read-only
   STATUS      current
   DESCRIPTION
      "Path: vpnBridgeGroup.performance.pppoEClient.mibCounters.h24Performance.ifInOctets

       64 bit unsigned wrappable counter."
   ::= {pr1646v2BgriMVPPPoEMCH24PEntry 67108864}

pr1646v2BgriMVPPPoEMCH24PIfInUCPkts OBJECT-TYPE
   SYNTAX      Counter64
   MAX-ACCESS  read-only
   STATUS      current
   DESCRIPTION
      "Path: vpnBridgeGroup.performance.pppoEClient.mibCounters.h24Performance.ifInUcastPkts

       64 bit unsigned wrappable counter."
   ::= {pr1646v2BgriMVPPPoEMCH24PEntry 83886080}

pr1646v2BgriMVPPPoEMCH24PIfInNUCPkts OBJECT-TYPE
   SYNTAX      Counter64
   MAX-ACCESS  read-only
   STATUS      current
   DESCRIPTION
      "Path: vpnBridgeGroup.performance.pppoEClient.mibCounters.h24Performance.ifInNUcastPkts

       64 bit unsigned wrappable counter."
   ::= {pr1646v2BgriMVPPPoEMCH24PEntry 100663296}

pr1646v2BgriMVPPPoEMCH24PIfInBCPkts OBJECT-TYPE
   SYNTAX      Counter64
   MAX-ACCESS  read-only
   STATUS      current
   DESCRIPTION
      "Path: vpnBridgeGroup.performance.pppoEClient.mibCounters.h24Performance.ifInBcastPkts

       64 bit unsigned wrappable counter."
   ::= {pr1646v2BgriMVPPPoEMCH24PEntry 419430400}

pr1646v2BgriMVPPPoEMCH24PIfInMCPkts OBJECT-TYPE
   SYNTAX      Counter64
   MAX-ACCESS  read-only
   STATUS      current
   DESCRIPTION
      "Path: vpnBridgeGroup.performance.pppoEClient.mibCounters.h24Performance.ifInMcastPkts

       64 bit unsigned wrappable counter."
   ::= {pr1646v2BgriMVPPPoEMCH24PEntry 436207616}

pr1646v2BgriMVPPPoEMCH24PIfInDiscards OBJECT-TYPE
   SYNTAX      Counter64
   MAX-ACCESS  read-only
   STATUS      current
   DESCRIPTION
      "Path: vpnBridgeGroup.performance.pppoEClient.mibCounters.h24Performance.ifInDiscards

       64 bit unsigned wrappable counter."
   ::= {pr1646v2BgriMVPPPoEMCH24PEntry 117440512}

pr1646v2BgriMVPPPoEMCH24PIfInErrors OBJECT-TYPE
   SYNTAX      Counter64
   MAX-ACCESS  read-only
   STATUS      current
   DESCRIPTION
      "Path: vpnBridgeGroup.performance.pppoEClient.mibCounters.h24Performance.ifInErrors

       64 bit unsigned wrappable counter."
   ::= {pr1646v2BgriMVPPPoEMCH24PEntry 134217728}

pr1646v2BgriMVPPPoEMCH24PIfInUnkwn OBJECT-TYPE
   SYNTAX      Counter64
   MAX-ACCESS  read-only
   STATUS      current
   DESCRIPTION
      "Path: vpnBridgeGroup.performance.pppoEClient.mibCounters.h24Performance.ifInUnknownProtos

       64 bit unsigned wrappable counter."
   ::= {pr1646v2BgriMVPPPoEMCH24PEntry 150994944}

pr1646v2BgriMVPPPoEMCH24PInDropEx OBJECT-TYPE
   SYNTAX      Counter64
   MAX-ACCESS  read-only
   STATUS      current
   DESCRIPTION
      "Path: vpnBridgeGroup.performance.pppoEClient.mibCounters.h24Performance.ifInDropLevelExceeded

       64 bit unsigned wrappable counter."
   ::= {pr1646v2BgriMVPPPoEMCH24PEntry 335544320}

pr1646v2BgriMVPPPoEMCH24PInDropNoMac OBJECT-TYPE
   SYNTAX      Counter64
   MAX-ACCESS  read-only
   STATUS      current
   DESCRIPTION
      "Path: vpnBridgeGroup.performance.pppoEClient.mibCounters.h24Performance.fInDiscardsNoMacFit

       64 bit unsigned wrappable counter."
   ::= {pr1646v2BgriMVPPPoEMCH24PEntry 301989888}

pr1646v2BgriMVPPPoEMCH24PInDropNUCast OBJECT-TYPE
   SYNTAX      Counter64
   MAX-ACCESS  read-only
   STATUS      current
   DESCRIPTION
      "Path: vpnBridgeGroup.performance.pppoEClient.mibCounters.h24Performance.fInDiscardsNUCast

       64 bit unsigned wrappable counter."
   ::= {pr1646v2BgriMVPPPoEMCH24PEntry 318767104}

pr1646v2BgriMVPPPoEMCH24PInDropFilter OBJECT-TYPE
   SYNTAX      Counter64
   MAX-ACCESS  read-only
   STATUS      current
   DESCRIPTION
      "Path: vpnBridgeGroup.performance.pppoEClient.mibCounters.h24Performance.fInDiscardsFilter

       64 bit unsigned wrappable counter."
   ::= {pr1646v2BgriMVPPPoEMCH24PEntry 385875968}

pr1646v2BgriMVPPPoEMCH24PIfInBandwidth OBJECT-TYPE
   SYNTAX      Integer32
   MAX-ACCESS  read-only
   STATUS      current
   DESCRIPTION
      "Path: vpnBridgeGroup.performance.pppoEClient.mibCounters.h24Performance.ifInBandwidth

       unit name = bps
       formula = 8 * ; 8 /"
   ::= {pr1646v2BgriMVPPPoEMCH24PEntry 268435456}

pr1646v2BgriMVPPPoEMCH24PIfOutOctets OBJECT-TYPE
   SYNTAX      Counter64
   MAX-ACCESS  read-only
   STATUS      current
   DESCRIPTION
      "Path: vpnBridgeGroup.performance.pppoEClient.mibCounters.h24Performance.ifOutOctets

       64 bit unsigned wrappable counter."
   ::= {pr1646v2BgriMVPPPoEMCH24PEntry 167772160}

pr1646v2BgriMVPPPoEMCH24PIfOutUCPkts OBJECT-TYPE
   SYNTAX      Counter64
   MAX-ACCESS  read-only
   STATUS      current
   DESCRIPTION
      "Path: vpnBridgeGroup.performance.pppoEClient.mibCounters.h24Performance.ifOutUcastPkts

       64 bit unsigned wrappable counter."
   ::= {pr1646v2BgriMVPPPoEMCH24PEntry 184549376}

pr1646v2BgriMVPPPoEMCH24PIfOutNUCPkts OBJECT-TYPE
   SYNTAX      Counter64
   MAX-ACCESS  read-only
   STATUS      current
   DESCRIPTION
      "Path: vpnBridgeGroup.performance.pppoEClient.mibCounters.h24Performance.ifOutNUcastPkts

       64 bit unsigned wrappable counter."
   ::= {pr1646v2BgriMVPPPoEMCH24PEntry 201326592}

pr1646v2BgriMVPPPoEMCH24PIfOutBCPkts OBJECT-TYPE
   SYNTAX      Counter64
   MAX-ACCESS  read-only
   STATUS      current
   DESCRIPTION
      "Path: vpnBridgeGroup.performance.pppoEClient.mibCounters.h24Performance.ifOutBcastPkts

       64 bit unsigned wrappable counter."
   ::= {pr1646v2BgriMVPPPoEMCH24PEntry 452984832}

pr1646v2BgriMVPPPoEMCH24PIfOutMCPkts OBJECT-TYPE
   SYNTAX      Counter64
   MAX-ACCESS  read-only
   STATUS      current
   DESCRIPTION
      "Path: vpnBridgeGroup.performance.pppoEClient.mibCounters.h24Performance.ifOutMcastPkts

       64 bit unsigned wrappable counter."
   ::= {pr1646v2BgriMVPPPoEMCH24PEntry 469762048}

pr1646v2BgriMVPPPoEMCH24PIfOutDiscards OBJECT-TYPE
   SYNTAX      Counter64
   MAX-ACCESS  read-only
   STATUS      current
   DESCRIPTION
      "Path: vpnBridgeGroup.performance.pppoEClient.mibCounters.h24Performance.ifOutDiscards

       64 bit unsigned wrappable counter."
   ::= {pr1646v2BgriMVPPPoEMCH24PEntry 218103808}

pr1646v2BgriMVPPPoEMCH24PIfOutErrors OBJECT-TYPE
   SYNTAX      Counter64
   MAX-ACCESS  read-only
   STATUS      current
   DESCRIPTION
      "Path: vpnBridgeGroup.performance.pppoEClient.mibCounters.h24Performance.ifOutErrors

       64 bit unsigned wrappable counter."
   ::= {pr1646v2BgriMVPPPoEMCH24PEntry 234881024}

pr1646v2BgriMVPPPoEMCH24POutDropEx OBJECT-TYPE
   SYNTAX      Counter64
   MAX-ACCESS  read-only
   STATUS      current
   DESCRIPTION
      "Path: vpnBridgeGroup.performance.pppoEClient.mibCounters.h24Performance.ifOutDropLevelExceeded

       64 bit unsigned wrappable counter."
   ::= {pr1646v2BgriMVPPPoEMCH24PEntry 352321536}

pr1646v2BgriMVPPPoEMCH24POutDropNoArp OBJECT-TYPE
   SYNTAX      Counter64
   MAX-ACCESS  read-only
   STATUS      current
   DESCRIPTION
      "Path: vpnBridgeGroup.performance.pppoEClient.mibCounters.h24Performance.ifOutDiscardsNoArp

       64 bit unsigned wrappable counter."
   ::= {pr1646v2BgriMVPPPoEMCH24PEntry 369098752}

pr1646v2BgriMVPPPoEMCH24POutDropFilter OBJECT-TYPE
   SYNTAX      Counter64
   MAX-ACCESS  read-only
   STATUS      current
   DESCRIPTION
      "Path: vpnBridgeGroup.performance.pppoEClient.mibCounters.h24Performance.ifOutDiscardsFilter

       64 bit unsigned wrappable counter."
   ::= {pr1646v2BgriMVPPPoEMCH24PEntry 402653184}

pr1646v2BgriMVPPPoEMCH24PIfOutBandwidth OBJECT-TYPE
   SYNTAX      Integer32
   MAX-ACCESS  read-only
   STATUS      current
   DESCRIPTION
      "Path: vpnBridgeGroup.performance.pppoEClient.mibCounters.h24Performance.ifOutBandwidth

       unit name = bps
       formula = 8 * ; 8 /"
   ::= {pr1646v2BgriMVPPPoEMCH24PEntry 285212672}

pr1646v2BgriMVPPPoEMCH24PIfErrSec OBJECT-TYPE
   SYNTAX      Counter32
   MAX-ACCESS  read-only
   STATUS      current
   DESCRIPTION
      "Path: vpnBridgeGroup.performance.pppoEClient.mibCounters.h24Performance.ifErrSec

       32 bit unsigned wrappable counter."
   ::= {pr1646v2BgriMVPPPoEMCH24PEntry 251658240}

pr1646v2BgriMVPPPoEMCD7P OBJECT-TYPE
   SYNTAX      SEQUENCE OF Pr1646v2BgriMVPPPoEMCD7PEntry
   MAX-ACCESS  not-accessible
   STATUS      current
   DESCRIPTION
      ""
   ::= {pr1646v2BgriMVPPPoE 41680896}

pr1646v2BgriMVPPPoEMCD7PEntry OBJECT-TYPE
   SYNTAX      Pr1646v2BgriMVPPPoEMCD7PEntry
   MAX-ACCESS  not-accessible
   STATUS      current
   DESCRIPTION
      ""
   INDEX      { pr1646v2BgriMVPPPoEMCD7PGlobalIx,
                pr1646v2BgriMVPPPoETableIx,
                pr1646v2BgriMVPPPoEMCD7PTableIx }
   ::= {pr1646v2BgriMVPPPoEMCD7P 1}

Pr1646v2BgriMVPPPoEMCD7PEntry ::=
   SEQUENCE
      {
      pr1646v2BgriMVPPPoEMCD7PGlobalIx
         GlobalIndex,
      pr1646v2BgriMVPPPoEMCD7PTableIx
         TableIndex,
      pr1646v2BgriMVPPPoEMCD7PSysUpTime
         TimeTicks,
      pr1646v2BgriMVPPPoEMCD7PIfUpTime
         TimeTicks,
      pr1646v2BgriMVPPPoEMCD7PIfStatChanges
         Counter32,
      pr1646v2BgriMVPPPoEMCD7PIfInOctets
         Counter64,
      pr1646v2BgriMVPPPoEMCD7PIfInUCPkts
         Counter64,
      pr1646v2BgriMVPPPoEMCD7PIfInNUCPkts
         Counter64,
      pr1646v2BgriMVPPPoEMCD7PIfInBCPkts
         Counter64,
      pr1646v2BgriMVPPPoEMCD7PIfInMCPkts
         Counter64,
      pr1646v2BgriMVPPPoEMCD7PIfInDiscards
         Counter64,
      pr1646v2BgriMVPPPoEMCD7PIfInErrors
         Counter64,
      pr1646v2BgriMVPPPoEMCD7PIfInUnkwn
         Counter64,
      pr1646v2BgriMVPPPoEMCD7PInDropEx
         Counter64,
      pr1646v2BgriMVPPPoEMCD7PInDropNoMac
         Counter64,
      pr1646v2BgriMVPPPoEMCD7PInDropNUCast
         Counter64,
      pr1646v2BgriMVPPPoEMCD7PInDropFilter
         Counter64,
      pr1646v2BgriMVPPPoEMCD7PIfInBandwidth
         Integer32,
      pr1646v2BgriMVPPPoEMCD7PIfOutOctets
         Counter64,
      pr1646v2BgriMVPPPoEMCD7PIfOutUCPkts
         Counter64,
      pr1646v2BgriMVPPPoEMCD7PIfOutNUCPkts
         Counter64,
      pr1646v2BgriMVPPPoEMCD7PIfOutBCPkts
         Counter64,
      pr1646v2BgriMVPPPoEMCD7PIfOutMCPkts
         Counter64,
      pr1646v2BgriMVPPPoEMCD7PIfOutDiscards
         Counter64,
      pr1646v2BgriMVPPPoEMCD7PIfOutErrors
         Counter64,
      pr1646v2BgriMVPPPoEMCD7POutDropEx
         Counter64,
      pr1646v2BgriMVPPPoEMCD7POutDropNoArp
         Counter64,
      pr1646v2BgriMVPPPoEMCD7POutDropFilter
         Counter64,
      pr1646v2BgriMVPPPoEMCD7PIfOutBandwidth
         Integer32,
      pr1646v2BgriMVPPPoEMCD7PIfErrSec
         Counter32
      }

pr1646v2BgriMVPPPoEMCD7PGlobalIx OBJECT-TYPE
   SYNTAX      GlobalIndex
   MAX-ACCESS  not-accessible
   STATUS      current
   DESCRIPTION
      "The value of the tlsCntTreeGlobalIndex of the MANAGED OBJECT."
   ::= {pr1646v2BgriMVPPPoEMCD7PEntry 10}

pr1646v2BgriMVPPPoEMCD7PTableIx OBJECT-TYPE
   SYNTAX      TableIndex
   MAX-ACCESS  not-accessible
   STATUS      current
   DESCRIPTION
      ""
   ::= {pr1646v2BgriMVPPPoEMCD7PEntry 11}

pr1646v2BgriMVPPPoEMCD7PSysUpTime OBJECT-TYPE
   SYNTAX      TimeTicks
   MAX-ACCESS  read-only
   STATUS      current
   DESCRIPTION
      "Path: vpnBridgeGroup.performance.pppoEClient.mibCounters.d7Performance.sysUpTime

       Time in centi-second."
   ::= {pr1646v2BgriMVPPPoEMCD7PEntry 16777216}

pr1646v2BgriMVPPPoEMCD7PIfUpTime OBJECT-TYPE
   SYNTAX      TimeTicks
   MAX-ACCESS  read-only
   STATUS      current
   DESCRIPTION
      "Path: vpnBridgeGroup.performance.pppoEClient.mibCounters.d7Performance.ifUpTime

       Time in centi-second."
   ::= {pr1646v2BgriMVPPPoEMCD7PEntry 33554432}

pr1646v2BgriMVPPPoEMCD7PIfStatChanges OBJECT-TYPE
   SYNTAX      Counter32
   MAX-ACCESS  read-only
   STATUS      current
   DESCRIPTION
      "Path: vpnBridgeGroup.performance.pppoEClient.mibCounters.d7Performance.ifStatusChanges

       32 bit unsigned wrappable counter."
   ::= {pr1646v2BgriMVPPPoEMCD7PEntry 50331648}

pr1646v2BgriMVPPPoEMCD7PIfInOctets OBJECT-TYPE
   SYNTAX      Counter64
   MAX-ACCESS  read-only
   STATUS      current
   DESCRIPTION
      "Path: vpnBridgeGroup.performance.pppoEClient.mibCounters.d7Performance.ifInOctets

       64 bit unsigned wrappable counter."
   ::= {pr1646v2BgriMVPPPoEMCD7PEntry 67108864}

pr1646v2BgriMVPPPoEMCD7PIfInUCPkts OBJECT-TYPE
   SYNTAX      Counter64
   MAX-ACCESS  read-only
   STATUS      current
   DESCRIPTION
      "Path: vpnBridgeGroup.performance.pppoEClient.mibCounters.d7Performance.ifInUcastPkts

       64 bit unsigned wrappable counter."
   ::= {pr1646v2BgriMVPPPoEMCD7PEntry 83886080}

pr1646v2BgriMVPPPoEMCD7PIfInNUCPkts OBJECT-TYPE
   SYNTAX      Counter64
   MAX-ACCESS  read-only
   STATUS      current
   DESCRIPTION
      "Path: vpnBridgeGroup.performance.pppoEClient.mibCounters.d7Performance.ifInNUcastPkts

       64 bit unsigned wrappable counter."
   ::= {pr1646v2BgriMVPPPoEMCD7PEntry 100663296}

pr1646v2BgriMVPPPoEMCD7PIfInBCPkts OBJECT-TYPE
   SYNTAX      Counter64
   MAX-ACCESS  read-only
   STATUS      current
   DESCRIPTION
      "Path: vpnBridgeGroup.performance.pppoEClient.mibCounters.d7Performance.ifInBcastPkts

       64 bit unsigned wrappable counter."
   ::= {pr1646v2BgriMVPPPoEMCD7PEntry 419430400}

pr1646v2BgriMVPPPoEMCD7PIfInMCPkts OBJECT-TYPE
   SYNTAX      Counter64
   MAX-ACCESS  read-only
   STATUS      current
   DESCRIPTION
      "Path: vpnBridgeGroup.performance.pppoEClient.mibCounters.d7Performance.ifInMcastPkts

       64 bit unsigned wrappable counter."
   ::= {pr1646v2BgriMVPPPoEMCD7PEntry 436207616}

pr1646v2BgriMVPPPoEMCD7PIfInDiscards OBJECT-TYPE
   SYNTAX      Counter64
   MAX-ACCESS  read-only
   STATUS      current
   DESCRIPTION
      "Path: vpnBridgeGroup.performance.pppoEClient.mibCounters.d7Performance.ifInDiscards

       64 bit unsigned wrappable counter."
   ::= {pr1646v2BgriMVPPPoEMCD7PEntry 117440512}

pr1646v2BgriMVPPPoEMCD7PIfInErrors OBJECT-TYPE
   SYNTAX      Counter64
   MAX-ACCESS  read-only
   STATUS      current
   DESCRIPTION
      "Path: vpnBridgeGroup.performance.pppoEClient.mibCounters.d7Performance.ifInErrors

       64 bit unsigned wrappable counter."
   ::= {pr1646v2BgriMVPPPoEMCD7PEntry 134217728}

pr1646v2BgriMVPPPoEMCD7PIfInUnkwn OBJECT-TYPE
   SYNTAX      Counter64
   MAX-ACCESS  read-only
   STATUS      current
   DESCRIPTION
      "Path: vpnBridgeGroup.performance.pppoEClient.mibCounters.d7Performance.ifInUnknownProtos

       64 bit unsigned wrappable counter."
   ::= {pr1646v2BgriMVPPPoEMCD7PEntry 150994944}

pr1646v2BgriMVPPPoEMCD7PInDropEx OBJECT-TYPE
   SYNTAX      Counter64
   MAX-ACCESS  read-only
   STATUS      current
   DESCRIPTION
      "Path: vpnBridgeGroup.performance.pppoEClient.mibCounters.d7Performance.ifInDropLevelExceeded

       64 bit unsigned wrappable counter."
   ::= {pr1646v2BgriMVPPPoEMCD7PEntry 335544320}

pr1646v2BgriMVPPPoEMCD7PInDropNoMac OBJECT-TYPE
   SYNTAX      Counter64
   MAX-ACCESS  read-only
   STATUS      current
   DESCRIPTION
      "Path: vpnBridgeGroup.performance.pppoEClient.mibCounters.d7Performance.fInDiscardsNoMacFit

       64 bit unsigned wrappable counter."
   ::= {pr1646v2BgriMVPPPoEMCD7PEntry 301989888}

pr1646v2BgriMVPPPoEMCD7PInDropNUCast OBJECT-TYPE
   SYNTAX      Counter64
   MAX-ACCESS  read-only
   STATUS      current
   DESCRIPTION
      "Path: vpnBridgeGroup.performance.pppoEClient.mibCounters.d7Performance.fInDiscardsNUCast

       64 bit unsigned wrappable counter."
   ::= {pr1646v2BgriMVPPPoEMCD7PEntry 318767104}

pr1646v2BgriMVPPPoEMCD7PInDropFilter OBJECT-TYPE
   SYNTAX      Counter64
   MAX-ACCESS  read-only
   STATUS      current
   DESCRIPTION
      "Path: vpnBridgeGroup.performance.pppoEClient.mibCounters.d7Performance.fInDiscardsFilter

       64 bit unsigned wrappable counter."
   ::= {pr1646v2BgriMVPPPoEMCD7PEntry 385875968}

pr1646v2BgriMVPPPoEMCD7PIfInBandwidth OBJECT-TYPE
   SYNTAX      Integer32
   MAX-ACCESS  read-only
   STATUS      current
   DESCRIPTION
      "Path: vpnBridgeGroup.performance.pppoEClient.mibCounters.d7Performance.ifInBandwidth

       unit name = bps
       formula = 8 * ; 8 /"
   ::= {pr1646v2BgriMVPPPoEMCD7PEntry 268435456}

pr1646v2BgriMVPPPoEMCD7PIfOutOctets OBJECT-TYPE
   SYNTAX      Counter64
   MAX-ACCESS  read-only
   STATUS      current
   DESCRIPTION
      "Path: vpnBridgeGroup.performance.pppoEClient.mibCounters.d7Performance.ifOutOctets

       64 bit unsigned wrappable counter."
   ::= {pr1646v2BgriMVPPPoEMCD7PEntry 167772160}

pr1646v2BgriMVPPPoEMCD7PIfOutUCPkts OBJECT-TYPE
   SYNTAX      Counter64
   MAX-ACCESS  read-only
   STATUS      current
   DESCRIPTION
      "Path: vpnBridgeGroup.performance.pppoEClient.mibCounters.d7Performance.ifOutUcastPkts

       64 bit unsigned wrappable counter."
   ::= {pr1646v2BgriMVPPPoEMCD7PEntry 184549376}

pr1646v2BgriMVPPPoEMCD7PIfOutNUCPkts OBJECT-TYPE
   SYNTAX      Counter64
   MAX-ACCESS  read-only
   STATUS      current
   DESCRIPTION
      "Path: vpnBridgeGroup.performance.pppoEClient.mibCounters.d7Performance.ifOutNUcastPkts

       64 bit unsigned wrappable counter."
   ::= {pr1646v2BgriMVPPPoEMCD7PEntry 201326592}

pr1646v2BgriMVPPPoEMCD7PIfOutBCPkts OBJECT-TYPE
   SYNTAX      Counter64
   MAX-ACCESS  read-only
   STATUS      current
   DESCRIPTION
      "Path: vpnBridgeGroup.performance.pppoEClient.mibCounters.d7Performance.ifOutBcastPkts

       64 bit unsigned wrappable counter."
   ::= {pr1646v2BgriMVPPPoEMCD7PEntry 452984832}

pr1646v2BgriMVPPPoEMCD7PIfOutMCPkts OBJECT-TYPE
   SYNTAX      Counter64
   MAX-ACCESS  read-only
   STATUS      current
   DESCRIPTION
      "Path: vpnBridgeGroup.performance.pppoEClient.mibCounters.d7Performance.ifOutMcastPkts

       64 bit unsigned wrappable counter."
   ::= {pr1646v2BgriMVPPPoEMCD7PEntry 469762048}

pr1646v2BgriMVPPPoEMCD7PIfOutDiscards OBJECT-TYPE
   SYNTAX      Counter64
   MAX-ACCESS  read-only
   STATUS      current
   DESCRIPTION
      "Path: vpnBridgeGroup.performance.pppoEClient.mibCounters.d7Performance.ifOutDiscards

       64 bit unsigned wrappable counter."
   ::= {pr1646v2BgriMVPPPoEMCD7PEntry 218103808}

pr1646v2BgriMVPPPoEMCD7PIfOutErrors OBJECT-TYPE
   SYNTAX      Counter64
   MAX-ACCESS  read-only
   STATUS      current
   DESCRIPTION
      "Path: vpnBridgeGroup.performance.pppoEClient.mibCounters.d7Performance.ifOutErrors

       64 bit unsigned wrappable counter."
   ::= {pr1646v2BgriMVPPPoEMCD7PEntry 234881024}

pr1646v2BgriMVPPPoEMCD7POutDropEx OBJECT-TYPE
   SYNTAX      Counter64
   MAX-ACCESS  read-only
   STATUS      current
   DESCRIPTION
      "Path: vpnBridgeGroup.performance.pppoEClient.mibCounters.d7Performance.ifOutDropLevelExceeded

       64 bit unsigned wrappable counter."
   ::= {pr1646v2BgriMVPPPoEMCD7PEntry 352321536}

pr1646v2BgriMVPPPoEMCD7POutDropNoArp OBJECT-TYPE
   SYNTAX      Counter64
   MAX-ACCESS  read-only
   STATUS      current
   DESCRIPTION
      "Path: vpnBridgeGroup.performance.pppoEClient.mibCounters.d7Performance.ifOutDiscardsNoArp

       64 bit unsigned wrappable counter."
   ::= {pr1646v2BgriMVPPPoEMCD7PEntry 369098752}

pr1646v2BgriMVPPPoEMCD7POutDropFilter OBJECT-TYPE
   SYNTAX      Counter64
   MAX-ACCESS  read-only
   STATUS      current
   DESCRIPTION
      "Path: vpnBridgeGroup.performance.pppoEClient.mibCounters.d7Performance.ifOutDiscardsFilter

       64 bit unsigned wrappable counter."
   ::= {pr1646v2BgriMVPPPoEMCD7PEntry 402653184}

pr1646v2BgriMVPPPoEMCD7PIfOutBandwidth OBJECT-TYPE
   SYNTAX      Integer32
   MAX-ACCESS  read-only
   STATUS      current
   DESCRIPTION
      "Path: vpnBridgeGroup.performance.pppoEClient.mibCounters.d7Performance.ifOutBandwidth

       unit name = bps
       formula = 8 * ; 8 /"
   ::= {pr1646v2BgriMVPPPoEMCD7PEntry 285212672}

pr1646v2BgriMVPPPoEMCD7PIfErrSec OBJECT-TYPE
   SYNTAX      Counter32
   MAX-ACCESS  read-only
   STATUS      current
   DESCRIPTION
      "Path: vpnBridgeGroup.performance.pppoEClient.mibCounters.d7Performance.ifErrSec

       32 bit unsigned wrappable counter."
   ::= {pr1646v2BgriMVPPPoEMCD7PEntry 251658240}



fr1646v2BgriMV OBJECT IDENTIFIER ::= {r1646v2BgriMV 13}


fr1646v2BgriMVAlarm OBJECT IDENTIFIER ::= {fr1646v2BgriMV 207}

fr1646v2BgriMVAlarmSSCTable OBJECT-TYPE
   SYNTAX      SEQUENCE OF Fr1646v2BgriMVAlarmEntry
   MAX-ACCESS  not-accessible
   STATUS      current
   DESCRIPTION
      "bridge group alarmInfo"
   ::= {fr1646v2BgriMVAlarm 1}

fr1646v2BgriMVAlarmEntry OBJECT-TYPE
   SYNTAX      Fr1646v2BgriMVAlarmEntry
   MAX-ACCESS  not-accessible
   STATUS      current
   DESCRIPTION
      ""
   INDEX      { fr1646v2BgriMVAlarmGlobalIx }
   ::= {fr1646v2BgriMVAlarmSSCTable 1}

Fr1646v2BgriMVAlarmEntry ::=
   SEQUENCE
      {
      fr1646v2BgriMVAlarmGlobalIx
         GlobalIndex,
      fr1646v2BgriMVAlarmDiscriminator
         Integer32,
      fr1646v2BgriMVAlarmCurrent
         Integer32,
      fr1646v2BgriMVAlarmPrevious
         Integer32,
      fr1646v2BgriMVAlarmMask
         Integer32,
      fr1646v2BgriMVAlarmLevelLinkDown
         Integer32,
      fr1646v2BgriMVAlarmLevelLinkShutdown
         Integer32
      }

fr1646v2BgriMVAlarmGlobalIx OBJECT-TYPE
   SYNTAX      GlobalIndex
   MAX-ACCESS  not-accessible
   STATUS      current
   DESCRIPTION
      "The value of the tlsCntTreeGlobalIndex of the MANAGED OBJECT."
   ::= {fr1646v2BgriMVAlarmEntry 10}

fr1646v2BgriMVAlarmDiscriminator OBJECT-TYPE
   SYNTAX      Integer32
   MAX-ACCESS  read-only
   STATUS      current
   DESCRIPTION
      "Path: vpnBridgeGroup.alarms.alarmInfo.discriminator"
   ::= {fr1646v2BgriMVAlarmEntry 16777216}

fr1646v2BgriMVAlarmCurrent OBJECT-TYPE
   SYNTAX      Integer32
   MAX-ACCESS  read-only
   STATUS      current
   DESCRIPTION
      "Path: vpnBridgeGroup.alarms.alarmInfo.currentAlarms

       Bit meanings:
               bit 0 = linkDown,
               bit 1 = linkShutdown"
   ::= {fr1646v2BgriMVAlarmEntry 33554432}

fr1646v2BgriMVAlarmPrevious OBJECT-TYPE
   SYNTAX      Integer32
   MAX-ACCESS  read-only
   STATUS      current
   DESCRIPTION
      "Path: vpnBridgeGroup.alarms.alarmInfo.previousAlarms

       Bit meanings:
               bit 0 = linkDown,
               bit 1 = linkShutdown"
   ::= {fr1646v2BgriMVAlarmEntry 50331648}

fr1646v2BgriMVAlarmMask OBJECT-TYPE
   SYNTAX      Integer32
   MAX-ACCESS  read-only
   STATUS      current
   DESCRIPTION
      "Path: vpnBridgeGroup.alarms.alarmInfo.alarmMask

       Bit meanings:
               bit 0 = linkDown,
               bit 1 = linkShutdown"
   ::= {fr1646v2BgriMVAlarmEntry 67108864}

fr1646v2BgriMVAlarmLevelLinkDown OBJECT-TYPE
   SYNTAX      Integer32
   MAX-ACCESS  read-only
   STATUS      current
   DESCRIPTION
      "Path: vpnBridgeGroup.alarms.alarmInfo.alarmLevel.linkDown"
   ::= {fr1646v2BgriMVAlarmEntry 83951616}

fr1646v2BgriMVAlarmLevelLinkShutdown OBJECT-TYPE
   SYNTAX      Integer32
   MAX-ACCESS  read-only
   STATUS      current
   DESCRIPTION
      "Path: vpnBridgeGroup.alarms.alarmInfo.alarmLevel.linkShutdown"
   ::= {fr1646v2BgriMVAlarmEntry 84017152}


fr1646v2BgriMVAlarmE2 OBJECT IDENTIFIER ::= {fr1646v2BgriMVAlarm 2}

fr1646v2BgriMVAlarmE2Entry OBJECT IDENTIFIER ::= {fr1646v2BgriMVAlarmE2 1}

fr1646v2BgriMVAlarmE2LinkDown OBJECT IDENTIFIER ::= {fr1646v2BgriMVAlarmE2Entry 10}

fr1646v2BgriMVAlarmE2LinkDownPfx OBJECT IDENTIFIER ::= {fr1646v2BgriMVAlarmE2LinkDown 0}

fr1646v2BgriMVAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'bridgeGroupInstanceMultiVlansMacEth1'
                (root='router1646') has changed from the ON to the OFF state."
   ::= {fr1646v2BgriMVAlarmE2LinkDownPfx 1}

fr1646v2BgriMVAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'bridgeGroupInstanceMultiVlansMacEth1'
                (root='router1646') has changed from the OFF to the ON state."
   ::= {fr1646v2BgriMVAlarmE2LinkDownPfx 2}

fr1646v2BgriMVAlarmE2LinkShutdown OBJECT IDENTIFIER ::= {fr1646v2BgriMVAlarmE2Entry 11}

fr1646v2BgriMVAlarmE2LinkShutdownPfx OBJECT IDENTIFIER ::= {fr1646v2BgriMVAlarmE2LinkShutdown 0}

fr1646v2BgriMVAlarmE2LinkShutdownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'bridgeGroupInstanceMultiVlansMacEth1'
                (root='router1646') has changed from the ON to the OFF state."
   ::= {fr1646v2BgriMVAlarmE2LinkShutdownPfx 1}

fr1646v2BgriMVAlarmE2LinkShutdownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'bridgeGroupInstanceMultiVlansMacEth1'
                (root='router1646') has changed from the OFF to the ON state."
   ::= {fr1646v2BgriMVAlarmE2LinkShutdownPfx 2}



ar1646v2BgriMV OBJECT IDENTIFIER ::= {r1646v2BgriMV 16}


ar1646v2BgriMVClearCounters OBJECT IDENTIFIER ::= {ar1646v2BgriMV 263}

ar1646v2BgriMVClearCountersTable OBJECT-TYPE
   SYNTAX      SEQUENCE OF Ar1646v2BgriMVClearCountersEntry
   MAX-ACCESS  not-accessible
   STATUS      current
   DESCRIPTION
      "reset counters"
   ::= {ar1646v2BgriMVClearCounters 1}

ar1646v2BgriMVClearCountersEntry OBJECT-TYPE
   SYNTAX      Ar1646v2BgriMVClearCountersEntry
   MAX-ACCESS  not-accessible
   STATUS      current
   DESCRIPTION
      ""
   INDEX      { ar1646v2BgriMVClearCountersGlobalIx }
   ::= {ar1646v2BgriMVClearCountersTable 1}

Ar1646v2BgriMVClearCountersEntry ::=
   SEQUENCE
      {
      ar1646v2BgriMVClearCountersGlobalIx
         GlobalIndex,
      ar1646v2BgriMVClearCountersValue
         Integer32
      }

ar1646v2BgriMVClearCountersGlobalIx OBJECT-TYPE
   SYNTAX      GlobalIndex
   MAX-ACCESS  not-accessible
   STATUS      current
   DESCRIPTION
      "The value of the tlsCntTreeGlobalIndex of the MANAGED OBJECT."
   ::= {ar1646v2BgriMVClearCountersEntry 10}

ar1646v2BgriMVClearCountersValue OBJECT-TYPE
   SYNTAX      Integer32
   MAX-ACCESS  read-write
   STATUS      current
   DESCRIPTION
      "Path: vpnBridgeGroup.actions.clearCounters"
   ::= {ar1646v2BgriMVClearCountersEntry 2147483648}


ar1646v2BgriMVClearBridgeCache OBJECT IDENTIFIER ::= {ar1646v2BgriMV 20}

ar1646v2BgriMVClearBridgeCacheTable OBJECT-TYPE
   SYNTAX      SEQUENCE OF Ar1646v2BgriMVClearBridgeCacheEntry
   MAX-ACCESS  not-accessible
   STATUS      current
   DESCRIPTION
      "clear all dynamic entries in bridge cache table"
   ::= {ar1646v2BgriMVClearBridgeCache 1}

ar1646v2BgriMVClearBridgeCacheEntry OBJECT-TYPE
   SYNTAX      Ar1646v2BgriMVClearBridgeCacheEntry
   MAX-ACCESS  not-accessible
   STATUS      current
   DESCRIPTION
      ""
   INDEX      { ar1646v2BgriMVClearBridgeCacheGlobalIx }
   ::= {ar1646v2BgriMVClearBridgeCacheTable 1}

Ar1646v2BgriMVClearBridgeCacheEntry ::=
   SEQUENCE
      {
      ar1646v2BgriMVClearBridgeCacheGlobalIx
         GlobalIndex,
      ar1646v2BgriMVClearBridgeCacheValue
         Integer32
      }

ar1646v2BgriMVClearBridgeCacheGlobalIx OBJECT-TYPE
   SYNTAX      GlobalIndex
   MAX-ACCESS  not-accessible
   STATUS      current
   DESCRIPTION
      "The value of the tlsCntTreeGlobalIndex of the MANAGED OBJECT."
   ::= {ar1646v2BgriMVClearBridgeCacheEntry 10}

ar1646v2BgriMVClearBridgeCacheValue OBJECT-TYPE
   SYNTAX      Integer32
   MAX-ACCESS  read-write
   STATUS      current
   DESCRIPTION
      "Path: vpnBridgeGroup.actions.clearBridgeCache"
   ::= {ar1646v2BgriMVClearBridgeCacheEntry 2147483648}


ar1646v2BgriMVBridgeShutdown OBJECT IDENTIFIER ::= {ar1646v2BgriMV 72}

ar1646v2BgriMVBridgeShutdownTable OBJECT-TYPE
   SYNTAX      SEQUENCE OF Ar1646v2BgriMVBridgeShutdownEntry
   MAX-ACCESS  not-accessible
   STATUS      current
   DESCRIPTION
      "shutdown interface manually"
   ::= {ar1646v2BgriMVBridgeShutdown 1}

ar1646v2BgriMVBridgeShutdownEntry OBJECT-TYPE
   SYNTAX      Ar1646v2BgriMVBridgeShutdownEntry
   MAX-ACCESS  not-accessible
   STATUS      current
   DESCRIPTION
      ""
   INDEX      { ar1646v2BgriMVBridgeShutdownGlobalIx }
   ::= {ar1646v2BgriMVBridgeShutdownTable 1}

Ar1646v2BgriMVBridgeShutdownEntry ::=
   SEQUENCE
      {
      ar1646v2BgriMVBridgeShutdownGlobalIx
         GlobalIndex,
      ar1646v2BgriMVBridgeShutdownValue
         Integer32
      }

ar1646v2BgriMVBridgeShutdownGlobalIx OBJECT-TYPE
   SYNTAX      GlobalIndex
   MAX-ACCESS  not-accessible
   STATUS      current
   DESCRIPTION
      "The value of the tlsCntTreeGlobalIndex of the MANAGED OBJECT."
   ::= {ar1646v2BgriMVBridgeShutdownEntry 10}

ar1646v2BgriMVBridgeShutdownValue OBJECT-TYPE
   SYNTAX      Integer32
   MAX-ACCESS  read-write
   STATUS      current
   DESCRIPTION
      "Path: vpnBridgeGroup.actions.bridgeShutdown"
   ::= {ar1646v2BgriMVBridgeShutdownEntry 2147483648}


ar1646v2BgriMVInterface OBJECT IDENTIFIER ::= {ar1646v2BgriMV 73}

ar1646v2BgriMVInterfaceTable OBJECT-TYPE
   SYNTAX      SEQUENCE OF Ar1646v2BgriMVInterfaceEntry
   MAX-ACCESS  not-accessible
   STATUS      current
   DESCRIPTION
      "interface name for action"
   ::= {ar1646v2BgriMVInterface 1}

ar1646v2BgriMVInterfaceEntry OBJECT-TYPE
   SYNTAX      Ar1646v2BgriMVInterfaceEntry
   MAX-ACCESS  not-accessible
   STATUS      current
   DESCRIPTION
      ""
   INDEX      { ar1646v2BgriMVInterfaceGlobalIx }
   ::= {ar1646v2BgriMVInterfaceTable 1}

Ar1646v2BgriMVInterfaceEntry ::=
   SEQUENCE
      {
      ar1646v2BgriMVInterfaceGlobalIx
         GlobalIndex,
      ar1646v2BgriMVInterfaceValue
         DisplayString
      }

ar1646v2BgriMVInterfaceGlobalIx OBJECT-TYPE
   SYNTAX      GlobalIndex
   MAX-ACCESS  not-accessible
   STATUS      current
   DESCRIPTION
      "The value of the tlsCntTreeGlobalIndex of the MANAGED OBJECT."
   ::= {ar1646v2BgriMVInterfaceEntry 10}

ar1646v2BgriMVInterfaceValue OBJECT-TYPE
   SYNTAX      DisplayString
   MAX-ACCESS  read-write
   STATUS      current
   DESCRIPTION
      "Path: vpnBridgeGroup.actions.interface"
   ::= {ar1646v2BgriMVInterfaceEntry 2147483648}


ar1646v2BgriMVBridgeRestart OBJECT IDENTIFIER ::= {ar1646v2BgriMV 70}

ar1646v2BgriMVBridgeRestartTable OBJECT-TYPE
   SYNTAX      SEQUENCE OF Ar1646v2BgriMVBridgeRestartEntry
   MAX-ACCESS  not-accessible
   STATUS      current
   DESCRIPTION
      "restart interface blocked by security"
   ::= {ar1646v2BgriMVBridgeRestart 1}

ar1646v2BgriMVBridgeRestartEntry OBJECT-TYPE
   SYNTAX      Ar1646v2BgriMVBridgeRestartEntry
   MAX-ACCESS  not-accessible
   STATUS      current
   DESCRIPTION
      ""
   INDEX      { ar1646v2BgriMVBridgeRestartGlobalIx }
   ::= {ar1646v2BgriMVBridgeRestartTable 1}

Ar1646v2BgriMVBridgeRestartEntry ::=
   SEQUENCE
      {
      ar1646v2BgriMVBridgeRestartGlobalIx
         GlobalIndex,
      ar1646v2BgriMVBridgeRestartValue
         Integer32
      }

ar1646v2BgriMVBridgeRestartGlobalIx OBJECT-TYPE
   SYNTAX      GlobalIndex
   MAX-ACCESS  not-accessible
   STATUS      current
   DESCRIPTION
      "The value of the tlsCntTreeGlobalIndex of the MANAGED OBJECT."
   ::= {ar1646v2BgriMVBridgeRestartEntry 10}

ar1646v2BgriMVBridgeRestartValue OBJECT-TYPE
   SYNTAX      Integer32
   MAX-ACCESS  read-write
   STATUS      current
   DESCRIPTION
      "Path: vpnBridgeGroup.actions.bridgeRestart"
   ::= {ar1646v2BgriMVBridgeRestartEntry 2147483648}


ar1646v2BgriMVBridgingInterface OBJECT IDENTIFIER ::= {ar1646v2BgriMV 71}

ar1646v2BgriMVBridgingInterfaceTable OBJECT-TYPE
   SYNTAX      SEQUENCE OF Ar1646v2BgriMVBridgingInterfaceEntry
   MAX-ACCESS  not-accessible
   STATUS      current
   DESCRIPTION
      "interface name for action"
   ::= {ar1646v2BgriMVBridgingInterface 1}

ar1646v2BgriMVBridgingInterfaceEntry OBJECT-TYPE
   SYNTAX      Ar1646v2BgriMVBridgingInterfaceEntry
   MAX-ACCESS  not-accessible
   STATUS      current
   DESCRIPTION
      ""
   INDEX      { ar1646v2BgriMVBridgingInterfaceGlobalIx }
   ::= {ar1646v2BgriMVBridgingInterfaceTable 1}

Ar1646v2BgriMVBridgingInterfaceEntry ::=
   SEQUENCE
      {
      ar1646v2BgriMVBridgingInterfaceGlobalIx
         GlobalIndex,
      ar1646v2BgriMVBridgingInterfaceValue
         DisplayString
      }

ar1646v2BgriMVBridgingInterfaceGlobalIx OBJECT-TYPE
   SYNTAX      GlobalIndex
   MAX-ACCESS  not-accessible
   STATUS      current
   DESCRIPTION
      "The value of the tlsCntTreeGlobalIndex of the MANAGED OBJECT."
   ::= {ar1646v2BgriMVBridgingInterfaceEntry 10}

ar1646v2BgriMVBridgingInterfaceValue OBJECT-TYPE
   SYNTAX      DisplayString
   MAX-ACCESS  read-write
   STATUS      current
   DESCRIPTION
      "Path: vpnBridgeGroup.actions.bridgingInterface"
   ::= {ar1646v2BgriMVBridgingInterfaceEntry 2147483648}


ar1646v2BgriMVClearArpCache OBJECT IDENTIFIER ::= {ar1646v2BgriMV 25}

ar1646v2BgriMVClearArpCacheTable OBJECT-TYPE
   SYNTAX      SEQUENCE OF Ar1646v2BgriMVClearArpCacheEntry
   MAX-ACCESS  not-accessible
   STATUS      current
   DESCRIPTION
      "clear all dynamic enties in ARP cache table"
   ::= {ar1646v2BgriMVClearArpCache 1}

ar1646v2BgriMVClearArpCacheEntry OBJECT-TYPE
   SYNTAX      Ar1646v2BgriMVClearArpCacheEntry
   MAX-ACCESS  not-accessible
   STATUS      current
   DESCRIPTION
      ""
   INDEX      { ar1646v2BgriMVClearArpCacheGlobalIx }
   ::= {ar1646v2BgriMVClearArpCacheTable 1}

Ar1646v2BgriMVClearArpCacheEntry ::=
   SEQUENCE
      {
      ar1646v2BgriMVClearArpCacheGlobalIx
         GlobalIndex,
      ar1646v2BgriMVClearArpCacheValue
         Integer32
      }

ar1646v2BgriMVClearArpCacheGlobalIx OBJECT-TYPE
   SYNTAX      GlobalIndex
   MAX-ACCESS  not-accessible
   STATUS      current
   DESCRIPTION
      "The value of the tlsCntTreeGlobalIndex of the MANAGED OBJECT."
   ::= {ar1646v2BgriMVClearArpCacheEntry 10}

ar1646v2BgriMVClearArpCacheValue OBJECT-TYPE
   SYNTAX      Integer32
   MAX-ACCESS  read-write
   STATUS      current
   DESCRIPTION
      "Path: vpnBridgeGroup.actions.clearArpCache"
   ::= {ar1646v2BgriMVClearArpCacheEntry 2147483648}



END
