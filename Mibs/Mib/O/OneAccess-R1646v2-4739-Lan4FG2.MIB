OneAccess-R1646v2-4739-Lan4FG2 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Lan4FG2 OBJECT IDENTIFIER ::= {r1646Rootv2 4739}

r1646v2Lan4FG2MOProp OBJECT IDENTIFIER ::= {r1646v2Lan4FG2 1}

r1646v2Lan4FG2MOPropEntry OBJECT IDENTIFIER ::= {r1646v2Lan4FG2MOProp 1}

r1646v2Lan4FG2MOPropPath OBJECT-TYPE
   SYNTAX      ContainmentPath
   MAX-ACCESS  read-only
   STATUS      current
   DESCRIPTION
      "Textual description of the containment tree from the instance of
       the root object down to the instance of the current object."
   ::= {r1646v2Lan4FG2MOPropEntry 3}

r1646v2Lan4FG2MOPropRev OBJECT-TYPE
   SYNTAX      ObjectRevision
   MAX-ACCESS  read-only
   STATUS      current
   DESCRIPTION
      "This value corresponds with the revision of the MANAGED OBJECT."
   ::= {r1646v2Lan4FG2MOPropEntry 4}



sr1646v2Lan4FG2 OBJECT IDENTIFIER ::= {r1646v2Lan4FG2 14}


sr1646v2Lan4FG2SnmpIndex OBJECT-TYPE
   SYNTAX      Integer32
   MAX-ACCESS  read-only
   STATUS      current
   DESCRIPTION
      "Path: ethernet4.status.snmpIndex
       Info: SNMP index assigned to this object"
   ::= {sr1646v2Lan4FG2 269}



ar1646v2Lan4FG2 OBJECT IDENTIFIER ::= {r1646v2Lan4FG2 16}


ar1646v2Lan4FG2PhyAction OBJECT-TYPE
   SYNTAX      Integer32
   MAX-ACCESS  read-write
   STATUS      current
   DESCRIPTION
      "Path: ethernet4.actions.phyAction
       Info: action in the debug group"
   ::= {ar1646v2Lan4FG2 90}



END
