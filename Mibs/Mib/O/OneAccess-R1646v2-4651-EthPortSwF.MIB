OneAccess-R1646v2-4651-EthPortSwF DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2EthPortSwF OBJECT IDENTIFIER ::= {r1646Rootv2 4651}

r1646v2EthPortSwFMOProp OBJECT-TYPE
   SYNTAX      SEQUENCE OF R1646v2EthPortSwFMOPropEntry
   MAX-ACCESS  not-accessible
   STATUS      current
   DESCRIPTION
      ""
   ::= {r1646v2EthPortSwF 1}

r1646v2EthPortSwFMOPropEntry OBJECT-TYPE
   SYNTAX      R1646v2EthPortSwFMOPropEntry
   MAX-ACCESS  not-accessible
   STATUS      current
   DESCRIPTION
      ""
   INDEX      { r1646v2EthPortSwFMOPropGlobalIx }
   ::= {r1646v2EthPortSwFMOProp 1}

R1646v2EthPortSwFMOPropEntry ::=
   SEQUENCE
      {
      r1646v2EthPortSwFMOPropPath
         ContainmentPath,
      r1646v2EthPortSwFMOPropRev
         ObjectRevision,
      r1646v2EthPortSwFMOPropGlobalIx
         GlobalIndex
      }

r1646v2EthPortSwFMOPropPath OBJECT-TYPE
   SYNTAX      ContainmentPath
   MAX-ACCESS  read-only
   STATUS      current
   DESCRIPTION
      "Textual description of the containment tree from the instance of
       the root object down to the instance of the current object."
   ::= {r1646v2EthPortSwFMOPropEntry 3}

r1646v2EthPortSwFMOPropRev OBJECT-TYPE
   SYNTAX      ObjectRevision
   MAX-ACCESS  read-only
   STATUS      current
   DESCRIPTION
      "This value corresponds with the revision of the MANAGED OBJECT."
   ::= {r1646v2EthPortSwFMOPropEntry 4}

r1646v2EthPortSwFMOPropGlobalIx OBJECT-TYPE
   SYNTAX      GlobalIndex
   MAX-ACCESS  read-only
   STATUS      current
   DESCRIPTION
      "The value of the tlsCntTreeGlobalIndex of the MANAGED OBJECT."
   ::= {r1646v2EthPortSwFMOPropEntry 10}



er1646v2EthPortSwF OBJECT IDENTIFIER ::= {r1646v2EthPortSwF 11}


er1646v2EthPortSwFRemark OBJECT IDENTIFIER ::= {er1646v2EthPortSwF 321}

er1646v2EthPortSwFRemarkTable OBJECT-TYPE
   SYNTAX      SEQUENCE OF Er1646v2EthPortSwFRemarkEntry
   MAX-ACCESS  not-accessible
   STATUS      current
   DESCRIPTION
      "intfRemark"
   ::= {er1646v2EthPortSwFRemark 1}

er1646v2EthPortSwFRemarkEntry OBJECT-TYPE
   SYNTAX      Er1646v2EthPortSwFRemarkEntry
   MAX-ACCESS  not-accessible
   STATUS      current
   DESCRIPTION
      ""
   INDEX      { er1646v2EthPortSwFRemarkGlobalIx }
   ::= {er1646v2EthPortSwFRemarkTable 1}

Er1646v2EthPortSwFRemarkEntry ::=
   SEQUENCE
      {
      er1646v2EthPortSwFRemarkGlobalIx
         GlobalIndex,
      er1646v2EthPortSwFRemarkValue
         DisplayString
      }

er1646v2EthPortSwFRemarkGlobalIx OBJECT-TYPE
   SYNTAX      GlobalIndex
   MAX-ACCESS  not-accessible
   STATUS      current
   DESCRIPTION
      "The value of the tlsCntTreeGlobalIndex of the MANAGED OBJECT."
   ::= {er1646v2EthPortSwFRemarkEntry 10}

er1646v2EthPortSwFRemarkValue OBJECT-TYPE
   SYNTAX      DisplayString
   MAX-ACCESS  read-write
   STATUS      current
   DESCRIPTION
      "Path: swPort.editConf.remark"
   ::= {er1646v2EthPortSwFRemarkEntry 2147483648}


er1646v2EthPortSwFArp OBJECT IDENTIFIER ::= {er1646v2EthPortSwF 19}

er1646v2EthPortSwFArpSSCTable OBJECT-TYPE
   SYNTAX      SEQUENCE OF Er1646v2EthPortSwFArpEntry
   MAX-ACCESS  not-accessible
   STATUS      current
   DESCRIPTION
      "ethernet related config parameters"
   ::= {er1646v2EthPortSwFArp 1}

er1646v2EthPortSwFArpEntry OBJECT-TYPE
   SYNTAX      Er1646v2EthPortSwFArpEntry
   MAX-ACCESS  not-accessible
   STATUS      current
   DESCRIPTION
      ""
   INDEX      { er1646v2EthPortSwFArpGlobalIx }
   ::= {er1646v2EthPortSwFArpSSCTable 1}

Er1646v2EthPortSwFArpEntry ::=
   SEQUENCE
      {
      er1646v2EthPortSwFArpGlobalIx
         GlobalIndex,
      er1646v2EthPortSwFArpTimeOut
         TimeTicks,
      er1646v2EthPortSwFArpProxyArp
         INTEGER
      }

er1646v2EthPortSwFArpGlobalIx OBJECT-TYPE
   SYNTAX      GlobalIndex
   MAX-ACCESS  not-accessible
   STATUS      current
   DESCRIPTION
      "The value of the tlsCntTreeGlobalIndex of the MANAGED OBJECT."
   ::= {er1646v2EthPortSwFArpEntry 10}

er1646v2EthPortSwFArpTimeOut OBJECT-TYPE
   SYNTAX      TimeTicks
   MAX-ACCESS  read-write
   STATUS      current
   DESCRIPTION
      "Path: swPort.editConf.arp.timeOut

       Time in centi-second."
   ::= {er1646v2EthPortSwFArpEntry 201326592}

er1646v2EthPortSwFArpProxyArp OBJECT-TYPE
   SYNTAX      INTEGER
               {
               disabled (0),
               enabled (1)
               }
   MAX-ACCESS  read-write
   STATUS      current
   DESCRIPTION
      "Path: swPort.editConf.arp.proxyArp

       Possibilities:
               disabled   (0)
               enabled   (1)"
   ::= {er1646v2EthPortSwFArpEntry 838860800}

er1646v2EthPortSwFArpStaticArp OBJECT-TYPE
   SYNTAX      SEQUENCE OF Er1646v2EthPortSwFArpStaticArpEntry
   MAX-ACCESS  not-accessible
   STATUS      current
   DESCRIPTION
      ""
   ::= {er1646v2EthPortSwFArp 50331648}

er1646v2EthPortSwFArpStaticArpEntry OBJECT-TYPE
   SYNTAX      Er1646v2EthPortSwFArpStaticArpEntry
   MAX-ACCESS  not-accessible
   STATUS      current
   DESCRIPTION
      ""
   INDEX      { er1646v2EthPortSwFArpStaticArpGlobalIx,
                er1646v2EthPortSwFArpStaticArpTableIx }
   ::= {er1646v2EthPortSwFArpStaticArp 1}

Er1646v2EthPortSwFArpStaticArpEntry ::=
   SEQUENCE
      {
      er1646v2EthPortSwFArpStaticArpActions
         VariableLengthTableActions,
      er1646v2EthPortSwFArpStaticArpGlobalIx
         GlobalIndex,
      er1646v2EthPortSwFArpStaticArpTableIx
         TableIndex,
      er1646v2EthPortSwFArpStaticArpMacAddress
         OCTET STRING,
      er1646v2EthPortSwFArpStaticArpIpAddress
         IpAddress
      }

er1646v2EthPortSwFArpStaticArpActions OBJECT-TYPE
   SYNTAX      VariableLengthTableActions
   MAX-ACCESS  read-write
   STATUS      current
   DESCRIPTION
      "By way of this field, some manipulations
       on this table may be performed."
   ::= {er1646v2EthPortSwFArpStaticArpEntry 2}

er1646v2EthPortSwFArpStaticArpGlobalIx OBJECT-TYPE
   SYNTAX      GlobalIndex
   MAX-ACCESS  not-accessible
   STATUS      current
   DESCRIPTION
      "The value of the tlsCntTreeGlobalIndex of the MANAGED OBJECT."
   ::= {er1646v2EthPortSwFArpStaticArpEntry 10}

er1646v2EthPortSwFArpStaticArpTableIx OBJECT-TYPE
   SYNTAX      TableIndex
   MAX-ACCESS  not-accessible
   STATUS      current
   DESCRIPTION
      ""
   ::= {er1646v2EthPortSwFArpStaticArpEntry 11}

er1646v2EthPortSwFArpStaticArpMacAddress OBJECT-TYPE
   SYNTAX      OCTET STRING
   MAX-ACCESS  read-write
   STATUS      current
   DESCRIPTION
      "Path: swPort.editConf.arp.staticArp.macAddress

       MAC address."
   ::= {er1646v2EthPortSwFArpStaticArpEntry 16777216}

er1646v2EthPortSwFArpStaticArpIpAddress OBJECT-TYPE
   SYNTAX      IpAddress
   MAX-ACCESS  read-write
   STATUS      current
   DESCRIPTION
      "Path: swPort.editConf.arp.staticArp.ipAddress"
   ::= {er1646v2EthPortSwFArpStaticArpEntry 33554432}


er1646v2EthPortSwFBrC OBJECT IDENTIFIER ::= {er1646v2EthPortSwF 27}

er1646v2EthPortSwFBrCSSCTable OBJECT-TYPE
   SYNTAX      SEQUENCE OF Er1646v2EthPortSwFBrCEntry
   MAX-ACCESS  not-accessible
   STATUS      current
   DESCRIPTION
      "Set bridging parameters"
   ::= {er1646v2EthPortSwFBrC 1}

er1646v2EthPortSwFBrCEntry OBJECT-TYPE
   SYNTAX      Er1646v2EthPortSwFBrCEntry
   MAX-ACCESS  not-accessible
   STATUS      current
   DESCRIPTION
      ""
   INDEX      { er1646v2EthPortSwFBrCGlobalIx }
   ::= {er1646v2EthPortSwFBrCSSCTable 1}

Er1646v2EthPortSwFBrCEntry ::=
   SEQUENCE
      {
      er1646v2EthPortSwFBrCGlobalIx
         GlobalIndex,
      er1646v2EthPortSwFBrCAccessList
         DisplayString,
      er1646v2EthPortSwFBrCInAccessList
         DisplayString,
      er1646v2EthPortSwFBrCTp
         DisplayString,
      er1646v2EthPortSwFBrCBridgeGroup
         DisplayString,
      er1646v2EthPortSwFBrCLimBC
         INTEGER,
      er1646v2EthPortSwFBrCPrivateMode
         INTEGER,
      er1646v2EthPortSwFBrCLearning
         INTEGER,
      er1646v2EthPortSwFBrCMaxCacheSize
         INTEGER,
      er1646v2EthPortSwFBrCRelearnDropOnRelearn
         INTEGER,
      er1646v2EthPortSwFBrCRelearnShutdownThreshold
         Integer32,
      er1646v2EthPortSwFBrCRelearnShutdownTime
         TimeTicks,
      er1646v2EthPortSwFBrCRelearnLoopDetection
         INTEGER,
      er1646v2EthPortSwFBrCRelearnLoopDetectionInterval
         TimeTicks,
      er1646v2EthPortSwFBrCVlanMemberShip
         INTEGER,
      er1646v2EthPortSwFBrCDot1adType
         INTEGER,
      er1646v2EthPortSwFBrCPriority
         Integer32,
      er1646v2EthPortSwFBrCPathCost
         Integer32,
      er1646v2EthPortSwFBrCInternalPathCost
         Integer32,
      er1646v2EthPortSwFBrCTCD
         INTEGER,
      er1646v2EthPortSwFBrCRestrictedRole
         INTEGER,
      er1646v2EthPortSwFBrCAdminEdge
         INTEGER,
      er1646v2EthPortSwFBrCMgmtInline
         INTEGER,
      er1646v2EthPortSwFBrCL2ptMode
         INTEGER,
      er1646v2EthPortSwFBrCL2ptProtocols
         Integer32,
      er1646v2EthPortSwFBrCL2ptDestMac
         OCTET STRING,
      er1646v2EthPortSwFBrCL2ptCos
         INTEGER,
      er1646v2EthPortSwFBrCL2ptDropThrStp
         INTEGER,
      er1646v2EthPortSwFBrCL2ptDropThrLldp
         INTEGER,
      er1646v2EthPortSwFBrCL2ptDropThrOam
         INTEGER,
      er1646v2EthPortSwFBrCL2ptDropThrCdp
         INTEGER,
      er1646v2EthPortSwFBrCL2ptDropThrVtp
         INTEGER,
      er1646v2EthPortSwFBrCL2ptDropThrLacp
         INTEGER,
      er1646v2EthPortSwFBrCL2ptDropThrEfmOam
         INTEGER,
      er1646v2EthPortSwFBrCL2ptDropThrPvst
         INTEGER,
      er1646v2EthPortSwFBrCL2ptDropThrMmrp
         INTEGER,
      er1646v2EthPortSwFBrCL2ptDropThrMvrp
         INTEGER,
      er1646v2EthPortSwFBrCL2ptDropThrGvrp
         INTEGER,
      er1646v2EthPortSwFBrCL2ptDropThrGmrp
         INTEGER,
      er1646v2EthPortSwFBrCL2ptDropThrDtp
         INTEGER,
      er1646v2EthPortSwFBrCL2ptDropThrPagp
         INTEGER,
      er1646v2EthPortSwFBrCL2ptDropThrUdld
         INTEGER
      }

er1646v2EthPortSwFBrCGlobalIx OBJECT-TYPE
   SYNTAX      GlobalIndex
   MAX-ACCESS  not-accessible
   STATUS      current
   DESCRIPTION
      "The value of the tlsCntTreeGlobalIndex of the MANAGED OBJECT."
   ::= {er1646v2EthPortSwFBrCEntry 10}

er1646v2EthPortSwFBrCAccessList OBJECT-TYPE
   SYNTAX      DisplayString
   MAX-ACCESS  read-write
   STATUS      current
   DESCRIPTION
      "Path: swPort.editConf.bridging.accessList"
   ::= {er1646v2EthPortSwFBrCEntry 83886080}

er1646v2EthPortSwFBrCInAccessList OBJECT-TYPE
   SYNTAX      DisplayString
   MAX-ACCESS  read-write
   STATUS      current
   DESCRIPTION
      "Path: swPort.editConf.bridging.inAccessList"
   ::= {er1646v2EthPortSwFBrCEntry 251658240}

er1646v2EthPortSwFBrCTp OBJECT-TYPE
   SYNTAX      DisplayString
   MAX-ACCESS  read-write
   STATUS      current
   DESCRIPTION
      "Path: swPort.editConf.bridging.trafficPolicy"
   ::= {er1646v2EthPortSwFBrCEntry 100663296}

er1646v2EthPortSwFBrCBridgeGroup OBJECT-TYPE
   SYNTAX      DisplayString
   MAX-ACCESS  read-write
   STATUS      current
   DESCRIPTION
      "Path: swPort.editConf.bridging.bridgeGroup"
   ::= {er1646v2EthPortSwFBrCEntry 117440512}

er1646v2EthPortSwFBrCLimBC OBJECT-TYPE
   SYNTAX      INTEGER
               {
               disabled (0),
               enabled (1)
               }
   MAX-ACCESS  read-write
   STATUS      current
   DESCRIPTION
      "Path: swPort.editConf.bridging.limitBroadcasts

       Possibilities:
               disabled   (0)
               enabled   (1)"
   ::= {er1646v2EthPortSwFBrCEntry 134217728}

er1646v2EthPortSwFBrCPrivateMode OBJECT-TYPE
   SYNTAX      INTEGER
               {
               disabled (0),
               enabled (1)
               }
   MAX-ACCESS  read-write
   STATUS      current
   DESCRIPTION
      "Path: swPort.editConf.bridging.privateMode

       Possibilities:
               disabled   (0)
               enabled   (1)"
   ::= {er1646v2EthPortSwFBrCEntry 419430400}

er1646v2EthPortSwFBrCLearning OBJECT-TYPE
   SYNTAX      INTEGER
               {
               disabled (0),
               enabled (1)
               }
   MAX-ACCESS  read-write
   STATUS      current
   DESCRIPTION
      "Path: swPort.editConf.bridging.learning

       Possibilities:
               disabled   (0)
               enabled   (1)"
   ::= {er1646v2EthPortSwFBrCEntry 201326592}

er1646v2EthPortSwFBrCMaxCacheSize OBJECT-TYPE
   SYNTAX      INTEGER
               {
               unlimited (0)
               }
   MAX-ACCESS  read-write
   STATUS      current
   DESCRIPTION
      "Path: swPort.editConf.bridging.maxCacheSize

       Possibilities:
               unlimited   (0)"
   ::= {er1646v2EthPortSwFBrCEntry 218103808}

er1646v2EthPortSwFBrCRelearnDropOnRelearn OBJECT-TYPE
   SYNTAX      INTEGER
               {
               disabled (0),
               enabled (1)
               }
   MAX-ACCESS  read-write
   STATUS      current
   DESCRIPTION
      "Path: swPort.editConf.bridging.relearn.dropOnRelearn

       Possibilities:
               disabled   (0)
               enabled   (1)"
   ::= {er1646v2EthPortSwFBrCEntry 234946560}

er1646v2EthPortSwFBrCRelearnShutdownThreshold OBJECT-TYPE
   SYNTAX      Integer32
   MAX-ACCESS  read-write
   STATUS      current
   DESCRIPTION
      "Path: swPort.editConf.bridging.relearn.shutdownThreshold"
   ::= {er1646v2EthPortSwFBrCEntry 235012096}

er1646v2EthPortSwFBrCRelearnShutdownTime OBJECT-TYPE
   SYNTAX      TimeTicks
   MAX-ACCESS  read-write
   STATUS      current
   DESCRIPTION
      "Path: swPort.editConf.bridging.relearn.shutdownTime

       Time in centi-second."
   ::= {er1646v2EthPortSwFBrCEntry 235077632}

er1646v2EthPortSwFBrCRelearnLoopDetection OBJECT-TYPE
   SYNTAX      INTEGER
               {
               disabled (0),
               passive (1),
               active (2)
               }
   MAX-ACCESS  read-write
   STATUS      current
   DESCRIPTION
      "Path: swPort.editConf.bridging.relearn.loopDetection

       Possibilities:
               disabled   (0)
               passive   (1)
               active   (2)"
   ::= {er1646v2EthPortSwFBrCEntry 235143168}

er1646v2EthPortSwFBrCRelearnLoopDetectionInterval OBJECT-TYPE
   SYNTAX      TimeTicks
   MAX-ACCESS  read-write
   STATUS      current
   DESCRIPTION
      "Path: swPort.editConf.bridging.relearn.loopDetectionInterval

       Time in centi-second."
   ::= {er1646v2EthPortSwFBrCEntry 235208704}

er1646v2EthPortSwFBrCVlanMemberShip OBJECT-TYPE
   SYNTAX      INTEGER
               {
               all (0),
               none (1),
               grouped (2)
               }
   MAX-ACCESS  read-write
   STATUS      current
   DESCRIPTION
      "Path: swPort.editConf.bridging.vlanMemberShip

       Possibilities:
               all   (0)
               none   (1)
               grouped   (2)"
   ::= {er1646v2EthPortSwFBrCEntry 318767104}

er1646v2EthPortSwFBrCDot1adType OBJECT-TYPE
   SYNTAX      INTEGER
               {
               slOPTg (0),
               cPort (4),
               sPort (1),
               nni (2)
               }
   MAX-ACCESS  read-write
   STATUS      current
   DESCRIPTION
      "Path: swPort.editConf.bridging.dot1ad.type

       Possibilities:
               <OPT>   (0)
               cPort   (4)
               sPort   (1)
               nni   (2)"
   ::= {er1646v2EthPortSwFBrCEntry 503382016}

er1646v2EthPortSwFBrCPriority OBJECT-TYPE
   SYNTAX      Integer32
   MAX-ACCESS  read-write
   STATUS      current
   DESCRIPTION
      "Path: swPort.editConf.bridging.priority"
   ::= {er1646v2EthPortSwFBrCEntry 33554432}

er1646v2EthPortSwFBrCPathCost OBJECT-TYPE
   SYNTAX      Integer32
   MAX-ACCESS  read-write
   STATUS      current
   DESCRIPTION
      "Path: swPort.editConf.bridging.pathCost"
   ::= {er1646v2EthPortSwFBrCEntry 50331648}

er1646v2EthPortSwFBrCInternalPathCost OBJECT-TYPE
   SYNTAX      Integer32
   MAX-ACCESS  read-write
   STATUS      current
   DESCRIPTION
      "Path: swPort.editConf.bridging.internalPathCost"
   ::= {er1646v2EthPortSwFBrCEntry 301989888}

er1646v2EthPortSwFBrCTCD OBJECT-TYPE
   SYNTAX      INTEGER
               {
               disabled (0),
               enabled (1)
               }
   MAX-ACCESS  read-write
   STATUS      current
   DESCRIPTION
      "Path: swPort.editConf.bridging.topologyChangeDetection

       Possibilities:
               disabled   (0)
               enabled   (1)"
   ::= {er1646v2EthPortSwFBrCEntry 67108864}

er1646v2EthPortSwFBrCRestrictedRole OBJECT-TYPE
   SYNTAX      INTEGER
               {
               disabled (0),
               enabled (1)
               }
   MAX-ACCESS  read-write
   STATUS      current
   DESCRIPTION
      "Path: swPort.editConf.bridging.restrictedRole

       Possibilities:
               disabled   (0)
               enabled   (1)"
   ::= {er1646v2EthPortSwFBrCEntry 335544320}

er1646v2EthPortSwFBrCAdminEdge OBJECT-TYPE
   SYNTAX      INTEGER
               {
               disabled (0),
               enabled (1)
               }
   MAX-ACCESS  read-write
   STATUS      current
   DESCRIPTION
      "Path: swPort.editConf.bridging.adminEdge

       Possibilities:
               disabled   (0)
               enabled   (1)"
   ::= {er1646v2EthPortSwFBrCEntry 268435456}

er1646v2EthPortSwFBrCMgmtInline OBJECT-TYPE
   SYNTAX      INTEGER
               {
               disabled (0),
               enabled (1)
               }
   MAX-ACCESS  read-write
   STATUS      current
   DESCRIPTION
      "Path: swPort.editConf.bridging.mgmtInline

       Possibilities:
               disabled   (0)
               enabled   (1)"
   ::= {er1646v2EthPortSwFBrCEntry 369098752}

er1646v2EthPortSwFBrCL2ptMode OBJECT-TYPE
   SYNTAX      INTEGER
               {
               disabled (0),
               enabled (1)
               }
   MAX-ACCESS  read-write
   STATUS      current
   DESCRIPTION
      "Path: swPort.editConf.bridging.l2ProtTunnel.mode

       Possibilities:
               disabled   (0)
               enabled   (1)"
   ::= {er1646v2EthPortSwFBrCEntry 403701760}

er1646v2EthPortSwFBrCL2ptProtocols OBJECT-TYPE
   SYNTAX      Integer32
   MAX-ACCESS  read-write
   STATUS      current
   DESCRIPTION
      "Path: swPort.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EthPortSwFBrCEntry 404750336}

er1646v2EthPortSwFBrCL2ptDestMac OBJECT-TYPE
   SYNTAX      OCTET STRING
   MAX-ACCESS  read-write
   STATUS      current
   DESCRIPTION
      "Path: swPort.editConf.bridging.l2ProtTunnel.destinationMac

       MAC address."
   ::= {er1646v2EthPortSwFBrCEntry 405798912}

er1646v2EthPortSwFBrCL2ptCos OBJECT-TYPE
   SYNTAX      INTEGER
               {
               unchanged (255)
               }
   MAX-ACCESS  read-write
   STATUS      current
   DESCRIPTION
      "Path: swPort.editConf.bridging.l2ProtTunnel.cos

       Possibilities:
               unchanged   (255)"
   ::= {er1646v2EthPortSwFBrCEntry 406847488}

er1646v2EthPortSwFBrCL2ptDropThrStp OBJECT-TYPE
   SYNTAX      INTEGER
               {
               unlimited (0)
               }
   UNITS       "packets/sec"
   MAX-ACCESS  read-write
   STATUS      current
   DESCRIPTION
      "Path: swPort.editConf.bridging.l2ProtTunnel.dropThresholds.stp

       unit name = packets/sec

       Possibilities:
               unlimited   (0)"
   ::= {er1646v2EthPortSwFBrCEntry 407900160}

er1646v2EthPortSwFBrCL2ptDropThrLldp OBJECT-TYPE
   SYNTAX      INTEGER
               {
               unlimited (0)
               }
   UNITS       "packets/sec"
   MAX-ACCESS  read-write
   STATUS      current
   DESCRIPTION
      "Path: swPort.editConf.bridging.l2ProtTunnel.dropThresholds.lldp

       unit name = packets/sec

       Possibilities:
               unlimited   (0)"
   ::= {er1646v2EthPortSwFBrCEntry 407904256}

er1646v2EthPortSwFBrCL2ptDropThrOam OBJECT-TYPE
   SYNTAX      INTEGER
               {
               unlimited (0)
               }
   UNITS       "packets/sec"
   MAX-ACCESS  read-write
   STATUS      current
   DESCRIPTION
      "Path: swPort.editConf.bridging.l2ProtTunnel.dropThresholds.oam

       unit name = packets/sec

       Possibilities:
               unlimited   (0)"
   ::= {er1646v2EthPortSwFBrCEntry 407908352}

er1646v2EthPortSwFBrCL2ptDropThrCdp OBJECT-TYPE
   SYNTAX      INTEGER
               {
               unlimited (0)
               }
   UNITS       "packets/sec"
   MAX-ACCESS  read-write
   STATUS      current
   DESCRIPTION
      "Path: swPort.editConf.bridging.l2ProtTunnel.dropThresholds.cdp

       unit name = packets/sec

       Possibilities:
               unlimited   (0)"
   ::= {er1646v2EthPortSwFBrCEntry 407912448}

er1646v2EthPortSwFBrCL2ptDropThrVtp OBJECT-TYPE
   SYNTAX      INTEGER
               {
               unlimited (0)
               }
   UNITS       "packets/sec"
   MAX-ACCESS  read-write
   STATUS      current
   DESCRIPTION
      "Path: swPort.editConf.bridging.l2ProtTunnel.dropThresholds.vtp

       unit name = packets/sec

       Possibilities:
               unlimited   (0)"
   ::= {er1646v2EthPortSwFBrCEntry 407916544}

er1646v2EthPortSwFBrCL2ptDropThrLacp OBJECT-TYPE
   SYNTAX      INTEGER
               {
               unlimited (0)
               }
   UNITS       "packets/sec"
   MAX-ACCESS  read-write
   STATUS      current
   DESCRIPTION
      "Path: swPort.editConf.bridging.l2ProtTunnel.dropThresholds.lacp

       unit name = packets/sec

       Possibilities:
               unlimited   (0)"
   ::= {er1646v2EthPortSwFBrCEntry 407920640}

er1646v2EthPortSwFBrCL2ptDropThrEfmOam OBJECT-TYPE
   SYNTAX      INTEGER
               {
               unlimited (0)
               }
   UNITS       "packets/sec"
   MAX-ACCESS  read-write
   STATUS      current
   DESCRIPTION
      "Path: swPort.editConf.bridging.l2ProtTunnel.dropThresholds.efmOam

       unit name = packets/sec

       Possibilities:
               unlimited   (0)"
   ::= {er1646v2EthPortSwFBrCEntry 407924736}

er1646v2EthPortSwFBrCL2ptDropThrPvst OBJECT-TYPE
   SYNTAX      INTEGER
               {
               unlimited (0)
               }
   UNITS       "packets/sec"
   MAX-ACCESS  read-write
   STATUS      current
   DESCRIPTION
      "Path: swPort.editConf.bridging.l2ProtTunnel.dropThresholds.pvst

       unit name = packets/sec

       Possibilities:
               unlimited   (0)"
   ::= {er1646v2EthPortSwFBrCEntry 407928832}

er1646v2EthPortSwFBrCL2ptDropThrMmrp OBJECT-TYPE
   SYNTAX      INTEGER
               {
               unlimited (0)
               }
   UNITS       "packets/sec"
   MAX-ACCESS  read-write
   STATUS      current
   DESCRIPTION
      "Path: swPort.editConf.bridging.l2ProtTunnel.dropThresholds.mmrp

       unit name = packets/sec

       Possibilities:
               unlimited   (0)"
   ::= {er1646v2EthPortSwFBrCEntry 407932928}

er1646v2EthPortSwFBrCL2ptDropThrMvrp OBJECT-TYPE
   SYNTAX      INTEGER
               {
               unlimited (0)
               }
   UNITS       "packets/sec"
   MAX-ACCESS  read-write
   STATUS      current
   DESCRIPTION
      "Path: swPort.editConf.bridging.l2ProtTunnel.dropThresholds.mvrp

       unit name = packets/sec

       Possibilities:
               unlimited   (0)"
   ::= {er1646v2EthPortSwFBrCEntry 407937024}

er1646v2EthPortSwFBrCL2ptDropThrGvrp OBJECT-TYPE
   SYNTAX      INTEGER
               {
               unlimited (0)
               }
   UNITS       "packets/sec"
   MAX-ACCESS  read-write
   STATUS      current
   DESCRIPTION
      "Path: swPort.editConf.bridging.l2ProtTunnel.dropThresholds.gvrp

       unit name = packets/sec

       Possibilities:
               unlimited   (0)"
   ::= {er1646v2EthPortSwFBrCEntry 407941120}

er1646v2EthPortSwFBrCL2ptDropThrGmrp OBJECT-TYPE
   SYNTAX      INTEGER
               {
               unlimited (0)
               }
   UNITS       "packets/sec"
   MAX-ACCESS  read-write
   STATUS      current
   DESCRIPTION
      "Path: swPort.editConf.bridging.l2ProtTunnel.dropThresholds.gmrp

       unit name = packets/sec

       Possibilities:
               unlimited   (0)"
   ::= {er1646v2EthPortSwFBrCEntry 407945216}

er1646v2EthPortSwFBrCL2ptDropThrDtp OBJECT-TYPE
   SYNTAX      INTEGER
               {
               unlimited (0)
               }
   UNITS       "packets/sec"
   MAX-ACCESS  read-write
   STATUS      current
   DESCRIPTION
      "Path: swPort.editConf.bridging.l2ProtTunnel.dropThresholds.dtp

       unit name = packets/sec

       Possibilities:
               unlimited   (0)"
   ::= {er1646v2EthPortSwFBrCEntry 407949312}

er1646v2EthPortSwFBrCL2ptDropThrPagp OBJECT-TYPE
   SYNTAX      INTEGER
               {
               unlimited (0)
               }
   UNITS       "packets/sec"
   MAX-ACCESS  read-write
   STATUS      current
   DESCRIPTION
      "Path: swPort.editConf.bridging.l2ProtTunnel.dropThresholds.pagp

       unit name = packets/sec

       Possibilities:
               unlimited   (0)"
   ::= {er1646v2EthPortSwFBrCEntry 407953408}

er1646v2EthPortSwFBrCL2ptDropThrUdld OBJECT-TYPE
   SYNTAX      INTEGER
               {
               unlimited (0)
               }
   UNITS       "packets/sec"
   MAX-ACCESS  read-write
   STATUS      current
   DESCRIPTION
      "Path: swPort.editConf.bridging.l2ProtTunnel.dropThresholds.udld

       unit name = packets/sec

       Possibilities:
               unlimited   (0)"
   ::= {er1646v2EthPortSwFBrCEntry 407957504}


er1646v2EthPortSwFVlanTagging OBJECT IDENTIFIER ::= {er1646v2EthPortSwF 14}

er1646v2EthPortSwFVlanTaggingSSCTable OBJECT-TYPE
   SYNTAX      SEQUENCE OF Er1646v2EthPortSwFVlanTaggingEntry
   MAX-ACCESS  not-accessible
   STATUS      current
   DESCRIPTION
      "vlan tagging config"
   ::= {er1646v2EthPortSwFVlanTagging 1}

er1646v2EthPortSwFVlanTaggingEntry OBJECT-TYPE
   SYNTAX      Er1646v2EthPortSwFVlanTaggingEntry
   MAX-ACCESS  not-accessible
   STATUS      current
   DESCRIPTION
      ""
   INDEX      { er1646v2EthPortSwFVlanTaggingGlobalIx }
   ::= {er1646v2EthPortSwFVlanTaggingSSCTable 1}

Er1646v2EthPortSwFVlanTaggingEntry ::=
   SEQUENCE
      {
      er1646v2EthPortSwFVlanTaggingGlobalIx
         GlobalIndex,
      er1646v2EthPortSwFVlanTaggingUntaggedAction
         INTEGER,
      er1646v2EthPortSwFVlanTaggingUntaggedTagInfoTpid
         INTEGER,
      er1646v2EthPortSwFVlanTaggingUntaggedTagInfoVid
         Integer32,
      er1646v2EthPortSwFVlanTaggingUnknownVlansAction
         INTEGER,
      er1646v2EthPortSwFVlanTaggingUnknownVlansTagInfoTpid
         INTEGER,
      er1646v2EthPortSwFVlanTaggingUnknownVlansTagInfoVid
         Integer32
      }

er1646v2EthPortSwFVlanTaggingGlobalIx OBJECT-TYPE
   SYNTAX      GlobalIndex
   MAX-ACCESS  not-accessible
   STATUS      current
   DESCRIPTION
      "The value of the tlsCntTreeGlobalIndex of the MANAGED OBJECT."
   ::= {er1646v2EthPortSwFVlanTaggingEntry 10}

er1646v2EthPortSwFVlanTaggingUntaggedAction OBJECT-TYPE
   SYNTAX      INTEGER
               {
               discard (0),
               accept (1),
               tag (2)
               }
   MAX-ACCESS  read-write
   STATUS      current
   DESCRIPTION
      "Path: swPort.editConf.vlanTagging.untagged.action

       Possibilities:
               discard   (0)
               accept   (1)
               tag   (2)"
   ::= {er1646v2EthPortSwFVlanTaggingEntry 671088640}

er1646v2EthPortSwFVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.untagged.tagInfo.tpid

       Possibilities:
               dot1Q   (33024)
               dot1ad   (34984)
               0x9100   (37120)
               0x9200   (37376)
               0x9300   (37632)"
   ::= {er1646v2EthPortSwFVlanTaggingEntry 746586112}

er1646v2EthPortSwFVlanTaggingUntaggedTagInfoVid OBJECT-TYPE
   SYNTAX      Integer32
   MAX-ACCESS  read-write
   STATUS      current
   DESCRIPTION
      "Path: swPort.editConf.vlanTagging.untagged.tagInfo.vid"
   ::= {er1646v2EthPortSwFVlanTaggingEntry 754974720}

er1646v2EthPortSwFVlanTaggingUnknownVlansAction OBJECT-TYPE
   SYNTAX      INTEGER
               {
               discard (0),
               accept (1),
               tag (2)
               }
   MAX-ACCESS  read-write
   STATUS      current
   DESCRIPTION
      "Path: swPort.editConf.vlanTagging.unknownVlans.action

       Possibilities:
               discard   (0)
               accept   (1)
               tag   (2)"
   ::= {er1646v2EthPortSwFVlanTaggingEntry 1744830464}

er1646v2EthPortSwFVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.unknownVlans.tagInfo.tpid

       Possibilities:
               dot1Q   (33024)
               dot1ad   (34984)
               0x9100   (37120)
               0x9200   (37376)
               0x9300   (37632)"
   ::= {er1646v2EthPortSwFVlanTaggingEntry 1820327936}

er1646v2EthPortSwFVlanTaggingUnknownVlansTagInfoVid OBJECT-TYPE
   SYNTAX      Integer32
   MAX-ACCESS  read-write
   STATUS      current
   DESCRIPTION
      "Path: swPort.editConf.vlanTagging.unknownVlans.tagInfo.vid"
   ::= {er1646v2EthPortSwFVlanTaggingEntry 1828716544}

er1646v2EthPortSwFVlanTaggingVlans OBJECT-TYPE
   SYNTAX      SEQUENCE OF Er1646v2EthPortSwFVlanTaggingVlansEntry
   MAX-ACCESS  not-accessible
   STATUS      current
   DESCRIPTION
      ""
   ::= {er1646v2EthPortSwFVlanTagging 1073741824}

er1646v2EthPortSwFVlanTaggingVlansEntry OBJECT-TYPE
   SYNTAX      Er1646v2EthPortSwFVlanTaggingVlansEntry
   MAX-ACCESS  not-accessible
   STATUS      current
   DESCRIPTION
      ""
   INDEX      { er1646v2EthPortSwFVlanTaggingVlansGlobalIx,
                er1646v2EthPortSwFVlanTaggingVlansTableIx }
   ::= {er1646v2EthPortSwFVlanTaggingVlans 1}

Er1646v2EthPortSwFVlanTaggingVlansEntry ::=
   SEQUENCE
      {
      er1646v2EthPortSwFVlanTaggingVlansActions
         VariableLengthTableActions,
      er1646v2EthPortSwFVlanTaggingVlansGlobalIx
         GlobalIndex,
      er1646v2EthPortSwFVlanTaggingVlansTableIx
         TableIndex,
      er1646v2EthPortSwFVlanTaggingVlansVid
         Integer32,
      er1646v2EthPortSwFVlanTaggingVlansEndVid
         Integer32,
      er1646v2EthPortSwFVlanTaggingVlansAction
         INTEGER,
      er1646v2EthPortSwFVlanTaggingVlansTagInfoTpid
         INTEGER,
      er1646v2EthPortSwFVlanTaggingVlansTagInfoVid
         Integer32
      }

er1646v2EthPortSwFVlanTaggingVlansActions OBJECT-TYPE
   SYNTAX      VariableLengthTableActions
   MAX-ACCESS  read-write
   STATUS      current
   DESCRIPTION
      "By way of this field, some manipulations
       on this table may be performed."
   ::= {er1646v2EthPortSwFVlanTaggingVlansEntry 2}

er1646v2EthPortSwFVlanTaggingVlansGlobalIx OBJECT-TYPE
   SYNTAX      GlobalIndex
   MAX-ACCESS  not-accessible
   STATUS      current
   DESCRIPTION
      "The value of the tlsCntTreeGlobalIndex of the MANAGED OBJECT."
   ::= {er1646v2EthPortSwFVlanTaggingVlansEntry 10}

er1646v2EthPortSwFVlanTaggingVlansTableIx OBJECT-TYPE
   SYNTAX      TableIndex
   MAX-ACCESS  not-accessible
   STATUS      current
   DESCRIPTION
      ""
   ::= {er1646v2EthPortSwFVlanTaggingVlansEntry 11}

er1646v2EthPortSwFVlanTaggingVlansVid OBJECT-TYPE
   SYNTAX      Integer32
   MAX-ACCESS  read-write
   STATUS      current
   DESCRIPTION
      "Path: swPort.editConf.vlanTagging.vlans.vid"
   ::= {er1646v2EthPortSwFVlanTaggingVlansEntry 536870912}

er1646v2EthPortSwFVlanTaggingVlansEndVid OBJECT-TYPE
   SYNTAX      Integer32
   MAX-ACCESS  read-write
   STATUS      current
   DESCRIPTION
      "Path: swPort.editConf.vlanTagging.vlans.endVid"
   ::= {er1646v2EthPortSwFVlanTaggingVlansEntry 2147483648}

er1646v2EthPortSwFVlanTaggingVlansAction OBJECT-TYPE
   SYNTAX      INTEGER
               {
               discard (0),
               accept (1),
               tag (2)
               }
   MAX-ACCESS  read-write
   STATUS      current
   DESCRIPTION
      "Path: swPort.editConf.vlanTagging.vlans.action

       Possibilities:
               discard   (0)
               accept   (1)
               tag   (2)"
   ::= {er1646v2EthPortSwFVlanTaggingVlansEntry 1073741824}

er1646v2EthPortSwFVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.vlans.tagInfo.tpid

       Possibilities:
               dot1Q   (33024)
               dot1ad   (34984)
               0x9100   (37120)
               0x9200   (37376)
               0x9300   (37632)"
   ::= {er1646v2EthPortSwFVlanTaggingVlansEntry 1677721600}

er1646v2EthPortSwFVlanTaggingVlansTagInfoVid OBJECT-TYPE
   SYNTAX      Integer32
   MAX-ACCESS  read-write
   STATUS      current
   DESCRIPTION
      "Path: swPort.editConf.vlanTagging.vlans.tagInfo.vid"
   ::= {er1646v2EthPortSwFVlanTaggingVlansEntry 1744830464}


er1646v2EthPortSwFOam OBJECT IDENTIFIER ::= {er1646v2EthPortSwF 900}

er1646v2EthPortSwFOamSSCTable OBJECT-TYPE
   SYNTAX      SEQUENCE OF Er1646v2EthPortSwFOamEntry
   MAX-ACCESS  not-accessible
   STATUS      current
   DESCRIPTION
      "OAM mode"
   ::= {er1646v2EthPortSwFOam 1}

er1646v2EthPortSwFOamEntry OBJECT-TYPE
   SYNTAX      Er1646v2EthPortSwFOamEntry
   MAX-ACCESS  not-accessible
   STATUS      current
   DESCRIPTION
      ""
   INDEX      { er1646v2EthPortSwFOamGlobalIx }
   ::= {er1646v2EthPortSwFOamSSCTable 1}

Er1646v2EthPortSwFOamEntry ::=
   SEQUENCE
      {
      er1646v2EthPortSwFOamGlobalIx
         GlobalIndex,
      er1646v2EthPortSwFOamMode
         INTEGER,
      er1646v2EthPortSwFOamLpbkLocalParAction
         INTEGER,
      er1646v2EthPortSwFOamLpbkSwapMacAddr
         INTEGER,
      er1646v2EthPortSwFOamLoopbackIgnoreRx
         INTEGER,
      er1646v2EthPortSwFOamEventsErroredSymbolEnabled
         INTEGER,
      er1646v2EthPortSwFOamEventsErroredSymbolWindowHi
         INTEGER,
      er1646v2EthPortSwFOamEventsErroredSymbolWindowLo
         INTEGER,
      er1646v2EthPortSwFOamEventsErroredSymbolThresholdHi
         Integer32,
      er1646v2EthPortSwFOamEventsErroredSymbolThresholdLo
         Integer32,
      er1646v2EthPortSwFOamEventsErroredFramePeriodEnabled
         INTEGER,
      er1646v2EthPortSwFOamEventsErroredFramePeriodWindow
         INTEGER,
      er1646v2EthPortSwFOamEventsErroredFramePeriodThreshold
         Integer32,
      er1646v2EthPortSwFOamEventsErroredFrameEnabled
         INTEGER,
      er1646v2EthPortSwFOamEventsErroredFrameWindow
         Integer32,
      er1646v2EthPortSwFOamEventsErroredFrameThreshold
         Integer32,
      er1646v2EthPortSwFOamEventsErroredFrameSecondsEnabled
         INTEGER,
      er1646v2EthPortSwFOamEventsErroredFrameSecondsWindow
         Integer32,
      er1646v2EthPortSwFOamEventsErroredFrameSecondsThreshold
         Integer32,
      er1646v2EthPortSwFOamEventsDyingGasp
         INTEGER,
      er1646v2EthPortSwFOamEventsCriticalEvent
         INTEGER
      }

er1646v2EthPortSwFOamGlobalIx OBJECT-TYPE
   SYNTAX      GlobalIndex
   MAX-ACCESS  not-accessible
   STATUS      current
   DESCRIPTION
      "The value of the tlsCntTreeGlobalIndex of the MANAGED OBJECT."
   ::= {er1646v2EthPortSwFOamEntry 10}

er1646v2EthPortSwFOamMode OBJECT-TYPE
   SYNTAX      INTEGER
               {
               disabled (0),
               passive (3),
               active (2)
               }
   MAX-ACCESS  read-write
   STATUS      current
   DESCRIPTION
      "Path: swPort.editConf.oam.mode

       Possibilities:
               disabled   (0)
               passive   (3)
               active   (2)"
   ::= {er1646v2EthPortSwFOamEntry 16777216}

er1646v2EthPortSwFOamLpbkLocalParAction OBJECT-TYPE
   SYNTAX      INTEGER
               {
               discard (0),
               forward (1)
               }
   MAX-ACCESS  read-write
   STATUS      current
   DESCRIPTION
      "Path: swPort.editConf.oam.loopbackLocalParserAction

       Possibilities:
               discard   (0)
               forward   (1)"
   ::= {er1646v2EthPortSwFOamEntry 33554432}

er1646v2EthPortSwFOamLpbkSwapMacAddr OBJECT-TYPE
   SYNTAX      INTEGER
               {
               disabled (0),
               enabled (1)
               }
   MAX-ACCESS  read-write
   STATUS      current
   DESCRIPTION
      "Path: swPort.editConf.oam.loopbackSwapMacAddresses

       Possibilities:
               disabled   (0)
               enabled   (1)"
   ::= {er1646v2EthPortSwFOamEntry 50331648}

er1646v2EthPortSwFOamLoopbackIgnoreRx OBJECT-TYPE
   SYNTAX      INTEGER
               {
               no (0),
               yes (1)
               }
   MAX-ACCESS  read-write
   STATUS      current
   DESCRIPTION
      "Path: swPort.editConf.oam.loopbackIgnoreRx

       Possibilities:
               no   (0)
               yes   (1)"
   ::= {er1646v2EthPortSwFOamEntry 67108864}

er1646v2EthPortSwFOamEventsErroredSymbolEnabled OBJECT-TYPE
   SYNTAX      INTEGER
               {
               no (0),
               yes (1)
               }
   MAX-ACCESS  read-write
   STATUS      current
   DESCRIPTION
      "Path: swPort.editConf.oam.events.erroredSymbol.enabled

       Possibilities:
               no   (0)
               yes   (1)"
   ::= {er1646v2EthPortSwFOamEntry 83951872}

er1646v2EthPortSwFOamEventsErroredSymbolWindowHi OBJECT-TYPE
   SYNTAX      INTEGER
               {
               default (0)
               }
   UNITS       "symbols"
   MAX-ACCESS  read-write
   STATUS      current
   DESCRIPTION
      "Path: swPort.editConf.oam.events.erroredSymbol.windowHi

       unit name = symbols

       Possibilities:
               default   (0)"
   ::= {er1646v2EthPortSwFOamEntry 83952128}

er1646v2EthPortSwFOamEventsErroredSymbolWindowLo OBJECT-TYPE
   SYNTAX      INTEGER
               {
               default (0)
               }
   UNITS       "symbols"
   MAX-ACCESS  read-write
   STATUS      current
   DESCRIPTION
      "Path: swPort.editConf.oam.events.erroredSymbol.windowLo

       unit name = symbols

       Possibilities:
               default   (0)"
   ::= {er1646v2EthPortSwFOamEntry 83952384}

er1646v2EthPortSwFOamEventsErroredSymbolThresholdHi OBJECT-TYPE
   SYNTAX      Integer32
   UNITS       "symbols"
   MAX-ACCESS  read-write
   STATUS      current
   DESCRIPTION
      "Path: swPort.editConf.oam.events.erroredSymbol.thresholdHi

       unit name = symbols"
   ::= {er1646v2EthPortSwFOamEntry 83952640}

er1646v2EthPortSwFOamEventsErroredSymbolThresholdLo OBJECT-TYPE
   SYNTAX      Integer32
   UNITS       "symbols"
   MAX-ACCESS  read-write
   STATUS      current
   DESCRIPTION
      "Path: swPort.editConf.oam.events.erroredSymbol.thresholdLo

       unit name = symbols"
   ::= {er1646v2EthPortSwFOamEntry 83952896}

er1646v2EthPortSwFOamEventsErroredFramePeriodEnabled OBJECT-TYPE
   SYNTAX      INTEGER
               {
               no (0),
               yes (1)
               }
   MAX-ACCESS  read-write
   STATUS      current
   DESCRIPTION
      "Path: swPort.editConf.oam.events.erroredFramePeriod.enabled

       Possibilities:
               no   (0)
               yes   (1)"
   ::= {er1646v2EthPortSwFOamEntry 84017408}

er1646v2EthPortSwFOamEventsErroredFramePeriodWindow OBJECT-TYPE
   SYNTAX      INTEGER
               {
               default (0)
               }
   UNITS       "frames"
   MAX-ACCESS  read-write
   STATUS      current
   DESCRIPTION
      "Path: swPort.editConf.oam.events.erroredFramePeriod.window

       unit name = frames

       Possibilities:
               default   (0)"
   ::= {er1646v2EthPortSwFOamEntry 84017664}

er1646v2EthPortSwFOamEventsErroredFramePeriodThreshold OBJECT-TYPE
   SYNTAX      Integer32
   UNITS       "frames"
   MAX-ACCESS  read-write
   STATUS      current
   DESCRIPTION
      "Path: swPort.editConf.oam.events.erroredFramePeriod.threshold

       unit name = frames"
   ::= {er1646v2EthPortSwFOamEntry 84017920}

er1646v2EthPortSwFOamEventsErroredFrameEnabled OBJECT-TYPE
   SYNTAX      INTEGER
               {
               no (0),
               yes (1)
               }
   MAX-ACCESS  read-write
   STATUS      current
   DESCRIPTION
      "Path: swPort.editConf.oam.events.erroredFrame.enabled

       Possibilities:
               no   (0)
               yes   (1)"
   ::= {er1646v2EthPortSwFOamEntry 84082944}

er1646v2EthPortSwFOamEventsErroredFrameWindow OBJECT-TYPE
   SYNTAX      Integer32
   UNITS       "100msec"
   MAX-ACCESS  read-write
   STATUS      current
   DESCRIPTION
      "Path: swPort.editConf.oam.events.erroredFrame.window

       unit name = 100msec"
   ::= {er1646v2EthPortSwFOamEntry 84083200}

er1646v2EthPortSwFOamEventsErroredFrameThreshold OBJECT-TYPE
   SYNTAX      Integer32
   UNITS       "frames"
   MAX-ACCESS  read-write
   STATUS      current
   DESCRIPTION
      "Path: swPort.editConf.oam.events.erroredFrame.threshold

       unit name = frames"
   ::= {er1646v2EthPortSwFOamEntry 84083456}

er1646v2EthPortSwFOamEventsErroredFrameSecondsEnabled OBJECT-TYPE
   SYNTAX      INTEGER
               {
               no (0),
               yes (1)
               }
   MAX-ACCESS  read-write
   STATUS      current
   DESCRIPTION
      "Path: swPort.editConf.oam.events.erroredFrameSeconds.enabled

       Possibilities:
               no   (0)
               yes   (1)"
   ::= {er1646v2EthPortSwFOamEntry 84148480}

er1646v2EthPortSwFOamEventsErroredFrameSecondsWindow OBJECT-TYPE
   SYNTAX      Integer32
   UNITS       "100msec"
   MAX-ACCESS  read-write
   STATUS      current
   DESCRIPTION
      "Path: swPort.editConf.oam.events.erroredFrameSeconds.window

       unit name = 100msec"
   ::= {er1646v2EthPortSwFOamEntry 84148736}

er1646v2EthPortSwFOamEventsErroredFrameSecondsThreshold OBJECT-TYPE
   SYNTAX      Integer32
   UNITS       "frames"
   MAX-ACCESS  read-write
   STATUS      current
   DESCRIPTION
      "Path: swPort.editConf.oam.events.erroredFrameSeconds.threshold

       unit name = frames"
   ::= {er1646v2EthPortSwFOamEntry 84148992}

er1646v2EthPortSwFOamEventsDyingGasp OBJECT-TYPE
   SYNTAX      INTEGER
               {
               disabled (0),
               enabled (1)
               }
   MAX-ACCESS  read-write
   STATUS      current
   DESCRIPTION
      "Path: swPort.editConf.oam.events.dyingGasp

       Possibilities:
               disabled   (0)
               enabled   (1)"
   ::= {er1646v2EthPortSwFOamEntry 84213760}

er1646v2EthPortSwFOamEventsCriticalEvent OBJECT-TYPE
   SYNTAX      INTEGER
               {
               disabled (0),
               enabled (1)
               }
   MAX-ACCESS  read-write
   STATUS      current
   DESCRIPTION
      "Path: swPort.editConf.oam.events.criticalEvent

       Possibilities:
               disabled   (0)
               enabled   (1)"
   ::= {er1646v2EthPortSwFOamEntry 84279296}


er1646v2EthPortSwFDot1x OBJECT IDENTIFIER ::= {er1646v2EthPortSwF 191}

er1646v2EthPortSwFDot1xSSCTable OBJECT-TYPE
   SYNTAX      SEQUENCE OF Er1646v2EthPortSwFDot1xEntry
   MAX-ACCESS  not-accessible
   STATUS      current
   DESCRIPTION
      "ppp server name on interface"
   ::= {er1646v2EthPortSwFDot1x 1}

er1646v2EthPortSwFDot1xEntry OBJECT-TYPE
   SYNTAX      Er1646v2EthPortSwFDot1xEntry
   MAX-ACCESS  not-accessible
   STATUS      current
   DESCRIPTION
      ""
   INDEX      { er1646v2EthPortSwFDot1xGlobalIx }
   ::= {er1646v2EthPortSwFDot1xSSCTable 1}

Er1646v2EthPortSwFDot1xEntry ::=
   SEQUENCE
      {
      er1646v2EthPortSwFDot1xGlobalIx
         GlobalIndex,
      er1646v2EthPortSwFDot1xMode
         INTEGER,
      er1646v2EthPortSwFDot1xMaxHosts
         Integer32,
      er1646v2EthPortSwFDot1xReAuthentication
         INTEGER,
      er1646v2EthPortSwFDot1xReAuthPeriod
         TimeTicks,
      er1646v2EthPortSwFDot1xQuietPeriod
         TimeTicks,
      er1646v2EthPortSwFDot1xSupplTimeout
         TimeTicks,
      er1646v2EthPortSwFDot1xServerTimeout
         TimeTicks,
      er1646v2EthPortSwFDot1xMaxReqCount
         Integer32
      }

er1646v2EthPortSwFDot1xGlobalIx OBJECT-TYPE
   SYNTAX      GlobalIndex
   MAX-ACCESS  not-accessible
   STATUS      current
   DESCRIPTION
      "The value of the tlsCntTreeGlobalIndex of the MANAGED OBJECT."
   ::= {er1646v2EthPortSwFDot1xEntry 10}

er1646v2EthPortSwFDot1xMode OBJECT-TYPE
   SYNTAX      INTEGER
               {
               inactive (0),
               auto (1)
               }
   MAX-ACCESS  read-write
   STATUS      current
   DESCRIPTION
      "Path: swPort.editConf.dot1x.mode

       Possibilities:
               inactive   (0)
               auto   (1)"
   ::= {er1646v2EthPortSwFDot1xEntry 16777216}

er1646v2EthPortSwFDot1xMaxHosts OBJECT-TYPE
   SYNTAX      Integer32
   MAX-ACCESS  read-write
   STATUS      current
   DESCRIPTION
      "Path: swPort.editConf.dot1x.maxHosts"
   ::= {er1646v2EthPortSwFDot1xEntry 33554432}

er1646v2EthPortSwFDot1xReAuthentication OBJECT-TYPE
   SYNTAX      INTEGER
               {
               disabled (0),
               enabled (1)
               }
   MAX-ACCESS  read-write
   STATUS      current
   DESCRIPTION
      "Path: swPort.editConf.dot1x.reAuthentication

       Possibilities:
               disabled   (0)
               enabled   (1)"
   ::= {er1646v2EthPortSwFDot1xEntry 50331648}

er1646v2EthPortSwFDot1xReAuthPeriod OBJECT-TYPE
   SYNTAX      TimeTicks
   MAX-ACCESS  read-write
   STATUS      current
   DESCRIPTION
      "Path: swPort.editConf.dot1x.reAuthPeriod

       Time in centi-second."
   ::= {er1646v2EthPortSwFDot1xEntry 67108864}

er1646v2EthPortSwFDot1xQuietPeriod OBJECT-TYPE
   SYNTAX      TimeTicks
   MAX-ACCESS  read-write
   STATUS      current
   DESCRIPTION
      "Path: swPort.editConf.dot1x.quietPeriod

       Time in centi-second."
   ::= {er1646v2EthPortSwFDot1xEntry 83886080}

er1646v2EthPortSwFDot1xSupplTimeout OBJECT-TYPE
   SYNTAX      TimeTicks
   MAX-ACCESS  read-write
   STATUS      current
   DESCRIPTION
      "Path: swPort.editConf.dot1x.supplTimeout

       Time in centi-second."
   ::= {er1646v2EthPortSwFDot1xEntry 100663296}

er1646v2EthPortSwFDot1xServerTimeout OBJECT-TYPE
   SYNTAX      TimeTicks
   MAX-ACCESS  read-write
   STATUS      current
   DESCRIPTION
      "Path: swPort.editConf.dot1x.serverTimeout

       Time in centi-second."
   ::= {er1646v2EthPortSwFDot1xEntry 117440512}

er1646v2EthPortSwFDot1xMaxReqCount OBJECT-TYPE
   SYNTAX      Integer32
   MAX-ACCESS  read-write
   STATUS      current
   DESCRIPTION
      "Path: swPort.editConf.dot1x.maxReqCount"
   ::= {er1646v2EthPortSwFDot1xEntry 134217728}


er1646v2EthPortSwFIpV6 OBJECT IDENTIFIER ::= {er1646v2EthPortSwF 15}

er1646v2EthPortSwFIpV6SSCTable OBJECT-TYPE
   SYNTAX      SEQUENCE OF Er1646v2EthPortSwFIpV6Entry
   MAX-ACCESS  not-accessible
   STATUS      current
   DESCRIPTION
      "IPv6 interface config parameters"
   ::= {er1646v2EthPortSwFIpV6 1}

er1646v2EthPortSwFIpV6Entry OBJECT-TYPE
   SYNTAX      Er1646v2EthPortSwFIpV6Entry
   MAX-ACCESS  not-accessible
   STATUS      current
   DESCRIPTION
      ""
   INDEX      { er1646v2EthPortSwFIpV6GlobalIx }
   ::= {er1646v2EthPortSwFIpV6SSCTable 1}

Er1646v2EthPortSwFIpV6Entry ::=
   SEQUENCE
      {
      er1646v2EthPortSwFIpV6GlobalIx
         GlobalIndex,
      er1646v2EthPortSwFIpV6VrfRouter
         DisplayString,
      er1646v2EthPortSwFIpV6AddrAutoConfigNrDupAddrDetects
         Integer32,
      er1646v2EthPortSwFIpV6AddrAutoConfigAcceptRa
         INTEGER,
      er1646v2EthPortSwFIpV6AddrAutoConfigAcceptRaRdnss
         INTEGER,
      er1646v2EthPortSwFIpV6AddrAutoConfigAcceptRaDnssl
         INTEGER,
      er1646v2EthPortSwFIpV6DefaultRoute
         INTEGER,
      er1646v2EthPortSwFIpV6RaSend
         INTEGER,
      er1646v2EthPortSwFIpV6RaMinInterval
         TimeTicks,
      er1646v2EthPortSwFIpV6RaMaxInterval
         TimeTicks,
      er1646v2EthPortSwFIpV6RaManagedFlag
         INTEGER,
      er1646v2EthPortSwFIpV6RaOtherConfFlag
         INTEGER,
      er1646v2EthPortSwFIpV6RaLinkMtu
         Integer32,
      er1646v2EthPortSwFIpV6RaReachableTime
         TimeTicks,
      er1646v2EthPortSwFIpV6RaRetransmitTime
         TimeTicks,
      er1646v2EthPortSwFIpV6RaHopLimit
         Integer32,
      er1646v2EthPortSwFIpV6RaDefaultLifeTime
         TimeTicks,
      er1646v2EthPortSwFIpV6RaDnsOptionsRdnssLifeTime
         TimeTicks,
      er1646v2EthPortSwFIpV6RaDnsOptionsRdnssImportServers
         INTEGER,
      er1646v2EthPortSwFIpV6RaDnsOptionsDnsslLifeTime
         TimeTicks,
      er1646v2EthPortSwFIpV6RaDnsOptionsDnsslImportDomains
         INTEGER,
      er1646v2EthPortSwFIpV6RsSend
         INTEGER,
      er1646v2EthPortSwFIpV6RsMaxRandomDelay
         TimeTicks,
      er1646v2EthPortSwFIpV6RsInterval
         TimeTicks,
      er1646v2EthPortSwFIpV6RsMaxSolicitations
         Integer32,
      er1646v2EthPortSwFIpV6TrafficPolicyInbound
         DisplayString,
      er1646v2EthPortSwFIpV6TrafficPolicyOutbound
         DisplayString,
      er1646v2EthPortSwFIpV6FirewallZone
         DisplayString,
      er1646v2EthPortSwFIpV6DhcpClientAddrAC
         INTEGER,
      er1646v2EthPortSwFIpV6DhcpClientPrDelMode
         INTEGER,
      er1646v2EthPortSwFIpV6DhcpClientPrDelPool
         DisplayString,
      er1646v2EthPortSwFIpV6DhcpClientPrDelPdExclOpt
         INTEGER,
      er1646v2EthPortSwFIpV6DhcpClientDnsServerPref
         Integer32,
      er1646v2EthPortSwFIpV6DhcpClientRapidCommit
         INTEGER,
      er1646v2EthPortSwFIpV6DhcpClientTimersSolTimeOut
         TimeTicks,
      er1646v2EthPortSwFIpV6DhcpClientTimersSolMaxRt
         TimeTicks,
      er1646v2EthPortSwFIpV6DhcpClientTimersInfoRefresh
         TimeTicks,
      er1646v2EthPortSwFIpV6DhcpServerMode
         INTEGER,
      er1646v2EthPortSwFIpV6DhcpServerPreference
         Integer32,
      er1646v2EthPortSwFIpV6DhcpServerPool
         DisplayString,
      er1646v2EthPortSwFIpV6DhcpServerRapidCommit
         INTEGER,
      er1646v2EthPortSwFIpV6DhcpServerTimersInfoRefresh
         TimeTicks,
      er1646v2EthPortSwFIpV6DhcpRelayMode
         INTEGER,
      er1646v2EthPortSwFIpV6SendRedirect
         INTEGER,
      er1646v2EthPortSwFIpV6LinkMtu
         Integer32,
      er1646v2EthPortSwFIpV6InterfaceId
         OCTET STRING,
      er1646v2EthPortSwFIpV6MF
         Integer32,
      er1646v2EthPortSwFIpV6IcmpMessagesNoRoute
         INTEGER,
      er1646v2EthPortSwFIpV6IcmpMessagesBeyondScope
         INTEGER,
      er1646v2EthPortSwFIpV6IcmpMessagesAddressUnreachable
         INTEGER,
      er1646v2EthPortSwFIpV6IcmpMessagesPortUnreachable
         INTEGER,
      er1646v2EthPortSwFIpV6IcmpMessagesPacketTooBig
         INTEGER,
      er1646v2EthPortSwFIpV6IcmpMessagesHopLimitExceeded
         INTEGER,
      er1646v2EthPortSwFIpV6IcmpMessagesFragTimeExceeded
         INTEGER,
      er1646v2EthPortSwFIpV6IcmpMessagesHeaderFieldErr
         INTEGER,
      er1646v2EthPortSwFIpV6IcmpMessagesOptionUnrecognized
         INTEGER,
      er1646v2EthPortSwFIpV6IcmpMessagesRedirect
         INTEGER
      }

er1646v2EthPortSwFIpV6GlobalIx OBJECT-TYPE
   SYNTAX      GlobalIndex
   MAX-ACCESS  not-accessible
   STATUS      current
   DESCRIPTION
      "The value of the tlsCntTreeGlobalIndex of the MANAGED OBJECT."
   ::= {er1646v2EthPortSwFIpV6Entry 10}

er1646v2EthPortSwFIpV6VrfRouter OBJECT-TYPE
   SYNTAX      DisplayString
   MAX-ACCESS  read-write
   STATUS      current
   DESCRIPTION
      "Path: swPort.editConf.ipV6.vrfRouter"
   ::= {er1646v2EthPortSwFIpV6Entry 16777216}

er1646v2EthPortSwFIpV6AddrAutoConfigNrDupAddrDetects OBJECT-TYPE
   SYNTAX      Integer32
   MAX-ACCESS  read-write
   STATUS      current
   DESCRIPTION
      "Path: swPort.editConf.ipV6.addrAutoConfig.nrDupAddrDetects"
   ::= {er1646v2EthPortSwFIpV6Entry 67174400}

er1646v2EthPortSwFIpV6AddrAutoConfigAcceptRa OBJECT-TYPE
   SYNTAX      INTEGER
               {
               disabled (0),
               enabled (1)
               }
   MAX-ACCESS  read-write
   STATUS      current
   DESCRIPTION
      "Path: swPort.editConf.ipV6.addrAutoConfig.acceptRa

       Possibilities:
               disabled   (0)
               enabled   (1)"
   ::= {er1646v2EthPortSwFIpV6Entry 67239936}

er1646v2EthPortSwFIpV6AddrAutoConfigAcceptRaRdnss OBJECT-TYPE
   SYNTAX      INTEGER
               {
               disabled (0),
               enabled (1)
               }
   MAX-ACCESS  read-write
   STATUS      current
   DESCRIPTION
      "Path: swPort.editConf.ipV6.addrAutoConfig.acceptRaRdnss

       Possibilities:
               disabled   (0)
               enabled   (1)"
   ::= {er1646v2EthPortSwFIpV6Entry 67305472}

er1646v2EthPortSwFIpV6AddrAutoConfigAcceptRaDnssl OBJECT-TYPE
   SYNTAX      INTEGER
               {
               disabled (0),
               enabled (1)
               }
   MAX-ACCESS  read-write
   STATUS      current
   DESCRIPTION
      "Path: swPort.editConf.ipV6.addrAutoConfig.acceptRaDnssl

       Possibilities:
               disabled   (0)
               enabled   (1)"
   ::= {er1646v2EthPortSwFIpV6Entry 67371008}

er1646v2EthPortSwFIpV6DefaultRoute OBJECT-TYPE
   SYNTAX      INTEGER
               {
               disabled (0),
               enabled (1)
               }
   MAX-ACCESS  read-write
   STATUS      current
   DESCRIPTION
      "Path: swPort.editConf.ipV6.defaultRoute

       Possibilities:
               disabled   (0)
               enabled   (1)"
   ::= {er1646v2EthPortSwFIpV6Entry 83886080}

er1646v2EthPortSwFIpV6RaSend OBJECT-TYPE
   SYNTAX      INTEGER
               {
               disabled (0),
               enabled (1)
               }
   MAX-ACCESS  read-write
   STATUS      current
   DESCRIPTION
      "Path: swPort.editConf.ipV6.ra.send

       Possibilities:
               disabled   (0)
               enabled   (1)"
   ::= {er1646v2EthPortSwFIpV6Entry 100728832}

er1646v2EthPortSwFIpV6RaMinInterval OBJECT-TYPE
   SYNTAX      TimeTicks
   MAX-ACCESS  read-write
   STATUS      current
   DESCRIPTION
      "Path: swPort.editConf.ipV6.ra.minInterval

       Time in centi-second."
   ::= {er1646v2EthPortSwFIpV6Entry 100794368}

er1646v2EthPortSwFIpV6RaMaxInterval OBJECT-TYPE
   SYNTAX      TimeTicks
   MAX-ACCESS  read-write
   STATUS      current
   DESCRIPTION
      "Path: swPort.editConf.ipV6.ra.maxInterval

       Time in centi-second."
   ::= {er1646v2EthPortSwFIpV6Entry 100859904}

er1646v2EthPortSwFIpV6RaManagedFlag OBJECT-TYPE
   SYNTAX      INTEGER
               {
               disabled (0),
               enabled (1)
               }
   MAX-ACCESS  read-write
   STATUS      current
   DESCRIPTION
      "Path: swPort.editConf.ipV6.ra.managedFlag

       Possibilities:
               disabled   (0)
               enabled   (1)"
   ::= {er1646v2EthPortSwFIpV6Entry 100925440}

er1646v2EthPortSwFIpV6RaOtherConfFlag OBJECT-TYPE
   SYNTAX      INTEGER
               {
               disabled (0),
               enabled (1)
               }
   MAX-ACCESS  read-write
   STATUS      current
   DESCRIPTION
      "Path: swPort.editConf.ipV6.ra.otherConfFlag

       Possibilities:
               disabled   (0)
               enabled   (1)"
   ::= {er1646v2EthPortSwFIpV6Entry 100990976}

er1646v2EthPortSwFIpV6RaLinkMtu OBJECT-TYPE
   SYNTAX      Integer32
   MAX-ACCESS  read-write
   STATUS      current
   DESCRIPTION
      "Path: swPort.editConf.ipV6.ra.linkMtu"
   ::= {er1646v2EthPortSwFIpV6Entry 101056512}

er1646v2EthPortSwFIpV6RaReachableTime OBJECT-TYPE
   SYNTAX      TimeTicks
   MAX-ACCESS  read-write
   STATUS      current
   DESCRIPTION
      "Path: swPort.editConf.ipV6.ra.reachableTime

       Time in centi-second."
   ::= {er1646v2EthPortSwFIpV6Entry 101122048}

er1646v2EthPortSwFIpV6RaRetransmitTime OBJECT-TYPE
   SYNTAX      TimeTicks
   MAX-ACCESS  read-write
   STATUS      current
   DESCRIPTION
      "Path: swPort.editConf.ipV6.ra.retransmitTime

       Time in centi-second."
   ::= {er1646v2EthPortSwFIpV6Entry 101187584}

er1646v2EthPortSwFIpV6RaHopLimit OBJECT-TYPE
   SYNTAX      Integer32
   MAX-ACCESS  read-write
   STATUS      current
   DESCRIPTION
      "Path: swPort.editConf.ipV6.ra.hopLimit"
   ::= {er1646v2EthPortSwFIpV6Entry 101253120}

er1646v2EthPortSwFIpV6RaDefaultLifeTime OBJECT-TYPE
   SYNTAX      TimeTicks
   MAX-ACCESS  read-write
   STATUS      current
   DESCRIPTION
      "Path: swPort.editConf.ipV6.ra.defaultLifeTime

       Time in centi-second."
   ::= {er1646v2EthPortSwFIpV6Entry 101318656}

er1646v2EthPortSwFIpV6RaDnsOptionsRdnssLifeTime OBJECT-TYPE
   SYNTAX      TimeTicks
   MAX-ACCESS  read-write
   STATUS      current
   DESCRIPTION
      "Path: swPort.editConf.ipV6.ra.dnsOptions.rdnss.lifeTime

       Time in centi-second."
   ::= {er1646v2EthPortSwFIpV6Entry 101393408}

er1646v2EthPortSwFIpV6RaDnsOptionsRdnssImportServers OBJECT-TYPE
   SYNTAX      INTEGER
               {
               disabled (0),
               enabled (1)
               }
   MAX-ACCESS  read-write
   STATUS      current
   DESCRIPTION
      "Path: swPort.editConf.ipV6.ra.dnsOptions.rdnss.importServers

       Possibilities:
               disabled   (0)
               enabled   (1)"
   ::= {er1646v2EthPortSwFIpV6Entry 101395456}

er1646v2EthPortSwFIpV6RaDnsOptionsDnsslLifeTime OBJECT-TYPE
   SYNTAX      TimeTicks
   MAX-ACCESS  read-write
   STATUS      current
   DESCRIPTION
      "Path: swPort.editConf.ipV6.ra.dnsOptions.dnssl.lifeTime

       Time in centi-second."
   ::= {er1646v2EthPortSwFIpV6Entry 101401600}

er1646v2EthPortSwFIpV6RaDnsOptionsDnsslImportDomains OBJECT-TYPE
   SYNTAX      INTEGER
               {
               disabled (0),
               enabled (1)
               }
   MAX-ACCESS  read-write
   STATUS      current
   DESCRIPTION
      "Path: swPort.editConf.ipV6.ra.dnsOptions.dnssl.importDomains

       Possibilities:
               disabled   (0)
               enabled   (1)"
   ::= {er1646v2EthPortSwFIpV6Entry 101403648}

er1646v2EthPortSwFIpV6RsSend OBJECT-TYPE
   SYNTAX      INTEGER
               {
               disabled (0),
               enabled (1)
               }
   MAX-ACCESS  read-write
   STATUS      current
   DESCRIPTION
      "Path: swPort.editConf.ipV6.rs.send

       Possibilities:
               disabled   (0)
               enabled   (1)"
   ::= {er1646v2EthPortSwFIpV6Entry 335609856}

er1646v2EthPortSwFIpV6RsMaxRandomDelay OBJECT-TYPE
   SYNTAX      TimeTicks
   MAX-ACCESS  read-write
   STATUS      current
   DESCRIPTION
      "Path: swPort.editConf.ipV6.rs.maxRandomDelay

       Time in centi-second."
   ::= {er1646v2EthPortSwFIpV6Entry 335675392}

er1646v2EthPortSwFIpV6RsInterval OBJECT-TYPE
   SYNTAX      TimeTicks
   MAX-ACCESS  read-write
   STATUS      current
   DESCRIPTION
      "Path: swPort.editConf.ipV6.rs.interval

       Time in centi-second."
   ::= {er1646v2EthPortSwFIpV6Entry 335740928}

er1646v2EthPortSwFIpV6RsMaxSolicitations OBJECT-TYPE
   SYNTAX      Integer32
   MAX-ACCESS  read-write
   STATUS      current
   DESCRIPTION
      "Path: swPort.editConf.ipV6.rs.maxSolicitations"
   ::= {er1646v2EthPortSwFIpV6Entry 335806464}

er1646v2EthPortSwFIpV6TrafficPolicyInbound OBJECT-TYPE
   SYNTAX      DisplayString
   MAX-ACCESS  read-write
   STATUS      current
   DESCRIPTION
      "Path: swPort.editConf.ipV6.trafficPolicy.inbound"
   ::= {er1646v2EthPortSwFIpV6Entry 184614912}

er1646v2EthPortSwFIpV6TrafficPolicyOutbound OBJECT-TYPE
   SYNTAX      DisplayString
   MAX-ACCESS  read-write
   STATUS      current
   DESCRIPTION
      "Path: swPort.editConf.ipV6.trafficPolicy.outbound"
   ::= {er1646v2EthPortSwFIpV6Entry 184680448}

er1646v2EthPortSwFIpV6FirewallZone OBJECT-TYPE
   SYNTAX      DisplayString
   MAX-ACCESS  read-write
   STATUS      current
   DESCRIPTION
      "Path: swPort.editConf.ipV6.firewall.zone"
   ::= {er1646v2EthPortSwFIpV6Entry 201392128}

er1646v2EthPortSwFIpV6DhcpClientAddrAC OBJECT-TYPE
   SYNTAX      INTEGER
               {
               disabled (0),
               enabled (1)
               }
   MAX-ACCESS  read-write
   STATUS      current
   DESCRIPTION
      "Path: swPort.editConf.ipV6.dhcp.client.addrAutoConfig

       Possibilities:
               disabled   (0)
               enabled   (1)"
   ::= {er1646v2EthPortSwFIpV6Entry 170131456}

er1646v2EthPortSwFIpV6DhcpClientPrDelMode OBJECT-TYPE
   SYNTAX      INTEGER
               {
               disabled (0),
               enabled (1)
               }
   MAX-ACCESS  read-write
   STATUS      current
   DESCRIPTION
      "Path: swPort.editConf.ipV6.dhcp.client.pd.mode

       Possibilities:
               disabled   (0)
               enabled   (1)"
   ::= {er1646v2EthPortSwFIpV6Entry 170394624}

er1646v2EthPortSwFIpV6DhcpClientPrDelPool OBJECT-TYPE
   SYNTAX      DisplayString
   MAX-ACCESS  read-write
   STATUS      current
   DESCRIPTION
      "Path: swPort.editConf.ipV6.dhcp.client.pd.pool"
   ::= {er1646v2EthPortSwFIpV6Entry 170395648}

er1646v2EthPortSwFIpV6DhcpClientPrDelPdExclOpt OBJECT-TYPE
   SYNTAX      INTEGER
               {
               disabled (0),
               enabled (1)
               }
   MAX-ACCESS  read-write
   STATUS      current
   DESCRIPTION
      "Path: swPort.editConf.ipV6.dhcp.client.pd.pdExclOpt

       Possibilities:
               disabled   (0)
               enabled   (1)"
   ::= {er1646v2EthPortSwFIpV6Entry 170396672}

er1646v2EthPortSwFIpV6DhcpClientDnsServerPref OBJECT-TYPE
   SYNTAX      Integer32
   MAX-ACCESS  read-write
   STATUS      current
   DESCRIPTION
      "Path: swPort.editConf.ipV6.dhcp.client.dns.serverPref"
   ::= {er1646v2EthPortSwFIpV6Entry 170918912}

er1646v2EthPortSwFIpV6DhcpClientRapidCommit OBJECT-TYPE
   SYNTAX      INTEGER
               {
               disabled (0),
               enabled (1)
               }
   MAX-ACCESS  read-write
   STATUS      current
   DESCRIPTION
      "Path: swPort.editConf.ipV6.dhcp.client.rapidCommit

       Possibilities:
               disabled   (0)
               enabled   (1)"
   ::= {er1646v2EthPortSwFIpV6Entry 170655744}

er1646v2EthPortSwFIpV6DhcpClientTimersSolTimeOut OBJECT-TYPE
   SYNTAX      TimeTicks
   MAX-ACCESS  read-write
   STATUS      current
   DESCRIPTION
      "Path: swPort.editConf.ipV6.dhcp.client.timers.solTimeOut

       Time in centi-second."
   ::= {er1646v2EthPortSwFIpV6Entry 171181056}

er1646v2EthPortSwFIpV6DhcpClientTimersSolMaxRt OBJECT-TYPE
   SYNTAX      TimeTicks
   MAX-ACCESS  read-write
   STATUS      current
   DESCRIPTION
      "Path: swPort.editConf.ipV6.dhcp.client.timers.solMaxRt

       Time in centi-second."
   ::= {er1646v2EthPortSwFIpV6Entry 171182080}

er1646v2EthPortSwFIpV6DhcpClientTimersInfoRefresh OBJECT-TYPE
   SYNTAX      TimeTicks
   MAX-ACCESS  read-write
   STATUS      current
   DESCRIPTION
      "Path: swPort.editConf.ipV6.dhcp.client.timers.infoRefresh

       Time in centi-second."
   ::= {er1646v2EthPortSwFIpV6Entry 171183104}

er1646v2EthPortSwFIpV6DhcpServerMode OBJECT-TYPE
   SYNTAX      INTEGER
               {
               disabled (0),
               enabled (1)
               }
   MAX-ACCESS  read-write
   STATUS      current
   DESCRIPTION
      "Path: swPort.editConf.ipV6.dhcp.server.mode

       Possibilities:
               disabled   (0)
               enabled   (1)"
   ::= {er1646v2EthPortSwFIpV6Entry 172228608}

er1646v2EthPortSwFIpV6DhcpServerPreference OBJECT-TYPE
   SYNTAX      Integer32
   MAX-ACCESS  read-write
   STATUS      current
   DESCRIPTION
      "Path: swPort.editConf.ipV6.dhcp.server.preference"
   ::= {er1646v2EthPortSwFIpV6Entry 172490752}

er1646v2EthPortSwFIpV6DhcpServerPool OBJECT-TYPE
   SYNTAX      DisplayString
   MAX-ACCESS  read-write
   STATUS      current
   DESCRIPTION
      "Path: swPort.editConf.ipV6.dhcp.server.pool"
   ::= {er1646v2EthPortSwFIpV6Entry 172752896}

er1646v2EthPortSwFIpV6DhcpServerRapidCommit OBJECT-TYPE
   SYNTAX      INTEGER
               {
               disabled (0),
               enabled (1)
               }
   MAX-ACCESS  read-write
   STATUS      current
   DESCRIPTION
      "Path: swPort.editConf.ipV6.dhcp.server.rapidCommit

       Possibilities:
               disabled   (0)
               enabled   (1)"
   ::= {er1646v2EthPortSwFIpV6Entry 173015040}

er1646v2EthPortSwFIpV6DhcpServerTimersInfoRefresh OBJECT-TYPE
   SYNTAX      TimeTicks
   MAX-ACCESS  read-write
   STATUS      current
   DESCRIPTION
      "Path: swPort.editConf.ipV6.dhcp.server.timers.infoRefresh

       Time in centi-second."
   ::= {er1646v2EthPortSwFIpV6Entry 173278208}

er1646v2EthPortSwFIpV6DhcpRelayMode OBJECT-TYPE
   SYNTAX      INTEGER
               {
               disabled (0),
               enabled (1)
               }
   MAX-ACCESS  read-write
   STATUS      current
   DESCRIPTION
      "Path: swPort.editConf.ipV6.dhcp.relay.mode

       Possibilities:
               disabled   (0)
               enabled   (1)"
   ::= {er1646v2EthPortSwFIpV6Entry 174071808}

er1646v2EthPortSwFIpV6SendRedirect OBJECT-TYPE
   SYNTAX      INTEGER
               {
               disabled (0),
               enabled (1)
               }
   MAX-ACCESS  read-write
   STATUS      current
   DESCRIPTION
      "Path: swPort.editConf.ipV6.sendRedirect

       Possibilities:
               disabled   (0)
               enabled   (1)"
   ::= {er1646v2EthPortSwFIpV6Entry 117440512}

er1646v2EthPortSwFIpV6LinkMtu OBJECT-TYPE
   SYNTAX      Integer32
   MAX-ACCESS  read-write
   STATUS      current
   DESCRIPTION
      "Path: swPort.editConf.ipV6.linkMtu"
   ::= {er1646v2EthPortSwFIpV6Entry 134217728}

er1646v2EthPortSwFIpV6InterfaceId OBJECT-TYPE
   SYNTAX      OCTET STRING
   MAX-ACCESS  read-write
   STATUS      current
   DESCRIPTION
      "Path: swPort.editConf.ipV6.interfaceId"
   ::= {er1646v2EthPortSwFIpV6Entry 150994944}

er1646v2EthPortSwFIpV6MF OBJECT-TYPE
   SYNTAX      Integer32
   MAX-ACCESS  read-write
   STATUS      current
   DESCRIPTION
      "Path: swPort.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwFIpV6Entry 285212672}

er1646v2EthPortSwFIpV6IcmpMessagesNoRoute OBJECT-TYPE
   SYNTAX      INTEGER
               {
               disabled (0),
               enabled (1)
               }
   MAX-ACCESS  read-write
   STATUS      current
   DESCRIPTION
      "Path: swPort.editConf.ipV6.icmpMessages.noRoute

       Possibilities:
               disabled   (0)
               enabled   (1)"
   ::= {er1646v2EthPortSwFIpV6Entry 302055424}

er1646v2EthPortSwFIpV6IcmpMessagesBeyondScope OBJECT-TYPE
   SYNTAX      INTEGER
               {
               disabled (0),
               enabled (1)
               }
   MAX-ACCESS  read-write
   STATUS      current
   DESCRIPTION
      "Path: swPort.editConf.ipV6.icmpMessages.beyondScope

       Possibilities:
               disabled   (0)
               enabled   (1)"
   ::= {er1646v2EthPortSwFIpV6Entry 302186496}

er1646v2EthPortSwFIpV6IcmpMessagesAddressUnreachable OBJECT-TYPE
   SYNTAX      INTEGER
               {
               disabled (0),
               enabled (1)
               }
   MAX-ACCESS  read-write
   STATUS      current
   DESCRIPTION
      "Path: swPort.editConf.ipV6.icmpMessages.addressUnreachable

       Possibilities:
               disabled   (0)
               enabled   (1)"
   ::= {er1646v2EthPortSwFIpV6Entry 302252032}

er1646v2EthPortSwFIpV6IcmpMessagesPortUnreachable OBJECT-TYPE
   SYNTAX      INTEGER
               {
               disabled (0),
               enabled (1)
               }
   MAX-ACCESS  read-write
   STATUS      current
   DESCRIPTION
      "Path: swPort.editConf.ipV6.icmpMessages.portUnreachable

       Possibilities:
               disabled   (0)
               enabled   (1)"
   ::= {er1646v2EthPortSwFIpV6Entry 302317568}

er1646v2EthPortSwFIpV6IcmpMessagesPacketTooBig OBJECT-TYPE
   SYNTAX      INTEGER
               {
               disabled (0),
               enabled (1)
               }
   MAX-ACCESS  read-write
   STATUS      current
   DESCRIPTION
      "Path: swPort.editConf.ipV6.icmpMessages.packetTooBig

       Possibilities:
               disabled   (0)
               enabled   (1)"
   ::= {er1646v2EthPortSwFIpV6Entry 302645248}

er1646v2EthPortSwFIpV6IcmpMessagesHopLimitExceeded OBJECT-TYPE
   SYNTAX      INTEGER
               {
               disabled (0),
               enabled (1)
               }
   MAX-ACCESS  read-write
   STATUS      current
   DESCRIPTION
      "Path: swPort.editConf.ipV6.icmpMessages.hopLimitExceeded

       Possibilities:
               disabled   (0)
               enabled   (1)"
   ::= {er1646v2EthPortSwFIpV6Entry 303300608}

er1646v2EthPortSwFIpV6IcmpMessagesFragTimeExceeded OBJECT-TYPE
   SYNTAX      INTEGER
               {
               disabled (0),
               enabled (1)
               }
   MAX-ACCESS  read-write
   STATUS      current
   DESCRIPTION
      "Path: swPort.editConf.ipV6.icmpMessages.fragTimeExceeded

       Possibilities:
               disabled   (0)
               enabled   (1)"
   ::= {er1646v2EthPortSwFIpV6Entry 303366144}

er1646v2EthPortSwFIpV6IcmpMessagesHeaderFieldErr OBJECT-TYPE
   SYNTAX      INTEGER
               {
               disabled (0),
               enabled (1)
               }
   MAX-ACCESS  read-write
   STATUS      current
   DESCRIPTION
      "Path: swPort.editConf.ipV6.icmpMessages.headerFieldErr

       Possibilities:
               disabled   (0)
               enabled   (1)"
   ::= {er1646v2EthPortSwFIpV6Entry 303955968}

er1646v2EthPortSwFIpV6IcmpMessagesOptionUnrecognized OBJECT-TYPE
   SYNTAX      INTEGER
               {
               disabled (0),
               enabled (1)
               }
   MAX-ACCESS  read-write
   STATUS      current
   DESCRIPTION
      "Path: swPort.editConf.ipV6.icmpMessages.optionUnrecognized

       Possibilities:
               disabled   (0)
               enabled   (1)"
   ::= {er1646v2EthPortSwFIpV6Entry 304087040}

er1646v2EthPortSwFIpV6IcmpMessagesRedirect OBJECT-TYPE
   SYNTAX      INTEGER
               {
               disabled (0),
               enabled (1)
               }
   MAX-ACCESS  read-write
   STATUS      current
   DESCRIPTION
      "Path: swPort.editConf.ipV6.icmpMessages.redirect

       Possibilities:
               disabled   (0)
               enabled   (1)"
   ::= {er1646v2EthPortSwFIpV6Entry 304611328}

er1646v2EthPortSwFIpV6Addresses OBJECT-TYPE
   SYNTAX      SEQUENCE OF Er1646v2EthPortSwFIpV6AddressesEntry
   MAX-ACCESS  not-accessible
   STATUS      current
   DESCRIPTION
      ""
   ::= {er1646v2EthPortSwFIpV6 50331648}

er1646v2EthPortSwFIpV6AddressesEntry OBJECT-TYPE
   SYNTAX      Er1646v2EthPortSwFIpV6AddressesEntry
   MAX-ACCESS  not-accessible
   STATUS      current
   DESCRIPTION
      ""
   INDEX      { er1646v2EthPortSwFIpV6AddressesGlobalIx,
                er1646v2EthPortSwFIpV6AddressesTableIx }
   ::= {er1646v2EthPortSwFIpV6Addresses 1}

Er1646v2EthPortSwFIpV6AddressesEntry ::=
   SEQUENCE
      {
      er1646v2EthPortSwFIpV6AddressesActions
         VariableLengthTableActions,
      er1646v2EthPortSwFIpV6AddressesGlobalIx
         GlobalIndex,
      er1646v2EthPortSwFIpV6AddressesTableIx
         TableIndex,
      er1646v2EthPortSwFIpV6AddressesType
         INTEGER,
      er1646v2EthPortSwFIpV6AddressesAddress
         Ipv6Address,
      er1646v2EthPortSwFIpV6AddressesPrefixLength
         Integer32,
      er1646v2EthPortSwFIpV6AddressesGeneralPrefix
         DisplayString,
      er1646v2EthPortSwFIpV6AddressesRaSend
         INTEGER,
      er1646v2EthPortSwFIpV6AddressesRaOnLinkFlag
         INTEGER,
      er1646v2EthPortSwFIpV6AddressesRaAutoFlag
         INTEGER,
      er1646v2EthPortSwFIpV6AddressesRaValidLifeTime
         TimeTicks,
      er1646v2EthPortSwFIpV6AddressesRaValidLTMode
         INTEGER,
      er1646v2EthPortSwFIpV6AddressesRaPrefLifeTime
         TimeTicks,
      er1646v2EthPortSwFIpV6AddressesRaPrefLTMode
         INTEGER
      }

er1646v2EthPortSwFIpV6AddressesActions OBJECT-TYPE
   SYNTAX      VariableLengthTableActions
   MAX-ACCESS  read-write
   STATUS      current
   DESCRIPTION
      "By way of this field, some manipulations
       on this table may be performed."
   ::= {er1646v2EthPortSwFIpV6AddressesEntry 2}

er1646v2EthPortSwFIpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwFIpV6AddressesEntry 10}

er1646v2EthPortSwFIpV6AddressesTableIx OBJECT-TYPE
   SYNTAX      TableIndex
   MAX-ACCESS  not-accessible
   STATUS      current
   DESCRIPTION
      ""
   ::= {er1646v2EthPortSwFIpV6AddressesEntry 11}

er1646v2EthPortSwFIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.ipV6.addresses.type

       Possibilities:
               unicast   (0)
               eui64   (1)
               anycast   (2)
               linkLocal   (3)
               generalPrefix   (4)"
   ::= {er1646v2EthPortSwFIpV6AddressesEntry 50331648}

er1646v2EthPortSwFIpV6AddressesAddress OBJECT-TYPE
   SYNTAX      Ipv6Address
   MAX-ACCESS  read-write
   STATUS      current
   DESCRIPTION
      "Path: swPort.editConf.ipV6.addresses.address

       ipv6 address"
   ::= {er1646v2EthPortSwFIpV6AddressesEntry 16777216}

er1646v2EthPortSwFIpV6AddressesPrefixLength OBJECT-TYPE
   SYNTAX      Integer32
   MAX-ACCESS  read-write
   STATUS      current
   DESCRIPTION
      "Path: swPort.editConf.ipV6.addresses.prefixLength"
   ::= {er1646v2EthPortSwFIpV6AddressesEntry 33554432}

er1646v2EthPortSwFIpV6AddressesGeneralPrefix OBJECT-TYPE
   SYNTAX      DisplayString
   MAX-ACCESS  read-write
   STATUS      current
   DESCRIPTION
      "Path: swPort.editConf.ipV6.addresses.generalPrefix"
   ::= {er1646v2EthPortSwFIpV6AddressesEntry 83886080}

er1646v2EthPortSwFIpV6AddressesRaSend OBJECT-TYPE
   SYNTAX      INTEGER
               {
               disabled (0),
               enabled (1)
               }
   MAX-ACCESS  read-write
   STATUS      current
   DESCRIPTION
      "Path: swPort.editConf.ipV6.addresses.ra.send

       Possibilities:
               disabled   (0)
               enabled   (1)"
   ::= {er1646v2EthPortSwFIpV6AddressesEntry 67174400}

er1646v2EthPortSwFIpV6AddressesRaOnLinkFlag OBJECT-TYPE
   SYNTAX      INTEGER
               {
               disabled (0),
               enabled (1)
               }
   MAX-ACCESS  read-write
   STATUS      current
   DESCRIPTION
      "Path: swPort.editConf.ipV6.addresses.ra.onLinkFlag

       Possibilities:
               disabled   (0)
               enabled   (1)"
   ::= {er1646v2EthPortSwFIpV6AddressesEntry 67371008}

er1646v2EthPortSwFIpV6AddressesRaAutoFlag OBJECT-TYPE
   SYNTAX      INTEGER
               {
               disabled (0),
               enabled (1)
               }
   MAX-ACCESS  read-write
   STATUS      current
   DESCRIPTION
      "Path: swPort.editConf.ipV6.addresses.ra.autonomousFlag

       Possibilities:
               disabled   (0)
               enabled   (1)"
   ::= {er1646v2EthPortSwFIpV6AddressesEntry 67567616}

er1646v2EthPortSwFIpV6AddressesRaValidLifeTime OBJECT-TYPE
   SYNTAX      TimeTicks
   MAX-ACCESS  read-write
   STATUS      current
   DESCRIPTION
      "Path: swPort.editConf.ipV6.addresses.ra.validLifeTime

       Time in centi-second."
   ::= {er1646v2EthPortSwFIpV6AddressesEntry 67239936}

er1646v2EthPortSwFIpV6AddressesRaValidLTMode OBJECT-TYPE
   SYNTAX      INTEGER
               {
               fixed (0),
               infinite (2)
               }
   MAX-ACCESS  read-write
   STATUS      current
   DESCRIPTION
      "Path: swPort.editConf.ipV6.addresses.ra.validLifeTimeMode

       Possibilities:
               fixed   (0)
               infinite   (2)"
   ::= {er1646v2EthPortSwFIpV6AddressesEntry 67305472}

er1646v2EthPortSwFIpV6AddressesRaPrefLifeTime OBJECT-TYPE
   SYNTAX      TimeTicks
   MAX-ACCESS  read-write
   STATUS      current
   DESCRIPTION
      "Path: swPort.editConf.ipV6.addresses.ra.prefLifeTime

       Time in centi-second."
   ::= {er1646v2EthPortSwFIpV6AddressesEntry 67436544}

er1646v2EthPortSwFIpV6AddressesRaPrefLTMode OBJECT-TYPE
   SYNTAX      INTEGER
               {
               fixed (0),
               infinite (2)
               }
   MAX-ACCESS  read-write
   STATUS      current
   DESCRIPTION
      "Path: swPort.editConf.ipV6.addresses.ra.prefLifeTimeMode

       Possibilities:
               fixed   (0)
               infinite   (2)"
   ::= {er1646v2EthPortSwFIpV6AddressesEntry 67502080}

er1646v2EthPortSwFIpV6RaDnsOptionsRdnssServers OBJECT-TYPE
   SYNTAX      SEQUENCE OF Er1646v2EthPortSwFIpV6RaDnsOptionsRdnssServersEntry
   MAX-ACCESS  not-accessible
   STATUS      current
   DESCRIPTION
      ""
   ::= {er1646v2EthPortSwFIpV6 101394432}

er1646v2EthPortSwFIpV6RaDnsOptionsRdnssServersEntry OBJECT-TYPE
   SYNTAX      Er1646v2EthPortSwFIpV6RaDnsOptionsRdnssServersEntry
   MAX-ACCESS  not-accessible
   STATUS      current
   DESCRIPTION
      ""
   INDEX      { er1646v2EthPortSwFIpV6RaDnsOptionsRdnssServersGlobalIx,
                er1646v2EthPortSwFIpV6RaDnsOptionsRdnssServersTableIx }
   ::= {er1646v2EthPortSwFIpV6RaDnsOptionsRdnssServers 1}

Er1646v2EthPortSwFIpV6RaDnsOptionsRdnssServersEntry ::=
   SEQUENCE
      {
      er1646v2EthPortSwFIpV6RaDnsOptionsRdnssServersActions
         VariableLengthTableActions,
      er1646v2EthPortSwFIpV6RaDnsOptionsRdnssServersGlobalIx
         GlobalIndex,
      er1646v2EthPortSwFIpV6RaDnsOptionsRdnssServersTableIx
         TableIndex,
      er1646v2EthPortSwFIpV6RaDnsOptionsRdnssServersAddress
         Ipv6Address
      }

er1646v2EthPortSwFIpV6RaDnsOptionsRdnssServersActions OBJECT-TYPE
   SYNTAX      VariableLengthTableActions
   MAX-ACCESS  read-write
   STATUS      current
   DESCRIPTION
      "By way of this field, some manipulations
       on this table may be performed."
   ::= {er1646v2EthPortSwFIpV6RaDnsOptionsRdnssServersEntry 2}

er1646v2EthPortSwFIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwFIpV6RaDnsOptionsRdnssServersEntry 10}

er1646v2EthPortSwFIpV6RaDnsOptionsRdnssServersTableIx OBJECT-TYPE
   SYNTAX      TableIndex
   MAX-ACCESS  not-accessible
   STATUS      current
   DESCRIPTION
      ""
   ::= {er1646v2EthPortSwFIpV6RaDnsOptionsRdnssServersEntry 11}

er1646v2EthPortSwFIpV6RaDnsOptionsRdnssServersAddress OBJECT-TYPE
   SYNTAX      Ipv6Address
   MAX-ACCESS  read-write
   STATUS      current
   DESCRIPTION
      "Path: swPort.editConf.ipV6.ra.dnsOptions.rdnss.servers.address

       ipv6 address"
   ::= {er1646v2EthPortSwFIpV6RaDnsOptionsRdnssServersEntry 16777216}

er1646v2EthPortSwFIpV6RaDnsOptionsDnsslDomains OBJECT-TYPE
   SYNTAX      SEQUENCE OF Er1646v2EthPortSwFIpV6RaDnsOptionsDnsslDomainsEntry
   MAX-ACCESS  not-accessible
   STATUS      current
   DESCRIPTION
      ""
   ::= {er1646v2EthPortSwFIpV6 101402624}

er1646v2EthPortSwFIpV6RaDnsOptionsDnsslDomainsEntry OBJECT-TYPE
   SYNTAX      Er1646v2EthPortSwFIpV6RaDnsOptionsDnsslDomainsEntry
   MAX-ACCESS  not-accessible
   STATUS      current
   DESCRIPTION
      ""
   INDEX      { er1646v2EthPortSwFIpV6RaDnsOptionsDnsslDomainsGlobalIx,
                er1646v2EthPortSwFIpV6RaDnsOptionsDnsslDomainsTableIx }
   ::= {er1646v2EthPortSwFIpV6RaDnsOptionsDnsslDomains 1}

Er1646v2EthPortSwFIpV6RaDnsOptionsDnsslDomainsEntry ::=
   SEQUENCE
      {
      er1646v2EthPortSwFIpV6RaDnsOptionsDnsslDomainsActions
         VariableLengthTableActions,
      er1646v2EthPortSwFIpV6RaDnsOptionsDnsslDomainsGlobalIx
         GlobalIndex,
      er1646v2EthPortSwFIpV6RaDnsOptionsDnsslDomainsTableIx
         TableIndex,
      er1646v2EthPortSwFIpV6RaDnsOptionsDnsslDomainsName
         DisplayString
      }

er1646v2EthPortSwFIpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwFIpV6RaDnsOptionsDnsslDomainsEntry 2}

er1646v2EthPortSwFIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwFIpV6RaDnsOptionsDnsslDomainsEntry 10}

er1646v2EthPortSwFIpV6RaDnsOptionsDnsslDomainsTableIx OBJECT-TYPE
   SYNTAX      TableIndex
   MAX-ACCESS  not-accessible
   STATUS      current
   DESCRIPTION
      ""
   ::= {er1646v2EthPortSwFIpV6RaDnsOptionsDnsslDomainsEntry 11}

er1646v2EthPortSwFIpV6RaDnsOptionsDnsslDomainsName OBJECT-TYPE
   SYNTAX      DisplayString
   MAX-ACCESS  read-write
   STATUS      current
   DESCRIPTION
      "Path: swPort.editConf.ipV6.ra.dnsOptions.dnssl.domains.name"
   ::= {er1646v2EthPortSwFIpV6RaDnsOptionsDnsslDomainsEntry 16777216}

er1646v2EthPortSwFIpV6DhcpClientUserClassOpt OBJECT-TYPE
   SYNTAX      SEQUENCE OF Er1646v2EthPortSwFIpV6DhcpClientUserClassOptEntry
   MAX-ACCESS  not-accessible
   STATUS      current
   DESCRIPTION
      ""
   ::= {er1646v2EthPortSwFIpV6 171442176}

er1646v2EthPortSwFIpV6DhcpClientUserClassOptEntry OBJECT-TYPE
   SYNTAX      Er1646v2EthPortSwFIpV6DhcpClientUserClassOptEntry
   MAX-ACCESS  not-accessible
   STATUS      current
   DESCRIPTION
      ""
   INDEX      { er1646v2EthPortSwFIpV6DhcpClientUserClassOptGlobalIx,
                er1646v2EthPortSwFIpV6DhcpClientUserClassOptTableIx }
   ::= {er1646v2EthPortSwFIpV6DhcpClientUserClassOpt 1}

Er1646v2EthPortSwFIpV6DhcpClientUserClassOptEntry ::=
   SEQUENCE
      {
      er1646v2EthPortSwFIpV6DhcpClientUserClassOptActions
         VariableLengthTableActions,
      er1646v2EthPortSwFIpV6DhcpClientUserClassOptGlobalIx
         GlobalIndex,
      er1646v2EthPortSwFIpV6DhcpClientUserClassOptTableIx
         TableIndex,
      er1646v2EthPortSwFIpV6DhcpClientUserClassOptValueAscii
         DisplayString,
      er1646v2EthPortSwFIpV6DhcpClientUserClassOptValueDecimal
         Integer32,
      er1646v2EthPortSwFIpV6DhcpClientUserClassOptValueHexData
         OCTET STRING
      }

er1646v2EthPortSwFIpV6DhcpClientUserClassOptActions OBJECT-TYPE
   SYNTAX      VariableLengthTableActions
   MAX-ACCESS  read-write
   STATUS      current
   DESCRIPTION
      "By way of this field, some manipulations
       on this table may be performed."
   ::= {er1646v2EthPortSwFIpV6DhcpClientUserClassOptEntry 2}

er1646v2EthPortSwFIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwFIpV6DhcpClientUserClassOptEntry 10}

er1646v2EthPortSwFIpV6DhcpClientUserClassOptTableIx OBJECT-TYPE
   SYNTAX      TableIndex
   MAX-ACCESS  not-accessible
   STATUS      current
   DESCRIPTION
      ""
   ::= {er1646v2EthPortSwFIpV6DhcpClientUserClassOptEntry 11}

er1646v2EthPortSwFIpV6DhcpClientUserClassOptValueAscii OBJECT-TYPE
   SYNTAX      DisplayString
   MAX-ACCESS  read-write
   STATUS      current
   DESCRIPTION
      "Path: swPort.editConf.ipV6.dhcp.client.userClassOpt.value.ascii"
   ::= {er1646v2EthPortSwFIpV6DhcpClientUserClassOptEntry 16842752}

er1646v2EthPortSwFIpV6DhcpClientUserClassOptValueDecimal OBJECT-TYPE
   SYNTAX      Integer32
   MAX-ACCESS  read-write
   STATUS      current
   DESCRIPTION
      "Path: swPort.editConf.ipV6.dhcp.client.userClassOpt.value.decimal"
   ::= {er1646v2EthPortSwFIpV6DhcpClientUserClassOptEntry 16908288}

er1646v2EthPortSwFIpV6DhcpClientUserClassOptValueHexData OBJECT-TYPE
   SYNTAX      OCTET STRING
   MAX-ACCESS  read-write
   STATUS      current
   DESCRIPTION
      "Path: swPort.editConf.ipV6.dhcp.client.userClassOpt.value.hexData"
   ::= {er1646v2EthPortSwFIpV6DhcpClientUserClassOptEntry 16973824}

er1646v2EthPortSwFIpV6DhcpClientVendorCl OBJECT-TYPE
   SYNTAX      SEQUENCE OF Er1646v2EthPortSwFIpV6DhcpClientVendorClEntry
   MAX-ACCESS  not-accessible
   STATUS      current
   DESCRIPTION
      ""
   ::= {er1646v2EthPortSwFIpV6 171704320}

er1646v2EthPortSwFIpV6DhcpClientVendorClEntry OBJECT-TYPE
   SYNTAX      Er1646v2EthPortSwFIpV6DhcpClientVendorClEntry
   MAX-ACCESS  not-accessible
   STATUS      current
   DESCRIPTION
      ""
   INDEX      { er1646v2EthPortSwFIpV6DhcpClientVendorClGlobalIx,
                er1646v2EthPortSwFIpV6DhcpClientVendorClTableIx }
   ::= {er1646v2EthPortSwFIpV6DhcpClientVendorCl 1}

Er1646v2EthPortSwFIpV6DhcpClientVendorClEntry ::=
   SEQUENCE
      {
      er1646v2EthPortSwFIpV6DhcpClientVendorClActions
         VariableLengthTableActions,
      er1646v2EthPortSwFIpV6DhcpClientVendorClGlobalIx
         GlobalIndex,
      er1646v2EthPortSwFIpV6DhcpClientVendorClTableIx
         TableIndex,
      er1646v2EthPortSwFIpV6DhcpClientVendorClValueAscii
         DisplayString,
      er1646v2EthPortSwFIpV6DhcpClientVendorClValueDecimal
         Integer32,
      er1646v2EthPortSwFIpV6DhcpClientVendorClValueHexData
         OCTET STRING
      }

er1646v2EthPortSwFIpV6DhcpClientVendorClActions OBJECT-TYPE
   SYNTAX      VariableLengthTableActions
   MAX-ACCESS  read-write
   STATUS      current
   DESCRIPTION
      "By way of this field, some manipulations
       on this table may be performed."
   ::= {er1646v2EthPortSwFIpV6DhcpClientVendorClEntry 2}

er1646v2EthPortSwFIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwFIpV6DhcpClientVendorClEntry 10}

er1646v2EthPortSwFIpV6DhcpClientVendorClTableIx OBJECT-TYPE
   SYNTAX      TableIndex
   MAX-ACCESS  not-accessible
   STATUS      current
   DESCRIPTION
      ""
   ::= {er1646v2EthPortSwFIpV6DhcpClientVendorClEntry 11}

er1646v2EthPortSwFIpV6DhcpClientVendorClValueAscii OBJECT-TYPE
   SYNTAX      DisplayString
   MAX-ACCESS  read-write
   STATUS      current
   DESCRIPTION
      "Path: swPort.editConf.ipV6.dhcp.client.vendorClassOpt.value.ascii"
   ::= {er1646v2EthPortSwFIpV6DhcpClientVendorClEntry 16842752}

er1646v2EthPortSwFIpV6DhcpClientVendorClValueDecimal OBJECT-TYPE
   SYNTAX      Integer32
   MAX-ACCESS  read-write
   STATUS      current
   DESCRIPTION
      "Path: swPort.editConf.ipV6.dhcp.client.vendorClassOpt.value.decimal"
   ::= {er1646v2EthPortSwFIpV6DhcpClientVendorClEntry 16908288}

er1646v2EthPortSwFIpV6DhcpClientVendorClValueHexData OBJECT-TYPE
   SYNTAX      OCTET STRING
   MAX-ACCESS  read-write
   STATUS      current
   DESCRIPTION
      "Path: swPort.editConf.ipV6.dhcp.client.vendorClassOpt.value.hexData"
   ::= {er1646v2EthPortSwFIpV6DhcpClientVendorClEntry 16973824}

er1646v2EthPortSwFIpV6DhcpRelayDestinations OBJECT-TYPE
   SYNTAX      SEQUENCE OF Er1646v2EthPortSwFIpV6DhcpRelayDestinationsEntry
   MAX-ACCESS  not-accessible
   STATUS      current
   DESCRIPTION
      ""
   ::= {er1646v2EthPortSwFIpV6 174080000}

er1646v2EthPortSwFIpV6DhcpRelayDestinationsEntry OBJECT-TYPE
   SYNTAX      Er1646v2EthPortSwFIpV6DhcpRelayDestinationsEntry
   MAX-ACCESS  not-accessible
   STATUS      current
   DESCRIPTION
      ""
   INDEX      { er1646v2EthPortSwFIpV6DhcpRelayDestinationsGlobalIx,
                er1646v2EthPortSwFIpV6DhcpRelayDestinationsTableIx }
   ::= {er1646v2EthPortSwFIpV6DhcpRelayDestinations 1}

Er1646v2EthPortSwFIpV6DhcpRelayDestinationsEntry ::=
   SEQUENCE
      {
      er1646v2EthPortSwFIpV6DhcpRelayDestinationsActions
         VariableLengthTableActions,
      er1646v2EthPortSwFIpV6DhcpRelayDestinationsGlobalIx
         GlobalIndex,
      er1646v2EthPortSwFIpV6DhcpRelayDestinationsTableIx
         TableIndex,
      er1646v2EthPortSwFIpV6DhcpRelayDestinationsAddress
         Ipv6Address,
      er1646v2EthPortSwFIpV6DhcpRelayDestinationsInterface
         DisplayString
      }

er1646v2EthPortSwFIpV6DhcpRelayDestinationsActions OBJECT-TYPE
   SYNTAX      VariableLengthTableActions
   MAX-ACCESS  read-write
   STATUS      current
   DESCRIPTION
      "By way of this field, some manipulations
       on this table may be performed."
   ::= {er1646v2EthPortSwFIpV6DhcpRelayDestinationsEntry 2}

er1646v2EthPortSwFIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwFIpV6DhcpRelayDestinationsEntry 10}

er1646v2EthPortSwFIpV6DhcpRelayDestinationsTableIx OBJECT-TYPE
   SYNTAX      TableIndex
   MAX-ACCESS  not-accessible
   STATUS      current
   DESCRIPTION
      ""
   ::= {er1646v2EthPortSwFIpV6DhcpRelayDestinationsEntry 11}

er1646v2EthPortSwFIpV6DhcpRelayDestinationsAddress OBJECT-TYPE
   SYNTAX      Ipv6Address
   MAX-ACCESS  read-write
   STATUS      current
   DESCRIPTION
      "Path: swPort.editConf.ipV6.dhcp.relay.destinations.address

       ipv6 address"
   ::= {er1646v2EthPortSwFIpV6DhcpRelayDestinationsEntry 16777216}

er1646v2EthPortSwFIpV6DhcpRelayDestinationsInterface OBJECT-TYPE
   SYNTAX      DisplayString
   MAX-ACCESS  read-write
   STATUS      current
   DESCRIPTION
      "Path: swPort.editConf.ipV6.dhcp.relay.destinations.interface"
   ::= {er1646v2EthPortSwFIpV6DhcpRelayDestinationsEntry 33554432}


er1646v2EthPortSwFMode OBJECT IDENTIFIER ::= {er1646v2EthPortSwF 29}

er1646v2EthPortSwFModeTable OBJECT-TYPE
   SYNTAX      SEQUENCE OF Er1646v2EthPortSwFModeEntry
   MAX-ACCESS  not-accessible
   STATUS      current
   DESCRIPTION
      "routing and/or bridging or ipV6 or multilink selection"
   ::= {er1646v2EthPortSwFMode 1}

er1646v2EthPortSwFModeEntry OBJECT-TYPE
   SYNTAX      Er1646v2EthPortSwFModeEntry
   MAX-ACCESS  not-accessible
   STATUS      current
   DESCRIPTION
      ""
   INDEX      { er1646v2EthPortSwFModeGlobalIx }
   ::= {er1646v2EthPortSwFModeTable 1}

Er1646v2EthPortSwFModeEntry ::=
   SEQUENCE
      {
      er1646v2EthPortSwFModeGlobalIx
         GlobalIndex,
      er1646v2EthPortSwFModeValue
         INTEGER
      }

er1646v2EthPortSwFModeGlobalIx OBJECT-TYPE
   SYNTAX      GlobalIndex
   MAX-ACCESS  not-accessible
   STATUS      current
   DESCRIPTION
      "The value of the tlsCntTreeGlobalIndex of the MANAGED OBJECT."
   ::= {er1646v2EthPortSwFModeEntry 10}

er1646v2EthPortSwFModeValue OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: swPort.editConf.mode

       Possibilities:
               bridging   (0)
               routing   (1)
               routingAndBridging   (2)
               ipV6   (3)
               ipV6/ipV4   (4)
               multilink   (5)"
   ::= {er1646v2EthPortSwFModeEntry 2147483648}


er1646v2EthPortSwFIp OBJECT IDENTIFIER ::= {er1646v2EthPortSwF 1}

er1646v2EthPortSwFIpSSCTable OBJECT-TYPE
   SYNTAX      SEQUENCE OF Er1646v2EthPortSwFIpEntry
   MAX-ACCESS  not-accessible
   STATUS      current
   DESCRIPTION
      "ip interface config parameters"
   ::= {er1646v2EthPortSwFIp 1}

er1646v2EthPortSwFIpEntry OBJECT-TYPE
   SYNTAX      Er1646v2EthPortSwFIpEntry
   MAX-ACCESS  not-accessible
   STATUS      current
   DESCRIPTION
      ""
   INDEX      { er1646v2EthPortSwFIpGlobalIx }
   ::= {er1646v2EthPortSwFIpSSCTable 1}

Er1646v2EthPortSwFIpEntry ::=
   SEQUENCE
      {
      er1646v2EthPortSwFIpGlobalIx
         GlobalIndex,
      er1646v2EthPortSwFIpVrfRouter
         DisplayString,
      er1646v2EthPortSwFIpAdr
         IpAddress,
      er1646v2EthPortSwFIpNetm
         IpAddress,
      er1646v2EthPortSwFIpSNetName
         INTEGER,
      er1646v2EthPortSwFIpSNetCust
         DisplayString,
      er1646v2EthPortSwFIpDhcpC
         INTEGER,
      er1646v2EthPortSwFIpDhcpGatewayPreference
         Integer32,
      er1646v2EthPortSwFIpDhcpRoutePreference
         Integer32,
      er1646v2EthPortSwFIpDhcpDnsPreference
         Integer32,
      er1646v2EthPortSwFIpMtu
         Integer32,
      er1646v2EthPortSwFIpMssAdjust
         INTEGER,
      er1646v2EthPortSwFIpRipMetric
         Integer32,
      er1646v2EthPortSwFIpRipMetricOut
         Integer32,
      er1646v2EthPortSwFIpRipMode
         INTEGER,
      er1646v2EthPortSwFIpRipTxVer
         INTEGER,
      er1646v2EthPortSwFIpRipRxVer
         INTEGER,
      er1646v2EthPortSwFIpRipSplitH
         INTEGER,
      er1646v2EthPortSwFIpRipAuth
         INTEGER,
      er1646v2EthPortSwFIpRipFilter
         DisplayString,
      er1646v2EthPortSwFIpRipFilterIn
         DisplayString,
      er1646v2EthPortSwFIpRipClearNextHop
         INTEGER,
      er1646v2EthPortSwFIpAccPol
         DisplayString,
      er1646v2EthPortSwFIpAB
         DisplayString,
      er1646v2EthPortSwFIpMA
         INTEGER,
      er1646v2EthPortSwFIpMF
         Integer32,
      er1646v2EthPortSwFIpDB
         INTEGER,
      er1646v2EthPortSwFIpIR
         INTEGER,
      er1646v2EthPortSwFIpIgmp
         INTEGER,
      er1646v2EthPortSwFIpNN
         DisplayString,
      er1646v2EthPortSwFIpVrrp
         INTEGER,
      er1646v2EthPortSwFIpPimMode
         INTEGER,
      er1646v2EthPortSwFIpPimDrPriority
         Counter32,
      er1646v2EthPortSwFIpPimHelloTime
         TimeTicks,
      er1646v2EthPortSwFIpPimPropagationDelay
         TimeTicks,
      er1646v2EthPortSwFIpPimOverrideInterval
         TimeTicks,
      er1646v2EthPortSwFIpPimBsrBorder
         INTEGER,
      er1646v2EthPortSwFIpPimTtlThreshold
         Integer32,
      er1646v2EthPortSwFIpIMNetworkUnreachable
         INTEGER,
      er1646v2EthPortSwFIpIMHostUnreachable
         INTEGER,
      er1646v2EthPortSwFIpIMProtocolUnreachable
         INTEGER,
      er1646v2EthPortSwFIpIMPortUnreachable
         INTEGER,
      er1646v2EthPortSwFIpIMMtuExceeded
         INTEGER,
      er1646v2EthPortSwFIpIMAdminProhibited
         INTEGER,
      er1646v2EthPortSwFIpIMTtlExceeded
         INTEGER,
      er1646v2EthPortSwFIpIMRedirect
         INTEGER
      }

er1646v2EthPortSwFIpGlobalIx OBJECT-TYPE
   SYNTAX      GlobalIndex
   MAX-ACCESS  not-accessible
   STATUS      current
   DESCRIPTION
      "The value of the tlsCntTreeGlobalIndex of the MANAGED OBJECT."
   ::= {er1646v2EthPortSwFIpEntry 10}

er1646v2EthPortSwFIpVrfRouter OBJECT-TYPE
   SYNTAX      DisplayString
   MAX-ACCESS  read-write
   STATUS      current
   DESCRIPTION
      "Path: swPort.editConf.ip.vrfRouter"
   ::= {er1646v2EthPortSwFIpEntry 738197504}

er1646v2EthPortSwFIpAdr OBJECT-TYPE
   SYNTAX      IpAddress
   MAX-ACCESS  read-write
   STATUS      current
   DESCRIPTION
      "Path: swPort.editConf.ip.address"
   ::= {er1646v2EthPortSwFIpEntry 2030043136}

er1646v2EthPortSwFIpNetm OBJECT-TYPE
   SYNTAX      IpAddress
   MAX-ACCESS  read-write
   STATUS      current
   DESCRIPTION
      "Path: swPort.editConf.ip.netMask"
   ::= {er1646v2EthPortSwFIpEntry 2063597568}

er1646v2EthPortSwFIpSNetName OBJECT-TYPE
   SYNTAX      INTEGER
               {
               slOPTg (0),
               corp (2),
               dmz (3),
               internet (1)
               }
   MAX-ACCESS  read-write
   STATUS      current
   DESCRIPTION
      "Path: swPort.editConf.ip.sNet.name

       Possibilities:
               <OPT>   (0)
               corp   (2)
               dmz   (3)
               internet   (1)"
   ::= {er1646v2EthPortSwFIpEntry 855703552}

er1646v2EthPortSwFIpSNetCust OBJECT-TYPE
   SYNTAX      DisplayString
   MAX-ACCESS  read-write
   STATUS      current
   DESCRIPTION
      "Path: swPort.editConf.ip.sNet.custom"
   ::= {er1646v2EthPortSwFIpEntry 855769088}

er1646v2EthPortSwFIpDhcpC OBJECT-TYPE
   SYNTAX      INTEGER
               {
               disabled (0),
               enabled (1)
               }
   MAX-ACCESS  read-write
   STATUS      current
   DESCRIPTION
      "Path: swPort.editConf.ip.dhcpClient

       Possibilities:
               disabled   (0)
               enabled   (1)"
   ::= {er1646v2EthPortSwFIpEntry 838860800}

er1646v2EthPortSwFIpDhcpGatewayPreference OBJECT-TYPE
   SYNTAX      Integer32
   MAX-ACCESS  read-write
   STATUS      current
   DESCRIPTION
      "Path: swPort.editConf.ip.dhcp.gatewayPreference"
   ::= {er1646v2EthPortSwFIpEntry 872480768}

er1646v2EthPortSwFIpDhcpRoutePreference OBJECT-TYPE
   SYNTAX      Integer32
   MAX-ACCESS  read-write
   STATUS      current
   DESCRIPTION
      "Path: swPort.editConf.ip.dhcp.routePreference"
   ::= {er1646v2EthPortSwFIpEntry 872546304}

er1646v2EthPortSwFIpDhcpDnsPreference OBJECT-TYPE
   SYNTAX      Integer32
   MAX-ACCESS  read-write
   STATUS      current
   DESCRIPTION
      "Path: swPort.editConf.ip.dhcp.dnsPreference"
   ::= {er1646v2EthPortSwFIpEntry 872611840}

er1646v2EthPortSwFIpMtu OBJECT-TYPE
   SYNTAX      Integer32
   MAX-ACCESS  read-write
   STATUS      current
   DESCRIPTION
      "Path: swPort.editConf.ip.mtu"
   ::= {er1646v2EthPortSwFIpEntry 671088640}

er1646v2EthPortSwFIpMssAdjust OBJECT-TYPE
   SYNTAX      INTEGER
               {
               disabled (0),
               auto (65536)
               }
   MAX-ACCESS  read-write
   STATUS      current
   DESCRIPTION
      "Path: swPort.editConf.ip.mssAdjust

       Possibilities:
               disabled   (0)
               auto   (65536)"
   ::= {er1646v2EthPortSwFIpEntry 754974720}

er1646v2EthPortSwFIpRipMetric OBJECT-TYPE
   SYNTAX      Integer32
   MAX-ACCESS  read-write
   STATUS      current
   DESCRIPTION
      "Path: swPort.editConf.ip.rip.metric"
   ::= {er1646v2EthPortSwFIpEntry 353566720}

er1646v2EthPortSwFIpRipMetricOut OBJECT-TYPE
   SYNTAX      Integer32
   MAX-ACCESS  read-write
   STATUS      current
   DESCRIPTION
      "Path: swPort.editConf.ip.rip.metricOut"
   ::= {er1646v2EthPortSwFIpEntry 353632256}

er1646v2EthPortSwFIpRipMode OBJECT-TYPE
   SYNTAX      INTEGER
               {
               disabled (0),
               passive (1),
               active (2)
               }
   MAX-ACCESS  read-write
   STATUS      current
   DESCRIPTION
      "Path: swPort.editConf.ip.rip.mode

       Possibilities:
               disabled   (0)
               passive   (1)
               active   (2)"
   ::= {er1646v2EthPortSwFIpEntry 353697792}

er1646v2EthPortSwFIpRipTxVer OBJECT-TYPE
   SYNTAX      INTEGER
               {
               rip1 (0),
               rip2 (1),
               rip1mcompatible (2)
               }
   MAX-ACCESS  read-write
   STATUS      current
   DESCRIPTION
      "Path: swPort.editConf.ip.rip.txVersion

       Possibilities:
               rip1   (0)
               rip2   (1)
               rip1-compatible   (2)"
   ::= {er1646v2EthPortSwFIpEntry 354615296}

er1646v2EthPortSwFIpRipRxVer OBJECT-TYPE
   SYNTAX      INTEGER
               {
               rip1only (0),
               rip2only (1),
               rip12 (2)
               }
   MAX-ACCESS  read-write
   STATUS      current
   DESCRIPTION
      "Path: swPort.editConf.ip.rip.rxVersion

       Possibilities:
               rip1only   (0)
               rip2only   (1)
               rip1&2   (2)"
   ::= {er1646v2EthPortSwFIpEntry 354680832}

er1646v2EthPortSwFIpRipSplitH OBJECT-TYPE
   SYNTAX      INTEGER
               {
               disabled (0),
               enabled (1),
               poisonedReverse (2)
               }
   MAX-ACCESS  read-write
   STATUS      current
   DESCRIPTION
      "Path: swPort.editConf.ip.rip.splitHorizon

       Possibilities:
               disabled   (0)
               enabled   (1)
               poisonedReverse   (2)"
   ::= {er1646v2EthPortSwFIpEntry 353828864}

er1646v2EthPortSwFIpRipAuth OBJECT-TYPE
   SYNTAX      INTEGER
               {
               disabled (0),
               texts (1),
               md5 (2)
               }
   MAX-ACCESS  read-write
   STATUS      current
   DESCRIPTION
      "Path: swPort.editConf.ip.rip.authentication

       Possibilities:
               disabled   (0)
               text    (1)
               md5   (2)"
   ::= {er1646v2EthPortSwFIpEntry 353501184}

er1646v2EthPortSwFIpRipFilter OBJECT-TYPE
   SYNTAX      DisplayString
   MAX-ACCESS  read-write
   STATUS      current
   DESCRIPTION
      "Path: swPort.editConf.ip.rip.filter"
   ::= {er1646v2EthPortSwFIpEntry 354418688}

er1646v2EthPortSwFIpRipFilterIn OBJECT-TYPE
   SYNTAX      DisplayString
   MAX-ACCESS  read-write
   STATUS      current
   DESCRIPTION
      "Path: swPort.editConf.ip.rip.filterIn"
   ::= {er1646v2EthPortSwFIpEntry 354484224}

er1646v2EthPortSwFIpRipClearNextHop OBJECT-TYPE
   SYNTAX      INTEGER
               {
               disabled (0),
               enabled (1)
               }
   MAX-ACCESS  read-write
   STATUS      current
   DESCRIPTION
      "Path: swPort.editConf.ip.rip.clearNextHop

       Possibilities:
               disabled   (0)
               enabled   (1)"
   ::= {er1646v2EthPortSwFIpEntry 352452608}

er1646v2EthPortSwFIpAccPol OBJECT-TYPE
   SYNTAX      DisplayString
   MAX-ACCESS  read-write
   STATUS      current
   DESCRIPTION
      "Path: swPort.editConf.ip.accessPolicy"
   ::= {er1646v2EthPortSwFIpEntry 704643072}

er1646v2EthPortSwFIpAB OBJECT-TYPE
   SYNTAX      DisplayString
   MAX-ACCESS  read-write
   STATUS      current
   DESCRIPTION
      "Path: swPort.editConf.ip.trafficPolicy"
   ::= {er1646v2EthPortSwFIpEntry 234881024}

er1646v2EthPortSwFIpMA OBJECT-TYPE
   SYNTAX      INTEGER
               {
               disabled (0),
               enabled (1)
               }
   MAX-ACCESS  read-write
   STATUS      current
   DESCRIPTION
      "Path: swPort.editConf.ip.mgmtAccess

       Possibilities:
               disabled   (0)
               enabled   (1)"
   ::= {er1646v2EthPortSwFIpEntry 268435456}

er1646v2EthPortSwFIpMF OBJECT-TYPE
   SYNTAX      Integer32
   MAX-ACCESS  read-write
   STATUS      current
   DESCRIPTION
      "Path: swPort.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwFIpEntry 285212672}

er1646v2EthPortSwFIpDB OBJECT-TYPE
   SYNTAX      INTEGER
               {
               disabled (0),
               enabled (1)
               }
   MAX-ACCESS  read-write
   STATUS      current
   DESCRIPTION
      "Path: swPort.editConf.ip.directedBroadcasts

       Possibilities:
               disabled   (0)
               enabled   (1)"
   ::= {er1646v2EthPortSwFIpEntry 369098752}

er1646v2EthPortSwFIpIR OBJECT-TYPE
   SYNTAX      INTEGER
               {
               disabled (0),
               enabled (1)
               }
   MAX-ACCESS  read-write
   STATUS      current
   DESCRIPTION
      "Path: swPort.editConf.ip.icmpRedirects

       Possibilities:
               disabled   (0)
               enabled   (1)"
   ::= {er1646v2EthPortSwFIpEntry 436207616}

er1646v2EthPortSwFIpIgmp OBJECT-TYPE
   SYNTAX      INTEGER
               {
               disabled (0),
               proxy (1),
               router (2),
               v3Router (5)
               }
   MAX-ACCESS  read-write
   STATUS      current
   DESCRIPTION
      "Path: swPort.editConf.ip.igmp

       Possibilities:
               disabled   (0)
               proxy   (1)
               router   (2)
               v3Router   (5)"
   ::= {er1646v2EthPortSwFIpEntry 536870912}

er1646v2EthPortSwFIpNN OBJECT-TYPE
   SYNTAX      DisplayString
   MAX-ACCESS  read-write
   STATUS      current
   DESCRIPTION
      "Path: swPort.editConf.ip.nat"
   ::= {er1646v2EthPortSwFIpEntry 452984832}

er1646v2EthPortSwFIpVrrp OBJECT-TYPE
   SYNTAX      INTEGER
               {
               disabled (0),
               enabled (1)
               }
   MAX-ACCESS  read-write
   STATUS      current
   DESCRIPTION
      "Path: swPort.editConf.ip.vrrp

       Possibilities:
               disabled   (0)
               enabled   (1)"
   ::= {er1646v2EthPortSwFIpEntry 721420288}

er1646v2EthPortSwFIpPimMode OBJECT-TYPE
   SYNTAX      INTEGER
               {
               disabled (0),
               sparse (1),
               passive (2)
               }
   MAX-ACCESS  read-write
   STATUS      current
   DESCRIPTION
      "Path: swPort.editConf.ip.pim.mode

       Possibilities:
               disabled   (0)
               sparse   (1)
               passive   (2)"
   ::= {er1646v2EthPortSwFIpEntry 771817472}

er1646v2EthPortSwFIpPimDrPriority OBJECT-TYPE
   SYNTAX      Counter32
   MAX-ACCESS  read-write
   STATUS      current
   DESCRIPTION
      "Path: swPort.editConf.ip.pim.drPriority

       32 bit unsigned wrappable counter."
   ::= {er1646v2EthPortSwFIpEntry 771883008}

er1646v2EthPortSwFIpPimHelloTime OBJECT-TYPE
   SYNTAX      TimeTicks
   MAX-ACCESS  read-write
   STATUS      current
   DESCRIPTION
      "Path: swPort.editConf.ip.pim.helloTime

       Time in centi-second."
   ::= {er1646v2EthPortSwFIpEntry 771948544}

er1646v2EthPortSwFIpPimPropagationDelay OBJECT-TYPE
   SYNTAX      TimeTicks
   MAX-ACCESS  read-write
   STATUS      current
   DESCRIPTION
      "Path: swPort.editConf.ip.pim.propagationDelay

       Time in centi-second."
   ::= {er1646v2EthPortSwFIpEntry 772014080}

er1646v2EthPortSwFIpPimOverrideInterval OBJECT-TYPE
   SYNTAX      TimeTicks
   MAX-ACCESS  read-write
   STATUS      current
   DESCRIPTION
      "Path: swPort.editConf.ip.pim.overrideInterval

       Time in centi-second."
   ::= {er1646v2EthPortSwFIpEntry 772079616}

er1646v2EthPortSwFIpPimBsrBorder OBJECT-TYPE
   SYNTAX      INTEGER
               {
               disabled (0),
               enabled (1)
               }
   MAX-ACCESS  read-write
   STATUS      current
   DESCRIPTION
      "Path: swPort.editConf.ip.pim.bsrBorder

       Possibilities:
               disabled   (0)
               enabled   (1)"
   ::= {er1646v2EthPortSwFIpEntry 772145152}

er1646v2EthPortSwFIpPimTtlThreshold OBJECT-TYPE
   SYNTAX      Integer32
   MAX-ACCESS  read-write
   STATUS      current
   DESCRIPTION
      "Path: swPort.editConf.ip.pim.ttlThreshold"
   ::= {er1646v2EthPortSwFIpEntry 772210688}

er1646v2EthPortSwFIpIMNetworkUnreachable OBJECT-TYPE
   SYNTAX      INTEGER
               {
               disabled (0),
               enabled (1)
               }
   MAX-ACCESS  read-write
   STATUS      current
   DESCRIPTION
      "Path: swPort.editConf.ip.icmpMessages.networkUnreachable

       Possibilities:
               disabled   (0)
               enabled   (1)"
   ::= {er1646v2EthPortSwFIpEntry 788594688}

er1646v2EthPortSwFIpIMHostUnreachable OBJECT-TYPE
   SYNTAX      INTEGER
               {
               disabled (0),
               enabled (1)
               }
   MAX-ACCESS  read-write
   STATUS      current
   DESCRIPTION
      "Path: swPort.editConf.ip.icmpMessages.hostUnreachable

       Possibilities:
               disabled   (0)
               enabled   (1)"
   ::= {er1646v2EthPortSwFIpEntry 788660224}

er1646v2EthPortSwFIpIMProtocolUnreachable OBJECT-TYPE
   SYNTAX      INTEGER
               {
               disabled (0),
               enabled (1)
               }
   MAX-ACCESS  read-write
   STATUS      current
   DESCRIPTION
      "Path: swPort.editConf.ip.icmpMessages.protocolUnreachable

       Possibilities:
               disabled   (0)
               enabled   (1)"
   ::= {er1646v2EthPortSwFIpEntry 788725760}

er1646v2EthPortSwFIpIMPortUnreachable OBJECT-TYPE
   SYNTAX      INTEGER
               {
               disabled (0),
               enabled (1)
               }
   MAX-ACCESS  read-write
   STATUS      current
   DESCRIPTION
      "Path: swPort.editConf.ip.icmpMessages.portUnreachable

       Possibilities:
               disabled   (0)
               enabled   (1)"
   ::= {er1646v2EthPortSwFIpEntry 788791296}

er1646v2EthPortSwFIpIMMtuExceeded OBJECT-TYPE
   SYNTAX      INTEGER
               {
               disabled (0),
               enabled (1)
               }
   MAX-ACCESS  read-write
   STATUS      current
   DESCRIPTION
      "Path: swPort.editConf.ip.icmpMessages.mtuExceeded

       Possibilities:
               disabled   (0)
               enabled   (1)"
   ::= {er1646v2EthPortSwFIpEntry 788856832}

er1646v2EthPortSwFIpIMAdminProhibited OBJECT-TYPE
   SYNTAX      INTEGER
               {
               disabled (0),
               enabled (1)
               }
   MAX-ACCESS  read-write
   STATUS      current
   DESCRIPTION
      "Path: swPort.editConf.ip.icmpMessages.adminProhibited

       Possibilities:
               disabled   (0)
               enabled   (1)"
   ::= {er1646v2EthPortSwFIpEntry 788922368}

er1646v2EthPortSwFIpIMTtlExceeded OBJECT-TYPE
   SYNTAX      INTEGER
               {
               disabled (0),
               enabled (1)
               }
   MAX-ACCESS  read-write
   STATUS      current
   DESCRIPTION
      "Path: swPort.editConf.ip.icmpMessages.ttlExceeded

       Possibilities:
               disabled   (0)
               enabled   (1)"
   ::= {er1646v2EthPortSwFIpEntry 788987904}

er1646v2EthPortSwFIpIMRedirect OBJECT-TYPE
   SYNTAX      INTEGER
               {
               disabled (0),
               enabled (1)
               }
   MAX-ACCESS  read-write
   STATUS      current
   DESCRIPTION
      "Path: swPort.editConf.ip.icmpMessages.redirect

       Possibilities:
               disabled   (0)
               enabled   (1)"
   ::= {er1646v2EthPortSwFIpEntry 789053440}

er1646v2EthPortSwFIpSaddr OBJECT-TYPE
   SYNTAX      SEQUENCE OF Er1646v2EthPortSwFIpSaddrEntry
   MAX-ACCESS  not-accessible
   STATUS      current
   DESCRIPTION
      ""
   ::= {er1646v2EthPortSwFIp 385875968}

er1646v2EthPortSwFIpSaddrEntry OBJECT-TYPE
   SYNTAX      Er1646v2EthPortSwFIpSaddrEntry
   MAX-ACCESS  not-accessible
   STATUS      current
   DESCRIPTION
      ""
   INDEX      { er1646v2EthPortSwFIpSaddrGlobalIx,
                er1646v2EthPortSwFIpSaddrTableIx }
   ::= {er1646v2EthPortSwFIpSaddr 1}

Er1646v2EthPortSwFIpSaddrEntry ::=
   SEQUENCE
      {
      er1646v2EthPortSwFIpSaddrActions
         VariableLengthTableActions,
      er1646v2EthPortSwFIpSaddrGlobalIx
         GlobalIndex,
      er1646v2EthPortSwFIpSaddrTableIx
         TableIndex,
      er1646v2EthPortSwFIpSaddrAddress
         IpAddress,
      er1646v2EthPortSwFIpSaddrNetMask
         IpAddress
      }

er1646v2EthPortSwFIpSaddrActions OBJECT-TYPE
   SYNTAX      VariableLengthTableActions
   MAX-ACCESS  read-write
   STATUS      current
   DESCRIPTION
      "By way of this field, some manipulations
       on this table may be performed."
   ::= {er1646v2EthPortSwFIpSaddrEntry 2}

er1646v2EthPortSwFIpSaddrGlobalIx OBJECT-TYPE
   SYNTAX      GlobalIndex
   MAX-ACCESS  not-accessible
   STATUS      current
   DESCRIPTION
      "The value of the tlsCntTreeGlobalIndex of the MANAGED OBJECT."
   ::= {er1646v2EthPortSwFIpSaddrEntry 10}

er1646v2EthPortSwFIpSaddrTableIx OBJECT-TYPE
   SYNTAX      TableIndex
   MAX-ACCESS  not-accessible
   STATUS      current
   DESCRIPTION
      ""
   ::= {er1646v2EthPortSwFIpSaddrEntry 11}

er1646v2EthPortSwFIpSaddrAddress OBJECT-TYPE
   SYNTAX      IpAddress
   MAX-ACCESS  read-write
   STATUS      current
   DESCRIPTION
      "Path: swPort.editConf.ip.secondaryIp.address"
   ::= {er1646v2EthPortSwFIpSaddrEntry 2030043136}

er1646v2EthPortSwFIpSaddrNetMask OBJECT-TYPE
   SYNTAX      IpAddress
   MAX-ACCESS  read-write
   STATUS      current
   DESCRIPTION
      "Path: swPort.editConf.ip.secondaryIp.netMask"
   ::= {er1646v2EthPortSwFIpSaddrEntry 2063597568}

er1646v2EthPortSwFIpH OBJECT-TYPE
   SYNTAX      SEQUENCE OF Er1646v2EthPortSwFIpHEntry
   MAX-ACCESS  not-accessible
   STATUS      current
   DESCRIPTION
      ""
   ::= {er1646v2EthPortSwFIp 251658240}

er1646v2EthPortSwFIpHEntry OBJECT-TYPE
   SYNTAX      Er1646v2EthPortSwFIpHEntry
   MAX-ACCESS  not-accessible
   STATUS      current
   DESCRIPTION
      ""
   INDEX      { er1646v2EthPortSwFIpHGlobalIx,
                er1646v2EthPortSwFIpHTableIx }
   ::= {er1646v2EthPortSwFIpH 1}

Er1646v2EthPortSwFIpHEntry ::=
   SEQUENCE
      {
      er1646v2EthPortSwFIpHActions
         VariableLengthTableActions,
      er1646v2EthPortSwFIpHGlobalIx
         GlobalIndex,
      er1646v2EthPortSwFIpHTableIx
         TableIndex,
      er1646v2EthPortSwFIpHAddress
         IpAddress,
      er1646v2EthPortSwFIpHDhcpRelayOptionSubscriberId
         DisplayString
      }

er1646v2EthPortSwFIpHActions OBJECT-TYPE
   SYNTAX      VariableLengthTableActions
   MAX-ACCESS  read-write
   STATUS      current
   DESCRIPTION
      "By way of this field, some manipulations
       on this table may be performed."
   ::= {er1646v2EthPortSwFIpHEntry 2}

er1646v2EthPortSwFIpHGlobalIx OBJECT-TYPE
   SYNTAX      GlobalIndex
   MAX-ACCESS  not-accessible
   STATUS      current
   DESCRIPTION
      "The value of the tlsCntTreeGlobalIndex of the MANAGED OBJECT."
   ::= {er1646v2EthPortSwFIpHEntry 10}

er1646v2EthPortSwFIpHTableIx OBJECT-TYPE
   SYNTAX      TableIndex
   MAX-ACCESS  not-accessible
   STATUS      current
   DESCRIPTION
      ""
   ::= {er1646v2EthPortSwFIpHEntry 11}

er1646v2EthPortSwFIpHAddress OBJECT-TYPE
   SYNTAX      IpAddress
   MAX-ACCESS  read-write
   STATUS      current
   DESCRIPTION
      "Path: swPort.editConf.ip.helpers.address"
   ::= {er1646v2EthPortSwFIpHEntry 16777216}

er1646v2EthPortSwFIpHDhcpRelayOptionSubscriberId OBJECT-TYPE
   SYNTAX      DisplayString
   MAX-ACCESS  read-write
   STATUS      current
   DESCRIPTION
      "Path: swPort.editConf.ip.helpers.dhcpRelayOption.subscriberId"
   ::= {er1646v2EthPortSwFIpHEntry 33947648}


er1646v2EthPortSwFName OBJECT IDENTIFIER ::= {er1646v2EthPortSwF 2}

er1646v2EthPortSwFNameTable OBJECT-TYPE
   SYNTAX      SEQUENCE OF Er1646v2EthPortSwFNameEntry
   MAX-ACCESS  not-accessible
   STATUS      current
   DESCRIPTION
      "config interface name"
   ::= {er1646v2EthPortSwFName 1}

er1646v2EthPortSwFNameEntry OBJECT-TYPE
   SYNTAX      Er1646v2EthPortSwFNameEntry
   MAX-ACCESS  not-accessible
   STATUS      current
   DESCRIPTION
      ""
   INDEX      { er1646v2EthPortSwFNameGlobalIx }
   ::= {er1646v2EthPortSwFNameTable 1}

Er1646v2EthPortSwFNameEntry ::=
   SEQUENCE
      {
      er1646v2EthPortSwFNameGlobalIx
         GlobalIndex,
      er1646v2EthPortSwFNameValue
         DisplayString
      }

er1646v2EthPortSwFNameGlobalIx OBJECT-TYPE
   SYNTAX      GlobalIndex
   MAX-ACCESS  not-accessible
   STATUS      current
   DESCRIPTION
      "The value of the tlsCntTreeGlobalIndex of the MANAGED OBJECT."
   ::= {er1646v2EthPortSwFNameEntry 10}

er1646v2EthPortSwFNameValue OBJECT-TYPE
   SYNTAX      DisplayString
   MAX-ACCESS  read-write
   STATUS      current
   DESCRIPTION
      "Path: swPort.editConf.name"
   ::= {er1646v2EthPortSwFNameEntry 2147483648}


er1646v2EthPortSwFBw OBJECT IDENTIFIER ::= {er1646v2EthPortSwF 5}

er1646v2EthPortSwFBwSSCTable OBJECT-TYPE
   SYNTAX      SEQUENCE OF Er1646v2EthPortSwFBwEntry
   MAX-ACCESS  not-accessible
   STATUS      current
   DESCRIPTION
      ""
   ::= {er1646v2EthPortSwFBw 1}

er1646v2EthPortSwFBwEntry OBJECT-TYPE
   SYNTAX      Er1646v2EthPortSwFBwEntry
   MAX-ACCESS  not-accessible
   STATUS      current
   DESCRIPTION
      ""
   INDEX      { er1646v2EthPortSwFBwGlobalIx }
   ::= {er1646v2EthPortSwFBwSSCTable 1}

Er1646v2EthPortSwFBwEntry ::=
   SEQUENCE
      {
      er1646v2EthPortSwFBwGlobalIx
         GlobalIndex,
      er1646v2EthPortSwFBwMode
         INTEGER,
      er1646v2EthPortSwFBwCir
         Integer32,
      er1646v2EthPortSwFBwEir
         Integer32,
      er1646v2EthPortSwFBwUnit
         INTEGER,
      er1646v2EthPortSwFBwTc
         INTEGER,
      er1646v2EthPortSwFBwTcFactor
         INTEGER,
      er1646v2EthPortSwFBwCorrType
         INTEGER,
      er1646v2EthPortSwFBwCorrPredefEncapsFrameRelay
         DisplayString,
      er1646v2EthPortSwFBwCorrPredefEncapsPpp
         DisplayString,
      er1646v2EthPortSwFBwCorrPredefEncapsAtmHl
         INTEGER,
      er1646v2EthPortSwFBwCorrPredefEncapsAtmMp
         INTEGER,
      er1646v2EthPortSwFBwCorrPredefEncapsHdlc
         DisplayString,
      er1646v2EthPortSwFBwCorrPredefEncapsEfmFs
         Integer32,
      er1646v2EthPortSwFBwCorrPredefEncapsEfmIb
         Integer32,
      er1646v2EthPortSwFBwCorrPredefMode
         INTEGER,
      er1646v2EthPortSwFBwCorrManualOverhead
         Integer32,
      er1646v2EthPortSwFBwCorrManualFrameData
         Counter32,
      er1646v2EthPortSwFBwCorrManualFrameHeader
         Counter32,
      er1646v2EthPortSwFBwMaxFifoQLen
         Integer32,
      er1646v2EthPortSwFBwDeFlagCir
         INTEGER,
      er1646v2EthPortSwFBwDeFlagEir
         INTEGER,
      er1646v2EthPortSwFBwDeFlagViolate
         INTEGER,
      er1646v2EthPortSwFBwActCirActNone
         OCTET STRING,
      er1646v2EthPortSwFBwActCirActEthCos1
         INTEGER,
      er1646v2EthPortSwFBwActCirActEthDei1
         INTEGER,
      er1646v2EthPortSwFBwActCirActEthCos2
         INTEGER,
      er1646v2EthPortSwFBwActCirActEthDei2
         INTEGER,
      er1646v2EthPortSwFBwActCirActEthCos3
         INTEGER,
      er1646v2EthPortSwFBwActCirActEthDei3
         INTEGER,
      er1646v2EthPortSwFBwActCirActEthCos4
         INTEGER,
      er1646v2EthPortSwFBwActCirActEthDei4
         INTEGER,
      er1646v2EthPortSwFBwActCirActEthCos5
         INTEGER,
      er1646v2EthPortSwFBwActCirActEthDei5
         INTEGER,
      er1646v2EthPortSwFBwActCirActEthCos6
         INTEGER,
      er1646v2EthPortSwFBwActCirActEthDei6
         INTEGER,
      er1646v2EthPortSwFBwActCirActEthCos7
         INTEGER,
      er1646v2EthPortSwFBwActCirActEthDei7
         INTEGER,
      er1646v2EthPortSwFBwActCirActEthCos8
         INTEGER,
      er1646v2EthPortSwFBwActCirActEthDei8
         INTEGER,
      er1646v2EthPortSwFBwActCirActEthTos
         INTEGER,
      er1646v2EthPortSwFBwActCirActEthQueue
         INTEGER,
      er1646v2EthPortSwFBwActCirActEthDrpLev
         INTEGER,
      er1646v2EthPortSwFBwActCirActEthDeFlag
         INTEGER,
      er1646v2EthPortSwFBwActCirActIpTos
         INTEGER,
      er1646v2EthPortSwFBwActCirActIpQueue
         INTEGER,
      er1646v2EthPortSwFBwActCirActIpDrpLev
         INTEGER,
      er1646v2EthPortSwFBwActCirActIpDeFlag
         INTEGER,
      er1646v2EthPortSwFBwActEirActNone
         OCTET STRING,
      er1646v2EthPortSwFBwActEirActEthCos1
         INTEGER,
      er1646v2EthPortSwFBwActEirActEthDei1
         INTEGER,
      er1646v2EthPortSwFBwActEirActEthCos2
         INTEGER,
      er1646v2EthPortSwFBwActEirActEthDei2
         INTEGER,
      er1646v2EthPortSwFBwActEirActEthCos3
         INTEGER,
      er1646v2EthPortSwFBwActEirActEthDei3
         INTEGER,
      er1646v2EthPortSwFBwActEirActEthCos4
         INTEGER,
      er1646v2EthPortSwFBwActEirActEthDei4
         INTEGER,
      er1646v2EthPortSwFBwActEirActEthCos5
         INTEGER,
      er1646v2EthPortSwFBwActEirActEthDei5
         INTEGER,
      er1646v2EthPortSwFBwActEirActEthCos6
         INTEGER,
      er1646v2EthPortSwFBwActEirActEthDei6
         INTEGER,
      er1646v2EthPortSwFBwActEirActEthCos7
         INTEGER,
      er1646v2EthPortSwFBwActEirActEthDei7
         INTEGER,
      er1646v2EthPortSwFBwActEirActEthCos8
         INTEGER,
      er1646v2EthPortSwFBwActEirActEthDei8
         INTEGER,
      er1646v2EthPortSwFBwActEirActEthTos
         INTEGER,
      er1646v2EthPortSwFBwActEirActEthQueue
         INTEGER,
      er1646v2EthPortSwFBwActEirActEthDrpLev
         INTEGER,
      er1646v2EthPortSwFBwActEirActEthDeFlag
         INTEGER,
      er1646v2EthPortSwFBwActEirActIpTos
         INTEGER,
      er1646v2EthPortSwFBwActEirActIpQueue
         INTEGER,
      er1646v2EthPortSwFBwActEirActIpDrpLev
         INTEGER,
      er1646v2EthPortSwFBwActEirActIpDeFlag
         INTEGER,
      er1646v2EthPortSwFBwActViolActNone
         OCTET STRING,
      er1646v2EthPortSwFBwActViolActDrop
         OCTET STRING,
      er1646v2EthPortSwFBwActViolActEthCos1
         INTEGER,
      er1646v2EthPortSwFBwActViolActEthDei1
         INTEGER,
      er1646v2EthPortSwFBwActViolActEthCos2
         INTEGER,
      er1646v2EthPortSwFBwActViolActEthDei2
         INTEGER,
      er1646v2EthPortSwFBwActViolActEthCos3
         INTEGER,
      er1646v2EthPortSwFBwActViolActEthDei3
         INTEGER,
      er1646v2EthPortSwFBwActViolActEthCos4
         INTEGER,
      er1646v2EthPortSwFBwActViolActEthDei4
         INTEGER,
      er1646v2EthPortSwFBwActViolActEthCos5
         INTEGER,
      er1646v2EthPortSwFBwActViolActEthDei5
         INTEGER,
      er1646v2EthPortSwFBwActViolActEthCos6
         INTEGER,
      er1646v2EthPortSwFBwActViolActEthDei6
         INTEGER,
      er1646v2EthPortSwFBwActViolActEthCos7
         INTEGER,
      er1646v2EthPortSwFBwActViolActEthDei7
         INTEGER,
      er1646v2EthPortSwFBwActViolActEthCos8
         INTEGER,
      er1646v2EthPortSwFBwActViolActEthDei8
         INTEGER,
      er1646v2EthPortSwFBwActViolActEthTos
         INTEGER,
      er1646v2EthPortSwFBwActViolActEthQueue
         INTEGER,
      er1646v2EthPortSwFBwActViolActEthDrpLev
         INTEGER,
      er1646v2EthPortSwFBwActViolActEthDeFlag
         INTEGER,
      er1646v2EthPortSwFBwActViolActIpTos
         INTEGER,
      er1646v2EthPortSwFBwActViolActIpQueue
         INTEGER,
      er1646v2EthPortSwFBwActViolActIpDrpLev
         INTEGER,
      er1646v2EthPortSwFBwActViolActIpDeFlag
         INTEGER
      }

er1646v2EthPortSwFBwGlobalIx OBJECT-TYPE
   SYNTAX      GlobalIndex
   MAX-ACCESS  not-accessible
   STATUS      current
   DESCRIPTION
      "The value of the tlsCntTreeGlobalIndex of the MANAGED OBJECT."
   ::= {er1646v2EthPortSwFBwEntry 10}

er1646v2EthPortSwFBwMode OBJECT-TYPE
   SYNTAX      INTEGER
               {
               reshaping (1),
               policing (2),
               policingReshape (3)
               }
   MAX-ACCESS  read-write
   STATUS      current
   DESCRIPTION
      "Path: swPort.editConf.bandwidth.mode

       Possibilities:
               reshaping   (1)
               policing   (2)
               policingReshape   (3)"
   ::= {er1646v2EthPortSwFBwEntry 3758096384}

er1646v2EthPortSwFBwCir OBJECT-TYPE
   SYNTAX      Integer32
   MAX-ACCESS  read-write
   STATUS      current
   DESCRIPTION
      "Path: swPort.editConf.bandwidth.cir"
   ::= {er1646v2EthPortSwFBwEntry 268435456}

er1646v2EthPortSwFBwEir OBJECT-TYPE
   SYNTAX      Integer32
   MAX-ACCESS  read-write
   STATUS      current
   DESCRIPTION
      "Path: swPort.editConf.bandwidth.eir"
   ::= {er1646v2EthPortSwFBwEntry 1879048192}

er1646v2EthPortSwFBwUnit OBJECT-TYPE
   SYNTAX      INTEGER
               {
               bitssec (1),
               percent (2)
               }
   MAX-ACCESS  read-write
   STATUS      current
   DESCRIPTION
      "Path: swPort.editConf.bandwidth.unit

       Possibilities:
               bits/sec   (1)
               percent   (2)"
   ::= {er1646v2EthPortSwFBwEntry 1342177280}

er1646v2EthPortSwFBwTc OBJECT-TYPE
   SYNTAX      INTEGER
               {
               auto (0)
               }
   MAX-ACCESS  read-write
   STATUS      current
   DESCRIPTION
      "Path: swPort.editConf.bandwidth.tc

       Possibilities:
               auto   (0)"
   ::= {er1646v2EthPortSwFBwEntry 1610612736}

er1646v2EthPortSwFBwTcFactor OBJECT-TYPE
   SYNTAX      INTEGER
               {
               ms (10),
               s100us (1)
               }
   MAX-ACCESS  read-write
   STATUS      current
   DESCRIPTION
      "Path: swPort.editConf.bandwidth.tcFactor

       Possibilities:
               ms   (10)
               *100us   (1)"
   ::= {er1646v2EthPortSwFBwEntry 2147483648}

er1646v2EthPortSwFBwCorrType OBJECT-TYPE
   SYNTAX      INTEGER
               {
               noCorrection (0),
               predefined (1),
               manual (2)
               }
   MAX-ACCESS  read-write
   STATUS      current
   DESCRIPTION
      "Path: swPort.editConf.bandwidth.correction.type

       Possibilities:
               noCorrection   (0)
               predefined   (1)
               manual   (2)"
   ::= {er1646v2EthPortSwFBwEntry 570425344}

er1646v2EthPortSwFBwCorrPredefEncapsFrameRelay OBJECT-TYPE
   SYNTAX      DisplayString
   MAX-ACCESS  read-write
   STATUS      current
   DESCRIPTION
      "Path: swPort.editConf.bandwidth.correction.predefined.encapsulation.frameRelay"
   ::= {er1646v2EthPortSwFBwEntry 608436224}

er1646v2EthPortSwFBwCorrPredefEncapsPpp OBJECT-TYPE
   SYNTAX      DisplayString
   MAX-ACCESS  read-write
   STATUS      current
   DESCRIPTION
      "Path: swPort.editConf.bandwidth.correction.predefined.encapsulation.ppp"
   ::= {er1646v2EthPortSwFBwEntry 608698368}

er1646v2EthPortSwFBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.bandwidth.correction.predefined.encapsulation.atm.higherLayer

       Possibilities:
               rfc2684   (0)
               ppp   (1)
               pppOverEthernet   (2)"
   ::= {er1646v2EthPortSwFBwEntry 608993280}

er1646v2EthPortSwFBwCorrPredefEncapsAtmMp OBJECT-TYPE
   SYNTAX      INTEGER
               {
               llcEncapsulation (0),
               vcMultiplexing (1)
               }
   MAX-ACCESS  read-write
   STATUS      current
   DESCRIPTION
      "Path: swPort.editConf.bandwidth.correction.predefined.encapsulation.atm.multiProtocol

       Possibilities:
               llcEncapsulation   (0)
               vcMultiplexing   (1)"
   ::= {er1646v2EthPortSwFBwEntry 609026048}

er1646v2EthPortSwFBwCorrPredefEncapsHdlc OBJECT-TYPE
   SYNTAX      DisplayString
   MAX-ACCESS  read-write
   STATUS      current
   DESCRIPTION
      "Path: swPort.editConf.bandwidth.correction.predefined.encapsulation.hdlc"
   ::= {er1646v2EthPortSwFBwEntry 609222656}

er1646v2EthPortSwFBwCorrPredefEncapsEfmFs OBJECT-TYPE
   SYNTAX      Integer32
   MAX-ACCESS  read-write
   STATUS      current
   DESCRIPTION
      "Path: swPort.editConf.bandwidth.correction.predefined.encapsulation.efm.fragmentSize"
   ::= {er1646v2EthPortSwFBwEntry 609517568}

er1646v2EthPortSwFBwCorrPredefEncapsEfmIb OBJECT-TYPE
   SYNTAX      Integer32
   MAX-ACCESS  read-write
   STATUS      current
   DESCRIPTION
      "Path: swPort.editConf.bandwidth.correction.predefined.encapsulation.efm.idleBytes"
   ::= {er1646v2EthPortSwFBwEntry 609550336}

er1646v2EthPortSwFBwCorrPredefMode OBJECT-TYPE
   SYNTAX      INTEGER
               {
               routing (0),
               bridging (1)
               }
   MAX-ACCESS  read-write
   STATUS      current
   DESCRIPTION
      "Path: swPort.editConf.bandwidth.correction.predefined.mode

       Possibilities:
               routing   (0)
               bridging   (1)"
   ::= {er1646v2EthPortSwFBwEntry 612368384}

er1646v2EthPortSwFBwCorrManualOverhead OBJECT-TYPE
   SYNTAX      Integer32
   MAX-ACCESS  read-write
   STATUS      current
   DESCRIPTION
      "Path: swPort.editConf.bandwidth.correction.manual.overhead"
   ::= {er1646v2EthPortSwFBwEntry 637665280}

er1646v2EthPortSwFBwCorrManualFrameData OBJECT-TYPE
   SYNTAX      Counter32
   MAX-ACCESS  read-write
   STATUS      current
   DESCRIPTION
      "Path: swPort.editConf.bandwidth.correction.manual.frameData

       32 bit unsigned wrappable counter."
   ::= {er1646v2EthPortSwFBwEntry 637796352}

er1646v2EthPortSwFBwCorrManualFrameHeader OBJECT-TYPE
   SYNTAX      Counter32
   MAX-ACCESS  read-write
   STATUS      current
   DESCRIPTION
      "Path: swPort.editConf.bandwidth.correction.manual.frameHeader

       32 bit unsigned wrappable counter."
   ::= {er1646v2EthPortSwFBwEntry 637927424}

er1646v2EthPortSwFBwMaxFifoQLen OBJECT-TYPE
   SYNTAX      Integer32
   MAX-ACCESS  read-write
   STATUS      current
   DESCRIPTION
      "Path: swPort.editConf.bandwidth.maxFifoQLen"
   ::= {er1646v2EthPortSwFBwEntry 805306368}

er1646v2EthPortSwFBwDeFlagCir OBJECT-TYPE
   SYNTAX      INTEGER
               {
               allowed (1),
               notAllowed (2)
               }
   MAX-ACCESS  read-write
   STATUS      current
   DESCRIPTION
      "Path: swPort.editConf.bandwidth.deFlag.cir

       Possibilities:
               allowed   (1)
               notAllowed   (2)"
   ::= {er1646v2EthPortSwFBwEntry 3490709504}

er1646v2EthPortSwFBwDeFlagEir OBJECT-TYPE
   SYNTAX      INTEGER
               {
               allowed (1),
               notAllowed (2)
               }
   MAX-ACCESS  read-write
   STATUS      current
   DESCRIPTION
      "Path: swPort.editConf.bandwidth.deFlag.eir

       Possibilities:
               allowed   (1)
               notAllowed   (2)"
   ::= {er1646v2EthPortSwFBwEntry 3491758080}

er1646v2EthPortSwFBwDeFlagViolate OBJECT-TYPE
   SYNTAX      INTEGER
               {
               allowed (1),
               notAllowed (2)
               }
   MAX-ACCESS  read-write
   STATUS      current
   DESCRIPTION
      "Path: swPort.editConf.bandwidth.deFlag.violate

       Possibilities:
               allowed   (1)
               notAllowed   (2)"
   ::= {er1646v2EthPortSwFBwEntry 3492806656}

er1646v2EthPortSwFBwActCirActNone OBJECT-TYPE
   SYNTAX      OCTET STRING
   MAX-ACCESS  read-write
   STATUS      current
   DESCRIPTION
      "Path: swPort.editConf.bandwidth.action.cirAction.none"
   ::= {er1646v2EthPortSwFBwEntry 4062183424}

er1646v2EthPortSwFBwActCirActEthCos1 OBJECT-TYPE
   SYNTAX      INTEGER
               {
               unchanged (256)
               }
   MAX-ACCESS  read-write
   STATUS      current
   DESCRIPTION
      "Path: swPort.editConf.bandwidth.action.cirAction.ethernet.cosDepth1

       Possibilities:
               unchanged   (256)"
   ::= {er1646v2EthPortSwFBwEntry 4064346112}

er1646v2EthPortSwFBwActCirActEthDei1 OBJECT-TYPE
   SYNTAX      INTEGER
               {
               unchanged (255),
               clear (0),
               set (1)
               }
   MAX-ACCESS  read-write
   STATUS      current
   DESCRIPTION
      "Path: swPort.editConf.bandwidth.action.cirAction.ethernet.deiDepth1

       Possibilities:
               unchanged   (255)
               clear   (0)
               set   (1)"
   ::= {er1646v2EthPortSwFBwEntry 4065656832}

er1646v2EthPortSwFBwActCirActEthCos2 OBJECT-TYPE
   SYNTAX      INTEGER
               {
               unchanged (256)
               }
   MAX-ACCESS  read-write
   STATUS      current
   DESCRIPTION
      "Path: swPort.editConf.bandwidth.action.cirAction.ethernet.cosDepth2

       Possibilities:
               unchanged   (256)"
   ::= {er1646v2EthPortSwFBwEntry 4064411648}

er1646v2EthPortSwFBwActCirActEthDei2 OBJECT-TYPE
   SYNTAX      INTEGER
               {
               unchanged (255),
               clear (0),
               set (1)
               }
   MAX-ACCESS  read-write
   STATUS      current
   DESCRIPTION
      "Path: swPort.editConf.bandwidth.action.cirAction.ethernet.deiDepth2

       Possibilities:
               unchanged   (255)
               clear   (0)
               set   (1)"
   ::= {er1646v2EthPortSwFBwEntry 4065722368}

er1646v2EthPortSwFBwActCirActEthCos3 OBJECT-TYPE
   SYNTAX      INTEGER
               {
               unchanged (256)
               }
   MAX-ACCESS  read-write
   STATUS      current
   DESCRIPTION
      "Path: swPort.editConf.bandwidth.action.cirAction.ethernet.cosDepth3

       Possibilities:
               unchanged   (256)"
   ::= {er1646v2EthPortSwFBwEntry 4064477184}

er1646v2EthPortSwFBwActCirActEthDei3 OBJECT-TYPE
   SYNTAX      INTEGER
               {
               unchanged (255),
               clear (0),
               set (1)
               }
   MAX-ACCESS  read-write
   STATUS      current
   DESCRIPTION
      "Path: swPort.editConf.bandwidth.action.cirAction.ethernet.deiDepth3

       Possibilities:
               unchanged   (255)
               clear   (0)
               set   (1)"
   ::= {er1646v2EthPortSwFBwEntry 4065787904}

er1646v2EthPortSwFBwActCirActEthCos4 OBJECT-TYPE
   SYNTAX      INTEGER
               {
               unchanged (256)
               }
   MAX-ACCESS  read-write
   STATUS      current
   DESCRIPTION
      "Path: swPort.editConf.bandwidth.action.cirAction.ethernet.cosDepth4

       Possibilities:
               unchanged   (256)"
   ::= {er1646v2EthPortSwFBwEntry 4064542720}

er1646v2EthPortSwFBwActCirActEthDei4 OBJECT-TYPE
   SYNTAX      INTEGER
               {
               unchanged (255),
               clear (0),
               set (1)
               }
   MAX-ACCESS  read-write
   STATUS      current
   DESCRIPTION
      "Path: swPort.editConf.bandwidth.action.cirAction.ethernet.deiDepth4

       Possibilities:
               unchanged   (255)
               clear   (0)
               set   (1)"
   ::= {er1646v2EthPortSwFBwEntry 4065853440}

er1646v2EthPortSwFBwActCirActEthCos5 OBJECT-TYPE
   SYNTAX      INTEGER
               {
               unchanged (256)
               }
   MAX-ACCESS  read-write
   STATUS      current
   DESCRIPTION
      "Path: swPort.editConf.bandwidth.action.cirAction.ethernet.cosDepth5

       Possibilities:
               unchanged   (256)"
   ::= {er1646v2EthPortSwFBwEntry 4064608256}

er1646v2EthPortSwFBwActCirActEthDei5 OBJECT-TYPE
   SYNTAX      INTEGER
               {
               unchanged (255),
               clear (0),
               set (1)
               }
   MAX-ACCESS  read-write
   STATUS      current
   DESCRIPTION
      "Path: swPort.editConf.bandwidth.action.cirAction.ethernet.deiDepth5

       Possibilities:
               unchanged   (255)
               clear   (0)
               set   (1)"
   ::= {er1646v2EthPortSwFBwEntry 4065918976}

er1646v2EthPortSwFBwActCirActEthCos6 OBJECT-TYPE
   SYNTAX      INTEGER
               {
               unchanged (256)
               }
   MAX-ACCESS  read-write
   STATUS      current
   DESCRIPTION
      "Path: swPort.editConf.bandwidth.action.cirAction.ethernet.cosDepth6

       Possibilities:
               unchanged   (256)"
   ::= {er1646v2EthPortSwFBwEntry 4064673792}

er1646v2EthPortSwFBwActCirActEthDei6 OBJECT-TYPE
   SYNTAX      INTEGER
               {
               unchanged (255),
               clear (0),
               set (1)
               }
   MAX-ACCESS  read-write
   STATUS      current
   DESCRIPTION
      "Path: swPort.editConf.bandwidth.action.cirAction.ethernet.deiDepth6

       Possibilities:
               unchanged   (255)
               clear   (0)
               set   (1)"
   ::= {er1646v2EthPortSwFBwEntry 4065984512}

er1646v2EthPortSwFBwActCirActEthCos7 OBJECT-TYPE
   SYNTAX      INTEGER
               {
               unchanged (256)
               }
   MAX-ACCESS  read-write
   STATUS      current
   DESCRIPTION
      "Path: swPort.editConf.bandwidth.action.cirAction.ethernet.cosDepth7

       Possibilities:
               unchanged   (256)"
   ::= {er1646v2EthPortSwFBwEntry 4064739328}

er1646v2EthPortSwFBwActCirActEthDei7 OBJECT-TYPE
   SYNTAX      INTEGER
               {
               unchanged (255),
               clear (0),
               set (1)
               }
   MAX-ACCESS  read-write
   STATUS      current
   DESCRIPTION
      "Path: swPort.editConf.bandwidth.action.cirAction.ethernet.deiDepth7

       Possibilities:
               unchanged   (255)
               clear   (0)
               set   (1)"
   ::= {er1646v2EthPortSwFBwEntry 4066050048}

er1646v2EthPortSwFBwActCirActEthCos8 OBJECT-TYPE
   SYNTAX      INTEGER
               {
               unchanged (256)
               }
   MAX-ACCESS  read-write
   STATUS      current
   DESCRIPTION
      "Path: swPort.editConf.bandwidth.action.cirAction.ethernet.cosDepth8

       Possibilities:
               unchanged   (256)"
   ::= {er1646v2EthPortSwFBwEntry 4064804864}

er1646v2EthPortSwFBwActCirActEthDei8 OBJECT-TYPE
   SYNTAX      INTEGER
               {
               unchanged (255),
               clear (0),
               set (1)
               }
   MAX-ACCESS  read-write
   STATUS      current
   DESCRIPTION
      "Path: swPort.editConf.bandwidth.action.cirAction.ethernet.deiDepth8

       Possibilities:
               unchanged   (255)
               clear   (0)
               set   (1)"
   ::= {er1646v2EthPortSwFBwEntry 4066115584}

er1646v2EthPortSwFBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4064870400}

er1646v2EthPortSwFBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4064935936}

er1646v2EthPortSwFBwActCirActEthDrpLev OBJECT-TYPE
   SYNTAX      INTEGER
               {
               unchanged (0)
               }
   MAX-ACCESS  read-write
   STATUS      current
   DESCRIPTION
      "Path: swPort.editConf.bandwidth.action.cirAction.ethernet.dropLevel

       Possibilities:
               unchanged   (0)"
   ::= {er1646v2EthPortSwFBwEntry 4065001472}

er1646v2EthPortSwFBwActCirActEthDeFlag OBJECT-TYPE
   SYNTAX      INTEGER
               {
               unchanged (255),
               clear (0),
               set (1)
               }
   MAX-ACCESS  read-write
   STATUS      current
   DESCRIPTION
      "Path: swPort.editConf.bandwidth.action.cirAction.ethernet.deFlag

       Possibilities:
               unchanged   (255)
               clear   (0)
               set   (1)"
   ::= {er1646v2EthPortSwFBwEntry 4065198080}

er1646v2EthPortSwFBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4071161856}

er1646v2EthPortSwFBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4071227392}

er1646v2EthPortSwFBwActCirActIpDrpLev OBJECT-TYPE
   SYNTAX      INTEGER
               {
               unchanged (0)
               }
   MAX-ACCESS  read-write
   STATUS      current
   DESCRIPTION
      "Path: swPort.editConf.bandwidth.action.cirAction.ip.dropLevel

       Possibilities:
               unchanged   (0)"
   ::= {er1646v2EthPortSwFBwEntry 4071292928}

er1646v2EthPortSwFBwActCirActIpDeFlag OBJECT-TYPE
   SYNTAX      INTEGER
               {
               unchanged (255),
               clear (0),
               set (1)
               }
   MAX-ACCESS  read-write
   STATUS      current
   DESCRIPTION
      "Path: swPort.editConf.bandwidth.action.cirAction.ip.deFlag

       Possibilities:
               unchanged   (255)
               clear   (0)
               set   (1)"
   ::= {er1646v2EthPortSwFBwEntry 4071489536}

er1646v2EthPortSwFBwActEirActNone OBJECT-TYPE
   SYNTAX      OCTET STRING
   MAX-ACCESS  read-write
   STATUS      current
   DESCRIPTION
      "Path: swPort.editConf.bandwidth.action.eirAction.none"
   ::= {er1646v2EthPortSwFBwEntry 4095737856}

er1646v2EthPortSwFBwActEirActEthCos1 OBJECT-TYPE
   SYNTAX      INTEGER
               {
               unchanged (256)
               }
   MAX-ACCESS  read-write
   STATUS      current
   DESCRIPTION
      "Path: swPort.editConf.bandwidth.action.eirAction.ethernet.cosDepth1

       Possibilities:
               unchanged   (256)"
   ::= {er1646v2EthPortSwFBwEntry 4097900544}

er1646v2EthPortSwFBwActEirActEthDei1 OBJECT-TYPE
   SYNTAX      INTEGER
               {
               unchanged (255),
               clear (0),
               set (1)
               }
   MAX-ACCESS  read-write
   STATUS      current
   DESCRIPTION
      "Path: swPort.editConf.bandwidth.action.eirAction.ethernet.deiDepth1

       Possibilities:
               unchanged   (255)
               clear   (0)
               set   (1)"
   ::= {er1646v2EthPortSwFBwEntry 4099211264}

er1646v2EthPortSwFBwActEirActEthCos2 OBJECT-TYPE
   SYNTAX      INTEGER
               {
               unchanged (256)
               }
   MAX-ACCESS  read-write
   STATUS      current
   DESCRIPTION
      "Path: swPort.editConf.bandwidth.action.eirAction.ethernet.cosDepth2

       Possibilities:
               unchanged   (256)"
   ::= {er1646v2EthPortSwFBwEntry 4097966080}

er1646v2EthPortSwFBwActEirActEthDei2 OBJECT-TYPE
   SYNTAX      INTEGER
               {
               unchanged (255),
               clear (0),
               set (1)
               }
   MAX-ACCESS  read-write
   STATUS      current
   DESCRIPTION
      "Path: swPort.editConf.bandwidth.action.eirAction.ethernet.deiDepth2

       Possibilities:
               unchanged   (255)
               clear   (0)
               set   (1)"
   ::= {er1646v2EthPortSwFBwEntry 4099276800}

er1646v2EthPortSwFBwActEirActEthCos3 OBJECT-TYPE
   SYNTAX      INTEGER
               {
               unchanged (256)
               }
   MAX-ACCESS  read-write
   STATUS      current
   DESCRIPTION
      "Path: swPort.editConf.bandwidth.action.eirAction.ethernet.cosDepth3

       Possibilities:
               unchanged   (256)"
   ::= {er1646v2EthPortSwFBwEntry 4098031616}

er1646v2EthPortSwFBwActEirActEthDei3 OBJECT-TYPE
   SYNTAX      INTEGER
               {
               unchanged (255),
               clear (0),
               set (1)
               }
   MAX-ACCESS  read-write
   STATUS      current
   DESCRIPTION
      "Path: swPort.editConf.bandwidth.action.eirAction.ethernet.deiDepth3

       Possibilities:
               unchanged   (255)
               clear   (0)
               set   (1)"
   ::= {er1646v2EthPortSwFBwEntry 4099342336}

er1646v2EthPortSwFBwActEirActEthCos4 OBJECT-TYPE
   SYNTAX      INTEGER
               {
               unchanged (256)
               }
   MAX-ACCESS  read-write
   STATUS      current
   DESCRIPTION
      "Path: swPort.editConf.bandwidth.action.eirAction.ethernet.cosDepth4

       Possibilities:
               unchanged   (256)"
   ::= {er1646v2EthPortSwFBwEntry 4098097152}

er1646v2EthPortSwFBwActEirActEthDei4 OBJECT-TYPE
   SYNTAX      INTEGER
               {
               unchanged (255),
               clear (0),
               set (1)
               }
   MAX-ACCESS  read-write
   STATUS      current
   DESCRIPTION
      "Path: swPort.editConf.bandwidth.action.eirAction.ethernet.deiDepth4

       Possibilities:
               unchanged   (255)
               clear   (0)
               set   (1)"
   ::= {er1646v2EthPortSwFBwEntry 4099407872}

er1646v2EthPortSwFBwActEirActEthCos5 OBJECT-TYPE
   SYNTAX      INTEGER
               {
               unchanged (256)
               }
   MAX-ACCESS  read-write
   STATUS      current
   DESCRIPTION
      "Path: swPort.editConf.bandwidth.action.eirAction.ethernet.cosDepth5

       Possibilities:
               unchanged   (256)"
   ::= {er1646v2EthPortSwFBwEntry 4098162688}

er1646v2EthPortSwFBwActEirActEthDei5 OBJECT-TYPE
   SYNTAX      INTEGER
               {
               unchanged (255),
               clear (0),
               set (1)
               }
   MAX-ACCESS  read-write
   STATUS      current
   DESCRIPTION
      "Path: swPort.editConf.bandwidth.action.eirAction.ethernet.deiDepth5

       Possibilities:
               unchanged   (255)
               clear   (0)
               set   (1)"
   ::= {er1646v2EthPortSwFBwEntry 4099473408}

er1646v2EthPortSwFBwActEirActEthCos6 OBJECT-TYPE
   SYNTAX      INTEGER
               {
               unchanged (256)
               }
   MAX-ACCESS  read-write
   STATUS      current
   DESCRIPTION
      "Path: swPort.editConf.bandwidth.action.eirAction.ethernet.cosDepth6

       Possibilities:
               unchanged   (256)"
   ::= {er1646v2EthPortSwFBwEntry 4098228224}

er1646v2EthPortSwFBwActEirActEthDei6 OBJECT-TYPE
   SYNTAX      INTEGER
               {
               unchanged (255),
               clear (0),
               set (1)
               }
   MAX-ACCESS  read-write
   STATUS      current
   DESCRIPTION
      "Path: swPort.editConf.bandwidth.action.eirAction.ethernet.deiDepth6

       Possibilities:
               unchanged   (255)
               clear   (0)
               set   (1)"
   ::= {er1646v2EthPortSwFBwEntry 4099538944}

er1646v2EthPortSwFBwActEirActEthCos7 OBJECT-TYPE
   SYNTAX      INTEGER
               {
               unchanged (256)
               }
   MAX-ACCESS  read-write
   STATUS      current
   DESCRIPTION
      "Path: swPort.editConf.bandwidth.action.eirAction.ethernet.cosDepth7

       Possibilities:
               unchanged   (256)"
   ::= {er1646v2EthPortSwFBwEntry 4098293760}

er1646v2EthPortSwFBwActEirActEthDei7 OBJECT-TYPE
   SYNTAX      INTEGER
               {
               unchanged (255),
               clear (0),
               set (1)
               }
   MAX-ACCESS  read-write
   STATUS      current
   DESCRIPTION
      "Path: swPort.editConf.bandwidth.action.eirAction.ethernet.deiDepth7

       Possibilities:
               unchanged   (255)
               clear   (0)
               set   (1)"
   ::= {er1646v2EthPortSwFBwEntry 4099604480}

er1646v2EthPortSwFBwActEirActEthCos8 OBJECT-TYPE
   SYNTAX      INTEGER
               {
               unchanged (256)
               }
   MAX-ACCESS  read-write
   STATUS      current
   DESCRIPTION
      "Path: swPort.editConf.bandwidth.action.eirAction.ethernet.cosDepth8

       Possibilities:
               unchanged   (256)"
   ::= {er1646v2EthPortSwFBwEntry 4098359296}

er1646v2EthPortSwFBwActEirActEthDei8 OBJECT-TYPE
   SYNTAX      INTEGER
               {
               unchanged (255),
               clear (0),
               set (1)
               }
   MAX-ACCESS  read-write
   STATUS      current
   DESCRIPTION
      "Path: swPort.editConf.bandwidth.action.eirAction.ethernet.deiDepth8

       Possibilities:
               unchanged   (255)
               clear   (0)
               set   (1)"
   ::= {er1646v2EthPortSwFBwEntry 4099670016}

er1646v2EthPortSwFBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4098424832}

er1646v2EthPortSwFBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4098490368}

er1646v2EthPortSwFBwActEirActEthDrpLev OBJECT-TYPE
   SYNTAX      INTEGER
               {
               unchanged (0)
               }
   MAX-ACCESS  read-write
   STATUS      current
   DESCRIPTION
      "Path: swPort.editConf.bandwidth.action.eirAction.ethernet.dropLevel

       Possibilities:
               unchanged   (0)"
   ::= {er1646v2EthPortSwFBwEntry 4098555904}

er1646v2EthPortSwFBwActEirActEthDeFlag OBJECT-TYPE
   SYNTAX      INTEGER
               {
               unchanged (255),
               clear (0),
               set (1)
               }
   MAX-ACCESS  read-write
   STATUS      current
   DESCRIPTION
      "Path: swPort.editConf.bandwidth.action.eirAction.ethernet.deFlag

       Possibilities:
               unchanged   (255)
               clear   (0)
               set   (1)"
   ::= {er1646v2EthPortSwFBwEntry 4098752512}

er1646v2EthPortSwFBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4104716288}

er1646v2EthPortSwFBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4104781824}

er1646v2EthPortSwFBwActEirActIpDrpLev OBJECT-TYPE
   SYNTAX      INTEGER
               {
               unchanged (0)
               }
   MAX-ACCESS  read-write
   STATUS      current
   DESCRIPTION
      "Path: swPort.editConf.bandwidth.action.eirAction.ip.dropLevel

       Possibilities:
               unchanged   (0)"
   ::= {er1646v2EthPortSwFBwEntry 4104847360}

er1646v2EthPortSwFBwActEirActIpDeFlag OBJECT-TYPE
   SYNTAX      INTEGER
               {
               unchanged (255),
               clear (0),
               set (1)
               }
   MAX-ACCESS  read-write
   STATUS      current
   DESCRIPTION
      "Path: swPort.editConf.bandwidth.action.eirAction.ip.deFlag

       Possibilities:
               unchanged   (255)
               clear   (0)
               set   (1)"
   ::= {er1646v2EthPortSwFBwEntry 4105043968}

er1646v2EthPortSwFBwActViolActNone OBJECT-TYPE
   SYNTAX      OCTET STRING
   MAX-ACCESS  read-write
   STATUS      current
   DESCRIPTION
      "Path: swPort.editConf.bandwidth.action.violateAction.none"
   ::= {er1646v2EthPortSwFBwEntry 4129292288}

er1646v2EthPortSwFBwActViolActDrop OBJECT-TYPE
   SYNTAX      OCTET STRING
   MAX-ACCESS  read-write
   STATUS      current
   DESCRIPTION
      "Path: swPort.editConf.bandwidth.action.violateAction.drop"
   ::= {er1646v2EthPortSwFBwEntry 4133486592}

er1646v2EthPortSwFBwActViolActEthCos1 OBJECT-TYPE
   SYNTAX      INTEGER
               {
               unchanged (256)
               }
   MAX-ACCESS  read-write
   STATUS      current
   DESCRIPTION
      "Path: swPort.editConf.bandwidth.action.violateAction.ethernet.cosDepth1

       Possibilities:
               unchanged   (256)"
   ::= {er1646v2EthPortSwFBwEntry 4131454976}

er1646v2EthPortSwFBwActViolActEthDei1 OBJECT-TYPE
   SYNTAX      INTEGER
               {
               unchanged (255),
               clear (0),
               set (1)
               }
   MAX-ACCESS  read-write
   STATUS      current
   DESCRIPTION
      "Path: swPort.editConf.bandwidth.action.violateAction.ethernet.deiDepth1

       Possibilities:
               unchanged   (255)
               clear   (0)
               set   (1)"
   ::= {er1646v2EthPortSwFBwEntry 4132765696}

er1646v2EthPortSwFBwActViolActEthCos2 OBJECT-TYPE
   SYNTAX      INTEGER
               {
               unchanged (256)
               }
   MAX-ACCESS  read-write
   STATUS      current
   DESCRIPTION
      "Path: swPort.editConf.bandwidth.action.violateAction.ethernet.cosDepth2

       Possibilities:
               unchanged   (256)"
   ::= {er1646v2EthPortSwFBwEntry 4131520512}

er1646v2EthPortSwFBwActViolActEthDei2 OBJECT-TYPE
   SYNTAX      INTEGER
               {
               unchanged (255),
               clear (0),
               set (1)
               }
   MAX-ACCESS  read-write
   STATUS      current
   DESCRIPTION
      "Path: swPort.editConf.bandwidth.action.violateAction.ethernet.deiDepth2

       Possibilities:
               unchanged   (255)
               clear   (0)
               set   (1)"
   ::= {er1646v2EthPortSwFBwEntry 4132831232}

er1646v2EthPortSwFBwActViolActEthCos3 OBJECT-TYPE
   SYNTAX      INTEGER
               {
               unchanged (256)
               }
   MAX-ACCESS  read-write
   STATUS      current
   DESCRIPTION
      "Path: swPort.editConf.bandwidth.action.violateAction.ethernet.cosDepth3

       Possibilities:
               unchanged   (256)"
   ::= {er1646v2EthPortSwFBwEntry 4131586048}

er1646v2EthPortSwFBwActViolActEthDei3 OBJECT-TYPE
   SYNTAX      INTEGER
               {
               unchanged (255),
               clear (0),
               set (1)
               }
   MAX-ACCESS  read-write
   STATUS      current
   DESCRIPTION
      "Path: swPort.editConf.bandwidth.action.violateAction.ethernet.deiDepth3

       Possibilities:
               unchanged   (255)
               clear   (0)
               set   (1)"
   ::= {er1646v2EthPortSwFBwEntry 4132896768}

er1646v2EthPortSwFBwActViolActEthCos4 OBJECT-TYPE
   SYNTAX      INTEGER
               {
               unchanged (256)
               }
   MAX-ACCESS  read-write
   STATUS      current
   DESCRIPTION
      "Path: swPort.editConf.bandwidth.action.violateAction.ethernet.cosDepth4

       Possibilities:
               unchanged   (256)"
   ::= {er1646v2EthPortSwFBwEntry 4131651584}

er1646v2EthPortSwFBwActViolActEthDei4 OBJECT-TYPE
   SYNTAX      INTEGER
               {
               unchanged (255),
               clear (0),
               set (1)
               }
   MAX-ACCESS  read-write
   STATUS      current
   DESCRIPTION
      "Path: swPort.editConf.bandwidth.action.violateAction.ethernet.deiDepth4

       Possibilities:
               unchanged   (255)
               clear   (0)
               set   (1)"
   ::= {er1646v2EthPortSwFBwEntry 4132962304}

er1646v2EthPortSwFBwActViolActEthCos5 OBJECT-TYPE
   SYNTAX      INTEGER
               {
               unchanged (256)
               }
   MAX-ACCESS  read-write
   STATUS      current
   DESCRIPTION
      "Path: swPort.editConf.bandwidth.action.violateAction.ethernet.cosDepth5

       Possibilities:
               unchanged   (256)"
   ::= {er1646v2EthPortSwFBwEntry 4131717120}

er1646v2EthPortSwFBwActViolActEthDei5 OBJECT-TYPE
   SYNTAX      INTEGER
               {
               unchanged (255),
               clear (0),
               set (1)
               }
   MAX-ACCESS  read-write
   STATUS      current
   DESCRIPTION
      "Path: swPort.editConf.bandwidth.action.violateAction.ethernet.deiDepth5

       Possibilities:
               unchanged   (255)
               clear   (0)
               set   (1)"
   ::= {er1646v2EthPortSwFBwEntry 4133027840}

er1646v2EthPortSwFBwActViolActEthCos6 OBJECT-TYPE
   SYNTAX      INTEGER
               {
               unchanged (256)
               }
   MAX-ACCESS  read-write
   STATUS      current
   DESCRIPTION
      "Path: swPort.editConf.bandwidth.action.violateAction.ethernet.cosDepth6

       Possibilities:
               unchanged   (256)"
   ::= {er1646v2EthPortSwFBwEntry 4131782656}

er1646v2EthPortSwFBwActViolActEthDei6 OBJECT-TYPE
   SYNTAX      INTEGER
               {
               unchanged (255),
               clear (0),
               set (1)
               }
   MAX-ACCESS  read-write
   STATUS      current
   DESCRIPTION
      "Path: swPort.editConf.bandwidth.action.violateAction.ethernet.deiDepth6

       Possibilities:
               unchanged   (255)
               clear   (0)
               set   (1)"
   ::= {er1646v2EthPortSwFBwEntry 4133093376}

er1646v2EthPortSwFBwActViolActEthCos7 OBJECT-TYPE
   SYNTAX      INTEGER
               {
               unchanged (256)
               }
   MAX-ACCESS  read-write
   STATUS      current
   DESCRIPTION
      "Path: swPort.editConf.bandwidth.action.violateAction.ethernet.cosDepth7

       Possibilities:
               unchanged   (256)"
   ::= {er1646v2EthPortSwFBwEntry 4131848192}

er1646v2EthPortSwFBwActViolActEthDei7 OBJECT-TYPE
   SYNTAX      INTEGER
               {
               unchanged (255),
               clear (0),
               set (1)
               }
   MAX-ACCESS  read-write
   STATUS      current
   DESCRIPTION
      "Path: swPort.editConf.bandwidth.action.violateAction.ethernet.deiDepth7

       Possibilities:
               unchanged   (255)
               clear   (0)
               set   (1)"
   ::= {er1646v2EthPortSwFBwEntry 4133158912}

er1646v2EthPortSwFBwActViolActEthCos8 OBJECT-TYPE
   SYNTAX      INTEGER
               {
               unchanged (256)
               }
   MAX-ACCESS  read-write
   STATUS      current
   DESCRIPTION
      "Path: swPort.editConf.bandwidth.action.violateAction.ethernet.cosDepth8

       Possibilities:
               unchanged   (256)"
   ::= {er1646v2EthPortSwFBwEntry 4131913728}

er1646v2EthPortSwFBwActViolActEthDei8 OBJECT-TYPE
   SYNTAX      INTEGER
               {
               unchanged (255),
               clear (0),
               set (1)
               }
   MAX-ACCESS  read-write
   STATUS      current
   DESCRIPTION
      "Path: swPort.editConf.bandwidth.action.violateAction.ethernet.deiDepth8

       Possibilities:
               unchanged   (255)
               clear   (0)
               set   (1)"
   ::= {er1646v2EthPortSwFBwEntry 4133224448}

er1646v2EthPortSwFBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4131979264}

er1646v2EthPortSwFBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4132044800}

er1646v2EthPortSwFBwActViolActEthDrpLev OBJECT-TYPE
   SYNTAX      INTEGER
               {
               unchanged (0)
               }
   MAX-ACCESS  read-write
   STATUS      current
   DESCRIPTION
      "Path: swPort.editConf.bandwidth.action.violateAction.ethernet.dropLevel

       Possibilities:
               unchanged   (0)"
   ::= {er1646v2EthPortSwFBwEntry 4132110336}

er1646v2EthPortSwFBwActViolActEthDeFlag OBJECT-TYPE
   SYNTAX      INTEGER
               {
               unchanged (255),
               clear (0),
               set (1)
               }
   MAX-ACCESS  read-write
   STATUS      current
   DESCRIPTION
      "Path: swPort.editConf.bandwidth.action.violateAction.ethernet.deFlag

       Possibilities:
               unchanged   (255)
               clear   (0)
               set   (1)"
   ::= {er1646v2EthPortSwFBwEntry 4132306944}

er1646v2EthPortSwFBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFBwEntry 4138270720}

er1646v2EthPortSwFBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFBwEntry 4138336256}

er1646v2EthPortSwFBwActViolActIpDrpLev OBJECT-TYPE
   SYNTAX      INTEGER
               {
               unchanged (0)
               }
   MAX-ACCESS  read-write
   STATUS      current
   DESCRIPTION
      "Path: swPort.editConf.bandwidth.action.violateAction.ip.dropLevel

       Possibilities:
               unchanged   (0)"
   ::= {er1646v2EthPortSwFBwEntry 4138401792}

er1646v2EthPortSwFBwActViolActIpDeFlag OBJECT-TYPE
   SYNTAX      INTEGER
               {
               unchanged (255),
               clear (0),
               set (1)
               }
   MAX-ACCESS  read-write
   STATUS      current
   DESCRIPTION
      "Path: swPort.editConf.bandwidth.action.violateAction.ip.deFlag

       Possibilities:
               unchanged   (255)
               clear   (0)
               set   (1)"
   ::= {er1646v2EthPortSwFBwEntry 4138598400}


er1646v2EthPortSwFIbw OBJECT IDENTIFIER ::= {er1646v2EthPortSwF 13}

er1646v2EthPortSwFIbwSSCTable OBJECT-TYPE
   SYNTAX      SEQUENCE OF Er1646v2EthPortSwFIbwEntry
   MAX-ACCESS  not-accessible
   STATUS      current
   DESCRIPTION
      ""
   ::= {er1646v2EthPortSwFIbw 1}

er1646v2EthPortSwFIbwEntry OBJECT-TYPE
   SYNTAX      Er1646v2EthPortSwFIbwEntry
   MAX-ACCESS  not-accessible
   STATUS      current
   DESCRIPTION
      ""
   INDEX      { er1646v2EthPortSwFIbwGlobalIx }
   ::= {er1646v2EthPortSwFIbwSSCTable 1}

Er1646v2EthPortSwFIbwEntry ::=
   SEQUENCE
      {
      er1646v2EthPortSwFIbwGlobalIx
         GlobalIndex,
      er1646v2EthPortSwFIbwMode
         INTEGER,
      er1646v2EthPortSwFIbwCir
         Integer32,
      er1646v2EthPortSwFIbwEir
         Integer32,
      er1646v2EthPortSwFIbwUnit
         INTEGER,
      er1646v2EthPortSwFIbwTc
         INTEGER,
      er1646v2EthPortSwFIbwTcFactor
         INTEGER,
      er1646v2EthPortSwFIbwCorrType
         INTEGER,
      er1646v2EthPortSwFIbwCorrPredefEncapsFrameRelay
         DisplayString,
      er1646v2EthPortSwFIbwCorrPredefEncapsPpp
         DisplayString,
      er1646v2EthPortSwFIbwCorrPredefEncapsAtmHl
         INTEGER,
      er1646v2EthPortSwFIbwCorrPredefEncapsAtmMp
         INTEGER,
      er1646v2EthPortSwFIbwCorrPredefEncapsHdlc
         DisplayString,
      er1646v2EthPortSwFIbwCorrPredefEncapsEfmFs
         Integer32,
      er1646v2EthPortSwFIbwCorrPredefEncapsEfmIb
         Integer32,
      er1646v2EthPortSwFIbwCorrPredefMode
         INTEGER,
      er1646v2EthPortSwFIbwCorrManualOverhead
         Integer32,
      er1646v2EthPortSwFIbwCorrManualFrameData
         Counter32,
      er1646v2EthPortSwFIbwCorrManualFrameHeader
         Counter32,
      er1646v2EthPortSwFIbwMaxFifoQLen
         Integer32,
      er1646v2EthPortSwFIbwPriorityPolicy
         DisplayString,
      er1646v2EthPortSwFIbwDeFlagCir
         INTEGER,
      er1646v2EthPortSwFIbwDeFlagEir
         INTEGER,
      er1646v2EthPortSwFIbwDeFlagViolate
         INTEGER,
      er1646v2EthPortSwFIbwActCirActNone
         OCTET STRING,
      er1646v2EthPortSwFIbwActCirActEthCos1
         INTEGER,
      er1646v2EthPortSwFIbwActCirActEthDei1
         INTEGER,
      er1646v2EthPortSwFIbwActCirActEthCos2
         INTEGER,
      er1646v2EthPortSwFIbwActCirActEthDei2
         INTEGER,
      er1646v2EthPortSwFIbwActCirActEthCos3
         INTEGER,
      er1646v2EthPortSwFIbwActCirActEthDei3
         INTEGER,
      er1646v2EthPortSwFIbwActCirActEthCos4
         INTEGER,
      er1646v2EthPortSwFIbwActCirActEthDei4
         INTEGER,
      er1646v2EthPortSwFIbwActCirActEthCos5
         INTEGER,
      er1646v2EthPortSwFIbwActCirActEthDei5
         INTEGER,
      er1646v2EthPortSwFIbwActCirActEthCos6
         INTEGER,
      er1646v2EthPortSwFIbwActCirActEthDei6
         INTEGER,
      er1646v2EthPortSwFIbwActCirActEthCos7
         INTEGER,
      er1646v2EthPortSwFIbwActCirActEthDei7
         INTEGER,
      er1646v2EthPortSwFIbwActCirActEthCos8
         INTEGER,
      er1646v2EthPortSwFIbwActCirActEthDei8
         INTEGER,
      er1646v2EthPortSwFIbwActCirActEthTos
         INTEGER,
      er1646v2EthPortSwFIbwActCirActEthQueue
         INTEGER,
      er1646v2EthPortSwFIbwActCirActEthDrpLev
         INTEGER,
      er1646v2EthPortSwFIbwActCirActEthDeFlag
         INTEGER,
      er1646v2EthPortSwFIbwActCirActIpTos
         INTEGER,
      er1646v2EthPortSwFIbwActCirActIpQueue
         INTEGER,
      er1646v2EthPortSwFIbwActCirActIpDrpLev
         INTEGER,
      er1646v2EthPortSwFIbwActCirActIpDeFlag
         INTEGER,
      er1646v2EthPortSwFIbwActEirActNone
         OCTET STRING,
      er1646v2EthPortSwFIbwActEirActEthCos1
         INTEGER,
      er1646v2EthPortSwFIbwActEirActEthDei1
         INTEGER,
      er1646v2EthPortSwFIbwActEirActEthCos2
         INTEGER,
      er1646v2EthPortSwFIbwActEirActEthDei2
         INTEGER,
      er1646v2EthPortSwFIbwActEirActEthCos3
         INTEGER,
      er1646v2EthPortSwFIbwActEirActEthDei3
         INTEGER,
      er1646v2EthPortSwFIbwActEirActEthCos4
         INTEGER,
      er1646v2EthPortSwFIbwActEirActEthDei4
         INTEGER,
      er1646v2EthPortSwFIbwActEirActEthCos5
         INTEGER,
      er1646v2EthPortSwFIbwActEirActEthDei5
         INTEGER,
      er1646v2EthPortSwFIbwActEirActEthCos6
         INTEGER,
      er1646v2EthPortSwFIbwActEirActEthDei6
         INTEGER,
      er1646v2EthPortSwFIbwActEirActEthCos7
         INTEGER,
      er1646v2EthPortSwFIbwActEirActEthDei7
         INTEGER,
      er1646v2EthPortSwFIbwActEirActEthCos8
         INTEGER,
      er1646v2EthPortSwFIbwActEirActEthDei8
         INTEGER,
      er1646v2EthPortSwFIbwActEirActEthTos
         INTEGER,
      er1646v2EthPortSwFIbwActEirActEthQueue
         INTEGER,
      er1646v2EthPortSwFIbwActEirActEthDrpLev
         INTEGER,
      er1646v2EthPortSwFIbwActEirActEthDeFlag
         INTEGER,
      er1646v2EthPortSwFIbwActEirActIpTos
         INTEGER,
      er1646v2EthPortSwFIbwActEirActIpQueue
         INTEGER,
      er1646v2EthPortSwFIbwActEirActIpDrpLev
         INTEGER,
      er1646v2EthPortSwFIbwActEirActIpDeFlag
         INTEGER,
      er1646v2EthPortSwFIbwActViolActNone
         OCTET STRING,
      er1646v2EthPortSwFIbwActViolActDrop
         OCTET STRING,
      er1646v2EthPortSwFIbwActViolActEthCos1
         INTEGER,
      er1646v2EthPortSwFIbwActViolActEthDei1
         INTEGER,
      er1646v2EthPortSwFIbwActViolActEthCos2
         INTEGER,
      er1646v2EthPortSwFIbwActViolActEthDei2
         INTEGER,
      er1646v2EthPortSwFIbwActViolActEthCos3
         INTEGER,
      er1646v2EthPortSwFIbwActViolActEthDei3
         INTEGER,
      er1646v2EthPortSwFIbwActViolActEthCos4
         INTEGER,
      er1646v2EthPortSwFIbwActViolActEthDei4
         INTEGER,
      er1646v2EthPortSwFIbwActViolActEthCos5
         INTEGER,
      er1646v2EthPortSwFIbwActViolActEthDei5
         INTEGER,
      er1646v2EthPortSwFIbwActViolActEthCos6
         INTEGER,
      er1646v2EthPortSwFIbwActViolActEthDei6
         INTEGER,
      er1646v2EthPortSwFIbwActViolActEthCos7
         INTEGER,
      er1646v2EthPortSwFIbwActViolActEthDei7
         INTEGER,
      er1646v2EthPortSwFIbwActViolActEthCos8
         INTEGER,
      er1646v2EthPortSwFIbwActViolActEthDei8
         INTEGER,
      er1646v2EthPortSwFIbwActViolActEthTos
         INTEGER,
      er1646v2EthPortSwFIbwActViolActEthQueue
         INTEGER,
      er1646v2EthPortSwFIbwActViolActEthDrpLev
         INTEGER,
      er1646v2EthPortSwFIbwActViolActEthDeFlag
         INTEGER,
      er1646v2EthPortSwFIbwActViolActIpTos
         INTEGER,
      er1646v2EthPortSwFIbwActViolActIpQueue
         INTEGER,
      er1646v2EthPortSwFIbwActViolActIpDrpLev
         INTEGER,
      er1646v2EthPortSwFIbwActViolActIpDeFlag
         INTEGER,
      er1646v2EthPortSwFIbwSubInterfacesExcluded
         INTEGER,
      er1646v2EthPortSwFIbwSubInterfacesIncludedInAccessList
         DisplayString
      }

er1646v2EthPortSwFIbwGlobalIx OBJECT-TYPE
   SYNTAX      GlobalIndex
   MAX-ACCESS  not-accessible
   STATUS      current
   DESCRIPTION
      "The value of the tlsCntTreeGlobalIndex of the MANAGED OBJECT."
   ::= {er1646v2EthPortSwFIbwEntry 10}

er1646v2EthPortSwFIbwMode OBJECT-TYPE
   SYNTAX      INTEGER
               {
               reshaping (1),
               policing (2)
               }
   MAX-ACCESS  read-write
   STATUS      current
   DESCRIPTION
      "Path: swPort.editConf.inboundBandwidth.mode

       Possibilities:
               reshaping   (1)
               policing   (2)"
   ::= {er1646v2EthPortSwFIbwEntry 3758096384}

er1646v2EthPortSwFIbwCir OBJECT-TYPE
   SYNTAX      Integer32
   MAX-ACCESS  read-write
   STATUS      current
   DESCRIPTION
      "Path: swPort.editConf.inboundBandwidth.cir"
   ::= {er1646v2EthPortSwFIbwEntry 268435456}

er1646v2EthPortSwFIbwEir OBJECT-TYPE
   SYNTAX      Integer32
   MAX-ACCESS  read-write
   STATUS      current
   DESCRIPTION
      "Path: swPort.editConf.inboundBandwidth.eir"
   ::= {er1646v2EthPortSwFIbwEntry 1879048192}

er1646v2EthPortSwFIbwUnit OBJECT-TYPE
   SYNTAX      INTEGER
               {
               bitssec (1),
               percent (2)
               }
   MAX-ACCESS  read-write
   STATUS      current
   DESCRIPTION
      "Path: swPort.editConf.inboundBandwidth.unit

       Possibilities:
               bits/sec   (1)
               percent   (2)"
   ::= {er1646v2EthPortSwFIbwEntry 1342177280}

er1646v2EthPortSwFIbwTc OBJECT-TYPE
   SYNTAX      INTEGER
               {
               auto (0)
               }
   MAX-ACCESS  read-write
   STATUS      current
   DESCRIPTION
      "Path: swPort.editConf.inboundBandwidth.tc

       Possibilities:
               auto   (0)"
   ::= {er1646v2EthPortSwFIbwEntry 1610612736}

er1646v2EthPortSwFIbwTcFactor OBJECT-TYPE
   SYNTAX      INTEGER
               {
               ms (10),
               s100us (1)
               }
   MAX-ACCESS  read-write
   STATUS      current
   DESCRIPTION
      "Path: swPort.editConf.inboundBandwidth.tcFactor

       Possibilities:
               ms   (10)
               *100us   (1)"
   ::= {er1646v2EthPortSwFIbwEntry 2147483648}

er1646v2EthPortSwFIbwCorrType OBJECT-TYPE
   SYNTAX      INTEGER
               {
               noCorrection (0),
               predefined (1),
               manual (2)
               }
   MAX-ACCESS  read-write
   STATUS      current
   DESCRIPTION
      "Path: swPort.editConf.inboundBandwidth.correction.type

       Possibilities:
               noCorrection   (0)
               predefined   (1)
               manual   (2)"
   ::= {er1646v2EthPortSwFIbwEntry 570425344}

er1646v2EthPortSwFIbwCorrPredefEncapsFrameRelay OBJECT-TYPE
   SYNTAX      DisplayString
   MAX-ACCESS  read-write
   STATUS      current
   DESCRIPTION
      "Path: swPort.editConf.inboundBandwidth.correction.predefined.encapsulation.frameRelay"
   ::= {er1646v2EthPortSwFIbwEntry 608436224}

er1646v2EthPortSwFIbwCorrPredefEncapsPpp OBJECT-TYPE
   SYNTAX      DisplayString
   MAX-ACCESS  read-write
   STATUS      current
   DESCRIPTION
      "Path: swPort.editConf.inboundBandwidth.correction.predefined.encapsulation.ppp"
   ::= {er1646v2EthPortSwFIbwEntry 608698368}

er1646v2EthPortSwFIbwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.inboundBandwidth.correction.predefined.encapsulation.atm.higherLayer

       Possibilities:
               rfc2684   (0)
               ppp   (1)
               pppOverEthernet   (2)"
   ::= {er1646v2EthPortSwFIbwEntry 608993280}

er1646v2EthPortSwFIbwCorrPredefEncapsAtmMp OBJECT-TYPE
   SYNTAX      INTEGER
               {
               llcEncapsulation (0),
               vcMultiplexing (1)
               }
   MAX-ACCESS  read-write
   STATUS      current
   DESCRIPTION
      "Path: swPort.editConf.inboundBandwidth.correction.predefined.encapsulation.atm.multiProtocol

       Possibilities:
               llcEncapsulation   (0)
               vcMultiplexing   (1)"
   ::= {er1646v2EthPortSwFIbwEntry 609026048}

er1646v2EthPortSwFIbwCorrPredefEncapsHdlc OBJECT-TYPE
   SYNTAX      DisplayString
   MAX-ACCESS  read-write
   STATUS      current
   DESCRIPTION
      "Path: swPort.editConf.inboundBandwidth.correction.predefined.encapsulation.hdlc"
   ::= {er1646v2EthPortSwFIbwEntry 609222656}

er1646v2EthPortSwFIbwCorrPredefEncapsEfmFs OBJECT-TYPE
   SYNTAX      Integer32
   MAX-ACCESS  read-write
   STATUS      current
   DESCRIPTION
      "Path: swPort.editConf.inboundBandwidth.correction.predefined.encapsulation.efm.fragmentSize"
   ::= {er1646v2EthPortSwFIbwEntry 609517568}

er1646v2EthPortSwFIbwCorrPredefEncapsEfmIb OBJECT-TYPE
   SYNTAX      Integer32
   MAX-ACCESS  read-write
   STATUS      current
   DESCRIPTION
      "Path: swPort.editConf.inboundBandwidth.correction.predefined.encapsulation.efm.idleBytes"
   ::= {er1646v2EthPortSwFIbwEntry 609550336}

er1646v2EthPortSwFIbwCorrPredefMode OBJECT-TYPE
   SYNTAX      INTEGER
               {
               routing (0),
               bridging (1)
               }
   MAX-ACCESS  read-write
   STATUS      current
   DESCRIPTION
      "Path: swPort.editConf.inboundBandwidth.correction.predefined.mode

       Possibilities:
               routing   (0)
               bridging   (1)"
   ::= {er1646v2EthPortSwFIbwEntry 612368384}

er1646v2EthPortSwFIbwCorrManualOverhead OBJECT-TYPE
   SYNTAX      Integer32
   MAX-ACCESS  read-write
   STATUS      current
   DESCRIPTION
      "Path: swPort.editConf.inboundBandwidth.correction.manual.overhead"
   ::= {er1646v2EthPortSwFIbwEntry 637665280}

er1646v2EthPortSwFIbwCorrManualFrameData OBJECT-TYPE
   SYNTAX      Counter32
   MAX-ACCESS  read-write
   STATUS      current
   DESCRIPTION
      "Path: swPort.editConf.inboundBandwidth.correction.manual.frameData

       32 bit unsigned wrappable counter."
   ::= {er1646v2EthPortSwFIbwEntry 637796352}

er1646v2EthPortSwFIbwCorrManualFrameHeader OBJECT-TYPE
   SYNTAX      Counter32
   MAX-ACCESS  read-write
   STATUS      current
   DESCRIPTION
      "Path: swPort.editConf.inboundBandwidth.correction.manual.frameHeader

       32 bit unsigned wrappable counter."
   ::= {er1646v2EthPortSwFIbwEntry 637927424}

er1646v2EthPortSwFIbwMaxFifoQLen OBJECT-TYPE
   SYNTAX      Integer32
   MAX-ACCESS  read-write
   STATUS      current
   DESCRIPTION
      "Path: swPort.editConf.inboundBandwidth.maxFifoQLen"
   ::= {er1646v2EthPortSwFIbwEntry 805306368}

er1646v2EthPortSwFIbwPriorityPolicy OBJECT-TYPE
   SYNTAX      DisplayString
   MAX-ACCESS  read-write
   STATUS      current
   DESCRIPTION
      "Path: swPort.editConf.inboundBandwidth.priorityPolicy"
   ::= {er1646v2EthPortSwFIbwEntry 1073741824}

er1646v2EthPortSwFIbwDeFlagCir OBJECT-TYPE
   SYNTAX      INTEGER
               {
               allowed (1),
               notAllowed (2)
               }
   MAX-ACCESS  read-write
   STATUS      current
   DESCRIPTION
      "Path: swPort.editConf.inboundBandwidth.deFlag.cir

       Possibilities:
               allowed   (1)
               notAllowed   (2)"
   ::= {er1646v2EthPortSwFIbwEntry 3490709504}

er1646v2EthPortSwFIbwDeFlagEir OBJECT-TYPE
   SYNTAX      INTEGER
               {
               allowed (1),
               notAllowed (2)
               }
   MAX-ACCESS  read-write
   STATUS      current
   DESCRIPTION
      "Path: swPort.editConf.inboundBandwidth.deFlag.eir

       Possibilities:
               allowed   (1)
               notAllowed   (2)"
   ::= {er1646v2EthPortSwFIbwEntry 3491758080}

er1646v2EthPortSwFIbwDeFlagViolate OBJECT-TYPE
   SYNTAX      INTEGER
               {
               allowed (1),
               notAllowed (2)
               }
   MAX-ACCESS  read-write
   STATUS      current
   DESCRIPTION
      "Path: swPort.editConf.inboundBandwidth.deFlag.violate

       Possibilities:
               allowed   (1)
               notAllowed   (2)"
   ::= {er1646v2EthPortSwFIbwEntry 3492806656}

er1646v2EthPortSwFIbwActCirActNone OBJECT-TYPE
   SYNTAX      OCTET STRING
   MAX-ACCESS  read-write
   STATUS      current
   DESCRIPTION
      "Path: swPort.editConf.inboundBandwidth.action.cirAction.none"
   ::= {er1646v2EthPortSwFIbwEntry 4062183424}

er1646v2EthPortSwFIbwActCirActEthCos1 OBJECT-TYPE
   SYNTAX      INTEGER
               {
               unchanged (256)
               }
   MAX-ACCESS  read-write
   STATUS      current
   DESCRIPTION
      "Path: swPort.editConf.inboundBandwidth.action.cirAction.ethernet.cosDepth1

       Possibilities:
               unchanged   (256)"
   ::= {er1646v2EthPortSwFIbwEntry 4064346112}

er1646v2EthPortSwFIbwActCirActEthDei1 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth1

       Possibilities:
               unchanged   (255)
               clear   (0)
               set   (1)"
   ::= {er1646v2EthPortSwFIbwEntry 4065656832}

er1646v2EthPortSwFIbwActCirActEthCos2 OBJECT-TYPE
   SYNTAX      INTEGER
               {
               unchanged (256)
               }
   MAX-ACCESS  read-write
   STATUS      current
   DESCRIPTION
      "Path: swPort.editConf.inboundBandwidth.action.cirAction.ethernet.cosDepth2

       Possibilities:
               unchanged   (256)"
   ::= {er1646v2EthPortSwFIbwEntry 4064411648}

er1646v2EthPortSwFIbwActCirActEthDei2 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth2

       Possibilities:
               unchanged   (255)
               clear   (0)
               set   (1)"
   ::= {er1646v2EthPortSwFIbwEntry 4065722368}

er1646v2EthPortSwFIbwActCirActEthCos3 OBJECT-TYPE
   SYNTAX      INTEGER
               {
               unchanged (256)
               }
   MAX-ACCESS  read-write
   STATUS      current
   DESCRIPTION
      "Path: swPort.editConf.inboundBandwidth.action.cirAction.ethernet.cosDepth3

       Possibilities:
               unchanged   (256)"
   ::= {er1646v2EthPortSwFIbwEntry 4064477184}

er1646v2EthPortSwFIbwActCirActEthDei3 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth3

       Possibilities:
               unchanged   (255)
               clear   (0)
               set   (1)"
   ::= {er1646v2EthPortSwFIbwEntry 4065787904}

er1646v2EthPortSwFIbwActCirActEthCos4 OBJECT-TYPE
   SYNTAX      INTEGER
               {
               unchanged (256)
               }
   MAX-ACCESS  read-write
   STATUS      current
   DESCRIPTION
      "Path: swPort.editConf.inboundBandwidth.action.cirAction.ethernet.cosDepth4

       Possibilities:
               unchanged   (256)"
   ::= {er1646v2EthPortSwFIbwEntry 4064542720}

er1646v2EthPortSwFIbwActCirActEthDei4 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth4

       Possibilities:
               unchanged   (255)
               clear   (0)
               set   (1)"
   ::= {er1646v2EthPortSwFIbwEntry 4065853440}

er1646v2EthPortSwFIbwActCirActEthCos5 OBJECT-TYPE
   SYNTAX      INTEGER
               {
               unchanged (256)
               }
   MAX-ACCESS  read-write
   STATUS      current
   DESCRIPTION
      "Path: swPort.editConf.inboundBandwidth.action.cirAction.ethernet.cosDepth5

       Possibilities:
               unchanged   (256)"
   ::= {er1646v2EthPortSwFIbwEntry 4064608256}

er1646v2EthPortSwFIbwActCirActEthDei5 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth5

       Possibilities:
               unchanged   (255)
               clear   (0)
               set   (1)"
   ::= {er1646v2EthPortSwFIbwEntry 4065918976}

er1646v2EthPortSwFIbwActCirActEthCos6 OBJECT-TYPE
   SYNTAX      INTEGER
               {
               unchanged (256)
               }
   MAX-ACCESS  read-write
   STATUS      current
   DESCRIPTION
      "Path: swPort.editConf.inboundBandwidth.action.cirAction.ethernet.cosDepth6

       Possibilities:
               unchanged   (256)"
   ::= {er1646v2EthPortSwFIbwEntry 4064673792}

er1646v2EthPortSwFIbwActCirActEthDei6 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth6

       Possibilities:
               unchanged   (255)
               clear   (0)
               set   (1)"
   ::= {er1646v2EthPortSwFIbwEntry 4065984512}

er1646v2EthPortSwFIbwActCirActEthCos7 OBJECT-TYPE
   SYNTAX      INTEGER
               {
               unchanged (256)
               }
   MAX-ACCESS  read-write
   STATUS      current
   DESCRIPTION
      "Path: swPort.editConf.inboundBandwidth.action.cirAction.ethernet.cosDepth7

       Possibilities:
               unchanged   (256)"
   ::= {er1646v2EthPortSwFIbwEntry 4064739328}

er1646v2EthPortSwFIbwActCirActEthDei7 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth7

       Possibilities:
               unchanged   (255)
               clear   (0)
               set   (1)"
   ::= {er1646v2EthPortSwFIbwEntry 4066050048}

er1646v2EthPortSwFIbwActCirActEthCos8 OBJECT-TYPE
   SYNTAX      INTEGER
               {
               unchanged (256)
               }
   MAX-ACCESS  read-write
   STATUS      current
   DESCRIPTION
      "Path: swPort.editConf.inboundBandwidth.action.cirAction.ethernet.cosDepth8

       Possibilities:
               unchanged   (256)"
   ::= {er1646v2EthPortSwFIbwEntry 4064804864}

er1646v2EthPortSwFIbwActCirActEthDei8 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth8

       Possibilities:
               unchanged   (255)
               clear   (0)
               set   (1)"
   ::= {er1646v2EthPortSwFIbwEntry 4066115584}

er1646v2EthPortSwFIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4064870400}

er1646v2EthPortSwFIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4064935936}

er1646v2EthPortSwFIbwActCirActEthDrpLev OBJECT-TYPE
   SYNTAX      INTEGER
               {
               unchanged (0)
               }
   MAX-ACCESS  read-write
   STATUS      current
   DESCRIPTION
      "Path: swPort.editConf.inboundBandwidth.action.cirAction.ethernet.dropLevel

       Possibilities:
               unchanged   (0)"
   ::= {er1646v2EthPortSwFIbwEntry 4065001472}

er1646v2EthPortSwFIbwActCirActEthDeFlag OBJECT-TYPE
   SYNTAX      INTEGER
               {
               unchanged (255),
               clear (0),
               set (1)
               }
   MAX-ACCESS  read-write
   STATUS      current
   DESCRIPTION
      "Path: swPort.editConf.inboundBandwidth.action.cirAction.ethernet.deFlag

       Possibilities:
               unchanged   (255)
               clear   (0)
               set   (1)"
   ::= {er1646v2EthPortSwFIbwEntry 4065198080}

er1646v2EthPortSwFIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4071161856}

er1646v2EthPortSwFIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4071227392}

er1646v2EthPortSwFIbwActCirActIpDrpLev OBJECT-TYPE
   SYNTAX      INTEGER
               {
               unchanged (0)
               }
   MAX-ACCESS  read-write
   STATUS      current
   DESCRIPTION
      "Path: swPort.editConf.inboundBandwidth.action.cirAction.ip.dropLevel

       Possibilities:
               unchanged   (0)"
   ::= {er1646v2EthPortSwFIbwEntry 4071292928}

er1646v2EthPortSwFIbwActCirActIpDeFlag OBJECT-TYPE
   SYNTAX      INTEGER
               {
               unchanged (255),
               clear (0),
               set (1)
               }
   MAX-ACCESS  read-write
   STATUS      current
   DESCRIPTION
      "Path: swPort.editConf.inboundBandwidth.action.cirAction.ip.deFlag

       Possibilities:
               unchanged   (255)
               clear   (0)
               set   (1)"
   ::= {er1646v2EthPortSwFIbwEntry 4071489536}

er1646v2EthPortSwFIbwActEirActNone OBJECT-TYPE
   SYNTAX      OCTET STRING
   MAX-ACCESS  read-write
   STATUS      current
   DESCRIPTION
      "Path: swPort.editConf.inboundBandwidth.action.eirAction.none"
   ::= {er1646v2EthPortSwFIbwEntry 4095737856}

er1646v2EthPortSwFIbwActEirActEthCos1 OBJECT-TYPE
   SYNTAX      INTEGER
               {
               unchanged (256)
               }
   MAX-ACCESS  read-write
   STATUS      current
   DESCRIPTION
      "Path: swPort.editConf.inboundBandwidth.action.eirAction.ethernet.cosDepth1

       Possibilities:
               unchanged   (256)"
   ::= {er1646v2EthPortSwFIbwEntry 4097900544}

er1646v2EthPortSwFIbwActEirActEthDei1 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth1

       Possibilities:
               unchanged   (255)
               clear   (0)
               set   (1)"
   ::= {er1646v2EthPortSwFIbwEntry 4099211264}

er1646v2EthPortSwFIbwActEirActEthCos2 OBJECT-TYPE
   SYNTAX      INTEGER
               {
               unchanged (256)
               }
   MAX-ACCESS  read-write
   STATUS      current
   DESCRIPTION
      "Path: swPort.editConf.inboundBandwidth.action.eirAction.ethernet.cosDepth2

       Possibilities:
               unchanged   (256)"
   ::= {er1646v2EthPortSwFIbwEntry 4097966080}

er1646v2EthPortSwFIbwActEirActEthDei2 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth2

       Possibilities:
               unchanged   (255)
               clear   (0)
               set   (1)"
   ::= {er1646v2EthPortSwFIbwEntry 4099276800}

er1646v2EthPortSwFIbwActEirActEthCos3 OBJECT-TYPE
   SYNTAX      INTEGER
               {
               unchanged (256)
               }
   MAX-ACCESS  read-write
   STATUS      current
   DESCRIPTION
      "Path: swPort.editConf.inboundBandwidth.action.eirAction.ethernet.cosDepth3

       Possibilities:
               unchanged   (256)"
   ::= {er1646v2EthPortSwFIbwEntry 4098031616}

er1646v2EthPortSwFIbwActEirActEthDei3 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth3

       Possibilities:
               unchanged   (255)
               clear   (0)
               set   (1)"
   ::= {er1646v2EthPortSwFIbwEntry 4099342336}

er1646v2EthPortSwFIbwActEirActEthCos4 OBJECT-TYPE
   SYNTAX      INTEGER
               {
               unchanged (256)
               }
   MAX-ACCESS  read-write
   STATUS      current
   DESCRIPTION
      "Path: swPort.editConf.inboundBandwidth.action.eirAction.ethernet.cosDepth4

       Possibilities:
               unchanged   (256)"
   ::= {er1646v2EthPortSwFIbwEntry 4098097152}

er1646v2EthPortSwFIbwActEirActEthDei4 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth4

       Possibilities:
               unchanged   (255)
               clear   (0)
               set   (1)"
   ::= {er1646v2EthPortSwFIbwEntry 4099407872}

er1646v2EthPortSwFIbwActEirActEthCos5 OBJECT-TYPE
   SYNTAX      INTEGER
               {
               unchanged (256)
               }
   MAX-ACCESS  read-write
   STATUS      current
   DESCRIPTION
      "Path: swPort.editConf.inboundBandwidth.action.eirAction.ethernet.cosDepth5

       Possibilities:
               unchanged   (256)"
   ::= {er1646v2EthPortSwFIbwEntry 4098162688}

er1646v2EthPortSwFIbwActEirActEthDei5 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth5

       Possibilities:
               unchanged   (255)
               clear   (0)
               set   (1)"
   ::= {er1646v2EthPortSwFIbwEntry 4099473408}

er1646v2EthPortSwFIbwActEirActEthCos6 OBJECT-TYPE
   SYNTAX      INTEGER
               {
               unchanged (256)
               }
   MAX-ACCESS  read-write
   STATUS      current
   DESCRIPTION
      "Path: swPort.editConf.inboundBandwidth.action.eirAction.ethernet.cosDepth6

       Possibilities:
               unchanged   (256)"
   ::= {er1646v2EthPortSwFIbwEntry 4098228224}

er1646v2EthPortSwFIbwActEirActEthDei6 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth6

       Possibilities:
               unchanged   (255)
               clear   (0)
               set   (1)"
   ::= {er1646v2EthPortSwFIbwEntry 4099538944}

er1646v2EthPortSwFIbwActEirActEthCos7 OBJECT-TYPE
   SYNTAX      INTEGER
               {
               unchanged (256)
               }
   MAX-ACCESS  read-write
   STATUS      current
   DESCRIPTION
      "Path: swPort.editConf.inboundBandwidth.action.eirAction.ethernet.cosDepth7

       Possibilities:
               unchanged   (256)"
   ::= {er1646v2EthPortSwFIbwEntry 4098293760}

er1646v2EthPortSwFIbwActEirActEthDei7 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth7

       Possibilities:
               unchanged   (255)
               clear   (0)
               set   (1)"
   ::= {er1646v2EthPortSwFIbwEntry 4099604480}

er1646v2EthPortSwFIbwActEirActEthCos8 OBJECT-TYPE
   SYNTAX      INTEGER
               {
               unchanged (256)
               }
   MAX-ACCESS  read-write
   STATUS      current
   DESCRIPTION
      "Path: swPort.editConf.inboundBandwidth.action.eirAction.ethernet.cosDepth8

       Possibilities:
               unchanged   (256)"
   ::= {er1646v2EthPortSwFIbwEntry 4098359296}

er1646v2EthPortSwFIbwActEirActEthDei8 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth8

       Possibilities:
               unchanged   (255)
               clear   (0)
               set   (1)"
   ::= {er1646v2EthPortSwFIbwEntry 4099670016}

er1646v2EthPortSwFIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4098424832}

er1646v2EthPortSwFIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4098490368}

er1646v2EthPortSwFIbwActEirActEthDrpLev OBJECT-TYPE
   SYNTAX      INTEGER
               {
               unchanged (0)
               }
   MAX-ACCESS  read-write
   STATUS      current
   DESCRIPTION
      "Path: swPort.editConf.inboundBandwidth.action.eirAction.ethernet.dropLevel

       Possibilities:
               unchanged   (0)"
   ::= {er1646v2EthPortSwFIbwEntry 4098555904}

er1646v2EthPortSwFIbwActEirActEthDeFlag OBJECT-TYPE
   SYNTAX      INTEGER
               {
               unchanged (255),
               clear (0),
               set (1)
               }
   MAX-ACCESS  read-write
   STATUS      current
   DESCRIPTION
      "Path: swPort.editConf.inboundBandwidth.action.eirAction.ethernet.deFlag

       Possibilities:
               unchanged   (255)
               clear   (0)
               set   (1)"
   ::= {er1646v2EthPortSwFIbwEntry 4098752512}

er1646v2EthPortSwFIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4104716288}

er1646v2EthPortSwFIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4104781824}

er1646v2EthPortSwFIbwActEirActIpDrpLev OBJECT-TYPE
   SYNTAX      INTEGER
               {
               unchanged (0)
               }
   MAX-ACCESS  read-write
   STATUS      current
   DESCRIPTION
      "Path: swPort.editConf.inboundBandwidth.action.eirAction.ip.dropLevel

       Possibilities:
               unchanged   (0)"
   ::= {er1646v2EthPortSwFIbwEntry 4104847360}

er1646v2EthPortSwFIbwActEirActIpDeFlag OBJECT-TYPE
   SYNTAX      INTEGER
               {
               unchanged (255),
               clear (0),
               set (1)
               }
   MAX-ACCESS  read-write
   STATUS      current
   DESCRIPTION
      "Path: swPort.editConf.inboundBandwidth.action.eirAction.ip.deFlag

       Possibilities:
               unchanged   (255)
               clear   (0)
               set   (1)"
   ::= {er1646v2EthPortSwFIbwEntry 4105043968}

er1646v2EthPortSwFIbwActViolActNone OBJECT-TYPE
   SYNTAX      OCTET STRING
   MAX-ACCESS  read-write
   STATUS      current
   DESCRIPTION
      "Path: swPort.editConf.inboundBandwidth.action.violateAction.none"
   ::= {er1646v2EthPortSwFIbwEntry 4129292288}

er1646v2EthPortSwFIbwActViolActDrop OBJECT-TYPE
   SYNTAX      OCTET STRING
   MAX-ACCESS  read-write
   STATUS      current
   DESCRIPTION
      "Path: swPort.editConf.inboundBandwidth.action.violateAction.drop"
   ::= {er1646v2EthPortSwFIbwEntry 4133486592}

er1646v2EthPortSwFIbwActViolActEthCos1 OBJECT-TYPE
   SYNTAX      INTEGER
               {
               unchanged (256)
               }
   MAX-ACCESS  read-write
   STATUS      current
   DESCRIPTION
      "Path: swPort.editConf.inboundBandwidth.action.violateAction.ethernet.cosDepth1

       Possibilities:
               unchanged   (256)"
   ::= {er1646v2EthPortSwFIbwEntry 4131454976}

er1646v2EthPortSwFIbwActViolActEthDei1 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth1

       Possibilities:
               unchanged   (255)
               clear   (0)
               set   (1)"
   ::= {er1646v2EthPortSwFIbwEntry 4132765696}

er1646v2EthPortSwFIbwActViolActEthCos2 OBJECT-TYPE
   SYNTAX      INTEGER
               {
               unchanged (256)
               }
   MAX-ACCESS  read-write
   STATUS      current
   DESCRIPTION
      "Path: swPort.editConf.inboundBandwidth.action.violateAction.ethernet.cosDepth2

       Possibilities:
               unchanged   (256)"
   ::= {er1646v2EthPortSwFIbwEntry 4131520512}

er1646v2EthPortSwFIbwActViolActEthDei2 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth2

       Possibilities:
               unchanged   (255)
               clear   (0)
               set   (1)"
   ::= {er1646v2EthPortSwFIbwEntry 4132831232}

er1646v2EthPortSwFIbwActViolActEthCos3 OBJECT-TYPE
   SYNTAX      INTEGER
               {
               unchanged (256)
               }
   MAX-ACCESS  read-write
   STATUS      current
   DESCRIPTION
      "Path: swPort.editConf.inboundBandwidth.action.violateAction.ethernet.cosDepth3

       Possibilities:
               unchanged   (256)"
   ::= {er1646v2EthPortSwFIbwEntry 4131586048}

er1646v2EthPortSwFIbwActViolActEthDei3 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth3

       Possibilities:
               unchanged   (255)
               clear   (0)
               set   (1)"
   ::= {er1646v2EthPortSwFIbwEntry 4132896768}

er1646v2EthPortSwFIbwActViolActEthCos4 OBJECT-TYPE
   SYNTAX      INTEGER
               {
               unchanged (256)
               }
   MAX-ACCESS  read-write
   STATUS      current
   DESCRIPTION
      "Path: swPort.editConf.inboundBandwidth.action.violateAction.ethernet.cosDepth4

       Possibilities:
               unchanged   (256)"
   ::= {er1646v2EthPortSwFIbwEntry 4131651584}

er1646v2EthPortSwFIbwActViolActEthDei4 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth4

       Possibilities:
               unchanged   (255)
               clear   (0)
               set   (1)"
   ::= {er1646v2EthPortSwFIbwEntry 4132962304}

er1646v2EthPortSwFIbwActViolActEthCos5 OBJECT-TYPE
   SYNTAX      INTEGER
               {
               unchanged (256)
               }
   MAX-ACCESS  read-write
   STATUS      current
   DESCRIPTION
      "Path: swPort.editConf.inboundBandwidth.action.violateAction.ethernet.cosDepth5

       Possibilities:
               unchanged   (256)"
   ::= {er1646v2EthPortSwFIbwEntry 4131717120}

er1646v2EthPortSwFIbwActViolActEthDei5 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth5

       Possibilities:
               unchanged   (255)
               clear   (0)
               set   (1)"
   ::= {er1646v2EthPortSwFIbwEntry 4133027840}

er1646v2EthPortSwFIbwActViolActEthCos6 OBJECT-TYPE
   SYNTAX      INTEGER
               {
               unchanged (256)
               }
   MAX-ACCESS  read-write
   STATUS      current
   DESCRIPTION
      "Path: swPort.editConf.inboundBandwidth.action.violateAction.ethernet.cosDepth6

       Possibilities:
               unchanged   (256)"
   ::= {er1646v2EthPortSwFIbwEntry 4131782656}

er1646v2EthPortSwFIbwActViolActEthDei6 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth6

       Possibilities:
               unchanged   (255)
               clear   (0)
               set   (1)"
   ::= {er1646v2EthPortSwFIbwEntry 4133093376}

er1646v2EthPortSwFIbwActViolActEthCos7 OBJECT-TYPE
   SYNTAX      INTEGER
               {
               unchanged (256)
               }
   MAX-ACCESS  read-write
   STATUS      current
   DESCRIPTION
      "Path: swPort.editConf.inboundBandwidth.action.violateAction.ethernet.cosDepth7

       Possibilities:
               unchanged   (256)"
   ::= {er1646v2EthPortSwFIbwEntry 4131848192}

er1646v2EthPortSwFIbwActViolActEthDei7 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth7

       Possibilities:
               unchanged   (255)
               clear   (0)
               set   (1)"
   ::= {er1646v2EthPortSwFIbwEntry 4133158912}

er1646v2EthPortSwFIbwActViolActEthCos8 OBJECT-TYPE
   SYNTAX      INTEGER
               {
               unchanged (256)
               }
   MAX-ACCESS  read-write
   STATUS      current
   DESCRIPTION
      "Path: swPort.editConf.inboundBandwidth.action.violateAction.ethernet.cosDepth8

       Possibilities:
               unchanged   (256)"
   ::= {er1646v2EthPortSwFIbwEntry 4131913728}

er1646v2EthPortSwFIbwActViolActEthDei8 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth8

       Possibilities:
               unchanged   (255)
               clear   (0)
               set   (1)"
   ::= {er1646v2EthPortSwFIbwEntry 4133224448}

er1646v2EthPortSwFIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4131979264}

er1646v2EthPortSwFIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4132044800}

er1646v2EthPortSwFIbwActViolActEthDrpLev OBJECT-TYPE
   SYNTAX      INTEGER
               {
               unchanged (0)
               }
   MAX-ACCESS  read-write
   STATUS      current
   DESCRIPTION
      "Path: swPort.editConf.inboundBandwidth.action.violateAction.ethernet.dropLevel

       Possibilities:
               unchanged   (0)"
   ::= {er1646v2EthPortSwFIbwEntry 4132110336}

er1646v2EthPortSwFIbwActViolActEthDeFlag OBJECT-TYPE
   SYNTAX      INTEGER
               {
               unchanged (255),
               clear (0),
               set (1)
               }
   MAX-ACCESS  read-write
   STATUS      current
   DESCRIPTION
      "Path: swPort.editConf.inboundBandwidth.action.violateAction.ethernet.deFlag

       Possibilities:
               unchanged   (255)
               clear   (0)
               set   (1)"
   ::= {er1646v2EthPortSwFIbwEntry 4132306944}

er1646v2EthPortSwFIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFIbwEntry 4138270720}

er1646v2EthPortSwFIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFIbwEntry 4138336256}

er1646v2EthPortSwFIbwActViolActIpDrpLev OBJECT-TYPE
   SYNTAX      INTEGER
               {
               unchanged (0)
               }
   MAX-ACCESS  read-write
   STATUS      current
   DESCRIPTION
      "Path: swPort.editConf.inboundBandwidth.action.violateAction.ip.dropLevel

       Possibilities:
               unchanged   (0)"
   ::= {er1646v2EthPortSwFIbwEntry 4138401792}

er1646v2EthPortSwFIbwActViolActIpDeFlag OBJECT-TYPE
   SYNTAX      INTEGER
               {
               unchanged (255),
               clear (0),
               set (1)
               }
   MAX-ACCESS  read-write
   STATUS      current
   DESCRIPTION
      "Path: swPort.editConf.inboundBandwidth.action.violateAction.ip.deFlag

       Possibilities:
               unchanged   (255)
               clear   (0)
               set   (1)"
   ::= {er1646v2EthPortSwFIbwEntry 4138598400}

er1646v2EthPortSwFIbwSubInterfacesExcluded OBJECT-TYPE
   SYNTAX      INTEGER
               {
               s (1)
               }
   MAX-ACCESS  read-write
   STATUS      current
   DESCRIPTION
      "Path: swPort.editConf.inboundBandwidth.subInterfaces.excluded

       Possibilities:
                  (1)"
   ::= {er1646v2EthPortSwFIbwEntry 2416967680}

er1646v2EthPortSwFIbwSubInterfacesIncludedInAccessList OBJECT-TYPE
   SYNTAX      DisplayString
   MAX-ACCESS  read-write
   STATUS      current
   DESCRIPTION
      "Path: swPort.editConf.inboundBandwidth.subInterfaces.included.inAccessList"
   ::= {er1646v2EthPortSwFIbwEntry 2418020352}


er1646v2EthPortSwFVlan OBJECT IDENTIFIER ::= {er1646v2EthPortSwF 33}

er1646v2EthPortSwFVlanSSCTable OBJECT-TYPE
   SYNTAX      SEQUENCE OF Er1646v2EthPortSwFVlanEntry
   MAX-ACCESS  not-accessible
   STATUS      current
   DESCRIPTION
      ""
   ::= {er1646v2EthPortSwFVlan 1}

er1646v2EthPortSwFVlanEntry OBJECT-TYPE
   SYNTAX      Er1646v2EthPortSwFVlanEntry
   MAX-ACCESS  not-accessible
   STATUS      current
   DESCRIPTION
      ""
   INDEX      { er1646v2EthPortSwFVlanGlobalIx,
                er1646v2EthPortSwFVlanTableIx }
   ::= {er1646v2EthPortSwFVlanSSCTable 1}

Er1646v2EthPortSwFVlanEntry ::=
   SEQUENCE
      {
      er1646v2EthPortSwFVlanActions
         VariableLengthTableActions,
      er1646v2EthPortSwFVlanGlobalIx
         GlobalIndex,
      er1646v2EthPortSwFVlanTableIx
         TableIndex,
      er1646v2EthPortSwFVlanName
         DisplayString,
      er1646v2EthPortSwFVlanRemark
         DisplayString,
      er1646v2EthPortSwFVlanAdminStatus
         INTEGER,
      er1646v2EthPortSwFVlanMode
         INTEGER,
      er1646v2EthPortSwFVlanPriorityPolicy
         DisplayString,
      er1646v2EthPortSwFVlanIpVrfRouter
         DisplayString,
      er1646v2EthPortSwFVlanIpAdr
         IpAddress,
      er1646v2EthPortSwFVlanIpNetm
         IpAddress,
      er1646v2EthPortSwFVlanIpSNetName
         INTEGER,
      er1646v2EthPortSwFVlanIpSNetCust
         DisplayString,
      er1646v2EthPortSwFVlanIpDhcpC
         INTEGER,
      er1646v2EthPortSwFVlanIpDhcpGatewayPreference
         Integer32,
      er1646v2EthPortSwFVlanIpDhcpRoutePreference
         Integer32,
      er1646v2EthPortSwFVlanIpDhcpDnsPreference
         Integer32,
      er1646v2EthPortSwFVlanIpMtu
         Integer32,
      er1646v2EthPortSwFVlanIpMssAdjust
         INTEGER,
      er1646v2EthPortSwFVlanIpRipMetric
         Integer32,
      er1646v2EthPortSwFVlanIpRipMetricOut
         Integer32,
      er1646v2EthPortSwFVlanIpRipMode
         INTEGER,
      er1646v2EthPortSwFVlanIpRipTxVer
         INTEGER,
      er1646v2EthPortSwFVlanIpRipRxVer
         INTEGER,
      er1646v2EthPortSwFVlanIpRipSplitH
         INTEGER,
      er1646v2EthPortSwFVlanIpRipAuth
         INTEGER,
      er1646v2EthPortSwFVlanIpRipFilter
         DisplayString,
      er1646v2EthPortSwFVlanIpRipFilterIn
         DisplayString,
      er1646v2EthPortSwFVlanIpRipClearNextHop
         INTEGER,
      er1646v2EthPortSwFVlanIpAccPol
         DisplayString,
      er1646v2EthPortSwFVlanIpAB
         DisplayString,
      er1646v2EthPortSwFVlanIpMA
         INTEGER,
      er1646v2EthPortSwFVlanIpMF
         Integer32,
      er1646v2EthPortSwFVlanIpDB
         INTEGER,
      er1646v2EthPortSwFVlanIpIR
         INTEGER,
      er1646v2EthPortSwFVlanIpIgmp
         INTEGER,
      er1646v2EthPortSwFVlanIpNN
         DisplayString,
      er1646v2EthPortSwFVlanIpVrrp
         INTEGER,
      er1646v2EthPortSwFVlanIpPimMode
         INTEGER,
      er1646v2EthPortSwFVlanIpPimDrPriority
         Counter32,
      er1646v2EthPortSwFVlanIpPimHelloTime
         TimeTicks,
      er1646v2EthPortSwFVlanIpPimPropagationDelay
         TimeTicks,
      er1646v2EthPortSwFVlanIpPimOverrideInterval
         TimeTicks,
      er1646v2EthPortSwFVlanIpPimBsrBorder
         INTEGER,
      er1646v2EthPortSwFVlanIpPimTtlThreshold
         Integer32,
      er1646v2EthPortSwFVlanIpIMNetworkUnreachable
         INTEGER,
      er1646v2EthPortSwFVlanIpIMHostUnreachable
         INTEGER,
      er1646v2EthPortSwFVlanIpIMProtocolUnreachable
         INTEGER,
      er1646v2EthPortSwFVlanIpIMPortUnreachable
         INTEGER,
      er1646v2EthPortSwFVlanIpIMMtuExceeded
         INTEGER,
      er1646v2EthPortSwFVlanIpIMAdminProhibited
         INTEGER,
      er1646v2EthPortSwFVlanIpIMTtlExceeded
         INTEGER,
      er1646v2EthPortSwFVlanIpIMRedirect
         INTEGER,
      er1646v2EthPortSwFVlanIpV6VrfRouter
         DisplayString,
      er1646v2EthPortSwFVlanIpV6AddrAutoConfigNrDupAddrDetects
         Integer32,
      er1646v2EthPortSwFVlanIpV6AddrAutoConfigAcceptRa
         INTEGER,
      er1646v2EthPortSwFVlanIpV6AddrAutoConfigAcceptRaRdnss
         INTEGER,
      er1646v2EthPortSwFVlanIpV6AddrAutoConfigAcceptRaDnssl
         INTEGER,
      er1646v2EthPortSwFVlanIpV6DefaultRoute
         INTEGER,
      er1646v2EthPortSwFVlanIpV6RaSend
         INTEGER,
      er1646v2EthPortSwFVlanIpV6RaMinInterval
         TimeTicks,
      er1646v2EthPortSwFVlanIpV6RaMaxInterval
         TimeTicks,
      er1646v2EthPortSwFVlanIpV6RaManagedFlag
         INTEGER,
      er1646v2EthPortSwFVlanIpV6RaOtherConfFlag
         INTEGER,
      er1646v2EthPortSwFVlanIpV6RaLinkMtu
         Integer32,
      er1646v2EthPortSwFVlanIpV6RaReachableTime
         TimeTicks,
      er1646v2EthPortSwFVlanIpV6RaRetransmitTime
         TimeTicks,
      er1646v2EthPortSwFVlanIpV6RaHopLimit
         Integer32,
      er1646v2EthPortSwFVlanIpV6RaDefaultLifeTime
         TimeTicks,
      er1646v2EthPortSwFVlanIpV6RaDnsOptionsRdnssLifeTime
         TimeTicks,
      er1646v2EthPortSwFVlanIpV6RaDnsOptionsRdnssImportServers
         INTEGER,
      er1646v2EthPortSwFVlanIpV6RaDnsOptionsDnsslLifeTime
         TimeTicks,
      er1646v2EthPortSwFVlanIpV6RaDnsOptionsDnsslImportDomains
         INTEGER,
      er1646v2EthPortSwFVlanIpV6RsSend
         INTEGER,
      er1646v2EthPortSwFVlanIpV6RsMaxRandomDelay
         TimeTicks,
      er1646v2EthPortSwFVlanIpV6RsInterval
         TimeTicks,
      er1646v2EthPortSwFVlanIpV6RsMaxSolicitations
         Integer32,
      er1646v2EthPortSwFVlanIpV6TrafficPolicyInbound
         DisplayString,
      er1646v2EthPortSwFVlanIpV6TrafficPolicyOutbound
         DisplayString,
      er1646v2EthPortSwFVlanIpV6FirewallZone
         DisplayString,
      er1646v2EthPortSwFVlanIpV6DhcpClientAddrAC
         INTEGER,
      er1646v2EthPortSwFVlanIpV6DhcpClientPrDelMode
         INTEGER,
      er1646v2EthPortSwFVlanIpV6DhcpClientPrDelPool
         DisplayString,
      er1646v2EthPortSwFVlanIpV6DhcpClientPrDelPdExclOpt
         INTEGER,
      er1646v2EthPortSwFVlanIpV6DhcpClientDnsServerPref
         Integer32,
      er1646v2EthPortSwFVlanIpV6DhcpClientRapidCommit
         INTEGER,
      er1646v2EthPortSwFVlanIpV6DhcpClientTimersSolTimeOut
         TimeTicks,
      er1646v2EthPortSwFVlanIpV6DhcpClientTimersSolMaxRt
         TimeTicks,
      er1646v2EthPortSwFVlanIpV6DhcpClientTimersInfoRefresh
         TimeTicks,
      er1646v2EthPortSwFVlanIpV6DhcpServerMode
         INTEGER,
      er1646v2EthPortSwFVlanIpV6DhcpServerPreference
         Integer32,
      er1646v2EthPortSwFVlanIpV6DhcpServerPool
         DisplayString,
      er1646v2EthPortSwFVlanIpV6DhcpServerRapidCommit
         INTEGER,
      er1646v2EthPortSwFVlanIpV6DhcpServerTimersInfoRefresh
         TimeTicks,
      er1646v2EthPortSwFVlanIpV6DhcpRelayMode
         INTEGER,
      er1646v2EthPortSwFVlanIpV6SendRedirect
         INTEGER,
      er1646v2EthPortSwFVlanIpV6LinkMtu
         Integer32,
      er1646v2EthPortSwFVlanIpV6InterfaceId
         OCTET STRING,
      er1646v2EthPortSwFVlanIpV6MF
         Integer32,
      er1646v2EthPortSwFVlanIpV6IcmpMessagesNoRoute
         INTEGER,
      er1646v2EthPortSwFVlanIpV6IcmpMessagesBeyondScope
         INTEGER,
      er1646v2EthPortSwFVlanIpV6IcmpMessagesAddressUnreachable
         INTEGER,
      er1646v2EthPortSwFVlanIpV6IcmpMessagesPortUnreachable
         INTEGER,
      er1646v2EthPortSwFVlanIpV6IcmpMessagesPacketTooBig
         INTEGER,
      er1646v2EthPortSwFVlanIpV6IcmpMessagesHopLimitExceeded
         INTEGER,
      er1646v2EthPortSwFVlanIpV6IcmpMessagesFragTimeExceeded
         INTEGER,
      er1646v2EthPortSwFVlanIpV6IcmpMessagesHeaderFieldErr
         INTEGER,
      er1646v2EthPortSwFVlanIpV6IcmpMessagesOptionUnrecognized
         INTEGER,
      er1646v2EthPortSwFVlanIpV6IcmpMessagesRedirect
         INTEGER,
      er1646v2EthPortSwFVlanBridgingAccList
         DisplayString,
      er1646v2EthPortSwFVlanBridgingInACL
         DisplayString,
      er1646v2EthPortSwFVlanBridgingTp
         DisplayString,
      er1646v2EthPortSwFVlanBridgingBrGrp
         DisplayString,
      er1646v2EthPortSwFVlanBridgingLimBC
         INTEGER,
      er1646v2EthPortSwFVlanBridgingPrivateMode
         INTEGER,
      er1646v2EthPortSwFVlanBridgingLearning
         INTEGER,
      er1646v2EthPortSwFVlanBridgingMaxCacheSize
         INTEGER,
      er1646v2EthPortSwFVlanBridgingRelearnDropOnRelearn
         INTEGER,
      er1646v2EthPortSwFVlanBridgingRelearnShutdownThreshold
         Integer32,
      er1646v2EthPortSwFVlanBridgingRelearnShutdownTime
         TimeTicks,
      er1646v2EthPortSwFVlanBridgingRelearnLoopDetection
         INTEGER,
      er1646v2EthPortSwFVlanBridgingRelearnLoopDetectionInterval
         TimeTicks,
      er1646v2EthPortSwFVlanBridgingVlanMemberShip
         INTEGER,
      er1646v2EthPortSwFVlanBridgingVlTUntaggedAction
         INTEGER,
      er1646v2EthPortSwFVlanBridgingVlTUntaggedTagInfoTpid
         INTEGER,
      er1646v2EthPortSwFVlanBridgingVlTUntaggedTagInfoVid
         Integer32,
      er1646v2EthPortSwFVlanBridgingVlTUnknownVlansAction
         INTEGER,
      er1646v2EthPortSwFVlanBridgingVlTUnknownVlansTagInfoTpid
         INTEGER,
      er1646v2EthPortSwFVlanBridgingVlTUnknownVlansTagInfoVid
         Integer32,
      er1646v2EthPortSwFVlanBridgingDot1adType
         INTEGER,
      er1646v2EthPortSwFVlanBridgingPriority
         Integer32,
      er1646v2EthPortSwFVlanBridgingPathCost
         Integer32,
      er1646v2EthPortSwFVlanBridgingInternalPathCost
         Integer32,
      er1646v2EthPortSwFVlanBridgingTCD
         INTEGER,
      er1646v2EthPortSwFVlanBridgingRestrictedRole
         INTEGER,
      er1646v2EthPortSwFVlanBridgingAdminEdge
         INTEGER,
      er1646v2EthPortSwFVlanBridgingOamMacDeviceMac
         DisplayString,
      er1646v2EthPortSwFVlanBridgingOamMacUserMac
         OCTET STRING,
      er1646v2EthPortSwFVlanBridgingOamMacBridgeMac
         DisplayString,
      er1646v2EthPortSwFVlanBridgingMgmtInline
         INTEGER,
      er1646v2EthPortSwFVlanBridgingL2ptMode
         INTEGER,
      er1646v2EthPortSwFVlanBridgingL2ptProtocols
         Integer32,
      er1646v2EthPortSwFVlanBridgingL2ptDestMac
         OCTET STRING,
      er1646v2EthPortSwFVlanBridgingL2ptCos
         INTEGER,
      er1646v2EthPortSwFVlanBridgingL2ptDropThrStp
         INTEGER,
      er1646v2EthPortSwFVlanBridgingL2ptDropThrLldp
         INTEGER,
      er1646v2EthPortSwFVlanBridgingL2ptDropThrOam
         INTEGER,
      er1646v2EthPortSwFVlanBridgingL2ptDropThrCdp
         INTEGER,
      er1646v2EthPortSwFVlanBridgingL2ptDropThrVtp
         INTEGER,
      er1646v2EthPortSwFVlanBridgingL2ptDropThrLacp
         INTEGER,
      er1646v2EthPortSwFVlanBridgingL2ptDropThrEfmOam
         INTEGER,
      er1646v2EthPortSwFVlanBridgingL2ptDropThrPvst
         INTEGER,
      er1646v2EthPortSwFVlanBridgingL2ptDropThrMmrp
         INTEGER,
      er1646v2EthPortSwFVlanBridgingL2ptDropThrMvrp
         INTEGER,
      er1646v2EthPortSwFVlanBridgingL2ptDropThrGvrp
         INTEGER,
      er1646v2EthPortSwFVlanBridgingL2ptDropThrGmrp
         INTEGER,
      er1646v2EthPortSwFVlanBridgingL2ptDropThrDtp
         INTEGER,
      er1646v2EthPortSwFVlanBridgingL2ptDropThrPagp
         INTEGER,
      er1646v2EthPortSwFVlanBridgingL2ptDropThrUdld
         INTEGER,
      er1646v2EthPortSwFVlanVlanVid
         INTEGER,
      er1646v2EthPortSwFVlanVlanVidExtensionSingle
         OCTET STRING,
      er1646v2EthPortSwFVlanVlanVidExtensionEndVid
         Integer32,
      er1646v2EthPortSwFVlanVlanTpid
         INTEGER,
      er1646v2EthPortSwFVlanVlanTagSign
         INTEGER,
      er1646v2EthPortSwFVlanVlanChTos
         INTEGER,
      er1646v2EthPortSwFVlanVlanCTMapP0
         INTEGER,
      er1646v2EthPortSwFVlanVlanCTMapP1
         INTEGER,
      er1646v2EthPortSwFVlanVlanCTMapP2
         INTEGER,
      er1646v2EthPortSwFVlanVlanCTMapP3
         INTEGER,
      er1646v2EthPortSwFVlanVlanCTMapP4
         INTEGER,
      er1646v2EthPortSwFVlanVlanCTMapP5
         INTEGER,
      er1646v2EthPortSwFVlanVlanCTMapP6
         INTEGER,
      er1646v2EthPortSwFVlanVlanCTMapP7
         INTEGER,
      er1646v2EthPortSwFVlanVlanTxCos
         INTEGER,
      er1646v2EthPortSwFVlanVlanCCMapP0
         Integer32,
      er1646v2EthPortSwFVlanVlanCCMapP1
         Integer32,
      er1646v2EthPortSwFVlanVlanCCMapP2
         Integer32,
      er1646v2EthPortSwFVlanVlanCCMapP3
         Integer32,
      er1646v2EthPortSwFVlanVlanCCMapP4
         Integer32,
      er1646v2EthPortSwFVlanVlanCCMapP5
         Integer32,
      er1646v2EthPortSwFVlanVlanCCMapP6
         Integer32,
      er1646v2EthPortSwFVlanVlanCCMapP7
         Integer32,
      er1646v2EthPortSwFVlanVlanQCMapQueue1
         Integer32,
      er1646v2EthPortSwFVlanVlanQCMapQueue2
         Integer32,
      er1646v2EthPortSwFVlanVlanQCMapQueue3
         Integer32,
      er1646v2EthPortSwFVlanVlanQCMapQueue4
         Integer32,
      er1646v2EthPortSwFVlanVlanQCMapQueue5
         Integer32,
      er1646v2EthPortSwFVlanVlanQCMapLowDelayQueue
         Integer32,
      er1646v2EthPortSwFVlanVlanQCMapLowDelay2Queue
         Integer32,
      er1646v2EthPortSwFVlanVlanQCMapSystemQueue
         Integer32,
      er1646v2EthPortSwFVlanVlanQinQSVid
         Integer32,
      er1646v2EthPortSwFVlanVlanQinQSTpid
         INTEGER,
      er1646v2EthPortSwFVlanVlanArpTimeOut
         TimeTicks,
      er1646v2EthPortSwFVlanVlanArpProxyArp
         INTEGER,
      er1646v2EthPortSwFVlanBandwidthMode
         INTEGER,
      er1646v2EthPortSwFVlanBandwidthCir
         Integer32,
      er1646v2EthPortSwFVlanBandwidthEir
         Integer32,
      er1646v2EthPortSwFVlanBandwidthUnit
         INTEGER,
      er1646v2EthPortSwFVlanBandwidthTc
         INTEGER,
      er1646v2EthPortSwFVlanBandwidthTcFactor
         INTEGER,
      er1646v2EthPortSwFVlanBandwidthCorrType
         INTEGER,
      er1646v2EthPortSwFVlanBandwidthCorrPredefEncapsFrameRelay
         DisplayString,
      er1646v2EthPortSwFVlanBandwidthCorrPredefEncapsPpp
         DisplayString,
      er1646v2EthPortSwFVlanBandwidthCorrPredefEncapsAtmHl
         INTEGER,
      er1646v2EthPortSwFVlanBandwidthCorrPredefEncapsAtmMp
         INTEGER,
      er1646v2EthPortSwFVlanBandwidthCorrPredefEncapsHdlc
         DisplayString,
      er1646v2EthPortSwFVlanBandwidthCorrPredefEncapsEfmFs
         Integer32,
      er1646v2EthPortSwFVlanBandwidthCorrPredefEncapsEfmIb
         Integer32,
      er1646v2EthPortSwFVlanBandwidthCorrPredefMode
         INTEGER,
      er1646v2EthPortSwFVlanBandwidthCorrManualOverhead
         Integer32,
      er1646v2EthPortSwFVlanBandwidthCorrManualFrameData
         Counter32,
      er1646v2EthPortSwFVlanBandwidthCorrManualFrameHeader
         Counter32,
      er1646v2EthPortSwFVlanBandwidthMaxFifoQLen
         Integer32,
      er1646v2EthPortSwFVlanBandwidthDeFlagCir
         INTEGER,
      er1646v2EthPortSwFVlanBandwidthDeFlagEir
         INTEGER,
      er1646v2EthPortSwFVlanBandwidthDeFlagViolate
         INTEGER,
      er1646v2EthPortSwFVlanBandwidthActCirActNone
         OCTET STRING,
      er1646v2EthPortSwFVlanBandwidthActCirActEthCos1
         INTEGER,
      er1646v2EthPortSwFVlanBandwidthActCirActEthDei1
         INTEGER,
      er1646v2EthPortSwFVlanBandwidthActCirActEthCos2
         INTEGER,
      er1646v2EthPortSwFVlanBandwidthActCirActEthDei2
         INTEGER,
      er1646v2EthPortSwFVlanBandwidthActCirActEthCos3
         INTEGER,
      er1646v2EthPortSwFVlanBandwidthActCirActEthDei3
         INTEGER,
      er1646v2EthPortSwFVlanBandwidthActCirActEthCos4
         INTEGER,
      er1646v2EthPortSwFVlanBandwidthActCirActEthDei4
         INTEGER,
      er1646v2EthPortSwFVlanBandwidthActCirActEthCos5
         INTEGER,
      er1646v2EthPortSwFVlanBandwidthActCirActEthDei5
         INTEGER,
      er1646v2EthPortSwFVlanBandwidthActCirActEthCos6
         INTEGER,
      er1646v2EthPortSwFVlanBandwidthActCirActEthDei6
         INTEGER,
      er1646v2EthPortSwFVlanBandwidthActCirActEthCos7
         INTEGER,
      er1646v2EthPortSwFVlanBandwidthActCirActEthDei7
         INTEGER,
      er1646v2EthPortSwFVlanBandwidthActCirActEthCos8
         INTEGER,
      er1646v2EthPortSwFVlanBandwidthActCirActEthDei8
         INTEGER,
      er1646v2EthPortSwFVlanBandwidthActCirActEthTos
         INTEGER,
      er1646v2EthPortSwFVlanBandwidthActCirActEthQueue
         INTEGER,
      er1646v2EthPortSwFVlanBandwidthActCirActEthDrpLev
         INTEGER,
      er1646v2EthPortSwFVlanBandwidthActCirActEthDeFlag
         INTEGER,
      er1646v2EthPortSwFVlanBandwidthActCirActIpTos
         INTEGER,
      er1646v2EthPortSwFVlanBandwidthActCirActIpQueue
         INTEGER,
      er1646v2EthPortSwFVlanBandwidthActCirActIpDrpLev
         INTEGER,
      er1646v2EthPortSwFVlanBandwidthActCirActIpDeFlag
         INTEGER,
      er1646v2EthPortSwFVlanBandwidthActEirActNone
         OCTET STRING,
      er1646v2EthPortSwFVlanBandwidthActEirActEthCos1
         INTEGER,
      er1646v2EthPortSwFVlanBandwidthActEirActEthDei1
         INTEGER,
      er1646v2EthPortSwFVlanBandwidthActEirActEthCos2
         INTEGER,
      er1646v2EthPortSwFVlanBandwidthActEirActEthDei2
         INTEGER,
      er1646v2EthPortSwFVlanBandwidthActEirActEthCos3
         INTEGER,
      er1646v2EthPortSwFVlanBandwidthActEirActEthDei3
         INTEGER,
      er1646v2EthPortSwFVlanBandwidthActEirActEthCos4
         INTEGER,
      er1646v2EthPortSwFVlanBandwidthActEirActEthDei4
         INTEGER,
      er1646v2EthPortSwFVlanBandwidthActEirActEthCos5
         INTEGER,
      er1646v2EthPortSwFVlanBandwidthActEirActEthDei5
         INTEGER,
      er1646v2EthPortSwFVlanBandwidthActEirActEthCos6
         INTEGER,
      er1646v2EthPortSwFVlanBandwidthActEirActEthDei6
         INTEGER,
      er1646v2EthPortSwFVlanBandwidthActEirActEthCos7
         INTEGER,
      er1646v2EthPortSwFVlanBandwidthActEirActEthDei7
         INTEGER,
      er1646v2EthPortSwFVlanBandwidthActEirActEthCos8
         INTEGER,
      er1646v2EthPortSwFVlanBandwidthActEirActEthDei8
         INTEGER,
      er1646v2EthPortSwFVlanBandwidthActEirActEthTos
         INTEGER,
      er1646v2EthPortSwFVlanBandwidthActEirActEthQueue
         INTEGER,
      er1646v2EthPortSwFVlanBandwidthActEirActEthDrpLev
         INTEGER,
      er1646v2EthPortSwFVlanBandwidthActEirActEthDeFlag
         INTEGER,
      er1646v2EthPortSwFVlanBandwidthActEirActIpTos
         INTEGER,
      er1646v2EthPortSwFVlanBandwidthActEirActIpQueue
         INTEGER,
      er1646v2EthPortSwFVlanBandwidthActEirActIpDrpLev
         INTEGER,
      er1646v2EthPortSwFVlanBandwidthActEirActIpDeFlag
         INTEGER,
      er1646v2EthPortSwFVlanBandwidthActViolActNone
         OCTET STRING,
      er1646v2EthPortSwFVlanBandwidthActViolActDrop
         OCTET STRING,
      er1646v2EthPortSwFVlanBandwidthActViolActEthCos1
         INTEGER,
      er1646v2EthPortSwFVlanBandwidthActViolActEthDei1
         INTEGER,
      er1646v2EthPortSwFVlanBandwidthActViolActEthCos2
         INTEGER,
      er1646v2EthPortSwFVlanBandwidthActViolActEthDei2
         INTEGER,
      er1646v2EthPortSwFVlanBandwidthActViolActEthCos3
         INTEGER,
      er1646v2EthPortSwFVlanBandwidthActViolActEthDei3
         INTEGER,
      er1646v2EthPortSwFVlanBandwidthActViolActEthCos4
         INTEGER,
      er1646v2EthPortSwFVlanBandwidthActViolActEthDei4
         INTEGER,
      er1646v2EthPortSwFVlanBandwidthActViolActEthCos5
         INTEGER,
      er1646v2EthPortSwFVlanBandwidthActViolActEthDei5
         INTEGER,
      er1646v2EthPortSwFVlanBandwidthActViolActEthCos6
         INTEGER,
      er1646v2EthPortSwFVlanBandwidthActViolActEthDei6
         INTEGER,
      er1646v2EthPortSwFVlanBandwidthActViolActEthCos7
         INTEGER,
      er1646v2EthPortSwFVlanBandwidthActViolActEthDei7
         INTEGER,
      er1646v2EthPortSwFVlanBandwidthActViolActEthCos8
         INTEGER,
      er1646v2EthPortSwFVlanBandwidthActViolActEthDei8
         INTEGER,
      er1646v2EthPortSwFVlanBandwidthActViolActEthTos
         INTEGER,
      er1646v2EthPortSwFVlanBandwidthActViolActEthQueue
         INTEGER,
      er1646v2EthPortSwFVlanBandwidthActViolActEthDrpLev
         INTEGER,
      er1646v2EthPortSwFVlanBandwidthActViolActEthDeFlag
         INTEGER,
      er1646v2EthPortSwFVlanBandwidthActViolActIpTos
         INTEGER,
      er1646v2EthPortSwFVlanBandwidthActViolActIpQueue
         INTEGER,
      er1646v2EthPortSwFVlanBandwidthActViolActIpDrpLev
         INTEGER,
      er1646v2EthPortSwFVlanBandwidthActViolActIpDeFlag
         INTEGER,
      er1646v2EthPortSwFVlanInbBwMode
         INTEGER,
      er1646v2EthPortSwFVlanInbBwCir
         Integer32,
      er1646v2EthPortSwFVlanInbBwEir
         Integer32,
      er1646v2EthPortSwFVlanInbBwUnit
         INTEGER,
      er1646v2EthPortSwFVlanInbBwTc
         INTEGER,
      er1646v2EthPortSwFVlanInbBwTcFactor
         INTEGER,
      er1646v2EthPortSwFVlanInbBwCorrType
         INTEGER,
      er1646v2EthPortSwFVlanInbBwCorrPredefEncapsFrameRelay
         DisplayString,
      er1646v2EthPortSwFVlanInbBwCorrPredefEncapsPpp
         DisplayString,
      er1646v2EthPortSwFVlanInbBwCorrPredefEncapsAtmHl
         INTEGER,
      er1646v2EthPortSwFVlanInbBwCorrPredefEncapsAtmMp
         INTEGER,
      er1646v2EthPortSwFVlanInbBwCorrPredefEncapsHdlc
         DisplayString,
      er1646v2EthPortSwFVlanInbBwCorrPredefEncapsEfmFs
         Integer32,
      er1646v2EthPortSwFVlanInbBwCorrPredefEncapsEfmIb
         Integer32,
      er1646v2EthPortSwFVlanInbBwCorrPredefMode
         INTEGER,
      er1646v2EthPortSwFVlanInbBwCorrManualOverhead
         Integer32,
      er1646v2EthPortSwFVlanInbBwCorrManualFrameData
         Counter32,
      er1646v2EthPortSwFVlanInbBwCorrManualFrameHeader
         Counter32,
      er1646v2EthPortSwFVlanInbBwMaxFifoQLen
         Integer32,
      er1646v2EthPortSwFVlanInbBwPriorityPolicy
         DisplayString,
      er1646v2EthPortSwFVlanInbBwDeFlagCir
         INTEGER,
      er1646v2EthPortSwFVlanInbBwDeFlagEir
         INTEGER,
      er1646v2EthPortSwFVlanInbBwDeFlagViolate
         INTEGER,
      er1646v2EthPortSwFVlanInbBwActCirActNone
         OCTET STRING,
      er1646v2EthPortSwFVlanInbBwActCirActEthCos1
         INTEGER,
      er1646v2EthPortSwFVlanInbBwActCirActEthDei1
         INTEGER,
      er1646v2EthPortSwFVlanInbBwActCirActEthCos2
         INTEGER,
      er1646v2EthPortSwFVlanInbBwActCirActEthDei2
         INTEGER,
      er1646v2EthPortSwFVlanInbBwActCirActEthCos3
         INTEGER,
      er1646v2EthPortSwFVlanInbBwActCirActEthDei3
         INTEGER,
      er1646v2EthPortSwFVlanInbBwActCirActEthCos4
         INTEGER,
      er1646v2EthPortSwFVlanInbBwActCirActEthDei4
         INTEGER,
      er1646v2EthPortSwFVlanInbBwActCirActEthCos5
         INTEGER,
      er1646v2EthPortSwFVlanInbBwActCirActEthDei5
         INTEGER,
      er1646v2EthPortSwFVlanInbBwActCirActEthCos6
         INTEGER,
      er1646v2EthPortSwFVlanInbBwActCirActEthDei6
         INTEGER,
      er1646v2EthPortSwFVlanInbBwActCirActEthCos7
         INTEGER,
      er1646v2EthPortSwFVlanInbBwActCirActEthDei7
         INTEGER,
      er1646v2EthPortSwFVlanInbBwActCirActEthCos8
         INTEGER,
      er1646v2EthPortSwFVlanInbBwActCirActEthDei8
         INTEGER,
      er1646v2EthPortSwFVlanInbBwActCirActEthTos
         INTEGER,
      er1646v2EthPortSwFVlanInbBwActCirActEthQueue
         INTEGER,
      er1646v2EthPortSwFVlanInbBwActCirActEthDrpLev
         INTEGER,
      er1646v2EthPortSwFVlanInbBwActCirActEthDeFlag
         INTEGER,
      er1646v2EthPortSwFVlanInbBwActCirActIpTos
         INTEGER,
      er1646v2EthPortSwFVlanInbBwActCirActIpQueue
         INTEGER,
      er1646v2EthPortSwFVlanInbBwActCirActIpDrpLev
         INTEGER,
      er1646v2EthPortSwFVlanInbBwActCirActIpDeFlag
         INTEGER,
      er1646v2EthPortSwFVlanInbBwActEirActNone
         OCTET STRING,
      er1646v2EthPortSwFVlanInbBwActEirActEthCos1
         INTEGER,
      er1646v2EthPortSwFVlanInbBwActEirActEthDei1
         INTEGER,
      er1646v2EthPortSwFVlanInbBwActEirActEthCos2
         INTEGER,
      er1646v2EthPortSwFVlanInbBwActEirActEthDei2
         INTEGER,
      er1646v2EthPortSwFVlanInbBwActEirActEthCos3
         INTEGER,
      er1646v2EthPortSwFVlanInbBwActEirActEthDei3
         INTEGER,
      er1646v2EthPortSwFVlanInbBwActEirActEthCos4
         INTEGER,
      er1646v2EthPortSwFVlanInbBwActEirActEthDei4
         INTEGER,
      er1646v2EthPortSwFVlanInbBwActEirActEthCos5
         INTEGER,
      er1646v2EthPortSwFVlanInbBwActEirActEthDei5
         INTEGER,
      er1646v2EthPortSwFVlanInbBwActEirActEthCos6
         INTEGER,
      er1646v2EthPortSwFVlanInbBwActEirActEthDei6
         INTEGER,
      er1646v2EthPortSwFVlanInbBwActEirActEthCos7
         INTEGER,
      er1646v2EthPortSwFVlanInbBwActEirActEthDei7
         INTEGER,
      er1646v2EthPortSwFVlanInbBwActEirActEthCos8
         INTEGER,
      er1646v2EthPortSwFVlanInbBwActEirActEthDei8
         INTEGER,
      er1646v2EthPortSwFVlanInbBwActEirActEthTos
         INTEGER,
      er1646v2EthPortSwFVlanInbBwActEirActEthQueue
         INTEGER,
      er1646v2EthPortSwFVlanInbBwActEirActEthDrpLev
         INTEGER,
      er1646v2EthPortSwFVlanInbBwActEirActEthDeFlag
         INTEGER,
      er1646v2EthPortSwFVlanInbBwActEirActIpTos
         INTEGER,
      er1646v2EthPortSwFVlanInbBwActEirActIpQueue
         INTEGER,
      er1646v2EthPortSwFVlanInbBwActEirActIpDrpLev
         INTEGER,
      er1646v2EthPortSwFVlanInbBwActEirActIpDeFlag
         INTEGER,
      er1646v2EthPortSwFVlanInbBwActViolActNone
         OCTET STRING,
      er1646v2EthPortSwFVlanInbBwActViolActDrop
         OCTET STRING,
      er1646v2EthPortSwFVlanInbBwActViolActEthCos1
         INTEGER,
      er1646v2EthPortSwFVlanInbBwActViolActEthDei1
         INTEGER,
      er1646v2EthPortSwFVlanInbBwActViolActEthCos2
         INTEGER,
      er1646v2EthPortSwFVlanInbBwActViolActEthDei2
         INTEGER,
      er1646v2EthPortSwFVlanInbBwActViolActEthCos3
         INTEGER,
      er1646v2EthPortSwFVlanInbBwActViolActEthDei3
         INTEGER,
      er1646v2EthPortSwFVlanInbBwActViolActEthCos4
         INTEGER,
      er1646v2EthPortSwFVlanInbBwActViolActEthDei4
         INTEGER,
      er1646v2EthPortSwFVlanInbBwActViolActEthCos5
         INTEGER,
      er1646v2EthPortSwFVlanInbBwActViolActEthDei5
         INTEGER,
      er1646v2EthPortSwFVlanInbBwActViolActEthCos6
         INTEGER,
      er1646v2EthPortSwFVlanInbBwActViolActEthDei6
         INTEGER,
      er1646v2EthPortSwFVlanInbBwActViolActEthCos7
         INTEGER,
      er1646v2EthPortSwFVlanInbBwActViolActEthDei7
         INTEGER,
      er1646v2EthPortSwFVlanInbBwActViolActEthCos8
         INTEGER,
      er1646v2EthPortSwFVlanInbBwActViolActEthDei8
         INTEGER,
      er1646v2EthPortSwFVlanInbBwActViolActEthTos
         INTEGER,
      er1646v2EthPortSwFVlanInbBwActViolActEthQueue
         INTEGER,
      er1646v2EthPortSwFVlanInbBwActViolActEthDrpLev
         INTEGER,
      er1646v2EthPortSwFVlanInbBwActViolActEthDeFlag
         INTEGER,
      er1646v2EthPortSwFVlanInbBwActViolActIpTos
         INTEGER,
      er1646v2EthPortSwFVlanInbBwActViolActIpQueue
         INTEGER,
      er1646v2EthPortSwFVlanInbBwActViolActIpDrpLev
         INTEGER,
      er1646v2EthPortSwFVlanInbBwActViolActIpDeFlag
         INTEGER,
      er1646v2EthPortSwFVlanPppoE
         INTEGER,
      er1646v2EthPortSwFVlanPppLnkMOperation
         INTEGER,
      er1646v2EthPortSwFVlanPppLnkMInterval
         TimeTicks,
      er1646v2EthPortSwFVlanPppLnkMRepTimeOut
         TimeTicks,
      er1646v2EthPortSwFVlanPppLnkMFailsPrmt
         Integer32,
      er1646v2EthPortSwFVlanPppAuthentication
         INTEGER,
      er1646v2EthPortSwFVlanPppAuthenPeriod
         TimeTicks,
      er1646v2EthPortSwFVlanPppSessionName
         DisplayString,
      er1646v2EthPortSwFVlanPppSessionSecret
         DisplayString,
      er1646v2EthPortSwFVlanPppEncModeSessionSecret
         INTEGER,
      er1646v2EthPortSwFVlanPppEncSessionSecret
         DisplayString,
      er1646v2EthPortSwFVlanPppServiceName
         DisplayString,
      er1646v2EthPortSwFVlanPbbMode
         INTEGER,
      er1646v2EthPortSwFVlanPbbTxCos
         Integer32,
      er1646v2EthPortSwFVlanPbbIsid
         Integer32,
      er1646v2EthPortSwFVlanPbbDestMac
         OCTET STRING,
      er1646v2EthPortSwFVlanPbbCustomGroupMac
         OCTET STRING
      }

er1646v2EthPortSwFVlanActions OBJECT-TYPE
   SYNTAX      VariableLengthTableActions
   MAX-ACCESS  read-write
   STATUS      current
   DESCRIPTION
      "By way of this field, some manipulations
       on this table may be performed."
   ::= {er1646v2EthPortSwFVlanEntry 2}

er1646v2EthPortSwFVlanGlobalIx OBJECT-TYPE
   SYNTAX      GlobalIndex
   MAX-ACCESS  not-accessible
   STATUS      current
   DESCRIPTION
      "The value of the tlsCntTreeGlobalIndex of the MANAGED OBJECT."
   ::= {er1646v2EthPortSwFVlanEntry 10}

er1646v2EthPortSwFVlanTableIx OBJECT-TYPE
   SYNTAX      TableIndex
   MAX-ACCESS  not-accessible
   STATUS      current
   DESCRIPTION
      ""
   ::= {er1646v2EthPortSwFVlanEntry 11}

er1646v2EthPortSwFVlanName OBJECT-TYPE
   SYNTAX      DisplayString
   MAX-ACCESS  read-write
   STATUS      current
   DESCRIPTION
      "Path: swPort.editConf.vlan.name"
   ::= {er1646v2EthPortSwFVlanEntry 16777216}

er1646v2EthPortSwFVlanRemark OBJECT-TYPE
   SYNTAX      DisplayString
   MAX-ACCESS  read-write
   STATUS      current
   DESCRIPTION
      "Path: swPort.editConf.vlan.remark"
   ::= {er1646v2EthPortSwFVlanEntry 1157627904}

er1646v2EthPortSwFVlanAdminStatus OBJECT-TYPE
   SYNTAX      INTEGER
               {
               up (1),
               down (2)
               }
   MAX-ACCESS  read-write
   STATUS      current
   DESCRIPTION
      "Path: swPort.editConf.vlan.adminStatus

       Possibilities:
               up   (1)
               down   (2)"
   ::= {er1646v2EthPortSwFVlanEntry 33554432}

er1646v2EthPortSwFVlanMode OBJECT-TYPE
   SYNTAX      INTEGER
               {
               routing (1),
               bridging (2),
               ipV6 (16),
               ipV6ipV4 (17),
               multilink (8)
               }
   MAX-ACCESS  read-write
   STATUS      current
   DESCRIPTION
      "Path: swPort.editConf.vlan.mode

       Possibilities:
               routing   (1)
               bridging   (2)
               ipV6   (16)
               ipV6/ipV4   (17)
               multilink   (8)"
   ::= {er1646v2EthPortSwFVlanEntry 67108864}

er1646v2EthPortSwFVlanPriorityPolicy OBJECT-TYPE
   SYNTAX      DisplayString
   MAX-ACCESS  read-write
   STATUS      current
   DESCRIPTION
      "Path: swPort.editConf.vlan.priorityPolicy"
   ::= {er1646v2EthPortSwFVlanEntry 83886080}

er1646v2EthPortSwFVlanIpVrfRouter OBJECT-TYPE
   SYNTAX      DisplayString
   MAX-ACCESS  read-write
   STATUS      current
   DESCRIPTION
      "Path: swPort.editConf.vlan.ip.vrfRouter"
   ::= {er1646v2EthPortSwFVlanEntry 53215232}

er1646v2EthPortSwFVlanIpAdr OBJECT-TYPE
   SYNTAX      IpAddress
   MAX-ACCESS  read-write
   STATUS      current
   DESCRIPTION
      "Path: swPort.editConf.vlan.ip.address"
   ::= {er1646v2EthPortSwFVlanEntry 58261504}

er1646v2EthPortSwFVlanIpNetm OBJECT-TYPE
   SYNTAX      IpAddress
   MAX-ACCESS  read-write
   STATUS      current
   DESCRIPTION
      "Path: swPort.editConf.vlan.ip.netMask"
   ::= {er1646v2EthPortSwFVlanEntry 58392576}

er1646v2EthPortSwFVlanIpSNetName OBJECT-TYPE
   SYNTAX      INTEGER
               {
               slOPTg (0),
               corp (2),
               dmz (3),
               internet (1)
               }
   MAX-ACCESS  read-write
   STATUS      current
   DESCRIPTION
      "Path: swPort.editConf.vlan.ip.sNet.name

       Possibilities:
               <OPT>   (0)
               corp   (2)
               dmz   (3)
               internet   (1)"
   ::= {er1646v2EthPortSwFVlanEntry 53674240}

er1646v2EthPortSwFVlanIpSNetCust OBJECT-TYPE
   SYNTAX      DisplayString
   MAX-ACCESS  read-write
   STATUS      current
   DESCRIPTION
      "Path: swPort.editConf.vlan.ip.sNet.custom"
   ::= {er1646v2EthPortSwFVlanEntry 53674496}

er1646v2EthPortSwFVlanIpDhcpC OBJECT-TYPE
   SYNTAX      INTEGER
               {
               disabled (0),
               enabled (1)
               }
   MAX-ACCESS  read-write
   STATUS      current
   DESCRIPTION
      "Path: swPort.editConf.vlan.ip.dhcpClient

       Possibilities:
               disabled   (0)
               enabled   (1)"
   ::= {er1646v2EthPortSwFVlanEntry 53608448}

er1646v2EthPortSwFVlanIpDhcpGatewayPreference OBJECT-TYPE
   SYNTAX      Integer32
   MAX-ACCESS  read-write
   STATUS      current
   DESCRIPTION
      "Path: swPort.editConf.vlan.ip.dhcp.gatewayPreference"
   ::= {er1646v2EthPortSwFVlanEntry 53739776}

er1646v2EthPortSwFVlanIpDhcpRoutePreference OBJECT-TYPE
   SYNTAX      Integer32
   MAX-ACCESS  read-write
   STATUS      current
   DESCRIPTION
      "Path: swPort.editConf.vlan.ip.dhcp.routePreference"
   ::= {er1646v2EthPortSwFVlanEntry 53740032}

er1646v2EthPortSwFVlanIpDhcpDnsPreference OBJECT-TYPE
   SYNTAX      Integer32
   MAX-ACCESS  read-write
   STATUS      current
   DESCRIPTION
      "Path: swPort.editConf.vlan.ip.dhcp.dnsPreference"
   ::= {er1646v2EthPortSwFVlanEntry 53740288}

er1646v2EthPortSwFVlanIpMtu OBJECT-TYPE
   SYNTAX      Integer32
   MAX-ACCESS  read-write
   STATUS      current
   DESCRIPTION
      "Path: swPort.editConf.vlan.ip.mtu"
   ::= {er1646v2EthPortSwFVlanEntry 52953088}

er1646v2EthPortSwFVlanIpMssAdjust OBJECT-TYPE
   SYNTAX      INTEGER
               {
               disabled (0),
               auto (65536)
               }
   MAX-ACCESS  read-write
   STATUS      current
   DESCRIPTION
      "Path: swPort.editConf.vlan.ip.mssAdjust

       Possibilities:
               disabled   (0)
               auto   (65536)"
   ::= {er1646v2EthPortSwFVlanEntry 53280768}

er1646v2EthPortSwFVlanIpRipMetric OBJECT-TYPE
   SYNTAX      Integer32
   MAX-ACCESS  read-write
   STATUS      current
   DESCRIPTION
      "Path: swPort.editConf.vlan.ip.rip.metric"
   ::= {er1646v2EthPortSwFVlanEntry 51712768}

er1646v2EthPortSwFVlanIpRipMetricOut OBJECT-TYPE
   SYNTAX      Integer32
   MAX-ACCESS  read-write
   STATUS      current
   DESCRIPTION
      "Path: swPort.editConf.vlan.ip.rip.metricOut"
   ::= {er1646v2EthPortSwFVlanEntry 51713024}

er1646v2EthPortSwFVlanIpRipMode OBJECT-TYPE
   SYNTAX      INTEGER
               {
               disabled (0),
               passive (1),
               active (2)
               }
   MAX-ACCESS  read-write
   STATUS      current
   DESCRIPTION
      "Path: swPort.editConf.vlan.ip.rip.mode

       Possibilities:
               disabled   (0)
               passive   (1)
               active   (2)"
   ::= {er1646v2EthPortSwFVlanEntry 51713280}

er1646v2EthPortSwFVlanIpRipTxVer OBJECT-TYPE
   SYNTAX      INTEGER
               {
               rip1 (0),
               rip2 (1),
               rip1mcompatible (2)
               }
   MAX-ACCESS  read-write
   STATUS      current
   DESCRIPTION
      "Path: swPort.editConf.vlan.ip.rip.txVersion

       Possibilities:
               rip1   (0)
               rip2   (1)
               rip1-compatible   (2)"
   ::= {er1646v2EthPortSwFVlanEntry 51716864}

er1646v2EthPortSwFVlanIpRipRxVer OBJECT-TYPE
   SYNTAX      INTEGER
               {
               rip1only (0),
               rip2only (1),
               rip12 (2)
               }
   MAX-ACCESS  read-write
   STATUS      current
   DESCRIPTION
      "Path: swPort.editConf.vlan.ip.rip.rxVersion

       Possibilities:
               rip1only   (0)
               rip2only   (1)
               rip1&2   (2)"
   ::= {er1646v2EthPortSwFVlanEntry 51717120}

er1646v2EthPortSwFVlanIpRipSplitH OBJECT-TYPE
   SYNTAX      INTEGER
               {
               disabled (0),
               enabled (1),
               poisonedReverse (2)
               }
   MAX-ACCESS  read-write
   STATUS      current
   DESCRIPTION
      "Path: swPort.editConf.vlan.ip.rip.splitHorizon

       Possibilities:
               disabled   (0)
               enabled   (1)
               poisonedReverse   (2)"
   ::= {er1646v2EthPortSwFVlanEntry 51713792}

er1646v2EthPortSwFVlanIpRipAuth OBJECT-TYPE
   SYNTAX      INTEGER
               {
               disabled (0),
               texts (1),
               md5 (2)
               }
   MAX-ACCESS  read-write
   STATUS      current
   DESCRIPTION
      "Path: swPort.editConf.vlan.ip.rip.authentication

       Possibilities:
               disabled   (0)
               text    (1)
               md5   (2)"
   ::= {er1646v2EthPortSwFVlanEntry 51712512}

er1646v2EthPortSwFVlanIpRipFilter OBJECT-TYPE
   SYNTAX      DisplayString
   MAX-ACCESS  read-write
   STATUS      current
   DESCRIPTION
      "Path: swPort.editConf.vlan.ip.rip.filter"
   ::= {er1646v2EthPortSwFVlanEntry 51716096}

er1646v2EthPortSwFVlanIpRipFilterIn OBJECT-TYPE
   SYNTAX      DisplayString
   MAX-ACCESS  read-write
   STATUS      current
   DESCRIPTION
      "Path: swPort.editConf.vlan.ip.rip.filterIn"
   ::= {er1646v2EthPortSwFVlanEntry 51716352}

er1646v2EthPortSwFVlanIpRipClearNextHop OBJECT-TYPE
   SYNTAX      INTEGER
               {
               disabled (0),
               enabled (1)
               }
   MAX-ACCESS  read-write
   STATUS      current
   DESCRIPTION
      "Path: swPort.editConf.vlan.ip.rip.clearNextHop

       Possibilities:
               disabled   (0)
               enabled   (1)"
   ::= {er1646v2EthPortSwFVlanEntry 51708416}

er1646v2EthPortSwFVlanIpAccPol OBJECT-TYPE
   SYNTAX      DisplayString
   MAX-ACCESS  read-write
   STATUS      current
   DESCRIPTION
      "Path: swPort.editConf.vlan.ip.accessPolicy"
   ::= {er1646v2EthPortSwFVlanEntry 53084160}

er1646v2EthPortSwFVlanIpAB OBJECT-TYPE
   SYNTAX      DisplayString
   MAX-ACCESS  read-write
   STATUS      current
   DESCRIPTION
      "Path: swPort.editConf.vlan.ip.trafficPolicy"
   ::= {er1646v2EthPortSwFVlanEntry 51249152}

er1646v2EthPortSwFVlanIpMA OBJECT-TYPE
   SYNTAX      INTEGER
               {
               disabled (0),
               enabled (1)
               }
   MAX-ACCESS  read-write
   STATUS      current
   DESCRIPTION
      "Path: swPort.editConf.vlan.ip.mgmtAccess

       Possibilities:
               disabled   (0)
               enabled   (1)"
   ::= {er1646v2EthPortSwFVlanEntry 51380224}

er1646v2EthPortSwFVlanIpMF OBJECT-TYPE
   SYNTAX      Integer32
   MAX-ACCESS  read-write
   STATUS      current
   DESCRIPTION
      "Path: swPort.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwFVlanEntry 51445760}

er1646v2EthPortSwFVlanIpDB OBJECT-TYPE
   SYNTAX      INTEGER
               {
               disabled (0),
               enabled (1)
               }
   MAX-ACCESS  read-write
   STATUS      current
   DESCRIPTION
      "Path: swPort.editConf.vlan.ip.directedBroadcasts

       Possibilities:
               disabled   (0)
               enabled   (1)"
   ::= {er1646v2EthPortSwFVlanEntry 51773440}

er1646v2EthPortSwFVlanIpIR OBJECT-TYPE
   SYNTAX      INTEGER
               {
               disabled (0),
               enabled (1)
               }
   MAX-ACCESS  read-write
   STATUS      current
   DESCRIPTION
      "Path: swPort.editConf.vlan.ip.icmpRedirects

       Possibilities:
               disabled   (0)
               enabled   (1)"
   ::= {er1646v2EthPortSwFVlanEntry 52035584}

er1646v2EthPortSwFVlanIpIgmp OBJECT-TYPE
   SYNTAX      INTEGER
               {
               disabled (0),
               proxy (1),
               router (2),
               v3Router (5)
               }
   MAX-ACCESS  read-write
   STATUS      current
   DESCRIPTION
      "Path: swPort.editConf.vlan.ip.igmp

       Possibilities:
               disabled   (0)
               proxy   (1)
               router   (2)
               v3Router   (5)"
   ::= {er1646v2EthPortSwFVlanEntry 52428800}

er1646v2EthPortSwFVlanIpNN OBJECT-TYPE
   SYNTAX      DisplayString
   MAX-ACCESS  read-write
   STATUS      current
   DESCRIPTION
      "Path: swPort.editConf.vlan.ip.nat"
   ::= {er1646v2EthPortSwFVlanEntry 52101120}

er1646v2EthPortSwFVlanIpVrrp OBJECT-TYPE
   SYNTAX      INTEGER
               {
               disabled (0),
               enabled (1)
               }
   MAX-ACCESS  read-write
   STATUS      current
   DESCRIPTION
      "Path: swPort.editConf.vlan.ip.vrrp

       Possibilities:
               disabled   (0)
               enabled   (1)"
   ::= {er1646v2EthPortSwFVlanEntry 53149696}

er1646v2EthPortSwFVlanIpPimMode OBJECT-TYPE
   SYNTAX      INTEGER
               {
               disabled (0),
               sparse (1),
               passive (2)
               }
   MAX-ACCESS  read-write
   STATUS      current
   DESCRIPTION
      "Path: swPort.editConf.vlan.ip.pim.mode

       Possibilities:
               disabled   (0)
               sparse   (1)
               passive   (2)"
   ::= {er1646v2EthPortSwFVlanEntry 53346560}

er1646v2EthPortSwFVlanIpPimDrPriority OBJECT-TYPE
   SYNTAX      Counter32
   MAX-ACCESS  read-write
   STATUS      current
   DESCRIPTION
      "Path: swPort.editConf.vlan.ip.pim.drPriority

       32 bit unsigned wrappable counter."
   ::= {er1646v2EthPortSwFVlanEntry 53346816}

er1646v2EthPortSwFVlanIpPimHelloTime OBJECT-TYPE
   SYNTAX      TimeTicks
   MAX-ACCESS  read-write
   STATUS      current
   DESCRIPTION
      "Path: swPort.editConf.vlan.ip.pim.helloTime

       Time in centi-second."
   ::= {er1646v2EthPortSwFVlanEntry 53347072}

er1646v2EthPortSwFVlanIpPimPropagationDelay OBJECT-TYPE
   SYNTAX      TimeTicks
   MAX-ACCESS  read-write
   STATUS      current
   DESCRIPTION
      "Path: swPort.editConf.vlan.ip.pim.propagationDelay

       Time in centi-second."
   ::= {er1646v2EthPortSwFVlanEntry 53347328}

er1646v2EthPortSwFVlanIpPimOverrideInterval OBJECT-TYPE
   SYNTAX      TimeTicks
   MAX-ACCESS  read-write
   STATUS      current
   DESCRIPTION
      "Path: swPort.editConf.vlan.ip.pim.overrideInterval

       Time in centi-second."
   ::= {er1646v2EthPortSwFVlanEntry 53347584}

er1646v2EthPortSwFVlanIpPimBsrBorder OBJECT-TYPE
   SYNTAX      INTEGER
               {
               disabled (0),
               enabled (1)
               }
   MAX-ACCESS  read-write
   STATUS      current
   DESCRIPTION
      "Path: swPort.editConf.vlan.ip.pim.bsrBorder

       Possibilities:
               disabled   (0)
               enabled   (1)"
   ::= {er1646v2EthPortSwFVlanEntry 53347840}

er1646v2EthPortSwFVlanIpPimTtlThreshold OBJECT-TYPE
   SYNTAX      Integer32
   MAX-ACCESS  read-write
   STATUS      current
   DESCRIPTION
      "Path: swPort.editConf.vlan.ip.pim.ttlThreshold"
   ::= {er1646v2EthPortSwFVlanEntry 53348096}

er1646v2EthPortSwFVlanIpIMNetworkUnreachable OBJECT-TYPE
   SYNTAX      INTEGER
               {
               disabled (0),
               enabled (1)
               }
   MAX-ACCESS  read-write
   STATUS      current
   DESCRIPTION
      "Path: swPort.editConf.vlan.ip.icmpMessages.networkUnreachable

       Possibilities:
               disabled   (0)
               enabled   (1)"
   ::= {er1646v2EthPortSwFVlanEntry 53412096}

er1646v2EthPortSwFVlanIpIMHostUnreachable OBJECT-TYPE
   SYNTAX      INTEGER
               {
               disabled (0),
               enabled (1)
               }
   MAX-ACCESS  read-write
   STATUS      current
   DESCRIPTION
      "Path: swPort.editConf.vlan.ip.icmpMessages.hostUnreachable

       Possibilities:
               disabled   (0)
               enabled   (1)"
   ::= {er1646v2EthPortSwFVlanEntry 53412352}

er1646v2EthPortSwFVlanIpIMProtocolUnreachable OBJECT-TYPE
   SYNTAX      INTEGER
               {
               disabled (0),
               enabled (1)
               }
   MAX-ACCESS  read-write
   STATUS      current
   DESCRIPTION
      "Path: swPort.editConf.vlan.ip.icmpMessages.protocolUnreachable

       Possibilities:
               disabled   (0)
               enabled   (1)"
   ::= {er1646v2EthPortSwFVlanEntry 53412608}

er1646v2EthPortSwFVlanIpIMPortUnreachable OBJECT-TYPE
   SYNTAX      INTEGER
               {
               disabled (0),
               enabled (1)
               }
   MAX-ACCESS  read-write
   STATUS      current
   DESCRIPTION
      "Path: swPort.editConf.vlan.ip.icmpMessages.portUnreachable

       Possibilities:
               disabled   (0)
               enabled   (1)"
   ::= {er1646v2EthPortSwFVlanEntry 53412864}

er1646v2EthPortSwFVlanIpIMMtuExceeded OBJECT-TYPE
   SYNTAX      INTEGER
               {
               disabled (0),
               enabled (1)
               }
   MAX-ACCESS  read-write
   STATUS      current
   DESCRIPTION
      "Path: swPort.editConf.vlan.ip.icmpMessages.mtuExceeded

       Possibilities:
               disabled   (0)
               enabled   (1)"
   ::= {er1646v2EthPortSwFVlanEntry 53413120}

er1646v2EthPortSwFVlanIpIMAdminProhibited OBJECT-TYPE
   SYNTAX      INTEGER
               {
               disabled (0),
               enabled (1)
               }
   MAX-ACCESS  read-write
   STATUS      current
   DESCRIPTION
      "Path: swPort.editConf.vlan.ip.icmpMessages.adminProhibited

       Possibilities:
               disabled   (0)
               enabled   (1)"
   ::= {er1646v2EthPortSwFVlanEntry 53413376}

er1646v2EthPortSwFVlanIpIMTtlExceeded OBJECT-TYPE
   SYNTAX      INTEGER
               {
               disabled (0),
               enabled (1)
               }
   MAX-ACCESS  read-write
   STATUS      current
   DESCRIPTION
      "Path: swPort.editConf.vlan.ip.icmpMessages.ttlExceeded

       Possibilities:
               disabled   (0)
               enabled   (1)"
   ::= {er1646v2EthPortSwFVlanEntry 53413632}

er1646v2EthPortSwFVlanIpIMRedirect OBJECT-TYPE
   SYNTAX      INTEGER
               {
               disabled (0),
               enabled (1)
               }
   MAX-ACCESS  read-write
   STATUS      current
   DESCRIPTION
      "Path: swPort.editConf.vlan.ip.icmpMessages.redirect

       Possibilities:
               disabled   (0)
               enabled   (1)"
   ::= {er1646v2EthPortSwFVlanEntry 53413888}

er1646v2EthPortSwFVlanIpV6VrfRouter OBJECT-TYPE
   SYNTAX      DisplayString
   MAX-ACCESS  read-write
   STATUS      current
   DESCRIPTION
      "Path: swPort.editConf.vlan.ipV6.vrfRouter"
   ::= {er1646v2EthPortSwFVlanEntry 704708608}

er1646v2EthPortSwFVlanIpV6AddrAutoConfigNrDupAddrDetects OBJECT-TYPE
   SYNTAX      Integer32
   MAX-ACCESS  read-write
   STATUS      current
   DESCRIPTION
      "Path: swPort.editConf.vlan.ipV6.addrAutoConfig.nrDupAddrDetects"
   ::= {er1646v2EthPortSwFVlanEntry 704905472}

er1646v2EthPortSwFVlanIpV6AddrAutoConfigAcceptRa OBJECT-TYPE
   SYNTAX      INTEGER
               {
               disabled (0),
               enabled (1)
               }
   MAX-ACCESS  read-write
   STATUS      current
   DESCRIPTION
      "Path: swPort.editConf.vlan.ipV6.addrAutoConfig.acceptRa

       Possibilities:
               disabled   (0)
               enabled   (1)"
   ::= {er1646v2EthPortSwFVlanEntry 704905728}

er1646v2EthPortSwFVlanIpV6AddrAutoConfigAcceptRaRdnss OBJECT-TYPE
   SYNTAX      INTEGER
               {
               disabled (0),
               enabled (1)
               }
   MAX-ACCESS  read-write
   STATUS      current
   DESCRIPTION
      "Path: swPort.editConf.vlan.ipV6.addrAutoConfig.acceptRaRdnss

       Possibilities:
               disabled   (0)
               enabled   (1)"
   ::= {er1646v2EthPortSwFVlanEntry 704905984}

er1646v2EthPortSwFVlanIpV6AddrAutoConfigAcceptRaDnssl OBJECT-TYPE
   SYNTAX      INTEGER
               {
               disabled (0),
               enabled (1)
               }
   MAX-ACCESS  read-write
   STATUS      current
   DESCRIPTION
      "Path: swPort.editConf.vlan.ipV6.addrAutoConfig.acceptRaDnssl

       Possibilities:
               disabled   (0)
               enabled   (1)"
   ::= {er1646v2EthPortSwFVlanEntry 704906240}

er1646v2EthPortSwFVlanIpV6DefaultRoute OBJECT-TYPE
   SYNTAX      INTEGER
               {
               disabled (0),
               enabled (1)
               }
   MAX-ACCESS  read-write
   STATUS      current
   DESCRIPTION
      "Path: swPort.editConf.vlan.ipV6.defaultRoute

       Possibilities:
               disabled   (0)
               enabled   (1)"
   ::= {er1646v2EthPortSwFVlanEntry 704970752}

er1646v2EthPortSwFVlanIpV6RaSend OBJECT-TYPE
   SYNTAX      INTEGER
               {
               disabled (0),
               enabled (1)
               }
   MAX-ACCESS  read-write
   STATUS      current
   DESCRIPTION
      "Path: swPort.editConf.vlan.ipV6.ra.send

       Possibilities:
               disabled   (0)
               enabled   (1)"
   ::= {er1646v2EthPortSwFVlanEntry 705036544}

er1646v2EthPortSwFVlanIpV6RaMinInterval OBJECT-TYPE
   SYNTAX      TimeTicks
   MAX-ACCESS  read-write
   STATUS      current
   DESCRIPTION
      "Path: swPort.editConf.vlan.ipV6.ra.minInterval

       Time in centi-second."
   ::= {er1646v2EthPortSwFVlanEntry 705036800}

er1646v2EthPortSwFVlanIpV6RaMaxInterval OBJECT-TYPE
   SYNTAX      TimeTicks
   MAX-ACCESS  read-write
   STATUS      current
   DESCRIPTION
      "Path: swPort.editConf.vlan.ipV6.ra.maxInterval

       Time in centi-second."
   ::= {er1646v2EthPortSwFVlanEntry 705037056}

er1646v2EthPortSwFVlanIpV6RaManagedFlag OBJECT-TYPE
   SYNTAX      INTEGER
               {
               disabled (0),
               enabled (1)
               }
   MAX-ACCESS  read-write
   STATUS      current
   DESCRIPTION
      "Path: swPort.editConf.vlan.ipV6.ra.managedFlag

       Possibilities:
               disabled   (0)
               enabled   (1)"
   ::= {er1646v2EthPortSwFVlanEntry 705037312}

er1646v2EthPortSwFVlanIpV6RaOtherConfFlag OBJECT-TYPE
   SYNTAX      INTEGER
               {
               disabled (0),
               enabled (1)
               }
   MAX-ACCESS  read-write
   STATUS      current
   DESCRIPTION
      "Path: swPort.editConf.vlan.ipV6.ra.otherConfFlag

       Possibilities:
               disabled   (0)
               enabled   (1)"
   ::= {er1646v2EthPortSwFVlanEntry 705037568}

er1646v2EthPortSwFVlanIpV6RaLinkMtu OBJECT-TYPE
   SYNTAX      Integer32
   MAX-ACCESS  read-write
   STATUS      current
   DESCRIPTION
      "Path: swPort.editConf.vlan.ipV6.ra.linkMtu"
   ::= {er1646v2EthPortSwFVlanEntry 705037824}

er1646v2EthPortSwFVlanIpV6RaReachableTime OBJECT-TYPE
   SYNTAX      TimeTicks
   MAX-ACCESS  read-write
   STATUS      current
   DESCRIPTION
      "Path: swPort.editConf.vlan.ipV6.ra.reachableTime

       Time in centi-second."
   ::= {er1646v2EthPortSwFVlanEntry 705038080}

er1646v2EthPortSwFVlanIpV6RaRetransmitTime OBJECT-TYPE
   SYNTAX      TimeTicks
   MAX-ACCESS  read-write
   STATUS      current
   DESCRIPTION
      "Path: swPort.editConf.vlan.ipV6.ra.retransmitTime

       Time in centi-second."
   ::= {er1646v2EthPortSwFVlanEntry 705038336}

er1646v2EthPortSwFVlanIpV6RaHopLimit OBJECT-TYPE
   SYNTAX      Integer32
   MAX-ACCESS  read-write
   STATUS      current
   DESCRIPTION
      "Path: swPort.editConf.vlan.ipV6.ra.hopLimit"
   ::= {er1646v2EthPortSwFVlanEntry 705038592}

er1646v2EthPortSwFVlanIpV6RaDefaultLifeTime OBJECT-TYPE
   SYNTAX      TimeTicks
   MAX-ACCESS  read-write
   STATUS      current
   DESCRIPTION
      "Path: swPort.editConf.vlan.ipV6.ra.defaultLifeTime

       Time in centi-second."
   ::= {er1646v2EthPortSwFVlanEntry 705038848}

er1646v2EthPortSwFVlanIpV6RaDnsOptionsRdnssLifeTime OBJECT-TYPE
   SYNTAX      TimeTicks
   MAX-ACCESS  read-write
   STATUS      current
   DESCRIPTION
      "Path: swPort.editConf.vlan.ipV6.ra.dnsOptions.rdnss.lifeTime

       Time in centi-second."
   ::= {er1646v2EthPortSwFVlanEntry 705039140}

er1646v2EthPortSwFVlanIpV6RaDnsOptionsRdnssImportServers OBJECT-TYPE
   SYNTAX      INTEGER
               {
               disabled (0),
               enabled (1)
               }
   MAX-ACCESS  read-write
   STATUS      current
   DESCRIPTION
      "Path: swPort.editConf.vlan.ipV6.ra.dnsOptions.rdnss.importServers

       Possibilities:
               disabled   (0)
               enabled   (1)"
   ::= {er1646v2EthPortSwFVlanEntry 705039148}

er1646v2EthPortSwFVlanIpV6RaDnsOptionsDnsslLifeTime OBJECT-TYPE
   SYNTAX      TimeTicks
   MAX-ACCESS  read-write
   STATUS      current
   DESCRIPTION
      "Path: swPort.editConf.vlan.ipV6.ra.dnsOptions.dnssl.lifeTime

       Time in centi-second."
   ::= {er1646v2EthPortSwFVlanEntry 705039172}

er1646v2EthPortSwFVlanIpV6RaDnsOptionsDnsslImportDomains OBJECT-TYPE
   SYNTAX      INTEGER
               {
               disabled (0),
               enabled (1)
               }
   MAX-ACCESS  read-write
   STATUS      current
   DESCRIPTION
      "Path: swPort.editConf.vlan.ipV6.ra.dnsOptions.dnssl.importDomains

       Possibilities:
               disabled   (0)
               enabled   (1)"
   ::= {er1646v2EthPortSwFVlanEntry 705039180}

er1646v2EthPortSwFVlanIpV6RsSend OBJECT-TYPE
   SYNTAX      INTEGER
               {
               disabled (0),
               enabled (1)
               }
   MAX-ACCESS  read-write
   STATUS      current
   DESCRIPTION
      "Path: swPort.editConf.vlan.ipV6.rs.send

       Possibilities:
               disabled   (0)
               enabled   (1)"
   ::= {er1646v2EthPortSwFVlanEntry 705954048}

er1646v2EthPortSwFVlanIpV6RsMaxRandomDelay OBJECT-TYPE
   SYNTAX      TimeTicks
   MAX-ACCESS  read-write
   STATUS      current
   DESCRIPTION
      "Path: swPort.editConf.vlan.ipV6.rs.maxRandomDelay

       Time in centi-second."
   ::= {er1646v2EthPortSwFVlanEntry 705954304}

er1646v2EthPortSwFVlanIpV6RsInterval OBJECT-TYPE
   SYNTAX      TimeTicks
   MAX-ACCESS  read-write
   STATUS      current
   DESCRIPTION
      "Path: swPort.editConf.vlan.ipV6.rs.interval

       Time in centi-second."
   ::= {er1646v2EthPortSwFVlanEntry 705954560}

er1646v2EthPortSwFVlanIpV6RsMaxSolicitations OBJECT-TYPE
   SYNTAX      Integer32
   MAX-ACCESS  read-write
   STATUS      current
   DESCRIPTION
      "Path: swPort.editConf.vlan.ipV6.rs.maxSolicitations"
   ::= {er1646v2EthPortSwFVlanEntry 705954816}

er1646v2EthPortSwFVlanIpV6TrafficPolicyInbound OBJECT-TYPE
   SYNTAX      DisplayString
   MAX-ACCESS  read-write
   STATUS      current
   DESCRIPTION
      "Path: swPort.editConf.vlan.ipV6.trafficPolicy.inbound"
   ::= {er1646v2EthPortSwFVlanEntry 705364224}

er1646v2EthPortSwFVlanIpV6TrafficPolicyOutbound OBJECT-TYPE
   SYNTAX      DisplayString
   MAX-ACCESS  read-write
   STATUS      current
   DESCRIPTION
      "Path: swPort.editConf.vlan.ipV6.trafficPolicy.outbound"
   ::= {er1646v2EthPortSwFVlanEntry 705364480}

er1646v2EthPortSwFVlanIpV6FirewallZone OBJECT-TYPE
   SYNTAX      DisplayString
   MAX-ACCESS  read-write
   STATUS      current
   DESCRIPTION
      "Path: swPort.editConf.vlan.ipV6.firewall.zone"
   ::= {er1646v2EthPortSwFVlanEntry 705429760}

er1646v2EthPortSwFVlanIpV6DhcpClientAddrAC OBJECT-TYPE
   SYNTAX      INTEGER
               {
               disabled (0),
               enabled (1)
               }
   MAX-ACCESS  read-write
   STATUS      current
   DESCRIPTION
      "Path: swPort.editConf.vlan.ipV6.dhcp.client.addrAutoConfig

       Possibilities:
               disabled   (0)
               enabled   (1)"
   ::= {er1646v2EthPortSwFVlanEntry 705307648}

er1646v2EthPortSwFVlanIpV6DhcpClientPrDelMode OBJECT-TYPE
   SYNTAX      INTEGER
               {
               disabled (0),
               enabled (1)
               }
   MAX-ACCESS  read-write
   STATUS      current
   DESCRIPTION
      "Path: swPort.editConf.vlan.ipV6.dhcp.client.pd.mode

       Possibilities:
               disabled   (0)
               enabled   (1)"
   ::= {er1646v2EthPortSwFVlanEntry 705308676}

er1646v2EthPortSwFVlanIpV6DhcpClientPrDelPool OBJECT-TYPE
   SYNTAX      DisplayString
   MAX-ACCESS  read-write
   STATUS      current
   DESCRIPTION
      "Path: swPort.editConf.vlan.ipV6.dhcp.client.pd.pool"
   ::= {er1646v2EthPortSwFVlanEntry 705308680}

er1646v2EthPortSwFVlanIpV6DhcpClientPrDelPdExclOpt OBJECT-TYPE
   SYNTAX      INTEGER
               {
               disabled (0),
               enabled (1)
               }
   MAX-ACCESS  read-write
   STATUS      current
   DESCRIPTION
      "Path: swPort.editConf.vlan.ipV6.dhcp.client.pd.pdExclOpt

       Possibilities:
               disabled   (0)
               enabled   (1)"
   ::= {er1646v2EthPortSwFVlanEntry 705308684}

er1646v2EthPortSwFVlanIpV6DhcpClientDnsServerPref OBJECT-TYPE
   SYNTAX      Integer32
   MAX-ACCESS  read-write
   STATUS      current
   DESCRIPTION
      "Path: swPort.editConf.vlan.ipV6.dhcp.client.dns.serverPref"
   ::= {er1646v2EthPortSwFVlanEntry 705310724}

er1646v2EthPortSwFVlanIpV6DhcpClientRapidCommit OBJECT-TYPE
   SYNTAX      INTEGER
               {
               disabled (0),
               enabled (1)
               }
   MAX-ACCESS  read-write
   STATUS      current
   DESCRIPTION
      "Path: swPort.editConf.vlan.ipV6.dhcp.client.rapidCommit

       Possibilities:
               disabled   (0)
               enabled   (1)"
   ::= {er1646v2EthPortSwFVlanEntry 705309696}

er1646v2EthPortSwFVlanIpV6DhcpClientTimersSolTimeOut OBJECT-TYPE
   SYNTAX      TimeTicks
   MAX-ACCESS  read-write
   STATUS      current
   DESCRIPTION
      "Path: swPort.editConf.vlan.ipV6.dhcp.client.timers.solTimeOut

       Time in centi-second."
   ::= {er1646v2EthPortSwFVlanEntry 705311748}

er1646v2EthPortSwFVlanIpV6DhcpClientTimersSolMaxRt OBJECT-TYPE
   SYNTAX      TimeTicks
   MAX-ACCESS  read-write
   STATUS      current
   DESCRIPTION
      "Path: swPort.editConf.vlan.ipV6.dhcp.client.timers.solMaxRt

       Time in centi-second."
   ::= {er1646v2EthPortSwFVlanEntry 705311752}

er1646v2EthPortSwFVlanIpV6DhcpClientTimersInfoRefresh OBJECT-TYPE
   SYNTAX      TimeTicks
   MAX-ACCESS  read-write
   STATUS      current
   DESCRIPTION
      "Path: swPort.editConf.vlan.ipV6.dhcp.client.timers.infoRefresh

       Time in centi-second."
   ::= {er1646v2EthPortSwFVlanEntry 705311756}

er1646v2EthPortSwFVlanIpV6DhcpServerMode OBJECT-TYPE
   SYNTAX      INTEGER
               {
               disabled (0),
               enabled (1)
               }
   MAX-ACCESS  read-write
   STATUS      current
   DESCRIPTION
      "Path: swPort.editConf.vlan.ipV6.dhcp.server.mode

       Possibilities:
               disabled   (0)
               enabled   (1)"
   ::= {er1646v2EthPortSwFVlanEntry 705315840}

er1646v2EthPortSwFVlanIpV6DhcpServerPreference OBJECT-TYPE
   SYNTAX      Integer32
   MAX-ACCESS  read-write
   STATUS      current
   DESCRIPTION
      "Path: swPort.editConf.vlan.ipV6.dhcp.server.preference"
   ::= {er1646v2EthPortSwFVlanEntry 705316864}

er1646v2EthPortSwFVlanIpV6DhcpServerPool OBJECT-TYPE
   SYNTAX      DisplayString
   MAX-ACCESS  read-write
   STATUS      current
   DESCRIPTION
      "Path: swPort.editConf.vlan.ipV6.dhcp.server.pool"
   ::= {er1646v2EthPortSwFVlanEntry 705317888}

er1646v2EthPortSwFVlanIpV6DhcpServerRapidCommit OBJECT-TYPE
   SYNTAX      INTEGER
               {
               disabled (0),
               enabled (1)
               }
   MAX-ACCESS  read-write
   STATUS      current
   DESCRIPTION
      "Path: swPort.editConf.vlan.ipV6.dhcp.server.rapidCommit

       Possibilities:
               disabled   (0)
               enabled   (1)"
   ::= {er1646v2EthPortSwFVlanEntry 705318912}

er1646v2EthPortSwFVlanIpV6DhcpServerTimersInfoRefresh OBJECT-TYPE
   SYNTAX      TimeTicks
   MAX-ACCESS  read-write
   STATUS      current
   DESCRIPTION
      "Path: swPort.editConf.vlan.ipV6.dhcp.server.timers.infoRefresh

       Time in centi-second."
   ::= {er1646v2EthPortSwFVlanEntry 705319940}

er1646v2EthPortSwFVlanIpV6DhcpRelayMode OBJECT-TYPE
   SYNTAX      INTEGER
               {
               disabled (0),
               enabled (1)
               }
   MAX-ACCESS  read-write
   STATUS      current
   DESCRIPTION
      "Path: swPort.editConf.vlan.ipV6.dhcp.relay.mode

       Possibilities:
               disabled   (0)
               enabled   (1)"
   ::= {er1646v2EthPortSwFVlanEntry 705323040}

er1646v2EthPortSwFVlanIpV6SendRedirect OBJECT-TYPE
   SYNTAX      INTEGER
               {
               disabled (0),
               enabled (1)
               }
   MAX-ACCESS  read-write
   STATUS      current
   DESCRIPTION
      "Path: swPort.editConf.vlan.ipV6.sendRedirect

       Possibilities:
               disabled   (0)
               enabled   (1)"
   ::= {er1646v2EthPortSwFVlanEntry 705101824}

er1646v2EthPortSwFVlanIpV6LinkMtu OBJECT-TYPE
   SYNTAX      Integer32
   MAX-ACCESS  read-write
   STATUS      current
   DESCRIPTION
      "Path: swPort.editConf.vlan.ipV6.linkMtu"
   ::= {er1646v2EthPortSwFVlanEntry 705167360}

er1646v2EthPortSwFVlanIpV6InterfaceId OBJECT-TYPE
   SYNTAX      OCTET STRING
   MAX-ACCESS  read-write
   STATUS      current
   DESCRIPTION
      "Path: swPort.editConf.vlan.ipV6.interfaceId"
   ::= {er1646v2EthPortSwFVlanEntry 705232896}

er1646v2EthPortSwFVlanIpV6MF OBJECT-TYPE
   SYNTAX      Integer32
   MAX-ACCESS  read-write
   STATUS      current
   DESCRIPTION
      "Path: swPort.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwFVlanEntry 705757184}

er1646v2EthPortSwFVlanIpV6IcmpMessagesNoRoute OBJECT-TYPE
   SYNTAX      INTEGER
               {
               disabled (0),
               enabled (1)
               }
   MAX-ACCESS  read-write
   STATUS      current
   DESCRIPTION
      "Path: swPort.editConf.vlan.ipV6.icmpMessages.noRoute

       Possibilities:
               disabled   (0)
               enabled   (1)"
   ::= {er1646v2EthPortSwFVlanEntry 705822976}

er1646v2EthPortSwFVlanIpV6IcmpMessagesBeyondScope OBJECT-TYPE
   SYNTAX      INTEGER
               {
               disabled (0),
               enabled (1)
               }
   MAX-ACCESS  read-write
   STATUS      current
   DESCRIPTION
      "Path: swPort.editConf.vlan.ipV6.icmpMessages.beyondScope

       Possibilities:
               disabled   (0)
               enabled   (1)"
   ::= {er1646v2EthPortSwFVlanEntry 705823488}

er1646v2EthPortSwFVlanIpV6IcmpMessagesAddressUnreachable OBJECT-TYPE
   SYNTAX      INTEGER
               {
               disabled (0),
               enabled (1)
               }
   MAX-ACCESS  read-write
   STATUS      current
   DESCRIPTION
      "Path: swPort.editConf.vlan.ipV6.icmpMessages.addressUnreachable

       Possibilities:
               disabled   (0)
               enabled   (1)"
   ::= {er1646v2EthPortSwFVlanEntry 705823744}

er1646v2EthPortSwFVlanIpV6IcmpMessagesPortUnreachable OBJECT-TYPE
   SYNTAX      INTEGER
               {
               disabled (0),
               enabled (1)
               }
   MAX-ACCESS  read-write
   STATUS      current
   DESCRIPTION
      "Path: swPort.editConf.vlan.ipV6.icmpMessages.portUnreachable

       Possibilities:
               disabled   (0)
               enabled   (1)"
   ::= {er1646v2EthPortSwFVlanEntry 705824000}

er1646v2EthPortSwFVlanIpV6IcmpMessagesPacketTooBig OBJECT-TYPE
   SYNTAX      INTEGER
               {
               disabled (0),
               enabled (1)
               }
   MAX-ACCESS  read-write
   STATUS      current
   DESCRIPTION
      "Path: swPort.editConf.vlan.ipV6.icmpMessages.packetTooBig

       Possibilities:
               disabled   (0)
               enabled   (1)"
   ::= {er1646v2EthPortSwFVlanEntry 705825280}

er1646v2EthPortSwFVlanIpV6IcmpMessagesHopLimitExceeded OBJECT-TYPE
   SYNTAX      INTEGER
               {
               disabled (0),
               enabled (1)
               }
   MAX-ACCESS  read-write
   STATUS      current
   DESCRIPTION
      "Path: swPort.editConf.vlan.ipV6.icmpMessages.hopLimitExceeded

       Possibilities:
               disabled   (0)
               enabled   (1)"
   ::= {er1646v2EthPortSwFVlanEntry 705827840}

er1646v2EthPortSwFVlanIpV6IcmpMessagesFragTimeExceeded OBJECT-TYPE
   SYNTAX      INTEGER
               {
               disabled (0),
               enabled (1)
               }
   MAX-ACCESS  read-write
   STATUS      current
   DESCRIPTION
      "Path: swPort.editConf.vlan.ipV6.icmpMessages.fragTimeExceeded

       Possibilities:
               disabled   (0)
               enabled   (1)"
   ::= {er1646v2EthPortSwFVlanEntry 705828096}

er1646v2EthPortSwFVlanIpV6IcmpMessagesHeaderFieldErr OBJECT-TYPE
   SYNTAX      INTEGER
               {
               disabled (0),
               enabled (1)
               }
   MAX-ACCESS  read-write
   STATUS      current
   DESCRIPTION
      "Path: swPort.editConf.vlan.ipV6.icmpMessages.headerFieldErr

       Possibilities:
               disabled   (0)
               enabled   (1)"
   ::= {er1646v2EthPortSwFVlanEntry 705830400}

er1646v2EthPortSwFVlanIpV6IcmpMessagesOptionUnrecognized OBJECT-TYPE
   SYNTAX      INTEGER
               {
               disabled (0),
               enabled (1)
               }
   MAX-ACCESS  read-write
   STATUS      current
   DESCRIPTION
      "Path: swPort.editConf.vlan.ipV6.icmpMessages.optionUnrecognized

       Possibilities:
               disabled   (0)
               enabled   (1)"
   ::= {er1646v2EthPortSwFVlanEntry 705830912}

er1646v2EthPortSwFVlanIpV6IcmpMessagesRedirect OBJECT-TYPE
   SYNTAX      INTEGER
               {
               disabled (0),
               enabled (1)
               }
   MAX-ACCESS  read-write
   STATUS      current
   DESCRIPTION
      "Path: swPort.editConf.vlan.ipV6.icmpMessages.redirect

       Possibilities:
               disabled   (0)
               enabled   (1)"
   ::= {er1646v2EthPortSwFVlanEntry 705832960}

er1646v2EthPortSwFVlanBridgingAccList OBJECT-TYPE
   SYNTAX      DisplayString
   MAX-ACCESS  read-write
   STATUS      current
   DESCRIPTION
      "Path: swPort.editConf.vlan.bridging.accessList"
   ::= {er1646v2EthPortSwFVlanEntry 453246976}

er1646v2EthPortSwFVlanBridgingInACL OBJECT-TYPE
   SYNTAX      DisplayString
   MAX-ACCESS  read-write
   STATUS      current
   DESCRIPTION
      "Path: swPort.editConf.vlan.bridging.inAccessList"
   ::= {er1646v2EthPortSwFVlanEntry 456916992}

er1646v2EthPortSwFVlanBridgingTp OBJECT-TYPE
   SYNTAX      DisplayString
   MAX-ACCESS  read-write
   STATUS      current
   DESCRIPTION
      "Path: swPort.editConf.vlan.bridging.trafficPolicy"
   ::= {er1646v2EthPortSwFVlanEntry 454295552}

er1646v2EthPortSwFVlanBridgingBrGrp OBJECT-TYPE
   SYNTAX      DisplayString
   MAX-ACCESS  read-write
   STATUS      current
   DESCRIPTION
      "Path: swPort.editConf.vlan.bridging.bridgeGroup"
   ::= {er1646v2EthPortSwFVlanEntry 454819840}

er1646v2EthPortSwFVlanBridgingLimBC OBJECT-TYPE
   SYNTAX      INTEGER
               {
               disabled (0),
               enabled (1)
               }
   MAX-ACCESS  read-write
   STATUS      current
   DESCRIPTION
      "Path: swPort.editConf.vlan.bridging.limitBroadcasts

       Possibilities:
               disabled   (0)
               enabled   (1)"
   ::= {er1646v2EthPortSwFVlanEntry 455081984}

er1646v2EthPortSwFVlanBridgingPrivateMode OBJECT-TYPE
   SYNTAX      INTEGER
               {
               disabled (0),
               enabled (1)
               }
   MAX-ACCESS  read-write
   STATUS      current
   DESCRIPTION
      "Path: swPort.editConf.vlan.bridging.privateMode

       Possibilities:
               disabled   (0)
               enabled   (1)"
   ::= {er1646v2EthPortSwFVlanEntry 459538432}

er1646v2EthPortSwFVlanBridgingLearning OBJECT-TYPE
   SYNTAX      INTEGER
               {
               disabled (0),
               enabled (1)
               }
   MAX-ACCESS  read-write
   STATUS      current
   DESCRIPTION
      "Path: swPort.editConf.vlan.bridging.learning

       Possibilities:
               disabled   (0)
               enabled   (1)"
   ::= {er1646v2EthPortSwFVlanEntry 456130560}

er1646v2EthPortSwFVlanBridgingMaxCacheSize OBJECT-TYPE
   SYNTAX      INTEGER
               {
               unlimited (0)
               }
   MAX-ACCESS  read-write
   STATUS      current
   DESCRIPTION
      "Path: swPort.editConf.vlan.bridging.maxCacheSize

       Possibilities:
               unlimited   (0)"
   ::= {er1646v2EthPortSwFVlanEntry 456392704}

er1646v2EthPortSwFVlanBridgingRelearnDropOnRelearn OBJECT-TYPE
   SYNTAX      INTEGER
               {
               disabled (0),
               enabled (1)
               }
   MAX-ACCESS  read-write
   STATUS      current
   DESCRIPTION
      "Path: swPort.editConf.vlan.bridging.relearn.dropOnRelearn

       Possibilities:
               disabled   (0)
               enabled   (1)"
   ::= {er1646v2EthPortSwFVlanEntry 456655872}

er1646v2EthPortSwFVlanBridgingRelearnShutdownThreshold OBJECT-TYPE
   SYNTAX      Integer32
   MAX-ACCESS  read-write
   STATUS      current
   DESCRIPTION
      "Path: swPort.editConf.vlan.bridging.relearn.shutdownThreshold"
   ::= {er1646v2EthPortSwFVlanEntry 456656896}

er1646v2EthPortSwFVlanBridgingRelearnShutdownTime OBJECT-TYPE
   SYNTAX      TimeTicks
   MAX-ACCESS  read-write
   STATUS      current
   DESCRIPTION
      "Path: swPort.editConf.vlan.bridging.relearn.shutdownTime

       Time in centi-second."
   ::= {er1646v2EthPortSwFVlanEntry 456657920}

er1646v2EthPortSwFVlanBridgingRelearnLoopDetection OBJECT-TYPE
   SYNTAX      INTEGER
               {
               disabled (0),
               passive (1),
               active (2)
               }
   MAX-ACCESS  read-write
   STATUS      current
   DESCRIPTION
      "Path: swPort.editConf.vlan.bridging.relearn.loopDetection

       Possibilities:
               disabled   (0)
               passive   (1)
               active   (2)"
   ::= {er1646v2EthPortSwFVlanEntry 456658944}

er1646v2EthPortSwFVlanBridgingRelearnLoopDetectionInterval OBJECT-TYPE
   SYNTAX      TimeTicks
   MAX-ACCESS  read-write
   STATUS      current
   DESCRIPTION
      "Path: swPort.editConf.vlan.bridging.relearn.loopDetectionInterval

       Time in centi-second."
   ::= {er1646v2EthPortSwFVlanEntry 456659968}

er1646v2EthPortSwFVlanBridgingVlanMemberShip OBJECT-TYPE
   SYNTAX      INTEGER
               {
               all (0),
               none (1),
               grouped (2)
               }
   MAX-ACCESS  read-write
   STATUS      current
   DESCRIPTION
      "Path: swPort.editConf.vlan.bridging.vlanMemberShip

       Possibilities:
               all   (0)
               none   (1)
               grouped   (2)"
   ::= {er1646v2EthPortSwFVlanEntry 457965568}

er1646v2EthPortSwFVlanBridgingVlTUntaggedAction OBJECT-TYPE
   SYNTAX      INTEGER
               {
               discard (0),
               accept (1),
               tag (2)
               }
   MAX-ACCESS  read-write
   STATUS      current
   DESCRIPTION
      "Path: swPort.editConf.vlan.bridging.vlanTagging.untagged.action

       Possibilities:
               discard   (0)
               accept   (1)
               tag   (2)"
   ::= {er1646v2EthPortSwFVlanEntry 459055104}

er1646v2EthPortSwFVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.untagged.tagInfo.tpid

       Possibilities:
               dot1Q   (33024)
               dot1ad   (34984)
               0x9100   (37120)
               0x9200   (37376)
               0x9300   (37632)"
   ::= {er1646v2EthPortSwFVlanEntry 459059712}

er1646v2EthPortSwFVlanBridgingVlTUntaggedTagInfoVid OBJECT-TYPE
   SYNTAX      Integer32
   MAX-ACCESS  read-write
   STATUS      current
   DESCRIPTION
      "Path: swPort.editConf.vlan.bridging.vlanTagging.untagged.tagInfo.vid"
   ::= {er1646v2EthPortSwFVlanEntry 459060224}

er1646v2EthPortSwFVlanBridgingVlTUnknownVlansAction OBJECT-TYPE
   SYNTAX      INTEGER
               {
               discard (0),
               accept (1),
               tag (2)
               }
   MAX-ACCESS  read-write
   STATUS      current
   DESCRIPTION
      "Path: swPort.editConf.vlan.bridging.vlanTagging.unknownVlans.action

       Possibilities:
               discard   (0)
               accept   (1)
               tag   (2)"
   ::= {er1646v2EthPortSwFVlanEntry 459120640}

er1646v2EthPortSwFVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.unknownVlans.tagInfo.tpid

       Possibilities:
               dot1Q   (33024)
               dot1ad   (34984)
               0x9100   (37120)
               0x9200   (37376)
               0x9300   (37632)"
   ::= {er1646v2EthPortSwFVlanEntry 459125248}

er1646v2EthPortSwFVlanBridgingVlTUnknownVlansTagInfoVid OBJECT-TYPE
   SYNTAX      Integer32
   MAX-ACCESS  read-write
   STATUS      current
   DESCRIPTION
      "Path: swPort.editConf.vlan.bridging.vlanTagging.unknownVlans.tagInfo.vid"
   ::= {er1646v2EthPortSwFVlanEntry 459125760}

er1646v2EthPortSwFVlanBridgingDot1adType OBJECT-TYPE
   SYNTAX      INTEGER
               {
               slOPTg (0),
               cPort (4),
               sPort (1),
               nni (2)
               }
   MAX-ACCESS  read-write
   STATUS      current
   DESCRIPTION
      "Path: swPort.editConf.vlan.bridging.dot1ad.type

       Possibilities:
               <OPT>   (0)
               cPort   (4)
               sPort   (1)
               nni   (2)"
   ::= {er1646v2EthPortSwFVlanEntry 460850176}

er1646v2EthPortSwFVlanBridgingPriority OBJECT-TYPE
   SYNTAX      Integer32
   MAX-ACCESS  read-write
   STATUS      current
   DESCRIPTION
      "Path: swPort.editConf.vlan.bridging.priority"
   ::= {er1646v2EthPortSwFVlanEntry 453509120}

er1646v2EthPortSwFVlanBridgingPathCost OBJECT-TYPE
   SYNTAX      Integer32
   MAX-ACCESS  read-write
   STATUS      current
   DESCRIPTION
      "Path: swPort.editConf.vlan.bridging.pathCost"
   ::= {er1646v2EthPortSwFVlanEntry 453771264}

er1646v2EthPortSwFVlanBridgingInternalPathCost OBJECT-TYPE
   SYNTAX      Integer32
   MAX-ACCESS  read-write
   STATUS      current
   DESCRIPTION
      "Path: swPort.editConf.vlan.bridging.internalPathCost"
   ::= {er1646v2EthPortSwFVlanEntry 457703424}

er1646v2EthPortSwFVlanBridgingTCD OBJECT-TYPE
   SYNTAX      INTEGER
               {
               disabled (0),
               enabled (1)
               }
   MAX-ACCESS  read-write
   STATUS      current
   DESCRIPTION
      "Path: swPort.editConf.vlan.bridging.topologyChangeDetection

       Possibilities:
               disabled   (0)
               enabled   (1)"
   ::= {er1646v2EthPortSwFVlanEntry 454033408}

er1646v2EthPortSwFVlanBridgingRestrictedRole OBJECT-TYPE
   SYNTAX      INTEGER
               {
               disabled (0),
               enabled (1)
               }
   MAX-ACCESS  read-write
   STATUS      current
   DESCRIPTION
      "Path: swPort.editConf.vlan.bridging.restrictedRole

       Possibilities:
               disabled   (0)
               enabled   (1)"
   ::= {er1646v2EthPortSwFVlanEntry 458227712}

er1646v2EthPortSwFVlanBridgingAdminEdge OBJECT-TYPE
   SYNTAX      INTEGER
               {
               disabled (0),
               enabled (1)
               }
   MAX-ACCESS  read-write
   STATUS      current
   DESCRIPTION
      "Path: swPort.editConf.vlan.bridging.adminEdge

       Possibilities:
               disabled   (0)
               enabled   (1)"
   ::= {er1646v2EthPortSwFVlanEntry 457179136}

er1646v2EthPortSwFVlanBridgingOamMacDeviceMac OBJECT-TYPE
   SYNTAX      DisplayString
   MAX-ACCESS  read-write
   STATUS      current
   DESCRIPTION
      "Path: swPort.editConf.vlan.bridging.ethOam.macAddress.deviceMac"
   ::= {er1646v2EthPortSwFVlanEntry 458506496}

er1646v2EthPortSwFVlanBridgingOamMacUserMac OBJECT-TYPE
   SYNTAX      OCTET STRING
   MAX-ACCESS  read-write
   STATUS      current
   DESCRIPTION
      "Path: swPort.editConf.vlan.bridging.ethOam.macAddress.userMac

       MAC address."
   ::= {er1646v2EthPortSwFVlanEntry 458506368}

er1646v2EthPortSwFVlanBridgingOamMacBridgeMac OBJECT-TYPE
   SYNTAX      DisplayString
   MAX-ACCESS  read-write
   STATUS      current
   DESCRIPTION
      "Path: swPort.editConf.vlan.bridging.ethOam.macAddress.bridgeMac"
   ::= {er1646v2EthPortSwFVlanEntry 458506432}

er1646v2EthPortSwFVlanBridgingMgmtInline OBJECT-TYPE
   SYNTAX      INTEGER
               {
               disabled (0),
               enabled (1)
               }
   MAX-ACCESS  read-write
   STATUS      current
   DESCRIPTION
      "Path: swPort.editConf.vlan.bridging.mgmtInline

       Possibilities:
               disabled   (0)
               enabled   (1)"
   ::= {er1646v2EthPortSwFVlanEntry 458752000}

er1646v2EthPortSwFVlanBridgingL2ptMode OBJECT-TYPE
   SYNTAX      INTEGER
               {
               disabled (0),
               enabled (1)
               }
   MAX-ACCESS  read-write
   STATUS      current
   DESCRIPTION
      "Path: swPort.editConf.vlan.bridging.l2ProtTunnel.mode

       Possibilities:
               disabled   (0)
               enabled   (1)"
   ::= {er1646v2EthPortSwFVlanEntry 459292672}

er1646v2EthPortSwFVlanBridgingL2ptProtocols OBJECT-TYPE
   SYNTAX      Integer32
   MAX-ACCESS  read-write
   STATUS      current
   DESCRIPTION
      "Path: swPort.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EthPortSwFVlanEntry 459309056}

er1646v2EthPortSwFVlanBridgingL2ptDestMac OBJECT-TYPE
   SYNTAX      OCTET STRING
   MAX-ACCESS  read-write
   STATUS      current
   DESCRIPTION
      "Path: swPort.editConf.vlan.bridging.l2ProtTunnel.destinationMac

       MAC address."
   ::= {er1646v2EthPortSwFVlanEntry 459325440}

er1646v2EthPortSwFVlanBridgingL2ptCos OBJECT-TYPE
   SYNTAX      INTEGER
               {
               unchanged (255)
               }
   MAX-ACCESS  read-write
   STATUS      current
   DESCRIPTION
      "Path: swPort.editConf.vlan.bridging.l2ProtTunnel.cos

       Possibilities:
               unchanged   (255)"
   ::= {er1646v2EthPortSwFVlanEntry 459341824}

er1646v2EthPortSwFVlanBridgingL2ptDropThrStp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.stp

       unit name = packets/sec

       Possibilities:
               unlimited   (0)"
   ::= {er1646v2EthPortSwFVlanEntry 459358272}

er1646v2EthPortSwFVlanBridgingL2ptDropThrLldp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lldp

       unit name = packets/sec

       Possibilities:
               unlimited   (0)"
   ::= {er1646v2EthPortSwFVlanEntry 459358336}

er1646v2EthPortSwFVlanBridgingL2ptDropThrOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.oam

       unit name = packets/sec

       Possibilities:
               unlimited   (0)"
   ::= {er1646v2EthPortSwFVlanEntry 459358400}

er1646v2EthPortSwFVlanBridgingL2ptDropThrCdp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.cdp

       unit name = packets/sec

       Possibilities:
               unlimited   (0)"
   ::= {er1646v2EthPortSwFVlanEntry 459358464}

er1646v2EthPortSwFVlanBridgingL2ptDropThrVtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.vtp

       unit name = packets/sec

       Possibilities:
               unlimited   (0)"
   ::= {er1646v2EthPortSwFVlanEntry 459358528}

er1646v2EthPortSwFVlanBridgingL2ptDropThrLacp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lacp

       unit name = packets/sec

       Possibilities:
               unlimited   (0)"
   ::= {er1646v2EthPortSwFVlanEntry 459358592}

er1646v2EthPortSwFVlanBridgingL2ptDropThrEfmOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.efmOam

       unit name = packets/sec

       Possibilities:
               unlimited   (0)"
   ::= {er1646v2EthPortSwFVlanEntry 459358656}

er1646v2EthPortSwFVlanBridgingL2ptDropThrPvst OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pvst

       unit name = packets/sec

       Possibilities:
               unlimited   (0)"
   ::= {er1646v2EthPortSwFVlanEntry 459358720}

er1646v2EthPortSwFVlanBridgingL2ptDropThrMmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mmrp

       unit name = packets/sec

       Possibilities:
               unlimited   (0)"
   ::= {er1646v2EthPortSwFVlanEntry 459358784}

er1646v2EthPortSwFVlanBridgingL2ptDropThrMvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mvrp

       unit name = packets/sec

       Possibilities:
               unlimited   (0)"
   ::= {er1646v2EthPortSwFVlanEntry 459358848}

er1646v2EthPortSwFVlanBridgingL2ptDropThrGvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gvrp

       unit name = packets/sec

       Possibilities:
               unlimited   (0)"
   ::= {er1646v2EthPortSwFVlanEntry 459358912}

er1646v2EthPortSwFVlanBridgingL2ptDropThrGmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gmrp

       unit name = packets/sec

       Possibilities:
               unlimited   (0)"
   ::= {er1646v2EthPortSwFVlanEntry 459358976}

er1646v2EthPortSwFVlanBridgingL2ptDropThrDtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.dtp

       unit name = packets/sec

       Possibilities:
               unlimited   (0)"
   ::= {er1646v2EthPortSwFVlanEntry 459359040}

er1646v2EthPortSwFVlanBridgingL2ptDropThrPagp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pagp

       unit name = packets/sec

       Possibilities:
               unlimited   (0)"
   ::= {er1646v2EthPortSwFVlanEntry 459359104}

er1646v2EthPortSwFVlanBridgingL2ptDropThrUdld OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.udld

       unit name = packets/sec

       Possibilities:
               unlimited   (0)"
   ::= {er1646v2EthPortSwFVlanEntry 459359168}

er1646v2EthPortSwFVlanVlanVid OBJECT-TYPE
   SYNTAX      INTEGER
               {
               untagged (0),
               prioTagged (4096),
               notUsed (4097)
               }
   MAX-ACCESS  read-write
   STATUS      current
   DESCRIPTION
      "Path: swPort.editConf.vlan.vlan.vid

       Possibilities:
               untagged   (0)
               prioTagged   (4096)
               notUsed   (4097)"
   ::= {er1646v2EthPortSwFVlanEntry 234946560}

er1646v2EthPortSwFVlanVlanVidExtensionSingle OBJECT-TYPE
   SYNTAX      OCTET STRING
   MAX-ACCESS  read-write
   STATUS      current
   DESCRIPTION
      "Path: swPort.editConf.vlan.vlan.vidExtension.single"
   ::= {er1646v2EthPortSwFVlanEntry 235340032}

er1646v2EthPortSwFVlanVlanVidExtensionEndVid OBJECT-TYPE
   SYNTAX      Integer32
   MAX-ACCESS  read-write
   STATUS      current
   DESCRIPTION
      "Path: swPort.editConf.vlan.vlan.vidExtension.endVid"
   ::= {er1646v2EthPortSwFVlanEntry 235340288}

er1646v2EthPortSwFVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tpid

       Possibilities:
               dot1Q   (33024)
               dot1ad   (34984)
               0x9100   (37120)
               0x9200   (37376)
               0x9300   (37632)"
   ::= {er1646v2EthPortSwFVlanEntry 241238016}

er1646v2EthPortSwFVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: swPort.editConf.vlan.vlan.tagSignificance

       Possibilities:
               global   (0)
               local   (1)
               sVlan   (2)
               sVlanGlobal   (6)
               cVlan   (3)
               scVlan   (5)
               cVlanLocal   (4)"
   ::= {er1646v2EthPortSwFVlanEntry 235012096}

er1646v2EthPortSwFVlanVlanChTos OBJECT-TYPE
   SYNTAX      INTEGER
               {
               disabled (0),
               enabled (1)
               }
   MAX-ACCESS  read-write
   STATUS      current
   DESCRIPTION
      "Path: swPort.editConf.vlan.vlan.changeTos

       Possibilities:
               disabled   (0)
               enabled   (1)"
   ::= {er1646v2EthPortSwFVlanEntry 235208704}

er1646v2EthPortSwFVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235143424}

er1646v2EthPortSwFVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235143680}

er1646v2EthPortSwFVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235143936}

er1646v2EthPortSwFVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235144192}

er1646v2EthPortSwFVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235144448}

er1646v2EthPortSwFVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235144704}

er1646v2EthPortSwFVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235144960}

er1646v2EthPortSwFVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwFVlanEntry 235145216}

er1646v2EthPortSwFVlanVlanTxCos OBJECT-TYPE
   SYNTAX      INTEGER
               {
               tosCosMap (8),
               queueCosMap (16)
               }
   MAX-ACCESS  read-write
   STATUS      current
   DESCRIPTION
      "Path: swPort.editConf.vlan.vlan.txCos

       Possibilities:
               tosCosMap   (8)
               queueCosMap   (16)"
   ::= {er1646v2EthPortSwFVlanEntry 235077632}

er1646v2EthPortSwFVlanVlanCCMapP0 OBJECT-TYPE
   SYNTAX      Integer32
   MAX-ACCESS  read-write
   STATUS      current
   DESCRIPTION
      "Path: swPort.editConf.vlan.vlan.cosCosMap.p0"
   ::= {er1646v2EthPortSwFVlanEntry 241303808}

er1646v2EthPortSwFVlanVlanCCMapP1 OBJECT-TYPE
   SYNTAX      Integer32
   MAX-ACCESS  read-write
   STATUS      current
   DESCRIPTION
      "Path: swPort.editConf.vlan.vlan.cosCosMap.p1"
   ::= {er1646v2EthPortSwFVlanEntry 241304064}

er1646v2EthPortSwFVlanVlanCCMapP2 OBJECT-TYPE
   SYNTAX      Integer32
   MAX-ACCESS  read-write
   STATUS      current
   DESCRIPTION
      "Path: swPort.editConf.vlan.vlan.cosCosMap.p2"
   ::= {er1646v2EthPortSwFVlanEntry 241304320}

er1646v2EthPortSwFVlanVlanCCMapP3 OBJECT-TYPE
   SYNTAX      Integer32
   MAX-ACCESS  read-write
   STATUS      current
   DESCRIPTION
      "Path: swPort.editConf.vlan.vlan.cosCosMap.p3"
   ::= {er1646v2EthPortSwFVlanEntry 241304576}

er1646v2EthPortSwFVlanVlanCCMapP4 OBJECT-TYPE
   SYNTAX      Integer32
   MAX-ACCESS  read-write
   STATUS      current
   DESCRIPTION
      "Path: swPort.editConf.vlan.vlan.cosCosMap.p4"
   ::= {er1646v2EthPortSwFVlanEntry 241304832}

er1646v2EthPortSwFVlanVlanCCMapP5 OBJECT-TYPE
   SYNTAX      Integer32
   MAX-ACCESS  read-write
   STATUS      current
   DESCRIPTION
      "Path: swPort.editConf.vlan.vlan.cosCosMap.p5"
   ::= {er1646v2EthPortSwFVlanEntry 241305088}

er1646v2EthPortSwFVlanVlanCCMapP6 OBJECT-TYPE
   SYNTAX      Integer32
   MAX-ACCESS  read-write
   STATUS      current
   DESCRIPTION
      "Path: swPort.editConf.vlan.vlan.cosCosMap.p6"
   ::= {er1646v2EthPortSwFVlanEntry 241305344}

er1646v2EthPortSwFVlanVlanCCMapP7 OBJECT-TYPE
   SYNTAX      Integer32
   MAX-ACCESS  read-write
   STATUS      current
   DESCRIPTION
      "Path: swPort.editConf.vlan.vlan.cosCosMap.p7"
   ::= {er1646v2EthPortSwFVlanEntry 241305600}

er1646v2EthPortSwFVlanVlanQCMapQueue1 OBJECT-TYPE
   SYNTAX      Integer32
   MAX-ACCESS  read-write
   STATUS      current
   DESCRIPTION
      "Path: swPort.editConf.vlan.vlan.queueCosMap.queue1"
   ::= {er1646v2EthPortSwFVlanEntry 241434880}

er1646v2EthPortSwFVlanVlanQCMapQueue2 OBJECT-TYPE
   SYNTAX      Integer32
   MAX-ACCESS  read-write
   STATUS      current
   DESCRIPTION
      "Path: swPort.editConf.vlan.vlan.queueCosMap.queue2"
   ::= {er1646v2EthPortSwFVlanEntry 241435136}

er1646v2EthPortSwFVlanVlanQCMapQueue3 OBJECT-TYPE
   SYNTAX      Integer32
   MAX-ACCESS  read-write
   STATUS      current
   DESCRIPTION
      "Path: swPort.editConf.vlan.vlan.queueCosMap.queue3"
   ::= {er1646v2EthPortSwFVlanEntry 241435392}

er1646v2EthPortSwFVlanVlanQCMapQueue4 OBJECT-TYPE
   SYNTAX      Integer32
   MAX-ACCESS  read-write
   STATUS      current
   DESCRIPTION
      "Path: swPort.editConf.vlan.vlan.queueCosMap.queue4"
   ::= {er1646v2EthPortSwFVlanEntry 241435648}

er1646v2EthPortSwFVlanVlanQCMapQueue5 OBJECT-TYPE
   SYNTAX      Integer32
   MAX-ACCESS  read-write
   STATUS      current
   DESCRIPTION
      "Path: swPort.editConf.vlan.vlan.queueCosMap.queue5"
   ::= {er1646v2EthPortSwFVlanEntry 241435904}

er1646v2EthPortSwFVlanVlanQCMapLowDelayQueue OBJECT-TYPE
   SYNTAX      Integer32
   MAX-ACCESS  read-write
   STATUS      current
   DESCRIPTION
      "Path: swPort.editConf.vlan.vlan.queueCosMap.lowDelayQueue"
   ::= {er1646v2EthPortSwFVlanEntry 241436160}

er1646v2EthPortSwFVlanVlanQCMapLowDelay2Queue OBJECT-TYPE
   SYNTAX      Integer32
   MAX-ACCESS  read-write
   STATUS      current
   DESCRIPTION
      "Path: swPort.editConf.vlan.vlan.queueCosMap.lowDelay2Queue"
   ::= {er1646v2EthPortSwFVlanEntry 241436416}

er1646v2EthPortSwFVlanVlanQCMapSystemQueue OBJECT-TYPE
   SYNTAX      Integer32
   MAX-ACCESS  read-write
   STATUS      current
   DESCRIPTION
      "Path: swPort.editConf.vlan.vlan.queueCosMap.systemQueue"
   ::= {er1646v2EthPortSwFVlanEntry 241436672}

er1646v2EthPortSwFVlanVlanQinQSVid OBJECT-TYPE
   SYNTAX      Integer32
   MAX-ACCESS  read-write
   STATUS      current
   DESCRIPTION
      "Path: swPort.editConf.vlan.vlan.tunnel.sVid"
   ::= {er1646v2EthPortSwFVlanEntry 241172736}

er1646v2EthPortSwFVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tunnel.sTpid

       Possibilities:
               dot1Q   (33024)
               dot1ad   (34984)
               0x9100   (37120)
               0x9200   (37376)
               0x9300   (37632)"
   ::= {er1646v2EthPortSwFVlanEntry 241172992}

er1646v2EthPortSwFVlanVlanArpTimeOut OBJECT-TYPE
   SYNTAX      TimeTicks
   MAX-ACCESS  read-write
   STATUS      current
   DESCRIPTION
      "Path: swPort.editConf.vlan.vlan.arp.timeOut

       Time in centi-second."
   ::= {er1646v2EthPortSwFVlanEntry 235277312}

er1646v2EthPortSwFVlanVlanArpProxyArp OBJECT-TYPE
   SYNTAX      INTEGER
               {
               disabled (0),
               enabled (1)
               }
   MAX-ACCESS  read-write
   STATUS      current
   DESCRIPTION
      "Path: swPort.editConf.vlan.vlan.arp.proxyArp

       Possibilities:
               disabled   (0)
               enabled   (1)"
   ::= {er1646v2EthPortSwFVlanEntry 235287040}

er1646v2EthPortSwFVlanBandwidthMode OBJECT-TYPE
   SYNTAX      INTEGER
               {
               reshaping (1),
               policing (2),
               policingReshape (3)
               }
   MAX-ACCESS  read-write
   STATUS      current
   DESCRIPTION
      "Path: swPort.editConf.vlan.bandwidth.mode

       Possibilities:
               reshaping   (1)
               policing   (2)
               policingReshape   (3)"
   ::= {er1646v2EthPortSwFVlanEntry 148897792}

er1646v2EthPortSwFVlanBandwidthCir OBJECT-TYPE
   SYNTAX      Integer32
   MAX-ACCESS  read-write
   STATUS      current
   DESCRIPTION
      "Path: swPort.editConf.vlan.bandwidth.cir"
   ::= {er1646v2EthPortSwFVlanEntry 135266304}

er1646v2EthPortSwFVlanBandwidthEir OBJECT-TYPE
   SYNTAX      Integer32
   MAX-ACCESS  read-write
   STATUS      current
   DESCRIPTION
      "Path: swPort.editConf.vlan.bandwidth.eir"
   ::= {er1646v2EthPortSwFVlanEntry 141557760}

er1646v2EthPortSwFVlanBandwidthUnit OBJECT-TYPE
   SYNTAX      INTEGER
               {
               bitssec (1),
               percent (2)
               }
   MAX-ACCESS  read-write
   STATUS      current
   DESCRIPTION
      "Path: swPort.editConf.vlan.bandwidth.unit

       Possibilities:
               bits/sec   (1)
               percent   (2)"
   ::= {er1646v2EthPortSwFVlanEntry 139460608}

er1646v2EthPortSwFVlanBandwidthTc OBJECT-TYPE
   SYNTAX      INTEGER
               {
               auto (0)
               }
   MAX-ACCESS  read-write
   STATUS      current
   DESCRIPTION
      "Path: swPort.editConf.vlan.bandwidth.tc

       Possibilities:
               auto   (0)"
   ::= {er1646v2EthPortSwFVlanEntry 140509184}

er1646v2EthPortSwFVlanBandwidthTcFactor OBJECT-TYPE
   SYNTAX      INTEGER
               {
               ms (10),
               s100us (1)
               }
   MAX-ACCESS  read-write
   STATUS      current
   DESCRIPTION
      "Path: swPort.editConf.vlan.bandwidth.tcFactor

       Possibilities:
               ms   (10)
               *100us   (1)"
   ::= {er1646v2EthPortSwFVlanEntry 142606336}

er1646v2EthPortSwFVlanBandwidthCorrType OBJECT-TYPE
   SYNTAX      INTEGER
               {
               noCorrection (0),
               predefined (1),
               manual (2)
               }
   MAX-ACCESS  read-write
   STATUS      current
   DESCRIPTION
      "Path: swPort.editConf.vlan.bandwidth.correction.type

       Possibilities:
               noCorrection   (0)
               predefined   (1)
               manual   (2)"
   ::= {er1646v2EthPortSwFVlanEntry 136445952}

er1646v2EthPortSwFVlanBandwidthCorrPredefEncapsFrameRelay OBJECT-TYPE
   SYNTAX      DisplayString
   MAX-ACCESS  read-write
   STATUS      current
   DESCRIPTION
      "Path: swPort.editConf.vlan.bandwidth.correction.predefined.encapsulation.frameRelay"
   ::= {er1646v2EthPortSwFVlanEntry 136594432}

er1646v2EthPortSwFVlanBandwidthCorrPredefEncapsPpp OBJECT-TYPE
   SYNTAX      DisplayString
   MAX-ACCESS  read-write
   STATUS      current
   DESCRIPTION
      "Path: swPort.editConf.vlan.bandwidth.correction.predefined.encapsulation.ppp"
   ::= {er1646v2EthPortSwFVlanEntry 136595456}

er1646v2EthPortSwFVlanBandwidthCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.bandwidth.correction.predefined.encapsulation.atm.higherLayer

       Possibilities:
               rfc2684   (0)
               ppp   (1)
               pppOverEthernet   (2)"
   ::= {er1646v2EthPortSwFVlanEntry 136596608}

er1646v2EthPortSwFVlanBandwidthCorrPredefEncapsAtmMp OBJECT-TYPE
   SYNTAX      INTEGER
               {
               llcEncapsulation (0),
               vcMultiplexing (1)
               }
   MAX-ACCESS  read-write
   STATUS      current
   DESCRIPTION
      "Path: swPort.editConf.vlan.bandwidth.correction.predefined.encapsulation.atm.multiProtocol

       Possibilities:
               llcEncapsulation   (0)
               vcMultiplexing   (1)"
   ::= {er1646v2EthPortSwFVlanEntry 136596736}

er1646v2EthPortSwFVlanBandwidthCorrPredefEncapsHdlc OBJECT-TYPE
   SYNTAX      DisplayString
   MAX-ACCESS  read-write
   STATUS      current
   DESCRIPTION
      "Path: swPort.editConf.vlan.bandwidth.correction.predefined.encapsulation.hdlc"
   ::= {er1646v2EthPortSwFVlanEntry 136597504}

er1646v2EthPortSwFVlanBandwidthCorrPredefEncapsEfmFs OBJECT-TYPE
   SYNTAX      Integer32
   MAX-ACCESS  read-write
   STATUS      current
   DESCRIPTION
      "Path: swPort.editConf.vlan.bandwidth.correction.predefined.encapsulation.efm.fragmentSize"
   ::= {er1646v2EthPortSwFVlanEntry 136598656}

er1646v2EthPortSwFVlanBandwidthCorrPredefEncapsEfmIb OBJECT-TYPE
   SYNTAX      Integer32
   MAX-ACCESS  read-write
   STATUS      current
   DESCRIPTION
      "Path: swPort.editConf.vlan.bandwidth.correction.predefined.encapsulation.efm.idleBytes"
   ::= {er1646v2EthPortSwFVlanEntry 136598784}

er1646v2EthPortSwFVlanBandwidthCorrPredefMode OBJECT-TYPE
   SYNTAX      INTEGER
               {
               routing (0),
               bridging (1)
               }
   MAX-ACCESS  read-write
   STATUS      current
   DESCRIPTION
      "Path: swPort.editConf.vlan.bandwidth.correction.predefined.mode

       Possibilities:
               routing   (0)
               bridging   (1)"
   ::= {er1646v2EthPortSwFVlanEntry 136609792}

er1646v2EthPortSwFVlanBandwidthCorrManualOverhead OBJECT-TYPE
   SYNTAX      Integer32
   MAX-ACCESS  read-write
   STATUS      current
   DESCRIPTION
      "Path: swPort.editConf.vlan.bandwidth.correction.manual.overhead"
   ::= {er1646v2EthPortSwFVlanEntry 136708608}

er1646v2EthPortSwFVlanBandwidthCorrManualFrameData OBJECT-TYPE
   SYNTAX      Counter32
   MAX-ACCESS  read-write
   STATUS      current
   DESCRIPTION
      "Path: swPort.editConf.vlan.bandwidth.correction.manual.frameData

       32 bit unsigned wrappable counter."
   ::= {er1646v2EthPortSwFVlanEntry 136709120}

er1646v2EthPortSwFVlanBandwidthCorrManualFrameHeader OBJECT-TYPE
   SYNTAX      Counter32
   MAX-ACCESS  read-write
   STATUS      current
   DESCRIPTION
      "Path: swPort.editConf.vlan.bandwidth.correction.manual.frameHeader

       32 bit unsigned wrappable counter."
   ::= {er1646v2EthPortSwFVlanEntry 136709632}

er1646v2EthPortSwFVlanBandwidthMaxFifoQLen OBJECT-TYPE
   SYNTAX      Integer32
   MAX-ACCESS  read-write
   STATUS      current
   DESCRIPTION
      "Path: swPort.editConf.vlan.bandwidth.maxFifoQLen"
   ::= {er1646v2EthPortSwFVlanEntry 137363456}

er1646v2EthPortSwFVlanBandwidthDeFlagCir OBJECT-TYPE
   SYNTAX      INTEGER
               {
               allowed (1),
               notAllowed (2)
               }
   MAX-ACCESS  read-write
   STATUS      current
   DESCRIPTION
      "Path: swPort.editConf.vlan.bandwidth.deFlag.cir

       Possibilities:
               allowed   (1)
               notAllowed   (2)"
   ::= {er1646v2EthPortSwFVlanEntry 147853312}

er1646v2EthPortSwFVlanBandwidthDeFlagEir OBJECT-TYPE
   SYNTAX      INTEGER
               {
               allowed (1),
               notAllowed (2)
               }
   MAX-ACCESS  read-write
   STATUS      current
   DESCRIPTION
      "Path: swPort.editConf.vlan.bandwidth.deFlag.eir

       Possibilities:
               allowed   (1)
               notAllowed   (2)"
   ::= {er1646v2EthPortSwFVlanEntry 147857408}

er1646v2EthPortSwFVlanBandwidthDeFlagViolate OBJECT-TYPE
   SYNTAX      INTEGER
               {
               allowed (1),
               notAllowed (2)
               }
   MAX-ACCESS  read-write
   STATUS      current
   DESCRIPTION
      "Path: swPort.editConf.vlan.bandwidth.deFlag.violate

       Possibilities:
               allowed   (1)
               notAllowed   (2)"
   ::= {er1646v2EthPortSwFVlanEntry 147861504}

er1646v2EthPortSwFVlanBandwidthActCirActNone OBJECT-TYPE
   SYNTAX      OCTET STRING
   MAX-ACCESS  read-write
   STATUS      current
   DESCRIPTION
      "Path: swPort.editConf.vlan.bandwidth.action.cirAction.none"
   ::= {er1646v2EthPortSwFVlanEntry 150085632}

er1646v2EthPortSwFVlanBandwidthActCirActEthCos1 OBJECT-TYPE
   SYNTAX      INTEGER
               {
               unchanged (256)
               }
   MAX-ACCESS  read-write
   STATUS      current
   DESCRIPTION
      "Path: swPort.editConf.vlan.bandwidth.action.cirAction.ethernet.cosDepth1

       Possibilities:
               unchanged   (256)"
   ::= {er1646v2EthPortSwFVlanEntry 150094080}

er1646v2EthPortSwFVlanBandwidthActCirActEthDei1 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth1

       Possibilities:
               unchanged   (255)
               clear   (0)
               set   (1)"
   ::= {er1646v2EthPortSwFVlanEntry 150099200}

er1646v2EthPortSwFVlanBandwidthActCirActEthCos2 OBJECT-TYPE
   SYNTAX      INTEGER
               {
               unchanged (256)
               }
   MAX-ACCESS  read-write
   STATUS      current
   DESCRIPTION
      "Path: swPort.editConf.vlan.bandwidth.action.cirAction.ethernet.cosDepth2

       Possibilities:
               unchanged   (256)"
   ::= {er1646v2EthPortSwFVlanEntry 150094336}

er1646v2EthPortSwFVlanBandwidthActCirActEthDei2 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth2

       Possibilities:
               unchanged   (255)
               clear   (0)
               set   (1)"
   ::= {er1646v2EthPortSwFVlanEntry 150099456}

er1646v2EthPortSwFVlanBandwidthActCirActEthCos3 OBJECT-TYPE
   SYNTAX      INTEGER
               {
               unchanged (256)
               }
   MAX-ACCESS  read-write
   STATUS      current
   DESCRIPTION
      "Path: swPort.editConf.vlan.bandwidth.action.cirAction.ethernet.cosDepth3

       Possibilities:
               unchanged   (256)"
   ::= {er1646v2EthPortSwFVlanEntry 150094592}

er1646v2EthPortSwFVlanBandwidthActCirActEthDei3 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth3

       Possibilities:
               unchanged   (255)
               clear   (0)
               set   (1)"
   ::= {er1646v2EthPortSwFVlanEntry 150099712}

er1646v2EthPortSwFVlanBandwidthActCirActEthCos4 OBJECT-TYPE
   SYNTAX      INTEGER
               {
               unchanged (256)
               }
   MAX-ACCESS  read-write
   STATUS      current
   DESCRIPTION
      "Path: swPort.editConf.vlan.bandwidth.action.cirAction.ethernet.cosDepth4

       Possibilities:
               unchanged   (256)"
   ::= {er1646v2EthPortSwFVlanEntry 150094848}

er1646v2EthPortSwFVlanBandwidthActCirActEthDei4 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth4

       Possibilities:
               unchanged   (255)
               clear   (0)
               set   (1)"
   ::= {er1646v2EthPortSwFVlanEntry 150099968}

er1646v2EthPortSwFVlanBandwidthActCirActEthCos5 OBJECT-TYPE
   SYNTAX      INTEGER
               {
               unchanged (256)
               }
   MAX-ACCESS  read-write
   STATUS      current
   DESCRIPTION
      "Path: swPort.editConf.vlan.bandwidth.action.cirAction.ethernet.cosDepth5

       Possibilities:
               unchanged   (256)"
   ::= {er1646v2EthPortSwFVlanEntry 150095104}

er1646v2EthPortSwFVlanBandwidthActCirActEthDei5 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth5

       Possibilities:
               unchanged   (255)
               clear   (0)
               set   (1)"
   ::= {er1646v2EthPortSwFVlanEntry 150100224}

er1646v2EthPortSwFVlanBandwidthActCirActEthCos6 OBJECT-TYPE
   SYNTAX      INTEGER
               {
               unchanged (256)
               }
   MAX-ACCESS  read-write
   STATUS      current
   DESCRIPTION
      "Path: swPort.editConf.vlan.bandwidth.action.cirAction.ethernet.cosDepth6

       Possibilities:
               unchanged   (256)"
   ::= {er1646v2EthPortSwFVlanEntry 150095360}

er1646v2EthPortSwFVlanBandwidthActCirActEthDei6 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth6

       Possibilities:
               unchanged   (255)
               clear   (0)
               set   (1)"
   ::= {er1646v2EthPortSwFVlanEntry 150100480}

er1646v2EthPortSwFVlanBandwidthActCirActEthCos7 OBJECT-TYPE
   SYNTAX      INTEGER
               {
               unchanged (256)
               }
   MAX-ACCESS  read-write
   STATUS      current
   DESCRIPTION
      "Path: swPort.editConf.vlan.bandwidth.action.cirAction.ethernet.cosDepth7

       Possibilities:
               unchanged   (256)"
   ::= {er1646v2EthPortSwFVlanEntry 150095616}

er1646v2EthPortSwFVlanBandwidthActCirActEthDei7 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth7

       Possibilities:
               unchanged   (255)
               clear   (0)
               set   (1)"
   ::= {er1646v2EthPortSwFVlanEntry 150100736}

er1646v2EthPortSwFVlanBandwidthActCirActEthCos8 OBJECT-TYPE
   SYNTAX      INTEGER
               {
               unchanged (256)
               }
   MAX-ACCESS  read-write
   STATUS      current
   DESCRIPTION
      "Path: swPort.editConf.vlan.bandwidth.action.cirAction.ethernet.cosDepth8

       Possibilities:
               unchanged   (256)"
   ::= {er1646v2EthPortSwFVlanEntry 150095872}

er1646v2EthPortSwFVlanBandwidthActCirActEthDei8 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth8

       Possibilities:
               unchanged   (255)
               clear   (0)
               set   (1)"
   ::= {er1646v2EthPortSwFVlanEntry 150100992}

er1646v2EthPortSwFVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150096128}

er1646v2EthPortSwFVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150096384}

er1646v2EthPortSwFVlanBandwidthActCirActEthDrpLev OBJECT-TYPE
   SYNTAX      INTEGER
               {
               unchanged (0)
               }
   MAX-ACCESS  read-write
   STATUS      current
   DESCRIPTION
      "Path: swPort.editConf.vlan.bandwidth.action.cirAction.ethernet.dropLevel

       Possibilities:
               unchanged   (0)"
   ::= {er1646v2EthPortSwFVlanEntry 150096640}

er1646v2EthPortSwFVlanBandwidthActCirActEthDeFlag OBJECT-TYPE
   SYNTAX      INTEGER
               {
               unchanged (255),
               clear (0),
               set (1)
               }
   MAX-ACCESS  read-write
   STATUS      current
   DESCRIPTION
      "Path: swPort.editConf.vlan.bandwidth.action.cirAction.ethernet.deFlag

       Possibilities:
               unchanged   (255)
               clear   (0)
               set   (1)"
   ::= {er1646v2EthPortSwFVlanEntry 150097408}

er1646v2EthPortSwFVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150120704}

er1646v2EthPortSwFVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150120960}

er1646v2EthPortSwFVlanBandwidthActCirActIpDrpLev OBJECT-TYPE
   SYNTAX      INTEGER
               {
               unchanged (0)
               }
   MAX-ACCESS  read-write
   STATUS      current
   DESCRIPTION
      "Path: swPort.editConf.vlan.bandwidth.action.cirAction.ip.dropLevel

       Possibilities:
               unchanged   (0)"
   ::= {er1646v2EthPortSwFVlanEntry 150121216}

er1646v2EthPortSwFVlanBandwidthActCirActIpDeFlag OBJECT-TYPE
   SYNTAX      INTEGER
               {
               unchanged (255),
               clear (0),
               set (1)
               }
   MAX-ACCESS  read-write
   STATUS      current
   DESCRIPTION
      "Path: swPort.editConf.vlan.bandwidth.action.cirAction.ip.deFlag

       Possibilities:
               unchanged   (255)
               clear   (0)
               set   (1)"
   ::= {er1646v2EthPortSwFVlanEntry 150121984}

er1646v2EthPortSwFVlanBandwidthActEirActNone OBJECT-TYPE
   SYNTAX      OCTET STRING
   MAX-ACCESS  read-write
   STATUS      current
   DESCRIPTION
      "Path: swPort.editConf.vlan.bandwidth.action.eirAction.none"
   ::= {er1646v2EthPortSwFVlanEntry 150216704}

er1646v2EthPortSwFVlanBandwidthActEirActEthCos1 OBJECT-TYPE
   SYNTAX      INTEGER
               {
               unchanged (256)
               }
   MAX-ACCESS  read-write
   STATUS      current
   DESCRIPTION
      "Path: swPort.editConf.vlan.bandwidth.action.eirAction.ethernet.cosDepth1

       Possibilities:
               unchanged   (256)"
   ::= {er1646v2EthPortSwFVlanEntry 150225152}

er1646v2EthPortSwFVlanBandwidthActEirActEthDei1 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth1

       Possibilities:
               unchanged   (255)
               clear   (0)
               set   (1)"
   ::= {er1646v2EthPortSwFVlanEntry 150230272}

er1646v2EthPortSwFVlanBandwidthActEirActEthCos2 OBJECT-TYPE
   SYNTAX      INTEGER
               {
               unchanged (256)
               }
   MAX-ACCESS  read-write
   STATUS      current
   DESCRIPTION
      "Path: swPort.editConf.vlan.bandwidth.action.eirAction.ethernet.cosDepth2

       Possibilities:
               unchanged   (256)"
   ::= {er1646v2EthPortSwFVlanEntry 150225408}

er1646v2EthPortSwFVlanBandwidthActEirActEthDei2 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth2

       Possibilities:
               unchanged   (255)
               clear   (0)
               set   (1)"
   ::= {er1646v2EthPortSwFVlanEntry 150230528}

er1646v2EthPortSwFVlanBandwidthActEirActEthCos3 OBJECT-TYPE
   SYNTAX      INTEGER
               {
               unchanged (256)
               }
   MAX-ACCESS  read-write
   STATUS      current
   DESCRIPTION
      "Path: swPort.editConf.vlan.bandwidth.action.eirAction.ethernet.cosDepth3

       Possibilities:
               unchanged   (256)"
   ::= {er1646v2EthPortSwFVlanEntry 150225664}

er1646v2EthPortSwFVlanBandwidthActEirActEthDei3 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth3

       Possibilities:
               unchanged   (255)
               clear   (0)
               set   (1)"
   ::= {er1646v2EthPortSwFVlanEntry 150230784}

er1646v2EthPortSwFVlanBandwidthActEirActEthCos4 OBJECT-TYPE
   SYNTAX      INTEGER
               {
               unchanged (256)
               }
   MAX-ACCESS  read-write
   STATUS      current
   DESCRIPTION
      "Path: swPort.editConf.vlan.bandwidth.action.eirAction.ethernet.cosDepth4

       Possibilities:
               unchanged   (256)"
   ::= {er1646v2EthPortSwFVlanEntry 150225920}

er1646v2EthPortSwFVlanBandwidthActEirActEthDei4 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth4

       Possibilities:
               unchanged   (255)
               clear   (0)
               set   (1)"
   ::= {er1646v2EthPortSwFVlanEntry 150231040}

er1646v2EthPortSwFVlanBandwidthActEirActEthCos5 OBJECT-TYPE
   SYNTAX      INTEGER
               {
               unchanged (256)
               }
   MAX-ACCESS  read-write
   STATUS      current
   DESCRIPTION
      "Path: swPort.editConf.vlan.bandwidth.action.eirAction.ethernet.cosDepth5

       Possibilities:
               unchanged   (256)"
   ::= {er1646v2EthPortSwFVlanEntry 150226176}

er1646v2EthPortSwFVlanBandwidthActEirActEthDei5 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth5

       Possibilities:
               unchanged   (255)
               clear   (0)
               set   (1)"
   ::= {er1646v2EthPortSwFVlanEntry 150231296}

er1646v2EthPortSwFVlanBandwidthActEirActEthCos6 OBJECT-TYPE
   SYNTAX      INTEGER
               {
               unchanged (256)
               }
   MAX-ACCESS  read-write
   STATUS      current
   DESCRIPTION
      "Path: swPort.editConf.vlan.bandwidth.action.eirAction.ethernet.cosDepth6

       Possibilities:
               unchanged   (256)"
   ::= {er1646v2EthPortSwFVlanEntry 150226432}

er1646v2EthPortSwFVlanBandwidthActEirActEthDei6 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth6

       Possibilities:
               unchanged   (255)
               clear   (0)
               set   (1)"
   ::= {er1646v2EthPortSwFVlanEntry 150231552}

er1646v2EthPortSwFVlanBandwidthActEirActEthCos7 OBJECT-TYPE
   SYNTAX      INTEGER
               {
               unchanged (256)
               }
   MAX-ACCESS  read-write
   STATUS      current
   DESCRIPTION
      "Path: swPort.editConf.vlan.bandwidth.action.eirAction.ethernet.cosDepth7

       Possibilities:
               unchanged   (256)"
   ::= {er1646v2EthPortSwFVlanEntry 150226688}

er1646v2EthPortSwFVlanBandwidthActEirActEthDei7 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth7

       Possibilities:
               unchanged   (255)
               clear   (0)
               set   (1)"
   ::= {er1646v2EthPortSwFVlanEntry 150231808}

er1646v2EthPortSwFVlanBandwidthActEirActEthCos8 OBJECT-TYPE
   SYNTAX      INTEGER
               {
               unchanged (256)
               }
   MAX-ACCESS  read-write
   STATUS      current
   DESCRIPTION
      "Path: swPort.editConf.vlan.bandwidth.action.eirAction.ethernet.cosDepth8

       Possibilities:
               unchanged   (256)"
   ::= {er1646v2EthPortSwFVlanEntry 150226944}

er1646v2EthPortSwFVlanBandwidthActEirActEthDei8 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth8

       Possibilities:
               unchanged   (255)
               clear   (0)
               set   (1)"
   ::= {er1646v2EthPortSwFVlanEntry 150232064}

er1646v2EthPortSwFVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150227200}

er1646v2EthPortSwFVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150227456}

er1646v2EthPortSwFVlanBandwidthActEirActEthDrpLev OBJECT-TYPE
   SYNTAX      INTEGER
               {
               unchanged (0)
               }
   MAX-ACCESS  read-write
   STATUS      current
   DESCRIPTION
      "Path: swPort.editConf.vlan.bandwidth.action.eirAction.ethernet.dropLevel

       Possibilities:
               unchanged   (0)"
   ::= {er1646v2EthPortSwFVlanEntry 150227712}

er1646v2EthPortSwFVlanBandwidthActEirActEthDeFlag OBJECT-TYPE
   SYNTAX      INTEGER
               {
               unchanged (255),
               clear (0),
               set (1)
               }
   MAX-ACCESS  read-write
   STATUS      current
   DESCRIPTION
      "Path: swPort.editConf.vlan.bandwidth.action.eirAction.ethernet.deFlag

       Possibilities:
               unchanged   (255)
               clear   (0)
               set   (1)"
   ::= {er1646v2EthPortSwFVlanEntry 150228480}

er1646v2EthPortSwFVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150251776}

er1646v2EthPortSwFVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150252032}

er1646v2EthPortSwFVlanBandwidthActEirActIpDrpLev OBJECT-TYPE
   SYNTAX      INTEGER
               {
               unchanged (0)
               }
   MAX-ACCESS  read-write
   STATUS      current
   DESCRIPTION
      "Path: swPort.editConf.vlan.bandwidth.action.eirAction.ip.dropLevel

       Possibilities:
               unchanged   (0)"
   ::= {er1646v2EthPortSwFVlanEntry 150252288}

er1646v2EthPortSwFVlanBandwidthActEirActIpDeFlag OBJECT-TYPE
   SYNTAX      INTEGER
               {
               unchanged (255),
               clear (0),
               set (1)
               }
   MAX-ACCESS  read-write
   STATUS      current
   DESCRIPTION
      "Path: swPort.editConf.vlan.bandwidth.action.eirAction.ip.deFlag

       Possibilities:
               unchanged   (255)
               clear   (0)
               set   (1)"
   ::= {er1646v2EthPortSwFVlanEntry 150253056}

er1646v2EthPortSwFVlanBandwidthActViolActNone OBJECT-TYPE
   SYNTAX      OCTET STRING
   MAX-ACCESS  read-write
   STATUS      current
   DESCRIPTION
      "Path: swPort.editConf.vlan.bandwidth.action.violateAction.none"
   ::= {er1646v2EthPortSwFVlanEntry 150347776}

er1646v2EthPortSwFVlanBandwidthActViolActDrop OBJECT-TYPE
   SYNTAX      OCTET STRING
   MAX-ACCESS  read-write
   STATUS      current
   DESCRIPTION
      "Path: swPort.editConf.vlan.bandwidth.action.violateAction.drop"
   ::= {er1646v2EthPortSwFVlanEntry 150364160}

er1646v2EthPortSwFVlanBandwidthActViolActEthCos1 OBJECT-TYPE
   SYNTAX      INTEGER
               {
               unchanged (256)
               }
   MAX-ACCESS  read-write
   STATUS      current
   DESCRIPTION
      "Path: swPort.editConf.vlan.bandwidth.action.violateAction.ethernet.cosDepth1

       Possibilities:
               unchanged   (256)"
   ::= {er1646v2EthPortSwFVlanEntry 150356224}

er1646v2EthPortSwFVlanBandwidthActViolActEthDei1 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth1

       Possibilities:
               unchanged   (255)
               clear   (0)
               set   (1)"
   ::= {er1646v2EthPortSwFVlanEntry 150361344}

er1646v2EthPortSwFVlanBandwidthActViolActEthCos2 OBJECT-TYPE
   SYNTAX      INTEGER
               {
               unchanged (256)
               }
   MAX-ACCESS  read-write
   STATUS      current
   DESCRIPTION
      "Path: swPort.editConf.vlan.bandwidth.action.violateAction.ethernet.cosDepth2

       Possibilities:
               unchanged   (256)"
   ::= {er1646v2EthPortSwFVlanEntry 150356480}

er1646v2EthPortSwFVlanBandwidthActViolActEthDei2 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth2

       Possibilities:
               unchanged   (255)
               clear   (0)
               set   (1)"
   ::= {er1646v2EthPortSwFVlanEntry 150361600}

er1646v2EthPortSwFVlanBandwidthActViolActEthCos3 OBJECT-TYPE
   SYNTAX      INTEGER
               {
               unchanged (256)
               }
   MAX-ACCESS  read-write
   STATUS      current
   DESCRIPTION
      "Path: swPort.editConf.vlan.bandwidth.action.violateAction.ethernet.cosDepth3

       Possibilities:
               unchanged   (256)"
   ::= {er1646v2EthPortSwFVlanEntry 150356736}

er1646v2EthPortSwFVlanBandwidthActViolActEthDei3 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth3

       Possibilities:
               unchanged   (255)
               clear   (0)
               set   (1)"
   ::= {er1646v2EthPortSwFVlanEntry 150361856}

er1646v2EthPortSwFVlanBandwidthActViolActEthCos4 OBJECT-TYPE
   SYNTAX      INTEGER
               {
               unchanged (256)
               }
   MAX-ACCESS  read-write
   STATUS      current
   DESCRIPTION
      "Path: swPort.editConf.vlan.bandwidth.action.violateAction.ethernet.cosDepth4

       Possibilities:
               unchanged   (256)"
   ::= {er1646v2EthPortSwFVlanEntry 150356992}

er1646v2EthPortSwFVlanBandwidthActViolActEthDei4 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth4

       Possibilities:
               unchanged   (255)
               clear   (0)
               set   (1)"
   ::= {er1646v2EthPortSwFVlanEntry 150362112}

er1646v2EthPortSwFVlanBandwidthActViolActEthCos5 OBJECT-TYPE
   SYNTAX      INTEGER
               {
               unchanged (256)
               }
   MAX-ACCESS  read-write
   STATUS      current
   DESCRIPTION
      "Path: swPort.editConf.vlan.bandwidth.action.violateAction.ethernet.cosDepth5

       Possibilities:
               unchanged   (256)"
   ::= {er1646v2EthPortSwFVlanEntry 150357248}

er1646v2EthPortSwFVlanBandwidthActViolActEthDei5 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth5

       Possibilities:
               unchanged   (255)
               clear   (0)
               set   (1)"
   ::= {er1646v2EthPortSwFVlanEntry 150362368}

er1646v2EthPortSwFVlanBandwidthActViolActEthCos6 OBJECT-TYPE
   SYNTAX      INTEGER
               {
               unchanged (256)
               }
   MAX-ACCESS  read-write
   STATUS      current
   DESCRIPTION
      "Path: swPort.editConf.vlan.bandwidth.action.violateAction.ethernet.cosDepth6

       Possibilities:
               unchanged   (256)"
   ::= {er1646v2EthPortSwFVlanEntry 150357504}

er1646v2EthPortSwFVlanBandwidthActViolActEthDei6 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth6

       Possibilities:
               unchanged   (255)
               clear   (0)
               set   (1)"
   ::= {er1646v2EthPortSwFVlanEntry 150362624}

er1646v2EthPortSwFVlanBandwidthActViolActEthCos7 OBJECT-TYPE
   SYNTAX      INTEGER
               {
               unchanged (256)
               }
   MAX-ACCESS  read-write
   STATUS      current
   DESCRIPTION
      "Path: swPort.editConf.vlan.bandwidth.action.violateAction.ethernet.cosDepth7

       Possibilities:
               unchanged   (256)"
   ::= {er1646v2EthPortSwFVlanEntry 150357760}

er1646v2EthPortSwFVlanBandwidthActViolActEthDei7 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth7

       Possibilities:
               unchanged   (255)
               clear   (0)
               set   (1)"
   ::= {er1646v2EthPortSwFVlanEntry 150362880}

er1646v2EthPortSwFVlanBandwidthActViolActEthCos8 OBJECT-TYPE
   SYNTAX      INTEGER
               {
               unchanged (256)
               }
   MAX-ACCESS  read-write
   STATUS      current
   DESCRIPTION
      "Path: swPort.editConf.vlan.bandwidth.action.violateAction.ethernet.cosDepth8

       Possibilities:
               unchanged   (256)"
   ::= {er1646v2EthPortSwFVlanEntry 150358016}

er1646v2EthPortSwFVlanBandwidthActViolActEthDei8 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth8

       Possibilities:
               unchanged   (255)
               clear   (0)
               set   (1)"
   ::= {er1646v2EthPortSwFVlanEntry 150363136}

er1646v2EthPortSwFVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150358272}

er1646v2EthPortSwFVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150358528}

er1646v2EthPortSwFVlanBandwidthActViolActEthDrpLev OBJECT-TYPE
   SYNTAX      INTEGER
               {
               unchanged (0)
               }
   MAX-ACCESS  read-write
   STATUS      current
   DESCRIPTION
      "Path: swPort.editConf.vlan.bandwidth.action.violateAction.ethernet.dropLevel

       Possibilities:
               unchanged   (0)"
   ::= {er1646v2EthPortSwFVlanEntry 150358784}

er1646v2EthPortSwFVlanBandwidthActViolActEthDeFlag OBJECT-TYPE
   SYNTAX      INTEGER
               {
               unchanged (255),
               clear (0),
               set (1)
               }
   MAX-ACCESS  read-write
   STATUS      current
   DESCRIPTION
      "Path: swPort.editConf.vlan.bandwidth.action.violateAction.ethernet.deFlag

       Possibilities:
               unchanged   (255)
               clear   (0)
               set   (1)"
   ::= {er1646v2EthPortSwFVlanEntry 150359552}

er1646v2EthPortSwFVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 150382848}

er1646v2EthPortSwFVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 150383104}

er1646v2EthPortSwFVlanBandwidthActViolActIpDrpLev OBJECT-TYPE
   SYNTAX      INTEGER
               {
               unchanged (0)
               }
   MAX-ACCESS  read-write
   STATUS      current
   DESCRIPTION
      "Path: swPort.editConf.vlan.bandwidth.action.violateAction.ip.dropLevel

       Possibilities:
               unchanged   (0)"
   ::= {er1646v2EthPortSwFVlanEntry 150383360}

er1646v2EthPortSwFVlanBandwidthActViolActIpDeFlag OBJECT-TYPE
   SYNTAX      INTEGER
               {
               unchanged (255),
               clear (0),
               set (1)
               }
   MAX-ACCESS  read-write
   STATUS      current
   DESCRIPTION
      "Path: swPort.editConf.vlan.bandwidth.action.violateAction.ip.deFlag

       Possibilities:
               unchanged   (255)
               clear   (0)
               set   (1)"
   ::= {er1646v2EthPortSwFVlanEntry 150384128}

er1646v2EthPortSwFVlanInbBwMode OBJECT-TYPE
   SYNTAX      INTEGER
               {
               reshaping (1),
               policing (2)
               }
   MAX-ACCESS  read-write
   STATUS      current
   DESCRIPTION
      "Path: swPort.editConf.vlan.inboundBandwidth.mode

       Possibilities:
               reshaping   (1)
               policing   (2)"
   ::= {er1646v2EthPortSwFVlanEntry 132120576}

er1646v2EthPortSwFVlanInbBwCir OBJECT-TYPE
   SYNTAX      Integer32
   MAX-ACCESS  read-write
   STATUS      current
   DESCRIPTION
      "Path: swPort.editConf.vlan.inboundBandwidth.cir"
   ::= {er1646v2EthPortSwFVlanEntry 118489088}

er1646v2EthPortSwFVlanInbBwEir OBJECT-TYPE
   SYNTAX      Integer32
   MAX-ACCESS  read-write
   STATUS      current
   DESCRIPTION
      "Path: swPort.editConf.vlan.inboundBandwidth.eir"
   ::= {er1646v2EthPortSwFVlanEntry 124780544}

er1646v2EthPortSwFVlanInbBwUnit OBJECT-TYPE
   SYNTAX      INTEGER
               {
               bitssec (1),
               percent (2)
               }
   MAX-ACCESS  read-write
   STATUS      current
   DESCRIPTION
      "Path: swPort.editConf.vlan.inboundBandwidth.unit

       Possibilities:
               bits/sec   (1)
               percent   (2)"
   ::= {er1646v2EthPortSwFVlanEntry 122683392}

er1646v2EthPortSwFVlanInbBwTc OBJECT-TYPE
   SYNTAX      INTEGER
               {
               auto (0)
               }
   MAX-ACCESS  read-write
   STATUS      current
   DESCRIPTION
      "Path: swPort.editConf.vlan.inboundBandwidth.tc

       Possibilities:
               auto   (0)"
   ::= {er1646v2EthPortSwFVlanEntry 123731968}

er1646v2EthPortSwFVlanInbBwTcFactor OBJECT-TYPE
   SYNTAX      INTEGER
               {
               ms (10),
               s100us (1)
               }
   MAX-ACCESS  read-write
   STATUS      current
   DESCRIPTION
      "Path: swPort.editConf.vlan.inboundBandwidth.tcFactor

       Possibilities:
               ms   (10)
               *100us   (1)"
   ::= {er1646v2EthPortSwFVlanEntry 125829120}

er1646v2EthPortSwFVlanInbBwCorrType OBJECT-TYPE
   SYNTAX      INTEGER
               {
               noCorrection (0),
               predefined (1),
               manual (2)
               }
   MAX-ACCESS  read-write
   STATUS      current
   DESCRIPTION
      "Path: swPort.editConf.vlan.inboundBandwidth.correction.type

       Possibilities:
               noCorrection   (0)
               predefined   (1)
               manual   (2)"
   ::= {er1646v2EthPortSwFVlanEntry 119668736}

er1646v2EthPortSwFVlanInbBwCorrPredefEncapsFrameRelay OBJECT-TYPE
   SYNTAX      DisplayString
   MAX-ACCESS  read-write
   STATUS      current
   DESCRIPTION
      "Path: swPort.editConf.vlan.inboundBandwidth.correction.predefined.encapsulation.frameRelay"
   ::= {er1646v2EthPortSwFVlanEntry 119817216}

er1646v2EthPortSwFVlanInbBwCorrPredefEncapsPpp OBJECT-TYPE
   SYNTAX      DisplayString
   MAX-ACCESS  read-write
   STATUS      current
   DESCRIPTION
      "Path: swPort.editConf.vlan.inboundBandwidth.correction.predefined.encapsulation.ppp"
   ::= {er1646v2EthPortSwFVlanEntry 119818240}

er1646v2EthPortSwFVlanInbBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.inboundBandwidth.correction.predefined.encapsulation.atm.higherLayer

       Possibilities:
               rfc2684   (0)
               ppp   (1)
               pppOverEthernet   (2)"
   ::= {er1646v2EthPortSwFVlanEntry 119819392}

er1646v2EthPortSwFVlanInbBwCorrPredefEncapsAtmMp OBJECT-TYPE
   SYNTAX      INTEGER
               {
               llcEncapsulation (0),
               vcMultiplexing (1)
               }
   MAX-ACCESS  read-write
   STATUS      current
   DESCRIPTION
      "Path: swPort.editConf.vlan.inboundBandwidth.correction.predefined.encapsulation.atm.multiProtocol

       Possibilities:
               llcEncapsulation   (0)
               vcMultiplexing   (1)"
   ::= {er1646v2EthPortSwFVlanEntry 119819520}

er1646v2EthPortSwFVlanInbBwCorrPredefEncapsHdlc OBJECT-TYPE
   SYNTAX      DisplayString
   MAX-ACCESS  read-write
   STATUS      current
   DESCRIPTION
      "Path: swPort.editConf.vlan.inboundBandwidth.correction.predefined.encapsulation.hdlc"
   ::= {er1646v2EthPortSwFVlanEntry 119820288}

er1646v2EthPortSwFVlanInbBwCorrPredefEncapsEfmFs OBJECT-TYPE
   SYNTAX      Integer32
   MAX-ACCESS  read-write
   STATUS      current
   DESCRIPTION
      "Path: swPort.editConf.vlan.inboundBandwidth.correction.predefined.encapsulation.efm.fragmentSize"
   ::= {er1646v2EthPortSwFVlanEntry 119821440}

er1646v2EthPortSwFVlanInbBwCorrPredefEncapsEfmIb OBJECT-TYPE
   SYNTAX      Integer32
   MAX-ACCESS  read-write
   STATUS      current
   DESCRIPTION
      "Path: swPort.editConf.vlan.inboundBandwidth.correction.predefined.encapsulation.efm.idleBytes"
   ::= {er1646v2EthPortSwFVlanEntry 119821568}

er1646v2EthPortSwFVlanInbBwCorrPredefMode OBJECT-TYPE
   SYNTAX      INTEGER
               {
               routing (0),
               bridging (1)
               }
   MAX-ACCESS  read-write
   STATUS      current
   DESCRIPTION
      "Path: swPort.editConf.vlan.inboundBandwidth.correction.predefined.mode

       Possibilities:
               routing   (0)
               bridging   (1)"
   ::= {er1646v2EthPortSwFVlanEntry 119832576}

er1646v2EthPortSwFVlanInbBwCorrManualOverhead OBJECT-TYPE
   SYNTAX      Integer32
   MAX-ACCESS  read-write
   STATUS      current
   DESCRIPTION
      "Path: swPort.editConf.vlan.inboundBandwidth.correction.manual.overhead"
   ::= {er1646v2EthPortSwFVlanEntry 119931392}

er1646v2EthPortSwFVlanInbBwCorrManualFrameData OBJECT-TYPE
   SYNTAX      Counter32
   MAX-ACCESS  read-write
   STATUS      current
   DESCRIPTION
      "Path: swPort.editConf.vlan.inboundBandwidth.correction.manual.frameData

       32 bit unsigned wrappable counter."
   ::= {er1646v2EthPortSwFVlanEntry 119931904}

er1646v2EthPortSwFVlanInbBwCorrManualFrameHeader OBJECT-TYPE
   SYNTAX      Counter32
   MAX-ACCESS  read-write
   STATUS      current
   DESCRIPTION
      "Path: swPort.editConf.vlan.inboundBandwidth.correction.manual.frameHeader

       32 bit unsigned wrappable counter."
   ::= {er1646v2EthPortSwFVlanEntry 119932416}

er1646v2EthPortSwFVlanInbBwMaxFifoQLen OBJECT-TYPE
   SYNTAX      Integer32
   MAX-ACCESS  read-write
   STATUS      current
   DESCRIPTION
      "Path: swPort.editConf.vlan.inboundBandwidth.maxFifoQLen"
   ::= {er1646v2EthPortSwFVlanEntry 120586240}

er1646v2EthPortSwFVlanInbBwPriorityPolicy OBJECT-TYPE
   SYNTAX      DisplayString
   MAX-ACCESS  read-write
   STATUS      current
   DESCRIPTION
      "Path: swPort.editConf.vlan.inboundBandwidth.priorityPolicy"
   ::= {er1646v2EthPortSwFVlanEntry 121634816}

er1646v2EthPortSwFVlanInbBwDeFlagCir OBJECT-TYPE
   SYNTAX      INTEGER
               {
               allowed (1),
               notAllowed (2)
               }
   MAX-ACCESS  read-write
   STATUS      current
   DESCRIPTION
      "Path: swPort.editConf.vlan.inboundBandwidth.deFlag.cir

       Possibilities:
               allowed   (1)
               notAllowed   (2)"
   ::= {er1646v2EthPortSwFVlanEntry 131076096}

er1646v2EthPortSwFVlanInbBwDeFlagEir OBJECT-TYPE
   SYNTAX      INTEGER
               {
               allowed (1),
               notAllowed (2)
               }
   MAX-ACCESS  read-write
   STATUS      current
   DESCRIPTION
      "Path: swPort.editConf.vlan.inboundBandwidth.deFlag.eir

       Possibilities:
               allowed   (1)
               notAllowed   (2)"
   ::= {er1646v2EthPortSwFVlanEntry 131080192}

er1646v2EthPortSwFVlanInbBwDeFlagViolate OBJECT-TYPE
   SYNTAX      INTEGER
               {
               allowed (1),
               notAllowed (2)
               }
   MAX-ACCESS  read-write
   STATUS      current
   DESCRIPTION
      "Path: swPort.editConf.vlan.inboundBandwidth.deFlag.violate

       Possibilities:
               allowed   (1)
               notAllowed   (2)"
   ::= {er1646v2EthPortSwFVlanEntry 131084288}

er1646v2EthPortSwFVlanInbBwActCirActNone OBJECT-TYPE
   SYNTAX      OCTET STRING
   MAX-ACCESS  read-write
   STATUS      current
   DESCRIPTION
      "Path: swPort.editConf.vlan.inboundBandwidth.action.cirAction.none"
   ::= {er1646v2EthPortSwFVlanEntry 133308416}

er1646v2EthPortSwFVlanInbBwActCirActEthCos1 OBJECT-TYPE
   SYNTAX      INTEGER
               {
               unchanged (256)
               }
   MAX-ACCESS  read-write
   STATUS      current
   DESCRIPTION
      "Path: swPort.editConf.vlan.inboundBandwidth.action.cirAction.ethernet.cosDepth1

       Possibilities:
               unchanged   (256)"
   ::= {er1646v2EthPortSwFVlanEntry 133316864}

er1646v2EthPortSwFVlanInbBwActCirActEthDei1 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth1

       Possibilities:
               unchanged   (255)
               clear   (0)
               set   (1)"
   ::= {er1646v2EthPortSwFVlanEntry 133321984}

er1646v2EthPortSwFVlanInbBwActCirActEthCos2 OBJECT-TYPE
   SYNTAX      INTEGER
               {
               unchanged (256)
               }
   MAX-ACCESS  read-write
   STATUS      current
   DESCRIPTION
      "Path: swPort.editConf.vlan.inboundBandwidth.action.cirAction.ethernet.cosDepth2

       Possibilities:
               unchanged   (256)"
   ::= {er1646v2EthPortSwFVlanEntry 133317120}

er1646v2EthPortSwFVlanInbBwActCirActEthDei2 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth2

       Possibilities:
               unchanged   (255)
               clear   (0)
               set   (1)"
   ::= {er1646v2EthPortSwFVlanEntry 133322240}

er1646v2EthPortSwFVlanInbBwActCirActEthCos3 OBJECT-TYPE
   SYNTAX      INTEGER
               {
               unchanged (256)
               }
   MAX-ACCESS  read-write
   STATUS      current
   DESCRIPTION
      "Path: swPort.editConf.vlan.inboundBandwidth.action.cirAction.ethernet.cosDepth3

       Possibilities:
               unchanged   (256)"
   ::= {er1646v2EthPortSwFVlanEntry 133317376}

er1646v2EthPortSwFVlanInbBwActCirActEthDei3 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth3

       Possibilities:
               unchanged   (255)
               clear   (0)
               set   (1)"
   ::= {er1646v2EthPortSwFVlanEntry 133322496}

er1646v2EthPortSwFVlanInbBwActCirActEthCos4 OBJECT-TYPE
   SYNTAX      INTEGER
               {
               unchanged (256)
               }
   MAX-ACCESS  read-write
   STATUS      current
   DESCRIPTION
      "Path: swPort.editConf.vlan.inboundBandwidth.action.cirAction.ethernet.cosDepth4

       Possibilities:
               unchanged   (256)"
   ::= {er1646v2EthPortSwFVlanEntry 133317632}

er1646v2EthPortSwFVlanInbBwActCirActEthDei4 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth4

       Possibilities:
               unchanged   (255)
               clear   (0)
               set   (1)"
   ::= {er1646v2EthPortSwFVlanEntry 133322752}

er1646v2EthPortSwFVlanInbBwActCirActEthCos5 OBJECT-TYPE
   SYNTAX      INTEGER
               {
               unchanged (256)
               }
   MAX-ACCESS  read-write
   STATUS      current
   DESCRIPTION
      "Path: swPort.editConf.vlan.inboundBandwidth.action.cirAction.ethernet.cosDepth5

       Possibilities:
               unchanged   (256)"
   ::= {er1646v2EthPortSwFVlanEntry 133317888}

er1646v2EthPortSwFVlanInbBwActCirActEthDei5 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth5

       Possibilities:
               unchanged   (255)
               clear   (0)
               set   (1)"
   ::= {er1646v2EthPortSwFVlanEntry 133323008}

er1646v2EthPortSwFVlanInbBwActCirActEthCos6 OBJECT-TYPE
   SYNTAX      INTEGER
               {
               unchanged (256)
               }
   MAX-ACCESS  read-write
   STATUS      current
   DESCRIPTION
      "Path: swPort.editConf.vlan.inboundBandwidth.action.cirAction.ethernet.cosDepth6

       Possibilities:
               unchanged   (256)"
   ::= {er1646v2EthPortSwFVlanEntry 133318144}

er1646v2EthPortSwFVlanInbBwActCirActEthDei6 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth6

       Possibilities:
               unchanged   (255)
               clear   (0)
               set   (1)"
   ::= {er1646v2EthPortSwFVlanEntry 133323264}

er1646v2EthPortSwFVlanInbBwActCirActEthCos7 OBJECT-TYPE
   SYNTAX      INTEGER
               {
               unchanged (256)
               }
   MAX-ACCESS  read-write
   STATUS      current
   DESCRIPTION
      "Path: swPort.editConf.vlan.inboundBandwidth.action.cirAction.ethernet.cosDepth7

       Possibilities:
               unchanged   (256)"
   ::= {er1646v2EthPortSwFVlanEntry 133318400}

er1646v2EthPortSwFVlanInbBwActCirActEthDei7 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth7

       Possibilities:
               unchanged   (255)
               clear   (0)
               set   (1)"
   ::= {er1646v2EthPortSwFVlanEntry 133323520}

er1646v2EthPortSwFVlanInbBwActCirActEthCos8 OBJECT-TYPE
   SYNTAX      INTEGER
               {
               unchanged (256)
               }
   MAX-ACCESS  read-write
   STATUS      current
   DESCRIPTION
      "Path: swPort.editConf.vlan.inboundBandwidth.action.cirAction.ethernet.cosDepth8

       Possibilities:
               unchanged   (256)"
   ::= {er1646v2EthPortSwFVlanEntry 133318656}

er1646v2EthPortSwFVlanInbBwActCirActEthDei8 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth8

       Possibilities:
               unchanged   (255)
               clear   (0)
               set   (1)"
   ::= {er1646v2EthPortSwFVlanEntry 133323776}

er1646v2EthPortSwFVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133318912}

er1646v2EthPortSwFVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133319168}

er1646v2EthPortSwFVlanInbBwActCirActEthDrpLev OBJECT-TYPE
   SYNTAX      INTEGER
               {
               unchanged (0)
               }
   MAX-ACCESS  read-write
   STATUS      current
   DESCRIPTION
      "Path: swPort.editConf.vlan.inboundBandwidth.action.cirAction.ethernet.dropLevel

       Possibilities:
               unchanged   (0)"
   ::= {er1646v2EthPortSwFVlanEntry 133319424}

er1646v2EthPortSwFVlanInbBwActCirActEthDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deFlag

       Possibilities:
               unchanged   (255)
               clear   (0)
               set   (1)"
   ::= {er1646v2EthPortSwFVlanEntry 133320192}

er1646v2EthPortSwFVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133343488}

er1646v2EthPortSwFVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133343744}

er1646v2EthPortSwFVlanInbBwActCirActIpDrpLev OBJECT-TYPE
   SYNTAX      INTEGER
               {
               unchanged (0)
               }
   MAX-ACCESS  read-write
   STATUS      current
   DESCRIPTION
      "Path: swPort.editConf.vlan.inboundBandwidth.action.cirAction.ip.dropLevel

       Possibilities:
               unchanged   (0)"
   ::= {er1646v2EthPortSwFVlanEntry 133344000}

er1646v2EthPortSwFVlanInbBwActCirActIpDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ip.deFlag

       Possibilities:
               unchanged   (255)
               clear   (0)
               set   (1)"
   ::= {er1646v2EthPortSwFVlanEntry 133344768}

er1646v2EthPortSwFVlanInbBwActEirActNone OBJECT-TYPE
   SYNTAX      OCTET STRING
   MAX-ACCESS  read-write
   STATUS      current
   DESCRIPTION
      "Path: swPort.editConf.vlan.inboundBandwidth.action.eirAction.none"
   ::= {er1646v2EthPortSwFVlanEntry 133439488}

er1646v2EthPortSwFVlanInbBwActEirActEthCos1 OBJECT-TYPE
   SYNTAX      INTEGER
               {
               unchanged (256)
               }
   MAX-ACCESS  read-write
   STATUS      current
   DESCRIPTION
      "Path: swPort.editConf.vlan.inboundBandwidth.action.eirAction.ethernet.cosDepth1

       Possibilities:
               unchanged   (256)"
   ::= {er1646v2EthPortSwFVlanEntry 133447936}

er1646v2EthPortSwFVlanInbBwActEirActEthDei1 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth1

       Possibilities:
               unchanged   (255)
               clear   (0)
               set   (1)"
   ::= {er1646v2EthPortSwFVlanEntry 133453056}

er1646v2EthPortSwFVlanInbBwActEirActEthCos2 OBJECT-TYPE
   SYNTAX      INTEGER
               {
               unchanged (256)
               }
   MAX-ACCESS  read-write
   STATUS      current
   DESCRIPTION
      "Path: swPort.editConf.vlan.inboundBandwidth.action.eirAction.ethernet.cosDepth2

       Possibilities:
               unchanged   (256)"
   ::= {er1646v2EthPortSwFVlanEntry 133448192}

er1646v2EthPortSwFVlanInbBwActEirActEthDei2 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth2

       Possibilities:
               unchanged   (255)
               clear   (0)
               set   (1)"
   ::= {er1646v2EthPortSwFVlanEntry 133453312}

er1646v2EthPortSwFVlanInbBwActEirActEthCos3 OBJECT-TYPE
   SYNTAX      INTEGER
               {
               unchanged (256)
               }
   MAX-ACCESS  read-write
   STATUS      current
   DESCRIPTION
      "Path: swPort.editConf.vlan.inboundBandwidth.action.eirAction.ethernet.cosDepth3

       Possibilities:
               unchanged   (256)"
   ::= {er1646v2EthPortSwFVlanEntry 133448448}

er1646v2EthPortSwFVlanInbBwActEirActEthDei3 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth3

       Possibilities:
               unchanged   (255)
               clear   (0)
               set   (1)"
   ::= {er1646v2EthPortSwFVlanEntry 133453568}

er1646v2EthPortSwFVlanInbBwActEirActEthCos4 OBJECT-TYPE
   SYNTAX      INTEGER
               {
               unchanged (256)
               }
   MAX-ACCESS  read-write
   STATUS      current
   DESCRIPTION
      "Path: swPort.editConf.vlan.inboundBandwidth.action.eirAction.ethernet.cosDepth4

       Possibilities:
               unchanged   (256)"
   ::= {er1646v2EthPortSwFVlanEntry 133448704}

er1646v2EthPortSwFVlanInbBwActEirActEthDei4 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth4

       Possibilities:
               unchanged   (255)
               clear   (0)
               set   (1)"
   ::= {er1646v2EthPortSwFVlanEntry 133453824}

er1646v2EthPortSwFVlanInbBwActEirActEthCos5 OBJECT-TYPE
   SYNTAX      INTEGER
               {
               unchanged (256)
               }
   MAX-ACCESS  read-write
   STATUS      current
   DESCRIPTION
      "Path: swPort.editConf.vlan.inboundBandwidth.action.eirAction.ethernet.cosDepth5

       Possibilities:
               unchanged   (256)"
   ::= {er1646v2EthPortSwFVlanEntry 133448960}

er1646v2EthPortSwFVlanInbBwActEirActEthDei5 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth5

       Possibilities:
               unchanged   (255)
               clear   (0)
               set   (1)"
   ::= {er1646v2EthPortSwFVlanEntry 133454080}

er1646v2EthPortSwFVlanInbBwActEirActEthCos6 OBJECT-TYPE
   SYNTAX      INTEGER
               {
               unchanged (256)
               }
   MAX-ACCESS  read-write
   STATUS      current
   DESCRIPTION
      "Path: swPort.editConf.vlan.inboundBandwidth.action.eirAction.ethernet.cosDepth6

       Possibilities:
               unchanged   (256)"
   ::= {er1646v2EthPortSwFVlanEntry 133449216}

er1646v2EthPortSwFVlanInbBwActEirActEthDei6 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth6

       Possibilities:
               unchanged   (255)
               clear   (0)
               set   (1)"
   ::= {er1646v2EthPortSwFVlanEntry 133454336}

er1646v2EthPortSwFVlanInbBwActEirActEthCos7 OBJECT-TYPE
   SYNTAX      INTEGER
               {
               unchanged (256)
               }
   MAX-ACCESS  read-write
   STATUS      current
   DESCRIPTION
      "Path: swPort.editConf.vlan.inboundBandwidth.action.eirAction.ethernet.cosDepth7

       Possibilities:
               unchanged   (256)"
   ::= {er1646v2EthPortSwFVlanEntry 133449472}

er1646v2EthPortSwFVlanInbBwActEirActEthDei7 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth7

       Possibilities:
               unchanged   (255)
               clear   (0)
               set   (1)"
   ::= {er1646v2EthPortSwFVlanEntry 133454592}

er1646v2EthPortSwFVlanInbBwActEirActEthCos8 OBJECT-TYPE
   SYNTAX      INTEGER
               {
               unchanged (256)
               }
   MAX-ACCESS  read-write
   STATUS      current
   DESCRIPTION
      "Path: swPort.editConf.vlan.inboundBandwidth.action.eirAction.ethernet.cosDepth8

       Possibilities:
               unchanged   (256)"
   ::= {er1646v2EthPortSwFVlanEntry 133449728}

er1646v2EthPortSwFVlanInbBwActEirActEthDei8 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth8

       Possibilities:
               unchanged   (255)
               clear   (0)
               set   (1)"
   ::= {er1646v2EthPortSwFVlanEntry 133454848}

er1646v2EthPortSwFVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133449984}

er1646v2EthPortSwFVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133450240}

er1646v2EthPortSwFVlanInbBwActEirActEthDrpLev OBJECT-TYPE
   SYNTAX      INTEGER
               {
               unchanged (0)
               }
   MAX-ACCESS  read-write
   STATUS      current
   DESCRIPTION
      "Path: swPort.editConf.vlan.inboundBandwidth.action.eirAction.ethernet.dropLevel

       Possibilities:
               unchanged   (0)"
   ::= {er1646v2EthPortSwFVlanEntry 133450496}

er1646v2EthPortSwFVlanInbBwActEirActEthDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deFlag

       Possibilities:
               unchanged   (255)
               clear   (0)
               set   (1)"
   ::= {er1646v2EthPortSwFVlanEntry 133451264}

er1646v2EthPortSwFVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133474560}

er1646v2EthPortSwFVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133474816}

er1646v2EthPortSwFVlanInbBwActEirActIpDrpLev OBJECT-TYPE
   SYNTAX      INTEGER
               {
               unchanged (0)
               }
   MAX-ACCESS  read-write
   STATUS      current
   DESCRIPTION
      "Path: swPort.editConf.vlan.inboundBandwidth.action.eirAction.ip.dropLevel

       Possibilities:
               unchanged   (0)"
   ::= {er1646v2EthPortSwFVlanEntry 133475072}

er1646v2EthPortSwFVlanInbBwActEirActIpDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ip.deFlag

       Possibilities:
               unchanged   (255)
               clear   (0)
               set   (1)"
   ::= {er1646v2EthPortSwFVlanEntry 133475840}

er1646v2EthPortSwFVlanInbBwActViolActNone OBJECT-TYPE
   SYNTAX      OCTET STRING
   MAX-ACCESS  read-write
   STATUS      current
   DESCRIPTION
      "Path: swPort.editConf.vlan.inboundBandwidth.action.violateAction.none"
   ::= {er1646v2EthPortSwFVlanEntry 133570560}

er1646v2EthPortSwFVlanInbBwActViolActDrop OBJECT-TYPE
   SYNTAX      OCTET STRING
   MAX-ACCESS  read-write
   STATUS      current
   DESCRIPTION
      "Path: swPort.editConf.vlan.inboundBandwidth.action.violateAction.drop"
   ::= {er1646v2EthPortSwFVlanEntry 133586944}

er1646v2EthPortSwFVlanInbBwActViolActEthCos1 OBJECT-TYPE
   SYNTAX      INTEGER
               {
               unchanged (256)
               }
   MAX-ACCESS  read-write
   STATUS      current
   DESCRIPTION
      "Path: swPort.editConf.vlan.inboundBandwidth.action.violateAction.ethernet.cosDepth1

       Possibilities:
               unchanged   (256)"
   ::= {er1646v2EthPortSwFVlanEntry 133579008}

er1646v2EthPortSwFVlanInbBwActViolActEthDei1 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth1

       Possibilities:
               unchanged   (255)
               clear   (0)
               set   (1)"
   ::= {er1646v2EthPortSwFVlanEntry 133584128}

er1646v2EthPortSwFVlanInbBwActViolActEthCos2 OBJECT-TYPE
   SYNTAX      INTEGER
               {
               unchanged (256)
               }
   MAX-ACCESS  read-write
   STATUS      current
   DESCRIPTION
      "Path: swPort.editConf.vlan.inboundBandwidth.action.violateAction.ethernet.cosDepth2

       Possibilities:
               unchanged   (256)"
   ::= {er1646v2EthPortSwFVlanEntry 133579264}

er1646v2EthPortSwFVlanInbBwActViolActEthDei2 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth2

       Possibilities:
               unchanged   (255)
               clear   (0)
               set   (1)"
   ::= {er1646v2EthPortSwFVlanEntry 133584384}

er1646v2EthPortSwFVlanInbBwActViolActEthCos3 OBJECT-TYPE
   SYNTAX      INTEGER
               {
               unchanged (256)
               }
   MAX-ACCESS  read-write
   STATUS      current
   DESCRIPTION
      "Path: swPort.editConf.vlan.inboundBandwidth.action.violateAction.ethernet.cosDepth3

       Possibilities:
               unchanged   (256)"
   ::= {er1646v2EthPortSwFVlanEntry 133579520}

er1646v2EthPortSwFVlanInbBwActViolActEthDei3 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth3

       Possibilities:
               unchanged   (255)
               clear   (0)
               set   (1)"
   ::= {er1646v2EthPortSwFVlanEntry 133584640}

er1646v2EthPortSwFVlanInbBwActViolActEthCos4 OBJECT-TYPE
   SYNTAX      INTEGER
               {
               unchanged (256)
               }
   MAX-ACCESS  read-write
   STATUS      current
   DESCRIPTION
      "Path: swPort.editConf.vlan.inboundBandwidth.action.violateAction.ethernet.cosDepth4

       Possibilities:
               unchanged   (256)"
   ::= {er1646v2EthPortSwFVlanEntry 133579776}

er1646v2EthPortSwFVlanInbBwActViolActEthDei4 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth4

       Possibilities:
               unchanged   (255)
               clear   (0)
               set   (1)"
   ::= {er1646v2EthPortSwFVlanEntry 133584896}

er1646v2EthPortSwFVlanInbBwActViolActEthCos5 OBJECT-TYPE
   SYNTAX      INTEGER
               {
               unchanged (256)
               }
   MAX-ACCESS  read-write
   STATUS      current
   DESCRIPTION
      "Path: swPort.editConf.vlan.inboundBandwidth.action.violateAction.ethernet.cosDepth5

       Possibilities:
               unchanged   (256)"
   ::= {er1646v2EthPortSwFVlanEntry 133580032}

er1646v2EthPortSwFVlanInbBwActViolActEthDei5 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth5

       Possibilities:
               unchanged   (255)
               clear   (0)
               set   (1)"
   ::= {er1646v2EthPortSwFVlanEntry 133585152}

er1646v2EthPortSwFVlanInbBwActViolActEthCos6 OBJECT-TYPE
   SYNTAX      INTEGER
               {
               unchanged (256)
               }
   MAX-ACCESS  read-write
   STATUS      current
   DESCRIPTION
      "Path: swPort.editConf.vlan.inboundBandwidth.action.violateAction.ethernet.cosDepth6

       Possibilities:
               unchanged   (256)"
   ::= {er1646v2EthPortSwFVlanEntry 133580288}

er1646v2EthPortSwFVlanInbBwActViolActEthDei6 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth6

       Possibilities:
               unchanged   (255)
               clear   (0)
               set   (1)"
   ::= {er1646v2EthPortSwFVlanEntry 133585408}

er1646v2EthPortSwFVlanInbBwActViolActEthCos7 OBJECT-TYPE
   SYNTAX      INTEGER
               {
               unchanged (256)
               }
   MAX-ACCESS  read-write
   STATUS      current
   DESCRIPTION
      "Path: swPort.editConf.vlan.inboundBandwidth.action.violateAction.ethernet.cosDepth7

       Possibilities:
               unchanged   (256)"
   ::= {er1646v2EthPortSwFVlanEntry 133580544}

er1646v2EthPortSwFVlanInbBwActViolActEthDei7 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth7

       Possibilities:
               unchanged   (255)
               clear   (0)
               set   (1)"
   ::= {er1646v2EthPortSwFVlanEntry 133585664}

er1646v2EthPortSwFVlanInbBwActViolActEthCos8 OBJECT-TYPE
   SYNTAX      INTEGER
               {
               unchanged (256)
               }
   MAX-ACCESS  read-write
   STATUS      current
   DESCRIPTION
      "Path: swPort.editConf.vlan.inboundBandwidth.action.violateAction.ethernet.cosDepth8

       Possibilities:
               unchanged   (256)"
   ::= {er1646v2EthPortSwFVlanEntry 133580800}

er1646v2EthPortSwFVlanInbBwActViolActEthDei8 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth8

       Possibilities:
               unchanged   (255)
               clear   (0)
               set   (1)"
   ::= {er1646v2EthPortSwFVlanEntry 133585920}

er1646v2EthPortSwFVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133581056}

er1646v2EthPortSwFVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133581312}

er1646v2EthPortSwFVlanInbBwActViolActEthDrpLev OBJECT-TYPE
   SYNTAX      INTEGER
               {
               unchanged (0)
               }
   MAX-ACCESS  read-write
   STATUS      current
   DESCRIPTION
      "Path: swPort.editConf.vlan.inboundBandwidth.action.violateAction.ethernet.dropLevel

       Possibilities:
               unchanged   (0)"
   ::= {er1646v2EthPortSwFVlanEntry 133581568}

er1646v2EthPortSwFVlanInbBwActViolActEthDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deFlag

       Possibilities:
               unchanged   (255)
               clear   (0)
               set   (1)"
   ::= {er1646v2EthPortSwFVlanEntry 133582336}

er1646v2EthPortSwFVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanEntry 133605632}

er1646v2EthPortSwFVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanEntry 133605888}

er1646v2EthPortSwFVlanInbBwActViolActIpDrpLev OBJECT-TYPE
   SYNTAX      INTEGER
               {
               unchanged (0)
               }
   MAX-ACCESS  read-write
   STATUS      current
   DESCRIPTION
      "Path: swPort.editConf.vlan.inboundBandwidth.action.violateAction.ip.dropLevel

       Possibilities:
               unchanged   (0)"
   ::= {er1646v2EthPortSwFVlanEntry 133606144}

er1646v2EthPortSwFVlanInbBwActViolActIpDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ip.deFlag

       Possibilities:
               unchanged   (255)
               clear   (0)
               set   (1)"
   ::= {er1646v2EthPortSwFVlanEntry 133606912}

er1646v2EthPortSwFVlanPppoE OBJECT-TYPE
   SYNTAX      INTEGER
               {
               disabled (0),
               enabled (1)
               }
   MAX-ACCESS  read-write
   STATUS      current
   DESCRIPTION
      "Path: swPort.editConf.vlan.pppoE

       Possibilities:
               disabled   (0)
               enabled   (1)"
   ::= {er1646v2EthPortSwFVlanEntry 838860800}

er1646v2EthPortSwFVlanPppLnkMOperation OBJECT-TYPE
   SYNTAX      INTEGER
               {
               disabled (0),
               enabled (1)
               }
   MAX-ACCESS  read-write
   STATUS      current
   DESCRIPTION
      "Path: swPort.editConf.vlan.ppp.linkMonitoring.operation

       Possibilities:
               disabled   (0)
               enabled   (1)"
   ::= {er1646v2EthPortSwFVlanEntry 251724032}

er1646v2EthPortSwFVlanPppLnkMInterval OBJECT-TYPE
   SYNTAX      TimeTicks
   MAX-ACCESS  read-write
   STATUS      current
   DESCRIPTION
      "Path: swPort.editConf.vlan.ppp.linkMonitoring.interval

       Time in centi-second."
   ::= {er1646v2EthPortSwFVlanEntry 251724288}

er1646v2EthPortSwFVlanPppLnkMRepTimeOut OBJECT-TYPE
   SYNTAX      TimeTicks
   MAX-ACCESS  read-write
   STATUS      current
   DESCRIPTION
      "Path: swPort.editConf.vlan.ppp.linkMonitoring.replyTimeOut

       Time in centi-second."
   ::= {er1646v2EthPortSwFVlanEntry 251724544}

er1646v2EthPortSwFVlanPppLnkMFailsPrmt OBJECT-TYPE
   SYNTAX      Integer32
   MAX-ACCESS  read-write
   STATUS      current
   DESCRIPTION
      "Path: swPort.editConf.vlan.ppp.linkMonitoring.failsPermitted"
   ::= {er1646v2EthPortSwFVlanEntry 251724800}

er1646v2EthPortSwFVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.vlan.ppp.authentication

       Possibilities:
               disabled   (0)
               chap   (1)
               pap   (2)
               chapOrPap   (3)
               msChap   (4)
               msChapV2   (5)"
   ::= {er1646v2EthPortSwFVlanEntry 251789312}

er1646v2EthPortSwFVlanPppAuthenPeriod OBJECT-TYPE
   SYNTAX      TimeTicks
   MAX-ACCESS  read-write
   STATUS      current
   DESCRIPTION
      "Path: swPort.editConf.vlan.ppp.authenPeriod

       Time in centi-second."
   ::= {er1646v2EthPortSwFVlanEntry 251854848}

er1646v2EthPortSwFVlanPppSessionName OBJECT-TYPE
   SYNTAX      DisplayString
   MAX-ACCESS  read-write
   STATUS      current
   DESCRIPTION
      "Path: swPort.editConf.vlan.ppp.sessionName"
   ::= {er1646v2EthPortSwFVlanEntry 251985920}

er1646v2EthPortSwFVlanPppSessionSecret OBJECT-TYPE
   SYNTAX      DisplayString
   MAX-ACCESS  read-write
   STATUS      current
   DESCRIPTION
      "Path: swPort.editConf.vlan.ppp.sessionSecret"
   ::= {er1646v2EthPortSwFVlanEntry 252051456}

er1646v2EthPortSwFVlanPppEncModeSessionSecret OBJECT-TYPE
   SYNTAX      INTEGER
               {
               none (1),
               encrypt (2),
               encType1 (3),
               invalid (128)
               }
   MAX-ACCESS  read-write
   STATUS      current
   DESCRIPTION
      "Path: swPort.editConf.vlan.ppp.encModeSessionSecret

       Possibilities:
               none   (1)
               encrypt   (2)
               encType1   (3)
               invalid   (128)"
   ::= {er1646v2EthPortSwFVlanEntry 252182528}

er1646v2EthPortSwFVlanPppEncSessionSecret OBJECT-TYPE
   SYNTAX      DisplayString
   MAX-ACCESS  read-write
   STATUS      current
   DESCRIPTION
      "Path: swPort.editConf.vlan.ppp.encSessionSecret"
   ::= {er1646v2EthPortSwFVlanEntry 252248064}

er1646v2EthPortSwFVlanPppServiceName OBJECT-TYPE
   SYNTAX      DisplayString
   MAX-ACCESS  read-write
   STATUS      current
   DESCRIPTION
      "Path: swPort.editConf.vlan.ppp.serviceName"
   ::= {er1646v2EthPortSwFVlanEntry 252116992}

er1646v2EthPortSwFVlanPbbMode OBJECT-TYPE
   SYNTAX      INTEGER
               {
               disabled (0),
               static (1),
               dynamicPtp (2),
               dynamicPtmp (3)
               }
   MAX-ACCESS  read-write
   STATUS      current
   DESCRIPTION
      "Path: swPort.editConf.vlan.pbb.mode

       Possibilities:
               disabled   (0)
               static   (1)
               dynamicPtp   (2)
               dynamicPtmp   (3)"
   ::= {er1646v2EthPortSwFVlanEntry 1174667264}

er1646v2EthPortSwFVlanPbbTxCos OBJECT-TYPE
   SYNTAX      Integer32
   MAX-ACCESS  read-write
   STATUS      current
   DESCRIPTION
      "Path: swPort.editConf.vlan.pbb.txCos"
   ::= {er1646v2EthPortSwFVlanEntry 1175191552}

er1646v2EthPortSwFVlanPbbIsid OBJECT-TYPE
   SYNTAX      Integer32
   MAX-ACCESS  read-write
   STATUS      current
   DESCRIPTION
      "Path: swPort.editConf.vlan.pbb.isid"
   ::= {er1646v2EthPortSwFVlanEntry 1175453696}

er1646v2EthPortSwFVlanPbbDestMac OBJECT-TYPE
   SYNTAX      OCTET STRING
   MAX-ACCESS  read-write
   STATUS      current
   DESCRIPTION
      "Path: swPort.editConf.vlan.pbb.destMac

       MAC address."
   ::= {er1646v2EthPortSwFVlanEntry 1175715840}

er1646v2EthPortSwFVlanPbbCustomGroupMac OBJECT-TYPE
   SYNTAX      OCTET STRING
   MAX-ACCESS  read-write
   STATUS      current
   DESCRIPTION
      "Path: swPort.editConf.vlan.pbb.customGroupMac

       MAC address."
   ::= {er1646v2EthPortSwFVlanEntry 1175977984}

er1646v2EthPortSwFVlanIpSaddr OBJECT-TYPE
   SYNTAX      SEQUENCE OF Er1646v2EthPortSwFVlanIpSaddrEntry
   MAX-ACCESS  not-accessible
   STATUS      current
   DESCRIPTION
      ""
   ::= {er1646v2EthPortSwFVlan 51838976}

er1646v2EthPortSwFVlanIpSaddrEntry OBJECT-TYPE
   SYNTAX      Er1646v2EthPortSwFVlanIpSaddrEntry
   MAX-ACCESS  not-accessible
   STATUS      current
   DESCRIPTION
      ""
   INDEX      { er1646v2EthPortSwFVlanIpSaddrGlobalIx,
                er1646v2EthPortSwFVlanTableIx,
                er1646v2EthPortSwFVlanIpSaddrTableIx }
   ::= {er1646v2EthPortSwFVlanIpSaddr 1}

Er1646v2EthPortSwFVlanIpSaddrEntry ::=
   SEQUENCE
      {
      er1646v2EthPortSwFVlanIpSaddrActions
         VariableLengthTableActions,
      er1646v2EthPortSwFVlanIpSaddrGlobalIx
         GlobalIndex,
      er1646v2EthPortSwFVlanIpSaddrTableIx
         TableIndex,
      er1646v2EthPortSwFVlanIpSaddrAddress
         IpAddress,
      er1646v2EthPortSwFVlanIpSaddrNetMask
         IpAddress
      }

er1646v2EthPortSwFVlanIpSaddrActions OBJECT-TYPE
   SYNTAX      VariableLengthTableActions
   MAX-ACCESS  read-write
   STATUS      current
   DESCRIPTION
      "By way of this field, some manipulations
       on this table may be performed."
   ::= {er1646v2EthPortSwFVlanIpSaddrEntry 2}

er1646v2EthPortSwFVlanIpSaddrGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpSaddrEntry 10}

er1646v2EthPortSwFVlanIpSaddrTableIx OBJECT-TYPE
   SYNTAX      TableIndex
   MAX-ACCESS  not-accessible
   STATUS      current
   DESCRIPTION
      ""
   ::= {er1646v2EthPortSwFVlanIpSaddrEntry 11}

er1646v2EthPortSwFVlanIpSaddrAddress OBJECT-TYPE
   SYNTAX      IpAddress
   MAX-ACCESS  read-write
   STATUS      current
   DESCRIPTION
      "Path: swPort.editConf.vlan.ip.secondaryIp.address"
   ::= {er1646v2EthPortSwFVlanIpSaddrEntry 2030043136}

er1646v2EthPortSwFVlanIpSaddrNetMask OBJECT-TYPE
   SYNTAX      IpAddress
   MAX-ACCESS  read-write
   STATUS      current
   DESCRIPTION
      "Path: swPort.editConf.vlan.ip.secondaryIp.netMask"
   ::= {er1646v2EthPortSwFVlanIpSaddrEntry 2063597568}

er1646v2EthPortSwFVlanIpH OBJECT-TYPE
   SYNTAX      SEQUENCE OF Er1646v2EthPortSwFVlanIpHEntry
   MAX-ACCESS  not-accessible
   STATUS      current
   DESCRIPTION
      ""
   ::= {er1646v2EthPortSwFVlan 51314688}

er1646v2EthPortSwFVlanIpHEntry OBJECT-TYPE
   SYNTAX      Er1646v2EthPortSwFVlanIpHEntry
   MAX-ACCESS  not-accessible
   STATUS      current
   DESCRIPTION
      ""
   INDEX      { er1646v2EthPortSwFVlanIpHGlobalIx,
                er1646v2EthPortSwFVlanTableIx,
                er1646v2EthPortSwFVlanIpHTableIx }
   ::= {er1646v2EthPortSwFVlanIpH 1}

Er1646v2EthPortSwFVlanIpHEntry ::=
   SEQUENCE
      {
      er1646v2EthPortSwFVlanIpHActions
         VariableLengthTableActions,
      er1646v2EthPortSwFVlanIpHGlobalIx
         GlobalIndex,
      er1646v2EthPortSwFVlanIpHTableIx
         TableIndex,
      er1646v2EthPortSwFVlanIpHAddress
         IpAddress,
      er1646v2EthPortSwFVlanIpHDhcpRelayOptionSubscriberId
         DisplayString
      }

er1646v2EthPortSwFVlanIpHActions OBJECT-TYPE
   SYNTAX      VariableLengthTableActions
   MAX-ACCESS  read-write
   STATUS      current
   DESCRIPTION
      "By way of this field, some manipulations
       on this table may be performed."
   ::= {er1646v2EthPortSwFVlanIpHEntry 2}

er1646v2EthPortSwFVlanIpHGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpHEntry 10}

er1646v2EthPortSwFVlanIpHTableIx OBJECT-TYPE
   SYNTAX      TableIndex
   MAX-ACCESS  not-accessible
   STATUS      current
   DESCRIPTION
      ""
   ::= {er1646v2EthPortSwFVlanIpHEntry 11}

er1646v2EthPortSwFVlanIpHAddress OBJECT-TYPE
   SYNTAX      IpAddress
   MAX-ACCESS  read-write
   STATUS      current
   DESCRIPTION
      "Path: swPort.editConf.vlan.ip.helpers.address"
   ::= {er1646v2EthPortSwFVlanIpHEntry 16777216}

er1646v2EthPortSwFVlanIpHDhcpRelayOptionSubscriberId OBJECT-TYPE
   SYNTAX      DisplayString
   MAX-ACCESS  read-write
   STATUS      current
   DESCRIPTION
      "Path: swPort.editConf.vlan.ip.helpers.dhcpRelayOption.subscriberId"
   ::= {er1646v2EthPortSwFVlanIpHEntry 33947648}

er1646v2EthPortSwFVlanIpV6Addresses OBJECT-TYPE
   SYNTAX      SEQUENCE OF Er1646v2EthPortSwFVlanIpV6AddressesEntry
   MAX-ACCESS  not-accessible
   STATUS      current
   DESCRIPTION
      ""
   ::= {er1646v2EthPortSwFVlan 704839680}

er1646v2EthPortSwFVlanIpV6AddressesEntry OBJECT-TYPE
   SYNTAX      Er1646v2EthPortSwFVlanIpV6AddressesEntry
   MAX-ACCESS  not-accessible
   STATUS      current
   DESCRIPTION
      ""
   INDEX      { er1646v2EthPortSwFVlanIpV6AddressesGlobalIx,
                er1646v2EthPortSwFVlanTableIx,
                er1646v2EthPortSwFVlanIpV6AddressesTableIx }
   ::= {er1646v2EthPortSwFVlanIpV6Addresses 1}

Er1646v2EthPortSwFVlanIpV6AddressesEntry ::=
   SEQUENCE
      {
      er1646v2EthPortSwFVlanIpV6AddressesActions
         VariableLengthTableActions,
      er1646v2EthPortSwFVlanIpV6AddressesGlobalIx
         GlobalIndex,
      er1646v2EthPortSwFVlanIpV6AddressesTableIx
         TableIndex,
      er1646v2EthPortSwFVlanIpV6AddressesType
         INTEGER,
      er1646v2EthPortSwFVlanIpV6AddressesAddress
         Ipv6Address,
      er1646v2EthPortSwFVlanIpV6AddressesPrefixLength
         Integer32,
      er1646v2EthPortSwFVlanIpV6AddressesGeneralPrefix
         DisplayString,
      er1646v2EthPortSwFVlanIpV6AddressesRaSend
         INTEGER,
      er1646v2EthPortSwFVlanIpV6AddressesRaOnLinkFlag
         INTEGER,
      er1646v2EthPortSwFVlanIpV6AddressesRaAutoFlag
         INTEGER,
      er1646v2EthPortSwFVlanIpV6AddressesRaValidLifeTime
         TimeTicks,
      er1646v2EthPortSwFVlanIpV6AddressesRaValidLTMode
         INTEGER,
      er1646v2EthPortSwFVlanIpV6AddressesRaPrefLifeTime
         TimeTicks,
      er1646v2EthPortSwFVlanIpV6AddressesRaPrefLTMode
         INTEGER
      }

er1646v2EthPortSwFVlanIpV6AddressesActions OBJECT-TYPE
   SYNTAX      VariableLengthTableActions
   MAX-ACCESS  read-write
   STATUS      current
   DESCRIPTION
      "By way of this field, some manipulations
       on this table may be performed."
   ::= {er1646v2EthPortSwFVlanIpV6AddressesEntry 2}

er1646v2EthPortSwFVlanIpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6AddressesEntry 10}

er1646v2EthPortSwFVlanIpV6AddressesTableIx OBJECT-TYPE
   SYNTAX      TableIndex
   MAX-ACCESS  not-accessible
   STATUS      current
   DESCRIPTION
      ""
   ::= {er1646v2EthPortSwFVlanIpV6AddressesEntry 11}

er1646v2EthPortSwFVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.vlan.ipV6.addresses.type

       Possibilities:
               unicast   (0)
               eui64   (1)
               anycast   (2)
               linkLocal   (3)
               generalPrefix   (4)"
   ::= {er1646v2EthPortSwFVlanIpV6AddressesEntry 50331648}

er1646v2EthPortSwFVlanIpV6AddressesAddress OBJECT-TYPE
   SYNTAX      Ipv6Address
   MAX-ACCESS  read-write
   STATUS      current
   DESCRIPTION
      "Path: swPort.editConf.vlan.ipV6.addresses.address

       ipv6 address"
   ::= {er1646v2EthPortSwFVlanIpV6AddressesEntry 16777216}

er1646v2EthPortSwFVlanIpV6AddressesPrefixLength OBJECT-TYPE
   SYNTAX      Integer32
   MAX-ACCESS  read-write
   STATUS      current
   DESCRIPTION
      "Path: swPort.editConf.vlan.ipV6.addresses.prefixLength"
   ::= {er1646v2EthPortSwFVlanIpV6AddressesEntry 33554432}

er1646v2EthPortSwFVlanIpV6AddressesGeneralPrefix OBJECT-TYPE
   SYNTAX      DisplayString
   MAX-ACCESS  read-write
   STATUS      current
   DESCRIPTION
      "Path: swPort.editConf.vlan.ipV6.addresses.generalPrefix"
   ::= {er1646v2EthPortSwFVlanIpV6AddressesEntry 83886080}

er1646v2EthPortSwFVlanIpV6AddressesRaSend OBJECT-TYPE
   SYNTAX      INTEGER
               {
               disabled (0),
               enabled (1)
               }
   MAX-ACCESS  read-write
   STATUS      current
   DESCRIPTION
      "Path: swPort.editConf.vlan.ipV6.addresses.ra.send

       Possibilities:
               disabled   (0)
               enabled   (1)"
   ::= {er1646v2EthPortSwFVlanIpV6AddressesEntry 67174400}

er1646v2EthPortSwFVlanIpV6AddressesRaOnLinkFlag OBJECT-TYPE
   SYNTAX      INTEGER
               {
               disabled (0),
               enabled (1)
               }
   MAX-ACCESS  read-write
   STATUS      current
   DESCRIPTION
      "Path: swPort.editConf.vlan.ipV6.addresses.ra.onLinkFlag

       Possibilities:
               disabled   (0)
               enabled   (1)"
   ::= {er1646v2EthPortSwFVlanIpV6AddressesEntry 67371008}

er1646v2EthPortSwFVlanIpV6AddressesRaAutoFlag OBJECT-TYPE
   SYNTAX      INTEGER
               {
               disabled (0),
               enabled (1)
               }
   MAX-ACCESS  read-write
   STATUS      current
   DESCRIPTION
      "Path: swPort.editConf.vlan.ipV6.addresses.ra.autonomousFlag

       Possibilities:
               disabled   (0)
               enabled   (1)"
   ::= {er1646v2EthPortSwFVlanIpV6AddressesEntry 67567616}

er1646v2EthPortSwFVlanIpV6AddressesRaValidLifeTime OBJECT-TYPE
   SYNTAX      TimeTicks
   MAX-ACCESS  read-write
   STATUS      current
   DESCRIPTION
      "Path: swPort.editConf.vlan.ipV6.addresses.ra.validLifeTime

       Time in centi-second."
   ::= {er1646v2EthPortSwFVlanIpV6AddressesEntry 67239936}

er1646v2EthPortSwFVlanIpV6AddressesRaValidLTMode OBJECT-TYPE
   SYNTAX      INTEGER
               {
               fixed (0),
               infinite (2)
               }
   MAX-ACCESS  read-write
   STATUS      current
   DESCRIPTION
      "Path: swPort.editConf.vlan.ipV6.addresses.ra.validLifeTimeMode

       Possibilities:
               fixed   (0)
               infinite   (2)"
   ::= {er1646v2EthPortSwFVlanIpV6AddressesEntry 67305472}

er1646v2EthPortSwFVlanIpV6AddressesRaPrefLifeTime OBJECT-TYPE
   SYNTAX      TimeTicks
   MAX-ACCESS  read-write
   STATUS      current
   DESCRIPTION
      "Path: swPort.editConf.vlan.ipV6.addresses.ra.prefLifeTime

       Time in centi-second."
   ::= {er1646v2EthPortSwFVlanIpV6AddressesEntry 67436544}

er1646v2EthPortSwFVlanIpV6AddressesRaPrefLTMode OBJECT-TYPE
   SYNTAX      INTEGER
               {
               fixed (0),
               infinite (2)
               }
   MAX-ACCESS  read-write
   STATUS      current
   DESCRIPTION
      "Path: swPort.editConf.vlan.ipV6.addresses.ra.prefLifeTimeMode

       Possibilities:
               fixed   (0)
               infinite   (2)"
   ::= {er1646v2EthPortSwFVlanIpV6AddressesEntry 67502080}

er1646v2EthPortSwFVlanIpV6RaDnsOptionsRdnssServers OBJECT-TYPE
   SYNTAX      SEQUENCE OF Er1646v2EthPortSwFVlanIpV6RaDnsOptionsRdnssServersEntry
   MAX-ACCESS  not-accessible
   STATUS      current
   DESCRIPTION
      ""
   ::= {er1646v2EthPortSwFVlan 705039144}

er1646v2EthPortSwFVlanIpV6RaDnsOptionsRdnssServersEntry OBJECT-TYPE
   SYNTAX      Er1646v2EthPortSwFVlanIpV6RaDnsOptionsRdnssServersEntry
   MAX-ACCESS  not-accessible
   STATUS      current
   DESCRIPTION
      ""
   INDEX      { er1646v2EthPortSwFVlanIpV6RaDnsOptionsRdnssServersGlobalIx,
                er1646v2EthPortSwFVlanTableIx,
                er1646v2EthPortSwFVlanIpV6RaDnsOptionsRdnssServersTableIx }
   ::= {er1646v2EthPortSwFVlanIpV6RaDnsOptionsRdnssServers 1}

Er1646v2EthPortSwFVlanIpV6RaDnsOptionsRdnssServersEntry ::=
   SEQUENCE
      {
      er1646v2EthPortSwFVlanIpV6RaDnsOptionsRdnssServersActions
         VariableLengthTableActions,
      er1646v2EthPortSwFVlanIpV6RaDnsOptionsRdnssServersGlobalIx
         GlobalIndex,
      er1646v2EthPortSwFVlanIpV6RaDnsOptionsRdnssServersTableIx
         TableIndex,
      er1646v2EthPortSwFVlanIpV6RaDnsOptionsRdnssServersAddress
         Ipv6Address
      }

er1646v2EthPortSwFVlanIpV6RaDnsOptionsRdnssServersActions OBJECT-TYPE
   SYNTAX      VariableLengthTableActions
   MAX-ACCESS  read-write
   STATUS      current
   DESCRIPTION
      "By way of this field, some manipulations
       on this table may be performed."
   ::= {er1646v2EthPortSwFVlanIpV6RaDnsOptionsRdnssServersEntry 2}

er1646v2EthPortSwFVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6RaDnsOptionsRdnssServersEntry 10}

er1646v2EthPortSwFVlanIpV6RaDnsOptionsRdnssServersTableIx OBJECT-TYPE
   SYNTAX      TableIndex
   MAX-ACCESS  not-accessible
   STATUS      current
   DESCRIPTION
      ""
   ::= {er1646v2EthPortSwFVlanIpV6RaDnsOptionsRdnssServersEntry 11}

er1646v2EthPortSwFVlanIpV6RaDnsOptionsRdnssServersAddress OBJECT-TYPE
   SYNTAX      Ipv6Address
   MAX-ACCESS  read-write
   STATUS      current
   DESCRIPTION
      "Path: swPort.editConf.vlan.ipV6.ra.dnsOptions.rdnss.servers.address

       ipv6 address"
   ::= {er1646v2EthPortSwFVlanIpV6RaDnsOptionsRdnssServersEntry 16777216}

er1646v2EthPortSwFVlanIpV6RaDnsOptionsDnsslDomains OBJECT-TYPE
   SYNTAX      SEQUENCE OF Er1646v2EthPortSwFVlanIpV6RaDnsOptionsDnsslDomainsEntry
   MAX-ACCESS  not-accessible
   STATUS      current
   DESCRIPTION
      ""
   ::= {er1646v2EthPortSwFVlan 705039176}

er1646v2EthPortSwFVlanIpV6RaDnsOptionsDnsslDomainsEntry OBJECT-TYPE
   SYNTAX      Er1646v2EthPortSwFVlanIpV6RaDnsOptionsDnsslDomainsEntry
   MAX-ACCESS  not-accessible
   STATUS      current
   DESCRIPTION
      ""
   INDEX      { er1646v2EthPortSwFVlanIpV6RaDnsOptionsDnsslDomainsGlobalIx,
                er1646v2EthPortSwFVlanTableIx,
                er1646v2EthPortSwFVlanIpV6RaDnsOptionsDnsslDomainsTableIx }
   ::= {er1646v2EthPortSwFVlanIpV6RaDnsOptionsDnsslDomains 1}

Er1646v2EthPortSwFVlanIpV6RaDnsOptionsDnsslDomainsEntry ::=
   SEQUENCE
      {
      er1646v2EthPortSwFVlanIpV6RaDnsOptionsDnsslDomainsActions
         VariableLengthTableActions,
      er1646v2EthPortSwFVlanIpV6RaDnsOptionsDnsslDomainsGlobalIx
         GlobalIndex,
      er1646v2EthPortSwFVlanIpV6RaDnsOptionsDnsslDomainsTableIx
         TableIndex,
      er1646v2EthPortSwFVlanIpV6RaDnsOptionsDnsslDomainsName
         DisplayString
      }

er1646v2EthPortSwFVlanIpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwFVlanIpV6RaDnsOptionsDnsslDomainsEntry 2}

er1646v2EthPortSwFVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6RaDnsOptionsDnsslDomainsEntry 10}

er1646v2EthPortSwFVlanIpV6RaDnsOptionsDnsslDomainsTableIx OBJECT-TYPE
   SYNTAX      TableIndex
   MAX-ACCESS  not-accessible
   STATUS      current
   DESCRIPTION
      ""
   ::= {er1646v2EthPortSwFVlanIpV6RaDnsOptionsDnsslDomainsEntry 11}

er1646v2EthPortSwFVlanIpV6RaDnsOptionsDnsslDomainsName OBJECT-TYPE
   SYNTAX      DisplayString
   MAX-ACCESS  read-write
   STATUS      current
   DESCRIPTION
      "Path: swPort.editConf.vlan.ipV6.ra.dnsOptions.dnssl.domains.name"
   ::= {er1646v2EthPortSwFVlanIpV6RaDnsOptionsDnsslDomainsEntry 16777216}

er1646v2EthPortSwFVlanIpV6DhcpClientUserClassOpt OBJECT-TYPE
   SYNTAX      SEQUENCE OF Er1646v2EthPortSwFVlanIpV6DhcpClientUserClassOptEntry
   MAX-ACCESS  not-accessible
   STATUS      current
   DESCRIPTION
      ""
   ::= {er1646v2EthPortSwFVlan 705312768}

er1646v2EthPortSwFVlanIpV6DhcpClientUserClassOptEntry OBJECT-TYPE
   SYNTAX      Er1646v2EthPortSwFVlanIpV6DhcpClientUserClassOptEntry
   MAX-ACCESS  not-accessible
   STATUS      current
   DESCRIPTION
      ""
   INDEX      { er1646v2EthPortSwFVlanIpV6DhcpClientUserClassOptGlobalIx,
                er1646v2EthPortSwFVlanTableIx,
                er1646v2EthPortSwFVlanIpV6DhcpClientUserClassOptTableIx }
   ::= {er1646v2EthPortSwFVlanIpV6DhcpClientUserClassOpt 1}

Er1646v2EthPortSwFVlanIpV6DhcpClientUserClassOptEntry ::=
   SEQUENCE
      {
      er1646v2EthPortSwFVlanIpV6DhcpClientUserClassOptActions
         VariableLengthTableActions,
      er1646v2EthPortSwFVlanIpV6DhcpClientUserClassOptGlobalIx
         GlobalIndex,
      er1646v2EthPortSwFVlanIpV6DhcpClientUserClassOptTableIx
         TableIndex,
      er1646v2EthPortSwFVlanIpV6DhcpClientUserClassOptValueAscii
         DisplayString,
      er1646v2EthPortSwFVlanIpV6DhcpClientUserClassOptValueDecimal
         Integer32,
      er1646v2EthPortSwFVlanIpV6DhcpClientUserClassOptValueHexData
         OCTET STRING
      }

er1646v2EthPortSwFVlanIpV6DhcpClientUserClassOptActions OBJECT-TYPE
   SYNTAX      VariableLengthTableActions
   MAX-ACCESS  read-write
   STATUS      current
   DESCRIPTION
      "By way of this field, some manipulations
       on this table may be performed."
   ::= {er1646v2EthPortSwFVlanIpV6DhcpClientUserClassOptEntry 2}

er1646v2EthPortSwFVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6DhcpClientUserClassOptEntry 10}

er1646v2EthPortSwFVlanIpV6DhcpClientUserClassOptTableIx OBJECT-TYPE
   SYNTAX      TableIndex
   MAX-ACCESS  not-accessible
   STATUS      current
   DESCRIPTION
      ""
   ::= {er1646v2EthPortSwFVlanIpV6DhcpClientUserClassOptEntry 11}

er1646v2EthPortSwFVlanIpV6DhcpClientUserClassOptValueAscii OBJECT-TYPE
   SYNTAX      DisplayString
   MAX-ACCESS  read-write
   STATUS      current
   DESCRIPTION
      "Path: swPort.editConf.vlan.ipV6.dhcp.client.userClassOpt.value.ascii"
   ::= {er1646v2EthPortSwFVlanIpV6DhcpClientUserClassOptEntry 16842752}

er1646v2EthPortSwFVlanIpV6DhcpClientUserClassOptValueDecimal OBJECT-TYPE
   SYNTAX      Integer32
   MAX-ACCESS  read-write
   STATUS      current
   DESCRIPTION
      "Path: swPort.editConf.vlan.ipV6.dhcp.client.userClassOpt.value.decimal"
   ::= {er1646v2EthPortSwFVlanIpV6DhcpClientUserClassOptEntry 16908288}

er1646v2EthPortSwFVlanIpV6DhcpClientUserClassOptValueHexData OBJECT-TYPE
   SYNTAX      OCTET STRING
   MAX-ACCESS  read-write
   STATUS      current
   DESCRIPTION
      "Path: swPort.editConf.vlan.ipV6.dhcp.client.userClassOpt.value.hexData"
   ::= {er1646v2EthPortSwFVlanIpV6DhcpClientUserClassOptEntry 16973824}

er1646v2EthPortSwFVlanIpV6DhcpClientVendorCl OBJECT-TYPE
   SYNTAX      SEQUENCE OF Er1646v2EthPortSwFVlanIpV6DhcpClientVendorClEntry
   MAX-ACCESS  not-accessible
   STATUS      current
   DESCRIPTION
      ""
   ::= {er1646v2EthPortSwFVlan 705313792}

er1646v2EthPortSwFVlanIpV6DhcpClientVendorClEntry OBJECT-TYPE
   SYNTAX      Er1646v2EthPortSwFVlanIpV6DhcpClientVendorClEntry
   MAX-ACCESS  not-accessible
   STATUS      current
   DESCRIPTION
      ""
   INDEX      { er1646v2EthPortSwFVlanIpV6DhcpClientVendorClGlobalIx,
                er1646v2EthPortSwFVlanTableIx,
                er1646v2EthPortSwFVlanIpV6DhcpClientVendorClTableIx }
   ::= {er1646v2EthPortSwFVlanIpV6DhcpClientVendorCl 1}

Er1646v2EthPortSwFVlanIpV6DhcpClientVendorClEntry ::=
   SEQUENCE
      {
      er1646v2EthPortSwFVlanIpV6DhcpClientVendorClActions
         VariableLengthTableActions,
      er1646v2EthPortSwFVlanIpV6DhcpClientVendorClGlobalIx
         GlobalIndex,
      er1646v2EthPortSwFVlanIpV6DhcpClientVendorClTableIx
         TableIndex,
      er1646v2EthPortSwFVlanIpV6DhcpClientVendorClValueAscii
         DisplayString,
      er1646v2EthPortSwFVlanIpV6DhcpClientVendorClValueDecimal
         Integer32,
      er1646v2EthPortSwFVlanIpV6DhcpClientVendorClValueHexData
         OCTET STRING
      }

er1646v2EthPortSwFVlanIpV6DhcpClientVendorClActions OBJECT-TYPE
   SYNTAX      VariableLengthTableActions
   MAX-ACCESS  read-write
   STATUS      current
   DESCRIPTION
      "By way of this field, some manipulations
       on this table may be performed."
   ::= {er1646v2EthPortSwFVlanIpV6DhcpClientVendorClEntry 2}

er1646v2EthPortSwFVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6DhcpClientVendorClEntry 10}

er1646v2EthPortSwFVlanIpV6DhcpClientVendorClTableIx OBJECT-TYPE
   SYNTAX      TableIndex
   MAX-ACCESS  not-accessible
   STATUS      current
   DESCRIPTION
      ""
   ::= {er1646v2EthPortSwFVlanIpV6DhcpClientVendorClEntry 11}

er1646v2EthPortSwFVlanIpV6DhcpClientVendorClValueAscii OBJECT-TYPE
   SYNTAX      DisplayString
   MAX-ACCESS  read-write
   STATUS      current
   DESCRIPTION
      "Path: swPort.editConf.vlan.ipV6.dhcp.client.vendorClassOpt.value.ascii"
   ::= {er1646v2EthPortSwFVlanIpV6DhcpClientVendorClEntry 16842752}

er1646v2EthPortSwFVlanIpV6DhcpClientVendorClValueDecimal OBJECT-TYPE
   SYNTAX      Integer32
   MAX-ACCESS  read-write
   STATUS      current
   DESCRIPTION
      "Path: swPort.editConf.vlan.ipV6.dhcp.client.vendorClassOpt.value.decimal"
   ::= {er1646v2EthPortSwFVlanIpV6DhcpClientVendorClEntry 16908288}

er1646v2EthPortSwFVlanIpV6DhcpClientVendorClValueHexData OBJECT-TYPE
   SYNTAX      OCTET STRING
   MAX-ACCESS  read-write
   STATUS      current
   DESCRIPTION
      "Path: swPort.editConf.vlan.ipV6.dhcp.client.vendorClassOpt.value.hexData"
   ::= {er1646v2EthPortSwFVlanIpV6DhcpClientVendorClEntry 16973824}

er1646v2EthPortSwFVlanIpV6DhcpRelayDestinations OBJECT-TYPE
   SYNTAX      SEQUENCE OF Er1646v2EthPortSwFVlanIpV6DhcpRelayDestinationsEntry
   MAX-ACCESS  not-accessible
   STATUS      current
   DESCRIPTION
      ""
   ::= {er1646v2EthPortSwFVlan 705323072}

er1646v2EthPortSwFVlanIpV6DhcpRelayDestinationsEntry OBJECT-TYPE
   SYNTAX      Er1646v2EthPortSwFVlanIpV6DhcpRelayDestinationsEntry
   MAX-ACCESS  not-accessible
   STATUS      current
   DESCRIPTION
      ""
   INDEX      { er1646v2EthPortSwFVlanIpV6DhcpRelayDestinationsGlobalIx,
                er1646v2EthPortSwFVlanTableIx,
                er1646v2EthPortSwFVlanIpV6DhcpRelayDestinationsTableIx }
   ::= {er1646v2EthPortSwFVlanIpV6DhcpRelayDestinations 1}

Er1646v2EthPortSwFVlanIpV6DhcpRelayDestinationsEntry ::=
   SEQUENCE
      {
      er1646v2EthPortSwFVlanIpV6DhcpRelayDestinationsActions
         VariableLengthTableActions,
      er1646v2EthPortSwFVlanIpV6DhcpRelayDestinationsGlobalIx
         GlobalIndex,
      er1646v2EthPortSwFVlanIpV6DhcpRelayDestinationsTableIx
         TableIndex,
      er1646v2EthPortSwFVlanIpV6DhcpRelayDestinationsAddress
         Ipv6Address,
      er1646v2EthPortSwFVlanIpV6DhcpRelayDestinationsInterface
         DisplayString
      }

er1646v2EthPortSwFVlanIpV6DhcpRelayDestinationsActions OBJECT-TYPE
   SYNTAX      VariableLengthTableActions
   MAX-ACCESS  read-write
   STATUS      current
   DESCRIPTION
      "By way of this field, some manipulations
       on this table may be performed."
   ::= {er1646v2EthPortSwFVlanIpV6DhcpRelayDestinationsEntry 2}

er1646v2EthPortSwFVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwFVlanIpV6DhcpRelayDestinationsEntry 10}

er1646v2EthPortSwFVlanIpV6DhcpRelayDestinationsTableIx OBJECT-TYPE
   SYNTAX      TableIndex
   MAX-ACCESS  not-accessible
   STATUS      current
   DESCRIPTION
      ""
   ::= {er1646v2EthPortSwFVlanIpV6DhcpRelayDestinationsEntry 11}

er1646v2EthPortSwFVlanIpV6DhcpRelayDestinationsAddress OBJECT-TYPE
   SYNTAX      Ipv6Address
   MAX-ACCESS  read-write
   STATUS      current
   DESCRIPTION
      "Path: swPort.editConf.vlan.ipV6.dhcp.relay.destinations.address

       ipv6 address"
   ::= {er1646v2EthPortSwFVlanIpV6DhcpRelayDestinationsEntry 16777216}

er1646v2EthPortSwFVlanIpV6DhcpRelayDestinationsInterface OBJECT-TYPE
   SYNTAX      DisplayString
   MAX-ACCESS  read-write
   STATUS      current
   DESCRIPTION
      "Path: swPort.editConf.vlan.ipV6.dhcp.relay.destinations.interface"
   ::= {er1646v2EthPortSwFVlanIpV6DhcpRelayDestinationsEntry 33554432}

er1646v2EthPortSwFVlanBridgingVlTVlans OBJECT-TYPE
   SYNTAX      SEQUENCE OF Er1646v2EthPortSwFVlanBridgingVlTVlansEntry
   MAX-ACCESS  not-accessible
   STATUS      current
   DESCRIPTION
      ""
   ::= {er1646v2EthPortSwFVlan 459079680}

er1646v2EthPortSwFVlanBridgingVlTVlansEntry OBJECT-TYPE
   SYNTAX      Er1646v2EthPortSwFVlanBridgingVlTVlansEntry
   MAX-ACCESS  not-accessible
   STATUS      current
   DESCRIPTION
      ""
   INDEX      { er1646v2EthPortSwFVlanBridgingVlTVlansGlobalIx,
                er1646v2EthPortSwFVlanTableIx,
                er1646v2EthPortSwFVlanBridgingVlTVlansTableIx }
   ::= {er1646v2EthPortSwFVlanBridgingVlTVlans 1}

Er1646v2EthPortSwFVlanBridgingVlTVlansEntry ::=
   SEQUENCE
      {
      er1646v2EthPortSwFVlanBridgingVlTVlansActions
         VariableLengthTableActions,
      er1646v2EthPortSwFVlanBridgingVlTVlansGlobalIx
         GlobalIndex,
      er1646v2EthPortSwFVlanBridgingVlTVlansTableIx
         TableIndex,
      er1646v2EthPortSwFVlanBridgingVlTVlansVid
         Integer32,
      er1646v2EthPortSwFVlanBridgingVlTVlansEndVid
         Integer32,
      er1646v2EthPortSwFVlanBridgingVlTVlansAction
         INTEGER,
      er1646v2EthPortSwFVlanBridgingVlTVlansTagInfoTpid
         INTEGER,
      er1646v2EthPortSwFVlanBridgingVlTVlansTagInfoVid
         Integer32
      }

er1646v2EthPortSwFVlanBridgingVlTVlansActions OBJECT-TYPE
   SYNTAX      VariableLengthTableActions
   MAX-ACCESS  read-write
   STATUS      current
   DESCRIPTION
      "By way of this field, some manipulations
       on this table may be performed."
   ::= {er1646v2EthPortSwFVlanBridgingVlTVlansEntry 2}

er1646v2EthPortSwFVlanBridgingVlTVlansGlobalIx OBJECT-TYPE
   SYNTAX      GlobalIndex
   MAX-ACCESS  not-accessible
   STATUS      current
   DESCRIPTION
      "The value of the tlsCntTreeGlobalIndex of the MANAGED OBJECT."
   ::= {er1646v2EthPortSwFVlanBridgingVlTVlansEntry 10}

er1646v2EthPortSwFVlanBridgingVlTVlansTableIx OBJECT-TYPE
   SYNTAX      TableIndex
   MAX-ACCESS  not-accessible
   STATUS      current
   DESCRIPTION
      ""
   ::= {er1646v2EthPortSwFVlanBridgingVlTVlansEntry 11}

er1646v2EthPortSwFVlanBridgingVlTVlansVid OBJECT-TYPE
   SYNTAX      Integer32
   MAX-ACCESS  read-write
   STATUS      current
   DESCRIPTION
      "Path: swPort.editConf.vlan.bridging.vlanTagging.vlans.vid"
   ::= {er1646v2EthPortSwFVlanBridgingVlTVlansEntry 536870912}

er1646v2EthPortSwFVlanBridgingVlTVlansEndVid OBJECT-TYPE
   SYNTAX      Integer32
   MAX-ACCESS  read-write
   STATUS      current
   DESCRIPTION
      "Path: swPort.editConf.vlan.bridging.vlanTagging.vlans.endVid"
   ::= {er1646v2EthPortSwFVlanBridgingVlTVlansEntry 2147483648}

er1646v2EthPortSwFVlanBridgingVlTVlansAction OBJECT-TYPE
   SYNTAX      INTEGER
               {
               discard (0),
               accept (1),
               tag (2)
               }
   MAX-ACCESS  read-write
   STATUS      current
   DESCRIPTION
      "Path: swPort.editConf.vlan.bridging.vlanTagging.vlans.action

       Possibilities:
               discard   (0)
               accept   (1)
               tag   (2)"
   ::= {er1646v2EthPortSwFVlanBridgingVlTVlansEntry 1073741824}

er1646v2EthPortSwFVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.vlans.tagInfo.tpid

       Possibilities:
               dot1Q   (33024)
               dot1ad   (34984)
               0x9100   (37120)
               0x9200   (37376)
               0x9300   (37632)"
   ::= {er1646v2EthPortSwFVlanBridgingVlTVlansEntry 1677721600}

er1646v2EthPortSwFVlanBridgingVlTVlansTagInfoVid OBJECT-TYPE
   SYNTAX      Integer32
   MAX-ACCESS  read-write
   STATUS      current
   DESCRIPTION
      "Path: swPort.editConf.vlan.bridging.vlanTagging.vlans.tagInfo.vid"
   ::= {er1646v2EthPortSwFVlanBridgingVlTVlansEntry 1744830464}

er1646v2EthPortSwFVlanVlanVidExtensionTable OBJECT-TYPE
   SYNTAX      SEQUENCE OF Er1646v2EthPortSwFVlanVlanVidExtensionTableEntry
   MAX-ACCESS  not-accessible
   STATUS      current
   DESCRIPTION
      ""
   ::= {er1646v2EthPortSwFVlan 235340544}

er1646v2EthPortSwFVlanVlanVidExtensionTableEntry OBJECT-TYPE
   SYNTAX      Er1646v2EthPortSwFVlanVlanVidExtensionTableEntry
   MAX-ACCESS  not-accessible
   STATUS      current
   DESCRIPTION
      ""
   INDEX      { er1646v2EthPortSwFVlanVlanVidExtensionTableGlobalIx,
                er1646v2EthPortSwFVlanTableIx,
                er1646v2EthPortSwFVlanVlanVidExtensionTableTableIx }
   ::= {er1646v2EthPortSwFVlanVlanVidExtensionTable 1}

Er1646v2EthPortSwFVlanVlanVidExtensionTableEntry ::=
   SEQUENCE
      {
      er1646v2EthPortSwFVlanVlanVidExtensionTableActions
         VariableLengthTableActions,
      er1646v2EthPortSwFVlanVlanVidExtensionTableGlobalIx
         GlobalIndex,
      er1646v2EthPortSwFVlanVlanVidExtensionTableTableIx
         TableIndex,
      er1646v2EthPortSwFVlanVlanVidExtensionTableTpid
         INTEGER,
      er1646v2EthPortSwFVlanVlanVidExtensionTableVid
         Integer32,
      er1646v2EthPortSwFVlanVlanVidExtensionTableEndVid
         Integer32
      }

er1646v2EthPortSwFVlanVlanVidExtensionTableActions OBJECT-TYPE
   SYNTAX      VariableLengthTableActions
   MAX-ACCESS  read-write
   STATUS      current
   DESCRIPTION
      "By way of this field, some manipulations
       on this table may be performed."
   ::= {er1646v2EthPortSwFVlanVlanVidExtensionTableEntry 2}

er1646v2EthPortSwFVlanVlanVidExtensionTableGlobalIx OBJECT-TYPE
   SYNTAX      GlobalIndex
   MAX-ACCESS  not-accessible
   STATUS      current
   DESCRIPTION
      "The value of the tlsCntTreeGlobalIndex of the MANAGED OBJECT."
   ::= {er1646v2EthPortSwFVlanVlanVidExtensionTableEntry 10}

er1646v2EthPortSwFVlanVlanVidExtensionTableTableIx OBJECT-TYPE
   SYNTAX      TableIndex
   MAX-ACCESS  not-accessible
   STATUS      current
   DESCRIPTION
      ""
   ::= {er1646v2EthPortSwFVlanVlanVidExtensionTableEntry 11}

er1646v2EthPortSwFVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.vidExtension.table.tpid

       Possibilities:
               dot1Q   (33024)
               dot1ad   (34984)
               0x9100   (37120)
               0x9200   (37376)
               0x9300   (37632)"
   ::= {er1646v2EthPortSwFVlanVlanVidExtensionTableEntry 16777216}

er1646v2EthPortSwFVlanVlanVidExtensionTableVid OBJECT-TYPE
   SYNTAX      Integer32
   MAX-ACCESS  read-write
   STATUS      current
   DESCRIPTION
      "Path: swPort.editConf.vlan.vlan.vidExtension.table.vid"
   ::= {er1646v2EthPortSwFVlanVlanVidExtensionTableEntry 33554432}

er1646v2EthPortSwFVlanVlanVidExtensionTableEndVid OBJECT-TYPE
   SYNTAX      Integer32
   MAX-ACCESS  read-write
   STATUS      current
   DESCRIPTION
      "Path: swPort.editConf.vlan.vlan.vidExtension.table.endVid"
   ::= {er1646v2EthPortSwFVlanVlanVidExtensionTableEntry 50331648}

er1646v2EthPortSwFVlanVlanCSMap OBJECT-TYPE
   SYNTAX      SEQUENCE OF Er1646v2EthPortSwFVlanVlanCSMapEntry
   MAX-ACCESS  not-accessible
   STATUS      current
   DESCRIPTION
      ""
   ::= {er1646v2EthPortSwFVlan 235405312}

er1646v2EthPortSwFVlanVlanCSMapEntry OBJECT-TYPE
   SYNTAX      Er1646v2EthPortSwFVlanVlanCSMapEntry
   MAX-ACCESS  not-accessible
   STATUS      current
   DESCRIPTION
      ""
   INDEX      { er1646v2EthPortSwFVlanVlanCSMapGlobalIx,
                er1646v2EthPortSwFVlanTableIx,
                er1646v2EthPortSwFVlanVlanCSMapTableIx }
   ::= {er1646v2EthPortSwFVlanVlanCSMap 1}

Er1646v2EthPortSwFVlanVlanCSMapEntry ::=
   SEQUENCE
      {
      er1646v2EthPortSwFVlanVlanCSMapActions
         VariableLengthTableActions,
      er1646v2EthPortSwFVlanVlanCSMapGlobalIx
         GlobalIndex,
      er1646v2EthPortSwFVlanVlanCSMapTableIx
         TableIndex,
      er1646v2EthPortSwFVlanVlanCSMapCos
         INTEGER,
      er1646v2EthPortSwFVlanVlanCSMapDei
         INTEGER,
      er1646v2EthPortSwFVlanVlanCSMapTos
         INTEGER,
      er1646v2EthPortSwFVlanVlanCSMapQueue
         INTEGER,
      er1646v2EthPortSwFVlanVlanCSMapDropLevel
         INTEGER,
      er1646v2EthPortSwFVlanVlanCSMapDeFlag
         INTEGER
      }

er1646v2EthPortSwFVlanVlanCSMapActions OBJECT-TYPE
   SYNTAX      VariableLengthTableActions
   MAX-ACCESS  read-write
   STATUS      current
   DESCRIPTION
      "By way of this field, some manipulations
       on this table may be performed."
   ::= {er1646v2EthPortSwFVlanVlanCSMapEntry 2}

er1646v2EthPortSwFVlanVlanCSMapGlobalIx OBJECT-TYPE
   SYNTAX      GlobalIndex
   MAX-ACCESS  not-accessible
   STATUS      current
   DESCRIPTION
      "The value of the tlsCntTreeGlobalIndex of the MANAGED OBJECT."
   ::= {er1646v2EthPortSwFVlanVlanCSMapEntry 10}

er1646v2EthPortSwFVlanVlanCSMapTableIx OBJECT-TYPE
   SYNTAX      TableIndex
   MAX-ACCESS  not-accessible
   STATUS      current
   DESCRIPTION
      ""
   ::= {er1646v2EthPortSwFVlanVlanCSMapEntry 11}

er1646v2EthPortSwFVlanVlanCSMapCos OBJECT-TYPE
   SYNTAX      INTEGER
               {
               any (8)
               }
   MAX-ACCESS  read-write
   STATUS      current
   DESCRIPTION
      "Path: swPort.editConf.vlan.vlan.cosMap.cos

       Possibilities:
               any   (8)"
   ::= {er1646v2EthPortSwFVlanVlanCSMapEntry 16777216}

er1646v2EthPortSwFVlanVlanCSMapDei OBJECT-TYPE
   SYNTAX      INTEGER
               {
               clear (0),
               set (1),
               any (2)
               }
   MAX-ACCESS  read-write
   STATUS      current
   DESCRIPTION
      "Path: swPort.editConf.vlan.vlan.cosMap.dei

       Possibilities:
               clear   (0)
               set   (1)
               any   (2)"
   ::= {er1646v2EthPortSwFVlanVlanCSMapEntry 33554432}

er1646v2EthPortSwFVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwFVlanVlanCSMapEntry 50331648}

er1646v2EthPortSwFVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwFVlanVlanCSMapEntry 67108864}

er1646v2EthPortSwFVlanVlanCSMapDropLevel OBJECT-TYPE
   SYNTAX      INTEGER
               {
               unchanged (-1),
               dropOnQueue (0)
               }
   MAX-ACCESS  read-write
   STATUS      current
   DESCRIPTION
      "Path: swPort.editConf.vlan.vlan.cosMap.dropLevel

       Possibilities:
               unchanged   (-1)
               dropOnQueue   (0)"
   ::= {er1646v2EthPortSwFVlanVlanCSMapEntry 83886080}

er1646v2EthPortSwFVlanVlanCSMapDeFlag OBJECT-TYPE
   SYNTAX      INTEGER
               {
               unchanged (255),
               clear (0),
               set (1)
               }
   MAX-ACCESS  read-write
   STATUS      current
   DESCRIPTION
      "Path: swPort.editConf.vlan.vlan.cosMap.deFlag

       Possibilities:
               unchanged   (255)
               clear   (0)
               set   (1)"
   ::= {er1646v2EthPortSwFVlanVlanCSMapEntry 117440512}

er1646v2EthPortSwFVlanVlanTCMap OBJECT-TYPE
   SYNTAX      SEQUENCE OF Er1646v2EthPortSwFVlanVlanTCMapEntry
   MAX-ACCESS  not-accessible
   STATUS      current
   DESCRIPTION
      ""
   ::= {er1646v2EthPortSwFVlan 241369088}

er1646v2EthPortSwFVlanVlanTCMapEntry OBJECT-TYPE
   SYNTAX      Er1646v2EthPortSwFVlanVlanTCMapEntry
   MAX-ACCESS  not-accessible
   STATUS      current
   DESCRIPTION
      ""
   INDEX      { er1646v2EthPortSwFVlanVlanTCMapGlobalIx,
                er1646v2EthPortSwFVlanTableIx,
                er1646v2EthPortSwFVlanVlanTCMapTableIx }
   ::= {er1646v2EthPortSwFVlanVlanTCMap 1}

Er1646v2EthPortSwFVlanVlanTCMapEntry ::=
   SEQUENCE
      {
      er1646v2EthPortSwFVlanVlanTCMapActions
         VariableLengthTableActions,
      er1646v2EthPortSwFVlanVlanTCMapGlobalIx
         GlobalIndex,
      er1646v2EthPortSwFVlanVlanTCMapTableIx
         TableIndex,
      er1646v2EthPortSwFVlanVlanTCMapStartTos
         INTEGER,
      er1646v2EthPortSwFVlanVlanTCMapEndTos
         INTEGER,
      er1646v2EthPortSwFVlanVlanTCMapCos
         INTEGER
      }

er1646v2EthPortSwFVlanVlanTCMapActions OBJECT-TYPE
   SYNTAX      VariableLengthTableActions
   MAX-ACCESS  read-write
   STATUS      current
   DESCRIPTION
      "By way of this field, some manipulations
       on this table may be performed."
   ::= {er1646v2EthPortSwFVlanVlanTCMapEntry 2}

er1646v2EthPortSwFVlanVlanTCMapGlobalIx OBJECT-TYPE
   SYNTAX      GlobalIndex
   MAX-ACCESS  not-accessible
   STATUS      current
   DESCRIPTION
      "The value of the tlsCntTreeGlobalIndex of the MANAGED OBJECT."
   ::= {er1646v2EthPortSwFVlanVlanTCMapEntry 10}

er1646v2EthPortSwFVlanVlanTCMapTableIx OBJECT-TYPE
   SYNTAX      TableIndex
   MAX-ACCESS  not-accessible
   STATUS      current
   DESCRIPTION
      ""
   ::= {er1646v2EthPortSwFVlanVlanTCMapEntry 11}

er1646v2EthPortSwFVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EthPortSwFVlanVlanTCMapEntry 16777216}

er1646v2EthPortSwFVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EthPortSwFVlanVlanTCMapEntry 33554432}

er1646v2EthPortSwFVlanVlanTCMapCos OBJECT-TYPE
   SYNTAX      INTEGER
               {
               queueCosMap (8)
               }
   MAX-ACCESS  read-write
   STATUS      current
   DESCRIPTION
      "Path: swPort.editConf.vlan.vlan.tosCosMap.cos

       Possibilities:
               queueCosMap   (8)"
   ::= {er1646v2EthPortSwFVlanVlanTCMapEntry 50331648}

er1646v2EthPortSwFVlanVlanArpStaticArp OBJECT-TYPE
   SYNTAX      SEQUENCE OF Er1646v2EthPortSwFVlanVlanArpStaticArpEntry
   MAX-ACCESS  not-accessible
   STATUS      current
   DESCRIPTION
      ""
   ::= {er1646v2EthPortSwFVlan 235275008}

er1646v2EthPortSwFVlanVlanArpStaticArpEntry OBJECT-TYPE
   SYNTAX      Er1646v2EthPortSwFVlanVlanArpStaticArpEntry
   MAX-ACCESS  not-accessible
   STATUS      current
   DESCRIPTION
      ""
   INDEX      { er1646v2EthPortSwFVlanVlanArpStaticArpGlobalIx,
                er1646v2EthPortSwFVlanTableIx,
                er1646v2EthPortSwFVlanVlanArpStaticArpTableIx }
   ::= {er1646v2EthPortSwFVlanVlanArpStaticArp 1}

Er1646v2EthPortSwFVlanVlanArpStaticArpEntry ::=
   SEQUENCE
      {
      er1646v2EthPortSwFVlanVlanArpStaticArpActions
         VariableLengthTableActions,
      er1646v2EthPortSwFVlanVlanArpStaticArpGlobalIx
         GlobalIndex,
      er1646v2EthPortSwFVlanVlanArpStaticArpTableIx
         TableIndex,
      er1646v2EthPortSwFVlanVlanArpStaticArpMacAddress
         OCTET STRING,
      er1646v2EthPortSwFVlanVlanArpStaticArpIpAddress
         IpAddress
      }

er1646v2EthPortSwFVlanVlanArpStaticArpActions OBJECT-TYPE
   SYNTAX      VariableLengthTableActions
   MAX-ACCESS  read-write
   STATUS      current
   DESCRIPTION
      "By way of this field, some manipulations
       on this table may be performed."
   ::= {er1646v2EthPortSwFVlanVlanArpStaticArpEntry 2}

er1646v2EthPortSwFVlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2EthPortSwFVlanVlanArpStaticArpEntry 10}

er1646v2EthPortSwFVlanVlanArpStaticArpTableIx OBJECT-TYPE
   SYNTAX      TableIndex
   MAX-ACCESS  not-accessible
   STATUS      current
   DESCRIPTION
      ""
   ::= {er1646v2EthPortSwFVlanVlanArpStaticArpEntry 11}

er1646v2EthPortSwFVlanVlanArpStaticArpMacAddress OBJECT-TYPE
   SYNTAX      OCTET STRING
   MAX-ACCESS  read-write
   STATUS      current
   DESCRIPTION
      "Path: swPort.editConf.vlan.vlan.arp.staticArp.macAddress

       MAC address."
   ::= {er1646v2EthPortSwFVlanVlanArpStaticArpEntry 16777216}

er1646v2EthPortSwFVlanVlanArpStaticArpIpAddress OBJECT-TYPE
   SYNTAX      IpAddress
   MAX-ACCESS  read-write
   STATUS      current
   DESCRIPTION
      "Path: swPort.editConf.vlan.vlan.arp.staticArp.ipAddress"
   ::= {er1646v2EthPortSwFVlanVlanArpStaticArpEntry 33554432}


er1646v2EthPortSwFPppOE OBJECT IDENTIFIER ::= {er1646v2EthPortSwF 35}

er1646v2EthPortSwFPppOESSCTable OBJECT-TYPE
   SYNTAX      SEQUENCE OF Er1646v2EthPortSwFPppOEEntry
   MAX-ACCESS  not-accessible
   STATUS      current
   DESCRIPTION
      ""
   ::= {er1646v2EthPortSwFPppOE 1}

er1646v2EthPortSwFPppOEEntry OBJECT-TYPE
   SYNTAX      Er1646v2EthPortSwFPppOEEntry
   MAX-ACCESS  not-accessible
   STATUS      current
   DESCRIPTION
      ""
   INDEX      { er1646v2EthPortSwFPppOEGlobalIx,
                er1646v2EthPortSwFPppOETableIx }
   ::= {er1646v2EthPortSwFPppOESSCTable 1}

Er1646v2EthPortSwFPppOEEntry ::=
   SEQUENCE
      {
      er1646v2EthPortSwFPppOEActions
         VariableLengthTableActions,
      er1646v2EthPortSwFPppOEGlobalIx
         GlobalIndex,
      er1646v2EthPortSwFPppOETableIx
         TableIndex,
      er1646v2EthPortSwFPppOEName
         DisplayString,
      er1646v2EthPortSwFPppOERemark
         DisplayString,
      er1646v2EthPortSwFPppOEAdminStatus
         INTEGER,
      er1646v2EthPortSwFPppOEMode
         INTEGER,
      er1646v2EthPortSwFPppOEIpVrfRouter
         DisplayString,
      er1646v2EthPortSwFPppOEIpAdr
         IpAddress,
      er1646v2EthPortSwFPppOEIpNetm
         IpAddress,
      er1646v2EthPortSwFPppOEIpSNetName
         INTEGER,
      er1646v2EthPortSwFPppOEIpSNetCust
         DisplayString,
      er1646v2EthPortSwFPppOEIpRem
         IpAddress,
      er1646v2EthPortSwFPppOEIpUnnumbered
         DisplayString,
      er1646v2EthPortSwFPppOEIpGwPref
         Integer32,
      er1646v2EthPortSwFPppOEIpRsn
         INTEGER,
      er1646v2EthPortSwFPppOEIpMtu
         Integer32,
      er1646v2EthPortSwFPppOEIpMssAdjust
         INTEGER,
      er1646v2EthPortSwFPppOEIpRipMetric
         Integer32,
      er1646v2EthPortSwFPppOEIpRipMetricOut
         Integer32,
      er1646v2EthPortSwFPppOEIpRipMode
         INTEGER,
      er1646v2EthPortSwFPppOEIpRipTxVer
         INTEGER,
      er1646v2EthPortSwFPppOEIpRipRxVer
         INTEGER,
      er1646v2EthPortSwFPppOEIpRipSplitH
         INTEGER,
      er1646v2EthPortSwFPppOEIpRipAuth
         INTEGER,
      er1646v2EthPortSwFPppOEIpRipFilter
         DisplayString,
      er1646v2EthPortSwFPppOEIpRipFilterIn
         DisplayString,
      er1646v2EthPortSwFPppOEIpRipClearNextHop
         INTEGER,
      er1646v2EthPortSwFPppOEIpAccPol
         DisplayString,
      er1646v2EthPortSwFPppOEIpAB
         DisplayString,
      er1646v2EthPortSwFPppOEIpMA
         INTEGER,
      er1646v2EthPortSwFPppOEIpMF
         Integer32,
      er1646v2EthPortSwFPppOEIpDB
         INTEGER,
      er1646v2EthPortSwFPppOEIpIR
         INTEGER,
      er1646v2EthPortSwFPppOEIpIgmp
         INTEGER,
      er1646v2EthPortSwFPppOEIpNN
         DisplayString,
      er1646v2EthPortSwFPppOEIpPimMode
         INTEGER,
      er1646v2EthPortSwFPppOEIpPimDrPriority
         Counter32,
      er1646v2EthPortSwFPppOEIpPimHelloTime
         TimeTicks,
      er1646v2EthPortSwFPppOEIpPimPropagationDelay
         TimeTicks,
      er1646v2EthPortSwFPppOEIpPimOverrideInterval
         TimeTicks,
      er1646v2EthPortSwFPppOEIpPimBsrBorder
         INTEGER,
      er1646v2EthPortSwFPppOEIpPimTtlThreshold
         Integer32,
      er1646v2EthPortSwFPppOEIpIMNetworkUnreachable
         INTEGER,
      er1646v2EthPortSwFPppOEIpIMHostUnreachable
         INTEGER,
      er1646v2EthPortSwFPppOEIpIMProtocolUnreachable
         INTEGER,
      er1646v2EthPortSwFPppOEIpIMPortUnreachable
         INTEGER,
      er1646v2EthPortSwFPppOEIpIMMtuExceeded
         INTEGER,
      er1646v2EthPortSwFPppOEIpIMAdminProhibited
         INTEGER,
      er1646v2EthPortSwFPppOEIpIMTtlExceeded
         INTEGER,
      er1646v2EthPortSwFPppOEIpIMRedirect
         INTEGER,
      er1646v2EthPortSwFPppOEIpV6VrfRouter
         DisplayString,
      er1646v2EthPortSwFPppOEIpV6AddrAutoConfigNrDupAddrDetects
         Integer32,
      er1646v2EthPortSwFPppOEIpV6AddrAutoConfigAcceptRa
         INTEGER,
      er1646v2EthPortSwFPppOEIpV6AddrAutoConfigAcceptRaRdnss
         INTEGER,
      er1646v2EthPortSwFPppOEIpV6AddrAutoConfigAcceptRaDnssl
         INTEGER,
      er1646v2EthPortSwFPppOEIpV6DefaultRoute
         INTEGER,
      er1646v2EthPortSwFPppOEIpV6RaSend
         INTEGER,
      er1646v2EthPortSwFPppOEIpV6RaMinInterval
         TimeTicks,
      er1646v2EthPortSwFPppOEIpV6RaMaxInterval
         TimeTicks,
      er1646v2EthPortSwFPppOEIpV6RaManagedFlag
         INTEGER,
      er1646v2EthPortSwFPppOEIpV6RaOtherConfFlag
         INTEGER,
      er1646v2EthPortSwFPppOEIpV6RaLinkMtu
         Integer32,
      er1646v2EthPortSwFPppOEIpV6RaReachableTime
         TimeTicks,
      er1646v2EthPortSwFPppOEIpV6RaRetransmitTime
         TimeTicks,
      er1646v2EthPortSwFPppOEIpV6RaHopLimit
         Integer32,
      er1646v2EthPortSwFPppOEIpV6RaDefaultLifeTime
         TimeTicks,
      er1646v2EthPortSwFPppOEIpV6RaDnsOptionsRdnssLifeTime
         TimeTicks,
      er1646v2EthPortSwFPppOEIpV6RaDnsOptionsRdnssImportServers
         INTEGER,
      er1646v2EthPortSwFPppOEIpV6RaDnsOptionsDnsslLifeTime
         TimeTicks,
      er1646v2EthPortSwFPppOEIpV6RaDnsOptionsDnsslImportDomains
         INTEGER,
      er1646v2EthPortSwFPppOEIpV6RsSend
         INTEGER,
      er1646v2EthPortSwFPppOEIpV6RsMaxRandomDelay
         TimeTicks,
      er1646v2EthPortSwFPppOEIpV6RsInterval
         TimeTicks,
      er1646v2EthPortSwFPppOEIpV6RsMaxSolicitations
         Integer32,
      er1646v2EthPortSwFPppOEIpV6TrafficPolicyInbound
         DisplayString,
      er1646v2EthPortSwFPppOEIpV6TrafficPolicyOutbound
         DisplayString,
      er1646v2EthPortSwFPppOEIpV6FirewallZone
         DisplayString,
      er1646v2EthPortSwFPppOEIpV6DhcpClientAddrAC
         INTEGER,
      er1646v2EthPortSwFPppOEIpV6DhcpClientPrDelMode
         INTEGER,
      er1646v2EthPortSwFPppOEIpV6DhcpClientPrDelPool
         DisplayString,
      er1646v2EthPortSwFPppOEIpV6DhcpClientPrDelPdExclOpt
         INTEGER,
      er1646v2EthPortSwFPppOEIpV6DhcpClientDnsServerPref
         Integer32,
      er1646v2EthPortSwFPppOEIpV6DhcpClientRapidCommit
         INTEGER,
      er1646v2EthPortSwFPppOEIpV6DhcpClientTimersSolTimeOut
         TimeTicks,
      er1646v2EthPortSwFPppOEIpV6DhcpClientTimersSolMaxRt
         TimeTicks,
      er1646v2EthPortSwFPppOEIpV6DhcpClientTimersInfoRefresh
         TimeTicks,
      er1646v2EthPortSwFPppOEIpV6DhcpServerMode
         INTEGER,
      er1646v2EthPortSwFPppOEIpV6DhcpServerPreference
         Integer32,
      er1646v2EthPortSwFPppOEIpV6DhcpServerPool
         DisplayString,
      er1646v2EthPortSwFPppOEIpV6DhcpServerRapidCommit
         INTEGER,
      er1646v2EthPortSwFPppOEIpV6DhcpServerTimersInfoRefresh
         TimeTicks,
      er1646v2EthPortSwFPppOEIpV6DhcpRelayMode
         INTEGER,
      er1646v2EthPortSwFPppOEIpV6SendRedirect
         INTEGER,
      er1646v2EthPortSwFPppOEIpV6LinkMtu
         Integer32,
      er1646v2EthPortSwFPppOEIpV6InterfaceId
         OCTET STRING,
      er1646v2EthPortSwFPppOEIpV6MF
         Integer32,
      er1646v2EthPortSwFPppOEIpV6IcmpMessagesNoRoute
         INTEGER,
      er1646v2EthPortSwFPppOEIpV6IcmpMessagesBeyondScope
         INTEGER,
      er1646v2EthPortSwFPppOEIpV6IcmpMessagesAddressUnreachable
         INTEGER,
      er1646v2EthPortSwFPppOEIpV6IcmpMessagesPortUnreachable
         INTEGER,
      er1646v2EthPortSwFPppOEIpV6IcmpMessagesPacketTooBig
         INTEGER,
      er1646v2EthPortSwFPppOEIpV6IcmpMessagesHopLimitExceeded
         INTEGER,
      er1646v2EthPortSwFPppOEIpV6IcmpMessagesFragTimeExceeded
         INTEGER,
      er1646v2EthPortSwFPppOEIpV6IcmpMessagesHeaderFieldErr
         INTEGER,
      er1646v2EthPortSwFPppOEIpV6IcmpMessagesOptionUnrecognized
         INTEGER,
      er1646v2EthPortSwFPppOEIpV6IcmpMessagesRedirect
         INTEGER,
      er1646v2EthPortSwFPppOEPppLnkMOperation
         INTEGER,
      er1646v2EthPortSwFPppOEPppLnkMInterval
         TimeTicks,
      er1646v2EthPortSwFPppOEPppLnkMRepTimeOut
         TimeTicks,
      er1646v2EthPortSwFPppOEPppLnkMFailsPrmt
         Integer32,
      er1646v2EthPortSwFPppOEPppAuthentication
         INTEGER,
      er1646v2EthPortSwFPppOEPppAuthenPeriod
         TimeTicks,
      er1646v2EthPortSwFPppOEPppSessionName
         DisplayString,
      er1646v2EthPortSwFPppOEPppSessionSecret
         DisplayString,
      er1646v2EthPortSwFPppOEPppEncModeSessionSecret
         INTEGER,
      er1646v2EthPortSwFPppOEPppEncSessionSecret
         DisplayString,
      er1646v2EthPortSwFPppOEPppServiceName
         DisplayString
      }

er1646v2EthPortSwFPppOEActions OBJECT-TYPE
   SYNTAX      VariableLengthTableActions
   MAX-ACCESS  read-write
   STATUS      current
   DESCRIPTION
      "By way of this field, some manipulations
       on this table may be performed."
   ::= {er1646v2EthPortSwFPppOEEntry 2}

er1646v2EthPortSwFPppOEGlobalIx OBJECT-TYPE
   SYNTAX      GlobalIndex
   MAX-ACCESS  not-accessible
   STATUS      current
   DESCRIPTION
      "The value of the tlsCntTreeGlobalIndex of the MANAGED OBJECT."
   ::= {er1646v2EthPortSwFPppOEEntry 10}

er1646v2EthPortSwFPppOETableIx OBJECT-TYPE
   SYNTAX      TableIndex
   MAX-ACCESS  not-accessible
   STATUS      current
   DESCRIPTION
      ""
   ::= {er1646v2EthPortSwFPppOEEntry 11}

er1646v2EthPortSwFPppOEName OBJECT-TYPE
   SYNTAX      DisplayString
   MAX-ACCESS  read-write
   STATUS      current
   DESCRIPTION
      "Path: swPort.editConf.pppoEClient.name"
   ::= {er1646v2EthPortSwFPppOEEntry 16777216}

er1646v2EthPortSwFPppOERemark OBJECT-TYPE
   SYNTAX      DisplayString
   MAX-ACCESS  read-write
   STATUS      current
   DESCRIPTION
      "Path: swPort.editConf.pppoEClient.remark"
   ::= {er1646v2EthPortSwFPppOEEntry 1157627904}

er1646v2EthPortSwFPppOEAdminStatus OBJECT-TYPE
   SYNTAX      INTEGER
               {
               up (1),
               down (2)
               }
   MAX-ACCESS  read-write
   STATUS      current
   DESCRIPTION
      "Path: swPort.editConf.pppoEClient.adminStatus

       Possibilities:
               up   (1)
               down   (2)"
   ::= {er1646v2EthPortSwFPppOEEntry 33554432}

er1646v2EthPortSwFPppOEMode OBJECT-TYPE
   SYNTAX      INTEGER
               {
               routing (1),
               multilink (8),
               ipV6 (16),
               ipV6ipV4 (17)
               }
   MAX-ACCESS  read-write
   STATUS      current
   DESCRIPTION
      "Path: swPort.editConf.pppoEClient.mode

       Possibilities:
               routing   (1)
               multilink   (8)
               ipV6   (16)
               ipV6/ipV4   (17)"
   ::= {er1646v2EthPortSwFPppOEEntry 67108864}

er1646v2EthPortSwFPppOEIpVrfRouter OBJECT-TYPE
   SYNTAX      DisplayString
   MAX-ACCESS  read-write
   STATUS      current
   DESCRIPTION
      "Path: swPort.editConf.pppoEClient.ip.vrfRouter"
   ::= {er1646v2EthPortSwFPppOEEntry 53215232}

er1646v2EthPortSwFPppOEIpAdr OBJECT-TYPE
   SYNTAX      IpAddress
   MAX-ACCESS  read-write
   STATUS      current
   DESCRIPTION
      "Path: swPort.editConf.pppoEClient.ip.address"
   ::= {er1646v2EthPortSwFPppOEEntry 58261504}

er1646v2EthPortSwFPppOEIpNetm OBJECT-TYPE
   SYNTAX      IpAddress
   MAX-ACCESS  read-write
   STATUS      current
   DESCRIPTION
      "Path: swPort.editConf.pppoEClient.ip.netMask"
   ::= {er1646v2EthPortSwFPppOEEntry 58392576}

er1646v2EthPortSwFPppOEIpSNetName OBJECT-TYPE
   SYNTAX      INTEGER
               {
               slOPTg (0),
               corp (2),
               dmz (3),
               internet (1)
               }
   MAX-ACCESS  read-write
   STATUS      current
   DESCRIPTION
      "Path: swPort.editConf.pppoEClient.ip.sNet.name

       Possibilities:
               <OPT>   (0)
               corp   (2)
               dmz   (3)
               internet   (1)"
   ::= {er1646v2EthPortSwFPppOEEntry 53674240}

er1646v2EthPortSwFPppOEIpSNetCust OBJECT-TYPE
   SYNTAX      DisplayString
   MAX-ACCESS  read-write
   STATUS      current
   DESCRIPTION
      "Path: swPort.editConf.pppoEClient.ip.sNet.custom"
   ::= {er1646v2EthPortSwFPppOEEntry 53674496}

er1646v2EthPortSwFPppOEIpRem OBJECT-TYPE
   SYNTAX      IpAddress
   MAX-ACCESS  read-write
   STATUS      current
   DESCRIPTION
      "Path: swPort.editConf.pppoEClient.ip.remote"
   ::= {er1646v2EthPortSwFPppOEEntry 58458112}

er1646v2EthPortSwFPppOEIpUnnumbered OBJECT-TYPE
   SYNTAX      DisplayString
   MAX-ACCESS  read-write
   STATUS      current
   DESCRIPTION
      "Path: swPort.editConf.pppoEClient.ip.unnumbered"
   ::= {er1646v2EthPortSwFPppOEEntry 52625408}

er1646v2EthPortSwFPppOEIpGwPref OBJECT-TYPE
   SYNTAX      Integer32
   MAX-ACCESS  read-write
   STATUS      current
   DESCRIPTION
      "Path: swPort.editConf.pppoEClient.ip.gatewayPreference"
   ::= {er1646v2EthPortSwFPppOEEntry 52690944}

er1646v2EthPortSwFPppOEIpRsn OBJECT-TYPE
   SYNTAX      INTEGER
               {
               disabled (0),
               enabled (1)
               }
   MAX-ACCESS  read-write
   STATUS      current
   DESCRIPTION
      "Path: swPort.editConf.pppoEClient.ip.requestSubnet

       Possibilities:
               disabled   (0)
               enabled   (1)"
   ::= {er1646v2EthPortSwFPppOEEntry 56688640}

er1646v2EthPortSwFPppOEIpMtu OBJECT-TYPE
   SYNTAX      Integer32
   MAX-ACCESS  read-write
   STATUS      current
   DESCRIPTION
      "Path: swPort.editConf.pppoEClient.ip.mtu"
   ::= {er1646v2EthPortSwFPppOEEntry 52953088}

er1646v2EthPortSwFPppOEIpMssAdjust OBJECT-TYPE
   SYNTAX      INTEGER
               {
               disabled (0),
               auto (65536)
               }
   MAX-ACCESS  read-write
   STATUS      current
   DESCRIPTION
      "Path: swPort.editConf.pppoEClient.ip.mssAdjust

       Possibilities:
               disabled   (0)
               auto   (65536)"
   ::= {er1646v2EthPortSwFPppOEEntry 53280768}

er1646v2EthPortSwFPppOEIpRipMetric OBJECT-TYPE
   SYNTAX      Integer32
   MAX-ACCESS  read-write
   STATUS      current
   DESCRIPTION
      "Path: swPort.editConf.pppoEClient.ip.rip.metric"
   ::= {er1646v2EthPortSwFPppOEEntry 51712768}

er1646v2EthPortSwFPppOEIpRipMetricOut OBJECT-TYPE
   SYNTAX      Integer32
   MAX-ACCESS  read-write
   STATUS      current
   DESCRIPTION
      "Path: swPort.editConf.pppoEClient.ip.rip.metricOut"
   ::= {er1646v2EthPortSwFPppOEEntry 51713024}

er1646v2EthPortSwFPppOEIpRipMode OBJECT-TYPE
   SYNTAX      INTEGER
               {
               disabled (0),
               passive (1),
               active (2)
               }
   MAX-ACCESS  read-write
   STATUS      current
   DESCRIPTION
      "Path: swPort.editConf.pppoEClient.ip.rip.mode

       Possibilities:
               disabled   (0)
               passive   (1)
               active   (2)"
   ::= {er1646v2EthPortSwFPppOEEntry 51713280}

er1646v2EthPortSwFPppOEIpRipTxVer OBJECT-TYPE
   SYNTAX      INTEGER
               {
               rip1 (0),
               rip2 (1),
               rip1mcompatible (2)
               }
   MAX-ACCESS  read-write
   STATUS      current
   DESCRIPTION
      "Path: swPort.editConf.pppoEClient.ip.rip.txVersion

       Possibilities:
               rip1   (0)
               rip2   (1)
               rip1-compatible   (2)"
   ::= {er1646v2EthPortSwFPppOEEntry 51716864}

er1646v2EthPortSwFPppOEIpRipRxVer OBJECT-TYPE
   SYNTAX      INTEGER
               {
               rip1only (0),
               rip2only (1),
               rip12 (2)
               }
   MAX-ACCESS  read-write
   STATUS      current
   DESCRIPTION
      "Path: swPort.editConf.pppoEClient.ip.rip.rxVersion

       Possibilities:
               rip1only   (0)
               rip2only   (1)
               rip1&2   (2)"
   ::= {er1646v2EthPortSwFPppOEEntry 51717120}

er1646v2EthPortSwFPppOEIpRipSplitH OBJECT-TYPE
   SYNTAX      INTEGER
               {
               disabled (0),
               enabled (1),
               poisonedReverse (2)
               }
   MAX-ACCESS  read-write
   STATUS      current
   DESCRIPTION
      "Path: swPort.editConf.pppoEClient.ip.rip.splitHorizon

       Possibilities:
               disabled   (0)
               enabled   (1)
               poisonedReverse   (2)"
   ::= {er1646v2EthPortSwFPppOEEntry 51713792}

er1646v2EthPortSwFPppOEIpRipAuth OBJECT-TYPE
   SYNTAX      INTEGER
               {
               disabled (0),
               texts (1),
               md5 (2)
               }
   MAX-ACCESS  read-write
   STATUS      current
   DESCRIPTION
      "Path: swPort.editConf.pppoEClient.ip.rip.authentication

       Possibilities:
               disabled   (0)
               text    (1)
               md5   (2)"
   ::= {er1646v2EthPortSwFPppOEEntry 51712512}

er1646v2EthPortSwFPppOEIpRipFilter OBJECT-TYPE
   SYNTAX      DisplayString
   MAX-ACCESS  read-write
   STATUS      current
   DESCRIPTION
      "Path: swPort.editConf.pppoEClient.ip.rip.filter"
   ::= {er1646v2EthPortSwFPppOEEntry 51716096}

er1646v2EthPortSwFPppOEIpRipFilterIn OBJECT-TYPE
   SYNTAX      DisplayString
   MAX-ACCESS  read-write
   STATUS      current
   DESCRIPTION
      "Path: swPort.editConf.pppoEClient.ip.rip.filterIn"
   ::= {er1646v2EthPortSwFPppOEEntry 51716352}

er1646v2EthPortSwFPppOEIpRipClearNextHop OBJECT-TYPE
   SYNTAX      INTEGER
               {
               disabled (0),
               enabled (1)
               }
   MAX-ACCESS  read-write
   STATUS      current
   DESCRIPTION
      "Path: swPort.editConf.pppoEClient.ip.rip.clearNextHop

       Possibilities:
               disabled   (0)
               enabled   (1)"
   ::= {er1646v2EthPortSwFPppOEEntry 51708416}

er1646v2EthPortSwFPppOEIpAccPol OBJECT-TYPE
   SYNTAX      DisplayString
   MAX-ACCESS  read-write
   STATUS      current
   DESCRIPTION
      "Path: swPort.editConf.pppoEClient.ip.accessPolicy"
   ::= {er1646v2EthPortSwFPppOEEntry 53084160}

er1646v2EthPortSwFPppOEIpAB OBJECT-TYPE
   SYNTAX      DisplayString
   MAX-ACCESS  read-write
   STATUS      current
   DESCRIPTION
      "Path: swPort.editConf.pppoEClient.ip.trafficPolicy"
   ::= {er1646v2EthPortSwFPppOEEntry 51249152}

er1646v2EthPortSwFPppOEIpMA OBJECT-TYPE
   SYNTAX      INTEGER
               {
               disabled (0),
               enabled (1)
               }
   MAX-ACCESS  read-write
   STATUS      current
   DESCRIPTION
      "Path: swPort.editConf.pppoEClient.ip.mgmtAccess

       Possibilities:
               disabled   (0)
               enabled   (1)"
   ::= {er1646v2EthPortSwFPppOEEntry 51380224}

er1646v2EthPortSwFPppOEIpMF OBJECT-TYPE
   SYNTAX      Integer32
   MAX-ACCESS  read-write
   STATUS      current
   DESCRIPTION
      "Path: swPort.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwFPppOEEntry 51445760}

er1646v2EthPortSwFPppOEIpDB OBJECT-TYPE
   SYNTAX      INTEGER
               {
               disabled (0),
               enabled (1)
               }
   MAX-ACCESS  read-write
   STATUS      current
   DESCRIPTION
      "Path: swPort.editConf.pppoEClient.ip.directedBroadcasts

       Possibilities:
               disabled   (0)
               enabled   (1)"
   ::= {er1646v2EthPortSwFPppOEEntry 51773440}

er1646v2EthPortSwFPppOEIpIR OBJECT-TYPE
   SYNTAX      INTEGER
               {
               disabled (0),
               enabled (1)
               }
   MAX-ACCESS  read-write
   STATUS      current
   DESCRIPTION
      "Path: swPort.editConf.pppoEClient.ip.icmpRedirects

       Possibilities:
               disabled   (0)
               enabled   (1)"
   ::= {er1646v2EthPortSwFPppOEEntry 52035584}

er1646v2EthPortSwFPppOEIpIgmp OBJECT-TYPE
   SYNTAX      INTEGER
               {
               disabled (0),
               proxy (1),
               router (2),
               v3Router (5)
               }
   MAX-ACCESS  read-write
   STATUS      current
   DESCRIPTION
      "Path: swPort.editConf.pppoEClient.ip.igmp

       Possibilities:
               disabled   (0)
               proxy   (1)
               router   (2)
               v3Router   (5)"
   ::= {er1646v2EthPortSwFPppOEEntry 52428800}

er1646v2EthPortSwFPppOEIpNN OBJECT-TYPE
   SYNTAX      DisplayString
   MAX-ACCESS  read-write
   STATUS      current
   DESCRIPTION
      "Path: swPort.editConf.pppoEClient.ip.nat"
   ::= {er1646v2EthPortSwFPppOEEntry 52101120}

er1646v2EthPortSwFPppOEIpPimMode OBJECT-TYPE
   SYNTAX      INTEGER
               {
               disabled (0),
               sparse (1),
               passive (2)
               }
   MAX-ACCESS  read-write
   STATUS      current
   DESCRIPTION
      "Path: swPort.editConf.pppoEClient.ip.pim.mode

       Possibilities:
               disabled   (0)
               sparse   (1)
               passive   (2)"
   ::= {er1646v2EthPortSwFPppOEEntry 53346560}

er1646v2EthPortSwFPppOEIpPimDrPriority OBJECT-TYPE
   SYNTAX      Counter32
   MAX-ACCESS  read-write
   STATUS      current
   DESCRIPTION
      "Path: swPort.editConf.pppoEClient.ip.pim.drPriority

       32 bit unsigned wrappable counter."
   ::= {er1646v2EthPortSwFPppOEEntry 53346816}

er1646v2EthPortSwFPppOEIpPimHelloTime OBJECT-TYPE
   SYNTAX      TimeTicks
   MAX-ACCESS  read-write
   STATUS      current
   DESCRIPTION
      "Path: swPort.editConf.pppoEClient.ip.pim.helloTime

       Time in centi-second."
   ::= {er1646v2EthPortSwFPppOEEntry 53347072}

er1646v2EthPortSwFPppOEIpPimPropagationDelay OBJECT-TYPE
   SYNTAX      TimeTicks
   MAX-ACCESS  read-write
   STATUS      current
   DESCRIPTION
      "Path: swPort.editConf.pppoEClient.ip.pim.propagationDelay

       Time in centi-second."
   ::= {er1646v2EthPortSwFPppOEEntry 53347328}

er1646v2EthPortSwFPppOEIpPimOverrideInterval OBJECT-TYPE
   SYNTAX      TimeTicks
   MAX-ACCESS  read-write
   STATUS      current
   DESCRIPTION
      "Path: swPort.editConf.pppoEClient.ip.pim.overrideInterval

       Time in centi-second."
   ::= {er1646v2EthPortSwFPppOEEntry 53347584}

er1646v2EthPortSwFPppOEIpPimBsrBorder OBJECT-TYPE
   SYNTAX      INTEGER
               {
               disabled (0),
               enabled (1)
               }
   MAX-ACCESS  read-write
   STATUS      current
   DESCRIPTION
      "Path: swPort.editConf.pppoEClient.ip.pim.bsrBorder

       Possibilities:
               disabled   (0)
               enabled   (1)"
   ::= {er1646v2EthPortSwFPppOEEntry 53347840}

er1646v2EthPortSwFPppOEIpPimTtlThreshold OBJECT-TYPE
   SYNTAX      Integer32
   MAX-ACCESS  read-write
   STATUS      current
   DESCRIPTION
      "Path: swPort.editConf.pppoEClient.ip.pim.ttlThreshold"
   ::= {er1646v2EthPortSwFPppOEEntry 53348096}

er1646v2EthPortSwFPppOEIpIMNetworkUnreachable OBJECT-TYPE
   SYNTAX      INTEGER
               {
               disabled (0),
               enabled (1)
               }
   MAX-ACCESS  read-write
   STATUS      current
   DESCRIPTION
      "Path: swPort.editConf.pppoEClient.ip.icmpMessages.networkUnreachable

       Possibilities:
               disabled   (0)
               enabled   (1)"
   ::= {er1646v2EthPortSwFPppOEEntry 53412096}

er1646v2EthPortSwFPppOEIpIMHostUnreachable OBJECT-TYPE
   SYNTAX      INTEGER
               {
               disabled (0),
               enabled (1)
               }
   MAX-ACCESS  read-write
   STATUS      current
   DESCRIPTION
      "Path: swPort.editConf.pppoEClient.ip.icmpMessages.hostUnreachable

       Possibilities:
               disabled   (0)
               enabled   (1)"
   ::= {er1646v2EthPortSwFPppOEEntry 53412352}

er1646v2EthPortSwFPppOEIpIMProtocolUnreachable OBJECT-TYPE
   SYNTAX      INTEGER
               {
               disabled (0),
               enabled (1)
               }
   MAX-ACCESS  read-write
   STATUS      current
   DESCRIPTION
      "Path: swPort.editConf.pppoEClient.ip.icmpMessages.protocolUnreachable

       Possibilities:
               disabled   (0)
               enabled   (1)"
   ::= {er1646v2EthPortSwFPppOEEntry 53412608}

er1646v2EthPortSwFPppOEIpIMPortUnreachable OBJECT-TYPE
   SYNTAX      INTEGER
               {
               disabled (0),
               enabled (1)
               }
   MAX-ACCESS  read-write
   STATUS      current
   DESCRIPTION
      "Path: swPort.editConf.pppoEClient.ip.icmpMessages.portUnreachable

       Possibilities:
               disabled   (0)
               enabled   (1)"
   ::= {er1646v2EthPortSwFPppOEEntry 53412864}

er1646v2EthPortSwFPppOEIpIMMtuExceeded OBJECT-TYPE
   SYNTAX      INTEGER
               {
               disabled (0),
               enabled (1)
               }
   MAX-ACCESS  read-write
   STATUS      current
   DESCRIPTION
      "Path: swPort.editConf.pppoEClient.ip.icmpMessages.mtuExceeded

       Possibilities:
               disabled   (0)
               enabled   (1)"
   ::= {er1646v2EthPortSwFPppOEEntry 53413120}

er1646v2EthPortSwFPppOEIpIMAdminProhibited OBJECT-TYPE
   SYNTAX      INTEGER
               {
               disabled (0),
               enabled (1)
               }
   MAX-ACCESS  read-write
   STATUS      current
   DESCRIPTION
      "Path: swPort.editConf.pppoEClient.ip.icmpMessages.adminProhibited

       Possibilities:
               disabled   (0)
               enabled   (1)"
   ::= {er1646v2EthPortSwFPppOEEntry 53413376}

er1646v2EthPortSwFPppOEIpIMTtlExceeded OBJECT-TYPE
   SYNTAX      INTEGER
               {
               disabled (0),
               enabled (1)
               }
   MAX-ACCESS  read-write
   STATUS      current
   DESCRIPTION
      "Path: swPort.editConf.pppoEClient.ip.icmpMessages.ttlExceeded

       Possibilities:
               disabled   (0)
               enabled   (1)"
   ::= {er1646v2EthPortSwFPppOEEntry 53413632}

er1646v2EthPortSwFPppOEIpIMRedirect OBJECT-TYPE
   SYNTAX      INTEGER
               {
               disabled (0),
               enabled (1)
               }
   MAX-ACCESS  read-write
   STATUS      current
   DESCRIPTION
      "Path: swPort.editConf.pppoEClient.ip.icmpMessages.redirect

       Possibilities:
               disabled   (0)
               enabled   (1)"
   ::= {er1646v2EthPortSwFPppOEEntry 53413888}

er1646v2EthPortSwFPppOEIpV6VrfRouter OBJECT-TYPE
   SYNTAX      DisplayString
   MAX-ACCESS  read-write
   STATUS      current
   DESCRIPTION
      "Path: swPort.editConf.pppoEClient.ipV6.vrfRouter"
   ::= {er1646v2EthPortSwFPppOEEntry 704708608}

er1646v2EthPortSwFPppOEIpV6AddrAutoConfigNrDupAddrDetects OBJECT-TYPE
   SYNTAX      Integer32
   MAX-ACCESS  read-write
   STATUS      current
   DESCRIPTION
      "Path: swPort.editConf.pppoEClient.ipV6.addrAutoConfig.nrDupAddrDetects"
   ::= {er1646v2EthPortSwFPppOEEntry 704905472}

er1646v2EthPortSwFPppOEIpV6AddrAutoConfigAcceptRa OBJECT-TYPE
   SYNTAX      INTEGER
               {
               disabled (0),
               enabled (1)
               }
   MAX-ACCESS  read-write
   STATUS      current
   DESCRIPTION
      "Path: swPort.editConf.pppoEClient.ipV6.addrAutoConfig.acceptRa

       Possibilities:
               disabled   (0)
               enabled   (1)"
   ::= {er1646v2EthPortSwFPppOEEntry 704905728}

er1646v2EthPortSwFPppOEIpV6AddrAutoConfigAcceptRaRdnss OBJECT-TYPE
   SYNTAX      INTEGER
               {
               disabled (0),
               enabled (1)
               }
   MAX-ACCESS  read-write
   STATUS      current
   DESCRIPTION
      "Path: swPort.editConf.pppoEClient.ipV6.addrAutoConfig.acceptRaRdnss

       Possibilities:
               disabled   (0)
               enabled   (1)"
   ::= {er1646v2EthPortSwFPppOEEntry 704905984}

er1646v2EthPortSwFPppOEIpV6AddrAutoConfigAcceptRaDnssl OBJECT-TYPE
   SYNTAX      INTEGER
               {
               disabled (0),
               enabled (1)
               }
   MAX-ACCESS  read-write
   STATUS      current
   DESCRIPTION
      "Path: swPort.editConf.pppoEClient.ipV6.addrAutoConfig.acceptRaDnssl

       Possibilities:
               disabled   (0)
               enabled   (1)"
   ::= {er1646v2EthPortSwFPppOEEntry 704906240}

er1646v2EthPortSwFPppOEIpV6DefaultRoute OBJECT-TYPE
   SYNTAX      INTEGER
               {
               disabled (0),
               enabled (1)
               }
   MAX-ACCESS  read-write
   STATUS      current
   DESCRIPTION
      "Path: swPort.editConf.pppoEClient.ipV6.defaultRoute

       Possibilities:
               disabled   (0)
               enabled   (1)"
   ::= {er1646v2EthPortSwFPppOEEntry 704970752}

er1646v2EthPortSwFPppOEIpV6RaSend OBJECT-TYPE
   SYNTAX      INTEGER
               {
               disabled (0),
               enabled (1)
               }
   MAX-ACCESS  read-write
   STATUS      current
   DESCRIPTION
      "Path: swPort.editConf.pppoEClient.ipV6.ra.send

       Possibilities:
               disabled   (0)
               enabled   (1)"
   ::= {er1646v2EthPortSwFPppOEEntry 705036544}

er1646v2EthPortSwFPppOEIpV6RaMinInterval OBJECT-TYPE
   SYNTAX      TimeTicks
   MAX-ACCESS  read-write
   STATUS      current
   DESCRIPTION
      "Path: swPort.editConf.pppoEClient.ipV6.ra.minInterval

       Time in centi-second."
   ::= {er1646v2EthPortSwFPppOEEntry 705036800}

er1646v2EthPortSwFPppOEIpV6RaMaxInterval OBJECT-TYPE
   SYNTAX      TimeTicks
   MAX-ACCESS  read-write
   STATUS      current
   DESCRIPTION
      "Path: swPort.editConf.pppoEClient.ipV6.ra.maxInterval

       Time in centi-second."
   ::= {er1646v2EthPortSwFPppOEEntry 705037056}

er1646v2EthPortSwFPppOEIpV6RaManagedFlag OBJECT-TYPE
   SYNTAX      INTEGER
               {
               disabled (0),
               enabled (1)
               }
   MAX-ACCESS  read-write
   STATUS      current
   DESCRIPTION
      "Path: swPort.editConf.pppoEClient.ipV6.ra.managedFlag

       Possibilities:
               disabled   (0)
               enabled   (1)"
   ::= {er1646v2EthPortSwFPppOEEntry 705037312}

er1646v2EthPortSwFPppOEIpV6RaOtherConfFlag OBJECT-TYPE
   SYNTAX      INTEGER
               {
               disabled (0),
               enabled (1)
               }
   MAX-ACCESS  read-write
   STATUS      current
   DESCRIPTION
      "Path: swPort.editConf.pppoEClient.ipV6.ra.otherConfFlag

       Possibilities:
               disabled   (0)
               enabled   (1)"
   ::= {er1646v2EthPortSwFPppOEEntry 705037568}

er1646v2EthPortSwFPppOEIpV6RaLinkMtu OBJECT-TYPE
   SYNTAX      Integer32
   MAX-ACCESS  read-write
   STATUS      current
   DESCRIPTION
      "Path: swPort.editConf.pppoEClient.ipV6.ra.linkMtu"
   ::= {er1646v2EthPortSwFPppOEEntry 705037824}

er1646v2EthPortSwFPppOEIpV6RaReachableTime OBJECT-TYPE
   SYNTAX      TimeTicks
   MAX-ACCESS  read-write
   STATUS      current
   DESCRIPTION
      "Path: swPort.editConf.pppoEClient.ipV6.ra.reachableTime

       Time in centi-second."
   ::= {er1646v2EthPortSwFPppOEEntry 705038080}

er1646v2EthPortSwFPppOEIpV6RaRetransmitTime OBJECT-TYPE
   SYNTAX      TimeTicks
   MAX-ACCESS  read-write
   STATUS      current
   DESCRIPTION
      "Path: swPort.editConf.pppoEClient.ipV6.ra.retransmitTime

       Time in centi-second."
   ::= {er1646v2EthPortSwFPppOEEntry 705038336}

er1646v2EthPortSwFPppOEIpV6RaHopLimit OBJECT-TYPE
   SYNTAX      Integer32
   MAX-ACCESS  read-write
   STATUS      current
   DESCRIPTION
      "Path: swPort.editConf.pppoEClient.ipV6.ra.hopLimit"
   ::= {er1646v2EthPortSwFPppOEEntry 705038592}

er1646v2EthPortSwFPppOEIpV6RaDefaultLifeTime OBJECT-TYPE
   SYNTAX      TimeTicks
   MAX-ACCESS  read-write
   STATUS      current
   DESCRIPTION
      "Path: swPort.editConf.pppoEClient.ipV6.ra.defaultLifeTime

       Time in centi-second."
   ::= {er1646v2EthPortSwFPppOEEntry 705038848}

er1646v2EthPortSwFPppOEIpV6RaDnsOptionsRdnssLifeTime OBJECT-TYPE
   SYNTAX      TimeTicks
   MAX-ACCESS  read-write
   STATUS      current
   DESCRIPTION
      "Path: swPort.editConf.pppoEClient.ipV6.ra.dnsOptions.rdnss.lifeTime

       Time in centi-second."
   ::= {er1646v2EthPortSwFPppOEEntry 705039140}

er1646v2EthPortSwFPppOEIpV6RaDnsOptionsRdnssImportServers OBJECT-TYPE
   SYNTAX      INTEGER
               {
               disabled (0),
               enabled (1)
               }
   MAX-ACCESS  read-write
   STATUS      current
   DESCRIPTION
      "Path: swPort.editConf.pppoEClient.ipV6.ra.dnsOptions.rdnss.importServers

       Possibilities:
               disabled   (0)
               enabled   (1)"
   ::= {er1646v2EthPortSwFPppOEEntry 705039148}

er1646v2EthPortSwFPppOEIpV6RaDnsOptionsDnsslLifeTime OBJECT-TYPE
   SYNTAX      TimeTicks
   MAX-ACCESS  read-write
   STATUS      current
   DESCRIPTION
      "Path: swPort.editConf.pppoEClient.ipV6.ra.dnsOptions.dnssl.lifeTime

       Time in centi-second."
   ::= {er1646v2EthPortSwFPppOEEntry 705039172}

er1646v2EthPortSwFPppOEIpV6RaDnsOptionsDnsslImportDomains OBJECT-TYPE
   SYNTAX      INTEGER
               {
               disabled (0),
               enabled (1)
               }
   MAX-ACCESS  read-write
   STATUS      current
   DESCRIPTION
      "Path: swPort.editConf.pppoEClient.ipV6.ra.dnsOptions.dnssl.importDomains

       Possibilities:
               disabled   (0)
               enabled   (1)"
   ::= {er1646v2EthPortSwFPppOEEntry 705039180}

er1646v2EthPortSwFPppOEIpV6RsSend OBJECT-TYPE
   SYNTAX      INTEGER
               {
               disabled (0),
               enabled (1)
               }
   MAX-ACCESS  read-write
   STATUS      current
   DESCRIPTION
      "Path: swPort.editConf.pppoEClient.ipV6.rs.send

       Possibilities:
               disabled   (0)
               enabled   (1)"
   ::= {er1646v2EthPortSwFPppOEEntry 705954048}

er1646v2EthPortSwFPppOEIpV6RsMaxRandomDelay OBJECT-TYPE
   SYNTAX      TimeTicks
   MAX-ACCESS  read-write
   STATUS      current
   DESCRIPTION
      "Path: swPort.editConf.pppoEClient.ipV6.rs.maxRandomDelay

       Time in centi-second."
   ::= {er1646v2EthPortSwFPppOEEntry 705954304}

er1646v2EthPortSwFPppOEIpV6RsInterval OBJECT-TYPE
   SYNTAX      TimeTicks
   MAX-ACCESS  read-write
   STATUS      current
   DESCRIPTION
      "Path: swPort.editConf.pppoEClient.ipV6.rs.interval

       Time in centi-second."
   ::= {er1646v2EthPortSwFPppOEEntry 705954560}

er1646v2EthPortSwFPppOEIpV6RsMaxSolicitations OBJECT-TYPE
   SYNTAX      Integer32
   MAX-ACCESS  read-write
   STATUS      current
   DESCRIPTION
      "Path: swPort.editConf.pppoEClient.ipV6.rs.maxSolicitations"
   ::= {er1646v2EthPortSwFPppOEEntry 705954816}

er1646v2EthPortSwFPppOEIpV6TrafficPolicyInbound OBJECT-TYPE
   SYNTAX      DisplayString
   MAX-ACCESS  read-write
   STATUS      current
   DESCRIPTION
      "Path: swPort.editConf.pppoEClient.ipV6.trafficPolicy.inbound"
   ::= {er1646v2EthPortSwFPppOEEntry 705364224}

er1646v2EthPortSwFPppOEIpV6TrafficPolicyOutbound OBJECT-TYPE
   SYNTAX      DisplayString
   MAX-ACCESS  read-write
   STATUS      current
   DESCRIPTION
      "Path: swPort.editConf.pppoEClient.ipV6.trafficPolicy.outbound"
   ::= {er1646v2EthPortSwFPppOEEntry 705364480}

er1646v2EthPortSwFPppOEIpV6FirewallZone OBJECT-TYPE
   SYNTAX      DisplayString
   MAX-ACCESS  read-write
   STATUS      current
   DESCRIPTION
      "Path: swPort.editConf.pppoEClient.ipV6.firewall.zone"
   ::= {er1646v2EthPortSwFPppOEEntry 705429760}

er1646v2EthPortSwFPppOEIpV6DhcpClientAddrAC OBJECT-TYPE
   SYNTAX      INTEGER
               {
               disabled (0),
               enabled (1)
               }
   MAX-ACCESS  read-write
   STATUS      current
   DESCRIPTION
      "Path: swPort.editConf.pppoEClient.ipV6.dhcp.client.addrAutoConfig

       Possibilities:
               disabled   (0)
               enabled   (1)"
   ::= {er1646v2EthPortSwFPppOEEntry 705307648}

er1646v2EthPortSwFPppOEIpV6DhcpClientPrDelMode OBJECT-TYPE
   SYNTAX      INTEGER
               {
               disabled (0),
               enabled (1)
               }
   MAX-ACCESS  read-write
   STATUS      current
   DESCRIPTION
      "Path: swPort.editConf.pppoEClient.ipV6.dhcp.client.pd.mode

       Possibilities:
               disabled   (0)
               enabled   (1)"
   ::= {er1646v2EthPortSwFPppOEEntry 705308676}

er1646v2EthPortSwFPppOEIpV6DhcpClientPrDelPool OBJECT-TYPE
   SYNTAX      DisplayString
   MAX-ACCESS  read-write
   STATUS      current
   DESCRIPTION
      "Path: swPort.editConf.pppoEClient.ipV6.dhcp.client.pd.pool"
   ::= {er1646v2EthPortSwFPppOEEntry 705308680}

er1646v2EthPortSwFPppOEIpV6DhcpClientPrDelPdExclOpt OBJECT-TYPE
   SYNTAX      INTEGER
               {
               disabled (0),
               enabled (1)
               }
   MAX-ACCESS  read-write
   STATUS      current
   DESCRIPTION
      "Path: swPort.editConf.pppoEClient.ipV6.dhcp.client.pd.pdExclOpt

       Possibilities:
               disabled   (0)
               enabled   (1)"
   ::= {er1646v2EthPortSwFPppOEEntry 705308684}

er1646v2EthPortSwFPppOEIpV6DhcpClientDnsServerPref OBJECT-TYPE
   SYNTAX      Integer32
   MAX-ACCESS  read-write
   STATUS      current
   DESCRIPTION
      "Path: swPort.editConf.pppoEClient.ipV6.dhcp.client.dns.serverPref"
   ::= {er1646v2EthPortSwFPppOEEntry 705310724}

er1646v2EthPortSwFPppOEIpV6DhcpClientRapidCommit OBJECT-TYPE
   SYNTAX      INTEGER
               {
               disabled (0),
               enabled (1)
               }
   MAX-ACCESS  read-write
   STATUS      current
   DESCRIPTION
      "Path: swPort.editConf.pppoEClient.ipV6.dhcp.client.rapidCommit

       Possibilities:
               disabled   (0)
               enabled   (1)"
   ::= {er1646v2EthPortSwFPppOEEntry 705309696}

er1646v2EthPortSwFPppOEIpV6DhcpClientTimersSolTimeOut OBJECT-TYPE
   SYNTAX      TimeTicks
   MAX-ACCESS  read-write
   STATUS      current
   DESCRIPTION
      "Path: swPort.editConf.pppoEClient.ipV6.dhcp.client.timers.solTimeOut

       Time in centi-second."
   ::= {er1646v2EthPortSwFPppOEEntry 705311748}

er1646v2EthPortSwFPppOEIpV6DhcpClientTimersSolMaxRt OBJECT-TYPE
   SYNTAX      TimeTicks
   MAX-ACCESS  read-write
   STATUS      current
   DESCRIPTION
      "Path: swPort.editConf.pppoEClient.ipV6.dhcp.client.timers.solMaxRt

       Time in centi-second."
   ::= {er1646v2EthPortSwFPppOEEntry 705311752}

er1646v2EthPortSwFPppOEIpV6DhcpClientTimersInfoRefresh OBJECT-TYPE
   SYNTAX      TimeTicks
   MAX-ACCESS  read-write
   STATUS      current
   DESCRIPTION
      "Path: swPort.editConf.pppoEClient.ipV6.dhcp.client.timers.infoRefresh

       Time in centi-second."
   ::= {er1646v2EthPortSwFPppOEEntry 705311756}

er1646v2EthPortSwFPppOEIpV6DhcpServerMode OBJECT-TYPE
   SYNTAX      INTEGER
               {
               disabled (0),
               enabled (1)
               }
   MAX-ACCESS  read-write
   STATUS      current
   DESCRIPTION
      "Path: swPort.editConf.pppoEClient.ipV6.dhcp.server.mode

       Possibilities:
               disabled   (0)
               enabled   (1)"
   ::= {er1646v2EthPortSwFPppOEEntry 705315840}

er1646v2EthPortSwFPppOEIpV6DhcpServerPreference OBJECT-TYPE
   SYNTAX      Integer32
   MAX-ACCESS  read-write
   STATUS      current
   DESCRIPTION
      "Path: swPort.editConf.pppoEClient.ipV6.dhcp.server.preference"
   ::= {er1646v2EthPortSwFPppOEEntry 705316864}

er1646v2EthPortSwFPppOEIpV6DhcpServerPool OBJECT-TYPE
   SYNTAX      DisplayString
   MAX-ACCESS  read-write
   STATUS      current
   DESCRIPTION
      "Path: swPort.editConf.pppoEClient.ipV6.dhcp.server.pool"
   ::= {er1646v2EthPortSwFPppOEEntry 705317888}

er1646v2EthPortSwFPppOEIpV6DhcpServerRapidCommit OBJECT-TYPE
   SYNTAX      INTEGER
               {
               disabled (0),
               enabled (1)
               }
   MAX-ACCESS  read-write
   STATUS      current
   DESCRIPTION
      "Path: swPort.editConf.pppoEClient.ipV6.dhcp.server.rapidCommit

       Possibilities:
               disabled   (0)
               enabled   (1)"
   ::= {er1646v2EthPortSwFPppOEEntry 705318912}

er1646v2EthPortSwFPppOEIpV6DhcpServerTimersInfoRefresh OBJECT-TYPE
   SYNTAX      TimeTicks
   MAX-ACCESS  read-write
   STATUS      current
   DESCRIPTION
      "Path: swPort.editConf.pppoEClient.ipV6.dhcp.server.timers.infoRefresh

       Time in centi-second."
   ::= {er1646v2EthPortSwFPppOEEntry 705319940}

er1646v2EthPortSwFPppOEIpV6DhcpRelayMode OBJECT-TYPE
   SYNTAX      INTEGER
               {
               disabled (0),
               enabled (1)
               }
   MAX-ACCESS  read-write
   STATUS      current
   DESCRIPTION
      "Path: swPort.editConf.pppoEClient.ipV6.dhcp.relay.mode

       Possibilities:
               disabled   (0)
               enabled   (1)"
   ::= {er1646v2EthPortSwFPppOEEntry 705323040}

er1646v2EthPortSwFPppOEIpV6SendRedirect OBJECT-TYPE
   SYNTAX      INTEGER
               {
               disabled (0),
               enabled (1)
               }
   MAX-ACCESS  read-write
   STATUS      current
   DESCRIPTION
      "Path: swPort.editConf.pppoEClient.ipV6.sendRedirect

       Possibilities:
               disabled   (0)
               enabled   (1)"
   ::= {er1646v2EthPortSwFPppOEEntry 705101824}

er1646v2EthPortSwFPppOEIpV6LinkMtu OBJECT-TYPE
   SYNTAX      Integer32
   MAX-ACCESS  read-write
   STATUS      current
   DESCRIPTION
      "Path: swPort.editConf.pppoEClient.ipV6.linkMtu"
   ::= {er1646v2EthPortSwFPppOEEntry 705167360}

er1646v2EthPortSwFPppOEIpV6InterfaceId OBJECT-TYPE
   SYNTAX      OCTET STRING
   MAX-ACCESS  read-write
   STATUS      current
   DESCRIPTION
      "Path: swPort.editConf.pppoEClient.ipV6.interfaceId"
   ::= {er1646v2EthPortSwFPppOEEntry 705232896}

er1646v2EthPortSwFPppOEIpV6MF OBJECT-TYPE
   SYNTAX      Integer32
   MAX-ACCESS  read-write
   STATUS      current
   DESCRIPTION
      "Path: swPort.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwFPppOEEntry 705757184}

er1646v2EthPortSwFPppOEIpV6IcmpMessagesNoRoute OBJECT-TYPE
   SYNTAX      INTEGER
               {
               disabled (0),
               enabled (1)
               }
   MAX-ACCESS  read-write
   STATUS      current
   DESCRIPTION
      "Path: swPort.editConf.pppoEClient.ipV6.icmpMessages.noRoute

       Possibilities:
               disabled   (0)
               enabled   (1)"
   ::= {er1646v2EthPortSwFPppOEEntry 705822976}

er1646v2EthPortSwFPppOEIpV6IcmpMessagesBeyondScope OBJECT-TYPE
   SYNTAX      INTEGER
               {
               disabled (0),
               enabled (1)
               }
   MAX-ACCESS  read-write
   STATUS      current
   DESCRIPTION
      "Path: swPort.editConf.pppoEClient.ipV6.icmpMessages.beyondScope

       Possibilities:
               disabled   (0)
               enabled   (1)"
   ::= {er1646v2EthPortSwFPppOEEntry 705823488}

er1646v2EthPortSwFPppOEIpV6IcmpMessagesAddressUnreachable OBJECT-TYPE
   SYNTAX      INTEGER
               {
               disabled (0),
               enabled (1)
               }
   MAX-ACCESS  read-write
   STATUS      current
   DESCRIPTION
      "Path: swPort.editConf.pppoEClient.ipV6.icmpMessages.addressUnreachable

       Possibilities:
               disabled   (0)
               enabled   (1)"
   ::= {er1646v2EthPortSwFPppOEEntry 705823744}

er1646v2EthPortSwFPppOEIpV6IcmpMessagesPortUnreachable OBJECT-TYPE
   SYNTAX      INTEGER
               {
               disabled (0),
               enabled (1)
               }
   MAX-ACCESS  read-write
   STATUS      current
   DESCRIPTION
      "Path: swPort.editConf.pppoEClient.ipV6.icmpMessages.portUnreachable

       Possibilities:
               disabled   (0)
               enabled   (1)"
   ::= {er1646v2EthPortSwFPppOEEntry 705824000}

er1646v2EthPortSwFPppOEIpV6IcmpMessagesPacketTooBig OBJECT-TYPE
   SYNTAX      INTEGER
               {
               disabled (0),
               enabled (1)
               }
   MAX-ACCESS  read-write
   STATUS      current
   DESCRIPTION
      "Path: swPort.editConf.pppoEClient.ipV6.icmpMessages.packetTooBig

       Possibilities:
               disabled   (0)
               enabled   (1)"
   ::= {er1646v2EthPortSwFPppOEEntry 705825280}

er1646v2EthPortSwFPppOEIpV6IcmpMessagesHopLimitExceeded OBJECT-TYPE
   SYNTAX      INTEGER
               {
               disabled (0),
               enabled (1)
               }
   MAX-ACCESS  read-write
   STATUS      current
   DESCRIPTION
      "Path: swPort.editConf.pppoEClient.ipV6.icmpMessages.hopLimitExceeded

       Possibilities:
               disabled   (0)
               enabled   (1)"
   ::= {er1646v2EthPortSwFPppOEEntry 705827840}

er1646v2EthPortSwFPppOEIpV6IcmpMessagesFragTimeExceeded OBJECT-TYPE
   SYNTAX      INTEGER
               {
               disabled (0),
               enabled (1)
               }
   MAX-ACCESS  read-write
   STATUS      current
   DESCRIPTION
      "Path: swPort.editConf.pppoEClient.ipV6.icmpMessages.fragTimeExceeded

       Possibilities:
               disabled   (0)
               enabled   (1)"
   ::= {er1646v2EthPortSwFPppOEEntry 705828096}

er1646v2EthPortSwFPppOEIpV6IcmpMessagesHeaderFieldErr OBJECT-TYPE
   SYNTAX      INTEGER
               {
               disabled (0),
               enabled (1)
               }
   MAX-ACCESS  read-write
   STATUS      current
   DESCRIPTION
      "Path: swPort.editConf.pppoEClient.ipV6.icmpMessages.headerFieldErr

       Possibilities:
               disabled   (0)
               enabled   (1)"
   ::= {er1646v2EthPortSwFPppOEEntry 705830400}

er1646v2EthPortSwFPppOEIpV6IcmpMessagesOptionUnrecognized OBJECT-TYPE
   SYNTAX      INTEGER
               {
               disabled (0),
               enabled (1)
               }
   MAX-ACCESS  read-write
   STATUS      current
   DESCRIPTION
      "Path: swPort.editConf.pppoEClient.ipV6.icmpMessages.optionUnrecognized

       Possibilities:
               disabled   (0)
               enabled   (1)"
   ::= {er1646v2EthPortSwFPppOEEntry 705830912}

er1646v2EthPortSwFPppOEIpV6IcmpMessagesRedirect OBJECT-TYPE
   SYNTAX      INTEGER
               {
               disabled (0),
               enabled (1)
               }
   MAX-ACCESS  read-write
   STATUS      current
   DESCRIPTION
      "Path: swPort.editConf.pppoEClient.ipV6.icmpMessages.redirect

       Possibilities:
               disabled   (0)
               enabled   (1)"
   ::= {er1646v2EthPortSwFPppOEEntry 705832960}

er1646v2EthPortSwFPppOEPppLnkMOperation OBJECT-TYPE
   SYNTAX      INTEGER
               {
               disabled (0),
               enabled (1)
               }
   MAX-ACCESS  read-write
   STATUS      current
   DESCRIPTION
      "Path: swPort.editConf.pppoEClient.ppp.linkMonitoring.operation

       Possibilities:
               disabled   (0)
               enabled   (1)"
   ::= {er1646v2EthPortSwFPppOEEntry 251724032}

er1646v2EthPortSwFPppOEPppLnkMInterval OBJECT-TYPE
   SYNTAX      TimeTicks
   MAX-ACCESS  read-write
   STATUS      current
   DESCRIPTION
      "Path: swPort.editConf.pppoEClient.ppp.linkMonitoring.interval

       Time in centi-second."
   ::= {er1646v2EthPortSwFPppOEEntry 251724288}

er1646v2EthPortSwFPppOEPppLnkMRepTimeOut OBJECT-TYPE
   SYNTAX      TimeTicks
   MAX-ACCESS  read-write
   STATUS      current
   DESCRIPTION
      "Path: swPort.editConf.pppoEClient.ppp.linkMonitoring.replyTimeOut

       Time in centi-second."
   ::= {er1646v2EthPortSwFPppOEEntry 251724544}

er1646v2EthPortSwFPppOEPppLnkMFailsPrmt OBJECT-TYPE
   SYNTAX      Integer32
   MAX-ACCESS  read-write
   STATUS      current
   DESCRIPTION
      "Path: swPort.editConf.pppoEClient.ppp.linkMonitoring.failsPermitted"
   ::= {er1646v2EthPortSwFPppOEEntry 251724800}

er1646v2EthPortSwFPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.pppoEClient.ppp.authentication

       Possibilities:
               disabled   (0)
               chap   (1)
               pap   (2)
               chapOrPap   (3)
               msChap   (4)
               msChapV2   (5)"
   ::= {er1646v2EthPortSwFPppOEEntry 251789312}

er1646v2EthPortSwFPppOEPppAuthenPeriod OBJECT-TYPE
   SYNTAX      TimeTicks
   MAX-ACCESS  read-write
   STATUS      current
   DESCRIPTION
      "Path: swPort.editConf.pppoEClient.ppp.authenPeriod

       Time in centi-second."
   ::= {er1646v2EthPortSwFPppOEEntry 251854848}

er1646v2EthPortSwFPppOEPppSessionName OBJECT-TYPE
   SYNTAX      DisplayString
   MAX-ACCESS  read-write
   STATUS      current
   DESCRIPTION
      "Path: swPort.editConf.pppoEClient.ppp.sessionName"
   ::= {er1646v2EthPortSwFPppOEEntry 251985920}

er1646v2EthPortSwFPppOEPppSessionSecret OBJECT-TYPE
   SYNTAX      DisplayString
   MAX-ACCESS  read-write
   STATUS      current
   DESCRIPTION
      "Path: swPort.editConf.pppoEClient.ppp.sessionSecret"
   ::= {er1646v2EthPortSwFPppOEEntry 252051456}

er1646v2EthPortSwFPppOEPppEncModeSessionSecret OBJECT-TYPE
   SYNTAX      INTEGER
               {
               none (1),
               encrypt (2),
               encType1 (3),
               invalid (128)
               }
   MAX-ACCESS  read-write
   STATUS      current
   DESCRIPTION
      "Path: swPort.editConf.pppoEClient.ppp.encModeSessionSecret

       Possibilities:
               none   (1)
               encrypt   (2)
               encType1   (3)
               invalid   (128)"
   ::= {er1646v2EthPortSwFPppOEEntry 252182528}

er1646v2EthPortSwFPppOEPppEncSessionSecret OBJECT-TYPE
   SYNTAX      DisplayString
   MAX-ACCESS  read-write
   STATUS      current
   DESCRIPTION
      "Path: swPort.editConf.pppoEClient.ppp.encSessionSecret"
   ::= {er1646v2EthPortSwFPppOEEntry 252248064}

er1646v2EthPortSwFPppOEPppServiceName OBJECT-TYPE
   SYNTAX      DisplayString
   MAX-ACCESS  read-write
   STATUS      current
   DESCRIPTION
      "Path: swPort.editConf.pppoEClient.ppp.serviceName"
   ::= {er1646v2EthPortSwFPppOEEntry 252116992}

er1646v2EthPortSwFPppOEIpH OBJECT-TYPE
   SYNTAX      SEQUENCE OF Er1646v2EthPortSwFPppOEIpHEntry
   MAX-ACCESS  not-accessible
   STATUS      current
   DESCRIPTION
      ""
   ::= {er1646v2EthPortSwFPppOE 51314688}

er1646v2EthPortSwFPppOEIpHEntry OBJECT-TYPE
   SYNTAX      Er1646v2EthPortSwFPppOEIpHEntry
   MAX-ACCESS  not-accessible
   STATUS      current
   DESCRIPTION
      ""
   INDEX      { er1646v2EthPortSwFPppOEIpHGlobalIx,
                er1646v2EthPortSwFPppOETableIx,
                er1646v2EthPortSwFPppOEIpHTableIx }
   ::= {er1646v2EthPortSwFPppOEIpH 1}

Er1646v2EthPortSwFPppOEIpHEntry ::=
   SEQUENCE
      {
      er1646v2EthPortSwFPppOEIpHActions
         VariableLengthTableActions,
      er1646v2EthPortSwFPppOEIpHGlobalIx
         GlobalIndex,
      er1646v2EthPortSwFPppOEIpHTableIx
         TableIndex,
      er1646v2EthPortSwFPppOEIpHAddress
         IpAddress,
      er1646v2EthPortSwFPppOEIpHDhcpRelayOptionSubscriberId
         DisplayString
      }

er1646v2EthPortSwFPppOEIpHActions OBJECT-TYPE
   SYNTAX      VariableLengthTableActions
   MAX-ACCESS  read-write
   STATUS      current
   DESCRIPTION
      "By way of this field, some manipulations
       on this table may be performed."
   ::= {er1646v2EthPortSwFPppOEIpHEntry 2}

er1646v2EthPortSwFPppOEIpHGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpHEntry 10}

er1646v2EthPortSwFPppOEIpHTableIx OBJECT-TYPE
   SYNTAX      TableIndex
   MAX-ACCESS  not-accessible
   STATUS      current
   DESCRIPTION
      ""
   ::= {er1646v2EthPortSwFPppOEIpHEntry 11}

er1646v2EthPortSwFPppOEIpHAddress OBJECT-TYPE
   SYNTAX      IpAddress
   MAX-ACCESS  read-write
   STATUS      current
   DESCRIPTION
      "Path: swPort.editConf.pppoEClient.ip.helpers.address"
   ::= {er1646v2EthPortSwFPppOEIpHEntry 16777216}

er1646v2EthPortSwFPppOEIpHDhcpRelayOptionSubscriberId OBJECT-TYPE
   SYNTAX      DisplayString
   MAX-ACCESS  read-write
   STATUS      current
   DESCRIPTION
      "Path: swPort.editConf.pppoEClient.ip.helpers.dhcpRelayOption.subscriberId"
   ::= {er1646v2EthPortSwFPppOEIpHEntry 33947648}

er1646v2EthPortSwFPppOEIpV6Addresses OBJECT-TYPE
   SYNTAX      SEQUENCE OF Er1646v2EthPortSwFPppOEIpV6AddressesEntry
   MAX-ACCESS  not-accessible
   STATUS      current
   DESCRIPTION
      ""
   ::= {er1646v2EthPortSwFPppOE 704839680}

er1646v2EthPortSwFPppOEIpV6AddressesEntry OBJECT-TYPE
   SYNTAX      Er1646v2EthPortSwFPppOEIpV6AddressesEntry
   MAX-ACCESS  not-accessible
   STATUS      current
   DESCRIPTION
      ""
   INDEX      { er1646v2EthPortSwFPppOEIpV6AddressesGlobalIx,
                er1646v2EthPortSwFPppOETableIx,
                er1646v2EthPortSwFPppOEIpV6AddressesTableIx }
   ::= {er1646v2EthPortSwFPppOEIpV6Addresses 1}

Er1646v2EthPortSwFPppOEIpV6AddressesEntry ::=
   SEQUENCE
      {
      er1646v2EthPortSwFPppOEIpV6AddressesActions
         VariableLengthTableActions,
      er1646v2EthPortSwFPppOEIpV6AddressesGlobalIx
         GlobalIndex,
      er1646v2EthPortSwFPppOEIpV6AddressesTableIx
         TableIndex,
      er1646v2EthPortSwFPppOEIpV6AddressesType
         INTEGER,
      er1646v2EthPortSwFPppOEIpV6AddressesAddress
         Ipv6Address,
      er1646v2EthPortSwFPppOEIpV6AddressesPrefixLength
         Integer32,
      er1646v2EthPortSwFPppOEIpV6AddressesGeneralPrefix
         DisplayString,
      er1646v2EthPortSwFPppOEIpV6AddressesRaSend
         INTEGER,
      er1646v2EthPortSwFPppOEIpV6AddressesRaOnLinkFlag
         INTEGER,
      er1646v2EthPortSwFPppOEIpV6AddressesRaAutoFlag
         INTEGER,
      er1646v2EthPortSwFPppOEIpV6AddressesRaValidLifeTime
         TimeTicks,
      er1646v2EthPortSwFPppOEIpV6AddressesRaValidLTMode
         INTEGER,
      er1646v2EthPortSwFPppOEIpV6AddressesRaPrefLifeTime
         TimeTicks,
      er1646v2EthPortSwFPppOEIpV6AddressesRaPrefLTMode
         INTEGER
      }

er1646v2EthPortSwFPppOEIpV6AddressesActions OBJECT-TYPE
   SYNTAX      VariableLengthTableActions
   MAX-ACCESS  read-write
   STATUS      current
   DESCRIPTION
      "By way of this field, some manipulations
       on this table may be performed."
   ::= {er1646v2EthPortSwFPppOEIpV6AddressesEntry 2}

er1646v2EthPortSwFPppOEIpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6AddressesEntry 10}

er1646v2EthPortSwFPppOEIpV6AddressesTableIx OBJECT-TYPE
   SYNTAX      TableIndex
   MAX-ACCESS  not-accessible
   STATUS      current
   DESCRIPTION
      ""
   ::= {er1646v2EthPortSwFPppOEIpV6AddressesEntry 11}

er1646v2EthPortSwFPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.pppoEClient.ipV6.addresses.type

       Possibilities:
               unicast   (0)
               eui64   (1)
               anycast   (2)
               linkLocal   (3)
               generalPrefix   (4)"
   ::= {er1646v2EthPortSwFPppOEIpV6AddressesEntry 50331648}

er1646v2EthPortSwFPppOEIpV6AddressesAddress OBJECT-TYPE
   SYNTAX      Ipv6Address
   MAX-ACCESS  read-write
   STATUS      current
   DESCRIPTION
      "Path: swPort.editConf.pppoEClient.ipV6.addresses.address

       ipv6 address"
   ::= {er1646v2EthPortSwFPppOEIpV6AddressesEntry 16777216}

er1646v2EthPortSwFPppOEIpV6AddressesPrefixLength OBJECT-TYPE
   SYNTAX      Integer32
   MAX-ACCESS  read-write
   STATUS      current
   DESCRIPTION
      "Path: swPort.editConf.pppoEClient.ipV6.addresses.prefixLength"
   ::= {er1646v2EthPortSwFPppOEIpV6AddressesEntry 33554432}

er1646v2EthPortSwFPppOEIpV6AddressesGeneralPrefix OBJECT-TYPE
   SYNTAX      DisplayString
   MAX-ACCESS  read-write
   STATUS      current
   DESCRIPTION
      "Path: swPort.editConf.pppoEClient.ipV6.addresses.generalPrefix"
   ::= {er1646v2EthPortSwFPppOEIpV6AddressesEntry 83886080}

er1646v2EthPortSwFPppOEIpV6AddressesRaSend OBJECT-TYPE
   SYNTAX      INTEGER
               {
               disabled (0),
               enabled (1)
               }
   MAX-ACCESS  read-write
   STATUS      current
   DESCRIPTION
      "Path: swPort.editConf.pppoEClient.ipV6.addresses.ra.send

       Possibilities:
               disabled   (0)
               enabled   (1)"
   ::= {er1646v2EthPortSwFPppOEIpV6AddressesEntry 67174400}

er1646v2EthPortSwFPppOEIpV6AddressesRaOnLinkFlag OBJECT-TYPE
   SYNTAX      INTEGER
               {
               disabled (0),
               enabled (1)
               }
   MAX-ACCESS  read-write
   STATUS      current
   DESCRIPTION
      "Path: swPort.editConf.pppoEClient.ipV6.addresses.ra.onLinkFlag

       Possibilities:
               disabled   (0)
               enabled   (1)"
   ::= {er1646v2EthPortSwFPppOEIpV6AddressesEntry 67371008}

er1646v2EthPortSwFPppOEIpV6AddressesRaAutoFlag OBJECT-TYPE
   SYNTAX      INTEGER
               {
               disabled (0),
               enabled (1)
               }
   MAX-ACCESS  read-write
   STATUS      current
   DESCRIPTION
      "Path: swPort.editConf.pppoEClient.ipV6.addresses.ra.autonomousFlag

       Possibilities:
               disabled   (0)
               enabled   (1)"
   ::= {er1646v2EthPortSwFPppOEIpV6AddressesEntry 67567616}

er1646v2EthPortSwFPppOEIpV6AddressesRaValidLifeTime OBJECT-TYPE
   SYNTAX      TimeTicks
   MAX-ACCESS  read-write
   STATUS      current
   DESCRIPTION
      "Path: swPort.editConf.pppoEClient.ipV6.addresses.ra.validLifeTime

       Time in centi-second."
   ::= {er1646v2EthPortSwFPppOEIpV6AddressesEntry 67239936}

er1646v2EthPortSwFPppOEIpV6AddressesRaValidLTMode OBJECT-TYPE
   SYNTAX      INTEGER
               {
               fixed (0),
               infinite (2)
               }
   MAX-ACCESS  read-write
   STATUS      current
   DESCRIPTION
      "Path: swPort.editConf.pppoEClient.ipV6.addresses.ra.validLifeTimeMode

       Possibilities:
               fixed   (0)
               infinite   (2)"
   ::= {er1646v2EthPortSwFPppOEIpV6AddressesEntry 67305472}

er1646v2EthPortSwFPppOEIpV6AddressesRaPrefLifeTime OBJECT-TYPE
   SYNTAX      TimeTicks
   MAX-ACCESS  read-write
   STATUS      current
   DESCRIPTION
      "Path: swPort.editConf.pppoEClient.ipV6.addresses.ra.prefLifeTime

       Time in centi-second."
   ::= {er1646v2EthPortSwFPppOEIpV6AddressesEntry 67436544}

er1646v2EthPortSwFPppOEIpV6AddressesRaPrefLTMode OBJECT-TYPE
   SYNTAX      INTEGER
               {
               fixed (0),
               infinite (2)
               }
   MAX-ACCESS  read-write
   STATUS      current
   DESCRIPTION
      "Path: swPort.editConf.pppoEClient.ipV6.addresses.ra.prefLifeTimeMode

       Possibilities:
               fixed   (0)
               infinite   (2)"
   ::= {er1646v2EthPortSwFPppOEIpV6AddressesEntry 67502080}

er1646v2EthPortSwFPppOEIpV6RaDnsOptionsRdnssServers OBJECT-TYPE
   SYNTAX      SEQUENCE OF Er1646v2EthPortSwFPppOEIpV6RaDnsOptionsRdnssServersEntry
   MAX-ACCESS  not-accessible
   STATUS      current
   DESCRIPTION
      ""
   ::= {er1646v2EthPortSwFPppOE 705039144}

er1646v2EthPortSwFPppOEIpV6RaDnsOptionsRdnssServersEntry OBJECT-TYPE
   SYNTAX      Er1646v2EthPortSwFPppOEIpV6RaDnsOptionsRdnssServersEntry
   MAX-ACCESS  not-accessible
   STATUS      current
   DESCRIPTION
      ""
   INDEX      { er1646v2EthPortSwFPppOEIpV6RaDnsOptionsRdnssServersGlobalIx,
                er1646v2EthPortSwFPppOETableIx,
                er1646v2EthPortSwFPppOEIpV6RaDnsOptionsRdnssServersTableIx }
   ::= {er1646v2EthPortSwFPppOEIpV6RaDnsOptionsRdnssServers 1}

Er1646v2EthPortSwFPppOEIpV6RaDnsOptionsRdnssServersEntry ::=
   SEQUENCE
      {
      er1646v2EthPortSwFPppOEIpV6RaDnsOptionsRdnssServersActions
         VariableLengthTableActions,
      er1646v2EthPortSwFPppOEIpV6RaDnsOptionsRdnssServersGlobalIx
         GlobalIndex,
      er1646v2EthPortSwFPppOEIpV6RaDnsOptionsRdnssServersTableIx
         TableIndex,
      er1646v2EthPortSwFPppOEIpV6RaDnsOptionsRdnssServersAddress
         Ipv6Address
      }

er1646v2EthPortSwFPppOEIpV6RaDnsOptionsRdnssServersActions OBJECT-TYPE
   SYNTAX      VariableLengthTableActions
   MAX-ACCESS  read-write
   STATUS      current
   DESCRIPTION
      "By way of this field, some manipulations
       on this table may be performed."
   ::= {er1646v2EthPortSwFPppOEIpV6RaDnsOptionsRdnssServersEntry 2}

er1646v2EthPortSwFPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6RaDnsOptionsRdnssServersEntry 10}

er1646v2EthPortSwFPppOEIpV6RaDnsOptionsRdnssServersTableIx OBJECT-TYPE
   SYNTAX      TableIndex
   MAX-ACCESS  not-accessible
   STATUS      current
   DESCRIPTION
      ""
   ::= {er1646v2EthPortSwFPppOEIpV6RaDnsOptionsRdnssServersEntry 11}

er1646v2EthPortSwFPppOEIpV6RaDnsOptionsRdnssServersAddress OBJECT-TYPE
   SYNTAX      Ipv6Address
   MAX-ACCESS  read-write
   STATUS      current
   DESCRIPTION
      "Path: swPort.editConf.pppoEClient.ipV6.ra.dnsOptions.rdnss.servers.address

       ipv6 address"
   ::= {er1646v2EthPortSwFPppOEIpV6RaDnsOptionsRdnssServersEntry 16777216}

er1646v2EthPortSwFPppOEIpV6RaDnsOptionsDnsslDomains OBJECT-TYPE
   SYNTAX      SEQUENCE OF Er1646v2EthPortSwFPppOEIpV6RaDnsOptionsDnsslDomainsEntry
   MAX-ACCESS  not-accessible
   STATUS      current
   DESCRIPTION
      ""
   ::= {er1646v2EthPortSwFPppOE 705039176}

er1646v2EthPortSwFPppOEIpV6RaDnsOptionsDnsslDomainsEntry OBJECT-TYPE
   SYNTAX      Er1646v2EthPortSwFPppOEIpV6RaDnsOptionsDnsslDomainsEntry
   MAX-ACCESS  not-accessible
   STATUS      current
   DESCRIPTION
      ""
   INDEX      { er1646v2EthPortSwFPppOEIpV6RaDnsOptionsDnsslDomainsGlobalIx,
                er1646v2EthPortSwFPppOETableIx,
                er1646v2EthPortSwFPppOEIpV6RaDnsOptionsDnsslDomainsTableIx }
   ::= {er1646v2EthPortSwFPppOEIpV6RaDnsOptionsDnsslDomains 1}

Er1646v2EthPortSwFPppOEIpV6RaDnsOptionsDnsslDomainsEntry ::=
   SEQUENCE
      {
      er1646v2EthPortSwFPppOEIpV6RaDnsOptionsDnsslDomainsActions
         VariableLengthTableActions,
      er1646v2EthPortSwFPppOEIpV6RaDnsOptionsDnsslDomainsGlobalIx
         GlobalIndex,
      er1646v2EthPortSwFPppOEIpV6RaDnsOptionsDnsslDomainsTableIx
         TableIndex,
      er1646v2EthPortSwFPppOEIpV6RaDnsOptionsDnsslDomainsName
         DisplayString
      }

er1646v2EthPortSwFPppOEIpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwFPppOEIpV6RaDnsOptionsDnsslDomainsEntry 2}

er1646v2EthPortSwFPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6RaDnsOptionsDnsslDomainsEntry 10}

er1646v2EthPortSwFPppOEIpV6RaDnsOptionsDnsslDomainsTableIx OBJECT-TYPE
   SYNTAX      TableIndex
   MAX-ACCESS  not-accessible
   STATUS      current
   DESCRIPTION
      ""
   ::= {er1646v2EthPortSwFPppOEIpV6RaDnsOptionsDnsslDomainsEntry 11}

er1646v2EthPortSwFPppOEIpV6RaDnsOptionsDnsslDomainsName OBJECT-TYPE
   SYNTAX      DisplayString
   MAX-ACCESS  read-write
   STATUS      current
   DESCRIPTION
      "Path: swPort.editConf.pppoEClient.ipV6.ra.dnsOptions.dnssl.domains.name"
   ::= {er1646v2EthPortSwFPppOEIpV6RaDnsOptionsDnsslDomainsEntry 16777216}

er1646v2EthPortSwFPppOEIpV6DhcpClientUserClassOpt OBJECT-TYPE
   SYNTAX      SEQUENCE OF Er1646v2EthPortSwFPppOEIpV6DhcpClientUserClassOptEntry
   MAX-ACCESS  not-accessible
   STATUS      current
   DESCRIPTION
      ""
   ::= {er1646v2EthPortSwFPppOE 705312768}

er1646v2EthPortSwFPppOEIpV6DhcpClientUserClassOptEntry OBJECT-TYPE
   SYNTAX      Er1646v2EthPortSwFPppOEIpV6DhcpClientUserClassOptEntry
   MAX-ACCESS  not-accessible
   STATUS      current
   DESCRIPTION
      ""
   INDEX      { er1646v2EthPortSwFPppOEIpV6DhcpClientUserClassOptGlobalIx,
                er1646v2EthPortSwFPppOETableIx,
                er1646v2EthPortSwFPppOEIpV6DhcpClientUserClassOptTableIx }
   ::= {er1646v2EthPortSwFPppOEIpV6DhcpClientUserClassOpt 1}

Er1646v2EthPortSwFPppOEIpV6DhcpClientUserClassOptEntry ::=
   SEQUENCE
      {
      er1646v2EthPortSwFPppOEIpV6DhcpClientUserClassOptActions
         VariableLengthTableActions,
      er1646v2EthPortSwFPppOEIpV6DhcpClientUserClassOptGlobalIx
         GlobalIndex,
      er1646v2EthPortSwFPppOEIpV6DhcpClientUserClassOptTableIx
         TableIndex,
      er1646v2EthPortSwFPppOEIpV6DhcpClientUserClassOptValueAscii
         DisplayString,
      er1646v2EthPortSwFPppOEIpV6DhcpClientUserClassOptValueDecimal
         Integer32,
      er1646v2EthPortSwFPppOEIpV6DhcpClientUserClassOptValueHexData
         OCTET STRING
      }

er1646v2EthPortSwFPppOEIpV6DhcpClientUserClassOptActions OBJECT-TYPE
   SYNTAX      VariableLengthTableActions
   MAX-ACCESS  read-write
   STATUS      current
   DESCRIPTION
      "By way of this field, some manipulations
       on this table may be performed."
   ::= {er1646v2EthPortSwFPppOEIpV6DhcpClientUserClassOptEntry 2}

er1646v2EthPortSwFPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6DhcpClientUserClassOptEntry 10}

er1646v2EthPortSwFPppOEIpV6DhcpClientUserClassOptTableIx OBJECT-TYPE
   SYNTAX      TableIndex
   MAX-ACCESS  not-accessible
   STATUS      current
   DESCRIPTION
      ""
   ::= {er1646v2EthPortSwFPppOEIpV6DhcpClientUserClassOptEntry 11}

er1646v2EthPortSwFPppOEIpV6DhcpClientUserClassOptValueAscii OBJECT-TYPE
   SYNTAX      DisplayString
   MAX-ACCESS  read-write
   STATUS      current
   DESCRIPTION
      "Path: swPort.editConf.pppoEClient.ipV6.dhcp.client.userClassOpt.value.ascii"
   ::= {er1646v2EthPortSwFPppOEIpV6DhcpClientUserClassOptEntry 16842752}

er1646v2EthPortSwFPppOEIpV6DhcpClientUserClassOptValueDecimal OBJECT-TYPE
   SYNTAX      Integer32
   MAX-ACCESS  read-write
   STATUS      current
   DESCRIPTION
      "Path: swPort.editConf.pppoEClient.ipV6.dhcp.client.userClassOpt.value.decimal"
   ::= {er1646v2EthPortSwFPppOEIpV6DhcpClientUserClassOptEntry 16908288}

er1646v2EthPortSwFPppOEIpV6DhcpClientUserClassOptValueHexData OBJECT-TYPE
   SYNTAX      OCTET STRING
   MAX-ACCESS  read-write
   STATUS      current
   DESCRIPTION
      "Path: swPort.editConf.pppoEClient.ipV6.dhcp.client.userClassOpt.value.hexData"
   ::= {er1646v2EthPortSwFPppOEIpV6DhcpClientUserClassOptEntry 16973824}

er1646v2EthPortSwFPppOEIpV6DhcpClientVendorCl OBJECT-TYPE
   SYNTAX      SEQUENCE OF Er1646v2EthPortSwFPppOEIpV6DhcpClientVendorClEntry
   MAX-ACCESS  not-accessible
   STATUS      current
   DESCRIPTION
      ""
   ::= {er1646v2EthPortSwFPppOE 705313792}

er1646v2EthPortSwFPppOEIpV6DhcpClientVendorClEntry OBJECT-TYPE
   SYNTAX      Er1646v2EthPortSwFPppOEIpV6DhcpClientVendorClEntry
   MAX-ACCESS  not-accessible
   STATUS      current
   DESCRIPTION
      ""
   INDEX      { er1646v2EthPortSwFPppOEIpV6DhcpClientVendorClGlobalIx,
                er1646v2EthPortSwFPppOETableIx,
                er1646v2EthPortSwFPppOEIpV6DhcpClientVendorClTableIx }
   ::= {er1646v2EthPortSwFPppOEIpV6DhcpClientVendorCl 1}

Er1646v2EthPortSwFPppOEIpV6DhcpClientVendorClEntry ::=
   SEQUENCE
      {
      er1646v2EthPortSwFPppOEIpV6DhcpClientVendorClActions
         VariableLengthTableActions,
      er1646v2EthPortSwFPppOEIpV6DhcpClientVendorClGlobalIx
         GlobalIndex,
      er1646v2EthPortSwFPppOEIpV6DhcpClientVendorClTableIx
         TableIndex,
      er1646v2EthPortSwFPppOEIpV6DhcpClientVendorClValueAscii
         DisplayString,
      er1646v2EthPortSwFPppOEIpV6DhcpClientVendorClValueDecimal
         Integer32,
      er1646v2EthPortSwFPppOEIpV6DhcpClientVendorClValueHexData
         OCTET STRING
      }

er1646v2EthPortSwFPppOEIpV6DhcpClientVendorClActions OBJECT-TYPE
   SYNTAX      VariableLengthTableActions
   MAX-ACCESS  read-write
   STATUS      current
   DESCRIPTION
      "By way of this field, some manipulations
       on this table may be performed."
   ::= {er1646v2EthPortSwFPppOEIpV6DhcpClientVendorClEntry 2}

er1646v2EthPortSwFPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6DhcpClientVendorClEntry 10}

er1646v2EthPortSwFPppOEIpV6DhcpClientVendorClTableIx OBJECT-TYPE
   SYNTAX      TableIndex
   MAX-ACCESS  not-accessible
   STATUS      current
   DESCRIPTION
      ""
   ::= {er1646v2EthPortSwFPppOEIpV6DhcpClientVendorClEntry 11}

er1646v2EthPortSwFPppOEIpV6DhcpClientVendorClValueAscii OBJECT-TYPE
   SYNTAX      DisplayString
   MAX-ACCESS  read-write
   STATUS      current
   DESCRIPTION
      "Path: swPort.editConf.pppoEClient.ipV6.dhcp.client.vendorClassOpt.value.ascii"
   ::= {er1646v2EthPortSwFPppOEIpV6DhcpClientVendorClEntry 16842752}

er1646v2EthPortSwFPppOEIpV6DhcpClientVendorClValueDecimal OBJECT-TYPE
   SYNTAX      Integer32
   MAX-ACCESS  read-write
   STATUS      current
   DESCRIPTION
      "Path: swPort.editConf.pppoEClient.ipV6.dhcp.client.vendorClassOpt.value.decimal"
   ::= {er1646v2EthPortSwFPppOEIpV6DhcpClientVendorClEntry 16908288}

er1646v2EthPortSwFPppOEIpV6DhcpClientVendorClValueHexData OBJECT-TYPE
   SYNTAX      OCTET STRING
   MAX-ACCESS  read-write
   STATUS      current
   DESCRIPTION
      "Path: swPort.editConf.pppoEClient.ipV6.dhcp.client.vendorClassOpt.value.hexData"
   ::= {er1646v2EthPortSwFPppOEIpV6DhcpClientVendorClEntry 16973824}

er1646v2EthPortSwFPppOEIpV6DhcpRelayDestinations OBJECT-TYPE
   SYNTAX      SEQUENCE OF Er1646v2EthPortSwFPppOEIpV6DhcpRelayDestinationsEntry
   MAX-ACCESS  not-accessible
   STATUS      current
   DESCRIPTION
      ""
   ::= {er1646v2EthPortSwFPppOE 705323072}

er1646v2EthPortSwFPppOEIpV6DhcpRelayDestinationsEntry OBJECT-TYPE
   SYNTAX      Er1646v2EthPortSwFPppOEIpV6DhcpRelayDestinationsEntry
   MAX-ACCESS  not-accessible
   STATUS      current
   DESCRIPTION
      ""
   INDEX      { er1646v2EthPortSwFPppOEIpV6DhcpRelayDestinationsGlobalIx,
                er1646v2EthPortSwFPppOETableIx,
                er1646v2EthPortSwFPppOEIpV6DhcpRelayDestinationsTableIx }
   ::= {er1646v2EthPortSwFPppOEIpV6DhcpRelayDestinations 1}

Er1646v2EthPortSwFPppOEIpV6DhcpRelayDestinationsEntry ::=
   SEQUENCE
      {
      er1646v2EthPortSwFPppOEIpV6DhcpRelayDestinationsActions
         VariableLengthTableActions,
      er1646v2EthPortSwFPppOEIpV6DhcpRelayDestinationsGlobalIx
         GlobalIndex,
      er1646v2EthPortSwFPppOEIpV6DhcpRelayDestinationsTableIx
         TableIndex,
      er1646v2EthPortSwFPppOEIpV6DhcpRelayDestinationsAddress
         Ipv6Address,
      er1646v2EthPortSwFPppOEIpV6DhcpRelayDestinationsInterface
         DisplayString
      }

er1646v2EthPortSwFPppOEIpV6DhcpRelayDestinationsActions OBJECT-TYPE
   SYNTAX      VariableLengthTableActions
   MAX-ACCESS  read-write
   STATUS      current
   DESCRIPTION
      "By way of this field, some manipulations
       on this table may be performed."
   ::= {er1646v2EthPortSwFPppOEIpV6DhcpRelayDestinationsEntry 2}

er1646v2EthPortSwFPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwFPppOEIpV6DhcpRelayDestinationsEntry 10}

er1646v2EthPortSwFPppOEIpV6DhcpRelayDestinationsTableIx OBJECT-TYPE
   SYNTAX      TableIndex
   MAX-ACCESS  not-accessible
   STATUS      current
   DESCRIPTION
      ""
   ::= {er1646v2EthPortSwFPppOEIpV6DhcpRelayDestinationsEntry 11}

er1646v2EthPortSwFPppOEIpV6DhcpRelayDestinationsAddress OBJECT-TYPE
   SYNTAX      Ipv6Address
   MAX-ACCESS  read-write
   STATUS      current
   DESCRIPTION
      "Path: swPort.editConf.pppoEClient.ipV6.dhcp.relay.destinations.address

       ipv6 address"
   ::= {er1646v2EthPortSwFPppOEIpV6DhcpRelayDestinationsEntry 16777216}

er1646v2EthPortSwFPppOEIpV6DhcpRelayDestinationsInterface OBJECT-TYPE
   SYNTAX      DisplayString
   MAX-ACCESS  read-write
   STATUS      current
   DESCRIPTION
      "Path: swPort.editConf.pppoEClient.ipV6.dhcp.relay.destinations.interface"
   ::= {er1646v2EthPortSwFPppOEIpV6DhcpRelayDestinationsEntry 33554432}


er1646v2EthPortSwFPppOES OBJECT IDENTIFIER ::= {er1646v2EthPortSwF 37}

er1646v2EthPortSwFPppOESTable OBJECT-TYPE
   SYNTAX      SEQUENCE OF Er1646v2EthPortSwFPppOESEntry
   MAX-ACCESS  not-accessible
   STATUS      current
   DESCRIPTION
      "ppp server name on interface"
   ::= {er1646v2EthPortSwFPppOES 1}

er1646v2EthPortSwFPppOESEntry OBJECT-TYPE
   SYNTAX      Er1646v2EthPortSwFPppOESEntry
   MAX-ACCESS  not-accessible
   STATUS      current
   DESCRIPTION
      ""
   INDEX      { er1646v2EthPortSwFPppOESGlobalIx }
   ::= {er1646v2EthPortSwFPppOESTable 1}

Er1646v2EthPortSwFPppOESEntry ::=
   SEQUENCE
      {
      er1646v2EthPortSwFPppOESGlobalIx
         GlobalIndex,
      er1646v2EthPortSwFPppOESValue
         DisplayString
      }

er1646v2EthPortSwFPppOESGlobalIx OBJECT-TYPE
   SYNTAX      GlobalIndex
   MAX-ACCESS  not-accessible
   STATUS      current
   DESCRIPTION
      "The value of the tlsCntTreeGlobalIndex of the MANAGED OBJECT."
   ::= {er1646v2EthPortSwFPppOESEntry 10}

er1646v2EthPortSwFPppOESValue OBJECT-TYPE
   SYNTAX      DisplayString
   MAX-ACCESS  read-write
   STATUS      current
   DESCRIPTION
      "Path: swPort.editConf.pppoEServer"
   ::= {er1646v2EthPortSwFPppOESEntry 2147483648}


er1646v2EthPortSwFAdminStatus OBJECT IDENTIFIER ::= {er1646v2EthPortSwF 106}

er1646v2EthPortSwFAdminStatusTable OBJECT-TYPE
   SYNTAX      SEQUENCE OF Er1646v2EthPortSwFAdminStatusEntry
   MAX-ACCESS  not-accessible
   STATUS      current
   DESCRIPTION
      "ifAdminStatus"
   ::= {er1646v2EthPortSwFAdminStatus 1}

er1646v2EthPortSwFAdminStatusEntry OBJECT-TYPE
   SYNTAX      Er1646v2EthPortSwFAdminStatusEntry
   MAX-ACCESS  not-accessible
   STATUS      current
   DESCRIPTION
      ""
   INDEX      { er1646v2EthPortSwFAdminStatusGlobalIx }
   ::= {er1646v2EthPortSwFAdminStatusTable 1}

Er1646v2EthPortSwFAdminStatusEntry ::=
   SEQUENCE
      {
      er1646v2EthPortSwFAdminStatusGlobalIx
         GlobalIndex,
      er1646v2EthPortSwFAdminStatusValue
         INTEGER
      }

er1646v2EthPortSwFAdminStatusGlobalIx OBJECT-TYPE
   SYNTAX      GlobalIndex
   MAX-ACCESS  not-accessible
   STATUS      current
   DESCRIPTION
      "The value of the tlsCntTreeGlobalIndex of the MANAGED OBJECT."
   ::= {er1646v2EthPortSwFAdminStatusEntry 10}

er1646v2EthPortSwFAdminStatusValue OBJECT-TYPE
   SYNTAX      INTEGER
               {
               up (1),
               down (2)
               }
   MAX-ACCESS  read-write
   STATUS      current
   DESCRIPTION
      "Path: swPort.editConf.adminStatus

       Possibilities:
               up   (1)
               down   (2)"
   ::= {er1646v2EthPortSwFAdminStatusEntry 2147483648}


er1646v2EthPortSwFAlarmMask OBJECT IDENTIFIER ::= {er1646v2EthPortSwF 135}

er1646v2EthPortSwFAlarmMaskTable OBJECT-TYPE
   SYNTAX      SEQUENCE OF Er1646v2EthPortSwFAlarmMaskEntry
   MAX-ACCESS  not-accessible
   STATUS      current
   DESCRIPTION
      "ifAlarmMask"
   ::= {er1646v2EthPortSwFAlarmMask 1}

er1646v2EthPortSwFAlarmMaskEntry OBJECT-TYPE
   SYNTAX      Er1646v2EthPortSwFAlarmMaskEntry
   MAX-ACCESS  not-accessible
   STATUS      current
   DESCRIPTION
      ""
   INDEX      { er1646v2EthPortSwFAlarmMaskGlobalIx }
   ::= {er1646v2EthPortSwFAlarmMaskTable 1}

Er1646v2EthPortSwFAlarmMaskEntry ::=
   SEQUENCE
      {
      er1646v2EthPortSwFAlarmMaskGlobalIx
         GlobalIndex,
      er1646v2EthPortSwFAlarmMaskValue
         Integer32
      }

er1646v2EthPortSwFAlarmMaskGlobalIx OBJECT-TYPE
   SYNTAX      GlobalIndex
   MAX-ACCESS  not-accessible
   STATUS      current
   DESCRIPTION
      "The value of the tlsCntTreeGlobalIndex of the MANAGED OBJECT."
   ::= {er1646v2EthPortSwFAlarmMaskEntry 10}

er1646v2EthPortSwFAlarmMaskValue OBJECT-TYPE
   SYNTAX      Integer32
   MAX-ACCESS  read-write
   STATUS      current
   DESCRIPTION
      "Path: swPort.editConf.alarmMask

       Bit meanings:
               bit 0 = linkDown,
               bit 9 = pppoEDown"
   ::= {er1646v2EthPortSwFAlarmMaskEntry 2147483648}


er1646v2EthPortSwFAlarmLev OBJECT IDENTIFIER ::= {er1646v2EthPortSwF 170}

er1646v2EthPortSwFAlarmLevSSCTable OBJECT-TYPE
   SYNTAX      SEQUENCE OF Er1646v2EthPortSwFAlarmLevEntry
   MAX-ACCESS  not-accessible
   STATUS      current
   DESCRIPTION
      "IfAlarmLevels"
   ::= {er1646v2EthPortSwFAlarmLev 1}

er1646v2EthPortSwFAlarmLevEntry OBJECT-TYPE
   SYNTAX      Er1646v2EthPortSwFAlarmLevEntry
   MAX-ACCESS  not-accessible
   STATUS      current
   DESCRIPTION
      ""
   INDEX      { er1646v2EthPortSwFAlarmLevGlobalIx }
   ::= {er1646v2EthPortSwFAlarmLevSSCTable 1}

Er1646v2EthPortSwFAlarmLevEntry ::=
   SEQUENCE
      {
      er1646v2EthPortSwFAlarmLevGlobalIx
         GlobalIndex,
      er1646v2EthPortSwFAlarmLevLinkDown
         Integer32,
      er1646v2EthPortSwFAlarmLevPppoEDown
         Integer32
      }

er1646v2EthPortSwFAlarmLevGlobalIx OBJECT-TYPE
   SYNTAX      GlobalIndex
   MAX-ACCESS  not-accessible
   STATUS      current
   DESCRIPTION
      "The value of the tlsCntTreeGlobalIndex of the MANAGED OBJECT."
   ::= {er1646v2EthPortSwFAlarmLevEntry 10}

er1646v2EthPortSwFAlarmLevLinkDown OBJECT-TYPE
   SYNTAX      Integer32
   MAX-ACCESS  read-write
   STATUS      current
   DESCRIPTION
      "Path: swPort.editConf.alarmLevel.linkDown"
   ::= {er1646v2EthPortSwFAlarmLevEntry 16777216}

er1646v2EthPortSwFAlarmLevPppoEDown OBJECT-TYPE
   SYNTAX      Integer32
   MAX-ACCESS  read-write
   STATUS      current
   DESCRIPTION
      "Path: swPort.editConf.alarmLevel.pppoEDown"
   ::= {er1646v2EthPortSwFAlarmLevEntry 167772160}


er1646v2EthPortSwFPriorityPolicy OBJECT IDENTIFIER ::= {er1646v2EthPortSwF 39}

er1646v2EthPortSwFPriorityPolicyTable OBJECT-TYPE
   SYNTAX      SEQUENCE OF Er1646v2EthPortSwFPriorityPolicyEntry
   MAX-ACCESS  not-accessible
   STATUS      current
   DESCRIPTION
      "Preferred Policy"
   ::= {er1646v2EthPortSwFPriorityPolicy 1}

er1646v2EthPortSwFPriorityPolicyEntry OBJECT-TYPE
   SYNTAX      Er1646v2EthPortSwFPriorityPolicyEntry
   MAX-ACCESS  not-accessible
   STATUS      current
   DESCRIPTION
      ""
   INDEX      { er1646v2EthPortSwFPriorityPolicyGlobalIx }
   ::= {er1646v2EthPortSwFPriorityPolicyTable 1}

Er1646v2EthPortSwFPriorityPolicyEntry ::=
   SEQUENCE
      {
      er1646v2EthPortSwFPriorityPolicyGlobalIx
         GlobalIndex,
      er1646v2EthPortSwFPriorityPolicyValue
         DisplayString
      }

er1646v2EthPortSwFPriorityPolicyGlobalIx OBJECT-TYPE
   SYNTAX      GlobalIndex
   MAX-ACCESS  not-accessible
   STATUS      current
   DESCRIPTION
      "The value of the tlsCntTreeGlobalIndex of the MANAGED OBJECT."
   ::= {er1646v2EthPortSwFPriorityPolicyEntry 10}

er1646v2EthPortSwFPriorityPolicyValue OBJECT-TYPE
   SYNTAX      DisplayString
   MAX-ACCESS  read-write
   STATUS      current
   DESCRIPTION
      "Path: swPort.editConf.priorityPolicy"
   ::= {er1646v2EthPortSwFPriorityPolicyEntry 2147483648}


er1646v2EthPortSwFLst OBJECT IDENTIFIER ::= {er1646v2EthPortSwF 12}

er1646v2EthPortSwFLstSSCTable OBJECT-TYPE
   SYNTAX      SEQUENCE OF Er1646v2EthPortSwFLstEntry
   MAX-ACCESS  not-accessible
   STATUS      current
   DESCRIPTION
      ""
   ::= {er1646v2EthPortSwFLst 1}

er1646v2EthPortSwFLstEntry OBJECT-TYPE
   SYNTAX      Er1646v2EthPortSwFLstEntry
   MAX-ACCESS  not-accessible
   STATUS      current
   DESCRIPTION
      ""
   INDEX      { er1646v2EthPortSwFLstGlobalIx }
   ::= {er1646v2EthPortSwFLstSSCTable 1}

Er1646v2EthPortSwFLstEntry ::=
   SEQUENCE
      {
      er1646v2EthPortSwFLstGlobalIx
         GlobalIndex,
      er1646v2EthPortSwFLstTrackedInterface
         DisplayString
      }

er1646v2EthPortSwFLstGlobalIx OBJECT-TYPE
   SYNTAX      GlobalIndex
   MAX-ACCESS  not-accessible
   STATUS      current
   DESCRIPTION
      "The value of the tlsCntTreeGlobalIndex of the MANAGED OBJECT."
   ::= {er1646v2EthPortSwFLstEntry 10}

er1646v2EthPortSwFLstTrackedInterface OBJECT-TYPE
   SYNTAX      DisplayString
   MAX-ACCESS  read-write
   STATUS      current
   DESCRIPTION
      "Path: swPort.editConf.linkStateTracking.trackedInterface"
   ::= {er1646v2EthPortSwFLstEntry 16777216}



sr1646v2EthPortSwF OBJECT IDENTIFIER ::= {r1646v2EthPortSwF 14}


sr1646v2EthPortSwFDescr OBJECT IDENTIFIER ::= {sr1646v2EthPortSwF 101}

sr1646v2EthPortSwFDescrTable OBJECT-TYPE
   SYNTAX      SEQUENCE OF Sr1646v2EthPortSwFDescrEntry
   MAX-ACCESS  not-accessible
   STATUS      current
   DESCRIPTION
      "ifDescr"
   ::= {sr1646v2EthPortSwFDescr 1}

sr1646v2EthPortSwFDescrEntry OBJECT-TYPE
   SYNTAX      Sr1646v2EthPortSwFDescrEntry
   MAX-ACCESS  not-accessible
   STATUS      current
   DESCRIPTION
      ""
   INDEX      { sr1646v2EthPortSwFDescrGlobalIx }
   ::= {sr1646v2EthPortSwFDescrTable 1}

Sr1646v2EthPortSwFDescrEntry ::=
   SEQUENCE
      {
      sr1646v2EthPortSwFDescrGlobalIx
         GlobalIndex,
      sr1646v2EthPortSwFDescrValue
         DisplayString
      }

sr1646v2EthPortSwFDescrGlobalIx OBJECT-TYPE
   SYNTAX      GlobalIndex
   MAX-ACCESS  not-accessible
   STATUS      current
   DESCRIPTION
      "The value of the tlsCntTreeGlobalIndex of the MANAGED OBJECT."
   ::= {sr1646v2EthPortSwFDescrEntry 10}

sr1646v2EthPortSwFDescrValue OBJECT-TYPE
   SYNTAX      DisplayString
   MAX-ACCESS  read-only
   STATUS      current
   DESCRIPTION
      "Path: swPort.status.ifDescr"
   ::= {sr1646v2EthPortSwFDescrEntry 2147483648}


sr1646v2EthPortSwFType OBJECT IDENTIFIER ::= {sr1646v2EthPortSwF 102}

sr1646v2EthPortSwFTypeTable OBJECT-TYPE
   SYNTAX      SEQUENCE OF Sr1646v2EthPortSwFTypeEntry
   MAX-ACCESS  not-accessible
   STATUS      current
   DESCRIPTION
      "ifType"
   ::= {sr1646v2EthPortSwFType 1}

sr1646v2EthPortSwFTypeEntry OBJECT-TYPE
   SYNTAX      Sr1646v2EthPortSwFTypeEntry
   MAX-ACCESS  not-accessible
   STATUS      current
   DESCRIPTION
      ""
   INDEX      { sr1646v2EthPortSwFTypeGlobalIx }
   ::= {sr1646v2EthPortSwFTypeTable 1}

Sr1646v2EthPortSwFTypeEntry ::=
   SEQUENCE
      {
      sr1646v2EthPortSwFTypeGlobalIx
         GlobalIndex,
      sr1646v2EthPortSwFTypeValue
         INTEGER
      }

sr1646v2EthPortSwFTypeGlobalIx OBJECT-TYPE
   SYNTAX      GlobalIndex
   MAX-ACCESS  not-accessible
   STATUS      current
   DESCRIPTION
      "The value of the tlsCntTreeGlobalIndex of the MANAGED OBJECT."
   ::= {sr1646v2EthPortSwFTypeEntry 10}

sr1646v2EthPortSwFTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: swPort.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2EthPortSwFTypeEntry 2147483648}


sr1646v2EthPortSwFMtu OBJECT IDENTIFIER ::= {sr1646v2EthPortSwF 103}

sr1646v2EthPortSwFMtuTable OBJECT-TYPE
   SYNTAX      SEQUENCE OF Sr1646v2EthPortSwFMtuEntry
   MAX-ACCESS  not-accessible
   STATUS      current
   DESCRIPTION
      "ifMtu"
   ::= {sr1646v2EthPortSwFMtu 1}

sr1646v2EthPortSwFMtuEntry OBJECT-TYPE
   SYNTAX      Sr1646v2EthPortSwFMtuEntry
   MAX-ACCESS  not-accessible
   STATUS      current
   DESCRIPTION
      ""
   INDEX      { sr1646v2EthPortSwFMtuGlobalIx }
   ::= {sr1646v2EthPortSwFMtuTable 1}

Sr1646v2EthPortSwFMtuEntry ::=
   SEQUENCE
      {
      sr1646v2EthPortSwFMtuGlobalIx
         GlobalIndex,
      sr1646v2EthPortSwFMtuValue
         Integer32
      }

sr1646v2EthPortSwFMtuGlobalIx OBJECT-TYPE
   SYNTAX      GlobalIndex
   MAX-ACCESS  not-accessible
   STATUS      current
   DESCRIPTION
      "The value of the tlsCntTreeGlobalIndex of the MANAGED OBJECT."
   ::= {sr1646v2EthPortSwFMtuEntry 10}

sr1646v2EthPortSwFMtuValue OBJECT-TYPE
   SYNTAX      Integer32
   MAX-ACCESS  read-only
   STATUS      current
   DESCRIPTION
      "Path: swPort.status.ifMtu"
   ::= {sr1646v2EthPortSwFMtuEntry 2147483648}


sr1646v2EthPortSwFOperStatus OBJECT IDENTIFIER ::= {sr1646v2EthPortSwF 107}

sr1646v2EthPortSwFOperStatusTable OBJECT-TYPE
   SYNTAX      SEQUENCE OF Sr1646v2EthPortSwFOperStatusEntry
   MAX-ACCESS  not-accessible
   STATUS      current
   DESCRIPTION
      "ifOperStatus"
   ::= {sr1646v2EthPortSwFOperStatus 1}

sr1646v2EthPortSwFOperStatusEntry OBJECT-TYPE
   SYNTAX      Sr1646v2EthPortSwFOperStatusEntry
   MAX-ACCESS  not-accessible
   STATUS      current
   DESCRIPTION
      ""
   INDEX      { sr1646v2EthPortSwFOperStatusGlobalIx }
   ::= {sr1646v2EthPortSwFOperStatusTable 1}

Sr1646v2EthPortSwFOperStatusEntry ::=
   SEQUENCE
      {
      sr1646v2EthPortSwFOperStatusGlobalIx
         GlobalIndex,
      sr1646v2EthPortSwFOperStatusValue
         INTEGER
      }

sr1646v2EthPortSwFOperStatusGlobalIx OBJECT-TYPE
   SYNTAX      GlobalIndex
   MAX-ACCESS  not-accessible
   STATUS      current
   DESCRIPTION
      "The value of the tlsCntTreeGlobalIndex of the MANAGED OBJECT."
   ::= {sr1646v2EthPortSwFOperStatusEntry 10}

sr1646v2EthPortSwFOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ifOperStatus

       Possibilities:
               up   (1)
               down   (2)
               testing   (3)
               unknown   (4)
               dormant   (5)
               notPresent   (6)
               lowerLayerDown   (7)"
   ::= {sr1646v2EthPortSwFOperStatusEntry 2147483648}


sr1646v2EthPortSwFLastChange OBJECT IDENTIFIER ::= {sr1646v2EthPortSwF 108}

sr1646v2EthPortSwFLastChangeTable OBJECT-TYPE
   SYNTAX      SEQUENCE OF Sr1646v2EthPortSwFLastChangeEntry
   MAX-ACCESS  not-accessible
   STATUS      current
   DESCRIPTION
      "ifLastChange"
   ::= {sr1646v2EthPortSwFLastChange 1}

sr1646v2EthPortSwFLastChangeEntry OBJECT-TYPE
   SYNTAX      Sr1646v2EthPortSwFLastChangeEntry
   MAX-ACCESS  not-accessible
   STATUS      current
   DESCRIPTION
      ""
   INDEX      { sr1646v2EthPortSwFLastChangeGlobalIx }
   ::= {sr1646v2EthPortSwFLastChangeTable 1}

Sr1646v2EthPortSwFLastChangeEntry ::=
   SEQUENCE
      {
      sr1646v2EthPortSwFLastChangeGlobalIx
         GlobalIndex,
      sr1646v2EthPortSwFLastChangeValue
         TimeTicks
      }

sr1646v2EthPortSwFLastChangeGlobalIx OBJECT-TYPE
   SYNTAX      GlobalIndex
   MAX-ACCESS  not-accessible
   STATUS      current
   DESCRIPTION
      "The value of the tlsCntTreeGlobalIndex of the MANAGED OBJECT."
   ::= {sr1646v2EthPortSwFLastChangeEntry 10}

sr1646v2EthPortSwFLastChangeValue OBJECT-TYPE
   SYNTAX      TimeTicks
   MAX-ACCESS  read-only
   STATUS      current
   DESCRIPTION
      "Path: swPort.status.ifLastChange

       Time in centi-second."
   ::= {sr1646v2EthPortSwFLastChangeEntry 2147483648}


sr1646v2EthPortSwFLastChangeD OBJECT IDENTIFIER ::= {sr1646v2EthPortSwF 183}

sr1646v2EthPortSwFLastChangeDTable OBJECT-TYPE
   SYNTAX      SEQUENCE OF Sr1646v2EthPortSwFLastChangeDEntry
   MAX-ACCESS  not-accessible
   STATUS      current
   DESCRIPTION
      "ifLastChangeDate"
   ::= {sr1646v2EthPortSwFLastChangeD 1}

sr1646v2EthPortSwFLastChangeDEntry OBJECT-TYPE
   SYNTAX      Sr1646v2EthPortSwFLastChangeDEntry
   MAX-ACCESS  not-accessible
   STATUS      current
   DESCRIPTION
      ""
   INDEX      { sr1646v2EthPortSwFLastChangeDGlobalIx }
   ::= {sr1646v2EthPortSwFLastChangeDTable 1}

Sr1646v2EthPortSwFLastChangeDEntry ::=
   SEQUENCE
      {
      sr1646v2EthPortSwFLastChangeDGlobalIx
         GlobalIndex,
      sr1646v2EthPortSwFLastChangeDValue
         DisplayString
      }

sr1646v2EthPortSwFLastChangeDGlobalIx OBJECT-TYPE
   SYNTAX      GlobalIndex
   MAX-ACCESS  not-accessible
   STATUS      current
   DESCRIPTION
      "The value of the tlsCntTreeGlobalIndex of the MANAGED OBJECT."
   ::= {sr1646v2EthPortSwFLastChangeDEntry 10}

sr1646v2EthPortSwFLastChangeDValue OBJECT-TYPE
   SYNTAX      DisplayString
   MAX-ACCESS  read-only
   STATUS      current
   DESCRIPTION
      "Path: swPort.status.ifLastChangeDate"
   ::= {sr1646v2EthPortSwFLastChangeDEntry 2147483648}


sr1646v2EthPortSwFSpeed OBJECT IDENTIFIER ::= {sr1646v2EthPortSwF 104}

sr1646v2EthPortSwFSpeedTable OBJECT-TYPE
   SYNTAX      SEQUENCE OF Sr1646v2EthPortSwFSpeedEntry
   MAX-ACCESS  not-accessible
   STATUS      current
   DESCRIPTION
      "ifSpeed"
   ::= {sr1646v2EthPortSwFSpeed 1}

sr1646v2EthPortSwFSpeedEntry OBJECT-TYPE
   SYNTAX      Sr1646v2EthPortSwFSpeedEntry
   MAX-ACCESS  not-accessible
   STATUS      current
   DESCRIPTION
      ""
   INDEX      { sr1646v2EthPortSwFSpeedGlobalIx }
   ::= {sr1646v2EthPortSwFSpeedTable 1}

Sr1646v2EthPortSwFSpeedEntry ::=
   SEQUENCE
      {
      sr1646v2EthPortSwFSpeedGlobalIx
         GlobalIndex,
      sr1646v2EthPortSwFSpeedValue
         Gauge32
      }

sr1646v2EthPortSwFSpeedGlobalIx OBJECT-TYPE
   SYNTAX      GlobalIndex
   MAX-ACCESS  not-accessible
   STATUS      current
   DESCRIPTION
      "The value of the tlsCntTreeGlobalIndex of the MANAGED OBJECT."
   ::= {sr1646v2EthPortSwFSpeedEntry 10}

sr1646v2EthPortSwFSpeedValue OBJECT-TYPE
   SYNTAX      Gauge32
   MAX-ACCESS  read-only
   STATUS      current
   DESCRIPTION
      "Path: swPort.status.ifSpeed

       32 bit unsigned gauge value."
   ::= {sr1646v2EthPortSwFSpeedEntry 2147483648}


sr1646v2EthPortSwFIp OBJECT IDENTIFIER ::= {sr1646v2EthPortSwF 16}

sr1646v2EthPortSwFIpSSCTable OBJECT-TYPE
   SYNTAX      SEQUENCE OF Sr1646v2EthPortSwFIpEntry
   MAX-ACCESS  not-accessible
   STATUS      current
   DESCRIPTION
      "ip interface status parameters"
   ::= {sr1646v2EthPortSwFIp 1}

sr1646v2EthPortSwFIpEntry OBJECT-TYPE
   SYNTAX      Sr1646v2EthPortSwFIpEntry
   MAX-ACCESS  not-accessible
   STATUS      current
   DESCRIPTION
      ""
   INDEX      { sr1646v2EthPortSwFIpGlobalIx }
   ::= {sr1646v2EthPortSwFIpSSCTable 1}

Sr1646v2EthPortSwFIpEntry ::=
   SEQUENCE
      {
      sr1646v2EthPortSwFIpGlobalIx
         GlobalIndex,
      sr1646v2EthPortSwFIpStatus
         INTEGER,
      sr1646v2EthPortSwFIpAddress
         IpAddress,
      sr1646v2EthPortSwFIpNetMask
         IpAddress,
      sr1646v2EthPortSwFIpDhcpStatus
         INTEGER,
      sr1646v2EthPortSwFIpDhcpLeaseTime
         TimeTicks
      }

sr1646v2EthPortSwFIpGlobalIx OBJECT-TYPE
   SYNTAX      GlobalIndex
   MAX-ACCESS  not-accessible
   STATUS      current
   DESCRIPTION
      "The value of the tlsCntTreeGlobalIndex of the MANAGED OBJECT."
   ::= {sr1646v2EthPortSwFIpEntry 10}

sr1646v2EthPortSwFIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ip.status

       Possibilities:
               up   (1)
               down   (2)
               testing   (3)
               unknown   (4)
               dormant   (5)
               notPresent   (6)
               lowerLayerDown   (7)"
   ::= {sr1646v2EthPortSwFIpEntry 1795162112}

sr1646v2EthPortSwFIpAddress OBJECT-TYPE
   SYNTAX      IpAddress
   MAX-ACCESS  read-only
   STATUS      current
   DESCRIPTION
      "Path: swPort.status.ip.address"
   ::= {sr1646v2EthPortSwFIpEntry 2030043136}

sr1646v2EthPortSwFIpNetMask OBJECT-TYPE
   SYNTAX      IpAddress
   MAX-ACCESS  read-only
   STATUS      current
   DESCRIPTION
      "Path: swPort.status.ip.netMask"
   ::= {sr1646v2EthPortSwFIpEntry 2063597568}

sr1646v2EthPortSwFIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.ip.dhcp.status

       Possibilities:
               none   (0)
               selecting   (1)
               requesting   (2)
               rebinding   (3)
               bound   (4)
               renewing   (5)
               rebooting   (6)
               initreboot   (7)"
   ::= {sr1646v2EthPortSwFIpEntry 402718720}

sr1646v2EthPortSwFIpDhcpLeaseTime OBJECT-TYPE
   SYNTAX      TimeTicks
   MAX-ACCESS  read-only
   STATUS      current
   DESCRIPTION
      "Path: swPort.status.ip.dhcp.leaseTime

       Time in centi-second."
   ::= {sr1646v2EthPortSwFIpEntry 402784256}

sr1646v2EthPortSwFIpSecondaryIp OBJECT-TYPE
   SYNTAX      SEQUENCE OF Sr1646v2EthPortSwFIpSecondaryIpEntry
   MAX-ACCESS  not-accessible
   STATUS      current
   DESCRIPTION
      ""
   ::= {sr1646v2EthPortSwFIp 385875968}

sr1646v2EthPortSwFIpSecondaryIpEntry OBJECT-TYPE
   SYNTAX      Sr1646v2EthPortSwFIpSecondaryIpEntry
   MAX-ACCESS  not-accessible
   STATUS      current
   DESCRIPTION
      ""
   INDEX      { sr1646v2EthPortSwFIpSecondaryIpGlobalIx,
                sr1646v2EthPortSwFIpSecondaryIpTableIx }
   ::= {sr1646v2EthPortSwFIpSecondaryIp 1}

Sr1646v2EthPortSwFIpSecondaryIpEntry ::=
   SEQUENCE
      {
      sr1646v2EthPortSwFIpSecondaryIpGlobalIx
         GlobalIndex,
      sr1646v2EthPortSwFIpSecondaryIpTableIx
         TableIndex,
      sr1646v2EthPortSwFIpSecondaryIpAddress
         IpAddress,
      sr1646v2EthPortSwFIpSecondaryIpNetMask
         IpAddress
      }

sr1646v2EthPortSwFIpSecondaryIpGlobalIx OBJECT-TYPE
   SYNTAX      GlobalIndex
   MAX-ACCESS  not-accessible
   STATUS      current
   DESCRIPTION
      "The value of the tlsCntTreeGlobalIndex of the MANAGED OBJECT."
   ::= {sr1646v2EthPortSwFIpSecondaryIpEntry 10}

sr1646v2EthPortSwFIpSecondaryIpTableIx OBJECT-TYPE
   SYNTAX      TableIndex
   MAX-ACCESS  not-accessible
   STATUS      current
   DESCRIPTION
      ""
   ::= {sr1646v2EthPortSwFIpSecondaryIpEntry 11}

sr1646v2EthPortSwFIpSecondaryIpAddress OBJECT-TYPE
   SYNTAX      IpAddress
   MAX-ACCESS  read-only
   STATUS      current
   DESCRIPTION
      "Path: swPort.status.ip.secondaryIp.address"
   ::= {sr1646v2EthPortSwFIpSecondaryIpEntry 2030043136}

sr1646v2EthPortSwFIpSecondaryIpNetMask OBJECT-TYPE
   SYNTAX      IpAddress
   MAX-ACCESS  read-only
   STATUS      current
   DESCRIPTION
      "Path: swPort.status.ip.secondaryIp.netMask"
   ::= {sr1646v2EthPortSwFIpSecondaryIpEntry 2063597568}


sr1646v2EthPortSwFArpCache OBJECT IDENTIFIER ::= {sr1646v2EthPortSwF 11}

sr1646v2EthPortSwFArpCacheSSCTable OBJECT-TYPE
   SYNTAX      SEQUENCE OF Sr1646v2EthPortSwFArpCacheEntry
   MAX-ACCESS  not-accessible
   STATUS      current
   DESCRIPTION
      "arp cache of ethernet interface"
   ::= {sr1646v2EthPortSwFArpCache 1}

sr1646v2EthPortSwFArpCacheEntry OBJECT-TYPE
   SYNTAX      Sr1646v2EthPortSwFArpCacheEntry
   MAX-ACCESS  not-accessible
   STATUS      current
   DESCRIPTION
      ""
   INDEX      { sr1646v2EthPortSwFArpCacheGlobalIx,
                sr1646v2EthPortSwFArpCacheTableIx }
   ::= {sr1646v2EthPortSwFArpCacheSSCTable 1}

Sr1646v2EthPortSwFArpCacheEntry ::=
   SEQUENCE
      {
      sr1646v2EthPortSwFArpCacheGlobalIx
         GlobalIndex,
      sr1646v2EthPortSwFArpCacheTableIx
         TableIndex,
      sr1646v2EthPortSwFArpCacheMacAddress
         OCTET STRING,
      sr1646v2EthPortSwFArpCacheIpAddress
         IpAddress,
      sr1646v2EthPortSwFArpCacheType
         INTEGER,
      sr1646v2EthPortSwFArpCacheTimeOut
         TimeTicks
      }

sr1646v2EthPortSwFArpCacheGlobalIx OBJECT-TYPE
   SYNTAX      GlobalIndex
   MAX-ACCESS  not-accessible
   STATUS      current
   DESCRIPTION
      "The value of the tlsCntTreeGlobalIndex of the MANAGED OBJECT."
   ::= {sr1646v2EthPortSwFArpCacheEntry 10}

sr1646v2EthPortSwFArpCacheTableIx OBJECT-TYPE
   SYNTAX      TableIndex
   MAX-ACCESS  not-accessible
   STATUS      current
   DESCRIPTION
      ""
   ::= {sr1646v2EthPortSwFArpCacheEntry 11}

sr1646v2EthPortSwFArpCacheMacAddress OBJECT-TYPE
   SYNTAX      OCTET STRING
   MAX-ACCESS  read-only
   STATUS      current
   DESCRIPTION
      "Path: swPort.status.arpCache.macAddress

       MAC address."
   ::= {sr1646v2EthPortSwFArpCacheEntry 16777216}

sr1646v2EthPortSwFArpCacheIpAddress OBJECT-TYPE
   SYNTAX      IpAddress
   MAX-ACCESS  read-only
   STATUS      current
   DESCRIPTION
      "Path: swPort.status.arpCache.ipAddress"
   ::= {sr1646v2EthPortSwFArpCacheEntry 33554432}

sr1646v2EthPortSwFArpCacheType OBJECT-TYPE
   SYNTAX      INTEGER
               {
               static (0),
               dynamic (1)
               }
   MAX-ACCESS  read-only
   STATUS      current
   DESCRIPTION
      "Path: swPort.status.arpCache.type

       Possibilities:
               static   (0)
               dynamic   (1)"
   ::= {sr1646v2EthPortSwFArpCacheEntry 50331648}

sr1646v2EthPortSwFArpCacheTimeOut OBJECT-TYPE
   SYNTAX      TimeTicks
   MAX-ACCESS  read-only
   STATUS      current
   DESCRIPTION
      "Path: swPort.status.arpCache.timeOut

       Time in centi-second."
   ::= {sr1646v2EthPortSwFArpCacheEntry 67108864}


sr1646v2EthPortSwFBrS OBJECT IDENTIFIER ::= {sr1646v2EthPortSwF 28}

sr1646v2EthPortSwFBrSSSCTable OBJECT-TYPE
   SYNTAX      SEQUENCE OF Sr1646v2EthPortSwFBrSEntry
   MAX-ACCESS  not-accessible
   STATUS      current
   DESCRIPTION
      "spanning tree status ethernet interface"
   ::= {sr1646v2EthPortSwFBrS 1}

sr1646v2EthPortSwFBrSEntry OBJECT-TYPE
   SYNTAX      Sr1646v2EthPortSwFBrSEntry
   MAX-ACCESS  not-accessible
   STATUS      current
   DESCRIPTION
      ""
   INDEX      { sr1646v2EthPortSwFBrSGlobalIx }
   ::= {sr1646v2EthPortSwFBrSSSCTable 1}

Sr1646v2EthPortSwFBrSEntry ::=
   SEQUENCE
      {
      sr1646v2EthPortSwFBrSGlobalIx
         GlobalIndex,
      sr1646v2EthPortSwFBrSStatus
         INTEGER,
      sr1646v2EthPortSwFBrSStPortRole
         INTEGER,
      sr1646v2EthPortSwFBrSStPortId
         Integer32,
      sr1646v2EthPortSwFBrSStPpCostExtPathCost
         Integer32,
      sr1646v2EthPortSwFBrSStPpCostIntPathCost
         Integer32,
      sr1646v2EthPortSwFBrSStExtRpCost
         Integer32,
      sr1646v2EthPortSwFBrSStIntRpCost
         Integer32,
      sr1646v2EthPortSwFBrSStDesBrIdPriority
         Integer32,
      sr1646v2EthPortSwFBrSStDesBrIdMacAddress
         OCTET STRING,
      sr1646v2EthPortSwFBrSStDesPrtId
         Integer32,
      sr1646v2EthPortSwFBrSStDesInt
         INTEGER,
      sr1646v2EthPortSwFBrSStEdgeDetection
         INTEGER
      }

sr1646v2EthPortSwFBrSGlobalIx OBJECT-TYPE
   SYNTAX      GlobalIndex
   MAX-ACCESS  not-accessible
   STATUS      current
   DESCRIPTION
      "The value of the tlsCntTreeGlobalIndex of the MANAGED OBJECT."
   ::= {sr1646v2EthPortSwFBrSEntry 10}

sr1646v2EthPortSwFBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.bridging.status

       Possibilities:
               disabled   (0)
               discarding   (1)
               learning   (2)
               forwarding   (3)
               backupBlockedIntfDown   (256)
               backupBlockedIntfUp   (259)
               shutdown   (255)"
   ::= {sr1646v2EthPortSwFBrSEntry 16777216}

sr1646v2EthPortSwFBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.bridging.spanningTree.portRole

       Possibilities:
               none   (0)
               root   (1)
               designated   (2)
               alternate   (3)
               backup   (4)
               disabled   (5)
               master   (6)"
   ::= {sr1646v2EthPortSwFBrSEntry 33619968}

sr1646v2EthPortSwFBrSStPortId OBJECT-TYPE
   SYNTAX      Integer32
   MAX-ACCESS  read-only
   STATUS      current
   DESCRIPTION
      "Path: swPort.status.bridging.spanningTree.portId"
   ::= {sr1646v2EthPortSwFBrSEntry 33685504}

sr1646v2EthPortSwFBrSStPpCostExtPathCost OBJECT-TYPE
   SYNTAX      Integer32
   MAX-ACCESS  read-only
   STATUS      current
   DESCRIPTION
      "Path: swPort.status.bridging.spanningTree.portPathCosts.extPathCost"
   ::= {sr1646v2EthPortSwFBrSEntry 33751296}

sr1646v2EthPortSwFBrSStPpCostIntPathCost OBJECT-TYPE
   SYNTAX      Integer32
   MAX-ACCESS  read-only
   STATUS      current
   DESCRIPTION
      "Path: swPort.status.bridging.spanningTree.portPathCosts.intPathCost"
   ::= {sr1646v2EthPortSwFBrSEntry 33751552}

sr1646v2EthPortSwFBrSStExtRpCost OBJECT-TYPE
   SYNTAX      Integer32
   MAX-ACCESS  read-only
   STATUS      current
   DESCRIPTION
      "Path: swPort.status.bridging.spanningTree.extRootPathCost"
   ::= {sr1646v2EthPortSwFBrSEntry 33816576}

sr1646v2EthPortSwFBrSStIntRpCost OBJECT-TYPE
   SYNTAX      Integer32
   MAX-ACCESS  read-only
   STATUS      current
   DESCRIPTION
      "Path: swPort.status.bridging.spanningTree.intRootPathCost"
   ::= {sr1646v2EthPortSwFBrSEntry 33882112}

sr1646v2EthPortSwFBrSStDesBrIdPriority OBJECT-TYPE
   SYNTAX      Integer32
   MAX-ACCESS  read-only
   STATUS      current
   DESCRIPTION
      "Path: swPort.status.bridging.spanningTree.designatedBridgeId.priority"
   ::= {sr1646v2EthPortSwFBrSEntry 33947904}

sr1646v2EthPortSwFBrSStDesBrIdMacAddress OBJECT-TYPE
   SYNTAX      OCTET STRING
   MAX-ACCESS  read-only
   STATUS      current
   DESCRIPTION
      "Path: swPort.status.bridging.spanningTree.designatedBridgeId.macAddress

       MAC address."
   ::= {sr1646v2EthPortSwFBrSEntry 33948160}

sr1646v2EthPortSwFBrSStDesPrtId OBJECT-TYPE
   SYNTAX      Integer32
   MAX-ACCESS  read-only
   STATUS      current
   DESCRIPTION
      "Path: swPort.status.bridging.spanningTree.designatedPortId"
   ::= {sr1646v2EthPortSwFBrSEntry 34013184}

sr1646v2EthPortSwFBrSStDesInt OBJECT-TYPE
   SYNTAX      INTEGER
               {
               no (0),
               yes (1)
               }
   MAX-ACCESS  read-only
   STATUS      current
   DESCRIPTION
      "Path: swPort.status.bridging.spanningTree.designatedOrInternal

       Possibilities:
               no   (0)
               yes   (1)"
   ::= {sr1646v2EthPortSwFBrSEntry 34078720}

sr1646v2EthPortSwFBrSStEdgeDetection OBJECT-TYPE
   SYNTAX      INTEGER
               {
               none (0),
               edge (1),
               notEdge (2)
               }
   MAX-ACCESS  read-only
   STATUS      current
   DESCRIPTION
      "Path: swPort.status.bridging.spanningTree.edgeDetection

       Possibilities:
               none   (0)
               edge   (1)
               notEdge   (2)"
   ::= {sr1646v2EthPortSwFBrSEntry 34144256}


sr1646v2EthPortSwFMacAddress OBJECT IDENTIFIER ::= {sr1646v2EthPortSwF 105}

sr1646v2EthPortSwFMacAddressTable OBJECT-TYPE
   SYNTAX      SEQUENCE OF Sr1646v2EthPortSwFMacAddressEntry
   MAX-ACCESS  not-accessible
   STATUS      current
   DESCRIPTION
      "ifPhysAddress"
   ::= {sr1646v2EthPortSwFMacAddress 1}

sr1646v2EthPortSwFMacAddressEntry OBJECT-TYPE
   SYNTAX      Sr1646v2EthPortSwFMacAddressEntry
   MAX-ACCESS  not-accessible
   STATUS      current
   DESCRIPTION
      ""
   INDEX      { sr1646v2EthPortSwFMacAddressGlobalIx }
   ::= {sr1646v2EthPortSwFMacAddressTable 1}

Sr1646v2EthPortSwFMacAddressEntry ::=
   SEQUENCE
      {
      sr1646v2EthPortSwFMacAddressGlobalIx
         GlobalIndex,
      sr1646v2EthPortSwFMacAddressValue
         OCTET STRING
      }

sr1646v2EthPortSwFMacAddressGlobalIx OBJECT-TYPE
   SYNTAX      GlobalIndex
   MAX-ACCESS  not-accessible
   STATUS      current
   DESCRIPTION
      "The value of the tlsCntTreeGlobalIndex of the MANAGED OBJECT."
   ::= {sr1646v2EthPortSwFMacAddressEntry 10}

sr1646v2EthPortSwFMacAddressValue OBJECT-TYPE
   SYNTAX      OCTET STRING
   MAX-ACCESS  read-only
   STATUS      current
   DESCRIPTION
      "Path: swPort.status.macAddress

       MAC address."
   ::= {sr1646v2EthPortSwFMacAddressEntry 2147483648}


sr1646v2EthPortSwFIpAdEntBcastAddr OBJECT IDENTIFIER ::= {sr1646v2EthPortSwF 124}

sr1646v2EthPortSwFIpAdEntBcastAddrTable OBJECT-TYPE
   SYNTAX      SEQUENCE OF Sr1646v2EthPortSwFIpAdEntBcastAddrEntry
   MAX-ACCESS  not-accessible
   STATUS      current
   DESCRIPTION
      "ipAdEntBcastAddr"
   ::= {sr1646v2EthPortSwFIpAdEntBcastAddr 1}

sr1646v2EthPortSwFIpAdEntBcastAddrEntry OBJECT-TYPE
   SYNTAX      Sr1646v2EthPortSwFIpAdEntBcastAddrEntry
   MAX-ACCESS  not-accessible
   STATUS      current
   DESCRIPTION
      ""
   INDEX      { sr1646v2EthPortSwFIpAdEntBcastAddrGlobalIx }
   ::= {sr1646v2EthPortSwFIpAdEntBcastAddrTable 1}

Sr1646v2EthPortSwFIpAdEntBcastAddrEntry ::=
   SEQUENCE
      {
      sr1646v2EthPortSwFIpAdEntBcastAddrGlobalIx
         GlobalIndex,
      sr1646v2EthPortSwFIpAdEntBcastAddrValue
         Integer32
      }

sr1646v2EthPortSwFIpAdEntBcastAddrGlobalIx OBJECT-TYPE
   SYNTAX      GlobalIndex
   MAX-ACCESS  not-accessible
   STATUS      current
   DESCRIPTION
      "The value of the tlsCntTreeGlobalIndex of the MANAGED OBJECT."
   ::= {sr1646v2EthPortSwFIpAdEntBcastAddrEntry 10}

sr1646v2EthPortSwFIpAdEntBcastAddrValue OBJECT-TYPE
   SYNTAX      Integer32
   MAX-ACCESS  read-only
   STATUS      current
   DESCRIPTION
      "Path: swPort.status.ipAdEntBcastAddr"
   ::= {sr1646v2EthPortSwFIpAdEntBcastAddrEntry 2147483648}


sr1646v2EthPortSwFIpAdEntReasmMaxSize OBJECT IDENTIFIER ::= {sr1646v2EthPortSwF 125}

sr1646v2EthPortSwFIpAdEntReasmMaxSizeTable OBJECT-TYPE
   SYNTAX      SEQUENCE OF Sr1646v2EthPortSwFIpAdEntReasmMaxSizeEntry
   MAX-ACCESS  not-accessible
   STATUS      current
   DESCRIPTION
      "ipAdEntReasmMaxSize"
   ::= {sr1646v2EthPortSwFIpAdEntReasmMaxSize 1}

sr1646v2EthPortSwFIpAdEntReasmMaxSizeEntry OBJECT-TYPE
   SYNTAX      Sr1646v2EthPortSwFIpAdEntReasmMaxSizeEntry
   MAX-ACCESS  not-accessible
   STATUS      current
   DESCRIPTION
      ""
   INDEX      { sr1646v2EthPortSwFIpAdEntReasmMaxSizeGlobalIx }
   ::= {sr1646v2EthPortSwFIpAdEntReasmMaxSizeTable 1}

Sr1646v2EthPortSwFIpAdEntReasmMaxSizeEntry ::=
   SEQUENCE
      {
      sr1646v2EthPortSwFIpAdEntReasmMaxSizeGlobalIx
         GlobalIndex,
      sr1646v2EthPortSwFIpAdEntReasmMaxSizeValue
         Integer32
      }

sr1646v2EthPortSwFIpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1646v2EthPortSwFIpAdEntReasmMaxSizeEntry 10}

sr1646v2EthPortSwFIpAdEntReasmMaxSizeValue OBJECT-TYPE
   SYNTAX      Integer32
   MAX-ACCESS  read-only
   STATUS      current
   DESCRIPTION
      "Path: swPort.status.ipAdEntReasmMaxSize"
   ::= {sr1646v2EthPortSwFIpAdEntReasmMaxSizeEntry 2147483648}


sr1646v2EthPortSwFOam OBJECT IDENTIFIER ::= {sr1646v2EthPortSwF 901}

sr1646v2EthPortSwFOamSSCTable OBJECT-TYPE
   SYNTAX      SEQUENCE OF Sr1646v2EthPortSwFOamEntry
   MAX-ACCESS  not-accessible
   STATUS      current
   DESCRIPTION
      "OAM discovery state"
   ::= {sr1646v2EthPortSwFOam 1}

sr1646v2EthPortSwFOamEntry OBJECT-TYPE
   SYNTAX      Sr1646v2EthPortSwFOamEntry
   MAX-ACCESS  not-accessible
   STATUS      current
   DESCRIPTION
      ""
   INDEX      { sr1646v2EthPortSwFOamGlobalIx }
   ::= {sr1646v2EthPortSwFOamSSCTable 1}

Sr1646v2EthPortSwFOamEntry ::=
   SEQUENCE
      {
      sr1646v2EthPortSwFOamGlobalIx
         GlobalIndex,
      sr1646v2EthPortSwFOamDiscovery
         INTEGER,
      sr1646v2EthPortSwFOamLoopback
         INTEGER,
      sr1646v2EthPortSwFOamLocalInfoVersion
         Integer32,
      sr1646v2EthPortSwFOamLocalInfoRevision
         Integer32,
      sr1646v2EthPortSwFOamLocalInfoStateMuxAction
         INTEGER,
      sr1646v2EthPortSwFOamLocalInfoStateParserAction
         INTEGER,
      sr1646v2EthPortSwFOamLocalInfoOui
         OCTET STRING,
      sr1646v2EthPortSwFOamLocalInfoVendorInfo
         OCTET STRING,
      sr1646v2EthPortSwFOamLocalInfoVarRetrieval
         INTEGER,
      sr1646v2EthPortSwFOamLocalInfoLinkEvents
         INTEGER,
      sr1646v2EthPortSwFOamLocalInfoLoopback
         INTEGER,
      sr1646v2EthPortSwFOamLocalInfoUnidirectional
         INTEGER,
      sr1646v2EthPortSwFOamLocalInfoMode
         INTEGER,
      sr1646v2EthPortSwFOamLocalInfoMaxPduSize
         Integer32,
      sr1646v2EthPortSwFOamRemoteInfoVersion
         Integer32,
      sr1646v2EthPortSwFOamRemoteInfoRevision
         Integer32,
      sr1646v2EthPortSwFOamRemoteInfoStateMuxAction
         INTEGER,
      sr1646v2EthPortSwFOamRemoteInfoStateParserAction
         INTEGER,
      sr1646v2EthPortSwFOamRemoteInfoOui
         OCTET STRING,
      sr1646v2EthPortSwFOamRemoteInfoVendorInfo
         OCTET STRING,
      sr1646v2EthPortSwFOamRemoteInfoVarRetrieval
         INTEGER,
      sr1646v2EthPortSwFOamRemoteInfoLinkEvents
         INTEGER,
      sr1646v2EthPortSwFOamRemoteInfoLoopback
         INTEGER,
      sr1646v2EthPortSwFOamRemoteInfoUnidirectional
         INTEGER,
      sr1646v2EthPortSwFOamRemoteInfoMode
         INTEGER,
      sr1646v2EthPortSwFOamRemoteInfoMaxPduSize
         Integer32,
      sr1646v2EthPortSwFOamEventsErroredSymbolWindow
         Integer32,
      sr1646v2EthPortSwFOamEventsErroredSymbolThreshold
         OCTET STRING,
      sr1646v2EthPortSwFOamEventsErroredFramePeriodWindow
         INTEGER,
      sr1646v2EthPortSwFOamEventsErroredFramePeriodThreshold
         Integer32,
      sr1646v2EthPortSwFOamEventsErroredFrameWindow
         Integer32,
      sr1646v2EthPortSwFOamEventsErroredFrameThreshold
         Integer32,
      sr1646v2EthPortSwFOamEventsErroredFrameSecondsWindow
         Integer32,
      sr1646v2EthPortSwFOamEventsErroredFrameSecondsThreshold
         Integer32
      }

sr1646v2EthPortSwFOamGlobalIx OBJECT-TYPE
   SYNTAX      GlobalIndex
   MAX-ACCESS  not-accessible
   STATUS      current
   DESCRIPTION
      "The value of the tlsCntTreeGlobalIndex of the MANAGED OBJECT."
   ::= {sr1646v2EthPortSwFOamEntry 10}

sr1646v2EthPortSwFOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: swPort.status.oam.discovery

       Possibilities:
               fault   (0)
               sendLocal   (1)
               passiveWait   (2)
               sendLocalRemote   (3)
               sendLocalRemoteOk   (4)
               sendAny   (5)"
   ::= {sr1646v2EthPortSwFOamEntry 16777216}

sr1646v2EthPortSwFOamLoopback OBJECT-TYPE
   SYNTAX      INTEGER
               {
               idle (0),
               waiting (1),
               localRunning (2),
               remoteRunning (3)
               }
   MAX-ACCESS  read-only
   STATUS      current
   DESCRIPTION
      "Path: swPort.status.oam.loopback

       Possibilities:
               idle   (0)
               waiting   (1)
               localRunning   (2)
               remoteRunning   (3)"
   ::= {sr1646v2EthPortSwFOamEntry 33554432}

sr1646v2EthPortSwFOamLocalInfoVersion OBJECT-TYPE
   SYNTAX      Integer32
   MAX-ACCESS  read-only
   STATUS      current
   DESCRIPTION
      "Path: swPort.status.oam.localInfo.version"
   ::= {sr1646v2EthPortSwFOamEntry 50397184}

sr1646v2EthPortSwFOamLocalInfoRevision OBJECT-TYPE
   SYNTAX      Integer32
   MAX-ACCESS  read-only
   STATUS      current
   DESCRIPTION
      "Path: swPort.status.oam.localInfo.revision"
   ::= {sr1646v2EthPortSwFOamEntry 50462720}

sr1646v2EthPortSwFOamLocalInfoStateMuxAction OBJECT-TYPE
   SYNTAX      INTEGER
               {
               forwarding (0),
               discarding (1)
               }
   MAX-ACCESS  read-only
   STATUS      current
   DESCRIPTION
      "Path: swPort.status.oam.localInfo.state.muxAction

       Possibilities:
               forwarding   (0)
               discarding   (1)"
   ::= {sr1646v2EthPortSwFOamEntry 50528512}

sr1646v2EthPortSwFOamLocalInfoStateParserAction OBJECT-TYPE
   SYNTAX      INTEGER
               {
               forwarding (0),
               loopback (1),
               discarding (2),
               reserved (3)
               }
   MAX-ACCESS  read-only
   STATUS      current
   DESCRIPTION
      "Path: swPort.status.oam.localInfo.state.parserAction

       Possibilities:
               forwarding   (0)
               loopback   (1)
               discarding   (2)
               reserved   (3)"
   ::= {sr1646v2EthPortSwFOamEntry 50528768}

sr1646v2EthPortSwFOamLocalInfoOui OBJECT-TYPE
   SYNTAX      OCTET STRING
   MAX-ACCESS  read-only
   STATUS      current
   DESCRIPTION
      "Path: swPort.status.oam.localInfo.oui"
   ::= {sr1646v2EthPortSwFOamEntry 50593792}

sr1646v2EthPortSwFOamLocalInfoVendorInfo OBJECT-TYPE
   SYNTAX      OCTET STRING
   MAX-ACCESS  read-only
   STATUS      current
   DESCRIPTION
      "Path: swPort.status.oam.localInfo.vendorInfo"
   ::= {sr1646v2EthPortSwFOamEntry 50659328}

sr1646v2EthPortSwFOamLocalInfoVarRetrieval OBJECT-TYPE
   SYNTAX      INTEGER
               {
               notSupported (0),
               supported (1)
               }
   MAX-ACCESS  read-only
   STATUS      current
   DESCRIPTION
      "Path: swPort.status.oam.localInfo.varRetrieval

       Possibilities:
               notSupported   (0)
               supported   (1)"
   ::= {sr1646v2EthPortSwFOamEntry 50724864}

sr1646v2EthPortSwFOamLocalInfoLinkEvents OBJECT-TYPE
   SYNTAX      INTEGER
               {
               ignored (0),
               interpreted (1)
               }
   MAX-ACCESS  read-only
   STATUS      current
   DESCRIPTION
      "Path: swPort.status.oam.localInfo.linkEvents

       Possibilities:
               ignored   (0)
               interpreted   (1)"
   ::= {sr1646v2EthPortSwFOamEntry 50790400}

sr1646v2EthPortSwFOamLocalInfoLoopback OBJECT-TYPE
   SYNTAX      INTEGER
               {
               notSupported (0),
               supported (1)
               }
   MAX-ACCESS  read-only
   STATUS      current
   DESCRIPTION
      "Path: swPort.status.oam.localInfo.loopback

       Possibilities:
               notSupported   (0)
               supported   (1)"
   ::= {sr1646v2EthPortSwFOamEntry 50855936}

sr1646v2EthPortSwFOamLocalInfoUnidirectional OBJECT-TYPE
   SYNTAX      INTEGER
               {
               notSupported (0),
               supported (1)
               }
   MAX-ACCESS  read-only
   STATUS      current
   DESCRIPTION
      "Path: swPort.status.oam.localInfo.unidirectional

       Possibilities:
               notSupported   (0)
               supported   (1)"
   ::= {sr1646v2EthPortSwFOamEntry 50921472}

sr1646v2EthPortSwFOamLocalInfoMode OBJECT-TYPE
   SYNTAX      INTEGER
               {
               passive (0),
               active (1)
               }
   MAX-ACCESS  read-only
   STATUS      current
   DESCRIPTION
      "Path: swPort.status.oam.localInfo.mode

       Possibilities:
               passive   (0)
               active   (1)"
   ::= {sr1646v2EthPortSwFOamEntry 50987008}

sr1646v2EthPortSwFOamLocalInfoMaxPduSize OBJECT-TYPE
   SYNTAX      Integer32
   MAX-ACCESS  read-only
   STATUS      current
   DESCRIPTION
      "Path: swPort.status.oam.localInfo.maxPduSize"
   ::= {sr1646v2EthPortSwFOamEntry 51052544}

sr1646v2EthPortSwFOamRemoteInfoVersion OBJECT-TYPE
   SYNTAX      Integer32
   MAX-ACCESS  read-only
   STATUS      current
   DESCRIPTION
      "Path: swPort.status.oam.remoteInfo.version"
   ::= {sr1646v2EthPortSwFOamEntry 67174400}

sr1646v2EthPortSwFOamRemoteInfoRevision OBJECT-TYPE
   SYNTAX      Integer32
   MAX-ACCESS  read-only
   STATUS      current
   DESCRIPTION
      "Path: swPort.status.oam.remoteInfo.revision"
   ::= {sr1646v2EthPortSwFOamEntry 67239936}

sr1646v2EthPortSwFOamRemoteInfoStateMuxAction OBJECT-TYPE
   SYNTAX      INTEGER
               {
               forwarding (0),
               discarding (1)
               }
   MAX-ACCESS  read-only
   STATUS      current
   DESCRIPTION
      "Path: swPort.status.oam.remoteInfo.state.muxAction

       Possibilities:
               forwarding   (0)
               discarding   (1)"
   ::= {sr1646v2EthPortSwFOamEntry 67305728}

sr1646v2EthPortSwFOamRemoteInfoStateParserAction OBJECT-TYPE
   SYNTAX      INTEGER
               {
               forwarding (0),
               loopback (1),
               discarding (2),
               reserved (3)
               }
   MAX-ACCESS  read-only
   STATUS      current
   DESCRIPTION
      "Path: swPort.status.oam.remoteInfo.state.parserAction

       Possibilities:
               forwarding   (0)
               loopback   (1)
               discarding   (2)
               reserved   (3)"
   ::= {sr1646v2EthPortSwFOamEntry 67305984}

sr1646v2EthPortSwFOamRemoteInfoOui OBJECT-TYPE
   SYNTAX      OCTET STRING
   MAX-ACCESS  read-only
   STATUS      current
   DESCRIPTION
      "Path: swPort.status.oam.remoteInfo.oui"
   ::= {sr1646v2EthPortSwFOamEntry 67371008}

sr1646v2EthPortSwFOamRemoteInfoVendorInfo OBJECT-TYPE
   SYNTAX      OCTET STRING
   MAX-ACCESS  read-only
   STATUS      current
   DESCRIPTION
      "Path: swPort.status.oam.remoteInfo.vendorInfo"
   ::= {sr1646v2EthPortSwFOamEntry 67436544}

sr1646v2EthPortSwFOamRemoteInfoVarRetrieval OBJECT-TYPE
   SYNTAX      INTEGER
               {
               notSupported (0),
               supported (1)
               }
   MAX-ACCESS  read-only
   STATUS      current
   DESCRIPTION
      "Path: swPort.status.oam.remoteInfo.varRetrieval

       Possibilities:
               notSupported   (0)
               supported   (1)"
   ::= {sr1646v2EthPortSwFOamEntry 67502080}

sr1646v2EthPortSwFOamRemoteInfoLinkEvents OBJECT-TYPE
   SYNTAX      INTEGER
               {
               ignored (0),
               interpreted (1)
               }
   MAX-ACCESS  read-only
   STATUS      current
   DESCRIPTION
      "Path: swPort.status.oam.remoteInfo.linkEvents

       Possibilities:
               ignored   (0)
               interpreted   (1)"
   ::= {sr1646v2EthPortSwFOamEntry 67567616}

sr1646v2EthPortSwFOamRemoteInfoLoopback OBJECT-TYPE
   SYNTAX      INTEGER
               {
               notSupported (0),
               supported (1)
               }
   MAX-ACCESS  read-only
   STATUS      current
   DESCRIPTION
      "Path: swPort.status.oam.remoteInfo.loopback

       Possibilities:
               notSupported   (0)
               supported   (1)"
   ::= {sr1646v2EthPortSwFOamEntry 67633152}

sr1646v2EthPortSwFOamRemoteInfoUnidirectional OBJECT-TYPE
   SYNTAX      INTEGER
               {
               notSupported (0),
               supported (1)
               }
   MAX-ACCESS  read-only
   STATUS      current
   DESCRIPTION
      "Path: swPort.status.oam.remoteInfo.unidirectional

       Possibilities:
               notSupported   (0)
               supported   (1)"
   ::= {sr1646v2EthPortSwFOamEntry 67698688}

sr1646v2EthPortSwFOamRemoteInfoMode OBJECT-TYPE
   SYNTAX      INTEGER
               {
               passive (0),
               active (1)
               }
   MAX-ACCESS  read-only
   STATUS      current
   DESCRIPTION
      "Path: swPort.status.oam.remoteInfo.mode

       Possibilities:
               passive   (0)
               active   (1)"
   ::= {sr1646v2EthPortSwFOamEntry 67764224}

sr1646v2EthPortSwFOamRemoteInfoMaxPduSize OBJECT-TYPE
   SYNTAX      Integer32
   MAX-ACCESS  read-only
   STATUS      current
   DESCRIPTION
      "Path: swPort.status.oam.remoteInfo.maxPduSize"
   ::= {sr1646v2EthPortSwFOamEntry 67829760}

sr1646v2EthPortSwFOamEventsErroredSymbolWindow OBJECT-TYPE
   SYNTAX      Integer32
   UNITS       "symbols"
   MAX-ACCESS  read-only
   STATUS      current
   DESCRIPTION
      "Path: swPort.status.oam.events.erroredSymbol.window

       unit name = symbols"
   ::= {sr1646v2EthPortSwFOamEntry 83951872}

sr1646v2EthPortSwFOamEventsErroredSymbolThreshold OBJECT-TYPE
   SYNTAX      OCTET STRING
   UNITS       "symbols"
   MAX-ACCESS  read-only
   STATUS      current
   DESCRIPTION
      "Path: swPort.status.oam.events.erroredSymbol.threshold

       unit name = symbols"
   ::= {sr1646v2EthPortSwFOamEntry 83952128}

sr1646v2EthPortSwFOamEventsErroredFramePeriodWindow OBJECT-TYPE
   SYNTAX      INTEGER
               {
               default (0)
               }
   UNITS       "frames"
   MAX-ACCESS  read-only
   STATUS      current
   DESCRIPTION
      "Path: swPort.status.oam.events.erroredFramePeriod.window

       unit name = frames

       Possibilities:
               default   (0)"
   ::= {sr1646v2EthPortSwFOamEntry 84017408}

sr1646v2EthPortSwFOamEventsErroredFramePeriodThreshold OBJECT-TYPE
   SYNTAX      Integer32
   UNITS       "frames"
   MAX-ACCESS  read-only
   STATUS      current
   DESCRIPTION
      "Path: swPort.status.oam.events.erroredFramePeriod.threshold

       unit name = frames"
   ::= {sr1646v2EthPortSwFOamEntry 84017664}

sr1646v2EthPortSwFOamEventsErroredFrameWindow OBJECT-TYPE
   SYNTAX      Integer32
   UNITS       "100msec"
   MAX-ACCESS  read-only
   STATUS      current
   DESCRIPTION
      "Path: swPort.status.oam.events.erroredFrame.window

       unit name = 100msec"
   ::= {sr1646v2EthPortSwFOamEntry 84082944}

sr1646v2EthPortSwFOamEventsErroredFrameThreshold OBJECT-TYPE
   SYNTAX      Integer32
   UNITS       "frames"
   MAX-ACCESS  read-only
   STATUS      current
   DESCRIPTION
      "Path: swPort.status.oam.events.erroredFrame.threshold

       unit name = frames"
   ::= {sr1646v2EthPortSwFOamEntry 84083200}

sr1646v2EthPortSwFOamEventsErroredFrameSecondsWindow OBJECT-TYPE
   SYNTAX      Integer32
   UNITS       "100msec"
   MAX-ACCESS  read-only
   STATUS      current
   DESCRIPTION
      "Path: swPort.status.oam.events.erroredFrameSeconds.window

       unit name = 100msec"
   ::= {sr1646v2EthPortSwFOamEntry 84148480}

sr1646v2EthPortSwFOamEventsErroredFrameSecondsThreshold OBJECT-TYPE
   SYNTAX      Integer32
   UNITS       "frames"
   MAX-ACCESS  read-only
   STATUS      current
   DESCRIPTION
      "Path: swPort.status.oam.events.erroredFrameSeconds.threshold

       unit name = frames"
   ::= {sr1646v2EthPortSwFOamEntry 84148736}


sr1646v2EthPortSwFOamEventLog OBJECT IDENTIFIER ::= {sr1646v2EthPortSwF 911}

sr1646v2EthPortSwFOamEventLogSSCTable OBJECT-TYPE
   SYNTAX      SEQUENCE OF Sr1646v2EthPortSwFOamEventLogEntry
   MAX-ACCESS  not-accessible
   STATUS      current
   DESCRIPTION
      "OAM event log"
   ::= {sr1646v2EthPortSwFOamEventLog 1}

sr1646v2EthPortSwFOamEventLogEntry OBJECT-TYPE
   SYNTAX      Sr1646v2EthPortSwFOamEventLogEntry
   MAX-ACCESS  not-accessible
   STATUS      current
   DESCRIPTION
      ""
   INDEX      { sr1646v2EthPortSwFOamEventLogGlobalIx,
                sr1646v2EthPortSwFOamEventLogTableIx }
   ::= {sr1646v2EthPortSwFOamEventLogSSCTable 1}

Sr1646v2EthPortSwFOamEventLogEntry ::=
   SEQUENCE
      {
      sr1646v2EthPortSwFOamEventLogGlobalIx
         GlobalIndex,
      sr1646v2EthPortSwFOamEventLogTableIx
         TableIndex,
      sr1646v2EthPortSwFOamEventLogSysUpTime
         TimeTicks,
      sr1646v2EthPortSwFOamEventLogLocation
         INTEGER,
      sr1646v2EthPortSwFOamEventLogType
         INTEGER,
      sr1646v2EthPortSwFOamEventLogOui
         OCTET STRING,
      sr1646v2EthPortSwFOamEventLogWindow
         Counter64,
      sr1646v2EthPortSwFOamEventLogThreshold
         Counter64,
      sr1646v2EthPortSwFOamEventLogTotal
         Counter32,
      sr1646v2EthPortSwFOamEventLogValue
         Counter64,
      sr1646v2EthPortSwFOamEventLogRunningTotal
         Counter64
      }

sr1646v2EthPortSwFOamEventLogGlobalIx OBJECT-TYPE
   SYNTAX      GlobalIndex
   MAX-ACCESS  not-accessible
   STATUS      current
   DESCRIPTION
      "The value of the tlsCntTreeGlobalIndex of the MANAGED OBJECT."
   ::= {sr1646v2EthPortSwFOamEventLogEntry 10}

sr1646v2EthPortSwFOamEventLogTableIx OBJECT-TYPE
   SYNTAX      TableIndex
   MAX-ACCESS  not-accessible
   STATUS      current
   DESCRIPTION
      ""
   ::= {sr1646v2EthPortSwFOamEventLogEntry 11}

sr1646v2EthPortSwFOamEventLogSysUpTime OBJECT-TYPE
   SYNTAX      TimeTicks
   MAX-ACCESS  read-only
   STATUS      current
   DESCRIPTION
      "Path: swPort.status.oamEventLog.sysUpTime

       Time in centi-second."
   ::= {sr1646v2EthPortSwFOamEventLogEntry 16777216}

sr1646v2EthPortSwFOamEventLogLocation OBJECT-TYPE
   SYNTAX      INTEGER
               {
               local (1),
               remote (2)
               }
   MAX-ACCESS  read-only
   STATUS      current
   DESCRIPTION
      "Path: swPort.status.oamEventLog.location

       Possibilities:
               local   (1)
               remote   (2)"
   ::= {sr1646v2EthPortSwFOamEventLogEntry 33554432}

sr1646v2EthPortSwFOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: swPort.status.oamEventLog.type

       Possibilities:
               erroredSymbols   (1)
               erroredFramePeriod   (2)
               erroredFrame   (3)
               erroredFrameSeconds   (4)
               linkFault   (256)
               dyingGasp   (257)
               criticalLink   (258)"
   ::= {sr1646v2EthPortSwFOamEventLogEntry 50331648}

sr1646v2EthPortSwFOamEventLogOui OBJECT-TYPE
   SYNTAX      OCTET STRING
   MAX-ACCESS  read-only
   STATUS      current
   DESCRIPTION
      "Path: swPort.status.oamEventLog.oui"
   ::= {sr1646v2EthPortSwFOamEventLogEntry 67108864}

sr1646v2EthPortSwFOamEventLogWindow OBJECT-TYPE
   SYNTAX      Counter64
   MAX-ACCESS  read-only
   STATUS      current
   DESCRIPTION
      "Path: swPort.status.oamEventLog.window

       64 bit unsigned wrappable counter."
   ::= {sr1646v2EthPortSwFOamEventLogEntry 83886080}

sr1646v2EthPortSwFOamEventLogThreshold OBJECT-TYPE
   SYNTAX      Counter64
   MAX-ACCESS  read-only
   STATUS      current
   DESCRIPTION
      "Path: swPort.status.oamEventLog.threshold

       64 bit unsigned wrappable counter."
   ::= {sr1646v2EthPortSwFOamEventLogEntry 100663296}

sr1646v2EthPortSwFOamEventLogTotal OBJECT-TYPE
   SYNTAX      Counter32
   MAX-ACCESS  read-only
   STATUS      current
   DESCRIPTION
      "Path: swPort.status.oamEventLog.total

       32 bit unsigned wrappable counter."
   ::= {sr1646v2EthPortSwFOamEventLogEntry 117440512}

sr1646v2EthPortSwFOamEventLogValue OBJECT-TYPE
   SYNTAX      Counter64
   MAX-ACCESS  read-only
   STATUS      current
   DESCRIPTION
      "Path: swPort.status.oamEventLog.value

       64 bit unsigned wrappable counter."
   ::= {sr1646v2EthPortSwFOamEventLogEntry 134217728}

sr1646v2EthPortSwFOamEventLogRunningTotal OBJECT-TYPE
   SYNTAX      Counter64
   MAX-ACCESS  read-only
   STATUS      current
   DESCRIPTION
      "Path: swPort.status.oamEventLog.runningTotal

       64 bit unsigned wrappable counter."
   ::= {sr1646v2EthPortSwFOamEventLogEntry 150994944}


sr1646v2EthPortSwFVlan OBJECT IDENTIFIER ::= {sr1646v2EthPortSwF 34}

sr1646v2EthPortSwFVlanSSCTable OBJECT-TYPE
   SYNTAX      SEQUENCE OF Sr1646v2EthPortSwFVlanEntry
   MAX-ACCESS  not-accessible
   STATUS      current
   DESCRIPTION
      ""
   ::= {sr1646v2EthPortSwFVlan 1}

sr1646v2EthPortSwFVlanEntry OBJECT-TYPE
   SYNTAX      Sr1646v2EthPortSwFVlanEntry
   MAX-ACCESS  not-accessible
   STATUS      current
   DESCRIPTION
      ""
   INDEX      { sr1646v2EthPortSwFVlanGlobalIx,
                sr1646v2EthPortSwFVlanTableIx }
   ::= {sr1646v2EthPortSwFVlanSSCTable 1}

Sr1646v2EthPortSwFVlanEntry ::=
   SEQUENCE
      {
      sr1646v2EthPortSwFVlanGlobalIx
         GlobalIndex,
      sr1646v2EthPortSwFVlanTableIx
         TableIndex,
      sr1646v2EthPortSwFVlanName
         DisplayString,
      sr1646v2EthPortSwFVlanMode
         INTEGER,
      sr1646v2EthPortSwFVlanIfOperStatus
         INTEGER,
      sr1646v2EthPortSwFVlanIfLastChange
         TimeTicks,
      sr1646v2EthPortSwFVlanIfLastChangeDate
         DisplayString,
      sr1646v2EthPortSwFVlanIpAddress
         IpAddress,
      sr1646v2EthPortSwFVlanIpNetMask
         IpAddress,
      sr1646v2EthPortSwFVlanIpRemote
         IpAddress,
      sr1646v2EthPortSwFVlanIpDhcpStatus
         INTEGER,
      sr1646v2EthPortSwFVlanIpDhcpLeaseTime
         TimeTicks,
      sr1646v2EthPortSwFVlanIpV6State
         INTEGER,
      sr1646v2EthPortSwFVlanIpV6InterfaceId
         OCTET STRING,
      sr1646v2EthPortSwFVlanIpV6LinkMtu
         Integer32,
      sr1646v2EthPortSwFVlanIpV6HopLimit
         Integer32,
      sr1646v2EthPortSwFVlanIpV6DhcpIaid
         Counter32,
      sr1646v2EthPortSwFVlanIpV6RaRcvOption
         Integer32,
      sr1646v2EthPortSwFVlanBridgingStatus
         INTEGER,
      sr1646v2EthPortSwFVlanBridgingSpanningTreePortRole
         INTEGER,
      sr1646v2EthPortSwFVlanBridgingSpanningTreePortId
         Integer32,
      sr1646v2EthPortSwFVlanBridgingSpanningTreePpCostExtPathCost
         Integer32,
      sr1646v2EthPortSwFVlanBridgingSpanningTreePpCostIntPathCost
         Integer32,
      sr1646v2EthPortSwFVlanBridgingSpanningTreeExtRpCost
         Integer32,
      sr1646v2EthPortSwFVlanBridgingSpanningTreeIntRpCost
         Integer32,
      sr1646v2EthPortSwFVlanBridgingSpanningTreeDesBrIdPriority
         Integer32,
      sr1646v2EthPortSwFVlanBridgingSpanningTreeDesBrIdMacAddress
         OCTET STRING,
      sr1646v2EthPortSwFVlanBridgingSpanningTreeDesPrtId
         Integer32,
      sr1646v2EthPortSwFVlanBridgingSpanningTreeDesInt
         INTEGER,
      sr1646v2EthPortSwFVlanBridgingSpanningTreeEdgeDetection
         INTEGER,
      sr1646v2EthPortSwFVlanVlanVid
         Integer32,
      sr1646v2EthPortSwFVlanPppOEthDiscState
         INTEGER,
      sr1646v2EthPortSwFVlanPppOEthPeerMac
         OCTET STRING,
      sr1646v2EthPortSwFVlanPppOEthServiceName
         DisplayString,
      sr1646v2EthPortSwFVlanPppLcpState
         INTEGER,
      sr1646v2EthPortSwFVlanPppIpcpState
         INTEGER,
      sr1646v2EthPortSwFVlanPppIp6cpState
         INTEGER,
      sr1646v2EthPortSwFVlanPppMyAutSt
         INTEGER,
      sr1646v2EthPortSwFVlanPppHisAutSt
         INTEGER,
      sr1646v2EthPortSwFVlanPppMru
         Integer32
      }

sr1646v2EthPortSwFVlanGlobalIx OBJECT-TYPE
   SYNTAX      GlobalIndex
   MAX-ACCESS  not-accessible
   STATUS      current
   DESCRIPTION
      "The value of the tlsCntTreeGlobalIndex of the MANAGED OBJECT."
   ::= {sr1646v2EthPortSwFVlanEntry 10}

sr1646v2EthPortSwFVlanTableIx OBJECT-TYPE
   SYNTAX      TableIndex
   MAX-ACCESS  not-accessible
   STATUS      current
   DESCRIPTION
      ""
   ::= {sr1646v2EthPortSwFVlanEntry 11}

sr1646v2EthPortSwFVlanName OBJECT-TYPE
   SYNTAX      DisplayString
   MAX-ACCESS  read-only
   STATUS      current
   DESCRIPTION
      "Path: swPort.status.vlan.name"
   ::= {sr1646v2EthPortSwFVlanEntry 16777216}

sr1646v2EthPortSwFVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EthPortSwFVlanEntry 335544320}

sr1646v2EthPortSwFVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.vlan.ifOperStatus

       Possibilities:
               up   (1)
               down   (2)
               testing   (3)
               unknown   (4)
               dormant   (5)
               notPresent   (6)
               lowerLayerDown   (7)"
   ::= {sr1646v2EthPortSwFVlanEntry 1795162112}

sr1646v2EthPortSwFVlanIfLastChange OBJECT-TYPE
   SYNTAX      TimeTicks
   MAX-ACCESS  read-only
   STATUS      current
   DESCRIPTION
      "Path: swPort.status.vlan.ifLastChange

       Time in centi-second."
   ::= {sr1646v2EthPortSwFVlanEntry 1811939328}

sr1646v2EthPortSwFVlanIfLastChangeDate OBJECT-TYPE
   SYNTAX      DisplayString
   MAX-ACCESS  read-only
   STATUS      current
   DESCRIPTION
      "Path: swPort.status.vlan.ifLastChangeDate"
   ::= {sr1646v2EthPortSwFVlanEntry 3070230528}

sr1646v2EthPortSwFVlanIpAddress OBJECT-TYPE
   SYNTAX      IpAddress
   MAX-ACCESS  read-only
   STATUS      current
   DESCRIPTION
      "Path: swPort.status.vlan.ip.address"
   ::= {sr1646v2EthPortSwFVlanEntry 51380224}

sr1646v2EthPortSwFVlanIpNetMask OBJECT-TYPE
   SYNTAX      IpAddress
   MAX-ACCESS  read-only
   STATUS      current
   DESCRIPTION
      "Path: swPort.status.vlan.ip.netMask"
   ::= {sr1646v2EthPortSwFVlanEntry 51445760}

sr1646v2EthPortSwFVlanIpRemote OBJECT-TYPE
   SYNTAX      IpAddress
   MAX-ACCESS  read-only
   STATUS      current
   DESCRIPTION
      "Path: swPort.status.vlan.ip.remote"
   ::= {sr1646v2EthPortSwFVlanEntry 51511296}

sr1646v2EthPortSwFVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.vlan.ip.dhcp.status

       Possibilities:
               none   (0)
               selecting   (1)
               requesting   (2)
               rebinding   (3)
               bound   (4)
               renewing   (5)
               rebooting   (6)
               initreboot   (7)"
   ::= {sr1646v2EthPortSwFVlanEntry 51904768}

sr1646v2EthPortSwFVlanIpDhcpLeaseTime OBJECT-TYPE
   SYNTAX      TimeTicks
   MAX-ACCESS  read-only
   STATUS      current
   DESCRIPTION
      "Path: swPort.status.vlan.ip.dhcp.leaseTime

       Time in centi-second."
   ::= {sr1646v2EthPortSwFVlanEntry 51905024}

sr1646v2EthPortSwFVlanIpV6State OBJECT-TYPE
   SYNTAX      INTEGER
               {
               disabled (0),
               enabled (1)
               }
   MAX-ACCESS  read-only
   STATUS      current
   DESCRIPTION
      "Path: swPort.status.vlan.ipV6.state

       Possibilities:
               disabled   (0)
               enabled   (1)"
   ::= {sr1646v2EthPortSwFVlanEntry 100728832}

sr1646v2EthPortSwFVlanIpV6InterfaceId OBJECT-TYPE
   SYNTAX      OCTET STRING
   MAX-ACCESS  read-only
   STATUS      current
   DESCRIPTION
      "Path: swPort.status.vlan.ipV6.interfaceId"
   ::= {sr1646v2EthPortSwFVlanEntry 100794368}

sr1646v2EthPortSwFVlanIpV6LinkMtu OBJECT-TYPE
   SYNTAX      Integer32
   MAX-ACCESS  read-only
   STATUS      current
   DESCRIPTION
      "Path: swPort.status.vlan.ipV6.linkMtu"
   ::= {sr1646v2EthPortSwFVlanEntry 100925440}

sr1646v2EthPortSwFVlanIpV6HopLimit OBJECT-TYPE
   SYNTAX      Integer32
   MAX-ACCESS  read-only
   STATUS      current
   DESCRIPTION
      "Path: swPort.status.vlan.ipV6.hopLimit"
   ::= {sr1646v2EthPortSwFVlanEntry 100990976}

sr1646v2EthPortSwFVlanIpV6DhcpIaid OBJECT-TYPE
   SYNTAX      Counter32
   MAX-ACCESS  read-only
   STATUS      current
   DESCRIPTION
      "Path: swPort.status.vlan.ipV6.dhcp.iaid

       32 bit unsigned wrappable counter."
   ::= {sr1646v2EthPortSwFVlanEntry 101056768}

sr1646v2EthPortSwFVlanIpV6RaRcvOption OBJECT-TYPE
   SYNTAX      Integer32
   MAX-ACCESS  read-only
   STATUS      current
   DESCRIPTION
      "Path: swPort.status.vlan.ipV6.raRcvOption

       Bit meanings:
               bit 0 = linkMtu,
               bit 1 = srcLinkLayer,
               bit 2 = prefixInfo,
               bit 3 = rdnss,
               bit 4 = dnssl"
   ::= {sr1646v2EthPortSwFVlanEntry 101122048}

sr1646v2EthPortSwFVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.vlan.bridging.status

       Possibilities:
               disabled   (0)
               discarding   (1)
               learning   (2)
               forwarding   (3)
               backupBlockedIntfDown   (256)
               backupBlockedIntfUp   (259)
               shutdown   (255)"
   ::= {sr1646v2EthPortSwFVlanEntry 453050368}

sr1646v2EthPortSwFVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.vlan.bridging.spanningTree.portRole

       Possibilities:
               none   (0)
               root   (1)
               designated   (2)
               alternate   (3)
               backup   (4)
               disabled   (5)
               master   (6)"
   ::= {sr1646v2EthPortSwFVlanEntry 453116160}

sr1646v2EthPortSwFVlanBridgingSpanningTreePortId OBJECT-TYPE
   SYNTAX      Integer32
   MAX-ACCESS  read-only
   STATUS      current
   DESCRIPTION
      "Path: swPort.status.vlan.bridging.spanningTree.portId"
   ::= {sr1646v2EthPortSwFVlanEntry 453116416}

sr1646v2EthPortSwFVlanBridgingSpanningTreePpCostExtPathCost OBJECT-TYPE
   SYNTAX      Integer32
   MAX-ACCESS  read-only
   STATUS      current
   DESCRIPTION
      "Path: swPort.status.vlan.bridging.spanningTree.portPathCosts.extPathCost"
   ::= {sr1646v2EthPortSwFVlanEntry 453116673}

sr1646v2EthPortSwFVlanBridgingSpanningTreePpCostIntPathCost OBJECT-TYPE
   SYNTAX      Integer32
   MAX-ACCESS  read-only
   STATUS      current
   DESCRIPTION
      "Path: swPort.status.vlan.bridging.spanningTree.portPathCosts.intPathCost"
   ::= {sr1646v2EthPortSwFVlanEntry 453116674}

sr1646v2EthPortSwFVlanBridgingSpanningTreeExtRpCost OBJECT-TYPE
   SYNTAX      Integer32
   MAX-ACCESS  read-only
   STATUS      current
   DESCRIPTION
      "Path: swPort.status.vlan.bridging.spanningTree.extRootPathCost"
   ::= {sr1646v2EthPortSwFVlanEntry 453116928}

sr1646v2EthPortSwFVlanBridgingSpanningTreeIntRpCost OBJECT-TYPE
   SYNTAX      Integer32
   MAX-ACCESS  read-only
   STATUS      current
   DESCRIPTION
      "Path: swPort.status.vlan.bridging.spanningTree.intRootPathCost"
   ::= {sr1646v2EthPortSwFVlanEntry 453117184}

sr1646v2EthPortSwFVlanBridgingSpanningTreeDesBrIdPriority OBJECT-TYPE
   SYNTAX      Integer32
   MAX-ACCESS  read-only
   STATUS      current
   DESCRIPTION
      "Path: swPort.status.vlan.bridging.spanningTree.designatedBridgeId.priority"
   ::= {sr1646v2EthPortSwFVlanEntry 453117441}

sr1646v2EthPortSwFVlanBridgingSpanningTreeDesBrIdMacAddress OBJECT-TYPE
   SYNTAX      OCTET STRING
   MAX-ACCESS  read-only
   STATUS      current
   DESCRIPTION
      "Path: swPort.status.vlan.bridging.spanningTree.designatedBridgeId.macAddress

       MAC address."
   ::= {sr1646v2EthPortSwFVlanEntry 453117442}

sr1646v2EthPortSwFVlanBridgingSpanningTreeDesPrtId OBJECT-TYPE
   SYNTAX      Integer32
   MAX-ACCESS  read-only
   STATUS      current
   DESCRIPTION
      "Path: swPort.status.vlan.bridging.spanningTree.designatedPortId"
   ::= {sr1646v2EthPortSwFVlanEntry 453117696}

sr1646v2EthPortSwFVlanBridgingSpanningTreeDesInt OBJECT-TYPE
   SYNTAX      INTEGER
               {
               no (0),
               yes (1)
               }
   MAX-ACCESS  read-only
   STATUS      current
   DESCRIPTION
      "Path: swPort.status.vlan.bridging.spanningTree.designatedOrInternal

       Possibilities:
               no   (0)
               yes   (1)"
   ::= {sr1646v2EthPortSwFVlanEntry 453117952}

sr1646v2EthPortSwFVlanBridgingSpanningTreeEdgeDetection OBJECT-TYPE
   SYNTAX      INTEGER
               {
               none (0),
               edge (1),
               notEdge (2)
               }
   MAX-ACCESS  read-only
   STATUS      current
   DESCRIPTION
      "Path: swPort.status.vlan.bridging.spanningTree.edgeDetection

       Possibilities:
               none   (0)
               edge   (1)
               notEdge   (2)"
   ::= {sr1646v2EthPortSwFVlanEntry 453118208}

sr1646v2EthPortSwFVlanVlanVid OBJECT-TYPE
   SYNTAX      Integer32
   MAX-ACCESS  read-only
   STATUS      current
   DESCRIPTION
      "Path: swPort.status.vlan.vlan.vid"
   ::= {sr1646v2EthPortSwFVlanEntry 234946560}

sr1646v2EthPortSwFVlanPppOEthDiscState OBJECT-TYPE
   SYNTAX      INTEGER
               {
               idle (0),
               waitForPADO (1),
               waitForPADS (2),
               established (3)
               }
   MAX-ACCESS  read-only
   STATUS      current
   DESCRIPTION
      "Path: swPort.status.vlan.pppOverEth.discState

       Possibilities:
               idle   (0)
               waitForPADO   (1)
               waitForPADS   (2)
               established   (3)"
   ::= {sr1646v2EthPortSwFVlanEntry 67174400}

sr1646v2EthPortSwFVlanPppOEthPeerMac OBJECT-TYPE
   SYNTAX      OCTET STRING
   MAX-ACCESS  read-only
   STATUS      current
   DESCRIPTION
      "Path: swPort.status.vlan.pppOverEth.remoteMacAddress

       MAC address."
   ::= {sr1646v2EthPortSwFVlanEntry 67239936}

sr1646v2EthPortSwFVlanPppOEthServiceName OBJECT-TYPE
   SYNTAX      DisplayString
   MAX-ACCESS  read-only
   STATUS      current
   DESCRIPTION
      "Path: swPort.status.vlan.pppOverEth.serviceName"
   ::= {sr1646v2EthPortSwFVlanEntry 67305472}

sr1646v2EthPortSwFVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFVlanEntry 83951616}

sr1646v2EthPortSwFVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFVlanEntry 84017152}

sr1646v2EthPortSwFVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFVlanEntry 84869120}

sr1646v2EthPortSwFVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EthPortSwFVlanEntry 84541440}

sr1646v2EthPortSwFVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EthPortSwFVlanEntry 84606976}

sr1646v2EthPortSwFVlanPppMru OBJECT-TYPE
   SYNTAX      Integer32
   MAX-ACCESS  read-only
   STATUS      current
   DESCRIPTION
      "Path: swPort.status.vlan.ppp.mru"
   ::= {sr1646v2EthPortSwFVlanEntry 84934656}

sr1646v2EthPortSwFVlanIpSecondaryIp OBJECT-TYPE
   SYNTAX      SEQUENCE OF Sr1646v2EthPortSwFVlanIpSecondaryIpEntry
   MAX-ACCESS  not-accessible
   STATUS      current
   DESCRIPTION
      ""
   ::= {sr1646v2EthPortSwFVlan 51838976}

sr1646v2EthPortSwFVlanIpSecondaryIpEntry OBJECT-TYPE
   SYNTAX      Sr1646v2EthPortSwFVlanIpSecondaryIpEntry
   MAX-ACCESS  not-accessible
   STATUS      current
   DESCRIPTION
      ""
   INDEX      { sr1646v2EthPortSwFVlanIpSecondaryIpGlobalIx,
                sr1646v2EthPortSwFVlanTableIx,
                sr1646v2EthPortSwFVlanIpSecondaryIpTableIx }
   ::= {sr1646v2EthPortSwFVlanIpSecondaryIp 1}

Sr1646v2EthPortSwFVlanIpSecondaryIpEntry ::=
   SEQUENCE
      {
      sr1646v2EthPortSwFVlanIpSecondaryIpGlobalIx
         GlobalIndex,
      sr1646v2EthPortSwFVlanIpSecondaryIpTableIx
         TableIndex,
      sr1646v2EthPortSwFVlanIpSecondaryIpAddress
         IpAddress,
      sr1646v2EthPortSwFVlanIpSecondaryIpNetMask
         IpAddress
      }

sr1646v2EthPortSwFVlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2EthPortSwFVlanIpSecondaryIpEntry 10}

sr1646v2EthPortSwFVlanIpSecondaryIpTableIx OBJECT-TYPE
   SYNTAX      TableIndex
   MAX-ACCESS  not-accessible
   STATUS      current
   DESCRIPTION
      ""
   ::= {sr1646v2EthPortSwFVlanIpSecondaryIpEntry 11}

sr1646v2EthPortSwFVlanIpSecondaryIpAddress OBJECT-TYPE
   SYNTAX      IpAddress
   MAX-ACCESS  read-only
   STATUS      current
   DESCRIPTION
      "Path: swPort.status.vlan.ip.secondaryIp.address"
   ::= {sr1646v2EthPortSwFVlanIpSecondaryIpEntry 2030043136}

sr1646v2EthPortSwFVlanIpSecondaryIpNetMask OBJECT-TYPE
   SYNTAX      IpAddress
   MAX-ACCESS  read-only
   STATUS      current
   DESCRIPTION
      "Path: swPort.status.vlan.ip.secondaryIp.netMask"
   ::= {sr1646v2EthPortSwFVlanIpSecondaryIpEntry 2063597568}

sr1646v2EthPortSwFVlanIpV6Addresses OBJECT-TYPE
   SYNTAX      SEQUENCE OF Sr1646v2EthPortSwFVlanIpV6AddressesEntry
   MAX-ACCESS  not-accessible
   STATUS      current
   DESCRIPTION
      ""
   ::= {sr1646v2EthPortSwFVlan 100859904}

sr1646v2EthPortSwFVlanIpV6AddressesEntry OBJECT-TYPE
   SYNTAX      Sr1646v2EthPortSwFVlanIpV6AddressesEntry
   MAX-ACCESS  not-accessible
   STATUS      current
   DESCRIPTION
      ""
   INDEX      { sr1646v2EthPortSwFVlanIpV6AddressesGlobalIx,
                sr1646v2EthPortSwFVlanTableIx,
                sr1646v2EthPortSwFVlanIpV6AddressesTableIx }
   ::= {sr1646v2EthPortSwFVlanIpV6Addresses 1}

Sr1646v2EthPortSwFVlanIpV6AddressesEntry ::=
   SEQUENCE
      {
      sr1646v2EthPortSwFVlanIpV6AddressesGlobalIx
         GlobalIndex,
      sr1646v2EthPortSwFVlanIpV6AddressesTableIx
         TableIndex,
      sr1646v2EthPortSwFVlanIpV6AddressesAddress
         Ipv6Address,
      sr1646v2EthPortSwFVlanIpV6AddressesPrefixLength
         Integer32,
      sr1646v2EthPortSwFVlanIpV6AddressesStatus
         INTEGER,
      sr1646v2EthPortSwFVlanIpV6AddressesOrigin
         INTEGER,
      sr1646v2EthPortSwFVlanIpV6AddressesFlagsInterfaceId
         INTEGER,
      sr1646v2EthPortSwFVlanIpV6AddressesFlagsAnycast
         INTEGER,
      sr1646v2EthPortSwFVlanIpV6AddressesTimersValidLifeTime
         TimeTicks,
      sr1646v2EthPortSwFVlanIpV6AddressesTimersPrefLifeTime
         TimeTicks
      }

sr1646v2EthPortSwFVlanIpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwFVlanIpV6AddressesEntry 10}

sr1646v2EthPortSwFVlanIpV6AddressesTableIx OBJECT-TYPE
   SYNTAX      TableIndex
   MAX-ACCESS  not-accessible
   STATUS      current
   DESCRIPTION
      ""
   ::= {sr1646v2EthPortSwFVlanIpV6AddressesEntry 11}

sr1646v2EthPortSwFVlanIpV6AddressesAddress OBJECT-TYPE
   SYNTAX      Ipv6Address
   MAX-ACCESS  read-only
   STATUS      current
   DESCRIPTION
      "Path: swPort.status.vlan.ipV6.addresses.address

       ipv6 address"
   ::= {sr1646v2EthPortSwFVlanIpV6AddressesEntry 16777216}

sr1646v2EthPortSwFVlanIpV6AddressesPrefixLength OBJECT-TYPE
   SYNTAX      Integer32
   MAX-ACCESS  read-only
   STATUS      current
   DESCRIPTION
      "Path: swPort.status.vlan.ipV6.addresses.prefixLength"
   ::= {sr1646v2EthPortSwFVlanIpV6AddressesEntry 33554432}

sr1646v2EthPortSwFVlanIpV6AddressesStatus OBJECT-TYPE
   SYNTAX      INTEGER
               {
               invalid (0),
               tentative (1),
               deprecated (2),
               preferred (3)
               }
   MAX-ACCESS  read-only
   STATUS      current
   DESCRIPTION
      "Path: swPort.status.vlan.ipV6.addresses.status

       Possibilities:
               invalid   (0)
               tentative   (1)
               deprecated   (2)
               preferred   (3)"
   ::= {sr1646v2EthPortSwFVlanIpV6AddressesEntry 50331648}

sr1646v2EthPortSwFVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.vlan.ipV6.addresses.origin

       Possibilities:
               unknown   (0)
               manual   (1)
               generalPrefix   (2)
               statelessAuto   (3)
               statefullAuto   (4)"
   ::= {sr1646v2EthPortSwFVlanIpV6AddressesEntry 67108864}

sr1646v2EthPortSwFVlanIpV6AddressesFlagsInterfaceId OBJECT-TYPE
   SYNTAX      INTEGER
               {
               no (0),
               yes (1)
               }
   MAX-ACCESS  read-only
   STATUS      current
   DESCRIPTION
      "Path: swPort.status.vlan.ipV6.addresses.flags.interfaceId

       Possibilities:
               no   (0)
               yes   (1)"
   ::= {sr1646v2EthPortSwFVlanIpV6AddressesEntry 83951616}

sr1646v2EthPortSwFVlanIpV6AddressesFlagsAnycast OBJECT-TYPE
   SYNTAX      INTEGER
               {
               no (0),
               yes (1)
               }
   MAX-ACCESS  read-only
   STATUS      current
   DESCRIPTION
      "Path: swPort.status.vlan.ipV6.addresses.flags.anycast

       Possibilities:
               no   (0)
               yes   (1)"
   ::= {sr1646v2EthPortSwFVlanIpV6AddressesEntry 84017152}

sr1646v2EthPortSwFVlanIpV6AddressesTimersValidLifeTime OBJECT-TYPE
   SYNTAX      TimeTicks
   MAX-ACCESS  read-only
   STATUS      current
   DESCRIPTION
      "Path: swPort.status.vlan.ipV6.addresses.timers.validLifeTime

       Time in centi-second."
   ::= {sr1646v2EthPortSwFVlanIpV6AddressesEntry 100794368}

sr1646v2EthPortSwFVlanIpV6AddressesTimersPrefLifeTime OBJECT-TYPE
   SYNTAX      TimeTicks
   MAX-ACCESS  read-only
   STATUS      current
   DESCRIPTION
      "Path: swPort.status.vlan.ipV6.addresses.timers.prefLifeTime

       Time in centi-second."
   ::= {sr1646v2EthPortSwFVlanIpV6AddressesEntry 100728832}

sr1646v2EthPortSwFVlanVlanArpCache OBJECT-TYPE
   SYNTAX      SEQUENCE OF Sr1646v2EthPortSwFVlanVlanArpCacheEntry
   MAX-ACCESS  not-accessible
   STATUS      current
   DESCRIPTION
      ""
   ::= {sr1646v2EthPortSwFVlan 235601920}

sr1646v2EthPortSwFVlanVlanArpCacheEntry OBJECT-TYPE
   SYNTAX      Sr1646v2EthPortSwFVlanVlanArpCacheEntry
   MAX-ACCESS  not-accessible
   STATUS      current
   DESCRIPTION
      ""
   INDEX      { sr1646v2EthPortSwFVlanVlanArpCacheGlobalIx,
                sr1646v2EthPortSwFVlanTableIx,
                sr1646v2EthPortSwFVlanVlanArpCacheTableIx }
   ::= {sr1646v2EthPortSwFVlanVlanArpCache 1}

Sr1646v2EthPortSwFVlanVlanArpCacheEntry ::=
   SEQUENCE
      {
      sr1646v2EthPortSwFVlanVlanArpCacheGlobalIx
         GlobalIndex,
      sr1646v2EthPortSwFVlanVlanArpCacheTableIx
         TableIndex,
      sr1646v2EthPortSwFVlanVlanArpCacheMacAddress
         OCTET STRING,
      sr1646v2EthPortSwFVlanVlanArpCacheIpAddress
         IpAddress,
      sr1646v2EthPortSwFVlanVlanArpCacheType
         INTEGER,
      sr1646v2EthPortSwFVlanVlanArpCacheTimeOut
         TimeTicks
      }

sr1646v2EthPortSwFVlanVlanArpCacheGlobalIx OBJECT-TYPE
   SYNTAX      GlobalIndex
   MAX-ACCESS  not-accessible
   STATUS      current
   DESCRIPTION
      "The value of the tlsCntTreeGlobalIndex of the MANAGED OBJECT."
   ::= {sr1646v2EthPortSwFVlanVlanArpCacheEntry 10}

sr1646v2EthPortSwFVlanVlanArpCacheTableIx OBJECT-TYPE
   SYNTAX      TableIndex
   MAX-ACCESS  not-accessible
   STATUS      current
   DESCRIPTION
      ""
   ::= {sr1646v2EthPortSwFVlanVlanArpCacheEntry 11}

sr1646v2EthPortSwFVlanVlanArpCacheMacAddress OBJECT-TYPE
   SYNTAX      OCTET STRING
   MAX-ACCESS  read-only
   STATUS      current
   DESCRIPTION
      "Path: swPort.status.vlan.vlan.arpCache.macAddress

       MAC address."
   ::= {sr1646v2EthPortSwFVlanVlanArpCacheEntry 16777216}

sr1646v2EthPortSwFVlanVlanArpCacheIpAddress OBJECT-TYPE
   SYNTAX      IpAddress
   MAX-ACCESS  read-only
   STATUS      current
   DESCRIPTION
      "Path: swPort.status.vlan.vlan.arpCache.ipAddress"
   ::= {sr1646v2EthPortSwFVlanVlanArpCacheEntry 33554432}

sr1646v2EthPortSwFVlanVlanArpCacheType OBJECT-TYPE
   SYNTAX      INTEGER
               {
               static (0),
               dynamic (1)
               }
   MAX-ACCESS  read-only
   STATUS      current
   DESCRIPTION
      "Path: swPort.status.vlan.vlan.arpCache.type

       Possibilities:
               static   (0)
               dynamic   (1)"
   ::= {sr1646v2EthPortSwFVlanVlanArpCacheEntry 50331648}

sr1646v2EthPortSwFVlanVlanArpCacheTimeOut OBJECT-TYPE
   SYNTAX      TimeTicks
   MAX-ACCESS  read-only
   STATUS      current
   DESCRIPTION
      "Path: swPort.status.vlan.vlan.arpCache.timeOut

       Time in centi-second."
   ::= {sr1646v2EthPortSwFVlanVlanArpCacheEntry 67108864}


sr1646v2EthPortSwFPppOE OBJECT IDENTIFIER ::= {sr1646v2EthPortSwF 36}

sr1646v2EthPortSwFPppOESSCTable OBJECT-TYPE
   SYNTAX      SEQUENCE OF Sr1646v2EthPortSwFPppOEEntry
   MAX-ACCESS  not-accessible
   STATUS      current
   DESCRIPTION
      ""
   ::= {sr1646v2EthPortSwFPppOE 1}

sr1646v2EthPortSwFPppOEEntry OBJECT-TYPE
   SYNTAX      Sr1646v2EthPortSwFPppOEEntry
   MAX-ACCESS  not-accessible
   STATUS      current
   DESCRIPTION
      ""
   INDEX      { sr1646v2EthPortSwFPppOEGlobalIx,
                sr1646v2EthPortSwFPppOETableIx }
   ::= {sr1646v2EthPortSwFPppOESSCTable 1}

Sr1646v2EthPortSwFPppOEEntry ::=
   SEQUENCE
      {
      sr1646v2EthPortSwFPppOEGlobalIx
         GlobalIndex,
      sr1646v2EthPortSwFPppOETableIx
         TableIndex,
      sr1646v2EthPortSwFPppOEName
         DisplayString,
      sr1646v2EthPortSwFPppOEMode
         INTEGER,
      sr1646v2EthPortSwFPppOEIfOperStatus
         INTEGER,
      sr1646v2EthPortSwFPppOEIfLastChange
         TimeTicks,
      sr1646v2EthPortSwFPppOEIfLastChangeDate
         DisplayString,
      sr1646v2EthPortSwFPppOEIpAddress
         IpAddress,
      sr1646v2EthPortSwFPppOEIpNetMask
         IpAddress,
      sr1646v2EthPortSwFPppOEIpRemote
         IpAddress,
      sr1646v2EthPortSwFPppOEPppOEthDiscState
         INTEGER,
      sr1646v2EthPortSwFPppOEPppOEthPeerMac
         OCTET STRING,
      sr1646v2EthPortSwFPppOEPppOEthServiceName
         DisplayString,
      sr1646v2EthPortSwFPppOEPppLcpState
         INTEGER,
      sr1646v2EthPortSwFPppOEPppIpcpState
         INTEGER,
      sr1646v2EthPortSwFPppOEPppIp6cpState
         INTEGER,
      sr1646v2EthPortSwFPppOEPppMyAutSt
         INTEGER,
      sr1646v2EthPortSwFPppOEPppHisAutSt
         INTEGER,
      sr1646v2EthPortSwFPppOEPppMru
         Integer32,
      sr1646v2EthPortSwFPppOEIpV6State
         INTEGER,
      sr1646v2EthPortSwFPppOEIpV6InterfaceId
         OCTET STRING,
      sr1646v2EthPortSwFPppOEIpV6LinkMtu
         Integer32,
      sr1646v2EthPortSwFPppOEIpV6HopLimit
         Integer32,
      sr1646v2EthPortSwFPppOEIpV6DhcpIaid
         Counter32,
      sr1646v2EthPortSwFPppOEIpV6RaRcvOption
         Integer32
      }

sr1646v2EthPortSwFPppOEGlobalIx OBJECT-TYPE
   SYNTAX      GlobalIndex
   MAX-ACCESS  not-accessible
   STATUS      current
   DESCRIPTION
      "The value of the tlsCntTreeGlobalIndex of the MANAGED OBJECT."
   ::= {sr1646v2EthPortSwFPppOEEntry 10}

sr1646v2EthPortSwFPppOETableIx OBJECT-TYPE
   SYNTAX      TableIndex
   MAX-ACCESS  not-accessible
   STATUS      current
   DESCRIPTION
      ""
   ::= {sr1646v2EthPortSwFPppOEEntry 11}

sr1646v2EthPortSwFPppOEName OBJECT-TYPE
   SYNTAX      DisplayString
   MAX-ACCESS  read-only
   STATUS      current
   DESCRIPTION
      "Path: swPort.status.pppoEClient.name"
   ::= {sr1646v2EthPortSwFPppOEEntry 16777216}

sr1646v2EthPortSwFPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EthPortSwFPppOEEntry 335544320}

sr1646v2EthPortSwFPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.pppoEClient.ifOperStatus

       Possibilities:
               up   (1)
               down   (2)
               testing   (3)
               unknown   (4)
               dormant   (5)
               notPresent   (6)
               lowerLayerDown   (7)"
   ::= {sr1646v2EthPortSwFPppOEEntry 1795162112}

sr1646v2EthPortSwFPppOEIfLastChange OBJECT-TYPE
   SYNTAX      TimeTicks
   MAX-ACCESS  read-only
   STATUS      current
   DESCRIPTION
      "Path: swPort.status.pppoEClient.ifLastChange

       Time in centi-second."
   ::= {sr1646v2EthPortSwFPppOEEntry 1811939328}

sr1646v2EthPortSwFPppOEIfLastChangeDate OBJECT-TYPE
   SYNTAX      DisplayString
   MAX-ACCESS  read-only
   STATUS      current
   DESCRIPTION
      "Path: swPort.status.pppoEClient.ifLastChangeDate"
   ::= {sr1646v2EthPortSwFPppOEEntry 3070230528}

sr1646v2EthPortSwFPppOEIpAddress OBJECT-TYPE
   SYNTAX      IpAddress
   MAX-ACCESS  read-only
   STATUS      current
   DESCRIPTION
      "Path: swPort.status.pppoEClient.ip.address"
   ::= {sr1646v2EthPortSwFPppOEEntry 51380224}

sr1646v2EthPortSwFPppOEIpNetMask OBJECT-TYPE
   SYNTAX      IpAddress
   MAX-ACCESS  read-only
   STATUS      current
   DESCRIPTION
      "Path: swPort.status.pppoEClient.ip.netMask"
   ::= {sr1646v2EthPortSwFPppOEEntry 51445760}

sr1646v2EthPortSwFPppOEIpRemote OBJECT-TYPE
   SYNTAX      IpAddress
   MAX-ACCESS  read-only
   STATUS      current
   DESCRIPTION
      "Path: swPort.status.pppoEClient.ip.remote"
   ::= {sr1646v2EthPortSwFPppOEEntry 51511296}

sr1646v2EthPortSwFPppOEPppOEthDiscState OBJECT-TYPE
   SYNTAX      INTEGER
               {
               idle (0),
               waitForPADO (1),
               waitForPADS (2),
               established (3)
               }
   MAX-ACCESS  read-only
   STATUS      current
   DESCRIPTION
      "Path: swPort.status.pppoEClient.pppOverEth.discState

       Possibilities:
               idle   (0)
               waitForPADO   (1)
               waitForPADS   (2)
               established   (3)"
   ::= {sr1646v2EthPortSwFPppOEEntry 67174400}

sr1646v2EthPortSwFPppOEPppOEthPeerMac OBJECT-TYPE
   SYNTAX      OCTET STRING
   MAX-ACCESS  read-only
   STATUS      current
   DESCRIPTION
      "Path: swPort.status.pppoEClient.pppOverEth.remoteMacAddress

       MAC address."
   ::= {sr1646v2EthPortSwFPppOEEntry 67239936}

sr1646v2EthPortSwFPppOEPppOEthServiceName OBJECT-TYPE
   SYNTAX      DisplayString
   MAX-ACCESS  read-only
   STATUS      current
   DESCRIPTION
      "Path: swPort.status.pppoEClient.pppOverEth.serviceName"
   ::= {sr1646v2EthPortSwFPppOEEntry 67305472}

sr1646v2EthPortSwFPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFPppOEEntry 83951616}

sr1646v2EthPortSwFPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFPppOEEntry 84017152}

sr1646v2EthPortSwFPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwFPppOEEntry 84869120}

sr1646v2EthPortSwFPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EthPortSwFPppOEEntry 84541440}

sr1646v2EthPortSwFPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EthPortSwFPppOEEntry 84606976}

sr1646v2EthPortSwFPppOEPppMru OBJECT-TYPE
   SYNTAX      Integer32
   MAX-ACCESS  read-only
   STATUS      current
   DESCRIPTION
      "Path: swPort.status.pppoEClient.ppp.mru"
   ::= {sr1646v2EthPortSwFPppOEEntry 84934656}

sr1646v2EthPortSwFPppOEIpV6State OBJECT-TYPE
   SYNTAX      INTEGER
               {
               disabled (0),
               enabled (1)
               }
   MAX-ACCESS  read-only
   STATUS      current
   DESCRIPTION
      "Path: swPort.status.pppoEClient.ipV6.state

       Possibilities:
               disabled   (0)
               enabled   (1)"
   ::= {sr1646v2EthPortSwFPppOEEntry 100728832}

sr1646v2EthPortSwFPppOEIpV6InterfaceId OBJECT-TYPE
   SYNTAX      OCTET STRING
   MAX-ACCESS  read-only
   STATUS      current
   DESCRIPTION
      "Path: swPort.status.pppoEClient.ipV6.interfaceId"
   ::= {sr1646v2EthPortSwFPppOEEntry 100794368}

sr1646v2EthPortSwFPppOEIpV6LinkMtu OBJECT-TYPE
   SYNTAX      Integer32
   MAX-ACCESS  read-only
   STATUS      current
   DESCRIPTION
      "Path: swPort.status.pppoEClient.ipV6.linkMtu"
   ::= {sr1646v2EthPortSwFPppOEEntry 100925440}

sr1646v2EthPortSwFPppOEIpV6HopLimit OBJECT-TYPE
   SYNTAX      Integer32
   MAX-ACCESS  read-only
   STATUS      current
   DESCRIPTION
      "Path: swPort.status.pppoEClient.ipV6.hopLimit"
   ::= {sr1646v2EthPortSwFPppOEEntry 100990976}

sr1646v2EthPortSwFPppOEIpV6DhcpIaid OBJECT-TYPE
   SYNTAX      Counter32
   MAX-ACCESS  read-only
   STATUS      current
   DESCRIPTION
      "Path: swPort.status.pppoEClient.ipV6.dhcp.iaid

       32 bit unsigned wrappable counter."
   ::= {sr1646v2EthPortSwFPppOEEntry 101056768}

sr1646v2EthPortSwFPppOEIpV6RaRcvOption OBJECT-TYPE
   SYNTAX      Integer32
   MAX-ACCESS  read-only
   STATUS      current
   DESCRIPTION
      "Path: swPort.status.pppoEClient.ipV6.raRcvOption

       Bit meanings:
               bit 0 = linkMtu,
               bit 1 = srcLinkLayer,
               bit 2 = prefixInfo,
               bit 3 = rdnss,
               bit 4 = dnssl"
   ::= {sr1646v2EthPortSwFPppOEEntry 101122048}

sr1646v2EthPortSwFPppOEIpV6Addresses OBJECT-TYPE
   SYNTAX      SEQUENCE OF Sr1646v2EthPortSwFPppOEIpV6AddressesEntry
   MAX-ACCESS  not-accessible
   STATUS      current
   DESCRIPTION
      ""
   ::= {sr1646v2EthPortSwFPppOE 100859904}

sr1646v2EthPortSwFPppOEIpV6AddressesEntry OBJECT-TYPE
   SYNTAX      Sr1646v2EthPortSwFPppOEIpV6AddressesEntry
   MAX-ACCESS  not-accessible
   STATUS      current
   DESCRIPTION
      ""
   INDEX      { sr1646v2EthPortSwFPppOEIpV6AddressesGlobalIx,
                sr1646v2EthPortSwFPppOETableIx,
                sr1646v2EthPortSwFPppOEIpV6AddressesTableIx }
   ::= {sr1646v2EthPortSwFPppOEIpV6Addresses 1}

Sr1646v2EthPortSwFPppOEIpV6AddressesEntry ::=
   SEQUENCE
      {
      sr1646v2EthPortSwFPppOEIpV6AddressesGlobalIx
         GlobalIndex,
      sr1646v2EthPortSwFPppOEIpV6AddressesTableIx
         TableIndex,
      sr1646v2EthPortSwFPppOEIpV6AddressesAddress
         Ipv6Address,
      sr1646v2EthPortSwFPppOEIpV6AddressesPrefixLength
         Integer32,
      sr1646v2EthPortSwFPppOEIpV6AddressesStatus
         INTEGER,
      sr1646v2EthPortSwFPppOEIpV6AddressesOrigin
         INTEGER,
      sr1646v2EthPortSwFPppOEIpV6AddressesFlagsInterfaceId
         INTEGER,
      sr1646v2EthPortSwFPppOEIpV6AddressesFlagsAnycast
         INTEGER,
      sr1646v2EthPortSwFPppOEIpV6AddressesTimersValidLifeTime
         TimeTicks,
      sr1646v2EthPortSwFPppOEIpV6AddressesTimersPrefLifeTime
         TimeTicks
      }

sr1646v2EthPortSwFPppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwFPppOEIpV6AddressesEntry 10}

sr1646v2EthPortSwFPppOEIpV6AddressesTableIx OBJECT-TYPE
   SYNTAX      TableIndex
   MAX-ACCESS  not-accessible
   STATUS      current
   DESCRIPTION
      ""
   ::= {sr1646v2EthPortSwFPppOEIpV6AddressesEntry 11}

sr1646v2EthPortSwFPppOEIpV6AddressesAddress OBJECT-TYPE
   SYNTAX      Ipv6Address
   MAX-ACCESS  read-only
   STATUS      current
   DESCRIPTION
      "Path: swPort.status.pppoEClient.ipV6.addresses.address

       ipv6 address"
   ::= {sr1646v2EthPortSwFPppOEIpV6AddressesEntry 16777216}

sr1646v2EthPortSwFPppOEIpV6AddressesPrefixLength OBJECT-TYPE
   SYNTAX      Integer32
   MAX-ACCESS  read-only
   STATUS      current
   DESCRIPTION
      "Path: swPort.status.pppoEClient.ipV6.addresses.prefixLength"
   ::= {sr1646v2EthPortSwFPppOEIpV6AddressesEntry 33554432}

sr1646v2EthPortSwFPppOEIpV6AddressesStatus OBJECT-TYPE
   SYNTAX      INTEGER
               {
               invalid (0),
               tentative (1),
               deprecated (2),
               preferred (3)
               }
   MAX-ACCESS  read-only
   STATUS      current
   DESCRIPTION
      "Path: swPort.status.pppoEClient.ipV6.addresses.status

       Possibilities:
               invalid   (0)
               tentative   (1)
               deprecated   (2)
               preferred   (3)"
   ::= {sr1646v2EthPortSwFPppOEIpV6AddressesEntry 50331648}

sr1646v2EthPortSwFPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.pppoEClient.ipV6.addresses.origin

       Possibilities:
               unknown   (0)
               manual   (1)
               generalPrefix   (2)
               statelessAuto   (3)
               statefullAuto   (4)"
   ::= {sr1646v2EthPortSwFPppOEIpV6AddressesEntry 67108864}

sr1646v2EthPortSwFPppOEIpV6AddressesFlagsInterfaceId OBJECT-TYPE
   SYNTAX      INTEGER
               {
               no (0),
               yes (1)
               }
   MAX-ACCESS  read-only
   STATUS      current
   DESCRIPTION
      "Path: swPort.status.pppoEClient.ipV6.addresses.flags.interfaceId

       Possibilities:
               no   (0)
               yes   (1)"
   ::= {sr1646v2EthPortSwFPppOEIpV6AddressesEntry 83951616}

sr1646v2EthPortSwFPppOEIpV6AddressesFlagsAnycast OBJECT-TYPE
   SYNTAX      INTEGER
               {
               no (0),
               yes (1)
               }
   MAX-ACCESS  read-only
   STATUS      current
   DESCRIPTION
      "Path: swPort.status.pppoEClient.ipV6.addresses.flags.anycast

       Possibilities:
               no   (0)
               yes   (1)"
   ::= {sr1646v2EthPortSwFPppOEIpV6AddressesEntry 84017152}

sr1646v2EthPortSwFPppOEIpV6AddressesTimersValidLifeTime OBJECT-TYPE
   SYNTAX      TimeTicks
   MAX-ACCESS  read-only
   STATUS      current
   DESCRIPTION
      "Path: swPort.status.pppoEClient.ipV6.addresses.timers.validLifeTime

       Time in centi-second."
   ::= {sr1646v2EthPortSwFPppOEIpV6AddressesEntry 100794368}

sr1646v2EthPortSwFPppOEIpV6AddressesTimersPrefLifeTime OBJECT-TYPE
   SYNTAX      TimeTicks
   MAX-ACCESS  read-only
   STATUS      current
   DESCRIPTION
      "Path: swPort.status.pppoEClient.ipV6.addresses.timers.prefLifeTime

       Time in centi-second."
   ::= {sr1646v2EthPortSwFPppOEIpV6AddressesEntry 100728832}


sr1646v2EthPortSwFDot1x OBJECT IDENTIFIER ::= {sr1646v2EthPortSwF 190}

sr1646v2EthPortSwFDot1xSSCTable OBJECT-TYPE
   SYNTAX      SEQUENCE OF Sr1646v2EthPortSwFDot1xEntry
   MAX-ACCESS  not-accessible
   STATUS      current
   DESCRIPTION
      "Ethernet Switch VLAN Table"
   ::= {sr1646v2EthPortSwFDot1x 1}

sr1646v2EthPortSwFDot1xEntry OBJECT-TYPE
   SYNTAX      Sr1646v2EthPortSwFDot1xEntry
   MAX-ACCESS  not-accessible
   STATUS      current
   DESCRIPTION
      ""
   INDEX      { sr1646v2EthPortSwFDot1xGlobalIx,
                sr1646v2EthPortSwFDot1xTableIx }
   ::= {sr1646v2EthPortSwFDot1xSSCTable 1}

Sr1646v2EthPortSwFDot1xEntry ::=
   SEQUENCE
      {
      sr1646v2EthPortSwFDot1xGlobalIx
         GlobalIndex,
      sr1646v2EthPortSwFDot1xTableIx
         TableIndex,
      sr1646v2EthPortSwFDot1xRemote
         OCTET STRING,
      sr1646v2EthPortSwFDot1xAuthorized
         INTEGER,
      sr1646v2EthPortSwFDot1xAuthenticator
         INTEGER,
      sr1646v2EthPortSwFDot1xBackEnd
         INTEGER,
      sr1646v2EthPortSwFDot1xRetries
         Integer32,
      sr1646v2EthPortSwFDot1xReAuthTime
         TimeTicks,
      sr1646v2EthPortSwFDot1xHoldTime
         TimeTicks
      }

sr1646v2EthPortSwFDot1xGlobalIx OBJECT-TYPE
   SYNTAX      GlobalIndex
   MAX-ACCESS  not-accessible
   STATUS      current
   DESCRIPTION
      "The value of the tlsCntTreeGlobalIndex of the MANAGED OBJECT."
   ::= {sr1646v2EthPortSwFDot1xEntry 10}

sr1646v2EthPortSwFDot1xTableIx OBJECT-TYPE
   SYNTAX      TableIndex
   MAX-ACCESS  not-accessible
   STATUS      current
   DESCRIPTION
      ""
   ::= {sr1646v2EthPortSwFDot1xEntry 11}

sr1646v2EthPortSwFDot1xRemote OBJECT-TYPE
   SYNTAX      OCTET STRING
   MAX-ACCESS  read-only
   STATUS      current
   DESCRIPTION
      "Path: swPort.status.dot1x.remote

       MAC address."
   ::= {sr1646v2EthPortSwFDot1xEntry 16777216}

sr1646v2EthPortSwFDot1xAuthorized OBJECT-TYPE
   SYNTAX      INTEGER
               {
               no (0),
               yes (1)
               }
   MAX-ACCESS  read-only
   STATUS      current
   DESCRIPTION
      "Path: swPort.status.dot1x.authorized

       Possibilities:
               no   (0)
               yes   (1)"
   ::= {sr1646v2EthPortSwFDot1xEntry 33554432}

sr1646v2EthPortSwFDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: swPort.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2EthPortSwFDot1xEntry 50331648}

sr1646v2EthPortSwFDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: swPort.status.dot1x.backEnd

       Possibilities:
               preInit   (0)
               initialize   (1)
               idle   (2)
               request   (3)
               response   (4)
               success   (5)
               failure   (6)
               radiusTimeout   (7)
               timeout   (8)"
   ::= {sr1646v2EthPortSwFDot1xEntry 67108864}

sr1646v2EthPortSwFDot1xRetries OBJECT-TYPE
   SYNTAX      Integer32
   MAX-ACCESS  read-only
   STATUS      current
   DESCRIPTION
      "Path: swPort.status.dot1x.retries"
   ::= {sr1646v2EthPortSwFDot1xEntry 83886080}

sr1646v2EthPortSwFDot1xReAuthTime OBJECT-TYPE
   SYNTAX      TimeTicks
   MAX-ACCESS  read-only
   STATUS      current
   DESCRIPTION
      "Path: swPort.status.dot1x.reAuthTime

       Time in centi-second."
   ::= {sr1646v2EthPortSwFDot1xEntry 100663296}

sr1646v2EthPortSwFDot1xHoldTime OBJECT-TYPE
   SYNTAX      TimeTicks
   MAX-ACCESS  read-only
   STATUS      current
   DESCRIPTION
      "Path: swPort.status.dot1x.holdTime

       Time in centi-second."
   ::= {sr1646v2EthPortSwFDot1xEntry 117440512}


sr1646v2EthPortSwFIpV6 OBJECT IDENTIFIER ::= {sr1646v2EthPortSwF 17}

sr1646v2EthPortSwFIpV6SSCTable OBJECT-TYPE
   SYNTAX      SEQUENCE OF Sr1646v2EthPortSwFIpV6Entry
   MAX-ACCESS  not-accessible
   STATUS      current
   DESCRIPTION
      "IPv6 interface config parameters"
   ::= {sr1646v2EthPortSwFIpV6 1}

sr1646v2EthPortSwFIpV6Entry OBJECT-TYPE
   SYNTAX      Sr1646v2EthPortSwFIpV6Entry
   MAX-ACCESS  not-accessible
   STATUS      current
   DESCRIPTION
      ""
   INDEX      { sr1646v2EthPortSwFIpV6GlobalIx }
   ::= {sr1646v2EthPortSwFIpV6SSCTable 1}

Sr1646v2EthPortSwFIpV6Entry ::=
   SEQUENCE
      {
      sr1646v2EthPortSwFIpV6GlobalIx
         GlobalIndex,
      sr1646v2EthPortSwFIpV6State
         INTEGER,
      sr1646v2EthPortSwFIpV6InterfaceId
         OCTET STRING,
      sr1646v2EthPortSwFIpV6LinkMtu
         Integer32,
      sr1646v2EthPortSwFIpV6HopLimit
         Integer32,
      sr1646v2EthPortSwFIpV6DhcpIaid
         Counter32,
      sr1646v2EthPortSwFIpV6RaRcvOption
         Integer32
      }

sr1646v2EthPortSwFIpV6GlobalIx OBJECT-TYPE
   SYNTAX      GlobalIndex
   MAX-ACCESS  not-accessible
   STATUS      current
   DESCRIPTION
      "The value of the tlsCntTreeGlobalIndex of the MANAGED OBJECT."
   ::= {sr1646v2EthPortSwFIpV6Entry 10}

sr1646v2EthPortSwFIpV6State OBJECT-TYPE
   SYNTAX      INTEGER
               {
               disabled (0),
               enabled (1)
               }
   MAX-ACCESS  read-only
   STATUS      current
   DESCRIPTION
      "Path: swPort.status.ipV6.state

       Possibilities:
               disabled   (0)
               enabled   (1)"
   ::= {sr1646v2EthPortSwFIpV6Entry 16777216}

sr1646v2EthPortSwFIpV6InterfaceId OBJECT-TYPE
   SYNTAX      OCTET STRING
   MAX-ACCESS  read-only
   STATUS      current
   DESCRIPTION
      "Path: swPort.status.ipV6.interfaceId"
   ::= {sr1646v2EthPortSwFIpV6Entry 33554432}

sr1646v2EthPortSwFIpV6LinkMtu OBJECT-TYPE
   SYNTAX      Integer32
   MAX-ACCESS  read-only
   STATUS      current
   DESCRIPTION
      "Path: swPort.status.ipV6.linkMtu"
   ::= {sr1646v2EthPortSwFIpV6Entry 67108864}

sr1646v2EthPortSwFIpV6HopLimit OBJECT-TYPE
   SYNTAX      Integer32
   MAX-ACCESS  read-only
   STATUS      current
   DESCRIPTION
      "Path: swPort.status.ipV6.hopLimit"
   ::= {sr1646v2EthPortSwFIpV6Entry 83886080}

sr1646v2EthPortSwFIpV6DhcpIaid OBJECT-TYPE
   SYNTAX      Counter32
   MAX-ACCESS  read-only
   STATUS      current
   DESCRIPTION
      "Path: swPort.status.ipV6.dhcp.iaid

       32 bit unsigned wrappable counter."
   ::= {sr1646v2EthPortSwFIpV6Entry 100728832}

sr1646v2EthPortSwFIpV6RaRcvOption OBJECT-TYPE
   SYNTAX      Integer32
   MAX-ACCESS  read-only
   STATUS      current
   DESCRIPTION
      "Path: swPort.status.ipV6.raRcvOption

       Bit meanings:
               bit 0 = linkMtu,
               bit 1 = srcLinkLayer,
               bit 2 = prefixInfo,
               bit 3 = rdnss,
               bit 4 = dnssl"
   ::= {sr1646v2EthPortSwFIpV6Entry 117440512}

sr1646v2EthPortSwFIpV6Addresses OBJECT-TYPE
   SYNTAX      SEQUENCE OF Sr1646v2EthPortSwFIpV6AddressesEntry
   MAX-ACCESS  not-accessible
   STATUS      current
   DESCRIPTION
      ""
   ::= {sr1646v2EthPortSwFIpV6 50331648}

sr1646v2EthPortSwFIpV6AddressesEntry OBJECT-TYPE
   SYNTAX      Sr1646v2EthPortSwFIpV6AddressesEntry
   MAX-ACCESS  not-accessible
   STATUS      current
   DESCRIPTION
      ""
   INDEX      { sr1646v2EthPortSwFIpV6AddressesGlobalIx,
                sr1646v2EthPortSwFIpV6AddressesTableIx }
   ::= {sr1646v2EthPortSwFIpV6Addresses 1}

Sr1646v2EthPortSwFIpV6AddressesEntry ::=
   SEQUENCE
      {
      sr1646v2EthPortSwFIpV6AddressesGlobalIx
         GlobalIndex,
      sr1646v2EthPortSwFIpV6AddressesTableIx
         TableIndex,
      sr1646v2EthPortSwFIpV6AddressesAddress
         Ipv6Address,
      sr1646v2EthPortSwFIpV6AddressesPrefixLength
         Integer32,
      sr1646v2EthPortSwFIpV6AddressesStatus
         INTEGER,
      sr1646v2EthPortSwFIpV6AddressesOrigin
         INTEGER,
      sr1646v2EthPortSwFIpV6AddressesFlagsInterfaceId
         INTEGER,
      sr1646v2EthPortSwFIpV6AddressesFlagsAnycast
         INTEGER,
      sr1646v2EthPortSwFIpV6AddressesTimersValidLifeTime
         TimeTicks,
      sr1646v2EthPortSwFIpV6AddressesTimersPrefLifeTime
         TimeTicks
      }

sr1646v2EthPortSwFIpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwFIpV6AddressesEntry 10}

sr1646v2EthPortSwFIpV6AddressesTableIx OBJECT-TYPE
   SYNTAX      TableIndex
   MAX-ACCESS  not-accessible
   STATUS      current
   DESCRIPTION
      ""
   ::= {sr1646v2EthPortSwFIpV6AddressesEntry 11}

sr1646v2EthPortSwFIpV6AddressesAddress OBJECT-TYPE
   SYNTAX      Ipv6Address
   MAX-ACCESS  read-only
   STATUS      current
   DESCRIPTION
      "Path: swPort.status.ipV6.addresses.address

       ipv6 address"
   ::= {sr1646v2EthPortSwFIpV6AddressesEntry 16777216}

sr1646v2EthPortSwFIpV6AddressesPrefixLength OBJECT-TYPE
   SYNTAX      Integer32
   MAX-ACCESS  read-only
   STATUS      current
   DESCRIPTION
      "Path: swPort.status.ipV6.addresses.prefixLength"
   ::= {sr1646v2EthPortSwFIpV6AddressesEntry 33554432}

sr1646v2EthPortSwFIpV6AddressesStatus OBJECT-TYPE
   SYNTAX      INTEGER
               {
               invalid (0),
               tentative (1),
               deprecated (2),
               preferred (3)
               }
   MAX-ACCESS  read-only
   STATUS      current
   DESCRIPTION
      "Path: swPort.status.ipV6.addresses.status

       Possibilities:
               invalid   (0)
               tentative   (1)
               deprecated   (2)
               preferred   (3)"
   ::= {sr1646v2EthPortSwFIpV6AddressesEntry 50331648}

sr1646v2EthPortSwFIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.ipV6.addresses.origin

       Possibilities:
               unknown   (0)
               manual   (1)
               generalPrefix   (2)
               statelessAuto   (3)
               statefullAuto   (4)"
   ::= {sr1646v2EthPortSwFIpV6AddressesEntry 67108864}

sr1646v2EthPortSwFIpV6AddressesFlagsInterfaceId OBJECT-TYPE
   SYNTAX      INTEGER
               {
               no (0),
               yes (1)
               }
   MAX-ACCESS  read-only
   STATUS      current
   DESCRIPTION
      "Path: swPort.status.ipV6.addresses.flags.interfaceId

       Possibilities:
               no   (0)
               yes   (1)"
   ::= {sr1646v2EthPortSwFIpV6AddressesEntry 83951616}

sr1646v2EthPortSwFIpV6AddressesFlagsAnycast OBJECT-TYPE
   SYNTAX      INTEGER
               {
               no (0),
               yes (1)
               }
   MAX-ACCESS  read-only
   STATUS      current
   DESCRIPTION
      "Path: swPort.status.ipV6.addresses.flags.anycast

       Possibilities:
               no   (0)
               yes   (1)"
   ::= {sr1646v2EthPortSwFIpV6AddressesEntry 84017152}

sr1646v2EthPortSwFIpV6AddressesTimersValidLifeTime OBJECT-TYPE
   SYNTAX      TimeTicks
   MAX-ACCESS  read-only
   STATUS      current
   DESCRIPTION
      "Path: swPort.status.ipV6.addresses.timers.validLifeTime

       Time in centi-second."
   ::= {sr1646v2EthPortSwFIpV6AddressesEntry 100794368}

sr1646v2EthPortSwFIpV6AddressesTimersPrefLifeTime OBJECT-TYPE
   SYNTAX      TimeTicks
   MAX-ACCESS  read-only
   STATUS      current
   DESCRIPTION
      "Path: swPort.status.ipV6.addresses.timers.prefLifeTime

       Time in centi-second."
   ::= {sr1646v2EthPortSwFIpV6AddressesEntry 100728832}


sr1646v2EthPortSwFSnmpIndex OBJECT IDENTIFIER ::= {sr1646v2EthPortSwF 269}

sr1646v2EthPortSwFSnmpIndexTable OBJECT-TYPE
   SYNTAX      SEQUENCE OF Sr1646v2EthPortSwFSnmpIndexEntry
   MAX-ACCESS  not-accessible
   STATUS      current
   DESCRIPTION
      "SNMP index assigned to this object"
   ::= {sr1646v2EthPortSwFSnmpIndex 1}

sr1646v2EthPortSwFSnmpIndexEntry OBJECT-TYPE
   SYNTAX      Sr1646v2EthPortSwFSnmpIndexEntry
   MAX-ACCESS  not-accessible
   STATUS      current
   DESCRIPTION
      ""
   INDEX      { sr1646v2EthPortSwFSnmpIndexGlobalIx }
   ::= {sr1646v2EthPortSwFSnmpIndexTable 1}

Sr1646v2EthPortSwFSnmpIndexEntry ::=
   SEQUENCE
      {
      sr1646v2EthPortSwFSnmpIndexGlobalIx
         GlobalIndex,
      sr1646v2EthPortSwFSnmpIndexValue
         Integer32
      }

sr1646v2EthPortSwFSnmpIndexGlobalIx OBJECT-TYPE
   SYNTAX      GlobalIndex
   MAX-ACCESS  not-accessible
   STATUS      current
   DESCRIPTION
      "The value of the tlsCntTreeGlobalIndex of the MANAGED OBJECT."
   ::= {sr1646v2EthPortSwFSnmpIndexEntry 10}

sr1646v2EthPortSwFSnmpIndexValue OBJECT-TYPE
   SYNTAX      Integer32
   MAX-ACCESS  read-only
   STATUS      current
   DESCRIPTION
      "Path: swPort.status.snmpIndex"
   ::= {sr1646v2EthPortSwFSnmpIndexEntry 2147483648}


sr1646v2EthPortSwFLst OBJECT IDENTIFIER ::= {sr1646v2EthPortSwF 18}

sr1646v2EthPortSwFLstSSCTable OBJECT-TYPE
   SYNTAX      SEQUENCE OF Sr1646v2EthPortSwFLstEntry
   MAX-ACCESS  not-accessible
   STATUS      current
   DESCRIPTION
      ""
   ::= {sr1646v2EthPortSwFLst 1}

sr1646v2EthPortSwFLstEntry OBJECT-TYPE
   SYNTAX      Sr1646v2EthPortSwFLstEntry
   MAX-ACCESS  not-accessible
   STATUS      current
   DESCRIPTION
      ""
   INDEX      { sr1646v2EthPortSwFLstGlobalIx }
   ::= {sr1646v2EthPortSwFLstSSCTable 1}

Sr1646v2EthPortSwFLstEntry ::=
   SEQUENCE
      {
      sr1646v2EthPortSwFLstGlobalIx
         GlobalIndex,
      sr1646v2EthPortSwFLstTrackedInterface
         DisplayString,
      sr1646v2EthPortSwFLstIfOperStatus
         INTEGER
      }

sr1646v2EthPortSwFLstGlobalIx OBJECT-TYPE
   SYNTAX      GlobalIndex
   MAX-ACCESS  not-accessible
   STATUS      current
   DESCRIPTION
      "The value of the tlsCntTreeGlobalIndex of the MANAGED OBJECT."
   ::= {sr1646v2EthPortSwFLstEntry 10}

sr1646v2EthPortSwFLstTrackedInterface OBJECT-TYPE
   SYNTAX      DisplayString
   MAX-ACCESS  read-only
   STATUS      current
   DESCRIPTION
      "Path: swPort.status.linkStateTracking.trackedInterface"
   ::= {sr1646v2EthPortSwFLstEntry 16777216}

sr1646v2EthPortSwFLstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: swPort.status.linkStateTracking.ifOperStatus

       Possibilities:
               up   (1)
               down   (2)
               testing   (3)
               unknown   (4)
               dormant   (5)
               notPresent   (6)
               lowerLayerDown   (7)
                  (255)"
   ::= {sr1646v2EthPortSwFLstEntry 50331648}


sr1646v2EthPortSwFHwPorts OBJECT IDENTIFIER ::= {sr1646v2EthPortSwF 270}

sr1646v2EthPortSwFHwPortsSSCTable OBJECT-TYPE
   SYNTAX      SEQUENCE OF Sr1646v2EthPortSwFHwPortsEntry
   MAX-ACCESS  not-accessible
   STATUS      current
   DESCRIPTION
      ""
   ::= {sr1646v2EthPortSwFHwPorts 1}

sr1646v2EthPortSwFHwPortsEntry OBJECT-TYPE
   SYNTAX      Sr1646v2EthPortSwFHwPortsEntry
   MAX-ACCESS  not-accessible
   STATUS      current
   DESCRIPTION
      ""
   INDEX      { sr1646v2EthPortSwFHwPortsGlobalIx,
                sr1646v2EthPortSwFHwPortsTableIx }
   ::= {sr1646v2EthPortSwFHwPortsSSCTable 1}

Sr1646v2EthPortSwFHwPortsEntry ::=
   SEQUENCE
      {
      sr1646v2EthPortSwFHwPortsGlobalIx
         GlobalIndex,
      sr1646v2EthPortSwFHwPortsTableIx
         TableIndex,
      sr1646v2EthPortSwFHwPortsHwPort
         INTEGER,
      sr1646v2EthPortSwFHwPortsStatus
         INTEGER
      }

sr1646v2EthPortSwFHwPortsGlobalIx OBJECT-TYPE
   SYNTAX      GlobalIndex
   MAX-ACCESS  not-accessible
   STATUS      current
   DESCRIPTION
      "The value of the tlsCntTreeGlobalIndex of the MANAGED OBJECT."
   ::= {sr1646v2EthPortSwFHwPortsEntry 10}

sr1646v2EthPortSwFHwPortsTableIx OBJECT-TYPE
   SYNTAX      TableIndex
   MAX-ACCESS  not-accessible
   STATUS      current
   DESCRIPTION
      ""
   ::= {sr1646v2EthPortSwFHwPortsEntry 11}

sr1646v2EthPortSwFHwPortsHwPort OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (65535)
               }
   MAX-ACCESS  read-only
   STATUS      current
   DESCRIPTION
      "Path: swPort.status.hwPorts.hwPort

       Possibilities:
               hwPort_1   (1)
               hwPort_2   (2)
               hwPort_3   (3)
               hwPort_4   (4)
               hwPort_5   (5)
               hwPort_6   (6)
               hwPort_7   (7)
               hwPort_8   (8)
               hwPort_LocalPort   (65535)"
   ::= {sr1646v2EthPortSwFHwPortsEntry 16777216}

sr1646v2EthPortSwFHwPortsStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.hwPorts.status

       Possibilities:
               up   (1)
               down   (2)
               testing   (3)
               unknown   (4)
               dormant   (5)
               notPresent   (6)
               lowerLayerDown   (7)"
   ::= {sr1646v2EthPortSwFHwPortsEntry 33554432}



pr1646v2EthPortSwF OBJECT IDENTIFIER ::= {r1646v2EthPortSwF 12}


pr1646v2EthPortSwFInOctets OBJECT IDENTIFIER ::= {pr1646v2EthPortSwF 109}

pr1646v2EthPortSwFInOctetsTable OBJECT-TYPE
   SYNTAX      SEQUENCE OF Pr1646v2EthPortSwFInOctetsEntry
   MAX-ACCESS  not-accessible
   STATUS      current
   DESCRIPTION
      "ifInOctets"
   ::= {pr1646v2EthPortSwFInOctets 1}

pr1646v2EthPortSwFInOctetsEntry OBJECT-TYPE
   SYNTAX      Pr1646v2EthPortSwFInOctetsEntry
   MAX-ACCESS  not-accessible
   STATUS      current
   DESCRIPTION
      ""
   INDEX      { pr1646v2EthPortSwFInOctetsGlobalIx }
   ::= {pr1646v2EthPortSwFInOctetsTable 1}

Pr1646v2EthPortSwFInOctetsEntry ::=
   SEQUENCE
      {
      pr1646v2EthPortSwFInOctetsGlobalIx
         GlobalIndex,
      pr1646v2EthPortSwFInOctetsValue
         Counter64
      }

pr1646v2EthPortSwFInOctetsGlobalIx OBJECT-TYPE
   SYNTAX      GlobalIndex
   MAX-ACCESS  not-accessible
   STATUS      current
   DESCRIPTION
      "The value of the tlsCntTreeGlobalIndex of the MANAGED OBJECT."
   ::= {pr1646v2EthPortSwFInOctetsEntry 10}

pr1646v2EthPortSwFInOctetsValue OBJECT-TYPE
   SYNTAX      Counter64
   MAX-ACCESS  read-only
   STATUS      current
   DESCRIPTION
      "Path: swPort.performance.ifInOctets

       64 bit unsigned wrappable counter."
   ::= {pr1646v2EthPortSwFInOctetsEntry 2147483648}


pr1646v2EthPortSwFInUcast OBJECT IDENTIFIER ::= {pr1646v2EthPortSwF 110}

pr1646v2EthPortSwFInUcastTable OBJECT-TYPE
   SYNTAX      SEQUENCE OF Pr1646v2EthPortSwFInUcastEntry
   MAX-ACCESS  not-accessible
   STATUS      current
   DESCRIPTION
      "ifInUcastPkts"
   ::= {pr1646v2EthPortSwFInUcast 1}

pr1646v2EthPortSwFInUcastEntry OBJECT-TYPE
   SYNTAX      Pr1646v2EthPortSwFInUcastEntry
   MAX-ACCESS  not-accessible
   STATUS      current
   DESCRIPTION
      ""
   INDEX      { pr1646v2EthPortSwFInUcastGlobalIx }
   ::= {pr1646v2EthPortSwFInUcastTable 1}

Pr1646v2EthPortSwFInUcastEntry ::=
   SEQUENCE
      {
      pr1646v2EthPortSwFInUcastGlobalIx
         GlobalIndex,
      pr1646v2EthPortSwFInUcastValue
         Counter64
      }

pr1646v2EthPortSwFInUcastGlobalIx OBJECT-TYPE
   SYNTAX      GlobalIndex
   MAX-ACCESS  not-accessible
   STATUS      current
   DESCRIPTION
      "The value of the tlsCntTreeGlobalIndex of the MANAGED OBJECT."
   ::= {pr1646v2EthPortSwFInUcastEntry 10}

pr1646v2EthPortSwFInUcastValue OBJECT-TYPE
   SYNTAX      Counter64
   MAX-ACCESS  read-only
   STATUS      current
   DESCRIPTION
      "Path: swPort.performance.ifInUcastPkts

       64 bit unsigned wrappable counter."
   ::= {pr1646v2EthPortSwFInUcastEntry 2147483648}


pr1646v2EthPortSwFInNUcastPkts OBJECT IDENTIFIER ::= {pr1646v2EthPortSwF 111}

pr1646v2EthPortSwFInNUcastPktsTable OBJECT-TYPE
   SYNTAX      SEQUENCE OF Pr1646v2EthPortSwFInNUcastPktsEntry
   MAX-ACCESS  not-accessible
   STATUS      current
   DESCRIPTION
      "ifInNUcastPkts"
   ::= {pr1646v2EthPortSwFInNUcastPkts 1}

pr1646v2EthPortSwFInNUcastPktsEntry OBJECT-TYPE
   SYNTAX      Pr1646v2EthPortSwFInNUcastPktsEntry
   MAX-ACCESS  not-accessible
   STATUS      current
   DESCRIPTION
      ""
   INDEX      { pr1646v2EthPortSwFInNUcastPktsGlobalIx }
   ::= {pr1646v2EthPortSwFInNUcastPktsTable 1}

Pr1646v2EthPortSwFInNUcastPktsEntry ::=
   SEQUENCE
      {
      pr1646v2EthPortSwFInNUcastPktsGlobalIx
         GlobalIndex,
      pr1646v2EthPortSwFInNUcastPktsValue
         Counter64
      }

pr1646v2EthPortSwFInNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFInNUcastPktsEntry 10}

pr1646v2EthPortSwFInNUcastPktsValue OBJECT-TYPE
   SYNTAX      Counter64
   MAX-ACCESS  read-only
   STATUS      current
   DESCRIPTION
      "Path: swPort.performance.ifInNUcastPkts

       64 bit unsigned wrappable counter."
   ::= {pr1646v2EthPortSwFInNUcastPktsEntry 2147483648}


pr1646v2EthPortSwFInBcastPkts OBJECT IDENTIFIER ::= {pr1646v2EthPortSwF 211}

pr1646v2EthPortSwFInBcastPktsTable OBJECT-TYPE
   SYNTAX      SEQUENCE OF Pr1646v2EthPortSwFInBcastPktsEntry
   MAX-ACCESS  not-accessible
   STATUS      current
   DESCRIPTION
      "ifInBcastPkts"
   ::= {pr1646v2EthPortSwFInBcastPkts 1}

pr1646v2EthPortSwFInBcastPktsEntry OBJECT-TYPE
   SYNTAX      Pr1646v2EthPortSwFInBcastPktsEntry
   MAX-ACCESS  not-accessible
   STATUS      current
   DESCRIPTION
      ""
   INDEX      { pr1646v2EthPortSwFInBcastPktsGlobalIx }
   ::= {pr1646v2EthPortSwFInBcastPktsTable 1}

Pr1646v2EthPortSwFInBcastPktsEntry ::=
   SEQUENCE
      {
      pr1646v2EthPortSwFInBcastPktsGlobalIx
         GlobalIndex,
      pr1646v2EthPortSwFInBcastPktsValue
         Counter64
      }

pr1646v2EthPortSwFInBcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFInBcastPktsEntry 10}

pr1646v2EthPortSwFInBcastPktsValue OBJECT-TYPE
   SYNTAX      Counter64
   MAX-ACCESS  read-only
   STATUS      current
   DESCRIPTION
      "Path: swPort.performance.ifInBcastPkts

       64 bit unsigned wrappable counter."
   ::= {pr1646v2EthPortSwFInBcastPktsEntry 2147483648}


pr1646v2EthPortSwFInMcastPkts OBJECT IDENTIFIER ::= {pr1646v2EthPortSwF 221}

pr1646v2EthPortSwFInMcastPktsTable OBJECT-TYPE
   SYNTAX      SEQUENCE OF Pr1646v2EthPortSwFInMcastPktsEntry
   MAX-ACCESS  not-accessible
   STATUS      current
   DESCRIPTION
      "ifInNUcastPkts"
   ::= {pr1646v2EthPortSwFInMcastPkts 1}

pr1646v2EthPortSwFInMcastPktsEntry OBJECT-TYPE
   SYNTAX      Pr1646v2EthPortSwFInMcastPktsEntry
   MAX-ACCESS  not-accessible
   STATUS      current
   DESCRIPTION
      ""
   INDEX      { pr1646v2EthPortSwFInMcastPktsGlobalIx }
   ::= {pr1646v2EthPortSwFInMcastPktsTable 1}

Pr1646v2EthPortSwFInMcastPktsEntry ::=
   SEQUENCE
      {
      pr1646v2EthPortSwFInMcastPktsGlobalIx
         GlobalIndex,
      pr1646v2EthPortSwFInMcastPktsValue
         Counter64
      }

pr1646v2EthPortSwFInMcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFInMcastPktsEntry 10}

pr1646v2EthPortSwFInMcastPktsValue OBJECT-TYPE
   SYNTAX      Counter64
   MAX-ACCESS  read-only
   STATUS      current
   DESCRIPTION
      "Path: swPort.performance.ifInMcastPkts

       64 bit unsigned wrappable counter."
   ::= {pr1646v2EthPortSwFInMcastPktsEntry 2147483648}


pr1646v2EthPortSwFInDiscards OBJECT IDENTIFIER ::= {pr1646v2EthPortSwF 112}

pr1646v2EthPortSwFInDiscardsTable OBJECT-TYPE
   SYNTAX      SEQUENCE OF Pr1646v2EthPortSwFInDiscardsEntry
   MAX-ACCESS  not-accessible
   STATUS      current
   DESCRIPTION
      "ifInDiscards"
   ::= {pr1646v2EthPortSwFInDiscards 1}

pr1646v2EthPortSwFInDiscardsEntry OBJECT-TYPE
   SYNTAX      Pr1646v2EthPortSwFInDiscardsEntry
   MAX-ACCESS  not-accessible
   STATUS      current
   DESCRIPTION
      ""
   INDEX      { pr1646v2EthPortSwFInDiscardsGlobalIx }
   ::= {pr1646v2EthPortSwFInDiscardsTable 1}

Pr1646v2EthPortSwFInDiscardsEntry ::=
   SEQUENCE
      {
      pr1646v2EthPortSwFInDiscardsGlobalIx
         GlobalIndex,
      pr1646v2EthPortSwFInDiscardsValue
         Counter64
      }

pr1646v2EthPortSwFInDiscardsGlobalIx OBJECT-TYPE
   SYNTAX      GlobalIndex
   MAX-ACCESS  not-accessible
   STATUS      current
   DESCRIPTION
      "The value of the tlsCntTreeGlobalIndex of the MANAGED OBJECT."
   ::= {pr1646v2EthPortSwFInDiscardsEntry 10}

pr1646v2EthPortSwFInDiscardsValue OBJECT-TYPE
   SYNTAX      Counter64
   MAX-ACCESS  read-only
   STATUS      current
   DESCRIPTION
      "Path: swPort.performance.ifInDiscards

       64 bit unsigned wrappable counter."
   ::= {pr1646v2EthPortSwFInDiscardsEntry 2147483648}


pr1646v2EthPortSwFInErrors OBJECT IDENTIFIER ::= {pr1646v2EthPortSwF 113}

pr1646v2EthPortSwFInErrorsTable OBJECT-TYPE
   SYNTAX      SEQUENCE OF Pr1646v2EthPortSwFInErrorsEntry
   MAX-ACCESS  not-accessible
   STATUS      current
   DESCRIPTION
      "ifInErrors"
   ::= {pr1646v2EthPortSwFInErrors 1}

pr1646v2EthPortSwFInErrorsEntry OBJECT-TYPE
   SYNTAX      Pr1646v2EthPortSwFInErrorsEntry
   MAX-ACCESS  not-accessible
   STATUS      current
   DESCRIPTION
      ""
   INDEX      { pr1646v2EthPortSwFInErrorsGlobalIx }
   ::= {pr1646v2EthPortSwFInErrorsTable 1}

Pr1646v2EthPortSwFInErrorsEntry ::=
   SEQUENCE
      {
      pr1646v2EthPortSwFInErrorsGlobalIx
         GlobalIndex,
      pr1646v2EthPortSwFInErrorsValue
         Counter64
      }

pr1646v2EthPortSwFInErrorsGlobalIx OBJECT-TYPE
   SYNTAX      GlobalIndex
   MAX-ACCESS  not-accessible
   STATUS      current
   DESCRIPTION
      "The value of the tlsCntTreeGlobalIndex of the MANAGED OBJECT."
   ::= {pr1646v2EthPortSwFInErrorsEntry 10}

pr1646v2EthPortSwFInErrorsValue OBJECT-TYPE
   SYNTAX      Counter64
   MAX-ACCESS  read-only
   STATUS      current
   DESCRIPTION
      "Path: swPort.performance.ifInErrors

       64 bit unsigned wrappable counter."
   ::= {pr1646v2EthPortSwFInErrorsEntry 2147483648}


pr1646v2EthPortSwFInUnknownProtos OBJECT IDENTIFIER ::= {pr1646v2EthPortSwF 114}

pr1646v2EthPortSwFInUnknownProtosTable OBJECT-TYPE
   SYNTAX      SEQUENCE OF Pr1646v2EthPortSwFInUnknownProtosEntry
   MAX-ACCESS  not-accessible
   STATUS      current
   DESCRIPTION
      "ifInUnknownprotos"
   ::= {pr1646v2EthPortSwFInUnknownProtos 1}

pr1646v2EthPortSwFInUnknownProtosEntry OBJECT-TYPE
   SYNTAX      Pr1646v2EthPortSwFInUnknownProtosEntry
   MAX-ACCESS  not-accessible
   STATUS      current
   DESCRIPTION
      ""
   INDEX      { pr1646v2EthPortSwFInUnknownProtosGlobalIx }
   ::= {pr1646v2EthPortSwFInUnknownProtosTable 1}

Pr1646v2EthPortSwFInUnknownProtosEntry ::=
   SEQUENCE
      {
      pr1646v2EthPortSwFInUnknownProtosGlobalIx
         GlobalIndex,
      pr1646v2EthPortSwFInUnknownProtosValue
         Counter64
      }

pr1646v2EthPortSwFInUnknownProtosGlobalIx OBJECT-TYPE
   SYNTAX      GlobalIndex
   MAX-ACCESS  not-accessible
   STATUS      current
   DESCRIPTION
      "The value of the tlsCntTreeGlobalIndex of the MANAGED OBJECT."
   ::= {pr1646v2EthPortSwFInUnknownProtosEntry 10}

pr1646v2EthPortSwFInUnknownProtosValue OBJECT-TYPE
   SYNTAX      Counter64
   MAX-ACCESS  read-only
   STATUS      current
   DESCRIPTION
      "Path: swPort.performance.ifInUnknownProtos

       64 bit unsigned wrappable counter."
   ::= {pr1646v2EthPortSwFInUnknownProtosEntry 2147483648}


pr1646v2EthPortSwFInDropEx OBJECT IDENTIFIER ::= {pr1646v2EthPortSwF 130}

pr1646v2EthPortSwFInDropExTable OBJECT-TYPE
   SYNTAX      SEQUENCE OF Pr1646v2EthPortSwFInDropExEntry
   MAX-ACCESS  not-accessible
   STATUS      current
   DESCRIPTION
      "ifInDiscards"
   ::= {pr1646v2EthPortSwFInDropEx 1}

pr1646v2EthPortSwFInDropExEntry OBJECT-TYPE
   SYNTAX      Pr1646v2EthPortSwFInDropExEntry
   MAX-ACCESS  not-accessible
   STATUS      current
   DESCRIPTION
      ""
   INDEX      { pr1646v2EthPortSwFInDropExGlobalIx }
   ::= {pr1646v2EthPortSwFInDropExTable 1}

Pr1646v2EthPortSwFInDropExEntry ::=
   SEQUENCE
      {
      pr1646v2EthPortSwFInDropExGlobalIx
         GlobalIndex,
      pr1646v2EthPortSwFInDropExValue
         Counter64
      }

pr1646v2EthPortSwFInDropExGlobalIx OBJECT-TYPE
   SYNTAX      GlobalIndex
   MAX-ACCESS  not-accessible
   STATUS      current
   DESCRIPTION
      "The value of the tlsCntTreeGlobalIndex of the MANAGED OBJECT."
   ::= {pr1646v2EthPortSwFInDropExEntry 10}

pr1646v2EthPortSwFInDropExValue OBJECT-TYPE
   SYNTAX      Counter64
   MAX-ACCESS  read-only
   STATUS      current
   DESCRIPTION
      "Path: swPort.performance.ifInDropLevelExceeded

       64 bit unsigned wrappable counter."
   ::= {pr1646v2EthPortSwFInDropExEntry 2147483648}


pr1646v2EthPortSwFInDropNoMac OBJECT IDENTIFIER ::= {pr1646v2EthPortSwF 133}

pr1646v2EthPortSwFInDropNoMacTable OBJECT-TYPE
   SYNTAX      SEQUENCE OF Pr1646v2EthPortSwFInDropNoMacEntry
   MAX-ACCESS  not-accessible
   STATUS      current
   DESCRIPTION
      "ifInDiscards"
   ::= {pr1646v2EthPortSwFInDropNoMac 1}

pr1646v2EthPortSwFInDropNoMacEntry OBJECT-TYPE
   SYNTAX      Pr1646v2EthPortSwFInDropNoMacEntry
   MAX-ACCESS  not-accessible
   STATUS      current
   DESCRIPTION
      ""
   INDEX      { pr1646v2EthPortSwFInDropNoMacGlobalIx }
   ::= {pr1646v2EthPortSwFInDropNoMacTable 1}

Pr1646v2EthPortSwFInDropNoMacEntry ::=
   SEQUENCE
      {
      pr1646v2EthPortSwFInDropNoMacGlobalIx
         GlobalIndex,
      pr1646v2EthPortSwFInDropNoMacValue
         Counter64
      }

pr1646v2EthPortSwFInDropNoMacGlobalIx OBJECT-TYPE
   SYNTAX      GlobalIndex
   MAX-ACCESS  not-accessible
   STATUS      current
   DESCRIPTION
      "The value of the tlsCntTreeGlobalIndex of the MANAGED OBJECT."
   ::= {pr1646v2EthPortSwFInDropNoMacEntry 10}

pr1646v2EthPortSwFInDropNoMacValue OBJECT-TYPE
   SYNTAX      Counter64
   MAX-ACCESS  read-only
   STATUS      current
   DESCRIPTION
      "Path: swPort.performance.ifInDiscardsNoMacFit

       64 bit unsigned wrappable counter."
   ::= {pr1646v2EthPortSwFInDropNoMacEntry 2147483648}


pr1646v2EthPortSwFInDropNUCast OBJECT IDENTIFIER ::= {pr1646v2EthPortSwF 136}

pr1646v2EthPortSwFInDropNUCastTable OBJECT-TYPE
   SYNTAX      SEQUENCE OF Pr1646v2EthPortSwFInDropNUCastEntry
   MAX-ACCESS  not-accessible
   STATUS      current
   DESCRIPTION
      "ifInDiscards"
   ::= {pr1646v2EthPortSwFInDropNUCast 1}

pr1646v2EthPortSwFInDropNUCastEntry OBJECT-TYPE
   SYNTAX      Pr1646v2EthPortSwFInDropNUCastEntry
   MAX-ACCESS  not-accessible
   STATUS      current
   DESCRIPTION
      ""
   INDEX      { pr1646v2EthPortSwFInDropNUCastGlobalIx }
   ::= {pr1646v2EthPortSwFInDropNUCastTable 1}

Pr1646v2EthPortSwFInDropNUCastEntry ::=
   SEQUENCE
      {
      pr1646v2EthPortSwFInDropNUCastGlobalIx
         GlobalIndex,
      pr1646v2EthPortSwFInDropNUCastValue
         Counter64
      }

pr1646v2EthPortSwFInDropNUCastGlobalIx OBJECT-TYPE
   SYNTAX      GlobalIndex
   MAX-ACCESS  not-accessible
   STATUS      current
   DESCRIPTION
      "The value of the tlsCntTreeGlobalIndex of the MANAGED OBJECT."
   ::= {pr1646v2EthPortSwFInDropNUCastEntry 10}

pr1646v2EthPortSwFInDropNUCastValue OBJECT-TYPE
   SYNTAX      Counter64
   MAX-ACCESS  read-only
   STATUS      current
   DESCRIPTION
      "Path: swPort.performance.ifInDiscardsNUCast

       64 bit unsigned wrappable counter."
   ::= {pr1646v2EthPortSwFInDropNUCastEntry 2147483648}


pr1646v2EthPortSwFInDropFilter OBJECT IDENTIFIER ::= {pr1646v2EthPortSwF 137}

pr1646v2EthPortSwFInDropFilterTable OBJECT-TYPE
   SYNTAX      SEQUENCE OF Pr1646v2EthPortSwFInDropFilterEntry
   MAX-ACCESS  not-accessible
   STATUS      current
   DESCRIPTION
      "ifInDiscards"
   ::= {pr1646v2EthPortSwFInDropFilter 1}

pr1646v2EthPortSwFInDropFilterEntry OBJECT-TYPE
   SYNTAX      Pr1646v2EthPortSwFInDropFilterEntry
   MAX-ACCESS  not-accessible
   STATUS      current
   DESCRIPTION
      ""
   INDEX      { pr1646v2EthPortSwFInDropFilterGlobalIx }
   ::= {pr1646v2EthPortSwFInDropFilterTable 1}

Pr1646v2EthPortSwFInDropFilterEntry ::=
   SEQUENCE
      {
      pr1646v2EthPortSwFInDropFilterGlobalIx
         GlobalIndex,
      pr1646v2EthPortSwFInDropFilterValue
         Counter64
      }

pr1646v2EthPortSwFInDropFilterGlobalIx OBJECT-TYPE
   SYNTAX      GlobalIndex
   MAX-ACCESS  not-accessible
   STATUS      current
   DESCRIPTION
      "The value of the tlsCntTreeGlobalIndex of the MANAGED OBJECT."
   ::= {pr1646v2EthPortSwFInDropFilterEntry 10}

pr1646v2EthPortSwFInDropFilterValue OBJECT-TYPE
   SYNTAX      Counter64
   MAX-ACCESS  read-only
   STATUS      current
   DESCRIPTION
      "Path: swPort.performance.ifInDiscardsFilter

       64 bit unsigned wrappable counter."
   ::= {pr1646v2EthPortSwFInDropFilterEntry 2147483648}


pr1646v2EthPortSwFInQueues OBJECT IDENTIFIER ::= {pr1646v2EthPortSwF 131}

pr1646v2EthPortSwFInQueuesSSCTable OBJECT-TYPE
   SYNTAX      SEQUENCE OF Pr1646v2EthPortSwFInQueuesEntry
   MAX-ACCESS  not-accessible
   STATUS      current
   DESCRIPTION
      "Queue Lengths"
   ::= {pr1646v2EthPortSwFInQueues 1}

pr1646v2EthPortSwFInQueuesEntry OBJECT-TYPE
   SYNTAX      Pr1646v2EthPortSwFInQueuesEntry
   MAX-ACCESS  not-accessible
   STATUS      current
   DESCRIPTION
      ""
   INDEX      { pr1646v2EthPortSwFInQueuesGlobalIx,
                pr1646v2EthPortSwFInQueuesTableIx }
   ::= {pr1646v2EthPortSwFInQueuesSSCTable 1}

Pr1646v2EthPortSwFInQueuesEntry ::=
   SEQUENCE
      {
      pr1646v2EthPortSwFInQueuesGlobalIx
         GlobalIndex,
      pr1646v2EthPortSwFInQueuesTableIx
         TableIndex,
      pr1646v2EthPortSwFInQueuesName
         INTEGER,
      pr1646v2EthPortSwFInQueuesLength
         Integer32,
      pr1646v2EthPortSwFInQueuesOctetLength
         Integer32,
      pr1646v2EthPortSwFInQueuesRedLength
         Integer32,
      pr1646v2EthPortSwFInQueuesPacketsTotal
         Counter64,
      pr1646v2EthPortSwFInQueuesPacketsDirectTx
         Counter64,
      pr1646v2EthPortSwFInQueuesPacketsQueued
         Counter64,
      pr1646v2EthPortSwFInQueuesPacketsDropped
         Counter64,
      pr1646v2EthPortSwFInQueuesPacketsRedDropped
         Counter64,
      pr1646v2EthPortSwFInQueuesPacketsCirTx
         Counter64,
      pr1646v2EthPortSwFInQueuesPacketsEirTx
         Counter64,
      pr1646v2EthPortSwFInQueuesPacketsViolateTx
         Counter64,
      pr1646v2EthPortSwFInQueuesOctetsTotal
         Counter64,
      pr1646v2EthPortSwFInQueuesOctetsDirectTx
         Counter64,
      pr1646v2EthPortSwFInQueuesOctetsQueued
         Counter64,
      pr1646v2EthPortSwFInQueuesOctetsDropped
         Counter64,
      pr1646v2EthPortSwFInQueuesOctetsRedDropped
         Counter64,
      pr1646v2EthPortSwFInQueuesOctetsCirTx
         Counter64,
      pr1646v2EthPortSwFInQueuesOctetsEirTx
         Counter64,
      pr1646v2EthPortSwFInQueuesOctetsViolateTx
         Counter64,
      pr1646v2EthPortSwFInQueuesOctetsBandwidth15sec
         Integer32,
      pr1646v2EthPortSwFInQueuesOctetsBandwidth30sec
         Integer32,
      pr1646v2EthPortSwFInQueuesOctetsBandwidth1min
         Integer32,
      pr1646v2EthPortSwFInQueuesOctetsBandwidth2min
         Integer32,
      pr1646v2EthPortSwFInQueuesOctetsBandwidth5min
         Integer32
      }

pr1646v2EthPortSwFInQueuesGlobalIx OBJECT-TYPE
   SYNTAX      GlobalIndex
   MAX-ACCESS  not-accessible
   STATUS      current
   DESCRIPTION
      "The value of the tlsCntTreeGlobalIndex of the MANAGED OBJECT."
   ::= {pr1646v2EthPortSwFInQueuesEntry 10}

pr1646v2EthPortSwFInQueuesTableIx OBJECT-TYPE
   SYNTAX      TableIndex
   MAX-ACCESS  not-accessible
   STATUS      current
   DESCRIPTION
      ""
   ::= {pr1646v2EthPortSwFInQueuesEntry 11}

pr1646v2EthPortSwFInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwFInQueuesEntry 16777216}

pr1646v2EthPortSwFInQueuesLength OBJECT-TYPE
   SYNTAX      Integer32
   MAX-ACCESS  read-only
   STATUS      current
   DESCRIPTION
      "Path: swPort.performance.ifInPriorityQueues.length"
   ::= {pr1646v2EthPortSwFInQueuesEntry 33554432}

pr1646v2EthPortSwFInQueuesOctetLength OBJECT-TYPE
   SYNTAX      Integer32
   MAX-ACCESS  read-only
   STATUS      current
   DESCRIPTION
      "Path: swPort.performance.ifInPriorityQueues.octetLength"
   ::= {pr1646v2EthPortSwFInQueuesEntry 150994944}

pr1646v2EthPortSwFInQueuesRedLength OBJECT-TYPE
   SYNTAX      Integer32
   MAX-ACCESS  read-only
   STATUS      current
   DESCRIPTION
      "Path: swPort.performance.ifInPriorityQueues.redLength"
   ::= {pr1646v2EthPortSwFInQueuesEntry 134217728}

pr1646v2EthPortSwFInQueuesPacketsTotal OBJECT-TYPE
   SYNTAX      Counter64
   MAX-ACCESS  read-only
   STATUS      current
   DESCRIPTION
      "Path: swPort.performance.ifInPriorityQueues.packets.total

       64 bit unsigned wrappable counter."
   ::= {pr1646v2EthPortSwFInQueuesEntry 50790400}

pr1646v2EthPortSwFInQueuesPacketsDirectTx OBJECT-TYPE
   SYNTAX      Counter64
   MAX-ACCESS  read-only
   STATUS      current
   DESCRIPTION
      "Path: swPort.performance.ifInPriorityQueues.packets.directTx

       64 bit unsigned wrappable counter."
   ::= {pr1646v2EthPortSwFInQueuesEntry 50397184}

pr1646v2EthPortSwFInQueuesPacketsQueued OBJECT-TYPE
   SYNTAX      Counter64
   MAX-ACCESS  read-only
   STATUS      current
   DESCRIPTION
      "Path: swPort.performance.ifInPriorityQueues.packets.queued

       64 bit unsigned wrappable counter."
   ::= {pr1646v2EthPortSwFInQueuesEntry 50462720}

pr1646v2EthPortSwFInQueuesPacketsDropped OBJECT-TYPE
   SYNTAX      Counter64
   MAX-ACCESS  read-only
   STATUS      current
   DESCRIPTION
      "Path: swPort.performance.ifInPriorityQueues.packets.dropped

       64 bit unsigned wrappable counter."
   ::= {pr1646v2EthPortSwFInQueuesEntry 50528256}

pr1646v2EthPortSwFInQueuesPacketsRedDropped OBJECT-TYPE
   SYNTAX      Counter64
   MAX-ACCESS  read-only
   STATUS      current
   DESCRIPTION
      "Path: swPort.performance.ifInPriorityQueues.packets.redDropped

       64 bit unsigned wrappable counter."
   ::= {pr1646v2EthPortSwFInQueuesEntry 50724864}

pr1646v2EthPortSwFInQueuesPacketsCirTx OBJECT-TYPE
   SYNTAX      Counter64
   MAX-ACCESS  read-only
   STATUS      current
   DESCRIPTION
      "Path: swPort.performance.ifInPriorityQueues.packets.cirTx

       64 bit unsigned wrappable counter."
   ::= {pr1646v2EthPortSwFInQueuesEntry 50593792}

pr1646v2EthPortSwFInQueuesPacketsEirTx OBJECT-TYPE
   SYNTAX      Counter64
   MAX-ACCESS  read-only
   STATUS      current
   DESCRIPTION
      "Path: swPort.performance.ifInPriorityQueues.packets.eirTx

       64 bit unsigned wrappable counter."
   ::= {pr1646v2EthPortSwFInQueuesEntry 50659328}

pr1646v2EthPortSwFInQueuesPacketsViolateTx OBJECT-TYPE
   SYNTAX      Counter64
   MAX-ACCESS  read-only
   STATUS      current
   DESCRIPTION
      "Path: swPort.performance.ifInPriorityQueues.packets.violateTx

       64 bit unsigned wrappable counter."
   ::= {pr1646v2EthPortSwFInQueuesEntry 50855936}

pr1646v2EthPortSwFInQueuesOctetsTotal OBJECT-TYPE
   SYNTAX      Counter64
   MAX-ACCESS  read-only
   STATUS      current
   DESCRIPTION
      "Path: swPort.performance.ifInPriorityQueues.octets.total

       64 bit unsigned wrappable counter."
   ::= {pr1646v2EthPortSwFInQueuesEntry 67567616}

pr1646v2EthPortSwFInQueuesOctetsDirectTx OBJECT-TYPE
   SYNTAX      Counter64
   MAX-ACCESS  read-only
   STATUS      current
   DESCRIPTION
      "Path: swPort.performance.ifInPriorityQueues.octets.directTx

       64 bit unsigned wrappable counter."
   ::= {pr1646v2EthPortSwFInQueuesEntry 67174400}

pr1646v2EthPortSwFInQueuesOctetsQueued OBJECT-TYPE
   SYNTAX      Counter64
   MAX-ACCESS  read-only
   STATUS      current
   DESCRIPTION
      "Path: swPort.performance.ifInPriorityQueues.octets.queued

       64 bit unsigned wrappable counter."
   ::= {pr1646v2EthPortSwFInQueuesEntry 67239936}

pr1646v2EthPortSwFInQueuesOctetsDropped OBJECT-TYPE
   SYNTAX      Counter64
   MAX-ACCESS  read-only
   STATUS      current
   DESCRIPTION
      "Path: swPort.performance.ifInPriorityQueues.octets.dropped

       64 bit unsigned wrappable counter."
   ::= {pr1646v2EthPortSwFInQueuesEntry 67305472}

pr1646v2EthPortSwFInQueuesOctetsRedDropped OBJECT-TYPE
   SYNTAX      Counter64
   MAX-ACCESS  read-only
   STATUS      current
   DESCRIPTION
      "Path: swPort.performance.ifInPriorityQueues.octets.redDropped

       64 bit unsigned wrappable counter."
   ::= {pr1646v2EthPortSwFInQueuesEntry 67502080}

pr1646v2EthPortSwFInQueuesOctetsCirTx OBJECT-TYPE
   SYNTAX      Counter64
   MAX-ACCESS  read-only
   STATUS      current
   DESCRIPTION
      "Path: swPort.performance.ifInPriorityQueues.octets.cirTx

       64 bit unsigned wrappable counter."
   ::= {pr1646v2EthPortSwFInQueuesEntry 67371008}

pr1646v2EthPortSwFInQueuesOctetsEirTx OBJECT-TYPE
   SYNTAX      Counter64
   MAX-ACCESS  read-only
   STATUS      current
   DESCRIPTION
      "Path: swPort.performance.ifInPriorityQueues.octets.eirTx

       64 bit unsigned wrappable counter."
   ::= {pr1646v2EthPortSwFInQueuesEntry 67436544}

pr1646v2EthPortSwFInQueuesOctetsViolateTx OBJECT-TYPE
   SYNTAX      Counter64
   MAX-ACCESS  read-only
   STATUS      current
   DESCRIPTION
      "Path: swPort.performance.ifInPriorityQueues.octets.violateTx

       64 bit unsigned wrappable counter."
   ::= {pr1646v2EthPortSwFInQueuesEntry 67633152}

pr1646v2EthPortSwFInQueuesOctetsBandwidth15sec OBJECT-TYPE
   SYNTAX      Integer32
   MAX-ACCESS  read-only
   STATUS      current
   DESCRIPTION
      "Path: swPort.performance.ifInPriorityQueues.octets.bandwidth.15sec

       unit name = bps
       formula = 8 * ; 8 /"
   ::= {pr1646v2EthPortSwFInQueuesEntry 70386944}

pr1646v2EthPortSwFInQueuesOctetsBandwidth30sec OBJECT-TYPE
   SYNTAX      Integer32
   MAX-ACCESS  read-only
   STATUS      current
   DESCRIPTION
      "Path: swPort.performance.ifInPriorityQueues.octets.bandwidth.30sec

       unit name = bps
       formula = 8 * ; 8 /"
   ::= {pr1646v2EthPortSwFInQueuesEntry 70388224}

pr1646v2EthPortSwFInQueuesOctetsBandwidth1min OBJECT-TYPE
   SYNTAX      Integer32
   MAX-ACCESS  read-only
   STATUS      current
   DESCRIPTION
      "Path: swPort.performance.ifInPriorityQueues.octets.bandwidth.1min

       unit name = bps
       formula = 8 * ; 8 /"
   ::= {pr1646v2EthPortSwFInQueuesEntry 70390784}

pr1646v2EthPortSwFInQueuesOctetsBandwidth2min OBJECT-TYPE
   SYNTAX      Integer32
   MAX-ACCESS  read-only
   STATUS      current
   DESCRIPTION
      "Path: swPort.performance.ifInPriorityQueues.octets.bandwidth.2min

       unit name = bps
       formula = 8 * ; 8 /"
   ::= {pr1646v2EthPortSwFInQueuesEntry 70395904}

pr1646v2EthPortSwFInQueuesOctetsBandwidth5min OBJECT-TYPE
   SYNTAX      Integer32
   MAX-ACCESS  read-only
   STATUS      current
   DESCRIPTION
      "Path: swPort.performance.ifInPriorityQueues.octets.bandwidth.5min

       unit name = bps
       formula = 8 * ; 8 /"
   ::= {pr1646v2EthPortSwFInQueuesEntry 70411264}

pr1646v2EthPortSwFInQueuesH2Performance OBJECT-TYPE
   SYNTAX      SEQUENCE OF Pr1646v2EthPortSwFInQueuesH2PerformanceEntry
   MAX-ACCESS  not-accessible
   STATUS      current
   DESCRIPTION
      ""
   ::= {pr1646v2EthPortSwFInQueues 83886080}

pr1646v2EthPortSwFInQueuesH2PerformanceEntry OBJECT-TYPE
   SYNTAX      Pr1646v2EthPortSwFInQueuesH2PerformanceEntry
   MAX-ACCESS  not-accessible
   STATUS      current
   DESCRIPTION
      ""
   INDEX      { pr1646v2EthPortSwFInQueuesH2PerformanceGlobalIx,
                pr1646v2EthPortSwFInQueuesTableIx,
                pr1646v2EthPortSwFInQueuesH2PerformanceTableIx }
   ::= {pr1646v2EthPortSwFInQueuesH2Performance 1}

Pr1646v2EthPortSwFInQueuesH2PerformanceEntry ::=
   SEQUENCE
      {
      pr1646v2EthPortSwFInQueuesH2PerformanceGlobalIx
         GlobalIndex,
      pr1646v2EthPortSwFInQueuesH2PerformanceTableIx
         TableIndex,
      pr1646v2EthPortSwFInQueuesH2PerformanceSysUpTime
         TimeTicks,
      pr1646v2EthPortSwFInQueuesH2PerformanceTotPkts
         Counter64,
      pr1646v2EthPortSwFInQueuesH2PerformanceDirTxPkts
         Counter64,
      pr1646v2EthPortSwFInQueuesH2PerformanceQdPkts
         Counter64,
      pr1646v2EthPortSwFInQueuesH2PerformanceDropPkts
         Counter64,
      pr1646v2EthPortSwFInQueuesH2PerformanceRDropPkts
         Counter64,
      pr1646v2EthPortSwFInQueuesH2PerformanceCirTxPkts
         Counter64,
      pr1646v2EthPortSwFInQueuesH2PerformanceEirTxPkts
         Counter64,
      pr1646v2EthPortSwFInQueuesH2PerformanceViolTxPkts
         Counter64,
      pr1646v2EthPortSwFInQueuesH2PerformanceTotOcts
         Counter64,
      pr1646v2EthPortSwFInQueuesH2PerformanceDirTxOcts
         Counter64,
      pr1646v2EthPortSwFInQueuesH2PerformanceQdOcts
         Counter64,
      pr1646v2EthPortSwFInQueuesH2PerformanceDropOcts
         Counter64,
      pr1646v2EthPortSwFInQueuesH2PerformanceRDropOcts
         Counter64,
      pr1646v2EthPortSwFInQueuesH2PerformanceCirTxOcts
         Counter64,
      pr1646v2EthPortSwFInQueuesH2PerformanceEirTxOcts
         Counter64,
      pr1646v2EthPortSwFInQueuesH2PerformanceViolTxOcts
         Counter64,
      pr1646v2EthPortSwFInQueuesH2PerformanceBandwidth
         Integer32
      }

pr1646v2EthPortSwFInQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFInQueuesH2PerformanceEntry 10}

pr1646v2EthPortSwFInQueuesH2PerformanceTableIx OBJECT-TYPE
   SYNTAX      TableIndex
   MAX-ACCESS  not-accessible
   STATUS      current
   DESCRIPTION
      ""
   ::= {pr1646v2EthPortSwFInQueuesH2PerformanceEntry 11}

pr1646v2EthPortSwFInQueuesH2PerformanceSysUpTime OBJECT-TYPE
   SYNTAX      TimeTicks
   MAX-ACCESS  read-only
   STATUS      current
   DESCRIPTION
      "Path: swPort.performance.ifInPriorityQueues.h2Performance.sysUpTime

       Time in centi-second."
   ::= {pr1646v2EthPortSwFInQueuesH2PerformanceEntry 16777216}

pr1646v2EthPortSwFInQueuesH2PerformanceTotPkts OBJECT-TYPE
   SYNTAX      Counter64
   MAX-ACCESS  read-only
   STATUS      current
   DESCRIPTION
      "Path: swPort.performance.ifInPriorityQueues.h2Performance.totalPkts

       64 bit unsigned wrappable counter."
   ::= {pr1646v2EthPortSwFInQueuesH2PerformanceEntry 234881024}

pr1646v2EthPortSwFInQueuesH2PerformanceDirTxPkts OBJECT-TYPE
   SYNTAX      Counter64
   MAX-ACCESS  read-only
   STATUS      current
   DESCRIPTION
      "Path: swPort.performance.ifInPriorityQueues.h2Performance.directTxPkts

       64 bit unsigned wrappable counter."
   ::= {pr1646v2EthPortSwFInQueuesH2PerformanceEntry 33554432}

pr1646v2EthPortSwFInQueuesH2PerformanceQdPkts OBJECT-TYPE
   SYNTAX      Counter64
   MAX-ACCESS  read-only
   STATUS      current
   DESCRIPTION
      "Path: swPort.performance.ifInPriorityQueues.h2Performance.queuedPkts

       64 bit unsigned wrappable counter."
   ::= {pr1646v2EthPortSwFInQueuesH2PerformanceEntry 50331648}

pr1646v2EthPortSwFInQueuesH2PerformanceDropPkts OBJECT-TYPE
   SYNTAX      Counter64
   MAX-ACCESS  read-only
   STATUS      current
   DESCRIPTION
      "Path: swPort.performance.ifInPriorityQueues.h2Performance.droppedPkts

       64 bit unsigned wrappable counter."
   ::= {pr1646v2EthPortSwFInQueuesH2PerformanceEntry 67108864}

pr1646v2EthPortSwFInQueuesH2PerformanceRDropPkts OBJECT-TYPE
   SYNTAX      Counter64
   MAX-ACCESS  read-only
   STATUS      current
   DESCRIPTION
      "Path: swPort.performance.ifInPriorityQueues.h2Performance.redDroppedPkts

       64 bit unsigned wrappable counter."
   ::= {pr1646v2EthPortSwFInQueuesH2PerformanceEntry 201326592}

pr1646v2EthPortSwFInQueuesH2PerformanceCirTxPkts OBJECT-TYPE
   SYNTAX      Counter64
   MAX-ACCESS  read-only
   STATUS      current
   DESCRIPTION
      "Path: swPort.performance.ifInPriorityQueues.h2Performance.cirTxPkts

       64 bit unsigned wrappable counter."
   ::= {pr1646v2EthPortSwFInQueuesH2PerformanceEntry 83886080}

pr1646v2EthPortSwFInQueuesH2PerformanceEirTxPkts OBJECT-TYPE
   SYNTAX      Counter64
   MAX-ACCESS  read-only
   STATUS      current
   DESCRIPTION
      "Path: swPort.performance.ifInPriorityQueues.h2Performance.eirTxPkts

       64 bit unsigned wrappable counter."
   ::= {pr1646v2EthPortSwFInQueuesH2PerformanceEntry 100663296}

pr1646v2EthPortSwFInQueuesH2PerformanceViolTxPkts OBJECT-TYPE
   SYNTAX      Counter64
   MAX-ACCESS  read-only
   STATUS      current
   DESCRIPTION
      "Path: swPort.performance.ifInPriorityQueues.h2Performance.violateTxPkts

       64 bit unsigned wrappable counter."
   ::= {pr1646v2EthPortSwFInQueuesH2PerformanceEntry 301989888}

pr1646v2EthPortSwFInQueuesH2PerformanceTotOcts OBJECT-TYPE
   SYNTAX      Counter64
   MAX-ACCESS  read-only
   STATUS      current
   DESCRIPTION
      "Path: swPort.performance.ifInPriorityQueues.h2Performance.totalOctets

       64 bit unsigned wrappable counter."
   ::= {pr1646v2EthPortSwFInQueuesH2PerformanceEntry 251658240}

pr1646v2EthPortSwFInQueuesH2PerformanceDirTxOcts OBJECT-TYPE
   SYNTAX      Counter64
   MAX-ACCESS  read-only
   STATUS      current
   DESCRIPTION
      "Path: swPort.performance.ifInPriorityQueues.h2Performance.directTxOctets

       64 bit unsigned wrappable counter."
   ::= {pr1646v2EthPortSwFInQueuesH2PerformanceEntry 117440512}

pr1646v2EthPortSwFInQueuesH2PerformanceQdOcts OBJECT-TYPE
   SYNTAX      Counter64
   MAX-ACCESS  read-only
   STATUS      current
   DESCRIPTION
      "Path: swPort.performance.ifInPriorityQueues.h2Performance.queuedOctets

       64 bit unsigned wrappable counter."
   ::= {pr1646v2EthPortSwFInQueuesH2PerformanceEntry 134217728}

pr1646v2EthPortSwFInQueuesH2PerformanceDropOcts OBJECT-TYPE
   SYNTAX      Counter64
   MAX-ACCESS  read-only
   STATUS      current
   DESCRIPTION
      "Path: swPort.performance.ifInPriorityQueues.h2Performance.droppedOctets

       64 bit unsigned wrappable counter."
   ::= {pr1646v2EthPortSwFInQueuesH2PerformanceEntry 150994944}

pr1646v2EthPortSwFInQueuesH2PerformanceRDropOcts OBJECT-TYPE
   SYNTAX      Counter64
   MAX-ACCESS  read-only
   STATUS      current
   DESCRIPTION
      "Path: swPort.performance.ifInPriorityQueues.h2Performance.redDroppedOctets

       64 bit unsigned wrappable counter."
   ::= {pr1646v2EthPortSwFInQueuesH2PerformanceEntry 218103808}

pr1646v2EthPortSwFInQueuesH2PerformanceCirTxOcts OBJECT-TYPE
   SYNTAX      Counter64
   MAX-ACCESS  read-only
   STATUS      current
   DESCRIPTION
      "Path: swPort.performance.ifInPriorityQueues.h2Performance.cirTxOctets

       64 bit unsigned wrappable counter."
   ::= {pr1646v2EthPortSwFInQueuesH2PerformanceEntry 167772160}

pr1646v2EthPortSwFInQueuesH2PerformanceEirTxOcts OBJECT-TYPE
   SYNTAX      Counter64
   MAX-ACCESS  read-only
   STATUS      current
   DESCRIPTION
      "Path: swPort.performance.ifInPriorityQueues.h2Performance.eirTxOctets

       64 bit unsigned wrappable counter."
   ::= {pr1646v2EthPortSwFInQueuesH2PerformanceEntry 184549376}

pr1646v2EthPortSwFInQueuesH2PerformanceViolTxOcts OBJECT-TYPE
   SYNTAX      Counter64
   MAX-ACCESS  read-only
   STATUS      current
   DESCRIPTION
      "Path: swPort.performance.ifInPriorityQueues.h2Performance.violateTxOctets

       64 bit unsigned wrappable counter."
   ::= {pr1646v2EthPortSwFInQueuesH2PerformanceEntry 318767104}

pr1646v2EthPortSwFInQueuesH2PerformanceBandwidth OBJECT-TYPE
   SYNTAX      Integer32
   MAX-ACCESS  read-only
   STATUS      current
   DESCRIPTION
      "Path: swPort.performance.ifInPriorityQueues.h2Performance.bandwidth

       unit name = bps
       formula = 8 * ; 8 /"
   ::= {pr1646v2EthPortSwFInQueuesH2PerformanceEntry 268435456}

pr1646v2EthPortSwFInQueuesH24Performance OBJECT-TYPE
   SYNTAX      SEQUENCE OF Pr1646v2EthPortSwFInQueuesH24PerformanceEntry
   MAX-ACCESS  not-accessible
   STATUS      current
   DESCRIPTION
      ""
   ::= {pr1646v2EthPortSwFInQueues 100663296}

pr1646v2EthPortSwFInQueuesH24PerformanceEntry OBJECT-TYPE
   SYNTAX      Pr1646v2EthPortSwFInQueuesH24PerformanceEntry
   MAX-ACCESS  not-accessible
   STATUS      current
   DESCRIPTION
      ""
   INDEX      { pr1646v2EthPortSwFInQueuesH24PerformanceGlobalIx,
                pr1646v2EthPortSwFInQueuesTableIx,
                pr1646v2EthPortSwFInQueuesH24PerformanceTableIx }
   ::= {pr1646v2EthPortSwFInQueuesH24Performance 1}

Pr1646v2EthPortSwFInQueuesH24PerformanceEntry ::=
   SEQUENCE
      {
      pr1646v2EthPortSwFInQueuesH24PerformanceGlobalIx
         GlobalIndex,
      pr1646v2EthPortSwFInQueuesH24PerformanceTableIx
         TableIndex,
      pr1646v2EthPortSwFInQueuesH24PerformanceSysUpTime
         TimeTicks,
      pr1646v2EthPortSwFInQueuesH24PerformanceTotPkts
         Counter64,
      pr1646v2EthPortSwFInQueuesH24PerformanceDirTxPkts
         Counter64,
      pr1646v2EthPortSwFInQueuesH24PerformanceQdPkts
         Counter64,
      pr1646v2EthPortSwFInQueuesH24PerformanceDropPkts
         Counter64,
      pr1646v2EthPortSwFInQueuesH24PerformanceRDropPkts
         Counter64,
      pr1646v2EthPortSwFInQueuesH24PerformanceCirTxPkts
         Counter64,
      pr1646v2EthPortSwFInQueuesH24PerformanceEirTxPkts
         Counter64,
      pr1646v2EthPortSwFInQueuesH24PerformanceViolTxPkts
         Counter64,
      pr1646v2EthPortSwFInQueuesH24PerformanceTotOcts
         Counter64,
      pr1646v2EthPortSwFInQueuesH24PerformanceDirTxOcts
         Counter64,
      pr1646v2EthPortSwFInQueuesH24PerformanceQdOcts
         Counter64,
      pr1646v2EthPortSwFInQueuesH24PerformanceDropOcts
         Counter64,
      pr1646v2EthPortSwFInQueuesH24PerformanceRDropOcts
         Counter64,
      pr1646v2EthPortSwFInQueuesH24PerformanceCirTxOcts
         Counter64,
      pr1646v2EthPortSwFInQueuesH24PerformanceEirTxOcts
         Counter64,
      pr1646v2EthPortSwFInQueuesH24PerformanceViolTxOcts
         Counter64,
      pr1646v2EthPortSwFInQueuesH24PerformanceBandwidth
         Integer32
      }

pr1646v2EthPortSwFInQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFInQueuesH24PerformanceEntry 10}

pr1646v2EthPortSwFInQueuesH24PerformanceTableIx OBJECT-TYPE
   SYNTAX      TableIndex
   MAX-ACCESS  not-accessible
   STATUS      current
   DESCRIPTION
      ""
   ::= {pr1646v2EthPortSwFInQueuesH24PerformanceEntry 11}

pr1646v2EthPortSwFInQueuesH24PerformanceSysUpTime OBJECT-TYPE
   SYNTAX      TimeTicks
   MAX-ACCESS  read-only
   STATUS      current
   DESCRIPTION
      "Path: swPort.performance.ifInPriorityQueues.h24Performance.sysUpTime

       Time in centi-second."
   ::= {pr1646v2EthPortSwFInQueuesH24PerformanceEntry 16777216}

pr1646v2EthPortSwFInQueuesH24PerformanceTotPkts OBJECT-TYPE
   SYNTAX      Counter64
   MAX-ACCESS  read-only
   STATUS      current
   DESCRIPTION
      "Path: swPort.performance.ifInPriorityQueues.h24Performance.totalPkts

       64 bit unsigned wrappable counter."
   ::= {pr1646v2EthPortSwFInQueuesH24PerformanceEntry 234881024}

pr1646v2EthPortSwFInQueuesH24PerformanceDirTxPkts OBJECT-TYPE
   SYNTAX      Counter64
   MAX-ACCESS  read-only
   STATUS      current
   DESCRIPTION
      "Path: swPort.performance.ifInPriorityQueues.h24Performance.directTxPkts

       64 bit unsigned wrappable counter."
   ::= {pr1646v2EthPortSwFInQueuesH24PerformanceEntry 33554432}

pr1646v2EthPortSwFInQueuesH24PerformanceQdPkts OBJECT-TYPE
   SYNTAX      Counter64
   MAX-ACCESS  read-only
   STATUS      current
   DESCRIPTION
      "Path: swPort.performance.ifInPriorityQueues.h24Performance.queuedPkts

       64 bit unsigned wrappable counter."
   ::= {pr1646v2EthPortSwFInQueuesH24PerformanceEntry 50331648}

pr1646v2EthPortSwFInQueuesH24PerformanceDropPkts OBJECT-TYPE
   SYNTAX      Counter64
   MAX-ACCESS  read-only
   STATUS      current
   DESCRIPTION
      "Path: swPort.performance.ifInPriorityQueues.h24Performance.droppedPkts

       64 bit unsigned wrappable counter."
   ::= {pr1646v2EthPortSwFInQueuesH24PerformanceEntry 67108864}

pr1646v2EthPortSwFInQueuesH24PerformanceRDropPkts OBJECT-TYPE
   SYNTAX      Counter64
   MAX-ACCESS  read-only
   STATUS      current
   DESCRIPTION
      "Path: swPort.performance.ifInPriorityQueues.h24Performance.redDroppedPkts

       64 bit unsigned wrappable counter."
   ::= {pr1646v2EthPortSwFInQueuesH24PerformanceEntry 201326592}

pr1646v2EthPortSwFInQueuesH24PerformanceCirTxPkts OBJECT-TYPE
   SYNTAX      Counter64
   MAX-ACCESS  read-only
   STATUS      current
   DESCRIPTION
      "Path: swPort.performance.ifInPriorityQueues.h24Performance.cirTxPkts

       64 bit unsigned wrappable counter."
   ::= {pr1646v2EthPortSwFInQueuesH24PerformanceEntry 83886080}

pr1646v2EthPortSwFInQueuesH24PerformanceEirTxPkts OBJECT-TYPE
   SYNTAX      Counter64
   MAX-ACCESS  read-only
   STATUS      current
   DESCRIPTION
      "Path: swPort.performance.ifInPriorityQueues.h24Performance.eirTxPkts

       64 bit unsigned wrappable counter."
   ::= {pr1646v2EthPortSwFInQueuesH24PerformanceEntry 100663296}

pr1646v2EthPortSwFInQueuesH24PerformanceViolTxPkts OBJECT-TYPE
   SYNTAX      Counter64
   MAX-ACCESS  read-only
   STATUS      current
   DESCRIPTION
      "Path: swPort.performance.ifInPriorityQueues.h24Performance.violateTxPkts

       64 bit unsigned wrappable counter."
   ::= {pr1646v2EthPortSwFInQueuesH24PerformanceEntry 301989888}

pr1646v2EthPortSwFInQueuesH24PerformanceTotOcts OBJECT-TYPE
   SYNTAX      Counter64
   MAX-ACCESS  read-only
   STATUS      current
   DESCRIPTION
      "Path: swPort.performance.ifInPriorityQueues.h24Performance.totalOctets

       64 bit unsigned wrappable counter."
   ::= {pr1646v2EthPortSwFInQueuesH24PerformanceEntry 251658240}

pr1646v2EthPortSwFInQueuesH24PerformanceDirTxOcts OBJECT-TYPE
   SYNTAX      Counter64
   MAX-ACCESS  read-only
   STATUS      current
   DESCRIPTION
      "Path: swPort.performance.ifInPriorityQueues.h24Performance.directTxOctets

       64 bit unsigned wrappable counter."
   ::= {pr1646v2EthPortSwFInQueuesH24PerformanceEntry 117440512}

pr1646v2EthPortSwFInQueuesH24PerformanceQdOcts OBJECT-TYPE
   SYNTAX      Counter64
   MAX-ACCESS  read-only
   STATUS      current
   DESCRIPTION
      "Path: swPort.performance.ifInPriorityQueues.h24Performance.queuedOctets

       64 bit unsigned wrappable counter."
   ::= {pr1646v2EthPortSwFInQueuesH24PerformanceEntry 134217728}

pr1646v2EthPortSwFInQueuesH24PerformanceDropOcts OBJECT-TYPE
   SYNTAX      Counter64
   MAX-ACCESS  read-only
   STATUS      current
   DESCRIPTION
      "Path: swPort.performance.ifInPriorityQueues.h24Performance.droppedOctets

       64 bit unsigned wrappable counter."
   ::= {pr1646v2EthPortSwFInQueuesH24PerformanceEntry 150994944}

pr1646v2EthPortSwFInQueuesH24PerformanceRDropOcts OBJECT-TYPE
   SYNTAX      Counter64
   MAX-ACCESS  read-only
   STATUS      current
   DESCRIPTION
      "Path: swPort.performance.ifInPriorityQueues.h24Performance.redDroppedOctets

       64 bit unsigned wrappable counter."
   ::= {pr1646v2EthPortSwFInQueuesH24PerformanceEntry 218103808}

pr1646v2EthPortSwFInQueuesH24PerformanceCirTxOcts OBJECT-TYPE
   SYNTAX      Counter64
   MAX-ACCESS  read-only
   STATUS      current
   DESCRIPTION
      "Path: swPort.performance.ifInPriorityQueues.h24Performance.cirTxOctets

       64 bit unsigned wrappable counter."
   ::= {pr1646v2EthPortSwFInQueuesH24PerformanceEntry 167772160}

pr1646v2EthPortSwFInQueuesH24PerformanceEirTxOcts OBJECT-TYPE
   SYNTAX      Counter64
   MAX-ACCESS  read-only
   STATUS      current
   DESCRIPTION
      "Path: swPort.performance.ifInPriorityQueues.h24Performance.eirTxOctets

       64 bit unsigned wrappable counter."
   ::= {pr1646v2EthPortSwFInQueuesH24PerformanceEntry 184549376}

pr1646v2EthPortSwFInQueuesH24PerformanceViolTxOcts OBJECT-TYPE
   SYNTAX      Counter64
   MAX-ACCESS  read-only
   STATUS      current
   DESCRIPTION
      "Path: swPort.performance.ifInPriorityQueues.h24Performance.violateTxOctets

       64 bit unsigned wrappable counter."
   ::= {pr1646v2EthPortSwFInQueuesH24PerformanceEntry 318767104}

pr1646v2EthPortSwFInQueuesH24PerformanceBandwidth OBJECT-TYPE
   SYNTAX      Integer32
   MAX-ACCESS  read-only
   STATUS      current
   DESCRIPTION
      "Path: swPort.performance.ifInPriorityQueues.h24Performance.bandwidth

       unit name = bps
       formula = 8 * ; 8 /"
   ::= {pr1646v2EthPortSwFInQueuesH24PerformanceEntry 268435456}

pr1646v2EthPortSwFInQueuesD7Performance OBJECT-TYPE
   SYNTAX      SEQUENCE OF Pr1646v2EthPortSwFInQueuesD7PerformanceEntry
   MAX-ACCESS  not-accessible
   STATUS      current
   DESCRIPTION
      ""
   ::= {pr1646v2EthPortSwFInQueues 117440512}

pr1646v2EthPortSwFInQueuesD7PerformanceEntry OBJECT-TYPE
   SYNTAX      Pr1646v2EthPortSwFInQueuesD7PerformanceEntry
   MAX-ACCESS  not-accessible
   STATUS      current
   DESCRIPTION
      ""
   INDEX      { pr1646v2EthPortSwFInQueuesD7PerformanceGlobalIx,
                pr1646v2EthPortSwFInQueuesTableIx,
                pr1646v2EthPortSwFInQueuesD7PerformanceTableIx }
   ::= {pr1646v2EthPortSwFInQueuesD7Performance 1}

Pr1646v2EthPortSwFInQueuesD7PerformanceEntry ::=
   SEQUENCE
      {
      pr1646v2EthPortSwFInQueuesD7PerformanceGlobalIx
         GlobalIndex,
      pr1646v2EthPortSwFInQueuesD7PerformanceTableIx
         TableIndex,
      pr1646v2EthPortSwFInQueuesD7PerformanceSysUpTime
         TimeTicks,
      pr1646v2EthPortSwFInQueuesD7PerformanceTotPkts
         Counter64,
      pr1646v2EthPortSwFInQueuesD7PerformanceDirTxPkts
         Counter64,
      pr1646v2EthPortSwFInQueuesD7PerformanceQdPkts
         Counter64,
      pr1646v2EthPortSwFInQueuesD7PerformanceDropPkts
         Counter64,
      pr1646v2EthPortSwFInQueuesD7PerformanceRDropPkts
         Counter64,
      pr1646v2EthPortSwFInQueuesD7PerformanceCirTxPkts
         Counter64,
      pr1646v2EthPortSwFInQueuesD7PerformanceEirTxPkts
         Counter64,
      pr1646v2EthPortSwFInQueuesD7PerformanceViolTxPkts
         Counter64,
      pr1646v2EthPortSwFInQueuesD7PerformanceTotOcts
         Counter64,
      pr1646v2EthPortSwFInQueuesD7PerformanceDirTxOcts
         Counter64,
      pr1646v2EthPortSwFInQueuesD7PerformanceQdOcts
         Counter64,
      pr1646v2EthPortSwFInQueuesD7PerformanceDropOcts
         Counter64,
      pr1646v2EthPortSwFInQueuesD7PerformanceRDropOcts
         Counter64,
      pr1646v2EthPortSwFInQueuesD7PerformanceCirTxOcts
         Counter64,
      pr1646v2EthPortSwFInQueuesD7PerformanceEirTxOcts
         Counter64,
      pr1646v2EthPortSwFInQueuesD7PerformanceViolTxOcts
         Counter64,
      pr1646v2EthPortSwFInQueuesD7PerformanceBandwidth
         Integer32
      }

pr1646v2EthPortSwFInQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFInQueuesD7PerformanceEntry 10}

pr1646v2EthPortSwFInQueuesD7PerformanceTableIx OBJECT-TYPE
   SYNTAX      TableIndex
   MAX-ACCESS  not-accessible
   STATUS      current
   DESCRIPTION
      ""
   ::= {pr1646v2EthPortSwFInQueuesD7PerformanceEntry 11}

pr1646v2EthPortSwFInQueuesD7PerformanceSysUpTime OBJECT-TYPE
   SYNTAX      TimeTicks
   MAX-ACCESS  read-only
   STATUS      current
   DESCRIPTION
      "Path: swPort.performance.ifInPriorityQueues.d7Performance.sysUpTime

       Time in centi-second."
   ::= {pr1646v2EthPortSwFInQueuesD7PerformanceEntry 16777216}

pr1646v2EthPortSwFInQueuesD7PerformanceTotPkts OBJECT-TYPE
   SYNTAX      Counter64
   MAX-ACCESS  read-only
   STATUS      current
   DESCRIPTION
      "Path: swPort.performance.ifInPriorityQueues.d7Performance.totalPkts

       64 bit unsigned wrappable counter."
   ::= {pr1646v2EthPortSwFInQueuesD7PerformanceEntry 234881024}

pr1646v2EthPortSwFInQueuesD7PerformanceDirTxPkts OBJECT-TYPE
   SYNTAX      Counter64
   MAX-ACCESS  read-only
   STATUS      current
   DESCRIPTION
      "Path: swPort.performance.ifInPriorityQueues.d7Performance.directTxPkts

       64 bit unsigned wrappable counter."
   ::= {pr1646v2EthPortSwFInQueuesD7PerformanceEntry 33554432}

pr1646v2EthPortSwFInQueuesD7PerformanceQdPkts OBJECT-TYPE
   SYNTAX      Counter64
   MAX-ACCESS  read-only
   STATUS      current
   DESCRIPTION
      "Path: swPort.performance.ifInPriorityQueues.d7Performance.queuedPkts

       64 bit unsigned wrappable counter."
   ::= {pr1646v2EthPortSwFInQueuesD7PerformanceEntry 50331648}

pr1646v2EthPortSwFInQueuesD7PerformanceDropPkts OBJECT-TYPE
   SYNTAX      Counter64
   MAX-ACCESS  read-only
   STATUS      current
   DESCRIPTION
      "Path: swPort.performance.ifInPriorityQueues.d7Performance.droppedPkts

       64 bit unsigned wrappable counter."
   ::= {pr1646v2EthPortSwFInQueuesD7PerformanceEntry 67108864}

pr1646v2EthPortSwFInQueuesD7PerformanceRDropPkts OBJECT-TYPE
   SYNTAX      Counter64
   MAX-ACCESS  read-only
   STATUS      current
   DESCRIPTION
      "Path: swPort.performance.ifInPriorityQueues.d7Performance.redDroppedPkts

       64 bit unsigned wrappable counter."
   ::= {pr1646v2EthPortSwFInQueuesD7PerformanceEntry 201326592}

pr1646v2EthPortSwFInQueuesD7PerformanceCirTxPkts OBJECT-TYPE
   SYNTAX      Counter64
   MAX-ACCESS  read-only
   STATUS      current
   DESCRIPTION
      "Path: swPort.performance.ifInPriorityQueues.d7Performance.cirTxPkts

       64 bit unsigned wrappable counter."
   ::= {pr1646v2EthPortSwFInQueuesD7PerformanceEntry 83886080}

pr1646v2EthPortSwFInQueuesD7PerformanceEirTxPkts OBJECT-TYPE
   SYNTAX      Counter64
   MAX-ACCESS  read-only
   STATUS      current
   DESCRIPTION
      "Path: swPort.performance.ifInPriorityQueues.d7Performance.eirTxPkts

       64 bit unsigned wrappable counter."
   ::= {pr1646v2EthPortSwFInQueuesD7PerformanceEntry 100663296}

pr1646v2EthPortSwFInQueuesD7PerformanceViolTxPkts OBJECT-TYPE
   SYNTAX      Counter64
   MAX-ACCESS  read-only
   STATUS      current
   DESCRIPTION
      "Path: swPort.performance.ifInPriorityQueues.d7Performance.violateTxPkts

       64 bit unsigned wrappable counter."
   ::= {pr1646v2EthPortSwFInQueuesD7PerformanceEntry 301989888}

pr1646v2EthPortSwFInQueuesD7PerformanceTotOcts OBJECT-TYPE
   SYNTAX      Counter64
   MAX-ACCESS  read-only
   STATUS      current
   DESCRIPTION
      "Path: swPort.performance.ifInPriorityQueues.d7Performance.totalOctets

       64 bit unsigned wrappable counter."
   ::= {pr1646v2EthPortSwFInQueuesD7PerformanceEntry 251658240}

pr1646v2EthPortSwFInQueuesD7PerformanceDirTxOcts OBJECT-TYPE
   SYNTAX      Counter64
   MAX-ACCESS  read-only
   STATUS      current
   DESCRIPTION
      "Path: swPort.performance.ifInPriorityQueues.d7Performance.directTxOctets

       64 bit unsigned wrappable counter."
   ::= {pr1646v2EthPortSwFInQueuesD7PerformanceEntry 117440512}

pr1646v2EthPortSwFInQueuesD7PerformanceQdOcts OBJECT-TYPE
   SYNTAX      Counter64
   MAX-ACCESS  read-only
   STATUS      current
   DESCRIPTION
      "Path: swPort.performance.ifInPriorityQueues.d7Performance.queuedOctets

       64 bit unsigned wrappable counter."
   ::= {pr1646v2EthPortSwFInQueuesD7PerformanceEntry 134217728}

pr1646v2EthPortSwFInQueuesD7PerformanceDropOcts OBJECT-TYPE
   SYNTAX      Counter64
   MAX-ACCESS  read-only
   STATUS      current
   DESCRIPTION
      "Path: swPort.performance.ifInPriorityQueues.d7Performance.droppedOctets

       64 bit unsigned wrappable counter."
   ::= {pr1646v2EthPortSwFInQueuesD7PerformanceEntry 150994944}

pr1646v2EthPortSwFInQueuesD7PerformanceRDropOcts OBJECT-TYPE
   SYNTAX      Counter64
   MAX-ACCESS  read-only
   STATUS      current
   DESCRIPTION
      "Path: swPort.performance.ifInPriorityQueues.d7Performance.redDroppedOctets

       64 bit unsigned wrappable counter."
   ::= {pr1646v2EthPortSwFInQueuesD7PerformanceEntry 218103808}

pr1646v2EthPortSwFInQueuesD7PerformanceCirTxOcts OBJECT-TYPE
   SYNTAX      Counter64
   MAX-ACCESS  read-only
   STATUS      current
   DESCRIPTION
      "Path: swPort.performance.ifInPriorityQueues.d7Performance.cirTxOctets

       64 bit unsigned wrappable counter."
   ::= {pr1646v2EthPortSwFInQueuesD7PerformanceEntry 167772160}

pr1646v2EthPortSwFInQueuesD7PerformanceEirTxOcts OBJECT-TYPE
   SYNTAX      Counter64
   MAX-ACCESS  read-only
   STATUS      current
   DESCRIPTION
      "Path: swPort.performance.ifInPriorityQueues.d7Performance.eirTxOctets

       64 bit unsigned wrappable counter."
   ::= {pr1646v2EthPortSwFInQueuesD7PerformanceEntry 184549376}

pr1646v2EthPortSwFInQueuesD7PerformanceViolTxOcts OBJECT-TYPE
   SYNTAX      Counter64
   MAX-ACCESS  read-only
   STATUS      current
   DESCRIPTION
      "Path: swPort.performance.ifInPriorityQueues.d7Performance.violateTxOctets

       64 bit unsigned wrappable counter."
   ::= {pr1646v2EthPortSwFInQueuesD7PerformanceEntry 318767104}

pr1646v2EthPortSwFInQueuesD7PerformanceBandwidth OBJECT-TYPE
   SYNTAX      Integer32
   MAX-ACCESS  read-only
   STATUS      current
   DESCRIPTION
      "Path: swPort.performance.ifInPriorityQueues.d7Performance.bandwidth

       unit name = bps
       formula = 8 * ; 8 /"
   ::= {pr1646v2EthPortSwFInQueuesD7PerformanceEntry 268435456}


pr1646v2EthPortSwFInBandwidth OBJECT IDENTIFIER ::= {pr1646v2EthPortSwF 181}

pr1646v2EthPortSwFInBandwidthSSCTable OBJECT-TYPE
   SYNTAX      SEQUENCE OF Pr1646v2EthPortSwFInBandwidthEntry
   MAX-ACCESS  not-accessible
   STATUS      current
   DESCRIPTION
      "bandwidth"
   ::= {pr1646v2EthPortSwFInBandwidth 1}

pr1646v2EthPortSwFInBandwidthEntry OBJECT-TYPE
   SYNTAX      Pr1646v2EthPortSwFInBandwidthEntry
   MAX-ACCESS  not-accessible
   STATUS      current
   DESCRIPTION
      ""
   INDEX      { pr1646v2EthPortSwFInBandwidthGlobalIx }
   ::= {pr1646v2EthPortSwFInBandwidthSSCTable 1}

Pr1646v2EthPortSwFInBandwidthEntry ::=
   SEQUENCE
      {
      pr1646v2EthPortSwFInBandwidthGlobalIx
         GlobalIndex,
      pr1646v2EthPortSwFInBandwidth15sec
         Integer32,
      pr1646v2EthPortSwFInBandwidth30sec
         Integer32,
      pr1646v2EthPortSwFInBandwidth1min
         Integer32,
      pr1646v2EthPortSwFInBandwidth2min
         Integer32,
      pr1646v2EthPortSwFInBandwidth5min
         Integer32
      }

pr1646v2EthPortSwFInBandwidthGlobalIx OBJECT-TYPE
   SYNTAX      GlobalIndex
   MAX-ACCESS  not-accessible
   STATUS      current
   DESCRIPTION
      "The value of the tlsCntTreeGlobalIndex of the MANAGED OBJECT."
   ::= {pr1646v2EthPortSwFInBandwidthEntry 10}

pr1646v2EthPortSwFInBandwidth15sec OBJECT-TYPE
   SYNTAX      Integer32
   MAX-ACCESS  read-only
   STATUS      current
   DESCRIPTION
      "Path: swPort.performance.ifInBandwidth.15sec

       unit name = bps
       formula = 8 * ; 8 /"
   ::= {pr1646v2EthPortSwFInBandwidthEntry 83886080}

pr1646v2EthPortSwFInBandwidth30sec OBJECT-TYPE
   SYNTAX      Integer32
   MAX-ACCESS  read-only
   STATUS      current
   DESCRIPTION
      "Path: swPort.performance.ifInBandwidth.30sec

       unit name = bps
       formula = 8 * ; 8 /"
   ::= {pr1646v2EthPortSwFInBandwidthEntry 167772160}

pr1646v2EthPortSwFInBandwidth1min OBJECT-TYPE
   SYNTAX      Integer32
   MAX-ACCESS  read-only
   STATUS      current
   DESCRIPTION
      "Path: swPort.performance.ifInBandwidth.1min

       unit name = bps
       formula = 8 * ; 8 /"
   ::= {pr1646v2EthPortSwFInBandwidthEntry 335544320}

pr1646v2EthPortSwFInBandwidth2min OBJECT-TYPE
   SYNTAX      Integer32
   MAX-ACCESS  read-only
   STATUS      current
   DESCRIPTION
      "Path: swPort.performance.ifInBandwidth.2min

       unit name = bps
       formula = 8 * ; 8 /"
   ::= {pr1646v2EthPortSwFInBandwidthEntry 671088640}

pr1646v2EthPortSwFInBandwidth5min OBJECT-TYPE
   SYNTAX      Integer32
   MAX-ACCESS  read-only
   STATUS      current
   DESCRIPTION
      "Path: swPort.performance.ifInBandwidth.5min

       unit name = bps
       formula = 8 * ; 8 /"
   ::= {pr1646v2EthPortSwFInBandwidthEntry 1677721600}


pr1646v2EthPortSwFOutOctets OBJECT IDENTIFIER ::= {pr1646v2EthPortSwF 115}

pr1646v2EthPortSwFOutOctetsTable OBJECT-TYPE
   SYNTAX      SEQUENCE OF Pr1646v2EthPortSwFOutOctetsEntry
   MAX-ACCESS  not-accessible
   STATUS      current
   DESCRIPTION
      "ifOutOctets"
   ::= {pr1646v2EthPortSwFOutOctets 1}

pr1646v2EthPortSwFOutOctetsEntry OBJECT-TYPE
   SYNTAX      Pr1646v2EthPortSwFOutOctetsEntry
   MAX-ACCESS  not-accessible
   STATUS      current
   DESCRIPTION
      ""
   INDEX      { pr1646v2EthPortSwFOutOctetsGlobalIx }
   ::= {pr1646v2EthPortSwFOutOctetsTable 1}

Pr1646v2EthPortSwFOutOctetsEntry ::=
   SEQUENCE
      {
      pr1646v2EthPortSwFOutOctetsGlobalIx
         GlobalIndex,
      pr1646v2EthPortSwFOutOctetsValue
         Counter64
      }

pr1646v2EthPortSwFOutOctetsGlobalIx OBJECT-TYPE
   SYNTAX      GlobalIndex
   MAX-ACCESS  not-accessible
   STATUS      current
   DESCRIPTION
      "The value of the tlsCntTreeGlobalIndex of the MANAGED OBJECT."
   ::= {pr1646v2EthPortSwFOutOctetsEntry 10}

pr1646v2EthPortSwFOutOctetsValue OBJECT-TYPE
   SYNTAX      Counter64
   MAX-ACCESS  read-only
   STATUS      current
   DESCRIPTION
      "Path: swPort.performance.ifOutOctets

       64 bit unsigned wrappable counter."
   ::= {pr1646v2EthPortSwFOutOctetsEntry 2147483648}


pr1646v2EthPortSwFOutUcastPkts OBJECT IDENTIFIER ::= {pr1646v2EthPortSwF 116}

pr1646v2EthPortSwFOutUcastPktsTable OBJECT-TYPE
   SYNTAX      SEQUENCE OF Pr1646v2EthPortSwFOutUcastPktsEntry
   MAX-ACCESS  not-accessible
   STATUS      current
   DESCRIPTION
      "ifOutUcastPkts"
   ::= {pr1646v2EthPortSwFOutUcastPkts 1}

pr1646v2EthPortSwFOutUcastPktsEntry OBJECT-TYPE
   SYNTAX      Pr1646v2EthPortSwFOutUcastPktsEntry
   MAX-ACCESS  not-accessible
   STATUS      current
   DESCRIPTION
      ""
   INDEX      { pr1646v2EthPortSwFOutUcastPktsGlobalIx }
   ::= {pr1646v2EthPortSwFOutUcastPktsTable 1}

Pr1646v2EthPortSwFOutUcastPktsEntry ::=
   SEQUENCE
      {
      pr1646v2EthPortSwFOutUcastPktsGlobalIx
         GlobalIndex,
      pr1646v2EthPortSwFOutUcastPktsValue
         Counter64
      }

pr1646v2EthPortSwFOutUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFOutUcastPktsEntry 10}

pr1646v2EthPortSwFOutUcastPktsValue OBJECT-TYPE
   SYNTAX      Counter64
   MAX-ACCESS  read-only
   STATUS      current
   DESCRIPTION
      "Path: swPort.performance.ifOutUcastPkts

       64 bit unsigned wrappable counter."
   ::= {pr1646v2EthPortSwFOutUcastPktsEntry 2147483648}


pr1646v2EthPortSwFOutNUcastPkts OBJECT IDENTIFIER ::= {pr1646v2EthPortSwF 117}

pr1646v2EthPortSwFOutNUcastPktsTable OBJECT-TYPE
   SYNTAX      SEQUENCE OF Pr1646v2EthPortSwFOutNUcastPktsEntry
   MAX-ACCESS  not-accessible
   STATUS      current
   DESCRIPTION
      "ifOutNUcastPkts"
   ::= {pr1646v2EthPortSwFOutNUcastPkts 1}

pr1646v2EthPortSwFOutNUcastPktsEntry OBJECT-TYPE
   SYNTAX      Pr1646v2EthPortSwFOutNUcastPktsEntry
   MAX-ACCESS  not-accessible
   STATUS      current
   DESCRIPTION
      ""
   INDEX      { pr1646v2EthPortSwFOutNUcastPktsGlobalIx }
   ::= {pr1646v2EthPortSwFOutNUcastPktsTable 1}

Pr1646v2EthPortSwFOutNUcastPktsEntry ::=
   SEQUENCE
      {
      pr1646v2EthPortSwFOutNUcastPktsGlobalIx
         GlobalIndex,
      pr1646v2EthPortSwFOutNUcastPktsValue
         Counter64
      }

pr1646v2EthPortSwFOutNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFOutNUcastPktsEntry 10}

pr1646v2EthPortSwFOutNUcastPktsValue OBJECT-TYPE
   SYNTAX      Counter64
   MAX-ACCESS  read-only
   STATUS      current
   DESCRIPTION
      "Path: swPort.performance.ifOutNUcastPkts

       64 bit unsigned wrappable counter."
   ::= {pr1646v2EthPortSwFOutNUcastPktsEntry 2147483648}


pr1646v2EthPortSwFOutBcastPkts OBJECT IDENTIFIER ::= {pr1646v2EthPortSwF 217}

pr1646v2EthPortSwFOutBcastPktsTable OBJECT-TYPE
   SYNTAX      SEQUENCE OF Pr1646v2EthPortSwFOutBcastPktsEntry
   MAX-ACCESS  not-accessible
   STATUS      current
   DESCRIPTION
      "ifOutBcastPkts"
   ::= {pr1646v2EthPortSwFOutBcastPkts 1}

pr1646v2EthPortSwFOutBcastPktsEntry OBJECT-TYPE
   SYNTAX      Pr1646v2EthPortSwFOutBcastPktsEntry
   MAX-ACCESS  not-accessible
   STATUS      current
   DESCRIPTION
      ""
   INDEX      { pr1646v2EthPortSwFOutBcastPktsGlobalIx }
   ::= {pr1646v2EthPortSwFOutBcastPktsTable 1}

Pr1646v2EthPortSwFOutBcastPktsEntry ::=
   SEQUENCE
      {
      pr1646v2EthPortSwFOutBcastPktsGlobalIx
         GlobalIndex,
      pr1646v2EthPortSwFOutBcastPktsValue
         Counter64
      }

pr1646v2EthPortSwFOutBcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFOutBcastPktsEntry 10}

pr1646v2EthPortSwFOutBcastPktsValue OBJECT-TYPE
   SYNTAX      Counter64
   MAX-ACCESS  read-only
   STATUS      current
   DESCRIPTION
      "Path: swPort.performance.ifOutBcastPkts

       64 bit unsigned wrappable counter."
   ::= {pr1646v2EthPortSwFOutBcastPktsEntry 2147483648}


pr1646v2EthPortSwFOutMcastPkts OBJECT IDENTIFIER ::= {pr1646v2EthPortSwF 227}

pr1646v2EthPortSwFOutMcastPktsTable OBJECT-TYPE
   SYNTAX      SEQUENCE OF Pr1646v2EthPortSwFOutMcastPktsEntry
   MAX-ACCESS  not-accessible
   STATUS      current
   DESCRIPTION
      "ifOutMcastPkts"
   ::= {pr1646v2EthPortSwFOutMcastPkts 1}

pr1646v2EthPortSwFOutMcastPktsEntry OBJECT-TYPE
   SYNTAX      Pr1646v2EthPortSwFOutMcastPktsEntry
   MAX-ACCESS  not-accessible
   STATUS      current
   DESCRIPTION
      ""
   INDEX      { pr1646v2EthPortSwFOutMcastPktsGlobalIx }
   ::= {pr1646v2EthPortSwFOutMcastPktsTable 1}

Pr1646v2EthPortSwFOutMcastPktsEntry ::=
   SEQUENCE
      {
      pr1646v2EthPortSwFOutMcastPktsGlobalIx
         GlobalIndex,
      pr1646v2EthPortSwFOutMcastPktsValue
         Counter64
      }

pr1646v2EthPortSwFOutMcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwFOutMcastPktsEntry 10}

pr1646v2EthPortSwFOutMcastPktsValue OBJECT-TYPE
   SYNTAX      Counter64
   MAX-ACCESS  read-only
   STATUS      current
   DESCRIPTION
      "Path: swPort.performance.ifOutMcastPkts

       64 bit unsigned wrappable counter."
   ::= {pr1646v2EthPortSwFOutMcastPktsEntry 2147483648}


pr1646v2EthPortSwFOutDiscards OBJECT IDENTIFIER ::= {pr1646v2EthPortSwF 118}

pr1646v2EthPortSwFOutDiscardsTable OBJECT-TYPE
   SYNTAX      SEQUENCE OF Pr1646v2EthPortSwFOutDiscardsEntry
   MAX-ACCESS  not-accessible
   STATUS      current
   DESCRIPTION
      "ifOutDiscards"
   ::= {pr1646v2EthPortSwFOutDiscards 1}

pr1646v2EthPortSwFOutDiscardsEntry OBJECT-TYPE
   SYNTAX      Pr1646v2EthPortSwFOutDiscardsEntry
   MAX-ACCESS  not-accessible
   STATUS      current
   DESCRIPTION
      ""
   INDEX      { pr1646v2EthPortSwFOutDiscardsGlobalIx }
   ::= {pr1646v2EthPortSwFOutDiscardsTable 1}

Pr1646v2EthPortSwFOutDiscardsEntry ::=
   SEQUENCE
      {
      pr1646v2EthPortSwFOutDiscardsGlobalIx
         GlobalIndex,
      pr1646v2EthPortSwFOutDiscardsValue
         Counter64
      }

pr1646v2EthPortSwFOutDiscardsGlobalIx OBJECT-TYPE
   SYNTAX      GlobalIndex
   MAX-ACCESS  not-accessible
   STATUS      current
   DESCRIPTION
      "The value of the tlsCntTreeGlobalIndex of the MANAGED OBJECT."
   ::= {pr1646v2EthPortSwFOutDiscardsEntry 10}

pr1646v2EthPortSwFOutDiscardsValue OBJECT-TYPE
   SYNTAX      Counter64
   MAX-ACCESS  read-only
   STATUS      current
   DESCRIPTION
      "Path: swPort.performance.ifOutDiscards

       64 bit unsigned wrappable counter."
   ::= {pr1646v2EthPortSwFOutDiscardsEntry 2147483648}


pr1646v2EthPortSwFOutErrors OBJECT IDENTIFIER ::= {pr1646v2EthPortSwF 119}

pr1646v2EthPortSwFOutErrorsTable OBJECT-TYPE
   SYNTAX      SEQUENCE OF Pr1646v2EthPortSwFOutErrorsEntry
   MAX-ACCESS  not-accessible
   STATUS      current
   DESCRIPTION
      "ifOutErrors"
   ::= {pr1646v2EthPortSwFOutErrors 1}

pr1646v2EthPortSwFOutErrorsEntry OBJECT-TYPE
   SYNTAX      Pr1646v2EthPortSwFOutErrorsEntry
   MAX-ACCESS  not-accessible
   STATUS      current
   DESCRIPTION
      ""
   INDEX      { pr1646v2EthPortSwFOutErrorsGlobalIx }
   ::= {pr1646v2EthPortSwFOutErrorsTable 1}

Pr1646v2EthPortSwFOutErrorsEntry ::=
   SEQUENCE
      {
      pr1646v2EthPortSwFOutErrorsGlobalIx
         GlobalIndex,
      pr1646v2EthPortSwFOutErrorsValue
         Counter64
      }

pr1646v2EthPortSwFOutErrorsGlobalIx OBJECT-TYPE
   SYNTAX      GlobalIndex
   MAX-ACCESS  not-accessible
   STATUS      current
   DESCRIPTION
      "The value of the tlsCntTreeGlobalIndex of the MANAGED OBJECT."
   ::= {pr1646v2EthPortSwFOutErrorsEntry 10}

pr1646v2EthPortSwFOutErrorsValue OBJECT-TYPE
   SYNTAX      Counter64
   MAX-ACCESS  read-only
   STATUS      current
   DESCRIPTION
      "Path: swPort.performance.ifOutErrors

       64 bit unsigned wrappable counter."
   ::= {pr1646v2EthPortSwFOutErrorsEntry 2147483648}


pr1646v2EthPortSwFOutQLen OBJECT IDENTIFIER ::= {pr1646v2EthPortSwF 120}

pr1646v2EthPortSwFOutQLenTable OBJECT-TYPE
   SYNTAX      SEQUENCE OF Pr1646v2EthPortSwFOutQLenEntry
   MAX-ACCESS  not-accessible
   STATUS      current
   DESCRIPTION
      "ifOutQLen"
   ::= {pr1646v2EthPortSwFOutQLen 1}

pr1646v2EthPortSwFOutQLenEntry OBJECT-TYPE
   SYNTAX      Pr1646v2EthPortSwFOutQLenEntry
   MAX-ACCESS  not-accessible
   STATUS      current
   DESCRIPTION
      ""
   INDEX      { pr1646v2EthPortSwFOutQLenGlobalIx }
   ::= {pr1646v2EthPortSwFOutQLenTable 1}

Pr1646v2EthPortSwFOutQLenEntry ::=
   SEQUENCE
      {
      pr1646v2EthPortSwFOutQLenGlobalIx
         GlobalIndex,
      pr1646v2EthPortSwFOutQLenValue
         Gauge32
      }

pr1646v2EthPortSwFOutQLenGlobalIx OBJECT-TYPE
   SYNTAX      GlobalIndex
   MAX-ACCESS  not-accessible
   STATUS      current
   DESCRIPTION
      "The value of the tlsCntTreeGlobalIndex of the MANAGED OBJECT."
   ::= {pr1646v2EthPortSwFOutQLenEntry 10}

pr1646v2EthPortSwFOutQLenValue OBJECT-TYPE
   SYNTAX      Gauge32
   MAX-ACCESS  read-only
   STATUS      current
   DESCRIPTION
      "Path: swPort.performance.ifOutQLen

       32 bit unsigned gauge value."
   ::= {pr1646v2EthPortSwFOutQLenEntry 2147483648}


pr1646v2EthPortSwFOutDropEx OBJECT IDENTIFIER ::= {pr1646v2EthPortSwF 127}

pr1646v2EthPortSwFOutDropExTable OBJECT-TYPE
   SYNTAX      SEQUENCE OF Pr1646v2EthPortSwFOutDropExEntry
   MAX-ACCESS  not-accessible
   STATUS      current
   DESCRIPTION
      "ifOutDiscards"
   ::= {pr1646v2EthPortSwFOutDropEx 1}

pr1646v2EthPortSwFOutDropExEntry OBJECT-TYPE
   SYNTAX      Pr1646v2EthPortSwFOutDropExEntry
   MAX-ACCESS  not-accessible
   STATUS      current
   DESCRIPTION
      ""
   INDEX      { pr1646v2EthPortSwFOutDropExGlobalIx }
   ::= {pr1646v2EthPortSwFOutDropExTable 1}

Pr1646v2EthPortSwFOutDropExEntry ::=
   SEQUENCE
      {
      pr1646v2EthPortSwFOutDropExGlobalIx
         GlobalIndex,
      pr1646v2EthPortSwFOutDropExValue
         Counter64
      }

pr1646v2EthPortSwFOutDropExGlobalIx OBJECT-TYPE
   SYNTAX      GlobalIndex
   MAX-ACCESS  not-accessible
   STATUS      current
   DESCRIPTION
      "The value of the tlsCntTreeGlobalIndex of the MANAGED OBJECT."
   ::= {pr1646v2EthPortSwFOutDropExEntry 10}

pr1646v2EthPortSwFOutDropExValue OBJECT-TYPE
   SYNTAX      Counter64
   MAX-ACCESS  read-only
   STATUS      current
   DESCRIPTION
      "Path: swPort.performance.ifOutDropLevelExceeded

       64 bit unsigned wrappable counter."
   ::= {pr1646v2EthPortSwFOutDropExEntry 2147483648}


pr1646v2EthPortSwFOutDropNoArp OBJECT IDENTIFIER ::= {pr1646v2EthPortSwF 134}

pr1646v2EthPortSwFOutDropNoArpTable OBJECT-TYPE
   SYNTAX      SEQUENCE OF Pr1646v2EthPortSwFOutDropNoArpEntry
   MAX-ACCESS  not-accessible
   STATUS      current
   DESCRIPTION
      "ifOutDiscards"
   ::= {pr1646v2EthPortSwFOutDropNoArp 1}

pr1646v2EthPortSwFOutDropNoArpEntry OBJECT-TYPE
   SYNTAX      Pr1646v2EthPortSwFOutDropNoArpEntry
   MAX-ACCESS  not-accessible
   STATUS      current
   DESCRIPTION
      ""
   INDEX      { pr1646v2EthPortSwFOutDropNoArpGlobalIx }
   ::= {pr1646v2EthPortSwFOutDropNoArpTable 1}

Pr1646v2EthPortSwFOutDropNoArpEntry ::=
   SEQUENCE
      {
      pr1646v2EthPortSwFOutDropNoArpGlobalIx
         GlobalIndex,
      pr1646v2EthPortSwFOutDropNoArpValue
         Counter64
      }

pr1646v2EthPortSwFOutDropNoArpGlobalIx OBJECT-TYPE
   SYNTAX      GlobalIndex
   MAX-ACCESS  not-accessible
   STATUS      current
   DESCRIPTION
      "The value of the tlsCntTreeGlobalIndex of the MANAGED OBJECT."
   ::= {pr1646v2EthPortSwFOutDropNoArpEntry 10}

pr1646v2EthPortSwFOutDropNoArpValue OBJECT-TYPE
   SYNTAX      Counter64
   MAX-ACCESS  read-only
   STATUS      current
   DESCRIPTION
      "Path: swPort.performance.ifOutDiscardsNoArp

       64 bit unsigned wrappable counter."
   ::= {pr1646v2EthPortSwFOutDropNoArpEntry 2147483648}


pr1646v2EthPortSwFOutDropFilter OBJECT IDENTIFIER ::= {pr1646v2EthPortSwF 138}

pr1646v2EthPortSwFOutDropFilterTable OBJECT-TYPE
   SYNTAX      SEQUENCE OF Pr1646v2EthPortSwFOutDropFilterEntry
   MAX-ACCESS  not-accessible
   STATUS      current
   DESCRIPTION
      "ifOutDiscards"
   ::= {pr1646v2EthPortSwFOutDropFilter 1}

pr1646v2EthPortSwFOutDropFilterEntry OBJECT-TYPE
   SYNTAX      Pr1646v2EthPortSwFOutDropFilterEntry
   MAX-ACCESS  not-accessible
   STATUS      current
   DESCRIPTION
      ""
   INDEX      { pr1646v2EthPortSwFOutDropFilterGlobalIx }
   ::= {pr1646v2EthPortSwFOutDropFilterTable 1}

Pr1646v2EthPortSwFOutDropFilterEntry ::=
   SEQUENCE
      {
      pr1646v2EthPortSwFOutDropFilterGlobalIx
         GlobalIndex,
      pr1646v2EthPortSwFOutDropFilterValue
         Counter64
      }

pr1646v2EthPortSwFOutDropFilterGlobalIx OBJECT-TYPE
   SYNTAX      GlobalIndex
   MAX-ACCESS  not-accessible
   STATUS      current
   DESCRIPTION
      "The value of the tlsCntTreeGlobalIndex of the MANAGED OBJECT."
   ::= {pr1646v2EthPortSwFOutDropFilterEntry 10}

pr1646v2EthPortSwFOutDropFilterValue OBJECT-TYPE
   SYNTAX      Counter64
   MAX-ACCESS  read-only
   STATUS      current
   DESCRIPTION
      "Path: swPort.performance.ifOutDiscardsFilter

       64 bit unsigned wrappable counter."
   ::= {pr1646v2EthPortSwFOutDropFilterEntry 2147483648}


pr1646v2EthPortSwFOutQueues OBJECT IDENTIFIER ::= {pr1646v2EthPortSwF 129}

pr1646v2EthPortSwFOutQueuesSSCTable OBJECT-TYPE
   SYNTAX      SEQUENCE OF Pr1646v2EthPortSwFOutQueuesEntry
   MAX-ACCESS  not-accessible
   STATUS      current
   DESCRIPTION
      "Queue Lengths"
   ::= {pr1646v2EthPortSwFOutQueues 1}

pr1646v2EthPortSwFOutQueuesEntry OBJECT-TYPE
   SYNTAX      Pr1646v2EthPortSwFOutQueuesEntry
   MAX-ACCESS  not-accessible
   STATUS      current
   DESCRIPTION
      ""
   INDEX      { pr1646v2EthPortSwFOutQueuesGlobalIx,
                pr1646v2EthPortSwFOutQueuesTableIx }
   ::= {pr1646v2EthPortSwFOutQueuesSSCTable 1}

Pr1646v2EthPortSwFOutQueuesEntry ::=
   SEQUENCE
      {
      pr1646v2EthPortSwFOutQueuesGlobalIx
         GlobalIndex,
      pr1646v2EthPortSwFOutQueuesTableIx
         TableIndex,
      pr1646v2EthPortSwFOutQueuesName
         INTEGER,
      pr1646v2EthPortSwFOutQueuesLength
         Integer32,
      pr1646v2EthPortSwFOutQueuesOctetLength
         Integer32,
      pr1646v2EthPortSwFOutQueuesRedLength
         Integer32,
      pr1646v2EthPortSwFOutQueuesPacketsTotal
         Counter64,
      pr1646v2EthPortSwFOutQueuesPacketsDirectTx
         Counter64,
      pr1646v2EthPortSwFOutQueuesPacketsQueued
         Counter64,
      pr1646v2EthPortSwFOutQueuesPacketsDropped
         Counter64,
      pr1646v2EthPortSwFOutQueuesPacketsRedDropped
         Counter64,
      pr1646v2EthPortSwFOutQueuesPacketsCirTx
         Counter64,
      pr1646v2EthPortSwFOutQueuesPacketsEirTx
         Counter64,
      pr1646v2EthPortSwFOutQueuesPacketsViolateTx
         Counter64,
      pr1646v2EthPortSwFOutQueuesOctetsTotal
         Counter64,
      pr1646v2EthPortSwFOutQueuesOctetsDirectTx
         Counter64,
      pr1646v2EthPortSwFOutQueuesOctetsQueued
         Counter64,
      pr1646v2EthPortSwFOutQueuesOctetsDropped
         Counter64,
      pr1646v2EthPortSwFOutQueuesOctetsRedDropped
         Counter64,
      pr1646v2EthPortSwFOutQueuesOctetsCirTx
         Counter64,
      pr1646v2EthPortSwFOutQueuesOctetsEirTx
         Counter64,
      pr1646v2EthPortSwFOutQueuesOctetsViolateTx
         Counter64,
      pr1646v2EthPortSwFOutQueuesOctetsBandwidth15sec
         Integer32,
      pr1646v2EthPortSwFOutQueuesOctetsBandwidth30sec
         Integer32,
      pr1646v2EthPortSwFOutQueuesOctetsBandwidth1min
         Integer32,
      pr1646v2EthPortSwFOutQueuesOctetsBandwidth2min
         Integer32,
      pr1646v2EthPortSwFOutQueuesOctetsBandwidth5min
         Integer32
      }

pr1646v2EthPortSwFOutQueuesGlobalIx OBJECT-TYPE
   SYNTAX      GlobalIndex
   MAX-ACCESS  not-accessible
   STATUS      current
   DESCRIPTION
      "The value of the tlsCntTreeGlobalIndex of the MANAGED OBJECT."
   ::= {pr1646v2EthPortSwFOutQueuesEntry 10}

pr1646v2EthPortSwFOutQueuesTableIx OBJECT-TYPE
   SYNTAX      TableIndex
   MAX-ACCESS  not-accessible
   STATUS      current
   DESCRIPTION
      ""
   ::= {pr1646v2EthPortSwFOutQueuesEntry 11}

pr1646v2EthPortSwFOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwFOutQueuesEntry 16777216}

pr1646v2EthPortSwFOutQueuesLength OBJECT-TYPE
   SYNTAX      Integer32
   MAX-ACCESS  read-only
   STATUS      current
   DESCRIPTION
      "Path: swPort.performance.ifOutPriorityQueues.length"
   ::= {pr1646v2EthPortSwFOutQueuesEntry 33554432}

pr1646v2EthPortSwFOutQueuesOctetLength OBJECT-TYPE
   SYNTAX      Integer32
   MAX-ACCESS  read-only
   STATUS      current
   DESCRIPTION
      "Path: swPort.performance.ifOutPriorityQueues.octetLength"
   ::= {pr1646v2EthPortSwFOutQueuesEntry 150994944}

pr1646v2EthPortSwFOutQueuesRedLength OBJECT-TYPE
   SYNTAX      Integer32
   MAX-ACCESS  read-only
   STATUS      current
   DESCRIPTION
      "Path: swPort.performance.ifOutPriorityQueues.redLength"
   ::= {pr1646v2EthPortSwFOutQueuesEntry 134217728}

pr1646v2EthPortSwFOutQueuesPacketsTotal OBJECT-TYPE
   SYNTAX      Counter64
   MAX-ACCESS  read-only
   STATUS      current
   DESCRIPTION
      "Path: swPort.performance.ifOutPriorityQueues.packets.total

       64 bit unsigned wrappable counter."
   ::= {pr1646v2EthPortSwFOutQueuesEntry 50790400}

pr1646v2EthPortSwFOutQueuesPacketsDirectTx OBJECT-TYPE
   SYNTAX      Counter64
   MAX-ACCESS  read-only
   STATUS      current
   DESCRIPTION
      "Path: swPort.performance.ifOutPriorityQueues.packets.directTx

       64 bit unsigned wrappable counter."
   ::= {pr1646v2EthPortSwFOutQueuesEntry 50397184}

pr1646v2EthPortSwFOutQueuesPacketsQueued OBJECT-TYPE
   SYNTAX      Counter64
   MAX-ACCESS  read-only
   STATUS      current
   DESCRIPTION
      "Path: swPort.performance.ifOutPriorityQueues.packets.queued

       64 bit unsigned wrappable counter."
   ::= {pr1646v2EthPortSwFOutQueuesEntry 50462720}

pr1646v2EthPortSwFOutQueuesPacketsDropped OBJECT-TYPE
   SYNTAX      Counter64
   MAX-ACCESS  read-only
   STATUS      current
   DESCRIPTION
      "Path: swPort.performance.ifOutPriorityQueues.packets.dropped

       64 bit unsigned wrappable counter."
   ::= {pr1646v2EthPortSwFOutQueuesEntry 50528256}

pr1646v2EthPortSwFOutQueuesPacketsRedDropped OBJECT-TYPE
   SYNTAX      Counter64
   MAX-ACCESS  read-only
   STATUS      current
   DESCRIPTION
      "Path: swPort.performance.ifOutPriorityQueues.packets.redDropped

       64 bit unsigned wrappable counter."
   ::= {pr1646v2EthPortSwFOutQueuesEntry 50724864}

pr1646v2EthPortSwFOutQueuesPacketsCirTx OBJECT-TYPE
   SYNTAX      Counter64
   MAX-ACCESS  read-only
   STATUS      current
   DESCRIPTION
      "Path: swPort.performance.ifOutPriorityQueues.packets.cirTx

       64 bit unsigned wrappable counter."
   ::= {pr1646v2EthPortSwFOutQueuesEntry 50593792}

pr1646v2EthPortSwFOutQueuesPacketsEirTx OBJECT-TYPE
   SYNTAX      Counter64
   MAX-ACCESS  read-only
   STATUS      current
   DESCRIPTION
      "Path: swPort.performance.ifOutPriorityQueues.packets.eirTx

       64 bit unsigned wrappable counter."
   ::= {pr1646v2EthPortSwFOutQueuesEntry 50659328}

pr1646v2EthPortSwFOutQueuesPacketsViolateTx OBJECT-TYPE
   SYNTAX      Counter64
   MAX-ACCESS  read-only
   STATUS      current
   DESCRIPTION
      "Path: swPort.performance.ifOutPriorityQueues.packets.violateTx

       64 bit unsigned wrappable counter."
   ::= {pr1646v2EthPortSwFOutQueuesEntry 50855936}

pr1646v2EthPortSwFOutQueuesOctetsTotal OBJECT-TYPE
   SYNTAX      Counter64
   MAX-ACCESS  read-only
   STATUS      current
   DESCRIPTION
      "Path: swPort.performance.ifOutPriorityQueues.octets.total

       64 bit unsigned wrappable counter."
   ::= {pr1646v2EthPortSwFOutQueuesEntry 67567616}

pr1646v2EthPortSwFOutQueuesOctetsDirectTx OBJECT-TYPE
   SYNTAX      Counter64
   MAX-ACCESS  read-only
   STATUS      current
   DESCRIPTION
      "Path: swPort.performance.ifOutPriorityQueues.octets.directTx

       64 bit unsigned wrappable counter."
   ::= {pr1646v2EthPortSwFOutQueuesEntry 67174400}

pr1646v2EthPortSwFOutQueuesOctetsQueued OBJECT-TYPE
   SYNTAX      Counter64
   MAX-ACCESS  read-only
   STATUS      current
   DESCRIPTION
      "Path: swPort.performance.ifOutPriorityQueues.octets.queued

       64 bit unsigned wrappable counter."
   ::= {pr1646v2EthPortSwFOutQueuesEntry 67239936}

pr1646v2EthPortSwFOutQueuesOctetsDropped OBJECT-TYPE
   SYNTAX      Counter64
   MAX-ACCESS  read-only
   STATUS      current
   DESCRIPTION
      "Path: swPort.performance.ifOutPriorityQueues.octets.dropped

       64 bit unsigned wrappable counter."
   ::= {pr1646v2EthPortSwFOutQueuesEntry 67305472}

pr1646v2EthPortSwFOutQueuesOctetsRedDropped OBJECT-TYPE
   SYNTAX      Counter64
   MAX-ACCESS  read-only
   STATUS      current
   DESCRIPTION
      "Path: swPort.performance.ifOutPriorityQueues.octets.redDropped

       64 bit unsigned wrappable counter."
   ::= {pr1646v2EthPortSwFOutQueuesEntry 67502080}

pr1646v2EthPortSwFOutQueuesOctetsCirTx OBJECT-TYPE
   SYNTAX      Counter64
   MAX-ACCESS  read-only
   STATUS      current
   DESCRIPTION
      "Path: swPort.performance.ifOutPriorityQueues.octets.cirTx

       64 bit unsigned wrappable counter."
   ::= {pr1646v2EthPortSwFOutQueuesEntry 67371008}

pr1646v2EthPortSwFOutQueuesOctetsEirTx OBJECT-TYPE
   SYNTAX      Counter64
   MAX-ACCESS  read-only
   STATUS      current
   DESCRIPTION
      "Path: swPort.performance.ifOutPriorityQueues.octets.eirTx

       64 bit unsigned wrappable counter."
   ::= {pr1646v2EthPortSwFOutQueuesEntry 67436544}

pr1646v2EthPortSwFOutQueuesOctetsViolateTx OBJECT-TYPE
   SYNTAX      Counter64
   MAX-ACCESS  read-only
   STATUS      current
   DESCRIPTION
      "Path: swPort.performance.ifOutPriorityQueues.octets.violateTx

       64 bit unsigned wrappable counter."
   ::= {pr1646v2EthPortSwFOutQueuesEntry 67633152}

pr1646v2EthPortSwFOutQueuesOctetsBandwidth15sec OBJECT-TYPE
   SYNTAX      Integer32
   MAX-ACCESS  read-only
   STATUS      current
   DESCRIPTION
      "Path: swPort.performance.ifOutPriorityQueues.octets.bandwidth.15sec

       unit name = bps
       formula = 8 * ; 8 /"
   ::= {pr1646v2EthPortSwFOutQueuesEntry 70386944}

pr1646v2EthPortSwFOutQueuesOctetsBandwidth30sec OBJECT-TYPE
   SYNTAX      Integer32
   MAX-ACCESS  read-only
   STATUS      current
   DESCRIPTION
      "Path: swPort.performance.ifOutPriorityQueues.octets.bandwidth.30sec

       unit name = bps
       formula = 8 * ; 8 /"
   ::= {pr1646v2EthPortSwFOutQueuesEntry 70388224}

pr1646v2EthPortSwFOutQueuesOctetsBandwidth1min OBJECT-TYPE
   SYNTAX      Integer32
   MAX-ACCESS  read-only
   STATUS      current
   DESCRIPTION
      "Path: swPort.performance.ifOutPriorityQueues.octets.bandwidth.1min

       unit name = bps
       formula = 8 * ; 8 /"
   ::= {pr1646v2EthPortSwFOutQueuesEntry 70390784}

pr1646v2EthPortSwFOutQueuesOctetsBandwidth2min OBJECT-TYPE
   SYNTAX      Integer32
   MAX-ACCESS  read-only
   STATUS      current
   DESCRIPTION
      "Path: swPort.performance.ifOutPriorityQueues.octets.bandwidth.2min

       unit name = bps
       formula = 8 * ; 8 /"
   ::= {pr1646v2EthPortSwFOutQueuesEntry 70395904}

pr1646v2EthPortSwFOutQueuesOctetsBandwidth5min OBJECT-TYPE
   SYNTAX      Integer32
   MAX-ACCESS  read-only
   STATUS      current
   DESCRIPTION
      "Path: swPort.performance.ifOutPriorityQueues.octets.bandwidth.5min

       unit name = bps
       formula = 8 * ; 8 /"
   ::= {pr1646v2EthPortSwFOutQueuesEntry 70411264}

pr1646v2EthPortSwFOutQueuesH2Performance OBJECT-TYPE
   SYNTAX      SEQUENCE OF Pr1646v2EthPortSwFOutQueuesH2PerformanceEntry
   MAX-ACCESS  not-accessible
   STATUS      current
   DESCRIPTION
      ""
   ::= {pr1646v2EthPortSwFOutQueues 83886080}

pr1646v2EthPortSwFOutQueuesH2PerformanceEntry OBJECT-TYPE
   SYNTAX      Pr1646v2EthPortSwFOutQueuesH2PerformanceEntry
   MAX-ACCESS  not-accessible
   STATUS      current
   DESCRIPTION
      ""
   INDEX      { pr1646v2EthPortSwFOutQueuesH2PerformanceGlobalIx,
                pr1646v2EthPortSwFOutQueuesTableIx,
                pr1646v2EthPortSwFOutQueuesH2PerformanceTableIx }
   ::= {pr1646v2EthPortSwFOutQueuesH2Performance 1}

Pr1646v2EthPortSwFOutQueuesH2PerformanceEntry ::=
   SEQUENCE
      {
      pr1646v2EthPortSwFOutQueuesH2PerformanceGlobalIx
         GlobalIndex,
      pr1646v2EthPortSwFOutQueuesH2PerformanceTableIx
         TableIndex,
      pr1646v2EthPortSwFOutQueuesH2PerformanceSysUpTime
         TimeTicks,
      pr1646v2EthPortSwFOutQueuesH2PerformanceTotPkts
         Counter64,
      pr1646v2EthPortSwFOutQueuesH2PerformanceDirTxPkts
         Counter64,
      pr1646v2EthPortSwFOutQueuesH2PerformanceQdPkts
         Counter64,
      pr1646v2EthPortSwFOutQueuesH2PerformanceDropPkts
         Counter64,
      pr1646v2EthPortSwFOutQueuesH2PerformanceRDropPkts
         Counter64,
      pr1646v2EthPortSwFOutQueuesH2PerformanceCirTxPkts
         Counter64,
      pr1646v2EthPortSwFOutQueuesH2PerformanceEirTxPkts
         Counter64,
      pr1646v2EthPortSwFOutQueuesH2PerformanceViolTxPkts
         Counter64,
      pr1646v2EthPortSwFOutQueuesH2PerformanceTotOcts
         Counter64,
      pr1646v2EthPortSwFOutQueuesH2PerformanceDirTxOcts
         Counter64,
      pr1646v2EthPortSwFOutQueuesH2PerformanceQdOcts
         Counter64,
      pr1646v2EthPortSwFOutQueuesH2PerformanceDropOcts
         Counter64,
      pr1646v2EthPortSwFOutQueuesH2PerformanceRDropOcts
         Counter64,
      pr1646v2EthPortSwFOutQueuesH2PerformanceCirTxOcts
         Counter64,
      pr1646v2EthPortSwFOutQueuesH2PerformanceEirTxOcts
         Counter64,
      pr1646v2EthPortSwFOutQueuesH2PerformanceViolTxOcts
         Counter64,
      pr1646v2EthPortSwFOutQueuesH2PerformanceBandwidth
         Integer32
      }

pr1646v2EthPortSwFOutQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFOutQueuesH2PerformanceEntry 10}

pr1646v2EthPortSwFOutQueuesH2PerformanceTableIx OBJECT-TYPE
   SYNTAX      TableIndex
   MAX-ACCESS  not-accessible
   STATUS      current
   DESCRIPTION
      ""
   ::= {pr1646v2EthPortSwFOutQueuesH2PerformanceEntry 11}

pr1646v2EthPortSwFOutQueuesH2PerformanceSysUpTime OBJECT-TYPE
   SYNTAX      TimeTicks
   MAX-ACCESS  read-only
   STATUS      current
   DESCRIPTION
      "Path: swPort.performance.ifOutPriorityQueues.h2Performance.sysUpTime

       Time in centi-second."
   ::= {pr1646v2EthPortSwFOutQueuesH2PerformanceEntry 16777216}

pr1646v2EthPortSwFOutQueuesH2PerformanceTotPkts OBJECT-TYPE
   SYNTAX      Counter64
   MAX-ACCESS  read-only
   STATUS      current
   DESCRIPTION
      "Path: swPort.performance.ifOutPriorityQueues.h2Performance.totalPkts

       64 bit unsigned wrappable counter."
   ::= {pr1646v2EthPortSwFOutQueuesH2PerformanceEntry 234881024}

pr1646v2EthPortSwFOutQueuesH2PerformanceDirTxPkts OBJECT-TYPE
   SYNTAX      Counter64
   MAX-ACCESS  read-only
   STATUS      current
   DESCRIPTION
      "Path: swPort.performance.ifOutPriorityQueues.h2Performance.directTxPkts

       64 bit unsigned wrappable counter."
   ::= {pr1646v2EthPortSwFOutQueuesH2PerformanceEntry 33554432}

pr1646v2EthPortSwFOutQueuesH2PerformanceQdPkts OBJECT-TYPE
   SYNTAX      Counter64
   MAX-ACCESS  read-only
   STATUS      current
   DESCRIPTION
      "Path: swPort.performance.ifOutPriorityQueues.h2Performance.queuedPkts

       64 bit unsigned wrappable counter."
   ::= {pr1646v2EthPortSwFOutQueuesH2PerformanceEntry 50331648}

pr1646v2EthPortSwFOutQueuesH2PerformanceDropPkts OBJECT-TYPE
   SYNTAX      Counter64
   MAX-ACCESS  read-only
   STATUS      current
   DESCRIPTION
      "Path: swPort.performance.ifOutPriorityQueues.h2Performance.droppedPkts

       64 bit unsigned wrappable counter."
   ::= {pr1646v2EthPortSwFOutQueuesH2PerformanceEntry 67108864}

pr1646v2EthPortSwFOutQueuesH2PerformanceRDropPkts OBJECT-TYPE
   SYNTAX      Counter64
   MAX-ACCESS  read-only
   STATUS      current
   DESCRIPTION
      "Path: swPort.performance.ifOutPriorityQueues.h2Performance.redDroppedPkts

       64 bit unsigned wrappable counter."
   ::= {pr1646v2EthPortSwFOutQueuesH2PerformanceEntry 201326592}

pr1646v2EthPortSwFOutQueuesH2PerformanceCirTxPkts OBJECT-TYPE
   SYNTAX      Counter64
   MAX-ACCESS  read-only
   STATUS      current
   DESCRIPTION
      "Path: swPort.performance.ifOutPriorityQueues.h2Performance.cirTxPkts

       64 bit unsigned wrappable counter."
   ::= {pr1646v2EthPortSwFOutQueuesH2PerformanceEntry 83886080}

pr1646v2EthPortSwFOutQueuesH2PerformanceEirTxPkts OBJECT-TYPE
   SYNTAX      Counter64
   MAX-ACCESS  read-only
   STATUS      current
   DESCRIPTION
      "Path: swPort.performance.ifOutPriorityQueues.h2Performance.eirTxPkts

       64 bit unsigned wrappable counter."
   ::= {pr1646v2EthPortSwFOutQueuesH2PerformanceEntry 100663296}

pr1646v2EthPortSwFOutQueuesH2PerformanceViolTxPkts OBJECT-TYPE
   SYNTAX      Counter64
   MAX-ACCESS  read-only
   STATUS      current
   DESCRIPTION
      "Path: swPort.performance.ifOutPriorityQueues.h2Performance.violateTxPkts

       64 bit unsigned wrappable counter."
   ::= {pr1646v2EthPortSwFOutQueuesH2PerformanceEntry 301989888}

pr1646v2EthPortSwFOutQueuesH2PerformanceTotOcts OBJECT-TYPE
   SYNTAX      Counter64
   MAX-ACCESS  read-only
   STATUS      current
   DESCRIPTION
      "Path: swPort.performance.ifOutPriorityQueues.h2Performance.totalOctets

       64 bit unsigned wrappable counter."
   ::= {pr1646v2EthPortSwFOutQueuesH2PerformanceEntry 251658240}

pr1646v2EthPortSwFOutQueuesH2PerformanceDirTxOcts OBJECT-TYPE
   SYNTAX      Counter64
   MAX-ACCESS  read-only
   STATUS      current
   DESCRIPTION
      "Path: swPort.performance.ifOutPriorityQueues.h2Performance.directTxOctets

       64 bit unsigned wrappable counter."
   ::= {pr1646v2EthPortSwFOutQueuesH2PerformanceEntry 117440512}

pr1646v2EthPortSwFOutQueuesH2PerformanceQdOcts OBJECT-TYPE
   SYNTAX      Counter64
   MAX-ACCESS  read-only
   STATUS      current
   DESCRIPTION
      "Path: swPort.performance.ifOutPriorityQueues.h2Performance.queuedOctets

       64 bit unsigned wrappable counter."
   ::= {pr1646v2EthPortSwFOutQueuesH2PerformanceEntry 134217728}

pr1646v2EthPortSwFOutQueuesH2PerformanceDropOcts OBJECT-TYPE
   SYNTAX      Counter64
   MAX-ACCESS  read-only
   STATUS      current
   DESCRIPTION
      "Path: swPort.performance.ifOutPriorityQueues.h2Performance.droppedOctets

       64 bit unsigned wrappable counter."
   ::= {pr1646v2EthPortSwFOutQueuesH2PerformanceEntry 150994944}

pr1646v2EthPortSwFOutQueuesH2PerformanceRDropOcts OBJECT-TYPE
   SYNTAX      Counter64
   MAX-ACCESS  read-only
   STATUS      current
   DESCRIPTION
      "Path: swPort.performance.ifOutPriorityQueues.h2Performance.redDroppedOctets

       64 bit unsigned wrappable counter."
   ::= {pr1646v2EthPortSwFOutQueuesH2PerformanceEntry 218103808}

pr1646v2EthPortSwFOutQueuesH2PerformanceCirTxOcts OBJECT-TYPE
   SYNTAX      Counter64
   MAX-ACCESS  read-only
   STATUS      current
   DESCRIPTION
      "Path: swPort.performance.ifOutPriorityQueues.h2Performance.cirTxOctets

       64 bit unsigned wrappable counter."
   ::= {pr1646v2EthPortSwFOutQueuesH2PerformanceEntry 167772160}

pr1646v2EthPortSwFOutQueuesH2PerformanceEirTxOcts OBJECT-TYPE
   SYNTAX      Counter64
   MAX-ACCESS  read-only
   STATUS      current
   DESCRIPTION
      "Path: swPort.performance.ifOutPriorityQueues.h2Performance.eirTxOctets

       64 bit unsigned wrappable counter."
   ::= {pr1646v2EthPortSwFOutQueuesH2PerformanceEntry 184549376}

pr1646v2EthPortSwFOutQueuesH2PerformanceViolTxOcts OBJECT-TYPE
   SYNTAX      Counter64
   MAX-ACCESS  read-only
   STATUS      current
   DESCRIPTION
      "Path: swPort.performance.ifOutPriorityQueues.h2Performance.violateTxOctets

       64 bit unsigned wrappable counter."
   ::= {pr1646v2EthPortSwFOutQueuesH2PerformanceEntry 318767104}

pr1646v2EthPortSwFOutQueuesH2PerformanceBandwidth OBJECT-TYPE
   SYNTAX      Integer32
   MAX-ACCESS  read-only
   STATUS      current
   DESCRIPTION
      "Path: swPort.performance.ifOutPriorityQueues.h2Performance.bandwidth

       unit name = bps
       formula = 8 * ; 8 /"
   ::= {pr1646v2EthPortSwFOutQueuesH2PerformanceEntry 268435456}

pr1646v2EthPortSwFOutQueuesH24Performance OBJECT-TYPE
   SYNTAX      SEQUENCE OF Pr1646v2EthPortSwFOutQueuesH24PerformanceEntry
   MAX-ACCESS  not-accessible
   STATUS      current
   DESCRIPTION
      ""
   ::= {pr1646v2EthPortSwFOutQueues 100663296}

pr1646v2EthPortSwFOutQueuesH24PerformanceEntry OBJECT-TYPE
   SYNTAX      Pr1646v2EthPortSwFOutQueuesH24PerformanceEntry
   MAX-ACCESS  not-accessible
   STATUS      current
   DESCRIPTION
      ""
   INDEX      { pr1646v2EthPortSwFOutQueuesH24PerformanceGlobalIx,
                pr1646v2EthPortSwFOutQueuesTableIx,
                pr1646v2EthPortSwFOutQueuesH24PerformanceTableIx }
   ::= {pr1646v2EthPortSwFOutQueuesH24Performance 1}

Pr1646v2EthPortSwFOutQueuesH24PerformanceEntry ::=
   SEQUENCE
      {
      pr1646v2EthPortSwFOutQueuesH24PerformanceGlobalIx
         GlobalIndex,
      pr1646v2EthPortSwFOutQueuesH24PerformanceTableIx
         TableIndex,
      pr1646v2EthPortSwFOutQueuesH24PerformanceSysUpTime
         TimeTicks,
      pr1646v2EthPortSwFOutQueuesH24PerformanceTotPkts
         Counter64,
      pr1646v2EthPortSwFOutQueuesH24PerformanceDirTxPkts
         Counter64,
      pr1646v2EthPortSwFOutQueuesH24PerformanceQdPkts
         Counter64,
      pr1646v2EthPortSwFOutQueuesH24PerformanceDropPkts
         Counter64,
      pr1646v2EthPortSwFOutQueuesH24PerformanceRDropPkts
         Counter64,
      pr1646v2EthPortSwFOutQueuesH24PerformanceCirTxPkts
         Counter64,
      pr1646v2EthPortSwFOutQueuesH24PerformanceEirTxPkts
         Counter64,
      pr1646v2EthPortSwFOutQueuesH24PerformanceViolTxPkts
         Counter64,
      pr1646v2EthPortSwFOutQueuesH24PerformanceTotOcts
         Counter64,
      pr1646v2EthPortSwFOutQueuesH24PerformanceDirTxOcts
         Counter64,
      pr1646v2EthPortSwFOutQueuesH24PerformanceQdOcts
         Counter64,
      pr1646v2EthPortSwFOutQueuesH24PerformanceDropOcts
         Counter64,
      pr1646v2EthPortSwFOutQueuesH24PerformanceRDropOcts
         Counter64,
      pr1646v2EthPortSwFOutQueuesH24PerformanceCirTxOcts
         Counter64,
      pr1646v2EthPortSwFOutQueuesH24PerformanceEirTxOcts
         Counter64,
      pr1646v2EthPortSwFOutQueuesH24PerformanceViolTxOcts
         Counter64,
      pr1646v2EthPortSwFOutQueuesH24PerformanceBandwidth
         Integer32
      }

pr1646v2EthPortSwFOutQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFOutQueuesH24PerformanceEntry 10}

pr1646v2EthPortSwFOutQueuesH24PerformanceTableIx OBJECT-TYPE
   SYNTAX      TableIndex
   MAX-ACCESS  not-accessible
   STATUS      current
   DESCRIPTION
      ""
   ::= {pr1646v2EthPortSwFOutQueuesH24PerformanceEntry 11}

pr1646v2EthPortSwFOutQueuesH24PerformanceSysUpTime OBJECT-TYPE
   SYNTAX      TimeTicks
   MAX-ACCESS  read-only
   STATUS      current
   DESCRIPTION
      "Path: swPort.performance.ifOutPriorityQueues.h24Performance.sysUpTime

       Time in centi-second."
   ::= {pr1646v2EthPortSwFOutQueuesH24PerformanceEntry 16777216}

pr1646v2EthPortSwFOutQueuesH24PerformanceTotPkts OBJECT-TYPE
   SYNTAX      Counter64
   MAX-ACCESS  read-only
   STATUS      current
   DESCRIPTION
      "Path: swPort.performance.ifOutPriorityQueues.h24Performance.totalPkts

       64 bit unsigned wrappable counter."
   ::= {pr1646v2EthPortSwFOutQueuesH24PerformanceEntry 234881024}

pr1646v2EthPortSwFOutQueuesH24PerformanceDirTxPkts OBJECT-TYPE
   SYNTAX      Counter64
   MAX-ACCESS  read-only
   STATUS      current
   DESCRIPTION
      "Path: swPort.performance.ifOutPriorityQueues.h24Performance.directTxPkts

       64 bit unsigned wrappable counter."
   ::= {pr1646v2EthPortSwFOutQueuesH24PerformanceEntry 33554432}

pr1646v2EthPortSwFOutQueuesH24PerformanceQdPkts OBJECT-TYPE
   SYNTAX      Counter64
   MAX-ACCESS  read-only
   STATUS      current
   DESCRIPTION
      "Path: swPort.performance.ifOutPriorityQueues.h24Performance.queuedPkts

       64 bit unsigned wrappable counter."
   ::= {pr1646v2EthPortSwFOutQueuesH24PerformanceEntry 50331648}

pr1646v2EthPortSwFOutQueuesH24PerformanceDropPkts OBJECT-TYPE
   SYNTAX      Counter64
   MAX-ACCESS  read-only
   STATUS      current
   DESCRIPTION
      "Path: swPort.performance.ifOutPriorityQueues.h24Performance.droppedPkts

       64 bit unsigned wrappable counter."
   ::= {pr1646v2EthPortSwFOutQueuesH24PerformanceEntry 67108864}

pr1646v2EthPortSwFOutQueuesH24PerformanceRDropPkts OBJECT-TYPE
   SYNTAX      Counter64
   MAX-ACCESS  read-only
   STATUS      current
   DESCRIPTION
      "Path: swPort.performance.ifOutPriorityQueues.h24Performance.redDroppedPkts

       64 bit unsigned wrappable counter."
   ::= {pr1646v2EthPortSwFOutQueuesH24PerformanceEntry 201326592}

pr1646v2EthPortSwFOutQueuesH24PerformanceCirTxPkts OBJECT-TYPE
   SYNTAX      Counter64
   MAX-ACCESS  read-only
   STATUS      current
   DESCRIPTION
      "Path: swPort.performance.ifOutPriorityQueues.h24Performance.cirTxPkts

       64 bit unsigned wrappable counter."
   ::= {pr1646v2EthPortSwFOutQueuesH24PerformanceEntry 83886080}

pr1646v2EthPortSwFOutQueuesH24PerformanceEirTxPkts OBJECT-TYPE
   SYNTAX      Counter64
   MAX-ACCESS  read-only
   STATUS      current
   DESCRIPTION
      "Path: swPort.performance.ifOutPriorityQueues.h24Performance.eirTxPkts

       64 bit unsigned wrappable counter."
   ::= {pr1646v2EthPortSwFOutQueuesH24PerformanceEntry 100663296}

pr1646v2EthPortSwFOutQueuesH24PerformanceViolTxPkts OBJECT-TYPE
   SYNTAX      Counter64
   MAX-ACCESS  read-only
   STATUS      current
   DESCRIPTION
      "Path: swPort.performance.ifOutPriorityQueues.h24Performance.violateTxPkts

       64 bit unsigned wrappable counter."
   ::= {pr1646v2EthPortSwFOutQueuesH24PerformanceEntry 301989888}

pr1646v2EthPortSwFOutQueuesH24PerformanceTotOcts OBJECT-TYPE
   SYNTAX      Counter64
   MAX-ACCESS  read-only
   STATUS      current
   DESCRIPTION
      "Path: swPort.performance.ifOutPriorityQueues.h24Performance.totalOctets

       64 bit unsigned wrappable counter."
   ::= {pr1646v2EthPortSwFOutQueuesH24PerformanceEntry 251658240}

pr1646v2EthPortSwFOutQueuesH24PerformanceDirTxOcts OBJECT-TYPE
   SYNTAX      Counter64
   MAX-ACCESS  read-only
   STATUS      current
   DESCRIPTION
      "Path: swPort.performance.ifOutPriorityQueues.h24Performance.directTxOctets

       64 bit unsigned wrappable counter."
   ::= {pr1646v2EthPortSwFOutQueuesH24PerformanceEntry 117440512}

pr1646v2EthPortSwFOutQueuesH24PerformanceQdOcts OBJECT-TYPE
   SYNTAX      Counter64
   MAX-ACCESS  read-only
   STATUS      current
   DESCRIPTION
      "Path: swPort.performance.ifOutPriorityQueues.h24Performance.queuedOctets

       64 bit unsigned wrappable counter."
   ::= {pr1646v2EthPortSwFOutQueuesH24PerformanceEntry 134217728}

pr1646v2EthPortSwFOutQueuesH24PerformanceDropOcts OBJECT-TYPE
   SYNTAX      Counter64
   MAX-ACCESS  read-only
   STATUS      current
   DESCRIPTION
      "Path: swPort.performance.ifOutPriorityQueues.h24Performance.droppedOctets

       64 bit unsigned wrappable counter."
   ::= {pr1646v2EthPortSwFOutQueuesH24PerformanceEntry 150994944}

pr1646v2EthPortSwFOutQueuesH24PerformanceRDropOcts OBJECT-TYPE
   SYNTAX      Counter64
   MAX-ACCESS  read-only
   STATUS      current
   DESCRIPTION
      "Path: swPort.performance.ifOutPriorityQueues.h24Performance.redDroppedOctets

       64 bit unsigned wrappable counter."
   ::= {pr1646v2EthPortSwFOutQueuesH24PerformanceEntry 218103808}

pr1646v2EthPortSwFOutQueuesH24PerformanceCirTxOcts OBJECT-TYPE
   SYNTAX      Counter64
   MAX-ACCESS  read-only
   STATUS      current
   DESCRIPTION
      "Path: swPort.performance.ifOutPriorityQueues.h24Performance.cirTxOctets

       64 bit unsigned wrappable counter."
   ::= {pr1646v2EthPortSwFOutQueuesH24PerformanceEntry 167772160}

pr1646v2EthPortSwFOutQueuesH24PerformanceEirTxOcts OBJECT-TYPE
   SYNTAX      Counter64
   MAX-ACCESS  read-only
   STATUS      current
   DESCRIPTION
      "Path: swPort.performance.ifOutPriorityQueues.h24Performance.eirTxOctets

       64 bit unsigned wrappable counter."
   ::= {pr1646v2EthPortSwFOutQueuesH24PerformanceEntry 184549376}

pr1646v2EthPortSwFOutQueuesH24PerformanceViolTxOcts OBJECT-TYPE
   SYNTAX      Counter64
   MAX-ACCESS  read-only
   STATUS      current
   DESCRIPTION
      "Path: swPort.performance.ifOutPriorityQueues.h24Performance.violateTxOctets

       64 bit unsigned wrappable counter."
   ::= {pr1646v2EthPortSwFOutQueuesH24PerformanceEntry 318767104}

pr1646v2EthPortSwFOutQueuesH24PerformanceBandwidth OBJECT-TYPE
   SYNTAX      Integer32
   MAX-ACCESS  read-only
   STATUS      current
   DESCRIPTION
      "Path: swPort.performance.ifOutPriorityQueues.h24Performance.bandwidth

       unit name = bps
       formula = 8 * ; 8 /"
   ::= {pr1646v2EthPortSwFOutQueuesH24PerformanceEntry 268435456}

pr1646v2EthPortSwFOutQueuesD7Performance OBJECT-TYPE
   SYNTAX      SEQUENCE OF Pr1646v2EthPortSwFOutQueuesD7PerformanceEntry
   MAX-ACCESS  not-accessible
   STATUS      current
   DESCRIPTION
      ""
   ::= {pr1646v2EthPortSwFOutQueues 117440512}

pr1646v2EthPortSwFOutQueuesD7PerformanceEntry OBJECT-TYPE
   SYNTAX      Pr1646v2EthPortSwFOutQueuesD7PerformanceEntry
   MAX-ACCESS  not-accessible
   STATUS      current
   DESCRIPTION
      ""
   INDEX      { pr1646v2EthPortSwFOutQueuesD7PerformanceGlobalIx,
                pr1646v2EthPortSwFOutQueuesTableIx,
                pr1646v2EthPortSwFOutQueuesD7PerformanceTableIx }
   ::= {pr1646v2EthPortSwFOutQueuesD7Performance 1}

Pr1646v2EthPortSwFOutQueuesD7PerformanceEntry ::=
   SEQUENCE
      {
      pr1646v2EthPortSwFOutQueuesD7PerformanceGlobalIx
         GlobalIndex,
      pr1646v2EthPortSwFOutQueuesD7PerformanceTableIx
         TableIndex,
      pr1646v2EthPortSwFOutQueuesD7PerformanceSysUpTime
         TimeTicks,
      pr1646v2EthPortSwFOutQueuesD7PerformanceTotPkts
         Counter64,
      pr1646v2EthPortSwFOutQueuesD7PerformanceDirTxPkts
         Counter64,
      pr1646v2EthPortSwFOutQueuesD7PerformanceQdPkts
         Counter64,
      pr1646v2EthPortSwFOutQueuesD7PerformanceDropPkts
         Counter64,
      pr1646v2EthPortSwFOutQueuesD7PerformanceRDropPkts
         Counter64,
      pr1646v2EthPortSwFOutQueuesD7PerformanceCirTxPkts
         Counter64,
      pr1646v2EthPortSwFOutQueuesD7PerformanceEirTxPkts
         Counter64,
      pr1646v2EthPortSwFOutQueuesD7PerformanceViolTxPkts
         Counter64,
      pr1646v2EthPortSwFOutQueuesD7PerformanceTotOcts
         Counter64,
      pr1646v2EthPortSwFOutQueuesD7PerformanceDirTxOcts
         Counter64,
      pr1646v2EthPortSwFOutQueuesD7PerformanceQdOcts
         Counter64,
      pr1646v2EthPortSwFOutQueuesD7PerformanceDropOcts
         Counter64,
      pr1646v2EthPortSwFOutQueuesD7PerformanceRDropOcts
         Counter64,
      pr1646v2EthPortSwFOutQueuesD7PerformanceCirTxOcts
         Counter64,
      pr1646v2EthPortSwFOutQueuesD7PerformanceEirTxOcts
         Counter64,
      pr1646v2EthPortSwFOutQueuesD7PerformanceViolTxOcts
         Counter64,
      pr1646v2EthPortSwFOutQueuesD7PerformanceBandwidth
         Integer32
      }

pr1646v2EthPortSwFOutQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFOutQueuesD7PerformanceEntry 10}

pr1646v2EthPortSwFOutQueuesD7PerformanceTableIx OBJECT-TYPE
   SYNTAX      TableIndex
   MAX-ACCESS  not-accessible
   STATUS      current
   DESCRIPTION
      ""
   ::= {pr1646v2EthPortSwFOutQueuesD7PerformanceEntry 11}

pr1646v2EthPortSwFOutQueuesD7PerformanceSysUpTime OBJECT-TYPE
   SYNTAX      TimeTicks
   MAX-ACCESS  read-only
   STATUS      current
   DESCRIPTION
      "Path: swPort.performance.ifOutPriorityQueues.d7Performance.sysUpTime

       Time in centi-second."
   ::= {pr1646v2EthPortSwFOutQueuesD7PerformanceEntry 16777216}

pr1646v2EthPortSwFOutQueuesD7PerformanceTotPkts OBJECT-TYPE
   SYNTAX      Counter64
   MAX-ACCESS  read-only
   STATUS      current
   DESCRIPTION
      "Path: swPort.performance.ifOutPriorityQueues.d7Performance.totalPkts

       64 bit unsigned wrappable counter."
   ::= {pr1646v2EthPortSwFOutQueuesD7PerformanceEntry 234881024}

pr1646v2EthPortSwFOutQueuesD7PerformanceDirTxPkts OBJECT-TYPE
   SYNTAX      Counter64
   MAX-ACCESS  read-only
   STATUS      current
   DESCRIPTION
      "Path: swPort.performance.ifOutPriorityQueues.d7Performance.directTxPkts

       64 bit unsigned wrappable counter."
   ::= {pr1646v2EthPortSwFOutQueuesD7PerformanceEntry 33554432}

pr1646v2EthPortSwFOutQueuesD7PerformanceQdPkts OBJECT-TYPE
   SYNTAX      Counter64
   MAX-ACCESS  read-only
   STATUS      current
   DESCRIPTION
      "Path: swPort.performance.ifOutPriorityQueues.d7Performance.queuedPkts

       64 bit unsigned wrappable counter."
   ::= {pr1646v2EthPortSwFOutQueuesD7PerformanceEntry 50331648}

pr1646v2EthPortSwFOutQueuesD7PerformanceDropPkts OBJECT-TYPE
   SYNTAX      Counter64
   MAX-ACCESS  read-only
   STATUS      current
   DESCRIPTION
      "Path: swPort.performance.ifOutPriorityQueues.d7Performance.droppedPkts

       64 bit unsigned wrappable counter."
   ::= {pr1646v2EthPortSwFOutQueuesD7PerformanceEntry 67108864}

pr1646v2EthPortSwFOutQueuesD7PerformanceRDropPkts OBJECT-TYPE
   SYNTAX      Counter64
   MAX-ACCESS  read-only
   STATUS      current
   DESCRIPTION
      "Path: swPort.performance.ifOutPriorityQueues.d7Performance.redDroppedPkts

       64 bit unsigned wrappable counter."
   ::= {pr1646v2EthPortSwFOutQueuesD7PerformanceEntry 201326592}

pr1646v2EthPortSwFOutQueuesD7PerformanceCirTxPkts OBJECT-TYPE
   SYNTAX      Counter64
   MAX-ACCESS  read-only
   STATUS      current
   DESCRIPTION
      "Path: swPort.performance.ifOutPriorityQueues.d7Performance.cirTxPkts

       64 bit unsigned wrappable counter."
   ::= {pr1646v2EthPortSwFOutQueuesD7PerformanceEntry 83886080}

pr1646v2EthPortSwFOutQueuesD7PerformanceEirTxPkts OBJECT-TYPE
   SYNTAX      Counter64
   MAX-ACCESS  read-only
   STATUS      current
   DESCRIPTION
      "Path: swPort.performance.ifOutPriorityQueues.d7Performance.eirTxPkts

       64 bit unsigned wrappable counter."
   ::= {pr1646v2EthPortSwFOutQueuesD7PerformanceEntry 100663296}

pr1646v2EthPortSwFOutQueuesD7PerformanceViolTxPkts OBJECT-TYPE
   SYNTAX      Counter64
   MAX-ACCESS  read-only
   STATUS      current
   DESCRIPTION
      "Path: swPort.performance.ifOutPriorityQueues.d7Performance.violateTxPkts

       64 bit unsigned wrappable counter."
   ::= {pr1646v2EthPortSwFOutQueuesD7PerformanceEntry 301989888}

pr1646v2EthPortSwFOutQueuesD7PerformanceTotOcts OBJECT-TYPE
   SYNTAX      Counter64
   MAX-ACCESS  read-only
   STATUS      current
   DESCRIPTION
      "Path: swPort.performance.ifOutPriorityQueues.d7Performance.totalOctets

       64 bit unsigned wrappable counter."
   ::= {pr1646v2EthPortSwFOutQueuesD7PerformanceEntry 251658240}

pr1646v2EthPortSwFOutQueuesD7PerformanceDirTxOcts OBJECT-TYPE
   SYNTAX      Counter64
   MAX-ACCESS  read-only
   STATUS      current
   DESCRIPTION
      "Path: swPort.performance.ifOutPriorityQueues.d7Performance.directTxOctets

       64 bit unsigned wrappable counter."
   ::= {pr1646v2EthPortSwFOutQueuesD7PerformanceEntry 117440512}

pr1646v2EthPortSwFOutQueuesD7PerformanceQdOcts OBJECT-TYPE
   SYNTAX      Counter64
   MAX-ACCESS  read-only
   STATUS      current
   DESCRIPTION
      "Path: swPort.performance.ifOutPriorityQueues.d7Performance.queuedOctets

       64 bit unsigned wrappable counter."
   ::= {pr1646v2EthPortSwFOutQueuesD7PerformanceEntry 134217728}

pr1646v2EthPortSwFOutQueuesD7PerformanceDropOcts OBJECT-TYPE
   SYNTAX      Counter64
   MAX-ACCESS  read-only
   STATUS      current
   DESCRIPTION
      "Path: swPort.performance.ifOutPriorityQueues.d7Performance.droppedOctets

       64 bit unsigned wrappable counter."
   ::= {pr1646v2EthPortSwFOutQueuesD7PerformanceEntry 150994944}

pr1646v2EthPortSwFOutQueuesD7PerformanceRDropOcts OBJECT-TYPE
   SYNTAX      Counter64
   MAX-ACCESS  read-only
   STATUS      current
   DESCRIPTION
      "Path: swPort.performance.ifOutPriorityQueues.d7Performance.redDroppedOctets

       64 bit unsigned wrappable counter."
   ::= {pr1646v2EthPortSwFOutQueuesD7PerformanceEntry 218103808}

pr1646v2EthPortSwFOutQueuesD7PerformanceCirTxOcts OBJECT-TYPE
   SYNTAX      Counter64
   MAX-ACCESS  read-only
   STATUS      current
   DESCRIPTION
      "Path: swPort.performance.ifOutPriorityQueues.d7Performance.cirTxOctets

       64 bit unsigned wrappable counter."
   ::= {pr1646v2EthPortSwFOutQueuesD7PerformanceEntry 167772160}

pr1646v2EthPortSwFOutQueuesD7PerformanceEirTxOcts OBJECT-TYPE
   SYNTAX      Counter64
   MAX-ACCESS  read-only
   STATUS      current
   DESCRIPTION
      "Path: swPort.performance.ifOutPriorityQueues.d7Performance.eirTxOctets

       64 bit unsigned wrappable counter."
   ::= {pr1646v2EthPortSwFOutQueuesD7PerformanceEntry 184549376}

pr1646v2EthPortSwFOutQueuesD7PerformanceViolTxOcts OBJECT-TYPE
   SYNTAX      Counter64
   MAX-ACCESS  read-only
   STATUS      current
   DESCRIPTION
      "Path: swPort.performance.ifOutPriorityQueues.d7Performance.violateTxOctets

       64 bit unsigned wrappable counter."
   ::= {pr1646v2EthPortSwFOutQueuesD7PerformanceEntry 318767104}

pr1646v2EthPortSwFOutQueuesD7PerformanceBandwidth OBJECT-TYPE
   SYNTAX      Integer32
   MAX-ACCESS  read-only
   STATUS      current
   DESCRIPTION
      "Path: swPort.performance.ifOutPriorityQueues.d7Performance.bandwidth

       unit name = bps
       formula = 8 * ; 8 /"
   ::= {pr1646v2EthPortSwFOutQueuesD7PerformanceEntry 268435456}


pr1646v2EthPortSwFOutBandwidth OBJECT IDENTIFIER ::= {pr1646v2EthPortSwF 182}

pr1646v2EthPortSwFOutBandwidthSSCTable OBJECT-TYPE
   SYNTAX      SEQUENCE OF Pr1646v2EthPortSwFOutBandwidthEntry
   MAX-ACCESS  not-accessible
   STATUS      current
   DESCRIPTION
      "bandwidth"
   ::= {pr1646v2EthPortSwFOutBandwidth 1}

pr1646v2EthPortSwFOutBandwidthEntry OBJECT-TYPE
   SYNTAX      Pr1646v2EthPortSwFOutBandwidthEntry
   MAX-ACCESS  not-accessible
   STATUS      current
   DESCRIPTION
      ""
   INDEX      { pr1646v2EthPortSwFOutBandwidthGlobalIx }
   ::= {pr1646v2EthPortSwFOutBandwidthSSCTable 1}

Pr1646v2EthPortSwFOutBandwidthEntry ::=
   SEQUENCE
      {
      pr1646v2EthPortSwFOutBandwidthGlobalIx
         GlobalIndex,
      pr1646v2EthPortSwFOutBandwidth15sec
         Integer32,
      pr1646v2EthPortSwFOutBandwidth30sec
         Integer32,
      pr1646v2EthPortSwFOutBandwidth1min
         Integer32,
      pr1646v2EthPortSwFOutBandwidth2min
         Integer32,
      pr1646v2EthPortSwFOutBandwidth5min
         Integer32
      }

pr1646v2EthPortSwFOutBandwidthGlobalIx OBJECT-TYPE
   SYNTAX      GlobalIndex
   MAX-ACCESS  not-accessible
   STATUS      current
   DESCRIPTION
      "The value of the tlsCntTreeGlobalIndex of the MANAGED OBJECT."
   ::= {pr1646v2EthPortSwFOutBandwidthEntry 10}

pr1646v2EthPortSwFOutBandwidth15sec OBJECT-TYPE
   SYNTAX      Integer32
   MAX-ACCESS  read-only
   STATUS      current
   DESCRIPTION
      "Path: swPort.performance.ifOutBandwidth.15sec

       unit name = bps
       formula = 8 * ; 8 /"
   ::= {pr1646v2EthPortSwFOutBandwidthEntry 83886080}

pr1646v2EthPortSwFOutBandwidth30sec OBJECT-TYPE
   SYNTAX      Integer32
   MAX-ACCESS  read-only
   STATUS      current
   DESCRIPTION
      "Path: swPort.performance.ifOutBandwidth.30sec

       unit name = bps
       formula = 8 * ; 8 /"
   ::= {pr1646v2EthPortSwFOutBandwidthEntry 167772160}

pr1646v2EthPortSwFOutBandwidth1min OBJECT-TYPE
   SYNTAX      Integer32
   MAX-ACCESS  read-only
   STATUS      current
   DESCRIPTION
      "Path: swPort.performance.ifOutBandwidth.1min

       unit name = bps
       formula = 8 * ; 8 /"
   ::= {pr1646v2EthPortSwFOutBandwidthEntry 335544320}

pr1646v2EthPortSwFOutBandwidth2min OBJECT-TYPE
   SYNTAX      Integer32
   MAX-ACCESS  read-only
   STATUS      current
   DESCRIPTION
      "Path: swPort.performance.ifOutBandwidth.2min

       unit name = bps
       formula = 8 * ; 8 /"
   ::= {pr1646v2EthPortSwFOutBandwidthEntry 671088640}

pr1646v2EthPortSwFOutBandwidth5min OBJECT-TYPE
   SYNTAX      Integer32
   MAX-ACCESS  read-only
   STATUS      current
   DESCRIPTION
      "Path: swPort.performance.ifOutBandwidth.5min

       unit name = bps
       formula = 8 * ; 8 /"
   ::= {pr1646v2EthPortSwFOutBandwidthEntry 1677721600}


pr1646v2EthPortSwFInP OBJECT IDENTIFIER ::= {pr1646v2EthPortSwF 307}

pr1646v2EthPortSwFInPSSCTable OBJECT-TYPE
   SYNTAX      SEQUENCE OF Pr1646v2EthPortSwFInPEntry
   MAX-ACCESS  not-accessible
   STATUS      current
   DESCRIPTION
      "h2IfInPerformance"
   ::= {pr1646v2EthPortSwFInP 1}

pr1646v2EthPortSwFInPEntry OBJECT-TYPE
   SYNTAX      Pr1646v2EthPortSwFInPEntry
   MAX-ACCESS  not-accessible
   STATUS      current
   DESCRIPTION
      ""
   INDEX      { pr1646v2EthPortSwFInPGlobalIx,
                pr1646v2EthPortSwFInPTableIx }
   ::= {pr1646v2EthPortSwFInPSSCTable 1}

Pr1646v2EthPortSwFInPEntry ::=
   SEQUENCE
      {
      pr1646v2EthPortSwFInPGlobalIx
         GlobalIndex,
      pr1646v2EthPortSwFInPTableIx
         TableIndex,
      pr1646v2EthPortSwFInPSysUpTime
         TimeTicks,
      pr1646v2EthPortSwFInPIfUpTime
         TimeTicks,
      pr1646v2EthPortSwFInPIfStatChanges
         Counter32,
      pr1646v2EthPortSwFInPIfInOctets
         Counter64,
      pr1646v2EthPortSwFInPIfInUCPkts
         Counter64,
      pr1646v2EthPortSwFInPIfInNUCPkts
         Counter64,
      pr1646v2EthPortSwFInPIfInBCPkts
         Counter64,
      pr1646v2EthPortSwFInPIfInMCPkts
         Counter64,
      pr1646v2EthPortSwFInPIfInDiscards
         Counter64,
      pr1646v2EthPortSwFInPIfInErrors
         Counter64,
      pr1646v2EthPortSwFInPIfInUnkwn
         Counter64,
      pr1646v2EthPortSwFInPInDropEx
         Counter64,
      pr1646v2EthPortSwFInPInDropNoMac
         Counter64,
      pr1646v2EthPortSwFInPInDropNUCast
         Counter64,
      pr1646v2EthPortSwFInPInDropFilter
         Counter64,
      pr1646v2EthPortSwFInPIfInBandwidth
         Integer32,
      pr1646v2EthPortSwFInPIfOutOctets
         Counter64,
      pr1646v2EthPortSwFInPIfOutUCPkts
         Counter64,
      pr1646v2EthPortSwFInPIfOutNUCPkts
         Counter64,
      pr1646v2EthPortSwFInPIfOutBCPkts
         Counter64,
      pr1646v2EthPortSwFInPIfOutMCPkts
         Counter64,
      pr1646v2EthPortSwFInPIfOutDiscards
         Counter64,
      pr1646v2EthPortSwFInPIfOutErrors
         Counter64,
      pr1646v2EthPortSwFInPOutDropEx
         Counter64,
      pr1646v2EthPortSwFInPOutDropNoArp
         Counter64,
      pr1646v2EthPortSwFInPOutDropFilter
         Counter64,
      pr1646v2EthPortSwFInPIfOutBandwidth
         Integer32,
      pr1646v2EthPortSwFInPIfErrSec
         Counter32
      }

pr1646v2EthPortSwFInPGlobalIx OBJECT-TYPE
   SYNTAX      GlobalIndex
   MAX-ACCESS  not-accessible
   STATUS      current
   DESCRIPTION
      "The value of the tlsCntTreeGlobalIndex of the MANAGED OBJECT."
   ::= {pr1646v2EthPortSwFInPEntry 10}

pr1646v2EthPortSwFInPTableIx OBJECT-TYPE
   SYNTAX      TableIndex
   MAX-ACCESS  not-accessible
   STATUS      current
   DESCRIPTION
      ""
   ::= {pr1646v2EthPortSwFInPEntry 11}

pr1646v2EthPortSwFInPSysUpTime OBJECT-TYPE
   SYNTAX      TimeTicks
   MAX-ACCESS  read-only
   STATUS      current
   DESCRIPTION
      "Path: swPort.performance.h2Performance.sysUpTime

       Time in centi-second."
   ::= {pr1646v2EthPortSwFInPEntry 16777216}

pr1646v2EthPortSwFInPIfUpTime OBJECT-TYPE
   SYNTAX      TimeTicks
   MAX-ACCESS  read-only
   STATUS      current
   DESCRIPTION
      "Path: swPort.performance.h2Performance.ifUpTime

       Time in centi-second."
   ::= {pr1646v2EthPortSwFInPEntry 33554432}

pr1646v2EthPortSwFInPIfStatChanges OBJECT-TYPE
   SYNTAX      Counter32
   MAX-ACCESS  read-only
   STATUS      current
   DESCRIPTION
      "Path: swPort.performance.h2Performance.ifStatusChanges

       32 bit unsigned wrappable counter."
   ::= {pr1646v2EthPortSwFInPEntry 50331648}

pr1646v2EthPortSwFInPIfInOctets OBJECT-TYPE
   SYNTAX      Counter64
   MAX-ACCESS  read-only
   STATUS      current
   DESCRIPTION
      "Path: swPort.performance.h2Performance.ifInOctets

       64 bit unsigned wrappable counter."
   ::= {pr1646v2EthPortSwFInPEntry 67108864}

pr1646v2EthPortSwFInPIfInUCPkts OBJECT-TYPE
   SYNTAX      Counter64
   MAX-ACCESS  read-only
   STATUS      current
   DESCRIPTION
      "Path: swPort.performance.h2Performance.ifInUcastPkts

       64 bit unsigned wrappable counter."
   ::= {pr1646v2EthPortSwFInPEntry 83886080}

pr1646v2EthPortSwFInPIfInNUCPkts OBJECT-TYPE
   SYNTAX      Counter64
   MAX-ACCESS  read-only
   STATUS      current
   DESCRIPTION
      "Path: swPort.performance.h2Performance.ifInNUcastPkts

       64 bit unsigned wrappable counter."
   ::= {pr1646v2EthPortSwFInPEntry 100663296}

pr1646v2EthPortSwFInPIfInBCPkts OBJECT-TYPE
   SYNTAX      Counter64
   MAX-ACCESS  read-only
   STATUS      current
   DESCRIPTION
      "Path: swPort.performance.h2Performance.ifInBcastPkts

       64 bit unsigned wrappable counter."
   ::= {pr1646v2EthPortSwFInPEntry 419430400}

pr1646v2EthPortSwFInPIfInMCPkts OBJECT-TYPE
   SYNTAX      Counter64
   MAX-ACCESS  read-only
   STATUS      current
   DESCRIPTION
      "Path: swPort.performance.h2Performance.ifInMcastPkts

       64 bit unsigned wrappable counter."
   ::= {pr1646v2EthPortSwFInPEntry 436207616}

pr1646v2EthPortSwFInPIfInDiscards OBJECT-TYPE
   SYNTAX      Counter64
   MAX-ACCESS  read-only
   STATUS      current
   DESCRIPTION
      "Path: swPort.performance.h2Performance.ifInDiscards

       64 bit unsigned wrappable counter."
   ::= {pr1646v2EthPortSwFInPEntry 117440512}

pr1646v2EthPortSwFInPIfInErrors OBJECT-TYPE
   SYNTAX      Counter64
   MAX-ACCESS  read-only
   STATUS      current
   DESCRIPTION
      "Path: swPort.performance.h2Performance.ifInErrors

       64 bit unsigned wrappable counter."
   ::= {pr1646v2EthPortSwFInPEntry 134217728}

pr1646v2EthPortSwFInPIfInUnkwn OBJECT-TYPE
   SYNTAX      Counter64
   MAX-ACCESS  read-only
   STATUS      current
   DESCRIPTION
      "Path: swPort.performance.h2Performance.ifInUnknownProtos

       64 bit unsigned wrappable counter."
   ::= {pr1646v2EthPortSwFInPEntry 150994944}

pr1646v2EthPortSwFInPInDropEx OBJECT-TYPE
   SYNTAX      Counter64
   MAX-ACCESS  read-only
   STATUS      current
   DESCRIPTION
      "Path: swPort.performance.h2Performance.ifInDropLevelExceeded

       64 bit unsigned wrappable counter."
   ::= {pr1646v2EthPortSwFInPEntry 335544320}

pr1646v2EthPortSwFInPInDropNoMac OBJECT-TYPE
   SYNTAX      Counter64
   MAX-ACCESS  read-only
   STATUS      current
   DESCRIPTION
      "Path: swPort.performance.h2Performance.fInDiscardsNoMacFit

       64 bit unsigned wrappable counter."
   ::= {pr1646v2EthPortSwFInPEntry 301989888}

pr1646v2EthPortSwFInPInDropNUCast OBJECT-TYPE
   SYNTAX      Counter64
   MAX-ACCESS  read-only
   STATUS      current
   DESCRIPTION
      "Path: swPort.performance.h2Performance.fInDiscardsNUCast

       64 bit unsigned wrappable counter."
   ::= {pr1646v2EthPortSwFInPEntry 318767104}

pr1646v2EthPortSwFInPInDropFilter OBJECT-TYPE
   SYNTAX      Counter64
   MAX-ACCESS  read-only
   STATUS      current
   DESCRIPTION
      "Path: swPort.performance.h2Performance.fInDiscardsFilter

       64 bit unsigned wrappable counter."
   ::= {pr1646v2EthPortSwFInPEntry 385875968}

pr1646v2EthPortSwFInPIfInBandwidth OBJECT-TYPE
   SYNTAX      Integer32
   MAX-ACCESS  read-only
   STATUS      current
   DESCRIPTION
      "Path: swPort.performance.h2Performance.ifInBandwidth

       unit name = bps
       formula = 8 * ; 8 /"
   ::= {pr1646v2EthPortSwFInPEntry 268435456}

pr1646v2EthPortSwFInPIfOutOctets OBJECT-TYPE
   SYNTAX      Counter64
   MAX-ACCESS  read-only
   STATUS      current
   DESCRIPTION
      "Path: swPort.performance.h2Performance.ifOutOctets

       64 bit unsigned wrappable counter."
   ::= {pr1646v2EthPortSwFInPEntry 167772160}

pr1646v2EthPortSwFInPIfOutUCPkts OBJECT-TYPE
   SYNTAX      Counter64
   MAX-ACCESS  read-only
   STATUS      current
   DESCRIPTION
      "Path: swPort.performance.h2Performance.ifOutUcastPkts

       64 bit unsigned wrappable counter."
   ::= {pr1646v2EthPortSwFInPEntry 184549376}

pr1646v2EthPortSwFInPIfOutNUCPkts OBJECT-TYPE
   SYNTAX      Counter64
   MAX-ACCESS  read-only
   STATUS      current
   DESCRIPTION
      "Path: swPort.performance.h2Performance.ifOutNUcastPkts

       64 bit unsigned wrappable counter."
   ::= {pr1646v2EthPortSwFInPEntry 201326592}

pr1646v2EthPortSwFInPIfOutBCPkts OBJECT-TYPE
   SYNTAX      Counter64
   MAX-ACCESS  read-only
   STATUS      current
   DESCRIPTION
      "Path: swPort.performance.h2Performance.ifOutBcastPkts

       64 bit unsigned wrappable counter."
   ::= {pr1646v2EthPortSwFInPEntry 452984832}

pr1646v2EthPortSwFInPIfOutMCPkts OBJECT-TYPE
   SYNTAX      Counter64
   MAX-ACCESS  read-only
   STATUS      current
   DESCRIPTION
      "Path: swPort.performance.h2Performance.ifOutMcastPkts

       64 bit unsigned wrappable counter."
   ::= {pr1646v2EthPortSwFInPEntry 469762048}

pr1646v2EthPortSwFInPIfOutDiscards OBJECT-TYPE
   SYNTAX      Counter64
   MAX-ACCESS  read-only
   STATUS      current
   DESCRIPTION
      "Path: swPort.performance.h2Performance.ifOutDiscards

       64 bit unsigned wrappable counter."
   ::= {pr1646v2EthPortSwFInPEntry 218103808}

pr1646v2EthPortSwFInPIfOutErrors OBJECT-TYPE
   SYNTAX      Counter64
   MAX-ACCESS  read-only
   STATUS      current
   DESCRIPTION
      "Path: swPort.performance.h2Performance.ifOutErrors

       64 bit unsigned wrappable counter."
   ::= {pr1646v2EthPortSwFInPEntry 234881024}

pr1646v2EthPortSwFInPOutDropEx OBJECT-TYPE
   SYNTAX      Counter64
   MAX-ACCESS  read-only
   STATUS      current
   DESCRIPTION
      "Path: swPort.performance.h2Performance.ifOutDropLevelExceeded

       64 bit unsigned wrappable counter."
   ::= {pr1646v2EthPortSwFInPEntry 352321536}

pr1646v2EthPortSwFInPOutDropNoArp OBJECT-TYPE
   SYNTAX      Counter64
   MAX-ACCESS  read-only
   STATUS      current
   DESCRIPTION
      "Path: swPort.performance.h2Performance.ifOutDiscardsNoArp

       64 bit unsigned wrappable counter."
   ::= {pr1646v2EthPortSwFInPEntry 369098752}

pr1646v2EthPortSwFInPOutDropFilter OBJECT-TYPE
   SYNTAX      Counter64
   MAX-ACCESS  read-only
   STATUS      current
   DESCRIPTION
      "Path: swPort.performance.h2Performance.ifOutDiscardsFilter

       64 bit unsigned wrappable counter."
   ::= {pr1646v2EthPortSwFInPEntry 402653184}

pr1646v2EthPortSwFInPIfOutBandwidth OBJECT-TYPE
   SYNTAX      Integer32
   MAX-ACCESS  read-only
   STATUS      current
   DESCRIPTION
      "Path: swPort.performance.h2Performance.ifOutBandwidth

       unit name = bps
       formula = 8 * ; 8 /"
   ::= {pr1646v2EthPortSwFInPEntry 285212672}

pr1646v2EthPortSwFInPIfErrSec OBJECT-TYPE
   SYNTAX      Counter32
   MAX-ACCESS  read-only
   STATUS      current
   DESCRIPTION
      "Path: swPort.performance.h2Performance.ifErrSec

       32 bit unsigned wrappable counter."
   ::= {pr1646v2EthPortSwFInPEntry 251658240}


pr1646v2EthPortSwFH24InP OBJECT IDENTIFIER ::= {pr1646v2EthPortSwF 308}

pr1646v2EthPortSwFH24InPSSCTable OBJECT-TYPE
   SYNTAX      SEQUENCE OF Pr1646v2EthPortSwFH24InPEntry
   MAX-ACCESS  not-accessible
   STATUS      current
   DESCRIPTION
      "h24IfInPerformance"
   ::= {pr1646v2EthPortSwFH24InP 1}

pr1646v2EthPortSwFH24InPEntry OBJECT-TYPE
   SYNTAX      Pr1646v2EthPortSwFH24InPEntry
   MAX-ACCESS  not-accessible
   STATUS      current
   DESCRIPTION
      ""
   INDEX      { pr1646v2EthPortSwFH24InPGlobalIx,
                pr1646v2EthPortSwFH24InPTableIx }
   ::= {pr1646v2EthPortSwFH24InPSSCTable 1}

Pr1646v2EthPortSwFH24InPEntry ::=
   SEQUENCE
      {
      pr1646v2EthPortSwFH24InPGlobalIx
         GlobalIndex,
      pr1646v2EthPortSwFH24InPTableIx
         TableIndex,
      pr1646v2EthPortSwFH24InPSysUpTime
         TimeTicks,
      pr1646v2EthPortSwFH24InPIfUpTime
         TimeTicks,
      pr1646v2EthPortSwFH24InPIfStatChanges
         Counter32,
      pr1646v2EthPortSwFH24InPIfInOctets
         Counter64,
      pr1646v2EthPortSwFH24InPIfInUCPkts
         Counter64,
      pr1646v2EthPortSwFH24InPIfInNUCPkts
         Counter64,
      pr1646v2EthPortSwFH24InPIfInBCPkts
         Counter64,
      pr1646v2EthPortSwFH24InPIfInMCPkts
         Counter64,
      pr1646v2EthPortSwFH24InPIfInDiscards
         Counter64,
      pr1646v2EthPortSwFH24InPIfInErrors
         Counter64,
      pr1646v2EthPortSwFH24InPIfInUnkwn
         Counter64,
      pr1646v2EthPortSwFH24InPInDropEx
         Counter64,
      pr1646v2EthPortSwFH24InPInDropNoMac
         Counter64,
      pr1646v2EthPortSwFH24InPInDropNUCast
         Counter64,
      pr1646v2EthPortSwFH24InPInDropFilter
         Counter64,
      pr1646v2EthPortSwFH24InPIfInBandwidth
         Integer32,
      pr1646v2EthPortSwFH24InPIfOutOctets
         Counter64,
      pr1646v2EthPortSwFH24InPIfOutUCPkts
         Counter64,
      pr1646v2EthPortSwFH24InPIfOutNUCPkts
         Counter64,
      pr1646v2EthPortSwFH24InPIfOutBCPkts
         Counter64,
      pr1646v2EthPortSwFH24InPIfOutMCPkts
         Counter64,
      pr1646v2EthPortSwFH24InPIfOutDiscards
         Counter64,
      pr1646v2EthPortSwFH24InPIfOutErrors
         Counter64,
      pr1646v2EthPortSwFH24InPOutDropEx
         Counter64,
      pr1646v2EthPortSwFH24InPOutDropNoArp
         Counter64,
      pr1646v2EthPortSwFH24InPOutDropFilter
         Counter64,
      pr1646v2EthPortSwFH24InPIfOutBandwidth
         Integer32,
      pr1646v2EthPortSwFH24InPIfErrSec
         Counter32
      }

pr1646v2EthPortSwFH24InPGlobalIx OBJECT-TYPE
   SYNTAX      GlobalIndex
   MAX-ACCESS  not-accessible
   STATUS      current
   DESCRIPTION
      "The value of the tlsCntTreeGlobalIndex of the MANAGED OBJECT."
   ::= {pr1646v2EthPortSwFH24InPEntry 10}

pr1646v2EthPortSwFH24InPTableIx OBJECT-TYPE
   SYNTAX      TableIndex
   MAX-ACCESS  not-accessible
   STATUS      current
   DESCRIPTION
      ""
   ::= {pr1646v2EthPortSwFH24InPEntry 11}

pr1646v2EthPortSwFH24InPSysUpTime OBJECT-TYPE
   SYNTAX      TimeTicks
   MAX-ACCESS  read-only
   STATUS      current
   DESCRIPTION
      "Path: swPort.performance.h24Performance.sysUpTime

       Time in centi-second."
   ::= {pr1646v2EthPortSwFH24InPEntry 16777216}

pr1646v2EthPortSwFH24InPIfUpTime OBJECT-TYPE
   SYNTAX      TimeTicks
   MAX-ACCESS  read-only
   STATUS      current
   DESCRIPTION
      "Path: swPort.performance.h24Performance.ifUpTime

       Time in centi-second."
   ::= {pr1646v2EthPortSwFH24InPEntry 33554432}

pr1646v2EthPortSwFH24InPIfStatChanges OBJECT-TYPE
   SYNTAX      Counter32
   MAX-ACCESS  read-only
   STATUS      current
   DESCRIPTION
      "Path: swPort.performance.h24Performance.ifStatusChanges

       32 bit unsigned wrappable counter."
   ::= {pr1646v2EthPortSwFH24InPEntry 50331648}

pr1646v2EthPortSwFH24InPIfInOctets OBJECT-TYPE
   SYNTAX      Counter64
   MAX-ACCESS  read-only
   STATUS      current
   DESCRIPTION
      "Path: swPort.performance.h24Performance.ifInOctets

       64 bit unsigned wrappable counter."
   ::= {pr1646v2EthPortSwFH24InPEntry 67108864}

pr1646v2EthPortSwFH24InPIfInUCPkts OBJECT-TYPE
   SYNTAX      Counter64
   MAX-ACCESS  read-only
   STATUS      current
   DESCRIPTION
      "Path: swPort.performance.h24Performance.ifInUcastPkts

       64 bit unsigned wrappable counter."
   ::= {pr1646v2EthPortSwFH24InPEntry 83886080}

pr1646v2EthPortSwFH24InPIfInNUCPkts OBJECT-TYPE
   SYNTAX      Counter64
   MAX-ACCESS  read-only
   STATUS      current
   DESCRIPTION
      "Path: swPort.performance.h24Performance.ifInNUcastPkts

       64 bit unsigned wrappable counter."
   ::= {pr1646v2EthPortSwFH24InPEntry 100663296}

pr1646v2EthPortSwFH24InPIfInBCPkts OBJECT-TYPE
   SYNTAX      Counter64
   MAX-ACCESS  read-only
   STATUS      current
   DESCRIPTION
      "Path: swPort.performance.h24Performance.ifInBcastPkts

       64 bit unsigned wrappable counter."
   ::= {pr1646v2EthPortSwFH24InPEntry 419430400}

pr1646v2EthPortSwFH24InPIfInMCPkts OBJECT-TYPE
   SYNTAX      Counter64
   MAX-ACCESS  read-only
   STATUS      current
   DESCRIPTION
      "Path: swPort.performance.h24Performance.ifInMcastPkts

       64 bit unsigned wrappable counter."
   ::= {pr1646v2EthPortSwFH24InPEntry 436207616}

pr1646v2EthPortSwFH24InPIfInDiscards OBJECT-TYPE
   SYNTAX      Counter64
   MAX-ACCESS  read-only
   STATUS      current
   DESCRIPTION
      "Path: swPort.performance.h24Performance.ifInDiscards

       64 bit unsigned wrappable counter."
   ::= {pr1646v2EthPortSwFH24InPEntry 117440512}

pr1646v2EthPortSwFH24InPIfInErrors OBJECT-TYPE
   SYNTAX      Counter64
   MAX-ACCESS  read-only
   STATUS      current
   DESCRIPTION
      "Path: swPort.performance.h24Performance.ifInErrors

       64 bit unsigned wrappable counter."
   ::= {pr1646v2EthPortSwFH24InPEntry 134217728}

pr1646v2EthPortSwFH24InPIfInUnkwn OBJECT-TYPE
   SYNTAX      Counter64
   MAX-ACCESS  read-only
   STATUS      current
   DESCRIPTION
      "Path: swPort.performance.h24Performance.ifInUnknownProtos

       64 bit unsigned wrappable counter."
   ::= {pr1646v2EthPortSwFH24InPEntry 150994944}

pr1646v2EthPortSwFH24InPInDropEx OBJECT-TYPE
   SYNTAX      Counter64
   MAX-ACCESS  read-only
   STATUS      current
   DESCRIPTION
      "Path: swPort.performance.h24Performance.ifInDropLevelExceeded

       64 bit unsigned wrappable counter."
   ::= {pr1646v2EthPortSwFH24InPEntry 335544320}

pr1646v2EthPortSwFH24InPInDropNoMac OBJECT-TYPE
   SYNTAX      Counter64
   MAX-ACCESS  read-only
   STATUS      current
   DESCRIPTION
      "Path: swPort.performance.h24Performance.fInDiscardsNoMacFit

       64 bit unsigned wrappable counter."
   ::= {pr1646v2EthPortSwFH24InPEntry 301989888}

pr1646v2EthPortSwFH24InPInDropNUCast OBJECT-TYPE
   SYNTAX      Counter64
   MAX-ACCESS  read-only
   STATUS      current
   DESCRIPTION
      "Path: swPort.performance.h24Performance.fInDiscardsNUCast

       64 bit unsigned wrappable counter."
   ::= {pr1646v2EthPortSwFH24InPEntry 318767104}

pr1646v2EthPortSwFH24InPInDropFilter OBJECT-TYPE
   SYNTAX      Counter64
   MAX-ACCESS  read-only
   STATUS      current
   DESCRIPTION
      "Path: swPort.performance.h24Performance.fInDiscardsFilter

       64 bit unsigned wrappable counter."
   ::= {pr1646v2EthPortSwFH24InPEntry 385875968}

pr1646v2EthPortSwFH24InPIfInBandwidth OBJECT-TYPE
   SYNTAX      Integer32
   MAX-ACCESS  read-only
   STATUS      current
   DESCRIPTION
      "Path: swPort.performance.h24Performance.ifInBandwidth

       unit name = bps
       formula = 8 * ; 8 /"
   ::= {pr1646v2EthPortSwFH24InPEntry 268435456}

pr1646v2EthPortSwFH24InPIfOutOctets OBJECT-TYPE
   SYNTAX      Counter64
   MAX-ACCESS  read-only
   STATUS      current
   DESCRIPTION
      "Path: swPort.performance.h24Performance.ifOutOctets

       64 bit unsigned wrappable counter."
   ::= {pr1646v2EthPortSwFH24InPEntry 167772160}

pr1646v2EthPortSwFH24InPIfOutUCPkts OBJECT-TYPE
   SYNTAX      Counter64
   MAX-ACCESS  read-only
   STATUS      current
   DESCRIPTION
      "Path: swPort.performance.h24Performance.ifOutUcastPkts

       64 bit unsigned wrappable counter."
   ::= {pr1646v2EthPortSwFH24InPEntry 184549376}

pr1646v2EthPortSwFH24InPIfOutNUCPkts OBJECT-TYPE
   SYNTAX      Counter64
   MAX-ACCESS  read-only
   STATUS      current
   DESCRIPTION
      "Path: swPort.performance.h24Performance.ifOutNUcastPkts

       64 bit unsigned wrappable counter."
   ::= {pr1646v2EthPortSwFH24InPEntry 201326592}

pr1646v2EthPortSwFH24InPIfOutBCPkts OBJECT-TYPE
   SYNTAX      Counter64
   MAX-ACCESS  read-only
   STATUS      current
   DESCRIPTION
      "Path: swPort.performance.h24Performance.ifOutBcastPkts

       64 bit unsigned wrappable counter."
   ::= {pr1646v2EthPortSwFH24InPEntry 452984832}

pr1646v2EthPortSwFH24InPIfOutMCPkts OBJECT-TYPE
   SYNTAX      Counter64
   MAX-ACCESS  read-only
   STATUS      current
   DESCRIPTION
      "Path: swPort.performance.h24Performance.ifOutMcastPkts

       64 bit unsigned wrappable counter."
   ::= {pr1646v2EthPortSwFH24InPEntry 469762048}

pr1646v2EthPortSwFH24InPIfOutDiscards OBJECT-TYPE
   SYNTAX      Counter64
   MAX-ACCESS  read-only
   STATUS      current
   DESCRIPTION
      "Path: swPort.performance.h24Performance.ifOutDiscards

       64 bit unsigned wrappable counter."
   ::= {pr1646v2EthPortSwFH24InPEntry 218103808}

pr1646v2EthPortSwFH24InPIfOutErrors OBJECT-TYPE
   SYNTAX      Counter64
   MAX-ACCESS  read-only
   STATUS      current
   DESCRIPTION
      "Path: swPort.performance.h24Performance.ifOutErrors

       64 bit unsigned wrappable counter."
   ::= {pr1646v2EthPortSwFH24InPEntry 234881024}

pr1646v2EthPortSwFH24InPOutDropEx OBJECT-TYPE
   SYNTAX      Counter64
   MAX-ACCESS  read-only
   STATUS      current
   DESCRIPTION
      "Path: swPort.performance.h24Performance.ifOutDropLevelExceeded

       64 bit unsigned wrappable counter."
   ::= {pr1646v2EthPortSwFH24InPEntry 352321536}

pr1646v2EthPortSwFH24InPOutDropNoArp OBJECT-TYPE
   SYNTAX      Counter64
   MAX-ACCESS  read-only
   STATUS      current
   DESCRIPTION
      "Path: swPort.performance.h24Performance.ifOutDiscardsNoArp

       64 bit unsigned wrappable counter."
   ::= {pr1646v2EthPortSwFH24InPEntry 369098752}

pr1646v2EthPortSwFH24InPOutDropFilter OBJECT-TYPE
   SYNTAX      Counter64
   MAX-ACCESS  read-only
   STATUS      current
   DESCRIPTION
      "Path: swPort.performance.h24Performance.ifOutDiscardsFilter

       64 bit unsigned wrappable counter."
   ::= {pr1646v2EthPortSwFH24InPEntry 402653184}

pr1646v2EthPortSwFH24InPIfOutBandwidth OBJECT-TYPE
   SYNTAX      Integer32
   MAX-ACCESS  read-only
   STATUS      current
   DESCRIPTION
      "Path: swPort.performance.h24Performance.ifOutBandwidth

       unit name = bps
       formula = 8 * ; 8 /"
   ::= {pr1646v2EthPortSwFH24InPEntry 285212672}

pr1646v2EthPortSwFH24InPIfErrSec OBJECT-TYPE
   SYNTAX      Counter32
   MAX-ACCESS  read-only
   STATUS      current
   DESCRIPTION
      "Path: swPort.performance.h24Performance.ifErrSec

       32 bit unsigned wrappable counter."
   ::= {pr1646v2EthPortSwFH24InPEntry 251658240}


pr1646v2EthPortSwFD7InP OBJECT IDENTIFIER ::= {pr1646v2EthPortSwF 309}

pr1646v2EthPortSwFD7InPSSCTable OBJECT-TYPE
   SYNTAX      SEQUENCE OF Pr1646v2EthPortSwFD7InPEntry
   MAX-ACCESS  not-accessible
   STATUS      current
   DESCRIPTION
      "d7IfInPerformance"
   ::= {pr1646v2EthPortSwFD7InP 1}

pr1646v2EthPortSwFD7InPEntry OBJECT-TYPE
   SYNTAX      Pr1646v2EthPortSwFD7InPEntry
   MAX-ACCESS  not-accessible
   STATUS      current
   DESCRIPTION
      ""
   INDEX      { pr1646v2EthPortSwFD7InPGlobalIx,
                pr1646v2EthPortSwFD7InPTableIx }
   ::= {pr1646v2EthPortSwFD7InPSSCTable 1}

Pr1646v2EthPortSwFD7InPEntry ::=
   SEQUENCE
      {
      pr1646v2EthPortSwFD7InPGlobalIx
         GlobalIndex,
      pr1646v2EthPortSwFD7InPTableIx
         TableIndex,
      pr1646v2EthPortSwFD7InPSysUpTime
         TimeTicks,
      pr1646v2EthPortSwFD7InPIfUpTime
         TimeTicks,
      pr1646v2EthPortSwFD7InPIfStatChanges
         Counter32,
      pr1646v2EthPortSwFD7InPIfInOctets
         Counter64,
      pr1646v2EthPortSwFD7InPIfInUCPkts
         Counter64,
      pr1646v2EthPortSwFD7InPIfInNUCPkts
         Counter64,
      pr1646v2EthPortSwFD7InPIfInBCPkts
         Counter64,
      pr1646v2EthPortSwFD7InPIfInMCPkts
         Counter64,
      pr1646v2EthPortSwFD7InPIfInDiscards
         Counter64,
      pr1646v2EthPortSwFD7InPIfInErrors
         Counter64,
      pr1646v2EthPortSwFD7InPIfInUnkwn
         Counter64,
      pr1646v2EthPortSwFD7InPInDropEx
         Counter64,
      pr1646v2EthPortSwFD7InPInDropNoMac
         Counter64,
      pr1646v2EthPortSwFD7InPInDropNUCast
         Counter64,
      pr1646v2EthPortSwFD7InPInDropFilter
         Counter64,
      pr1646v2EthPortSwFD7InPIfInBandwidth
         Integer32,
      pr1646v2EthPortSwFD7InPIfOutOctets
         Counter64,
      pr1646v2EthPortSwFD7InPIfOutUCPkts
         Counter64,
      pr1646v2EthPortSwFD7InPIfOutNUCPkts
         Counter64,
      pr1646v2EthPortSwFD7InPIfOutBCPkts
         Counter64,
      pr1646v2EthPortSwFD7InPIfOutMCPkts
         Counter64,
      pr1646v2EthPortSwFD7InPIfOutDiscards
         Counter64,
      pr1646v2EthPortSwFD7InPIfOutErrors
         Counter64,
      pr1646v2EthPortSwFD7InPOutDropEx
         Counter64,
      pr1646v2EthPortSwFD7InPOutDropNoArp
         Counter64,
      pr1646v2EthPortSwFD7InPOutDropFilter
         Counter64,
      pr1646v2EthPortSwFD7InPIfOutBandwidth
         Integer32,
      pr1646v2EthPortSwFD7InPIfErrSec
         Counter32
      }

pr1646v2EthPortSwFD7InPGlobalIx OBJECT-TYPE
   SYNTAX      GlobalIndex
   MAX-ACCESS  not-accessible
   STATUS      current
   DESCRIPTION
      "The value of the tlsCntTreeGlobalIndex of the MANAGED OBJECT."
   ::= {pr1646v2EthPortSwFD7InPEntry 10}

pr1646v2EthPortSwFD7InPTableIx OBJECT-TYPE
   SYNTAX      TableIndex
   MAX-ACCESS  not-accessible
   STATUS      current
   DESCRIPTION
      ""
   ::= {pr1646v2EthPortSwFD7InPEntry 11}

pr1646v2EthPortSwFD7InPSysUpTime OBJECT-TYPE
   SYNTAX      TimeTicks
   MAX-ACCESS  read-only
   STATUS      current
   DESCRIPTION
      "Path: swPort.performance.d7Performance.sysUpTime

       Time in centi-second."
   ::= {pr1646v2EthPortSwFD7InPEntry 16777216}

pr1646v2EthPortSwFD7InPIfUpTime OBJECT-TYPE
   SYNTAX      TimeTicks
   MAX-ACCESS  read-only
   STATUS      current
   DESCRIPTION
      "Path: swPort.performance.d7Performance.ifUpTime

       Time in centi-second."
   ::= {pr1646v2EthPortSwFD7InPEntry 33554432}

pr1646v2EthPortSwFD7InPIfStatChanges OBJECT-TYPE
   SYNTAX      Counter32
   MAX-ACCESS  read-only
   STATUS      current
   DESCRIPTION
      "Path: swPort.performance.d7Performance.ifStatusChanges

       32 bit unsigned wrappable counter."
   ::= {pr1646v2EthPortSwFD7InPEntry 50331648}

pr1646v2EthPortSwFD7InPIfInOctets OBJECT-TYPE
   SYNTAX      Counter64
   MAX-ACCESS  read-only
   STATUS      current
   DESCRIPTION
      "Path: swPort.performance.d7Performance.ifInOctets

       64 bit unsigned wrappable counter."
   ::= {pr1646v2EthPortSwFD7InPEntry 67108864}

pr1646v2EthPortSwFD7InPIfInUCPkts OBJECT-TYPE
   SYNTAX      Counter64
   MAX-ACCESS  read-only
   STATUS      current
   DESCRIPTION
      "Path: swPort.performance.d7Performance.ifInUcastPkts

       64 bit unsigned wrappable counter."
   ::= {pr1646v2EthPortSwFD7InPEntry 83886080}

pr1646v2EthPortSwFD7InPIfInNUCPkts OBJECT-TYPE
   SYNTAX      Counter64
   MAX-ACCESS  read-only
   STATUS      current
   DESCRIPTION
      "Path: swPort.performance.d7Performance.ifInNUcastPkts

       64 bit unsigned wrappable counter."
   ::= {pr1646v2EthPortSwFD7InPEntry 100663296}

pr1646v2EthPortSwFD7InPIfInBCPkts OBJECT-TYPE
   SYNTAX      Counter64
   MAX-ACCESS  read-only
   STATUS      current
   DESCRIPTION
      "Path: swPort.performance.d7Performance.ifInBcastPkts

       64 bit unsigned wrappable counter."
   ::= {pr1646v2EthPortSwFD7InPEntry 419430400}

pr1646v2EthPortSwFD7InPIfInMCPkts OBJECT-TYPE
   SYNTAX      Counter64
   MAX-ACCESS  read-only
   STATUS      current
   DESCRIPTION
      "Path: swPort.performance.d7Performance.ifInMcastPkts

       64 bit unsigned wrappable counter."
   ::= {pr1646v2EthPortSwFD7InPEntry 436207616}

pr1646v2EthPortSwFD7InPIfInDiscards OBJECT-TYPE
   SYNTAX      Counter64
   MAX-ACCESS  read-only
   STATUS      current
   DESCRIPTION
      "Path: swPort.performance.d7Performance.ifInDiscards

       64 bit unsigned wrappable counter."
   ::= {pr1646v2EthPortSwFD7InPEntry 117440512}

pr1646v2EthPortSwFD7InPIfInErrors OBJECT-TYPE
   SYNTAX      Counter64
   MAX-ACCESS  read-only
   STATUS      current
   DESCRIPTION
      "Path: swPort.performance.d7Performance.ifInErrors

       64 bit unsigned wrappable counter."
   ::= {pr1646v2EthPortSwFD7InPEntry 134217728}

pr1646v2EthPortSwFD7InPIfInUnkwn OBJECT-TYPE
   SYNTAX      Counter64
   MAX-ACCESS  read-only
   STATUS      current
   DESCRIPTION
      "Path: swPort.performance.d7Performance.ifInUnknownProtos

       64 bit unsigned wrappable counter."
   ::= {pr1646v2EthPortSwFD7InPEntry 150994944}

pr1646v2EthPortSwFD7InPInDropEx OBJECT-TYPE
   SYNTAX      Counter64
   MAX-ACCESS  read-only
   STATUS      current
   DESCRIPTION
      "Path: swPort.performance.d7Performance.ifInDropLevelExceeded

       64 bit unsigned wrappable counter."
   ::= {pr1646v2EthPortSwFD7InPEntry 335544320}

pr1646v2EthPortSwFD7InPInDropNoMac OBJECT-TYPE
   SYNTAX      Counter64
   MAX-ACCESS  read-only
   STATUS      current
   DESCRIPTION
      "Path: swPort.performance.d7Performance.fInDiscardsNoMacFit

       64 bit unsigned wrappable counter."
   ::= {pr1646v2EthPortSwFD7InPEntry 301989888}

pr1646v2EthPortSwFD7InPInDropNUCast OBJECT-TYPE
   SYNTAX      Counter64
   MAX-ACCESS  read-only
   STATUS      current
   DESCRIPTION
      "Path: swPort.performance.d7Performance.fInDiscardsNUCast

       64 bit unsigned wrappable counter."
   ::= {pr1646v2EthPortSwFD7InPEntry 318767104}

pr1646v2EthPortSwFD7InPInDropFilter OBJECT-TYPE
   SYNTAX      Counter64
   MAX-ACCESS  read-only
   STATUS      current
   DESCRIPTION
      "Path: swPort.performance.d7Performance.fInDiscardsFilter

       64 bit unsigned wrappable counter."
   ::= {pr1646v2EthPortSwFD7InPEntry 385875968}

pr1646v2EthPortSwFD7InPIfInBandwidth OBJECT-TYPE
   SYNTAX      Integer32
   MAX-ACCESS  read-only
   STATUS      current
   DESCRIPTION
      "Path: swPort.performance.d7Performance.ifInBandwidth

       unit name = bps
       formula = 8 * ; 8 /"
   ::= {pr1646v2EthPortSwFD7InPEntry 268435456}

pr1646v2EthPortSwFD7InPIfOutOctets OBJECT-TYPE
   SYNTAX      Counter64
   MAX-ACCESS  read-only
   STATUS      current
   DESCRIPTION
      "Path: swPort.performance.d7Performance.ifOutOctets

       64 bit unsigned wrappable counter."
   ::= {pr1646v2EthPortSwFD7InPEntry 167772160}

pr1646v2EthPortSwFD7InPIfOutUCPkts OBJECT-TYPE
   SYNTAX      Counter64
   MAX-ACCESS  read-only
   STATUS      current
   DESCRIPTION
      "Path: swPort.performance.d7Performance.ifOutUcastPkts

       64 bit unsigned wrappable counter."
   ::= {pr1646v2EthPortSwFD7InPEntry 184549376}

pr1646v2EthPortSwFD7InPIfOutNUCPkts OBJECT-TYPE
   SYNTAX      Counter64
   MAX-ACCESS  read-only
   STATUS      current
   DESCRIPTION
      "Path: swPort.performance.d7Performance.ifOutNUcastPkts

       64 bit unsigned wrappable counter."
   ::= {pr1646v2EthPortSwFD7InPEntry 201326592}

pr1646v2EthPortSwFD7InPIfOutBCPkts OBJECT-TYPE
   SYNTAX      Counter64
   MAX-ACCESS  read-only
   STATUS      current
   DESCRIPTION
      "Path: swPort.performance.d7Performance.ifOutBcastPkts

       64 bit unsigned wrappable counter."
   ::= {pr1646v2EthPortSwFD7InPEntry 452984832}

pr1646v2EthPortSwFD7InPIfOutMCPkts OBJECT-TYPE
   SYNTAX      Counter64
   MAX-ACCESS  read-only
   STATUS      current
   DESCRIPTION
      "Path: swPort.performance.d7Performance.ifOutMcastPkts

       64 bit unsigned wrappable counter."
   ::= {pr1646v2EthPortSwFD7InPEntry 469762048}

pr1646v2EthPortSwFD7InPIfOutDiscards OBJECT-TYPE
   SYNTAX      Counter64
   MAX-ACCESS  read-only
   STATUS      current
   DESCRIPTION
      "Path: swPort.performance.d7Performance.ifOutDiscards

       64 bit unsigned wrappable counter."
   ::= {pr1646v2EthPortSwFD7InPEntry 218103808}

pr1646v2EthPortSwFD7InPIfOutErrors OBJECT-TYPE
   SYNTAX      Counter64
   MAX-ACCESS  read-only
   STATUS      current
   DESCRIPTION
      "Path: swPort.performance.d7Performance.ifOutErrors

       64 bit unsigned wrappable counter."
   ::= {pr1646v2EthPortSwFD7InPEntry 234881024}

pr1646v2EthPortSwFD7InPOutDropEx OBJECT-TYPE
   SYNTAX      Counter64
   MAX-ACCESS  read-only
   STATUS      current
   DESCRIPTION
      "Path: swPort.performance.d7Performance.ifOutDropLevelExceeded

       64 bit unsigned wrappable counter."
   ::= {pr1646v2EthPortSwFD7InPEntry 352321536}

pr1646v2EthPortSwFD7InPOutDropNoArp OBJECT-TYPE
   SYNTAX      Counter64
   MAX-ACCESS  read-only
   STATUS      current
   DESCRIPTION
      "Path: swPort.performance.d7Performance.ifOutDiscardsNoArp

       64 bit unsigned wrappable counter."
   ::= {pr1646v2EthPortSwFD7InPEntry 369098752}

pr1646v2EthPortSwFD7InPOutDropFilter OBJECT-TYPE
   SYNTAX      Counter64
   MAX-ACCESS  read-only
   STATUS      current
   DESCRIPTION
      "Path: swPort.performance.d7Performance.ifOutDiscardsFilter

       64 bit unsigned wrappable counter."
   ::= {pr1646v2EthPortSwFD7InPEntry 402653184}

pr1646v2EthPortSwFD7InPIfOutBandwidth OBJECT-TYPE
   SYNTAX      Integer32
   MAX-ACCESS  read-only
   STATUS      current
   DESCRIPTION
      "Path: swPort.performance.d7Performance.ifOutBandwidth

       unit name = bps
       formula = 8 * ; 8 /"
   ::= {pr1646v2EthPortSwFD7InPEntry 285212672}

pr1646v2EthPortSwFD7InPIfErrSec OBJECT-TYPE
   SYNTAX      Counter32
   MAX-ACCESS  read-only
   STATUS      current
   DESCRIPTION
      "Path: swPort.performance.d7Performance.ifErrSec

       32 bit unsigned wrappable counter."
   ::= {pr1646v2EthPortSwFD7InPEntry 251658240}


pr1646v2EthPortSwFOam OBJECT IDENTIFIER ::= {pr1646v2EthPortSwF 910}

pr1646v2EthPortSwFOamSSCTable OBJECT-TYPE
   SYNTAX      SEQUENCE OF Pr1646v2EthPortSwFOamEntry
   MAX-ACCESS  not-accessible
   STATUS      current
   DESCRIPTION
      "OAM statistics"
   ::= {pr1646v2EthPortSwFOam 1}

pr1646v2EthPortSwFOamEntry OBJECT-TYPE
   SYNTAX      Pr1646v2EthPortSwFOamEntry
   MAX-ACCESS  not-accessible
   STATUS      current
   DESCRIPTION
      ""
   INDEX      { pr1646v2EthPortSwFOamGlobalIx }
   ::= {pr1646v2EthPortSwFOamSSCTable 1}

Pr1646v2EthPortSwFOamEntry ::=
   SEQUENCE
      {
      pr1646v2EthPortSwFOamGlobalIx
         GlobalIndex,
      pr1646v2EthPortSwFOamInformationTx
         Counter32,
      pr1646v2EthPortSwFOamInformationRx
         Counter32,
      pr1646v2EthPortSwFOamUniqueEventNotifTx
         Counter32,
      pr1646v2EthPortSwFOamUniqueEventNotifRx
         Counter32,
      pr1646v2EthPortSwFOamLoopbackCtrlTx
         Counter32,
      pr1646v2EthPortSwFOamLoopbackCtrlRx
         Counter32,
      pr1646v2EthPortSwFOamVarReqTx
         Counter32,
      pr1646v2EthPortSwFOamVarReqRx
         Counter32,
      pr1646v2EthPortSwFOamVarRespTx
         Counter32,
      pr1646v2EthPortSwFOamVarRespRx
         Counter32,
      pr1646v2EthPortSwFOamOrgSpecificTx
         Counter32,
      pr1646v2EthPortSwFOamOrgSpecificRx
         Counter32,
      pr1646v2EthPortSwFOamUnsupportedCodesTx
         Counter32,
      pr1646v2EthPortSwFOamUnsupportedCodesRx
         Counter32,
      pr1646v2EthPortSwFOamPduDiscardRx
         Counter32,
      pr1646v2EthPortSwFOamDataDiscardTx
         Counter32,
      pr1646v2EthPortSwFOamDataDiscardRx
         Counter32
      }

pr1646v2EthPortSwFOamGlobalIx OBJECT-TYPE
   SYNTAX      GlobalIndex
   MAX-ACCESS  not-accessible
   STATUS      current
   DESCRIPTION
      "The value of the tlsCntTreeGlobalIndex of the MANAGED OBJECT."
   ::= {pr1646v2EthPortSwFOamEntry 10}

pr1646v2EthPortSwFOamInformationTx OBJECT-TYPE
   SYNTAX      Counter32
   MAX-ACCESS  read-only
   STATUS      current
   DESCRIPTION
      "Path: swPort.performance.oam.informationTx

       32 bit unsigned wrappable counter."
   ::= {pr1646v2EthPortSwFOamEntry 16777216}

pr1646v2EthPortSwFOamInformationRx OBJECT-TYPE
   SYNTAX      Counter32
   MAX-ACCESS  read-only
   STATUS      current
   DESCRIPTION
      "Path: swPort.performance.oam.informationRx

       32 bit unsigned wrappable counter."
   ::= {pr1646v2EthPortSwFOamEntry 33554432}

pr1646v2EthPortSwFOamUniqueEventNotifTx OBJECT-TYPE
   SYNTAX      Counter32
   MAX-ACCESS  read-only
   STATUS      current
   DESCRIPTION
      "Path: swPort.performance.oam.uniqueEventNotifTx

       32 bit unsigned wrappable counter."
   ::= {pr1646v2EthPortSwFOamEntry 50331648}

pr1646v2EthPortSwFOamUniqueEventNotifRx OBJECT-TYPE
   SYNTAX      Counter32
   MAX-ACCESS  read-only
   STATUS      current
   DESCRIPTION
      "Path: swPort.performance.oam.uniqueEventNotifRx

       32 bit unsigned wrappable counter."
   ::= {pr1646v2EthPortSwFOamEntry 67108864}

pr1646v2EthPortSwFOamLoopbackCtrlTx OBJECT-TYPE
   SYNTAX      Counter32
   MAX-ACCESS  read-only
   STATUS      current
   DESCRIPTION
      "Path: swPort.performance.oam.loopbackCtrlTx

       32 bit unsigned wrappable counter."
   ::= {pr1646v2EthPortSwFOamEntry 117440512}

pr1646v2EthPortSwFOamLoopbackCtrlRx OBJECT-TYPE
   SYNTAX      Counter32
   MAX-ACCESS  read-only
   STATUS      current
   DESCRIPTION
      "Path: swPort.performance.oam.loopbackCtrlRx

       32 bit unsigned wrappable counter."
   ::= {pr1646v2EthPortSwFOamEntry 134217728}

pr1646v2EthPortSwFOamVarReqTx OBJECT-TYPE
   SYNTAX      Counter32
   MAX-ACCESS  read-only
   STATUS      current
   DESCRIPTION
      "Path: swPort.performance.oam.varReqTx

       32 bit unsigned wrappable counter."
   ::= {pr1646v2EthPortSwFOamEntry 150994944}

pr1646v2EthPortSwFOamVarReqRx OBJECT-TYPE
   SYNTAX      Counter32
   MAX-ACCESS  read-only
   STATUS      current
   DESCRIPTION
      "Path: swPort.performance.oam.varReqRx

       32 bit unsigned wrappable counter."
   ::= {pr1646v2EthPortSwFOamEntry 167772160}

pr1646v2EthPortSwFOamVarRespTx OBJECT-TYPE
   SYNTAX      Counter32
   MAX-ACCESS  read-only
   STATUS      current
   DESCRIPTION
      "Path: swPort.performance.oam.varRespTx

       32 bit unsigned wrappable counter."
   ::= {pr1646v2EthPortSwFOamEntry 184549376}

pr1646v2EthPortSwFOamVarRespRx OBJECT-TYPE
   SYNTAX      Counter32
   MAX-ACCESS  read-only
   STATUS      current
   DESCRIPTION
      "Path: swPort.performance.oam.varRespRx

       32 bit unsigned wrappable counter."
   ::= {pr1646v2EthPortSwFOamEntry 201326592}

pr1646v2EthPortSwFOamOrgSpecificTx OBJECT-TYPE
   SYNTAX      Counter32
   MAX-ACCESS  read-only
   STATUS      current
   DESCRIPTION
      "Path: swPort.performance.oam.orgSpecificTx

       32 bit unsigned wrappable counter."
   ::= {pr1646v2EthPortSwFOamEntry 218103808}

pr1646v2EthPortSwFOamOrgSpecificRx OBJECT-TYPE
   SYNTAX      Counter32
   MAX-ACCESS  read-only
   STATUS      current
   DESCRIPTION
      "Path: swPort.performance.oam.orgSpecificRx

       32 bit unsigned wrappable counter."
   ::= {pr1646v2EthPortSwFOamEntry 234881024}

pr1646v2EthPortSwFOamUnsupportedCodesTx OBJECT-TYPE
   SYNTAX      Counter32
   MAX-ACCESS  read-only
   STATUS      current
   DESCRIPTION
      "Path: swPort.performance.oam.unsupportedCodesTx

       32 bit unsigned wrappable counter."
   ::= {pr1646v2EthPortSwFOamEntry 251658240}

pr1646v2EthPortSwFOamUnsupportedCodesRx OBJECT-TYPE
   SYNTAX      Counter32
   MAX-ACCESS  read-only
   STATUS      current
   DESCRIPTION
      "Path: swPort.performance.oam.unsupportedCodesRx

       32 bit unsigned wrappable counter."
   ::= {pr1646v2EthPortSwFOamEntry 268435456}

pr1646v2EthPortSwFOamPduDiscardRx OBJECT-TYPE
   SYNTAX      Counter32
   MAX-ACCESS  read-only
   STATUS      current
   DESCRIPTION
      "Path: swPort.performance.oam.pduDiscardRx

       32 bit unsigned wrappable counter."
   ::= {pr1646v2EthPortSwFOamEntry 1694498816}

pr1646v2EthPortSwFOamDataDiscardTx OBJECT-TYPE
   SYNTAX      Counter32
   MAX-ACCESS  read-only
   STATUS      current
   DESCRIPTION
      "Path: swPort.performance.oam.dataDiscardTx

       32 bit unsigned wrappable counter."
   ::= {pr1646v2EthPortSwFOamEntry 1711276032}

pr1646v2EthPortSwFOamDataDiscardRx OBJECT-TYPE
   SYNTAX      Counter32
   MAX-ACCESS  read-only
   STATUS      current
   DESCRIPTION
      "Path: swPort.performance.oam.dataDiscardRx

       32 bit unsigned wrappable counter."
   ::= {pr1646v2EthPortSwFOamEntry 1728053248}


pr1646v2EthPortSwFVlan OBJECT IDENTIFIER ::= {pr1646v2EthPortSwF 310}

pr1646v2EthPortSwFVlanSSCTable OBJECT-TYPE
   SYNTAX      SEQUENCE OF Pr1646v2EthPortSwFVlanEntry
   MAX-ACCESS  not-accessible
   STATUS      current
   DESCRIPTION
      ""
   ::= {pr1646v2EthPortSwFVlan 1}

pr1646v2EthPortSwFVlanEntry OBJECT-TYPE
   SYNTAX      Pr1646v2EthPortSwFVlanEntry
   MAX-ACCESS  not-accessible
   STATUS      current
   DESCRIPTION
      ""
   INDEX      { pr1646v2EthPortSwFVlanGlobalIx,
                pr1646v2EthPortSwFVlanTableIx }
   ::= {pr1646v2EthPortSwFVlanSSCTable 1}

Pr1646v2EthPortSwFVlanEntry ::=
   SEQUENCE
      {
      pr1646v2EthPortSwFVlanGlobalIx
         GlobalIndex,
      pr1646v2EthPortSwFVlanTableIx
         TableIndex,
      pr1646v2EthPortSwFVlanName
         DisplayString,
      pr1646v2EthPortSwFVlanMCInOctets
         Counter64,
      pr1646v2EthPortSwFVlanMCInUcast
         Counter64,
      pr1646v2EthPortSwFVlanMCInNUcastPkts
         Counter64,
      pr1646v2EthPortSwFVlanMCInBcastPkts
         Counter64,
      pr1646v2EthPortSwFVlanMCInMcastPkts
         Counter64,
      pr1646v2EthPortSwFVlanMCInDiscards
         Counter64,
      pr1646v2EthPortSwFVlanMCInErrors
         Counter64,
      pr1646v2EthPortSwFVlanMCInUnknownProtos
         Counter64,
      pr1646v2EthPortSwFVlanMCInDropEx
         Counter64,
      pr1646v2EthPortSwFVlanMCInDropNoMac
         Counter64,
      pr1646v2EthPortSwFVlanMCInDropNUCast
         Counter64,
      pr1646v2EthPortSwFVlanMCInDropFilter
         Counter64,
      pr1646v2EthPortSwFVlanMCInBandwidth15sec
         Integer32,
      pr1646v2EthPortSwFVlanMCInBandwidth30sec
         Integer32,
      pr1646v2EthPortSwFVlanMCInBandwidth1min
         Integer32,
      pr1646v2EthPortSwFVlanMCInBandwidth2min
         Integer32,
      pr1646v2EthPortSwFVlanMCInBandwidth5min
         Integer32,
      pr1646v2EthPortSwFVlanMCOutOctets
         Counter64,
      pr1646v2EthPortSwFVlanMCOutUcastPkts
         Counter64,
      pr1646v2EthPortSwFVlanMCOutNUcastPkts
         Counter64,
      pr1646v2EthPortSwFVlanMCOutBcastPkts
         Counter64,
      pr1646v2EthPortSwFVlanMCOutMcastPkts
         Counter64,
      pr1646v2EthPortSwFVlanMCOutDiscards
         Counter64,
      pr1646v2EthPortSwFVlanMCOutErrors
         Counter64,
      pr1646v2EthPortSwFVlanMCOutQLen
         Counter32,
      pr1646v2EthPortSwFVlanMCOutDropEx
         Counter64,
      pr1646v2EthPortSwFVlanMCOutDropNoArp
         Counter64,
      pr1646v2EthPortSwFVlanMCOutDropFilter
         Counter64,
      pr1646v2EthPortSwFVlanMCOutBandwidth15sec
         Integer32,
      pr1646v2EthPortSwFVlanMCOutBandwidth30sec
         Integer32,
      pr1646v2EthPortSwFVlanMCOutBandwidth1min
         Integer32,
      pr1646v2EthPortSwFVlanMCOutBandwidth2min
         Integer32,
      pr1646v2EthPortSwFVlanMCOutBandwidth5min
         Integer32,
      pr1646v2EthPortSwFVlanVlanVid
         Integer32,
      pr1646v2EthPortSwFVlanPppLinkMonitoringRequestsSent
         Gauge32,
      pr1646v2EthPortSwFVlanPppLinkMonitoringRepliesRcvd
         Gauge32,
      pr1646v2EthPortSwFVlanPppLinkMonitoringRequestsRcvd
         Gauge32,
      pr1646v2EthPortSwFVlanPppLinkMonitoringRepliesSent
         Gauge32
      }

pr1646v2EthPortSwFVlanGlobalIx OBJECT-TYPE
   SYNTAX      GlobalIndex
   MAX-ACCESS  not-accessible
   STATUS      current
   DESCRIPTION
      "The value of the tlsCntTreeGlobalIndex of the MANAGED OBJECT."
   ::= {pr1646v2EthPortSwFVlanEntry 10}

pr1646v2EthPortSwFVlanTableIx OBJECT-TYPE
   SYNTAX      TableIndex
   MAX-ACCESS  not-accessible
   STATUS      current
   DESCRIPTION
      ""
   ::= {pr1646v2EthPortSwFVlanEntry 11}

pr1646v2EthPortSwFVlanName OBJECT-TYPE
   SYNTAX      DisplayString
   MAX-ACCESS  read-only
   STATUS      current
   DESCRIPTION
      "Path: swPort.performance.vlan.name"
   ::= {pr1646v2EthPortSwFVlanEntry 16777216}

pr1646v2EthPortSwFVlanMCInOctets OBJECT-TYPE
   SYNTAX      Counter64
   MAX-ACCESS  read-only
   STATUS      current
   DESCRIPTION
      "Path: swPort.performance.vlan.mibCounters.ifInOctets

       64 bit unsigned wrappable counter."
   ::= {pr1646v2EthPortSwFVlanEntry 40697856}

pr1646v2EthPortSwFVlanMCInUcast OBJECT-TYPE
   SYNTAX      Counter64
   MAX-ACCESS  read-only
   STATUS      current
   DESCRIPTION
      "Path: swPort.performance.vlan.mibCounters.ifInUcastPkts

       64 bit unsigned wrappable counter."
   ::= {pr1646v2EthPortSwFVlanEntry 40763392}

pr1646v2EthPortSwFVlanMCInNUcastPkts OBJECT-TYPE
   SYNTAX      Counter64
   MAX-ACCESS  read-only
   STATUS      current
   DESCRIPTION
      "Path: swPort.performance.vlan.mibCounters.ifInNUcastPkts

       64 bit unsigned wrappable counter."
   ::= {pr1646v2EthPortSwFVlanEntry 40828928}

pr1646v2EthPortSwFVlanMCInBcastPkts OBJECT-TYPE
   SYNTAX      Counter64
   MAX-ACCESS  read-only
   STATUS      current
   DESCRIPTION
      "Path: swPort.performance.vlan.mibCounters.ifInBcastPkts

       64 bit unsigned wrappable counter."
   ::= {pr1646v2EthPortSwFVlanEntry 47382528}

pr1646v2EthPortSwFVlanMCInMcastPkts OBJECT-TYPE
   SYNTAX      Counter64
   MAX-ACCESS  read-only
   STATUS      current
   DESCRIPTION
      "Path: swPort.performance.vlan.mibCounters.ifInMcastPkts

       64 bit unsigned wrappable counter."
   ::= {pr1646v2EthPortSwFVlanEntry 48037888}

pr1646v2EthPortSwFVlanMCInDiscards OBJECT-TYPE
   SYNTAX      Counter64
   MAX-ACCESS  read-only
   STATUS      current
   DESCRIPTION
      "Path: swPort.performance.vlan.mibCounters.ifInDiscards

       64 bit unsigned wrappable counter."
   ::= {pr1646v2EthPortSwFVlanEntry 40894464}

pr1646v2EthPortSwFVlanMCInErrors OBJECT-TYPE
   SYNTAX      Counter64
   MAX-ACCESS  read-only
   STATUS      current
   DESCRIPTION
      "Path: swPort.performance.vlan.mibCounters.ifInErrors

       64 bit unsigned wrappable counter."
   ::= {pr1646v2EthPortSwFVlanEntry 40960000}

pr1646v2EthPortSwFVlanMCInUnknownProtos OBJECT-TYPE
   SYNTAX      Counter64
   MAX-ACCESS  read-only
   STATUS      current
   DESCRIPTION
      "Path: swPort.performance.vlan.mibCounters.ifInUnknownProtos

       64 bit unsigned wrappable counter."
   ::= {pr1646v2EthPortSwFVlanEntry 41025536}

pr1646v2EthPortSwFVlanMCInDropEx OBJECT-TYPE
   SYNTAX      Counter64
   MAX-ACCESS  read-only
   STATUS      current
   DESCRIPTION
      "Path: swPort.performance.vlan.mibCounters.ifInDropLevelExceeded

       64 bit unsigned wrappable counter."
   ::= {pr1646v2EthPortSwFVlanEntry 42074112}

pr1646v2EthPortSwFVlanMCInDropNoMac OBJECT-TYPE
   SYNTAX      Counter64
   MAX-ACCESS  read-only
   STATUS      current
   DESCRIPTION
      "Path: swPort.performance.vlan.mibCounters.ifInDiscardsNoMacFit

       64 bit unsigned wrappable counter."
   ::= {pr1646v2EthPortSwFVlanEntry 42270720}

pr1646v2EthPortSwFVlanMCInDropNUCast OBJECT-TYPE
   SYNTAX      Counter64
   MAX-ACCESS  read-only
   STATUS      current
   DESCRIPTION
      "Path: swPort.performance.vlan.mibCounters.ifInDiscardsNUCast

       64 bit unsigned wrappable counter."
   ::= {pr1646v2EthPortSwFVlanEntry 42467328}

pr1646v2EthPortSwFVlanMCInDropFilter OBJECT-TYPE
   SYNTAX      Counter64
   MAX-ACCESS  read-only
   STATUS      current
   DESCRIPTION
      "Path: swPort.performance.vlan.mibCounters.ifInDiscardsFilter

       64 bit unsigned wrappable counter."
   ::= {pr1646v2EthPortSwFVlanEntry 42532864}

pr1646v2EthPortSwFVlanMCInBandwidth15sec OBJECT-TYPE
   SYNTAX      Integer32
   MAX-ACCESS  read-only
   STATUS      current
   DESCRIPTION
      "Path: swPort.performance.vlan.mibCounters.ifInBandwidth.15sec

       unit name = bps
       formula = 8 * ; 8 /"
   ::= {pr1646v2EthPortSwFVlanEntry 45417728}

pr1646v2EthPortSwFVlanMCInBandwidth30sec OBJECT-TYPE
   SYNTAX      Integer32
   MAX-ACCESS  read-only
   STATUS      current
   DESCRIPTION
      "Path: swPort.performance.vlan.mibCounters.ifInBandwidth.30sec

       unit name = bps
       formula = 8 * ; 8 /"
   ::= {pr1646v2EthPortSwFVlanEntry 45419008}

pr1646v2EthPortSwFVlanMCInBandwidth1min OBJECT-TYPE
   SYNTAX      Integer32
   MAX-ACCESS  read-only
   STATUS      current
   DESCRIPTION
      "Path: swPort.performance.vlan.mibCounters.ifInBandwidth.1min

       unit name = bps
       formula = 8 * ; 8 /"
   ::= {pr1646v2EthPortSwFVlanEntry 45421568}

pr1646v2EthPortSwFVlanMCInBandwidth2min OBJECT-TYPE
   SYNTAX      Integer32
   MAX-ACCESS  read-only
   STATUS      current
   DESCRIPTION
      "Path: swPort.performance.vlan.mibCounters.ifInBandwidth.2min

       unit name = bps
       formula = 8 * ; 8 /"
   ::= {pr1646v2EthPortSwFVlanEntry 45426688}

pr1646v2EthPortSwFVlanMCInBandwidth5min OBJECT-TYPE
   SYNTAX      Integer32
   MAX-ACCESS  read-only
   STATUS      current
   DESCRIPTION
      "Path: swPort.performance.vlan.mibCounters.ifInBandwidth.5min

       unit name = bps
       formula = 8 * ; 8 /"
   ::= {pr1646v2EthPortSwFVlanEntry 45442048}

pr1646v2EthPortSwFVlanMCOutOctets OBJECT-TYPE
   SYNTAX      Counter64
   MAX-ACCESS  read-only
   STATUS      current
   DESCRIPTION
      "Path: swPort.performance.vlan.mibCounters.ifOutOctets

       64 bit unsigned wrappable counter."
   ::= {pr1646v2EthPortSwFVlanEntry 41091072}

pr1646v2EthPortSwFVlanMCOutUcastPkts OBJECT-TYPE
   SYNTAX      Counter64
   MAX-ACCESS  read-only
   STATUS      current
   DESCRIPTION
      "Path: swPort.performance.vlan.mibCounters.ifOutUcastPkts

       64 bit unsigned wrappable counter."
   ::= {pr1646v2EthPortSwFVlanEntry 41156608}

pr1646v2EthPortSwFVlanMCOutNUcastPkts OBJECT-TYPE
   SYNTAX      Counter64
   MAX-ACCESS  read-only
   STATUS      current
   DESCRIPTION
      "Path: swPort.performance.vlan.mibCounters.ifOutNUcastPkts

       64 bit unsigned wrappable counter."
   ::= {pr1646v2EthPortSwFVlanEntry 41222144}

pr1646v2EthPortSwFVlanMCOutBcastPkts OBJECT-TYPE
   SYNTAX      Counter64
   MAX-ACCESS  read-only
   STATUS      current
   DESCRIPTION
      "Path: swPort.performance.vlan.mibCounters.ifOutBcastPkts

       64 bit unsigned wrappable counter."
   ::= {pr1646v2EthPortSwFVlanEntry 47775744}

pr1646v2EthPortSwFVlanMCOutMcastPkts OBJECT-TYPE
   SYNTAX      Counter64
   MAX-ACCESS  read-only
   STATUS      current
   DESCRIPTION
      "Path: swPort.performance.vlan.mibCounters.ifOutMcastPkts

       64 bit unsigned wrappable counter."
   ::= {pr1646v2EthPortSwFVlanEntry 48431104}

pr1646v2EthPortSwFVlanMCOutDiscards OBJECT-TYPE
   SYNTAX      Counter64
   MAX-ACCESS  read-only
   STATUS      current
   DESCRIPTION
      "Path: swPort.performance.vlan.mibCounters.ifOutDiscards

       64 bit unsigned wrappable counter."
   ::= {pr1646v2EthPortSwFVlanEntry 41287680}

pr1646v2EthPortSwFVlanMCOutErrors OBJECT-TYPE
   SYNTAX      Counter64
   MAX-ACCESS  read-only
   STATUS      current
   DESCRIPTION
      "Path: swPort.performance.vlan.mibCounters.ifOutErrors

       64 bit unsigned wrappable counter."
   ::= {pr1646v2EthPortSwFVlanEntry 41353216}

pr1646v2EthPortSwFVlanMCOutQLen OBJECT-TYPE
   SYNTAX      Counter32
   MAX-ACCESS  read-only
   STATUS      current
   DESCRIPTION
      "Path: swPort.performance.vlan.mibCounters.ifOutQLen

       32 bit unsigned wrappable counter."
   ::= {pr1646v2EthPortSwFVlanEntry 41418752}

pr1646v2EthPortSwFVlanMCOutDropEx OBJECT-TYPE
   SYNTAX      Counter64
   MAX-ACCESS  read-only
   STATUS      current
   DESCRIPTION
      "Path: swPort.performance.vlan.mibCounters.ifOutDropLevelExceeded

       64 bit unsigned wrappable counter."
   ::= {pr1646v2EthPortSwFVlanEntry 41484288}

pr1646v2EthPortSwFVlanMCOutDropNoArp OBJECT-TYPE
   SYNTAX      Counter64
   MAX-ACCESS  read-only
   STATUS      current
   DESCRIPTION
      "Path: swPort.performance.vlan.mibCounters.ifOutDiscardsNoArp

       64 bit unsigned wrappable counter."
   ::= {pr1646v2EthPortSwFVlanEntry 42336256}

pr1646v2EthPortSwFVlanMCOutDropFilter OBJECT-TYPE
   SYNTAX      Counter64
   MAX-ACCESS  read-only
   STATUS      current
   DESCRIPTION
      "Path: swPort.performance.vlan.mibCounters.ifOutDiscardsFilter

       64 bit unsigned wrappable counter."
   ::= {pr1646v2EthPortSwFVlanEntry 42598400}

pr1646v2EthPortSwFVlanMCOutBandwidth15sec OBJECT-TYPE
   SYNTAX      Integer32
   MAX-ACCESS  read-only
   STATUS      current
   DESCRIPTION
      "Path: swPort.performance.vlan.mibCounters.ifOutBandwidth.15sec

       unit name = bps
       formula = 8 * ; 8 /"
   ::= {pr1646v2EthPortSwFVlanEntry 45483264}

pr1646v2EthPortSwFVlanMCOutBandwidth30sec OBJECT-TYPE
   SYNTAX      Integer32
   MAX-ACCESS  read-only
   STATUS      current
   DESCRIPTION
      "Path: swPort.performance.vlan.mibCounters.ifOutBandwidth.30sec

       unit name = bps
       formula = 8 * ; 8 /"
   ::= {pr1646v2EthPortSwFVlanEntry 45484544}

pr1646v2EthPortSwFVlanMCOutBandwidth1min OBJECT-TYPE
   SYNTAX      Integer32
   MAX-ACCESS  read-only
   STATUS      current
   DESCRIPTION
      "Path: swPort.performance.vlan.mibCounters.ifOutBandwidth.1min

       unit name = bps
       formula = 8 * ; 8 /"
   ::= {pr1646v2EthPortSwFVlanEntry 45487104}

pr1646v2EthPortSwFVlanMCOutBandwidth2min OBJECT-TYPE
   SYNTAX      Integer32
   MAX-ACCESS  read-only
   STATUS      current
   DESCRIPTION
      "Path: swPort.performance.vlan.mibCounters.ifOutBandwidth.2min

       unit name = bps
       formula = 8 * ; 8 /"
   ::= {pr1646v2EthPortSwFVlanEntry 45492224}

pr1646v2EthPortSwFVlanMCOutBandwidth5min OBJECT-TYPE
   SYNTAX      Integer32
   MAX-ACCESS  read-only
   STATUS      current
   DESCRIPTION
      "Path: swPort.performance.vlan.mibCounters.ifOutBandwidth.5min

       unit name = bps
       formula = 8 * ; 8 /"
   ::= {pr1646v2EthPortSwFVlanEntry 45507584}

pr1646v2EthPortSwFVlanVlanVid OBJECT-TYPE
   SYNTAX      Integer32
   MAX-ACCESS  read-only
   STATUS      current
   DESCRIPTION
      "Path: swPort.performance.vlan.vlan.vid"
   ::= {pr1646v2EthPortSwFVlanEntry 234946560}

pr1646v2EthPortSwFVlanPppLinkMonitoringRequestsSent OBJECT-TYPE
   SYNTAX      Gauge32
   MAX-ACCESS  read-only
   STATUS      current
   DESCRIPTION
      "Path: swPort.performance.vlan.ppp.linkMonitoring.requestsSent

       32 bit unsigned gauge value."
   ::= {pr1646v2EthPortSwFVlanEntry 50397440}

pr1646v2EthPortSwFVlanPppLinkMonitoringRepliesRcvd OBJECT-TYPE
   SYNTAX      Gauge32
   MAX-ACCESS  read-only
   STATUS      current
   DESCRIPTION
      "Path: swPort.performance.vlan.ppp.linkMonitoring.repliesRcvd

       32 bit unsigned gauge value."
   ::= {pr1646v2EthPortSwFVlanEntry 50397696}

pr1646v2EthPortSwFVlanPppLinkMonitoringRequestsRcvd OBJECT-TYPE
   SYNTAX      Gauge32
   MAX-ACCESS  read-only
   STATUS      current
   DESCRIPTION
      "Path: swPort.performance.vlan.ppp.linkMonitoring.requestsRcvd

       32 bit unsigned gauge value."
   ::= {pr1646v2EthPortSwFVlanEntry 50397952}

pr1646v2EthPortSwFVlanPppLinkMonitoringRepliesSent OBJECT-TYPE
   SYNTAX      Gauge32
   MAX-ACCESS  read-only
   STATUS      current
   DESCRIPTION
      "Path: swPort.performance.vlan.ppp.linkMonitoring.repliesSent

       32 bit unsigned gauge value."
   ::= {pr1646v2EthPortSwFVlanEntry 50398208}

pr1646v2EthPortSwFVlanMCH2P OBJECT-TYPE
   SYNTAX      SEQUENCE OF Pr1646v2EthPortSwFVlanMCH2PEntry
   MAX-ACCESS  not-accessible
   STATUS      current
   DESCRIPTION
      ""
   ::= {pr1646v2EthPortSwFVlan 41549824}

pr1646v2EthPortSwFVlanMCH2PEntry OBJECT-TYPE
   SYNTAX      Pr1646v2EthPortSwFVlanMCH2PEntry
   MAX-ACCESS  not-accessible
   STATUS      current
   DESCRIPTION
      ""
   INDEX      { pr1646v2EthPortSwFVlanMCH2PGlobalIx,
                pr1646v2EthPortSwFVlanTableIx,
                pr1646v2EthPortSwFVlanMCH2PTableIx }
   ::= {pr1646v2EthPortSwFVlanMCH2P 1}

Pr1646v2EthPortSwFVlanMCH2PEntry ::=
   SEQUENCE
      {
      pr1646v2EthPortSwFVlanMCH2PGlobalIx
         GlobalIndex,
      pr1646v2EthPortSwFVlanMCH2PTableIx
         TableIndex,
      pr1646v2EthPortSwFVlanMCH2PSysUpTime
         TimeTicks,
      pr1646v2EthPortSwFVlanMCH2PIfUpTime
         TimeTicks,
      pr1646v2EthPortSwFVlanMCH2PIfStatChanges
         Counter32,
      pr1646v2EthPortSwFVlanMCH2PIfInOctets
         Counter64,
      pr1646v2EthPortSwFVlanMCH2PIfInUCPkts
         Counter64,
      pr1646v2EthPortSwFVlanMCH2PIfInNUCPkts
         Counter64,
      pr1646v2EthPortSwFVlanMCH2PIfInBCPkts
         Counter64,
      pr1646v2EthPortSwFVlanMCH2PIfInMCPkts
         Counter64,
      pr1646v2EthPortSwFVlanMCH2PIfInDiscards
         Counter64,
      pr1646v2EthPortSwFVlanMCH2PIfInErrors
         Counter64,
      pr1646v2EthPortSwFVlanMCH2PIfInUnkwn
         Counter64,
      pr1646v2EthPortSwFVlanMCH2PInDropEx
         Counter64,
      pr1646v2EthPortSwFVlanMCH2PInDropNoMac
         Counter64,
      pr1646v2EthPortSwFVlanMCH2PInDropNUCast
         Counter64,
      pr1646v2EthPortSwFVlanMCH2PInDropFilter
         Counter64,
      pr1646v2EthPortSwFVlanMCH2PIfInBandwidth
         Integer32,
      pr1646v2EthPortSwFVlanMCH2PIfOutOctets
         Counter64,
      pr1646v2EthPortSwFVlanMCH2PIfOutUCPkts
         Counter64,
      pr1646v2EthPortSwFVlanMCH2PIfOutNUCPkts
         Counter64,
      pr1646v2EthPortSwFVlanMCH2PIfOutBCPkts
         Counter64,
      pr1646v2EthPortSwFVlanMCH2PIfOutMCPkts
         Counter64,
      pr1646v2EthPortSwFVlanMCH2PIfOutDiscards
         Counter64,
      pr1646v2EthPortSwFVlanMCH2PIfOutErrors
         Counter64,
      pr1646v2EthPortSwFVlanMCH2POutDropEx
         Counter64,
      pr1646v2EthPortSwFVlanMCH2POutDropNoArp
         Counter64,
      pr1646v2EthPortSwFVlanMCH2POutDropFilter
         Counter64,
      pr1646v2EthPortSwFVlanMCH2PIfOutBandwidth
         Integer32,
      pr1646v2EthPortSwFVlanMCH2PIfErrSec
         Counter32
      }

pr1646v2EthPortSwFVlanMCH2PGlobalIx OBJECT-TYPE
   SYNTAX      GlobalIndex
   MAX-ACCESS  not-accessible
   STATUS      current
   DESCRIPTION
      "The value of the tlsCntTreeGlobalIndex of the MANAGED OBJECT."
   ::= {pr1646v2EthPortSwFVlanMCH2PEntry 10}

pr1646v2EthPortSwFVlanMCH2PTableIx OBJECT-TYPE
   SYNTAX      TableIndex
   MAX-ACCESS  not-accessible
   STATUS      current
   DESCRIPTION
      ""
   ::= {pr1646v2EthPortSwFVlanMCH2PEntry 11}

pr1646v2EthPortSwFVlanMCH2PSysUpTime OBJECT-TYPE
   SYNTAX      TimeTicks
   MAX-ACCESS  read-only
   STATUS      current
   DESCRIPTION
      "Path: swPort.performance.vlan.mibCounters.h2Performance.sysUpTime

       Time in centi-second."
   ::= {pr1646v2EthPortSwFVlanMCH2PEntry 16777216}

pr1646v2EthPortSwFVlanMCH2PIfUpTime OBJECT-TYPE
   SYNTAX      TimeTicks
   MAX-ACCESS  read-only
   STATUS      current
   DESCRIPTION
      "Path: swPort.performance.vlan.mibCounters.h2Performance.ifUpTime

       Time in centi-second."
   ::= {pr1646v2EthPortSwFVlanMCH2PEntry 33554432}

pr1646v2EthPortSwFVlanMCH2PIfStatChanges OBJECT-TYPE
   SYNTAX      Counter32
   MAX-ACCESS  read-only
   STATUS      current
   DESCRIPTION
      "Path: swPort.performance.vlan.mibCounters.h2Performance.ifStatusChanges

       32 bit unsigned wrappable counter."
   ::= {pr1646v2EthPortSwFVlanMCH2PEntry 50331648}

pr1646v2EthPortSwFVlanMCH2PIfInOctets OBJECT-TYPE
   SYNTAX      Counter64
   MAX-ACCESS  read-only
   STATUS      current
   DESCRIPTION
      "Path: swPort.performance.vlan.mibCounters.h2Performance.ifInOctets

       64 bit unsigned wrappable counter."
   ::= {pr1646v2EthPortSwFVlanMCH2PEntry 67108864}

pr1646v2EthPortSwFVlanMCH2PIfInUCPkts OBJECT-TYPE
   SYNTAX      Counter64
   MAX-ACCESS  read-only
   STATUS      current
   DESCRIPTION
      "Path: swPort.performance.vlan.mibCounters.h2Performance.ifInUcastPkts

       64 bit unsigned wrappable counter."
   ::= {pr1646v2EthPortSwFVlanMCH2PEntry 83886080}

pr1646v2EthPortSwFVlanMCH2PIfInNUCPkts OBJECT-TYPE
   SYNTAX      Counter64
   MAX-ACCESS  read-only
   STATUS      current
   DESCRIPTION
      "Path: swPort.performance.vlan.mibCounters.h2Performance.ifInNUcastPkts

       64 bit unsigned wrappable counter."
   ::= {pr1646v2EthPortSwFVlanMCH2PEntry 100663296}

pr1646v2EthPortSwFVlanMCH2PIfInBCPkts OBJECT-TYPE
   SYNTAX      Counter64
   MAX-ACCESS  read-only
   STATUS      current
   DESCRIPTION
      "Path: swPort.performance.vlan.mibCounters.h2Performance.ifInBcastPkts

       64 bit unsigned wrappable counter."
   ::= {pr1646v2EthPortSwFVlanMCH2PEntry 419430400}

pr1646v2EthPortSwFVlanMCH2PIfInMCPkts OBJECT-TYPE
   SYNTAX      Counter64
   MAX-ACCESS  read-only
   STATUS      current
   DESCRIPTION
      "Path: swPort.performance.vlan.mibCounters.h2Performance.ifInMcastPkts

       64 bit unsigned wrappable counter."
   ::= {pr1646v2EthPortSwFVlanMCH2PEntry 436207616}

pr1646v2EthPortSwFVlanMCH2PIfInDiscards OBJECT-TYPE
   SYNTAX      Counter64
   MAX-ACCESS  read-only
   STATUS      current
   DESCRIPTION
      "Path: swPort.performance.vlan.mibCounters.h2Performance.ifInDiscards

       64 bit unsigned wrappable counter."
   ::= {pr1646v2EthPortSwFVlanMCH2PEntry 117440512}

pr1646v2EthPortSwFVlanMCH2PIfInErrors OBJECT-TYPE
   SYNTAX      Counter64
   MAX-ACCESS  read-only
   STATUS      current
   DESCRIPTION
      "Path: swPort.performance.vlan.mibCounters.h2Performance.ifInErrors

       64 bit unsigned wrappable counter."
   ::= {pr1646v2EthPortSwFVlanMCH2PEntry 134217728}

pr1646v2EthPortSwFVlanMCH2PIfInUnkwn OBJECT-TYPE
   SYNTAX      Counter64
   MAX-ACCESS  read-only
   STATUS      current
   DESCRIPTION
      "Path: swPort.performance.vlan.mibCounters.h2Performance.ifInUnknownProtos

       64 bit unsigned wrappable counter."
   ::= {pr1646v2EthPortSwFVlanMCH2PEntry 150994944}

pr1646v2EthPortSwFVlanMCH2PInDropEx OBJECT-TYPE
   SYNTAX      Counter64
   MAX-ACCESS  read-only
   STATUS      current
   DESCRIPTION
      "Path: swPort.performance.vlan.mibCounters.h2Performance.ifInDropLevelExceeded

       64 bit unsigned wrappable counter."
   ::= {pr1646v2EthPortSwFVlanMCH2PEntry 335544320}

pr1646v2EthPortSwFVlanMCH2PInDropNoMac OBJECT-TYPE
   SYNTAX      Counter64
   MAX-ACCESS  read-only
   STATUS      current
   DESCRIPTION
      "Path: swPort.performance.vlan.mibCounters.h2Performance.fInDiscardsNoMacFit

       64 bit unsigned wrappable counter."
   ::= {pr1646v2EthPortSwFVlanMCH2PEntry 301989888}

pr1646v2EthPortSwFVlanMCH2PInDropNUCast OBJECT-TYPE
   SYNTAX      Counter64
   MAX-ACCESS  read-only
   STATUS      current
   DESCRIPTION
      "Path: swPort.performance.vlan.mibCounters.h2Performance.fInDiscardsNUCast

       64 bit unsigned wrappable counter."
   ::= {pr1646v2EthPortSwFVlanMCH2PEntry 318767104}

pr1646v2EthPortSwFVlanMCH2PInDropFilter OBJECT-TYPE
   SYNTAX      Counter64
   MAX-ACCESS  read-only
   STATUS      current
   DESCRIPTION
      "Path: swPort.performance.vlan.mibCounters.h2Performance.fInDiscardsFilter

       64 bit unsigned wrappable counter."
   ::= {pr1646v2EthPortSwFVlanMCH2PEntry 385875968}

pr1646v2EthPortSwFVlanMCH2PIfInBandwidth OBJECT-TYPE
   SYNTAX      Integer32
   MAX-ACCESS  read-only
   STATUS      current
   DESCRIPTION
      "Path: swPort.performance.vlan.mibCounters.h2Performance.ifInBandwidth

       unit name = bps
       formula = 8 * ; 8 /"
   ::= {pr1646v2EthPortSwFVlanMCH2PEntry 268435456}

pr1646v2EthPortSwFVlanMCH2PIfOutOctets OBJECT-TYPE
   SYNTAX      Counter64
   MAX-ACCESS  read-only
   STATUS      current
   DESCRIPTION
      "Path: swPort.performance.vlan.mibCounters.h2Performance.ifOutOctets

       64 bit unsigned wrappable counter."
   ::= {pr1646v2EthPortSwFVlanMCH2PEntry 167772160}

pr1646v2EthPortSwFVlanMCH2PIfOutUCPkts OBJECT-TYPE
   SYNTAX      Counter64
   MAX-ACCESS  read-only
   STATUS      current
   DESCRIPTION
      "Path: swPort.performance.vlan.mibCounters.h2Performance.ifOutUcastPkts

       64 bit unsigned wrappable counter."
   ::= {pr1646v2EthPortSwFVlanMCH2PEntry 184549376}

pr1646v2EthPortSwFVlanMCH2PIfOutNUCPkts OBJECT-TYPE
   SYNTAX      Counter64
   MAX-ACCESS  read-only
   STATUS      current
   DESCRIPTION
      "Path: swPort.performance.vlan.mibCounters.h2Performance.ifOutNUcastPkts

       64 bit unsigned wrappable counter."
   ::= {pr1646v2EthPortSwFVlanMCH2PEntry 201326592}

pr1646v2EthPortSwFVlanMCH2PIfOutBCPkts OBJECT-TYPE
   SYNTAX      Counter64
   MAX-ACCESS  read-only
   STATUS      current
   DESCRIPTION
      "Path: swPort.performance.vlan.mibCounters.h2Performance.ifOutBcastPkts

       64 bit unsigned wrappable counter."
   ::= {pr1646v2EthPortSwFVlanMCH2PEntry 452984832}

pr1646v2EthPortSwFVlanMCH2PIfOutMCPkts OBJECT-TYPE
   SYNTAX      Counter64
   MAX-ACCESS  read-only
   STATUS      current
   DESCRIPTION
      "Path: swPort.performance.vlan.mibCounters.h2Performance.ifOutMcastPkts

       64 bit unsigned wrappable counter."
   ::= {pr1646v2EthPortSwFVlanMCH2PEntry 469762048}

pr1646v2EthPortSwFVlanMCH2PIfOutDiscards OBJECT-TYPE
   SYNTAX      Counter64
   MAX-ACCESS  read-only
   STATUS      current
   DESCRIPTION
      "Path: swPort.performance.vlan.mibCounters.h2Performance.ifOutDiscards

       64 bit unsigned wrappable counter."
   ::= {pr1646v2EthPortSwFVlanMCH2PEntry 218103808}

pr1646v2EthPortSwFVlanMCH2PIfOutErrors OBJECT-TYPE
   SYNTAX      Counter64
   MAX-ACCESS  read-only
   STATUS      current
   DESCRIPTION
      "Path: swPort.performance.vlan.mibCounters.h2Performance.ifOutErrors

       64 bit unsigned wrappable counter."
   ::= {pr1646v2EthPortSwFVlanMCH2PEntry 234881024}

pr1646v2EthPortSwFVlanMCH2POutDropEx OBJECT-TYPE
   SYNTAX      Counter64
   MAX-ACCESS  read-only
   STATUS      current
   DESCRIPTION
      "Path: swPort.performance.vlan.mibCounters.h2Performance.ifOutDropLevelExceeded

       64 bit unsigned wrappable counter."
   ::= {pr1646v2EthPortSwFVlanMCH2PEntry 352321536}

pr1646v2EthPortSwFVlanMCH2POutDropNoArp OBJECT-TYPE
   SYNTAX      Counter64
   MAX-ACCESS  read-only
   STATUS      current
   DESCRIPTION
      "Path: swPort.performance.vlan.mibCounters.h2Performance.ifOutDiscardsNoArp

       64 bit unsigned wrappable counter."
   ::= {pr1646v2EthPortSwFVlanMCH2PEntry 369098752}

pr1646v2EthPortSwFVlanMCH2POutDropFilter OBJECT-TYPE
   SYNTAX      Counter64
   MAX-ACCESS  read-only
   STATUS      current
   DESCRIPTION
      "Path: swPort.performance.vlan.mibCounters.h2Performance.ifOutDiscardsFilter

       64 bit unsigned wrappable counter."
   ::= {pr1646v2EthPortSwFVlanMCH2PEntry 402653184}

pr1646v2EthPortSwFVlanMCH2PIfOutBandwidth OBJECT-TYPE
   SYNTAX      Integer32
   MAX-ACCESS  read-only
   STATUS      current
   DESCRIPTION
      "Path: swPort.performance.vlan.mibCounters.h2Performance.ifOutBandwidth

       unit name = bps
       formula = 8 * ; 8 /"
   ::= {pr1646v2EthPortSwFVlanMCH2PEntry 285212672}

pr1646v2EthPortSwFVlanMCH2PIfErrSec OBJECT-TYPE
   SYNTAX      Counter32
   MAX-ACCESS  read-only
   STATUS      current
   DESCRIPTION
      "Path: swPort.performance.vlan.mibCounters.h2Performance.ifErrSec

       32 bit unsigned wrappable counter."
   ::= {pr1646v2EthPortSwFVlanMCH2PEntry 251658240}

pr1646v2EthPortSwFVlanMCH24P OBJECT-TYPE
   SYNTAX      SEQUENCE OF Pr1646v2EthPortSwFVlanMCH24PEntry
   MAX-ACCESS  not-accessible
   STATUS      current
   DESCRIPTION
      ""
   ::= {pr1646v2EthPortSwFVlan 41615360}

pr1646v2EthPortSwFVlanMCH24PEntry OBJECT-TYPE
   SYNTAX      Pr1646v2EthPortSwFVlanMCH24PEntry
   MAX-ACCESS  not-accessible
   STATUS      current
   DESCRIPTION
      ""
   INDEX      { pr1646v2EthPortSwFVlanMCH24PGlobalIx,
                pr1646v2EthPortSwFVlanTableIx,
                pr1646v2EthPortSwFVlanMCH24PTableIx }
   ::= {pr1646v2EthPortSwFVlanMCH24P 1}

Pr1646v2EthPortSwFVlanMCH24PEntry ::=
   SEQUENCE
      {
      pr1646v2EthPortSwFVlanMCH24PGlobalIx
         GlobalIndex,
      pr1646v2EthPortSwFVlanMCH24PTableIx
         TableIndex,
      pr1646v2EthPortSwFVlanMCH24PSysUpTime
         TimeTicks,
      pr1646v2EthPortSwFVlanMCH24PIfUpTime
         TimeTicks,
      pr1646v2EthPortSwFVlanMCH24PIfStatChanges
         Counter32,
      pr1646v2EthPortSwFVlanMCH24PIfInOctets
         Counter64,
      pr1646v2EthPortSwFVlanMCH24PIfInUCPkts
         Counter64,
      pr1646v2EthPortSwFVlanMCH24PIfInNUCPkts
         Counter64,
      pr1646v2EthPortSwFVlanMCH24PIfInBCPkts
         Counter64,
      pr1646v2EthPortSwFVlanMCH24PIfInMCPkts
         Counter64,
      pr1646v2EthPortSwFVlanMCH24PIfInDiscards
         Counter64,
      pr1646v2EthPortSwFVlanMCH24PIfInErrors
         Counter64,
      pr1646v2EthPortSwFVlanMCH24PIfInUnkwn
         Counter64,
      pr1646v2EthPortSwFVlanMCH24PInDropEx
         Counter64,
      pr1646v2EthPortSwFVlanMCH24PInDropNoMac
         Counter64,
      pr1646v2EthPortSwFVlanMCH24PInDropNUCast
         Counter64,
      pr1646v2EthPortSwFVlanMCH24PInDropFilter
         Counter64,
      pr1646v2EthPortSwFVlanMCH24PIfInBandwidth
         Integer32,
      pr1646v2EthPortSwFVlanMCH24PIfOutOctets
         Counter64,
      pr1646v2EthPortSwFVlanMCH24PIfOutUCPkts
         Counter64,
      pr1646v2EthPortSwFVlanMCH24PIfOutNUCPkts
         Counter64,
      pr1646v2EthPortSwFVlanMCH24PIfOutBCPkts
         Counter64,
      pr1646v2EthPortSwFVlanMCH24PIfOutMCPkts
         Counter64,
      pr1646v2EthPortSwFVlanMCH24PIfOutDiscards
         Counter64,
      pr1646v2EthPortSwFVlanMCH24PIfOutErrors
         Counter64,
      pr1646v2EthPortSwFVlanMCH24POutDropEx
         Counter64,
      pr1646v2EthPortSwFVlanMCH24POutDropNoArp
         Counter64,
      pr1646v2EthPortSwFVlanMCH24POutDropFilter
         Counter64,
      pr1646v2EthPortSwFVlanMCH24PIfOutBandwidth
         Integer32,
      pr1646v2EthPortSwFVlanMCH24PIfErrSec
         Counter32
      }

pr1646v2EthPortSwFVlanMCH24PGlobalIx OBJECT-TYPE
   SYNTAX      GlobalIndex
   MAX-ACCESS  not-accessible
   STATUS      current
   DESCRIPTION
      "The value of the tlsCntTreeGlobalIndex of the MANAGED OBJECT."
   ::= {pr1646v2EthPortSwFVlanMCH24PEntry 10}

pr1646v2EthPortSwFVlanMCH24PTableIx OBJECT-TYPE
   SYNTAX      TableIndex
   MAX-ACCESS  not-accessible
   STATUS      current
   DESCRIPTION
      ""
   ::= {pr1646v2EthPortSwFVlanMCH24PEntry 11}

pr1646v2EthPortSwFVlanMCH24PSysUpTime OBJECT-TYPE
   SYNTAX      TimeTicks
   MAX-ACCESS  read-only
   STATUS      current
   DESCRIPTION
      "Path: swPort.performance.vlan.mibCounters.h24Performance.sysUpTime

       Time in centi-second."
   ::= {pr1646v2EthPortSwFVlanMCH24PEntry 16777216}

pr1646v2EthPortSwFVlanMCH24PIfUpTime OBJECT-TYPE
   SYNTAX      TimeTicks
   MAX-ACCESS  read-only
   STATUS      current
   DESCRIPTION
      "Path: swPort.performance.vlan.mibCounters.h24Performance.ifUpTime

       Time in centi-second."
   ::= {pr1646v2EthPortSwFVlanMCH24PEntry 33554432}

pr1646v2EthPortSwFVlanMCH24PIfStatChanges OBJECT-TYPE
   SYNTAX      Counter32
   MAX-ACCESS  read-only
   STATUS      current
   DESCRIPTION
      "Path: swPort.performance.vlan.mibCounters.h24Performance.ifStatusChanges

       32 bit unsigned wrappable counter."
   ::= {pr1646v2EthPortSwFVlanMCH24PEntry 50331648}

pr1646v2EthPortSwFVlanMCH24PIfInOctets OBJECT-TYPE
   SYNTAX      Counter64
   MAX-ACCESS  read-only
   STATUS      current
   DESCRIPTION
      "Path: swPort.performance.vlan.mibCounters.h24Performance.ifInOctets

       64 bit unsigned wrappable counter."
   ::= {pr1646v2EthPortSwFVlanMCH24PEntry 67108864}

pr1646v2EthPortSwFVlanMCH24PIfInUCPkts OBJECT-TYPE
   SYNTAX      Counter64
   MAX-ACCESS  read-only
   STATUS      current
   DESCRIPTION
      "Path: swPort.performance.vlan.mibCounters.h24Performance.ifInUcastPkts

       64 bit unsigned wrappable counter."
   ::= {pr1646v2EthPortSwFVlanMCH24PEntry 83886080}

pr1646v2EthPortSwFVlanMCH24PIfInNUCPkts OBJECT-TYPE
   SYNTAX      Counter64
   MAX-ACCESS  read-only
   STATUS      current
   DESCRIPTION
      "Path: swPort.performance.vlan.mibCounters.h24Performance.ifInNUcastPkts

       64 bit unsigned wrappable counter."
   ::= {pr1646v2EthPortSwFVlanMCH24PEntry 100663296}

pr1646v2EthPortSwFVlanMCH24PIfInBCPkts OBJECT-TYPE
   SYNTAX      Counter64
   MAX-ACCESS  read-only
   STATUS      current
   DESCRIPTION
      "Path: swPort.performance.vlan.mibCounters.h24Performance.ifInBcastPkts

       64 bit unsigned wrappable counter."
   ::= {pr1646v2EthPortSwFVlanMCH24PEntry 419430400}

pr1646v2EthPortSwFVlanMCH24PIfInMCPkts OBJECT-TYPE
   SYNTAX      Counter64
   MAX-ACCESS  read-only
   STATUS      current
   DESCRIPTION
      "Path: swPort.performance.vlan.mibCounters.h24Performance.ifInMcastPkts

       64 bit unsigned wrappable counter."
   ::= {pr1646v2EthPortSwFVlanMCH24PEntry 436207616}

pr1646v2EthPortSwFVlanMCH24PIfInDiscards OBJECT-TYPE
   SYNTAX      Counter64
   MAX-ACCESS  read-only
   STATUS      current
   DESCRIPTION
      "Path: swPort.performance.vlan.mibCounters.h24Performance.ifInDiscards

       64 bit unsigned wrappable counter."
   ::= {pr1646v2EthPortSwFVlanMCH24PEntry 117440512}

pr1646v2EthPortSwFVlanMCH24PIfInErrors OBJECT-TYPE
   SYNTAX      Counter64
   MAX-ACCESS  read-only
   STATUS      current
   DESCRIPTION
      "Path: swPort.performance.vlan.mibCounters.h24Performance.ifInErrors

       64 bit unsigned wrappable counter."
   ::= {pr1646v2EthPortSwFVlanMCH24PEntry 134217728}

pr1646v2EthPortSwFVlanMCH24PIfInUnkwn OBJECT-TYPE
   SYNTAX      Counter64
   MAX-ACCESS  read-only
   STATUS      current
   DESCRIPTION
      "Path: swPort.performance.vlan.mibCounters.h24Performance.ifInUnknownProtos

       64 bit unsigned wrappable counter."
   ::= {pr1646v2EthPortSwFVlanMCH24PEntry 150994944}

pr1646v2EthPortSwFVlanMCH24PInDropEx OBJECT-TYPE
   SYNTAX      Counter64
   MAX-ACCESS  read-only
   STATUS      current
   DESCRIPTION
      "Path: swPort.performance.vlan.mibCounters.h24Performance.ifInDropLevelExceeded

       64 bit unsigned wrappable counter."
   ::= {pr1646v2EthPortSwFVlanMCH24PEntry 335544320}

pr1646v2EthPortSwFVlanMCH24PInDropNoMac OBJECT-TYPE
   SYNTAX      Counter64
   MAX-ACCESS  read-only
   STATUS      current
   DESCRIPTION
      "Path: swPort.performance.vlan.mibCounters.h24Performance.fInDiscardsNoMacFit

       64 bit unsigned wrappable counter."
   ::= {pr1646v2EthPortSwFVlanMCH24PEntry 301989888}

pr1646v2EthPortSwFVlanMCH24PInDropNUCast OBJECT-TYPE
   SYNTAX      Counter64
   MAX-ACCESS  read-only
   STATUS      current
   DESCRIPTION
      "Path: swPort.performance.vlan.mibCounters.h24Performance.fInDiscardsNUCast

       64 bit unsigned wrappable counter."
   ::= {pr1646v2EthPortSwFVlanMCH24PEntry 318767104}

pr1646v2EthPortSwFVlanMCH24PInDropFilter OBJECT-TYPE
   SYNTAX      Counter64
   MAX-ACCESS  read-only
   STATUS      current
   DESCRIPTION
      "Path: swPort.performance.vlan.mibCounters.h24Performance.fInDiscardsFilter

       64 bit unsigned wrappable counter."
   ::= {pr1646v2EthPortSwFVlanMCH24PEntry 385875968}

pr1646v2EthPortSwFVlanMCH24PIfInBandwidth OBJECT-TYPE
   SYNTAX      Integer32
   MAX-ACCESS  read-only
   STATUS      current
   DESCRIPTION
      "Path: swPort.performance.vlan.mibCounters.h24Performance.ifInBandwidth

       unit name = bps
       formula = 8 * ; 8 /"
   ::= {pr1646v2EthPortSwFVlanMCH24PEntry 268435456}

pr1646v2EthPortSwFVlanMCH24PIfOutOctets OBJECT-TYPE
   SYNTAX      Counter64
   MAX-ACCESS  read-only
   STATUS      current
   DESCRIPTION
      "Path: swPort.performance.vlan.mibCounters.h24Performance.ifOutOctets

       64 bit unsigned wrappable counter."
   ::= {pr1646v2EthPortSwFVlanMCH24PEntry 167772160}

pr1646v2EthPortSwFVlanMCH24PIfOutUCPkts OBJECT-TYPE
   SYNTAX      Counter64
   MAX-ACCESS  read-only
   STATUS      current
   DESCRIPTION
      "Path: swPort.performance.vlan.mibCounters.h24Performance.ifOutUcastPkts

       64 bit unsigned wrappable counter."
   ::= {pr1646v2EthPortSwFVlanMCH24PEntry 184549376}

pr1646v2EthPortSwFVlanMCH24PIfOutNUCPkts OBJECT-TYPE
   SYNTAX      Counter64
   MAX-ACCESS  read-only
   STATUS      current
   DESCRIPTION
      "Path: swPort.performance.vlan.mibCounters.h24Performance.ifOutNUcastPkts

       64 bit unsigned wrappable counter."
   ::= {pr1646v2EthPortSwFVlanMCH24PEntry 201326592}

pr1646v2EthPortSwFVlanMCH24PIfOutBCPkts OBJECT-TYPE
   SYNTAX      Counter64
   MAX-ACCESS  read-only
   STATUS      current
   DESCRIPTION
      "Path: swPort.performance.vlan.mibCounters.h24Performance.ifOutBcastPkts

       64 bit unsigned wrappable counter."
   ::= {pr1646v2EthPortSwFVlanMCH24PEntry 452984832}

pr1646v2EthPortSwFVlanMCH24PIfOutMCPkts OBJECT-TYPE
   SYNTAX      Counter64
   MAX-ACCESS  read-only
   STATUS      current
   DESCRIPTION
      "Path: swPort.performance.vlan.mibCounters.h24Performance.ifOutMcastPkts

       64 bit unsigned wrappable counter."
   ::= {pr1646v2EthPortSwFVlanMCH24PEntry 469762048}

pr1646v2EthPortSwFVlanMCH24PIfOutDiscards OBJECT-TYPE
   SYNTAX      Counter64
   MAX-ACCESS  read-only
   STATUS      current
   DESCRIPTION
      "Path: swPort.performance.vlan.mibCounters.h24Performance.ifOutDiscards

       64 bit unsigned wrappable counter."
   ::= {pr1646v2EthPortSwFVlanMCH24PEntry 218103808}

pr1646v2EthPortSwFVlanMCH24PIfOutErrors OBJECT-TYPE
   SYNTAX      Counter64
   MAX-ACCESS  read-only
   STATUS      current
   DESCRIPTION
      "Path: swPort.performance.vlan.mibCounters.h24Performance.ifOutErrors

       64 bit unsigned wrappable counter."
   ::= {pr1646v2EthPortSwFVlanMCH24PEntry 234881024}

pr1646v2EthPortSwFVlanMCH24POutDropEx OBJECT-TYPE
   SYNTAX      Counter64
   MAX-ACCESS  read-only
   STATUS      current
   DESCRIPTION
      "Path: swPort.performance.vlan.mibCounters.h24Performance.ifOutDropLevelExceeded

       64 bit unsigned wrappable counter."
   ::= {pr1646v2EthPortSwFVlanMCH24PEntry 352321536}

pr1646v2EthPortSwFVlanMCH24POutDropNoArp OBJECT-TYPE
   SYNTAX      Counter64
   MAX-ACCESS  read-only
   STATUS      current
   DESCRIPTION
      "Path: swPort.performance.vlan.mibCounters.h24Performance.ifOutDiscardsNoArp

       64 bit unsigned wrappable counter."
   ::= {pr1646v2EthPortSwFVlanMCH24PEntry 369098752}

pr1646v2EthPortSwFVlanMCH24POutDropFilter OBJECT-TYPE
   SYNTAX      Counter64
   MAX-ACCESS  read-only
   STATUS      current
   DESCRIPTION
      "Path: swPort.performance.vlan.mibCounters.h24Performance.ifOutDiscardsFilter

       64 bit unsigned wrappable counter."
   ::= {pr1646v2EthPortSwFVlanMCH24PEntry 402653184}

pr1646v2EthPortSwFVlanMCH24PIfOutBandwidth OBJECT-TYPE
   SYNTAX      Integer32
   MAX-ACCESS  read-only
   STATUS      current
   DESCRIPTION
      "Path: swPort.performance.vlan.mibCounters.h24Performance.ifOutBandwidth

       unit name = bps
       formula = 8 * ; 8 /"
   ::= {pr1646v2EthPortSwFVlanMCH24PEntry 285212672}

pr1646v2EthPortSwFVlanMCH24PIfErrSec OBJECT-TYPE
   SYNTAX      Counter32
   MAX-ACCESS  read-only
   STATUS      current
   DESCRIPTION
      "Path: swPort.performance.vlan.mibCounters.h24Performance.ifErrSec

       32 bit unsigned wrappable counter."
   ::= {pr1646v2EthPortSwFVlanMCH24PEntry 251658240}

pr1646v2EthPortSwFVlanMCD7P OBJECT-TYPE
   SYNTAX      SEQUENCE OF Pr1646v2EthPortSwFVlanMCD7PEntry
   MAX-ACCESS  not-accessible
   STATUS      current
   DESCRIPTION
      ""
   ::= {pr1646v2EthPortSwFVlan 41680896}

pr1646v2EthPortSwFVlanMCD7PEntry OBJECT-TYPE
   SYNTAX      Pr1646v2EthPortSwFVlanMCD7PEntry
   MAX-ACCESS  not-accessible
   STATUS      current
   DESCRIPTION
      ""
   INDEX      { pr1646v2EthPortSwFVlanMCD7PGlobalIx,
                pr1646v2EthPortSwFVlanTableIx,
                pr1646v2EthPortSwFVlanMCD7PTableIx }
   ::= {pr1646v2EthPortSwFVlanMCD7P 1}

Pr1646v2EthPortSwFVlanMCD7PEntry ::=
   SEQUENCE
      {
      pr1646v2EthPortSwFVlanMCD7PGlobalIx
         GlobalIndex,
      pr1646v2EthPortSwFVlanMCD7PTableIx
         TableIndex,
      pr1646v2EthPortSwFVlanMCD7PSysUpTime
         TimeTicks,
      pr1646v2EthPortSwFVlanMCD7PIfUpTime
         TimeTicks,
      pr1646v2EthPortSwFVlanMCD7PIfStatChanges
         Counter32,
      pr1646v2EthPortSwFVlanMCD7PIfInOctets
         Counter64,
      pr1646v2EthPortSwFVlanMCD7PIfInUCPkts
         Counter64,
      pr1646v2EthPortSwFVlanMCD7PIfInNUCPkts
         Counter64,
      pr1646v2EthPortSwFVlanMCD7PIfInBCPkts
         Counter64,
      pr1646v2EthPortSwFVlanMCD7PIfInMCPkts
         Counter64,
      pr1646v2EthPortSwFVlanMCD7PIfInDiscards
         Counter64,
      pr1646v2EthPortSwFVlanMCD7PIfInErrors
         Counter64,
      pr1646v2EthPortSwFVlanMCD7PIfInUnkwn
         Counter64,
      pr1646v2EthPortSwFVlanMCD7PInDropEx
         Counter64,
      pr1646v2EthPortSwFVlanMCD7PInDropNoMac
         Counter64,
      pr1646v2EthPortSwFVlanMCD7PInDropNUCast
         Counter64,
      pr1646v2EthPortSwFVlanMCD7PInDropFilter
         Counter64,
      pr1646v2EthPortSwFVlanMCD7PIfInBandwidth
         Integer32,
      pr1646v2EthPortSwFVlanMCD7PIfOutOctets
         Counter64,
      pr1646v2EthPortSwFVlanMCD7PIfOutUCPkts
         Counter64,
      pr1646v2EthPortSwFVlanMCD7PIfOutNUCPkts
         Counter64,
      pr1646v2EthPortSwFVlanMCD7PIfOutBCPkts
         Counter64,
      pr1646v2EthPortSwFVlanMCD7PIfOutMCPkts
         Counter64,
      pr1646v2EthPortSwFVlanMCD7PIfOutDiscards
         Counter64,
      pr1646v2EthPortSwFVlanMCD7PIfOutErrors
         Counter64,
      pr1646v2EthPortSwFVlanMCD7POutDropEx
         Counter64,
      pr1646v2EthPortSwFVlanMCD7POutDropNoArp
         Counter64,
      pr1646v2EthPortSwFVlanMCD7POutDropFilter
         Counter64,
      pr1646v2EthPortSwFVlanMCD7PIfOutBandwidth
         Integer32,
      pr1646v2EthPortSwFVlanMCD7PIfErrSec
         Counter32
      }

pr1646v2EthPortSwFVlanMCD7PGlobalIx OBJECT-TYPE
   SYNTAX      GlobalIndex
   MAX-ACCESS  not-accessible
   STATUS      current
   DESCRIPTION
      "The value of the tlsCntTreeGlobalIndex of the MANAGED OBJECT."
   ::= {pr1646v2EthPortSwFVlanMCD7PEntry 10}

pr1646v2EthPortSwFVlanMCD7PTableIx OBJECT-TYPE
   SYNTAX      TableIndex
   MAX-ACCESS  not-accessible
   STATUS      current
   DESCRIPTION
      ""
   ::= {pr1646v2EthPortSwFVlanMCD7PEntry 11}

pr1646v2EthPortSwFVlanMCD7PSysUpTime OBJECT-TYPE
   SYNTAX      TimeTicks
   MAX-ACCESS  read-only
   STATUS      current
   DESCRIPTION
      "Path: swPort.performance.vlan.mibCounters.d7Performance.sysUpTime

       Time in centi-second."
   ::= {pr1646v2EthPortSwFVlanMCD7PEntry 16777216}

pr1646v2EthPortSwFVlanMCD7PIfUpTime OBJECT-TYPE
   SYNTAX      TimeTicks
   MAX-ACCESS  read-only
   STATUS      current
   DESCRIPTION
      "Path: swPort.performance.vlan.mibCounters.d7Performance.ifUpTime

       Time in centi-second."
   ::= {pr1646v2EthPortSwFVlanMCD7PEntry 33554432}

pr1646v2EthPortSwFVlanMCD7PIfStatChanges OBJECT-TYPE
   SYNTAX      Counter32
   MAX-ACCESS  read-only
   STATUS      current
   DESCRIPTION
      "Path: swPort.performance.vlan.mibCounters.d7Performance.ifStatusChanges

       32 bit unsigned wrappable counter."
   ::= {pr1646v2EthPortSwFVlanMCD7PEntry 50331648}

pr1646v2EthPortSwFVlanMCD7PIfInOctets OBJECT-TYPE
   SYNTAX      Counter64
   MAX-ACCESS  read-only
   STATUS      current
   DESCRIPTION
      "Path: swPort.performance.vlan.mibCounters.d7Performance.ifInOctets

       64 bit unsigned wrappable counter."
   ::= {pr1646v2EthPortSwFVlanMCD7PEntry 67108864}

pr1646v2EthPortSwFVlanMCD7PIfInUCPkts OBJECT-TYPE
   SYNTAX      Counter64
   MAX-ACCESS  read-only
   STATUS      current
   DESCRIPTION
      "Path: swPort.performance.vlan.mibCounters.d7Performance.ifInUcastPkts

       64 bit unsigned wrappable counter."
   ::= {pr1646v2EthPortSwFVlanMCD7PEntry 83886080}

pr1646v2EthPortSwFVlanMCD7PIfInNUCPkts OBJECT-TYPE
   SYNTAX      Counter64
   MAX-ACCESS  read-only
   STATUS      current
   DESCRIPTION
      "Path: swPort.performance.vlan.mibCounters.d7Performance.ifInNUcastPkts

       64 bit unsigned wrappable counter."
   ::= {pr1646v2EthPortSwFVlanMCD7PEntry 100663296}

pr1646v2EthPortSwFVlanMCD7PIfInBCPkts OBJECT-TYPE
   SYNTAX      Counter64
   MAX-ACCESS  read-only
   STATUS      current
   DESCRIPTION
      "Path: swPort.performance.vlan.mibCounters.d7Performance.ifInBcastPkts

       64 bit unsigned wrappable counter."
   ::= {pr1646v2EthPortSwFVlanMCD7PEntry 419430400}

pr1646v2EthPortSwFVlanMCD7PIfInMCPkts OBJECT-TYPE
   SYNTAX      Counter64
   MAX-ACCESS  read-only
   STATUS      current
   DESCRIPTION
      "Path: swPort.performance.vlan.mibCounters.d7Performance.ifInMcastPkts

       64 bit unsigned wrappable counter."
   ::= {pr1646v2EthPortSwFVlanMCD7PEntry 436207616}

pr1646v2EthPortSwFVlanMCD7PIfInDiscards OBJECT-TYPE
   SYNTAX      Counter64
   MAX-ACCESS  read-only
   STATUS      current
   DESCRIPTION
      "Path: swPort.performance.vlan.mibCounters.d7Performance.ifInDiscards

       64 bit unsigned wrappable counter."
   ::= {pr1646v2EthPortSwFVlanMCD7PEntry 117440512}

pr1646v2EthPortSwFVlanMCD7PIfInErrors OBJECT-TYPE
   SYNTAX      Counter64
   MAX-ACCESS  read-only
   STATUS      current
   DESCRIPTION
      "Path: swPort.performance.vlan.mibCounters.d7Performance.ifInErrors

       64 bit unsigned wrappable counter."
   ::= {pr1646v2EthPortSwFVlanMCD7PEntry 134217728}

pr1646v2EthPortSwFVlanMCD7PIfInUnkwn OBJECT-TYPE
   SYNTAX      Counter64
   MAX-ACCESS  read-only
   STATUS      current
   DESCRIPTION
      "Path: swPort.performance.vlan.mibCounters.d7Performance.ifInUnknownProtos

       64 bit unsigned wrappable counter."
   ::= {pr1646v2EthPortSwFVlanMCD7PEntry 150994944}

pr1646v2EthPortSwFVlanMCD7PInDropEx OBJECT-TYPE
   SYNTAX      Counter64
   MAX-ACCESS  read-only
   STATUS      current
   DESCRIPTION
      "Path: swPort.performance.vlan.mibCounters.d7Performance.ifInDropLevelExceeded

       64 bit unsigned wrappable counter."
   ::= {pr1646v2EthPortSwFVlanMCD7PEntry 335544320}

pr1646v2EthPortSwFVlanMCD7PInDropNoMac OBJECT-TYPE
   SYNTAX      Counter64
   MAX-ACCESS  read-only
   STATUS      current
   DESCRIPTION
      "Path: swPort.performance.vlan.mibCounters.d7Performance.fInDiscardsNoMacFit

       64 bit unsigned wrappable counter."
   ::= {pr1646v2EthPortSwFVlanMCD7PEntry 301989888}

pr1646v2EthPortSwFVlanMCD7PInDropNUCast OBJECT-TYPE
   SYNTAX      Counter64
   MAX-ACCESS  read-only
   STATUS      current
   DESCRIPTION
      "Path: swPort.performance.vlan.mibCounters.d7Performance.fInDiscardsNUCast

       64 bit unsigned wrappable counter."
   ::= {pr1646v2EthPortSwFVlanMCD7PEntry 318767104}

pr1646v2EthPortSwFVlanMCD7PInDropFilter OBJECT-TYPE
   SYNTAX      Counter64
   MAX-ACCESS  read-only
   STATUS      current
   DESCRIPTION
      "Path: swPort.performance.vlan.mibCounters.d7Performance.fInDiscardsFilter

       64 bit unsigned wrappable counter."
   ::= {pr1646v2EthPortSwFVlanMCD7PEntry 385875968}

pr1646v2EthPortSwFVlanMCD7PIfInBandwidth OBJECT-TYPE
   SYNTAX      Integer32
   MAX-ACCESS  read-only
   STATUS      current
   DESCRIPTION
      "Path: swPort.performance.vlan.mibCounters.d7Performance.ifInBandwidth

       unit name = bps
       formula = 8 * ; 8 /"
   ::= {pr1646v2EthPortSwFVlanMCD7PEntry 268435456}

pr1646v2EthPortSwFVlanMCD7PIfOutOctets OBJECT-TYPE
   SYNTAX      Counter64
   MAX-ACCESS  read-only
   STATUS      current
   DESCRIPTION
      "Path: swPort.performance.vlan.mibCounters.d7Performance.ifOutOctets

       64 bit unsigned wrappable counter."
   ::= {pr1646v2EthPortSwFVlanMCD7PEntry 167772160}

pr1646v2EthPortSwFVlanMCD7PIfOutUCPkts OBJECT-TYPE
   SYNTAX      Counter64
   MAX-ACCESS  read-only
   STATUS      current
   DESCRIPTION
      "Path: swPort.performance.vlan.mibCounters.d7Performance.ifOutUcastPkts

       64 bit unsigned wrappable counter."
   ::= {pr1646v2EthPortSwFVlanMCD7PEntry 184549376}

pr1646v2EthPortSwFVlanMCD7PIfOutNUCPkts OBJECT-TYPE
   SYNTAX      Counter64
   MAX-ACCESS  read-only
   STATUS      current
   DESCRIPTION
      "Path: swPort.performance.vlan.mibCounters.d7Performance.ifOutNUcastPkts

       64 bit unsigned wrappable counter."
   ::= {pr1646v2EthPortSwFVlanMCD7PEntry 201326592}

pr1646v2EthPortSwFVlanMCD7PIfOutBCPkts OBJECT-TYPE
   SYNTAX      Counter64
   MAX-ACCESS  read-only
   STATUS      current
   DESCRIPTION
      "Path: swPort.performance.vlan.mibCounters.d7Performance.ifOutBcastPkts

       64 bit unsigned wrappable counter."
   ::= {pr1646v2EthPortSwFVlanMCD7PEntry 452984832}

pr1646v2EthPortSwFVlanMCD7PIfOutMCPkts OBJECT-TYPE
   SYNTAX      Counter64
   MAX-ACCESS  read-only
   STATUS      current
   DESCRIPTION
      "Path: swPort.performance.vlan.mibCounters.d7Performance.ifOutMcastPkts

       64 bit unsigned wrappable counter."
   ::= {pr1646v2EthPortSwFVlanMCD7PEntry 469762048}

pr1646v2EthPortSwFVlanMCD7PIfOutDiscards OBJECT-TYPE
   SYNTAX      Counter64
   MAX-ACCESS  read-only
   STATUS      current
   DESCRIPTION
      "Path: swPort.performance.vlan.mibCounters.d7Performance.ifOutDiscards

       64 bit unsigned wrappable counter."
   ::= {pr1646v2EthPortSwFVlanMCD7PEntry 218103808}

pr1646v2EthPortSwFVlanMCD7PIfOutErrors OBJECT-TYPE
   SYNTAX      Counter64
   MAX-ACCESS  read-only
   STATUS      current
   DESCRIPTION
      "Path: swPort.performance.vlan.mibCounters.d7Performance.ifOutErrors

       64 bit unsigned wrappable counter."
   ::= {pr1646v2EthPortSwFVlanMCD7PEntry 234881024}

pr1646v2EthPortSwFVlanMCD7POutDropEx OBJECT-TYPE
   SYNTAX      Counter64
   MAX-ACCESS  read-only
   STATUS      current
   DESCRIPTION
      "Path: swPort.performance.vlan.mibCounters.d7Performance.ifOutDropLevelExceeded

       64 bit unsigned wrappable counter."
   ::= {pr1646v2EthPortSwFVlanMCD7PEntry 352321536}

pr1646v2EthPortSwFVlanMCD7POutDropNoArp OBJECT-TYPE
   SYNTAX      Counter64
   MAX-ACCESS  read-only
   STATUS      current
   DESCRIPTION
      "Path: swPort.performance.vlan.mibCounters.d7Performance.ifOutDiscardsNoArp

       64 bit unsigned wrappable counter."
   ::= {pr1646v2EthPortSwFVlanMCD7PEntry 369098752}

pr1646v2EthPortSwFVlanMCD7POutDropFilter OBJECT-TYPE
   SYNTAX      Counter64
   MAX-ACCESS  read-only
   STATUS      current
   DESCRIPTION
      "Path: swPort.performance.vlan.mibCounters.d7Performance.ifOutDiscardsFilter

       64 bit unsigned wrappable counter."
   ::= {pr1646v2EthPortSwFVlanMCD7PEntry 402653184}

pr1646v2EthPortSwFVlanMCD7PIfOutBandwidth OBJECT-TYPE
   SYNTAX      Integer32
   MAX-ACCESS  read-only
   STATUS      current
   DESCRIPTION
      "Path: swPort.performance.vlan.mibCounters.d7Performance.ifOutBandwidth

       unit name = bps
       formula = 8 * ; 8 /"
   ::= {pr1646v2EthPortSwFVlanMCD7PEntry 285212672}

pr1646v2EthPortSwFVlanMCD7PIfErrSec OBJECT-TYPE
   SYNTAX      Counter32
   MAX-ACCESS  read-only
   STATUS      current
   DESCRIPTION
      "Path: swPort.performance.vlan.mibCounters.d7Performance.ifErrSec

       32 bit unsigned wrappable counter."
   ::= {pr1646v2EthPortSwFVlanMCD7PEntry 251658240}

pr1646v2EthPortSwFVlanInPQs OBJECT-TYPE
   SYNTAX      SEQUENCE OF Pr1646v2EthPortSwFVlanInPQsEntry
   MAX-ACCESS  not-accessible
   STATUS      current
   DESCRIPTION
      ""
   ::= {pr1646v2EthPortSwFVlan 100663296}

pr1646v2EthPortSwFVlanInPQsEntry OBJECT-TYPE
   SYNTAX      Pr1646v2EthPortSwFVlanInPQsEntry
   MAX-ACCESS  not-accessible
   STATUS      current
   DESCRIPTION
      ""
   INDEX      { pr1646v2EthPortSwFVlanInPQsGlobalIx,
                pr1646v2EthPortSwFVlanTableIx,
                pr1646v2EthPortSwFVlanInPQsTableIx }
   ::= {pr1646v2EthPortSwFVlanInPQs 1}

Pr1646v2EthPortSwFVlanInPQsEntry ::=
   SEQUENCE
      {
      pr1646v2EthPortSwFVlanInPQsGlobalIx
         GlobalIndex,
      pr1646v2EthPortSwFVlanInPQsTableIx
         TableIndex,
      pr1646v2EthPortSwFVlanInPQsName
         INTEGER,
      pr1646v2EthPortSwFVlanInPQsLength
         Integer32,
      pr1646v2EthPortSwFVlanInPQsOctetLength
         Integer32,
      pr1646v2EthPortSwFVlanInPQsRedLength
         Integer32,
      pr1646v2EthPortSwFVlanInPQsPacketsTotal
         Counter64,
      pr1646v2EthPortSwFVlanInPQsPacketsDirectTx
         Counter64,
      pr1646v2EthPortSwFVlanInPQsPacketsQueued
         Counter64,
      pr1646v2EthPortSwFVlanInPQsPacketsDropped
         Counter64,
      pr1646v2EthPortSwFVlanInPQsPacketsRedDropped
         Counter64,
      pr1646v2EthPortSwFVlanInPQsPacketsCirTx
         Counter64,
      pr1646v2EthPortSwFVlanInPQsPacketsEirTx
         Counter64,
      pr1646v2EthPortSwFVlanInPQsPacketsViolateTx
         Counter64,
      pr1646v2EthPortSwFVlanInPQsOctetsTotal
         Counter64,
      pr1646v2EthPortSwFVlanInPQsOctetsDirectTx
         Counter64,
      pr1646v2EthPortSwFVlanInPQsOctetsQueued
         Counter64,
      pr1646v2EthPortSwFVlanInPQsOctetsDropped
         Counter64,
      pr1646v2EthPortSwFVlanInPQsOctetsRedDropped
         Counter64,
      pr1646v2EthPortSwFVlanInPQsOctetsCirTx
         Counter64,
      pr1646v2EthPortSwFVlanInPQsOctetsEirTx
         Counter64,
      pr1646v2EthPortSwFVlanInPQsOctetsViolateTx
         Counter64,
      pr1646v2EthPortSwFVlanInPQsOctetsBandwidth15sec
         Integer32,
      pr1646v2EthPortSwFVlanInPQsOctetsBandwidth30sec
         Integer32,
      pr1646v2EthPortSwFVlanInPQsOctetsBandwidth1min
         Integer32,
      pr1646v2EthPortSwFVlanInPQsOctetsBandwidth2min
         Integer32,
      pr1646v2EthPortSwFVlanInPQsOctetsBandwidth5min
         Integer32
      }

pr1646v2EthPortSwFVlanInPQsGlobalIx OBJECT-TYPE
   SYNTAX      GlobalIndex
   MAX-ACCESS  not-accessible
   STATUS      current
   DESCRIPTION
      "The value of the tlsCntTreeGlobalIndex of the MANAGED OBJECT."
   ::= {pr1646v2EthPortSwFVlanInPQsEntry 10}

pr1646v2EthPortSwFVlanInPQsTableIx OBJECT-TYPE
   SYNTAX      TableIndex
   MAX-ACCESS  not-accessible
   STATUS      current
   DESCRIPTION
      ""
   ::= {pr1646v2EthPortSwFVlanInPQsEntry 11}

pr1646v2EthPortSwFVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwFVlanInPQsEntry 16777216}

pr1646v2EthPortSwFVlanInPQsLength OBJECT-TYPE
   SYNTAX      Integer32
   MAX-ACCESS  read-only
   STATUS      current
   DESCRIPTION
      "Path: swPort.performance.vlan.inPriorityQueues.length"
   ::= {pr1646v2EthPortSwFVlanInPQsEntry 33554432}

pr1646v2EthPortSwFVlanInPQsOctetLength OBJECT-TYPE
   SYNTAX      Integer32
   MAX-ACCESS  read-only
   STATUS      current
   DESCRIPTION
      "Path: swPort.performance.vlan.inPriorityQueues.octetLength"
   ::= {pr1646v2EthPortSwFVlanInPQsEntry 150994944}

pr1646v2EthPortSwFVlanInPQsRedLength OBJECT-TYPE
   SYNTAX      Integer32
   MAX-ACCESS  read-only
   STATUS      current
   DESCRIPTION
      "Path: swPort.performance.vlan.inPriorityQueues.redLength"
   ::= {pr1646v2EthPortSwFVlanInPQsEntry 134217728}

pr1646v2EthPortSwFVlanInPQsPacketsTotal OBJECT-TYPE
   SYNTAX      Counter64
   MAX-ACCESS  read-only
   STATUS      current
   DESCRIPTION
      "Path: swPort.performance.vlan.inPriorityQueues.packets.total

       64 bit unsigned wrappable counter."
   ::= {pr1646v2EthPortSwFVlanInPQsEntry 50790400}

pr1646v2EthPortSwFVlanInPQsPacketsDirectTx OBJECT-TYPE
   SYNTAX      Counter64
   MAX-ACCESS  read-only
   STATUS      current
   DESCRIPTION
      "Path: swPort.performance.vlan.inPriorityQueues.packets.directTx

       64 bit unsigned wrappable counter."
   ::= {pr1646v2EthPortSwFVlanInPQsEntry 50397184}

pr1646v2EthPortSwFVlanInPQsPacketsQueued OBJECT-TYPE
   SYNTAX      Counter64
   MAX-ACCESS  read-only
   STATUS      current
   DESCRIPTION
      "Path: swPort.performance.vlan.inPriorityQueues.packets.queued

       64 bit unsigned wrappable counter."
   ::= {pr1646v2EthPortSwFVlanInPQsEntry 50462720}

pr1646v2EthPortSwFVlanInPQsPacketsDropped OBJECT-TYPE
   SYNTAX      Counter64
   MAX-ACCESS  read-only
   STATUS      current
   DESCRIPTION
      "Path: swPort.performance.vlan.inPriorityQueues.packets.dropped

       64 bit unsigned wrappable counter."
   ::= {pr1646v2EthPortSwFVlanInPQsEntry 50528256}

pr1646v2EthPortSwFVlanInPQsPacketsRedDropped OBJECT-TYPE
   SYNTAX      Counter64
   MAX-ACCESS  read-only
   STATUS      current
   DESCRIPTION
      "Path: swPort.performance.vlan.inPriorityQueues.packets.redDropped

       64 bit unsigned wrappable counter."
   ::= {pr1646v2EthPortSwFVlanInPQsEntry 50724864}

pr1646v2EthPortSwFVlanInPQsPacketsCirTx OBJECT-TYPE
   SYNTAX      Counter64
   MAX-ACCESS  read-only
   STATUS      current
   DESCRIPTION
      "Path: swPort.performance.vlan.inPriorityQueues.packets.cirTx

       64 bit unsigned wrappable counter."
   ::= {pr1646v2EthPortSwFVlanInPQsEntry 50593792}

pr1646v2EthPortSwFVlanInPQsPacketsEirTx OBJECT-TYPE
   SYNTAX      Counter64
   MAX-ACCESS  read-only
   STATUS      current
   DESCRIPTION
      "Path: swPort.performance.vlan.inPriorityQueues.packets.eirTx

       64 bit unsigned wrappable counter."
   ::= {pr1646v2EthPortSwFVlanInPQsEntry 50659328}

pr1646v2EthPortSwFVlanInPQsPacketsViolateTx OBJECT-TYPE
   SYNTAX      Counter64
   MAX-ACCESS  read-only
   STATUS      current
   DESCRIPTION
      "Path: swPort.performance.vlan.inPriorityQueues.packets.violateTx

       64 bit unsigned wrappable counter."
   ::= {pr1646v2EthPortSwFVlanInPQsEntry 50855936}

pr1646v2EthPortSwFVlanInPQsOctetsTotal OBJECT-TYPE
   SYNTAX      Counter64
   MAX-ACCESS  read-only
   STATUS      current
   DESCRIPTION
      "Path: swPort.performance.vlan.inPriorityQueues.octets.total

       64 bit unsigned wrappable counter."
   ::= {pr1646v2EthPortSwFVlanInPQsEntry 67567616}

pr1646v2EthPortSwFVlanInPQsOctetsDirectTx OBJECT-TYPE
   SYNTAX      Counter64
   MAX-ACCESS  read-only
   STATUS      current
   DESCRIPTION
      "Path: swPort.performance.vlan.inPriorityQueues.octets.directTx

       64 bit unsigned wrappable counter."
   ::= {pr1646v2EthPortSwFVlanInPQsEntry 67174400}

pr1646v2EthPortSwFVlanInPQsOctetsQueued OBJECT-TYPE
   SYNTAX      Counter64
   MAX-ACCESS  read-only
   STATUS      current
   DESCRIPTION
      "Path: swPort.performance.vlan.inPriorityQueues.octets.queued

       64 bit unsigned wrappable counter."
   ::= {pr1646v2EthPortSwFVlanInPQsEntry 67239936}

pr1646v2EthPortSwFVlanInPQsOctetsDropped OBJECT-TYPE
   SYNTAX      Counter64
   MAX-ACCESS  read-only
   STATUS      current
   DESCRIPTION
      "Path: swPort.performance.vlan.inPriorityQueues.octets.dropped

       64 bit unsigned wrappable counter."
   ::= {pr1646v2EthPortSwFVlanInPQsEntry 67305472}

pr1646v2EthPortSwFVlanInPQsOctetsRedDropped OBJECT-TYPE
   SYNTAX      Counter64
   MAX-ACCESS  read-only
   STATUS      current
   DESCRIPTION
      "Path: swPort.performance.vlan.inPriorityQueues.octets.redDropped

       64 bit unsigned wrappable counter."
   ::= {pr1646v2EthPortSwFVlanInPQsEntry 67502080}

pr1646v2EthPortSwFVlanInPQsOctetsCirTx OBJECT-TYPE
   SYNTAX      Counter64
   MAX-ACCESS  read-only
   STATUS      current
   DESCRIPTION
      "Path: swPort.performance.vlan.inPriorityQueues.octets.cirTx

       64 bit unsigned wrappable counter."
   ::= {pr1646v2EthPortSwFVlanInPQsEntry 67371008}

pr1646v2EthPortSwFVlanInPQsOctetsEirTx OBJECT-TYPE
   SYNTAX      Counter64
   MAX-ACCESS  read-only
   STATUS      current
   DESCRIPTION
      "Path: swPort.performance.vlan.inPriorityQueues.octets.eirTx

       64 bit unsigned wrappable counter."
   ::= {pr1646v2EthPortSwFVlanInPQsEntry 67436544}

pr1646v2EthPortSwFVlanInPQsOctetsViolateTx OBJECT-TYPE
   SYNTAX      Counter64
   MAX-ACCESS  read-only
   STATUS      current
   DESCRIPTION
      "Path: swPort.performance.vlan.inPriorityQueues.octets.violateTx

       64 bit unsigned wrappable counter."
   ::= {pr1646v2EthPortSwFVlanInPQsEntry 67633152}

pr1646v2EthPortSwFVlanInPQsOctetsBandwidth15sec OBJECT-TYPE
   SYNTAX      Integer32
   MAX-ACCESS  read-only
   STATUS      current
   DESCRIPTION
      "Path: swPort.performance.vlan.inPriorityQueues.octets.bandwidth.15sec

       unit name = bps
       formula = 8 * ; 8 /"
   ::= {pr1646v2EthPortSwFVlanInPQsEntry 70386944}

pr1646v2EthPortSwFVlanInPQsOctetsBandwidth30sec OBJECT-TYPE
   SYNTAX      Integer32
   MAX-ACCESS  read-only
   STATUS      current
   DESCRIPTION
      "Path: swPort.performance.vlan.inPriorityQueues.octets.bandwidth.30sec

       unit name = bps
       formula = 8 * ; 8 /"
   ::= {pr1646v2EthPortSwFVlanInPQsEntry 70388224}

pr1646v2EthPortSwFVlanInPQsOctetsBandwidth1min OBJECT-TYPE
   SYNTAX      Integer32
   MAX-ACCESS  read-only
   STATUS      current
   DESCRIPTION
      "Path: swPort.performance.vlan.inPriorityQueues.octets.bandwidth.1min

       unit name = bps
       formula = 8 * ; 8 /"
   ::= {pr1646v2EthPortSwFVlanInPQsEntry 70390784}

pr1646v2EthPortSwFVlanInPQsOctetsBandwidth2min OBJECT-TYPE
   SYNTAX      Integer32
   MAX-ACCESS  read-only
   STATUS      current
   DESCRIPTION
      "Path: swPort.performance.vlan.inPriorityQueues.octets.bandwidth.2min

       unit name = bps
       formula = 8 * ; 8 /"
   ::= {pr1646v2EthPortSwFVlanInPQsEntry 70395904}

pr1646v2EthPortSwFVlanInPQsOctetsBandwidth5min OBJECT-TYPE
   SYNTAX      Integer32
   MAX-ACCESS  read-only
   STATUS      current
   DESCRIPTION
      "Path: swPort.performance.vlan.inPriorityQueues.octets.bandwidth.5min

       unit name = bps
       formula = 8 * ; 8 /"
   ::= {pr1646v2EthPortSwFVlanInPQsEntry 70411264}

pr1646v2EthPortSwFVlanInPQsH2Performance OBJECT-TYPE
   SYNTAX      SEQUENCE OF Pr1646v2EthPortSwFVlanInPQsH2PerformanceEntry
   MAX-ACCESS  not-accessible
   STATUS      current
   DESCRIPTION
      ""
   ::= {pr1646v2EthPortSwFVlan 100990976}

pr1646v2EthPortSwFVlanInPQsH2PerformanceEntry OBJECT-TYPE
   SYNTAX      Pr1646v2EthPortSwFVlanInPQsH2PerformanceEntry
   MAX-ACCESS  not-accessible
   STATUS      current
   DESCRIPTION
      ""
   INDEX      { pr1646v2EthPortSwFVlanInPQsH2PerformanceGlobalIx,
                pr1646v2EthPortSwFVlanTableIx,
                pr1646v2EthPortSwFVlanInPQsTableIx,
                pr1646v2EthPortSwFVlanInPQsH2PerformanceTableIx }
   ::= {pr1646v2EthPortSwFVlanInPQsH2Performance 1}

Pr1646v2EthPortSwFVlanInPQsH2PerformanceEntry ::=
   SEQUENCE
      {
      pr1646v2EthPortSwFVlanInPQsH2PerformanceGlobalIx
         GlobalIndex,
      pr1646v2EthPortSwFVlanInPQsH2PerformanceTableIx
         TableIndex,
      pr1646v2EthPortSwFVlanInPQsH2PerformanceSysUpTime
         TimeTicks,
      pr1646v2EthPortSwFVlanInPQsH2PerformanceTotPkts
         Counter64,
      pr1646v2EthPortSwFVlanInPQsH2PerformanceDirTxPkts
         Counter64,
      pr1646v2EthPortSwFVlanInPQsH2PerformanceQdPkts
         Counter64,
      pr1646v2EthPortSwFVlanInPQsH2PerformanceDropPkts
         Counter64,
      pr1646v2EthPortSwFVlanInPQsH2PerformanceRDropPkts
         Counter64,
      pr1646v2EthPortSwFVlanInPQsH2PerformanceCirTxPkts
         Counter64,
      pr1646v2EthPortSwFVlanInPQsH2PerformanceEirTxPkts
         Counter64,
      pr1646v2EthPortSwFVlanInPQsH2PerformanceViolTxPkts
         Counter64,
      pr1646v2EthPortSwFVlanInPQsH2PerformanceTotOcts
         Counter64,
      pr1646v2EthPortSwFVlanInPQsH2PerformanceDirTxOcts
         Counter64,
      pr1646v2EthPortSwFVlanInPQsH2PerformanceQdOcts
         Counter64,
      pr1646v2EthPortSwFVlanInPQsH2PerformanceDropOcts
         Counter64,
      pr1646v2EthPortSwFVlanInPQsH2PerformanceRDropOcts
         Counter64,
      pr1646v2EthPortSwFVlanInPQsH2PerformanceCirTxOcts
         Counter64,
      pr1646v2EthPortSwFVlanInPQsH2PerformanceEirTxOcts
         Counter64,
      pr1646v2EthPortSwFVlanInPQsH2PerformanceViolTxOcts
         Counter64,
      pr1646v2EthPortSwFVlanInPQsH2PerformanceBandwidth
         Integer32
      }

pr1646v2EthPortSwFVlanInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanInPQsH2PerformanceEntry 10}

pr1646v2EthPortSwFVlanInPQsH2PerformanceTableIx OBJECT-TYPE
   SYNTAX      TableIndex
   MAX-ACCESS  not-accessible
   STATUS      current
   DESCRIPTION
      ""
   ::= {pr1646v2EthPortSwFVlanInPQsH2PerformanceEntry 11}

pr1646v2EthPortSwFVlanInPQsH2PerformanceSysUpTime OBJECT-TYPE
   SYNTAX      TimeTicks
   MAX-ACCESS  read-only
   STATUS      current
   DESCRIPTION
      "Path: swPort.performance.vlan.inPriorityQueues.h2Performance.sysUpTime

       Time in centi-second."
   ::= {pr1646v2EthPortSwFVlanInPQsH2PerformanceEntry 16777216}

pr1646v2EthPortSwFVlanInPQsH2PerformanceTotPkts OBJECT-TYPE
   SYNTAX      Counter64
   MAX-ACCESS  read-only
   STATUS      current
   DESCRIPTION
      "Path: swPort.performance.vlan.inPriorityQueues.h2Performance.totalPkts

       64 bit unsigned wrappable counter."
   ::= {pr1646v2EthPortSwFVlanInPQsH2PerformanceEntry 234881024}

pr1646v2EthPortSwFVlanInPQsH2PerformanceDirTxPkts OBJECT-TYPE
   SYNTAX      Counter64
   MAX-ACCESS  read-only
   STATUS      current
   DESCRIPTION
      "Path: swPort.performance.vlan.inPriorityQueues.h2Performance.directTxPkts

       64 bit unsigned wrappable counter."
   ::= {pr1646v2EthPortSwFVlanInPQsH2PerformanceEntry 33554432}

pr1646v2EthPortSwFVlanInPQsH2PerformanceQdPkts OBJECT-TYPE
   SYNTAX      Counter64
   MAX-ACCESS  read-only
   STATUS      current
   DESCRIPTION
      "Path: swPort.performance.vlan.inPriorityQueues.h2Performance.queuedPkts

       64 bit unsigned wrappable counter."
   ::= {pr1646v2EthPortSwFVlanInPQsH2PerformanceEntry 50331648}

pr1646v2EthPortSwFVlanInPQsH2PerformanceDropPkts OBJECT-TYPE
   SYNTAX      Counter64
   MAX-ACCESS  read-only
   STATUS      current
   DESCRIPTION
      "Path: swPort.performance.vlan.inPriorityQueues.h2Performance.droppedPkts

       64 bit unsigned wrappable counter."
   ::= {pr1646v2EthPortSwFVlanInPQsH2PerformanceEntry 67108864}

pr1646v2EthPortSwFVlanInPQsH2PerformanceRDropPkts OBJECT-TYPE
   SYNTAX      Counter64
   MAX-ACCESS  read-only
   STATUS      current
   DESCRIPTION
      "Path: swPort.performance.vlan.inPriorityQueues.h2Performance.redDroppedPkts

       64 bit unsigned wrappable counter."
   ::= {pr1646v2EthPortSwFVlanInPQsH2PerformanceEntry 201326592}

pr1646v2EthPortSwFVlanInPQsH2PerformanceCirTxPkts OBJECT-TYPE
   SYNTAX      Counter64
   MAX-ACCESS  read-only
   STATUS      current
   DESCRIPTION
      "Path: swPort.performance.vlan.inPriorityQueues.h2Performance.cirTxPkts

       64 bit unsigned wrappable counter."
   ::= {pr1646v2EthPortSwFVlanInPQsH2PerformanceEntry 83886080}

pr1646v2EthPortSwFVlanInPQsH2PerformanceEirTxPkts OBJECT-TYPE
   SYNTAX      Counter64
   MAX-ACCESS  read-only
   STATUS      current
   DESCRIPTION
      "Path: swPort.performance.vlan.inPriorityQueues.h2Performance.eirTxPkts

       64 bit unsigned wrappable counter."
   ::= {pr1646v2EthPortSwFVlanInPQsH2PerformanceEntry 100663296}

pr1646v2EthPortSwFVlanInPQsH2PerformanceViolTxPkts OBJECT-TYPE
   SYNTAX      Counter64
   MAX-ACCESS  read-only
   STATUS      current
   DESCRIPTION
      "Path: swPort.performance.vlan.inPriorityQueues.h2Performance.violateTxPkts

       64 bit unsigned wrappable counter."
   ::= {pr1646v2EthPortSwFVlanInPQsH2PerformanceEntry 301989888}

pr1646v2EthPortSwFVlanInPQsH2PerformanceTotOcts OBJECT-TYPE
   SYNTAX      Counter64
   MAX-ACCESS  read-only
   STATUS      current
   DESCRIPTION
      "Path: swPort.performance.vlan.inPriorityQueues.h2Performance.totalOctets

       64 bit unsigned wrappable counter."
   ::= {pr1646v2EthPortSwFVlanInPQsH2PerformanceEntry 251658240}

pr1646v2EthPortSwFVlanInPQsH2PerformanceDirTxOcts OBJECT-TYPE
   SYNTAX      Counter64
   MAX-ACCESS  read-only
   STATUS      current
   DESCRIPTION
      "Path: swPort.performance.vlan.inPriorityQueues.h2Performance.directTxOctets

       64 bit unsigned wrappable counter."
   ::= {pr1646v2EthPortSwFVlanInPQsH2PerformanceEntry 117440512}

pr1646v2EthPortSwFVlanInPQsH2PerformanceQdOcts OBJECT-TYPE
   SYNTAX      Counter64
   MAX-ACCESS  read-only
   STATUS      current
   DESCRIPTION
      "Path: swPort.performance.vlan.inPriorityQueues.h2Performance.queuedOctets

       64 bit unsigned wrappable counter."
   ::= {pr1646v2EthPortSwFVlanInPQsH2PerformanceEntry 134217728}

pr1646v2EthPortSwFVlanInPQsH2PerformanceDropOcts OBJECT-TYPE
   SYNTAX      Counter64
   MAX-ACCESS  read-only
   STATUS      current
   DESCRIPTION
      "Path: swPort.performance.vlan.inPriorityQueues.h2Performance.droppedOctets

       64 bit unsigned wrappable counter."
   ::= {pr1646v2EthPortSwFVlanInPQsH2PerformanceEntry 150994944}

pr1646v2EthPortSwFVlanInPQsH2PerformanceRDropOcts OBJECT-TYPE
   SYNTAX      Counter64
   MAX-ACCESS  read-only
   STATUS      current
   DESCRIPTION
      "Path: swPort.performance.vlan.inPriorityQueues.h2Performance.redDroppedOctets

       64 bit unsigned wrappable counter."
   ::= {pr1646v2EthPortSwFVlanInPQsH2PerformanceEntry 218103808}

pr1646v2EthPortSwFVlanInPQsH2PerformanceCirTxOcts OBJECT-TYPE
   SYNTAX      Counter64
   MAX-ACCESS  read-only
   STATUS      current
   DESCRIPTION
      "Path: swPort.performance.vlan.inPriorityQueues.h2Performance.cirTxOctets

       64 bit unsigned wrappable counter."
   ::= {pr1646v2EthPortSwFVlanInPQsH2PerformanceEntry 167772160}

pr1646v2EthPortSwFVlanInPQsH2PerformanceEirTxOcts OBJECT-TYPE
   SYNTAX      Counter64
   MAX-ACCESS  read-only
   STATUS      current
   DESCRIPTION
      "Path: swPort.performance.vlan.inPriorityQueues.h2Performance.eirTxOctets

       64 bit unsigned wrappable counter."
   ::= {pr1646v2EthPortSwFVlanInPQsH2PerformanceEntry 184549376}

pr1646v2EthPortSwFVlanInPQsH2PerformanceViolTxOcts OBJECT-TYPE
   SYNTAX      Counter64
   MAX-ACCESS  read-only
   STATUS      current
   DESCRIPTION
      "Path: swPort.performance.vlan.inPriorityQueues.h2Performance.violateTxOctets

       64 bit unsigned wrappable counter."
   ::= {pr1646v2EthPortSwFVlanInPQsH2PerformanceEntry 318767104}

pr1646v2EthPortSwFVlanInPQsH2PerformanceBandwidth OBJECT-TYPE
   SYNTAX      Integer32
   MAX-ACCESS  read-only
   STATUS      current
   DESCRIPTION
      "Path: swPort.performance.vlan.inPriorityQueues.h2Performance.bandwidth

       unit name = bps
       formula = 8 * ; 8 /"
   ::= {pr1646v2EthPortSwFVlanInPQsH2PerformanceEntry 268435456}

pr1646v2EthPortSwFVlanInPQsH24Performance OBJECT-TYPE
   SYNTAX      SEQUENCE OF Pr1646v2EthPortSwFVlanInPQsH24PerformanceEntry
   MAX-ACCESS  not-accessible
   STATUS      current
   DESCRIPTION
      ""
   ::= {pr1646v2EthPortSwFVlan 101056512}

pr1646v2EthPortSwFVlanInPQsH24PerformanceEntry OBJECT-TYPE
   SYNTAX      Pr1646v2EthPortSwFVlanInPQsH24PerformanceEntry
   MAX-ACCESS  not-accessible
   STATUS      current
   DESCRIPTION
      ""
   INDEX      { pr1646v2EthPortSwFVlanInPQsH24PerformanceGlobalIx,
                pr1646v2EthPortSwFVlanTableIx,
                pr1646v2EthPortSwFVlanInPQsTableIx,
                pr1646v2EthPortSwFVlanInPQsH24PerformanceTableIx }
   ::= {pr1646v2EthPortSwFVlanInPQsH24Performance 1}

Pr1646v2EthPortSwFVlanInPQsH24PerformanceEntry ::=
   SEQUENCE
      {
      pr1646v2EthPortSwFVlanInPQsH24PerformanceGlobalIx
         GlobalIndex,
      pr1646v2EthPortSwFVlanInPQsH24PerformanceTableIx
         TableIndex,
      pr1646v2EthPortSwFVlanInPQsH24PerformanceSysUpTime
         TimeTicks,
      pr1646v2EthPortSwFVlanInPQsH24PerformanceTotPkts
         Counter64,
      pr1646v2EthPortSwFVlanInPQsH24PerformanceDirTxPkts
         Counter64,
      pr1646v2EthPortSwFVlanInPQsH24PerformanceQdPkts
         Counter64,
      pr1646v2EthPortSwFVlanInPQsH24PerformanceDropPkts
         Counter64,
      pr1646v2EthPortSwFVlanInPQsH24PerformanceRDropPkts
         Counter64,
      pr1646v2EthPortSwFVlanInPQsH24PerformanceCirTxPkts
         Counter64,
      pr1646v2EthPortSwFVlanInPQsH24PerformanceEirTxPkts
         Counter64,
      pr1646v2EthPortSwFVlanInPQsH24PerformanceViolTxPkts
         Counter64,
      pr1646v2EthPortSwFVlanInPQsH24PerformanceTotOcts
         Counter64,
      pr1646v2EthPortSwFVlanInPQsH24PerformanceDirTxOcts
         Counter64,
      pr1646v2EthPortSwFVlanInPQsH24PerformanceQdOcts
         Counter64,
      pr1646v2EthPortSwFVlanInPQsH24PerformanceDropOcts
         Counter64,
      pr1646v2EthPortSwFVlanInPQsH24PerformanceRDropOcts
         Counter64,
      pr1646v2EthPortSwFVlanInPQsH24PerformanceCirTxOcts
         Counter64,
      pr1646v2EthPortSwFVlanInPQsH24PerformanceEirTxOcts
         Counter64,
      pr1646v2EthPortSwFVlanInPQsH24PerformanceViolTxOcts
         Counter64,
      pr1646v2EthPortSwFVlanInPQsH24PerformanceBandwidth
         Integer32
      }

pr1646v2EthPortSwFVlanInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanInPQsH24PerformanceEntry 10}

pr1646v2EthPortSwFVlanInPQsH24PerformanceTableIx OBJECT-TYPE
   SYNTAX      TableIndex
   MAX-ACCESS  not-accessible
   STATUS      current
   DESCRIPTION
      ""
   ::= {pr1646v2EthPortSwFVlanInPQsH24PerformanceEntry 11}

pr1646v2EthPortSwFVlanInPQsH24PerformanceSysUpTime OBJECT-TYPE
   SYNTAX      TimeTicks
   MAX-ACCESS  read-only
   STATUS      current
   DESCRIPTION
      "Path: swPort.performance.vlan.inPriorityQueues.h24Performance.sysUpTime

       Time in centi-second."
   ::= {pr1646v2EthPortSwFVlanInPQsH24PerformanceEntry 16777216}

pr1646v2EthPortSwFVlanInPQsH24PerformanceTotPkts OBJECT-TYPE
   SYNTAX      Counter64
   MAX-ACCESS  read-only
   STATUS      current
   DESCRIPTION
      "Path: swPort.performance.vlan.inPriorityQueues.h24Performance.totalPkts

       64 bit unsigned wrappable counter."
   ::= {pr1646v2EthPortSwFVlanInPQsH24PerformanceEntry 234881024}

pr1646v2EthPortSwFVlanInPQsH24PerformanceDirTxPkts OBJECT-TYPE
   SYNTAX      Counter64
   MAX-ACCESS  read-only
   STATUS      current
   DESCRIPTION
      "Path: swPort.performance.vlan.inPriorityQueues.h24Performance.directTxPkts

       64 bit unsigned wrappable counter."
   ::= {pr1646v2EthPortSwFVlanInPQsH24PerformanceEntry 33554432}

pr1646v2EthPortSwFVlanInPQsH24PerformanceQdPkts OBJECT-TYPE
   SYNTAX      Counter64
   MAX-ACCESS  read-only
   STATUS      current
   DESCRIPTION
      "Path: swPort.performance.vlan.inPriorityQueues.h24Performance.queuedPkts

       64 bit unsigned wrappable counter."
   ::= {pr1646v2EthPortSwFVlanInPQsH24PerformanceEntry 50331648}

pr1646v2EthPortSwFVlanInPQsH24PerformanceDropPkts OBJECT-TYPE
   SYNTAX      Counter64
   MAX-ACCESS  read-only
   STATUS      current
   DESCRIPTION
      "Path: swPort.performance.vlan.inPriorityQueues.h24Performance.droppedPkts

       64 bit unsigned wrappable counter."
   ::= {pr1646v2EthPortSwFVlanInPQsH24PerformanceEntry 67108864}

pr1646v2EthPortSwFVlanInPQsH24PerformanceRDropPkts OBJECT-TYPE
   SYNTAX      Counter64
   MAX-ACCESS  read-only
   STATUS      current
   DESCRIPTION
      "Path: swPort.performance.vlan.inPriorityQueues.h24Performance.redDroppedPkts

       64 bit unsigned wrappable counter."
   ::= {pr1646v2EthPortSwFVlanInPQsH24PerformanceEntry 201326592}

pr1646v2EthPortSwFVlanInPQsH24PerformanceCirTxPkts OBJECT-TYPE
   SYNTAX      Counter64
   MAX-ACCESS  read-only
   STATUS      current
   DESCRIPTION
      "Path: swPort.performance.vlan.inPriorityQueues.h24Performance.cirTxPkts

       64 bit unsigned wrappable counter."
   ::= {pr1646v2EthPortSwFVlanInPQsH24PerformanceEntry 83886080}

pr1646v2EthPortSwFVlanInPQsH24PerformanceEirTxPkts OBJECT-TYPE
   SYNTAX      Counter64
   MAX-ACCESS  read-only
   STATUS      current
   DESCRIPTION
      "Path: swPort.performance.vlan.inPriorityQueues.h24Performance.eirTxPkts

       64 bit unsigned wrappable counter."
   ::= {pr1646v2EthPortSwFVlanInPQsH24PerformanceEntry 100663296}

pr1646v2EthPortSwFVlanInPQsH24PerformanceViolTxPkts OBJECT-TYPE
   SYNTAX      Counter64
   MAX-ACCESS  read-only
   STATUS      current
   DESCRIPTION
      "Path: swPort.performance.vlan.inPriorityQueues.h24Performance.violateTxPkts

       64 bit unsigned wrappable counter."
   ::= {pr1646v2EthPortSwFVlanInPQsH24PerformanceEntry 301989888}

pr1646v2EthPortSwFVlanInPQsH24PerformanceTotOcts OBJECT-TYPE
   SYNTAX      Counter64
   MAX-ACCESS  read-only
   STATUS      current
   DESCRIPTION
      "Path: swPort.performance.vlan.inPriorityQueues.h24Performance.totalOctets

       64 bit unsigned wrappable counter."
   ::= {pr1646v2EthPortSwFVlanInPQsH24PerformanceEntry 251658240}

pr1646v2EthPortSwFVlanInPQsH24PerformanceDirTxOcts OBJECT-TYPE
   SYNTAX      Counter64
   MAX-ACCESS  read-only
   STATUS      current
   DESCRIPTION
      "Path: swPort.performance.vlan.inPriorityQueues.h24Performance.directTxOctets

       64 bit unsigned wrappable counter."
   ::= {pr1646v2EthPortSwFVlanInPQsH24PerformanceEntry 117440512}

pr1646v2EthPortSwFVlanInPQsH24PerformanceQdOcts OBJECT-TYPE
   SYNTAX      Counter64
   MAX-ACCESS  read-only
   STATUS      current
   DESCRIPTION
      "Path: swPort.performance.vlan.inPriorityQueues.h24Performance.queuedOctets

       64 bit unsigned wrappable counter."
   ::= {pr1646v2EthPortSwFVlanInPQsH24PerformanceEntry 134217728}

pr1646v2EthPortSwFVlanInPQsH24PerformanceDropOcts OBJECT-TYPE
   SYNTAX      Counter64
   MAX-ACCESS  read-only
   STATUS      current
   DESCRIPTION
      "Path: swPort.performance.vlan.inPriorityQueues.h24Performance.droppedOctets

       64 bit unsigned wrappable counter."
   ::= {pr1646v2EthPortSwFVlanInPQsH24PerformanceEntry 150994944}

pr1646v2EthPortSwFVlanInPQsH24PerformanceRDropOcts OBJECT-TYPE
   SYNTAX      Counter64
   MAX-ACCESS  read-only
   STATUS      current
   DESCRIPTION
      "Path: swPort.performance.vlan.inPriorityQueues.h24Performance.redDroppedOctets

       64 bit unsigned wrappable counter."
   ::= {pr1646v2EthPortSwFVlanInPQsH24PerformanceEntry 218103808}

pr1646v2EthPortSwFVlanInPQsH24PerformanceCirTxOcts OBJECT-TYPE
   SYNTAX      Counter64
   MAX-ACCESS  read-only
   STATUS      current
   DESCRIPTION
      "Path: swPort.performance.vlan.inPriorityQueues.h24Performance.cirTxOctets

       64 bit unsigned wrappable counter."
   ::= {pr1646v2EthPortSwFVlanInPQsH24PerformanceEntry 167772160}

pr1646v2EthPortSwFVlanInPQsH24PerformanceEirTxOcts OBJECT-TYPE
   SYNTAX      Counter64
   MAX-ACCESS  read-only
   STATUS      current
   DESCRIPTION
      "Path: swPort.performance.vlan.inPriorityQueues.h24Performance.eirTxOctets

       64 bit unsigned wrappable counter."
   ::= {pr1646v2EthPortSwFVlanInPQsH24PerformanceEntry 184549376}

pr1646v2EthPortSwFVlanInPQsH24PerformanceViolTxOcts OBJECT-TYPE
   SYNTAX      Counter64
   MAX-ACCESS  read-only
   STATUS      current
   DESCRIPTION
      "Path: swPort.performance.vlan.inPriorityQueues.h24Performance.violateTxOctets

       64 bit unsigned wrappable counter."
   ::= {pr1646v2EthPortSwFVlanInPQsH24PerformanceEntry 318767104}

pr1646v2EthPortSwFVlanInPQsH24PerformanceBandwidth OBJECT-TYPE
   SYNTAX      Integer32
   MAX-ACCESS  read-only
   STATUS      current
   DESCRIPTION
      "Path: swPort.performance.vlan.inPriorityQueues.h24Performance.bandwidth

       unit name = bps
       formula = 8 * ; 8 /"
   ::= {pr1646v2EthPortSwFVlanInPQsH24PerformanceEntry 268435456}

pr1646v2EthPortSwFVlanInPQsD7Performance OBJECT-TYPE
   SYNTAX      SEQUENCE OF Pr1646v2EthPortSwFVlanInPQsD7PerformanceEntry
   MAX-ACCESS  not-accessible
   STATUS      current
   DESCRIPTION
      ""
   ::= {pr1646v2EthPortSwFVlan 101122048}

pr1646v2EthPortSwFVlanInPQsD7PerformanceEntry OBJECT-TYPE
   SYNTAX      Pr1646v2EthPortSwFVlanInPQsD7PerformanceEntry
   MAX-ACCESS  not-accessible
   STATUS      current
   DESCRIPTION
      ""
   INDEX      { pr1646v2EthPortSwFVlanInPQsD7PerformanceGlobalIx,
                pr1646v2EthPortSwFVlanTableIx,
                pr1646v2EthPortSwFVlanInPQsTableIx,
                pr1646v2EthPortSwFVlanInPQsD7PerformanceTableIx }
   ::= {pr1646v2EthPortSwFVlanInPQsD7Performance 1}

Pr1646v2EthPortSwFVlanInPQsD7PerformanceEntry ::=
   SEQUENCE
      {
      pr1646v2EthPortSwFVlanInPQsD7PerformanceGlobalIx
         GlobalIndex,
      pr1646v2EthPortSwFVlanInPQsD7PerformanceTableIx
         TableIndex,
      pr1646v2EthPortSwFVlanInPQsD7PerformanceSysUpTime
         TimeTicks,
      pr1646v2EthPortSwFVlanInPQsD7PerformanceTotPkts
         Counter64,
      pr1646v2EthPortSwFVlanInPQsD7PerformanceDirTxPkts
         Counter64,
      pr1646v2EthPortSwFVlanInPQsD7PerformanceQdPkts
         Counter64,
      pr1646v2EthPortSwFVlanInPQsD7PerformanceDropPkts
         Counter64,
      pr1646v2EthPortSwFVlanInPQsD7PerformanceRDropPkts
         Counter64,
      pr1646v2EthPortSwFVlanInPQsD7PerformanceCirTxPkts
         Counter64,
      pr1646v2EthPortSwFVlanInPQsD7PerformanceEirTxPkts
         Counter64,
      pr1646v2EthPortSwFVlanInPQsD7PerformanceViolTxPkts
         Counter64,
      pr1646v2EthPortSwFVlanInPQsD7PerformanceTotOcts
         Counter64,
      pr1646v2EthPortSwFVlanInPQsD7PerformanceDirTxOcts
         Counter64,
      pr1646v2EthPortSwFVlanInPQsD7PerformanceQdOcts
         Counter64,
      pr1646v2EthPortSwFVlanInPQsD7PerformanceDropOcts
         Counter64,
      pr1646v2EthPortSwFVlanInPQsD7PerformanceRDropOcts
         Counter64,
      pr1646v2EthPortSwFVlanInPQsD7PerformanceCirTxOcts
         Counter64,
      pr1646v2EthPortSwFVlanInPQsD7PerformanceEirTxOcts
         Counter64,
      pr1646v2EthPortSwFVlanInPQsD7PerformanceViolTxOcts
         Counter64,
      pr1646v2EthPortSwFVlanInPQsD7PerformanceBandwidth
         Integer32
      }

pr1646v2EthPortSwFVlanInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanInPQsD7PerformanceEntry 10}

pr1646v2EthPortSwFVlanInPQsD7PerformanceTableIx OBJECT-TYPE
   SYNTAX      TableIndex
   MAX-ACCESS  not-accessible
   STATUS      current
   DESCRIPTION
      ""
   ::= {pr1646v2EthPortSwFVlanInPQsD7PerformanceEntry 11}

pr1646v2EthPortSwFVlanInPQsD7PerformanceSysUpTime OBJECT-TYPE
   SYNTAX      TimeTicks
   MAX-ACCESS  read-only
   STATUS      current
   DESCRIPTION
      "Path: swPort.performance.vlan.inPriorityQueues.d7Performance.sysUpTime

       Time in centi-second."
   ::= {pr1646v2EthPortSwFVlanInPQsD7PerformanceEntry 16777216}

pr1646v2EthPortSwFVlanInPQsD7PerformanceTotPkts OBJECT-TYPE
   SYNTAX      Counter64
   MAX-ACCESS  read-only
   STATUS      current
   DESCRIPTION
      "Path: swPort.performance.vlan.inPriorityQueues.d7Performance.totalPkts

       64 bit unsigned wrappable counter."
   ::= {pr1646v2EthPortSwFVlanInPQsD7PerformanceEntry 234881024}

pr1646v2EthPortSwFVlanInPQsD7PerformanceDirTxPkts OBJECT-TYPE
   SYNTAX      Counter64
   MAX-ACCESS  read-only
   STATUS      current
   DESCRIPTION
      "Path: swPort.performance.vlan.inPriorityQueues.d7Performance.directTxPkts

       64 bit unsigned wrappable counter."
   ::= {pr1646v2EthPortSwFVlanInPQsD7PerformanceEntry 33554432}

pr1646v2EthPortSwFVlanInPQsD7PerformanceQdPkts OBJECT-TYPE
   SYNTAX      Counter64
   MAX-ACCESS  read-only
   STATUS      current
   DESCRIPTION
      "Path: swPort.performance.vlan.inPriorityQueues.d7Performance.queuedPkts

       64 bit unsigned wrappable counter."
   ::= {pr1646v2EthPortSwFVlanInPQsD7PerformanceEntry 50331648}

pr1646v2EthPortSwFVlanInPQsD7PerformanceDropPkts OBJECT-TYPE
   SYNTAX      Counter64
   MAX-ACCESS  read-only
   STATUS      current
   DESCRIPTION
      "Path: swPort.performance.vlan.inPriorityQueues.d7Performance.droppedPkts

       64 bit unsigned wrappable counter."
   ::= {pr1646v2EthPortSwFVlanInPQsD7PerformanceEntry 67108864}

pr1646v2EthPortSwFVlanInPQsD7PerformanceRDropPkts OBJECT-TYPE
   SYNTAX      Counter64
   MAX-ACCESS  read-only
   STATUS      current
   DESCRIPTION
      "Path: swPort.performance.vlan.inPriorityQueues.d7Performance.redDroppedPkts

       64 bit unsigned wrappable counter."
   ::= {pr1646v2EthPortSwFVlanInPQsD7PerformanceEntry 201326592}

pr1646v2EthPortSwFVlanInPQsD7PerformanceCirTxPkts OBJECT-TYPE
   SYNTAX      Counter64
   MAX-ACCESS  read-only
   STATUS      current
   DESCRIPTION
      "Path: swPort.performance.vlan.inPriorityQueues.d7Performance.cirTxPkts

       64 bit unsigned wrappable counter."
   ::= {pr1646v2EthPortSwFVlanInPQsD7PerformanceEntry 83886080}

pr1646v2EthPortSwFVlanInPQsD7PerformanceEirTxPkts OBJECT-TYPE
   SYNTAX      Counter64
   MAX-ACCESS  read-only
   STATUS      current
   DESCRIPTION
      "Path: swPort.performance.vlan.inPriorityQueues.d7Performance.eirTxPkts

       64 bit unsigned wrappable counter."
   ::= {pr1646v2EthPortSwFVlanInPQsD7PerformanceEntry 100663296}

pr1646v2EthPortSwFVlanInPQsD7PerformanceViolTxPkts OBJECT-TYPE
   SYNTAX      Counter64
   MAX-ACCESS  read-only
   STATUS      current
   DESCRIPTION
      "Path: swPort.performance.vlan.inPriorityQueues.d7Performance.violateTxPkts

       64 bit unsigned wrappable counter."
   ::= {pr1646v2EthPortSwFVlanInPQsD7PerformanceEntry 301989888}

pr1646v2EthPortSwFVlanInPQsD7PerformanceTotOcts OBJECT-TYPE
   SYNTAX      Counter64
   MAX-ACCESS  read-only
   STATUS      current
   DESCRIPTION
      "Path: swPort.performance.vlan.inPriorityQueues.d7Performance.totalOctets

       64 bit unsigned wrappable counter."
   ::= {pr1646v2EthPortSwFVlanInPQsD7PerformanceEntry 251658240}

pr1646v2EthPortSwFVlanInPQsD7PerformanceDirTxOcts OBJECT-TYPE
   SYNTAX      Counter64
   MAX-ACCESS  read-only
   STATUS      current
   DESCRIPTION
      "Path: swPort.performance.vlan.inPriorityQueues.d7Performance.directTxOctets

       64 bit unsigned wrappable counter."
   ::= {pr1646v2EthPortSwFVlanInPQsD7PerformanceEntry 117440512}

pr1646v2EthPortSwFVlanInPQsD7PerformanceQdOcts OBJECT-TYPE
   SYNTAX      Counter64
   MAX-ACCESS  read-only
   STATUS      current
   DESCRIPTION
      "Path: swPort.performance.vlan.inPriorityQueues.d7Performance.queuedOctets

       64 bit unsigned wrappable counter."
   ::= {pr1646v2EthPortSwFVlanInPQsD7PerformanceEntry 134217728}

pr1646v2EthPortSwFVlanInPQsD7PerformanceDropOcts OBJECT-TYPE
   SYNTAX      Counter64
   MAX-ACCESS  read-only
   STATUS      current
   DESCRIPTION
      "Path: swPort.performance.vlan.inPriorityQueues.d7Performance.droppedOctets

       64 bit unsigned wrappable counter."
   ::= {pr1646v2EthPortSwFVlanInPQsD7PerformanceEntry 150994944}

pr1646v2EthPortSwFVlanInPQsD7PerformanceRDropOcts OBJECT-TYPE
   SYNTAX      Counter64
   MAX-ACCESS  read-only
   STATUS      current
   DESCRIPTION
      "Path: swPort.performance.vlan.inPriorityQueues.d7Performance.redDroppedOctets

       64 bit unsigned wrappable counter."
   ::= {pr1646v2EthPortSwFVlanInPQsD7PerformanceEntry 218103808}

pr1646v2EthPortSwFVlanInPQsD7PerformanceCirTxOcts OBJECT-TYPE
   SYNTAX      Counter64
   MAX-ACCESS  read-only
   STATUS      current
   DESCRIPTION
      "Path: swPort.performance.vlan.inPriorityQueues.d7Performance.cirTxOctets

       64 bit unsigned wrappable counter."
   ::= {pr1646v2EthPortSwFVlanInPQsD7PerformanceEntry 167772160}

pr1646v2EthPortSwFVlanInPQsD7PerformanceEirTxOcts OBJECT-TYPE
   SYNTAX      Counter64
   MAX-ACCESS  read-only
   STATUS      current
   DESCRIPTION
      "Path: swPort.performance.vlan.inPriorityQueues.d7Performance.eirTxOctets

       64 bit unsigned wrappable counter."
   ::= {pr1646v2EthPortSwFVlanInPQsD7PerformanceEntry 184549376}

pr1646v2EthPortSwFVlanInPQsD7PerformanceViolTxOcts OBJECT-TYPE
   SYNTAX      Counter64
   MAX-ACCESS  read-only
   STATUS      current
   DESCRIPTION
      "Path: swPort.performance.vlan.inPriorityQueues.d7Performance.violateTxOctets

       64 bit unsigned wrappable counter."
   ::= {pr1646v2EthPortSwFVlanInPQsD7PerformanceEntry 318767104}

pr1646v2EthPortSwFVlanInPQsD7PerformanceBandwidth OBJECT-TYPE
   SYNTAX      Integer32
   MAX-ACCESS  read-only
   STATUS      current
   DESCRIPTION
      "Path: swPort.performance.vlan.inPriorityQueues.d7Performance.bandwidth

       unit name = bps
       formula = 8 * ; 8 /"
   ::= {pr1646v2EthPortSwFVlanInPQsD7PerformanceEntry 268435456}

pr1646v2EthPortSwFVlanOutPQs OBJECT-TYPE
   SYNTAX      SEQUENCE OF Pr1646v2EthPortSwFVlanOutPQsEntry
   MAX-ACCESS  not-accessible
   STATUS      current
   DESCRIPTION
      ""
   ::= {pr1646v2EthPortSwFVlan 83886080}

pr1646v2EthPortSwFVlanOutPQsEntry OBJECT-TYPE
   SYNTAX      Pr1646v2EthPortSwFVlanOutPQsEntry
   MAX-ACCESS  not-accessible
   STATUS      current
   DESCRIPTION
      ""
   INDEX      { pr1646v2EthPortSwFVlanOutPQsGlobalIx,
                pr1646v2EthPortSwFVlanTableIx,
                pr1646v2EthPortSwFVlanOutPQsTableIx }
   ::= {pr1646v2EthPortSwFVlanOutPQs 1}

Pr1646v2EthPortSwFVlanOutPQsEntry ::=
   SEQUENCE
      {
      pr1646v2EthPortSwFVlanOutPQsGlobalIx
         GlobalIndex,
      pr1646v2EthPortSwFVlanOutPQsTableIx
         TableIndex,
      pr1646v2EthPortSwFVlanOutPQsName
         INTEGER,
      pr1646v2EthPortSwFVlanOutPQsLength
         Integer32,
      pr1646v2EthPortSwFVlanOutPQsOctetLength
         Integer32,
      pr1646v2EthPortSwFVlanOutPQsRedLength
         Integer32,
      pr1646v2EthPortSwFVlanOutPQsPacketsTotal
         Counter64,
      pr1646v2EthPortSwFVlanOutPQsPacketsDirectTx
         Counter64,
      pr1646v2EthPortSwFVlanOutPQsPacketsQueued
         Counter64,
      pr1646v2EthPortSwFVlanOutPQsPacketsDropped
         Counter64,
      pr1646v2EthPortSwFVlanOutPQsPacketsRedDropped
         Counter64,
      pr1646v2EthPortSwFVlanOutPQsPacketsCirTx
         Counter64,
      pr1646v2EthPortSwFVlanOutPQsPacketsEirTx
         Counter64,
      pr1646v2EthPortSwFVlanOutPQsPacketsViolateTx
         Counter64,
      pr1646v2EthPortSwFVlanOutPQsOctetsTotal
         Counter64,
      pr1646v2EthPortSwFVlanOutPQsOctetsDirectTx
         Counter64,
      pr1646v2EthPortSwFVlanOutPQsOctetsQueued
         Counter64,
      pr1646v2EthPortSwFVlanOutPQsOctetsDropped
         Counter64,
      pr1646v2EthPortSwFVlanOutPQsOctetsRedDropped
         Counter64,
      pr1646v2EthPortSwFVlanOutPQsOctetsCirTx
         Counter64,
      pr1646v2EthPortSwFVlanOutPQsOctetsEirTx
         Counter64,
      pr1646v2EthPortSwFVlanOutPQsOctetsViolateTx
         Counter64,
      pr1646v2EthPortSwFVlanOutPQsOctetsBandwidth15sec
         Integer32,
      pr1646v2EthPortSwFVlanOutPQsOctetsBandwidth30sec
         Integer32,
      pr1646v2EthPortSwFVlanOutPQsOctetsBandwidth1min
         Integer32,
      pr1646v2EthPortSwFVlanOutPQsOctetsBandwidth2min
         Integer32,
      pr1646v2EthPortSwFVlanOutPQsOctetsBandwidth5min
         Integer32
      }

pr1646v2EthPortSwFVlanOutPQsGlobalIx OBJECT-TYPE
   SYNTAX      GlobalIndex
   MAX-ACCESS  not-accessible
   STATUS      current
   DESCRIPTION
      "The value of the tlsCntTreeGlobalIndex of the MANAGED OBJECT."
   ::= {pr1646v2EthPortSwFVlanOutPQsEntry 10}

pr1646v2EthPortSwFVlanOutPQsTableIx OBJECT-TYPE
   SYNTAX      TableIndex
   MAX-ACCESS  not-accessible
   STATUS      current
   DESCRIPTION
      ""
   ::= {pr1646v2EthPortSwFVlanOutPQsEntry 11}

pr1646v2EthPortSwFVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwFVlanOutPQsEntry 16777216}

pr1646v2EthPortSwFVlanOutPQsLength OBJECT-TYPE
   SYNTAX      Integer32
   MAX-ACCESS  read-only
   STATUS      current
   DESCRIPTION
      "Path: swPort.performance.vlan.outPriorityQueues.length"
   ::= {pr1646v2EthPortSwFVlanOutPQsEntry 33554432}

pr1646v2EthPortSwFVlanOutPQsOctetLength OBJECT-TYPE
   SYNTAX      Integer32
   MAX-ACCESS  read-only
   STATUS      current
   DESCRIPTION
      "Path: swPort.performance.vlan.outPriorityQueues.octetLength"
   ::= {pr1646v2EthPortSwFVlanOutPQsEntry 150994944}

pr1646v2EthPortSwFVlanOutPQsRedLength OBJECT-TYPE
   SYNTAX      Integer32
   MAX-ACCESS  read-only
   STATUS      current
   DESCRIPTION
      "Path: swPort.performance.vlan.outPriorityQueues.redLength"
   ::= {pr1646v2EthPortSwFVlanOutPQsEntry 134217728}

pr1646v2EthPortSwFVlanOutPQsPacketsTotal OBJECT-TYPE
   SYNTAX      Counter64
   MAX-ACCESS  read-only
   STATUS      current
   DESCRIPTION
      "Path: swPort.performance.vlan.outPriorityQueues.packets.total

       64 bit unsigned wrappable counter."
   ::= {pr1646v2EthPortSwFVlanOutPQsEntry 50790400}

pr1646v2EthPortSwFVlanOutPQsPacketsDirectTx OBJECT-TYPE
   SYNTAX      Counter64
   MAX-ACCESS  read-only
   STATUS      current
   DESCRIPTION
      "Path: swPort.performance.vlan.outPriorityQueues.packets.directTx

       64 bit unsigned wrappable counter."
   ::= {pr1646v2EthPortSwFVlanOutPQsEntry 50397184}

pr1646v2EthPortSwFVlanOutPQsPacketsQueued OBJECT-TYPE
   SYNTAX      Counter64
   MAX-ACCESS  read-only
   STATUS      current
   DESCRIPTION
      "Path: swPort.performance.vlan.outPriorityQueues.packets.queued

       64 bit unsigned wrappable counter."
   ::= {pr1646v2EthPortSwFVlanOutPQsEntry 50462720}

pr1646v2EthPortSwFVlanOutPQsPacketsDropped OBJECT-TYPE
   SYNTAX      Counter64
   MAX-ACCESS  read-only
   STATUS      current
   DESCRIPTION
      "Path: swPort.performance.vlan.outPriorityQueues.packets.dropped

       64 bit unsigned wrappable counter."
   ::= {pr1646v2EthPortSwFVlanOutPQsEntry 50528256}

pr1646v2EthPortSwFVlanOutPQsPacketsRedDropped OBJECT-TYPE
   SYNTAX      Counter64
   MAX-ACCESS  read-only
   STATUS      current
   DESCRIPTION
      "Path: swPort.performance.vlan.outPriorityQueues.packets.redDropped

       64 bit unsigned wrappable counter."
   ::= {pr1646v2EthPortSwFVlanOutPQsEntry 50724864}

pr1646v2EthPortSwFVlanOutPQsPacketsCirTx OBJECT-TYPE
   SYNTAX      Counter64
   MAX-ACCESS  read-only
   STATUS      current
   DESCRIPTION
      "Path: swPort.performance.vlan.outPriorityQueues.packets.cirTx

       64 bit unsigned wrappable counter."
   ::= {pr1646v2EthPortSwFVlanOutPQsEntry 50593792}

pr1646v2EthPortSwFVlanOutPQsPacketsEirTx OBJECT-TYPE
   SYNTAX      Counter64
   MAX-ACCESS  read-only
   STATUS      current
   DESCRIPTION
      "Path: swPort.performance.vlan.outPriorityQueues.packets.eirTx

       64 bit unsigned wrappable counter."
   ::= {pr1646v2EthPortSwFVlanOutPQsEntry 50659328}

pr1646v2EthPortSwFVlanOutPQsPacketsViolateTx OBJECT-TYPE
   SYNTAX      Counter64
   MAX-ACCESS  read-only
   STATUS      current
   DESCRIPTION
      "Path: swPort.performance.vlan.outPriorityQueues.packets.violateTx

       64 bit unsigned wrappable counter."
   ::= {pr1646v2EthPortSwFVlanOutPQsEntry 50855936}

pr1646v2EthPortSwFVlanOutPQsOctetsTotal OBJECT-TYPE
   SYNTAX      Counter64
   MAX-ACCESS  read-only
   STATUS      current
   DESCRIPTION
      "Path: swPort.performance.vlan.outPriorityQueues.octets.total

       64 bit unsigned wrappable counter."
   ::= {pr1646v2EthPortSwFVlanOutPQsEntry 67567616}

pr1646v2EthPortSwFVlanOutPQsOctetsDirectTx OBJECT-TYPE
   SYNTAX      Counter64
   MAX-ACCESS  read-only
   STATUS      current
   DESCRIPTION
      "Path: swPort.performance.vlan.outPriorityQueues.octets.directTx

       64 bit unsigned wrappable counter."
   ::= {pr1646v2EthPortSwFVlanOutPQsEntry 67174400}

pr1646v2EthPortSwFVlanOutPQsOctetsQueued OBJECT-TYPE
   SYNTAX      Counter64
   MAX-ACCESS  read-only
   STATUS      current
   DESCRIPTION
      "Path: swPort.performance.vlan.outPriorityQueues.octets.queued

       64 bit unsigned wrappable counter."
   ::= {pr1646v2EthPortSwFVlanOutPQsEntry 67239936}

pr1646v2EthPortSwFVlanOutPQsOctetsDropped OBJECT-TYPE
   SYNTAX      Counter64
   MAX-ACCESS  read-only
   STATUS      current
   DESCRIPTION
      "Path: swPort.performance.vlan.outPriorityQueues.octets.dropped

       64 bit unsigned wrappable counter."
   ::= {pr1646v2EthPortSwFVlanOutPQsEntry 67305472}

pr1646v2EthPortSwFVlanOutPQsOctetsRedDropped OBJECT-TYPE
   SYNTAX      Counter64
   MAX-ACCESS  read-only
   STATUS      current
   DESCRIPTION
      "Path: swPort.performance.vlan.outPriorityQueues.octets.redDropped

       64 bit unsigned wrappable counter."
   ::= {pr1646v2EthPortSwFVlanOutPQsEntry 67502080}

pr1646v2EthPortSwFVlanOutPQsOctetsCirTx OBJECT-TYPE
   SYNTAX      Counter64
   MAX-ACCESS  read-only
   STATUS      current
   DESCRIPTION
      "Path: swPort.performance.vlan.outPriorityQueues.octets.cirTx

       64 bit unsigned wrappable counter."
   ::= {pr1646v2EthPortSwFVlanOutPQsEntry 67371008}

pr1646v2EthPortSwFVlanOutPQsOctetsEirTx OBJECT-TYPE
   SYNTAX      Counter64
   MAX-ACCESS  read-only
   STATUS      current
   DESCRIPTION
      "Path: swPort.performance.vlan.outPriorityQueues.octets.eirTx

       64 bit unsigned wrappable counter."
   ::= {pr1646v2EthPortSwFVlanOutPQsEntry 67436544}

pr1646v2EthPortSwFVlanOutPQsOctetsViolateTx OBJECT-TYPE
   SYNTAX      Counter64
   MAX-ACCESS  read-only
   STATUS      current
   DESCRIPTION
      "Path: swPort.performance.vlan.outPriorityQueues.octets.violateTx

       64 bit unsigned wrappable counter."
   ::= {pr1646v2EthPortSwFVlanOutPQsEntry 67633152}

pr1646v2EthPortSwFVlanOutPQsOctetsBandwidth15sec OBJECT-TYPE
   SYNTAX      Integer32
   MAX-ACCESS  read-only
   STATUS      current
   DESCRIPTION
      "Path: swPort.performance.vlan.outPriorityQueues.octets.bandwidth.15sec

       unit name = bps
       formula = 8 * ; 8 /"
   ::= {pr1646v2EthPortSwFVlanOutPQsEntry 70386944}

pr1646v2EthPortSwFVlanOutPQsOctetsBandwidth30sec OBJECT-TYPE
   SYNTAX      Integer32
   MAX-ACCESS  read-only
   STATUS      current
   DESCRIPTION
      "Path: swPort.performance.vlan.outPriorityQueues.octets.bandwidth.30sec

       unit name = bps
       formula = 8 * ; 8 /"
   ::= {pr1646v2EthPortSwFVlanOutPQsEntry 70388224}

pr1646v2EthPortSwFVlanOutPQsOctetsBandwidth1min OBJECT-TYPE
   SYNTAX      Integer32
   MAX-ACCESS  read-only
   STATUS      current
   DESCRIPTION
      "Path: swPort.performance.vlan.outPriorityQueues.octets.bandwidth.1min

       unit name = bps
       formula = 8 * ; 8 /"
   ::= {pr1646v2EthPortSwFVlanOutPQsEntry 70390784}

pr1646v2EthPortSwFVlanOutPQsOctetsBandwidth2min OBJECT-TYPE
   SYNTAX      Integer32
   MAX-ACCESS  read-only
   STATUS      current
   DESCRIPTION
      "Path: swPort.performance.vlan.outPriorityQueues.octets.bandwidth.2min

       unit name = bps
       formula = 8 * ; 8 /"
   ::= {pr1646v2EthPortSwFVlanOutPQsEntry 70395904}

pr1646v2EthPortSwFVlanOutPQsOctetsBandwidth5min OBJECT-TYPE
   SYNTAX      Integer32
   MAX-ACCESS  read-only
   STATUS      current
   DESCRIPTION
      "Path: swPort.performance.vlan.outPriorityQueues.octets.bandwidth.5min

       unit name = bps
       formula = 8 * ; 8 /"
   ::= {pr1646v2EthPortSwFVlanOutPQsEntry 70411264}

pr1646v2EthPortSwFVlanOutPQsH2Performance OBJECT-TYPE
   SYNTAX      SEQUENCE OF Pr1646v2EthPortSwFVlanOutPQsH2PerformanceEntry
   MAX-ACCESS  not-accessible
   STATUS      current
   DESCRIPTION
      ""
   ::= {pr1646v2EthPortSwFVlan 84213760}

pr1646v2EthPortSwFVlanOutPQsH2PerformanceEntry OBJECT-TYPE
   SYNTAX      Pr1646v2EthPortSwFVlanOutPQsH2PerformanceEntry
   MAX-ACCESS  not-accessible
   STATUS      current
   DESCRIPTION
      ""
   INDEX      { pr1646v2EthPortSwFVlanOutPQsH2PerformanceGlobalIx,
                pr1646v2EthPortSwFVlanTableIx,
                pr1646v2EthPortSwFVlanOutPQsTableIx,
                pr1646v2EthPortSwFVlanOutPQsH2PerformanceTableIx }
   ::= {pr1646v2EthPortSwFVlanOutPQsH2Performance 1}

Pr1646v2EthPortSwFVlanOutPQsH2PerformanceEntry ::=
   SEQUENCE
      {
      pr1646v2EthPortSwFVlanOutPQsH2PerformanceGlobalIx
         GlobalIndex,
      pr1646v2EthPortSwFVlanOutPQsH2PerformanceTableIx
         TableIndex,
      pr1646v2EthPortSwFVlanOutPQsH2PerformanceSysUpTime
         TimeTicks,
      pr1646v2EthPortSwFVlanOutPQsH2PerformanceTotPkts
         Counter64,
      pr1646v2EthPortSwFVlanOutPQsH2PerformanceDirTxPkts
         Counter64,
      pr1646v2EthPortSwFVlanOutPQsH2PerformanceQdPkts
         Counter64,
      pr1646v2EthPortSwFVlanOutPQsH2PerformanceDropPkts
         Counter64,
      pr1646v2EthPortSwFVlanOutPQsH2PerformanceRDropPkts
         Counter64,
      pr1646v2EthPortSwFVlanOutPQsH2PerformanceCirTxPkts
         Counter64,
      pr1646v2EthPortSwFVlanOutPQsH2PerformanceEirTxPkts
         Counter64,
      pr1646v2EthPortSwFVlanOutPQsH2PerformanceViolTxPkts
         Counter64,
      pr1646v2EthPortSwFVlanOutPQsH2PerformanceTotOcts
         Counter64,
      pr1646v2EthPortSwFVlanOutPQsH2PerformanceDirTxOcts
         Counter64,
      pr1646v2EthPortSwFVlanOutPQsH2PerformanceQdOcts
         Counter64,
      pr1646v2EthPortSwFVlanOutPQsH2PerformanceDropOcts
         Counter64,
      pr1646v2EthPortSwFVlanOutPQsH2PerformanceRDropOcts
         Counter64,
      pr1646v2EthPortSwFVlanOutPQsH2PerformanceCirTxOcts
         Counter64,
      pr1646v2EthPortSwFVlanOutPQsH2PerformanceEirTxOcts
         Counter64,
      pr1646v2EthPortSwFVlanOutPQsH2PerformanceViolTxOcts
         Counter64,
      pr1646v2EthPortSwFVlanOutPQsH2PerformanceBandwidth
         Integer32
      }

pr1646v2EthPortSwFVlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanOutPQsH2PerformanceEntry 10}

pr1646v2EthPortSwFVlanOutPQsH2PerformanceTableIx OBJECT-TYPE
   SYNTAX      TableIndex
   MAX-ACCESS  not-accessible
   STATUS      current
   DESCRIPTION
      ""
   ::= {pr1646v2EthPortSwFVlanOutPQsH2PerformanceEntry 11}

pr1646v2EthPortSwFVlanOutPQsH2PerformanceSysUpTime OBJECT-TYPE
   SYNTAX      TimeTicks
   MAX-ACCESS  read-only
   STATUS      current
   DESCRIPTION
      "Path: swPort.performance.vlan.outPriorityQueues.h2Performance.sysUpTime

       Time in centi-second."
   ::= {pr1646v2EthPortSwFVlanOutPQsH2PerformanceEntry 16777216}

pr1646v2EthPortSwFVlanOutPQsH2PerformanceTotPkts OBJECT-TYPE
   SYNTAX      Counter64
   MAX-ACCESS  read-only
   STATUS      current
   DESCRIPTION
      "Path: swPort.performance.vlan.outPriorityQueues.h2Performance.totalPkts

       64 bit unsigned wrappable counter."
   ::= {pr1646v2EthPortSwFVlanOutPQsH2PerformanceEntry 234881024}

pr1646v2EthPortSwFVlanOutPQsH2PerformanceDirTxPkts OBJECT-TYPE
   SYNTAX      Counter64
   MAX-ACCESS  read-only
   STATUS      current
   DESCRIPTION
      "Path: swPort.performance.vlan.outPriorityQueues.h2Performance.directTxPkts

       64 bit unsigned wrappable counter."
   ::= {pr1646v2EthPortSwFVlanOutPQsH2PerformanceEntry 33554432}

pr1646v2EthPortSwFVlanOutPQsH2PerformanceQdPkts OBJECT-TYPE
   SYNTAX      Counter64
   MAX-ACCESS  read-only
   STATUS      current
   DESCRIPTION
      "Path: swPort.performance.vlan.outPriorityQueues.h2Performance.queuedPkts

       64 bit unsigned wrappable counter."
   ::= {pr1646v2EthPortSwFVlanOutPQsH2PerformanceEntry 50331648}

pr1646v2EthPortSwFVlanOutPQsH2PerformanceDropPkts OBJECT-TYPE
   SYNTAX      Counter64
   MAX-ACCESS  read-only
   STATUS      current
   DESCRIPTION
      "Path: swPort.performance.vlan.outPriorityQueues.h2Performance.droppedPkts

       64 bit unsigned wrappable counter."
   ::= {pr1646v2EthPortSwFVlanOutPQsH2PerformanceEntry 67108864}

pr1646v2EthPortSwFVlanOutPQsH2PerformanceRDropPkts OBJECT-TYPE
   SYNTAX      Counter64
   MAX-ACCESS  read-only
   STATUS      current
   DESCRIPTION
      "Path: swPort.performance.vlan.outPriorityQueues.h2Performance.redDroppedPkts

       64 bit unsigned wrappable counter."
   ::= {pr1646v2EthPortSwFVlanOutPQsH2PerformanceEntry 201326592}

pr1646v2EthPortSwFVlanOutPQsH2PerformanceCirTxPkts OBJECT-TYPE
   SYNTAX      Counter64
   MAX-ACCESS  read-only
   STATUS      current
   DESCRIPTION
      "Path: swPort.performance.vlan.outPriorityQueues.h2Performance.cirTxPkts

       64 bit unsigned wrappable counter."
   ::= {pr1646v2EthPortSwFVlanOutPQsH2PerformanceEntry 83886080}

pr1646v2EthPortSwFVlanOutPQsH2PerformanceEirTxPkts OBJECT-TYPE
   SYNTAX      Counter64
   MAX-ACCESS  read-only
   STATUS      current
   DESCRIPTION
      "Path: swPort.performance.vlan.outPriorityQueues.h2Performance.eirTxPkts

       64 bit unsigned wrappable counter."
   ::= {pr1646v2EthPortSwFVlanOutPQsH2PerformanceEntry 100663296}

pr1646v2EthPortSwFVlanOutPQsH2PerformanceViolTxPkts OBJECT-TYPE
   SYNTAX      Counter64
   MAX-ACCESS  read-only
   STATUS      current
   DESCRIPTION
      "Path: swPort.performance.vlan.outPriorityQueues.h2Performance.violateTxPkts

       64 bit unsigned wrappable counter."
   ::= {pr1646v2EthPortSwFVlanOutPQsH2PerformanceEntry 301989888}

pr1646v2EthPortSwFVlanOutPQsH2PerformanceTotOcts OBJECT-TYPE
   SYNTAX      Counter64
   MAX-ACCESS  read-only
   STATUS      current
   DESCRIPTION
      "Path: swPort.performance.vlan.outPriorityQueues.h2Performance.totalOctets

       64 bit unsigned wrappable counter."
   ::= {pr1646v2EthPortSwFVlanOutPQsH2PerformanceEntry 251658240}

pr1646v2EthPortSwFVlanOutPQsH2PerformanceDirTxOcts OBJECT-TYPE
   SYNTAX      Counter64
   MAX-ACCESS  read-only
   STATUS      current
   DESCRIPTION
      "Path: swPort.performance.vlan.outPriorityQueues.h2Performance.directTxOctets

       64 bit unsigned wrappable counter."
   ::= {pr1646v2EthPortSwFVlanOutPQsH2PerformanceEntry 117440512}

pr1646v2EthPortSwFVlanOutPQsH2PerformanceQdOcts OBJECT-TYPE
   SYNTAX      Counter64
   MAX-ACCESS  read-only
   STATUS      current
   DESCRIPTION
      "Path: swPort.performance.vlan.outPriorityQueues.h2Performance.queuedOctets

       64 bit unsigned wrappable counter."
   ::= {pr1646v2EthPortSwFVlanOutPQsH2PerformanceEntry 134217728}

pr1646v2EthPortSwFVlanOutPQsH2PerformanceDropOcts OBJECT-TYPE
   SYNTAX      Counter64
   MAX-ACCESS  read-only
   STATUS      current
   DESCRIPTION
      "Path: swPort.performance.vlan.outPriorityQueues.h2Performance.droppedOctets

       64 bit unsigned wrappable counter."
   ::= {pr1646v2EthPortSwFVlanOutPQsH2PerformanceEntry 150994944}

pr1646v2EthPortSwFVlanOutPQsH2PerformanceRDropOcts OBJECT-TYPE
   SYNTAX      Counter64
   MAX-ACCESS  read-only
   STATUS      current
   DESCRIPTION
      "Path: swPort.performance.vlan.outPriorityQueues.h2Performance.redDroppedOctets

       64 bit unsigned wrappable counter."
   ::= {pr1646v2EthPortSwFVlanOutPQsH2PerformanceEntry 218103808}

pr1646v2EthPortSwFVlanOutPQsH2PerformanceCirTxOcts OBJECT-TYPE
   SYNTAX      Counter64
   MAX-ACCESS  read-only
   STATUS      current
   DESCRIPTION
      "Path: swPort.performance.vlan.outPriorityQueues.h2Performance.cirTxOctets

       64 bit unsigned wrappable counter."
   ::= {pr1646v2EthPortSwFVlanOutPQsH2PerformanceEntry 167772160}

pr1646v2EthPortSwFVlanOutPQsH2PerformanceEirTxOcts OBJECT-TYPE
   SYNTAX      Counter64
   MAX-ACCESS  read-only
   STATUS      current
   DESCRIPTION
      "Path: swPort.performance.vlan.outPriorityQueues.h2Performance.eirTxOctets

       64 bit unsigned wrappable counter."
   ::= {pr1646v2EthPortSwFVlanOutPQsH2PerformanceEntry 184549376}

pr1646v2EthPortSwFVlanOutPQsH2PerformanceViolTxOcts OBJECT-TYPE
   SYNTAX      Counter64
   MAX-ACCESS  read-only
   STATUS      current
   DESCRIPTION
      "Path: swPort.performance.vlan.outPriorityQueues.h2Performance.violateTxOctets

       64 bit unsigned wrappable counter."
   ::= {pr1646v2EthPortSwFVlanOutPQsH2PerformanceEntry 318767104}

pr1646v2EthPortSwFVlanOutPQsH2PerformanceBandwidth OBJECT-TYPE
   SYNTAX      Integer32
   MAX-ACCESS  read-only
   STATUS      current
   DESCRIPTION
      "Path: swPort.performance.vlan.outPriorityQueues.h2Performance.bandwidth

       unit name = bps
       formula = 8 * ; 8 /"
   ::= {pr1646v2EthPortSwFVlanOutPQsH2PerformanceEntry 268435456}

pr1646v2EthPortSwFVlanOutPQsH24Performance OBJECT-TYPE
   SYNTAX      SEQUENCE OF Pr1646v2EthPortSwFVlanOutPQsH24PerformanceEntry
   MAX-ACCESS  not-accessible
   STATUS      current
   DESCRIPTION
      ""
   ::= {pr1646v2EthPortSwFVlan 84279296}

pr1646v2EthPortSwFVlanOutPQsH24PerformanceEntry OBJECT-TYPE
   SYNTAX      Pr1646v2EthPortSwFVlanOutPQsH24PerformanceEntry
   MAX-ACCESS  not-accessible
   STATUS      current
   DESCRIPTION
      ""
   INDEX      { pr1646v2EthPortSwFVlanOutPQsH24PerformanceGlobalIx,
                pr1646v2EthPortSwFVlanTableIx,
                pr1646v2EthPortSwFVlanOutPQsTableIx,
                pr1646v2EthPortSwFVlanOutPQsH24PerformanceTableIx }
   ::= {pr1646v2EthPortSwFVlanOutPQsH24Performance 1}

Pr1646v2EthPortSwFVlanOutPQsH24PerformanceEntry ::=
   SEQUENCE
      {
      pr1646v2EthPortSwFVlanOutPQsH24PerformanceGlobalIx
         GlobalIndex,
      pr1646v2EthPortSwFVlanOutPQsH24PerformanceTableIx
         TableIndex,
      pr1646v2EthPortSwFVlanOutPQsH24PerformanceSysUpTime
         TimeTicks,
      pr1646v2EthPortSwFVlanOutPQsH24PerformanceTotPkts
         Counter64,
      pr1646v2EthPortSwFVlanOutPQsH24PerformanceDirTxPkts
         Counter64,
      pr1646v2EthPortSwFVlanOutPQsH24PerformanceQdPkts
         Counter64,
      pr1646v2EthPortSwFVlanOutPQsH24PerformanceDropPkts
         Counter64,
      pr1646v2EthPortSwFVlanOutPQsH24PerformanceRDropPkts
         Counter64,
      pr1646v2EthPortSwFVlanOutPQsH24PerformanceCirTxPkts
         Counter64,
      pr1646v2EthPortSwFVlanOutPQsH24PerformanceEirTxPkts
         Counter64,
      pr1646v2EthPortSwFVlanOutPQsH24PerformanceViolTxPkts
         Counter64,
      pr1646v2EthPortSwFVlanOutPQsH24PerformanceTotOcts
         Counter64,
      pr1646v2EthPortSwFVlanOutPQsH24PerformanceDirTxOcts
         Counter64,
      pr1646v2EthPortSwFVlanOutPQsH24PerformanceQdOcts
         Counter64,
      pr1646v2EthPortSwFVlanOutPQsH24PerformanceDropOcts
         Counter64,
      pr1646v2EthPortSwFVlanOutPQsH24PerformanceRDropOcts
         Counter64,
      pr1646v2EthPortSwFVlanOutPQsH24PerformanceCirTxOcts
         Counter64,
      pr1646v2EthPortSwFVlanOutPQsH24PerformanceEirTxOcts
         Counter64,
      pr1646v2EthPortSwFVlanOutPQsH24PerformanceViolTxOcts
         Counter64,
      pr1646v2EthPortSwFVlanOutPQsH24PerformanceBandwidth
         Integer32
      }

pr1646v2EthPortSwFVlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanOutPQsH24PerformanceEntry 10}

pr1646v2EthPortSwFVlanOutPQsH24PerformanceTableIx OBJECT-TYPE
   SYNTAX      TableIndex
   MAX-ACCESS  not-accessible
   STATUS      current
   DESCRIPTION
      ""
   ::= {pr1646v2EthPortSwFVlanOutPQsH24PerformanceEntry 11}

pr1646v2EthPortSwFVlanOutPQsH24PerformanceSysUpTime OBJECT-TYPE
   SYNTAX      TimeTicks
   MAX-ACCESS  read-only
   STATUS      current
   DESCRIPTION
      "Path: swPort.performance.vlan.outPriorityQueues.h24Performance.sysUpTime

       Time in centi-second."
   ::= {pr1646v2EthPortSwFVlanOutPQsH24PerformanceEntry 16777216}

pr1646v2EthPortSwFVlanOutPQsH24PerformanceTotPkts OBJECT-TYPE
   SYNTAX      Counter64
   MAX-ACCESS  read-only
   STATUS      current
   DESCRIPTION
      "Path: swPort.performance.vlan.outPriorityQueues.h24Performance.totalPkts

       64 bit unsigned wrappable counter."
   ::= {pr1646v2EthPortSwFVlanOutPQsH24PerformanceEntry 234881024}

pr1646v2EthPortSwFVlanOutPQsH24PerformanceDirTxPkts OBJECT-TYPE
   SYNTAX      Counter64
   MAX-ACCESS  read-only
   STATUS      current
   DESCRIPTION
      "Path: swPort.performance.vlan.outPriorityQueues.h24Performance.directTxPkts

       64 bit unsigned wrappable counter."
   ::= {pr1646v2EthPortSwFVlanOutPQsH24PerformanceEntry 33554432}

pr1646v2EthPortSwFVlanOutPQsH24PerformanceQdPkts OBJECT-TYPE
   SYNTAX      Counter64
   MAX-ACCESS  read-only
   STATUS      current
   DESCRIPTION
      "Path: swPort.performance.vlan.outPriorityQueues.h24Performance.queuedPkts

       64 bit unsigned wrappable counter."
   ::= {pr1646v2EthPortSwFVlanOutPQsH24PerformanceEntry 50331648}

pr1646v2EthPortSwFVlanOutPQsH24PerformanceDropPkts OBJECT-TYPE
   SYNTAX      Counter64
   MAX-ACCESS  read-only
   STATUS      current
   DESCRIPTION
      "Path: swPort.performance.vlan.outPriorityQueues.h24Performance.droppedPkts

       64 bit unsigned wrappable counter."
   ::= {pr1646v2EthPortSwFVlanOutPQsH24PerformanceEntry 67108864}

pr1646v2EthPortSwFVlanOutPQsH24PerformanceRDropPkts OBJECT-TYPE
   SYNTAX      Counter64
   MAX-ACCESS  read-only
   STATUS      current
   DESCRIPTION
      "Path: swPort.performance.vlan.outPriorityQueues.h24Performance.redDroppedPkts

       64 bit unsigned wrappable counter."
   ::= {pr1646v2EthPortSwFVlanOutPQsH24PerformanceEntry 201326592}

pr1646v2EthPortSwFVlanOutPQsH24PerformanceCirTxPkts OBJECT-TYPE
   SYNTAX      Counter64
   MAX-ACCESS  read-only
   STATUS      current
   DESCRIPTION
      "Path: swPort.performance.vlan.outPriorityQueues.h24Performance.cirTxPkts

       64 bit unsigned wrappable counter."
   ::= {pr1646v2EthPortSwFVlanOutPQsH24PerformanceEntry 83886080}

pr1646v2EthPortSwFVlanOutPQsH24PerformanceEirTxPkts OBJECT-TYPE
   SYNTAX      Counter64
   MAX-ACCESS  read-only
   STATUS      current
   DESCRIPTION
      "Path: swPort.performance.vlan.outPriorityQueues.h24Performance.eirTxPkts

       64 bit unsigned wrappable counter."
   ::= {pr1646v2EthPortSwFVlanOutPQsH24PerformanceEntry 100663296}

pr1646v2EthPortSwFVlanOutPQsH24PerformanceViolTxPkts OBJECT-TYPE
   SYNTAX      Counter64
   MAX-ACCESS  read-only
   STATUS      current
   DESCRIPTION
      "Path: swPort.performance.vlan.outPriorityQueues.h24Performance.violateTxPkts

       64 bit unsigned wrappable counter."
   ::= {pr1646v2EthPortSwFVlanOutPQsH24PerformanceEntry 301989888}

pr1646v2EthPortSwFVlanOutPQsH24PerformanceTotOcts OBJECT-TYPE
   SYNTAX      Counter64
   MAX-ACCESS  read-only
   STATUS      current
   DESCRIPTION
      "Path: swPort.performance.vlan.outPriorityQueues.h24Performance.totalOctets

       64 bit unsigned wrappable counter."
   ::= {pr1646v2EthPortSwFVlanOutPQsH24PerformanceEntry 251658240}

pr1646v2EthPortSwFVlanOutPQsH24PerformanceDirTxOcts OBJECT-TYPE
   SYNTAX      Counter64
   MAX-ACCESS  read-only
   STATUS      current
   DESCRIPTION
      "Path: swPort.performance.vlan.outPriorityQueues.h24Performance.directTxOctets

       64 bit unsigned wrappable counter."
   ::= {pr1646v2EthPortSwFVlanOutPQsH24PerformanceEntry 117440512}

pr1646v2EthPortSwFVlanOutPQsH24PerformanceQdOcts OBJECT-TYPE
   SYNTAX      Counter64
   MAX-ACCESS  read-only
   STATUS      current
   DESCRIPTION
      "Path: swPort.performance.vlan.outPriorityQueues.h24Performance.queuedOctets

       64 bit unsigned wrappable counter."
   ::= {pr1646v2EthPortSwFVlanOutPQsH24PerformanceEntry 134217728}

pr1646v2EthPortSwFVlanOutPQsH24PerformanceDropOcts OBJECT-TYPE
   SYNTAX      Counter64
   MAX-ACCESS  read-only
   STATUS      current
   DESCRIPTION
      "Path: swPort.performance.vlan.outPriorityQueues.h24Performance.droppedOctets

       64 bit unsigned wrappable counter."
   ::= {pr1646v2EthPortSwFVlanOutPQsH24PerformanceEntry 150994944}

pr1646v2EthPortSwFVlanOutPQsH24PerformanceRDropOcts OBJECT-TYPE
   SYNTAX      Counter64
   MAX-ACCESS  read-only
   STATUS      current
   DESCRIPTION
      "Path: swPort.performance.vlan.outPriorityQueues.h24Performance.redDroppedOctets

       64 bit unsigned wrappable counter."
   ::= {pr1646v2EthPortSwFVlanOutPQsH24PerformanceEntry 218103808}

pr1646v2EthPortSwFVlanOutPQsH24PerformanceCirTxOcts OBJECT-TYPE
   SYNTAX      Counter64
   MAX-ACCESS  read-only
   STATUS      current
   DESCRIPTION
      "Path: swPort.performance.vlan.outPriorityQueues.h24Performance.cirTxOctets

       64 bit unsigned wrappable counter."
   ::= {pr1646v2EthPortSwFVlanOutPQsH24PerformanceEntry 167772160}

pr1646v2EthPortSwFVlanOutPQsH24PerformanceEirTxOcts OBJECT-TYPE
   SYNTAX      Counter64
   MAX-ACCESS  read-only
   STATUS      current
   DESCRIPTION
      "Path: swPort.performance.vlan.outPriorityQueues.h24Performance.eirTxOctets

       64 bit unsigned wrappable counter."
   ::= {pr1646v2EthPortSwFVlanOutPQsH24PerformanceEntry 184549376}

pr1646v2EthPortSwFVlanOutPQsH24PerformanceViolTxOcts OBJECT-TYPE
   SYNTAX      Counter64
   MAX-ACCESS  read-only
   STATUS      current
   DESCRIPTION
      "Path: swPort.performance.vlan.outPriorityQueues.h24Performance.violateTxOctets

       64 bit unsigned wrappable counter."
   ::= {pr1646v2EthPortSwFVlanOutPQsH24PerformanceEntry 318767104}

pr1646v2EthPortSwFVlanOutPQsH24PerformanceBandwidth OBJECT-TYPE
   SYNTAX      Integer32
   MAX-ACCESS  read-only
   STATUS      current
   DESCRIPTION
      "Path: swPort.performance.vlan.outPriorityQueues.h24Performance.bandwidth

       unit name = bps
       formula = 8 * ; 8 /"
   ::= {pr1646v2EthPortSwFVlanOutPQsH24PerformanceEntry 268435456}

pr1646v2EthPortSwFVlanOutPQsD7Performance OBJECT-TYPE
   SYNTAX      SEQUENCE OF Pr1646v2EthPortSwFVlanOutPQsD7PerformanceEntry
   MAX-ACCESS  not-accessible
   STATUS      current
   DESCRIPTION
      ""
   ::= {pr1646v2EthPortSwFVlan 84344832}

pr1646v2EthPortSwFVlanOutPQsD7PerformanceEntry OBJECT-TYPE
   SYNTAX      Pr1646v2EthPortSwFVlanOutPQsD7PerformanceEntry
   MAX-ACCESS  not-accessible
   STATUS      current
   DESCRIPTION
      ""
   INDEX      { pr1646v2EthPortSwFVlanOutPQsD7PerformanceGlobalIx,
                pr1646v2EthPortSwFVlanTableIx,
                pr1646v2EthPortSwFVlanOutPQsTableIx,
                pr1646v2EthPortSwFVlanOutPQsD7PerformanceTableIx }
   ::= {pr1646v2EthPortSwFVlanOutPQsD7Performance 1}

Pr1646v2EthPortSwFVlanOutPQsD7PerformanceEntry ::=
   SEQUENCE
      {
      pr1646v2EthPortSwFVlanOutPQsD7PerformanceGlobalIx
         GlobalIndex,
      pr1646v2EthPortSwFVlanOutPQsD7PerformanceTableIx
         TableIndex,
      pr1646v2EthPortSwFVlanOutPQsD7PerformanceSysUpTime
         TimeTicks,
      pr1646v2EthPortSwFVlanOutPQsD7PerformanceTotPkts
         Counter64,
      pr1646v2EthPortSwFVlanOutPQsD7PerformanceDirTxPkts
         Counter64,
      pr1646v2EthPortSwFVlanOutPQsD7PerformanceQdPkts
         Counter64,
      pr1646v2EthPortSwFVlanOutPQsD7PerformanceDropPkts
         Counter64,
      pr1646v2EthPortSwFVlanOutPQsD7PerformanceRDropPkts
         Counter64,
      pr1646v2EthPortSwFVlanOutPQsD7PerformanceCirTxPkts
         Counter64,
      pr1646v2EthPortSwFVlanOutPQsD7PerformanceEirTxPkts
         Counter64,
      pr1646v2EthPortSwFVlanOutPQsD7PerformanceViolTxPkts
         Counter64,
      pr1646v2EthPortSwFVlanOutPQsD7PerformanceTotOcts
         Counter64,
      pr1646v2EthPortSwFVlanOutPQsD7PerformanceDirTxOcts
         Counter64,
      pr1646v2EthPortSwFVlanOutPQsD7PerformanceQdOcts
         Counter64,
      pr1646v2EthPortSwFVlanOutPQsD7PerformanceDropOcts
         Counter64,
      pr1646v2EthPortSwFVlanOutPQsD7PerformanceRDropOcts
         Counter64,
      pr1646v2EthPortSwFVlanOutPQsD7PerformanceCirTxOcts
         Counter64,
      pr1646v2EthPortSwFVlanOutPQsD7PerformanceEirTxOcts
         Counter64,
      pr1646v2EthPortSwFVlanOutPQsD7PerformanceViolTxOcts
         Counter64,
      pr1646v2EthPortSwFVlanOutPQsD7PerformanceBandwidth
         Integer32
      }

pr1646v2EthPortSwFVlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwFVlanOutPQsD7PerformanceEntry 10}

pr1646v2EthPortSwFVlanOutPQsD7PerformanceTableIx OBJECT-TYPE
   SYNTAX      TableIndex
   MAX-ACCESS  not-accessible
   STATUS      current
   DESCRIPTION
      ""
   ::= {pr1646v2EthPortSwFVlanOutPQsD7PerformanceEntry 11}

pr1646v2EthPortSwFVlanOutPQsD7PerformanceSysUpTime OBJECT-TYPE
   SYNTAX      TimeTicks
   MAX-ACCESS  read-only
   STATUS      current
   DESCRIPTION
      "Path: swPort.performance.vlan.outPriorityQueues.d7Performance.sysUpTime

       Time in centi-second."
   ::= {pr1646v2EthPortSwFVlanOutPQsD7PerformanceEntry 16777216}

pr1646v2EthPortSwFVlanOutPQsD7PerformanceTotPkts OBJECT-TYPE
   SYNTAX      Counter64
   MAX-ACCESS  read-only
   STATUS      current
   DESCRIPTION
      "Path: swPort.performance.vlan.outPriorityQueues.d7Performance.totalPkts

       64 bit unsigned wrappable counter."
   ::= {pr1646v2EthPortSwFVlanOutPQsD7PerformanceEntry 234881024}

pr1646v2EthPortSwFVlanOutPQsD7PerformanceDirTxPkts OBJECT-TYPE
   SYNTAX      Counter64
   MAX-ACCESS  read-only
   STATUS      current
   DESCRIPTION
      "Path: swPort.performance.vlan.outPriorityQueues.d7Performance.directTxPkts

       64 bit unsigned wrappable counter."
   ::= {pr1646v2EthPortSwFVlanOutPQsD7PerformanceEntry 33554432}

pr1646v2EthPortSwFVlanOutPQsD7PerformanceQdPkts OBJECT-TYPE
   SYNTAX      Counter64
   MAX-ACCESS  read-only
   STATUS      current
   DESCRIPTION
      "Path: swPort.performance.vlan.outPriorityQueues.d7Performance.queuedPkts

       64 bit unsigned wrappable counter."
   ::= {pr1646v2EthPortSwFVlanOutPQsD7PerformanceEntry 50331648}

pr1646v2EthPortSwFVlanOutPQsD7PerformanceDropPkts OBJECT-TYPE
   SYNTAX      Counter64
   MAX-ACCESS  read-only
   STATUS      current
   DESCRIPTION
      "Path: swPort.performance.vlan.outPriorityQueues.d7Performance.droppedPkts

       64 bit unsigned wrappable counter."
   ::= {pr1646v2EthPortSwFVlanOutPQsD7PerformanceEntry 67108864}

pr1646v2EthPortSwFVlanOutPQsD7PerformanceRDropPkts OBJECT-TYPE
   SYNTAX      Counter64
   MAX-ACCESS  read-only
   STATUS      current
   DESCRIPTION
      "Path: swPort.performance.vlan.outPriorityQueues.d7Performance.redDroppedPkts

       64 bit unsigned wrappable counter."
   ::= {pr1646v2EthPortSwFVlanOutPQsD7PerformanceEntry 201326592}

pr1646v2EthPortSwFVlanOutPQsD7PerformanceCirTxPkts OBJECT-TYPE
   SYNTAX      Counter64
   MAX-ACCESS  read-only
   STATUS      current
   DESCRIPTION
      "Path: swPort.performance.vlan.outPriorityQueues.d7Performance.cirTxPkts

       64 bit unsigned wrappable counter."
   ::= {pr1646v2EthPortSwFVlanOutPQsD7PerformanceEntry 83886080}

pr1646v2EthPortSwFVlanOutPQsD7PerformanceEirTxPkts OBJECT-TYPE
   SYNTAX      Counter64
   MAX-ACCESS  read-only
   STATUS      current
   DESCRIPTION
      "Path: swPort.performance.vlan.outPriorityQueues.d7Performance.eirTxPkts

       64 bit unsigned wrappable counter."
   ::= {pr1646v2EthPortSwFVlanOutPQsD7PerformanceEntry 100663296}

pr1646v2EthPortSwFVlanOutPQsD7PerformanceViolTxPkts OBJECT-TYPE
   SYNTAX      Counter64
   MAX-ACCESS  read-only
   STATUS      current
   DESCRIPTION
      "Path: swPort.performance.vlan.outPriorityQueues.d7Performance.violateTxPkts

       64 bit unsigned wrappable counter."
   ::= {pr1646v2EthPortSwFVlanOutPQsD7PerformanceEntry 301989888}

pr1646v2EthPortSwFVlanOutPQsD7PerformanceTotOcts OBJECT-TYPE
   SYNTAX      Counter64
   MAX-ACCESS  read-only
   STATUS      current
   DESCRIPTION
      "Path: swPort.performance.vlan.outPriorityQueues.d7Performance.totalOctets

       64 bit unsigned wrappable counter."
   ::= {pr1646v2EthPortSwFVlanOutPQsD7PerformanceEntry 251658240}

pr1646v2EthPortSwFVlanOutPQsD7PerformanceDirTxOcts OBJECT-TYPE
   SYNTAX      Counter64
   MAX-ACCESS  read-only
   STATUS      current
   DESCRIPTION
      "Path: swPort.performance.vlan.outPriorityQueues.d7Performance.directTxOctets

       64 bit unsigned wrappable counter."
   ::= {pr1646v2EthPortSwFVlanOutPQsD7PerformanceEntry 117440512}

pr1646v2EthPortSwFVlanOutPQsD7PerformanceQdOcts OBJECT-TYPE
   SYNTAX      Counter64
   MAX-ACCESS  read-only
   STATUS      current
   DESCRIPTION
      "Path: swPort.performance.vlan.outPriorityQueues.d7Performance.queuedOctets

       64 bit unsigned wrappable counter."
   ::= {pr1646v2EthPortSwFVlanOutPQsD7PerformanceEntry 134217728}

pr1646v2EthPortSwFVlanOutPQsD7PerformanceDropOcts OBJECT-TYPE
   SYNTAX      Counter64
   MAX-ACCESS  read-only
   STATUS      current
   DESCRIPTION
      "Path: swPort.performance.vlan.outPriorityQueues.d7Performance.droppedOctets

       64 bit unsigned wrappable counter."
   ::= {pr1646v2EthPortSwFVlanOutPQsD7PerformanceEntry 150994944}

pr1646v2EthPortSwFVlanOutPQsD7PerformanceRDropOcts OBJECT-TYPE
   SYNTAX      Counter64
   MAX-ACCESS  read-only
   STATUS      current
   DESCRIPTION
      "Path: swPort.performance.vlan.outPriorityQueues.d7Performance.redDroppedOctets

       64 bit unsigned wrappable counter."
   ::= {pr1646v2EthPortSwFVlanOutPQsD7PerformanceEntry 218103808}

pr1646v2EthPortSwFVlanOutPQsD7PerformanceCirTxOcts OBJECT-TYPE
   SYNTAX      Counter64
   MAX-ACCESS  read-only
   STATUS      current
   DESCRIPTION
      "Path: swPort.performance.vlan.outPriorityQueues.d7Performance.cirTxOctets

       64 bit unsigned wrappable counter."
   ::= {pr1646v2EthPortSwFVlanOutPQsD7PerformanceEntry 167772160}

pr1646v2EthPortSwFVlanOutPQsD7PerformanceEirTxOcts OBJECT-TYPE
   SYNTAX      Counter64
   MAX-ACCESS  read-only
   STATUS      current
   DESCRIPTION
      "Path: swPort.performance.vlan.outPriorityQueues.d7Performance.eirTxOctets

       64 bit unsigned wrappable counter."
   ::= {pr1646v2EthPortSwFVlanOutPQsD7PerformanceEntry 184549376}

pr1646v2EthPortSwFVlanOutPQsD7PerformanceViolTxOcts OBJECT-TYPE
   SYNTAX      Counter64
   MAX-ACCESS  read-only
   STATUS      current
   DESCRIPTION
      "Path: swPort.performance.vlan.outPriorityQueues.d7Performance.violateTxOctets

       64 bit unsigned wrappable counter."
   ::= {pr1646v2EthPortSwFVlanOutPQsD7PerformanceEntry 318767104}

pr1646v2EthPortSwFVlanOutPQsD7PerformanceBandwidth OBJECT-TYPE
   SYNTAX      Integer32
   MAX-ACCESS  read-only
   STATUS      current
   DESCRIPTION
      "Path: swPort.performance.vlan.outPriorityQueues.d7Performance.bandwidth

       unit name = bps
       formula = 8 * ; 8 /"
   ::= {pr1646v2EthPortSwFVlanOutPQsD7PerformanceEntry 268435456}


pr1646v2EthPortSwFPPPoE OBJECT IDENTIFIER ::= {pr1646v2EthPortSwF 53}

pr1646v2EthPortSwFPPPoESSCTable OBJECT-TYPE
   SYNTAX      SEQUENCE OF Pr1646v2EthPortSwFPPPoEEntry
   MAX-ACCESS  not-accessible
   STATUS      current
   DESCRIPTION
      ""
   ::= {pr1646v2EthPortSwFPPPoE 1}

pr1646v2EthPortSwFPPPoEEntry OBJECT-TYPE
   SYNTAX      Pr1646v2EthPortSwFPPPoEEntry
   MAX-ACCESS  not-accessible
   STATUS      current
   DESCRIPTION
      ""
   INDEX      { pr1646v2EthPortSwFPPPoEGlobalIx,
                pr1646v2EthPortSwFPPPoETableIx }
   ::= {pr1646v2EthPortSwFPPPoESSCTable 1}

Pr1646v2EthPortSwFPPPoEEntry ::=
   SEQUENCE
      {
      pr1646v2EthPortSwFPPPoEGlobalIx
         GlobalIndex,
      pr1646v2EthPortSwFPPPoETableIx
         TableIndex,
      pr1646v2EthPortSwFPPPoEName
         DisplayString,
      pr1646v2EthPortSwFPPPoEMCInOctets
         Counter64,
      pr1646v2EthPortSwFPPPoEMCInUcast
         Counter64,
      pr1646v2EthPortSwFPPPoEMCInNUcastPkts
         Counter64,
      pr1646v2EthPortSwFPPPoEMCInBcastPkts
         Counter64,
      pr1646v2EthPortSwFPPPoEMCInMcastPkts
         Counter64,
      pr1646v2EthPortSwFPPPoEMCInDiscards
         Counter64,
      pr1646v2EthPortSwFPPPoEMCInErrors
         Counter64,
      pr1646v2EthPortSwFPPPoEMCInUnknownProtos
         Counter64,
      pr1646v2EthPortSwFPPPoEMCInDropEx
         Counter64,
      pr1646v2EthPortSwFPPPoEMCInDropNoMac
         Counter64,
      pr1646v2EthPortSwFPPPoEMCInDropNUCast
         Counter64,
      pr1646v2EthPortSwFPPPoEMCInDropFilter
         Counter64,
      pr1646v2EthPortSwFPPPoEMCInBandwidth15sec
         Integer32,
      pr1646v2EthPortSwFPPPoEMCInBandwidth30sec
         Integer32,
      pr1646v2EthPortSwFPPPoEMCInBandwidth1min
         Integer32,
      pr1646v2EthPortSwFPPPoEMCInBandwidth2min
         Integer32,
      pr1646v2EthPortSwFPPPoEMCInBandwidth5min
         Integer32,
      pr1646v2EthPortSwFPPPoEMCOutOctets
         Counter64,
      pr1646v2EthPortSwFPPPoEMCOutUcastPkts
         Counter64,
      pr1646v2EthPortSwFPPPoEMCOutNUcastPkts
         Counter64,
      pr1646v2EthPortSwFPPPoEMCOutBcastPkts
         Counter64,
      pr1646v2EthPortSwFPPPoEMCOutMcastPkts
         Counter64,
      pr1646v2EthPortSwFPPPoEMCOutDiscards
         Counter64,
      pr1646v2EthPortSwFPPPoEMCOutErrors
         Counter64,
      pr1646v2EthPortSwFPPPoEMCOutQLen
         Counter32,
      pr1646v2EthPortSwFPPPoEMCOutDropEx
         Counter64,
      pr1646v2EthPortSwFPPPoEMCOutDropNoArp
         Counter64,
      pr1646v2EthPortSwFPPPoEMCOutDropFilter
         Counter64,
      pr1646v2EthPortSwFPPPoEMCOutBandwidth15sec
         Integer32,
      pr1646v2EthPortSwFPPPoEMCOutBandwidth30sec
         Integer32,
      pr1646v2EthPortSwFPPPoEMCOutBandwidth1min
         Integer32,
      pr1646v2EthPortSwFPPPoEMCOutBandwidth2min
         Integer32,
      pr1646v2EthPortSwFPPPoEMCOutBandwidth5min
         Integer32,
      pr1646v2EthPortSwFPPPoEPppLinkMonitoringRequestsSent
         Gauge32,
      pr1646v2EthPortSwFPPPoEPppLinkMonitoringRepliesRcvd
         Gauge32,
      pr1646v2EthPortSwFPPPoEPppLinkMonitoringRequestsRcvd
         Gauge32,
      pr1646v2EthPortSwFPPPoEPppLinkMonitoringRepliesSent
         Gauge32
      }

pr1646v2EthPortSwFPPPoEGlobalIx OBJECT-TYPE
   SYNTAX      GlobalIndex
   MAX-ACCESS  not-accessible
   STATUS      current
   DESCRIPTION
      "The value of the tlsCntTreeGlobalIndex of the MANAGED OBJECT."
   ::= {pr1646v2EthPortSwFPPPoEEntry 10}

pr1646v2EthPortSwFPPPoETableIx OBJECT-TYPE
   SYNTAX      TableIndex
   MAX-ACCESS  not-accessible
   STATUS      current
   DESCRIPTION
      ""
   ::= {pr1646v2EthPortSwFPPPoEEntry 11}

pr1646v2EthPortSwFPPPoEName OBJECT-TYPE
   SYNTAX      DisplayString
   MAX-ACCESS  read-only
   STATUS      current
   DESCRIPTION
      "Path: swPort.performance.pppoEClient.name"
   ::= {pr1646v2EthPortSwFPPPoEEntry 16777216}

pr1646v2EthPortSwFPPPoEMCInOctets OBJECT-TYPE
   SYNTAX      Counter64
   MAX-ACCESS  read-only
   STATUS      current
   DESCRIPTION
      "Path: swPort.performance.pppoEClient.mibCounters.ifInOctets

       64 bit unsigned wrappable counter."
   ::= {pr1646v2EthPortSwFPPPoEEntry 40697856}

pr1646v2EthPortSwFPPPoEMCInUcast OBJECT-TYPE
   SYNTAX      Counter64
   MAX-ACCESS  read-only
   STATUS      current
   DESCRIPTION
      "Path: swPort.performance.pppoEClient.mibCounters.ifInUcastPkts

       64 bit unsigned wrappable counter."
   ::= {pr1646v2EthPortSwFPPPoEEntry 40763392}

pr1646v2EthPortSwFPPPoEMCInNUcastPkts OBJECT-TYPE
   SYNTAX      Counter64
   MAX-ACCESS  read-only
   STATUS      current
   DESCRIPTION
      "Path: swPort.performance.pppoEClient.mibCounters.ifInNUcastPkts

       64 bit unsigned wrappable counter."
   ::= {pr1646v2EthPortSwFPPPoEEntry 40828928}

pr1646v2EthPortSwFPPPoEMCInBcastPkts OBJECT-TYPE
   SYNTAX      Counter64
   MAX-ACCESS  read-only
   STATUS      current
   DESCRIPTION
      "Path: swPort.performance.pppoEClient.mibCounters.ifInBcastPkts

       64 bit unsigned wrappable counter."
   ::= {pr1646v2EthPortSwFPPPoEEntry 47382528}

pr1646v2EthPortSwFPPPoEMCInMcastPkts OBJECT-TYPE
   SYNTAX      Counter64
   MAX-ACCESS  read-only
   STATUS      current
   DESCRIPTION
      "Path: swPort.performance.pppoEClient.mibCounters.ifInMcastPkts

       64 bit unsigned wrappable counter."
   ::= {pr1646v2EthPortSwFPPPoEEntry 48037888}

pr1646v2EthPortSwFPPPoEMCInDiscards OBJECT-TYPE
   SYNTAX      Counter64
   MAX-ACCESS  read-only
   STATUS      current
   DESCRIPTION
      "Path: swPort.performance.pppoEClient.mibCounters.ifInDiscards

       64 bit unsigned wrappable counter."
   ::= {pr1646v2EthPortSwFPPPoEEntry 40894464}

pr1646v2EthPortSwFPPPoEMCInErrors OBJECT-TYPE
   SYNTAX      Counter64
   MAX-ACCESS  read-only
   STATUS      current
   DESCRIPTION
      "Path: swPort.performance.pppoEClient.mibCounters.ifInErrors

       64 bit unsigned wrappable counter."
   ::= {pr1646v2EthPortSwFPPPoEEntry 40960000}

pr1646v2EthPortSwFPPPoEMCInUnknownProtos OBJECT-TYPE
   SYNTAX      Counter64
   MAX-ACCESS  read-only
   STATUS      current
   DESCRIPTION
      "Path: swPort.performance.pppoEClient.mibCounters.ifInUnknownProtos

       64 bit unsigned wrappable counter."
   ::= {pr1646v2EthPortSwFPPPoEEntry 41025536}

pr1646v2EthPortSwFPPPoEMCInDropEx OBJECT-TYPE
   SYNTAX      Counter64
   MAX-ACCESS  read-only
   STATUS      current
   DESCRIPTION
      "Path: swPort.performance.pppoEClient.mibCounters.ifInDropLevelExceeded

       64 bit unsigned wrappable counter."
   ::= {pr1646v2EthPortSwFPPPoEEntry 42074112}

pr1646v2EthPortSwFPPPoEMCInDropNoMac OBJECT-TYPE
   SYNTAX      Counter64
   MAX-ACCESS  read-only
   STATUS      current
   DESCRIPTION
      "Path: swPort.performance.pppoEClient.mibCounters.ifInDiscardsNoMacFit

       64 bit unsigned wrappable counter."
   ::= {pr1646v2EthPortSwFPPPoEEntry 42270720}

pr1646v2EthPortSwFPPPoEMCInDropNUCast OBJECT-TYPE
   SYNTAX      Counter64
   MAX-ACCESS  read-only
   STATUS      current
   DESCRIPTION
      "Path: swPort.performance.pppoEClient.mibCounters.ifInDiscardsNUCast

       64 bit unsigned wrappable counter."
   ::= {pr1646v2EthPortSwFPPPoEEntry 42467328}

pr1646v2EthPortSwFPPPoEMCInDropFilter OBJECT-TYPE
   SYNTAX      Counter64
   MAX-ACCESS  read-only
   STATUS      current
   DESCRIPTION
      "Path: swPort.performance.pppoEClient.mibCounters.ifInDiscardsFilter

       64 bit unsigned wrappable counter."
   ::= {pr1646v2EthPortSwFPPPoEEntry 42532864}

pr1646v2EthPortSwFPPPoEMCInBandwidth15sec OBJECT-TYPE
   SYNTAX      Integer32
   MAX-ACCESS  read-only
   STATUS      current
   DESCRIPTION
      "Path: swPort.performance.pppoEClient.mibCounters.ifInBandwidth.15sec

       unit name = bps
       formula = 8 * ; 8 /"
   ::= {pr1646v2EthPortSwFPPPoEEntry 45417728}

pr1646v2EthPortSwFPPPoEMCInBandwidth30sec OBJECT-TYPE
   SYNTAX      Integer32
   MAX-ACCESS  read-only
   STATUS      current
   DESCRIPTION
      "Path: swPort.performance.pppoEClient.mibCounters.ifInBandwidth.30sec

       unit name = bps
       formula = 8 * ; 8 /"
   ::= {pr1646v2EthPortSwFPPPoEEntry 45419008}

pr1646v2EthPortSwFPPPoEMCInBandwidth1min OBJECT-TYPE
   SYNTAX      Integer32
   MAX-ACCESS  read-only
   STATUS      current
   DESCRIPTION
      "Path: swPort.performance.pppoEClient.mibCounters.ifInBandwidth.1min

       unit name = bps
       formula = 8 * ; 8 /"
   ::= {pr1646v2EthPortSwFPPPoEEntry 45421568}

pr1646v2EthPortSwFPPPoEMCInBandwidth2min OBJECT-TYPE
   SYNTAX      Integer32
   MAX-ACCESS  read-only
   STATUS      current
   DESCRIPTION
      "Path: swPort.performance.pppoEClient.mibCounters.ifInBandwidth.2min

       unit name = bps
       formula = 8 * ; 8 /"
   ::= {pr1646v2EthPortSwFPPPoEEntry 45426688}

pr1646v2EthPortSwFPPPoEMCInBandwidth5min OBJECT-TYPE
   SYNTAX      Integer32
   MAX-ACCESS  read-only
   STATUS      current
   DESCRIPTION
      "Path: swPort.performance.pppoEClient.mibCounters.ifInBandwidth.5min

       unit name = bps
       formula = 8 * ; 8 /"
   ::= {pr1646v2EthPortSwFPPPoEEntry 45442048}

pr1646v2EthPortSwFPPPoEMCOutOctets OBJECT-TYPE
   SYNTAX      Counter64
   MAX-ACCESS  read-only
   STATUS      current
   DESCRIPTION
      "Path: swPort.performance.pppoEClient.mibCounters.ifOutOctets

       64 bit unsigned wrappable counter."
   ::= {pr1646v2EthPortSwFPPPoEEntry 41091072}

pr1646v2EthPortSwFPPPoEMCOutUcastPkts OBJECT-TYPE
   SYNTAX      Counter64
   MAX-ACCESS  read-only
   STATUS      current
   DESCRIPTION
      "Path: swPort.performance.pppoEClient.mibCounters.ifOutUcastPkts

       64 bit unsigned wrappable counter."
   ::= {pr1646v2EthPortSwFPPPoEEntry 41156608}

pr1646v2EthPortSwFPPPoEMCOutNUcastPkts OBJECT-TYPE
   SYNTAX      Counter64
   MAX-ACCESS  read-only
   STATUS      current
   DESCRIPTION
      "Path: swPort.performance.pppoEClient.mibCounters.ifOutNUcastPkts

       64 bit unsigned wrappable counter."
   ::= {pr1646v2EthPortSwFPPPoEEntry 41222144}

pr1646v2EthPortSwFPPPoEMCOutBcastPkts OBJECT-TYPE
   SYNTAX      Counter64
   MAX-ACCESS  read-only
   STATUS      current
   DESCRIPTION
      "Path: swPort.performance.pppoEClient.mibCounters.ifOutBcastPkts

       64 bit unsigned wrappable counter."
   ::= {pr1646v2EthPortSwFPPPoEEntry 47775744}

pr1646v2EthPortSwFPPPoEMCOutMcastPkts OBJECT-TYPE
   SYNTAX      Counter64
   MAX-ACCESS  read-only
   STATUS      current
   DESCRIPTION
      "Path: swPort.performance.pppoEClient.mibCounters.ifOutMcastPkts

       64 bit unsigned wrappable counter."
   ::= {pr1646v2EthPortSwFPPPoEEntry 48431104}

pr1646v2EthPortSwFPPPoEMCOutDiscards OBJECT-TYPE
   SYNTAX      Counter64
   MAX-ACCESS  read-only
   STATUS      current
   DESCRIPTION
      "Path: swPort.performance.pppoEClient.mibCounters.ifOutDiscards

       64 bit unsigned wrappable counter."
   ::= {pr1646v2EthPortSwFPPPoEEntry 41287680}

pr1646v2EthPortSwFPPPoEMCOutErrors OBJECT-TYPE
   SYNTAX      Counter64
   MAX-ACCESS  read-only
   STATUS      current
   DESCRIPTION
      "Path: swPort.performance.pppoEClient.mibCounters.ifOutErrors

       64 bit unsigned wrappable counter."
   ::= {pr1646v2EthPortSwFPPPoEEntry 41353216}

pr1646v2EthPortSwFPPPoEMCOutQLen OBJECT-TYPE
   SYNTAX      Counter32
   MAX-ACCESS  read-only
   STATUS      current
   DESCRIPTION
      "Path: swPort.performance.pppoEClient.mibCounters.ifOutQLen

       32 bit unsigned wrappable counter."
   ::= {pr1646v2EthPortSwFPPPoEEntry 41418752}

pr1646v2EthPortSwFPPPoEMCOutDropEx OBJECT-TYPE
   SYNTAX      Counter64
   MAX-ACCESS  read-only
   STATUS      current
   DESCRIPTION
      "Path: swPort.performance.pppoEClient.mibCounters.ifOutDropLevelExceeded

       64 bit unsigned wrappable counter."
   ::= {pr1646v2EthPortSwFPPPoEEntry 41484288}

pr1646v2EthPortSwFPPPoEMCOutDropNoArp OBJECT-TYPE
   SYNTAX      Counter64
   MAX-ACCESS  read-only
   STATUS      current
   DESCRIPTION
      "Path: swPort.performance.pppoEClient.mibCounters.ifOutDiscardsNoArp

       64 bit unsigned wrappable counter."
   ::= {pr1646v2EthPortSwFPPPoEEntry 42336256}

pr1646v2EthPortSwFPPPoEMCOutDropFilter OBJECT-TYPE
   SYNTAX      Counter64
   MAX-ACCESS  read-only
   STATUS      current
   DESCRIPTION
      "Path: swPort.performance.pppoEClient.mibCounters.ifOutDiscardsFilter

       64 bit unsigned wrappable counter."
   ::= {pr1646v2EthPortSwFPPPoEEntry 42598400}

pr1646v2EthPortSwFPPPoEMCOutBandwidth15sec OBJECT-TYPE
   SYNTAX      Integer32
   MAX-ACCESS  read-only
   STATUS      current
   DESCRIPTION
      "Path: swPort.performance.pppoEClient.mibCounters.ifOutBandwidth.15sec

       unit name = bps
       formula = 8 * ; 8 /"
   ::= {pr1646v2EthPortSwFPPPoEEntry 45483264}

pr1646v2EthPortSwFPPPoEMCOutBandwidth30sec OBJECT-TYPE
   SYNTAX      Integer32
   MAX-ACCESS  read-only
   STATUS      current
   DESCRIPTION
      "Path: swPort.performance.pppoEClient.mibCounters.ifOutBandwidth.30sec

       unit name = bps
       formula = 8 * ; 8 /"
   ::= {pr1646v2EthPortSwFPPPoEEntry 45484544}

pr1646v2EthPortSwFPPPoEMCOutBandwidth1min OBJECT-TYPE
   SYNTAX      Integer32
   MAX-ACCESS  read-only
   STATUS      current
   DESCRIPTION
      "Path: swPort.performance.pppoEClient.mibCounters.ifOutBandwidth.1min

       unit name = bps
       formula = 8 * ; 8 /"
   ::= {pr1646v2EthPortSwFPPPoEEntry 45487104}

pr1646v2EthPortSwFPPPoEMCOutBandwidth2min OBJECT-TYPE
   SYNTAX      Integer32
   MAX-ACCESS  read-only
   STATUS      current
   DESCRIPTION
      "Path: swPort.performance.pppoEClient.mibCounters.ifOutBandwidth.2min

       unit name = bps
       formula = 8 * ; 8 /"
   ::= {pr1646v2EthPortSwFPPPoEEntry 45492224}

pr1646v2EthPortSwFPPPoEMCOutBandwidth5min OBJECT-TYPE
   SYNTAX      Integer32
   MAX-ACCESS  read-only
   STATUS      current
   DESCRIPTION
      "Path: swPort.performance.pppoEClient.mibCounters.ifOutBandwidth.5min

       unit name = bps
       formula = 8 * ; 8 /"
   ::= {pr1646v2EthPortSwFPPPoEEntry 45507584}

pr1646v2EthPortSwFPPPoEPppLinkMonitoringRequestsSent OBJECT-TYPE
   SYNTAX      Gauge32
   MAX-ACCESS  read-only
   STATUS      current
   DESCRIPTION
      "Path: swPort.performance.pppoEClient.ppp.linkMonitoring.requestsSent

       32 bit unsigned gauge value."
   ::= {pr1646v2EthPortSwFPPPoEEntry 50397440}

pr1646v2EthPortSwFPPPoEPppLinkMonitoringRepliesRcvd OBJECT-TYPE
   SYNTAX      Gauge32
   MAX-ACCESS  read-only
   STATUS      current
   DESCRIPTION
      "Path: swPort.performance.pppoEClient.ppp.linkMonitoring.repliesRcvd

       32 bit unsigned gauge value."
   ::= {pr1646v2EthPortSwFPPPoEEntry 50397696}

pr1646v2EthPortSwFPPPoEPppLinkMonitoringRequestsRcvd OBJECT-TYPE
   SYNTAX      Gauge32
   MAX-ACCESS  read-only
   STATUS      current
   DESCRIPTION
      "Path: swPort.performance.pppoEClient.ppp.linkMonitoring.requestsRcvd

       32 bit unsigned gauge value."
   ::= {pr1646v2EthPortSwFPPPoEEntry 50397952}

pr1646v2EthPortSwFPPPoEPppLinkMonitoringRepliesSent OBJECT-TYPE
   SYNTAX      Gauge32
   MAX-ACCESS  read-only
   STATUS      current
   DESCRIPTION
      "Path: swPort.performance.pppoEClient.ppp.linkMonitoring.repliesSent

       32 bit unsigned gauge value."
   ::= {pr1646v2EthPortSwFPPPoEEntry 50398208}

pr1646v2EthPortSwFPPPoEMCH2P OBJECT-TYPE
   SYNTAX      SEQUENCE OF Pr1646v2EthPortSwFPPPoEMCH2PEntry
   MAX-ACCESS  not-accessible
   STATUS      current
   DESCRIPTION
      ""
   ::= {pr1646v2EthPortSwFPPPoE 41549824}

pr1646v2EthPortSwFPPPoEMCH2PEntry OBJECT-TYPE
   SYNTAX      Pr1646v2EthPortSwFPPPoEMCH2PEntry
   MAX-ACCESS  not-accessible
   STATUS      current
   DESCRIPTION
      ""
   INDEX      { pr1646v2EthPortSwFPPPoEMCH2PGlobalIx,
                pr1646v2EthPortSwFPPPoETableIx,
                pr1646v2EthPortSwFPPPoEMCH2PTableIx }
   ::= {pr1646v2EthPortSwFPPPoEMCH2P 1}

Pr1646v2EthPortSwFPPPoEMCH2PEntry ::=
   SEQUENCE
      {
      pr1646v2EthPortSwFPPPoEMCH2PGlobalIx
         GlobalIndex,
      pr1646v2EthPortSwFPPPoEMCH2PTableIx
         TableIndex,
      pr1646v2EthPortSwFPPPoEMCH2PSysUpTime
         TimeTicks,
      pr1646v2EthPortSwFPPPoEMCH2PIfUpTime
         TimeTicks,
      pr1646v2EthPortSwFPPPoEMCH2PIfStatChanges
         Counter32,
      pr1646v2EthPortSwFPPPoEMCH2PIfInOctets
         Counter64,
      pr1646v2EthPortSwFPPPoEMCH2PIfInUCPkts
         Counter64,
      pr1646v2EthPortSwFPPPoEMCH2PIfInNUCPkts
         Counter64,
      pr1646v2EthPortSwFPPPoEMCH2PIfInBCPkts
         Counter64,
      pr1646v2EthPortSwFPPPoEMCH2PIfInMCPkts
         Counter64,
      pr1646v2EthPortSwFPPPoEMCH2PIfInDiscards
         Counter64,
      pr1646v2EthPortSwFPPPoEMCH2PIfInErrors
         Counter64,
      pr1646v2EthPortSwFPPPoEMCH2PIfInUnkwn
         Counter64,
      pr1646v2EthPortSwFPPPoEMCH2PInDropEx
         Counter64,
      pr1646v2EthPortSwFPPPoEMCH2PInDropNoMac
         Counter64,
      pr1646v2EthPortSwFPPPoEMCH2PInDropNUCast
         Counter64,
      pr1646v2EthPortSwFPPPoEMCH2PInDropFilter
         Counter64,
      pr1646v2EthPortSwFPPPoEMCH2PIfInBandwidth
         Integer32,
      pr1646v2EthPortSwFPPPoEMCH2PIfOutOctets
         Counter64,
      pr1646v2EthPortSwFPPPoEMCH2PIfOutUCPkts
         Counter64,
      pr1646v2EthPortSwFPPPoEMCH2PIfOutNUCPkts
         Counter64,
      pr1646v2EthPortSwFPPPoEMCH2PIfOutBCPkts
         Counter64,
      pr1646v2EthPortSwFPPPoEMCH2PIfOutMCPkts
         Counter64,
      pr1646v2EthPortSwFPPPoEMCH2PIfOutDiscards
         Counter64,
      pr1646v2EthPortSwFPPPoEMCH2PIfOutErrors
         Counter64,
      pr1646v2EthPortSwFPPPoEMCH2POutDropEx
         Counter64,
      pr1646v2EthPortSwFPPPoEMCH2POutDropNoArp
         Counter64,
      pr1646v2EthPortSwFPPPoEMCH2POutDropFilter
         Counter64,
      pr1646v2EthPortSwFPPPoEMCH2PIfOutBandwidth
         Integer32,
      pr1646v2EthPortSwFPPPoEMCH2PIfErrSec
         Counter32
      }

pr1646v2EthPortSwFPPPoEMCH2PGlobalIx OBJECT-TYPE
   SYNTAX      GlobalIndex
   MAX-ACCESS  not-accessible
   STATUS      current
   DESCRIPTION
      "The value of the tlsCntTreeGlobalIndex of the MANAGED OBJECT."
   ::= {pr1646v2EthPortSwFPPPoEMCH2PEntry 10}

pr1646v2EthPortSwFPPPoEMCH2PTableIx OBJECT-TYPE
   SYNTAX      TableIndex
   MAX-ACCESS  not-accessible
   STATUS      current
   DESCRIPTION
      ""
   ::= {pr1646v2EthPortSwFPPPoEMCH2PEntry 11}

pr1646v2EthPortSwFPPPoEMCH2PSysUpTime OBJECT-TYPE
   SYNTAX      TimeTicks
   MAX-ACCESS  read-only
   STATUS      current
   DESCRIPTION
      "Path: swPort.performance.pppoEClient.mibCounters.h2Performance.sysUpTime

       Time in centi-second."
   ::= {pr1646v2EthPortSwFPPPoEMCH2PEntry 16777216}

pr1646v2EthPortSwFPPPoEMCH2PIfUpTime OBJECT-TYPE
   SYNTAX      TimeTicks
   MAX-ACCESS  read-only
   STATUS      current
   DESCRIPTION
      "Path: swPort.performance.pppoEClient.mibCounters.h2Performance.ifUpTime

       Time in centi-second."
   ::= {pr1646v2EthPortSwFPPPoEMCH2PEntry 33554432}

pr1646v2EthPortSwFPPPoEMCH2PIfStatChanges OBJECT-TYPE
   SYNTAX      Counter32
   MAX-ACCESS  read-only
   STATUS      current
   DESCRIPTION
      "Path: swPort.performance.pppoEClient.mibCounters.h2Performance.ifStatusChanges

       32 bit unsigned wrappable counter."
   ::= {pr1646v2EthPortSwFPPPoEMCH2PEntry 50331648}

pr1646v2EthPortSwFPPPoEMCH2PIfInOctets OBJECT-TYPE
   SYNTAX      Counter64
   MAX-ACCESS  read-only
   STATUS      current
   DESCRIPTION
      "Path: swPort.performance.pppoEClient.mibCounters.h2Performance.ifInOctets

       64 bit unsigned wrappable counter."
   ::= {pr1646v2EthPortSwFPPPoEMCH2PEntry 67108864}

pr1646v2EthPortSwFPPPoEMCH2PIfInUCPkts OBJECT-TYPE
   SYNTAX      Counter64
   MAX-ACCESS  read-only
   STATUS      current
   DESCRIPTION
      "Path: swPort.performance.pppoEClient.mibCounters.h2Performance.ifInUcastPkts

       64 bit unsigned wrappable counter."
   ::= {pr1646v2EthPortSwFPPPoEMCH2PEntry 83886080}

pr1646v2EthPortSwFPPPoEMCH2PIfInNUCPkts OBJECT-TYPE
   SYNTAX      Counter64
   MAX-ACCESS  read-only
   STATUS      current
   DESCRIPTION
      "Path: swPort.performance.pppoEClient.mibCounters.h2Performance.ifInNUcastPkts

       64 bit unsigned wrappable counter."
   ::= {pr1646v2EthPortSwFPPPoEMCH2PEntry 100663296}

pr1646v2EthPortSwFPPPoEMCH2PIfInBCPkts OBJECT-TYPE
   SYNTAX      Counter64
   MAX-ACCESS  read-only
   STATUS      current
   DESCRIPTION
      "Path: swPort.performance.pppoEClient.mibCounters.h2Performance.ifInBcastPkts

       64 bit unsigned wrappable counter."
   ::= {pr1646v2EthPortSwFPPPoEMCH2PEntry 419430400}

pr1646v2EthPortSwFPPPoEMCH2PIfInMCPkts OBJECT-TYPE
   SYNTAX      Counter64
   MAX-ACCESS  read-only
   STATUS      current
   DESCRIPTION
      "Path: swPort.performance.pppoEClient.mibCounters.h2Performance.ifInMcastPkts

       64 bit unsigned wrappable counter."
   ::= {pr1646v2EthPortSwFPPPoEMCH2PEntry 436207616}

pr1646v2EthPortSwFPPPoEMCH2PIfInDiscards OBJECT-TYPE
   SYNTAX      Counter64
   MAX-ACCESS  read-only
   STATUS      current
   DESCRIPTION
      "Path: swPort.performance.pppoEClient.mibCounters.h2Performance.ifInDiscards

       64 bit unsigned wrappable counter."
   ::= {pr1646v2EthPortSwFPPPoEMCH2PEntry 117440512}

pr1646v2EthPortSwFPPPoEMCH2PIfInErrors OBJECT-TYPE
   SYNTAX      Counter64
   MAX-ACCESS  read-only
   STATUS      current
   DESCRIPTION
      "Path: swPort.performance.pppoEClient.mibCounters.h2Performance.ifInErrors

       64 bit unsigned wrappable counter."
   ::= {pr1646v2EthPortSwFPPPoEMCH2PEntry 134217728}

pr1646v2EthPortSwFPPPoEMCH2PIfInUnkwn OBJECT-TYPE
   SYNTAX      Counter64
   MAX-ACCESS  read-only
   STATUS      current
   DESCRIPTION
      "Path: swPort.performance.pppoEClient.mibCounters.h2Performance.ifInUnknownProtos

       64 bit unsigned wrappable counter."
   ::= {pr1646v2EthPortSwFPPPoEMCH2PEntry 150994944}

pr1646v2EthPortSwFPPPoEMCH2PInDropEx OBJECT-TYPE
   SYNTAX      Counter64
   MAX-ACCESS  read-only
   STATUS      current
   DESCRIPTION
      "Path: swPort.performance.pppoEClient.mibCounters.h2Performance.ifInDropLevelExceeded

       64 bit unsigned wrappable counter."
   ::= {pr1646v2EthPortSwFPPPoEMCH2PEntry 335544320}

pr1646v2EthPortSwFPPPoEMCH2PInDropNoMac OBJECT-TYPE
   SYNTAX      Counter64
   MAX-ACCESS  read-only
   STATUS      current
   DESCRIPTION
      "Path: swPort.performance.pppoEClient.mibCounters.h2Performance.fInDiscardsNoMacFit

       64 bit unsigned wrappable counter."
   ::= {pr1646v2EthPortSwFPPPoEMCH2PEntry 301989888}

pr1646v2EthPortSwFPPPoEMCH2PInDropNUCast OBJECT-TYPE
   SYNTAX      Counter64
   MAX-ACCESS  read-only
   STATUS      current
   DESCRIPTION
      "Path: swPort.performance.pppoEClient.mibCounters.h2Performance.fInDiscardsNUCast

       64 bit unsigned wrappable counter."
   ::= {pr1646v2EthPortSwFPPPoEMCH2PEntry 318767104}

pr1646v2EthPortSwFPPPoEMCH2PInDropFilter OBJECT-TYPE
   SYNTAX      Counter64
   MAX-ACCESS  read-only
   STATUS      current
   DESCRIPTION
      "Path: swPort.performance.pppoEClient.mibCounters.h2Performance.fInDiscardsFilter

       64 bit unsigned wrappable counter."
   ::= {pr1646v2EthPortSwFPPPoEMCH2PEntry 385875968}

pr1646v2EthPortSwFPPPoEMCH2PIfInBandwidth OBJECT-TYPE
   SYNTAX      Integer32
   MAX-ACCESS  read-only
   STATUS      current
   DESCRIPTION
      "Path: swPort.performance.pppoEClient.mibCounters.h2Performance.ifInBandwidth

       unit name = bps
       formula = 8 * ; 8 /"
   ::= {pr1646v2EthPortSwFPPPoEMCH2PEntry 268435456}

pr1646v2EthPortSwFPPPoEMCH2PIfOutOctets OBJECT-TYPE
   SYNTAX      Counter64
   MAX-ACCESS  read-only
   STATUS      current
   DESCRIPTION
      "Path: swPort.performance.pppoEClient.mibCounters.h2Performance.ifOutOctets

       64 bit unsigned wrappable counter."
   ::= {pr1646v2EthPortSwFPPPoEMCH2PEntry 167772160}

pr1646v2EthPortSwFPPPoEMCH2PIfOutUCPkts OBJECT-TYPE
   SYNTAX      Counter64
   MAX-ACCESS  read-only
   STATUS      current
   DESCRIPTION
      "Path: swPort.performance.pppoEClient.mibCounters.h2Performance.ifOutUcastPkts

       64 bit unsigned wrappable counter."
   ::= {pr1646v2EthPortSwFPPPoEMCH2PEntry 184549376}

pr1646v2EthPortSwFPPPoEMCH2PIfOutNUCPkts OBJECT-TYPE
   SYNTAX      Counter64
   MAX-ACCESS  read-only
   STATUS      current
   DESCRIPTION
      "Path: swPort.performance.pppoEClient.mibCounters.h2Performance.ifOutNUcastPkts

       64 bit unsigned wrappable counter."
   ::= {pr1646v2EthPortSwFPPPoEMCH2PEntry 201326592}

pr1646v2EthPortSwFPPPoEMCH2PIfOutBCPkts OBJECT-TYPE
   SYNTAX      Counter64
   MAX-ACCESS  read-only
   STATUS      current
   DESCRIPTION
      "Path: swPort.performance.pppoEClient.mibCounters.h2Performance.ifOutBcastPkts

       64 bit unsigned wrappable counter."
   ::= {pr1646v2EthPortSwFPPPoEMCH2PEntry 452984832}

pr1646v2EthPortSwFPPPoEMCH2PIfOutMCPkts OBJECT-TYPE
   SYNTAX      Counter64
   MAX-ACCESS  read-only
   STATUS      current
   DESCRIPTION
      "Path: swPort.performance.pppoEClient.mibCounters.h2Performance.ifOutMcastPkts

       64 bit unsigned wrappable counter."
   ::= {pr1646v2EthPortSwFPPPoEMCH2PEntry 469762048}

pr1646v2EthPortSwFPPPoEMCH2PIfOutDiscards OBJECT-TYPE
   SYNTAX      Counter64
   MAX-ACCESS  read-only
   STATUS      current
   DESCRIPTION
      "Path: swPort.performance.pppoEClient.mibCounters.h2Performance.ifOutDiscards

       64 bit unsigned wrappable counter."
   ::= {pr1646v2EthPortSwFPPPoEMCH2PEntry 218103808}

pr1646v2EthPortSwFPPPoEMCH2PIfOutErrors OBJECT-TYPE
   SYNTAX      Counter64
   MAX-ACCESS  read-only
   STATUS      current
   DESCRIPTION
      "Path: swPort.performance.pppoEClient.mibCounters.h2Performance.ifOutErrors

       64 bit unsigned wrappable counter."
   ::= {pr1646v2EthPortSwFPPPoEMCH2PEntry 234881024}

pr1646v2EthPortSwFPPPoEMCH2POutDropEx OBJECT-TYPE
   SYNTAX      Counter64
   MAX-ACCESS  read-only
   STATUS      current
   DESCRIPTION
      "Path: swPort.performance.pppoEClient.mibCounters.h2Performance.ifOutDropLevelExceeded

       64 bit unsigned wrappable counter."
   ::= {pr1646v2EthPortSwFPPPoEMCH2PEntry 352321536}

pr1646v2EthPortSwFPPPoEMCH2POutDropNoArp OBJECT-TYPE
   SYNTAX      Counter64
   MAX-ACCESS  read-only
   STATUS      current
   DESCRIPTION
      "Path: swPort.performance.pppoEClient.mibCounters.h2Performance.ifOutDiscardsNoArp

       64 bit unsigned wrappable counter."
   ::= {pr1646v2EthPortSwFPPPoEMCH2PEntry 369098752}

pr1646v2EthPortSwFPPPoEMCH2POutDropFilter OBJECT-TYPE
   SYNTAX      Counter64
   MAX-ACCESS  read-only
   STATUS      current
   DESCRIPTION
      "Path: swPort.performance.pppoEClient.mibCounters.h2Performance.ifOutDiscardsFilter

       64 bit unsigned wrappable counter."
   ::= {pr1646v2EthPortSwFPPPoEMCH2PEntry 402653184}

pr1646v2EthPortSwFPPPoEMCH2PIfOutBandwidth OBJECT-TYPE
   SYNTAX      Integer32
   MAX-ACCESS  read-only
   STATUS      current
   DESCRIPTION
      "Path: swPort.performance.pppoEClient.mibCounters.h2Performance.ifOutBandwidth

       unit name = bps
       formula = 8 * ; 8 /"
   ::= {pr1646v2EthPortSwFPPPoEMCH2PEntry 285212672}

pr1646v2EthPortSwFPPPoEMCH2PIfErrSec OBJECT-TYPE
   SYNTAX      Counter32
   MAX-ACCESS  read-only
   STATUS      current
   DESCRIPTION
      "Path: swPort.performance.pppoEClient.mibCounters.h2Performance.ifErrSec

       32 bit unsigned wrappable counter."
   ::= {pr1646v2EthPortSwFPPPoEMCH2PEntry 251658240}

pr1646v2EthPortSwFPPPoEMCH24P OBJECT-TYPE
   SYNTAX      SEQUENCE OF Pr1646v2EthPortSwFPPPoEMCH24PEntry
   MAX-ACCESS  not-accessible
   STATUS      current
   DESCRIPTION
      ""
   ::= {pr1646v2EthPortSwFPPPoE 41615360}

pr1646v2EthPortSwFPPPoEMCH24PEntry OBJECT-TYPE
   SYNTAX      Pr1646v2EthPortSwFPPPoEMCH24PEntry
   MAX-ACCESS  not-accessible
   STATUS      current
   DESCRIPTION
      ""
   INDEX      { pr1646v2EthPortSwFPPPoEMCH24PGlobalIx,
                pr1646v2EthPortSwFPPPoETableIx,
                pr1646v2EthPortSwFPPPoEMCH24PTableIx }
   ::= {pr1646v2EthPortSwFPPPoEMCH24P 1}

Pr1646v2EthPortSwFPPPoEMCH24PEntry ::=
   SEQUENCE
      {
      pr1646v2EthPortSwFPPPoEMCH24PGlobalIx
         GlobalIndex,
      pr1646v2EthPortSwFPPPoEMCH24PTableIx
         TableIndex,
      pr1646v2EthPortSwFPPPoEMCH24PSysUpTime
         TimeTicks,
      pr1646v2EthPortSwFPPPoEMCH24PIfUpTime
         TimeTicks,
      pr1646v2EthPortSwFPPPoEMCH24PIfStatChanges
         Counter32,
      pr1646v2EthPortSwFPPPoEMCH24PIfInOctets
         Counter64,
      pr1646v2EthPortSwFPPPoEMCH24PIfInUCPkts
         Counter64,
      pr1646v2EthPortSwFPPPoEMCH24PIfInNUCPkts
         Counter64,
      pr1646v2EthPortSwFPPPoEMCH24PIfInBCPkts
         Counter64,
      pr1646v2EthPortSwFPPPoEMCH24PIfInMCPkts
         Counter64,
      pr1646v2EthPortSwFPPPoEMCH24PIfInDiscards
         Counter64,
      pr1646v2EthPortSwFPPPoEMCH24PIfInErrors
         Counter64,
      pr1646v2EthPortSwFPPPoEMCH24PIfInUnkwn
         Counter64,
      pr1646v2EthPortSwFPPPoEMCH24PInDropEx
         Counter64,
      pr1646v2EthPortSwFPPPoEMCH24PInDropNoMac
         Counter64,
      pr1646v2EthPortSwFPPPoEMCH24PInDropNUCast
         Counter64,
      pr1646v2EthPortSwFPPPoEMCH24PInDropFilter
         Counter64,
      pr1646v2EthPortSwFPPPoEMCH24PIfInBandwidth
         Integer32,
      pr1646v2EthPortSwFPPPoEMCH24PIfOutOctets
         Counter64,
      pr1646v2EthPortSwFPPPoEMCH24PIfOutUCPkts
         Counter64,
      pr1646v2EthPortSwFPPPoEMCH24PIfOutNUCPkts
         Counter64,
      pr1646v2EthPortSwFPPPoEMCH24PIfOutBCPkts
         Counter64,
      pr1646v2EthPortSwFPPPoEMCH24PIfOutMCPkts
         Counter64,
      pr1646v2EthPortSwFPPPoEMCH24PIfOutDiscards
         Counter64,
      pr1646v2EthPortSwFPPPoEMCH24PIfOutErrors
         Counter64,
      pr1646v2EthPortSwFPPPoEMCH24POutDropEx
         Counter64,
      pr1646v2EthPortSwFPPPoEMCH24POutDropNoArp
         Counter64,
      pr1646v2EthPortSwFPPPoEMCH24POutDropFilter
         Counter64,
      pr1646v2EthPortSwFPPPoEMCH24PIfOutBandwidth
         Integer32,
      pr1646v2EthPortSwFPPPoEMCH24PIfErrSec
         Counter32
      }

pr1646v2EthPortSwFPPPoEMCH24PGlobalIx OBJECT-TYPE
   SYNTAX      GlobalIndex
   MAX-ACCESS  not-accessible
   STATUS      current
   DESCRIPTION
      "The value of the tlsCntTreeGlobalIndex of the MANAGED OBJECT."
   ::= {pr1646v2EthPortSwFPPPoEMCH24PEntry 10}

pr1646v2EthPortSwFPPPoEMCH24PTableIx OBJECT-TYPE
   SYNTAX      TableIndex
   MAX-ACCESS  not-accessible
   STATUS      current
   DESCRIPTION
      ""
   ::= {pr1646v2EthPortSwFPPPoEMCH24PEntry 11}

pr1646v2EthPortSwFPPPoEMCH24PSysUpTime OBJECT-TYPE
   SYNTAX      TimeTicks
   MAX-ACCESS  read-only
   STATUS      current
   DESCRIPTION
      "Path: swPort.performance.pppoEClient.mibCounters.h24Performance.sysUpTime

       Time in centi-second."
   ::= {pr1646v2EthPortSwFPPPoEMCH24PEntry 16777216}

pr1646v2EthPortSwFPPPoEMCH24PIfUpTime OBJECT-TYPE
   SYNTAX      TimeTicks
   MAX-ACCESS  read-only
   STATUS      current
   DESCRIPTION
      "Path: swPort.performance.pppoEClient.mibCounters.h24Performance.ifUpTime

       Time in centi-second."
   ::= {pr1646v2EthPortSwFPPPoEMCH24PEntry 33554432}

pr1646v2EthPortSwFPPPoEMCH24PIfStatChanges OBJECT-TYPE
   SYNTAX      Counter32
   MAX-ACCESS  read-only
   STATUS      current
   DESCRIPTION
      "Path: swPort.performance.pppoEClient.mibCounters.h24Performance.ifStatusChanges

       32 bit unsigned wrappable counter."
   ::= {pr1646v2EthPortSwFPPPoEMCH24PEntry 50331648}

pr1646v2EthPortSwFPPPoEMCH24PIfInOctets OBJECT-TYPE
   SYNTAX      Counter64
   MAX-ACCESS  read-only
   STATUS      current
   DESCRIPTION
      "Path: swPort.performance.pppoEClient.mibCounters.h24Performance.ifInOctets

       64 bit unsigned wrappable counter."
   ::= {pr1646v2EthPortSwFPPPoEMCH24PEntry 67108864}

pr1646v2EthPortSwFPPPoEMCH24PIfInUCPkts OBJECT-TYPE
   SYNTAX      Counter64
   MAX-ACCESS  read-only
   STATUS      current
   DESCRIPTION
      "Path: swPort.performance.pppoEClient.mibCounters.h24Performance.ifInUcastPkts

       64 bit unsigned wrappable counter."
   ::= {pr1646v2EthPortSwFPPPoEMCH24PEntry 83886080}

pr1646v2EthPortSwFPPPoEMCH24PIfInNUCPkts OBJECT-TYPE
   SYNTAX      Counter64
   MAX-ACCESS  read-only
   STATUS      current
   DESCRIPTION
      "Path: swPort.performance.pppoEClient.mibCounters.h24Performance.ifInNUcastPkts

       64 bit unsigned wrappable counter."
   ::= {pr1646v2EthPortSwFPPPoEMCH24PEntry 100663296}

pr1646v2EthPortSwFPPPoEMCH24PIfInBCPkts OBJECT-TYPE
   SYNTAX      Counter64
   MAX-ACCESS  read-only
   STATUS      current
   DESCRIPTION
      "Path: swPort.performance.pppoEClient.mibCounters.h24Performance.ifInBcastPkts

       64 bit unsigned wrappable counter."
   ::= {pr1646v2EthPortSwFPPPoEMCH24PEntry 419430400}

pr1646v2EthPortSwFPPPoEMCH24PIfInMCPkts OBJECT-TYPE
   SYNTAX      Counter64
   MAX-ACCESS  read-only
   STATUS      current
   DESCRIPTION
      "Path: swPort.performance.pppoEClient.mibCounters.h24Performance.ifInMcastPkts

       64 bit unsigned wrappable counter."
   ::= {pr1646v2EthPortSwFPPPoEMCH24PEntry 436207616}

pr1646v2EthPortSwFPPPoEMCH24PIfInDiscards OBJECT-TYPE
   SYNTAX      Counter64
   MAX-ACCESS  read-only
   STATUS      current
   DESCRIPTION
      "Path: swPort.performance.pppoEClient.mibCounters.h24Performance.ifInDiscards

       64 bit unsigned wrappable counter."
   ::= {pr1646v2EthPortSwFPPPoEMCH24PEntry 117440512}

pr1646v2EthPortSwFPPPoEMCH24PIfInErrors OBJECT-TYPE
   SYNTAX      Counter64
   MAX-ACCESS  read-only
   STATUS      current
   DESCRIPTION
      "Path: swPort.performance.pppoEClient.mibCounters.h24Performance.ifInErrors

       64 bit unsigned wrappable counter."
   ::= {pr1646v2EthPortSwFPPPoEMCH24PEntry 134217728}

pr1646v2EthPortSwFPPPoEMCH24PIfInUnkwn OBJECT-TYPE
   SYNTAX      Counter64
   MAX-ACCESS  read-only
   STATUS      current
   DESCRIPTION
      "Path: swPort.performance.pppoEClient.mibCounters.h24Performance.ifInUnknownProtos

       64 bit unsigned wrappable counter."
   ::= {pr1646v2EthPortSwFPPPoEMCH24PEntry 150994944}

pr1646v2EthPortSwFPPPoEMCH24PInDropEx OBJECT-TYPE
   SYNTAX      Counter64
   MAX-ACCESS  read-only
   STATUS      current
   DESCRIPTION
      "Path: swPort.performance.pppoEClient.mibCounters.h24Performance.ifInDropLevelExceeded

       64 bit unsigned wrappable counter."
   ::= {pr1646v2EthPortSwFPPPoEMCH24PEntry 335544320}

pr1646v2EthPortSwFPPPoEMCH24PInDropNoMac OBJECT-TYPE
   SYNTAX      Counter64
   MAX-ACCESS  read-only
   STATUS      current
   DESCRIPTION
      "Path: swPort.performance.pppoEClient.mibCounters.h24Performance.fInDiscardsNoMacFit

       64 bit unsigned wrappable counter."
   ::= {pr1646v2EthPortSwFPPPoEMCH24PEntry 301989888}

pr1646v2EthPortSwFPPPoEMCH24PInDropNUCast OBJECT-TYPE
   SYNTAX      Counter64
   MAX-ACCESS  read-only
   STATUS      current
   DESCRIPTION
      "Path: swPort.performance.pppoEClient.mibCounters.h24Performance.fInDiscardsNUCast

       64 bit unsigned wrappable counter."
   ::= {pr1646v2EthPortSwFPPPoEMCH24PEntry 318767104}

pr1646v2EthPortSwFPPPoEMCH24PInDropFilter OBJECT-TYPE
   SYNTAX      Counter64
   MAX-ACCESS  read-only
   STATUS      current
   DESCRIPTION
      "Path: swPort.performance.pppoEClient.mibCounters.h24Performance.fInDiscardsFilter

       64 bit unsigned wrappable counter."
   ::= {pr1646v2EthPortSwFPPPoEMCH24PEntry 385875968}

pr1646v2EthPortSwFPPPoEMCH24PIfInBandwidth OBJECT-TYPE
   SYNTAX      Integer32
   MAX-ACCESS  read-only
   STATUS      current
   DESCRIPTION
      "Path: swPort.performance.pppoEClient.mibCounters.h24Performance.ifInBandwidth

       unit name = bps
       formula = 8 * ; 8 /"
   ::= {pr1646v2EthPortSwFPPPoEMCH24PEntry 268435456}

pr1646v2EthPortSwFPPPoEMCH24PIfOutOctets OBJECT-TYPE
   SYNTAX      Counter64
   MAX-ACCESS  read-only
   STATUS      current
   DESCRIPTION
      "Path: swPort.performance.pppoEClient.mibCounters.h24Performance.ifOutOctets

       64 bit unsigned wrappable counter."
   ::= {pr1646v2EthPortSwFPPPoEMCH24PEntry 167772160}

pr1646v2EthPortSwFPPPoEMCH24PIfOutUCPkts OBJECT-TYPE
   SYNTAX      Counter64
   MAX-ACCESS  read-only
   STATUS      current
   DESCRIPTION
      "Path: swPort.performance.pppoEClient.mibCounters.h24Performance.ifOutUcastPkts

       64 bit unsigned wrappable counter."
   ::= {pr1646v2EthPortSwFPPPoEMCH24PEntry 184549376}

pr1646v2EthPortSwFPPPoEMCH24PIfOutNUCPkts OBJECT-TYPE
   SYNTAX      Counter64
   MAX-ACCESS  read-only
   STATUS      current
   DESCRIPTION
      "Path: swPort.performance.pppoEClient.mibCounters.h24Performance.ifOutNUcastPkts

       64 bit unsigned wrappable counter."
   ::= {pr1646v2EthPortSwFPPPoEMCH24PEntry 201326592}

pr1646v2EthPortSwFPPPoEMCH24PIfOutBCPkts OBJECT-TYPE
   SYNTAX      Counter64
   MAX-ACCESS  read-only
   STATUS      current
   DESCRIPTION
      "Path: swPort.performance.pppoEClient.mibCounters.h24Performance.ifOutBcastPkts

       64 bit unsigned wrappable counter."
   ::= {pr1646v2EthPortSwFPPPoEMCH24PEntry 452984832}

pr1646v2EthPortSwFPPPoEMCH24PIfOutMCPkts OBJECT-TYPE
   SYNTAX      Counter64
   MAX-ACCESS  read-only
   STATUS      current
   DESCRIPTION
      "Path: swPort.performance.pppoEClient.mibCounters.h24Performance.ifOutMcastPkts

       64 bit unsigned wrappable counter."
   ::= {pr1646v2EthPortSwFPPPoEMCH24PEntry 469762048}

pr1646v2EthPortSwFPPPoEMCH24PIfOutDiscards OBJECT-TYPE
   SYNTAX      Counter64
   MAX-ACCESS  read-only
   STATUS      current
   DESCRIPTION
      "Path: swPort.performance.pppoEClient.mibCounters.h24Performance.ifOutDiscards

       64 bit unsigned wrappable counter."
   ::= {pr1646v2EthPortSwFPPPoEMCH24PEntry 218103808}

pr1646v2EthPortSwFPPPoEMCH24PIfOutErrors OBJECT-TYPE
   SYNTAX      Counter64
   MAX-ACCESS  read-only
   STATUS      current
   DESCRIPTION
      "Path: swPort.performance.pppoEClient.mibCounters.h24Performance.ifOutErrors

       64 bit unsigned wrappable counter."
   ::= {pr1646v2EthPortSwFPPPoEMCH24PEntry 234881024}

pr1646v2EthPortSwFPPPoEMCH24POutDropEx OBJECT-TYPE
   SYNTAX      Counter64
   MAX-ACCESS  read-only
   STATUS      current
   DESCRIPTION
      "Path: swPort.performance.pppoEClient.mibCounters.h24Performance.ifOutDropLevelExceeded

       64 bit unsigned wrappable counter."
   ::= {pr1646v2EthPortSwFPPPoEMCH24PEntry 352321536}

pr1646v2EthPortSwFPPPoEMCH24POutDropNoArp OBJECT-TYPE
   SYNTAX      Counter64
   MAX-ACCESS  read-only
   STATUS      current
   DESCRIPTION
      "Path: swPort.performance.pppoEClient.mibCounters.h24Performance.ifOutDiscardsNoArp

       64 bit unsigned wrappable counter."
   ::= {pr1646v2EthPortSwFPPPoEMCH24PEntry 369098752}

pr1646v2EthPortSwFPPPoEMCH24POutDropFilter OBJECT-TYPE
   SYNTAX      Counter64
   MAX-ACCESS  read-only
   STATUS      current
   DESCRIPTION
      "Path: swPort.performance.pppoEClient.mibCounters.h24Performance.ifOutDiscardsFilter

       64 bit unsigned wrappable counter."
   ::= {pr1646v2EthPortSwFPPPoEMCH24PEntry 402653184}

pr1646v2EthPortSwFPPPoEMCH24PIfOutBandwidth OBJECT-TYPE
   SYNTAX      Integer32
   MAX-ACCESS  read-only
   STATUS      current
   DESCRIPTION
      "Path: swPort.performance.pppoEClient.mibCounters.h24Performance.ifOutBandwidth

       unit name = bps
       formula = 8 * ; 8 /"
   ::= {pr1646v2EthPortSwFPPPoEMCH24PEntry 285212672}

pr1646v2EthPortSwFPPPoEMCH24PIfErrSec OBJECT-TYPE
   SYNTAX      Counter32
   MAX-ACCESS  read-only
   STATUS      current
   DESCRIPTION
      "Path: swPort.performance.pppoEClient.mibCounters.h24Performance.ifErrSec

       32 bit unsigned wrappable counter."
   ::= {pr1646v2EthPortSwFPPPoEMCH24PEntry 251658240}

pr1646v2EthPortSwFPPPoEMCD7P OBJECT-TYPE
   SYNTAX      SEQUENCE OF Pr1646v2EthPortSwFPPPoEMCD7PEntry
   MAX-ACCESS  not-accessible
   STATUS      current
   DESCRIPTION
      ""
   ::= {pr1646v2EthPortSwFPPPoE 41680896}

pr1646v2EthPortSwFPPPoEMCD7PEntry OBJECT-TYPE
   SYNTAX      Pr1646v2EthPortSwFPPPoEMCD7PEntry
   MAX-ACCESS  not-accessible
   STATUS      current
   DESCRIPTION
      ""
   INDEX      { pr1646v2EthPortSwFPPPoEMCD7PGlobalIx,
                pr1646v2EthPortSwFPPPoETableIx,
                pr1646v2EthPortSwFPPPoEMCD7PTableIx }
   ::= {pr1646v2EthPortSwFPPPoEMCD7P 1}

Pr1646v2EthPortSwFPPPoEMCD7PEntry ::=
   SEQUENCE
      {
      pr1646v2EthPortSwFPPPoEMCD7PGlobalIx
         GlobalIndex,
      pr1646v2EthPortSwFPPPoEMCD7PTableIx
         TableIndex,
      pr1646v2EthPortSwFPPPoEMCD7PSysUpTime
         TimeTicks,
      pr1646v2EthPortSwFPPPoEMCD7PIfUpTime
         TimeTicks,
      pr1646v2EthPortSwFPPPoEMCD7PIfStatChanges
         Counter32,
      pr1646v2EthPortSwFPPPoEMCD7PIfInOctets
         Counter64,
      pr1646v2EthPortSwFPPPoEMCD7PIfInUCPkts
         Counter64,
      pr1646v2EthPortSwFPPPoEMCD7PIfInNUCPkts
         Counter64,
      pr1646v2EthPortSwFPPPoEMCD7PIfInBCPkts
         Counter64,
      pr1646v2EthPortSwFPPPoEMCD7PIfInMCPkts
         Counter64,
      pr1646v2EthPortSwFPPPoEMCD7PIfInDiscards
         Counter64,
      pr1646v2EthPortSwFPPPoEMCD7PIfInErrors
         Counter64,
      pr1646v2EthPortSwFPPPoEMCD7PIfInUnkwn
         Counter64,
      pr1646v2EthPortSwFPPPoEMCD7PInDropEx
         Counter64,
      pr1646v2EthPortSwFPPPoEMCD7PInDropNoMac
         Counter64,
      pr1646v2EthPortSwFPPPoEMCD7PInDropNUCast
         Counter64,
      pr1646v2EthPortSwFPPPoEMCD7PInDropFilter
         Counter64,
      pr1646v2EthPortSwFPPPoEMCD7PIfInBandwidth
         Integer32,
      pr1646v2EthPortSwFPPPoEMCD7PIfOutOctets
         Counter64,
      pr1646v2EthPortSwFPPPoEMCD7PIfOutUCPkts
         Counter64,
      pr1646v2EthPortSwFPPPoEMCD7PIfOutNUCPkts
         Counter64,
      pr1646v2EthPortSwFPPPoEMCD7PIfOutBCPkts
         Counter64,
      pr1646v2EthPortSwFPPPoEMCD7PIfOutMCPkts
         Counter64,
      pr1646v2EthPortSwFPPPoEMCD7PIfOutDiscards
         Counter64,
      pr1646v2EthPortSwFPPPoEMCD7PIfOutErrors
         Counter64,
      pr1646v2EthPortSwFPPPoEMCD7POutDropEx
         Counter64,
      pr1646v2EthPortSwFPPPoEMCD7POutDropNoArp
         Counter64,
      pr1646v2EthPortSwFPPPoEMCD7POutDropFilter
         Counter64,
      pr1646v2EthPortSwFPPPoEMCD7PIfOutBandwidth
         Integer32,
      pr1646v2EthPortSwFPPPoEMCD7PIfErrSec
         Counter32
      }

pr1646v2EthPortSwFPPPoEMCD7PGlobalIx OBJECT-TYPE
   SYNTAX      GlobalIndex
   MAX-ACCESS  not-accessible
   STATUS      current
   DESCRIPTION
      "The value of the tlsCntTreeGlobalIndex of the MANAGED OBJECT."
   ::= {pr1646v2EthPortSwFPPPoEMCD7PEntry 10}

pr1646v2EthPortSwFPPPoEMCD7PTableIx OBJECT-TYPE
   SYNTAX      TableIndex
   MAX-ACCESS  not-accessible
   STATUS      current
   DESCRIPTION
      ""
   ::= {pr1646v2EthPortSwFPPPoEMCD7PEntry 11}

pr1646v2EthPortSwFPPPoEMCD7PSysUpTime OBJECT-TYPE
   SYNTAX      TimeTicks
   MAX-ACCESS  read-only
   STATUS      current
   DESCRIPTION
      "Path: swPort.performance.pppoEClient.mibCounters.d7Performance.sysUpTime

       Time in centi-second."
   ::= {pr1646v2EthPortSwFPPPoEMCD7PEntry 16777216}

pr1646v2EthPortSwFPPPoEMCD7PIfUpTime OBJECT-TYPE
   SYNTAX      TimeTicks
   MAX-ACCESS  read-only
   STATUS      current
   DESCRIPTION
      "Path: swPort.performance.pppoEClient.mibCounters.d7Performance.ifUpTime

       Time in centi-second."
   ::= {pr1646v2EthPortSwFPPPoEMCD7PEntry 33554432}

pr1646v2EthPortSwFPPPoEMCD7PIfStatChanges OBJECT-TYPE
   SYNTAX      Counter32
   MAX-ACCESS  read-only
   STATUS      current
   DESCRIPTION
      "Path: swPort.performance.pppoEClient.mibCounters.d7Performance.ifStatusChanges

       32 bit unsigned wrappable counter."
   ::= {pr1646v2EthPortSwFPPPoEMCD7PEntry 50331648}

pr1646v2EthPortSwFPPPoEMCD7PIfInOctets OBJECT-TYPE
   SYNTAX      Counter64
   MAX-ACCESS  read-only
   STATUS      current
   DESCRIPTION
      "Path: swPort.performance.pppoEClient.mibCounters.d7Performance.ifInOctets

       64 bit unsigned wrappable counter."
   ::= {pr1646v2EthPortSwFPPPoEMCD7PEntry 67108864}

pr1646v2EthPortSwFPPPoEMCD7PIfInUCPkts OBJECT-TYPE
   SYNTAX      Counter64
   MAX-ACCESS  read-only
   STATUS      current
   DESCRIPTION
      "Path: swPort.performance.pppoEClient.mibCounters.d7Performance.ifInUcastPkts

       64 bit unsigned wrappable counter."
   ::= {pr1646v2EthPortSwFPPPoEMCD7PEntry 83886080}

pr1646v2EthPortSwFPPPoEMCD7PIfInNUCPkts OBJECT-TYPE
   SYNTAX      Counter64
   MAX-ACCESS  read-only
   STATUS      current
   DESCRIPTION
      "Path: swPort.performance.pppoEClient.mibCounters.d7Performance.ifInNUcastPkts

       64 bit unsigned wrappable counter."
   ::= {pr1646v2EthPortSwFPPPoEMCD7PEntry 100663296}

pr1646v2EthPortSwFPPPoEMCD7PIfInBCPkts OBJECT-TYPE
   SYNTAX      Counter64
   MAX-ACCESS  read-only
   STATUS      current
   DESCRIPTION
      "Path: swPort.performance.pppoEClient.mibCounters.d7Performance.ifInBcastPkts

       64 bit unsigned wrappable counter."
   ::= {pr1646v2EthPortSwFPPPoEMCD7PEntry 419430400}

pr1646v2EthPortSwFPPPoEMCD7PIfInMCPkts OBJECT-TYPE
   SYNTAX      Counter64
   MAX-ACCESS  read-only
   STATUS      current
   DESCRIPTION
      "Path: swPort.performance.pppoEClient.mibCounters.d7Performance.ifInMcastPkts

       64 bit unsigned wrappable counter."
   ::= {pr1646v2EthPortSwFPPPoEMCD7PEntry 436207616}

pr1646v2EthPortSwFPPPoEMCD7PIfInDiscards OBJECT-TYPE
   SYNTAX      Counter64
   MAX-ACCESS  read-only
   STATUS      current
   DESCRIPTION
      "Path: swPort.performance.pppoEClient.mibCounters.d7Performance.ifInDiscards

       64 bit unsigned wrappable counter."
   ::= {pr1646v2EthPortSwFPPPoEMCD7PEntry 117440512}

pr1646v2EthPortSwFPPPoEMCD7PIfInErrors OBJECT-TYPE
   SYNTAX      Counter64
   MAX-ACCESS  read-only
   STATUS      current
   DESCRIPTION
      "Path: swPort.performance.pppoEClient.mibCounters.d7Performance.ifInErrors

       64 bit unsigned wrappable counter."
   ::= {pr1646v2EthPortSwFPPPoEMCD7PEntry 134217728}

pr1646v2EthPortSwFPPPoEMCD7PIfInUnkwn OBJECT-TYPE
   SYNTAX      Counter64
   MAX-ACCESS  read-only
   STATUS      current
   DESCRIPTION
      "Path: swPort.performance.pppoEClient.mibCounters.d7Performance.ifInUnknownProtos

       64 bit unsigned wrappable counter."
   ::= {pr1646v2EthPortSwFPPPoEMCD7PEntry 150994944}

pr1646v2EthPortSwFPPPoEMCD7PInDropEx OBJECT-TYPE
   SYNTAX      Counter64
   MAX-ACCESS  read-only
   STATUS      current
   DESCRIPTION
      "Path: swPort.performance.pppoEClient.mibCounters.d7Performance.ifInDropLevelExceeded

       64 bit unsigned wrappable counter."
   ::= {pr1646v2EthPortSwFPPPoEMCD7PEntry 335544320}

pr1646v2EthPortSwFPPPoEMCD7PInDropNoMac OBJECT-TYPE
   SYNTAX      Counter64
   MAX-ACCESS  read-only
   STATUS      current
   DESCRIPTION
      "Path: swPort.performance.pppoEClient.mibCounters.d7Performance.fInDiscardsNoMacFit

       64 bit unsigned wrappable counter."
   ::= {pr1646v2EthPortSwFPPPoEMCD7PEntry 301989888}

pr1646v2EthPortSwFPPPoEMCD7PInDropNUCast OBJECT-TYPE
   SYNTAX      Counter64
   MAX-ACCESS  read-only
   STATUS      current
   DESCRIPTION
      "Path: swPort.performance.pppoEClient.mibCounters.d7Performance.fInDiscardsNUCast

       64 bit unsigned wrappable counter."
   ::= {pr1646v2EthPortSwFPPPoEMCD7PEntry 318767104}

pr1646v2EthPortSwFPPPoEMCD7PInDropFilter OBJECT-TYPE
   SYNTAX      Counter64
   MAX-ACCESS  read-only
   STATUS      current
   DESCRIPTION
      "Path: swPort.performance.pppoEClient.mibCounters.d7Performance.fInDiscardsFilter

       64 bit unsigned wrappable counter."
   ::= {pr1646v2EthPortSwFPPPoEMCD7PEntry 385875968}

pr1646v2EthPortSwFPPPoEMCD7PIfInBandwidth OBJECT-TYPE
   SYNTAX      Integer32
   MAX-ACCESS  read-only
   STATUS      current
   DESCRIPTION
      "Path: swPort.performance.pppoEClient.mibCounters.d7Performance.ifInBandwidth

       unit name = bps
       formula = 8 * ; 8 /"
   ::= {pr1646v2EthPortSwFPPPoEMCD7PEntry 268435456}

pr1646v2EthPortSwFPPPoEMCD7PIfOutOctets OBJECT-TYPE
   SYNTAX      Counter64
   MAX-ACCESS  read-only
   STATUS      current
   DESCRIPTION
      "Path: swPort.performance.pppoEClient.mibCounters.d7Performance.ifOutOctets

       64 bit unsigned wrappable counter."
   ::= {pr1646v2EthPortSwFPPPoEMCD7PEntry 167772160}

pr1646v2EthPortSwFPPPoEMCD7PIfOutUCPkts OBJECT-TYPE
   SYNTAX      Counter64
   MAX-ACCESS  read-only
   STATUS      current
   DESCRIPTION
      "Path: swPort.performance.pppoEClient.mibCounters.d7Performance.ifOutUcastPkts

       64 bit unsigned wrappable counter."
   ::= {pr1646v2EthPortSwFPPPoEMCD7PEntry 184549376}

pr1646v2EthPortSwFPPPoEMCD7PIfOutNUCPkts OBJECT-TYPE
   SYNTAX      Counter64
   MAX-ACCESS  read-only
   STATUS      current
   DESCRIPTION
      "Path: swPort.performance.pppoEClient.mibCounters.d7Performance.ifOutNUcastPkts

       64 bit unsigned wrappable counter."
   ::= {pr1646v2EthPortSwFPPPoEMCD7PEntry 201326592}

pr1646v2EthPortSwFPPPoEMCD7PIfOutBCPkts OBJECT-TYPE
   SYNTAX      Counter64
   MAX-ACCESS  read-only
   STATUS      current
   DESCRIPTION
      "Path: swPort.performance.pppoEClient.mibCounters.d7Performance.ifOutBcastPkts

       64 bit unsigned wrappable counter."
   ::= {pr1646v2EthPortSwFPPPoEMCD7PEntry 452984832}

pr1646v2EthPortSwFPPPoEMCD7PIfOutMCPkts OBJECT-TYPE
   SYNTAX      Counter64
   MAX-ACCESS  read-only
   STATUS      current
   DESCRIPTION
      "Path: swPort.performance.pppoEClient.mibCounters.d7Performance.ifOutMcastPkts

       64 bit unsigned wrappable counter."
   ::= {pr1646v2EthPortSwFPPPoEMCD7PEntry 469762048}

pr1646v2EthPortSwFPPPoEMCD7PIfOutDiscards OBJECT-TYPE
   SYNTAX      Counter64
   MAX-ACCESS  read-only
   STATUS      current
   DESCRIPTION
      "Path: swPort.performance.pppoEClient.mibCounters.d7Performance.ifOutDiscards

       64 bit unsigned wrappable counter."
   ::= {pr1646v2EthPortSwFPPPoEMCD7PEntry 218103808}

pr1646v2EthPortSwFPPPoEMCD7PIfOutErrors OBJECT-TYPE
   SYNTAX      Counter64
   MAX-ACCESS  read-only
   STATUS      current
   DESCRIPTION
      "Path: swPort.performance.pppoEClient.mibCounters.d7Performance.ifOutErrors

       64 bit unsigned wrappable counter."
   ::= {pr1646v2EthPortSwFPPPoEMCD7PEntry 234881024}

pr1646v2EthPortSwFPPPoEMCD7POutDropEx OBJECT-TYPE
   SYNTAX      Counter64
   MAX-ACCESS  read-only
   STATUS      current
   DESCRIPTION
      "Path: swPort.performance.pppoEClient.mibCounters.d7Performance.ifOutDropLevelExceeded

       64 bit unsigned wrappable counter."
   ::= {pr1646v2EthPortSwFPPPoEMCD7PEntry 352321536}

pr1646v2EthPortSwFPPPoEMCD7POutDropNoArp OBJECT-TYPE
   SYNTAX      Counter64
   MAX-ACCESS  read-only
   STATUS      current
   DESCRIPTION
      "Path: swPort.performance.pppoEClient.mibCounters.d7Performance.ifOutDiscardsNoArp

       64 bit unsigned wrappable counter."
   ::= {pr1646v2EthPortSwFPPPoEMCD7PEntry 369098752}

pr1646v2EthPortSwFPPPoEMCD7POutDropFilter OBJECT-TYPE
   SYNTAX      Counter64
   MAX-ACCESS  read-only
   STATUS      current
   DESCRIPTION
      "Path: swPort.performance.pppoEClient.mibCounters.d7Performance.ifOutDiscardsFilter

       64 bit unsigned wrappable counter."
   ::= {pr1646v2EthPortSwFPPPoEMCD7PEntry 402653184}

pr1646v2EthPortSwFPPPoEMCD7PIfOutBandwidth OBJECT-TYPE
   SYNTAX      Integer32
   MAX-ACCESS  read-only
   STATUS      current
   DESCRIPTION
      "Path: swPort.performance.pppoEClient.mibCounters.d7Performance.ifOutBandwidth

       unit name = bps
       formula = 8 * ; 8 /"
   ::= {pr1646v2EthPortSwFPPPoEMCD7PEntry 285212672}

pr1646v2EthPortSwFPPPoEMCD7PIfErrSec OBJECT-TYPE
   SYNTAX      Counter32
   MAX-ACCESS  read-only
   STATUS      current
   DESCRIPTION
      "Path: swPort.performance.pppoEClient.mibCounters.d7Performance.ifErrSec

       32 bit unsigned wrappable counter."
   ::= {pr1646v2EthPortSwFPPPoEMCD7PEntry 251658240}



ar1646v2EthPortSwF OBJECT IDENTIFIER ::= {r1646v2EthPortSwF 16}


ar1646v2EthPortSwFClearCounters OBJECT IDENTIFIER ::= {ar1646v2EthPortSwF 263}

ar1646v2EthPortSwFClearCountersTable OBJECT-TYPE
   SYNTAX      SEQUENCE OF Ar1646v2EthPortSwFClearCountersEntry
   MAX-ACCESS  not-accessible
   STATUS      current
   DESCRIPTION
      "reset counters"
   ::= {ar1646v2EthPortSwFClearCounters 1}

ar1646v2EthPortSwFClearCountersEntry OBJECT-TYPE
   SYNTAX      Ar1646v2EthPortSwFClearCountersEntry
   MAX-ACCESS  not-accessible
   STATUS      current
   DESCRIPTION
      ""
   INDEX      { ar1646v2EthPortSwFClearCountersGlobalIx }
   ::= {ar1646v2EthPortSwFClearCountersTable 1}

Ar1646v2EthPortSwFClearCountersEntry ::=
   SEQUENCE
      {
      ar1646v2EthPortSwFClearCountersGlobalIx
         GlobalIndex,
      ar1646v2EthPortSwFClearCountersValue
         Integer32
      }

ar1646v2EthPortSwFClearCountersGlobalIx OBJECT-TYPE
   SYNTAX      GlobalIndex
   MAX-ACCESS  not-accessible
   STATUS      current
   DESCRIPTION
      "The value of the tlsCntTreeGlobalIndex of the MANAGED OBJECT."
   ::= {ar1646v2EthPortSwFClearCountersEntry 10}

ar1646v2EthPortSwFClearCountersValue OBJECT-TYPE
   SYNTAX      Integer32
   MAX-ACCESS  read-write
   STATUS      current
   DESCRIPTION
      "Path: swPort.actions.clearCounters"
   ::= {ar1646v2EthPortSwFClearCountersEntry 2147483648}


ar1646v2EthPortSwFRestartIntf OBJECT IDENTIFIER ::= {ar1646v2EthPortSwF 67}

ar1646v2EthPortSwFRestartIntfTable OBJECT-TYPE
   SYNTAX      SEQUENCE OF Ar1646v2EthPortSwFRestartIntfEntry
   MAX-ACCESS  not-accessible
   STATUS      current
   DESCRIPTION
      "action in the debug group"
   ::= {ar1646v2EthPortSwFRestartIntf 1}

ar1646v2EthPortSwFRestartIntfEntry OBJECT-TYPE
   SYNTAX      Ar1646v2EthPortSwFRestartIntfEntry
   MAX-ACCESS  not-accessible
   STATUS      current
   DESCRIPTION
      ""
   INDEX      { ar1646v2EthPortSwFRestartIntfGlobalIx }
   ::= {ar1646v2EthPortSwFRestartIntfTable 1}

Ar1646v2EthPortSwFRestartIntfEntry ::=
   SEQUENCE
      {
      ar1646v2EthPortSwFRestartIntfGlobalIx
         GlobalIndex,
      ar1646v2EthPortSwFRestartIntfValue
         Integer32
      }

ar1646v2EthPortSwFRestartIntfGlobalIx OBJECT-TYPE
   SYNTAX      GlobalIndex
   MAX-ACCESS  not-accessible
   STATUS      current
   DESCRIPTION
      "The value of the tlsCntTreeGlobalIndex of the MANAGED OBJECT."
   ::= {ar1646v2EthPortSwFRestartIntfEntry 10}

ar1646v2EthPortSwFRestartIntfValue OBJECT-TYPE
   SYNTAX      Integer32
   MAX-ACCESS  read-write
   STATUS      current
   DESCRIPTION
      "Path: swPort.actions.restartIntf"
   ::= {ar1646v2EthPortSwFRestartIntfEntry 2147483648}


ar1646v2EthPortSwFClearOamEventLog OBJECT IDENTIFIER ::= {ar1646v2EthPortSwF 916}

ar1646v2EthPortSwFClearOamEventLogTable OBJECT-TYPE
   SYNTAX      SEQUENCE OF Ar1646v2EthPortSwFClearOamEventLogEntry
   MAX-ACCESS  not-accessible
   STATUS      current
   DESCRIPTION
      "clear the OAM event log"
   ::= {ar1646v2EthPortSwFClearOamEventLog 1}

ar1646v2EthPortSwFClearOamEventLogEntry OBJECT-TYPE
   SYNTAX      Ar1646v2EthPortSwFClearOamEventLogEntry
   MAX-ACCESS  not-accessible
   STATUS      current
   DESCRIPTION
      ""
   INDEX      { ar1646v2EthPortSwFClearOamEventLogGlobalIx }
   ::= {ar1646v2EthPortSwFClearOamEventLogTable 1}

Ar1646v2EthPortSwFClearOamEventLogEntry ::=
   SEQUENCE
      {
      ar1646v2EthPortSwFClearOamEventLogGlobalIx
         GlobalIndex,
      ar1646v2EthPortSwFClearOamEventLogValue
         Integer32
      }

ar1646v2EthPortSwFClearOamEventLogGlobalIx OBJECT-TYPE
   SYNTAX      GlobalIndex
   MAX-ACCESS  not-accessible
   STATUS      current
   DESCRIPTION
      "The value of the tlsCntTreeGlobalIndex of the MANAGED OBJECT."
   ::= {ar1646v2EthPortSwFClearOamEventLogEntry 10}

ar1646v2EthPortSwFClearOamEventLogValue OBJECT-TYPE
   SYNTAX      Integer32
   MAX-ACCESS  read-write
   STATUS      current
   DESCRIPTION
      "Path: swPort.actions.clearOamEventLog"
   ::= {ar1646v2EthPortSwFClearOamEventLogEntry 2147483648}


ar1646v2EthPortSwFLoopback OBJECT IDENTIFIER ::= {ar1646v2EthPortSwF 914}

ar1646v2EthPortSwFLoopbackTable OBJECT-TYPE
   SYNTAX      SEQUENCE OF Ar1646v2EthPortSwFLoopbackEntry
   MAX-ACCESS  not-accessible
   STATUS      current
   DESCRIPTION
      "ethernet loopback"
   ::= {ar1646v2EthPortSwFLoopback 1}

ar1646v2EthPortSwFLoopbackEntry OBJECT-TYPE
   SYNTAX      Ar1646v2EthPortSwFLoopbackEntry
   MAX-ACCESS  not-accessible
   STATUS      current
   DESCRIPTION
      ""
   INDEX      { ar1646v2EthPortSwFLoopbackGlobalIx }
   ::= {ar1646v2EthPortSwFLoopbackTable 1}

Ar1646v2EthPortSwFLoopbackEntry ::=
   SEQUENCE
      {
      ar1646v2EthPortSwFLoopbackGlobalIx
         GlobalIndex,
      ar1646v2EthPortSwFLoopbackValue
         Integer32
      }

ar1646v2EthPortSwFLoopbackGlobalIx OBJECT-TYPE
   SYNTAX      GlobalIndex
   MAX-ACCESS  not-accessible
   STATUS      current
   DESCRIPTION
      "The value of the tlsCntTreeGlobalIndex of the MANAGED OBJECT."
   ::= {ar1646v2EthPortSwFLoopbackEntry 10}

ar1646v2EthPortSwFLoopbackValue OBJECT-TYPE
   SYNTAX      Integer32
   MAX-ACCESS  read-write
   STATUS      current
   DESCRIPTION
      "Path: swPort.actions.loopback"
   ::= {ar1646v2EthPortSwFLoopbackEntry 2147483648}


ar1646v2EthPortSwFLoop OBJECT IDENTIFIER ::= {ar1646v2EthPortSwF 915}

ar1646v2EthPortSwFLoopSSCTable OBJECT-TYPE
   SYNTAX      SEQUENCE OF Ar1646v2EthPortSwFLoopEntry
   MAX-ACCESS  not-accessible
   STATUS      current
   DESCRIPTION
      "ethernet loopback type"
   ::= {ar1646v2EthPortSwFLoop 1}

ar1646v2EthPortSwFLoopEntry OBJECT-TYPE
   SYNTAX      Ar1646v2EthPortSwFLoopEntry
   MAX-ACCESS  not-accessible
   STATUS      current
   DESCRIPTION
      ""
   INDEX      { ar1646v2EthPortSwFLoopGlobalIx }
   ::= {ar1646v2EthPortSwFLoopSSCTable 1}

Ar1646v2EthPortSwFLoopEntry ::=
   SEQUENCE
      {
      ar1646v2EthPortSwFLoopGlobalIx
         GlobalIndex,
      ar1646v2EthPortSwFLoopAction
         INTEGER,
      ar1646v2EthPortSwFLoopTime
         TimeTicks,
      ar1646v2EthPortSwFLoopIntfName
         DisplayString
      }

ar1646v2EthPortSwFLoopGlobalIx OBJECT-TYPE
   SYNTAX      GlobalIndex
   MAX-ACCESS  not-accessible
   STATUS      current
   DESCRIPTION
      "The value of the tlsCntTreeGlobalIndex of the MANAGED OBJECT."
   ::= {ar1646v2EthPortSwFLoopEntry 10}

ar1646v2EthPortSwFLoopAction OBJECT-TYPE
   SYNTAX      INTEGER
               {
               start (1),
               stop (2)
               }
   MAX-ACCESS  read-write
   STATUS      current
   DESCRIPTION
      "Path: swPort.actions.loop.action

       Possibilities:
               start   (1)
               stop   (2)"
   ::= {ar1646v2EthPortSwFLoopEntry 16777216}

ar1646v2EthPortSwFLoopTime OBJECT-TYPE
   SYNTAX      TimeTicks
   MAX-ACCESS  read-write
   STATUS      current
   DESCRIPTION
      "Path: swPort.actions.loop.time

       Time in centi-second."
   ::= {ar1646v2EthPortSwFLoopEntry 50331648}

ar1646v2EthPortSwFLoopIntfName OBJECT-TYPE
   SYNTAX      DisplayString
   MAX-ACCESS  read-write
   STATUS      current
   DESCRIPTION
      "Path: swPort.actions.loop.intfName"
   ::= {ar1646v2EthPortSwFLoopEntry 67108864}


ar1646v2EthPortSwFOamRemLoopback OBJECT IDENTIFIER ::= {ar1646v2EthPortSwF 912}

ar1646v2EthPortSwFOamRemLoopbackTable OBJECT-TYPE
   SYNTAX      SEQUENCE OF Ar1646v2EthPortSwFOamRemLoopbackEntry
   MAX-ACCESS  not-accessible
   STATUS      current
   DESCRIPTION
      "OAM Remote Loopback"
   ::= {ar1646v2EthPortSwFOamRemLoopback 1}

ar1646v2EthPortSwFOamRemLoopbackEntry OBJECT-TYPE
   SYNTAX      Ar1646v2EthPortSwFOamRemLoopbackEntry
   MAX-ACCESS  not-accessible
   STATUS      current
   DESCRIPTION
      ""
   INDEX      { ar1646v2EthPortSwFOamRemLoopbackGlobalIx }
   ::= {ar1646v2EthPortSwFOamRemLoopbackTable 1}

Ar1646v2EthPortSwFOamRemLoopbackEntry ::=
   SEQUENCE
      {
      ar1646v2EthPortSwFOamRemLoopbackGlobalIx
         GlobalIndex,
      ar1646v2EthPortSwFOamRemLoopbackValue
         Integer32
      }

ar1646v2EthPortSwFOamRemLoopbackGlobalIx OBJECT-TYPE
   SYNTAX      GlobalIndex
   MAX-ACCESS  not-accessible
   STATUS      current
   DESCRIPTION
      "The value of the tlsCntTreeGlobalIndex of the MANAGED OBJECT."
   ::= {ar1646v2EthPortSwFOamRemLoopbackEntry 10}

ar1646v2EthPortSwFOamRemLoopbackValue OBJECT-TYPE
   SYNTAX      Integer32
   MAX-ACCESS  read-write
   STATUS      current
   DESCRIPTION
      "Path: swPort.actions.oamRemLoopback"
   ::= {ar1646v2EthPortSwFOamRemLoopbackEntry 2147483648}


ar1646v2EthPortSwFType OBJECT IDENTIFIER ::= {ar1646v2EthPortSwF 913}

ar1646v2EthPortSwFTypeTable OBJECT-TYPE
   SYNTAX      SEQUENCE OF Ar1646v2EthPortSwFTypeEntry
   MAX-ACCESS  not-accessible
   STATUS      current
   DESCRIPTION
      "OAM Remote Loopback type"
   ::= {ar1646v2EthPortSwFType 1}

ar1646v2EthPortSwFTypeEntry OBJECT-TYPE
   SYNTAX      Ar1646v2EthPortSwFTypeEntry
   MAX-ACCESS  not-accessible
   STATUS      current
   DESCRIPTION
      ""
   INDEX      { ar1646v2EthPortSwFTypeGlobalIx }
   ::= {ar1646v2EthPortSwFTypeTable 1}

Ar1646v2EthPortSwFTypeEntry ::=
   SEQUENCE
      {
      ar1646v2EthPortSwFTypeGlobalIx
         GlobalIndex,
      ar1646v2EthPortSwFTypeValue
         INTEGER
      }

ar1646v2EthPortSwFTypeGlobalIx OBJECT-TYPE
   SYNTAX      GlobalIndex
   MAX-ACCESS  not-accessible
   STATUS      current
   DESCRIPTION
      "The value of the tlsCntTreeGlobalIndex of the MANAGED OBJECT."
   ::= {ar1646v2EthPortSwFTypeEntry 10}

ar1646v2EthPortSwFTypeValue OBJECT-TYPE
   SYNTAX      INTEGER
               {
               start (0),
               stop (1)
               }
   MAX-ACCESS  read-write
   STATUS      current
   DESCRIPTION
      "Path: swPort.actions.type

       Possibilities:
               start   (0)
               stop   (1)"
   ::= {ar1646v2EthPortSwFTypeEntry 2147483648}


ar1646v2EthPortSwFSendWOL OBJECT IDENTIFIER ::= {ar1646v2EthPortSwF 333}

ar1646v2EthPortSwFSendWOLTable OBJECT-TYPE
   SYNTAX      SEQUENCE OF Ar1646v2EthPortSwFSendWOLEntry
   MAX-ACCESS  not-accessible
   STATUS      current
   DESCRIPTION
      "send a WakeOnLan message on this interface"
   ::= {ar1646v2EthPortSwFSendWOL 1}

ar1646v2EthPortSwFSendWOLEntry OBJECT-TYPE
   SYNTAX      Ar1646v2EthPortSwFSendWOLEntry
   MAX-ACCESS  not-accessible
   STATUS      current
   DESCRIPTION
      ""
   INDEX      { ar1646v2EthPortSwFSendWOLGlobalIx }
   ::= {ar1646v2EthPortSwFSendWOLTable 1}

Ar1646v2EthPortSwFSendWOLEntry ::=
   SEQUENCE
      {
      ar1646v2EthPortSwFSendWOLGlobalIx
         GlobalIndex,
      ar1646v2EthPortSwFSendWOLValue
         Integer32
      }

ar1646v2EthPortSwFSendWOLGlobalIx OBJECT-TYPE
   SYNTAX      GlobalIndex
   MAX-ACCESS  not-accessible
   STATUS      current
   DESCRIPTION
      "The value of the tlsCntTreeGlobalIndex of the MANAGED OBJECT."
   ::= {ar1646v2EthPortSwFSendWOLEntry 10}

ar1646v2EthPortSwFSendWOLValue OBJECT-TYPE
   SYNTAX      Integer32
   MAX-ACCESS  read-write
   STATUS      current
   DESCRIPTION
      "Path: swPort.actions.sendWOL"
   ::= {ar1646v2EthPortSwFSendWOLEntry 2147483648}


ar1646v2EthPortSwFWolInfo OBJECT IDENTIFIER ::= {ar1646v2EthPortSwF 332}

ar1646v2EthPortSwFWolInfoSSCTable OBJECT-TYPE
   SYNTAX      SEQUENCE OF Ar1646v2EthPortSwFWolInfoEntry
   MAX-ACCESS  not-accessible
   STATUS      current
   DESCRIPTION
      "content of a WakeOnLan message"
   ::= {ar1646v2EthPortSwFWolInfo 1}

ar1646v2EthPortSwFWolInfoEntry OBJECT-TYPE
   SYNTAX      Ar1646v2EthPortSwFWolInfoEntry
   MAX-ACCESS  not-accessible
   STATUS      current
   DESCRIPTION
      ""
   INDEX      { ar1646v2EthPortSwFWolInfoGlobalIx }
   ::= {ar1646v2EthPortSwFWolInfoSSCTable 1}

Ar1646v2EthPortSwFWolInfoEntry ::=
   SEQUENCE
      {
      ar1646v2EthPortSwFWolInfoGlobalIx
         GlobalIndex,
      ar1646v2EthPortSwFWolInfoTargetMAC
         OCTET STRING,
      ar1646v2EthPortSwFWolInfoPassword
         OCTET STRING
      }

ar1646v2EthPortSwFWolInfoGlobalIx OBJECT-TYPE
   SYNTAX      GlobalIndex
   MAX-ACCESS  not-accessible
   STATUS      current
   DESCRIPTION
      "The value of the tlsCntTreeGlobalIndex of the MANAGED OBJECT."
   ::= {ar1646v2EthPortSwFWolInfoEntry 10}

ar1646v2EthPortSwFWolInfoTargetMAC OBJECT-TYPE
   SYNTAX      OCTET STRING
   MAX-ACCESS  read-write
   STATUS      current
   DESCRIPTION
      "Path: swPort.actions.wolInfo.targetMAC

       MAC address."
   ::= {ar1646v2EthPortSwFWolInfoEntry 16777216}

ar1646v2EthPortSwFWolInfoPassword OBJECT-TYPE
   SYNTAX      OCTET STRING
   MAX-ACCESS  read-write
   STATUS      current
   DESCRIPTION
      "Path: swPort.actions.wolInfo.password"
   ::= {ar1646v2EthPortSwFWolInfoEntry 33554432}


ar1646v2EthPortSwFClearArpCache OBJECT IDENTIFIER ::= {ar1646v2EthPortSwF 25}

ar1646v2EthPortSwFClearArpCacheTable OBJECT-TYPE
   SYNTAX      SEQUENCE OF Ar1646v2EthPortSwFClearArpCacheEntry
   MAX-ACCESS  not-accessible
   STATUS      current
   DESCRIPTION
      "clear all dynamic enties in ARP cache table"
   ::= {ar1646v2EthPortSwFClearArpCache 1}

ar1646v2EthPortSwFClearArpCacheEntry OBJECT-TYPE
   SYNTAX      Ar1646v2EthPortSwFClearArpCacheEntry
   MAX-ACCESS  not-accessible
   STATUS      current
   DESCRIPTION
      ""
   INDEX      { ar1646v2EthPortSwFClearArpCacheGlobalIx }
   ::= {ar1646v2EthPortSwFClearArpCacheTable 1}

Ar1646v2EthPortSwFClearArpCacheEntry ::=
   SEQUENCE
      {
      ar1646v2EthPortSwFClearArpCacheGlobalIx
         GlobalIndex,
      ar1646v2EthPortSwFClearArpCacheValue
         Integer32
      }

ar1646v2EthPortSwFClearArpCacheGlobalIx OBJECT-TYPE
   SYNTAX      GlobalIndex
   MAX-ACCESS  not-accessible
   STATUS      current
   DESCRIPTION
      "The value of the tlsCntTreeGlobalIndex of the MANAGED OBJECT."
   ::= {ar1646v2EthPortSwFClearArpCacheEntry 10}

ar1646v2EthPortSwFClearArpCacheValue OBJECT-TYPE
   SYNTAX      Integer32
   MAX-ACCESS  read-write
   STATUS      current
   DESCRIPTION
      "Path: swPort.actions.clearArpCache"
   ::= {ar1646v2EthPortSwFClearArpCacheEntry 2147483648}



fr1646v2EthPortSwF OBJECT IDENTIFIER ::= {r1646v2EthPortSwF 13}


fr1646v2EthPortSwFAlarm OBJECT IDENTIFIER ::= {fr1646v2EthPortSwF 207}

fr1646v2EthPortSwFAlarmSSCTable OBJECT-TYPE
   SYNTAX      SEQUENCE OF Fr1646v2EthPortSwFAlarmEntry
   MAX-ACCESS  not-accessible
   STATUS      current
   DESCRIPTION
      "IfAlarmInfo"
   ::= {fr1646v2EthPortSwFAlarm 1}

fr1646v2EthPortSwFAlarmEntry OBJECT-TYPE
   SYNTAX      Fr1646v2EthPortSwFAlarmEntry
   MAX-ACCESS  not-accessible
   STATUS      current
   DESCRIPTION
      ""
   INDEX      { fr1646v2EthPortSwFAlarmGlobalIx }
   ::= {fr1646v2EthPortSwFAlarmSSCTable 1}

Fr1646v2EthPortSwFAlarmEntry ::=
   SEQUENCE
      {
      fr1646v2EthPortSwFAlarmGlobalIx
         GlobalIndex,
      fr1646v2EthPortSwFAlarmDiscriminator
         Integer32,
      fr1646v2EthPortSwFAlarmCurrent
         Integer32,
      fr1646v2EthPortSwFAlarmPrevious
         Integer32,
      fr1646v2EthPortSwFAlarmMask
         Integer32,
      fr1646v2EthPortSwFAlarmLevLinkDown
         Integer32,
      fr1646v2EthPortSwFAlarmLevPppoEDown
         Integer32
      }

fr1646v2EthPortSwFAlarmGlobalIx OBJECT-TYPE
   SYNTAX      GlobalIndex
   MAX-ACCESS  not-accessible
   STATUS      current
   DESCRIPTION
      "The value of the tlsCntTreeGlobalIndex of the MANAGED OBJECT."
   ::= {fr1646v2EthPortSwFAlarmEntry 10}

fr1646v2EthPortSwFAlarmDiscriminator OBJECT-TYPE
   SYNTAX      Integer32
   MAX-ACCESS  read-only
   STATUS      current
   DESCRIPTION
      "Path: swPort.alarms.alarmInfo.discriminator"
   ::= {fr1646v2EthPortSwFAlarmEntry 16777216}

fr1646v2EthPortSwFAlarmCurrent OBJECT-TYPE
   SYNTAX      Integer32
   MAX-ACCESS  read-only
   STATUS      current
   DESCRIPTION
      "Path: swPort.alarms.alarmInfo.currentAlarms

       Bit meanings:
               bit 0 = linkDown,
               bit 9 = pppoEDown"
   ::= {fr1646v2EthPortSwFAlarmEntry 33554432}

fr1646v2EthPortSwFAlarmPrevious OBJECT-TYPE
   SYNTAX      Integer32
   MAX-ACCESS  read-only
   STATUS      current
   DESCRIPTION
      "Path: swPort.alarms.alarmInfo.previousAlarms

       Bit meanings:
               bit 0 = linkDown,
               bit 9 = pppoEDown"
   ::= {fr1646v2EthPortSwFAlarmEntry 50331648}

fr1646v2EthPortSwFAlarmMask OBJECT-TYPE
   SYNTAX      Integer32
   MAX-ACCESS  read-only
   STATUS      current
   DESCRIPTION
      "Path: swPort.alarms.alarmInfo.alarmMask

       Bit meanings:
               bit 0 = linkDown,
               bit 9 = pppoEDown"
   ::= {fr1646v2EthPortSwFAlarmEntry 67108864}

fr1646v2EthPortSwFAlarmLevLinkDown OBJECT-TYPE
   SYNTAX      Integer32
   MAX-ACCESS  read-only
   STATUS      current
   DESCRIPTION
      "Path: swPort.alarms.alarmInfo.alarmLevel.linkDown"
   ::= {fr1646v2EthPortSwFAlarmEntry 83951616}

fr1646v2EthPortSwFAlarmLevPppoEDown OBJECT-TYPE
   SYNTAX      Integer32
   MAX-ACCESS  read-only
   STATUS      current
   DESCRIPTION
      "Path: swPort.alarms.alarmInfo.alarmLevel.pppoEDown"
   ::= {fr1646v2EthPortSwFAlarmEntry 84541440}


fr1646v2EthPortSwFAlarmE2 OBJECT IDENTIFIER ::= {fr1646v2EthPortSwFAlarm 2}

fr1646v2EthPortSwFAlarmE2Entry OBJECT IDENTIFIER ::= {fr1646v2EthPortSwFAlarmE2 1}

fr1646v2EthPortSwFAlarmE2LinkDown OBJECT IDENTIFIER ::= {fr1646v2EthPortSwFAlarmE2Entry 10}

fr1646v2EthPortSwFAlarmE2LinkDownPfx OBJECT IDENTIFIER ::= {fr1646v2EthPortSwFAlarmE2LinkDown 0}

fr1646v2EthPortSwFAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwFix'
                (root='router1646') has changed from the ON to the OFF state."
   ::= {fr1646v2EthPortSwFAlarmE2LinkDownPfx 1}

fr1646v2EthPortSwFAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwFix'
                (root='router1646') has changed from the OFF to the ON state."
   ::= {fr1646v2EthPortSwFAlarmE2LinkDownPfx 2}

fr1646v2EthPortSwFAlarmE2PppoEDown OBJECT IDENTIFIER ::= {fr1646v2EthPortSwFAlarmE2Entry 19}

fr1646v2EthPortSwFAlarmE2PppoEDownPfx OBJECT IDENTIFIER ::= {fr1646v2EthPortSwFAlarmE2PppoEDown 0}

fr1646v2EthPortSwFAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwFix'
                (root='router1646') has changed from the ON to the OFF state."
   ::= {fr1646v2EthPortSwFAlarmE2PppoEDownPfx 1}

fr1646v2EthPortSwFAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwFix'
                (root='router1646') has changed from the OFF to the ON state."
   ::= {fr1646v2EthPortSwFAlarmE2PppoEDownPfx 2}



END
