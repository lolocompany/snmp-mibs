OneAccess-R1646v2-4647-PingSession DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2PingSession OBJECT IDENTIFIER ::= {r1646Rootv2 4647}

r1646v2PingSessionMOProp OBJECT-TYPE
   SYNTAX      SEQUENCE OF R1646v2PingSessionMOPropEntry
   MAX-ACCESS  not-accessible
   STATUS      current
   DESCRIPTION
      ""
   ::= {r1646v2PingSession 1}

r1646v2PingSessionMOPropEntry OBJECT-TYPE
   SYNTAX      R1646v2PingSessionMOPropEntry
   MAX-ACCESS  not-accessible
   STATUS      current
   DESCRIPTION
      ""
   INDEX      { r1646v2PingSessionMOPropGlobalIx }
   ::= {r1646v2PingSessionMOProp 1}

R1646v2PingSessionMOPropEntry ::=
   SEQUENCE
      {
      r1646v2PingSessionMOPropPath
         ContainmentPath,
      r1646v2PingSessionMOPropRev
         ObjectRevision,
      r1646v2PingSessionMOPropGlobalIx
         GlobalIndex
      }

r1646v2PingSessionMOPropPath OBJECT-TYPE
   SYNTAX      ContainmentPath
   MAX-ACCESS  read-only
   STATUS      current
   DESCRIPTION
      "Textual description of the containment tree from the instance of
       the root object down to the instance of the current object."
   ::= {r1646v2PingSessionMOPropEntry 3}

r1646v2PingSessionMOPropRev OBJECT-TYPE
   SYNTAX      ObjectRevision
   MAX-ACCESS  read-only
   STATUS      current
   DESCRIPTION
      "This value corresponds with the revision of the MANAGED OBJECT."
   ::= {r1646v2PingSessionMOPropEntry 4}

r1646v2PingSessionMOPropGlobalIx OBJECT-TYPE
   SYNTAX      GlobalIndex
   MAX-ACCESS  read-only
   STATUS      current
   DESCRIPTION
      "The value of the tlsCntTreeGlobalIndex of the MANAGED OBJECT."
   ::= {r1646v2PingSessionMOPropEntry 10}



sr1646v2PingSession OBJECT IDENTIFIER ::= {r1646v2PingSession 14}


sr1646v2PingSessionName OBJECT IDENTIFIER ::= {sr1646v2PingSession 1218}

sr1646v2PingSessionNameTable OBJECT-TYPE
   SYNTAX      SEQUENCE OF Sr1646v2PingSessionNameEntry
   MAX-ACCESS  not-accessible
   STATUS      current
   DESCRIPTION
      ""
   ::= {sr1646v2PingSessionName 1}

sr1646v2PingSessionNameEntry OBJECT-TYPE
   SYNTAX      Sr1646v2PingSessionNameEntry
   MAX-ACCESS  not-accessible
   STATUS      current
   DESCRIPTION
      ""
   INDEX      { sr1646v2PingSessionNameGlobalIx }
   ::= {sr1646v2PingSessionNameTable 1}

Sr1646v2PingSessionNameEntry ::=
   SEQUENCE
      {
      sr1646v2PingSessionNameGlobalIx
         GlobalIndex,
      sr1646v2PingSessionNameValue
         DisplayString
      }

sr1646v2PingSessionNameGlobalIx OBJECT-TYPE
   SYNTAX      GlobalIndex
   MAX-ACCESS  not-accessible
   STATUS      current
   DESCRIPTION
      "The value of the tlsCntTreeGlobalIndex of the MANAGED OBJECT."
   ::= {sr1646v2PingSessionNameEntry 10}

sr1646v2PingSessionNameValue OBJECT-TYPE
   SYNTAX      DisplayString
   MAX-ACCESS  read-only
   STATUS      current
   DESCRIPTION
      "Path: session.status.name"
   ::= {sr1646v2PingSessionNameEntry 2147483648}


sr1646v2PingSessionGlobalStartDate OBJECT IDENTIFIER ::= {sr1646v2PingSession 1217}

sr1646v2PingSessionGlobalStartDateTable OBJECT-TYPE
   SYNTAX      SEQUENCE OF Sr1646v2PingSessionGlobalStartDateEntry
   MAX-ACCESS  not-accessible
   STATUS      current
   DESCRIPTION
      ""
   ::= {sr1646v2PingSessionGlobalStartDate 1}

sr1646v2PingSessionGlobalStartDateEntry OBJECT-TYPE
   SYNTAX      Sr1646v2PingSessionGlobalStartDateEntry
   MAX-ACCESS  not-accessible
   STATUS      current
   DESCRIPTION
      ""
   INDEX      { sr1646v2PingSessionGlobalStartDateGlobalIx }
   ::= {sr1646v2PingSessionGlobalStartDateTable 1}

Sr1646v2PingSessionGlobalStartDateEntry ::=
   SEQUENCE
      {
      sr1646v2PingSessionGlobalStartDateGlobalIx
         GlobalIndex,
      sr1646v2PingSessionGlobalStartDateValue
         DisplayString
      }

sr1646v2PingSessionGlobalStartDateGlobalIx OBJECT-TYPE
   SYNTAX      GlobalIndex
   MAX-ACCESS  not-accessible
   STATUS      current
   DESCRIPTION
      "The value of the tlsCntTreeGlobalIndex of the MANAGED OBJECT."
   ::= {sr1646v2PingSessionGlobalStartDateEntry 10}

sr1646v2PingSessionGlobalStartDateValue OBJECT-TYPE
   SYNTAX      DisplayString
   MAX-ACCESS  read-only
   STATUS      current
   DESCRIPTION
      "Path: session.status.globalStartDate"
   ::= {sr1646v2PingSessionGlobalStartDateEntry 2147483648}


sr1646v2PingSessionStatus OBJECT IDENTIFIER ::= {sr1646v2PingSession 1140}

sr1646v2PingSessionStatusTable OBJECT-TYPE
   SYNTAX      SEQUENCE OF Sr1646v2PingSessionStatusEntry
   MAX-ACCESS  not-accessible
   STATUS      current
   DESCRIPTION
      ""
   ::= {sr1646v2PingSessionStatus 1}

sr1646v2PingSessionStatusEntry OBJECT-TYPE
   SYNTAX      Sr1646v2PingSessionStatusEntry
   MAX-ACCESS  not-accessible
   STATUS      current
   DESCRIPTION
      ""
   INDEX      { sr1646v2PingSessionStatusGlobalIx }
   ::= {sr1646v2PingSessionStatusTable 1}

Sr1646v2PingSessionStatusEntry ::=
   SEQUENCE
      {
      sr1646v2PingSessionStatusGlobalIx
         GlobalIndex,
      sr1646v2PingSessionStatusValue
         INTEGER
      }

sr1646v2PingSessionStatusGlobalIx OBJECT-TYPE
   SYNTAX      GlobalIndex
   MAX-ACCESS  not-accessible
   STATUS      current
   DESCRIPTION
      "The value of the tlsCntTreeGlobalIndex of the MANAGED OBJECT."
   ::= {sr1646v2PingSessionStatusEntry 10}

sr1646v2PingSessionStatusValue OBJECT-TYPE
   SYNTAX      INTEGER
               {
               idle (128),
               destinationProblem (40),
               openSocketProblem (41),
               logProblem (42),
               waitHalfDuplexSetup (2),
               waitGroup (3),
               waitDns (4),
               waitDnsStart (5),
               releaseSocket (6),
               waitForRepeat (7),
               runFlood (11),
               runAsymFlood (12),
               runNormal (13),
               runBandwidth (14),
               runPacketsASec (15),
               haltedFlood (21),
               haltedAsymFlood (22),
               haltedNormal (23),
               haltedBandwidth (24),
               haltedPacketsASec (25),
               optimumFlood (31),
               optimumAsymFlood (32),
               optimumNormal (33),
               optimumBandwidth (34),
               optimumPacketsASec (35),
               problemHaltedFlood (26),
               problemHaltedAsymFlood (27),
               problemHaltedNormal (28),
               problemHaltedBandwidth (29),
               problemHaltedPacketsASec (30),
               testRunFlood (51),
               testRunAsymFlood (52),
               testRunNormal (53),
               testRunBandwidth (54),
               testRunPacketsASec (55),
               testReleaseSocket (56),
               testWaitForRepeat (57),
               testHaltedFlood (61),
               testHaltedAsymFlood (62),
               testHaltedNormal (63),
               testHaltedBandwidth (64),
               testHaltedPacketsASec (65)
               }
   MAX-ACCESS  read-only
   STATUS      current
   DESCRIPTION
      "Path: session.status.status

       Possibilities:
               idle   (128)
               destinationProblem   (40)
               openSocketProblem   (41)
               logProblem   (42)
               waitHalfDuplexSetup   (2)
               waitGroup   (3)
               waitDns   (4)
               waitDnsStart   (5)
               releaseSocket   (6)
               waitForRepeat   (7)
               runFlood   (11)
               runAsymFlood   (12)
               runNormal   (13)
               runBandwidth   (14)
               runPacketsASec   (15)
               haltedFlood   (21)
               haltedAsymFlood   (22)
               haltedNormal   (23)
               haltedBandwidth   (24)
               haltedPacketsASec   (25)
               optimumFlood   (31)
               optimumAsymFlood   (32)
               optimumNormal   (33)
               optimumBandwidth   (34)
               optimumPacketsASec   (35)
               problemHaltedFlood   (26)
               problemHaltedAsymFlood   (27)
               problemHaltedNormal   (28)
               problemHaltedBandwidth   (29)
               problemHaltedPacketsASec   (30)
               testRunFlood   (51)
               testRunAsymFlood   (52)
               testRunNormal   (53)
               testRunBandwidth   (54)
               testRunPacketsASec   (55)
               testReleaseSocket   (56)
               testWaitForRepeat   (57)
               testHaltedFlood   (61)
               testHaltedAsymFlood   (62)
               testHaltedNormal   (63)
               testHaltedBandwidth   (64)
               testHaltedPacketsASec   (65)"
   ::= {sr1646v2PingSessionStatusEntry 2147483648}


sr1646v2PingSessionDuration OBJECT IDENTIFIER ::= {sr1646v2PingSession 1141}

sr1646v2PingSessionDurationTable OBJECT-TYPE
   SYNTAX      SEQUENCE OF Sr1646v2PingSessionDurationEntry
   MAX-ACCESS  not-accessible
   STATUS      current
   DESCRIPTION
      ""
   ::= {sr1646v2PingSessionDuration 1}

sr1646v2PingSessionDurationEntry OBJECT-TYPE
   SYNTAX      Sr1646v2PingSessionDurationEntry
   MAX-ACCESS  not-accessible
   STATUS      current
   DESCRIPTION
      ""
   INDEX      { sr1646v2PingSessionDurationGlobalIx }
   ::= {sr1646v2PingSessionDurationTable 1}

Sr1646v2PingSessionDurationEntry ::=
   SEQUENCE
      {
      sr1646v2PingSessionDurationGlobalIx
         GlobalIndex,
      sr1646v2PingSessionDurationValue
         TimeTicks
      }

sr1646v2PingSessionDurationGlobalIx OBJECT-TYPE
   SYNTAX      GlobalIndex
   MAX-ACCESS  not-accessible
   STATUS      current
   DESCRIPTION
      "The value of the tlsCntTreeGlobalIndex of the MANAGED OBJECT."
   ::= {sr1646v2PingSessionDurationEntry 10}

sr1646v2PingSessionDurationValue OBJECT-TYPE
   SYNTAX      TimeTicks
   MAX-ACCESS  read-only
   STATUS      current
   DESCRIPTION
      "Path: session.status.duration

       Time in centi-second."
   ::= {sr1646v2PingSessionDurationEntry 2147483648}


sr1646v2PingSessionStartDate OBJECT IDENTIFIER ::= {sr1646v2PingSession 1142}

sr1646v2PingSessionStartDateTable OBJECT-TYPE
   SYNTAX      SEQUENCE OF Sr1646v2PingSessionStartDateEntry
   MAX-ACCESS  not-accessible
   STATUS      current
   DESCRIPTION
      ""
   ::= {sr1646v2PingSessionStartDate 1}

sr1646v2PingSessionStartDateEntry OBJECT-TYPE
   SYNTAX      Sr1646v2PingSessionStartDateEntry
   MAX-ACCESS  not-accessible
   STATUS      current
   DESCRIPTION
      ""
   INDEX      { sr1646v2PingSessionStartDateGlobalIx }
   ::= {sr1646v2PingSessionStartDateTable 1}

Sr1646v2PingSessionStartDateEntry ::=
   SEQUENCE
      {
      sr1646v2PingSessionStartDateGlobalIx
         GlobalIndex,
      sr1646v2PingSessionStartDateValue
         DisplayString
      }

sr1646v2PingSessionStartDateGlobalIx OBJECT-TYPE
   SYNTAX      GlobalIndex
   MAX-ACCESS  not-accessible
   STATUS      current
   DESCRIPTION
      "The value of the tlsCntTreeGlobalIndex of the MANAGED OBJECT."
   ::= {sr1646v2PingSessionStartDateEntry 10}

sr1646v2PingSessionStartDateValue OBJECT-TYPE
   SYNTAX      DisplayString
   MAX-ACCESS  read-only
   STATUS      current
   DESCRIPTION
      "Path: session.status.startDate"
   ::= {sr1646v2PingSessionStartDateEntry 2147483648}


sr1646v2PingSessionEndDate OBJECT IDENTIFIER ::= {sr1646v2PingSession 1143}

sr1646v2PingSessionEndDateTable OBJECT-TYPE
   SYNTAX      SEQUENCE OF Sr1646v2PingSessionEndDateEntry
   MAX-ACCESS  not-accessible
   STATUS      current
   DESCRIPTION
      ""
   ::= {sr1646v2PingSessionEndDate 1}

sr1646v2PingSessionEndDateEntry OBJECT-TYPE
   SYNTAX      Sr1646v2PingSessionEndDateEntry
   MAX-ACCESS  not-accessible
   STATUS      current
   DESCRIPTION
      ""
   INDEX      { sr1646v2PingSessionEndDateGlobalIx }
   ::= {sr1646v2PingSessionEndDateTable 1}

Sr1646v2PingSessionEndDateEntry ::=
   SEQUENCE
      {
      sr1646v2PingSessionEndDateGlobalIx
         GlobalIndex,
      sr1646v2PingSessionEndDateValue
         DisplayString
      }

sr1646v2PingSessionEndDateGlobalIx OBJECT-TYPE
   SYNTAX      GlobalIndex
   MAX-ACCESS  not-accessible
   STATUS      current
   DESCRIPTION
      "The value of the tlsCntTreeGlobalIndex of the MANAGED OBJECT."
   ::= {sr1646v2PingSessionEndDateEntry 10}

sr1646v2PingSessionEndDateValue OBJECT-TYPE
   SYNTAX      DisplayString
   MAX-ACCESS  read-only
   STATUS      current
   DESCRIPTION
      "Path: session.status.endDate"
   ::= {sr1646v2PingSessionEndDateEntry 2147483648}


sr1646v2PingSessionDestination OBJECT IDENTIFIER ::= {sr1646v2PingSession 1199}

sr1646v2PingSessionDestinationTable OBJECT-TYPE
   SYNTAX      SEQUENCE OF Sr1646v2PingSessionDestinationEntry
   MAX-ACCESS  not-accessible
   STATUS      current
   DESCRIPTION
      ""
   ::= {sr1646v2PingSessionDestination 1}

sr1646v2PingSessionDestinationEntry OBJECT-TYPE
   SYNTAX      Sr1646v2PingSessionDestinationEntry
   MAX-ACCESS  not-accessible
   STATUS      current
   DESCRIPTION
      ""
   INDEX      { sr1646v2PingSessionDestinationGlobalIx }
   ::= {sr1646v2PingSessionDestinationTable 1}

Sr1646v2PingSessionDestinationEntry ::=
   SEQUENCE
      {
      sr1646v2PingSessionDestinationGlobalIx
         GlobalIndex,
      sr1646v2PingSessionDestinationValue
         DisplayString
      }

sr1646v2PingSessionDestinationGlobalIx OBJECT-TYPE
   SYNTAX      GlobalIndex
   MAX-ACCESS  not-accessible
   STATUS      current
   DESCRIPTION
      "The value of the tlsCntTreeGlobalIndex of the MANAGED OBJECT."
   ::= {sr1646v2PingSessionDestinationEntry 10}

sr1646v2PingSessionDestinationValue OBJECT-TYPE
   SYNTAX      DisplayString
   MAX-ACCESS  read-only
   STATUS      current
   DESCRIPTION
      "Path: session.status.destination"
   ::= {sr1646v2PingSessionDestinationEntry 2147483648}


sr1646v2PingSessionFromSize OBJECT IDENTIFIER ::= {sr1646v2PingSession 1208}

sr1646v2PingSessionFromSizeTable OBJECT-TYPE
   SYNTAX      SEQUENCE OF Sr1646v2PingSessionFromSizeEntry
   MAX-ACCESS  not-accessible
   STATUS      current
   DESCRIPTION
      ""
   ::= {sr1646v2PingSessionFromSize 1}

sr1646v2PingSessionFromSizeEntry OBJECT-TYPE
   SYNTAX      Sr1646v2PingSessionFromSizeEntry
   MAX-ACCESS  not-accessible
   STATUS      current
   DESCRIPTION
      ""
   INDEX      { sr1646v2PingSessionFromSizeGlobalIx }
   ::= {sr1646v2PingSessionFromSizeTable 1}

Sr1646v2PingSessionFromSizeEntry ::=
   SEQUENCE
      {
      sr1646v2PingSessionFromSizeGlobalIx
         GlobalIndex,
      sr1646v2PingSessionFromSizeValue
         Integer32
      }

sr1646v2PingSessionFromSizeGlobalIx OBJECT-TYPE
   SYNTAX      GlobalIndex
   MAX-ACCESS  not-accessible
   STATUS      current
   DESCRIPTION
      "The value of the tlsCntTreeGlobalIndex of the MANAGED OBJECT."
   ::= {sr1646v2PingSessionFromSizeEntry 10}

sr1646v2PingSessionFromSizeValue OBJECT-TYPE
   SYNTAX      Integer32
   MAX-ACCESS  read-only
   STATUS      current
   DESCRIPTION
      "Path: session.status.fromSize"
   ::= {sr1646v2PingSessionFromSizeEntry 2147483648}


sr1646v2PingSessionToSize OBJECT IDENTIFIER ::= {sr1646v2PingSession 1209}

sr1646v2PingSessionToSizeTable OBJECT-TYPE
   SYNTAX      SEQUENCE OF Sr1646v2PingSessionToSizeEntry
   MAX-ACCESS  not-accessible
   STATUS      current
   DESCRIPTION
      ""
   ::= {sr1646v2PingSessionToSize 1}

sr1646v2PingSessionToSizeEntry OBJECT-TYPE
   SYNTAX      Sr1646v2PingSessionToSizeEntry
   MAX-ACCESS  not-accessible
   STATUS      current
   DESCRIPTION
      ""
   INDEX      { sr1646v2PingSessionToSizeGlobalIx }
   ::= {sr1646v2PingSessionToSizeTable 1}

Sr1646v2PingSessionToSizeEntry ::=
   SEQUENCE
      {
      sr1646v2PingSessionToSizeGlobalIx
         GlobalIndex,
      sr1646v2PingSessionToSizeValue
         INTEGER
      }

sr1646v2PingSessionToSizeGlobalIx OBJECT-TYPE
   SYNTAX      GlobalIndex
   MAX-ACCESS  not-accessible
   STATUS      current
   DESCRIPTION
      "The value of the tlsCntTreeGlobalIndex of the MANAGED OBJECT."
   ::= {sr1646v2PingSessionToSizeEntry 10}

sr1646v2PingSessionToSizeValue OBJECT-TYPE
   SYNTAX      INTEGER
               {
               slnotsinsuseg (-1)
               }
   MAX-ACCESS  read-only
   STATUS      current
   DESCRIPTION
      "Path: session.status.toSize

       Possibilities:
               <not in use>   (-1)"
   ::= {sr1646v2PingSessionToSizeEntry 2147483648}


sr1646v2PingSessionSizeType OBJECT IDENTIFIER ::= {sr1646v2PingSession 1210}

sr1646v2PingSessionSizeTypeTable OBJECT-TYPE
   SYNTAX      SEQUENCE OF Sr1646v2PingSessionSizeTypeEntry
   MAX-ACCESS  not-accessible
   STATUS      current
   DESCRIPTION
      ""
   ::= {sr1646v2PingSessionSizeType 1}

sr1646v2PingSessionSizeTypeEntry OBJECT-TYPE
   SYNTAX      Sr1646v2PingSessionSizeTypeEntry
   MAX-ACCESS  not-accessible
   STATUS      current
   DESCRIPTION
      ""
   INDEX      { sr1646v2PingSessionSizeTypeGlobalIx }
   ::= {sr1646v2PingSessionSizeTypeTable 1}

Sr1646v2PingSessionSizeTypeEntry ::=
   SEQUENCE
      {
      sr1646v2PingSessionSizeTypeGlobalIx
         GlobalIndex,
      sr1646v2PingSessionSizeTypeValue
         INTEGER
      }

sr1646v2PingSessionSizeTypeGlobalIx OBJECT-TYPE
   SYNTAX      GlobalIndex
   MAX-ACCESS  not-accessible
   STATUS      current
   DESCRIPTION
      "The value of the tlsCntTreeGlobalIndex of the MANAGED OBJECT."
   ::= {sr1646v2PingSessionSizeTypeEntry 10}

sr1646v2PingSessionSizeTypeValue OBJECT-TYPE
   SYNTAX      INTEGER
               {
               single (1),
               range (2),
               toggle (3)
               }
   MAX-ACCESS  read-only
   STATUS      current
   DESCRIPTION
      "Path: session.status.sizeType

       Possibilities:
               single   (1)
               range   (2)
               toggle   (3)"
   ::= {sr1646v2PingSessionSizeTypeEntry 2147483648}


sr1646v2PingSessionTimeOut OBJECT IDENTIFIER ::= {sr1646v2PingSession 1211}

sr1646v2PingSessionTimeOutTable OBJECT-TYPE
   SYNTAX      SEQUENCE OF Sr1646v2PingSessionTimeOutEntry
   MAX-ACCESS  not-accessible
   STATUS      current
   DESCRIPTION
      ""
   ::= {sr1646v2PingSessionTimeOut 1}

sr1646v2PingSessionTimeOutEntry OBJECT-TYPE
   SYNTAX      Sr1646v2PingSessionTimeOutEntry
   MAX-ACCESS  not-accessible
   STATUS      current
   DESCRIPTION
      ""
   INDEX      { sr1646v2PingSessionTimeOutGlobalIx }
   ::= {sr1646v2PingSessionTimeOutTable 1}

Sr1646v2PingSessionTimeOutEntry ::=
   SEQUENCE
      {
      sr1646v2PingSessionTimeOutGlobalIx
         GlobalIndex,
      sr1646v2PingSessionTimeOutValue
         Integer32
      }

sr1646v2PingSessionTimeOutGlobalIx OBJECT-TYPE
   SYNTAX      GlobalIndex
   MAX-ACCESS  not-accessible
   STATUS      current
   DESCRIPTION
      "The value of the tlsCntTreeGlobalIndex of the MANAGED OBJECT."
   ::= {sr1646v2PingSessionTimeOutEntry 10}

sr1646v2PingSessionTimeOutValue OBJECT-TYPE
   SYNTAX      Integer32
   MAX-ACCESS  read-only
   STATUS      current
   DESCRIPTION
      "Path: session.status.timeOut"
   ::= {sr1646v2PingSessionTimeOutEntry 2147483648}


sr1646v2PingSessionRepeatCount OBJECT IDENTIFIER ::= {sr1646v2PingSession 1214}

sr1646v2PingSessionRepeatCountTable OBJECT-TYPE
   SYNTAX      SEQUENCE OF Sr1646v2PingSessionRepeatCountEntry
   MAX-ACCESS  not-accessible
   STATUS      current
   DESCRIPTION
      ""
   ::= {sr1646v2PingSessionRepeatCount 1}

sr1646v2PingSessionRepeatCountEntry OBJECT-TYPE
   SYNTAX      Sr1646v2PingSessionRepeatCountEntry
   MAX-ACCESS  not-accessible
   STATUS      current
   DESCRIPTION
      ""
   INDEX      { sr1646v2PingSessionRepeatCountGlobalIx }
   ::= {sr1646v2PingSessionRepeatCountTable 1}

Sr1646v2PingSessionRepeatCountEntry ::=
   SEQUENCE
      {
      sr1646v2PingSessionRepeatCountGlobalIx
         GlobalIndex,
      sr1646v2PingSessionRepeatCountValue
         Integer32
      }

sr1646v2PingSessionRepeatCountGlobalIx OBJECT-TYPE
   SYNTAX      GlobalIndex
   MAX-ACCESS  not-accessible
   STATUS      current
   DESCRIPTION
      "The value of the tlsCntTreeGlobalIndex of the MANAGED OBJECT."
   ::= {sr1646v2PingSessionRepeatCountEntry 10}

sr1646v2PingSessionRepeatCountValue OBJECT-TYPE
   SYNTAX      Integer32
   MAX-ACCESS  read-only
   STATUS      current
   DESCRIPTION
      "Path: session.status.repeatCount"
   ::= {sr1646v2PingSessionRepeatCountEntry 2147483648}


sr1646v2PingSessionTimeBetween OBJECT IDENTIFIER ::= {sr1646v2PingSession 1206}

sr1646v2PingSessionTimeBetweenTable OBJECT-TYPE
   SYNTAX      SEQUENCE OF Sr1646v2PingSessionTimeBetweenEntry
   MAX-ACCESS  not-accessible
   STATUS      current
   DESCRIPTION
      ""
   ::= {sr1646v2PingSessionTimeBetween 1}

sr1646v2PingSessionTimeBetweenEntry OBJECT-TYPE
   SYNTAX      Sr1646v2PingSessionTimeBetweenEntry
   MAX-ACCESS  not-accessible
   STATUS      current
   DESCRIPTION
      ""
   INDEX      { sr1646v2PingSessionTimeBetweenGlobalIx }
   ::= {sr1646v2PingSessionTimeBetweenTable 1}

Sr1646v2PingSessionTimeBetweenEntry ::=
   SEQUENCE
      {
      sr1646v2PingSessionTimeBetweenGlobalIx
         GlobalIndex,
      sr1646v2PingSessionTimeBetweenValue
         INTEGER
      }

sr1646v2PingSessionTimeBetweenGlobalIx OBJECT-TYPE
   SYNTAX      GlobalIndex
   MAX-ACCESS  not-accessible
   STATUS      current
   DESCRIPTION
      "The value of the tlsCntTreeGlobalIndex of the MANAGED OBJECT."
   ::= {sr1646v2PingSessionTimeBetweenEntry 10}

sr1646v2PingSessionTimeBetweenValue OBJECT-TYPE
   SYNTAX      INTEGER
               {
               slnotsinsuseg (-1)
               }
   MAX-ACCESS  read-only
   STATUS      current
   DESCRIPTION
      "Path: session.status.timeBetween

       Possibilities:
               <not in use>   (-1)"
   ::= {sr1646v2PingSessionTimeBetweenEntry 2147483648}


sr1646v2PingSessionBandwidth OBJECT IDENTIFIER ::= {sr1646v2PingSession 1207}

sr1646v2PingSessionBandwidthTable OBJECT-TYPE
   SYNTAX      SEQUENCE OF Sr1646v2PingSessionBandwidthEntry
   MAX-ACCESS  not-accessible
   STATUS      current
   DESCRIPTION
      ""
   ::= {sr1646v2PingSessionBandwidth 1}

sr1646v2PingSessionBandwidthEntry OBJECT-TYPE
   SYNTAX      Sr1646v2PingSessionBandwidthEntry
   MAX-ACCESS  not-accessible
   STATUS      current
   DESCRIPTION
      ""
   INDEX      { sr1646v2PingSessionBandwidthGlobalIx }
   ::= {sr1646v2PingSessionBandwidthTable 1}

Sr1646v2PingSessionBandwidthEntry ::=
   SEQUENCE
      {
      sr1646v2PingSessionBandwidthGlobalIx
         GlobalIndex,
      sr1646v2PingSessionBandwidthValue
         INTEGER
      }

sr1646v2PingSessionBandwidthGlobalIx OBJECT-TYPE
   SYNTAX      GlobalIndex
   MAX-ACCESS  not-accessible
   STATUS      current
   DESCRIPTION
      "The value of the tlsCntTreeGlobalIndex of the MANAGED OBJECT."
   ::= {sr1646v2PingSessionBandwidthEntry 10}

sr1646v2PingSessionBandwidthValue OBJECT-TYPE
   SYNTAX      INTEGER
               {
               slnotsinsuseg (-1)
               }
   MAX-ACCESS  read-only
   STATUS      current
   DESCRIPTION
      "Path: session.status.bandwidth

       Possibilities:
               <not in use>   (-1)"
   ::= {sr1646v2PingSessionBandwidthEntry 2147483648}


sr1646v2PingSessionPacketsASec OBJECT IDENTIFIER ::= {sr1646v2PingSession 1215}

sr1646v2PingSessionPacketsASecTable OBJECT-TYPE
   SYNTAX      SEQUENCE OF Sr1646v2PingSessionPacketsASecEntry
   MAX-ACCESS  not-accessible
   STATUS      current
   DESCRIPTION
      ""
   ::= {sr1646v2PingSessionPacketsASec 1}

sr1646v2PingSessionPacketsASecEntry OBJECT-TYPE
   SYNTAX      Sr1646v2PingSessionPacketsASecEntry
   MAX-ACCESS  not-accessible
   STATUS      current
   DESCRIPTION
      ""
   INDEX      { sr1646v2PingSessionPacketsASecGlobalIx }
   ::= {sr1646v2PingSessionPacketsASecTable 1}

Sr1646v2PingSessionPacketsASecEntry ::=
   SEQUENCE
      {
      sr1646v2PingSessionPacketsASecGlobalIx
         GlobalIndex,
      sr1646v2PingSessionPacketsASecValue
         INTEGER
      }

sr1646v2PingSessionPacketsASecGlobalIx OBJECT-TYPE
   SYNTAX      GlobalIndex
   MAX-ACCESS  not-accessible
   STATUS      current
   DESCRIPTION
      "The value of the tlsCntTreeGlobalIndex of the MANAGED OBJECT."
   ::= {sr1646v2PingSessionPacketsASecEntry 10}

sr1646v2PingSessionPacketsASecValue OBJECT-TYPE
   SYNTAX      INTEGER
               {
               slnotsinsuseg (-1)
               }
   MAX-ACCESS  read-only
   STATUS      current
   DESCRIPTION
      "Path: session.status.packetsASec

       Possibilities:
               <not in use>   (-1)"
   ::= {sr1646v2PingSessionPacketsASecEntry 2147483648}


sr1646v2PingSessionTxTc OBJECT IDENTIFIER ::= {sr1646v2PingSession 1219}

sr1646v2PingSessionTxTcTable OBJECT-TYPE
   SYNTAX      SEQUENCE OF Sr1646v2PingSessionTxTcEntry
   MAX-ACCESS  not-accessible
   STATUS      current
   DESCRIPTION
      ""
   ::= {sr1646v2PingSessionTxTc 1}

sr1646v2PingSessionTxTcEntry OBJECT-TYPE
   SYNTAX      Sr1646v2PingSessionTxTcEntry
   MAX-ACCESS  not-accessible
   STATUS      current
   DESCRIPTION
      ""
   INDEX      { sr1646v2PingSessionTxTcGlobalIx }
   ::= {sr1646v2PingSessionTxTcTable 1}

Sr1646v2PingSessionTxTcEntry ::=
   SEQUENCE
      {
      sr1646v2PingSessionTxTcGlobalIx
         GlobalIndex,
      sr1646v2PingSessionTxTcValue
         INTEGER
      }

sr1646v2PingSessionTxTcGlobalIx OBJECT-TYPE
   SYNTAX      GlobalIndex
   MAX-ACCESS  not-accessible
   STATUS      current
   DESCRIPTION
      "The value of the tlsCntTreeGlobalIndex of the MANAGED OBJECT."
   ::= {sr1646v2PingSessionTxTcEntry 10}

sr1646v2PingSessionTxTcValue OBJECT-TYPE
   SYNTAX      INTEGER
               {
               slnotsinsuseg (-1)
               }
   UNITS       "us"
   MAX-ACCESS  read-only
   STATUS      current
   DESCRIPTION
      "Path: session.status.txTc

       unit name = us

       Possibilities:
               <not in use>   (-1)"
   ::= {sr1646v2PingSessionTxTcEntry 2147483648}


sr1646v2PingSessionOutStanding OBJECT IDENTIFIER ::= {sr1646v2PingSession 1203}

sr1646v2PingSessionOutStandingTable OBJECT-TYPE
   SYNTAX      SEQUENCE OF Sr1646v2PingSessionOutStandingEntry
   MAX-ACCESS  not-accessible
   STATUS      current
   DESCRIPTION
      ""
   ::= {sr1646v2PingSessionOutStanding 1}

sr1646v2PingSessionOutStandingEntry OBJECT-TYPE
   SYNTAX      Sr1646v2PingSessionOutStandingEntry
   MAX-ACCESS  not-accessible
   STATUS      current
   DESCRIPTION
      ""
   INDEX      { sr1646v2PingSessionOutStandingGlobalIx }
   ::= {sr1646v2PingSessionOutStandingTable 1}

Sr1646v2PingSessionOutStandingEntry ::=
   SEQUENCE
      {
      sr1646v2PingSessionOutStandingGlobalIx
         GlobalIndex,
      sr1646v2PingSessionOutStandingValue
         INTEGER
      }

sr1646v2PingSessionOutStandingGlobalIx OBJECT-TYPE
   SYNTAX      GlobalIndex
   MAX-ACCESS  not-accessible
   STATUS      current
   DESCRIPTION
      "The value of the tlsCntTreeGlobalIndex of the MANAGED OBJECT."
   ::= {sr1646v2PingSessionOutStandingEntry 10}

sr1646v2PingSessionOutStandingValue OBJECT-TYPE
   SYNTAX      INTEGER
               {
               slnotsinsuseg (-1)
               }
   MAX-ACCESS  read-only
   STATUS      current
   DESCRIPTION
      "Path: session.status.outStanding

       Possibilities:
               <not in use>   (-1)"
   ::= {sr1646v2PingSessionOutStandingEntry 2147483648}


sr1646v2PingSessionSameSequence OBJECT IDENTIFIER ::= {sr1646v2PingSession 1202}

sr1646v2PingSessionSameSequenceTable OBJECT-TYPE
   SYNTAX      SEQUENCE OF Sr1646v2PingSessionSameSequenceEntry
   MAX-ACCESS  not-accessible
   STATUS      current
   DESCRIPTION
      ""
   ::= {sr1646v2PingSessionSameSequence 1}

sr1646v2PingSessionSameSequenceEntry OBJECT-TYPE
   SYNTAX      Sr1646v2PingSessionSameSequenceEntry
   MAX-ACCESS  not-accessible
   STATUS      current
   DESCRIPTION
      ""
   INDEX      { sr1646v2PingSessionSameSequenceGlobalIx }
   ::= {sr1646v2PingSessionSameSequenceTable 1}

Sr1646v2PingSessionSameSequenceEntry ::=
   SEQUENCE
      {
      sr1646v2PingSessionSameSequenceGlobalIx
         GlobalIndex,
      sr1646v2PingSessionSameSequenceValue
         INTEGER
      }

sr1646v2PingSessionSameSequenceGlobalIx OBJECT-TYPE
   SYNTAX      GlobalIndex
   MAX-ACCESS  not-accessible
   STATUS      current
   DESCRIPTION
      "The value of the tlsCntTreeGlobalIndex of the MANAGED OBJECT."
   ::= {sr1646v2PingSessionSameSequenceEntry 10}

sr1646v2PingSessionSameSequenceValue OBJECT-TYPE
   SYNTAX      INTEGER
               {
               slnotsinsuseg (-1)
               }
   MAX-ACCESS  read-only
   STATUS      current
   DESCRIPTION
      "Path: session.status.sameSequence

       Possibilities:
               <not in use>   (-1)"
   ::= {sr1646v2PingSessionSameSequenceEntry 2147483648}


sr1646v2PingSessionTestTime OBJECT IDENTIFIER ::= {sr1646v2PingSession 1204}

sr1646v2PingSessionTestTimeTable OBJECT-TYPE
   SYNTAX      SEQUENCE OF Sr1646v2PingSessionTestTimeEntry
   MAX-ACCESS  not-accessible
   STATUS      current
   DESCRIPTION
      ""
   ::= {sr1646v2PingSessionTestTime 1}

sr1646v2PingSessionTestTimeEntry OBJECT-TYPE
   SYNTAX      Sr1646v2PingSessionTestTimeEntry
   MAX-ACCESS  not-accessible
   STATUS      current
   DESCRIPTION
      ""
   INDEX      { sr1646v2PingSessionTestTimeGlobalIx }
   ::= {sr1646v2PingSessionTestTimeTable 1}

Sr1646v2PingSessionTestTimeEntry ::=
   SEQUENCE
      {
      sr1646v2PingSessionTestTimeGlobalIx
         GlobalIndex,
      sr1646v2PingSessionTestTimeValue
         INTEGER
      }

sr1646v2PingSessionTestTimeGlobalIx OBJECT-TYPE
   SYNTAX      GlobalIndex
   MAX-ACCESS  not-accessible
   STATUS      current
   DESCRIPTION
      "The value of the tlsCntTreeGlobalIndex of the MANAGED OBJECT."
   ::= {sr1646v2PingSessionTestTimeEntry 10}

sr1646v2PingSessionTestTimeValue OBJECT-TYPE
   SYNTAX      INTEGER
               {
               slnotsinsuseg (-1)
               }
   MAX-ACCESS  read-only
   STATUS      current
   DESCRIPTION
      "Path: session.status.testTime

       Possibilities:
               <not in use>   (-1)"
   ::= {sr1646v2PingSessionTestTimeEntry 2147483648}


sr1646v2PingSessionNrPackets OBJECT IDENTIFIER ::= {sr1646v2PingSession 1205}

sr1646v2PingSessionNrPacketsTable OBJECT-TYPE
   SYNTAX      SEQUENCE OF Sr1646v2PingSessionNrPacketsEntry
   MAX-ACCESS  not-accessible
   STATUS      current
   DESCRIPTION
      ""
   ::= {sr1646v2PingSessionNrPackets 1}

sr1646v2PingSessionNrPacketsEntry OBJECT-TYPE
   SYNTAX      Sr1646v2PingSessionNrPacketsEntry
   MAX-ACCESS  not-accessible
   STATUS      current
   DESCRIPTION
      ""
   INDEX      { sr1646v2PingSessionNrPacketsGlobalIx }
   ::= {sr1646v2PingSessionNrPacketsTable 1}

Sr1646v2PingSessionNrPacketsEntry ::=
   SEQUENCE
      {
      sr1646v2PingSessionNrPacketsGlobalIx
         GlobalIndex,
      sr1646v2PingSessionNrPacketsValue
         INTEGER
      }

sr1646v2PingSessionNrPacketsGlobalIx OBJECT-TYPE
   SYNTAX      GlobalIndex
   MAX-ACCESS  not-accessible
   STATUS      current
   DESCRIPTION
      "The value of the tlsCntTreeGlobalIndex of the MANAGED OBJECT."
   ::= {sr1646v2PingSessionNrPacketsEntry 10}

sr1646v2PingSessionNrPacketsValue OBJECT-TYPE
   SYNTAX      INTEGER
               {
               slnotsinsuseg (-1)
               }
   MAX-ACCESS  read-only
   STATUS      current
   DESCRIPTION
      "Path: session.status.nrPackets

       Possibilities:
               <not in use>   (-1)"
   ::= {sr1646v2PingSessionNrPacketsEntry 2147483648}


sr1646v2PingSessionSnmpIndex OBJECT IDENTIFIER ::= {sr1646v2PingSession 269}

sr1646v2PingSessionSnmpIndexTable OBJECT-TYPE
   SYNTAX      SEQUENCE OF Sr1646v2PingSessionSnmpIndexEntry
   MAX-ACCESS  not-accessible
   STATUS      current
   DESCRIPTION
      "SNMP index assigned to this object"
   ::= {sr1646v2PingSessionSnmpIndex 1}

sr1646v2PingSessionSnmpIndexEntry OBJECT-TYPE
   SYNTAX      Sr1646v2PingSessionSnmpIndexEntry
   MAX-ACCESS  not-accessible
   STATUS      current
   DESCRIPTION
      ""
   INDEX      { sr1646v2PingSessionSnmpIndexGlobalIx }
   ::= {sr1646v2PingSessionSnmpIndexTable 1}

Sr1646v2PingSessionSnmpIndexEntry ::=
   SEQUENCE
      {
      sr1646v2PingSessionSnmpIndexGlobalIx
         GlobalIndex,
      sr1646v2PingSessionSnmpIndexValue
         Integer32
      }

sr1646v2PingSessionSnmpIndexGlobalIx OBJECT-TYPE
   SYNTAX      GlobalIndex
   MAX-ACCESS  not-accessible
   STATUS      current
   DESCRIPTION
      "The value of the tlsCntTreeGlobalIndex of the MANAGED OBJECT."
   ::= {sr1646v2PingSessionSnmpIndexEntry 10}

sr1646v2PingSessionSnmpIndexValue OBJECT-TYPE
   SYNTAX      Integer32
   MAX-ACCESS  read-only
   STATUS      current
   DESCRIPTION
      "Path: session.status.snmpIndex"
   ::= {sr1646v2PingSessionSnmpIndexEntry 2147483648}



pr1646v2PingSession OBJECT IDENTIFIER ::= {r1646v2PingSession 12}


pr1646v2PingSessionName OBJECT IDENTIFIER ::= {pr1646v2PingSession 1218}

pr1646v2PingSessionNameTable OBJECT-TYPE
   SYNTAX      SEQUENCE OF Pr1646v2PingSessionNameEntry
   MAX-ACCESS  not-accessible
   STATUS      current
   DESCRIPTION
      ""
   ::= {pr1646v2PingSessionName 1}

pr1646v2PingSessionNameEntry OBJECT-TYPE
   SYNTAX      Pr1646v2PingSessionNameEntry
   MAX-ACCESS  not-accessible
   STATUS      current
   DESCRIPTION
      ""
   INDEX      { pr1646v2PingSessionNameGlobalIx }
   ::= {pr1646v2PingSessionNameTable 1}

Pr1646v2PingSessionNameEntry ::=
   SEQUENCE
      {
      pr1646v2PingSessionNameGlobalIx
         GlobalIndex,
      pr1646v2PingSessionNameValue
         DisplayString
      }

pr1646v2PingSessionNameGlobalIx OBJECT-TYPE
   SYNTAX      GlobalIndex
   MAX-ACCESS  not-accessible
   STATUS      current
   DESCRIPTION
      "The value of the tlsCntTreeGlobalIndex of the MANAGED OBJECT."
   ::= {pr1646v2PingSessionNameEntry 10}

pr1646v2PingSessionNameValue OBJECT-TYPE
   SYNTAX      DisplayString
   MAX-ACCESS  read-only
   STATUS      current
   DESCRIPTION
      "Path: session.performance.name"
   ::= {pr1646v2PingSessionNameEntry 2147483648}


pr1646v2PingSessionGlobalStartDate OBJECT IDENTIFIER ::= {pr1646v2PingSession 1217}

pr1646v2PingSessionGlobalStartDateTable OBJECT-TYPE
   SYNTAX      SEQUENCE OF Pr1646v2PingSessionGlobalStartDateEntry
   MAX-ACCESS  not-accessible
   STATUS      current
   DESCRIPTION
      ""
   ::= {pr1646v2PingSessionGlobalStartDate 1}

pr1646v2PingSessionGlobalStartDateEntry OBJECT-TYPE
   SYNTAX      Pr1646v2PingSessionGlobalStartDateEntry
   MAX-ACCESS  not-accessible
   STATUS      current
   DESCRIPTION
      ""
   INDEX      { pr1646v2PingSessionGlobalStartDateGlobalIx }
   ::= {pr1646v2PingSessionGlobalStartDateTable 1}

Pr1646v2PingSessionGlobalStartDateEntry ::=
   SEQUENCE
      {
      pr1646v2PingSessionGlobalStartDateGlobalIx
         GlobalIndex,
      pr1646v2PingSessionGlobalStartDateValue
         DisplayString
      }

pr1646v2PingSessionGlobalStartDateGlobalIx OBJECT-TYPE
   SYNTAX      GlobalIndex
   MAX-ACCESS  not-accessible
   STATUS      current
   DESCRIPTION
      "The value of the tlsCntTreeGlobalIndex of the MANAGED OBJECT."
   ::= {pr1646v2PingSessionGlobalStartDateEntry 10}

pr1646v2PingSessionGlobalStartDateValue OBJECT-TYPE
   SYNTAX      DisplayString
   MAX-ACCESS  read-only
   STATUS      current
   DESCRIPTION
      "Path: session.performance.globalStartDate"
   ::= {pr1646v2PingSessionGlobalStartDateEntry 2147483648}


pr1646v2PingSessionStatus OBJECT IDENTIFIER ::= {pr1646v2PingSession 1140}

pr1646v2PingSessionStatusTable OBJECT-TYPE
   SYNTAX      SEQUENCE OF Pr1646v2PingSessionStatusEntry
   MAX-ACCESS  not-accessible
   STATUS      current
   DESCRIPTION
      ""
   ::= {pr1646v2PingSessionStatus 1}

pr1646v2PingSessionStatusEntry OBJECT-TYPE
   SYNTAX      Pr1646v2PingSessionStatusEntry
   MAX-ACCESS  not-accessible
   STATUS      current
   DESCRIPTION
      ""
   INDEX      { pr1646v2PingSessionStatusGlobalIx }
   ::= {pr1646v2PingSessionStatusTable 1}

Pr1646v2PingSessionStatusEntry ::=
   SEQUENCE
      {
      pr1646v2PingSessionStatusGlobalIx
         GlobalIndex,
      pr1646v2PingSessionStatusValue
         INTEGER
      }

pr1646v2PingSessionStatusGlobalIx OBJECT-TYPE
   SYNTAX      GlobalIndex
   MAX-ACCESS  not-accessible
   STATUS      current
   DESCRIPTION
      "The value of the tlsCntTreeGlobalIndex of the MANAGED OBJECT."
   ::= {pr1646v2PingSessionStatusEntry 10}

pr1646v2PingSessionStatusValue OBJECT-TYPE
   SYNTAX      INTEGER
               {
               idle (128),
               destinationProblem (40),
               openSocketProblem (41),
               logProblem (42),
               waitHalfDuplexSetup (2),
               waitGroup (3),
               waitDns (4),
               waitDnsStart (5),
               releaseSocket (6),
               waitForRepeat (7),
               runFlood (11),
               runAsymFlood (12),
               runNormal (13),
               runBandwidth (14),
               runPacketsASec (15),
               haltedFlood (21),
               haltedAsymFlood (22),
               haltedNormal (23),
               haltedBandwidth (24),
               haltedPacketsASec (25),
               optimumFlood (31),
               optimumAsymFlood (32),
               optimumNormal (33),
               optimumBandwidth (34),
               optimumPacketsASec (35),
               problemHaltedFlood (26),
               problemHaltedAsymFlood (27),
               problemHaltedNormal (28),
               problemHaltedBandwidth (29),
               problemHaltedPacketsASec (30),
               testRunFlood (51),
               testRunAsymFlood (52),
               testRunNormal (53),
               testRunBandwidth (54),
               testRunPacketsASec (55),
               testReleaseSocket (56),
               testWaitForRepeat (57),
               testHaltedFlood (61),
               testHaltedAsymFlood (62),
               testHaltedNormal (63),
               testHaltedBandwidth (64),
               testHaltedPacketsASec (65)
               }
   MAX-ACCESS  read-only
   STATUS      current
   DESCRIPTION
      "Path: session.performance.status

       Possibilities:
               idle   (128)
               destinationProblem   (40)
               openSocketProblem   (41)
               logProblem   (42)
               waitHalfDuplexSetup   (2)
               waitGroup   (3)
               waitDns   (4)
               waitDnsStart   (5)
               releaseSocket   (6)
               waitForRepeat   (7)
               runFlood   (11)
               runAsymFlood   (12)
               runNormal   (13)
               runBandwidth   (14)
               runPacketsASec   (15)
               haltedFlood   (21)
               haltedAsymFlood   (22)
               haltedNormal   (23)
               haltedBandwidth   (24)
               haltedPacketsASec   (25)
               optimumFlood   (31)
               optimumAsymFlood   (32)
               optimumNormal   (33)
               optimumBandwidth   (34)
               optimumPacketsASec   (35)
               problemHaltedFlood   (26)
               problemHaltedAsymFlood   (27)
               problemHaltedNormal   (28)
               problemHaltedBandwidth   (29)
               problemHaltedPacketsASec   (30)
               testRunFlood   (51)
               testRunAsymFlood   (52)
               testRunNormal   (53)
               testRunBandwidth   (54)
               testRunPacketsASec   (55)
               testReleaseSocket   (56)
               testWaitForRepeat   (57)
               testHaltedFlood   (61)
               testHaltedAsymFlood   (62)
               testHaltedNormal   (63)
               testHaltedBandwidth   (64)
               testHaltedPacketsASec   (65)"
   ::= {pr1646v2PingSessionStatusEntry 2147483648}


pr1646v2PingSessionDuration OBJECT IDENTIFIER ::= {pr1646v2PingSession 1141}

pr1646v2PingSessionDurationTable OBJECT-TYPE
   SYNTAX      SEQUENCE OF Pr1646v2PingSessionDurationEntry
   MAX-ACCESS  not-accessible
   STATUS      current
   DESCRIPTION
      ""
   ::= {pr1646v2PingSessionDuration 1}

pr1646v2PingSessionDurationEntry OBJECT-TYPE
   SYNTAX      Pr1646v2PingSessionDurationEntry
   MAX-ACCESS  not-accessible
   STATUS      current
   DESCRIPTION
      ""
   INDEX      { pr1646v2PingSessionDurationGlobalIx }
   ::= {pr1646v2PingSessionDurationTable 1}

Pr1646v2PingSessionDurationEntry ::=
   SEQUENCE
      {
      pr1646v2PingSessionDurationGlobalIx
         GlobalIndex,
      pr1646v2PingSessionDurationValue
         TimeTicks
      }

pr1646v2PingSessionDurationGlobalIx OBJECT-TYPE
   SYNTAX      GlobalIndex
   MAX-ACCESS  not-accessible
   STATUS      current
   DESCRIPTION
      "The value of the tlsCntTreeGlobalIndex of the MANAGED OBJECT."
   ::= {pr1646v2PingSessionDurationEntry 10}

pr1646v2PingSessionDurationValue OBJECT-TYPE
   SYNTAX      TimeTicks
   MAX-ACCESS  read-only
   STATUS      current
   DESCRIPTION
      "Path: session.performance.duration

       Time in centi-second."
   ::= {pr1646v2PingSessionDurationEntry 2147483648}


pr1646v2PingSessionStartDate OBJECT IDENTIFIER ::= {pr1646v2PingSession 1142}

pr1646v2PingSessionStartDateTable OBJECT-TYPE
   SYNTAX      SEQUENCE OF Pr1646v2PingSessionStartDateEntry
   MAX-ACCESS  not-accessible
   STATUS      current
   DESCRIPTION
      ""
   ::= {pr1646v2PingSessionStartDate 1}

pr1646v2PingSessionStartDateEntry OBJECT-TYPE
   SYNTAX      Pr1646v2PingSessionStartDateEntry
   MAX-ACCESS  not-accessible
   STATUS      current
   DESCRIPTION
      ""
   INDEX      { pr1646v2PingSessionStartDateGlobalIx }
   ::= {pr1646v2PingSessionStartDateTable 1}

Pr1646v2PingSessionStartDateEntry ::=
   SEQUENCE
      {
      pr1646v2PingSessionStartDateGlobalIx
         GlobalIndex,
      pr1646v2PingSessionStartDateValue
         DisplayString
      }

pr1646v2PingSessionStartDateGlobalIx OBJECT-TYPE
   SYNTAX      GlobalIndex
   MAX-ACCESS  not-accessible
   STATUS      current
   DESCRIPTION
      "The value of the tlsCntTreeGlobalIndex of the MANAGED OBJECT."
   ::= {pr1646v2PingSessionStartDateEntry 10}

pr1646v2PingSessionStartDateValue OBJECT-TYPE
   SYNTAX      DisplayString
   MAX-ACCESS  read-only
   STATUS      current
   DESCRIPTION
      "Path: session.performance.startDate"
   ::= {pr1646v2PingSessionStartDateEntry 2147483648}


pr1646v2PingSessionEndDate OBJECT IDENTIFIER ::= {pr1646v2PingSession 1143}

pr1646v2PingSessionEndDateTable OBJECT-TYPE
   SYNTAX      SEQUENCE OF Pr1646v2PingSessionEndDateEntry
   MAX-ACCESS  not-accessible
   STATUS      current
   DESCRIPTION
      ""
   ::= {pr1646v2PingSessionEndDate 1}

pr1646v2PingSessionEndDateEntry OBJECT-TYPE
   SYNTAX      Pr1646v2PingSessionEndDateEntry
   MAX-ACCESS  not-accessible
   STATUS      current
   DESCRIPTION
      ""
   INDEX      { pr1646v2PingSessionEndDateGlobalIx }
   ::= {pr1646v2PingSessionEndDateTable 1}

Pr1646v2PingSessionEndDateEntry ::=
   SEQUENCE
      {
      pr1646v2PingSessionEndDateGlobalIx
         GlobalIndex,
      pr1646v2PingSessionEndDateValue
         DisplayString
      }

pr1646v2PingSessionEndDateGlobalIx OBJECT-TYPE
   SYNTAX      GlobalIndex
   MAX-ACCESS  not-accessible
   STATUS      current
   DESCRIPTION
      "The value of the tlsCntTreeGlobalIndex of the MANAGED OBJECT."
   ::= {pr1646v2PingSessionEndDateEntry 10}

pr1646v2PingSessionEndDateValue OBJECT-TYPE
   SYNTAX      DisplayString
   MAX-ACCESS  read-only
   STATUS      current
   DESCRIPTION
      "Path: session.performance.endDate"
   ::= {pr1646v2PingSessionEndDateEntry 2147483648}


pr1646v2PingSessionSent OBJECT IDENTIFIER ::= {pr1646v2PingSession 1144}

pr1646v2PingSessionSentTable OBJECT-TYPE
   SYNTAX      SEQUENCE OF Pr1646v2PingSessionSentEntry
   MAX-ACCESS  not-accessible
   STATUS      current
   DESCRIPTION
      ""
   ::= {pr1646v2PingSessionSent 1}

pr1646v2PingSessionSentEntry OBJECT-TYPE
   SYNTAX      Pr1646v2PingSessionSentEntry
   MAX-ACCESS  not-accessible
   STATUS      current
   DESCRIPTION
      ""
   INDEX      { pr1646v2PingSessionSentGlobalIx }
   ::= {pr1646v2PingSessionSentTable 1}

Pr1646v2PingSessionSentEntry ::=
   SEQUENCE
      {
      pr1646v2PingSessionSentGlobalIx
         GlobalIndex,
      pr1646v2PingSessionSentValue
         Counter64
      }

pr1646v2PingSessionSentGlobalIx OBJECT-TYPE
   SYNTAX      GlobalIndex
   MAX-ACCESS  not-accessible
   STATUS      current
   DESCRIPTION
      "The value of the tlsCntTreeGlobalIndex of the MANAGED OBJECT."
   ::= {pr1646v2PingSessionSentEntry 10}

pr1646v2PingSessionSentValue OBJECT-TYPE
   SYNTAX      Counter64
   MAX-ACCESS  read-only
   STATUS      current
   DESCRIPTION
      "Path: session.performance.sent

       64 bit unsigned wrappable counter."
   ::= {pr1646v2PingSessionSentEntry 2147483648}


pr1646v2PingSessionReceived OBJECT IDENTIFIER ::= {pr1646v2PingSession 1145}

pr1646v2PingSessionReceivedTable OBJECT-TYPE
   SYNTAX      SEQUENCE OF Pr1646v2PingSessionReceivedEntry
   MAX-ACCESS  not-accessible
   STATUS      current
   DESCRIPTION
      ""
   ::= {pr1646v2PingSessionReceived 1}

pr1646v2PingSessionReceivedEntry OBJECT-TYPE
   SYNTAX      Pr1646v2PingSessionReceivedEntry
   MAX-ACCESS  not-accessible
   STATUS      current
   DESCRIPTION
      ""
   INDEX      { pr1646v2PingSessionReceivedGlobalIx }
   ::= {pr1646v2PingSessionReceivedTable 1}

Pr1646v2PingSessionReceivedEntry ::=
   SEQUENCE
      {
      pr1646v2PingSessionReceivedGlobalIx
         GlobalIndex,
      pr1646v2PingSessionReceivedValue
         Counter64
      }

pr1646v2PingSessionReceivedGlobalIx OBJECT-TYPE
   SYNTAX      GlobalIndex
   MAX-ACCESS  not-accessible
   STATUS      current
   DESCRIPTION
      "The value of the tlsCntTreeGlobalIndex of the MANAGED OBJECT."
   ::= {pr1646v2PingSessionReceivedEntry 10}

pr1646v2PingSessionReceivedValue OBJECT-TYPE
   SYNTAX      Counter64
   MAX-ACCESS  read-only
   STATUS      current
   DESCRIPTION
      "Path: session.performance.received

       64 bit unsigned wrappable counter."
   ::= {pr1646v2PingSessionReceivedEntry 2147483648}


pr1646v2PingSessionBytesStat OBJECT IDENTIFIER ::= {pr1646v2PingSession 1157}

pr1646v2PingSessionBytesStatSSCTable OBJECT-TYPE
   SYNTAX      SEQUENCE OF Pr1646v2PingSessionBytesStatEntry
   MAX-ACCESS  not-accessible
   STATUS      current
   DESCRIPTION
      ""
   ::= {pr1646v2PingSessionBytesStat 1}

pr1646v2PingSessionBytesStatEntry OBJECT-TYPE
   SYNTAX      Pr1646v2PingSessionBytesStatEntry
   MAX-ACCESS  not-accessible
   STATUS      current
   DESCRIPTION
      ""
   INDEX      { pr1646v2PingSessionBytesStatGlobalIx }
   ::= {pr1646v2PingSessionBytesStatSSCTable 1}

Pr1646v2PingSessionBytesStatEntry ::=
   SEQUENCE
      {
      pr1646v2PingSessionBytesStatGlobalIx
         GlobalIndex,
      pr1646v2PingSessionBytesStatEncapsTx
         Counter64,
      pr1646v2PingSessionBytesStatOverheadTx
         Counter64,
      pr1646v2PingSessionBytesStatEncapsRx
         Counter64,
      pr1646v2PingSessionBytesStatOverheadRx
         Counter64
      }

pr1646v2PingSessionBytesStatGlobalIx OBJECT-TYPE
   SYNTAX      GlobalIndex
   MAX-ACCESS  not-accessible
   STATUS      current
   DESCRIPTION
      "The value of the tlsCntTreeGlobalIndex of the MANAGED OBJECT."
   ::= {pr1646v2PingSessionBytesStatEntry 10}

pr1646v2PingSessionBytesStatEncapsTx OBJECT-TYPE
   SYNTAX      Counter64
   MAX-ACCESS  read-only
   STATUS      current
   DESCRIPTION
      "Path: session.performance.bytesStat.encapsTx

       64 bit unsigned wrappable counter."
   ::= {pr1646v2PingSessionBytesStatEntry 16777216}

pr1646v2PingSessionBytesStatOverheadTx OBJECT-TYPE
   SYNTAX      Counter64
   MAX-ACCESS  read-only
   STATUS      current
   DESCRIPTION
      "Path: session.performance.bytesStat.overheadTx

       64 bit unsigned wrappable counter."
   ::= {pr1646v2PingSessionBytesStatEntry 67108864}

pr1646v2PingSessionBytesStatEncapsRx OBJECT-TYPE
   SYNTAX      Counter64
   MAX-ACCESS  read-only
   STATUS      current
   DESCRIPTION
      "Path: session.performance.bytesStat.encapsRx

       64 bit unsigned wrappable counter."
   ::= {pr1646v2PingSessionBytesStatEntry 83886080}

pr1646v2PingSessionBytesStatOverheadRx OBJECT-TYPE
   SYNTAX      Counter64
   MAX-ACCESS  read-only
   STATUS      current
   DESCRIPTION
      "Path: session.performance.bytesStat.overheadRx

       64 bit unsigned wrappable counter."
   ::= {pr1646v2PingSessionBytesStatEntry 134217728}


pr1646v2PingSessionBitsSec OBJECT IDENTIFIER ::= {pr1646v2PingSession 1159}

pr1646v2PingSessionBitsSecSSCTable OBJECT-TYPE
   SYNTAX      SEQUENCE OF Pr1646v2PingSessionBitsSecEntry
   MAX-ACCESS  not-accessible
   STATUS      current
   DESCRIPTION
      ""
   ::= {pr1646v2PingSessionBitsSec 1}

pr1646v2PingSessionBitsSecEntry OBJECT-TYPE
   SYNTAX      Pr1646v2PingSessionBitsSecEntry
   MAX-ACCESS  not-accessible
   STATUS      current
   DESCRIPTION
      ""
   INDEX      { pr1646v2PingSessionBitsSecGlobalIx }
   ::= {pr1646v2PingSessionBitsSecSSCTable 1}

Pr1646v2PingSessionBitsSecEntry ::=
   SEQUENCE
      {
      pr1646v2PingSessionBitsSecGlobalIx
         GlobalIndex,
      pr1646v2PingSessionBitsSecEncapsTx
         Integer32,
      pr1646v2PingSessionBitsSecOverheadTx
         Integer32,
      pr1646v2PingSessionBitsSecEncapsRx
         Integer32,
      pr1646v2PingSessionBitsSecOverheadRx
         Integer32,
      pr1646v2PingSessionBitsSecEncapsRxMin
         Integer32,
      pr1646v2PingSessionBitsSecEncapsRxMax
         Integer32
      }

pr1646v2PingSessionBitsSecGlobalIx OBJECT-TYPE
   SYNTAX      GlobalIndex
   MAX-ACCESS  not-accessible
   STATUS      current
   DESCRIPTION
      "The value of the tlsCntTreeGlobalIndex of the MANAGED OBJECT."
   ::= {pr1646v2PingSessionBitsSecEntry 10}

pr1646v2PingSessionBitsSecEncapsTx OBJECT-TYPE
   SYNTAX      Integer32
   MAX-ACCESS  read-only
   STATUS      current
   DESCRIPTION
      "Path: session.performance.bitsSec.encapsTx"
   ::= {pr1646v2PingSessionBitsSecEntry 16777216}

pr1646v2PingSessionBitsSecOverheadTx OBJECT-TYPE
   SYNTAX      Integer32
   MAX-ACCESS  read-only
   STATUS      current
   DESCRIPTION
      "Path: session.performance.bitsSec.overheadTx"
   ::= {pr1646v2PingSessionBitsSecEntry 67108864}

pr1646v2PingSessionBitsSecEncapsRx OBJECT-TYPE
   SYNTAX      Integer32
   MAX-ACCESS  read-only
   STATUS      current
   DESCRIPTION
      "Path: session.performance.bitsSec.encapsRx"
   ::= {pr1646v2PingSessionBitsSecEntry 83886080}

pr1646v2PingSessionBitsSecOverheadRx OBJECT-TYPE
   SYNTAX      Integer32
   MAX-ACCESS  read-only
   STATUS      current
   DESCRIPTION
      "Path: session.performance.bitsSec.overheadRx"
   ::= {pr1646v2PingSessionBitsSecEntry 134217728}

pr1646v2PingSessionBitsSecEncapsRxMin OBJECT-TYPE
   SYNTAX      Integer32
   MAX-ACCESS  read-only
   STATUS      current
   DESCRIPTION
      "Path: session.performance.bitsSec.encapsRxMin"
   ::= {pr1646v2PingSessionBitsSecEntry 167772160}

pr1646v2PingSessionBitsSecEncapsRxMax OBJECT-TYPE
   SYNTAX      Integer32
   MAX-ACCESS  read-only
   STATUS      current
   DESCRIPTION
      "Path: session.performance.bitsSec.encapsRxMax"
   ::= {pr1646v2PingSessionBitsSecEntry 184549376}


pr1646v2PingSessionPacketLoss OBJECT IDENTIFIER ::= {pr1646v2PingSession 1146}

pr1646v2PingSessionPacketLossTable OBJECT-TYPE
   SYNTAX      SEQUENCE OF Pr1646v2PingSessionPacketLossEntry
   MAX-ACCESS  not-accessible
   STATUS      current
   DESCRIPTION
      ""
   ::= {pr1646v2PingSessionPacketLoss 1}

pr1646v2PingSessionPacketLossEntry OBJECT-TYPE
   SYNTAX      Pr1646v2PingSessionPacketLossEntry
   MAX-ACCESS  not-accessible
   STATUS      current
   DESCRIPTION
      ""
   INDEX      { pr1646v2PingSessionPacketLossGlobalIx }
   ::= {pr1646v2PingSessionPacketLossTable 1}

Pr1646v2PingSessionPacketLossEntry ::=
   SEQUENCE
      {
      pr1646v2PingSessionPacketLossGlobalIx
         GlobalIndex,
      pr1646v2PingSessionPacketLossValue
         Counter64
      }

pr1646v2PingSessionPacketLossGlobalIx OBJECT-TYPE
   SYNTAX      GlobalIndex
   MAX-ACCESS  not-accessible
   STATUS      current
   DESCRIPTION
      "The value of the tlsCntTreeGlobalIndex of the MANAGED OBJECT."
   ::= {pr1646v2PingSessionPacketLossEntry 10}

pr1646v2PingSessionPacketLossValue OBJECT-TYPE
   SYNTAX      Counter64
   MAX-ACCESS  read-only
   STATUS      current
   DESCRIPTION
      "Path: session.performance.packetLoss

       64 bit unsigned wrappable counter."
   ::= {pr1646v2PingSessionPacketLossEntry 2147483648}


pr1646v2PingSessionPacketLossPer OBJECT IDENTIFIER ::= {pr1646v2PingSession 1147}

pr1646v2PingSessionPacketLossPerTable OBJECT-TYPE
   SYNTAX      SEQUENCE OF Pr1646v2PingSessionPacketLossPerEntry
   MAX-ACCESS  not-accessible
   STATUS      current
   DESCRIPTION
      ""
   ::= {pr1646v2PingSessionPacketLossPer 1}

pr1646v2PingSessionPacketLossPerEntry OBJECT-TYPE
   SYNTAX      Pr1646v2PingSessionPacketLossPerEntry
   MAX-ACCESS  not-accessible
   STATUS      current
   DESCRIPTION
      ""
   INDEX      { pr1646v2PingSessionPacketLossPerGlobalIx }
   ::= {pr1646v2PingSessionPacketLossPerTable 1}

Pr1646v2PingSessionPacketLossPerEntry ::=
   SEQUENCE
      {
      pr1646v2PingSessionPacketLossPerGlobalIx
         GlobalIndex,
      pr1646v2PingSessionPacketLossPerValue
         INTEGER
      }

pr1646v2PingSessionPacketLossPerGlobalIx OBJECT-TYPE
   SYNTAX      GlobalIndex
   MAX-ACCESS  not-accessible
   STATUS      current
   DESCRIPTION
      "The value of the tlsCntTreeGlobalIndex of the MANAGED OBJECT."
   ::= {pr1646v2PingSessionPacketLossPerEntry 10}

pr1646v2PingSessionPacketLossPerValue OBJECT-TYPE
   SYNTAX      INTEGER
               {
               slnotsinsuseg (2147483647)
               }
   MAX-ACCESS  read-only
   STATUS      current
   DESCRIPTION
      "Path: session.performance.packetLossPer

       unit name = %
       formula = 100 / ; 100 *

       Possibilities:
               <not in use>   (2147483647)"
   ::= {pr1646v2PingSessionPacketLossPerEntry 2147483648}


pr1646v2PingSessionSyncLoss OBJECT IDENTIFIER ::= {pr1646v2PingSession 1148}

pr1646v2PingSessionSyncLossTable OBJECT-TYPE
   SYNTAX      SEQUENCE OF Pr1646v2PingSessionSyncLossEntry
   MAX-ACCESS  not-accessible
   STATUS      current
   DESCRIPTION
      ""
   ::= {pr1646v2PingSessionSyncLoss 1}

pr1646v2PingSessionSyncLossEntry OBJECT-TYPE
   SYNTAX      Pr1646v2PingSessionSyncLossEntry
   MAX-ACCESS  not-accessible
   STATUS      current
   DESCRIPTION
      ""
   INDEX      { pr1646v2PingSessionSyncLossGlobalIx }
   ::= {pr1646v2PingSessionSyncLossTable 1}

Pr1646v2PingSessionSyncLossEntry ::=
   SEQUENCE
      {
      pr1646v2PingSessionSyncLossGlobalIx
         GlobalIndex,
      pr1646v2PingSessionSyncLossValue
         INTEGER
      }

pr1646v2PingSessionSyncLossGlobalIx OBJECT-TYPE
   SYNTAX      GlobalIndex
   MAX-ACCESS  not-accessible
   STATUS      current
   DESCRIPTION
      "The value of the tlsCntTreeGlobalIndex of the MANAGED OBJECT."
   ::= {pr1646v2PingSessionSyncLossEntry 10}

pr1646v2PingSessionSyncLossValue OBJECT-TYPE
   SYNTAX      INTEGER
               {
               slnotsinsuseg (-1)
               }
   MAX-ACCESS  read-only
   STATUS      current
   DESCRIPTION
      "Path: session.performance.syncLoss

       Possibilities:
               <not in use>   (-1)"
   ::= {pr1646v2PingSessionSyncLossEntry 2147483648}


pr1646v2PingSessionOutOfSequence OBJECT IDENTIFIER ::= {pr1646v2PingSession 1149}

pr1646v2PingSessionOutOfSequenceTable OBJECT-TYPE
   SYNTAX      SEQUENCE OF Pr1646v2PingSessionOutOfSequenceEntry
   MAX-ACCESS  not-accessible
   STATUS      current
   DESCRIPTION
      ""
   ::= {pr1646v2PingSessionOutOfSequence 1}

pr1646v2PingSessionOutOfSequenceEntry OBJECT-TYPE
   SYNTAX      Pr1646v2PingSessionOutOfSequenceEntry
   MAX-ACCESS  not-accessible
   STATUS      current
   DESCRIPTION
      ""
   INDEX      { pr1646v2PingSessionOutOfSequenceGlobalIx }
   ::= {pr1646v2PingSessionOutOfSequenceTable 1}

Pr1646v2PingSessionOutOfSequenceEntry ::=
   SEQUENCE
      {
      pr1646v2PingSessionOutOfSequenceGlobalIx
         GlobalIndex,
      pr1646v2PingSessionOutOfSequenceValue
         Integer32
      }

pr1646v2PingSessionOutOfSequenceGlobalIx OBJECT-TYPE
   SYNTAX      GlobalIndex
   MAX-ACCESS  not-accessible
   STATUS      current
   DESCRIPTION
      "The value of the tlsCntTreeGlobalIndex of the MANAGED OBJECT."
   ::= {pr1646v2PingSessionOutOfSequenceEntry 10}

pr1646v2PingSessionOutOfSequenceValue OBJECT-TYPE
   SYNTAX      Integer32
   MAX-ACCESS  read-only
   STATUS      current
   DESCRIPTION
      "Path: session.performance.outOfSequence"
   ::= {pr1646v2PingSessionOutOfSequenceEntry 2147483648}


pr1646v2PingSessionCrcErrors OBJECT IDENTIFIER ::= {pr1646v2PingSession 1150}

pr1646v2PingSessionCrcErrorsTable OBJECT-TYPE
   SYNTAX      SEQUENCE OF Pr1646v2PingSessionCrcErrorsEntry
   MAX-ACCESS  not-accessible
   STATUS      current
   DESCRIPTION
      ""
   ::= {pr1646v2PingSessionCrcErrors 1}

pr1646v2PingSessionCrcErrorsEntry OBJECT-TYPE
   SYNTAX      Pr1646v2PingSessionCrcErrorsEntry
   MAX-ACCESS  not-accessible
   STATUS      current
   DESCRIPTION
      ""
   INDEX      { pr1646v2PingSessionCrcErrorsGlobalIx }
   ::= {pr1646v2PingSessionCrcErrorsTable 1}

Pr1646v2PingSessionCrcErrorsEntry ::=
   SEQUENCE
      {
      pr1646v2PingSessionCrcErrorsGlobalIx
         GlobalIndex,
      pr1646v2PingSessionCrcErrorsValue
         INTEGER
      }

pr1646v2PingSessionCrcErrorsGlobalIx OBJECT-TYPE
   SYNTAX      GlobalIndex
   MAX-ACCESS  not-accessible
   STATUS      current
   DESCRIPTION
      "The value of the tlsCntTreeGlobalIndex of the MANAGED OBJECT."
   ::= {pr1646v2PingSessionCrcErrorsEntry 10}

pr1646v2PingSessionCrcErrorsValue OBJECT-TYPE
   SYNTAX      INTEGER
               {
               slnotsinsuseg (-1)
               }
   MAX-ACCESS  read-only
   STATUS      current
   DESCRIPTION
      "Path: session.performance.crcErrors

       Possibilities:
               <not in use>   (-1)"
   ::= {pr1646v2PingSessionCrcErrorsEntry 2147483648}


pr1646v2PingSessionLengthErrors OBJECT IDENTIFIER ::= {pr1646v2PingSession 1151}

pr1646v2PingSessionLengthErrorsTable OBJECT-TYPE
   SYNTAX      SEQUENCE OF Pr1646v2PingSessionLengthErrorsEntry
   MAX-ACCESS  not-accessible
   STATUS      current
   DESCRIPTION
      ""
   ::= {pr1646v2PingSessionLengthErrors 1}

pr1646v2PingSessionLengthErrorsEntry OBJECT-TYPE
   SYNTAX      Pr1646v2PingSessionLengthErrorsEntry
   MAX-ACCESS  not-accessible
   STATUS      current
   DESCRIPTION
      ""
   INDEX      { pr1646v2PingSessionLengthErrorsGlobalIx }
   ::= {pr1646v2PingSessionLengthErrorsTable 1}

Pr1646v2PingSessionLengthErrorsEntry ::=
   SEQUENCE
      {
      pr1646v2PingSessionLengthErrorsGlobalIx
         GlobalIndex,
      pr1646v2PingSessionLengthErrorsValue
         Counter64
      }

pr1646v2PingSessionLengthErrorsGlobalIx OBJECT-TYPE
   SYNTAX      GlobalIndex
   MAX-ACCESS  not-accessible
   STATUS      current
   DESCRIPTION
      "The value of the tlsCntTreeGlobalIndex of the MANAGED OBJECT."
   ::= {pr1646v2PingSessionLengthErrorsEntry 10}

pr1646v2PingSessionLengthErrorsValue OBJECT-TYPE
   SYNTAX      Counter64
   MAX-ACCESS  read-only
   STATUS      current
   DESCRIPTION
      "Path: session.performance.lengthErrors

       64 bit unsigned wrappable counter."
   ::= {pr1646v2PingSessionLengthErrorsEntry 2147483648}


pr1646v2PingSessionRecAfterTimeOut OBJECT IDENTIFIER ::= {pr1646v2PingSession 1130}

pr1646v2PingSessionRecAfterTimeOutTable OBJECT-TYPE
   SYNTAX      SEQUENCE OF Pr1646v2PingSessionRecAfterTimeOutEntry
   MAX-ACCESS  not-accessible
   STATUS      current
   DESCRIPTION
      ""
   ::= {pr1646v2PingSessionRecAfterTimeOut 1}

pr1646v2PingSessionRecAfterTimeOutEntry OBJECT-TYPE
   SYNTAX      Pr1646v2PingSessionRecAfterTimeOutEntry
   MAX-ACCESS  not-accessible
   STATUS      current
   DESCRIPTION
      ""
   INDEX      { pr1646v2PingSessionRecAfterTimeOutGlobalIx }
   ::= {pr1646v2PingSessionRecAfterTimeOutTable 1}

Pr1646v2PingSessionRecAfterTimeOutEntry ::=
   SEQUENCE
      {
      pr1646v2PingSessionRecAfterTimeOutGlobalIx
         GlobalIndex,
      pr1646v2PingSessionRecAfterTimeOutValue
         Counter64
      }

pr1646v2PingSessionRecAfterTimeOutGlobalIx OBJECT-TYPE
   SYNTAX      GlobalIndex
   MAX-ACCESS  not-accessible
   STATUS      current
   DESCRIPTION
      "The value of the tlsCntTreeGlobalIndex of the MANAGED OBJECT."
   ::= {pr1646v2PingSessionRecAfterTimeOutEntry 10}

pr1646v2PingSessionRecAfterTimeOutValue OBJECT-TYPE
   SYNTAX      Counter64
   MAX-ACCESS  read-only
   STATUS      current
   DESCRIPTION
      "Path: session.performance.recAfterTimeOut

       64 bit unsigned wrappable counter."
   ::= {pr1646v2PingSessionRecAfterTimeOutEntry 2147483648}


pr1646v2PingSessionLastFault OBJECT IDENTIFIER ::= {pr1646v2PingSession 1152}

pr1646v2PingSessionLastFaultTable OBJECT-TYPE
   SYNTAX      SEQUENCE OF Pr1646v2PingSessionLastFaultEntry
   MAX-ACCESS  not-accessible
   STATUS      current
   DESCRIPTION
      ""
   ::= {pr1646v2PingSessionLastFault 1}

pr1646v2PingSessionLastFaultEntry OBJECT-TYPE
   SYNTAX      Pr1646v2PingSessionLastFaultEntry
   MAX-ACCESS  not-accessible
   STATUS      current
   DESCRIPTION
      ""
   INDEX      { pr1646v2PingSessionLastFaultGlobalIx }
   ::= {pr1646v2PingSessionLastFaultTable 1}

Pr1646v2PingSessionLastFaultEntry ::=
   SEQUENCE
      {
      pr1646v2PingSessionLastFaultGlobalIx
         GlobalIndex,
      pr1646v2PingSessionLastFaultValue
         Counter64
      }

pr1646v2PingSessionLastFaultGlobalIx OBJECT-TYPE
   SYNTAX      GlobalIndex
   MAX-ACCESS  not-accessible
   STATUS      current
   DESCRIPTION
      "The value of the tlsCntTreeGlobalIndex of the MANAGED OBJECT."
   ::= {pr1646v2PingSessionLastFaultEntry 10}

pr1646v2PingSessionLastFaultValue OBJECT-TYPE
   SYNTAX      Counter64
   MAX-ACCESS  read-only
   STATUS      current
   DESCRIPTION
      "Path: session.performance.lastFault

       64 bit unsigned wrappable counter."
   ::= {pr1646v2PingSessionLastFaultEntry 2147483648}


pr1646v2PingSessionDelayMin OBJECT IDENTIFIER ::= {pr1646v2PingSession 1153}

pr1646v2PingSessionDelayMinTable OBJECT-TYPE
   SYNTAX      SEQUENCE OF Pr1646v2PingSessionDelayMinEntry
   MAX-ACCESS  not-accessible
   STATUS      current
   DESCRIPTION
      ""
   ::= {pr1646v2PingSessionDelayMin 1}

pr1646v2PingSessionDelayMinEntry OBJECT-TYPE
   SYNTAX      Pr1646v2PingSessionDelayMinEntry
   MAX-ACCESS  not-accessible
   STATUS      current
   DESCRIPTION
      ""
   INDEX      { pr1646v2PingSessionDelayMinGlobalIx }
   ::= {pr1646v2PingSessionDelayMinTable 1}

Pr1646v2PingSessionDelayMinEntry ::=
   SEQUENCE
      {
      pr1646v2PingSessionDelayMinGlobalIx
         GlobalIndex,
      pr1646v2PingSessionDelayMinValue
         INTEGER
      }

pr1646v2PingSessionDelayMinGlobalIx OBJECT-TYPE
   SYNTAX      GlobalIndex
   MAX-ACCESS  not-accessible
   STATUS      current
   DESCRIPTION
      "The value of the tlsCntTreeGlobalIndex of the MANAGED OBJECT."
   ::= {pr1646v2PingSessionDelayMinEntry 10}

pr1646v2PingSessionDelayMinValue OBJECT-TYPE
   SYNTAX      INTEGER
               {
               slnotsinsuseg (2147483647)
               }
   MAX-ACCESS  read-only
   STATUS      current
   DESCRIPTION
      "Path: session.performance.delayMin

       unit name = ms
       formula = 10 / ; 10 *

       Possibilities:
               <not in use>   (2147483647)"
   ::= {pr1646v2PingSessionDelayMinEntry 2147483648}


pr1646v2PingSessionDelayAvrg OBJECT IDENTIFIER ::= {pr1646v2PingSession 1154}

pr1646v2PingSessionDelayAvrgTable OBJECT-TYPE
   SYNTAX      SEQUENCE OF Pr1646v2PingSessionDelayAvrgEntry
   MAX-ACCESS  not-accessible
   STATUS      current
   DESCRIPTION
      ""
   ::= {pr1646v2PingSessionDelayAvrg 1}

pr1646v2PingSessionDelayAvrgEntry OBJECT-TYPE
   SYNTAX      Pr1646v2PingSessionDelayAvrgEntry
   MAX-ACCESS  not-accessible
   STATUS      current
   DESCRIPTION
      ""
   INDEX      { pr1646v2PingSessionDelayAvrgGlobalIx }
   ::= {pr1646v2PingSessionDelayAvrgTable 1}

Pr1646v2PingSessionDelayAvrgEntry ::=
   SEQUENCE
      {
      pr1646v2PingSessionDelayAvrgGlobalIx
         GlobalIndex,
      pr1646v2PingSessionDelayAvrgValue
         INTEGER
      }

pr1646v2PingSessionDelayAvrgGlobalIx OBJECT-TYPE
   SYNTAX      GlobalIndex
   MAX-ACCESS  not-accessible
   STATUS      current
   DESCRIPTION
      "The value of the tlsCntTreeGlobalIndex of the MANAGED OBJECT."
   ::= {pr1646v2PingSessionDelayAvrgEntry 10}

pr1646v2PingSessionDelayAvrgValue OBJECT-TYPE
   SYNTAX      INTEGER
               {
               slnotsinsuseg (2147483647)
               }
   MAX-ACCESS  read-only
   STATUS      current
   DESCRIPTION
      "Path: session.performance.delayAvrg

       unit name = ms
       formula = 10 / ; 10 *

       Possibilities:
               <not in use>   (2147483647)"
   ::= {pr1646v2PingSessionDelayAvrgEntry 2147483648}


pr1646v2PingSessionDelayMax OBJECT IDENTIFIER ::= {pr1646v2PingSession 1155}

pr1646v2PingSessionDelayMaxTable OBJECT-TYPE
   SYNTAX      SEQUENCE OF Pr1646v2PingSessionDelayMaxEntry
   MAX-ACCESS  not-accessible
   STATUS      current
   DESCRIPTION
      ""
   ::= {pr1646v2PingSessionDelayMax 1}

pr1646v2PingSessionDelayMaxEntry OBJECT-TYPE
   SYNTAX      Pr1646v2PingSessionDelayMaxEntry
   MAX-ACCESS  not-accessible
   STATUS      current
   DESCRIPTION
      ""
   INDEX      { pr1646v2PingSessionDelayMaxGlobalIx }
   ::= {pr1646v2PingSessionDelayMaxTable 1}

Pr1646v2PingSessionDelayMaxEntry ::=
   SEQUENCE
      {
      pr1646v2PingSessionDelayMaxGlobalIx
         GlobalIndex,
      pr1646v2PingSessionDelayMaxValue
         INTEGER
      }

pr1646v2PingSessionDelayMaxGlobalIx OBJECT-TYPE
   SYNTAX      GlobalIndex
   MAX-ACCESS  not-accessible
   STATUS      current
   DESCRIPTION
      "The value of the tlsCntTreeGlobalIndex of the MANAGED OBJECT."
   ::= {pr1646v2PingSessionDelayMaxEntry 10}

pr1646v2PingSessionDelayMaxValue OBJECT-TYPE
   SYNTAX      INTEGER
               {
               slnotsinsuseg (2147483647)
               }
   MAX-ACCESS  read-only
   STATUS      current
   DESCRIPTION
      "Path: session.performance.delayMax

       unit name = ms
       formula = 10 / ; 10 *

       Possibilities:
               <not in use>   (2147483647)"
   ::= {pr1646v2PingSessionDelayMaxEntry 2147483648}


pr1646v2PingSessionJitterAvrg OBJECT IDENTIFIER ::= {pr1646v2PingSession 1183}

pr1646v2PingSessionJitterAvrgTable OBJECT-TYPE
   SYNTAX      SEQUENCE OF Pr1646v2PingSessionJitterAvrgEntry
   MAX-ACCESS  not-accessible
   STATUS      current
   DESCRIPTION
      ""
   ::= {pr1646v2PingSessionJitterAvrg 1}

pr1646v2PingSessionJitterAvrgEntry OBJECT-TYPE
   SYNTAX      Pr1646v2PingSessionJitterAvrgEntry
   MAX-ACCESS  not-accessible
   STATUS      current
   DESCRIPTION
      ""
   INDEX      { pr1646v2PingSessionJitterAvrgGlobalIx }
   ::= {pr1646v2PingSessionJitterAvrgTable 1}

Pr1646v2PingSessionJitterAvrgEntry ::=
   SEQUENCE
      {
      pr1646v2PingSessionJitterAvrgGlobalIx
         GlobalIndex,
      pr1646v2PingSessionJitterAvrgValue
         INTEGER
      }

pr1646v2PingSessionJitterAvrgGlobalIx OBJECT-TYPE
   SYNTAX      GlobalIndex
   MAX-ACCESS  not-accessible
   STATUS      current
   DESCRIPTION
      "The value of the tlsCntTreeGlobalIndex of the MANAGED OBJECT."
   ::= {pr1646v2PingSessionJitterAvrgEntry 10}

pr1646v2PingSessionJitterAvrgValue OBJECT-TYPE
   SYNTAX      INTEGER
               {
               slnotsinsuseg (2147483647)
               }
   MAX-ACCESS  read-only
   STATUS      current
   DESCRIPTION
      "Path: session.performance.jitterAvrg

       unit name = ms
       formula = 10 / ; 10 *

       Possibilities:
               <not in use>   (2147483647)"
   ::= {pr1646v2PingSessionJitterAvrgEntry 2147483648}


pr1646v2PingSessionJitterMax OBJECT IDENTIFIER ::= {pr1646v2PingSession 1184}

pr1646v2PingSessionJitterMaxTable OBJECT-TYPE
   SYNTAX      SEQUENCE OF Pr1646v2PingSessionJitterMaxEntry
   MAX-ACCESS  not-accessible
   STATUS      current
   DESCRIPTION
      ""
   ::= {pr1646v2PingSessionJitterMax 1}

pr1646v2PingSessionJitterMaxEntry OBJECT-TYPE
   SYNTAX      Pr1646v2PingSessionJitterMaxEntry
   MAX-ACCESS  not-accessible
   STATUS      current
   DESCRIPTION
      ""
   INDEX      { pr1646v2PingSessionJitterMaxGlobalIx }
   ::= {pr1646v2PingSessionJitterMaxTable 1}

Pr1646v2PingSessionJitterMaxEntry ::=
   SEQUENCE
      {
      pr1646v2PingSessionJitterMaxGlobalIx
         GlobalIndex,
      pr1646v2PingSessionJitterMaxValue
         INTEGER
      }

pr1646v2PingSessionJitterMaxGlobalIx OBJECT-TYPE
   SYNTAX      GlobalIndex
   MAX-ACCESS  not-accessible
   STATUS      current
   DESCRIPTION
      "The value of the tlsCntTreeGlobalIndex of the MANAGED OBJECT."
   ::= {pr1646v2PingSessionJitterMaxEntry 10}

pr1646v2PingSessionJitterMaxValue OBJECT-TYPE
   SYNTAX      INTEGER
               {
               slnotsinsuseg (2147483647)
               }
   MAX-ACCESS  read-only
   STATUS      current
   DESCRIPTION
      "Path: session.performance.jitterMax

       unit name = ms
       formula = 10 / ; 10 *

       Possibilities:
               <not in use>   (2147483647)"
   ::= {pr1646v2PingSessionJitterMaxEntry 2147483648}


pr1646v2PingSessionTxPacketSec OBJECT IDENTIFIER ::= {pr1646v2PingSession 1156}

pr1646v2PingSessionTxPacketSecTable OBJECT-TYPE
   SYNTAX      SEQUENCE OF Pr1646v2PingSessionTxPacketSecEntry
   MAX-ACCESS  not-accessible
   STATUS      current
   DESCRIPTION
      ""
   ::= {pr1646v2PingSessionTxPacketSec 1}

pr1646v2PingSessionTxPacketSecEntry OBJECT-TYPE
   SYNTAX      Pr1646v2PingSessionTxPacketSecEntry
   MAX-ACCESS  not-accessible
   STATUS      current
   DESCRIPTION
      ""
   INDEX      { pr1646v2PingSessionTxPacketSecGlobalIx }
   ::= {pr1646v2PingSessionTxPacketSecTable 1}

Pr1646v2PingSessionTxPacketSecEntry ::=
   SEQUENCE
      {
      pr1646v2PingSessionTxPacketSecGlobalIx
         GlobalIndex,
      pr1646v2PingSessionTxPacketSecValue
         Integer32
      }

pr1646v2PingSessionTxPacketSecGlobalIx OBJECT-TYPE
   SYNTAX      GlobalIndex
   MAX-ACCESS  not-accessible
   STATUS      current
   DESCRIPTION
      "The value of the tlsCntTreeGlobalIndex of the MANAGED OBJECT."
   ::= {pr1646v2PingSessionTxPacketSecEntry 10}

pr1646v2PingSessionTxPacketSecValue OBJECT-TYPE
   SYNTAX      Integer32
   MAX-ACCESS  read-only
   STATUS      current
   DESCRIPTION
      "Path: session.performance.txPacketSec

       formula = 100 / ; 100 *"
   ::= {pr1646v2PingSessionTxPacketSecEntry 2147483648}


pr1646v2PingSessionRxPacketSec OBJECT IDENTIFIER ::= {pr1646v2PingSession 1172}

pr1646v2PingSessionRxPacketSecTable OBJECT-TYPE
   SYNTAX      SEQUENCE OF Pr1646v2PingSessionRxPacketSecEntry
   MAX-ACCESS  not-accessible
   STATUS      current
   DESCRIPTION
      ""
   ::= {pr1646v2PingSessionRxPacketSec 1}

pr1646v2PingSessionRxPacketSecEntry OBJECT-TYPE
   SYNTAX      Pr1646v2PingSessionRxPacketSecEntry
   MAX-ACCESS  not-accessible
   STATUS      current
   DESCRIPTION
      ""
   INDEX      { pr1646v2PingSessionRxPacketSecGlobalIx }
   ::= {pr1646v2PingSessionRxPacketSecTable 1}

Pr1646v2PingSessionRxPacketSecEntry ::=
   SEQUENCE
      {
      pr1646v2PingSessionRxPacketSecGlobalIx
         GlobalIndex,
      pr1646v2PingSessionRxPacketSecValue
         Integer32
      }

pr1646v2PingSessionRxPacketSecGlobalIx OBJECT-TYPE
   SYNTAX      GlobalIndex
   MAX-ACCESS  not-accessible
   STATUS      current
   DESCRIPTION
      "The value of the tlsCntTreeGlobalIndex of the MANAGED OBJECT."
   ::= {pr1646v2PingSessionRxPacketSecEntry 10}

pr1646v2PingSessionRxPacketSecValue OBJECT-TYPE
   SYNTAX      Integer32
   MAX-ACCESS  read-only
   STATUS      current
   DESCRIPTION
      "Path: session.performance.rxPacketSec

       formula = 100 / ; 100 *"
   ::= {pr1646v2PingSessionRxPacketSecEntry 2147483648}


pr1646v2PingSessionTxTarget OBJECT IDENTIFIER ::= {pr1646v2PingSession 1170}

pr1646v2PingSessionTxTargetTable OBJECT-TYPE
   SYNTAX      SEQUENCE OF Pr1646v2PingSessionTxTargetEntry
   MAX-ACCESS  not-accessible
   STATUS      current
   DESCRIPTION
      ""
   ::= {pr1646v2PingSessionTxTarget 1}

pr1646v2PingSessionTxTargetEntry OBJECT-TYPE
   SYNTAX      Pr1646v2PingSessionTxTargetEntry
   MAX-ACCESS  not-accessible
   STATUS      current
   DESCRIPTION
      ""
   INDEX      { pr1646v2PingSessionTxTargetGlobalIx }
   ::= {pr1646v2PingSessionTxTargetTable 1}

Pr1646v2PingSessionTxTargetEntry ::=
   SEQUENCE
      {
      pr1646v2PingSessionTxTargetGlobalIx
         GlobalIndex,
      pr1646v2PingSessionTxTargetValue
         INTEGER
      }

pr1646v2PingSessionTxTargetGlobalIx OBJECT-TYPE
   SYNTAX      GlobalIndex
   MAX-ACCESS  not-accessible
   STATUS      current
   DESCRIPTION
      "The value of the tlsCntTreeGlobalIndex of the MANAGED OBJECT."
   ::= {pr1646v2PingSessionTxTargetEntry 10}

pr1646v2PingSessionTxTargetValue OBJECT-TYPE
   SYNTAX      INTEGER
               {
               slnotsinsuseg (2147483647)
               }
   MAX-ACCESS  read-only
   STATUS      current
   DESCRIPTION
      "Path: session.performance.txTarget

       unit name = %
       formula = 100 / ; 100 *

       Possibilities:
               <not in use>   (2147483647)"
   ::= {pr1646v2PingSessionTxTargetEntry 2147483648}


pr1646v2PingSessionRxTarget OBJECT IDENTIFIER ::= {pr1646v2PingSession 1171}

pr1646v2PingSessionRxTargetTable OBJECT-TYPE
   SYNTAX      SEQUENCE OF Pr1646v2PingSessionRxTargetEntry
   MAX-ACCESS  not-accessible
   STATUS      current
   DESCRIPTION
      ""
   ::= {pr1646v2PingSessionRxTarget 1}

pr1646v2PingSessionRxTargetEntry OBJECT-TYPE
   SYNTAX      Pr1646v2PingSessionRxTargetEntry
   MAX-ACCESS  not-accessible
   STATUS      current
   DESCRIPTION
      ""
   INDEX      { pr1646v2PingSessionRxTargetGlobalIx }
   ::= {pr1646v2PingSessionRxTargetTable 1}

Pr1646v2PingSessionRxTargetEntry ::=
   SEQUENCE
      {
      pr1646v2PingSessionRxTargetGlobalIx
         GlobalIndex,
      pr1646v2PingSessionRxTargetValue
         INTEGER
      }

pr1646v2PingSessionRxTargetGlobalIx OBJECT-TYPE
   SYNTAX      GlobalIndex
   MAX-ACCESS  not-accessible
   STATUS      current
   DESCRIPTION
      "The value of the tlsCntTreeGlobalIndex of the MANAGED OBJECT."
   ::= {pr1646v2PingSessionRxTargetEntry 10}

pr1646v2PingSessionRxTargetValue OBJECT-TYPE
   SYNTAX      INTEGER
               {
               slnotsinsuseg (2147483647)
               }
   MAX-ACCESS  read-only
   STATUS      current
   DESCRIPTION
      "Path: session.performance.rxTarget

       unit name = %
       formula = 100 / ; 100 *

       Possibilities:
               <not in use>   (2147483647)"
   ::= {pr1646v2PingSessionRxTargetEntry 2147483648}


pr1646v2PingSessionResultLog OBJECT IDENTIFIER ::= {pr1646v2PingSession 1180}

pr1646v2PingSessionResultLogSSCTable OBJECT-TYPE
   SYNTAX      SEQUENCE OF Pr1646v2PingSessionResultLogEntry
   MAX-ACCESS  not-accessible
   STATUS      current
   DESCRIPTION
      ""
   ::= {pr1646v2PingSessionResultLog 1}

pr1646v2PingSessionResultLogEntry OBJECT-TYPE
   SYNTAX      Pr1646v2PingSessionResultLogEntry
   MAX-ACCESS  not-accessible
   STATUS      current
   DESCRIPTION
      ""
   INDEX      { pr1646v2PingSessionResultLogGlobalIx,
                pr1646v2PingSessionResultLogTableIx }
   ::= {pr1646v2PingSessionResultLogSSCTable 1}

Pr1646v2PingSessionResultLogEntry ::=
   SEQUENCE
      {
      pr1646v2PingSessionResultLogGlobalIx
         GlobalIndex,
      pr1646v2PingSessionResultLogTableIx
         TableIndex,
      pr1646v2PingSessionResultLogName
         DisplayString,
      pr1646v2PingSessionResultLogStatus
         INTEGER,
      pr1646v2PingSessionResultLogStartDate
         DisplayString,
      pr1646v2PingSessionResultLogEndDate
         DisplayString,
      pr1646v2PingSessionResultLogTestTime
         TimeTicks,
      pr1646v2PingSessionResultLogSent
         Counter64,
      pr1646v2PingSessionResultLogReceived
         Counter64,
      pr1646v2PingSessionResultLogPacketLoss
         Counter64,
      pr1646v2PingSessionResultLogPacketLossPer
         INTEGER,
      pr1646v2PingSessionResultLogTxTarget
         INTEGER,
      pr1646v2PingSessionResultLogRxTarget
         INTEGER,
      pr1646v2PingSessionResultLogSyncLoss
         INTEGER,
      pr1646v2PingSessionResultLogOutOfSequence
         Integer32,
      pr1646v2PingSessionResultLogRecAfterTim
         Counter64,
      pr1646v2PingSessionResultLogCrcErrors
         INTEGER,
      pr1646v2PingSessionResultLogLengthErrors
         Counter64,
      pr1646v2PingSessionResultLogDelayMin
         INTEGER,
      pr1646v2PingSessionResultLogDelayAvrg
         INTEGER,
      pr1646v2PingSessionResultLogDelayMax
         INTEGER,
      pr1646v2PingSessionResultLogJitterAvrg
         INTEGER,
      pr1646v2PingSessionResultLogJitterMax
         INTEGER,
      pr1646v2PingSessionResultLogTxPacketSec
         Integer32,
      pr1646v2PingSessionResultLogRxPacketSec
         Integer32,
      pr1646v2PingSessionResultLogBytesStatEncapsTx
         Counter64,
      pr1646v2PingSessionResultLogBytesStatOverheadTx
         Counter64,
      pr1646v2PingSessionResultLogBytesStatEncapsRx
         Counter64,
      pr1646v2PingSessionResultLogBytesStatOverheadRx
         Counter64,
      pr1646v2PingSessionResultLogBitsSecEncapsTx
         Integer32,
      pr1646v2PingSessionResultLogBitsSecOverheadTx
         Integer32,
      pr1646v2PingSessionResultLogBitsSecEncapsRx
         Integer32,
      pr1646v2PingSessionResultLogBitsSecOverheadRx
         Integer32,
      pr1646v2PingSessionResultLogBitsSecEncapsRxMin
         Integer32,
      pr1646v2PingSessionResultLogBitsSecEncapsRxMax
         Integer32,
      pr1646v2PingSessionResultLogAttributesDestination
         DisplayString,
      pr1646v2PingSessionResultLogAttributesFrameFromSize
         Integer32,
      pr1646v2PingSessionResultLogAttributesFrameToSize
         INTEGER,
      pr1646v2PingSessionResultLogAttributesFrameSizeType
         INTEGER,
      pr1646v2PingSessionResultLogAttributesFrameTimeOut
         Integer32,
      pr1646v2PingSessionResultLogAttributesFrameCrc
         INTEGER,
      pr1646v2PingSessionResultLogAttributesFrameTc
         Integer32,
      pr1646v2PingSessionResultLogAttributesTypeTimeBetween
         INTEGER,
      pr1646v2PingSessionResultLogAttributesTypeBandwidth
         INTEGER,
      pr1646v2PingSessionResultLogAttributesTypePacketsASec
         INTEGER,
      pr1646v2PingSessionResultLogAttributesTypeTxTc
         INTEGER,
      pr1646v2PingSessionResultLogAttributesTypeOutStanding
         INTEGER,
      pr1646v2PingSessionResultLogAttributesTypeBurstBeforeRx
         INTEGER,
      pr1646v2PingSessionResultLogAttributesTypeSameSequence
         INTEGER,
      pr1646v2PingSessionResultLogAttributesDuration
         INTEGER,
      pr1646v2PingSessionResultLogAttributesNrPackets
         INTEGER
      }

pr1646v2PingSessionResultLogGlobalIx OBJECT-TYPE
   SYNTAX      GlobalIndex
   MAX-ACCESS  not-accessible
   STATUS      current
   DESCRIPTION
      "The value of the tlsCntTreeGlobalIndex of the MANAGED OBJECT."
   ::= {pr1646v2PingSessionResultLogEntry 10}

pr1646v2PingSessionResultLogTableIx OBJECT-TYPE
   SYNTAX      TableIndex
   MAX-ACCESS  not-accessible
   STATUS      current
   DESCRIPTION
      ""
   ::= {pr1646v2PingSessionResultLogEntry 11}

pr1646v2PingSessionResultLogName OBJECT-TYPE
   SYNTAX      DisplayString
   MAX-ACCESS  read-only
   STATUS      current
   DESCRIPTION
      "Path: session.performance.resultLog.name"
   ::= {pr1646v2PingSessionResultLogEntry 100663296}

pr1646v2PingSessionResultLogStatus OBJECT-TYPE
   SYNTAX      INTEGER
               {
               idle (128),
               destinationProblem (40),
               openSocketProblem (41),
               logProblem (42),
               waitHalfDuplexSetup (2),
               waitGroup (3),
               waitDns (4),
               waitDnsStart (5),
               releaseSocket (6),
               waitForRepeat (7),
               runFlood (11),
               runAsymFlood (12),
               runNormal (13),
               runBandwidth (14),
               runPacketsASec (15),
               haltedFlood (21),
               haltedAsymFlood (22),
               haltedNormal (23),
               haltedBandwidth (24),
               haltedPacketsASec (25),
               optimumFlood (31),
               optimumAsymFlood (32),
               optimumNormal (33),
               optimumBandwidth (34),
               optimumPacketsASec (35),
               problemHaltedFlood (26),
               problemHaltedAsymFlood (27),
               problemHaltedNormal (28),
               problemHaltedBandwidth (29),
               problemHaltedPacketsASec (30),
               testRunFlood (51),
               testRunAsymFlood (52),
               testRunNormal (53),
               testRunBandwidth (54),
               testRunPacketsASec (55),
               testReleaseSocket (56),
               testWaitForRepeat (57),
               testHaltedFlood (61),
               testHaltedAsymFlood (62),
               testHaltedNormal (63),
               testHaltedBandwidth (64),
               testHaltedPacketsASec (65)
               }
   MAX-ACCESS  read-only
   STATUS      current
   DESCRIPTION
      "Path: session.performance.resultLog.status

       Possibilities:
               idle   (128)
               destinationProblem   (40)
               openSocketProblem   (41)
               logProblem   (42)
               waitHalfDuplexSetup   (2)
               waitGroup   (3)
               waitDns   (4)
               waitDnsStart   (5)
               releaseSocket   (6)
               waitForRepeat   (7)
               runFlood   (11)
               runAsymFlood   (12)
               runNormal   (13)
               runBandwidth   (14)
               runPacketsASec   (15)
               haltedFlood   (21)
               haltedAsymFlood   (22)
               haltedNormal   (23)
               haltedBandwidth   (24)
               haltedPacketsASec   (25)
               optimumFlood   (31)
               optimumAsymFlood   (32)
               optimumNormal   (33)
               optimumBandwidth   (34)
               optimumPacketsASec   (35)
               problemHaltedFlood   (26)
               problemHaltedAsymFlood   (27)
               problemHaltedNormal   (28)
               problemHaltedBandwidth   (29)
               problemHaltedPacketsASec   (30)
               testRunFlood   (51)
               testRunAsymFlood   (52)
               testRunNormal   (53)
               testRunBandwidth   (54)
               testRunPacketsASec   (55)
               testReleaseSocket   (56)
               testWaitForRepeat   (57)
               testHaltedFlood   (61)
               testHaltedAsymFlood   (62)
               testHaltedNormal   (63)
               testHaltedBandwidth   (64)
               testHaltedPacketsASec   (65)"
   ::= {pr1646v2PingSessionResultLogEntry 16777216}

pr1646v2PingSessionResultLogStartDate OBJECT-TYPE
   SYNTAX      DisplayString
   MAX-ACCESS  read-only
   STATUS      current
   DESCRIPTION
      "Path: session.performance.resultLog.startDate"
   ::= {pr1646v2PingSessionResultLogEntry 2382364672}

pr1646v2PingSessionResultLogEndDate OBJECT-TYPE
   SYNTAX      DisplayString
   MAX-ACCESS  read-only
   STATUS      current
   DESCRIPTION
      "Path: session.performance.resultLog.endDate"
   ::= {pr1646v2PingSessionResultLogEntry 2399141888}

pr1646v2PingSessionResultLogTestTime OBJECT-TYPE
   SYNTAX      TimeTicks
   MAX-ACCESS  read-only
   STATUS      current
   DESCRIPTION
      "Path: session.performance.resultLog.testTime

       Time in centi-second."
   ::= {pr1646v2PingSessionResultLogEntry 2365587456}

pr1646v2PingSessionResultLogSent OBJECT-TYPE
   SYNTAX      Counter64
   MAX-ACCESS  read-only
   STATUS      current
   DESCRIPTION
      "Path: session.performance.resultLog.sent

       64 bit unsigned wrappable counter."
   ::= {pr1646v2PingSessionResultLogEntry 2415919104}

pr1646v2PingSessionResultLogReceived OBJECT-TYPE
   SYNTAX      Counter64
   MAX-ACCESS  read-only
   STATUS      current
   DESCRIPTION
      "Path: session.performance.resultLog.received

       64 bit unsigned wrappable counter."
   ::= {pr1646v2PingSessionResultLogEntry 2432696320}

pr1646v2PingSessionResultLogPacketLoss OBJECT-TYPE
   SYNTAX      Counter64
   MAX-ACCESS  read-only
   STATUS      current
   DESCRIPTION
      "Path: session.performance.resultLog.packetLoss

       64 bit unsigned wrappable counter."
   ::= {pr1646v2PingSessionResultLogEntry 2449473536}

pr1646v2PingSessionResultLogPacketLossPer OBJECT-TYPE
   SYNTAX      INTEGER
               {
               slnotsinsuseg (2147483647)
               }
   MAX-ACCESS  read-only
   STATUS      current
   DESCRIPTION
      "Path: session.performance.resultLog.packetLossPer

       unit name = %
       formula = 100 / ; 100 *

       Possibilities:
               <not in use>   (2147483647)"
   ::= {pr1646v2PingSessionResultLogEntry 2466250752}

pr1646v2PingSessionResultLogTxTarget OBJECT-TYPE
   SYNTAX      INTEGER
               {
               slnotsinsuseg (2147483647)
               }
   MAX-ACCESS  read-only
   STATUS      current
   DESCRIPTION
      "Path: session.performance.resultLog.txTarget

       unit name = %
       formula = 100 / ; 100 *

       Possibilities:
               <not in use>   (2147483647)"
   ::= {pr1646v2PingSessionResultLogEntry 2684354560}

pr1646v2PingSessionResultLogRxTarget OBJECT-TYPE
   SYNTAX      INTEGER
               {
               slnotsinsuseg (2147483647)
               }
   MAX-ACCESS  read-only
   STATUS      current
   DESCRIPTION
      "Path: session.performance.resultLog.rxTarget

       unit name = %
       formula = 100 / ; 100 *

       Possibilities:
               <not in use>   (2147483647)"
   ::= {pr1646v2PingSessionResultLogEntry 2701131776}

pr1646v2PingSessionResultLogSyncLoss OBJECT-TYPE
   SYNTAX      INTEGER
               {
               slnotsinsuseg (-1)
               }
   MAX-ACCESS  read-only
   STATUS      current
   DESCRIPTION
      "Path: session.performance.resultLog.syncLoss

       Possibilities:
               <not in use>   (-1)"
   ::= {pr1646v2PingSessionResultLogEntry 2499805184}

pr1646v2PingSessionResultLogOutOfSequence OBJECT-TYPE
   SYNTAX      Integer32
   MAX-ACCESS  read-only
   STATUS      current
   DESCRIPTION
      "Path: session.performance.resultLog.outOfSequence"
   ::= {pr1646v2PingSessionResultLogEntry 2483027968}

pr1646v2PingSessionResultLogRecAfterTim OBJECT-TYPE
   SYNTAX      Counter64
   MAX-ACCESS  read-only
   STATUS      current
   DESCRIPTION
      "Path: session.performance.resultLog.recAfterTim

       64 bit unsigned wrappable counter."
   ::= {pr1646v2PingSessionResultLogEntry 2550136832}

pr1646v2PingSessionResultLogCrcErrors OBJECT-TYPE
   SYNTAX      INTEGER
               {
               slnotsinsuseg (-1)
               }
   MAX-ACCESS  read-only
   STATUS      current
   DESCRIPTION
      "Path: session.performance.resultLog.crcErrors

       Possibilities:
               <not in use>   (-1)"
   ::= {pr1646v2PingSessionResultLogEntry 2516582400}

pr1646v2PingSessionResultLogLengthErrors OBJECT-TYPE
   SYNTAX      Counter64
   MAX-ACCESS  read-only
   STATUS      current
   DESCRIPTION
      "Path: session.performance.resultLog.lengthErrors

       64 bit unsigned wrappable counter."
   ::= {pr1646v2PingSessionResultLogEntry 2533359616}

pr1646v2PingSessionResultLogDelayMin OBJECT-TYPE
   SYNTAX      INTEGER
               {
               slnotsinsuseg (2147483647)
               }
   MAX-ACCESS  read-only
   STATUS      current
   DESCRIPTION
      "Path: session.performance.resultLog.delayMin

       unit name = ms
       formula = 10 / ; 10 *

       Possibilities:
               <not in use>   (2147483647)"
   ::= {pr1646v2PingSessionResultLogEntry 2566914048}

pr1646v2PingSessionResultLogDelayAvrg OBJECT-TYPE
   SYNTAX      INTEGER
               {
               slnotsinsuseg (2147483647)
               }
   MAX-ACCESS  read-only
   STATUS      current
   DESCRIPTION
      "Path: session.performance.resultLog.delayAvrg

       unit name = ms
       formula = 10 / ; 10 *

       Possibilities:
               <not in use>   (2147483647)"
   ::= {pr1646v2PingSessionResultLogEntry 2583691264}

pr1646v2PingSessionResultLogDelayMax OBJECT-TYPE
   SYNTAX      INTEGER
               {
               slnotsinsuseg (2147483647)
               }
   MAX-ACCESS  read-only
   STATUS      current
   DESCRIPTION
      "Path: session.performance.resultLog.delayMax

       unit name = ms
       formula = 10 / ; 10 *

       Possibilities:
               <not in use>   (2147483647)"
   ::= {pr1646v2PingSessionResultLogEntry 2600468480}

pr1646v2PingSessionResultLogJitterAvrg OBJECT-TYPE
   SYNTAX      INTEGER
               {
               slnotsinsuseg (2147483647)
               }
   MAX-ACCESS  read-only
   STATUS      current
   DESCRIPTION
      "Path: session.performance.resultLog.jitterAvrg

       unit name = ms
       formula = 10 / ; 10 *

       Possibilities:
               <not in use>   (2147483647)"
   ::= {pr1646v2PingSessionResultLogEntry 2734686208}

pr1646v2PingSessionResultLogJitterMax OBJECT-TYPE
   SYNTAX      INTEGER
               {
               slnotsinsuseg (2147483647)
               }
   MAX-ACCESS  read-only
   STATUS      current
   DESCRIPTION
      "Path: session.performance.resultLog.jitterMax

       unit name = ms
       formula = 10 / ; 10 *

       Possibilities:
               <not in use>   (2147483647)"
   ::= {pr1646v2PingSessionResultLogEntry 2751463424}

pr1646v2PingSessionResultLogTxPacketSec OBJECT-TYPE
   SYNTAX      Integer32
   MAX-ACCESS  read-only
   STATUS      current
   DESCRIPTION
      "Path: session.performance.resultLog.txPacketSec

       formula = 100 / ; 100 *"
   ::= {pr1646v2PingSessionResultLogEntry 2617245696}

pr1646v2PingSessionResultLogRxPacketSec OBJECT-TYPE
   SYNTAX      Integer32
   MAX-ACCESS  read-only
   STATUS      current
   DESCRIPTION
      "Path: session.performance.resultLog.rxPacketSec

       formula = 100 / ; 100 *"
   ::= {pr1646v2PingSessionResultLogEntry 2717908992}

pr1646v2PingSessionResultLogBytesStatEncapsTx OBJECT-TYPE
   SYNTAX      Counter64
   MAX-ACCESS  read-only
   STATUS      current
   DESCRIPTION
      "Path: session.performance.resultLog.bytesStat.encapsTx

       64 bit unsigned wrappable counter."
   ::= {pr1646v2PingSessionResultLogEntry 2634088448}

pr1646v2PingSessionResultLogBytesStatOverheadTx OBJECT-TYPE
   SYNTAX      Counter64
   MAX-ACCESS  read-only
   STATUS      current
   DESCRIPTION
      "Path: session.performance.resultLog.bytesStat.overheadTx

       64 bit unsigned wrappable counter."
   ::= {pr1646v2PingSessionResultLogEntry 2634285056}

pr1646v2PingSessionResultLogBytesStatEncapsRx OBJECT-TYPE
   SYNTAX      Counter64
   MAX-ACCESS  read-only
   STATUS      current
   DESCRIPTION
      "Path: session.performance.resultLog.bytesStat.encapsRx

       64 bit unsigned wrappable counter."
   ::= {pr1646v2PingSessionResultLogEntry 2634350592}

pr1646v2PingSessionResultLogBytesStatOverheadRx OBJECT-TYPE
   SYNTAX      Counter64
   MAX-ACCESS  read-only
   STATUS      current
   DESCRIPTION
      "Path: session.performance.resultLog.bytesStat.overheadRx

       64 bit unsigned wrappable counter."
   ::= {pr1646v2PingSessionResultLogEntry 2634547200}

pr1646v2PingSessionResultLogBitsSecEncapsTx OBJECT-TYPE
   SYNTAX      Integer32
   MAX-ACCESS  read-only
   STATUS      current
   DESCRIPTION
      "Path: session.performance.resultLog.bitsSec.encapsTx"
   ::= {pr1646v2PingSessionResultLogEntry 2667642880}

pr1646v2PingSessionResultLogBitsSecOverheadTx OBJECT-TYPE
   SYNTAX      Integer32
   MAX-ACCESS  read-only
   STATUS      current
   DESCRIPTION
      "Path: session.performance.resultLog.bitsSec.overheadTx"
   ::= {pr1646v2PingSessionResultLogEntry 2667839488}

pr1646v2PingSessionResultLogBitsSecEncapsRx OBJECT-TYPE
   SYNTAX      Integer32
   MAX-ACCESS  read-only
   STATUS      current
   DESCRIPTION
      "Path: session.performance.resultLog.bitsSec.encapsRx"
   ::= {pr1646v2PingSessionResultLogEntry 2667905024}

pr1646v2PingSessionResultLogBitsSecOverheadRx OBJECT-TYPE
   SYNTAX      Integer32
   MAX-ACCESS  read-only
   STATUS      current
   DESCRIPTION
      "Path: session.performance.resultLog.bitsSec.overheadRx"
   ::= {pr1646v2PingSessionResultLogEntry 2668101632}

pr1646v2PingSessionResultLogBitsSecEncapsRxMin OBJECT-TYPE
   SYNTAX      Integer32
   MAX-ACCESS  read-only
   STATUS      current
   DESCRIPTION
      "Path: session.performance.resultLog.bitsSec.encapsRxMin"
   ::= {pr1646v2PingSessionResultLogEntry 2668232704}

pr1646v2PingSessionResultLogBitsSecEncapsRxMax OBJECT-TYPE
   SYNTAX      Integer32
   MAX-ACCESS  read-only
   STATUS      current
   DESCRIPTION
      "Path: session.performance.resultLog.bitsSec.encapsRxMax"
   ::= {pr1646v2PingSessionResultLogEntry 2668298240}

pr1646v2PingSessionResultLogAttributesDestination OBJECT-TYPE
   SYNTAX      DisplayString
   MAX-ACCESS  read-only
   STATUS      current
   DESCRIPTION
      "Path: session.performance.resultLog.attributes.destination"
   ::= {pr1646v2PingSessionResultLogEntry 96993280}

pr1646v2PingSessionResultLogAttributesFrameFromSize OBJECT-TYPE
   SYNTAX      Integer32
   MAX-ACCESS  read-only
   STATUS      current
   DESCRIPTION
      "Path: session.performance.resultLog.attributes.frame.fromSize"
   ::= {pr1646v2PingSessionResultLogEntry 97124608}

pr1646v2PingSessionResultLogAttributesFrameToSize OBJECT-TYPE
   SYNTAX      INTEGER
               {
               slnotsinsuseg (-1)
               }
   MAX-ACCESS  read-only
   STATUS      current
   DESCRIPTION
      "Path: session.performance.resultLog.attributes.frame.toSize

       Possibilities:
               <not in use>   (-1)"
   ::= {pr1646v2PingSessionResultLogEntry 97124864}

pr1646v2PingSessionResultLogAttributesFrameSizeType OBJECT-TYPE
   SYNTAX      INTEGER
               {
               single (1),
               range (2),
               toggle (3)
               }
   MAX-ACCESS  read-only
   STATUS      current
   DESCRIPTION
      "Path: session.performance.resultLog.attributes.frame.sizeType

       Possibilities:
               single   (1)
               range   (2)
               toggle   (3)"
   ::= {pr1646v2PingSessionResultLogEntry 97125120}

pr1646v2PingSessionResultLogAttributesFrameTimeOut OBJECT-TYPE
   SYNTAX      Integer32
   MAX-ACCESS  read-only
   STATUS      current
   DESCRIPTION
      "Path: session.performance.resultLog.attributes.frame.timeOut"
   ::= {pr1646v2PingSessionResultLogEntry 97125376}

pr1646v2PingSessionResultLogAttributesFrameCrc OBJECT-TYPE
   SYNTAX      INTEGER
               {
               txRx (1),
               tx (2),
               no (3)
               }
   MAX-ACCESS  read-only
   STATUS      current
   DESCRIPTION
      "Path: session.performance.resultLog.attributes.frame.crc

       Possibilities:
               txRx   (1)
               tx   (2)
               no   (3)"
   ::= {pr1646v2PingSessionResultLogEntry 97126656}

pr1646v2PingSessionResultLogAttributesFrameTc OBJECT-TYPE
   SYNTAX      Integer32
   MAX-ACCESS  read-only
   STATUS      current
   DESCRIPTION
      "Path: session.performance.resultLog.attributes.frame.tc"
   ::= {pr1646v2PingSessionResultLogEntry 97128448}

pr1646v2PingSessionResultLogAttributesTypeTimeBetween OBJECT-TYPE
   SYNTAX      INTEGER
               {
               slnotsinsuseg (-1)
               }
   MAX-ACCESS  read-only
   STATUS      current
   DESCRIPTION
      "Path: session.performance.resultLog.attributes.type.timeBetween

       Possibilities:
               <not in use>   (-1)"
   ::= {pr1646v2PingSessionResultLogEntry 97190144}

pr1646v2PingSessionResultLogAttributesTypeBandwidth OBJECT-TYPE
   SYNTAX      INTEGER
               {
               slnotsinsuseg (-1)
               }
   MAX-ACCESS  read-only
   STATUS      current
   DESCRIPTION
      "Path: session.performance.resultLog.attributes.type.bandwidth

       Possibilities:
               <not in use>   (-1)"
   ::= {pr1646v2PingSessionResultLogEntry 97190400}

pr1646v2PingSessionResultLogAttributesTypePacketsASec OBJECT-TYPE
   SYNTAX      INTEGER
               {
               slnotsinsuseg (-1)
               }
   MAX-ACCESS  read-only
   STATUS      current
   DESCRIPTION
      "Path: session.performance.resultLog.attributes.type.packetsASec

       Possibilities:
               <not in use>   (-1)"
   ::= {pr1646v2PingSessionResultLogEntry 97191168}

pr1646v2PingSessionResultLogAttributesTypeTxTc OBJECT-TYPE
   SYNTAX      INTEGER
               {
               slnotsinsuseg (-1)
               }
   UNITS       "us"
   MAX-ACCESS  read-only
   STATUS      current
   DESCRIPTION
      "Path: session.performance.resultLog.attributes.type.txTc

       unit name = us

       Possibilities:
               <not in use>   (-1)"
   ::= {pr1646v2PingSessionResultLogEntry 97192960}

pr1646v2PingSessionResultLogAttributesTypeOutStanding OBJECT-TYPE
   SYNTAX      INTEGER
               {
               slnotsinsuseg (-1)
               }
   MAX-ACCESS  read-only
   STATUS      current
   DESCRIPTION
      "Path: session.performance.resultLog.attributes.type.outStanding

       Possibilities:
               <not in use>   (-1)"
   ::= {pr1646v2PingSessionResultLogEntry 97190656}

pr1646v2PingSessionResultLogAttributesTypeBurstBeforeRx OBJECT-TYPE
   SYNTAX      INTEGER
               {
               slnotsinsuseg (-1)
               }
   MAX-ACCESS  read-only
   STATUS      current
   DESCRIPTION
      "Path: session.performance.resultLog.attributes.type.burstBeforeRx

       Possibilities:
               <not in use>   (-1)"
   ::= {pr1646v2PingSessionResultLogEntry 97191424}

pr1646v2PingSessionResultLogAttributesTypeSameSequence OBJECT-TYPE
   SYNTAX      INTEGER
               {
               slnotsinsuseg (-1)
               }
   MAX-ACCESS  read-only
   STATUS      current
   DESCRIPTION
      "Path: session.performance.resultLog.attributes.type.sameSequence

       Possibilities:
               <not in use>   (-1)"
   ::= {pr1646v2PingSessionResultLogEntry 97190912}

pr1646v2PingSessionResultLogAttributesDuration OBJECT-TYPE
   SYNTAX      INTEGER
               {
               slnotsinsuseg (-1)
               }
   MAX-ACCESS  read-only
   STATUS      current
   DESCRIPTION
      "Path: session.performance.resultLog.attributes.duration

       Possibilities:
               <not in use>   (-1)"
   ::= {pr1646v2PingSessionResultLogEntry 97255424}

pr1646v2PingSessionResultLogAttributesNrPackets OBJECT-TYPE
   SYNTAX      INTEGER
               {
               slnotsinsuseg (-1)
               }
   MAX-ACCESS  read-only
   STATUS      current
   DESCRIPTION
      "Path: session.performance.resultLog.attributes.nrPackets

       Possibilities:
               <not in use>   (-1)"
   ::= {pr1646v2PingSessionResultLogEntry 97320960}


pr1646v2PingSessionStatisticsLog OBJECT IDENTIFIER ::= {pr1646v2PingSession 1181}

pr1646v2PingSessionStatisticsLogSSCTable OBJECT-TYPE
   SYNTAX      SEQUENCE OF Pr1646v2PingSessionStatisticsLogEntry
   MAX-ACCESS  not-accessible
   STATUS      current
   DESCRIPTION
      ""
   ::= {pr1646v2PingSessionStatisticsLog 1}

pr1646v2PingSessionStatisticsLogEntry OBJECT-TYPE
   SYNTAX      Pr1646v2PingSessionStatisticsLogEntry
   MAX-ACCESS  not-accessible
   STATUS      current
   DESCRIPTION
      ""
   INDEX      { pr1646v2PingSessionStatisticsLogGlobalIx,
                pr1646v2PingSessionStatisticsLogTableIx }
   ::= {pr1646v2PingSessionStatisticsLogSSCTable 1}

Pr1646v2PingSessionStatisticsLogEntry ::=
   SEQUENCE
      {
      pr1646v2PingSessionStatisticsLogGlobalIx
         GlobalIndex,
      pr1646v2PingSessionStatisticsLogTableIx
         TableIndex,
      pr1646v2PingSessionStatisticsLogTestDate
         DisplayString,
      pr1646v2PingSessionStatisticsLogTestTime
         TimeTicks,
      pr1646v2PingSessionStatisticsLogSent
         Counter64,
      pr1646v2PingSessionStatisticsLogBytesSent
         Counter64,
      pr1646v2PingSessionStatisticsLogOverhBytesSent
         Counter64,
      pr1646v2PingSessionStatisticsLogReceived
         Counter64,
      pr1646v2PingSessionStatisticsLogBytesReceived
         Counter64,
      pr1646v2PingSessionStatisticsLogOverhBytesRec
         Counter64,
      pr1646v2PingSessionStatisticsLogPacketLoss
         Counter64,
      pr1646v2PingSessionStatisticsLogSyncLoss
         Counter64,
      pr1646v2PingSessionStatisticsLogCrcErrors
         Counter64,
      pr1646v2PingSessionStatisticsLogLengthErrors
         Counter64,
      pr1646v2PingSessionStatisticsLogRecTimeOut
         Counter64,
      pr1646v2PingSessionStatisticsLogDelayMin
         INTEGER,
      pr1646v2PingSessionStatisticsLogDelayAvrg
         INTEGER,
      pr1646v2PingSessionStatisticsLogDelayMax
         INTEGER,
      pr1646v2PingSessionStatisticsLogDelayLast
         INTEGER
      }

pr1646v2PingSessionStatisticsLogGlobalIx OBJECT-TYPE
   SYNTAX      GlobalIndex
   MAX-ACCESS  not-accessible
   STATUS      current
   DESCRIPTION
      "The value of the tlsCntTreeGlobalIndex of the MANAGED OBJECT."
   ::= {pr1646v2PingSessionStatisticsLogEntry 10}

pr1646v2PingSessionStatisticsLogTableIx OBJECT-TYPE
   SYNTAX      TableIndex
   MAX-ACCESS  not-accessible
   STATUS      current
   DESCRIPTION
      ""
   ::= {pr1646v2PingSessionStatisticsLogEntry 11}

pr1646v2PingSessionStatisticsLogTestDate OBJECT-TYPE
   SYNTAX      DisplayString
   MAX-ACCESS  read-only
   STATUS      current
   DESCRIPTION
      "Path: session.performance.statisticsLog.testDate"
   ::= {pr1646v2PingSessionStatisticsLogEntry 285212672}

pr1646v2PingSessionStatisticsLogTestTime OBJECT-TYPE
   SYNTAX      TimeTicks
   MAX-ACCESS  read-only
   STATUS      current
   DESCRIPTION
      "Path: session.performance.statisticsLog.testTime

       Time in centi-second."
   ::= {pr1646v2PingSessionStatisticsLogEntry 16777216}

pr1646v2PingSessionStatisticsLogSent OBJECT-TYPE
   SYNTAX      Counter64
   MAX-ACCESS  read-only
   STATUS      current
   DESCRIPTION
      "Path: session.performance.statisticsLog.sent

       64 bit unsigned wrappable counter."
   ::= {pr1646v2PingSessionStatisticsLogEntry 33554432}

pr1646v2PingSessionStatisticsLogBytesSent OBJECT-TYPE
   SYNTAX      Counter64
   MAX-ACCESS  read-only
   STATUS      current
   DESCRIPTION
      "Path: session.performance.statisticsLog.bytesSent

       64 bit unsigned wrappable counter."
   ::= {pr1646v2PingSessionStatisticsLogEntry 50331648}

pr1646v2PingSessionStatisticsLogOverhBytesSent OBJECT-TYPE
   SYNTAX      Counter64
   MAX-ACCESS  read-only
   STATUS      current
   DESCRIPTION
      "Path: session.performance.statisticsLog.overhBytesSent

       64 bit unsigned wrappable counter."
   ::= {pr1646v2PingSessionStatisticsLogEntry 67108864}

pr1646v2PingSessionStatisticsLogReceived OBJECT-TYPE
   SYNTAX      Counter64
   MAX-ACCESS  read-only
   STATUS      current
   DESCRIPTION
      "Path: session.performance.statisticsLog.received

       64 bit unsigned wrappable counter."
   ::= {pr1646v2PingSessionStatisticsLogEntry 83886080}

pr1646v2PingSessionStatisticsLogBytesReceived OBJECT-TYPE
   SYNTAX      Counter64
   MAX-ACCESS  read-only
   STATUS      current
   DESCRIPTION
      "Path: session.performance.statisticsLog.bytesReceived

       64 bit unsigned wrappable counter."
   ::= {pr1646v2PingSessionStatisticsLogEntry 100663296}

pr1646v2PingSessionStatisticsLogOverhBytesRec OBJECT-TYPE
   SYNTAX      Counter64
   MAX-ACCESS  read-only
   STATUS      current
   DESCRIPTION
      "Path: session.performance.statisticsLog.overhBytesRec

       64 bit unsigned wrappable counter."
   ::= {pr1646v2PingSessionStatisticsLogEntry 117440512}

pr1646v2PingSessionStatisticsLogPacketLoss OBJECT-TYPE
   SYNTAX      Counter64
   MAX-ACCESS  read-only
   STATUS      current
   DESCRIPTION
      "Path: session.performance.statisticsLog.packetLoss

       64 bit unsigned wrappable counter."
   ::= {pr1646v2PingSessionStatisticsLogEntry 134217728}

pr1646v2PingSessionStatisticsLogSyncLoss OBJECT-TYPE
   SYNTAX      Counter64
   MAX-ACCESS  read-only
   STATUS      current
   DESCRIPTION
      "Path: session.performance.statisticsLog.syncLoss

       64 bit unsigned wrappable counter."
   ::= {pr1646v2PingSessionStatisticsLogEntry 150994944}

pr1646v2PingSessionStatisticsLogCrcErrors OBJECT-TYPE
   SYNTAX      Counter64
   MAX-ACCESS  read-only
   STATUS      current
   DESCRIPTION
      "Path: session.performance.statisticsLog.crcErrors

       64 bit unsigned wrappable counter."
   ::= {pr1646v2PingSessionStatisticsLogEntry 167772160}

pr1646v2PingSessionStatisticsLogLengthErrors OBJECT-TYPE
   SYNTAX      Counter64
   MAX-ACCESS  read-only
   STATUS      current
   DESCRIPTION
      "Path: session.performance.statisticsLog.lengthErrors

       64 bit unsigned wrappable counter."
   ::= {pr1646v2PingSessionStatisticsLogEntry 184549376}

pr1646v2PingSessionStatisticsLogRecTimeOut OBJECT-TYPE
   SYNTAX      Counter64
   MAX-ACCESS  read-only
   STATUS      current
   DESCRIPTION
      "Path: session.performance.statisticsLog.recTimeOut

       64 bit unsigned wrappable counter."
   ::= {pr1646v2PingSessionStatisticsLogEntry 201326592}

pr1646v2PingSessionStatisticsLogDelayMin OBJECT-TYPE
   SYNTAX      INTEGER
               {
               slnotsinsuseg (2147483647)
               }
   MAX-ACCESS  read-only
   STATUS      current
   DESCRIPTION
      "Path: session.performance.statisticsLog.delayMin

       unit name = ms
       formula = 10 / ; 10 *

       Possibilities:
               <not in use>   (2147483647)"
   ::= {pr1646v2PingSessionStatisticsLogEntry 251658240}

pr1646v2PingSessionStatisticsLogDelayAvrg OBJECT-TYPE
   SYNTAX      INTEGER
               {
               slnotsinsuseg (2147483647)
               }
   MAX-ACCESS  read-only
   STATUS      current
   DESCRIPTION
      "Path: session.performance.statisticsLog.delayAvrg

       unit name = ms
       formula = 10 / ; 10 *

       Possibilities:
               <not in use>   (2147483647)"
   ::= {pr1646v2PingSessionStatisticsLogEntry 218103808}

pr1646v2PingSessionStatisticsLogDelayMax OBJECT-TYPE
   SYNTAX      INTEGER
               {
               slnotsinsuseg (2147483647)
               }
   MAX-ACCESS  read-only
   STATUS      current
   DESCRIPTION
      "Path: session.performance.statisticsLog.delayMax

       unit name = ms
       formula = 10 / ; 10 *

       Possibilities:
               <not in use>   (2147483647)"
   ::= {pr1646v2PingSessionStatisticsLogEntry 268435456}

pr1646v2PingSessionStatisticsLogDelayLast OBJECT-TYPE
   SYNTAX      INTEGER
               {
               slnotsinsuseg (2147483647)
               }
   MAX-ACCESS  read-only
   STATUS      current
   DESCRIPTION
      "Path: session.performance.statisticsLog.delayLast

       unit name = ms
       formula = 10 / ; 10 *

       Possibilities:
               <not in use>   (2147483647)"
   ::= {pr1646v2PingSessionStatisticsLogEntry 234881024}


pr1646v2PingSessionErrorLog OBJECT IDENTIFIER ::= {pr1646v2PingSession 1182}

pr1646v2PingSessionErrorLogSSCTable OBJECT-TYPE
   SYNTAX      SEQUENCE OF Pr1646v2PingSessionErrorLogEntry
   MAX-ACCESS  not-accessible
   STATUS      current
   DESCRIPTION
      ""
   ::= {pr1646v2PingSessionErrorLog 1}

pr1646v2PingSessionErrorLogEntry OBJECT-TYPE
   SYNTAX      Pr1646v2PingSessionErrorLogEntry
   MAX-ACCESS  not-accessible
   STATUS      current
   DESCRIPTION
      ""
   INDEX      { pr1646v2PingSessionErrorLogGlobalIx,
                pr1646v2PingSessionErrorLogTableIx }
   ::= {pr1646v2PingSessionErrorLogSSCTable 1}

Pr1646v2PingSessionErrorLogEntry ::=
   SEQUENCE
      {
      pr1646v2PingSessionErrorLogGlobalIx
         GlobalIndex,
      pr1646v2PingSessionErrorLogTableIx
         TableIndex,
      pr1646v2PingSessionErrorLogTestTime
         TimeTicks,
      pr1646v2PingSessionErrorLogTestNumber
         Integer32,
      pr1646v2PingSessionErrorLogLastFaultSequenceNr
         Counter64,
      pr1646v2PingSessionErrorLogLoss
         Integer32,
      pr1646v2PingSessionErrorLogLength
         Integer32,
      pr1646v2PingSessionErrorLogCrc
         Integer32,
      pr1646v2PingSessionErrorLogSyncLoss
         Integer32,
      pr1646v2PingSessionErrorLogRecTimeOut
         Integer32,
      pr1646v2PingSessionErrorLogOutOfSequence
         Integer32,
      pr1646v2PingSessionErrorLogStreaming
         Integer32
      }

pr1646v2PingSessionErrorLogGlobalIx OBJECT-TYPE
   SYNTAX      GlobalIndex
   MAX-ACCESS  not-accessible
   STATUS      current
   DESCRIPTION
      "The value of the tlsCntTreeGlobalIndex of the MANAGED OBJECT."
   ::= {pr1646v2PingSessionErrorLogEntry 10}

pr1646v2PingSessionErrorLogTableIx OBJECT-TYPE
   SYNTAX      TableIndex
   MAX-ACCESS  not-accessible
   STATUS      current
   DESCRIPTION
      ""
   ::= {pr1646v2PingSessionErrorLogEntry 11}

pr1646v2PingSessionErrorLogTestTime OBJECT-TYPE
   SYNTAX      TimeTicks
   MAX-ACCESS  read-only
   STATUS      current
   DESCRIPTION
      "Path: session.performance.errorLog.testTime

       Time in centi-second."
   ::= {pr1646v2PingSessionErrorLogEntry 16777216}

pr1646v2PingSessionErrorLogTestNumber OBJECT-TYPE
   SYNTAX      Integer32
   MAX-ACCESS  read-only
   STATUS      current
   DESCRIPTION
      "Path: session.performance.errorLog.testNumber"
   ::= {pr1646v2PingSessionErrorLogEntry 134217728}

pr1646v2PingSessionErrorLogLastFaultSequenceNr OBJECT-TYPE
   SYNTAX      Counter64
   MAX-ACCESS  read-only
   STATUS      current
   DESCRIPTION
      "Path: session.performance.errorLog.lastFaultSequenceNr

       64 bit unsigned wrappable counter."
   ::= {pr1646v2PingSessionErrorLogEntry 33554432}

pr1646v2PingSessionErrorLogLoss OBJECT-TYPE
   SYNTAX      Integer32
   MAX-ACCESS  read-only
   STATUS      current
   DESCRIPTION
      "Path: session.performance.errorLog.loss"
   ::= {pr1646v2PingSessionErrorLogEntry 67108864}

pr1646v2PingSessionErrorLogLength OBJECT-TYPE
   SYNTAX      Integer32
   MAX-ACCESS  read-only
   STATUS      current
   DESCRIPTION
      "Path: session.performance.errorLog.length"
   ::= {pr1646v2PingSessionErrorLogEntry 50331648}

pr1646v2PingSessionErrorLogCrc OBJECT-TYPE
   SYNTAX      Integer32
   MAX-ACCESS  read-only
   STATUS      current
   DESCRIPTION
      "Path: session.performance.errorLog.crc"
   ::= {pr1646v2PingSessionErrorLogEntry 83886080}

pr1646v2PingSessionErrorLogSyncLoss OBJECT-TYPE
   SYNTAX      Integer32
   MAX-ACCESS  read-only
   STATUS      current
   DESCRIPTION
      "Path: session.performance.errorLog.syncLoss"
   ::= {pr1646v2PingSessionErrorLogEntry 100663296}

pr1646v2PingSessionErrorLogRecTimeOut OBJECT-TYPE
   SYNTAX      Integer32
   MAX-ACCESS  read-only
   STATUS      current
   DESCRIPTION
      "Path: session.performance.errorLog.recTimeOut"
   ::= {pr1646v2PingSessionErrorLogEntry 117440512}

pr1646v2PingSessionErrorLogOutOfSequence OBJECT-TYPE
   SYNTAX      Integer32
   MAX-ACCESS  read-only
   STATUS      current
   DESCRIPTION
      "Path: session.performance.errorLog.outOfSequence"
   ::= {pr1646v2PingSessionErrorLogEntry 184549376}

pr1646v2PingSessionErrorLogStreaming OBJECT-TYPE
   SYNTAX      Integer32
   MAX-ACCESS  read-only
   STATUS      current
   DESCRIPTION
      "Path: session.performance.errorLog.streaming"
   ::= {pr1646v2PingSessionErrorLogEntry 167772160}


pr1646v2PingSessionRfcTest OBJECT IDENTIFIER ::= {pr1646v2PingSession 1185}

pr1646v2PingSessionRfcTestSSCTable OBJECT-TYPE
   SYNTAX      SEQUENCE OF Pr1646v2PingSessionRfcTestEntry
   MAX-ACCESS  not-accessible
   STATUS      current
   DESCRIPTION
      ""
   ::= {pr1646v2PingSessionRfcTest 1}

pr1646v2PingSessionRfcTestEntry OBJECT-TYPE
   SYNTAX      Pr1646v2PingSessionRfcTestEntry
   MAX-ACCESS  not-accessible
   STATUS      current
   DESCRIPTION
      ""
   INDEX      { pr1646v2PingSessionRfcTestGlobalIx,
                pr1646v2PingSessionRfcTestTableIx }
   ::= {pr1646v2PingSessionRfcTestSSCTable 1}

Pr1646v2PingSessionRfcTestEntry ::=
   SEQUENCE
      {
      pr1646v2PingSessionRfcTestGlobalIx
         GlobalIndex,
      pr1646v2PingSessionRfcTestTableIx
         TableIndex,
      pr1646v2PingSessionRfcTestStream
         DisplayString,
      pr1646v2PingSessionRfcTestType
         DisplayString,
      pr1646v2PingSessionRfcTestLength
         Integer32,
      pr1646v2PingSessionRfcTestTxBandwidth
         Integer32,
      pr1646v2PingSessionRfcTestTxPacketSec
         Integer32,
      pr1646v2PingSessionRfcTestRxBandwidth
         Integer32,
      pr1646v2PingSessionRfcTestRxPacketSec
         Integer32,
      pr1646v2PingSessionRfcTestPacketLoss
         Counter64,
      pr1646v2PingSessionRfcTestPacketLossPer
         INTEGER,
      pr1646v2PingSessionRfcTestDelayMin
         INTEGER,
      pr1646v2PingSessionRfcTestDelayAvrg
         INTEGER,
      pr1646v2PingSessionRfcTestDelayMax
         INTEGER,
      pr1646v2PingSessionRfcTestJitterAvrg
         INTEGER,
      pr1646v2PingSessionRfcTestJitterMax
         INTEGER
      }

pr1646v2PingSessionRfcTestGlobalIx OBJECT-TYPE
   SYNTAX      GlobalIndex
   MAX-ACCESS  not-accessible
   STATUS      current
   DESCRIPTION
      "The value of the tlsCntTreeGlobalIndex of the MANAGED OBJECT."
   ::= {pr1646v2PingSessionRfcTestEntry 10}

pr1646v2PingSessionRfcTestTableIx OBJECT-TYPE
   SYNTAX      TableIndex
   MAX-ACCESS  not-accessible
   STATUS      current
   DESCRIPTION
      ""
   ::= {pr1646v2PingSessionRfcTestEntry 11}

pr1646v2PingSessionRfcTestStream OBJECT-TYPE
   SYNTAX      DisplayString
   MAX-ACCESS  read-only
   STATUS      current
   DESCRIPTION
      "Path: session.performance.rfcTest.stream"
   ::= {pr1646v2PingSessionRfcTestEntry 16777216}

pr1646v2PingSessionRfcTestType OBJECT-TYPE
   SYNTAX      DisplayString
   MAX-ACCESS  read-only
   STATUS      current
   DESCRIPTION
      "Path: session.performance.rfcTest.type"
   ::= {pr1646v2PingSessionRfcTestEntry 234881024}

pr1646v2PingSessionRfcTestLength OBJECT-TYPE
   SYNTAX      Integer32
   MAX-ACCESS  read-only
   STATUS      current
   DESCRIPTION
      "Path: session.performance.rfcTest.length"
   ::= {pr1646v2PingSessionRfcTestEntry 33554432}

pr1646v2PingSessionRfcTestTxBandwidth OBJECT-TYPE
   SYNTAX      Integer32
   MAX-ACCESS  read-only
   STATUS      current
   DESCRIPTION
      "Path: session.performance.rfcTest.txBandwidth"
   ::= {pr1646v2PingSessionRfcTestEntry 50331648}

pr1646v2PingSessionRfcTestTxPacketSec OBJECT-TYPE
   SYNTAX      Integer32
   MAX-ACCESS  read-only
   STATUS      current
   DESCRIPTION
      "Path: session.performance.rfcTest.txPacketSec"
   ::= {pr1646v2PingSessionRfcTestEntry 67108864}

pr1646v2PingSessionRfcTestRxBandwidth OBJECT-TYPE
   SYNTAX      Integer32
   MAX-ACCESS  read-only
   STATUS      current
   DESCRIPTION
      "Path: session.performance.rfcTest.rxBandwidth"
   ::= {pr1646v2PingSessionRfcTestEntry 83886080}

pr1646v2PingSessionRfcTestRxPacketSec OBJECT-TYPE
   SYNTAX      Integer32
   MAX-ACCESS  read-only
   STATUS      current
   DESCRIPTION
      "Path: session.performance.rfcTest.rxPacketSec"
   ::= {pr1646v2PingSessionRfcTestEntry 100663296}

pr1646v2PingSessionRfcTestPacketLoss OBJECT-TYPE
   SYNTAX      Counter64
   MAX-ACCESS  read-only
   STATUS      current
   DESCRIPTION
      "Path: session.performance.rfcTest.packetLoss

       64 bit unsigned wrappable counter."
   ::= {pr1646v2PingSessionRfcTestEntry 117440512}

pr1646v2PingSessionRfcTestPacketLossPer OBJECT-TYPE
   SYNTAX      INTEGER
               {
               slnotsinsuseg (2147483647)
               }
   MAX-ACCESS  read-only
   STATUS      current
   DESCRIPTION
      "Path: session.performance.rfcTest.packetLossPer

       unit name = %
       formula = 100 / ; 100 *

       Possibilities:
               <not in use>   (2147483647)"
   ::= {pr1646v2PingSessionRfcTestEntry 134217728}

pr1646v2PingSessionRfcTestDelayMin OBJECT-TYPE
   SYNTAX      INTEGER
               {
               slnotsinsuseg (2147483647)
               }
   MAX-ACCESS  read-only
   STATUS      current
   DESCRIPTION
      "Path: session.performance.rfcTest.delayMin

       unit name = ms
       formula = 10 / ; 10 *

       Possibilities:
               <not in use>   (2147483647)"
   ::= {pr1646v2PingSessionRfcTestEntry 150994944}

pr1646v2PingSessionRfcTestDelayAvrg OBJECT-TYPE
   SYNTAX      INTEGER
               {
               slnotsinsuseg (2147483647)
               }
   MAX-ACCESS  read-only
   STATUS      current
   DESCRIPTION
      "Path: session.performance.rfcTest.delayAvrg

       unit name = ms
       formula = 10 / ; 10 *

       Possibilities:
               <not in use>   (2147483647)"
   ::= {pr1646v2PingSessionRfcTestEntry 167772160}

pr1646v2PingSessionRfcTestDelayMax OBJECT-TYPE
   SYNTAX      INTEGER
               {
               slnotsinsuseg (2147483647)
               }
   MAX-ACCESS  read-only
   STATUS      current
   DESCRIPTION
      "Path: session.performance.rfcTest.delayMax

       unit name = ms
       formula = 10 / ; 10 *

       Possibilities:
               <not in use>   (2147483647)"
   ::= {pr1646v2PingSessionRfcTestEntry 184549376}

pr1646v2PingSessionRfcTestJitterAvrg OBJECT-TYPE
   SYNTAX      INTEGER
               {
               slnotsinsuseg (2147483647)
               }
   MAX-ACCESS  read-only
   STATUS      current
   DESCRIPTION
      "Path: session.performance.rfcTest.jitterAvrg

       unit name = ms
       formula = 10 / ; 10 *

       Possibilities:
               <not in use>   (2147483647)"
   ::= {pr1646v2PingSessionRfcTestEntry 201326592}

pr1646v2PingSessionRfcTestJitterMax OBJECT-TYPE
   SYNTAX      INTEGER
               {
               slnotsinsuseg (2147483647)
               }
   MAX-ACCESS  read-only
   STATUS      current
   DESCRIPTION
      "Path: session.performance.rfcTest.jitterMax

       unit name = ms
       formula = 10 / ; 10 *

       Possibilities:
               <not in use>   (2147483647)"
   ::= {pr1646v2PingSessionRfcTestEntry 218103808}



ar1646v2PingSession OBJECT IDENTIFIER ::= {r1646v2PingSession 16}


ar1646v2PingSessionClearStatLog OBJECT IDENTIFIER ::= {ar1646v2PingSession 1164}

ar1646v2PingSessionClearStatLogTable OBJECT-TYPE
   SYNTAX      SEQUENCE OF Ar1646v2PingSessionClearStatLogEntry
   MAX-ACCESS  not-accessible
   STATUS      current
   DESCRIPTION
      "restart all sessions"
   ::= {ar1646v2PingSessionClearStatLog 1}

ar1646v2PingSessionClearStatLogEntry OBJECT-TYPE
   SYNTAX      Ar1646v2PingSessionClearStatLogEntry
   MAX-ACCESS  not-accessible
   STATUS      current
   DESCRIPTION
      ""
   INDEX      { ar1646v2PingSessionClearStatLogGlobalIx }
   ::= {ar1646v2PingSessionClearStatLogTable 1}

Ar1646v2PingSessionClearStatLogEntry ::=
   SEQUENCE
      {
      ar1646v2PingSessionClearStatLogGlobalIx
         GlobalIndex,
      ar1646v2PingSessionClearStatLogValue
         Integer32
      }

ar1646v2PingSessionClearStatLogGlobalIx OBJECT-TYPE
   SYNTAX      GlobalIndex
   MAX-ACCESS  not-accessible
   STATUS      current
   DESCRIPTION
      "The value of the tlsCntTreeGlobalIndex of the MANAGED OBJECT."
   ::= {ar1646v2PingSessionClearStatLogEntry 10}

ar1646v2PingSessionClearStatLogValue OBJECT-TYPE
   SYNTAX      Integer32
   MAX-ACCESS  read-write
   STATUS      current
   DESCRIPTION
      "Path: session.actions.clearStatLog"
   ::= {ar1646v2PingSessionClearStatLogEntry 2147483648}


ar1646v2PingSessionClearErrorLog OBJECT IDENTIFIER ::= {ar1646v2PingSession 1163}

ar1646v2PingSessionClearErrorLogTable OBJECT-TYPE
   SYNTAX      SEQUENCE OF Ar1646v2PingSessionClearErrorLogEntry
   MAX-ACCESS  not-accessible
   STATUS      current
   DESCRIPTION
      "restart all sessions"
   ::= {ar1646v2PingSessionClearErrorLog 1}

ar1646v2PingSessionClearErrorLogEntry OBJECT-TYPE
   SYNTAX      Ar1646v2PingSessionClearErrorLogEntry
   MAX-ACCESS  not-accessible
   STATUS      current
   DESCRIPTION
      ""
   INDEX      { ar1646v2PingSessionClearErrorLogGlobalIx }
   ::= {ar1646v2PingSessionClearErrorLogTable 1}

Ar1646v2PingSessionClearErrorLogEntry ::=
   SEQUENCE
      {
      ar1646v2PingSessionClearErrorLogGlobalIx
         GlobalIndex,
      ar1646v2PingSessionClearErrorLogValue
         Integer32
      }

ar1646v2PingSessionClearErrorLogGlobalIx OBJECT-TYPE
   SYNTAX      GlobalIndex
   MAX-ACCESS  not-accessible
   STATUS      current
   DESCRIPTION
      "The value of the tlsCntTreeGlobalIndex of the MANAGED OBJECT."
   ::= {ar1646v2PingSessionClearErrorLogEntry 10}

ar1646v2PingSessionClearErrorLogValue OBJECT-TYPE
   SYNTAX      Integer32
   MAX-ACCESS  read-write
   STATUS      current
   DESCRIPTION
      "Path: session.actions.clearErrorLog"
   ::= {ar1646v2PingSessionClearErrorLogEntry 2147483648}


ar1646v2PingSessionClearResultLog OBJECT IDENTIFIER ::= {ar1646v2PingSession 1162}

ar1646v2PingSessionClearResultLogTable OBJECT-TYPE
   SYNTAX      SEQUENCE OF Ar1646v2PingSessionClearResultLogEntry
   MAX-ACCESS  not-accessible
   STATUS      current
   DESCRIPTION
      "restart all sessions"
   ::= {ar1646v2PingSessionClearResultLog 1}

ar1646v2PingSessionClearResultLogEntry OBJECT-TYPE
   SYNTAX      Ar1646v2PingSessionClearResultLogEntry
   MAX-ACCESS  not-accessible
   STATUS      current
   DESCRIPTION
      ""
   INDEX      { ar1646v2PingSessionClearResultLogGlobalIx }
   ::= {ar1646v2PingSessionClearResultLogTable 1}

Ar1646v2PingSessionClearResultLogEntry ::=
   SEQUENCE
      {
      ar1646v2PingSessionClearResultLogGlobalIx
         GlobalIndex,
      ar1646v2PingSessionClearResultLogValue
         Integer32
      }

ar1646v2PingSessionClearResultLogGlobalIx OBJECT-TYPE
   SYNTAX      GlobalIndex
   MAX-ACCESS  not-accessible
   STATUS      current
   DESCRIPTION
      "The value of the tlsCntTreeGlobalIndex of the MANAGED OBJECT."
   ::= {ar1646v2PingSessionClearResultLogEntry 10}

ar1646v2PingSessionClearResultLogValue OBJECT-TYPE
   SYNTAX      Integer32
   MAX-ACCESS  read-write
   STATUS      current
   DESCRIPTION
      "Path: session.actions.clearResultLog"
   ::= {ar1646v2PingSessionClearResultLogEntry 2147483648}


ar1646v2PingSessionClearLog OBJECT IDENTIFIER ::= {ar1646v2PingSession 1165}

ar1646v2PingSessionClearLogTable OBJECT-TYPE
   SYNTAX      SEQUENCE OF Ar1646v2PingSessionClearLogEntry
   MAX-ACCESS  not-accessible
   STATUS      current
   DESCRIPTION
      "restart all sessions"
   ::= {ar1646v2PingSessionClearLog 1}

ar1646v2PingSessionClearLogEntry OBJECT-TYPE
   SYNTAX      Ar1646v2PingSessionClearLogEntry
   MAX-ACCESS  not-accessible
   STATUS      current
   DESCRIPTION
      ""
   INDEX      { ar1646v2PingSessionClearLogGlobalIx }
   ::= {ar1646v2PingSessionClearLogTable 1}

Ar1646v2PingSessionClearLogEntry ::=
   SEQUENCE
      {
      ar1646v2PingSessionClearLogGlobalIx
         GlobalIndex,
      ar1646v2PingSessionClearLogValue
         Integer32
      }

ar1646v2PingSessionClearLogGlobalIx OBJECT-TYPE
   SYNTAX      GlobalIndex
   MAX-ACCESS  not-accessible
   STATUS      current
   DESCRIPTION
      "The value of the tlsCntTreeGlobalIndex of the MANAGED OBJECT."
   ::= {ar1646v2PingSessionClearLogEntry 10}

ar1646v2PingSessionClearLogValue OBJECT-TYPE
   SYNTAX      Integer32
   MAX-ACCESS  read-write
   STATUS      current
   DESCRIPTION
      "Path: session.actions.clearLog"
   ::= {ar1646v2PingSessionClearLogEntry 2147483648}


ar1646v2PingSessionInitxSession OBJECT IDENTIFIER ::= {ar1646v2PingSession 1242}

ar1646v2PingSessionInitxSessionTable OBJECT-TYPE
   SYNTAX      SEQUENCE OF Ar1646v2PingSessionInitxSessionEntry
   MAX-ACCESS  not-accessible
   STATUS      current
   DESCRIPTION
      "restart all sessions"
   ::= {ar1646v2PingSessionInitxSession 1}

ar1646v2PingSessionInitxSessionEntry OBJECT-TYPE
   SYNTAX      Ar1646v2PingSessionInitxSessionEntry
   MAX-ACCESS  not-accessible
   STATUS      current
   DESCRIPTION
      ""
   INDEX      { ar1646v2PingSessionInitxSessionGlobalIx }
   ::= {ar1646v2PingSessionInitxSessionTable 1}

Ar1646v2PingSessionInitxSessionEntry ::=
   SEQUENCE
      {
      ar1646v2PingSessionInitxSessionGlobalIx
         GlobalIndex,
      ar1646v2PingSessionInitxSessionValue
         Integer32
      }

ar1646v2PingSessionInitxSessionGlobalIx OBJECT-TYPE
   SYNTAX      GlobalIndex
   MAX-ACCESS  not-accessible
   STATUS      current
   DESCRIPTION
      "The value of the tlsCntTreeGlobalIndex of the MANAGED OBJECT."
   ::= {ar1646v2PingSessionInitxSessionEntry 10}

ar1646v2PingSessionInitxSessionValue OBJECT-TYPE
   SYNTAX      Integer32
   MAX-ACCESS  read-write
   STATUS      current
   DESCRIPTION
      "Path: session.actions.initxSession"
   ::= {ar1646v2PingSessionInitxSessionEntry 2147483648}


ar1646v2PingSessionRestartSession OBJECT IDENTIFIER ::= {ar1646v2PingSession 1161}

ar1646v2PingSessionRestartSessionTable OBJECT-TYPE
   SYNTAX      SEQUENCE OF Ar1646v2PingSessionRestartSessionEntry
   MAX-ACCESS  not-accessible
   STATUS      current
   DESCRIPTION
      "restart all sessions"
   ::= {ar1646v2PingSessionRestartSession 1}

ar1646v2PingSessionRestartSessionEntry OBJECT-TYPE
   SYNTAX      Ar1646v2PingSessionRestartSessionEntry
   MAX-ACCESS  not-accessible
   STATUS      current
   DESCRIPTION
      ""
   INDEX      { ar1646v2PingSessionRestartSessionGlobalIx }
   ::= {ar1646v2PingSessionRestartSessionTable 1}

Ar1646v2PingSessionRestartSessionEntry ::=
   SEQUENCE
      {
      ar1646v2PingSessionRestartSessionGlobalIx
         GlobalIndex,
      ar1646v2PingSessionRestartSessionValue
         Integer32
      }

ar1646v2PingSessionRestartSessionGlobalIx OBJECT-TYPE
   SYNTAX      GlobalIndex
   MAX-ACCESS  not-accessible
   STATUS      current
   DESCRIPTION
      "The value of the tlsCntTreeGlobalIndex of the MANAGED OBJECT."
   ::= {ar1646v2PingSessionRestartSessionEntry 10}

ar1646v2PingSessionRestartSessionValue OBJECT-TYPE
   SYNTAX      Integer32
   MAX-ACCESS  read-write
   STATUS      current
   DESCRIPTION
      "Path: session.actions.restartSession"
   ::= {ar1646v2PingSessionRestartSessionEntry 2147483648}


ar1646v2PingSessionStopSession OBJECT IDENTIFIER ::= {ar1646v2PingSession 1160}

ar1646v2PingSessionStopSessionTable OBJECT-TYPE
   SYNTAX      SEQUENCE OF Ar1646v2PingSessionStopSessionEntry
   MAX-ACCESS  not-accessible
   STATUS      current
   DESCRIPTION
      "stop all sessions"
   ::= {ar1646v2PingSessionStopSession 1}

ar1646v2PingSessionStopSessionEntry OBJECT-TYPE
   SYNTAX      Ar1646v2PingSessionStopSessionEntry
   MAX-ACCESS  not-accessible
   STATUS      current
   DESCRIPTION
      ""
   INDEX      { ar1646v2PingSessionStopSessionGlobalIx }
   ::= {ar1646v2PingSessionStopSessionTable 1}

Ar1646v2PingSessionStopSessionEntry ::=
   SEQUENCE
      {
      ar1646v2PingSessionStopSessionGlobalIx
         GlobalIndex,
      ar1646v2PingSessionStopSessionValue
         Integer32
      }

ar1646v2PingSessionStopSessionGlobalIx OBJECT-TYPE
   SYNTAX      GlobalIndex
   MAX-ACCESS  not-accessible
   STATUS      current
   DESCRIPTION
      "The value of the tlsCntTreeGlobalIndex of the MANAGED OBJECT."
   ::= {ar1646v2PingSessionStopSessionEntry 10}

ar1646v2PingSessionStopSessionValue OBJECT-TYPE
   SYNTAX      Integer32
   MAX-ACCESS  read-write
   STATUS      current
   DESCRIPTION
      "Path: session.actions.stopSession"
   ::= {ar1646v2PingSessionStopSessionEntry 2147483648}



END
