OneAccess-R1646v2-3135-Zbac DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Zbac OBJECT IDENTIFIER ::= {r1646Rootv2 3135}

r1646v2ZbacMOProp OBJECT-TYPE
   SYNTAX      SEQUENCE OF R1646v2ZbacMOPropEntry
   MAX-ACCESS  not-accessible
   STATUS      current
   DESCRIPTION
      ""
   ::= {r1646v2Zbac 1}

r1646v2ZbacMOPropEntry OBJECT-TYPE
   SYNTAX      R1646v2ZbacMOPropEntry
   MAX-ACCESS  not-accessible
   STATUS      current
   DESCRIPTION
      ""
   INDEX      { r1646v2ZbacMOPropGlobalIx }
   ::= {r1646v2ZbacMOProp 1}

R1646v2ZbacMOPropEntry ::=
   SEQUENCE
      {
      r1646v2ZbacMOPropPath
         ContainmentPath,
      r1646v2ZbacMOPropRev
         ObjectRevision,
      r1646v2ZbacMOPropGlobalIx
         GlobalIndex
      }

r1646v2ZbacMOPropPath OBJECT-TYPE
   SYNTAX      ContainmentPath
   MAX-ACCESS  read-only
   STATUS      current
   DESCRIPTION
      "Textual description of the containment tree from the instance of
       the root object down to the instance of the current object."
   ::= {r1646v2ZbacMOPropEntry 3}

r1646v2ZbacMOPropRev OBJECT-TYPE
   SYNTAX      ObjectRevision
   MAX-ACCESS  read-only
   STATUS      current
   DESCRIPTION
      "This value corresponds with the revision of the MANAGED OBJECT."
   ::= {r1646v2ZbacMOPropEntry 4}

r1646v2ZbacMOPropGlobalIx OBJECT-TYPE
   SYNTAX      GlobalIndex
   MAX-ACCESS  read-only
   STATUS      current
   DESCRIPTION
      "The value of the tlsCntTreeGlobalIndex of the MANAGED OBJECT."
   ::= {r1646v2ZbacMOPropEntry 10}



er1646v2Zbac OBJECT IDENTIFIER ::= {r1646v2Zbac 11}


er1646v2ZbacSnmpIndexOffset OBJECT IDENTIFIER ::= {er1646v2Zbac 268}

er1646v2ZbacSnmpIndexOffsetTable OBJECT-TYPE
   SYNTAX      SEQUENCE OF Er1646v2ZbacSnmpIndexOffsetEntry
   MAX-ACCESS  not-accessible
   STATUS      current
   DESCRIPTION
      "Preferred offset in the range of SNMP indices for this SWinst, 0 means automatic"
   ::= {er1646v2ZbacSnmpIndexOffset 1}

er1646v2ZbacSnmpIndexOffsetEntry OBJECT-TYPE
   SYNTAX      Er1646v2ZbacSnmpIndexOffsetEntry
   MAX-ACCESS  not-accessible
   STATUS      current
   DESCRIPTION
      ""
   INDEX      { er1646v2ZbacSnmpIndexOffsetGlobalIx }
   ::= {er1646v2ZbacSnmpIndexOffsetTable 1}

Er1646v2ZbacSnmpIndexOffsetEntry ::=
   SEQUENCE
      {
      er1646v2ZbacSnmpIndexOffsetGlobalIx
         GlobalIndex,
      er1646v2ZbacSnmpIndexOffsetValue
         Integer32
      }

er1646v2ZbacSnmpIndexOffsetGlobalIx OBJECT-TYPE
   SYNTAX      GlobalIndex
   MAX-ACCESS  not-accessible
   STATUS      current
   DESCRIPTION
      "The value of the tlsCntTreeGlobalIndex of the MANAGED OBJECT."
   ::= {er1646v2ZbacSnmpIndexOffsetEntry 10}

er1646v2ZbacSnmpIndexOffsetValue OBJECT-TYPE
   SYNTAX      Integer32
   MAX-ACCESS  read-write
   STATUS      current
   DESCRIPTION
      "Path: addressCollection.editConf.snmpIndexOffset"
   ::= {er1646v2ZbacSnmpIndexOffsetEntry 2147483648}


er1646v2ZbacAddressRanges OBJECT IDENTIFIER ::= {er1646v2Zbac 2}

er1646v2ZbacAddressRangesSSCTable OBJECT-TYPE
   SYNTAX      SEQUENCE OF Er1646v2ZbacAddressRangesEntry
   MAX-ACCESS  not-accessible
   STATUS      current
   DESCRIPTION
      "ipAddresses"
   ::= {er1646v2ZbacAddressRanges 1}

er1646v2ZbacAddressRangesEntry OBJECT-TYPE
   SYNTAX      Er1646v2ZbacAddressRangesEntry
   MAX-ACCESS  not-accessible
   STATUS      current
   DESCRIPTION
      ""
   INDEX      { er1646v2ZbacAddressRangesGlobalIx,
                er1646v2ZbacAddressRangesTableIx }
   ::= {er1646v2ZbacAddressRangesSSCTable 1}

Er1646v2ZbacAddressRangesEntry ::=
   SEQUENCE
      {
      er1646v2ZbacAddressRangesActions
         VariableLengthTableActions,
      er1646v2ZbacAddressRangesGlobalIx
         GlobalIndex,
      er1646v2ZbacAddressRangesTableIx
         TableIndex,
      er1646v2ZbacAddressRangesRange
         DisplayString
      }

er1646v2ZbacAddressRangesActions OBJECT-TYPE
   SYNTAX      VariableLengthTableActions
   MAX-ACCESS  read-write
   STATUS      current
   DESCRIPTION
      "By way of this field, some manipulations
       on this table may be performed."
   ::= {er1646v2ZbacAddressRangesEntry 2}

er1646v2ZbacAddressRangesGlobalIx OBJECT-TYPE
   SYNTAX      GlobalIndex
   MAX-ACCESS  not-accessible
   STATUS      current
   DESCRIPTION
      "The value of the tlsCntTreeGlobalIndex of the MANAGED OBJECT."
   ::= {er1646v2ZbacAddressRangesEntry 10}

er1646v2ZbacAddressRangesTableIx OBJECT-TYPE
   SYNTAX      TableIndex
   MAX-ACCESS  not-accessible
   STATUS      current
   DESCRIPTION
      ""
   ::= {er1646v2ZbacAddressRangesEntry 11}

er1646v2ZbacAddressRangesRange OBJECT-TYPE
   SYNTAX      DisplayString
   MAX-ACCESS  read-write
   STATUS      current
   DESCRIPTION
      "Path: addressCollection.editConf.addressRanges.range"
   ::= {er1646v2ZbacAddressRangesEntry 16777216}



sr1646v2Zbac OBJECT IDENTIFIER ::= {r1646v2Zbac 14}


sr1646v2ZbacSnmpIndex OBJECT IDENTIFIER ::= {sr1646v2Zbac 269}

sr1646v2ZbacSnmpIndexTable OBJECT-TYPE
   SYNTAX      SEQUENCE OF Sr1646v2ZbacSnmpIndexEntry
   MAX-ACCESS  not-accessible
   STATUS      current
   DESCRIPTION
      "SNMP index assigned to this object"
   ::= {sr1646v2ZbacSnmpIndex 1}

sr1646v2ZbacSnmpIndexEntry OBJECT-TYPE
   SYNTAX      Sr1646v2ZbacSnmpIndexEntry
   MAX-ACCESS  not-accessible
   STATUS      current
   DESCRIPTION
      ""
   INDEX      { sr1646v2ZbacSnmpIndexGlobalIx }
   ::= {sr1646v2ZbacSnmpIndexTable 1}

Sr1646v2ZbacSnmpIndexEntry ::=
   SEQUENCE
      {
      sr1646v2ZbacSnmpIndexGlobalIx
         GlobalIndex,
      sr1646v2ZbacSnmpIndexValue
         Integer32
      }

sr1646v2ZbacSnmpIndexGlobalIx OBJECT-TYPE
   SYNTAX      GlobalIndex
   MAX-ACCESS  not-accessible
   STATUS      current
   DESCRIPTION
      "The value of the tlsCntTreeGlobalIndex of the MANAGED OBJECT."
   ::= {sr1646v2ZbacSnmpIndexEntry 10}

sr1646v2ZbacSnmpIndexValue OBJECT-TYPE
   SYNTAX      Integer32
   MAX-ACCESS  read-only
   STATUS      current
   DESCRIPTION
      "Path: addressCollection.status.snmpIndex"
   ::= {sr1646v2ZbacSnmpIndexEntry 2147483648}



END
