OneAccess-R1646v2-4716-XEfm DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2XEfm OBJECT IDENTIFIER ::= {r1646Rootv2 4716}

r1646v2XEfmMOProp OBJECT IDENTIFIER ::= {r1646v2XEfm 1}

r1646v2XEfmMOPropEntry OBJECT IDENTIFIER ::= {r1646v2XEfmMOProp 1}

r1646v2XEfmMOPropPath OBJECT-TYPE
   SYNTAX      ContainmentPath
   MAX-ACCESS  read-only
   STATUS      current
   DESCRIPTION
      "Textual description of the containment tree from the instance of
       the root object down to the instance of the current object."
   ::= {r1646v2XEfmMOPropEntry 3}

r1646v2XEfmMOPropRev OBJECT-TYPE
   SYNTAX      ObjectRevision
   MAX-ACCESS  read-only
   STATUS      current
   DESCRIPTION
      "This value corresponds with the revision of the MANAGED OBJECT."
   ::= {r1646v2XEfmMOPropEntry 4}



er1646v2XEfm OBJECT IDENTIFIER ::= {r1646v2XEfm 11}


er1646v2XEfmRemark OBJECT-TYPE
   SYNTAX      DisplayString
   MAX-ACCESS  read-write
   STATUS      current
   DESCRIPTION
      "Path: efm.editConf.remark
       Info: intfRemark"
   ::= {er1646v2XEfm 321}


er1646v2XEfmBw OBJECT IDENTIFIER ::= {er1646v2XEfm 5}

er1646v2XEfmBwSSC OBJECT IDENTIFIER ::= {er1646v2XEfmBw 1}

er1646v2XEfmBwEntry OBJECT IDENTIFIER ::= {er1646v2XEfmBwSSC 1}

er1646v2XEfmBwMode OBJECT-TYPE
   SYNTAX      INTEGER
               {
               reshaping (1),
               policing (2),
               policingReshape (3)
               }
   MAX-ACCESS  read-write
   STATUS      current
   DESCRIPTION
      "Path: efm.editConf.bandwidth.mode

       Possibilities:
               reshaping   (1)
               policing   (2)
               policingReshape   (3)"
   ::= {er1646v2XEfmBwEntry 3758096384}

er1646v2XEfmBwCir OBJECT-TYPE
   SYNTAX      Integer32
   MAX-ACCESS  read-write
   STATUS      current
   DESCRIPTION
      "Path: efm.editConf.bandwidth.cir"
   ::= {er1646v2XEfmBwEntry 268435456}

er1646v2XEfmBwEir OBJECT-TYPE
   SYNTAX      Integer32
   MAX-ACCESS  read-write
   STATUS      current
   DESCRIPTION
      "Path: efm.editConf.bandwidth.eir"
   ::= {er1646v2XEfmBwEntry 1879048192}

er1646v2XEfmBwUnit OBJECT-TYPE
   SYNTAX      INTEGER
               {
               bitssec (1),
               percent (2)
               }
   MAX-ACCESS  read-write
   STATUS      current
   DESCRIPTION
      "Path: efm.editConf.bandwidth.unit

       Possibilities:
               bits/sec   (1)
               percent   (2)"
   ::= {er1646v2XEfmBwEntry 1342177280}

er1646v2XEfmBwTc OBJECT-TYPE
   SYNTAX      INTEGER
               {
               auto (0)
               }
   MAX-ACCESS  read-write
   STATUS      current
   DESCRIPTION
      "Path: efm.editConf.bandwidth.tc

       Possibilities:
               auto   (0)"
   ::= {er1646v2XEfmBwEntry 1610612736}

er1646v2XEfmBwTcFactor OBJECT-TYPE
   SYNTAX      INTEGER
               {
               ms (10),
               s100us (1)
               }
   MAX-ACCESS  read-write
   STATUS      current
   DESCRIPTION
      "Path: efm.editConf.bandwidth.tcFactor

       Possibilities:
               ms   (10)
               *100us   (1)"
   ::= {er1646v2XEfmBwEntry 2147483648}

er1646v2XEfmBwCorrType OBJECT-TYPE
   SYNTAX      INTEGER
               {
               noCorrection (0),
               predefined (1),
               manual (2)
               }
   MAX-ACCESS  read-write
   STATUS      current
   DESCRIPTION
      "Path: efm.editConf.bandwidth.correction.type

       Possibilities:
               noCorrection   (0)
               predefined   (1)
               manual   (2)"
   ::= {er1646v2XEfmBwEntry 570425344}

er1646v2XEfmBwCorrPredefEncapsFrameRelay OBJECT-TYPE
   SYNTAX      DisplayString
   MAX-ACCESS  read-write
   STATUS      current
   DESCRIPTION
      "Path: efm.editConf.bandwidth.correction.predefined.encapsulation.frameRelay"
   ::= {er1646v2XEfmBwEntry 608436224}

er1646v2XEfmBwCorrPredefEncapsPpp OBJECT-TYPE
   SYNTAX      DisplayString
   MAX-ACCESS  read-write
   STATUS      current
   DESCRIPTION
      "Path: efm.editConf.bandwidth.correction.predefined.encapsulation.ppp"
   ::= {er1646v2XEfmBwEntry 608698368}

er1646v2XEfmBwCorrPredefEncapsAtmHl OBJECT-TYPE
   SYNTAX      INTEGER
               {
               rfc2684 (0),
               ppp (1),
               pppOverEthernet (2)
               }
   MAX-ACCESS  read-write
   STATUS      current
   DESCRIPTION
      "Path: efm.editConf.bandwidth.correction.predefined.encapsulation.atm.higherLayer

       Possibilities:
               rfc2684   (0)
               ppp   (1)
               pppOverEthernet   (2)"
   ::= {er1646v2XEfmBwEntry 608993280}

er1646v2XEfmBwCorrPredefEncapsAtmMp OBJECT-TYPE
   SYNTAX      INTEGER
               {
               llcEncapsulation (0),
               vcMultiplexing (1)
               }
   MAX-ACCESS  read-write
   STATUS      current
   DESCRIPTION
      "Path: efm.editConf.bandwidth.correction.predefined.encapsulation.atm.multiProtocol

       Possibilities:
               llcEncapsulation   (0)
               vcMultiplexing   (1)"
   ::= {er1646v2XEfmBwEntry 609026048}

er1646v2XEfmBwCorrPredefEncapsHdlc OBJECT-TYPE
   SYNTAX      DisplayString
   MAX-ACCESS  read-write
   STATUS      current
   DESCRIPTION
      "Path: efm.editConf.bandwidth.correction.predefined.encapsulation.hdlc"
   ::= {er1646v2XEfmBwEntry 609222656}

er1646v2XEfmBwCorrPredefEncapsEfmFs OBJECT-TYPE
   SYNTAX      Integer32
   MAX-ACCESS  read-write
   STATUS      current
   DESCRIPTION
      "Path: efm.editConf.bandwidth.correction.predefined.encapsulation.efm.fragmentSize"
   ::= {er1646v2XEfmBwEntry 609517568}

er1646v2XEfmBwCorrPredefEncapsEfmIb OBJECT-TYPE
   SYNTAX      Integer32
   MAX-ACCESS  read-write
   STATUS      current
   DESCRIPTION
      "Path: efm.editConf.bandwidth.correction.predefined.encapsulation.efm.idleBytes"
   ::= {er1646v2XEfmBwEntry 609550336}

er1646v2XEfmBwCorrPredefMode OBJECT-TYPE
   SYNTAX      INTEGER
               {
               routing (0),
               bridging (1)
               }
   MAX-ACCESS  read-write
   STATUS      current
   DESCRIPTION
      "Path: efm.editConf.bandwidth.correction.predefined.mode

       Possibilities:
               routing   (0)
               bridging   (1)"
   ::= {er1646v2XEfmBwEntry 612368384}

er1646v2XEfmBwCorrManualOverhead OBJECT-TYPE
   SYNTAX      Integer32
   MAX-ACCESS  read-write
   STATUS      current
   DESCRIPTION
      "Path: efm.editConf.bandwidth.correction.manual.overhead"
   ::= {er1646v2XEfmBwEntry 637665280}

er1646v2XEfmBwCorrManualFrameData OBJECT-TYPE
   SYNTAX      Counter32
   MAX-ACCESS  read-write
   STATUS      current
   DESCRIPTION
      "Path: efm.editConf.bandwidth.correction.manual.frameData

       32 bit unsigned wrappable counter."
   ::= {er1646v2XEfmBwEntry 637796352}

er1646v2XEfmBwCorrManualFrameHeader OBJECT-TYPE
   SYNTAX      Counter32
   MAX-ACCESS  read-write
   STATUS      current
   DESCRIPTION
      "Path: efm.editConf.bandwidth.correction.manual.frameHeader

       32 bit unsigned wrappable counter."
   ::= {er1646v2XEfmBwEntry 637927424}

er1646v2XEfmBwMaxFifoQLen OBJECT-TYPE
   SYNTAX      Integer32
   MAX-ACCESS  read-write
   STATUS      current
   DESCRIPTION
      "Path: efm.editConf.bandwidth.maxFifoQLen"
   ::= {er1646v2XEfmBwEntry 805306368}

er1646v2XEfmBwDeFlagCir OBJECT-TYPE
   SYNTAX      INTEGER
               {
               allowed (1),
               notAllowed (2)
               }
   MAX-ACCESS  read-write
   STATUS      current
   DESCRIPTION
      "Path: efm.editConf.bandwidth.deFlag.cir

       Possibilities:
               allowed   (1)
               notAllowed   (2)"
   ::= {er1646v2XEfmBwEntry 3490709504}

er1646v2XEfmBwDeFlagEir OBJECT-TYPE
   SYNTAX      INTEGER
               {
               allowed (1),
               notAllowed (2)
               }
   MAX-ACCESS  read-write
   STATUS      current
   DESCRIPTION
      "Path: efm.editConf.bandwidth.deFlag.eir

       Possibilities:
               allowed   (1)
               notAllowed   (2)"
   ::= {er1646v2XEfmBwEntry 3491758080}

er1646v2XEfmBwDeFlagViolate OBJECT-TYPE
   SYNTAX      INTEGER
               {
               allowed (1),
               notAllowed (2)
               }
   MAX-ACCESS  read-write
   STATUS      current
   DESCRIPTION
      "Path: efm.editConf.bandwidth.deFlag.violate

       Possibilities:
               allowed   (1)
               notAllowed   (2)"
   ::= {er1646v2XEfmBwEntry 3492806656}

er1646v2XEfmBwActCirActNone OBJECT-TYPE
   SYNTAX      OCTET STRING
   MAX-ACCESS  read-write
   STATUS      current
   DESCRIPTION
      "Path: efm.editConf.bandwidth.action.cirAction.none"
   ::= {er1646v2XEfmBwEntry 4062183424}

er1646v2XEfmBwActCirActEthCos1 OBJECT-TYPE
   SYNTAX      INTEGER
               {
               unchanged (256)
               }
   MAX-ACCESS  read-write
   STATUS      current
   DESCRIPTION
      "Path: efm.editConf.bandwidth.action.cirAction.ethernet.cosDepth1

       Possibilities:
               unchanged   (256)"
   ::= {er1646v2XEfmBwEntry 4064346112}

er1646v2XEfmBwActCirActEthDei1 OBJECT-TYPE
   SYNTAX      INTEGER
               {
               unchanged (255),
               clear (0),
               set (1)
               }
   MAX-ACCESS  read-write
   STATUS      current
   DESCRIPTION
      "Path: efm.editConf.bandwidth.action.cirAction.ethernet.deiDepth1

       Possibilities:
               unchanged   (255)
               clear   (0)
               set   (1)"
   ::= {er1646v2XEfmBwEntry 4065656832}

er1646v2XEfmBwActCirActEthCos2 OBJECT-TYPE
   SYNTAX      INTEGER
               {
               unchanged (256)
               }
   MAX-ACCESS  read-write
   STATUS      current
   DESCRIPTION
      "Path: efm.editConf.bandwidth.action.cirAction.ethernet.cosDepth2

       Possibilities:
               unchanged   (256)"
   ::= {er1646v2XEfmBwEntry 4064411648}

er1646v2XEfmBwActCirActEthDei2 OBJECT-TYPE
   SYNTAX      INTEGER
               {
               unchanged (255),
               clear (0),
               set (1)
               }
   MAX-ACCESS  read-write
   STATUS      current
   DESCRIPTION
      "Path: efm.editConf.bandwidth.action.cirAction.ethernet.deiDepth2

       Possibilities:
               unchanged   (255)
               clear   (0)
               set   (1)"
   ::= {er1646v2XEfmBwEntry 4065722368}

er1646v2XEfmBwActCirActEthCos3 OBJECT-TYPE
   SYNTAX      INTEGER
               {
               unchanged (256)
               }
   MAX-ACCESS  read-write
   STATUS      current
   DESCRIPTION
      "Path: efm.editConf.bandwidth.action.cirAction.ethernet.cosDepth3

       Possibilities:
               unchanged   (256)"
   ::= {er1646v2XEfmBwEntry 4064477184}

er1646v2XEfmBwActCirActEthDei3 OBJECT-TYPE
   SYNTAX      INTEGER
               {
               unchanged (255),
               clear (0),
               set (1)
               }
   MAX-ACCESS  read-write
   STATUS      current
   DESCRIPTION
      "Path: efm.editConf.bandwidth.action.cirAction.ethernet.deiDepth3

       Possibilities:
               unchanged   (255)
               clear   (0)
               set   (1)"
   ::= {er1646v2XEfmBwEntry 4065787904}

er1646v2XEfmBwActCirActEthCos4 OBJECT-TYPE
   SYNTAX      INTEGER
               {
               unchanged (256)
               }
   MAX-ACCESS  read-write
   STATUS      current
   DESCRIPTION
      "Path: efm.editConf.bandwidth.action.cirAction.ethernet.cosDepth4

       Possibilities:
               unchanged   (256)"
   ::= {er1646v2XEfmBwEntry 4064542720}

er1646v2XEfmBwActCirActEthDei4 OBJECT-TYPE
   SYNTAX      INTEGER
               {
               unchanged (255),
               clear (0),
               set (1)
               }
   MAX-ACCESS  read-write
   STATUS      current
   DESCRIPTION
      "Path: efm.editConf.bandwidth.action.cirAction.ethernet.deiDepth4

       Possibilities:
               unchanged   (255)
               clear   (0)
               set   (1)"
   ::= {er1646v2XEfmBwEntry 4065853440}

er1646v2XEfmBwActCirActEthCos5 OBJECT-TYPE
   SYNTAX      INTEGER
               {
               unchanged (256)
               }
   MAX-ACCESS  read-write
   STATUS      current
   DESCRIPTION
      "Path: efm.editConf.bandwidth.action.cirAction.ethernet.cosDepth5

       Possibilities:
               unchanged   (256)"
   ::= {er1646v2XEfmBwEntry 4064608256}

er1646v2XEfmBwActCirActEthDei5 OBJECT-TYPE
   SYNTAX      INTEGER
               {
               unchanged (255),
               clear (0),
               set (1)
               }
   MAX-ACCESS  read-write
   STATUS      current
   DESCRIPTION
      "Path: efm.editConf.bandwidth.action.cirAction.ethernet.deiDepth5

       Possibilities:
               unchanged   (255)
               clear   (0)
               set   (1)"
   ::= {er1646v2XEfmBwEntry 4065918976}

er1646v2XEfmBwActCirActEthCos6 OBJECT-TYPE
   SYNTAX      INTEGER
               {
               unchanged (256)
               }
   MAX-ACCESS  read-write
   STATUS      current
   DESCRIPTION
      "Path: efm.editConf.bandwidth.action.cirAction.ethernet.cosDepth6

       Possibilities:
               unchanged   (256)"
   ::= {er1646v2XEfmBwEntry 4064673792}

er1646v2XEfmBwActCirActEthDei6 OBJECT-TYPE
   SYNTAX      INTEGER
               {
               unchanged (255),
               clear (0),
               set (1)
               }
   MAX-ACCESS  read-write
   STATUS      current
   DESCRIPTION
      "Path: efm.editConf.bandwidth.action.cirAction.ethernet.deiDepth6

       Possibilities:
               unchanged   (255)
               clear   (0)
               set   (1)"
   ::= {er1646v2XEfmBwEntry 4065984512}

er1646v2XEfmBwActCirActEthCos7 OBJECT-TYPE
   SYNTAX      INTEGER
               {
               unchanged (256)
               }
   MAX-ACCESS  read-write
   STATUS      current
   DESCRIPTION
      "Path: efm.editConf.bandwidth.action.cirAction.ethernet.cosDepth7

       Possibilities:
               unchanged   (256)"
   ::= {er1646v2XEfmBwEntry 4064739328}

er1646v2XEfmBwActCirActEthDei7 OBJECT-TYPE
   SYNTAX      INTEGER
               {
               unchanged (255),
               clear (0),
               set (1)
               }
   MAX-ACCESS  read-write
   STATUS      current
   DESCRIPTION
      "Path: efm.editConf.bandwidth.action.cirAction.ethernet.deiDepth7

       Possibilities:
               unchanged   (255)
               clear   (0)
               set   (1)"
   ::= {er1646v2XEfmBwEntry 4066050048}

er1646v2XEfmBwActCirActEthCos8 OBJECT-TYPE
   SYNTAX      INTEGER
               {
               unchanged (256)
               }
   MAX-ACCESS  read-write
   STATUS      current
   DESCRIPTION
      "Path: efm.editConf.bandwidth.action.cirAction.ethernet.cosDepth8

       Possibilities:
               unchanged   (256)"
   ::= {er1646v2XEfmBwEntry 4064804864}

er1646v2XEfmBwActCirActEthDei8 OBJECT-TYPE
   SYNTAX      INTEGER
               {
               unchanged (255),
               clear (0),
               set (1)
               }
   MAX-ACCESS  read-write
   STATUS      current
   DESCRIPTION
      "Path: efm.editConf.bandwidth.action.cirAction.ethernet.deiDepth8

       Possibilities:
               unchanged   (255)
               clear   (0)
               set   (1)"
   ::= {er1646v2XEfmBwEntry 4066115584}

er1646v2XEfmBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4064870400}

er1646v2XEfmBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4064935936}

er1646v2XEfmBwActCirActEthDrpLev OBJECT-TYPE
   SYNTAX      INTEGER
               {
               unchanged (0)
               }
   MAX-ACCESS  read-write
   STATUS      current
   DESCRIPTION
      "Path: efm.editConf.bandwidth.action.cirAction.ethernet.dropLevel

       Possibilities:
               unchanged   (0)"
   ::= {er1646v2XEfmBwEntry 4065001472}

er1646v2XEfmBwActCirActEthDeFlag OBJECT-TYPE
   SYNTAX      INTEGER
               {
               unchanged (255),
               clear (0),
               set (1)
               }
   MAX-ACCESS  read-write
   STATUS      current
   DESCRIPTION
      "Path: efm.editConf.bandwidth.action.cirAction.ethernet.deFlag

       Possibilities:
               unchanged   (255)
               clear   (0)
               set   (1)"
   ::= {er1646v2XEfmBwEntry 4065198080}

er1646v2XEfmBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4071161856}

er1646v2XEfmBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4071227392}

er1646v2XEfmBwActCirActIpDrpLev OBJECT-TYPE
   SYNTAX      INTEGER
               {
               unchanged (0)
               }
   MAX-ACCESS  read-write
   STATUS      current
   DESCRIPTION
      "Path: efm.editConf.bandwidth.action.cirAction.ip.dropLevel

       Possibilities:
               unchanged   (0)"
   ::= {er1646v2XEfmBwEntry 4071292928}

er1646v2XEfmBwActCirActIpDeFlag OBJECT-TYPE
   SYNTAX      INTEGER
               {
               unchanged (255),
               clear (0),
               set (1)
               }
   MAX-ACCESS  read-write
   STATUS      current
   DESCRIPTION
      "Path: efm.editConf.bandwidth.action.cirAction.ip.deFlag

       Possibilities:
               unchanged   (255)
               clear   (0)
               set   (1)"
   ::= {er1646v2XEfmBwEntry 4071489536}

er1646v2XEfmBwActEirActNone OBJECT-TYPE
   SYNTAX      OCTET STRING
   MAX-ACCESS  read-write
   STATUS      current
   DESCRIPTION
      "Path: efm.editConf.bandwidth.action.eirAction.none"
   ::= {er1646v2XEfmBwEntry 4095737856}

er1646v2XEfmBwActEirActEthCos1 OBJECT-TYPE
   SYNTAX      INTEGER
               {
               unchanged (256)
               }
   MAX-ACCESS  read-write
   STATUS      current
   DESCRIPTION
      "Path: efm.editConf.bandwidth.action.eirAction.ethernet.cosDepth1

       Possibilities:
               unchanged   (256)"
   ::= {er1646v2XEfmBwEntry 4097900544}

er1646v2XEfmBwActEirActEthDei1 OBJECT-TYPE
   SYNTAX      INTEGER
               {
               unchanged (255),
               clear (0),
               set (1)
               }
   MAX-ACCESS  read-write
   STATUS      current
   DESCRIPTION
      "Path: efm.editConf.bandwidth.action.eirAction.ethernet.deiDepth1

       Possibilities:
               unchanged   (255)
               clear   (0)
               set   (1)"
   ::= {er1646v2XEfmBwEntry 4099211264}

er1646v2XEfmBwActEirActEthCos2 OBJECT-TYPE
   SYNTAX      INTEGER
               {
               unchanged (256)
               }
   MAX-ACCESS  read-write
   STATUS      current
   DESCRIPTION
      "Path: efm.editConf.bandwidth.action.eirAction.ethernet.cosDepth2

       Possibilities:
               unchanged   (256)"
   ::= {er1646v2XEfmBwEntry 4097966080}

er1646v2XEfmBwActEirActEthDei2 OBJECT-TYPE
   SYNTAX      INTEGER
               {
               unchanged (255),
               clear (0),
               set (1)
               }
   MAX-ACCESS  read-write
   STATUS      current
   DESCRIPTION
      "Path: efm.editConf.bandwidth.action.eirAction.ethernet.deiDepth2

       Possibilities:
               unchanged   (255)
               clear   (0)
               set   (1)"
   ::= {er1646v2XEfmBwEntry 4099276800}

er1646v2XEfmBwActEirActEthCos3 OBJECT-TYPE
   SYNTAX      INTEGER
               {
               unchanged (256)
               }
   MAX-ACCESS  read-write
   STATUS      current
   DESCRIPTION
      "Path: efm.editConf.bandwidth.action.eirAction.ethernet.cosDepth3

       Possibilities:
               unchanged   (256)"
   ::= {er1646v2XEfmBwEntry 4098031616}

er1646v2XEfmBwActEirActEthDei3 OBJECT-TYPE
   SYNTAX      INTEGER
               {
               unchanged (255),
               clear (0),
               set (1)
               }
   MAX-ACCESS  read-write
   STATUS      current
   DESCRIPTION
      "Path: efm.editConf.bandwidth.action.eirAction.ethernet.deiDepth3

       Possibilities:
               unchanged   (255)
               clear   (0)
               set   (1)"
   ::= {er1646v2XEfmBwEntry 4099342336}

er1646v2XEfmBwActEirActEthCos4 OBJECT-TYPE
   SYNTAX      INTEGER
               {
               unchanged (256)
               }
   MAX-ACCESS  read-write
   STATUS      current
   DESCRIPTION
      "Path: efm.editConf.bandwidth.action.eirAction.ethernet.cosDepth4

       Possibilities:
               unchanged   (256)"
   ::= {er1646v2XEfmBwEntry 4098097152}

er1646v2XEfmBwActEirActEthDei4 OBJECT-TYPE
   SYNTAX      INTEGER
               {
               unchanged (255),
               clear (0),
               set (1)
               }
   MAX-ACCESS  read-write
   STATUS      current
   DESCRIPTION
      "Path: efm.editConf.bandwidth.action.eirAction.ethernet.deiDepth4

       Possibilities:
               unchanged   (255)
               clear   (0)
               set   (1)"
   ::= {er1646v2XEfmBwEntry 4099407872}

er1646v2XEfmBwActEirActEthCos5 OBJECT-TYPE
   SYNTAX      INTEGER
               {
               unchanged (256)
               }
   MAX-ACCESS  read-write
   STATUS      current
   DESCRIPTION
      "Path: efm.editConf.bandwidth.action.eirAction.ethernet.cosDepth5

       Possibilities:
               unchanged   (256)"
   ::= {er1646v2XEfmBwEntry 4098162688}

er1646v2XEfmBwActEirActEthDei5 OBJECT-TYPE
   SYNTAX      INTEGER
               {
               unchanged (255),
               clear (0),
               set (1)
               }
   MAX-ACCESS  read-write
   STATUS      current
   DESCRIPTION
      "Path: efm.editConf.bandwidth.action.eirAction.ethernet.deiDepth5

       Possibilities:
               unchanged   (255)
               clear   (0)
               set   (1)"
   ::= {er1646v2XEfmBwEntry 4099473408}

er1646v2XEfmBwActEirActEthCos6 OBJECT-TYPE
   SYNTAX      INTEGER
               {
               unchanged (256)
               }
   MAX-ACCESS  read-write
   STATUS      current
   DESCRIPTION
      "Path: efm.editConf.bandwidth.action.eirAction.ethernet.cosDepth6

       Possibilities:
               unchanged   (256)"
   ::= {er1646v2XEfmBwEntry 4098228224}

er1646v2XEfmBwActEirActEthDei6 OBJECT-TYPE
   SYNTAX      INTEGER
               {
               unchanged (255),
               clear (0),
               set (1)
               }
   MAX-ACCESS  read-write
   STATUS      current
   DESCRIPTION
      "Path: efm.editConf.bandwidth.action.eirAction.ethernet.deiDepth6

       Possibilities:
               unchanged   (255)
               clear   (0)
               set   (1)"
   ::= {er1646v2XEfmBwEntry 4099538944}

er1646v2XEfmBwActEirActEthCos7 OBJECT-TYPE
   SYNTAX      INTEGER
               {
               unchanged (256)
               }
   MAX-ACCESS  read-write
   STATUS      current
   DESCRIPTION
      "Path: efm.editConf.bandwidth.action.eirAction.ethernet.cosDepth7

       Possibilities:
               unchanged   (256)"
   ::= {er1646v2XEfmBwEntry 4098293760}

er1646v2XEfmBwActEirActEthDei7 OBJECT-TYPE
   SYNTAX      INTEGER
               {
               unchanged (255),
               clear (0),
               set (1)
               }
   MAX-ACCESS  read-write
   STATUS      current
   DESCRIPTION
      "Path: efm.editConf.bandwidth.action.eirAction.ethernet.deiDepth7

       Possibilities:
               unchanged   (255)
               clear   (0)
               set   (1)"
   ::= {er1646v2XEfmBwEntry 4099604480}

er1646v2XEfmBwActEirActEthCos8 OBJECT-TYPE
   SYNTAX      INTEGER
               {
               unchanged (256)
               }
   MAX-ACCESS  read-write
   STATUS      current
   DESCRIPTION
      "Path: efm.editConf.bandwidth.action.eirAction.ethernet.cosDepth8

       Possibilities:
               unchanged   (256)"
   ::= {er1646v2XEfmBwEntry 4098359296}

er1646v2XEfmBwActEirActEthDei8 OBJECT-TYPE
   SYNTAX      INTEGER
               {
               unchanged (255),
               clear (0),
               set (1)
               }
   MAX-ACCESS  read-write
   STATUS      current
   DESCRIPTION
      "Path: efm.editConf.bandwidth.action.eirAction.ethernet.deiDepth8

       Possibilities:
               unchanged   (255)
               clear   (0)
               set   (1)"
   ::= {er1646v2XEfmBwEntry 4099670016}

er1646v2XEfmBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4098424832}

er1646v2XEfmBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4098490368}

er1646v2XEfmBwActEirActEthDrpLev OBJECT-TYPE
   SYNTAX      INTEGER
               {
               unchanged (0)
               }
   MAX-ACCESS  read-write
   STATUS      current
   DESCRIPTION
      "Path: efm.editConf.bandwidth.action.eirAction.ethernet.dropLevel

       Possibilities:
               unchanged   (0)"
   ::= {er1646v2XEfmBwEntry 4098555904}

er1646v2XEfmBwActEirActEthDeFlag OBJECT-TYPE
   SYNTAX      INTEGER
               {
               unchanged (255),
               clear (0),
               set (1)
               }
   MAX-ACCESS  read-write
   STATUS      current
   DESCRIPTION
      "Path: efm.editConf.bandwidth.action.eirAction.ethernet.deFlag

       Possibilities:
               unchanged   (255)
               clear   (0)
               set   (1)"
   ::= {er1646v2XEfmBwEntry 4098752512}

er1646v2XEfmBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4104716288}

er1646v2XEfmBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4104781824}

er1646v2XEfmBwActEirActIpDrpLev OBJECT-TYPE
   SYNTAX      INTEGER
               {
               unchanged (0)
               }
   MAX-ACCESS  read-write
   STATUS      current
   DESCRIPTION
      "Path: efm.editConf.bandwidth.action.eirAction.ip.dropLevel

       Possibilities:
               unchanged   (0)"
   ::= {er1646v2XEfmBwEntry 4104847360}

er1646v2XEfmBwActEirActIpDeFlag OBJECT-TYPE
   SYNTAX      INTEGER
               {
               unchanged (255),
               clear (0),
               set (1)
               }
   MAX-ACCESS  read-write
   STATUS      current
   DESCRIPTION
      "Path: efm.editConf.bandwidth.action.eirAction.ip.deFlag

       Possibilities:
               unchanged   (255)
               clear   (0)
               set   (1)"
   ::= {er1646v2XEfmBwEntry 4105043968}

er1646v2XEfmBwActViolActNone OBJECT-TYPE
   SYNTAX      OCTET STRING
   MAX-ACCESS  read-write
   STATUS      current
   DESCRIPTION
      "Path: efm.editConf.bandwidth.action.violateAction.none"
   ::= {er1646v2XEfmBwEntry 4129292288}

er1646v2XEfmBwActViolActDrop OBJECT-TYPE
   SYNTAX      OCTET STRING
   MAX-ACCESS  read-write
   STATUS      current
   DESCRIPTION
      "Path: efm.editConf.bandwidth.action.violateAction.drop"
   ::= {er1646v2XEfmBwEntry 4133486592}

er1646v2XEfmBwActViolActEthCos1 OBJECT-TYPE
   SYNTAX      INTEGER
               {
               unchanged (256)
               }
   MAX-ACCESS  read-write
   STATUS      current
   DESCRIPTION
      "Path: efm.editConf.bandwidth.action.violateAction.ethernet.cosDepth1

       Possibilities:
               unchanged   (256)"
   ::= {er1646v2XEfmBwEntry 4131454976}

er1646v2XEfmBwActViolActEthDei1 OBJECT-TYPE
   SYNTAX      INTEGER
               {
               unchanged (255),
               clear (0),
               set (1)
               }
   MAX-ACCESS  read-write
   STATUS      current
   DESCRIPTION
      "Path: efm.editConf.bandwidth.action.violateAction.ethernet.deiDepth1

       Possibilities:
               unchanged   (255)
               clear   (0)
               set   (1)"
   ::= {er1646v2XEfmBwEntry 4132765696}

er1646v2XEfmBwActViolActEthCos2 OBJECT-TYPE
   SYNTAX      INTEGER
               {
               unchanged (256)
               }
   MAX-ACCESS  read-write
   STATUS      current
   DESCRIPTION
      "Path: efm.editConf.bandwidth.action.violateAction.ethernet.cosDepth2

       Possibilities:
               unchanged   (256)"
   ::= {er1646v2XEfmBwEntry 4131520512}

er1646v2XEfmBwActViolActEthDei2 OBJECT-TYPE
   SYNTAX      INTEGER
               {
               unchanged (255),
               clear (0),
               set (1)
               }
   MAX-ACCESS  read-write
   STATUS      current
   DESCRIPTION
      "Path: efm.editConf.bandwidth.action.violateAction.ethernet.deiDepth2

       Possibilities:
               unchanged   (255)
               clear   (0)
               set   (1)"
   ::= {er1646v2XEfmBwEntry 4132831232}

er1646v2XEfmBwActViolActEthCos3 OBJECT-TYPE
   SYNTAX      INTEGER
               {
               unchanged (256)
               }
   MAX-ACCESS  read-write
   STATUS      current
   DESCRIPTION
      "Path: efm.editConf.bandwidth.action.violateAction.ethernet.cosDepth3

       Possibilities:
               unchanged   (256)"
   ::= {er1646v2XEfmBwEntry 4131586048}

er1646v2XEfmBwActViolActEthDei3 OBJECT-TYPE
   SYNTAX      INTEGER
               {
               unchanged (255),
               clear (0),
               set (1)
               }
   MAX-ACCESS  read-write
   STATUS      current
   DESCRIPTION
      "Path: efm.editConf.bandwidth.action.violateAction.ethernet.deiDepth3

       Possibilities:
               unchanged   (255)
               clear   (0)
               set   (1)"
   ::= {er1646v2XEfmBwEntry 4132896768}

er1646v2XEfmBwActViolActEthCos4 OBJECT-TYPE
   SYNTAX      INTEGER
               {
               unchanged (256)
               }
   MAX-ACCESS  read-write
   STATUS      current
   DESCRIPTION
      "Path: efm.editConf.bandwidth.action.violateAction.ethernet.cosDepth4

       Possibilities:
               unchanged   (256)"
   ::= {er1646v2XEfmBwEntry 4131651584}

er1646v2XEfmBwActViolActEthDei4 OBJECT-TYPE
   SYNTAX      INTEGER
               {
               unchanged (255),
               clear (0),
               set (1)
               }
   MAX-ACCESS  read-write
   STATUS      current
   DESCRIPTION
      "Path: efm.editConf.bandwidth.action.violateAction.ethernet.deiDepth4

       Possibilities:
               unchanged   (255)
               clear   (0)
               set   (1)"
   ::= {er1646v2XEfmBwEntry 4132962304}

er1646v2XEfmBwActViolActEthCos5 OBJECT-TYPE
   SYNTAX      INTEGER
               {
               unchanged (256)
               }
   MAX-ACCESS  read-write
   STATUS      current
   DESCRIPTION
      "Path: efm.editConf.bandwidth.action.violateAction.ethernet.cosDepth5

       Possibilities:
               unchanged   (256)"
   ::= {er1646v2XEfmBwEntry 4131717120}

er1646v2XEfmBwActViolActEthDei5 OBJECT-TYPE
   SYNTAX      INTEGER
               {
               unchanged (255),
               clear (0),
               set (1)
               }
   MAX-ACCESS  read-write
   STATUS      current
   DESCRIPTION
      "Path: efm.editConf.bandwidth.action.violateAction.ethernet.deiDepth5

       Possibilities:
               unchanged   (255)
               clear   (0)
               set   (1)"
   ::= {er1646v2XEfmBwEntry 4133027840}

er1646v2XEfmBwActViolActEthCos6 OBJECT-TYPE
   SYNTAX      INTEGER
               {
               unchanged (256)
               }
   MAX-ACCESS  read-write
   STATUS      current
   DESCRIPTION
      "Path: efm.editConf.bandwidth.action.violateAction.ethernet.cosDepth6

       Possibilities:
               unchanged   (256)"
   ::= {er1646v2XEfmBwEntry 4131782656}

er1646v2XEfmBwActViolActEthDei6 OBJECT-TYPE
   SYNTAX      INTEGER
               {
               unchanged (255),
               clear (0),
               set (1)
               }
   MAX-ACCESS  read-write
   STATUS      current
   DESCRIPTION
      "Path: efm.editConf.bandwidth.action.violateAction.ethernet.deiDepth6

       Possibilities:
               unchanged   (255)
               clear   (0)
               set   (1)"
   ::= {er1646v2XEfmBwEntry 4133093376}

er1646v2XEfmBwActViolActEthCos7 OBJECT-TYPE
   SYNTAX      INTEGER
               {
               unchanged (256)
               }
   MAX-ACCESS  read-write
   STATUS      current
   DESCRIPTION
      "Path: efm.editConf.bandwidth.action.violateAction.ethernet.cosDepth7

       Possibilities:
               unchanged   (256)"
   ::= {er1646v2XEfmBwEntry 4131848192}

er1646v2XEfmBwActViolActEthDei7 OBJECT-TYPE
   SYNTAX      INTEGER
               {
               unchanged (255),
               clear (0),
               set (1)
               }
   MAX-ACCESS  read-write
   STATUS      current
   DESCRIPTION
      "Path: efm.editConf.bandwidth.action.violateAction.ethernet.deiDepth7

       Possibilities:
               unchanged   (255)
               clear   (0)
               set   (1)"
   ::= {er1646v2XEfmBwEntry 4133158912}

er1646v2XEfmBwActViolActEthCos8 OBJECT-TYPE
   SYNTAX      INTEGER
               {
               unchanged (256)
               }
   MAX-ACCESS  read-write
   STATUS      current
   DESCRIPTION
      "Path: efm.editConf.bandwidth.action.violateAction.ethernet.cosDepth8

       Possibilities:
               unchanged   (256)"
   ::= {er1646v2XEfmBwEntry 4131913728}

er1646v2XEfmBwActViolActEthDei8 OBJECT-TYPE
   SYNTAX      INTEGER
               {
               unchanged (255),
               clear (0),
               set (1)
               }
   MAX-ACCESS  read-write
   STATUS      current
   DESCRIPTION
      "Path: efm.editConf.bandwidth.action.violateAction.ethernet.deiDepth8

       Possibilities:
               unchanged   (255)
               clear   (0)
               set   (1)"
   ::= {er1646v2XEfmBwEntry 4133224448}

er1646v2XEfmBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4131979264}

er1646v2XEfmBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4132044800}

er1646v2XEfmBwActViolActEthDrpLev OBJECT-TYPE
   SYNTAX      INTEGER
               {
               unchanged (0)
               }
   MAX-ACCESS  read-write
   STATUS      current
   DESCRIPTION
      "Path: efm.editConf.bandwidth.action.violateAction.ethernet.dropLevel

       Possibilities:
               unchanged   (0)"
   ::= {er1646v2XEfmBwEntry 4132110336}

er1646v2XEfmBwActViolActEthDeFlag OBJECT-TYPE
   SYNTAX      INTEGER
               {
               unchanged (255),
               clear (0),
               set (1)
               }
   MAX-ACCESS  read-write
   STATUS      current
   DESCRIPTION
      "Path: efm.editConf.bandwidth.action.violateAction.ethernet.deFlag

       Possibilities:
               unchanged   (255)
               clear   (0)
               set   (1)"
   ::= {er1646v2XEfmBwEntry 4132306944}

er1646v2XEfmBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmBwEntry 4138270720}

er1646v2XEfmBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmBwEntry 4138336256}

er1646v2XEfmBwActViolActIpDrpLev OBJECT-TYPE
   SYNTAX      INTEGER
               {
               unchanged (0)
               }
   MAX-ACCESS  read-write
   STATUS      current
   DESCRIPTION
      "Path: efm.editConf.bandwidth.action.violateAction.ip.dropLevel

       Possibilities:
               unchanged   (0)"
   ::= {er1646v2XEfmBwEntry 4138401792}

er1646v2XEfmBwActViolActIpDeFlag OBJECT-TYPE
   SYNTAX      INTEGER
               {
               unchanged (255),
               clear (0),
               set (1)
               }
   MAX-ACCESS  read-write
   STATUS      current
   DESCRIPTION
      "Path: efm.editConf.bandwidth.action.violateAction.ip.deFlag

       Possibilities:
               unchanged   (255)
               clear   (0)
               set   (1)"
   ::= {er1646v2XEfmBwEntry 4138598400}


er1646v2XEfmPriorityPolicy OBJECT-TYPE
   SYNTAX      DisplayString
   MAX-ACCESS  read-write
   STATUS      current
   DESCRIPTION
      "Path: efm.editConf.priorityPolicy
       Info: Preferred Policy"
   ::= {er1646v2XEfm 39}


er1646v2XEfmDelayOptimisation OBJECT-TYPE
   SYNTAX      INTEGER
               {
               disabled (0),
               enabled (1)
               }
   MAX-ACCESS  read-write
   STATUS      current
   DESCRIPTION
      "Path: efm.editConf.delayOptimisation
       Info: optimise delay

       Possibilities:
               disabled   (0)
               enabled   (1)"
   ::= {er1646v2XEfm 80}


er1646v2XEfmArp OBJECT IDENTIFIER ::= {er1646v2XEfm 19}

er1646v2XEfmArpSSC OBJECT IDENTIFIER ::= {er1646v2XEfmArp 1}

er1646v2XEfmArpEntry OBJECT IDENTIFIER ::= {er1646v2XEfmArpSSC 1}

er1646v2XEfmArpTimeOut OBJECT-TYPE
   SYNTAX      TimeTicks
   MAX-ACCESS  read-write
   STATUS      current
   DESCRIPTION
      "Path: efm.editConf.arp.timeOut

       Time in centi-second."
   ::= {er1646v2XEfmArpEntry 201326592}

er1646v2XEfmArpProxyArp OBJECT-TYPE
   SYNTAX      INTEGER
               {
               disabled (0),
               enabled (1)
               }
   MAX-ACCESS  read-write
   STATUS      current
   DESCRIPTION
      "Path: efm.editConf.arp.proxyArp

       Possibilities:
               disabled   (0)
               enabled   (1)"
   ::= {er1646v2XEfmArpEntry 838860800}

er1646v2XEfmArpStaticArp OBJECT-TYPE
   SYNTAX      SEQUENCE OF Er1646v2XEfmArpStaticArpEntry
   MAX-ACCESS  not-accessible
   STATUS      current
   DESCRIPTION
      ""
   ::= {er1646v2XEfmArp 50331648}

er1646v2XEfmArpStaticArpEntry OBJECT-TYPE
   SYNTAX      Er1646v2XEfmArpStaticArpEntry
   MAX-ACCESS  not-accessible
   STATUS      current
   DESCRIPTION
      ""
   INDEX      { er1646v2XEfmArpStaticArpTableIx }
   ::= {er1646v2XEfmArpStaticArp 1}

Er1646v2XEfmArpStaticArpEntry ::=
   SEQUENCE
      {
      er1646v2XEfmArpStaticArpActions
         VariableLengthTableActions,
      er1646v2XEfmArpStaticArpTableIx
         TableIndex,
      er1646v2XEfmArpStaticArpMacAddress
         OCTET STRING,
      er1646v2XEfmArpStaticArpIpAddress
         IpAddress
      }

er1646v2XEfmArpStaticArpActions OBJECT-TYPE
   SYNTAX      VariableLengthTableActions
   MAX-ACCESS  read-write
   STATUS      current
   DESCRIPTION
      "By way of this field, some manipulations
       on this table may be performed."
   ::= {er1646v2XEfmArpStaticArpEntry 2}

er1646v2XEfmArpStaticArpTableIx OBJECT-TYPE
   SYNTAX      TableIndex
   MAX-ACCESS  not-accessible
   STATUS      current
   DESCRIPTION
      ""
   ::= {er1646v2XEfmArpStaticArpEntry 11}

er1646v2XEfmArpStaticArpMacAddress OBJECT-TYPE
   SYNTAX      OCTET STRING
   MAX-ACCESS  read-write
   STATUS      current
   DESCRIPTION
      "Path: efm.editConf.arp.staticArp.macAddress

       MAC address."
   ::= {er1646v2XEfmArpStaticArpEntry 16777216}

er1646v2XEfmArpStaticArpIpAddress OBJECT-TYPE
   SYNTAX      IpAddress
   MAX-ACCESS  read-write
   STATUS      current
   DESCRIPTION
      "Path: efm.editConf.arp.staticArp.ipAddress"
   ::= {er1646v2XEfmArpStaticArpEntry 33554432}


er1646v2XEfmBrC OBJECT IDENTIFIER ::= {er1646v2XEfm 27}

er1646v2XEfmBrCSSC OBJECT IDENTIFIER ::= {er1646v2XEfmBrC 1}

er1646v2XEfmBrCEntry OBJECT IDENTIFIER ::= {er1646v2XEfmBrCSSC 1}

er1646v2XEfmBrCAccessList OBJECT-TYPE
   SYNTAX      DisplayString
   MAX-ACCESS  read-write
   STATUS      current
   DESCRIPTION
      "Path: efm.editConf.bridging.accessList"
   ::= {er1646v2XEfmBrCEntry 83886080}

er1646v2XEfmBrCInAccessList OBJECT-TYPE
   SYNTAX      DisplayString
   MAX-ACCESS  read-write
   STATUS      current
   DESCRIPTION
      "Path: efm.editConf.bridging.inAccessList"
   ::= {er1646v2XEfmBrCEntry 251658240}

er1646v2XEfmBrCTp OBJECT-TYPE
   SYNTAX      DisplayString
   MAX-ACCESS  read-write
   STATUS      current
   DESCRIPTION
      "Path: efm.editConf.bridging.trafficPolicy"
   ::= {er1646v2XEfmBrCEntry 100663296}

er1646v2XEfmBrCBridgeGroup OBJECT-TYPE
   SYNTAX      DisplayString
   MAX-ACCESS  read-write
   STATUS      current
   DESCRIPTION
      "Path: efm.editConf.bridging.bridgeGroup"
   ::= {er1646v2XEfmBrCEntry 117440512}

er1646v2XEfmBrCLimBC OBJECT-TYPE
   SYNTAX      INTEGER
               {
               disabled (0),
               enabled (1)
               }
   MAX-ACCESS  read-write
   STATUS      current
   DESCRIPTION
      "Path: efm.editConf.bridging.limitBroadcasts

       Possibilities:
               disabled   (0)
               enabled   (1)"
   ::= {er1646v2XEfmBrCEntry 134217728}

er1646v2XEfmBrCPrivateMode OBJECT-TYPE
   SYNTAX      INTEGER
               {
               disabled (0),
               enabled (1)
               }
   MAX-ACCESS  read-write
   STATUS      current
   DESCRIPTION
      "Path: efm.editConf.bridging.privateMode

       Possibilities:
               disabled   (0)
               enabled   (1)"
   ::= {er1646v2XEfmBrCEntry 419430400}

er1646v2XEfmBrCLearning OBJECT-TYPE
   SYNTAX      INTEGER
               {
               disabled (0),
               enabled (1)
               }
   MAX-ACCESS  read-write
   STATUS      current
   DESCRIPTION
      "Path: efm.editConf.bridging.learning

       Possibilities:
               disabled   (0)
               enabled   (1)"
   ::= {er1646v2XEfmBrCEntry 201326592}

er1646v2XEfmBrCMaxCacheSize OBJECT-TYPE
   SYNTAX      INTEGER
               {
               unlimited (0)
               }
   MAX-ACCESS  read-write
   STATUS      current
   DESCRIPTION
      "Path: efm.editConf.bridging.maxCacheSize

       Possibilities:
               unlimited   (0)"
   ::= {er1646v2XEfmBrCEntry 218103808}

er1646v2XEfmBrCRelearnDropOnRelearn OBJECT-TYPE
   SYNTAX      INTEGER
               {
               disabled (0),
               enabled (1)
               }
   MAX-ACCESS  read-write
   STATUS      current
   DESCRIPTION
      "Path: efm.editConf.bridging.relearn.dropOnRelearn

       Possibilities:
               disabled   (0)
               enabled   (1)"
   ::= {er1646v2XEfmBrCEntry 234946560}

er1646v2XEfmBrCRelearnShutdownThreshold OBJECT-TYPE
   SYNTAX      Integer32
   MAX-ACCESS  read-write
   STATUS      current
   DESCRIPTION
      "Path: efm.editConf.bridging.relearn.shutdownThreshold"
   ::= {er1646v2XEfmBrCEntry 235012096}

er1646v2XEfmBrCRelearnShutdownTime OBJECT-TYPE
   SYNTAX      TimeTicks
   MAX-ACCESS  read-write
   STATUS      current
   DESCRIPTION
      "Path: efm.editConf.bridging.relearn.shutdownTime

       Time in centi-second."
   ::= {er1646v2XEfmBrCEntry 235077632}

er1646v2XEfmBrCRelearnLoopDetection OBJECT-TYPE
   SYNTAX      INTEGER
               {
               disabled (0),
               passive (1),
               active (2)
               }
   MAX-ACCESS  read-write
   STATUS      current
   DESCRIPTION
      "Path: efm.editConf.bridging.relearn.loopDetection

       Possibilities:
               disabled   (0)
               passive   (1)
               active   (2)"
   ::= {er1646v2XEfmBrCEntry 235143168}

er1646v2XEfmBrCRelearnLoopDetectionInterval OBJECT-TYPE
   SYNTAX      TimeTicks
   MAX-ACCESS  read-write
   STATUS      current
   DESCRIPTION
      "Path: efm.editConf.bridging.relearn.loopDetectionInterval

       Time in centi-second."
   ::= {er1646v2XEfmBrCEntry 235208704}

er1646v2XEfmBrCVlanMemberShip OBJECT-TYPE
   SYNTAX      INTEGER
               {
               all (0),
               none (1),
               grouped (2)
               }
   MAX-ACCESS  read-write
   STATUS      current
   DESCRIPTION
      "Path: efm.editConf.bridging.vlanMemberShip

       Possibilities:
               all   (0)
               none   (1)
               grouped   (2)"
   ::= {er1646v2XEfmBrCEntry 318767104}

er1646v2XEfmBrCDot1adType OBJECT-TYPE
   SYNTAX      INTEGER
               {
               slOPTg (0),
               cPort (4),
               sPort (1),
               nni (2)
               }
   MAX-ACCESS  read-write
   STATUS      current
   DESCRIPTION
      "Path: efm.editConf.bridging.dot1ad.type

       Possibilities:
               <OPT>   (0)
               cPort   (4)
               sPort   (1)
               nni   (2)"
   ::= {er1646v2XEfmBrCEntry 503382016}

er1646v2XEfmBrCPriority OBJECT-TYPE
   SYNTAX      Integer32
   MAX-ACCESS  read-write
   STATUS      current
   DESCRIPTION
      "Path: efm.editConf.bridging.priority"
   ::= {er1646v2XEfmBrCEntry 33554432}

er1646v2XEfmBrCPathCost OBJECT-TYPE
   SYNTAX      Integer32
   MAX-ACCESS  read-write
   STATUS      current
   DESCRIPTION
      "Path: efm.editConf.bridging.pathCost"
   ::= {er1646v2XEfmBrCEntry 50331648}

er1646v2XEfmBrCInternalPathCost OBJECT-TYPE
   SYNTAX      Integer32
   MAX-ACCESS  read-write
   STATUS      current
   DESCRIPTION
      "Path: efm.editConf.bridging.internalPathCost"
   ::= {er1646v2XEfmBrCEntry 301989888}

er1646v2XEfmBrCTCD OBJECT-TYPE
   SYNTAX      INTEGER
               {
               disabled (0),
               enabled (1)
               }
   MAX-ACCESS  read-write
   STATUS      current
   DESCRIPTION
      "Path: efm.editConf.bridging.topologyChangeDetection

       Possibilities:
               disabled   (0)
               enabled   (1)"
   ::= {er1646v2XEfmBrCEntry 67108864}

er1646v2XEfmBrCRestrictedRole OBJECT-TYPE
   SYNTAX      INTEGER
               {
               disabled (0),
               enabled (1)
               }
   MAX-ACCESS  read-write
   STATUS      current
   DESCRIPTION
      "Path: efm.editConf.bridging.restrictedRole

       Possibilities:
               disabled   (0)
               enabled   (1)"
   ::= {er1646v2XEfmBrCEntry 335544320}

er1646v2XEfmBrCAdminEdge OBJECT-TYPE
   SYNTAX      INTEGER
               {
               disabled (0),
               enabled (1)
               }
   MAX-ACCESS  read-write
   STATUS      current
   DESCRIPTION
      "Path: efm.editConf.bridging.adminEdge

       Possibilities:
               disabled   (0)
               enabled   (1)"
   ::= {er1646v2XEfmBrCEntry 268435456}

er1646v2XEfmBrCMgmtInline OBJECT-TYPE
   SYNTAX      INTEGER
               {
               disabled (0),
               enabled (1)
               }
   MAX-ACCESS  read-write
   STATUS      current
   DESCRIPTION
      "Path: efm.editConf.bridging.mgmtInline

       Possibilities:
               disabled   (0)
               enabled   (1)"
   ::= {er1646v2XEfmBrCEntry 369098752}

er1646v2XEfmBrCL2ptMode OBJECT-TYPE
   SYNTAX      INTEGER
               {
               disabled (0),
               enabled (1)
               }
   MAX-ACCESS  read-write
   STATUS      current
   DESCRIPTION
      "Path: efm.editConf.bridging.l2ProtTunnel.mode

       Possibilities:
               disabled   (0)
               enabled   (1)"
   ::= {er1646v2XEfmBrCEntry 403701760}

er1646v2XEfmBrCL2ptProtocols OBJECT-TYPE
   SYNTAX      Integer32
   MAX-ACCESS  read-write
   STATUS      current
   DESCRIPTION
      "Path: efm.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2XEfmBrCEntry 404750336}

er1646v2XEfmBrCL2ptDestMac OBJECT-TYPE
   SYNTAX      OCTET STRING
   MAX-ACCESS  read-write
   STATUS      current
   DESCRIPTION
      "Path: efm.editConf.bridging.l2ProtTunnel.destinationMac

       MAC address."
   ::= {er1646v2XEfmBrCEntry 405798912}

er1646v2XEfmBrCL2ptCos OBJECT-TYPE
   SYNTAX      INTEGER
               {
               unchanged (255)
               }
   MAX-ACCESS  read-write
   STATUS      current
   DESCRIPTION
      "Path: efm.editConf.bridging.l2ProtTunnel.cos

       Possibilities:
               unchanged   (255)"
   ::= {er1646v2XEfmBrCEntry 406847488}

er1646v2XEfmBrCL2ptDropThrStp OBJECT-TYPE
   SYNTAX      INTEGER
               {
               unlimited (0)
               }
   UNITS       "packets/sec"
   MAX-ACCESS  read-write
   STATUS      current
   DESCRIPTION
      "Path: efm.editConf.bridging.l2ProtTunnel.dropThresholds.stp

       unit name = packets/sec

       Possibilities:
               unlimited   (0)"
   ::= {er1646v2XEfmBrCEntry 407900160}

er1646v2XEfmBrCL2ptDropThrLldp OBJECT-TYPE
   SYNTAX      INTEGER
               {
               unlimited (0)
               }
   UNITS       "packets/sec"
   MAX-ACCESS  read-write
   STATUS      current
   DESCRIPTION
      "Path: efm.editConf.bridging.l2ProtTunnel.dropThresholds.lldp

       unit name = packets/sec

       Possibilities:
               unlimited   (0)"
   ::= {er1646v2XEfmBrCEntry 407904256}

er1646v2XEfmBrCL2ptDropThrOam OBJECT-TYPE
   SYNTAX      INTEGER
               {
               unlimited (0)
               }
   UNITS       "packets/sec"
   MAX-ACCESS  read-write
   STATUS      current
   DESCRIPTION
      "Path: efm.editConf.bridging.l2ProtTunnel.dropThresholds.oam

       unit name = packets/sec

       Possibilities:
               unlimited   (0)"
   ::= {er1646v2XEfmBrCEntry 407908352}

er1646v2XEfmBrCL2ptDropThrCdp OBJECT-TYPE
   SYNTAX      INTEGER
               {
               unlimited (0)
               }
   UNITS       "packets/sec"
   MAX-ACCESS  read-write
   STATUS      current
   DESCRIPTION
      "Path: efm.editConf.bridging.l2ProtTunnel.dropThresholds.cdp

       unit name = packets/sec

       Possibilities:
               unlimited   (0)"
   ::= {er1646v2XEfmBrCEntry 407912448}

er1646v2XEfmBrCL2ptDropThrVtp OBJECT-TYPE
   SYNTAX      INTEGER
               {
               unlimited (0)
               }
   UNITS       "packets/sec"
   MAX-ACCESS  read-write
   STATUS      current
   DESCRIPTION
      "Path: efm.editConf.bridging.l2ProtTunnel.dropThresholds.vtp

       unit name = packets/sec

       Possibilities:
               unlimited   (0)"
   ::= {er1646v2XEfmBrCEntry 407916544}

er1646v2XEfmBrCL2ptDropThrLacp OBJECT-TYPE
   SYNTAX      INTEGER
               {
               unlimited (0)
               }
   UNITS       "packets/sec"
   MAX-ACCESS  read-write
   STATUS      current
   DESCRIPTION
      "Path: efm.editConf.bridging.l2ProtTunnel.dropThresholds.lacp

       unit name = packets/sec

       Possibilities:
               unlimited   (0)"
   ::= {er1646v2XEfmBrCEntry 407920640}

er1646v2XEfmBrCL2ptDropThrEfmOam OBJECT-TYPE
   SYNTAX      INTEGER
               {
               unlimited (0)
               }
   UNITS       "packets/sec"
   MAX-ACCESS  read-write
   STATUS      current
   DESCRIPTION
      "Path: efm.editConf.bridging.l2ProtTunnel.dropThresholds.efmOam

       unit name = packets/sec

       Possibilities:
               unlimited   (0)"
   ::= {er1646v2XEfmBrCEntry 407924736}

er1646v2XEfmBrCL2ptDropThrPvst OBJECT-TYPE
   SYNTAX      INTEGER
               {
               unlimited (0)
               }
   UNITS       "packets/sec"
   MAX-ACCESS  read-write
   STATUS      current
   DESCRIPTION
      "Path: efm.editConf.bridging.l2ProtTunnel.dropThresholds.pvst

       unit name = packets/sec

       Possibilities:
               unlimited   (0)"
   ::= {er1646v2XEfmBrCEntry 407928832}

er1646v2XEfmBrCL2ptDropThrMmrp OBJECT-TYPE
   SYNTAX      INTEGER
               {
               unlimited (0)
               }
   UNITS       "packets/sec"
   MAX-ACCESS  read-write
   STATUS      current
   DESCRIPTION
      "Path: efm.editConf.bridging.l2ProtTunnel.dropThresholds.mmrp

       unit name = packets/sec

       Possibilities:
               unlimited   (0)"
   ::= {er1646v2XEfmBrCEntry 407932928}

er1646v2XEfmBrCL2ptDropThrMvrp OBJECT-TYPE
   SYNTAX      INTEGER
               {
               unlimited (0)
               }
   UNITS       "packets/sec"
   MAX-ACCESS  read-write
   STATUS      current
   DESCRIPTION
      "Path: efm.editConf.bridging.l2ProtTunnel.dropThresholds.mvrp

       unit name = packets/sec

       Possibilities:
               unlimited   (0)"
   ::= {er1646v2XEfmBrCEntry 407937024}

er1646v2XEfmBrCL2ptDropThrGvrp OBJECT-TYPE
   SYNTAX      INTEGER
               {
               unlimited (0)
               }
   UNITS       "packets/sec"
   MAX-ACCESS  read-write
   STATUS      current
   DESCRIPTION
      "Path: efm.editConf.bridging.l2ProtTunnel.dropThresholds.gvrp

       unit name = packets/sec

       Possibilities:
               unlimited   (0)"
   ::= {er1646v2XEfmBrCEntry 407941120}

er1646v2XEfmBrCL2ptDropThrGmrp OBJECT-TYPE
   SYNTAX      INTEGER
               {
               unlimited (0)
               }
   UNITS       "packets/sec"
   MAX-ACCESS  read-write
   STATUS      current
   DESCRIPTION
      "Path: efm.editConf.bridging.l2ProtTunnel.dropThresholds.gmrp

       unit name = packets/sec

       Possibilities:
               unlimited   (0)"
   ::= {er1646v2XEfmBrCEntry 407945216}

er1646v2XEfmBrCL2ptDropThrDtp OBJECT-TYPE
   SYNTAX      INTEGER
               {
               unlimited (0)
               }
   UNITS       "packets/sec"
   MAX-ACCESS  read-write
   STATUS      current
   DESCRIPTION
      "Path: efm.editConf.bridging.l2ProtTunnel.dropThresholds.dtp

       unit name = packets/sec

       Possibilities:
               unlimited   (0)"
   ::= {er1646v2XEfmBrCEntry 407949312}

er1646v2XEfmBrCL2ptDropThrPagp OBJECT-TYPE
   SYNTAX      INTEGER
               {
               unlimited (0)
               }
   UNITS       "packets/sec"
   MAX-ACCESS  read-write
   STATUS      current
   DESCRIPTION
      "Path: efm.editConf.bridging.l2ProtTunnel.dropThresholds.pagp

       unit name = packets/sec

       Possibilities:
               unlimited   (0)"
   ::= {er1646v2XEfmBrCEntry 407953408}

er1646v2XEfmBrCL2ptDropThrUdld OBJECT-TYPE
   SYNTAX      INTEGER
               {
               unlimited (0)
               }
   UNITS       "packets/sec"
   MAX-ACCESS  read-write
   STATUS      current
   DESCRIPTION
      "Path: efm.editConf.bridging.l2ProtTunnel.dropThresholds.udld

       unit name = packets/sec

       Possibilities:
               unlimited   (0)"
   ::= {er1646v2XEfmBrCEntry 407957504}


er1646v2XEfmVlanTagging OBJECT IDENTIFIER ::= {er1646v2XEfm 14}

er1646v2XEfmVlanTaggingSSC OBJECT IDENTIFIER ::= {er1646v2XEfmVlanTagging 1}

er1646v2XEfmVlanTaggingEntry OBJECT IDENTIFIER ::= {er1646v2XEfmVlanTaggingSSC 1}

er1646v2XEfmVlanTaggingUntaggedAction OBJECT-TYPE
   SYNTAX      INTEGER
               {
               discard (0),
               accept (1),
               tag (2)
               }
   MAX-ACCESS  read-write
   STATUS      current
   DESCRIPTION
      "Path: efm.editConf.vlanTagging.untagged.action

       Possibilities:
               discard   (0)
               accept   (1)
               tag   (2)"
   ::= {er1646v2XEfmVlanTaggingEntry 671088640}

er1646v2XEfmVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.untagged.tagInfo.tpid

       Possibilities:
               dot1Q   (33024)
               dot1ad   (34984)
               0x9100   (37120)
               0x9200   (37376)
               0x9300   (37632)"
   ::= {er1646v2XEfmVlanTaggingEntry 746586112}

er1646v2XEfmVlanTaggingUntaggedTagInfoVid OBJECT-TYPE
   SYNTAX      Integer32
   MAX-ACCESS  read-write
   STATUS      current
   DESCRIPTION
      "Path: efm.editConf.vlanTagging.untagged.tagInfo.vid"
   ::= {er1646v2XEfmVlanTaggingEntry 754974720}

er1646v2XEfmVlanTaggingUnknownVlansAction OBJECT-TYPE
   SYNTAX      INTEGER
               {
               discard (0),
               accept (1),
               tag (2)
               }
   MAX-ACCESS  read-write
   STATUS      current
   DESCRIPTION
      "Path: efm.editConf.vlanTagging.unknownVlans.action

       Possibilities:
               discard   (0)
               accept   (1)
               tag   (2)"
   ::= {er1646v2XEfmVlanTaggingEntry 1744830464}

er1646v2XEfmVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.unknownVlans.tagInfo.tpid

       Possibilities:
               dot1Q   (33024)
               dot1ad   (34984)
               0x9100   (37120)
               0x9200   (37376)
               0x9300   (37632)"
   ::= {er1646v2XEfmVlanTaggingEntry 1820327936}

er1646v2XEfmVlanTaggingUnknownVlansTagInfoVid OBJECT-TYPE
   SYNTAX      Integer32
   MAX-ACCESS  read-write
   STATUS      current
   DESCRIPTION
      "Path: efm.editConf.vlanTagging.unknownVlans.tagInfo.vid"
   ::= {er1646v2XEfmVlanTaggingEntry 1828716544}

er1646v2XEfmVlanTaggingVlans OBJECT-TYPE
   SYNTAX      SEQUENCE OF Er1646v2XEfmVlanTaggingVlansEntry
   MAX-ACCESS  not-accessible
   STATUS      current
   DESCRIPTION
      ""
   ::= {er1646v2XEfmVlanTagging 1073741824}

er1646v2XEfmVlanTaggingVlansEntry OBJECT-TYPE
   SYNTAX      Er1646v2XEfmVlanTaggingVlansEntry
   MAX-ACCESS  not-accessible
   STATUS      current
   DESCRIPTION
      ""
   INDEX      { er1646v2XEfmVlanTaggingVlansTableIx }
   ::= {er1646v2XEfmVlanTaggingVlans 1}

Er1646v2XEfmVlanTaggingVlansEntry ::=
   SEQUENCE
      {
      er1646v2XEfmVlanTaggingVlansActions
         VariableLengthTableActions,
      er1646v2XEfmVlanTaggingVlansTableIx
         TableIndex,
      er1646v2XEfmVlanTaggingVlansVid
         Integer32,
      er1646v2XEfmVlanTaggingVlansEndVid
         Integer32,
      er1646v2XEfmVlanTaggingVlansAction
         INTEGER,
      er1646v2XEfmVlanTaggingVlansTagInfoTpid
         INTEGER,
      er1646v2XEfmVlanTaggingVlansTagInfoVid
         Integer32
      }

er1646v2XEfmVlanTaggingVlansActions OBJECT-TYPE
   SYNTAX      VariableLengthTableActions
   MAX-ACCESS  read-write
   STATUS      current
   DESCRIPTION
      "By way of this field, some manipulations
       on this table may be performed."
   ::= {er1646v2XEfmVlanTaggingVlansEntry 2}

er1646v2XEfmVlanTaggingVlansTableIx OBJECT-TYPE
   SYNTAX      TableIndex
   MAX-ACCESS  not-accessible
   STATUS      current
   DESCRIPTION
      ""
   ::= {er1646v2XEfmVlanTaggingVlansEntry 11}

er1646v2XEfmVlanTaggingVlansVid OBJECT-TYPE
   SYNTAX      Integer32
   MAX-ACCESS  read-write
   STATUS      current
   DESCRIPTION
      "Path: efm.editConf.vlanTagging.vlans.vid"
   ::= {er1646v2XEfmVlanTaggingVlansEntry 536870912}

er1646v2XEfmVlanTaggingVlansEndVid OBJECT-TYPE
   SYNTAX      Integer32
   MAX-ACCESS  read-write
   STATUS      current
   DESCRIPTION
      "Path: efm.editConf.vlanTagging.vlans.endVid"
   ::= {er1646v2XEfmVlanTaggingVlansEntry 2147483648}

er1646v2XEfmVlanTaggingVlansAction OBJECT-TYPE
   SYNTAX      INTEGER
               {
               discard (0),
               accept (1),
               tag (2)
               }
   MAX-ACCESS  read-write
   STATUS      current
   DESCRIPTION
      "Path: efm.editConf.vlanTagging.vlans.action

       Possibilities:
               discard   (0)
               accept   (1)
               tag   (2)"
   ::= {er1646v2XEfmVlanTaggingVlansEntry 1073741824}

er1646v2XEfmVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.vlans.tagInfo.tpid

       Possibilities:
               dot1Q   (33024)
               dot1ad   (34984)
               0x9100   (37120)
               0x9200   (37376)
               0x9300   (37632)"
   ::= {er1646v2XEfmVlanTaggingVlansEntry 1677721600}

er1646v2XEfmVlanTaggingVlansTagInfoVid OBJECT-TYPE
   SYNTAX      Integer32
   MAX-ACCESS  read-write
   STATUS      current
   DESCRIPTION
      "Path: efm.editConf.vlanTagging.vlans.tagInfo.vid"
   ::= {er1646v2XEfmVlanTaggingVlansEntry 1744830464}


er1646v2XEfmOam OBJECT IDENTIFIER ::= {er1646v2XEfm 900}

er1646v2XEfmOamSSC OBJECT IDENTIFIER ::= {er1646v2XEfmOam 1}

er1646v2XEfmOamEntry OBJECT IDENTIFIER ::= {er1646v2XEfmOamSSC 1}

er1646v2XEfmOamMode OBJECT-TYPE
   SYNTAX      INTEGER
               {
               disabled (0),
               passive (3),
               active (2)
               }
   MAX-ACCESS  read-write
   STATUS      current
   DESCRIPTION
      "Path: efm.editConf.oam.mode

       Possibilities:
               disabled   (0)
               passive   (3)
               active   (2)"
   ::= {er1646v2XEfmOamEntry 16777216}

er1646v2XEfmOamLpbkLocalParAction OBJECT-TYPE
   SYNTAX      INTEGER
               {
               discard (0),
               forward (1)
               }
   MAX-ACCESS  read-write
   STATUS      current
   DESCRIPTION
      "Path: efm.editConf.oam.loopbackLocalParserAction

       Possibilities:
               discard   (0)
               forward   (1)"
   ::= {er1646v2XEfmOamEntry 33554432}

er1646v2XEfmOamLpbkSwapMacAddr OBJECT-TYPE
   SYNTAX      INTEGER
               {
               disabled (0),
               enabled (1)
               }
   MAX-ACCESS  read-write
   STATUS      current
   DESCRIPTION
      "Path: efm.editConf.oam.loopbackSwapMacAddresses

       Possibilities:
               disabled   (0)
               enabled   (1)"
   ::= {er1646v2XEfmOamEntry 50331648}

er1646v2XEfmOamLoopbackIgnoreRx OBJECT-TYPE
   SYNTAX      INTEGER
               {
               no (0),
               yes (1)
               }
   MAX-ACCESS  read-write
   STATUS      current
   DESCRIPTION
      "Path: efm.editConf.oam.loopbackIgnoreRx

       Possibilities:
               no   (0)
               yes   (1)"
   ::= {er1646v2XEfmOamEntry 67108864}

er1646v2XEfmOamEventsErroredSymbolEnabled OBJECT-TYPE
   SYNTAX      INTEGER
               {
               no (0),
               yes (1)
               }
   MAX-ACCESS  read-write
   STATUS      current
   DESCRIPTION
      "Path: efm.editConf.oam.events.erroredSymbol.enabled

       Possibilities:
               no   (0)
               yes   (1)"
   ::= {er1646v2XEfmOamEntry 83951872}

er1646v2XEfmOamEventsErroredSymbolWindowHi OBJECT-TYPE
   SYNTAX      INTEGER
               {
               default (0)
               }
   UNITS       "symbols"
   MAX-ACCESS  read-write
   STATUS      current
   DESCRIPTION
      "Path: efm.editConf.oam.events.erroredSymbol.windowHi

       unit name = symbols

       Possibilities:
               default   (0)"
   ::= {er1646v2XEfmOamEntry 83952128}

er1646v2XEfmOamEventsErroredSymbolWindowLo OBJECT-TYPE
   SYNTAX      INTEGER
               {
               default (0)
               }
   UNITS       "symbols"
   MAX-ACCESS  read-write
   STATUS      current
   DESCRIPTION
      "Path: efm.editConf.oam.events.erroredSymbol.windowLo

       unit name = symbols

       Possibilities:
               default   (0)"
   ::= {er1646v2XEfmOamEntry 83952384}

er1646v2XEfmOamEventsErroredSymbolThresholdHi OBJECT-TYPE
   SYNTAX      Integer32
   UNITS       "symbols"
   MAX-ACCESS  read-write
   STATUS      current
   DESCRIPTION
      "Path: efm.editConf.oam.events.erroredSymbol.thresholdHi

       unit name = symbols"
   ::= {er1646v2XEfmOamEntry 83952640}

er1646v2XEfmOamEventsErroredSymbolThresholdLo OBJECT-TYPE
   SYNTAX      Integer32
   UNITS       "symbols"
   MAX-ACCESS  read-write
   STATUS      current
   DESCRIPTION
      "Path: efm.editConf.oam.events.erroredSymbol.thresholdLo

       unit name = symbols"
   ::= {er1646v2XEfmOamEntry 83952896}

er1646v2XEfmOamEventsErroredFramePeriodEnabled OBJECT-TYPE
   SYNTAX      INTEGER
               {
               no (0),
               yes (1)
               }
   MAX-ACCESS  read-write
   STATUS      current
   DESCRIPTION
      "Path: efm.editConf.oam.events.erroredFramePeriod.enabled

       Possibilities:
               no   (0)
               yes   (1)"
   ::= {er1646v2XEfmOamEntry 84017408}

er1646v2XEfmOamEventsErroredFramePeriodWindow OBJECT-TYPE
   SYNTAX      INTEGER
               {
               default (0)
               }
   UNITS       "frames"
   MAX-ACCESS  read-write
   STATUS      current
   DESCRIPTION
      "Path: efm.editConf.oam.events.erroredFramePeriod.window

       unit name = frames

       Possibilities:
               default   (0)"
   ::= {er1646v2XEfmOamEntry 84017664}

er1646v2XEfmOamEventsErroredFramePeriodThreshold OBJECT-TYPE
   SYNTAX      Integer32
   UNITS       "frames"
   MAX-ACCESS  read-write
   STATUS      current
   DESCRIPTION
      "Path: efm.editConf.oam.events.erroredFramePeriod.threshold

       unit name = frames"
   ::= {er1646v2XEfmOamEntry 84017920}

er1646v2XEfmOamEventsErroredFrameEnabled OBJECT-TYPE
   SYNTAX      INTEGER
               {
               no (0),
               yes (1)
               }
   MAX-ACCESS  read-write
   STATUS      current
   DESCRIPTION
      "Path: efm.editConf.oam.events.erroredFrame.enabled

       Possibilities:
               no   (0)
               yes   (1)"
   ::= {er1646v2XEfmOamEntry 84082944}

er1646v2XEfmOamEventsErroredFrameWindow OBJECT-TYPE
   SYNTAX      Integer32
   UNITS       "100msec"
   MAX-ACCESS  read-write
   STATUS      current
   DESCRIPTION
      "Path: efm.editConf.oam.events.erroredFrame.window

       unit name = 100msec"
   ::= {er1646v2XEfmOamEntry 84083200}

er1646v2XEfmOamEventsErroredFrameThreshold OBJECT-TYPE
   SYNTAX      Integer32
   UNITS       "frames"
   MAX-ACCESS  read-write
   STATUS      current
   DESCRIPTION
      "Path: efm.editConf.oam.events.erroredFrame.threshold

       unit name = frames"
   ::= {er1646v2XEfmOamEntry 84083456}

er1646v2XEfmOamEventsErroredFrameSecondsEnabled OBJECT-TYPE
   SYNTAX      INTEGER
               {
               no (0),
               yes (1)
               }
   MAX-ACCESS  read-write
   STATUS      current
   DESCRIPTION
      "Path: efm.editConf.oam.events.erroredFrameSeconds.enabled

       Possibilities:
               no   (0)
               yes   (1)"
   ::= {er1646v2XEfmOamEntry 84148480}

er1646v2XEfmOamEventsErroredFrameSecondsWindow OBJECT-TYPE
   SYNTAX      Integer32
   UNITS       "100msec"
   MAX-ACCESS  read-write
   STATUS      current
   DESCRIPTION
      "Path: efm.editConf.oam.events.erroredFrameSeconds.window

       unit name = 100msec"
   ::= {er1646v2XEfmOamEntry 84148736}

er1646v2XEfmOamEventsErroredFrameSecondsThreshold OBJECT-TYPE
   SYNTAX      Integer32
   UNITS       "frames"
   MAX-ACCESS  read-write
   STATUS      current
   DESCRIPTION
      "Path: efm.editConf.oam.events.erroredFrameSeconds.threshold

       unit name = frames"
   ::= {er1646v2XEfmOamEntry 84148992}

er1646v2XEfmOamEventsDyingGasp OBJECT-TYPE
   SYNTAX      INTEGER
               {
               disabled (0),
               enabled (1)
               }
   MAX-ACCESS  read-write
   STATUS      current
   DESCRIPTION
      "Path: efm.editConf.oam.events.dyingGasp

       Possibilities:
               disabled   (0)
               enabled   (1)"
   ::= {er1646v2XEfmOamEntry 84213760}

er1646v2XEfmOamEventsCriticalEvent OBJECT-TYPE
   SYNTAX      INTEGER
               {
               disabled (0),
               enabled (1)
               }
   MAX-ACCESS  read-write
   STATUS      current
   DESCRIPTION
      "Path: efm.editConf.oam.events.criticalEvent

       Possibilities:
               disabled   (0)
               enabled   (1)"
   ::= {er1646v2XEfmOamEntry 84279296}


er1646v2XEfmIp OBJECT IDENTIFIER ::= {er1646v2XEfm 1}

er1646v2XEfmIpSSC OBJECT IDENTIFIER ::= {er1646v2XEfmIp 1}

er1646v2XEfmIpEntry OBJECT IDENTIFIER ::= {er1646v2XEfmIpSSC 1}

er1646v2XEfmIpVrfRouter OBJECT-TYPE
   SYNTAX      DisplayString
   MAX-ACCESS  read-write
   STATUS      current
   DESCRIPTION
      "Path: efm.editConf.ip.vrfRouter"
   ::= {er1646v2XEfmIpEntry 738197504}

er1646v2XEfmIpAdr OBJECT-TYPE
   SYNTAX      IpAddress
   MAX-ACCESS  read-write
   STATUS      current
   DESCRIPTION
      "Path: efm.editConf.ip.address"
   ::= {er1646v2XEfmIpEntry 2030043136}

er1646v2XEfmIpNetm OBJECT-TYPE
   SYNTAX      IpAddress
   MAX-ACCESS  read-write
   STATUS      current
   DESCRIPTION
      "Path: efm.editConf.ip.netMask"
   ::= {er1646v2XEfmIpEntry 2063597568}

er1646v2XEfmIpSNetName OBJECT-TYPE
   SYNTAX      INTEGER
               {
               slOPTg (0),
               corp (2),
               dmz (3),
               internet (1)
               }
   MAX-ACCESS  read-write
   STATUS      current
   DESCRIPTION
      "Path: efm.editConf.ip.sNet.name

       Possibilities:
               <OPT>   (0)
               corp   (2)
               dmz   (3)
               internet   (1)"
   ::= {er1646v2XEfmIpEntry 855703552}

er1646v2XEfmIpSNetCust OBJECT-TYPE
   SYNTAX      DisplayString
   MAX-ACCESS  read-write
   STATUS      current
   DESCRIPTION
      "Path: efm.editConf.ip.sNet.custom"
   ::= {er1646v2XEfmIpEntry 855769088}

er1646v2XEfmIpDhcpC OBJECT-TYPE
   SYNTAX      INTEGER
               {
               disabled (0),
               enabled (1)
               }
   MAX-ACCESS  read-write
   STATUS      current
   DESCRIPTION
      "Path: efm.editConf.ip.dhcpClient

       Possibilities:
               disabled   (0)
               enabled   (1)"
   ::= {er1646v2XEfmIpEntry 838860800}

er1646v2XEfmIpDhcpGatewayPreference OBJECT-TYPE
   SYNTAX      Integer32
   MAX-ACCESS  read-write
   STATUS      current
   DESCRIPTION
      "Path: efm.editConf.ip.dhcp.gatewayPreference"
   ::= {er1646v2XEfmIpEntry 872480768}

er1646v2XEfmIpDhcpRoutePreference OBJECT-TYPE
   SYNTAX      Integer32
   MAX-ACCESS  read-write
   STATUS      current
   DESCRIPTION
      "Path: efm.editConf.ip.dhcp.routePreference"
   ::= {er1646v2XEfmIpEntry 872546304}

er1646v2XEfmIpDhcpDnsPreference OBJECT-TYPE
   SYNTAX      Integer32
   MAX-ACCESS  read-write
   STATUS      current
   DESCRIPTION
      "Path: efm.editConf.ip.dhcp.dnsPreference"
   ::= {er1646v2XEfmIpEntry 872611840}

er1646v2XEfmIpMtu OBJECT-TYPE
   SYNTAX      Integer32
   MAX-ACCESS  read-write
   STATUS      current
   DESCRIPTION
      "Path: efm.editConf.ip.mtu"
   ::= {er1646v2XEfmIpEntry 671088640}

er1646v2XEfmIpMssAdjust OBJECT-TYPE
   SYNTAX      INTEGER
               {
               disabled (0),
               auto (65536)
               }
   MAX-ACCESS  read-write
   STATUS      current
   DESCRIPTION
      "Path: efm.editConf.ip.mssAdjust

       Possibilities:
               disabled   (0)
               auto   (65536)"
   ::= {er1646v2XEfmIpEntry 754974720}

er1646v2XEfmIpRipMetric OBJECT-TYPE
   SYNTAX      Integer32
   MAX-ACCESS  read-write
   STATUS      current
   DESCRIPTION
      "Path: efm.editConf.ip.rip.metric"
   ::= {er1646v2XEfmIpEntry 353566720}

er1646v2XEfmIpRipMetricOut OBJECT-TYPE
   SYNTAX      Integer32
   MAX-ACCESS  read-write
   STATUS      current
   DESCRIPTION
      "Path: efm.editConf.ip.rip.metricOut"
   ::= {er1646v2XEfmIpEntry 353632256}

er1646v2XEfmIpRipMode OBJECT-TYPE
   SYNTAX      INTEGER
               {
               disabled (0),
               passive (1),
               active (2)
               }
   MAX-ACCESS  read-write
   STATUS      current
   DESCRIPTION
      "Path: efm.editConf.ip.rip.mode

       Possibilities:
               disabled   (0)
               passive   (1)
               active   (2)"
   ::= {er1646v2XEfmIpEntry 353697792}

er1646v2XEfmIpRipTxVer OBJECT-TYPE
   SYNTAX      INTEGER
               {
               rip1 (0),
               rip2 (1),
               rip1mcompatible (2)
               }
   MAX-ACCESS  read-write
   STATUS      current
   DESCRIPTION
      "Path: efm.editConf.ip.rip.txVersion

       Possibilities:
               rip1   (0)
               rip2   (1)
               rip1-compatible   (2)"
   ::= {er1646v2XEfmIpEntry 354615296}

er1646v2XEfmIpRipRxVer OBJECT-TYPE
   SYNTAX      INTEGER
               {
               rip1only (0),
               rip2only (1),
               rip12 (2)
               }
   MAX-ACCESS  read-write
   STATUS      current
   DESCRIPTION
      "Path: efm.editConf.ip.rip.rxVersion

       Possibilities:
               rip1only   (0)
               rip2only   (1)
               rip1&2   (2)"
   ::= {er1646v2XEfmIpEntry 354680832}

er1646v2XEfmIpRipSplitH OBJECT-TYPE
   SYNTAX      INTEGER
               {
               disabled (0),
               enabled (1),
               poisonedReverse (2)
               }
   MAX-ACCESS  read-write
   STATUS      current
   DESCRIPTION
      "Path: efm.editConf.ip.rip.splitHorizon

       Possibilities:
               disabled   (0)
               enabled   (1)
               poisonedReverse   (2)"
   ::= {er1646v2XEfmIpEntry 353828864}

er1646v2XEfmIpRipAuth OBJECT-TYPE
   SYNTAX      INTEGER
               {
               disabled (0),
               texts (1),
               md5 (2)
               }
   MAX-ACCESS  read-write
   STATUS      current
   DESCRIPTION
      "Path: efm.editConf.ip.rip.authentication

       Possibilities:
               disabled   (0)
               text    (1)
               md5   (2)"
   ::= {er1646v2XEfmIpEntry 353501184}

er1646v2XEfmIpRipFilter OBJECT-TYPE
   SYNTAX      DisplayString
   MAX-ACCESS  read-write
   STATUS      current
   DESCRIPTION
      "Path: efm.editConf.ip.rip.filter"
   ::= {er1646v2XEfmIpEntry 354418688}

er1646v2XEfmIpRipFilterIn OBJECT-TYPE
   SYNTAX      DisplayString
   MAX-ACCESS  read-write
   STATUS      current
   DESCRIPTION
      "Path: efm.editConf.ip.rip.filterIn"
   ::= {er1646v2XEfmIpEntry 354484224}

er1646v2XEfmIpRipClearNextHop OBJECT-TYPE
   SYNTAX      INTEGER
               {
               disabled (0),
               enabled (1)
               }
   MAX-ACCESS  read-write
   STATUS      current
   DESCRIPTION
      "Path: efm.editConf.ip.rip.clearNextHop

       Possibilities:
               disabled   (0)
               enabled   (1)"
   ::= {er1646v2XEfmIpEntry 352452608}

er1646v2XEfmIpAccPol OBJECT-TYPE
   SYNTAX      DisplayString
   MAX-ACCESS  read-write
   STATUS      current
   DESCRIPTION
      "Path: efm.editConf.ip.accessPolicy"
   ::= {er1646v2XEfmIpEntry 704643072}

er1646v2XEfmIpAB OBJECT-TYPE
   SYNTAX      DisplayString
   MAX-ACCESS  read-write
   STATUS      current
   DESCRIPTION
      "Path: efm.editConf.ip.trafficPolicy"
   ::= {er1646v2XEfmIpEntry 234881024}

er1646v2XEfmIpMA OBJECT-TYPE
   SYNTAX      INTEGER
               {
               disabled (0),
               enabled (1)
               }
   MAX-ACCESS  read-write
   STATUS      current
   DESCRIPTION
      "Path: efm.editConf.ip.mgmtAccess

       Possibilities:
               disabled   (0)
               enabled   (1)"
   ::= {er1646v2XEfmIpEntry 268435456}

er1646v2XEfmIpMF OBJECT-TYPE
   SYNTAX      Integer32
   MAX-ACCESS  read-write
   STATUS      current
   DESCRIPTION
      "Path: efm.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2XEfmIpEntry 285212672}

er1646v2XEfmIpDB OBJECT-TYPE
   SYNTAX      INTEGER
               {
               disabled (0),
               enabled (1)
               }
   MAX-ACCESS  read-write
   STATUS      current
   DESCRIPTION
      "Path: efm.editConf.ip.directedBroadcasts

       Possibilities:
               disabled   (0)
               enabled   (1)"
   ::= {er1646v2XEfmIpEntry 369098752}

er1646v2XEfmIpIR OBJECT-TYPE
   SYNTAX      INTEGER
               {
               disabled (0),
               enabled (1)
               }
   MAX-ACCESS  read-write
   STATUS      current
   DESCRIPTION
      "Path: efm.editConf.ip.icmpRedirects

       Possibilities:
               disabled   (0)
               enabled   (1)"
   ::= {er1646v2XEfmIpEntry 436207616}

er1646v2XEfmIpIgmp OBJECT-TYPE
   SYNTAX      INTEGER
               {
               disabled (0),
               proxy (1),
               router (2),
               v3Router (5)
               }
   MAX-ACCESS  read-write
   STATUS      current
   DESCRIPTION
      "Path: efm.editConf.ip.igmp

       Possibilities:
               disabled   (0)
               proxy   (1)
               router   (2)
               v3Router   (5)"
   ::= {er1646v2XEfmIpEntry 536870912}

er1646v2XEfmIpNN OBJECT-TYPE
   SYNTAX      DisplayString
   MAX-ACCESS  read-write
   STATUS      current
   DESCRIPTION
      "Path: efm.editConf.ip.nat"
   ::= {er1646v2XEfmIpEntry 452984832}

er1646v2XEfmIpVrrp OBJECT-TYPE
   SYNTAX      INTEGER
               {
               disabled (0),
               enabled (1)
               }
   MAX-ACCESS  read-write
   STATUS      current
   DESCRIPTION
      "Path: efm.editConf.ip.vrrp

       Possibilities:
               disabled   (0)
               enabled   (1)"
   ::= {er1646v2XEfmIpEntry 721420288}

er1646v2XEfmIpPimMode OBJECT-TYPE
   SYNTAX      INTEGER
               {
               disabled (0),
               sparse (1),
               passive (2)
               }
   MAX-ACCESS  read-write
   STATUS      current
   DESCRIPTION
      "Path: efm.editConf.ip.pim.mode

       Possibilities:
               disabled   (0)
               sparse   (1)
               passive   (2)"
   ::= {er1646v2XEfmIpEntry 771817472}

er1646v2XEfmIpPimDrPriority OBJECT-TYPE
   SYNTAX      Counter32
   MAX-ACCESS  read-write
   STATUS      current
   DESCRIPTION
      "Path: efm.editConf.ip.pim.drPriority

       32 bit unsigned wrappable counter."
   ::= {er1646v2XEfmIpEntry 771883008}

er1646v2XEfmIpPimHelloTime OBJECT-TYPE
   SYNTAX      TimeTicks
   MAX-ACCESS  read-write
   STATUS      current
   DESCRIPTION
      "Path: efm.editConf.ip.pim.helloTime

       Time in centi-second."
   ::= {er1646v2XEfmIpEntry 771948544}

er1646v2XEfmIpPimPropagationDelay OBJECT-TYPE
   SYNTAX      TimeTicks
   MAX-ACCESS  read-write
   STATUS      current
   DESCRIPTION
      "Path: efm.editConf.ip.pim.propagationDelay

       Time in centi-second."
   ::= {er1646v2XEfmIpEntry 772014080}

er1646v2XEfmIpPimOverrideInterval OBJECT-TYPE
   SYNTAX      TimeTicks
   MAX-ACCESS  read-write
   STATUS      current
   DESCRIPTION
      "Path: efm.editConf.ip.pim.overrideInterval

       Time in centi-second."
   ::= {er1646v2XEfmIpEntry 772079616}

er1646v2XEfmIpPimBsrBorder OBJECT-TYPE
   SYNTAX      INTEGER
               {
               disabled (0),
               enabled (1)
               }
   MAX-ACCESS  read-write
   STATUS      current
   DESCRIPTION
      "Path: efm.editConf.ip.pim.bsrBorder

       Possibilities:
               disabled   (0)
               enabled   (1)"
   ::= {er1646v2XEfmIpEntry 772145152}

er1646v2XEfmIpPimTtlThreshold OBJECT-TYPE
   SYNTAX      Integer32
   MAX-ACCESS  read-write
   STATUS      current
   DESCRIPTION
      "Path: efm.editConf.ip.pim.ttlThreshold"
   ::= {er1646v2XEfmIpEntry 772210688}

er1646v2XEfmIpIMNetworkUnreachable OBJECT-TYPE
   SYNTAX      INTEGER
               {
               disabled (0),
               enabled (1)
               }
   MAX-ACCESS  read-write
   STATUS      current
   DESCRIPTION
      "Path: efm.editConf.ip.icmpMessages.networkUnreachable

       Possibilities:
               disabled   (0)
               enabled   (1)"
   ::= {er1646v2XEfmIpEntry 788594688}

er1646v2XEfmIpIMHostUnreachable OBJECT-TYPE
   SYNTAX      INTEGER
               {
               disabled (0),
               enabled (1)
               }
   MAX-ACCESS  read-write
   STATUS      current
   DESCRIPTION
      "Path: efm.editConf.ip.icmpMessages.hostUnreachable

       Possibilities:
               disabled   (0)
               enabled   (1)"
   ::= {er1646v2XEfmIpEntry 788660224}

er1646v2XEfmIpIMProtocolUnreachable OBJECT-TYPE
   SYNTAX      INTEGER
               {
               disabled (0),
               enabled (1)
               }
   MAX-ACCESS  read-write
   STATUS      current
   DESCRIPTION
      "Path: efm.editConf.ip.icmpMessages.protocolUnreachable

       Possibilities:
               disabled   (0)
               enabled   (1)"
   ::= {er1646v2XEfmIpEntry 788725760}

er1646v2XEfmIpIMPortUnreachable OBJECT-TYPE
   SYNTAX      INTEGER
               {
               disabled (0),
               enabled (1)
               }
   MAX-ACCESS  read-write
   STATUS      current
   DESCRIPTION
      "Path: efm.editConf.ip.icmpMessages.portUnreachable

       Possibilities:
               disabled   (0)
               enabled   (1)"
   ::= {er1646v2XEfmIpEntry 788791296}

er1646v2XEfmIpIMMtuExceeded OBJECT-TYPE
   SYNTAX      INTEGER
               {
               disabled (0),
               enabled (1)
               }
   MAX-ACCESS  read-write
   STATUS      current
   DESCRIPTION
      "Path: efm.editConf.ip.icmpMessages.mtuExceeded

       Possibilities:
               disabled   (0)
               enabled   (1)"
   ::= {er1646v2XEfmIpEntry 788856832}

er1646v2XEfmIpIMAdminProhibited OBJECT-TYPE
   SYNTAX      INTEGER
               {
               disabled (0),
               enabled (1)
               }
   MAX-ACCESS  read-write
   STATUS      current
   DESCRIPTION
      "Path: efm.editConf.ip.icmpMessages.adminProhibited

       Possibilities:
               disabled   (0)
               enabled   (1)"
   ::= {er1646v2XEfmIpEntry 788922368}

er1646v2XEfmIpIMTtlExceeded OBJECT-TYPE
   SYNTAX      INTEGER
               {
               disabled (0),
               enabled (1)
               }
   MAX-ACCESS  read-write
   STATUS      current
   DESCRIPTION
      "Path: efm.editConf.ip.icmpMessages.ttlExceeded

       Possibilities:
               disabled   (0)
               enabled   (1)"
   ::= {er1646v2XEfmIpEntry 788987904}

er1646v2XEfmIpIMRedirect OBJECT-TYPE
   SYNTAX      INTEGER
               {
               disabled (0),
               enabled (1)
               }
   MAX-ACCESS  read-write
   STATUS      current
   DESCRIPTION
      "Path: efm.editConf.ip.icmpMessages.redirect

       Possibilities:
               disabled   (0)
               enabled   (1)"
   ::= {er1646v2XEfmIpEntry 789053440}

er1646v2XEfmIpSaddr OBJECT-TYPE
   SYNTAX      SEQUENCE OF Er1646v2XEfmIpSaddrEntry
   MAX-ACCESS  not-accessible
   STATUS      current
   DESCRIPTION
      ""
   ::= {er1646v2XEfmIp 385875968}

er1646v2XEfmIpSaddrEntry OBJECT-TYPE
   SYNTAX      Er1646v2XEfmIpSaddrEntry
   MAX-ACCESS  not-accessible
   STATUS      current
   DESCRIPTION
      ""
   INDEX      { er1646v2XEfmIpSaddrTableIx }
   ::= {er1646v2XEfmIpSaddr 1}

Er1646v2XEfmIpSaddrEntry ::=
   SEQUENCE
      {
      er1646v2XEfmIpSaddrActions
         VariableLengthTableActions,
      er1646v2XEfmIpSaddrTableIx
         TableIndex,
      er1646v2XEfmIpSaddrAddress
         IpAddress,
      er1646v2XEfmIpSaddrNetMask
         IpAddress
      }

er1646v2XEfmIpSaddrActions OBJECT-TYPE
   SYNTAX      VariableLengthTableActions
   MAX-ACCESS  read-write
   STATUS      current
   DESCRIPTION
      "By way of this field, some manipulations
       on this table may be performed."
   ::= {er1646v2XEfmIpSaddrEntry 2}

er1646v2XEfmIpSaddrTableIx OBJECT-TYPE
   SYNTAX      TableIndex
   MAX-ACCESS  not-accessible
   STATUS      current
   DESCRIPTION
      ""
   ::= {er1646v2XEfmIpSaddrEntry 11}

er1646v2XEfmIpSaddrAddress OBJECT-TYPE
   SYNTAX      IpAddress
   MAX-ACCESS  read-write
   STATUS      current
   DESCRIPTION
      "Path: efm.editConf.ip.secondaryIp.address"
   ::= {er1646v2XEfmIpSaddrEntry 2030043136}

er1646v2XEfmIpSaddrNetMask OBJECT-TYPE
   SYNTAX      IpAddress
   MAX-ACCESS  read-write
   STATUS      current
   DESCRIPTION
      "Path: efm.editConf.ip.secondaryIp.netMask"
   ::= {er1646v2XEfmIpSaddrEntry 2063597568}

er1646v2XEfmIpH OBJECT-TYPE
   SYNTAX      SEQUENCE OF Er1646v2XEfmIpHEntry
   MAX-ACCESS  not-accessible
   STATUS      current
   DESCRIPTION
      ""
   ::= {er1646v2XEfmIp 251658240}

er1646v2XEfmIpHEntry OBJECT-TYPE
   SYNTAX      Er1646v2XEfmIpHEntry
   MAX-ACCESS  not-accessible
   STATUS      current
   DESCRIPTION
      ""
   INDEX      { er1646v2XEfmIpHTableIx }
   ::= {er1646v2XEfmIpH 1}

Er1646v2XEfmIpHEntry ::=
   SEQUENCE
      {
      er1646v2XEfmIpHActions
         VariableLengthTableActions,
      er1646v2XEfmIpHTableIx
         TableIndex,
      er1646v2XEfmIpHAddress
         IpAddress,
      er1646v2XEfmIpHDhcpRelayOptionSubscriberId
         DisplayString
      }

er1646v2XEfmIpHActions OBJECT-TYPE
   SYNTAX      VariableLengthTableActions
   MAX-ACCESS  read-write
   STATUS      current
   DESCRIPTION
      "By way of this field, some manipulations
       on this table may be performed."
   ::= {er1646v2XEfmIpHEntry 2}

er1646v2XEfmIpHTableIx OBJECT-TYPE
   SYNTAX      TableIndex
   MAX-ACCESS  not-accessible
   STATUS      current
   DESCRIPTION
      ""
   ::= {er1646v2XEfmIpHEntry 11}

er1646v2XEfmIpHAddress OBJECT-TYPE
   SYNTAX      IpAddress
   MAX-ACCESS  read-write
   STATUS      current
   DESCRIPTION
      "Path: efm.editConf.ip.helpers.address"
   ::= {er1646v2XEfmIpHEntry 16777216}

er1646v2XEfmIpHDhcpRelayOptionSubscriberId OBJECT-TYPE
   SYNTAX      DisplayString
   MAX-ACCESS  read-write
   STATUS      current
   DESCRIPTION
      "Path: efm.editConf.ip.helpers.dhcpRelayOption.subscriberId"
   ::= {er1646v2XEfmIpHEntry 33947648}


er1646v2XEfmVlan OBJECT IDENTIFIER ::= {er1646v2XEfm 33}

er1646v2XEfmVlanSSCTable OBJECT-TYPE
   SYNTAX      SEQUENCE OF Er1646v2XEfmVlanEntry
   MAX-ACCESS  not-accessible
   STATUS      current
   DESCRIPTION
      ""
   ::= {er1646v2XEfmVlan 1}

er1646v2XEfmVlanEntry OBJECT-TYPE
   SYNTAX      Er1646v2XEfmVlanEntry
   MAX-ACCESS  not-accessible
   STATUS      current
   DESCRIPTION
      ""
   INDEX      { er1646v2XEfmVlanTableIx }
   ::= {er1646v2XEfmVlanSSCTable 1}

Er1646v2XEfmVlanEntry ::=
   SEQUENCE
      {
      er1646v2XEfmVlanActions
         VariableLengthTableActions,
      er1646v2XEfmVlanTableIx
         TableIndex,
      er1646v2XEfmVlanName
         DisplayString,
      er1646v2XEfmVlanRemark
         DisplayString,
      er1646v2XEfmVlanAdminStatus
         INTEGER,
      er1646v2XEfmVlanMode
         INTEGER,
      er1646v2XEfmVlanPriorityPolicy
         DisplayString,
      er1646v2XEfmVlanIpVrfRouter
         DisplayString,
      er1646v2XEfmVlanIpAdr
         IpAddress,
      er1646v2XEfmVlanIpNetm
         IpAddress,
      er1646v2XEfmVlanIpSNetName
         INTEGER,
      er1646v2XEfmVlanIpSNetCust
         DisplayString,
      er1646v2XEfmVlanIpDhcpC
         INTEGER,
      er1646v2XEfmVlanIpDhcpGatewayPreference
         Integer32,
      er1646v2XEfmVlanIpDhcpRoutePreference
         Integer32,
      er1646v2XEfmVlanIpDhcpDnsPreference
         Integer32,
      er1646v2XEfmVlanIpMtu
         Integer32,
      er1646v2XEfmVlanIpMssAdjust
         INTEGER,
      er1646v2XEfmVlanIpRipMetric
         Integer32,
      er1646v2XEfmVlanIpRipMetricOut
         Integer32,
      er1646v2XEfmVlanIpRipMode
         INTEGER,
      er1646v2XEfmVlanIpRipTxVer
         INTEGER,
      er1646v2XEfmVlanIpRipRxVer
         INTEGER,
      er1646v2XEfmVlanIpRipSplitH
         INTEGER,
      er1646v2XEfmVlanIpRipAuth
         INTEGER,
      er1646v2XEfmVlanIpRipFilter
         DisplayString,
      er1646v2XEfmVlanIpRipFilterIn
         DisplayString,
      er1646v2XEfmVlanIpRipClearNextHop
         INTEGER,
      er1646v2XEfmVlanIpAccPol
         DisplayString,
      er1646v2XEfmVlanIpAB
         DisplayString,
      er1646v2XEfmVlanIpMA
         INTEGER,
      er1646v2XEfmVlanIpMF
         Integer32,
      er1646v2XEfmVlanIpDB
         INTEGER,
      er1646v2XEfmVlanIpIR
         INTEGER,
      er1646v2XEfmVlanIpIgmp
         INTEGER,
      er1646v2XEfmVlanIpNN
         DisplayString,
      er1646v2XEfmVlanIpVrrp
         INTEGER,
      er1646v2XEfmVlanIpPimMode
         INTEGER,
      er1646v2XEfmVlanIpPimDrPriority
         Counter32,
      er1646v2XEfmVlanIpPimHelloTime
         TimeTicks,
      er1646v2XEfmVlanIpPimPropagationDelay
         TimeTicks,
      er1646v2XEfmVlanIpPimOverrideInterval
         TimeTicks,
      er1646v2XEfmVlanIpPimBsrBorder
         INTEGER,
      er1646v2XEfmVlanIpPimTtlThreshold
         Integer32,
      er1646v2XEfmVlanIpIMNetworkUnreachable
         INTEGER,
      er1646v2XEfmVlanIpIMHostUnreachable
         INTEGER,
      er1646v2XEfmVlanIpIMProtocolUnreachable
         INTEGER,
      er1646v2XEfmVlanIpIMPortUnreachable
         INTEGER,
      er1646v2XEfmVlanIpIMMtuExceeded
         INTEGER,
      er1646v2XEfmVlanIpIMAdminProhibited
         INTEGER,
      er1646v2XEfmVlanIpIMTtlExceeded
         INTEGER,
      er1646v2XEfmVlanIpIMRedirect
         INTEGER,
      er1646v2XEfmVlanIpV6VrfRouter
         DisplayString,
      er1646v2XEfmVlanIpV6AddrAutoConfigNrDupAddrDetects
         Integer32,
      er1646v2XEfmVlanIpV6AddrAutoConfigAcceptRa
         INTEGER,
      er1646v2XEfmVlanIpV6AddrAutoConfigAcceptRaRdnss
         INTEGER,
      er1646v2XEfmVlanIpV6AddrAutoConfigAcceptRaDnssl
         INTEGER,
      er1646v2XEfmVlanIpV6DefaultRoute
         INTEGER,
      er1646v2XEfmVlanIpV6RaSend
         INTEGER,
      er1646v2XEfmVlanIpV6RaMinInterval
         TimeTicks,
      er1646v2XEfmVlanIpV6RaMaxInterval
         TimeTicks,
      er1646v2XEfmVlanIpV6RaManagedFlag
         INTEGER,
      er1646v2XEfmVlanIpV6RaOtherConfFlag
         INTEGER,
      er1646v2XEfmVlanIpV6RaLinkMtu
         Integer32,
      er1646v2XEfmVlanIpV6RaReachableTime
         TimeTicks,
      er1646v2XEfmVlanIpV6RaRetransmitTime
         TimeTicks,
      er1646v2XEfmVlanIpV6RaHopLimit
         Integer32,
      er1646v2XEfmVlanIpV6RaDefaultLifeTime
         TimeTicks,
      er1646v2XEfmVlanIpV6RaDnsOptionsRdnssLifeTime
         TimeTicks,
      er1646v2XEfmVlanIpV6RaDnsOptionsRdnssImportServers
         INTEGER,
      er1646v2XEfmVlanIpV6RaDnsOptionsDnsslLifeTime
         TimeTicks,
      er1646v2XEfmVlanIpV6RaDnsOptionsDnsslImportDomains
         INTEGER,
      er1646v2XEfmVlanIpV6RsSend
         INTEGER,
      er1646v2XEfmVlanIpV6RsMaxRandomDelay
         TimeTicks,
      er1646v2XEfmVlanIpV6RsInterval
         TimeTicks,
      er1646v2XEfmVlanIpV6RsMaxSolicitations
         Integer32,
      er1646v2XEfmVlanIpV6TrafficPolicyInbound
         DisplayString,
      er1646v2XEfmVlanIpV6TrafficPolicyOutbound
         DisplayString,
      er1646v2XEfmVlanIpV6FirewallZone
         DisplayString,
      er1646v2XEfmVlanIpV6DhcpClientAddrAC
         INTEGER,
      er1646v2XEfmVlanIpV6DhcpClientPrDelMode
         INTEGER,
      er1646v2XEfmVlanIpV6DhcpClientPrDelPool
         DisplayString,
      er1646v2XEfmVlanIpV6DhcpClientPrDelPdExclOpt
         INTEGER,
      er1646v2XEfmVlanIpV6DhcpClientDnsServerPref
         Integer32,
      er1646v2XEfmVlanIpV6DhcpClientRapidCommit
         INTEGER,
      er1646v2XEfmVlanIpV6DhcpClientTimersSolTimeOut
         TimeTicks,
      er1646v2XEfmVlanIpV6DhcpClientTimersSolMaxRt
         TimeTicks,
      er1646v2XEfmVlanIpV6DhcpClientTimersInfoRefresh
         TimeTicks,
      er1646v2XEfmVlanIpV6DhcpServerMode
         INTEGER,
      er1646v2XEfmVlanIpV6DhcpServerPreference
         Integer32,
      er1646v2XEfmVlanIpV6DhcpServerPool
         DisplayString,
      er1646v2XEfmVlanIpV6DhcpServerRapidCommit
         INTEGER,
      er1646v2XEfmVlanIpV6DhcpServerTimersInfoRefresh
         TimeTicks,
      er1646v2XEfmVlanIpV6DhcpRelayMode
         INTEGER,
      er1646v2XEfmVlanIpV6SendRedirect
         INTEGER,
      er1646v2XEfmVlanIpV6LinkMtu
         Integer32,
      er1646v2XEfmVlanIpV6InterfaceId
         OCTET STRING,
      er1646v2XEfmVlanIpV6MF
         Integer32,
      er1646v2XEfmVlanIpV6IcmpMessagesNoRoute
         INTEGER,
      er1646v2XEfmVlanIpV6IcmpMessagesBeyondScope
         INTEGER,
      er1646v2XEfmVlanIpV6IcmpMessagesAddressUnreachable
         INTEGER,
      er1646v2XEfmVlanIpV6IcmpMessagesPortUnreachable
         INTEGER,
      er1646v2XEfmVlanIpV6IcmpMessagesPacketTooBig
         INTEGER,
      er1646v2XEfmVlanIpV6IcmpMessagesHopLimitExceeded
         INTEGER,
      er1646v2XEfmVlanIpV6IcmpMessagesFragTimeExceeded
         INTEGER,
      er1646v2XEfmVlanIpV6IcmpMessagesHeaderFieldErr
         INTEGER,
      er1646v2XEfmVlanIpV6IcmpMessagesOptionUnrecognized
         INTEGER,
      er1646v2XEfmVlanIpV6IcmpMessagesRedirect
         INTEGER,
      er1646v2XEfmVlanBridgingAccList
         DisplayString,
      er1646v2XEfmVlanBridgingInACL
         DisplayString,
      er1646v2XEfmVlanBridgingTp
         DisplayString,
      er1646v2XEfmVlanBridgingBrGrp
         DisplayString,
      er1646v2XEfmVlanBridgingLimBC
         INTEGER,
      er1646v2XEfmVlanBridgingPrivateMode
         INTEGER,
      er1646v2XEfmVlanBridgingLearning
         INTEGER,
      er1646v2XEfmVlanBridgingMaxCacheSize
         INTEGER,
      er1646v2XEfmVlanBridgingRelearnDropOnRelearn
         INTEGER,
      er1646v2XEfmVlanBridgingRelearnShutdownThreshold
         Integer32,
      er1646v2XEfmVlanBridgingRelearnShutdownTime
         TimeTicks,
      er1646v2XEfmVlanBridgingRelearnLoopDetection
         INTEGER,
      er1646v2XEfmVlanBridgingRelearnLoopDetectionInterval
         TimeTicks,
      er1646v2XEfmVlanBridgingVlanMemberShip
         INTEGER,
      er1646v2XEfmVlanBridgingVlTUntaggedAction
         INTEGER,
      er1646v2XEfmVlanBridgingVlTUntaggedTagInfoTpid
         INTEGER,
      er1646v2XEfmVlanBridgingVlTUntaggedTagInfoVid
         Integer32,
      er1646v2XEfmVlanBridgingVlTUnknownVlansAction
         INTEGER,
      er1646v2XEfmVlanBridgingVlTUnknownVlansTagInfoTpid
         INTEGER,
      er1646v2XEfmVlanBridgingVlTUnknownVlansTagInfoVid
         Integer32,
      er1646v2XEfmVlanBridgingDot1adType
         INTEGER,
      er1646v2XEfmVlanBridgingPriority
         Integer32,
      er1646v2XEfmVlanBridgingPathCost
         Integer32,
      er1646v2XEfmVlanBridgingInternalPathCost
         Integer32,
      er1646v2XEfmVlanBridgingTCD
         INTEGER,
      er1646v2XEfmVlanBridgingRestrictedRole
         INTEGER,
      er1646v2XEfmVlanBridgingAdminEdge
         INTEGER,
      er1646v2XEfmVlanBridgingOamMacDeviceMac
         DisplayString,
      er1646v2XEfmVlanBridgingOamMacUserMac
         OCTET STRING,
      er1646v2XEfmVlanBridgingOamMacBridgeMac
         DisplayString,
      er1646v2XEfmVlanBridgingMgmtInline
         INTEGER,
      er1646v2XEfmVlanBridgingL2ptMode
         INTEGER,
      er1646v2XEfmVlanBridgingL2ptProtocols
         Integer32,
      er1646v2XEfmVlanBridgingL2ptDestMac
         OCTET STRING,
      er1646v2XEfmVlanBridgingL2ptCos
         INTEGER,
      er1646v2XEfmVlanBridgingL2ptDropThrStp
         INTEGER,
      er1646v2XEfmVlanBridgingL2ptDropThrLldp
         INTEGER,
      er1646v2XEfmVlanBridgingL2ptDropThrOam
         INTEGER,
      er1646v2XEfmVlanBridgingL2ptDropThrCdp
         INTEGER,
      er1646v2XEfmVlanBridgingL2ptDropThrVtp
         INTEGER,
      er1646v2XEfmVlanBridgingL2ptDropThrLacp
         INTEGER,
      er1646v2XEfmVlanBridgingL2ptDropThrEfmOam
         INTEGER,
      er1646v2XEfmVlanBridgingL2ptDropThrPvst
         INTEGER,
      er1646v2XEfmVlanBridgingL2ptDropThrMmrp
         INTEGER,
      er1646v2XEfmVlanBridgingL2ptDropThrMvrp
         INTEGER,
      er1646v2XEfmVlanBridgingL2ptDropThrGvrp
         INTEGER,
      er1646v2XEfmVlanBridgingL2ptDropThrGmrp
         INTEGER,
      er1646v2XEfmVlanBridgingL2ptDropThrDtp
         INTEGER,
      er1646v2XEfmVlanBridgingL2ptDropThrPagp
         INTEGER,
      er1646v2XEfmVlanBridgingL2ptDropThrUdld
         INTEGER,
      er1646v2XEfmVlanVlanVid
         INTEGER,
      er1646v2XEfmVlanVlanVidExtensionSingle
         OCTET STRING,
      er1646v2XEfmVlanVlanVidExtensionEndVid
         Integer32,
      er1646v2XEfmVlanVlanTpid
         INTEGER,
      er1646v2XEfmVlanVlanTagSign
         INTEGER,
      er1646v2XEfmVlanVlanChTos
         INTEGER,
      er1646v2XEfmVlanVlanCTMapP0
         INTEGER,
      er1646v2XEfmVlanVlanCTMapP1
         INTEGER,
      er1646v2XEfmVlanVlanCTMapP2
         INTEGER,
      er1646v2XEfmVlanVlanCTMapP3
         INTEGER,
      er1646v2XEfmVlanVlanCTMapP4
         INTEGER,
      er1646v2XEfmVlanVlanCTMapP5
         INTEGER,
      er1646v2XEfmVlanVlanCTMapP6
         INTEGER,
      er1646v2XEfmVlanVlanCTMapP7
         INTEGER,
      er1646v2XEfmVlanVlanTxCos
         INTEGER,
      er1646v2XEfmVlanVlanCCMapP0
         Integer32,
      er1646v2XEfmVlanVlanCCMapP1
         Integer32,
      er1646v2XEfmVlanVlanCCMapP2
         Integer32,
      er1646v2XEfmVlanVlanCCMapP3
         Integer32,
      er1646v2XEfmVlanVlanCCMapP4
         Integer32,
      er1646v2XEfmVlanVlanCCMapP5
         Integer32,
      er1646v2XEfmVlanVlanCCMapP6
         Integer32,
      er1646v2XEfmVlanVlanCCMapP7
         Integer32,
      er1646v2XEfmVlanVlanQCMapQueue1
         Integer32,
      er1646v2XEfmVlanVlanQCMapQueue2
         Integer32,
      er1646v2XEfmVlanVlanQCMapQueue3
         Integer32,
      er1646v2XEfmVlanVlanQCMapQueue4
         Integer32,
      er1646v2XEfmVlanVlanQCMapQueue5
         Integer32,
      er1646v2XEfmVlanVlanQCMapLowDelayQueue
         Integer32,
      er1646v2XEfmVlanVlanQCMapLowDelay2Queue
         Integer32,
      er1646v2XEfmVlanVlanQCMapSystemQueue
         Integer32,
      er1646v2XEfmVlanVlanQinQSVid
         Integer32,
      er1646v2XEfmVlanVlanQinQSTpid
         INTEGER,
      er1646v2XEfmVlanVlanArpTimeOut
         TimeTicks,
      er1646v2XEfmVlanVlanArpProxyArp
         INTEGER,
      er1646v2XEfmVlanBandwidthMode
         INTEGER,
      er1646v2XEfmVlanBandwidthCir
         Integer32,
      er1646v2XEfmVlanBandwidthEir
         Integer32,
      er1646v2XEfmVlanBandwidthUnit
         INTEGER,
      er1646v2XEfmVlanBandwidthTc
         INTEGER,
      er1646v2XEfmVlanBandwidthTcFactor
         INTEGER,
      er1646v2XEfmVlanBandwidthCorrType
         INTEGER,
      er1646v2XEfmVlanBandwidthCorrPredefEncapsFrameRelay
         DisplayString,
      er1646v2XEfmVlanBandwidthCorrPredefEncapsPpp
         DisplayString,
      er1646v2XEfmVlanBandwidthCorrPredefEncapsAtmHl
         INTEGER,
      er1646v2XEfmVlanBandwidthCorrPredefEncapsAtmMp
         INTEGER,
      er1646v2XEfmVlanBandwidthCorrPredefEncapsHdlc
         DisplayString,
      er1646v2XEfmVlanBandwidthCorrPredefEncapsEfmFs
         Integer32,
      er1646v2XEfmVlanBandwidthCorrPredefEncapsEfmIb
         Integer32,
      er1646v2XEfmVlanBandwidthCorrPredefMode
         INTEGER,
      er1646v2XEfmVlanBandwidthCorrManualOverhead
         Integer32,
      er1646v2XEfmVlanBandwidthCorrManualFrameData
         Counter32,
      er1646v2XEfmVlanBandwidthCorrManualFrameHeader
         Counter32,
      er1646v2XEfmVlanBandwidthMaxFifoQLen
         Integer32,
      er1646v2XEfmVlanBandwidthDeFlagCir
         INTEGER,
      er1646v2XEfmVlanBandwidthDeFlagEir
         INTEGER,
      er1646v2XEfmVlanBandwidthDeFlagViolate
         INTEGER,
      er1646v2XEfmVlanBandwidthActCirActNone
         OCTET STRING,
      er1646v2XEfmVlanBandwidthActCirActEthCos1
         INTEGER,
      er1646v2XEfmVlanBandwidthActCirActEthDei1
         INTEGER,
      er1646v2XEfmVlanBandwidthActCirActEthCos2
         INTEGER,
      er1646v2XEfmVlanBandwidthActCirActEthDei2
         INTEGER,
      er1646v2XEfmVlanBandwidthActCirActEthCos3
         INTEGER,
      er1646v2XEfmVlanBandwidthActCirActEthDei3
         INTEGER,
      er1646v2XEfmVlanBandwidthActCirActEthCos4
         INTEGER,
      er1646v2XEfmVlanBandwidthActCirActEthDei4
         INTEGER,
      er1646v2XEfmVlanBandwidthActCirActEthCos5
         INTEGER,
      er1646v2XEfmVlanBandwidthActCirActEthDei5
         INTEGER,
      er1646v2XEfmVlanBandwidthActCirActEthCos6
         INTEGER,
      er1646v2XEfmVlanBandwidthActCirActEthDei6
         INTEGER,
      er1646v2XEfmVlanBandwidthActCirActEthCos7
         INTEGER,
      er1646v2XEfmVlanBandwidthActCirActEthDei7
         INTEGER,
      er1646v2XEfmVlanBandwidthActCirActEthCos8
         INTEGER,
      er1646v2XEfmVlanBandwidthActCirActEthDei8
         INTEGER,
      er1646v2XEfmVlanBandwidthActCirActEthTos
         INTEGER,
      er1646v2XEfmVlanBandwidthActCirActEthQueue
         INTEGER,
      er1646v2XEfmVlanBandwidthActCirActEthDrpLev
         INTEGER,
      er1646v2XEfmVlanBandwidthActCirActEthDeFlag
         INTEGER,
      er1646v2XEfmVlanBandwidthActCirActIpTos
         INTEGER,
      er1646v2XEfmVlanBandwidthActCirActIpQueue
         INTEGER,
      er1646v2XEfmVlanBandwidthActCirActIpDrpLev
         INTEGER,
      er1646v2XEfmVlanBandwidthActCirActIpDeFlag
         INTEGER,
      er1646v2XEfmVlanBandwidthActEirActNone
         OCTET STRING,
      er1646v2XEfmVlanBandwidthActEirActEthCos1
         INTEGER,
      er1646v2XEfmVlanBandwidthActEirActEthDei1
         INTEGER,
      er1646v2XEfmVlanBandwidthActEirActEthCos2
         INTEGER,
      er1646v2XEfmVlanBandwidthActEirActEthDei2
         INTEGER,
      er1646v2XEfmVlanBandwidthActEirActEthCos3
         INTEGER,
      er1646v2XEfmVlanBandwidthActEirActEthDei3
         INTEGER,
      er1646v2XEfmVlanBandwidthActEirActEthCos4
         INTEGER,
      er1646v2XEfmVlanBandwidthActEirActEthDei4
         INTEGER,
      er1646v2XEfmVlanBandwidthActEirActEthCos5
         INTEGER,
      er1646v2XEfmVlanBandwidthActEirActEthDei5
         INTEGER,
      er1646v2XEfmVlanBandwidthActEirActEthCos6
         INTEGER,
      er1646v2XEfmVlanBandwidthActEirActEthDei6
         INTEGER,
      er1646v2XEfmVlanBandwidthActEirActEthCos7
         INTEGER,
      er1646v2XEfmVlanBandwidthActEirActEthDei7
         INTEGER,
      er1646v2XEfmVlanBandwidthActEirActEthCos8
         INTEGER,
      er1646v2XEfmVlanBandwidthActEirActEthDei8
         INTEGER,
      er1646v2XEfmVlanBandwidthActEirActEthTos
         INTEGER,
      er1646v2XEfmVlanBandwidthActEirActEthQueue
         INTEGER,
      er1646v2XEfmVlanBandwidthActEirActEthDrpLev
         INTEGER,
      er1646v2XEfmVlanBandwidthActEirActEthDeFlag
         INTEGER,
      er1646v2XEfmVlanBandwidthActEirActIpTos
         INTEGER,
      er1646v2XEfmVlanBandwidthActEirActIpQueue
         INTEGER,
      er1646v2XEfmVlanBandwidthActEirActIpDrpLev
         INTEGER,
      er1646v2XEfmVlanBandwidthActEirActIpDeFlag
         INTEGER,
      er1646v2XEfmVlanBandwidthActViolActNone
         OCTET STRING,
      er1646v2XEfmVlanBandwidthActViolActDrop
         OCTET STRING,
      er1646v2XEfmVlanBandwidthActViolActEthCos1
         INTEGER,
      er1646v2XEfmVlanBandwidthActViolActEthDei1
         INTEGER,
      er1646v2XEfmVlanBandwidthActViolActEthCos2
         INTEGER,
      er1646v2XEfmVlanBandwidthActViolActEthDei2
         INTEGER,
      er1646v2XEfmVlanBandwidthActViolActEthCos3
         INTEGER,
      er1646v2XEfmVlanBandwidthActViolActEthDei3
         INTEGER,
      er1646v2XEfmVlanBandwidthActViolActEthCos4
         INTEGER,
      er1646v2XEfmVlanBandwidthActViolActEthDei4
         INTEGER,
      er1646v2XEfmVlanBandwidthActViolActEthCos5
         INTEGER,
      er1646v2XEfmVlanBandwidthActViolActEthDei5
         INTEGER,
      er1646v2XEfmVlanBandwidthActViolActEthCos6
         INTEGER,
      er1646v2XEfmVlanBandwidthActViolActEthDei6
         INTEGER,
      er1646v2XEfmVlanBandwidthActViolActEthCos7
         INTEGER,
      er1646v2XEfmVlanBandwidthActViolActEthDei7
         INTEGER,
      er1646v2XEfmVlanBandwidthActViolActEthCos8
         INTEGER,
      er1646v2XEfmVlanBandwidthActViolActEthDei8
         INTEGER,
      er1646v2XEfmVlanBandwidthActViolActEthTos
         INTEGER,
      er1646v2XEfmVlanBandwidthActViolActEthQueue
         INTEGER,
      er1646v2XEfmVlanBandwidthActViolActEthDrpLev
         INTEGER,
      er1646v2XEfmVlanBandwidthActViolActEthDeFlag
         INTEGER,
      er1646v2XEfmVlanBandwidthActViolActIpTos
         INTEGER,
      er1646v2XEfmVlanBandwidthActViolActIpQueue
         INTEGER,
      er1646v2XEfmVlanBandwidthActViolActIpDrpLev
         INTEGER,
      er1646v2XEfmVlanBandwidthActViolActIpDeFlag
         INTEGER,
      er1646v2XEfmVlanInbBwMode
         INTEGER,
      er1646v2XEfmVlanInbBwCir
         Integer32,
      er1646v2XEfmVlanInbBwEir
         Integer32,
      er1646v2XEfmVlanInbBwUnit
         INTEGER,
      er1646v2XEfmVlanInbBwTc
         INTEGER,
      er1646v2XEfmVlanInbBwTcFactor
         INTEGER,
      er1646v2XEfmVlanInbBwCorrType
         INTEGER,
      er1646v2XEfmVlanInbBwCorrPredefEncapsFrameRelay
         DisplayString,
      er1646v2XEfmVlanInbBwCorrPredefEncapsPpp
         DisplayString,
      er1646v2XEfmVlanInbBwCorrPredefEncapsAtmHl
         INTEGER,
      er1646v2XEfmVlanInbBwCorrPredefEncapsAtmMp
         INTEGER,
      er1646v2XEfmVlanInbBwCorrPredefEncapsHdlc
         DisplayString,
      er1646v2XEfmVlanInbBwCorrPredefEncapsEfmFs
         Integer32,
      er1646v2XEfmVlanInbBwCorrPredefEncapsEfmIb
         Integer32,
      er1646v2XEfmVlanInbBwCorrPredefMode
         INTEGER,
      er1646v2XEfmVlanInbBwCorrManualOverhead
         Integer32,
      er1646v2XEfmVlanInbBwCorrManualFrameData
         Counter32,
      er1646v2XEfmVlanInbBwCorrManualFrameHeader
         Counter32,
      er1646v2XEfmVlanInbBwMaxFifoQLen
         Integer32,
      er1646v2XEfmVlanInbBwPriorityPolicy
         DisplayString,
      er1646v2XEfmVlanInbBwDeFlagCir
         INTEGER,
      er1646v2XEfmVlanInbBwDeFlagEir
         INTEGER,
      er1646v2XEfmVlanInbBwDeFlagViolate
         INTEGER,
      er1646v2XEfmVlanInbBwActCirActNone
         OCTET STRING,
      er1646v2XEfmVlanInbBwActCirActEthCos1
         INTEGER,
      er1646v2XEfmVlanInbBwActCirActEthDei1
         INTEGER,
      er1646v2XEfmVlanInbBwActCirActEthCos2
         INTEGER,
      er1646v2XEfmVlanInbBwActCirActEthDei2
         INTEGER,
      er1646v2XEfmVlanInbBwActCirActEthCos3
         INTEGER,
      er1646v2XEfmVlanInbBwActCirActEthDei3
         INTEGER,
      er1646v2XEfmVlanInbBwActCirActEthCos4
         INTEGER,
      er1646v2XEfmVlanInbBwActCirActEthDei4
         INTEGER,
      er1646v2XEfmVlanInbBwActCirActEthCos5
         INTEGER,
      er1646v2XEfmVlanInbBwActCirActEthDei5
         INTEGER,
      er1646v2XEfmVlanInbBwActCirActEthCos6
         INTEGER,
      er1646v2XEfmVlanInbBwActCirActEthDei6
         INTEGER,
      er1646v2XEfmVlanInbBwActCirActEthCos7
         INTEGER,
      er1646v2XEfmVlanInbBwActCirActEthDei7
         INTEGER,
      er1646v2XEfmVlanInbBwActCirActEthCos8
         INTEGER,
      er1646v2XEfmVlanInbBwActCirActEthDei8
         INTEGER,
      er1646v2XEfmVlanInbBwActCirActEthTos
         INTEGER,
      er1646v2XEfmVlanInbBwActCirActEthQueue
         INTEGER,
      er1646v2XEfmVlanInbBwActCirActEthDrpLev
         INTEGER,
      er1646v2XEfmVlanInbBwActCirActEthDeFlag
         INTEGER,
      er1646v2XEfmVlanInbBwActCirActIpTos
         INTEGER,
      er1646v2XEfmVlanInbBwActCirActIpQueue
         INTEGER,
      er1646v2XEfmVlanInbBwActCirActIpDrpLev
         INTEGER,
      er1646v2XEfmVlanInbBwActCirActIpDeFlag
         INTEGER,
      er1646v2XEfmVlanInbBwActEirActNone
         OCTET STRING,
      er1646v2XEfmVlanInbBwActEirActEthCos1
         INTEGER,
      er1646v2XEfmVlanInbBwActEirActEthDei1
         INTEGER,
      er1646v2XEfmVlanInbBwActEirActEthCos2
         INTEGER,
      er1646v2XEfmVlanInbBwActEirActEthDei2
         INTEGER,
      er1646v2XEfmVlanInbBwActEirActEthCos3
         INTEGER,
      er1646v2XEfmVlanInbBwActEirActEthDei3
         INTEGER,
      er1646v2XEfmVlanInbBwActEirActEthCos4
         INTEGER,
      er1646v2XEfmVlanInbBwActEirActEthDei4
         INTEGER,
      er1646v2XEfmVlanInbBwActEirActEthCos5
         INTEGER,
      er1646v2XEfmVlanInbBwActEirActEthDei5
         INTEGER,
      er1646v2XEfmVlanInbBwActEirActEthCos6
         INTEGER,
      er1646v2XEfmVlanInbBwActEirActEthDei6
         INTEGER,
      er1646v2XEfmVlanInbBwActEirActEthCos7
         INTEGER,
      er1646v2XEfmVlanInbBwActEirActEthDei7
         INTEGER,
      er1646v2XEfmVlanInbBwActEirActEthCos8
         INTEGER,
      er1646v2XEfmVlanInbBwActEirActEthDei8
         INTEGER,
      er1646v2XEfmVlanInbBwActEirActEthTos
         INTEGER,
      er1646v2XEfmVlanInbBwActEirActEthQueue
         INTEGER,
      er1646v2XEfmVlanInbBwActEirActEthDrpLev
         INTEGER,
      er1646v2XEfmVlanInbBwActEirActEthDeFlag
         INTEGER,
      er1646v2XEfmVlanInbBwActEirActIpTos
         INTEGER,
      er1646v2XEfmVlanInbBwActEirActIpQueue
         INTEGER,
      er1646v2XEfmVlanInbBwActEirActIpDrpLev
         INTEGER,
      er1646v2XEfmVlanInbBwActEirActIpDeFlag
         INTEGER,
      er1646v2XEfmVlanInbBwActViolActNone
         OCTET STRING,
      er1646v2XEfmVlanInbBwActViolActDrop
         OCTET STRING,
      er1646v2XEfmVlanInbBwActViolActEthCos1
         INTEGER,
      er1646v2XEfmVlanInbBwActViolActEthDei1
         INTEGER,
      er1646v2XEfmVlanInbBwActViolActEthCos2
         INTEGER,
      er1646v2XEfmVlanInbBwActViolActEthDei2
         INTEGER,
      er1646v2XEfmVlanInbBwActViolActEthCos3
         INTEGER,
      er1646v2XEfmVlanInbBwActViolActEthDei3
         INTEGER,
      er1646v2XEfmVlanInbBwActViolActEthCos4
         INTEGER,
      er1646v2XEfmVlanInbBwActViolActEthDei4
         INTEGER,
      er1646v2XEfmVlanInbBwActViolActEthCos5
         INTEGER,
      er1646v2XEfmVlanInbBwActViolActEthDei5
         INTEGER,
      er1646v2XEfmVlanInbBwActViolActEthCos6
         INTEGER,
      er1646v2XEfmVlanInbBwActViolActEthDei6
         INTEGER,
      er1646v2XEfmVlanInbBwActViolActEthCos7
         INTEGER,
      er1646v2XEfmVlanInbBwActViolActEthDei7
         INTEGER,
      er1646v2XEfmVlanInbBwActViolActEthCos8
         INTEGER,
      er1646v2XEfmVlanInbBwActViolActEthDei8
         INTEGER,
      er1646v2XEfmVlanInbBwActViolActEthTos
         INTEGER,
      er1646v2XEfmVlanInbBwActViolActEthQueue
         INTEGER,
      er1646v2XEfmVlanInbBwActViolActEthDrpLev
         INTEGER,
      er1646v2XEfmVlanInbBwActViolActEthDeFlag
         INTEGER,
      er1646v2XEfmVlanInbBwActViolActIpTos
         INTEGER,
      er1646v2XEfmVlanInbBwActViolActIpQueue
         INTEGER,
      er1646v2XEfmVlanInbBwActViolActIpDrpLev
         INTEGER,
      er1646v2XEfmVlanInbBwActViolActIpDeFlag
         INTEGER,
      er1646v2XEfmVlanPppoE
         INTEGER,
      er1646v2XEfmVlanPppLnkMOperation
         INTEGER,
      er1646v2XEfmVlanPppLnkMInterval
         TimeTicks,
      er1646v2XEfmVlanPppLnkMRepTimeOut
         TimeTicks,
      er1646v2XEfmVlanPppLnkMFailsPrmt
         Integer32,
      er1646v2XEfmVlanPppAuthentication
         INTEGER,
      er1646v2XEfmVlanPppAuthenPeriod
         TimeTicks,
      er1646v2XEfmVlanPppSessionName
         DisplayString,
      er1646v2XEfmVlanPppSessionSecret
         DisplayString,
      er1646v2XEfmVlanPppEncModeSessionSecret
         INTEGER,
      er1646v2XEfmVlanPppEncSessionSecret
         DisplayString,
      er1646v2XEfmVlanPppServiceName
         DisplayString,
      er1646v2XEfmVlanPbbMode
         INTEGER,
      er1646v2XEfmVlanPbbTxCos
         Integer32,
      er1646v2XEfmVlanPbbIsid
         Integer32,
      er1646v2XEfmVlanPbbDestMac
         OCTET STRING,
      er1646v2XEfmVlanPbbCustomGroupMac
         OCTET STRING
      }

er1646v2XEfmVlanActions OBJECT-TYPE
   SYNTAX      VariableLengthTableActions
   MAX-ACCESS  read-write
   STATUS      current
   DESCRIPTION
      "By way of this field, some manipulations
       on this table may be performed."
   ::= {er1646v2XEfmVlanEntry 2}

er1646v2XEfmVlanTableIx OBJECT-TYPE
   SYNTAX      TableIndex
   MAX-ACCESS  not-accessible
   STATUS      current
   DESCRIPTION
      ""
   ::= {er1646v2XEfmVlanEntry 11}

er1646v2XEfmVlanName OBJECT-TYPE
   SYNTAX      DisplayString
   MAX-ACCESS  read-write
   STATUS      current
   DESCRIPTION
      "Path: efm.editConf.vlan.name"
   ::= {er1646v2XEfmVlanEntry 16777216}

er1646v2XEfmVlanRemark OBJECT-TYPE
   SYNTAX      DisplayString
   MAX-ACCESS  read-write
   STATUS      current
   DESCRIPTION
      "Path: efm.editConf.vlan.remark"
   ::= {er1646v2XEfmVlanEntry 1157627904}

er1646v2XEfmVlanAdminStatus OBJECT-TYPE
   SYNTAX      INTEGER
               {
               up (1),
               down (2)
               }
   MAX-ACCESS  read-write
   STATUS      current
   DESCRIPTION
      "Path: efm.editConf.vlan.adminStatus

       Possibilities:
               up   (1)
               down   (2)"
   ::= {er1646v2XEfmVlanEntry 33554432}

er1646v2XEfmVlanMode OBJECT-TYPE
   SYNTAX      INTEGER
               {
               routing (1),
               bridging (2),
               ipV6 (16),
               ipV6ipV4 (17),
               multilink (8)
               }
   MAX-ACCESS  read-write
   STATUS      current
   DESCRIPTION
      "Path: efm.editConf.vlan.mode

       Possibilities:
               routing   (1)
               bridging   (2)
               ipV6   (16)
               ipV6/ipV4   (17)
               multilink   (8)"
   ::= {er1646v2XEfmVlanEntry 67108864}

er1646v2XEfmVlanPriorityPolicy OBJECT-TYPE
   SYNTAX      DisplayString
   MAX-ACCESS  read-write
   STATUS      current
   DESCRIPTION
      "Path: efm.editConf.vlan.priorityPolicy"
   ::= {er1646v2XEfmVlanEntry 83886080}

er1646v2XEfmVlanIpVrfRouter OBJECT-TYPE
   SYNTAX      DisplayString
   MAX-ACCESS  read-write
   STATUS      current
   DESCRIPTION
      "Path: efm.editConf.vlan.ip.vrfRouter"
   ::= {er1646v2XEfmVlanEntry 53215232}

er1646v2XEfmVlanIpAdr OBJECT-TYPE
   SYNTAX      IpAddress
   MAX-ACCESS  read-write
   STATUS      current
   DESCRIPTION
      "Path: efm.editConf.vlan.ip.address"
   ::= {er1646v2XEfmVlanEntry 58261504}

er1646v2XEfmVlanIpNetm OBJECT-TYPE
   SYNTAX      IpAddress
   MAX-ACCESS  read-write
   STATUS      current
   DESCRIPTION
      "Path: efm.editConf.vlan.ip.netMask"
   ::= {er1646v2XEfmVlanEntry 58392576}

er1646v2XEfmVlanIpSNetName OBJECT-TYPE
   SYNTAX      INTEGER
               {
               slOPTg (0),
               corp (2),
               dmz (3),
               internet (1)
               }
   MAX-ACCESS  read-write
   STATUS      current
   DESCRIPTION
      "Path: efm.editConf.vlan.ip.sNet.name

       Possibilities:
               <OPT>   (0)
               corp   (2)
               dmz   (3)
               internet   (1)"
   ::= {er1646v2XEfmVlanEntry 53674240}

er1646v2XEfmVlanIpSNetCust OBJECT-TYPE
   SYNTAX      DisplayString
   MAX-ACCESS  read-write
   STATUS      current
   DESCRIPTION
      "Path: efm.editConf.vlan.ip.sNet.custom"
   ::= {er1646v2XEfmVlanEntry 53674496}

er1646v2XEfmVlanIpDhcpC OBJECT-TYPE
   SYNTAX      INTEGER
               {
               disabled (0),
               enabled (1)
               }
   MAX-ACCESS  read-write
   STATUS      current
   DESCRIPTION
      "Path: efm.editConf.vlan.ip.dhcpClient

       Possibilities:
               disabled   (0)
               enabled   (1)"
   ::= {er1646v2XEfmVlanEntry 53608448}

er1646v2XEfmVlanIpDhcpGatewayPreference OBJECT-TYPE
   SYNTAX      Integer32
   MAX-ACCESS  read-write
   STATUS      current
   DESCRIPTION
      "Path: efm.editConf.vlan.ip.dhcp.gatewayPreference"
   ::= {er1646v2XEfmVlanEntry 53739776}

er1646v2XEfmVlanIpDhcpRoutePreference OBJECT-TYPE
   SYNTAX      Integer32
   MAX-ACCESS  read-write
   STATUS      current
   DESCRIPTION
      "Path: efm.editConf.vlan.ip.dhcp.routePreference"
   ::= {er1646v2XEfmVlanEntry 53740032}

er1646v2XEfmVlanIpDhcpDnsPreference OBJECT-TYPE
   SYNTAX      Integer32
   MAX-ACCESS  read-write
   STATUS      current
   DESCRIPTION
      "Path: efm.editConf.vlan.ip.dhcp.dnsPreference"
   ::= {er1646v2XEfmVlanEntry 53740288}

er1646v2XEfmVlanIpMtu OBJECT-TYPE
   SYNTAX      Integer32
   MAX-ACCESS  read-write
   STATUS      current
   DESCRIPTION
      "Path: efm.editConf.vlan.ip.mtu"
   ::= {er1646v2XEfmVlanEntry 52953088}

er1646v2XEfmVlanIpMssAdjust OBJECT-TYPE
   SYNTAX      INTEGER
               {
               disabled (0),
               auto (65536)
               }
   MAX-ACCESS  read-write
   STATUS      current
   DESCRIPTION
      "Path: efm.editConf.vlan.ip.mssAdjust

       Possibilities:
               disabled   (0)
               auto   (65536)"
   ::= {er1646v2XEfmVlanEntry 53280768}

er1646v2XEfmVlanIpRipMetric OBJECT-TYPE
   SYNTAX      Integer32
   MAX-ACCESS  read-write
   STATUS      current
   DESCRIPTION
      "Path: efm.editConf.vlan.ip.rip.metric"
   ::= {er1646v2XEfmVlanEntry 51712768}

er1646v2XEfmVlanIpRipMetricOut OBJECT-TYPE
   SYNTAX      Integer32
   MAX-ACCESS  read-write
   STATUS      current
   DESCRIPTION
      "Path: efm.editConf.vlan.ip.rip.metricOut"
   ::= {er1646v2XEfmVlanEntry 51713024}

er1646v2XEfmVlanIpRipMode OBJECT-TYPE
   SYNTAX      INTEGER
               {
               disabled (0),
               passive (1),
               active (2)
               }
   MAX-ACCESS  read-write
   STATUS      current
   DESCRIPTION
      "Path: efm.editConf.vlan.ip.rip.mode

       Possibilities:
               disabled   (0)
               passive   (1)
               active   (2)"
   ::= {er1646v2XEfmVlanEntry 51713280}

er1646v2XEfmVlanIpRipTxVer OBJECT-TYPE
   SYNTAX      INTEGER
               {
               rip1 (0),
               rip2 (1),
               rip1mcompatible (2)
               }
   MAX-ACCESS  read-write
   STATUS      current
   DESCRIPTION
      "Path: efm.editConf.vlan.ip.rip.txVersion

       Possibilities:
               rip1   (0)
               rip2   (1)
               rip1-compatible   (2)"
   ::= {er1646v2XEfmVlanEntry 51716864}

er1646v2XEfmVlanIpRipRxVer OBJECT-TYPE
   SYNTAX      INTEGER
               {
               rip1only (0),
               rip2only (1),
               rip12 (2)
               }
   MAX-ACCESS  read-write
   STATUS      current
   DESCRIPTION
      "Path: efm.editConf.vlan.ip.rip.rxVersion

       Possibilities:
               rip1only   (0)
               rip2only   (1)
               rip1&2   (2)"
   ::= {er1646v2XEfmVlanEntry 51717120}

er1646v2XEfmVlanIpRipSplitH OBJECT-TYPE
   SYNTAX      INTEGER
               {
               disabled (0),
               enabled (1),
               poisonedReverse (2)
               }
   MAX-ACCESS  read-write
   STATUS      current
   DESCRIPTION
      "Path: efm.editConf.vlan.ip.rip.splitHorizon

       Possibilities:
               disabled   (0)
               enabled   (1)
               poisonedReverse   (2)"
   ::= {er1646v2XEfmVlanEntry 51713792}

er1646v2XEfmVlanIpRipAuth OBJECT-TYPE
   SYNTAX      INTEGER
               {
               disabled (0),
               texts (1),
               md5 (2)
               }
   MAX-ACCESS  read-write
   STATUS      current
   DESCRIPTION
      "Path: efm.editConf.vlan.ip.rip.authentication

       Possibilities:
               disabled   (0)
               text    (1)
               md5   (2)"
   ::= {er1646v2XEfmVlanEntry 51712512}

er1646v2XEfmVlanIpRipFilter OBJECT-TYPE
   SYNTAX      DisplayString
   MAX-ACCESS  read-write
   STATUS      current
   DESCRIPTION
      "Path: efm.editConf.vlan.ip.rip.filter"
   ::= {er1646v2XEfmVlanEntry 51716096}

er1646v2XEfmVlanIpRipFilterIn OBJECT-TYPE
   SYNTAX      DisplayString
   MAX-ACCESS  read-write
   STATUS      current
   DESCRIPTION
      "Path: efm.editConf.vlan.ip.rip.filterIn"
   ::= {er1646v2XEfmVlanEntry 51716352}

er1646v2XEfmVlanIpRipClearNextHop OBJECT-TYPE
   SYNTAX      INTEGER
               {
               disabled (0),
               enabled (1)
               }
   MAX-ACCESS  read-write
   STATUS      current
   DESCRIPTION
      "Path: efm.editConf.vlan.ip.rip.clearNextHop

       Possibilities:
               disabled   (0)
               enabled   (1)"
   ::= {er1646v2XEfmVlanEntry 51708416}

er1646v2XEfmVlanIpAccPol OBJECT-TYPE
   SYNTAX      DisplayString
   MAX-ACCESS  read-write
   STATUS      current
   DESCRIPTION
      "Path: efm.editConf.vlan.ip.accessPolicy"
   ::= {er1646v2XEfmVlanEntry 53084160}

er1646v2XEfmVlanIpAB OBJECT-TYPE
   SYNTAX      DisplayString
   MAX-ACCESS  read-write
   STATUS      current
   DESCRIPTION
      "Path: efm.editConf.vlan.ip.trafficPolicy"
   ::= {er1646v2XEfmVlanEntry 51249152}

er1646v2XEfmVlanIpMA OBJECT-TYPE
   SYNTAX      INTEGER
               {
               disabled (0),
               enabled (1)
               }
   MAX-ACCESS  read-write
   STATUS      current
   DESCRIPTION
      "Path: efm.editConf.vlan.ip.mgmtAccess

       Possibilities:
               disabled   (0)
               enabled   (1)"
   ::= {er1646v2XEfmVlanEntry 51380224}

er1646v2XEfmVlanIpMF OBJECT-TYPE
   SYNTAX      Integer32
   MAX-ACCESS  read-write
   STATUS      current
   DESCRIPTION
      "Path: efm.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2XEfmVlanEntry 51445760}

er1646v2XEfmVlanIpDB OBJECT-TYPE
   SYNTAX      INTEGER
               {
               disabled (0),
               enabled (1)
               }
   MAX-ACCESS  read-write
   STATUS      current
   DESCRIPTION
      "Path: efm.editConf.vlan.ip.directedBroadcasts

       Possibilities:
               disabled   (0)
               enabled   (1)"
   ::= {er1646v2XEfmVlanEntry 51773440}

er1646v2XEfmVlanIpIR OBJECT-TYPE
   SYNTAX      INTEGER
               {
               disabled (0),
               enabled (1)
               }
   MAX-ACCESS  read-write
   STATUS      current
   DESCRIPTION
      "Path: efm.editConf.vlan.ip.icmpRedirects

       Possibilities:
               disabled   (0)
               enabled   (1)"
   ::= {er1646v2XEfmVlanEntry 52035584}

er1646v2XEfmVlanIpIgmp OBJECT-TYPE
   SYNTAX      INTEGER
               {
               disabled (0),
               proxy (1),
               router (2),
               v3Router (5)
               }
   MAX-ACCESS  read-write
   STATUS      current
   DESCRIPTION
      "Path: efm.editConf.vlan.ip.igmp

       Possibilities:
               disabled   (0)
               proxy   (1)
               router   (2)
               v3Router   (5)"
   ::= {er1646v2XEfmVlanEntry 52428800}

er1646v2XEfmVlanIpNN OBJECT-TYPE
   SYNTAX      DisplayString
   MAX-ACCESS  read-write
   STATUS      current
   DESCRIPTION
      "Path: efm.editConf.vlan.ip.nat"
   ::= {er1646v2XEfmVlanEntry 52101120}

er1646v2XEfmVlanIpVrrp OBJECT-TYPE
   SYNTAX      INTEGER
               {
               disabled (0),
               enabled (1)
               }
   MAX-ACCESS  read-write
   STATUS      current
   DESCRIPTION
      "Path: efm.editConf.vlan.ip.vrrp

       Possibilities:
               disabled   (0)
               enabled   (1)"
   ::= {er1646v2XEfmVlanEntry 53149696}

er1646v2XEfmVlanIpPimMode OBJECT-TYPE
   SYNTAX      INTEGER
               {
               disabled (0),
               sparse (1),
               passive (2)
               }
   MAX-ACCESS  read-write
   STATUS      current
   DESCRIPTION
      "Path: efm.editConf.vlan.ip.pim.mode

       Possibilities:
               disabled   (0)
               sparse   (1)
               passive   (2)"
   ::= {er1646v2XEfmVlanEntry 53346560}

er1646v2XEfmVlanIpPimDrPriority OBJECT-TYPE
   SYNTAX      Counter32
   MAX-ACCESS  read-write
   STATUS      current
   DESCRIPTION
      "Path: efm.editConf.vlan.ip.pim.drPriority

       32 bit unsigned wrappable counter."
   ::= {er1646v2XEfmVlanEntry 53346816}

er1646v2XEfmVlanIpPimHelloTime OBJECT-TYPE
   SYNTAX      TimeTicks
   MAX-ACCESS  read-write
   STATUS      current
   DESCRIPTION
      "Path: efm.editConf.vlan.ip.pim.helloTime

       Time in centi-second."
   ::= {er1646v2XEfmVlanEntry 53347072}

er1646v2XEfmVlanIpPimPropagationDelay OBJECT-TYPE
   SYNTAX      TimeTicks
   MAX-ACCESS  read-write
   STATUS      current
   DESCRIPTION
      "Path: efm.editConf.vlan.ip.pim.propagationDelay

       Time in centi-second."
   ::= {er1646v2XEfmVlanEntry 53347328}

er1646v2XEfmVlanIpPimOverrideInterval OBJECT-TYPE
   SYNTAX      TimeTicks
   MAX-ACCESS  read-write
   STATUS      current
   DESCRIPTION
      "Path: efm.editConf.vlan.ip.pim.overrideInterval

       Time in centi-second."
   ::= {er1646v2XEfmVlanEntry 53347584}

er1646v2XEfmVlanIpPimBsrBorder OBJECT-TYPE
   SYNTAX      INTEGER
               {
               disabled (0),
               enabled (1)
               }
   MAX-ACCESS  read-write
   STATUS      current
   DESCRIPTION
      "Path: efm.editConf.vlan.ip.pim.bsrBorder

       Possibilities:
               disabled   (0)
               enabled   (1)"
   ::= {er1646v2XEfmVlanEntry 53347840}

er1646v2XEfmVlanIpPimTtlThreshold OBJECT-TYPE
   SYNTAX      Integer32
   MAX-ACCESS  read-write
   STATUS      current
   DESCRIPTION
      "Path: efm.editConf.vlan.ip.pim.ttlThreshold"
   ::= {er1646v2XEfmVlanEntry 53348096}

er1646v2XEfmVlanIpIMNetworkUnreachable OBJECT-TYPE
   SYNTAX      INTEGER
               {
               disabled (0),
               enabled (1)
               }
   MAX-ACCESS  read-write
   STATUS      current
   DESCRIPTION
      "Path: efm.editConf.vlan.ip.icmpMessages.networkUnreachable

       Possibilities:
               disabled   (0)
               enabled   (1)"
   ::= {er1646v2XEfmVlanEntry 53412096}

er1646v2XEfmVlanIpIMHostUnreachable OBJECT-TYPE
   SYNTAX      INTEGER
               {
               disabled (0),
               enabled (1)
               }
   MAX-ACCESS  read-write
   STATUS      current
   DESCRIPTION
      "Path: efm.editConf.vlan.ip.icmpMessages.hostUnreachable

       Possibilities:
               disabled   (0)
               enabled   (1)"
   ::= {er1646v2XEfmVlanEntry 53412352}

er1646v2XEfmVlanIpIMProtocolUnreachable OBJECT-TYPE
   SYNTAX      INTEGER
               {
               disabled (0),
               enabled (1)
               }
   MAX-ACCESS  read-write
   STATUS      current
   DESCRIPTION
      "Path: efm.editConf.vlan.ip.icmpMessages.protocolUnreachable

       Possibilities:
               disabled   (0)
               enabled   (1)"
   ::= {er1646v2XEfmVlanEntry 53412608}

er1646v2XEfmVlanIpIMPortUnreachable OBJECT-TYPE
   SYNTAX      INTEGER
               {
               disabled (0),
               enabled (1)
               }
   MAX-ACCESS  read-write
   STATUS      current
   DESCRIPTION
      "Path: efm.editConf.vlan.ip.icmpMessages.portUnreachable

       Possibilities:
               disabled   (0)
               enabled   (1)"
   ::= {er1646v2XEfmVlanEntry 53412864}

er1646v2XEfmVlanIpIMMtuExceeded OBJECT-TYPE
   SYNTAX      INTEGER
               {
               disabled (0),
               enabled (1)
               }
   MAX-ACCESS  read-write
   STATUS      current
   DESCRIPTION
      "Path: efm.editConf.vlan.ip.icmpMessages.mtuExceeded

       Possibilities:
               disabled   (0)
               enabled   (1)"
   ::= {er1646v2XEfmVlanEntry 53413120}

er1646v2XEfmVlanIpIMAdminProhibited OBJECT-TYPE
   SYNTAX      INTEGER
               {
               disabled (0),
               enabled (1)
               }
   MAX-ACCESS  read-write
   STATUS      current
   DESCRIPTION
      "Path: efm.editConf.vlan.ip.icmpMessages.adminProhibited

       Possibilities:
               disabled   (0)
               enabled   (1)"
   ::= {er1646v2XEfmVlanEntry 53413376}

er1646v2XEfmVlanIpIMTtlExceeded OBJECT-TYPE
   SYNTAX      INTEGER
               {
               disabled (0),
               enabled (1)
               }
   MAX-ACCESS  read-write
   STATUS      current
   DESCRIPTION
      "Path: efm.editConf.vlan.ip.icmpMessages.ttlExceeded

       Possibilities:
               disabled   (0)
               enabled   (1)"
   ::= {er1646v2XEfmVlanEntry 53413632}

er1646v2XEfmVlanIpIMRedirect OBJECT-TYPE
   SYNTAX      INTEGER
               {
               disabled (0),
               enabled (1)
               }
   MAX-ACCESS  read-write
   STATUS      current
   DESCRIPTION
      "Path: efm.editConf.vlan.ip.icmpMessages.redirect

       Possibilities:
               disabled   (0)
               enabled   (1)"
   ::= {er1646v2XEfmVlanEntry 53413888}

er1646v2XEfmVlanIpV6VrfRouter OBJECT-TYPE
   SYNTAX      DisplayString
   MAX-ACCESS  read-write
   STATUS      current
   DESCRIPTION
      "Path: efm.editConf.vlan.ipV6.vrfRouter"
   ::= {er1646v2XEfmVlanEntry 704708608}

er1646v2XEfmVlanIpV6AddrAutoConfigNrDupAddrDetects OBJECT-TYPE
   SYNTAX      Integer32
   MAX-ACCESS  read-write
   STATUS      current
   DESCRIPTION
      "Path: efm.editConf.vlan.ipV6.addrAutoConfig.nrDupAddrDetects"
   ::= {er1646v2XEfmVlanEntry 704905472}

er1646v2XEfmVlanIpV6AddrAutoConfigAcceptRa OBJECT-TYPE
   SYNTAX      INTEGER
               {
               disabled (0),
               enabled (1)
               }
   MAX-ACCESS  read-write
   STATUS      current
   DESCRIPTION
      "Path: efm.editConf.vlan.ipV6.addrAutoConfig.acceptRa

       Possibilities:
               disabled   (0)
               enabled   (1)"
   ::= {er1646v2XEfmVlanEntry 704905728}

er1646v2XEfmVlanIpV6AddrAutoConfigAcceptRaRdnss OBJECT-TYPE
   SYNTAX      INTEGER
               {
               disabled (0),
               enabled (1)
               }
   MAX-ACCESS  read-write
   STATUS      current
   DESCRIPTION
      "Path: efm.editConf.vlan.ipV6.addrAutoConfig.acceptRaRdnss

       Possibilities:
               disabled   (0)
               enabled   (1)"
   ::= {er1646v2XEfmVlanEntry 704905984}

er1646v2XEfmVlanIpV6AddrAutoConfigAcceptRaDnssl OBJECT-TYPE
   SYNTAX      INTEGER
               {
               disabled (0),
               enabled (1)
               }
   MAX-ACCESS  read-write
   STATUS      current
   DESCRIPTION
      "Path: efm.editConf.vlan.ipV6.addrAutoConfig.acceptRaDnssl

       Possibilities:
               disabled   (0)
               enabled   (1)"
   ::= {er1646v2XEfmVlanEntry 704906240}

er1646v2XEfmVlanIpV6DefaultRoute OBJECT-TYPE
   SYNTAX      INTEGER
               {
               disabled (0),
               enabled (1)
               }
   MAX-ACCESS  read-write
   STATUS      current
   DESCRIPTION
      "Path: efm.editConf.vlan.ipV6.defaultRoute

       Possibilities:
               disabled   (0)
               enabled   (1)"
   ::= {er1646v2XEfmVlanEntry 704970752}

er1646v2XEfmVlanIpV6RaSend OBJECT-TYPE
   SYNTAX      INTEGER
               {
               disabled (0),
               enabled (1)
               }
   MAX-ACCESS  read-write
   STATUS      current
   DESCRIPTION
      "Path: efm.editConf.vlan.ipV6.ra.send

       Possibilities:
               disabled   (0)
               enabled   (1)"
   ::= {er1646v2XEfmVlanEntry 705036544}

er1646v2XEfmVlanIpV6RaMinInterval OBJECT-TYPE
   SYNTAX      TimeTicks
   MAX-ACCESS  read-write
   STATUS      current
   DESCRIPTION
      "Path: efm.editConf.vlan.ipV6.ra.minInterval

       Time in centi-second."
   ::= {er1646v2XEfmVlanEntry 705036800}

er1646v2XEfmVlanIpV6RaMaxInterval OBJECT-TYPE
   SYNTAX      TimeTicks
   MAX-ACCESS  read-write
   STATUS      current
   DESCRIPTION
      "Path: efm.editConf.vlan.ipV6.ra.maxInterval

       Time in centi-second."
   ::= {er1646v2XEfmVlanEntry 705037056}

er1646v2XEfmVlanIpV6RaManagedFlag OBJECT-TYPE
   SYNTAX      INTEGER
               {
               disabled (0),
               enabled (1)
               }
   MAX-ACCESS  read-write
   STATUS      current
   DESCRIPTION
      "Path: efm.editConf.vlan.ipV6.ra.managedFlag

       Possibilities:
               disabled   (0)
               enabled   (1)"
   ::= {er1646v2XEfmVlanEntry 705037312}

er1646v2XEfmVlanIpV6RaOtherConfFlag OBJECT-TYPE
   SYNTAX      INTEGER
               {
               disabled (0),
               enabled (1)
               }
   MAX-ACCESS  read-write
   STATUS      current
   DESCRIPTION
      "Path: efm.editConf.vlan.ipV6.ra.otherConfFlag

       Possibilities:
               disabled   (0)
               enabled   (1)"
   ::= {er1646v2XEfmVlanEntry 705037568}

er1646v2XEfmVlanIpV6RaLinkMtu OBJECT-TYPE
   SYNTAX      Integer32
   MAX-ACCESS  read-write
   STATUS      current
   DESCRIPTION
      "Path: efm.editConf.vlan.ipV6.ra.linkMtu"
   ::= {er1646v2XEfmVlanEntry 705037824}

er1646v2XEfmVlanIpV6RaReachableTime OBJECT-TYPE
   SYNTAX      TimeTicks
   MAX-ACCESS  read-write
   STATUS      current
   DESCRIPTION
      "Path: efm.editConf.vlan.ipV6.ra.reachableTime

       Time in centi-second."
   ::= {er1646v2XEfmVlanEntry 705038080}

er1646v2XEfmVlanIpV6RaRetransmitTime OBJECT-TYPE
   SYNTAX      TimeTicks
   MAX-ACCESS  read-write
   STATUS      current
   DESCRIPTION
      "Path: efm.editConf.vlan.ipV6.ra.retransmitTime

       Time in centi-second."
   ::= {er1646v2XEfmVlanEntry 705038336}

er1646v2XEfmVlanIpV6RaHopLimit OBJECT-TYPE
   SYNTAX      Integer32
   MAX-ACCESS  read-write
   STATUS      current
   DESCRIPTION
      "Path: efm.editConf.vlan.ipV6.ra.hopLimit"
   ::= {er1646v2XEfmVlanEntry 705038592}

er1646v2XEfmVlanIpV6RaDefaultLifeTime OBJECT-TYPE
   SYNTAX      TimeTicks
   MAX-ACCESS  read-write
   STATUS      current
   DESCRIPTION
      "Path: efm.editConf.vlan.ipV6.ra.defaultLifeTime

       Time in centi-second."
   ::= {er1646v2XEfmVlanEntry 705038848}

er1646v2XEfmVlanIpV6RaDnsOptionsRdnssLifeTime OBJECT-TYPE
   SYNTAX      TimeTicks
   MAX-ACCESS  read-write
   STATUS      current
   DESCRIPTION
      "Path: efm.editConf.vlan.ipV6.ra.dnsOptions.rdnss.lifeTime

       Time in centi-second."
   ::= {er1646v2XEfmVlanEntry 705039140}

er1646v2XEfmVlanIpV6RaDnsOptionsRdnssImportServers OBJECT-TYPE
   SYNTAX      INTEGER
               {
               disabled (0),
               enabled (1)
               }
   MAX-ACCESS  read-write
   STATUS      current
   DESCRIPTION
      "Path: efm.editConf.vlan.ipV6.ra.dnsOptions.rdnss.importServers

       Possibilities:
               disabled   (0)
               enabled   (1)"
   ::= {er1646v2XEfmVlanEntry 705039148}

er1646v2XEfmVlanIpV6RaDnsOptionsDnsslLifeTime OBJECT-TYPE
   SYNTAX      TimeTicks
   MAX-ACCESS  read-write
   STATUS      current
   DESCRIPTION
      "Path: efm.editConf.vlan.ipV6.ra.dnsOptions.dnssl.lifeTime

       Time in centi-second."
   ::= {er1646v2XEfmVlanEntry 705039172}

er1646v2XEfmVlanIpV6RaDnsOptionsDnsslImportDomains OBJECT-TYPE
   SYNTAX      INTEGER
               {
               disabled (0),
               enabled (1)
               }
   MAX-ACCESS  read-write
   STATUS      current
   DESCRIPTION
      "Path: efm.editConf.vlan.ipV6.ra.dnsOptions.dnssl.importDomains

       Possibilities:
               disabled   (0)
               enabled   (1)"
   ::= {er1646v2XEfmVlanEntry 705039180}

er1646v2XEfmVlanIpV6RsSend OBJECT-TYPE
   SYNTAX      INTEGER
               {
               disabled (0),
               enabled (1)
               }
   MAX-ACCESS  read-write
   STATUS      current
   DESCRIPTION
      "Path: efm.editConf.vlan.ipV6.rs.send

       Possibilities:
               disabled   (0)
               enabled   (1)"
   ::= {er1646v2XEfmVlanEntry 705954048}

er1646v2XEfmVlanIpV6RsMaxRandomDelay OBJECT-TYPE
   SYNTAX      TimeTicks
   MAX-ACCESS  read-write
   STATUS      current
   DESCRIPTION
      "Path: efm.editConf.vlan.ipV6.rs.maxRandomDelay

       Time in centi-second."
   ::= {er1646v2XEfmVlanEntry 705954304}

er1646v2XEfmVlanIpV6RsInterval OBJECT-TYPE
   SYNTAX      TimeTicks
   MAX-ACCESS  read-write
   STATUS      current
   DESCRIPTION
      "Path: efm.editConf.vlan.ipV6.rs.interval

       Time in centi-second."
   ::= {er1646v2XEfmVlanEntry 705954560}

er1646v2XEfmVlanIpV6RsMaxSolicitations OBJECT-TYPE
   SYNTAX      Integer32
   MAX-ACCESS  read-write
   STATUS      current
   DESCRIPTION
      "Path: efm.editConf.vlan.ipV6.rs.maxSolicitations"
   ::= {er1646v2XEfmVlanEntry 705954816}

er1646v2XEfmVlanIpV6TrafficPolicyInbound OBJECT-TYPE
   SYNTAX      DisplayString
   MAX-ACCESS  read-write
   STATUS      current
   DESCRIPTION
      "Path: efm.editConf.vlan.ipV6.trafficPolicy.inbound"
   ::= {er1646v2XEfmVlanEntry 705364224}

er1646v2XEfmVlanIpV6TrafficPolicyOutbound OBJECT-TYPE
   SYNTAX      DisplayString
   MAX-ACCESS  read-write
   STATUS      current
   DESCRIPTION
      "Path: efm.editConf.vlan.ipV6.trafficPolicy.outbound"
   ::= {er1646v2XEfmVlanEntry 705364480}

er1646v2XEfmVlanIpV6FirewallZone OBJECT-TYPE
   SYNTAX      DisplayString
   MAX-ACCESS  read-write
   STATUS      current
   DESCRIPTION
      "Path: efm.editConf.vlan.ipV6.firewall.zone"
   ::= {er1646v2XEfmVlanEntry 705429760}

er1646v2XEfmVlanIpV6DhcpClientAddrAC OBJECT-TYPE
   SYNTAX      INTEGER
               {
               disabled (0),
               enabled (1)
               }
   MAX-ACCESS  read-write
   STATUS      current
   DESCRIPTION
      "Path: efm.editConf.vlan.ipV6.dhcp.client.addrAutoConfig

       Possibilities:
               disabled   (0)
               enabled   (1)"
   ::= {er1646v2XEfmVlanEntry 705307648}

er1646v2XEfmVlanIpV6DhcpClientPrDelMode OBJECT-TYPE
   SYNTAX      INTEGER
               {
               disabled (0),
               enabled (1)
               }
   MAX-ACCESS  read-write
   STATUS      current
   DESCRIPTION
      "Path: efm.editConf.vlan.ipV6.dhcp.client.pd.mode

       Possibilities:
               disabled   (0)
               enabled   (1)"
   ::= {er1646v2XEfmVlanEntry 705308676}

er1646v2XEfmVlanIpV6DhcpClientPrDelPool OBJECT-TYPE
   SYNTAX      DisplayString
   MAX-ACCESS  read-write
   STATUS      current
   DESCRIPTION
      "Path: efm.editConf.vlan.ipV6.dhcp.client.pd.pool"
   ::= {er1646v2XEfmVlanEntry 705308680}

er1646v2XEfmVlanIpV6DhcpClientPrDelPdExclOpt OBJECT-TYPE
   SYNTAX      INTEGER
               {
               disabled (0),
               enabled (1)
               }
   MAX-ACCESS  read-write
   STATUS      current
   DESCRIPTION
      "Path: efm.editConf.vlan.ipV6.dhcp.client.pd.pdExclOpt

       Possibilities:
               disabled   (0)
               enabled   (1)"
   ::= {er1646v2XEfmVlanEntry 705308684}

er1646v2XEfmVlanIpV6DhcpClientDnsServerPref OBJECT-TYPE
   SYNTAX      Integer32
   MAX-ACCESS  read-write
   STATUS      current
   DESCRIPTION
      "Path: efm.editConf.vlan.ipV6.dhcp.client.dns.serverPref"
   ::= {er1646v2XEfmVlanEntry 705310724}

er1646v2XEfmVlanIpV6DhcpClientRapidCommit OBJECT-TYPE
   SYNTAX      INTEGER
               {
               disabled (0),
               enabled (1)
               }
   MAX-ACCESS  read-write
   STATUS      current
   DESCRIPTION
      "Path: efm.editConf.vlan.ipV6.dhcp.client.rapidCommit

       Possibilities:
               disabled   (0)
               enabled   (1)"
   ::= {er1646v2XEfmVlanEntry 705309696}

er1646v2XEfmVlanIpV6DhcpClientTimersSolTimeOut OBJECT-TYPE
   SYNTAX      TimeTicks
   MAX-ACCESS  read-write
   STATUS      current
   DESCRIPTION
      "Path: efm.editConf.vlan.ipV6.dhcp.client.timers.solTimeOut

       Time in centi-second."
   ::= {er1646v2XEfmVlanEntry 705311748}

er1646v2XEfmVlanIpV6DhcpClientTimersSolMaxRt OBJECT-TYPE
   SYNTAX      TimeTicks
   MAX-ACCESS  read-write
   STATUS      current
   DESCRIPTION
      "Path: efm.editConf.vlan.ipV6.dhcp.client.timers.solMaxRt

       Time in centi-second."
   ::= {er1646v2XEfmVlanEntry 705311752}

er1646v2XEfmVlanIpV6DhcpClientTimersInfoRefresh OBJECT-TYPE
   SYNTAX      TimeTicks
   MAX-ACCESS  read-write
   STATUS      current
   DESCRIPTION
      "Path: efm.editConf.vlan.ipV6.dhcp.client.timers.infoRefresh

       Time in centi-second."
   ::= {er1646v2XEfmVlanEntry 705311756}

er1646v2XEfmVlanIpV6DhcpServerMode OBJECT-TYPE
   SYNTAX      INTEGER
               {
               disabled (0),
               enabled (1)
               }
   MAX-ACCESS  read-write
   STATUS      current
   DESCRIPTION
      "Path: efm.editConf.vlan.ipV6.dhcp.server.mode

       Possibilities:
               disabled   (0)
               enabled   (1)"
   ::= {er1646v2XEfmVlanEntry 705315840}

er1646v2XEfmVlanIpV6DhcpServerPreference OBJECT-TYPE
   SYNTAX      Integer32
   MAX-ACCESS  read-write
   STATUS      current
   DESCRIPTION
      "Path: efm.editConf.vlan.ipV6.dhcp.server.preference"
   ::= {er1646v2XEfmVlanEntry 705316864}

er1646v2XEfmVlanIpV6DhcpServerPool OBJECT-TYPE
   SYNTAX      DisplayString
   MAX-ACCESS  read-write
   STATUS      current
   DESCRIPTION
      "Path: efm.editConf.vlan.ipV6.dhcp.server.pool"
   ::= {er1646v2XEfmVlanEntry 705317888}

er1646v2XEfmVlanIpV6DhcpServerRapidCommit OBJECT-TYPE
   SYNTAX      INTEGER
               {
               disabled (0),
               enabled (1)
               }
   MAX-ACCESS  read-write
   STATUS      current
   DESCRIPTION
      "Path: efm.editConf.vlan.ipV6.dhcp.server.rapidCommit

       Possibilities:
               disabled   (0)
               enabled   (1)"
   ::= {er1646v2XEfmVlanEntry 705318912}

er1646v2XEfmVlanIpV6DhcpServerTimersInfoRefresh OBJECT-TYPE
   SYNTAX      TimeTicks
   MAX-ACCESS  read-write
   STATUS      current
   DESCRIPTION
      "Path: efm.editConf.vlan.ipV6.dhcp.server.timers.infoRefresh

       Time in centi-second."
   ::= {er1646v2XEfmVlanEntry 705319940}

er1646v2XEfmVlanIpV6DhcpRelayMode OBJECT-TYPE
   SYNTAX      INTEGER
               {
               disabled (0),
               enabled (1)
               }
   MAX-ACCESS  read-write
   STATUS      current
   DESCRIPTION
      "Path: efm.editConf.vlan.ipV6.dhcp.relay.mode

       Possibilities:
               disabled   (0)
               enabled   (1)"
   ::= {er1646v2XEfmVlanEntry 705323040}

er1646v2XEfmVlanIpV6SendRedirect OBJECT-TYPE
   SYNTAX      INTEGER
               {
               disabled (0),
               enabled (1)
               }
   MAX-ACCESS  read-write
   STATUS      current
   DESCRIPTION
      "Path: efm.editConf.vlan.ipV6.sendRedirect

       Possibilities:
               disabled   (0)
               enabled   (1)"
   ::= {er1646v2XEfmVlanEntry 705101824}

er1646v2XEfmVlanIpV6LinkMtu OBJECT-TYPE
   SYNTAX      Integer32
   MAX-ACCESS  read-write
   STATUS      current
   DESCRIPTION
      "Path: efm.editConf.vlan.ipV6.linkMtu"
   ::= {er1646v2XEfmVlanEntry 705167360}

er1646v2XEfmVlanIpV6InterfaceId OBJECT-TYPE
   SYNTAX      OCTET STRING
   MAX-ACCESS  read-write
   STATUS      current
   DESCRIPTION
      "Path: efm.editConf.vlan.ipV6.interfaceId"
   ::= {er1646v2XEfmVlanEntry 705232896}

er1646v2XEfmVlanIpV6MF OBJECT-TYPE
   SYNTAX      Integer32
   MAX-ACCESS  read-write
   STATUS      current
   DESCRIPTION
      "Path: efm.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2XEfmVlanEntry 705757184}

er1646v2XEfmVlanIpV6IcmpMessagesNoRoute OBJECT-TYPE
   SYNTAX      INTEGER
               {
               disabled (0),
               enabled (1)
               }
   MAX-ACCESS  read-write
   STATUS      current
   DESCRIPTION
      "Path: efm.editConf.vlan.ipV6.icmpMessages.noRoute

       Possibilities:
               disabled   (0)
               enabled   (1)"
   ::= {er1646v2XEfmVlanEntry 705822976}

er1646v2XEfmVlanIpV6IcmpMessagesBeyondScope OBJECT-TYPE
   SYNTAX      INTEGER
               {
               disabled (0),
               enabled (1)
               }
   MAX-ACCESS  read-write
   STATUS      current
   DESCRIPTION
      "Path: efm.editConf.vlan.ipV6.icmpMessages.beyondScope

       Possibilities:
               disabled   (0)
               enabled   (1)"
   ::= {er1646v2XEfmVlanEntry 705823488}

er1646v2XEfmVlanIpV6IcmpMessagesAddressUnreachable OBJECT-TYPE
   SYNTAX      INTEGER
               {
               disabled (0),
               enabled (1)
               }
   MAX-ACCESS  read-write
   STATUS      current
   DESCRIPTION
      "Path: efm.editConf.vlan.ipV6.icmpMessages.addressUnreachable

       Possibilities:
               disabled   (0)
               enabled   (1)"
   ::= {er1646v2XEfmVlanEntry 705823744}

er1646v2XEfmVlanIpV6IcmpMessagesPortUnreachable OBJECT-TYPE
   SYNTAX      INTEGER
               {
               disabled (0),
               enabled (1)
               }
   MAX-ACCESS  read-write
   STATUS      current
   DESCRIPTION
      "Path: efm.editConf.vlan.ipV6.icmpMessages.portUnreachable

       Possibilities:
               disabled   (0)
               enabled   (1)"
   ::= {er1646v2XEfmVlanEntry 705824000}

er1646v2XEfmVlanIpV6IcmpMessagesPacketTooBig OBJECT-TYPE
   SYNTAX      INTEGER
               {
               disabled (0),
               enabled (1)
               }
   MAX-ACCESS  read-write
   STATUS      current
   DESCRIPTION
      "Path: efm.editConf.vlan.ipV6.icmpMessages.packetTooBig

       Possibilities:
               disabled   (0)
               enabled   (1)"
   ::= {er1646v2XEfmVlanEntry 705825280}

er1646v2XEfmVlanIpV6IcmpMessagesHopLimitExceeded OBJECT-TYPE
   SYNTAX      INTEGER
               {
               disabled (0),
               enabled (1)
               }
   MAX-ACCESS  read-write
   STATUS      current
   DESCRIPTION
      "Path: efm.editConf.vlan.ipV6.icmpMessages.hopLimitExceeded

       Possibilities:
               disabled   (0)
               enabled   (1)"
   ::= {er1646v2XEfmVlanEntry 705827840}

er1646v2XEfmVlanIpV6IcmpMessagesFragTimeExceeded OBJECT-TYPE
   SYNTAX      INTEGER
               {
               disabled (0),
               enabled (1)
               }
   MAX-ACCESS  read-write
   STATUS      current
   DESCRIPTION
      "Path: efm.editConf.vlan.ipV6.icmpMessages.fragTimeExceeded

       Possibilities:
               disabled   (0)
               enabled   (1)"
   ::= {er1646v2XEfmVlanEntry 705828096}

er1646v2XEfmVlanIpV6IcmpMessagesHeaderFieldErr OBJECT-TYPE
   SYNTAX      INTEGER
               {
               disabled (0),
               enabled (1)
               }
   MAX-ACCESS  read-write
   STATUS      current
   DESCRIPTION
      "Path: efm.editConf.vlan.ipV6.icmpMessages.headerFieldErr

       Possibilities:
               disabled   (0)
               enabled   (1)"
   ::= {er1646v2XEfmVlanEntry 705830400}

er1646v2XEfmVlanIpV6IcmpMessagesOptionUnrecognized OBJECT-TYPE
   SYNTAX      INTEGER
               {
               disabled (0),
               enabled (1)
               }
   MAX-ACCESS  read-write
   STATUS      current
   DESCRIPTION
      "Path: efm.editConf.vlan.ipV6.icmpMessages.optionUnrecognized

       Possibilities:
               disabled   (0)
               enabled   (1)"
   ::= {er1646v2XEfmVlanEntry 705830912}

er1646v2XEfmVlanIpV6IcmpMessagesRedirect OBJECT-TYPE
   SYNTAX      INTEGER
               {
               disabled (0),
               enabled (1)
               }
   MAX-ACCESS  read-write
   STATUS      current
   DESCRIPTION
      "Path: efm.editConf.vlan.ipV6.icmpMessages.redirect

       Possibilities:
               disabled   (0)
               enabled   (1)"
   ::= {er1646v2XEfmVlanEntry 705832960}

er1646v2XEfmVlanBridgingAccList OBJECT-TYPE
   SYNTAX      DisplayString
   MAX-ACCESS  read-write
   STATUS      current
   DESCRIPTION
      "Path: efm.editConf.vlan.bridging.accessList"
   ::= {er1646v2XEfmVlanEntry 453246976}

er1646v2XEfmVlanBridgingInACL OBJECT-TYPE
   SYNTAX      DisplayString
   MAX-ACCESS  read-write
   STATUS      current
   DESCRIPTION
      "Path: efm.editConf.vlan.bridging.inAccessList"
   ::= {er1646v2XEfmVlanEntry 456916992}

er1646v2XEfmVlanBridgingTp OBJECT-TYPE
   SYNTAX      DisplayString
   MAX-ACCESS  read-write
   STATUS      current
   DESCRIPTION
      "Path: efm.editConf.vlan.bridging.trafficPolicy"
   ::= {er1646v2XEfmVlanEntry 454295552}

er1646v2XEfmVlanBridgingBrGrp OBJECT-TYPE
   SYNTAX      DisplayString
   MAX-ACCESS  read-write
   STATUS      current
   DESCRIPTION
      "Path: efm.editConf.vlan.bridging.bridgeGroup"
   ::= {er1646v2XEfmVlanEntry 454819840}

er1646v2XEfmVlanBridgingLimBC OBJECT-TYPE
   SYNTAX      INTEGER
               {
               disabled (0),
               enabled (1)
               }
   MAX-ACCESS  read-write
   STATUS      current
   DESCRIPTION
      "Path: efm.editConf.vlan.bridging.limitBroadcasts

       Possibilities:
               disabled   (0)
               enabled   (1)"
   ::= {er1646v2XEfmVlanEntry 455081984}

er1646v2XEfmVlanBridgingPrivateMode OBJECT-TYPE
   SYNTAX      INTEGER
               {
               disabled (0),
               enabled (1)
               }
   MAX-ACCESS  read-write
   STATUS      current
   DESCRIPTION
      "Path: efm.editConf.vlan.bridging.privateMode

       Possibilities:
               disabled   (0)
               enabled   (1)"
   ::= {er1646v2XEfmVlanEntry 459538432}

er1646v2XEfmVlanBridgingLearning OBJECT-TYPE
   SYNTAX      INTEGER
               {
               disabled (0),
               enabled (1)
               }
   MAX-ACCESS  read-write
   STATUS      current
   DESCRIPTION
      "Path: efm.editConf.vlan.bridging.learning

       Possibilities:
               disabled   (0)
               enabled   (1)"
   ::= {er1646v2XEfmVlanEntry 456130560}

er1646v2XEfmVlanBridgingMaxCacheSize OBJECT-TYPE
   SYNTAX      INTEGER
               {
               unlimited (0)
               }
   MAX-ACCESS  read-write
   STATUS      current
   DESCRIPTION
      "Path: efm.editConf.vlan.bridging.maxCacheSize

       Possibilities:
               unlimited   (0)"
   ::= {er1646v2XEfmVlanEntry 456392704}

er1646v2XEfmVlanBridgingRelearnDropOnRelearn OBJECT-TYPE
   SYNTAX      INTEGER
               {
               disabled (0),
               enabled (1)
               }
   MAX-ACCESS  read-write
   STATUS      current
   DESCRIPTION
      "Path: efm.editConf.vlan.bridging.relearn.dropOnRelearn

       Possibilities:
               disabled   (0)
               enabled   (1)"
   ::= {er1646v2XEfmVlanEntry 456655872}

er1646v2XEfmVlanBridgingRelearnShutdownThreshold OBJECT-TYPE
   SYNTAX      Integer32
   MAX-ACCESS  read-write
   STATUS      current
   DESCRIPTION
      "Path: efm.editConf.vlan.bridging.relearn.shutdownThreshold"
   ::= {er1646v2XEfmVlanEntry 456656896}

er1646v2XEfmVlanBridgingRelearnShutdownTime OBJECT-TYPE
   SYNTAX      TimeTicks
   MAX-ACCESS  read-write
   STATUS      current
   DESCRIPTION
      "Path: efm.editConf.vlan.bridging.relearn.shutdownTime

       Time in centi-second."
   ::= {er1646v2XEfmVlanEntry 456657920}

er1646v2XEfmVlanBridgingRelearnLoopDetection OBJECT-TYPE
   SYNTAX      INTEGER
               {
               disabled (0),
               passive (1),
               active (2)
               }
   MAX-ACCESS  read-write
   STATUS      current
   DESCRIPTION
      "Path: efm.editConf.vlan.bridging.relearn.loopDetection

       Possibilities:
               disabled   (0)
               passive   (1)
               active   (2)"
   ::= {er1646v2XEfmVlanEntry 456658944}

er1646v2XEfmVlanBridgingRelearnLoopDetectionInterval OBJECT-TYPE
   SYNTAX      TimeTicks
   MAX-ACCESS  read-write
   STATUS      current
   DESCRIPTION
      "Path: efm.editConf.vlan.bridging.relearn.loopDetectionInterval

       Time in centi-second."
   ::= {er1646v2XEfmVlanEntry 456659968}

er1646v2XEfmVlanBridgingVlanMemberShip OBJECT-TYPE
   SYNTAX      INTEGER
               {
               all (0),
               none (1),
               grouped (2)
               }
   MAX-ACCESS  read-write
   STATUS      current
   DESCRIPTION
      "Path: efm.editConf.vlan.bridging.vlanMemberShip

       Possibilities:
               all   (0)
               none   (1)
               grouped   (2)"
   ::= {er1646v2XEfmVlanEntry 457965568}

er1646v2XEfmVlanBridgingVlTUntaggedAction OBJECT-TYPE
   SYNTAX      INTEGER
               {
               discard (0),
               accept (1),
               tag (2)
               }
   MAX-ACCESS  read-write
   STATUS      current
   DESCRIPTION
      "Path: efm.editConf.vlan.bridging.vlanTagging.untagged.action

       Possibilities:
               discard   (0)
               accept   (1)
               tag   (2)"
   ::= {er1646v2XEfmVlanEntry 459055104}

er1646v2XEfmVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.untagged.tagInfo.tpid

       Possibilities:
               dot1Q   (33024)
               dot1ad   (34984)
               0x9100   (37120)
               0x9200   (37376)
               0x9300   (37632)"
   ::= {er1646v2XEfmVlanEntry 459059712}

er1646v2XEfmVlanBridgingVlTUntaggedTagInfoVid OBJECT-TYPE
   SYNTAX      Integer32
   MAX-ACCESS  read-write
   STATUS      current
   DESCRIPTION
      "Path: efm.editConf.vlan.bridging.vlanTagging.untagged.tagInfo.vid"
   ::= {er1646v2XEfmVlanEntry 459060224}

er1646v2XEfmVlanBridgingVlTUnknownVlansAction OBJECT-TYPE
   SYNTAX      INTEGER
               {
               discard (0),
               accept (1),
               tag (2)
               }
   MAX-ACCESS  read-write
   STATUS      current
   DESCRIPTION
      "Path: efm.editConf.vlan.bridging.vlanTagging.unknownVlans.action

       Possibilities:
               discard   (0)
               accept   (1)
               tag   (2)"
   ::= {er1646v2XEfmVlanEntry 459120640}

er1646v2XEfmVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.unknownVlans.tagInfo.tpid

       Possibilities:
               dot1Q   (33024)
               dot1ad   (34984)
               0x9100   (37120)
               0x9200   (37376)
               0x9300   (37632)"
   ::= {er1646v2XEfmVlanEntry 459125248}

er1646v2XEfmVlanBridgingVlTUnknownVlansTagInfoVid OBJECT-TYPE
   SYNTAX      Integer32
   MAX-ACCESS  read-write
   STATUS      current
   DESCRIPTION
      "Path: efm.editConf.vlan.bridging.vlanTagging.unknownVlans.tagInfo.vid"
   ::= {er1646v2XEfmVlanEntry 459125760}

er1646v2XEfmVlanBridgingDot1adType OBJECT-TYPE
   SYNTAX      INTEGER
               {
               slOPTg (0),
               cPort (4),
               sPort (1),
               nni (2)
               }
   MAX-ACCESS  read-write
   STATUS      current
   DESCRIPTION
      "Path: efm.editConf.vlan.bridging.dot1ad.type

       Possibilities:
               <OPT>   (0)
               cPort   (4)
               sPort   (1)
               nni   (2)"
   ::= {er1646v2XEfmVlanEntry 460850176}

er1646v2XEfmVlanBridgingPriority OBJECT-TYPE
   SYNTAX      Integer32
   MAX-ACCESS  read-write
   STATUS      current
   DESCRIPTION
      "Path: efm.editConf.vlan.bridging.priority"
   ::= {er1646v2XEfmVlanEntry 453509120}

er1646v2XEfmVlanBridgingPathCost OBJECT-TYPE
   SYNTAX      Integer32
   MAX-ACCESS  read-write
   STATUS      current
   DESCRIPTION
      "Path: efm.editConf.vlan.bridging.pathCost"
   ::= {er1646v2XEfmVlanEntry 453771264}

er1646v2XEfmVlanBridgingInternalPathCost OBJECT-TYPE
   SYNTAX      Integer32
   MAX-ACCESS  read-write
   STATUS      current
   DESCRIPTION
      "Path: efm.editConf.vlan.bridging.internalPathCost"
   ::= {er1646v2XEfmVlanEntry 457703424}

er1646v2XEfmVlanBridgingTCD OBJECT-TYPE
   SYNTAX      INTEGER
               {
               disabled (0),
               enabled (1)
               }
   MAX-ACCESS  read-write
   STATUS      current
   DESCRIPTION
      "Path: efm.editConf.vlan.bridging.topologyChangeDetection

       Possibilities:
               disabled   (0)
               enabled   (1)"
   ::= {er1646v2XEfmVlanEntry 454033408}

er1646v2XEfmVlanBridgingRestrictedRole OBJECT-TYPE
   SYNTAX      INTEGER
               {
               disabled (0),
               enabled (1)
               }
   MAX-ACCESS  read-write
   STATUS      current
   DESCRIPTION
      "Path: efm.editConf.vlan.bridging.restrictedRole

       Possibilities:
               disabled   (0)
               enabled   (1)"
   ::= {er1646v2XEfmVlanEntry 458227712}

er1646v2XEfmVlanBridgingAdminEdge OBJECT-TYPE
   SYNTAX      INTEGER
               {
               disabled (0),
               enabled (1)
               }
   MAX-ACCESS  read-write
   STATUS      current
   DESCRIPTION
      "Path: efm.editConf.vlan.bridging.adminEdge

       Possibilities:
               disabled   (0)
               enabled   (1)"
   ::= {er1646v2XEfmVlanEntry 457179136}

er1646v2XEfmVlanBridgingOamMacDeviceMac OBJECT-TYPE
   SYNTAX      DisplayString
   MAX-ACCESS  read-write
   STATUS      current
   DESCRIPTION
      "Path: efm.editConf.vlan.bridging.ethOam.macAddress.deviceMac"
   ::= {er1646v2XEfmVlanEntry 458506496}

er1646v2XEfmVlanBridgingOamMacUserMac OBJECT-TYPE
   SYNTAX      OCTET STRING
   MAX-ACCESS  read-write
   STATUS      current
   DESCRIPTION
      "Path: efm.editConf.vlan.bridging.ethOam.macAddress.userMac

       MAC address."
   ::= {er1646v2XEfmVlanEntry 458506368}

er1646v2XEfmVlanBridgingOamMacBridgeMac OBJECT-TYPE
   SYNTAX      DisplayString
   MAX-ACCESS  read-write
   STATUS      current
   DESCRIPTION
      "Path: efm.editConf.vlan.bridging.ethOam.macAddress.bridgeMac"
   ::= {er1646v2XEfmVlanEntry 458506432}

er1646v2XEfmVlanBridgingMgmtInline OBJECT-TYPE
   SYNTAX      INTEGER
               {
               disabled (0),
               enabled (1)
               }
   MAX-ACCESS  read-write
   STATUS      current
   DESCRIPTION
      "Path: efm.editConf.vlan.bridging.mgmtInline

       Possibilities:
               disabled   (0)
               enabled   (1)"
   ::= {er1646v2XEfmVlanEntry 458752000}

er1646v2XEfmVlanBridgingL2ptMode OBJECT-TYPE
   SYNTAX      INTEGER
               {
               disabled (0),
               enabled (1)
               }
   MAX-ACCESS  read-write
   STATUS      current
   DESCRIPTION
      "Path: efm.editConf.vlan.bridging.l2ProtTunnel.mode

       Possibilities:
               disabled   (0)
               enabled   (1)"
   ::= {er1646v2XEfmVlanEntry 459292672}

er1646v2XEfmVlanBridgingL2ptProtocols OBJECT-TYPE
   SYNTAX      Integer32
   MAX-ACCESS  read-write
   STATUS      current
   DESCRIPTION
      "Path: efm.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2XEfmVlanEntry 459309056}

er1646v2XEfmVlanBridgingL2ptDestMac OBJECT-TYPE
   SYNTAX      OCTET STRING
   MAX-ACCESS  read-write
   STATUS      current
   DESCRIPTION
      "Path: efm.editConf.vlan.bridging.l2ProtTunnel.destinationMac

       MAC address."
   ::= {er1646v2XEfmVlanEntry 459325440}

er1646v2XEfmVlanBridgingL2ptCos OBJECT-TYPE
   SYNTAX      INTEGER
               {
               unchanged (255)
               }
   MAX-ACCESS  read-write
   STATUS      current
   DESCRIPTION
      "Path: efm.editConf.vlan.bridging.l2ProtTunnel.cos

       Possibilities:
               unchanged   (255)"
   ::= {er1646v2XEfmVlanEntry 459341824}

er1646v2XEfmVlanBridgingL2ptDropThrStp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.stp

       unit name = packets/sec

       Possibilities:
               unlimited   (0)"
   ::= {er1646v2XEfmVlanEntry 459358272}

er1646v2XEfmVlanBridgingL2ptDropThrLldp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.lldp

       unit name = packets/sec

       Possibilities:
               unlimited   (0)"
   ::= {er1646v2XEfmVlanEntry 459358336}

er1646v2XEfmVlanBridgingL2ptDropThrOam OBJECT-TYPE
   SYNTAX      INTEGER
               {
               unlimited (0)
               }
   UNITS       "packets/sec"
   MAX-ACCESS  read-write
   STATUS      current
   DESCRIPTION
      "Path: efm.editConf.vlan.bridging.l2ProtTunnel.dropThresholds.oam

       unit name = packets/sec

       Possibilities:
               unlimited   (0)"
   ::= {er1646v2XEfmVlanEntry 459358400}

er1646v2XEfmVlanBridgingL2ptDropThrCdp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.cdp

       unit name = packets/sec

       Possibilities:
               unlimited   (0)"
   ::= {er1646v2XEfmVlanEntry 459358464}

er1646v2XEfmVlanBridgingL2ptDropThrVtp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.vtp

       unit name = packets/sec

       Possibilities:
               unlimited   (0)"
   ::= {er1646v2XEfmVlanEntry 459358528}

er1646v2XEfmVlanBridgingL2ptDropThrLacp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.lacp

       unit name = packets/sec

       Possibilities:
               unlimited   (0)"
   ::= {er1646v2XEfmVlanEntry 459358592}

er1646v2XEfmVlanBridgingL2ptDropThrEfmOam OBJECT-TYPE
   SYNTAX      INTEGER
               {
               unlimited (0)
               }
   UNITS       "packets/sec"
   MAX-ACCESS  read-write
   STATUS      current
   DESCRIPTION
      "Path: efm.editConf.vlan.bridging.l2ProtTunnel.dropThresholds.efmOam

       unit name = packets/sec

       Possibilities:
               unlimited   (0)"
   ::= {er1646v2XEfmVlanEntry 459358656}

er1646v2XEfmVlanBridgingL2ptDropThrPvst OBJECT-TYPE
   SYNTAX      INTEGER
               {
               unlimited (0)
               }
   UNITS       "packets/sec"
   MAX-ACCESS  read-write
   STATUS      current
   DESCRIPTION
      "Path: efm.editConf.vlan.bridging.l2ProtTunnel.dropThresholds.pvst

       unit name = packets/sec

       Possibilities:
               unlimited   (0)"
   ::= {er1646v2XEfmVlanEntry 459358720}

er1646v2XEfmVlanBridgingL2ptDropThrMmrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.mmrp

       unit name = packets/sec

       Possibilities:
               unlimited   (0)"
   ::= {er1646v2XEfmVlanEntry 459358784}

er1646v2XEfmVlanBridgingL2ptDropThrMvrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.mvrp

       unit name = packets/sec

       Possibilities:
               unlimited   (0)"
   ::= {er1646v2XEfmVlanEntry 459358848}

er1646v2XEfmVlanBridgingL2ptDropThrGvrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.gvrp

       unit name = packets/sec

       Possibilities:
               unlimited   (0)"
   ::= {er1646v2XEfmVlanEntry 459358912}

er1646v2XEfmVlanBridgingL2ptDropThrGmrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.gmrp

       unit name = packets/sec

       Possibilities:
               unlimited   (0)"
   ::= {er1646v2XEfmVlanEntry 459358976}

er1646v2XEfmVlanBridgingL2ptDropThrDtp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.dtp

       unit name = packets/sec

       Possibilities:
               unlimited   (0)"
   ::= {er1646v2XEfmVlanEntry 459359040}

er1646v2XEfmVlanBridgingL2ptDropThrPagp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.pagp

       unit name = packets/sec

       Possibilities:
               unlimited   (0)"
   ::= {er1646v2XEfmVlanEntry 459359104}

er1646v2XEfmVlanBridgingL2ptDropThrUdld OBJECT-TYPE
   SYNTAX      INTEGER
               {
               unlimited (0)
               }
   UNITS       "packets/sec"
   MAX-ACCESS  read-write
   STATUS      current
   DESCRIPTION
      "Path: efm.editConf.vlan.bridging.l2ProtTunnel.dropThresholds.udld

       unit name = packets/sec

       Possibilities:
               unlimited   (0)"
   ::= {er1646v2XEfmVlanEntry 459359168}

er1646v2XEfmVlanVlanVid OBJECT-TYPE
   SYNTAX      INTEGER
               {
               untagged (0),
               prioTagged (4096),
               notUsed (4097)
               }
   MAX-ACCESS  read-write
   STATUS      current
   DESCRIPTION
      "Path: efm.editConf.vlan.vlan.vid

       Possibilities:
               untagged   (0)
               prioTagged   (4096)
               notUsed   (4097)"
   ::= {er1646v2XEfmVlanEntry 234946560}

er1646v2XEfmVlanVlanVidExtensionSingle OBJECT-TYPE
   SYNTAX      OCTET STRING
   MAX-ACCESS  read-write
   STATUS      current
   DESCRIPTION
      "Path: efm.editConf.vlan.vlan.vidExtension.single"
   ::= {er1646v2XEfmVlanEntry 235340032}

er1646v2XEfmVlanVlanVidExtensionEndVid OBJECT-TYPE
   SYNTAX      Integer32
   MAX-ACCESS  read-write
   STATUS      current
   DESCRIPTION
      "Path: efm.editConf.vlan.vlan.vidExtension.endVid"
   ::= {er1646v2XEfmVlanEntry 235340288}

er1646v2XEfmVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.tpid

       Possibilities:
               dot1Q   (33024)
               dot1ad   (34984)
               0x9100   (37120)
               0x9200   (37376)
               0x9300   (37632)"
   ::= {er1646v2XEfmVlanEntry 241238016}

er1646v2XEfmVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: efm.editConf.vlan.vlan.tagSignificance

       Possibilities:
               global   (0)
               local   (1)
               sVlan   (2)
               sVlanGlobal   (6)
               cVlan   (3)
               scVlan   (5)
               cVlanLocal   (4)"
   ::= {er1646v2XEfmVlanEntry 235012096}

er1646v2XEfmVlanVlanChTos OBJECT-TYPE
   SYNTAX      INTEGER
               {
               disabled (0),
               enabled (1)
               }
   MAX-ACCESS  read-write
   STATUS      current
   DESCRIPTION
      "Path: efm.editConf.vlan.vlan.changeTos

       Possibilities:
               disabled   (0)
               enabled   (1)"
   ::= {er1646v2XEfmVlanEntry 235208704}

er1646v2XEfmVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235143424}

er1646v2XEfmVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235143680}

er1646v2XEfmVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235143936}

er1646v2XEfmVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235144192}

er1646v2XEfmVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235144448}

er1646v2XEfmVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235144704}

er1646v2XEfmVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235144960}

er1646v2XEfmVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2XEfmVlanEntry 235145216}

er1646v2XEfmVlanVlanTxCos OBJECT-TYPE
   SYNTAX      INTEGER
               {
               tosCosMap (8),
               queueCosMap (16)
               }
   MAX-ACCESS  read-write
   STATUS      current
   DESCRIPTION
      "Path: efm.editConf.vlan.vlan.txCos

       Possibilities:
               tosCosMap   (8)
               queueCosMap   (16)"
   ::= {er1646v2XEfmVlanEntry 235077632}

er1646v2XEfmVlanVlanCCMapP0 OBJECT-TYPE
   SYNTAX      Integer32
   MAX-ACCESS  read-write
   STATUS      current
   DESCRIPTION
      "Path: efm.editConf.vlan.vlan.cosCosMap.p0"
   ::= {er1646v2XEfmVlanEntry 241303808}

er1646v2XEfmVlanVlanCCMapP1 OBJECT-TYPE
   SYNTAX      Integer32
   MAX-ACCESS  read-write
   STATUS      current
   DESCRIPTION
      "Path: efm.editConf.vlan.vlan.cosCosMap.p1"
   ::= {er1646v2XEfmVlanEntry 241304064}

er1646v2XEfmVlanVlanCCMapP2 OBJECT-TYPE
   SYNTAX      Integer32
   MAX-ACCESS  read-write
   STATUS      current
   DESCRIPTION
      "Path: efm.editConf.vlan.vlan.cosCosMap.p2"
   ::= {er1646v2XEfmVlanEntry 241304320}

er1646v2XEfmVlanVlanCCMapP3 OBJECT-TYPE
   SYNTAX      Integer32
   MAX-ACCESS  read-write
   STATUS      current
   DESCRIPTION
      "Path: efm.editConf.vlan.vlan.cosCosMap.p3"
   ::= {er1646v2XEfmVlanEntry 241304576}

er1646v2XEfmVlanVlanCCMapP4 OBJECT-TYPE
   SYNTAX      Integer32
   MAX-ACCESS  read-write
   STATUS      current
   DESCRIPTION
      "Path: efm.editConf.vlan.vlan.cosCosMap.p4"
   ::= {er1646v2XEfmVlanEntry 241304832}

er1646v2XEfmVlanVlanCCMapP5 OBJECT-TYPE
   SYNTAX      Integer32
   MAX-ACCESS  read-write
   STATUS      current
   DESCRIPTION
      "Path: efm.editConf.vlan.vlan.cosCosMap.p5"
   ::= {er1646v2XEfmVlanEntry 241305088}

er1646v2XEfmVlanVlanCCMapP6 OBJECT-TYPE
   SYNTAX      Integer32
   MAX-ACCESS  read-write
   STATUS      current
   DESCRIPTION
      "Path: efm.editConf.vlan.vlan.cosCosMap.p6"
   ::= {er1646v2XEfmVlanEntry 241305344}

er1646v2XEfmVlanVlanCCMapP7 OBJECT-TYPE
   SYNTAX      Integer32
   MAX-ACCESS  read-write
   STATUS      current
   DESCRIPTION
      "Path: efm.editConf.vlan.vlan.cosCosMap.p7"
   ::= {er1646v2XEfmVlanEntry 241305600}

er1646v2XEfmVlanVlanQCMapQueue1 OBJECT-TYPE
   SYNTAX      Integer32
   MAX-ACCESS  read-write
   STATUS      current
   DESCRIPTION
      "Path: efm.editConf.vlan.vlan.queueCosMap.queue1"
   ::= {er1646v2XEfmVlanEntry 241434880}

er1646v2XEfmVlanVlanQCMapQueue2 OBJECT-TYPE
   SYNTAX      Integer32
   MAX-ACCESS  read-write
   STATUS      current
   DESCRIPTION
      "Path: efm.editConf.vlan.vlan.queueCosMap.queue2"
   ::= {er1646v2XEfmVlanEntry 241435136}

er1646v2XEfmVlanVlanQCMapQueue3 OBJECT-TYPE
   SYNTAX      Integer32
   MAX-ACCESS  read-write
   STATUS      current
   DESCRIPTION
      "Path: efm.editConf.vlan.vlan.queueCosMap.queue3"
   ::= {er1646v2XEfmVlanEntry 241435392}

er1646v2XEfmVlanVlanQCMapQueue4 OBJECT-TYPE
   SYNTAX      Integer32
   MAX-ACCESS  read-write
   STATUS      current
   DESCRIPTION
      "Path: efm.editConf.vlan.vlan.queueCosMap.queue4"
   ::= {er1646v2XEfmVlanEntry 241435648}

er1646v2XEfmVlanVlanQCMapQueue5 OBJECT-TYPE
   SYNTAX      Integer32
   MAX-ACCESS  read-write
   STATUS      current
   DESCRIPTION
      "Path: efm.editConf.vlan.vlan.queueCosMap.queue5"
   ::= {er1646v2XEfmVlanEntry 241435904}

er1646v2XEfmVlanVlanQCMapLowDelayQueue OBJECT-TYPE
   SYNTAX      Integer32
   MAX-ACCESS  read-write
   STATUS      current
   DESCRIPTION
      "Path: efm.editConf.vlan.vlan.queueCosMap.lowDelayQueue"
   ::= {er1646v2XEfmVlanEntry 241436160}

er1646v2XEfmVlanVlanQCMapLowDelay2Queue OBJECT-TYPE
   SYNTAX      Integer32
   MAX-ACCESS  read-write
   STATUS      current
   DESCRIPTION
      "Path: efm.editConf.vlan.vlan.queueCosMap.lowDelay2Queue"
   ::= {er1646v2XEfmVlanEntry 241436416}

er1646v2XEfmVlanVlanQCMapSystemQueue OBJECT-TYPE
   SYNTAX      Integer32
   MAX-ACCESS  read-write
   STATUS      current
   DESCRIPTION
      "Path: efm.editConf.vlan.vlan.queueCosMap.systemQueue"
   ::= {er1646v2XEfmVlanEntry 241436672}

er1646v2XEfmVlanVlanQinQSVid OBJECT-TYPE
   SYNTAX      Integer32
   MAX-ACCESS  read-write
   STATUS      current
   DESCRIPTION
      "Path: efm.editConf.vlan.vlan.tunnel.sVid"
   ::= {er1646v2XEfmVlanEntry 241172736}

er1646v2XEfmVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.tunnel.sTpid

       Possibilities:
               dot1Q   (33024)
               dot1ad   (34984)
               0x9100   (37120)
               0x9200   (37376)
               0x9300   (37632)"
   ::= {er1646v2XEfmVlanEntry 241172992}

er1646v2XEfmVlanVlanArpTimeOut OBJECT-TYPE
   SYNTAX      TimeTicks
   MAX-ACCESS  read-write
   STATUS      current
   DESCRIPTION
      "Path: efm.editConf.vlan.vlan.arp.timeOut

       Time in centi-second."
   ::= {er1646v2XEfmVlanEntry 235277312}

er1646v2XEfmVlanVlanArpProxyArp OBJECT-TYPE
   SYNTAX      INTEGER
               {
               disabled (0),
               enabled (1)
               }
   MAX-ACCESS  read-write
   STATUS      current
   DESCRIPTION
      "Path: efm.editConf.vlan.vlan.arp.proxyArp

       Possibilities:
               disabled   (0)
               enabled   (1)"
   ::= {er1646v2XEfmVlanEntry 235287040}

er1646v2XEfmVlanBandwidthMode OBJECT-TYPE
   SYNTAX      INTEGER
               {
               reshaping (1),
               policing (2),
               policingReshape (3)
               }
   MAX-ACCESS  read-write
   STATUS      current
   DESCRIPTION
      "Path: efm.editConf.vlan.bandwidth.mode

       Possibilities:
               reshaping   (1)
               policing   (2)
               policingReshape   (3)"
   ::= {er1646v2XEfmVlanEntry 148897792}

er1646v2XEfmVlanBandwidthCir OBJECT-TYPE
   SYNTAX      Integer32
   MAX-ACCESS  read-write
   STATUS      current
   DESCRIPTION
      "Path: efm.editConf.vlan.bandwidth.cir"
   ::= {er1646v2XEfmVlanEntry 135266304}

er1646v2XEfmVlanBandwidthEir OBJECT-TYPE
   SYNTAX      Integer32
   MAX-ACCESS  read-write
   STATUS      current
   DESCRIPTION
      "Path: efm.editConf.vlan.bandwidth.eir"
   ::= {er1646v2XEfmVlanEntry 141557760}

er1646v2XEfmVlanBandwidthUnit OBJECT-TYPE
   SYNTAX      INTEGER
               {
               bitssec (1),
               percent (2)
               }
   MAX-ACCESS  read-write
   STATUS      current
   DESCRIPTION
      "Path: efm.editConf.vlan.bandwidth.unit

       Possibilities:
               bits/sec   (1)
               percent   (2)"
   ::= {er1646v2XEfmVlanEntry 139460608}

er1646v2XEfmVlanBandwidthTc OBJECT-TYPE
   SYNTAX      INTEGER
               {
               auto (0)
               }
   MAX-ACCESS  read-write
   STATUS      current
   DESCRIPTION
      "Path: efm.editConf.vlan.bandwidth.tc

       Possibilities:
               auto   (0)"
   ::= {er1646v2XEfmVlanEntry 140509184}

er1646v2XEfmVlanBandwidthTcFactor OBJECT-TYPE
   SYNTAX      INTEGER
               {
               ms (10),
               s100us (1)
               }
   MAX-ACCESS  read-write
   STATUS      current
   DESCRIPTION
      "Path: efm.editConf.vlan.bandwidth.tcFactor

       Possibilities:
               ms   (10)
               *100us   (1)"
   ::= {er1646v2XEfmVlanEntry 142606336}

er1646v2XEfmVlanBandwidthCorrType OBJECT-TYPE
   SYNTAX      INTEGER
               {
               noCorrection (0),
               predefined (1),
               manual (2)
               }
   MAX-ACCESS  read-write
   STATUS      current
   DESCRIPTION
      "Path: efm.editConf.vlan.bandwidth.correction.type

       Possibilities:
               noCorrection   (0)
               predefined   (1)
               manual   (2)"
   ::= {er1646v2XEfmVlanEntry 136445952}

er1646v2XEfmVlanBandwidthCorrPredefEncapsFrameRelay OBJECT-TYPE
   SYNTAX      DisplayString
   MAX-ACCESS  read-write
   STATUS      current
   DESCRIPTION
      "Path: efm.editConf.vlan.bandwidth.correction.predefined.encapsulation.frameRelay"
   ::= {er1646v2XEfmVlanEntry 136594432}

er1646v2XEfmVlanBandwidthCorrPredefEncapsPpp OBJECT-TYPE
   SYNTAX      DisplayString
   MAX-ACCESS  read-write
   STATUS      current
   DESCRIPTION
      "Path: efm.editConf.vlan.bandwidth.correction.predefined.encapsulation.ppp"
   ::= {er1646v2XEfmVlanEntry 136595456}

er1646v2XEfmVlanBandwidthCorrPredefEncapsAtmHl OBJECT-TYPE
   SYNTAX      INTEGER
               {
               rfc2684 (0),
               ppp (1),
               pppOverEthernet (2)
               }
   MAX-ACCESS  read-write
   STATUS      current
   DESCRIPTION
      "Path: efm.editConf.vlan.bandwidth.correction.predefined.encapsulation.atm.higherLayer

       Possibilities:
               rfc2684   (0)
               ppp   (1)
               pppOverEthernet   (2)"
   ::= {er1646v2XEfmVlanEntry 136596608}

er1646v2XEfmVlanBandwidthCorrPredefEncapsAtmMp OBJECT-TYPE
   SYNTAX      INTEGER
               {
               llcEncapsulation (0),
               vcMultiplexing (1)
               }
   MAX-ACCESS  read-write
   STATUS      current
   DESCRIPTION
      "Path: efm.editConf.vlan.bandwidth.correction.predefined.encapsulation.atm.multiProtocol

       Possibilities:
               llcEncapsulation   (0)
               vcMultiplexing   (1)"
   ::= {er1646v2XEfmVlanEntry 136596736}

er1646v2XEfmVlanBandwidthCorrPredefEncapsHdlc OBJECT-TYPE
   SYNTAX      DisplayString
   MAX-ACCESS  read-write
   STATUS      current
   DESCRIPTION
      "Path: efm.editConf.vlan.bandwidth.correction.predefined.encapsulation.hdlc"
   ::= {er1646v2XEfmVlanEntry 136597504}

er1646v2XEfmVlanBandwidthCorrPredefEncapsEfmFs OBJECT-TYPE
   SYNTAX      Integer32
   MAX-ACCESS  read-write
   STATUS      current
   DESCRIPTION
      "Path: efm.editConf.vlan.bandwidth.correction.predefined.encapsulation.efm.fragmentSize"
   ::= {er1646v2XEfmVlanEntry 136598656}

er1646v2XEfmVlanBandwidthCorrPredefEncapsEfmIb OBJECT-TYPE
   SYNTAX      Integer32
   MAX-ACCESS  read-write
   STATUS      current
   DESCRIPTION
      "Path: efm.editConf.vlan.bandwidth.correction.predefined.encapsulation.efm.idleBytes"
   ::= {er1646v2XEfmVlanEntry 136598784}

er1646v2XEfmVlanBandwidthCorrPredefMode OBJECT-TYPE
   SYNTAX      INTEGER
               {
               routing (0),
               bridging (1)
               }
   MAX-ACCESS  read-write
   STATUS      current
   DESCRIPTION
      "Path: efm.editConf.vlan.bandwidth.correction.predefined.mode

       Possibilities:
               routing   (0)
               bridging   (1)"
   ::= {er1646v2XEfmVlanEntry 136609792}

er1646v2XEfmVlanBandwidthCorrManualOverhead OBJECT-TYPE
   SYNTAX      Integer32
   MAX-ACCESS  read-write
   STATUS      current
   DESCRIPTION
      "Path: efm.editConf.vlan.bandwidth.correction.manual.overhead"
   ::= {er1646v2XEfmVlanEntry 136708608}

er1646v2XEfmVlanBandwidthCorrManualFrameData OBJECT-TYPE
   SYNTAX      Counter32
   MAX-ACCESS  read-write
   STATUS      current
   DESCRIPTION
      "Path: efm.editConf.vlan.bandwidth.correction.manual.frameData

       32 bit unsigned wrappable counter."
   ::= {er1646v2XEfmVlanEntry 136709120}

er1646v2XEfmVlanBandwidthCorrManualFrameHeader OBJECT-TYPE
   SYNTAX      Counter32
   MAX-ACCESS  read-write
   STATUS      current
   DESCRIPTION
      "Path: efm.editConf.vlan.bandwidth.correction.manual.frameHeader

       32 bit unsigned wrappable counter."
   ::= {er1646v2XEfmVlanEntry 136709632}

er1646v2XEfmVlanBandwidthMaxFifoQLen OBJECT-TYPE
   SYNTAX      Integer32
   MAX-ACCESS  read-write
   STATUS      current
   DESCRIPTION
      "Path: efm.editConf.vlan.bandwidth.maxFifoQLen"
   ::= {er1646v2XEfmVlanEntry 137363456}

er1646v2XEfmVlanBandwidthDeFlagCir OBJECT-TYPE
   SYNTAX      INTEGER
               {
               allowed (1),
               notAllowed (2)
               }
   MAX-ACCESS  read-write
   STATUS      current
   DESCRIPTION
      "Path: efm.editConf.vlan.bandwidth.deFlag.cir

       Possibilities:
               allowed   (1)
               notAllowed   (2)"
   ::= {er1646v2XEfmVlanEntry 147853312}

er1646v2XEfmVlanBandwidthDeFlagEir OBJECT-TYPE
   SYNTAX      INTEGER
               {
               allowed (1),
               notAllowed (2)
               }
   MAX-ACCESS  read-write
   STATUS      current
   DESCRIPTION
      "Path: efm.editConf.vlan.bandwidth.deFlag.eir

       Possibilities:
               allowed   (1)
               notAllowed   (2)"
   ::= {er1646v2XEfmVlanEntry 147857408}

er1646v2XEfmVlanBandwidthDeFlagViolate OBJECT-TYPE
   SYNTAX      INTEGER
               {
               allowed (1),
               notAllowed (2)
               }
   MAX-ACCESS  read-write
   STATUS      current
   DESCRIPTION
      "Path: efm.editConf.vlan.bandwidth.deFlag.violate

       Possibilities:
               allowed   (1)
               notAllowed   (2)"
   ::= {er1646v2XEfmVlanEntry 147861504}

er1646v2XEfmVlanBandwidthActCirActNone OBJECT-TYPE
   SYNTAX      OCTET STRING
   MAX-ACCESS  read-write
   STATUS      current
   DESCRIPTION
      "Path: efm.editConf.vlan.bandwidth.action.cirAction.none"
   ::= {er1646v2XEfmVlanEntry 150085632}

er1646v2XEfmVlanBandwidthActCirActEthCos1 OBJECT-TYPE
   SYNTAX      INTEGER
               {
               unchanged (256)
               }
   MAX-ACCESS  read-write
   STATUS      current
   DESCRIPTION
      "Path: efm.editConf.vlan.bandwidth.action.cirAction.ethernet.cosDepth1

       Possibilities:
               unchanged   (256)"
   ::= {er1646v2XEfmVlanEntry 150094080}

er1646v2XEfmVlanBandwidthActCirActEthDei1 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth1

       Possibilities:
               unchanged   (255)
               clear   (0)
               set   (1)"
   ::= {er1646v2XEfmVlanEntry 150099200}

er1646v2XEfmVlanBandwidthActCirActEthCos2 OBJECT-TYPE
   SYNTAX      INTEGER
               {
               unchanged (256)
               }
   MAX-ACCESS  read-write
   STATUS      current
   DESCRIPTION
      "Path: efm.editConf.vlan.bandwidth.action.cirAction.ethernet.cosDepth2

       Possibilities:
               unchanged   (256)"
   ::= {er1646v2XEfmVlanEntry 150094336}

er1646v2XEfmVlanBandwidthActCirActEthDei2 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth2

       Possibilities:
               unchanged   (255)
               clear   (0)
               set   (1)"
   ::= {er1646v2XEfmVlanEntry 150099456}

er1646v2XEfmVlanBandwidthActCirActEthCos3 OBJECT-TYPE
   SYNTAX      INTEGER
               {
               unchanged (256)
               }
   MAX-ACCESS  read-write
   STATUS      current
   DESCRIPTION
      "Path: efm.editConf.vlan.bandwidth.action.cirAction.ethernet.cosDepth3

       Possibilities:
               unchanged   (256)"
   ::= {er1646v2XEfmVlanEntry 150094592}

er1646v2XEfmVlanBandwidthActCirActEthDei3 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth3

       Possibilities:
               unchanged   (255)
               clear   (0)
               set   (1)"
   ::= {er1646v2XEfmVlanEntry 150099712}

er1646v2XEfmVlanBandwidthActCirActEthCos4 OBJECT-TYPE
   SYNTAX      INTEGER
               {
               unchanged (256)
               }
   MAX-ACCESS  read-write
   STATUS      current
   DESCRIPTION
      "Path: efm.editConf.vlan.bandwidth.action.cirAction.ethernet.cosDepth4

       Possibilities:
               unchanged   (256)"
   ::= {er1646v2XEfmVlanEntry 150094848}

er1646v2XEfmVlanBandwidthActCirActEthDei4 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth4

       Possibilities:
               unchanged   (255)
               clear   (0)
               set   (1)"
   ::= {er1646v2XEfmVlanEntry 150099968}

er1646v2XEfmVlanBandwidthActCirActEthCos5 OBJECT-TYPE
   SYNTAX      INTEGER
               {
               unchanged (256)
               }
   MAX-ACCESS  read-write
   STATUS      current
   DESCRIPTION
      "Path: efm.editConf.vlan.bandwidth.action.cirAction.ethernet.cosDepth5

       Possibilities:
               unchanged   (256)"
   ::= {er1646v2XEfmVlanEntry 150095104}

er1646v2XEfmVlanBandwidthActCirActEthDei5 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth5

       Possibilities:
               unchanged   (255)
               clear   (0)
               set   (1)"
   ::= {er1646v2XEfmVlanEntry 150100224}

er1646v2XEfmVlanBandwidthActCirActEthCos6 OBJECT-TYPE
   SYNTAX      INTEGER
               {
               unchanged (256)
               }
   MAX-ACCESS  read-write
   STATUS      current
   DESCRIPTION
      "Path: efm.editConf.vlan.bandwidth.action.cirAction.ethernet.cosDepth6

       Possibilities:
               unchanged   (256)"
   ::= {er1646v2XEfmVlanEntry 150095360}

er1646v2XEfmVlanBandwidthActCirActEthDei6 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth6

       Possibilities:
               unchanged   (255)
               clear   (0)
               set   (1)"
   ::= {er1646v2XEfmVlanEntry 150100480}

er1646v2XEfmVlanBandwidthActCirActEthCos7 OBJECT-TYPE
   SYNTAX      INTEGER
               {
               unchanged (256)
               }
   MAX-ACCESS  read-write
   STATUS      current
   DESCRIPTION
      "Path: efm.editConf.vlan.bandwidth.action.cirAction.ethernet.cosDepth7

       Possibilities:
               unchanged   (256)"
   ::= {er1646v2XEfmVlanEntry 150095616}

er1646v2XEfmVlanBandwidthActCirActEthDei7 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth7

       Possibilities:
               unchanged   (255)
               clear   (0)
               set   (1)"
   ::= {er1646v2XEfmVlanEntry 150100736}

er1646v2XEfmVlanBandwidthActCirActEthCos8 OBJECT-TYPE
   SYNTAX      INTEGER
               {
               unchanged (256)
               }
   MAX-ACCESS  read-write
   STATUS      current
   DESCRIPTION
      "Path: efm.editConf.vlan.bandwidth.action.cirAction.ethernet.cosDepth8

       Possibilities:
               unchanged   (256)"
   ::= {er1646v2XEfmVlanEntry 150095872}

er1646v2XEfmVlanBandwidthActCirActEthDei8 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth8

       Possibilities:
               unchanged   (255)
               clear   (0)
               set   (1)"
   ::= {er1646v2XEfmVlanEntry 150100992}

er1646v2XEfmVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150096128}

er1646v2XEfmVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150096384}

er1646v2XEfmVlanBandwidthActCirActEthDrpLev OBJECT-TYPE
   SYNTAX      INTEGER
               {
               unchanged (0)
               }
   MAX-ACCESS  read-write
   STATUS      current
   DESCRIPTION
      "Path: efm.editConf.vlan.bandwidth.action.cirAction.ethernet.dropLevel

       Possibilities:
               unchanged   (0)"
   ::= {er1646v2XEfmVlanEntry 150096640}

er1646v2XEfmVlanBandwidthActCirActEthDeFlag OBJECT-TYPE
   SYNTAX      INTEGER
               {
               unchanged (255),
               clear (0),
               set (1)
               }
   MAX-ACCESS  read-write
   STATUS      current
   DESCRIPTION
      "Path: efm.editConf.vlan.bandwidth.action.cirAction.ethernet.deFlag

       Possibilities:
               unchanged   (255)
               clear   (0)
               set   (1)"
   ::= {er1646v2XEfmVlanEntry 150097408}

er1646v2XEfmVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150120704}

er1646v2XEfmVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150120960}

er1646v2XEfmVlanBandwidthActCirActIpDrpLev OBJECT-TYPE
   SYNTAX      INTEGER
               {
               unchanged (0)
               }
   MAX-ACCESS  read-write
   STATUS      current
   DESCRIPTION
      "Path: efm.editConf.vlan.bandwidth.action.cirAction.ip.dropLevel

       Possibilities:
               unchanged   (0)"
   ::= {er1646v2XEfmVlanEntry 150121216}

er1646v2XEfmVlanBandwidthActCirActIpDeFlag OBJECT-TYPE
   SYNTAX      INTEGER
               {
               unchanged (255),
               clear (0),
               set (1)
               }
   MAX-ACCESS  read-write
   STATUS      current
   DESCRIPTION
      "Path: efm.editConf.vlan.bandwidth.action.cirAction.ip.deFlag

       Possibilities:
               unchanged   (255)
               clear   (0)
               set   (1)"
   ::= {er1646v2XEfmVlanEntry 150121984}

er1646v2XEfmVlanBandwidthActEirActNone OBJECT-TYPE
   SYNTAX      OCTET STRING
   MAX-ACCESS  read-write
   STATUS      current
   DESCRIPTION
      "Path: efm.editConf.vlan.bandwidth.action.eirAction.none"
   ::= {er1646v2XEfmVlanEntry 150216704}

er1646v2XEfmVlanBandwidthActEirActEthCos1 OBJECT-TYPE
   SYNTAX      INTEGER
               {
               unchanged (256)
               }
   MAX-ACCESS  read-write
   STATUS      current
   DESCRIPTION
      "Path: efm.editConf.vlan.bandwidth.action.eirAction.ethernet.cosDepth1

       Possibilities:
               unchanged   (256)"
   ::= {er1646v2XEfmVlanEntry 150225152}

er1646v2XEfmVlanBandwidthActEirActEthDei1 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth1

       Possibilities:
               unchanged   (255)
               clear   (0)
               set   (1)"
   ::= {er1646v2XEfmVlanEntry 150230272}

er1646v2XEfmVlanBandwidthActEirActEthCos2 OBJECT-TYPE
   SYNTAX      INTEGER
               {
               unchanged (256)
               }
   MAX-ACCESS  read-write
   STATUS      current
   DESCRIPTION
      "Path: efm.editConf.vlan.bandwidth.action.eirAction.ethernet.cosDepth2

       Possibilities:
               unchanged   (256)"
   ::= {er1646v2XEfmVlanEntry 150225408}

er1646v2XEfmVlanBandwidthActEirActEthDei2 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth2

       Possibilities:
               unchanged   (255)
               clear   (0)
               set   (1)"
   ::= {er1646v2XEfmVlanEntry 150230528}

er1646v2XEfmVlanBandwidthActEirActEthCos3 OBJECT-TYPE
   SYNTAX      INTEGER
               {
               unchanged (256)
               }
   MAX-ACCESS  read-write
   STATUS      current
   DESCRIPTION
      "Path: efm.editConf.vlan.bandwidth.action.eirAction.ethernet.cosDepth3

       Possibilities:
               unchanged   (256)"
   ::= {er1646v2XEfmVlanEntry 150225664}

er1646v2XEfmVlanBandwidthActEirActEthDei3 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth3

       Possibilities:
               unchanged   (255)
               clear   (0)
               set   (1)"
   ::= {er1646v2XEfmVlanEntry 150230784}

er1646v2XEfmVlanBandwidthActEirActEthCos4 OBJECT-TYPE
   SYNTAX      INTEGER
               {
               unchanged (256)
               }
   MAX-ACCESS  read-write
   STATUS      current
   DESCRIPTION
      "Path: efm.editConf.vlan.bandwidth.action.eirAction.ethernet.cosDepth4

       Possibilities:
               unchanged   (256)"
   ::= {er1646v2XEfmVlanEntry 150225920}

er1646v2XEfmVlanBandwidthActEirActEthDei4 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth4

       Possibilities:
               unchanged   (255)
               clear   (0)
               set   (1)"
   ::= {er1646v2XEfmVlanEntry 150231040}

er1646v2XEfmVlanBandwidthActEirActEthCos5 OBJECT-TYPE
   SYNTAX      INTEGER
               {
               unchanged (256)
               }
   MAX-ACCESS  read-write
   STATUS      current
   DESCRIPTION
      "Path: efm.editConf.vlan.bandwidth.action.eirAction.ethernet.cosDepth5

       Possibilities:
               unchanged   (256)"
   ::= {er1646v2XEfmVlanEntry 150226176}

er1646v2XEfmVlanBandwidthActEirActEthDei5 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth5

       Possibilities:
               unchanged   (255)
               clear   (0)
               set   (1)"
   ::= {er1646v2XEfmVlanEntry 150231296}

er1646v2XEfmVlanBandwidthActEirActEthCos6 OBJECT-TYPE
   SYNTAX      INTEGER
               {
               unchanged (256)
               }
   MAX-ACCESS  read-write
   STATUS      current
   DESCRIPTION
      "Path: efm.editConf.vlan.bandwidth.action.eirAction.ethernet.cosDepth6

       Possibilities:
               unchanged   (256)"
   ::= {er1646v2XEfmVlanEntry 150226432}

er1646v2XEfmVlanBandwidthActEirActEthDei6 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth6

       Possibilities:
               unchanged   (255)
               clear   (0)
               set   (1)"
   ::= {er1646v2XEfmVlanEntry 150231552}

er1646v2XEfmVlanBandwidthActEirActEthCos7 OBJECT-TYPE
   SYNTAX      INTEGER
               {
               unchanged (256)
               }
   MAX-ACCESS  read-write
   STATUS      current
   DESCRIPTION
      "Path: efm.editConf.vlan.bandwidth.action.eirAction.ethernet.cosDepth7

       Possibilities:
               unchanged   (256)"
   ::= {er1646v2XEfmVlanEntry 150226688}

er1646v2XEfmVlanBandwidthActEirActEthDei7 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth7

       Possibilities:
               unchanged   (255)
               clear   (0)
               set   (1)"
   ::= {er1646v2XEfmVlanEntry 150231808}

er1646v2XEfmVlanBandwidthActEirActEthCos8 OBJECT-TYPE
   SYNTAX      INTEGER
               {
               unchanged (256)
               }
   MAX-ACCESS  read-write
   STATUS      current
   DESCRIPTION
      "Path: efm.editConf.vlan.bandwidth.action.eirAction.ethernet.cosDepth8

       Possibilities:
               unchanged   (256)"
   ::= {er1646v2XEfmVlanEntry 150226944}

er1646v2XEfmVlanBandwidthActEirActEthDei8 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth8

       Possibilities:
               unchanged   (255)
               clear   (0)
               set   (1)"
   ::= {er1646v2XEfmVlanEntry 150232064}

er1646v2XEfmVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150227200}

er1646v2XEfmVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150227456}

er1646v2XEfmVlanBandwidthActEirActEthDrpLev OBJECT-TYPE
   SYNTAX      INTEGER
               {
               unchanged (0)
               }
   MAX-ACCESS  read-write
   STATUS      current
   DESCRIPTION
      "Path: efm.editConf.vlan.bandwidth.action.eirAction.ethernet.dropLevel

       Possibilities:
               unchanged   (0)"
   ::= {er1646v2XEfmVlanEntry 150227712}

er1646v2XEfmVlanBandwidthActEirActEthDeFlag OBJECT-TYPE
   SYNTAX      INTEGER
               {
               unchanged (255),
               clear (0),
               set (1)
               }
   MAX-ACCESS  read-write
   STATUS      current
   DESCRIPTION
      "Path: efm.editConf.vlan.bandwidth.action.eirAction.ethernet.deFlag

       Possibilities:
               unchanged   (255)
               clear   (0)
               set   (1)"
   ::= {er1646v2XEfmVlanEntry 150228480}

er1646v2XEfmVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150251776}

er1646v2XEfmVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150252032}

er1646v2XEfmVlanBandwidthActEirActIpDrpLev OBJECT-TYPE
   SYNTAX      INTEGER
               {
               unchanged (0)
               }
   MAX-ACCESS  read-write
   STATUS      current
   DESCRIPTION
      "Path: efm.editConf.vlan.bandwidth.action.eirAction.ip.dropLevel

       Possibilities:
               unchanged   (0)"
   ::= {er1646v2XEfmVlanEntry 150252288}

er1646v2XEfmVlanBandwidthActEirActIpDeFlag OBJECT-TYPE
   SYNTAX      INTEGER
               {
               unchanged (255),
               clear (0),
               set (1)
               }
   MAX-ACCESS  read-write
   STATUS      current
   DESCRIPTION
      "Path: efm.editConf.vlan.bandwidth.action.eirAction.ip.deFlag

       Possibilities:
               unchanged   (255)
               clear   (0)
               set   (1)"
   ::= {er1646v2XEfmVlanEntry 150253056}

er1646v2XEfmVlanBandwidthActViolActNone OBJECT-TYPE
   SYNTAX      OCTET STRING
   MAX-ACCESS  read-write
   STATUS      current
   DESCRIPTION
      "Path: efm.editConf.vlan.bandwidth.action.violateAction.none"
   ::= {er1646v2XEfmVlanEntry 150347776}

er1646v2XEfmVlanBandwidthActViolActDrop OBJECT-TYPE
   SYNTAX      OCTET STRING
   MAX-ACCESS  read-write
   STATUS      current
   DESCRIPTION
      "Path: efm.editConf.vlan.bandwidth.action.violateAction.drop"
   ::= {er1646v2XEfmVlanEntry 150364160}

er1646v2XEfmVlanBandwidthActViolActEthCos1 OBJECT-TYPE
   SYNTAX      INTEGER
               {
               unchanged (256)
               }
   MAX-ACCESS  read-write
   STATUS      current
   DESCRIPTION
      "Path: efm.editConf.vlan.bandwidth.action.violateAction.ethernet.cosDepth1

       Possibilities:
               unchanged   (256)"
   ::= {er1646v2XEfmVlanEntry 150356224}

er1646v2XEfmVlanBandwidthActViolActEthDei1 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth1

       Possibilities:
               unchanged   (255)
               clear   (0)
               set   (1)"
   ::= {er1646v2XEfmVlanEntry 150361344}

er1646v2XEfmVlanBandwidthActViolActEthCos2 OBJECT-TYPE
   SYNTAX      INTEGER
               {
               unchanged (256)
               }
   MAX-ACCESS  read-write
   STATUS      current
   DESCRIPTION
      "Path: efm.editConf.vlan.bandwidth.action.violateAction.ethernet.cosDepth2

       Possibilities:
               unchanged   (256)"
   ::= {er1646v2XEfmVlanEntry 150356480}

er1646v2XEfmVlanBandwidthActViolActEthDei2 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth2

       Possibilities:
               unchanged   (255)
               clear   (0)
               set   (1)"
   ::= {er1646v2XEfmVlanEntry 150361600}

er1646v2XEfmVlanBandwidthActViolActEthCos3 OBJECT-TYPE
   SYNTAX      INTEGER
               {
               unchanged (256)
               }
   MAX-ACCESS  read-write
   STATUS      current
   DESCRIPTION
      "Path: efm.editConf.vlan.bandwidth.action.violateAction.ethernet.cosDepth3

       Possibilities:
               unchanged   (256)"
   ::= {er1646v2XEfmVlanEntry 150356736}

er1646v2XEfmVlanBandwidthActViolActEthDei3 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth3

       Possibilities:
               unchanged   (255)
               clear   (0)
               set   (1)"
   ::= {er1646v2XEfmVlanEntry 150361856}

er1646v2XEfmVlanBandwidthActViolActEthCos4 OBJECT-TYPE
   SYNTAX      INTEGER
               {
               unchanged (256)
               }
   MAX-ACCESS  read-write
   STATUS      current
   DESCRIPTION
      "Path: efm.editConf.vlan.bandwidth.action.violateAction.ethernet.cosDepth4

       Possibilities:
               unchanged   (256)"
   ::= {er1646v2XEfmVlanEntry 150356992}

er1646v2XEfmVlanBandwidthActViolActEthDei4 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth4

       Possibilities:
               unchanged   (255)
               clear   (0)
               set   (1)"
   ::= {er1646v2XEfmVlanEntry 150362112}

er1646v2XEfmVlanBandwidthActViolActEthCos5 OBJECT-TYPE
   SYNTAX      INTEGER
               {
               unchanged (256)
               }
   MAX-ACCESS  read-write
   STATUS      current
   DESCRIPTION
      "Path: efm.editConf.vlan.bandwidth.action.violateAction.ethernet.cosDepth5

       Possibilities:
               unchanged   (256)"
   ::= {er1646v2XEfmVlanEntry 150357248}

er1646v2XEfmVlanBandwidthActViolActEthDei5 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth5

       Possibilities:
               unchanged   (255)
               clear   (0)
               set   (1)"
   ::= {er1646v2XEfmVlanEntry 150362368}

er1646v2XEfmVlanBandwidthActViolActEthCos6 OBJECT-TYPE
   SYNTAX      INTEGER
               {
               unchanged (256)
               }
   MAX-ACCESS  read-write
   STATUS      current
   DESCRIPTION
      "Path: efm.editConf.vlan.bandwidth.action.violateAction.ethernet.cosDepth6

       Possibilities:
               unchanged   (256)"
   ::= {er1646v2XEfmVlanEntry 150357504}

er1646v2XEfmVlanBandwidthActViolActEthDei6 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth6

       Possibilities:
               unchanged   (255)
               clear   (0)
               set   (1)"
   ::= {er1646v2XEfmVlanEntry 150362624}

er1646v2XEfmVlanBandwidthActViolActEthCos7 OBJECT-TYPE
   SYNTAX      INTEGER
               {
               unchanged (256)
               }
   MAX-ACCESS  read-write
   STATUS      current
   DESCRIPTION
      "Path: efm.editConf.vlan.bandwidth.action.violateAction.ethernet.cosDepth7

       Possibilities:
               unchanged   (256)"
   ::= {er1646v2XEfmVlanEntry 150357760}

er1646v2XEfmVlanBandwidthActViolActEthDei7 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth7

       Possibilities:
               unchanged   (255)
               clear   (0)
               set   (1)"
   ::= {er1646v2XEfmVlanEntry 150362880}

er1646v2XEfmVlanBandwidthActViolActEthCos8 OBJECT-TYPE
   SYNTAX      INTEGER
               {
               unchanged (256)
               }
   MAX-ACCESS  read-write
   STATUS      current
   DESCRIPTION
      "Path: efm.editConf.vlan.bandwidth.action.violateAction.ethernet.cosDepth8

       Possibilities:
               unchanged   (256)"
   ::= {er1646v2XEfmVlanEntry 150358016}

er1646v2XEfmVlanBandwidthActViolActEthDei8 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth8

       Possibilities:
               unchanged   (255)
               clear   (0)
               set   (1)"
   ::= {er1646v2XEfmVlanEntry 150363136}

er1646v2XEfmVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150358272}

er1646v2XEfmVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150358528}

er1646v2XEfmVlanBandwidthActViolActEthDrpLev OBJECT-TYPE
   SYNTAX      INTEGER
               {
               unchanged (0)
               }
   MAX-ACCESS  read-write
   STATUS      current
   DESCRIPTION
      "Path: efm.editConf.vlan.bandwidth.action.violateAction.ethernet.dropLevel

       Possibilities:
               unchanged   (0)"
   ::= {er1646v2XEfmVlanEntry 150358784}

er1646v2XEfmVlanBandwidthActViolActEthDeFlag OBJECT-TYPE
   SYNTAX      INTEGER
               {
               unchanged (255),
               clear (0),
               set (1)
               }
   MAX-ACCESS  read-write
   STATUS      current
   DESCRIPTION
      "Path: efm.editConf.vlan.bandwidth.action.violateAction.ethernet.deFlag

       Possibilities:
               unchanged   (255)
               clear   (0)
               set   (1)"
   ::= {er1646v2XEfmVlanEntry 150359552}

er1646v2XEfmVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 150382848}

er1646v2XEfmVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 150383104}

er1646v2XEfmVlanBandwidthActViolActIpDrpLev OBJECT-TYPE
   SYNTAX      INTEGER
               {
               unchanged (0)
               }
   MAX-ACCESS  read-write
   STATUS      current
   DESCRIPTION
      "Path: efm.editConf.vlan.bandwidth.action.violateAction.ip.dropLevel

       Possibilities:
               unchanged   (0)"
   ::= {er1646v2XEfmVlanEntry 150383360}

er1646v2XEfmVlanBandwidthActViolActIpDeFlag OBJECT-TYPE
   SYNTAX      INTEGER
               {
               unchanged (255),
               clear (0),
               set (1)
               }
   MAX-ACCESS  read-write
   STATUS      current
   DESCRIPTION
      "Path: efm.editConf.vlan.bandwidth.action.violateAction.ip.deFlag

       Possibilities:
               unchanged   (255)
               clear   (0)
               set   (1)"
   ::= {er1646v2XEfmVlanEntry 150384128}

er1646v2XEfmVlanInbBwMode OBJECT-TYPE
   SYNTAX      INTEGER
               {
               reshaping (1),
               policing (2)
               }
   MAX-ACCESS  read-write
   STATUS      current
   DESCRIPTION
      "Path: efm.editConf.vlan.inboundBandwidth.mode

       Possibilities:
               reshaping   (1)
               policing   (2)"
   ::= {er1646v2XEfmVlanEntry 132120576}

er1646v2XEfmVlanInbBwCir OBJECT-TYPE
   SYNTAX      Integer32
   MAX-ACCESS  read-write
   STATUS      current
   DESCRIPTION
      "Path: efm.editConf.vlan.inboundBandwidth.cir"
   ::= {er1646v2XEfmVlanEntry 118489088}

er1646v2XEfmVlanInbBwEir OBJECT-TYPE
   SYNTAX      Integer32
   MAX-ACCESS  read-write
   STATUS      current
   DESCRIPTION
      "Path: efm.editConf.vlan.inboundBandwidth.eir"
   ::= {er1646v2XEfmVlanEntry 124780544}

er1646v2XEfmVlanInbBwUnit OBJECT-TYPE
   SYNTAX      INTEGER
               {
               bitssec (1),
               percent (2)
               }
   MAX-ACCESS  read-write
   STATUS      current
   DESCRIPTION
      "Path: efm.editConf.vlan.inboundBandwidth.unit

       Possibilities:
               bits/sec   (1)
               percent   (2)"
   ::= {er1646v2XEfmVlanEntry 122683392}

er1646v2XEfmVlanInbBwTc OBJECT-TYPE
   SYNTAX      INTEGER
               {
               auto (0)
               }
   MAX-ACCESS  read-write
   STATUS      current
   DESCRIPTION
      "Path: efm.editConf.vlan.inboundBandwidth.tc

       Possibilities:
               auto   (0)"
   ::= {er1646v2XEfmVlanEntry 123731968}

er1646v2XEfmVlanInbBwTcFactor OBJECT-TYPE
   SYNTAX      INTEGER
               {
               ms (10),
               s100us (1)
               }
   MAX-ACCESS  read-write
   STATUS      current
   DESCRIPTION
      "Path: efm.editConf.vlan.inboundBandwidth.tcFactor

       Possibilities:
               ms   (10)
               *100us   (1)"
   ::= {er1646v2XEfmVlanEntry 125829120}

er1646v2XEfmVlanInbBwCorrType OBJECT-TYPE
   SYNTAX      INTEGER
               {
               noCorrection (0),
               predefined (1),
               manual (2)
               }
   MAX-ACCESS  read-write
   STATUS      current
   DESCRIPTION
      "Path: efm.editConf.vlan.inboundBandwidth.correction.type

       Possibilities:
               noCorrection   (0)
               predefined   (1)
               manual   (2)"
   ::= {er1646v2XEfmVlanEntry 119668736}

er1646v2XEfmVlanInbBwCorrPredefEncapsFrameRelay OBJECT-TYPE
   SYNTAX      DisplayString
   MAX-ACCESS  read-write
   STATUS      current
   DESCRIPTION
      "Path: efm.editConf.vlan.inboundBandwidth.correction.predefined.encapsulation.frameRelay"
   ::= {er1646v2XEfmVlanEntry 119817216}

er1646v2XEfmVlanInbBwCorrPredefEncapsPpp OBJECT-TYPE
   SYNTAX      DisplayString
   MAX-ACCESS  read-write
   STATUS      current
   DESCRIPTION
      "Path: efm.editConf.vlan.inboundBandwidth.correction.predefined.encapsulation.ppp"
   ::= {er1646v2XEfmVlanEntry 119818240}

er1646v2XEfmVlanInbBwCorrPredefEncapsAtmHl OBJECT-TYPE
   SYNTAX      INTEGER
               {
               rfc2684 (0),
               ppp (1),
               pppOverEthernet (2)
               }
   MAX-ACCESS  read-write
   STATUS      current
   DESCRIPTION
      "Path: efm.editConf.vlan.inboundBandwidth.correction.predefined.encapsulation.atm.higherLayer

       Possibilities:
               rfc2684   (0)
               ppp   (1)
               pppOverEthernet   (2)"
   ::= {er1646v2XEfmVlanEntry 119819392}

er1646v2XEfmVlanInbBwCorrPredefEncapsAtmMp OBJECT-TYPE
   SYNTAX      INTEGER
               {
               llcEncapsulation (0),
               vcMultiplexing (1)
               }
   MAX-ACCESS  read-write
   STATUS      current
   DESCRIPTION
      "Path: efm.editConf.vlan.inboundBandwidth.correction.predefined.encapsulation.atm.multiProtocol

       Possibilities:
               llcEncapsulation   (0)
               vcMultiplexing   (1)"
   ::= {er1646v2XEfmVlanEntry 119819520}

er1646v2XEfmVlanInbBwCorrPredefEncapsHdlc OBJECT-TYPE
   SYNTAX      DisplayString
   MAX-ACCESS  read-write
   STATUS      current
   DESCRIPTION
      "Path: efm.editConf.vlan.inboundBandwidth.correction.predefined.encapsulation.hdlc"
   ::= {er1646v2XEfmVlanEntry 119820288}

er1646v2XEfmVlanInbBwCorrPredefEncapsEfmFs OBJECT-TYPE
   SYNTAX      Integer32
   MAX-ACCESS  read-write
   STATUS      current
   DESCRIPTION
      "Path: efm.editConf.vlan.inboundBandwidth.correction.predefined.encapsulation.efm.fragmentSize"
   ::= {er1646v2XEfmVlanEntry 119821440}

er1646v2XEfmVlanInbBwCorrPredefEncapsEfmIb OBJECT-TYPE
   SYNTAX      Integer32
   MAX-ACCESS  read-write
   STATUS      current
   DESCRIPTION
      "Path: efm.editConf.vlan.inboundBandwidth.correction.predefined.encapsulation.efm.idleBytes"
   ::= {er1646v2XEfmVlanEntry 119821568}

er1646v2XEfmVlanInbBwCorrPredefMode OBJECT-TYPE
   SYNTAX      INTEGER
               {
               routing (0),
               bridging (1)
               }
   MAX-ACCESS  read-write
   STATUS      current
   DESCRIPTION
      "Path: efm.editConf.vlan.inboundBandwidth.correction.predefined.mode

       Possibilities:
               routing   (0)
               bridging   (1)"
   ::= {er1646v2XEfmVlanEntry 119832576}

er1646v2XEfmVlanInbBwCorrManualOverhead OBJECT-TYPE
   SYNTAX      Integer32
   MAX-ACCESS  read-write
   STATUS      current
   DESCRIPTION
      "Path: efm.editConf.vlan.inboundBandwidth.correction.manual.overhead"
   ::= {er1646v2XEfmVlanEntry 119931392}

er1646v2XEfmVlanInbBwCorrManualFrameData OBJECT-TYPE
   SYNTAX      Counter32
   MAX-ACCESS  read-write
   STATUS      current
   DESCRIPTION
      "Path: efm.editConf.vlan.inboundBandwidth.correction.manual.frameData

       32 bit unsigned wrappable counter."
   ::= {er1646v2XEfmVlanEntry 119931904}

er1646v2XEfmVlanInbBwCorrManualFrameHeader OBJECT-TYPE
   SYNTAX      Counter32
   MAX-ACCESS  read-write
   STATUS      current
   DESCRIPTION
      "Path: efm.editConf.vlan.inboundBandwidth.correction.manual.frameHeader

       32 bit unsigned wrappable counter."
   ::= {er1646v2XEfmVlanEntry 119932416}

er1646v2XEfmVlanInbBwMaxFifoQLen OBJECT-TYPE
   SYNTAX      Integer32
   MAX-ACCESS  read-write
   STATUS      current
   DESCRIPTION
      "Path: efm.editConf.vlan.inboundBandwidth.maxFifoQLen"
   ::= {er1646v2XEfmVlanEntry 120586240}

er1646v2XEfmVlanInbBwPriorityPolicy OBJECT-TYPE
   SYNTAX      DisplayString
   MAX-ACCESS  read-write
   STATUS      current
   DESCRIPTION
      "Path: efm.editConf.vlan.inboundBandwidth.priorityPolicy"
   ::= {er1646v2XEfmVlanEntry 121634816}

er1646v2XEfmVlanInbBwDeFlagCir OBJECT-TYPE
   SYNTAX      INTEGER
               {
               allowed (1),
               notAllowed (2)
               }
   MAX-ACCESS  read-write
   STATUS      current
   DESCRIPTION
      "Path: efm.editConf.vlan.inboundBandwidth.deFlag.cir

       Possibilities:
               allowed   (1)
               notAllowed   (2)"
   ::= {er1646v2XEfmVlanEntry 131076096}

er1646v2XEfmVlanInbBwDeFlagEir OBJECT-TYPE
   SYNTAX      INTEGER
               {
               allowed (1),
               notAllowed (2)
               }
   MAX-ACCESS  read-write
   STATUS      current
   DESCRIPTION
      "Path: efm.editConf.vlan.inboundBandwidth.deFlag.eir

       Possibilities:
               allowed   (1)
               notAllowed   (2)"
   ::= {er1646v2XEfmVlanEntry 131080192}

er1646v2XEfmVlanInbBwDeFlagViolate OBJECT-TYPE
   SYNTAX      INTEGER
               {
               allowed (1),
               notAllowed (2)
               }
   MAX-ACCESS  read-write
   STATUS      current
   DESCRIPTION
      "Path: efm.editConf.vlan.inboundBandwidth.deFlag.violate

       Possibilities:
               allowed   (1)
               notAllowed   (2)"
   ::= {er1646v2XEfmVlanEntry 131084288}

er1646v2XEfmVlanInbBwActCirActNone OBJECT-TYPE
   SYNTAX      OCTET STRING
   MAX-ACCESS  read-write
   STATUS      current
   DESCRIPTION
      "Path: efm.editConf.vlan.inboundBandwidth.action.cirAction.none"
   ::= {er1646v2XEfmVlanEntry 133308416}

er1646v2XEfmVlanInbBwActCirActEthCos1 OBJECT-TYPE
   SYNTAX      INTEGER
               {
               unchanged (256)
               }
   MAX-ACCESS  read-write
   STATUS      current
   DESCRIPTION
      "Path: efm.editConf.vlan.inboundBandwidth.action.cirAction.ethernet.cosDepth1

       Possibilities:
               unchanged   (256)"
   ::= {er1646v2XEfmVlanEntry 133316864}

er1646v2XEfmVlanInbBwActCirActEthDei1 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth1

       Possibilities:
               unchanged   (255)
               clear   (0)
               set   (1)"
   ::= {er1646v2XEfmVlanEntry 133321984}

er1646v2XEfmVlanInbBwActCirActEthCos2 OBJECT-TYPE
   SYNTAX      INTEGER
               {
               unchanged (256)
               }
   MAX-ACCESS  read-write
   STATUS      current
   DESCRIPTION
      "Path: efm.editConf.vlan.inboundBandwidth.action.cirAction.ethernet.cosDepth2

       Possibilities:
               unchanged   (256)"
   ::= {er1646v2XEfmVlanEntry 133317120}

er1646v2XEfmVlanInbBwActCirActEthDei2 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth2

       Possibilities:
               unchanged   (255)
               clear   (0)
               set   (1)"
   ::= {er1646v2XEfmVlanEntry 133322240}

er1646v2XEfmVlanInbBwActCirActEthCos3 OBJECT-TYPE
   SYNTAX      INTEGER
               {
               unchanged (256)
               }
   MAX-ACCESS  read-write
   STATUS      current
   DESCRIPTION
      "Path: efm.editConf.vlan.inboundBandwidth.action.cirAction.ethernet.cosDepth3

       Possibilities:
               unchanged   (256)"
   ::= {er1646v2XEfmVlanEntry 133317376}

er1646v2XEfmVlanInbBwActCirActEthDei3 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth3

       Possibilities:
               unchanged   (255)
               clear   (0)
               set   (1)"
   ::= {er1646v2XEfmVlanEntry 133322496}

er1646v2XEfmVlanInbBwActCirActEthCos4 OBJECT-TYPE
   SYNTAX      INTEGER
               {
               unchanged (256)
               }
   MAX-ACCESS  read-write
   STATUS      current
   DESCRIPTION
      "Path: efm.editConf.vlan.inboundBandwidth.action.cirAction.ethernet.cosDepth4

       Possibilities:
               unchanged   (256)"
   ::= {er1646v2XEfmVlanEntry 133317632}

er1646v2XEfmVlanInbBwActCirActEthDei4 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth4

       Possibilities:
               unchanged   (255)
               clear   (0)
               set   (1)"
   ::= {er1646v2XEfmVlanEntry 133322752}

er1646v2XEfmVlanInbBwActCirActEthCos5 OBJECT-TYPE
   SYNTAX      INTEGER
               {
               unchanged (256)
               }
   MAX-ACCESS  read-write
   STATUS      current
   DESCRIPTION
      "Path: efm.editConf.vlan.inboundBandwidth.action.cirAction.ethernet.cosDepth5

       Possibilities:
               unchanged   (256)"
   ::= {er1646v2XEfmVlanEntry 133317888}

er1646v2XEfmVlanInbBwActCirActEthDei5 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth5

       Possibilities:
               unchanged   (255)
               clear   (0)
               set   (1)"
   ::= {er1646v2XEfmVlanEntry 133323008}

er1646v2XEfmVlanInbBwActCirActEthCos6 OBJECT-TYPE
   SYNTAX      INTEGER
               {
               unchanged (256)
               }
   MAX-ACCESS  read-write
   STATUS      current
   DESCRIPTION
      "Path: efm.editConf.vlan.inboundBandwidth.action.cirAction.ethernet.cosDepth6

       Possibilities:
               unchanged   (256)"
   ::= {er1646v2XEfmVlanEntry 133318144}

er1646v2XEfmVlanInbBwActCirActEthDei6 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth6

       Possibilities:
               unchanged   (255)
               clear   (0)
               set   (1)"
   ::= {er1646v2XEfmVlanEntry 133323264}

er1646v2XEfmVlanInbBwActCirActEthCos7 OBJECT-TYPE
   SYNTAX      INTEGER
               {
               unchanged (256)
               }
   MAX-ACCESS  read-write
   STATUS      current
   DESCRIPTION
      "Path: efm.editConf.vlan.inboundBandwidth.action.cirAction.ethernet.cosDepth7

       Possibilities:
               unchanged   (256)"
   ::= {er1646v2XEfmVlanEntry 133318400}

er1646v2XEfmVlanInbBwActCirActEthDei7 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth7

       Possibilities:
               unchanged   (255)
               clear   (0)
               set   (1)"
   ::= {er1646v2XEfmVlanEntry 133323520}

er1646v2XEfmVlanInbBwActCirActEthCos8 OBJECT-TYPE
   SYNTAX      INTEGER
               {
               unchanged (256)
               }
   MAX-ACCESS  read-write
   STATUS      current
   DESCRIPTION
      "Path: efm.editConf.vlan.inboundBandwidth.action.cirAction.ethernet.cosDepth8

       Possibilities:
               unchanged   (256)"
   ::= {er1646v2XEfmVlanEntry 133318656}

er1646v2XEfmVlanInbBwActCirActEthDei8 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth8

       Possibilities:
               unchanged   (255)
               clear   (0)
               set   (1)"
   ::= {er1646v2XEfmVlanEntry 133323776}

er1646v2XEfmVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133318912}

er1646v2XEfmVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133319168}

er1646v2XEfmVlanInbBwActCirActEthDrpLev OBJECT-TYPE
   SYNTAX      INTEGER
               {
               unchanged (0)
               }
   MAX-ACCESS  read-write
   STATUS      current
   DESCRIPTION
      "Path: efm.editConf.vlan.inboundBandwidth.action.cirAction.ethernet.dropLevel

       Possibilities:
               unchanged   (0)"
   ::= {er1646v2XEfmVlanEntry 133319424}

er1646v2XEfmVlanInbBwActCirActEthDeFlag OBJECT-TYPE
   SYNTAX      INTEGER
               {
               unchanged (255),
               clear (0),
               set (1)
               }
   MAX-ACCESS  read-write
   STATUS      current
   DESCRIPTION
      "Path: efm.editConf.vlan.inboundBandwidth.action.cirAction.ethernet.deFlag

       Possibilities:
               unchanged   (255)
               clear   (0)
               set   (1)"
   ::= {er1646v2XEfmVlanEntry 133320192}

er1646v2XEfmVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133343488}

er1646v2XEfmVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133343744}

er1646v2XEfmVlanInbBwActCirActIpDrpLev OBJECT-TYPE
   SYNTAX      INTEGER
               {
               unchanged (0)
               }
   MAX-ACCESS  read-write
   STATUS      current
   DESCRIPTION
      "Path: efm.editConf.vlan.inboundBandwidth.action.cirAction.ip.dropLevel

       Possibilities:
               unchanged   (0)"
   ::= {er1646v2XEfmVlanEntry 133344000}

er1646v2XEfmVlanInbBwActCirActIpDeFlag OBJECT-TYPE
   SYNTAX      INTEGER
               {
               unchanged (255),
               clear (0),
               set (1)
               }
   MAX-ACCESS  read-write
   STATUS      current
   DESCRIPTION
      "Path: efm.editConf.vlan.inboundBandwidth.action.cirAction.ip.deFlag

       Possibilities:
               unchanged   (255)
               clear   (0)
               set   (1)"
   ::= {er1646v2XEfmVlanEntry 133344768}

er1646v2XEfmVlanInbBwActEirActNone OBJECT-TYPE
   SYNTAX      OCTET STRING
   MAX-ACCESS  read-write
   STATUS      current
   DESCRIPTION
      "Path: efm.editConf.vlan.inboundBandwidth.action.eirAction.none"
   ::= {er1646v2XEfmVlanEntry 133439488}

er1646v2XEfmVlanInbBwActEirActEthCos1 OBJECT-TYPE
   SYNTAX      INTEGER
               {
               unchanged (256)
               }
   MAX-ACCESS  read-write
   STATUS      current
   DESCRIPTION
      "Path: efm.editConf.vlan.inboundBandwidth.action.eirAction.ethernet.cosDepth1

       Possibilities:
               unchanged   (256)"
   ::= {er1646v2XEfmVlanEntry 133447936}

er1646v2XEfmVlanInbBwActEirActEthDei1 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth1

       Possibilities:
               unchanged   (255)
               clear   (0)
               set   (1)"
   ::= {er1646v2XEfmVlanEntry 133453056}

er1646v2XEfmVlanInbBwActEirActEthCos2 OBJECT-TYPE
   SYNTAX      INTEGER
               {
               unchanged (256)
               }
   MAX-ACCESS  read-write
   STATUS      current
   DESCRIPTION
      "Path: efm.editConf.vlan.inboundBandwidth.action.eirAction.ethernet.cosDepth2

       Possibilities:
               unchanged   (256)"
   ::= {er1646v2XEfmVlanEntry 133448192}

er1646v2XEfmVlanInbBwActEirActEthDei2 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth2

       Possibilities:
               unchanged   (255)
               clear   (0)
               set   (1)"
   ::= {er1646v2XEfmVlanEntry 133453312}

er1646v2XEfmVlanInbBwActEirActEthCos3 OBJECT-TYPE
   SYNTAX      INTEGER
               {
               unchanged (256)
               }
   MAX-ACCESS  read-write
   STATUS      current
   DESCRIPTION
      "Path: efm.editConf.vlan.inboundBandwidth.action.eirAction.ethernet.cosDepth3

       Possibilities:
               unchanged   (256)"
   ::= {er1646v2XEfmVlanEntry 133448448}

er1646v2XEfmVlanInbBwActEirActEthDei3 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth3

       Possibilities:
               unchanged   (255)
               clear   (0)
               set   (1)"
   ::= {er1646v2XEfmVlanEntry 133453568}

er1646v2XEfmVlanInbBwActEirActEthCos4 OBJECT-TYPE
   SYNTAX      INTEGER
               {
               unchanged (256)
               }
   MAX-ACCESS  read-write
   STATUS      current
   DESCRIPTION
      "Path: efm.editConf.vlan.inboundBandwidth.action.eirAction.ethernet.cosDepth4

       Possibilities:
               unchanged   (256)"
   ::= {er1646v2XEfmVlanEntry 133448704}

er1646v2XEfmVlanInbBwActEirActEthDei4 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth4

       Possibilities:
               unchanged   (255)
               clear   (0)
               set   (1)"
   ::= {er1646v2XEfmVlanEntry 133453824}

er1646v2XEfmVlanInbBwActEirActEthCos5 OBJECT-TYPE
   SYNTAX      INTEGER
               {
               unchanged (256)
               }
   MAX-ACCESS  read-write
   STATUS      current
   DESCRIPTION
      "Path: efm.editConf.vlan.inboundBandwidth.action.eirAction.ethernet.cosDepth5

       Possibilities:
               unchanged   (256)"
   ::= {er1646v2XEfmVlanEntry 133448960}

er1646v2XEfmVlanInbBwActEirActEthDei5 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth5

       Possibilities:
               unchanged   (255)
               clear   (0)
               set   (1)"
   ::= {er1646v2XEfmVlanEntry 133454080}

er1646v2XEfmVlanInbBwActEirActEthCos6 OBJECT-TYPE
   SYNTAX      INTEGER
               {
               unchanged (256)
               }
   MAX-ACCESS  read-write
   STATUS      current
   DESCRIPTION
      "Path: efm.editConf.vlan.inboundBandwidth.action.eirAction.ethernet.cosDepth6

       Possibilities:
               unchanged   (256)"
   ::= {er1646v2XEfmVlanEntry 133449216}

er1646v2XEfmVlanInbBwActEirActEthDei6 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth6

       Possibilities:
               unchanged   (255)
               clear   (0)
               set   (1)"
   ::= {er1646v2XEfmVlanEntry 133454336}

er1646v2XEfmVlanInbBwActEirActEthCos7 OBJECT-TYPE
   SYNTAX      INTEGER
               {
               unchanged (256)
               }
   MAX-ACCESS  read-write
   STATUS      current
   DESCRIPTION
      "Path: efm.editConf.vlan.inboundBandwidth.action.eirAction.ethernet.cosDepth7

       Possibilities:
               unchanged   (256)"
   ::= {er1646v2XEfmVlanEntry 133449472}

er1646v2XEfmVlanInbBwActEirActEthDei7 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth7

       Possibilities:
               unchanged   (255)
               clear   (0)
               set   (1)"
   ::= {er1646v2XEfmVlanEntry 133454592}

er1646v2XEfmVlanInbBwActEirActEthCos8 OBJECT-TYPE
   SYNTAX      INTEGER
               {
               unchanged (256)
               }
   MAX-ACCESS  read-write
   STATUS      current
   DESCRIPTION
      "Path: efm.editConf.vlan.inboundBandwidth.action.eirAction.ethernet.cosDepth8

       Possibilities:
               unchanged   (256)"
   ::= {er1646v2XEfmVlanEntry 133449728}

er1646v2XEfmVlanInbBwActEirActEthDei8 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth8

       Possibilities:
               unchanged   (255)
               clear   (0)
               set   (1)"
   ::= {er1646v2XEfmVlanEntry 133454848}

er1646v2XEfmVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133449984}

er1646v2XEfmVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133450240}

er1646v2XEfmVlanInbBwActEirActEthDrpLev OBJECT-TYPE
   SYNTAX      INTEGER
               {
               unchanged (0)
               }
   MAX-ACCESS  read-write
   STATUS      current
   DESCRIPTION
      "Path: efm.editConf.vlan.inboundBandwidth.action.eirAction.ethernet.dropLevel

       Possibilities:
               unchanged   (0)"
   ::= {er1646v2XEfmVlanEntry 133450496}

er1646v2XEfmVlanInbBwActEirActEthDeFlag OBJECT-TYPE
   SYNTAX      INTEGER
               {
               unchanged (255),
               clear (0),
               set (1)
               }
   MAX-ACCESS  read-write
   STATUS      current
   DESCRIPTION
      "Path: efm.editConf.vlan.inboundBandwidth.action.eirAction.ethernet.deFlag

       Possibilities:
               unchanged   (255)
               clear   (0)
               set   (1)"
   ::= {er1646v2XEfmVlanEntry 133451264}

er1646v2XEfmVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133474560}

er1646v2XEfmVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133474816}

er1646v2XEfmVlanInbBwActEirActIpDrpLev OBJECT-TYPE
   SYNTAX      INTEGER
               {
               unchanged (0)
               }
   MAX-ACCESS  read-write
   STATUS      current
   DESCRIPTION
      "Path: efm.editConf.vlan.inboundBandwidth.action.eirAction.ip.dropLevel

       Possibilities:
               unchanged   (0)"
   ::= {er1646v2XEfmVlanEntry 133475072}

er1646v2XEfmVlanInbBwActEirActIpDeFlag OBJECT-TYPE
   SYNTAX      INTEGER
               {
               unchanged (255),
               clear (0),
               set (1)
               }
   MAX-ACCESS  read-write
   STATUS      current
   DESCRIPTION
      "Path: efm.editConf.vlan.inboundBandwidth.action.eirAction.ip.deFlag

       Possibilities:
               unchanged   (255)
               clear   (0)
               set   (1)"
   ::= {er1646v2XEfmVlanEntry 133475840}

er1646v2XEfmVlanInbBwActViolActNone OBJECT-TYPE
   SYNTAX      OCTET STRING
   MAX-ACCESS  read-write
   STATUS      current
   DESCRIPTION
      "Path: efm.editConf.vlan.inboundBandwidth.action.violateAction.none"
   ::= {er1646v2XEfmVlanEntry 133570560}

er1646v2XEfmVlanInbBwActViolActDrop OBJECT-TYPE
   SYNTAX      OCTET STRING
   MAX-ACCESS  read-write
   STATUS      current
   DESCRIPTION
      "Path: efm.editConf.vlan.inboundBandwidth.action.violateAction.drop"
   ::= {er1646v2XEfmVlanEntry 133586944}

er1646v2XEfmVlanInbBwActViolActEthCos1 OBJECT-TYPE
   SYNTAX      INTEGER
               {
               unchanged (256)
               }
   MAX-ACCESS  read-write
   STATUS      current
   DESCRIPTION
      "Path: efm.editConf.vlan.inboundBandwidth.action.violateAction.ethernet.cosDepth1

       Possibilities:
               unchanged   (256)"
   ::= {er1646v2XEfmVlanEntry 133579008}

er1646v2XEfmVlanInbBwActViolActEthDei1 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth1

       Possibilities:
               unchanged   (255)
               clear   (0)
               set   (1)"
   ::= {er1646v2XEfmVlanEntry 133584128}

er1646v2XEfmVlanInbBwActViolActEthCos2 OBJECT-TYPE
   SYNTAX      INTEGER
               {
               unchanged (256)
               }
   MAX-ACCESS  read-write
   STATUS      current
   DESCRIPTION
      "Path: efm.editConf.vlan.inboundBandwidth.action.violateAction.ethernet.cosDepth2

       Possibilities:
               unchanged   (256)"
   ::= {er1646v2XEfmVlanEntry 133579264}

er1646v2XEfmVlanInbBwActViolActEthDei2 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth2

       Possibilities:
               unchanged   (255)
               clear   (0)
               set   (1)"
   ::= {er1646v2XEfmVlanEntry 133584384}

er1646v2XEfmVlanInbBwActViolActEthCos3 OBJECT-TYPE
   SYNTAX      INTEGER
               {
               unchanged (256)
               }
   MAX-ACCESS  read-write
   STATUS      current
   DESCRIPTION
      "Path: efm.editConf.vlan.inboundBandwidth.action.violateAction.ethernet.cosDepth3

       Possibilities:
               unchanged   (256)"
   ::= {er1646v2XEfmVlanEntry 133579520}

er1646v2XEfmVlanInbBwActViolActEthDei3 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth3

       Possibilities:
               unchanged   (255)
               clear   (0)
               set   (1)"
   ::= {er1646v2XEfmVlanEntry 133584640}

er1646v2XEfmVlanInbBwActViolActEthCos4 OBJECT-TYPE
   SYNTAX      INTEGER
               {
               unchanged (256)
               }
   MAX-ACCESS  read-write
   STATUS      current
   DESCRIPTION
      "Path: efm.editConf.vlan.inboundBandwidth.action.violateAction.ethernet.cosDepth4

       Possibilities:
               unchanged   (256)"
   ::= {er1646v2XEfmVlanEntry 133579776}

er1646v2XEfmVlanInbBwActViolActEthDei4 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth4

       Possibilities:
               unchanged   (255)
               clear   (0)
               set   (1)"
   ::= {er1646v2XEfmVlanEntry 133584896}

er1646v2XEfmVlanInbBwActViolActEthCos5 OBJECT-TYPE
   SYNTAX      INTEGER
               {
               unchanged (256)
               }
   MAX-ACCESS  read-write
   STATUS      current
   DESCRIPTION
      "Path: efm.editConf.vlan.inboundBandwidth.action.violateAction.ethernet.cosDepth5

       Possibilities:
               unchanged   (256)"
   ::= {er1646v2XEfmVlanEntry 133580032}

er1646v2XEfmVlanInbBwActViolActEthDei5 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth5

       Possibilities:
               unchanged   (255)
               clear   (0)
               set   (1)"
   ::= {er1646v2XEfmVlanEntry 133585152}

er1646v2XEfmVlanInbBwActViolActEthCos6 OBJECT-TYPE
   SYNTAX      INTEGER
               {
               unchanged (256)
               }
   MAX-ACCESS  read-write
   STATUS      current
   DESCRIPTION
      "Path: efm.editConf.vlan.inboundBandwidth.action.violateAction.ethernet.cosDepth6

       Possibilities:
               unchanged   (256)"
   ::= {er1646v2XEfmVlanEntry 133580288}

er1646v2XEfmVlanInbBwActViolActEthDei6 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth6

       Possibilities:
               unchanged   (255)
               clear   (0)
               set   (1)"
   ::= {er1646v2XEfmVlanEntry 133585408}

er1646v2XEfmVlanInbBwActViolActEthCos7 OBJECT-TYPE
   SYNTAX      INTEGER
               {
               unchanged (256)
               }
   MAX-ACCESS  read-write
   STATUS      current
   DESCRIPTION
      "Path: efm.editConf.vlan.inboundBandwidth.action.violateAction.ethernet.cosDepth7

       Possibilities:
               unchanged   (256)"
   ::= {er1646v2XEfmVlanEntry 133580544}

er1646v2XEfmVlanInbBwActViolActEthDei7 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth7

       Possibilities:
               unchanged   (255)
               clear   (0)
               set   (1)"
   ::= {er1646v2XEfmVlanEntry 133585664}

er1646v2XEfmVlanInbBwActViolActEthCos8 OBJECT-TYPE
   SYNTAX      INTEGER
               {
               unchanged (256)
               }
   MAX-ACCESS  read-write
   STATUS      current
   DESCRIPTION
      "Path: efm.editConf.vlan.inboundBandwidth.action.violateAction.ethernet.cosDepth8

       Possibilities:
               unchanged   (256)"
   ::= {er1646v2XEfmVlanEntry 133580800}

er1646v2XEfmVlanInbBwActViolActEthDei8 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth8

       Possibilities:
               unchanged   (255)
               clear   (0)
               set   (1)"
   ::= {er1646v2XEfmVlanEntry 133585920}

er1646v2XEfmVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133581056}

er1646v2XEfmVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133581312}

er1646v2XEfmVlanInbBwActViolActEthDrpLev OBJECT-TYPE
   SYNTAX      INTEGER
               {
               unchanged (0)
               }
   MAX-ACCESS  read-write
   STATUS      current
   DESCRIPTION
      "Path: efm.editConf.vlan.inboundBandwidth.action.violateAction.ethernet.dropLevel

       Possibilities:
               unchanged   (0)"
   ::= {er1646v2XEfmVlanEntry 133581568}

er1646v2XEfmVlanInbBwActViolActEthDeFlag OBJECT-TYPE
   SYNTAX      INTEGER
               {
               unchanged (255),
               clear (0),
               set (1)
               }
   MAX-ACCESS  read-write
   STATUS      current
   DESCRIPTION
      "Path: efm.editConf.vlan.inboundBandwidth.action.violateAction.ethernet.deFlag

       Possibilities:
               unchanged   (255)
               clear   (0)
               set   (1)"
   ::= {er1646v2XEfmVlanEntry 133582336}

er1646v2XEfmVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanEntry 133605632}

er1646v2XEfmVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanEntry 133605888}

er1646v2XEfmVlanInbBwActViolActIpDrpLev OBJECT-TYPE
   SYNTAX      INTEGER
               {
               unchanged (0)
               }
   MAX-ACCESS  read-write
   STATUS      current
   DESCRIPTION
      "Path: efm.editConf.vlan.inboundBandwidth.action.violateAction.ip.dropLevel

       Possibilities:
               unchanged   (0)"
   ::= {er1646v2XEfmVlanEntry 133606144}

er1646v2XEfmVlanInbBwActViolActIpDeFlag OBJECT-TYPE
   SYNTAX      INTEGER
               {
               unchanged (255),
               clear (0),
               set (1)
               }
   MAX-ACCESS  read-write
   STATUS      current
   DESCRIPTION
      "Path: efm.editConf.vlan.inboundBandwidth.action.violateAction.ip.deFlag

       Possibilities:
               unchanged   (255)
               clear   (0)
               set   (1)"
   ::= {er1646v2XEfmVlanEntry 133606912}

er1646v2XEfmVlanPppoE OBJECT-TYPE
   SYNTAX      INTEGER
               {
               disabled (0),
               enabled (1)
               }
   MAX-ACCESS  read-write
   STATUS      current
   DESCRIPTION
      "Path: efm.editConf.vlan.pppoE

       Possibilities:
               disabled   (0)
               enabled   (1)"
   ::= {er1646v2XEfmVlanEntry 838860800}

er1646v2XEfmVlanPppLnkMOperation OBJECT-TYPE
   SYNTAX      INTEGER
               {
               disabled (0),
               enabled (1)
               }
   MAX-ACCESS  read-write
   STATUS      current
   DESCRIPTION
      "Path: efm.editConf.vlan.ppp.linkMonitoring.operation

       Possibilities:
               disabled   (0)
               enabled   (1)"
   ::= {er1646v2XEfmVlanEntry 251724032}

er1646v2XEfmVlanPppLnkMInterval OBJECT-TYPE
   SYNTAX      TimeTicks
   MAX-ACCESS  read-write
   STATUS      current
   DESCRIPTION
      "Path: efm.editConf.vlan.ppp.linkMonitoring.interval

       Time in centi-second."
   ::= {er1646v2XEfmVlanEntry 251724288}

er1646v2XEfmVlanPppLnkMRepTimeOut OBJECT-TYPE
   SYNTAX      TimeTicks
   MAX-ACCESS  read-write
   STATUS      current
   DESCRIPTION
      "Path: efm.editConf.vlan.ppp.linkMonitoring.replyTimeOut

       Time in centi-second."
   ::= {er1646v2XEfmVlanEntry 251724544}

er1646v2XEfmVlanPppLnkMFailsPrmt OBJECT-TYPE
   SYNTAX      Integer32
   MAX-ACCESS  read-write
   STATUS      current
   DESCRIPTION
      "Path: efm.editConf.vlan.ppp.linkMonitoring.failsPermitted"
   ::= {er1646v2XEfmVlanEntry 251724800}

er1646v2XEfmVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: efm.editConf.vlan.ppp.authentication

       Possibilities:
               disabled   (0)
               chap   (1)
               pap   (2)
               chapOrPap   (3)
               msChap   (4)
               msChapV2   (5)"
   ::= {er1646v2XEfmVlanEntry 251789312}

er1646v2XEfmVlanPppAuthenPeriod OBJECT-TYPE
   SYNTAX      TimeTicks
   MAX-ACCESS  read-write
   STATUS      current
   DESCRIPTION
      "Path: efm.editConf.vlan.ppp.authenPeriod

       Time in centi-second."
   ::= {er1646v2XEfmVlanEntry 251854848}

er1646v2XEfmVlanPppSessionName OBJECT-TYPE
   SYNTAX      DisplayString
   MAX-ACCESS  read-write
   STATUS      current
   DESCRIPTION
      "Path: efm.editConf.vlan.ppp.sessionName"
   ::= {er1646v2XEfmVlanEntry 251985920}

er1646v2XEfmVlanPppSessionSecret OBJECT-TYPE
   SYNTAX      DisplayString
   MAX-ACCESS  read-write
   STATUS      current
   DESCRIPTION
      "Path: efm.editConf.vlan.ppp.sessionSecret"
   ::= {er1646v2XEfmVlanEntry 252051456}

er1646v2XEfmVlanPppEncModeSessionSecret OBJECT-TYPE
   SYNTAX      INTEGER
               {
               none (1),
               encrypt (2),
               encType1 (3),
               invalid (128)
               }
   MAX-ACCESS  read-write
   STATUS      current
   DESCRIPTION
      "Path: efm.editConf.vlan.ppp.encModeSessionSecret

       Possibilities:
               none   (1)
               encrypt   (2)
               encType1   (3)
               invalid   (128)"
   ::= {er1646v2XEfmVlanEntry 252182528}

er1646v2XEfmVlanPppEncSessionSecret OBJECT-TYPE
   SYNTAX      DisplayString
   MAX-ACCESS  read-write
   STATUS      current
   DESCRIPTION
      "Path: efm.editConf.vlan.ppp.encSessionSecret"
   ::= {er1646v2XEfmVlanEntry 252248064}

er1646v2XEfmVlanPppServiceName OBJECT-TYPE
   SYNTAX      DisplayString
   MAX-ACCESS  read-write
   STATUS      current
   DESCRIPTION
      "Path: efm.editConf.vlan.ppp.serviceName"
   ::= {er1646v2XEfmVlanEntry 252116992}

er1646v2XEfmVlanPbbMode OBJECT-TYPE
   SYNTAX      INTEGER
               {
               disabled (0),
               static (1),
               dynamicPtp (2),
               dynamicPtmp (3)
               }
   MAX-ACCESS  read-write
   STATUS      current
   DESCRIPTION
      "Path: efm.editConf.vlan.pbb.mode

       Possibilities:
               disabled   (0)
               static   (1)
               dynamicPtp   (2)
               dynamicPtmp   (3)"
   ::= {er1646v2XEfmVlanEntry 1174667264}

er1646v2XEfmVlanPbbTxCos OBJECT-TYPE
   SYNTAX      Integer32
   MAX-ACCESS  read-write
   STATUS      current
   DESCRIPTION
      "Path: efm.editConf.vlan.pbb.txCos"
   ::= {er1646v2XEfmVlanEntry 1175191552}

er1646v2XEfmVlanPbbIsid OBJECT-TYPE
   SYNTAX      Integer32
   MAX-ACCESS  read-write
   STATUS      current
   DESCRIPTION
      "Path: efm.editConf.vlan.pbb.isid"
   ::= {er1646v2XEfmVlanEntry 1175453696}

er1646v2XEfmVlanPbbDestMac OBJECT-TYPE
   SYNTAX      OCTET STRING
   MAX-ACCESS  read-write
   STATUS      current
   DESCRIPTION
      "Path: efm.editConf.vlan.pbb.destMac

       MAC address."
   ::= {er1646v2XEfmVlanEntry 1175715840}

er1646v2XEfmVlanPbbCustomGroupMac OBJECT-TYPE
   SYNTAX      OCTET STRING
   MAX-ACCESS  read-write
   STATUS      current
   DESCRIPTION
      "Path: efm.editConf.vlan.pbb.customGroupMac

       MAC address."
   ::= {er1646v2XEfmVlanEntry 1175977984}

er1646v2XEfmVlanIpSaddr OBJECT-TYPE
   SYNTAX      SEQUENCE OF Er1646v2XEfmVlanIpSaddrEntry
   MAX-ACCESS  not-accessible
   STATUS      current
   DESCRIPTION
      ""
   ::= {er1646v2XEfmVlan 51838976}

er1646v2XEfmVlanIpSaddrEntry OBJECT-TYPE
   SYNTAX      Er1646v2XEfmVlanIpSaddrEntry
   MAX-ACCESS  not-accessible
   STATUS      current
   DESCRIPTION
      ""
   INDEX      { er1646v2XEfmVlanTableIx,
                er1646v2XEfmVlanIpSaddrTableIx }
   ::= {er1646v2XEfmVlanIpSaddr 1}

Er1646v2XEfmVlanIpSaddrEntry ::=
   SEQUENCE
      {
      er1646v2XEfmVlanIpSaddrActions
         VariableLengthTableActions,
      er1646v2XEfmVlanIpSaddrTableIx
         TableIndex,
      er1646v2XEfmVlanIpSaddrAddress
         IpAddress,
      er1646v2XEfmVlanIpSaddrNetMask
         IpAddress
      }

er1646v2XEfmVlanIpSaddrActions OBJECT-TYPE
   SYNTAX      VariableLengthTableActions
   MAX-ACCESS  read-write
   STATUS      current
   DESCRIPTION
      "By way of this field, some manipulations
       on this table may be performed."
   ::= {er1646v2XEfmVlanIpSaddrEntry 2}

er1646v2XEfmVlanIpSaddrTableIx OBJECT-TYPE
   SYNTAX      TableIndex
   MAX-ACCESS  not-accessible
   STATUS      current
   DESCRIPTION
      ""
   ::= {er1646v2XEfmVlanIpSaddrEntry 11}

er1646v2XEfmVlanIpSaddrAddress OBJECT-TYPE
   SYNTAX      IpAddress
   MAX-ACCESS  read-write
   STATUS      current
   DESCRIPTION
      "Path: efm.editConf.vlan.ip.secondaryIp.address"
   ::= {er1646v2XEfmVlanIpSaddrEntry 2030043136}

er1646v2XEfmVlanIpSaddrNetMask OBJECT-TYPE
   SYNTAX      IpAddress
   MAX-ACCESS  read-write
   STATUS      current
   DESCRIPTION
      "Path: efm.editConf.vlan.ip.secondaryIp.netMask"
   ::= {er1646v2XEfmVlanIpSaddrEntry 2063597568}

er1646v2XEfmVlanIpH OBJECT-TYPE
   SYNTAX      SEQUENCE OF Er1646v2XEfmVlanIpHEntry
   MAX-ACCESS  not-accessible
   STATUS      current
   DESCRIPTION
      ""
   ::= {er1646v2XEfmVlan 51314688}

er1646v2XEfmVlanIpHEntry OBJECT-TYPE
   SYNTAX      Er1646v2XEfmVlanIpHEntry
   MAX-ACCESS  not-accessible
   STATUS      current
   DESCRIPTION
      ""
   INDEX      { er1646v2XEfmVlanTableIx,
                er1646v2XEfmVlanIpHTableIx }
   ::= {er1646v2XEfmVlanIpH 1}

Er1646v2XEfmVlanIpHEntry ::=
   SEQUENCE
      {
      er1646v2XEfmVlanIpHActions
         VariableLengthTableActions,
      er1646v2XEfmVlanIpHTableIx
         TableIndex,
      er1646v2XEfmVlanIpHAddress
         IpAddress,
      er1646v2XEfmVlanIpHDhcpRelayOptionSubscriberId
         DisplayString
      }

er1646v2XEfmVlanIpHActions OBJECT-TYPE
   SYNTAX      VariableLengthTableActions
   MAX-ACCESS  read-write
   STATUS      current
   DESCRIPTION
      "By way of this field, some manipulations
       on this table may be performed."
   ::= {er1646v2XEfmVlanIpHEntry 2}

er1646v2XEfmVlanIpHTableIx OBJECT-TYPE
   SYNTAX      TableIndex
   MAX-ACCESS  not-accessible
   STATUS      current
   DESCRIPTION
      ""
   ::= {er1646v2XEfmVlanIpHEntry 11}

er1646v2XEfmVlanIpHAddress OBJECT-TYPE
   SYNTAX      IpAddress
   MAX-ACCESS  read-write
   STATUS      current
   DESCRIPTION
      "Path: efm.editConf.vlan.ip.helpers.address"
   ::= {er1646v2XEfmVlanIpHEntry 16777216}

er1646v2XEfmVlanIpHDhcpRelayOptionSubscriberId OBJECT-TYPE
   SYNTAX      DisplayString
   MAX-ACCESS  read-write
   STATUS      current
   DESCRIPTION
      "Path: efm.editConf.vlan.ip.helpers.dhcpRelayOption.subscriberId"
   ::= {er1646v2XEfmVlanIpHEntry 33947648}

er1646v2XEfmVlanIpV6Addresses OBJECT-TYPE
   SYNTAX      SEQUENCE OF Er1646v2XEfmVlanIpV6AddressesEntry
   MAX-ACCESS  not-accessible
   STATUS      current
   DESCRIPTION
      ""
   ::= {er1646v2XEfmVlan 704839680}

er1646v2XEfmVlanIpV6AddressesEntry OBJECT-TYPE
   SYNTAX      Er1646v2XEfmVlanIpV6AddressesEntry
   MAX-ACCESS  not-accessible
   STATUS      current
   DESCRIPTION
      ""
   INDEX      { er1646v2XEfmVlanTableIx,
                er1646v2XEfmVlanIpV6AddressesTableIx }
   ::= {er1646v2XEfmVlanIpV6Addresses 1}

Er1646v2XEfmVlanIpV6AddressesEntry ::=
   SEQUENCE
      {
      er1646v2XEfmVlanIpV6AddressesActions
         VariableLengthTableActions,
      er1646v2XEfmVlanIpV6AddressesTableIx
         TableIndex,
      er1646v2XEfmVlanIpV6AddressesType
         INTEGER,
      er1646v2XEfmVlanIpV6AddressesAddress
         Ipv6Address,
      er1646v2XEfmVlanIpV6AddressesPrefixLength
         Integer32,
      er1646v2XEfmVlanIpV6AddressesGeneralPrefix
         DisplayString,
      er1646v2XEfmVlanIpV6AddressesRaSend
         INTEGER,
      er1646v2XEfmVlanIpV6AddressesRaOnLinkFlag
         INTEGER,
      er1646v2XEfmVlanIpV6AddressesRaAutoFlag
         INTEGER,
      er1646v2XEfmVlanIpV6AddressesRaValidLifeTime
         TimeTicks,
      er1646v2XEfmVlanIpV6AddressesRaValidLTMode
         INTEGER,
      er1646v2XEfmVlanIpV6AddressesRaPrefLifeTime
         TimeTicks,
      er1646v2XEfmVlanIpV6AddressesRaPrefLTMode
         INTEGER
      }

er1646v2XEfmVlanIpV6AddressesActions OBJECT-TYPE
   SYNTAX      VariableLengthTableActions
   MAX-ACCESS  read-write
   STATUS      current
   DESCRIPTION
      "By way of this field, some manipulations
       on this table may be performed."
   ::= {er1646v2XEfmVlanIpV6AddressesEntry 2}

er1646v2XEfmVlanIpV6AddressesTableIx OBJECT-TYPE
   SYNTAX      TableIndex
   MAX-ACCESS  not-accessible
   STATUS      current
   DESCRIPTION
      ""
   ::= {er1646v2XEfmVlanIpV6AddressesEntry 11}

er1646v2XEfmVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.vlan.ipV6.addresses.type

       Possibilities:
               unicast   (0)
               eui64   (1)
               anycast   (2)
               linkLocal   (3)
               generalPrefix   (4)"
   ::= {er1646v2XEfmVlanIpV6AddressesEntry 50331648}

er1646v2XEfmVlanIpV6AddressesAddress OBJECT-TYPE
   SYNTAX      Ipv6Address
   MAX-ACCESS  read-write
   STATUS      current
   DESCRIPTION
      "Path: efm.editConf.vlan.ipV6.addresses.address

       ipv6 address"
   ::= {er1646v2XEfmVlanIpV6AddressesEntry 16777216}

er1646v2XEfmVlanIpV6AddressesPrefixLength OBJECT-TYPE
   SYNTAX      Integer32
   MAX-ACCESS  read-write
   STATUS      current
   DESCRIPTION
      "Path: efm.editConf.vlan.ipV6.addresses.prefixLength"
   ::= {er1646v2XEfmVlanIpV6AddressesEntry 33554432}

er1646v2XEfmVlanIpV6AddressesGeneralPrefix OBJECT-TYPE
   SYNTAX      DisplayString
   MAX-ACCESS  read-write
   STATUS      current
   DESCRIPTION
      "Path: efm.editConf.vlan.ipV6.addresses.generalPrefix"
   ::= {er1646v2XEfmVlanIpV6AddressesEntry 83886080}

er1646v2XEfmVlanIpV6AddressesRaSend OBJECT-TYPE
   SYNTAX      INTEGER
               {
               disabled (0),
               enabled (1)
               }
   MAX-ACCESS  read-write
   STATUS      current
   DESCRIPTION
      "Path: efm.editConf.vlan.ipV6.addresses.ra.send

       Possibilities:
               disabled   (0)
               enabled   (1)"
   ::= {er1646v2XEfmVlanIpV6AddressesEntry 67174400}

er1646v2XEfmVlanIpV6AddressesRaOnLinkFlag OBJECT-TYPE
   SYNTAX      INTEGER
               {
               disabled (0),
               enabled (1)
               }
   MAX-ACCESS  read-write
   STATUS      current
   DESCRIPTION
      "Path: efm.editConf.vlan.ipV6.addresses.ra.onLinkFlag

       Possibilities:
               disabled   (0)
               enabled   (1)"
   ::= {er1646v2XEfmVlanIpV6AddressesEntry 67371008}

er1646v2XEfmVlanIpV6AddressesRaAutoFlag OBJECT-TYPE
   SYNTAX      INTEGER
               {
               disabled (0),
               enabled (1)
               }
   MAX-ACCESS  read-write
   STATUS      current
   DESCRIPTION
      "Path: efm.editConf.vlan.ipV6.addresses.ra.autonomousFlag

       Possibilities:
               disabled   (0)
               enabled   (1)"
   ::= {er1646v2XEfmVlanIpV6AddressesEntry 67567616}

er1646v2XEfmVlanIpV6AddressesRaValidLifeTime OBJECT-TYPE
   SYNTAX      TimeTicks
   MAX-ACCESS  read-write
   STATUS      current
   DESCRIPTION
      "Path: efm.editConf.vlan.ipV6.addresses.ra.validLifeTime

       Time in centi-second."
   ::= {er1646v2XEfmVlanIpV6AddressesEntry 67239936}

er1646v2XEfmVlanIpV6AddressesRaValidLTMode OBJECT-TYPE
   SYNTAX      INTEGER
               {
               fixed (0),
               infinite (2)
               }
   MAX-ACCESS  read-write
   STATUS      current
   DESCRIPTION
      "Path: efm.editConf.vlan.ipV6.addresses.ra.validLifeTimeMode

       Possibilities:
               fixed   (0)
               infinite   (2)"
   ::= {er1646v2XEfmVlanIpV6AddressesEntry 67305472}

er1646v2XEfmVlanIpV6AddressesRaPrefLifeTime OBJECT-TYPE
   SYNTAX      TimeTicks
   MAX-ACCESS  read-write
   STATUS      current
   DESCRIPTION
      "Path: efm.editConf.vlan.ipV6.addresses.ra.prefLifeTime

       Time in centi-second."
   ::= {er1646v2XEfmVlanIpV6AddressesEntry 67436544}

er1646v2XEfmVlanIpV6AddressesRaPrefLTMode OBJECT-TYPE
   SYNTAX      INTEGER
               {
               fixed (0),
               infinite (2)
               }
   MAX-ACCESS  read-write
   STATUS      current
   DESCRIPTION
      "Path: efm.editConf.vlan.ipV6.addresses.ra.prefLifeTimeMode

       Possibilities:
               fixed   (0)
               infinite   (2)"
   ::= {er1646v2XEfmVlanIpV6AddressesEntry 67502080}

er1646v2XEfmVlanIpV6RaDnsOptionsRdnssServers OBJECT-TYPE
   SYNTAX      SEQUENCE OF Er1646v2XEfmVlanIpV6RaDnsOptionsRdnssServersEntry
   MAX-ACCESS  not-accessible
   STATUS      current
   DESCRIPTION
      ""
   ::= {er1646v2XEfmVlan 705039144}

er1646v2XEfmVlanIpV6RaDnsOptionsRdnssServersEntry OBJECT-TYPE
   SYNTAX      Er1646v2XEfmVlanIpV6RaDnsOptionsRdnssServersEntry
   MAX-ACCESS  not-accessible
   STATUS      current
   DESCRIPTION
      ""
   INDEX      { er1646v2XEfmVlanTableIx,
                er1646v2XEfmVlanIpV6RaDnsOptionsRdnssServersTableIx }
   ::= {er1646v2XEfmVlanIpV6RaDnsOptionsRdnssServers 1}

Er1646v2XEfmVlanIpV6RaDnsOptionsRdnssServersEntry ::=
   SEQUENCE
      {
      er1646v2XEfmVlanIpV6RaDnsOptionsRdnssServersActions
         VariableLengthTableActions,
      er1646v2XEfmVlanIpV6RaDnsOptionsRdnssServersTableIx
         TableIndex,
      er1646v2XEfmVlanIpV6RaDnsOptionsRdnssServersAddress
         Ipv6Address
      }

er1646v2XEfmVlanIpV6RaDnsOptionsRdnssServersActions OBJECT-TYPE
   SYNTAX      VariableLengthTableActions
   MAX-ACCESS  read-write
   STATUS      current
   DESCRIPTION
      "By way of this field, some manipulations
       on this table may be performed."
   ::= {er1646v2XEfmVlanIpV6RaDnsOptionsRdnssServersEntry 2}

er1646v2XEfmVlanIpV6RaDnsOptionsRdnssServersTableIx OBJECT-TYPE
   SYNTAX      TableIndex
   MAX-ACCESS  not-accessible
   STATUS      current
   DESCRIPTION
      ""
   ::= {er1646v2XEfmVlanIpV6RaDnsOptionsRdnssServersEntry 11}

er1646v2XEfmVlanIpV6RaDnsOptionsRdnssServersAddress OBJECT-TYPE
   SYNTAX      Ipv6Address
   MAX-ACCESS  read-write
   STATUS      current
   DESCRIPTION
      "Path: efm.editConf.vlan.ipV6.ra.dnsOptions.rdnss.servers.address

       ipv6 address"
   ::= {er1646v2XEfmVlanIpV6RaDnsOptionsRdnssServersEntry 16777216}

er1646v2XEfmVlanIpV6RaDnsOptionsDnsslDomains OBJECT-TYPE
   SYNTAX      SEQUENCE OF Er1646v2XEfmVlanIpV6RaDnsOptionsDnsslDomainsEntry
   MAX-ACCESS  not-accessible
   STATUS      current
   DESCRIPTION
      ""
   ::= {er1646v2XEfmVlan 705039176}

er1646v2XEfmVlanIpV6RaDnsOptionsDnsslDomainsEntry OBJECT-TYPE
   SYNTAX      Er1646v2XEfmVlanIpV6RaDnsOptionsDnsslDomainsEntry
   MAX-ACCESS  not-accessible
   STATUS      current
   DESCRIPTION
      ""
   INDEX      { er1646v2XEfmVlanTableIx,
                er1646v2XEfmVlanIpV6RaDnsOptionsDnsslDomainsTableIx }
   ::= {er1646v2XEfmVlanIpV6RaDnsOptionsDnsslDomains 1}

Er1646v2XEfmVlanIpV6RaDnsOptionsDnsslDomainsEntry ::=
   SEQUENCE
      {
      er1646v2XEfmVlanIpV6RaDnsOptionsDnsslDomainsActions
         VariableLengthTableActions,
      er1646v2XEfmVlanIpV6RaDnsOptionsDnsslDomainsTableIx
         TableIndex,
      er1646v2XEfmVlanIpV6RaDnsOptionsDnsslDomainsName
         DisplayString
      }

er1646v2XEfmVlanIpV6RaDnsOptionsDnsslDomainsActions OBJECT-TYPE
   SYNTAX      VariableLengthTableActions
   MAX-ACCESS  read-write
   STATUS      current
   DESCRIPTION
      "By way of this field, some manipulations
       on this table may be performed."
   ::= {er1646v2XEfmVlanIpV6RaDnsOptionsDnsslDomainsEntry 2}

er1646v2XEfmVlanIpV6RaDnsOptionsDnsslDomainsTableIx OBJECT-TYPE
   SYNTAX      TableIndex
   MAX-ACCESS  not-accessible
   STATUS      current
   DESCRIPTION
      ""
   ::= {er1646v2XEfmVlanIpV6RaDnsOptionsDnsslDomainsEntry 11}

er1646v2XEfmVlanIpV6RaDnsOptionsDnsslDomainsName OBJECT-TYPE
   SYNTAX      DisplayString
   MAX-ACCESS  read-write
   STATUS      current
   DESCRIPTION
      "Path: efm.editConf.vlan.ipV6.ra.dnsOptions.dnssl.domains.name"
   ::= {er1646v2XEfmVlanIpV6RaDnsOptionsDnsslDomainsEntry 16777216}

er1646v2XEfmVlanIpV6DhcpClientUserClassOpt OBJECT-TYPE
   SYNTAX      SEQUENCE OF Er1646v2XEfmVlanIpV6DhcpClientUserClassOptEntry
   MAX-ACCESS  not-accessible
   STATUS      current
   DESCRIPTION
      ""
   ::= {er1646v2XEfmVlan 705312768}

er1646v2XEfmVlanIpV6DhcpClientUserClassOptEntry OBJECT-TYPE
   SYNTAX      Er1646v2XEfmVlanIpV6DhcpClientUserClassOptEntry
   MAX-ACCESS  not-accessible
   STATUS      current
   DESCRIPTION
      ""
   INDEX      { er1646v2XEfmVlanTableIx,
                er1646v2XEfmVlanIpV6DhcpClientUserClassOptTableIx }
   ::= {er1646v2XEfmVlanIpV6DhcpClientUserClassOpt 1}

Er1646v2XEfmVlanIpV6DhcpClientUserClassOptEntry ::=
   SEQUENCE
      {
      er1646v2XEfmVlanIpV6DhcpClientUserClassOptActions
         VariableLengthTableActions,
      er1646v2XEfmVlanIpV6DhcpClientUserClassOptTableIx
         TableIndex,
      er1646v2XEfmVlanIpV6DhcpClientUserClassOptValueAscii
         DisplayString,
      er1646v2XEfmVlanIpV6DhcpClientUserClassOptValueDecimal
         Integer32,
      er1646v2XEfmVlanIpV6DhcpClientUserClassOptValueHexData
         OCTET STRING
      }

er1646v2XEfmVlanIpV6DhcpClientUserClassOptActions OBJECT-TYPE
   SYNTAX      VariableLengthTableActions
   MAX-ACCESS  read-write
   STATUS      current
   DESCRIPTION
      "By way of this field, some manipulations
       on this table may be performed."
   ::= {er1646v2XEfmVlanIpV6DhcpClientUserClassOptEntry 2}

er1646v2XEfmVlanIpV6DhcpClientUserClassOptTableIx OBJECT-TYPE
   SYNTAX      TableIndex
   MAX-ACCESS  not-accessible
   STATUS      current
   DESCRIPTION
      ""
   ::= {er1646v2XEfmVlanIpV6DhcpClientUserClassOptEntry 11}

er1646v2XEfmVlanIpV6DhcpClientUserClassOptValueAscii OBJECT-TYPE
   SYNTAX      DisplayString
   MAX-ACCESS  read-write
   STATUS      current
   DESCRIPTION
      "Path: efm.editConf.vlan.ipV6.dhcp.client.userClassOpt.value.ascii"
   ::= {er1646v2XEfmVlanIpV6DhcpClientUserClassOptEntry 16842752}

er1646v2XEfmVlanIpV6DhcpClientUserClassOptValueDecimal OBJECT-TYPE
   SYNTAX      Integer32
   MAX-ACCESS  read-write
   STATUS      current
   DESCRIPTION
      "Path: efm.editConf.vlan.ipV6.dhcp.client.userClassOpt.value.decimal"
   ::= {er1646v2XEfmVlanIpV6DhcpClientUserClassOptEntry 16908288}

er1646v2XEfmVlanIpV6DhcpClientUserClassOptValueHexData OBJECT-TYPE
   SYNTAX      OCTET STRING
   MAX-ACCESS  read-write
   STATUS      current
   DESCRIPTION
      "Path: efm.editConf.vlan.ipV6.dhcp.client.userClassOpt.value.hexData"
   ::= {er1646v2XEfmVlanIpV6DhcpClientUserClassOptEntry 16973824}

er1646v2XEfmVlanIpV6DhcpClientVendorCl OBJECT-TYPE
   SYNTAX      SEQUENCE OF Er1646v2XEfmVlanIpV6DhcpClientVendorClEntry
   MAX-ACCESS  not-accessible
   STATUS      current
   DESCRIPTION
      ""
   ::= {er1646v2XEfmVlan 705313792}

er1646v2XEfmVlanIpV6DhcpClientVendorClEntry OBJECT-TYPE
   SYNTAX      Er1646v2XEfmVlanIpV6DhcpClientVendorClEntry
   MAX-ACCESS  not-accessible
   STATUS      current
   DESCRIPTION
      ""
   INDEX      { er1646v2XEfmVlanTableIx,
                er1646v2XEfmVlanIpV6DhcpClientVendorClTableIx }
   ::= {er1646v2XEfmVlanIpV6DhcpClientVendorCl 1}

Er1646v2XEfmVlanIpV6DhcpClientVendorClEntry ::=
   SEQUENCE
      {
      er1646v2XEfmVlanIpV6DhcpClientVendorClActions
         VariableLengthTableActions,
      er1646v2XEfmVlanIpV6DhcpClientVendorClTableIx
         TableIndex,
      er1646v2XEfmVlanIpV6DhcpClientVendorClValueAscii
         DisplayString,
      er1646v2XEfmVlanIpV6DhcpClientVendorClValueDecimal
         Integer32,
      er1646v2XEfmVlanIpV6DhcpClientVendorClValueHexData
         OCTET STRING
      }

er1646v2XEfmVlanIpV6DhcpClientVendorClActions OBJECT-TYPE
   SYNTAX      VariableLengthTableActions
   MAX-ACCESS  read-write
   STATUS      current
   DESCRIPTION
      "By way of this field, some manipulations
       on this table may be performed."
   ::= {er1646v2XEfmVlanIpV6DhcpClientVendorClEntry 2}

er1646v2XEfmVlanIpV6DhcpClientVendorClTableIx OBJECT-TYPE
   SYNTAX      TableIndex
   MAX-ACCESS  not-accessible
   STATUS      current
   DESCRIPTION
      ""
   ::= {er1646v2XEfmVlanIpV6DhcpClientVendorClEntry 11}

er1646v2XEfmVlanIpV6DhcpClientVendorClValueAscii OBJECT-TYPE
   SYNTAX      DisplayString
   MAX-ACCESS  read-write
   STATUS      current
   DESCRIPTION
      "Path: efm.editConf.vlan.ipV6.dhcp.client.vendorClassOpt.value.ascii"
   ::= {er1646v2XEfmVlanIpV6DhcpClientVendorClEntry 16842752}

er1646v2XEfmVlanIpV6DhcpClientVendorClValueDecimal OBJECT-TYPE
   SYNTAX      Integer32
   MAX-ACCESS  read-write
   STATUS      current
   DESCRIPTION
      "Path: efm.editConf.vlan.ipV6.dhcp.client.vendorClassOpt.value.decimal"
   ::= {er1646v2XEfmVlanIpV6DhcpClientVendorClEntry 16908288}

er1646v2XEfmVlanIpV6DhcpClientVendorClValueHexData OBJECT-TYPE
   SYNTAX      OCTET STRING
   MAX-ACCESS  read-write
   STATUS      current
   DESCRIPTION
      "Path: efm.editConf.vlan.ipV6.dhcp.client.vendorClassOpt.value.hexData"
   ::= {er1646v2XEfmVlanIpV6DhcpClientVendorClEntry 16973824}

er1646v2XEfmVlanIpV6DhcpRelayDestinations OBJECT-TYPE
   SYNTAX      SEQUENCE OF Er1646v2XEfmVlanIpV6DhcpRelayDestinationsEntry
   MAX-ACCESS  not-accessible
   STATUS      current
   DESCRIPTION
      ""
   ::= {er1646v2XEfmVlan 705323072}

er1646v2XEfmVlanIpV6DhcpRelayDestinationsEntry OBJECT-TYPE
   SYNTAX      Er1646v2XEfmVlanIpV6DhcpRelayDestinationsEntry
   MAX-ACCESS  not-accessible
   STATUS      current
   DESCRIPTION
      ""
   INDEX      { er1646v2XEfmVlanTableIx,
                er1646v2XEfmVlanIpV6DhcpRelayDestinationsTableIx }
   ::= {er1646v2XEfmVlanIpV6DhcpRelayDestinations 1}

Er1646v2XEfmVlanIpV6DhcpRelayDestinationsEntry ::=
   SEQUENCE
      {
      er1646v2XEfmVlanIpV6DhcpRelayDestinationsActions
         VariableLengthTableActions,
      er1646v2XEfmVlanIpV6DhcpRelayDestinationsTableIx
         TableIndex,
      er1646v2XEfmVlanIpV6DhcpRelayDestinationsAddress
         Ipv6Address,
      er1646v2XEfmVlanIpV6DhcpRelayDestinationsInterface
         DisplayString
      }

er1646v2XEfmVlanIpV6DhcpRelayDestinationsActions OBJECT-TYPE
   SYNTAX      VariableLengthTableActions
   MAX-ACCESS  read-write
   STATUS      current
   DESCRIPTION
      "By way of this field, some manipulations
       on this table may be performed."
   ::= {er1646v2XEfmVlanIpV6DhcpRelayDestinationsEntry 2}

er1646v2XEfmVlanIpV6DhcpRelayDestinationsTableIx OBJECT-TYPE
   SYNTAX      TableIndex
   MAX-ACCESS  not-accessible
   STATUS      current
   DESCRIPTION
      ""
   ::= {er1646v2XEfmVlanIpV6DhcpRelayDestinationsEntry 11}

er1646v2XEfmVlanIpV6DhcpRelayDestinationsAddress OBJECT-TYPE
   SYNTAX      Ipv6Address
   MAX-ACCESS  read-write
   STATUS      current
   DESCRIPTION
      "Path: efm.editConf.vlan.ipV6.dhcp.relay.destinations.address

       ipv6 address"
   ::= {er1646v2XEfmVlanIpV6DhcpRelayDestinationsEntry 16777216}

er1646v2XEfmVlanIpV6DhcpRelayDestinationsInterface OBJECT-TYPE
   SYNTAX      DisplayString
   MAX-ACCESS  read-write
   STATUS      current
   DESCRIPTION
      "Path: efm.editConf.vlan.ipV6.dhcp.relay.destinations.interface"
   ::= {er1646v2XEfmVlanIpV6DhcpRelayDestinationsEntry 33554432}

er1646v2XEfmVlanBridgingVlTVlans OBJECT-TYPE
   SYNTAX      SEQUENCE OF Er1646v2XEfmVlanBridgingVlTVlansEntry
   MAX-ACCESS  not-accessible
   STATUS      current
   DESCRIPTION
      ""
   ::= {er1646v2XEfmVlan 459079680}

er1646v2XEfmVlanBridgingVlTVlansEntry OBJECT-TYPE
   SYNTAX      Er1646v2XEfmVlanBridgingVlTVlansEntry
   MAX-ACCESS  not-accessible
   STATUS      current
   DESCRIPTION
      ""
   INDEX      { er1646v2XEfmVlanTableIx,
                er1646v2XEfmVlanBridgingVlTVlansTableIx }
   ::= {er1646v2XEfmVlanBridgingVlTVlans 1}

Er1646v2XEfmVlanBridgingVlTVlansEntry ::=
   SEQUENCE
      {
      er1646v2XEfmVlanBridgingVlTVlansActions
         VariableLengthTableActions,
      er1646v2XEfmVlanBridgingVlTVlansTableIx
         TableIndex,
      er1646v2XEfmVlanBridgingVlTVlansVid
         Integer32,
      er1646v2XEfmVlanBridgingVlTVlansEndVid
         Integer32,
      er1646v2XEfmVlanBridgingVlTVlansAction
         INTEGER,
      er1646v2XEfmVlanBridgingVlTVlansTagInfoTpid
         INTEGER,
      er1646v2XEfmVlanBridgingVlTVlansTagInfoVid
         Integer32
      }

er1646v2XEfmVlanBridgingVlTVlansActions OBJECT-TYPE
   SYNTAX      VariableLengthTableActions
   MAX-ACCESS  read-write
   STATUS      current
   DESCRIPTION
      "By way of this field, some manipulations
       on this table may be performed."
   ::= {er1646v2XEfmVlanBridgingVlTVlansEntry 2}

er1646v2XEfmVlanBridgingVlTVlansTableIx OBJECT-TYPE
   SYNTAX      TableIndex
   MAX-ACCESS  not-accessible
   STATUS      current
   DESCRIPTION
      ""
   ::= {er1646v2XEfmVlanBridgingVlTVlansEntry 11}

er1646v2XEfmVlanBridgingVlTVlansVid OBJECT-TYPE
   SYNTAX      Integer32
   MAX-ACCESS  read-write
   STATUS      current
   DESCRIPTION
      "Path: efm.editConf.vlan.bridging.vlanTagging.vlans.vid"
   ::= {er1646v2XEfmVlanBridgingVlTVlansEntry 536870912}

er1646v2XEfmVlanBridgingVlTVlansEndVid OBJECT-TYPE
   SYNTAX      Integer32
   MAX-ACCESS  read-write
   STATUS      current
   DESCRIPTION
      "Path: efm.editConf.vlan.bridging.vlanTagging.vlans.endVid"
   ::= {er1646v2XEfmVlanBridgingVlTVlansEntry 2147483648}

er1646v2XEfmVlanBridgingVlTVlansAction OBJECT-TYPE
   SYNTAX      INTEGER
               {
               discard (0),
               accept (1),
               tag (2)
               }
   MAX-ACCESS  read-write
   STATUS      current
   DESCRIPTION
      "Path: efm.editConf.vlan.bridging.vlanTagging.vlans.action

       Possibilities:
               discard   (0)
               accept   (1)
               tag   (2)"
   ::= {er1646v2XEfmVlanBridgingVlTVlansEntry 1073741824}

er1646v2XEfmVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.vlans.tagInfo.tpid

       Possibilities:
               dot1Q   (33024)
               dot1ad   (34984)
               0x9100   (37120)
               0x9200   (37376)
               0x9300   (37632)"
   ::= {er1646v2XEfmVlanBridgingVlTVlansEntry 1677721600}

er1646v2XEfmVlanBridgingVlTVlansTagInfoVid OBJECT-TYPE
   SYNTAX      Integer32
   MAX-ACCESS  read-write
   STATUS      current
   DESCRIPTION
      "Path: efm.editConf.vlan.bridging.vlanTagging.vlans.tagInfo.vid"
   ::= {er1646v2XEfmVlanBridgingVlTVlansEntry 1744830464}

er1646v2XEfmVlanVlanVidExtensionTable OBJECT-TYPE
   SYNTAX      SEQUENCE OF Er1646v2XEfmVlanVlanVidExtensionTableEntry
   MAX-ACCESS  not-accessible
   STATUS      current
   DESCRIPTION
      ""
   ::= {er1646v2XEfmVlan 235340544}

er1646v2XEfmVlanVlanVidExtensionTableEntry OBJECT-TYPE
   SYNTAX      Er1646v2XEfmVlanVlanVidExtensionTableEntry
   MAX-ACCESS  not-accessible
   STATUS      current
   DESCRIPTION
      ""
   INDEX      { er1646v2XEfmVlanTableIx,
                er1646v2XEfmVlanVlanVidExtensionTableTableIx }
   ::= {er1646v2XEfmVlanVlanVidExtensionTable 1}

Er1646v2XEfmVlanVlanVidExtensionTableEntry ::=
   SEQUENCE
      {
      er1646v2XEfmVlanVlanVidExtensionTableActions
         VariableLengthTableActions,
      er1646v2XEfmVlanVlanVidExtensionTableTableIx
         TableIndex,
      er1646v2XEfmVlanVlanVidExtensionTableTpid
         INTEGER,
      er1646v2XEfmVlanVlanVidExtensionTableVid
         Integer32,
      er1646v2XEfmVlanVlanVidExtensionTableEndVid
         Integer32
      }

er1646v2XEfmVlanVlanVidExtensionTableActions OBJECT-TYPE
   SYNTAX      VariableLengthTableActions
   MAX-ACCESS  read-write
   STATUS      current
   DESCRIPTION
      "By way of this field, some manipulations
       on this table may be performed."
   ::= {er1646v2XEfmVlanVlanVidExtensionTableEntry 2}

er1646v2XEfmVlanVlanVidExtensionTableTableIx OBJECT-TYPE
   SYNTAX      TableIndex
   MAX-ACCESS  not-accessible
   STATUS      current
   DESCRIPTION
      ""
   ::= {er1646v2XEfmVlanVlanVidExtensionTableEntry 11}

er1646v2XEfmVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.vidExtension.table.tpid

       Possibilities:
               dot1Q   (33024)
               dot1ad   (34984)
               0x9100   (37120)
               0x9200   (37376)
               0x9300   (37632)"
   ::= {er1646v2XEfmVlanVlanVidExtensionTableEntry 16777216}

er1646v2XEfmVlanVlanVidExtensionTableVid OBJECT-TYPE
   SYNTAX      Integer32
   MAX-ACCESS  read-write
   STATUS      current
   DESCRIPTION
      "Path: efm.editConf.vlan.vlan.vidExtension.table.vid"
   ::= {er1646v2XEfmVlanVlanVidExtensionTableEntry 33554432}

er1646v2XEfmVlanVlanVidExtensionTableEndVid OBJECT-TYPE
   SYNTAX      Integer32
   MAX-ACCESS  read-write
   STATUS      current
   DESCRIPTION
      "Path: efm.editConf.vlan.vlan.vidExtension.table.endVid"
   ::= {er1646v2XEfmVlanVlanVidExtensionTableEntry 50331648}

er1646v2XEfmVlanVlanCSMap OBJECT-TYPE
   SYNTAX      SEQUENCE OF Er1646v2XEfmVlanVlanCSMapEntry
   MAX-ACCESS  not-accessible
   STATUS      current
   DESCRIPTION
      ""
   ::= {er1646v2XEfmVlan 235405312}

er1646v2XEfmVlanVlanCSMapEntry OBJECT-TYPE
   SYNTAX      Er1646v2XEfmVlanVlanCSMapEntry
   MAX-ACCESS  not-accessible
   STATUS      current
   DESCRIPTION
      ""
   INDEX      { er1646v2XEfmVlanTableIx,
                er1646v2XEfmVlanVlanCSMapTableIx }
   ::= {er1646v2XEfmVlanVlanCSMap 1}

Er1646v2XEfmVlanVlanCSMapEntry ::=
   SEQUENCE
      {
      er1646v2XEfmVlanVlanCSMapActions
         VariableLengthTableActions,
      er1646v2XEfmVlanVlanCSMapTableIx
         TableIndex,
      er1646v2XEfmVlanVlanCSMapCos
         INTEGER,
      er1646v2XEfmVlanVlanCSMapDei
         INTEGER,
      er1646v2XEfmVlanVlanCSMapTos
         INTEGER,
      er1646v2XEfmVlanVlanCSMapQueue
         INTEGER,
      er1646v2XEfmVlanVlanCSMapDropLevel
         INTEGER,
      er1646v2XEfmVlanVlanCSMapDeFlag
         INTEGER
      }

er1646v2XEfmVlanVlanCSMapActions OBJECT-TYPE
   SYNTAX      VariableLengthTableActions
   MAX-ACCESS  read-write
   STATUS      current
   DESCRIPTION
      "By way of this field, some manipulations
       on this table may be performed."
   ::= {er1646v2XEfmVlanVlanCSMapEntry 2}

er1646v2XEfmVlanVlanCSMapTableIx OBJECT-TYPE
   SYNTAX      TableIndex
   MAX-ACCESS  not-accessible
   STATUS      current
   DESCRIPTION
      ""
   ::= {er1646v2XEfmVlanVlanCSMapEntry 11}

er1646v2XEfmVlanVlanCSMapCos OBJECT-TYPE
   SYNTAX      INTEGER
               {
               any (8)
               }
   MAX-ACCESS  read-write
   STATUS      current
   DESCRIPTION
      "Path: efm.editConf.vlan.vlan.cosMap.cos

       Possibilities:
               any   (8)"
   ::= {er1646v2XEfmVlanVlanCSMapEntry 16777216}

er1646v2XEfmVlanVlanCSMapDei OBJECT-TYPE
   SYNTAX      INTEGER
               {
               clear (0),
               set (1),
               any (2)
               }
   MAX-ACCESS  read-write
   STATUS      current
   DESCRIPTION
      "Path: efm.editConf.vlan.vlan.cosMap.dei

       Possibilities:
               clear   (0)
               set   (1)
               any   (2)"
   ::= {er1646v2XEfmVlanVlanCSMapEntry 33554432}

er1646v2XEfmVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmVlanVlanCSMapEntry 50331648}

er1646v2XEfmVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2XEfmVlanVlanCSMapEntry 67108864}

er1646v2XEfmVlanVlanCSMapDropLevel OBJECT-TYPE
   SYNTAX      INTEGER
               {
               unchanged (-1),
               dropOnQueue (0)
               }
   MAX-ACCESS  read-write
   STATUS      current
   DESCRIPTION
      "Path: efm.editConf.vlan.vlan.cosMap.dropLevel

       Possibilities:
               unchanged   (-1)
               dropOnQueue   (0)"
   ::= {er1646v2XEfmVlanVlanCSMapEntry 83886080}

er1646v2XEfmVlanVlanCSMapDeFlag OBJECT-TYPE
   SYNTAX      INTEGER
               {
               unchanged (255),
               clear (0),
               set (1)
               }
   MAX-ACCESS  read-write
   STATUS      current
   DESCRIPTION
      "Path: efm.editConf.vlan.vlan.cosMap.deFlag

       Possibilities:
               unchanged   (255)
               clear   (0)
               set   (1)"
   ::= {er1646v2XEfmVlanVlanCSMapEntry 117440512}

er1646v2XEfmVlanVlanTCMap OBJECT-TYPE
   SYNTAX      SEQUENCE OF Er1646v2XEfmVlanVlanTCMapEntry
   MAX-ACCESS  not-accessible
   STATUS      current
   DESCRIPTION
      ""
   ::= {er1646v2XEfmVlan 241369088}

er1646v2XEfmVlanVlanTCMapEntry OBJECT-TYPE
   SYNTAX      Er1646v2XEfmVlanVlanTCMapEntry
   MAX-ACCESS  not-accessible
   STATUS      current
   DESCRIPTION
      ""
   INDEX      { er1646v2XEfmVlanTableIx,
                er1646v2XEfmVlanVlanTCMapTableIx }
   ::= {er1646v2XEfmVlanVlanTCMap 1}

Er1646v2XEfmVlanVlanTCMapEntry ::=
   SEQUENCE
      {
      er1646v2XEfmVlanVlanTCMapActions
         VariableLengthTableActions,
      er1646v2XEfmVlanVlanTCMapTableIx
         TableIndex,
      er1646v2XEfmVlanVlanTCMapStartTos
         INTEGER,
      er1646v2XEfmVlanVlanTCMapEndTos
         INTEGER,
      er1646v2XEfmVlanVlanTCMapCos
         INTEGER
      }

er1646v2XEfmVlanVlanTCMapActions OBJECT-TYPE
   SYNTAX      VariableLengthTableActions
   MAX-ACCESS  read-write
   STATUS      current
   DESCRIPTION
      "By way of this field, some manipulations
       on this table may be performed."
   ::= {er1646v2XEfmVlanVlanTCMapEntry 2}

er1646v2XEfmVlanVlanTCMapTableIx OBJECT-TYPE
   SYNTAX      TableIndex
   MAX-ACCESS  not-accessible
   STATUS      current
   DESCRIPTION
      ""
   ::= {er1646v2XEfmVlanVlanTCMapEntry 11}

er1646v2XEfmVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: efm.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2XEfmVlanVlanTCMapEntry 16777216}

er1646v2XEfmVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: efm.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2XEfmVlanVlanTCMapEntry 33554432}

er1646v2XEfmVlanVlanTCMapCos OBJECT-TYPE
   SYNTAX      INTEGER
               {
               queueCosMap (8)
               }
   MAX-ACCESS  read-write
   STATUS      current
   DESCRIPTION
      "Path: efm.editConf.vlan.vlan.tosCosMap.cos

       Possibilities:
               queueCosMap   (8)"
   ::= {er1646v2XEfmVlanVlanTCMapEntry 50331648}

er1646v2XEfmVlanVlanArpStaticArp OBJECT-TYPE
   SYNTAX      SEQUENCE OF Er1646v2XEfmVlanVlanArpStaticArpEntry
   MAX-ACCESS  not-accessible
   STATUS      current
   DESCRIPTION
      ""
   ::= {er1646v2XEfmVlan 235275008}

er1646v2XEfmVlanVlanArpStaticArpEntry OBJECT-TYPE
   SYNTAX      Er1646v2XEfmVlanVlanArpStaticArpEntry
   MAX-ACCESS  not-accessible
   STATUS      current
   DESCRIPTION
      ""
   INDEX      { er1646v2XEfmVlanTableIx,
                er1646v2XEfmVlanVlanArpStaticArpTableIx }
   ::= {er1646v2XEfmVlanVlanArpStaticArp 1}

Er1646v2XEfmVlanVlanArpStaticArpEntry ::=
   SEQUENCE
      {
      er1646v2XEfmVlanVlanArpStaticArpActions
         VariableLengthTableActions,
      er1646v2XEfmVlanVlanArpStaticArpTableIx
         TableIndex,
      er1646v2XEfmVlanVlanArpStaticArpMacAddress
         OCTET STRING,
      er1646v2XEfmVlanVlanArpStaticArpIpAddress
         IpAddress
      }

er1646v2XEfmVlanVlanArpStaticArpActions OBJECT-TYPE
   SYNTAX      VariableLengthTableActions
   MAX-ACCESS  read-write
   STATUS      current
   DESCRIPTION
      "By way of this field, some manipulations
       on this table may be performed."
   ::= {er1646v2XEfmVlanVlanArpStaticArpEntry 2}

er1646v2XEfmVlanVlanArpStaticArpTableIx OBJECT-TYPE
   SYNTAX      TableIndex
   MAX-ACCESS  not-accessible
   STATUS      current
   DESCRIPTION
      ""
   ::= {er1646v2XEfmVlanVlanArpStaticArpEntry 11}

er1646v2XEfmVlanVlanArpStaticArpMacAddress OBJECT-TYPE
   SYNTAX      OCTET STRING
   MAX-ACCESS  read-write
   STATUS      current
   DESCRIPTION
      "Path: efm.editConf.vlan.vlan.arp.staticArp.macAddress

       MAC address."
   ::= {er1646v2XEfmVlanVlanArpStaticArpEntry 16777216}

er1646v2XEfmVlanVlanArpStaticArpIpAddress OBJECT-TYPE
   SYNTAX      IpAddress
   MAX-ACCESS  read-write
   STATUS      current
   DESCRIPTION
      "Path: efm.editConf.vlan.vlan.arp.staticArp.ipAddress"
   ::= {er1646v2XEfmVlanVlanArpStaticArpEntry 33554432}


er1646v2XEfmPppOE OBJECT IDENTIFIER ::= {er1646v2XEfm 35}

er1646v2XEfmPppOESSCTable OBJECT-TYPE
   SYNTAX      SEQUENCE OF Er1646v2XEfmPppOEEntry
   MAX-ACCESS  not-accessible
   STATUS      current
   DESCRIPTION
      ""
   ::= {er1646v2XEfmPppOE 1}

er1646v2XEfmPppOEEntry OBJECT-TYPE
   SYNTAX      Er1646v2XEfmPppOEEntry
   MAX-ACCESS  not-accessible
   STATUS      current
   DESCRIPTION
      ""
   INDEX      { er1646v2XEfmPppOETableIx }
   ::= {er1646v2XEfmPppOESSCTable 1}

Er1646v2XEfmPppOEEntry ::=
   SEQUENCE
      {
      er1646v2XEfmPppOEActions
         VariableLengthTableActions,
      er1646v2XEfmPppOETableIx
         TableIndex,
      er1646v2XEfmPppOEName
         DisplayString,
      er1646v2XEfmPppOERemark
         DisplayString,
      er1646v2XEfmPppOEAdminStatus
         INTEGER,
      er1646v2XEfmPppOEMode
         INTEGER,
      er1646v2XEfmPppOEIpVrfRouter
         DisplayString,
      er1646v2XEfmPppOEIpAdr
         IpAddress,
      er1646v2XEfmPppOEIpNetm
         IpAddress,
      er1646v2XEfmPppOEIpSNetName
         INTEGER,
      er1646v2XEfmPppOEIpSNetCust
         DisplayString,
      er1646v2XEfmPppOEIpRem
         IpAddress,
      er1646v2XEfmPppOEIpUnnumbered
         DisplayString,
      er1646v2XEfmPppOEIpGwPref
         Integer32,
      er1646v2XEfmPppOEIpRsn
         INTEGER,
      er1646v2XEfmPppOEIpMtu
         Integer32,
      er1646v2XEfmPppOEIpMssAdjust
         INTEGER,
      er1646v2XEfmPppOEIpRipMetric
         Integer32,
      er1646v2XEfmPppOEIpRipMetricOut
         Integer32,
      er1646v2XEfmPppOEIpRipMode
         INTEGER,
      er1646v2XEfmPppOEIpRipTxVer
         INTEGER,
      er1646v2XEfmPppOEIpRipRxVer
         INTEGER,
      er1646v2XEfmPppOEIpRipSplitH
         INTEGER,
      er1646v2XEfmPppOEIpRipAuth
         INTEGER,
      er1646v2XEfmPppOEIpRipFilter
         DisplayString,
      er1646v2XEfmPppOEIpRipFilterIn
         DisplayString,
      er1646v2XEfmPppOEIpRipClearNextHop
         INTEGER,
      er1646v2XEfmPppOEIpAccPol
         DisplayString,
      er1646v2XEfmPppOEIpAB
         DisplayString,
      er1646v2XEfmPppOEIpMA
         INTEGER,
      er1646v2XEfmPppOEIpMF
         Integer32,
      er1646v2XEfmPppOEIpDB
         INTEGER,
      er1646v2XEfmPppOEIpIR
         INTEGER,
      er1646v2XEfmPppOEIpIgmp
         INTEGER,
      er1646v2XEfmPppOEIpNN
         DisplayString,
      er1646v2XEfmPppOEIpPimMode
         INTEGER,
      er1646v2XEfmPppOEIpPimDrPriority
         Counter32,
      er1646v2XEfmPppOEIpPimHelloTime
         TimeTicks,
      er1646v2XEfmPppOEIpPimPropagationDelay
         TimeTicks,
      er1646v2XEfmPppOEIpPimOverrideInterval
         TimeTicks,
      er1646v2XEfmPppOEIpPimBsrBorder
         INTEGER,
      er1646v2XEfmPppOEIpPimTtlThreshold
         Integer32,
      er1646v2XEfmPppOEIpIMNetworkUnreachable
         INTEGER,
      er1646v2XEfmPppOEIpIMHostUnreachable
         INTEGER,
      er1646v2XEfmPppOEIpIMProtocolUnreachable
         INTEGER,
      er1646v2XEfmPppOEIpIMPortUnreachable
         INTEGER,
      er1646v2XEfmPppOEIpIMMtuExceeded
         INTEGER,
      er1646v2XEfmPppOEIpIMAdminProhibited
         INTEGER,
      er1646v2XEfmPppOEIpIMTtlExceeded
         INTEGER,
      er1646v2XEfmPppOEIpIMRedirect
         INTEGER,
      er1646v2XEfmPppOEIpV6VrfRouter
         DisplayString,
      er1646v2XEfmPppOEIpV6AddrAutoConfigNrDupAddrDetects
         Integer32,
      er1646v2XEfmPppOEIpV6AddrAutoConfigAcceptRa
         INTEGER,
      er1646v2XEfmPppOEIpV6AddrAutoConfigAcceptRaRdnss
         INTEGER,
      er1646v2XEfmPppOEIpV6AddrAutoConfigAcceptRaDnssl
         INTEGER,
      er1646v2XEfmPppOEIpV6DefaultRoute
         INTEGER,
      er1646v2XEfmPppOEIpV6RaSend
         INTEGER,
      er1646v2XEfmPppOEIpV6RaMinInterval
         TimeTicks,
      er1646v2XEfmPppOEIpV6RaMaxInterval
         TimeTicks,
      er1646v2XEfmPppOEIpV6RaManagedFlag
         INTEGER,
      er1646v2XEfmPppOEIpV6RaOtherConfFlag
         INTEGER,
      er1646v2XEfmPppOEIpV6RaLinkMtu
         Integer32,
      er1646v2XEfmPppOEIpV6RaReachableTime
         TimeTicks,
      er1646v2XEfmPppOEIpV6RaRetransmitTime
         TimeTicks,
      er1646v2XEfmPppOEIpV6RaHopLimit
         Integer32,
      er1646v2XEfmPppOEIpV6RaDefaultLifeTime
         TimeTicks,
      er1646v2XEfmPppOEIpV6RaDnsOptionsRdnssLifeTime
         TimeTicks,
      er1646v2XEfmPppOEIpV6RaDnsOptionsRdnssImportServers
         INTEGER,
      er1646v2XEfmPppOEIpV6RaDnsOptionsDnsslLifeTime
         TimeTicks,
      er1646v2XEfmPppOEIpV6RaDnsOptionsDnsslImportDomains
         INTEGER,
      er1646v2XEfmPppOEIpV6RsSend
         INTEGER,
      er1646v2XEfmPppOEIpV6RsMaxRandomDelay
         TimeTicks,
      er1646v2XEfmPppOEIpV6RsInterval
         TimeTicks,
      er1646v2XEfmPppOEIpV6RsMaxSolicitations
         Integer32,
      er1646v2XEfmPppOEIpV6TrafficPolicyInbound
         DisplayString,
      er1646v2XEfmPppOEIpV6TrafficPolicyOutbound
         DisplayString,
      er1646v2XEfmPppOEIpV6FirewallZone
         DisplayString,
      er1646v2XEfmPppOEIpV6DhcpClientAddrAC
         INTEGER,
      er1646v2XEfmPppOEIpV6DhcpClientPrDelMode
         INTEGER,
      er1646v2XEfmPppOEIpV6DhcpClientPrDelPool
         DisplayString,
      er1646v2XEfmPppOEIpV6DhcpClientPrDelPdExclOpt
         INTEGER,
      er1646v2XEfmPppOEIpV6DhcpClientDnsServerPref
         Integer32,
      er1646v2XEfmPppOEIpV6DhcpClientRapidCommit
         INTEGER,
      er1646v2XEfmPppOEIpV6DhcpClientTimersSolTimeOut
         TimeTicks,
      er1646v2XEfmPppOEIpV6DhcpClientTimersSolMaxRt
         TimeTicks,
      er1646v2XEfmPppOEIpV6DhcpClientTimersInfoRefresh
         TimeTicks,
      er1646v2XEfmPppOEIpV6DhcpServerMode
         INTEGER,
      er1646v2XEfmPppOEIpV6DhcpServerPreference
         Integer32,
      er1646v2XEfmPppOEIpV6DhcpServerPool
         DisplayString,
      er1646v2XEfmPppOEIpV6DhcpServerRapidCommit
         INTEGER,
      er1646v2XEfmPppOEIpV6DhcpServerTimersInfoRefresh
         TimeTicks,
      er1646v2XEfmPppOEIpV6DhcpRelayMode
         INTEGER,
      er1646v2XEfmPppOEIpV6SendRedirect
         INTEGER,
      er1646v2XEfmPppOEIpV6LinkMtu
         Integer32,
      er1646v2XEfmPppOEIpV6InterfaceId
         OCTET STRING,
      er1646v2XEfmPppOEIpV6MF
         Integer32,
      er1646v2XEfmPppOEIpV6IcmpMessagesNoRoute
         INTEGER,
      er1646v2XEfmPppOEIpV6IcmpMessagesBeyondScope
         INTEGER,
      er1646v2XEfmPppOEIpV6IcmpMessagesAddressUnreachable
         INTEGER,
      er1646v2XEfmPppOEIpV6IcmpMessagesPortUnreachable
         INTEGER,
      er1646v2XEfmPppOEIpV6IcmpMessagesPacketTooBig
         INTEGER,
      er1646v2XEfmPppOEIpV6IcmpMessagesHopLimitExceeded
         INTEGER,
      er1646v2XEfmPppOEIpV6IcmpMessagesFragTimeExceeded
         INTEGER,
      er1646v2XEfmPppOEIpV6IcmpMessagesHeaderFieldErr
         INTEGER,
      er1646v2XEfmPppOEIpV6IcmpMessagesOptionUnrecognized
         INTEGER,
      er1646v2XEfmPppOEIpV6IcmpMessagesRedirect
         INTEGER,
      er1646v2XEfmPppOEPppLnkMOperation
         INTEGER,
      er1646v2XEfmPppOEPppLnkMInterval
         TimeTicks,
      er1646v2XEfmPppOEPppLnkMRepTimeOut
         TimeTicks,
      er1646v2XEfmPppOEPppLnkMFailsPrmt
         Integer32,
      er1646v2XEfmPppOEPppAuthentication
         INTEGER,
      er1646v2XEfmPppOEPppAuthenPeriod
         TimeTicks,
      er1646v2XEfmPppOEPppSessionName
         DisplayString,
      er1646v2XEfmPppOEPppSessionSecret
         DisplayString,
      er1646v2XEfmPppOEPppEncModeSessionSecret
         INTEGER,
      er1646v2XEfmPppOEPppEncSessionSecret
         DisplayString,
      er1646v2XEfmPppOEPppServiceName
         DisplayString
      }

er1646v2XEfmPppOEActions OBJECT-TYPE
   SYNTAX      VariableLengthTableActions
   MAX-ACCESS  read-write
   STATUS      current
   DESCRIPTION
      "By way of this field, some manipulations
       on this table may be performed."
   ::= {er1646v2XEfmPppOEEntry 2}

er1646v2XEfmPppOETableIx OBJECT-TYPE
   SYNTAX      TableIndex
   MAX-ACCESS  not-accessible
   STATUS      current
   DESCRIPTION
      ""
   ::= {er1646v2XEfmPppOEEntry 11}

er1646v2XEfmPppOEName OBJECT-TYPE
   SYNTAX      DisplayString
   MAX-ACCESS  read-write
   STATUS      current
   DESCRIPTION
      "Path: efm.editConf.pppoEClient.name"
   ::= {er1646v2XEfmPppOEEntry 16777216}

er1646v2XEfmPppOERemark OBJECT-TYPE
   SYNTAX      DisplayString
   MAX-ACCESS  read-write
   STATUS      current
   DESCRIPTION
      "Path: efm.editConf.pppoEClient.remark"
   ::= {er1646v2XEfmPppOEEntry 1157627904}

er1646v2XEfmPppOEAdminStatus OBJECT-TYPE
   SYNTAX      INTEGER
               {
               up (1),
               down (2)
               }
   MAX-ACCESS  read-write
   STATUS      current
   DESCRIPTION
      "Path: efm.editConf.pppoEClient.adminStatus

       Possibilities:
               up   (1)
               down   (2)"
   ::= {er1646v2XEfmPppOEEntry 33554432}

er1646v2XEfmPppOEMode OBJECT-TYPE
   SYNTAX      INTEGER
               {
               routing (1),
               multilink (8),
               ipV6 (16),
               ipV6ipV4 (17)
               }
   MAX-ACCESS  read-write
   STATUS      current
   DESCRIPTION
      "Path: efm.editConf.pppoEClient.mode

       Possibilities:
               routing   (1)
               multilink   (8)
               ipV6   (16)
               ipV6/ipV4   (17)"
   ::= {er1646v2XEfmPppOEEntry 67108864}

er1646v2XEfmPppOEIpVrfRouter OBJECT-TYPE
   SYNTAX      DisplayString
   MAX-ACCESS  read-write
   STATUS      current
   DESCRIPTION
      "Path: efm.editConf.pppoEClient.ip.vrfRouter"
   ::= {er1646v2XEfmPppOEEntry 53215232}

er1646v2XEfmPppOEIpAdr OBJECT-TYPE
   SYNTAX      IpAddress
   MAX-ACCESS  read-write
   STATUS      current
   DESCRIPTION
      "Path: efm.editConf.pppoEClient.ip.address"
   ::= {er1646v2XEfmPppOEEntry 58261504}

er1646v2XEfmPppOEIpNetm OBJECT-TYPE
   SYNTAX      IpAddress
   MAX-ACCESS  read-write
   STATUS      current
   DESCRIPTION
      "Path: efm.editConf.pppoEClient.ip.netMask"
   ::= {er1646v2XEfmPppOEEntry 58392576}

er1646v2XEfmPppOEIpSNetName OBJECT-TYPE
   SYNTAX      INTEGER
               {
               slOPTg (0),
               corp (2),
               dmz (3),
               internet (1)
               }
   MAX-ACCESS  read-write
   STATUS      current
   DESCRIPTION
      "Path: efm.editConf.pppoEClient.ip.sNet.name

       Possibilities:
               <OPT>   (0)
               corp   (2)
               dmz   (3)
               internet   (1)"
   ::= {er1646v2XEfmPppOEEntry 53674240}

er1646v2XEfmPppOEIpSNetCust OBJECT-TYPE
   SYNTAX      DisplayString
   MAX-ACCESS  read-write
   STATUS      current
   DESCRIPTION
      "Path: efm.editConf.pppoEClient.ip.sNet.custom"
   ::= {er1646v2XEfmPppOEEntry 53674496}

er1646v2XEfmPppOEIpRem OBJECT-TYPE
   SYNTAX      IpAddress
   MAX-ACCESS  read-write
   STATUS      current
   DESCRIPTION
      "Path: efm.editConf.pppoEClient.ip.remote"
   ::= {er1646v2XEfmPppOEEntry 58458112}

er1646v2XEfmPppOEIpUnnumbered OBJECT-TYPE
   SYNTAX      DisplayString
   MAX-ACCESS  read-write
   STATUS      current
   DESCRIPTION
      "Path: efm.editConf.pppoEClient.ip.unnumbered"
   ::= {er1646v2XEfmPppOEEntry 52625408}

er1646v2XEfmPppOEIpGwPref OBJECT-TYPE
   SYNTAX      Integer32
   MAX-ACCESS  read-write
   STATUS      current
   DESCRIPTION
      "Path: efm.editConf.pppoEClient.ip.gatewayPreference"
   ::= {er1646v2XEfmPppOEEntry 52690944}

er1646v2XEfmPppOEIpRsn OBJECT-TYPE
   SYNTAX      INTEGER
               {
               disabled (0),
               enabled (1)
               }
   MAX-ACCESS  read-write
   STATUS      current
   DESCRIPTION
      "Path: efm.editConf.pppoEClient.ip.requestSubnet

       Possibilities:
               disabled   (0)
               enabled   (1)"
   ::= {er1646v2XEfmPppOEEntry 56688640}

er1646v2XEfmPppOEIpMtu OBJECT-TYPE
   SYNTAX      Integer32
   MAX-ACCESS  read-write
   STATUS      current
   DESCRIPTION
      "Path: efm.editConf.pppoEClient.ip.mtu"
   ::= {er1646v2XEfmPppOEEntry 52953088}

er1646v2XEfmPppOEIpMssAdjust OBJECT-TYPE
   SYNTAX      INTEGER
               {
               disabled (0),
               auto (65536)
               }
   MAX-ACCESS  read-write
   STATUS      current
   DESCRIPTION
      "Path: efm.editConf.pppoEClient.ip.mssAdjust

       Possibilities:
               disabled   (0)
               auto   (65536)"
   ::= {er1646v2XEfmPppOEEntry 53280768}

er1646v2XEfmPppOEIpRipMetric OBJECT-TYPE
   SYNTAX      Integer32
   MAX-ACCESS  read-write
   STATUS      current
   DESCRIPTION
      "Path: efm.editConf.pppoEClient.ip.rip.metric"
   ::= {er1646v2XEfmPppOEEntry 51712768}

er1646v2XEfmPppOEIpRipMetricOut OBJECT-TYPE
   SYNTAX      Integer32
   MAX-ACCESS  read-write
   STATUS      current
   DESCRIPTION
      "Path: efm.editConf.pppoEClient.ip.rip.metricOut"
   ::= {er1646v2XEfmPppOEEntry 51713024}

er1646v2XEfmPppOEIpRipMode OBJECT-TYPE
   SYNTAX      INTEGER
               {
               disabled (0),
               passive (1),
               active (2)
               }
   MAX-ACCESS  read-write
   STATUS      current
   DESCRIPTION
      "Path: efm.editConf.pppoEClient.ip.rip.mode

       Possibilities:
               disabled   (0)
               passive   (1)
               active   (2)"
   ::= {er1646v2XEfmPppOEEntry 51713280}

er1646v2XEfmPppOEIpRipTxVer OBJECT-TYPE
   SYNTAX      INTEGER
               {
               rip1 (0),
               rip2 (1),
               rip1mcompatible (2)
               }
   MAX-ACCESS  read-write
   STATUS      current
   DESCRIPTION
      "Path: efm.editConf.pppoEClient.ip.rip.txVersion

       Possibilities:
               rip1   (0)
               rip2   (1)
               rip1-compatible   (2)"
   ::= {er1646v2XEfmPppOEEntry 51716864}

er1646v2XEfmPppOEIpRipRxVer OBJECT-TYPE
   SYNTAX      INTEGER
               {
               rip1only (0),
               rip2only (1),
               rip12 (2)
               }
   MAX-ACCESS  read-write
   STATUS      current
   DESCRIPTION
      "Path: efm.editConf.pppoEClient.ip.rip.rxVersion

       Possibilities:
               rip1only   (0)
               rip2only   (1)
               rip1&2   (2)"
   ::= {er1646v2XEfmPppOEEntry 51717120}

er1646v2XEfmPppOEIpRipSplitH OBJECT-TYPE
   SYNTAX      INTEGER
               {
               disabled (0),
               enabled (1),
               poisonedReverse (2)
               }
   MAX-ACCESS  read-write
   STATUS      current
   DESCRIPTION
      "Path: efm.editConf.pppoEClient.ip.rip.splitHorizon

       Possibilities:
               disabled   (0)
               enabled   (1)
               poisonedReverse   (2)"
   ::= {er1646v2XEfmPppOEEntry 51713792}

er1646v2XEfmPppOEIpRipAuth OBJECT-TYPE
   SYNTAX      INTEGER
               {
               disabled (0),
               texts (1),
               md5 (2)
               }
   MAX-ACCESS  read-write
   STATUS      current
   DESCRIPTION
      "Path: efm.editConf.pppoEClient.ip.rip.authentication

       Possibilities:
               disabled   (0)
               text    (1)
               md5   (2)"
   ::= {er1646v2XEfmPppOEEntry 51712512}

er1646v2XEfmPppOEIpRipFilter OBJECT-TYPE
   SYNTAX      DisplayString
   MAX-ACCESS  read-write
   STATUS      current
   DESCRIPTION
      "Path: efm.editConf.pppoEClient.ip.rip.filter"
   ::= {er1646v2XEfmPppOEEntry 51716096}

er1646v2XEfmPppOEIpRipFilterIn OBJECT-TYPE
   SYNTAX      DisplayString
   MAX-ACCESS  read-write
   STATUS      current
   DESCRIPTION
      "Path: efm.editConf.pppoEClient.ip.rip.filterIn"
   ::= {er1646v2XEfmPppOEEntry 51716352}

er1646v2XEfmPppOEIpRipClearNextHop OBJECT-TYPE
   SYNTAX      INTEGER
               {
               disabled (0),
               enabled (1)
               }
   MAX-ACCESS  read-write
   STATUS      current
   DESCRIPTION
      "Path: efm.editConf.pppoEClient.ip.rip.clearNextHop

       Possibilities:
               disabled   (0)
               enabled   (1)"
   ::= {er1646v2XEfmPppOEEntry 51708416}

er1646v2XEfmPppOEIpAccPol OBJECT-TYPE
   SYNTAX      DisplayString
   MAX-ACCESS  read-write
   STATUS      current
   DESCRIPTION
      "Path: efm.editConf.pppoEClient.ip.accessPolicy"
   ::= {er1646v2XEfmPppOEEntry 53084160}

er1646v2XEfmPppOEIpAB OBJECT-TYPE
   SYNTAX      DisplayString
   MAX-ACCESS  read-write
   STATUS      current
   DESCRIPTION
      "Path: efm.editConf.pppoEClient.ip.trafficPolicy"
   ::= {er1646v2XEfmPppOEEntry 51249152}

er1646v2XEfmPppOEIpMA OBJECT-TYPE
   SYNTAX      INTEGER
               {
               disabled (0),
               enabled (1)
               }
   MAX-ACCESS  read-write
   STATUS      current
   DESCRIPTION
      "Path: efm.editConf.pppoEClient.ip.mgmtAccess

       Possibilities:
               disabled   (0)
               enabled   (1)"
   ::= {er1646v2XEfmPppOEEntry 51380224}

er1646v2XEfmPppOEIpMF OBJECT-TYPE
   SYNTAX      Integer32
   MAX-ACCESS  read-write
   STATUS      current
   DESCRIPTION
      "Path: efm.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2XEfmPppOEEntry 51445760}

er1646v2XEfmPppOEIpDB OBJECT-TYPE
   SYNTAX      INTEGER
               {
               disabled (0),
               enabled (1)
               }
   MAX-ACCESS  read-write
   STATUS      current
   DESCRIPTION
      "Path: efm.editConf.pppoEClient.ip.directedBroadcasts

       Possibilities:
               disabled   (0)
               enabled   (1)"
   ::= {er1646v2XEfmPppOEEntry 51773440}

er1646v2XEfmPppOEIpIR OBJECT-TYPE
   SYNTAX      INTEGER
               {
               disabled (0),
               enabled (1)
               }
   MAX-ACCESS  read-write
   STATUS      current
   DESCRIPTION
      "Path: efm.editConf.pppoEClient.ip.icmpRedirects

       Possibilities:
               disabled   (0)
               enabled   (1)"
   ::= {er1646v2XEfmPppOEEntry 52035584}

er1646v2XEfmPppOEIpIgmp OBJECT-TYPE
   SYNTAX      INTEGER
               {
               disabled (0),
               proxy (1),
               router (2),
               v3Router (5)
               }
   MAX-ACCESS  read-write
   STATUS      current
   DESCRIPTION
      "Path: efm.editConf.pppoEClient.ip.igmp

       Possibilities:
               disabled   (0)
               proxy   (1)
               router   (2)
               v3Router   (5)"
   ::= {er1646v2XEfmPppOEEntry 52428800}

er1646v2XEfmPppOEIpNN OBJECT-TYPE
   SYNTAX      DisplayString
   MAX-ACCESS  read-write
   STATUS      current
   DESCRIPTION
      "Path: efm.editConf.pppoEClient.ip.nat"
   ::= {er1646v2XEfmPppOEEntry 52101120}

er1646v2XEfmPppOEIpPimMode OBJECT-TYPE
   SYNTAX      INTEGER
               {
               disabled (0),
               sparse (1),
               passive (2)
               }
   MAX-ACCESS  read-write
   STATUS      current
   DESCRIPTION
      "Path: efm.editConf.pppoEClient.ip.pim.mode

       Possibilities:
               disabled   (0)
               sparse   (1)
               passive   (2)"
   ::= {er1646v2XEfmPppOEEntry 53346560}

er1646v2XEfmPppOEIpPimDrPriority OBJECT-TYPE
   SYNTAX      Counter32
   MAX-ACCESS  read-write
   STATUS      current
   DESCRIPTION
      "Path: efm.editConf.pppoEClient.ip.pim.drPriority

       32 bit unsigned wrappable counter."
   ::= {er1646v2XEfmPppOEEntry 53346816}

er1646v2XEfmPppOEIpPimHelloTime OBJECT-TYPE
   SYNTAX      TimeTicks
   MAX-ACCESS  read-write
   STATUS      current
   DESCRIPTION
      "Path: efm.editConf.pppoEClient.ip.pim.helloTime

       Time in centi-second."
   ::= {er1646v2XEfmPppOEEntry 53347072}

er1646v2XEfmPppOEIpPimPropagationDelay OBJECT-TYPE
   SYNTAX      TimeTicks
   MAX-ACCESS  read-write
   STATUS      current
   DESCRIPTION
      "Path: efm.editConf.pppoEClient.ip.pim.propagationDelay

       Time in centi-second."
   ::= {er1646v2XEfmPppOEEntry 53347328}

er1646v2XEfmPppOEIpPimOverrideInterval OBJECT-TYPE
   SYNTAX      TimeTicks
   MAX-ACCESS  read-write
   STATUS      current
   DESCRIPTION
      "Path: efm.editConf.pppoEClient.ip.pim.overrideInterval

       Time in centi-second."
   ::= {er1646v2XEfmPppOEEntry 53347584}

er1646v2XEfmPppOEIpPimBsrBorder OBJECT-TYPE
   SYNTAX      INTEGER
               {
               disabled (0),
               enabled (1)
               }
   MAX-ACCESS  read-write
   STATUS      current
   DESCRIPTION
      "Path: efm.editConf.pppoEClient.ip.pim.bsrBorder

       Possibilities:
               disabled   (0)
               enabled   (1)"
   ::= {er1646v2XEfmPppOEEntry 53347840}

er1646v2XEfmPppOEIpPimTtlThreshold OBJECT-TYPE
   SYNTAX      Integer32
   MAX-ACCESS  read-write
   STATUS      current
   DESCRIPTION
      "Path: efm.editConf.pppoEClient.ip.pim.ttlThreshold"
   ::= {er1646v2XEfmPppOEEntry 53348096}

er1646v2XEfmPppOEIpIMNetworkUnreachable OBJECT-TYPE
   SYNTAX      INTEGER
               {
               disabled (0),
               enabled (1)
               }
   MAX-ACCESS  read-write
   STATUS      current
   DESCRIPTION
      "Path: efm.editConf.pppoEClient.ip.icmpMessages.networkUnreachable

       Possibilities:
               disabled   (0)
               enabled   (1)"
   ::= {er1646v2XEfmPppOEEntry 53412096}

er1646v2XEfmPppOEIpIMHostUnreachable OBJECT-TYPE
   SYNTAX      INTEGER
               {
               disabled (0),
               enabled (1)
               }
   MAX-ACCESS  read-write
   STATUS      current
   DESCRIPTION
      "Path: efm.editConf.pppoEClient.ip.icmpMessages.hostUnreachable

       Possibilities:
               disabled   (0)
               enabled   (1)"
   ::= {er1646v2XEfmPppOEEntry 53412352}

er1646v2XEfmPppOEIpIMProtocolUnreachable OBJECT-TYPE
   SYNTAX      INTEGER
               {
               disabled (0),
               enabled (1)
               }
   MAX-ACCESS  read-write
   STATUS      current
   DESCRIPTION
      "Path: efm.editConf.pppoEClient.ip.icmpMessages.protocolUnreachable

       Possibilities:
               disabled   (0)
               enabled   (1)"
   ::= {er1646v2XEfmPppOEEntry 53412608}

er1646v2XEfmPppOEIpIMPortUnreachable OBJECT-TYPE
   SYNTAX      INTEGER
               {
               disabled (0),
               enabled (1)
               }
   MAX-ACCESS  read-write
   STATUS      current
   DESCRIPTION
      "Path: efm.editConf.pppoEClient.ip.icmpMessages.portUnreachable

       Possibilities:
               disabled   (0)
               enabled   (1)"
   ::= {er1646v2XEfmPppOEEntry 53412864}

er1646v2XEfmPppOEIpIMMtuExceeded OBJECT-TYPE
   SYNTAX      INTEGER
               {
               disabled (0),
               enabled (1)
               }
   MAX-ACCESS  read-write
   STATUS      current
   DESCRIPTION
      "Path: efm.editConf.pppoEClient.ip.icmpMessages.mtuExceeded

       Possibilities:
               disabled   (0)
               enabled   (1)"
   ::= {er1646v2XEfmPppOEEntry 53413120}

er1646v2XEfmPppOEIpIMAdminProhibited OBJECT-TYPE
   SYNTAX      INTEGER
               {
               disabled (0),
               enabled (1)
               }
   MAX-ACCESS  read-write
   STATUS      current
   DESCRIPTION
      "Path: efm.editConf.pppoEClient.ip.icmpMessages.adminProhibited

       Possibilities:
               disabled   (0)
               enabled   (1)"
   ::= {er1646v2XEfmPppOEEntry 53413376}

er1646v2XEfmPppOEIpIMTtlExceeded OBJECT-TYPE
   SYNTAX      INTEGER
               {
               disabled (0),
               enabled (1)
               }
   MAX-ACCESS  read-write
   STATUS      current
   DESCRIPTION
      "Path: efm.editConf.pppoEClient.ip.icmpMessages.ttlExceeded

       Possibilities:
               disabled   (0)
               enabled   (1)"
   ::= {er1646v2XEfmPppOEEntry 53413632}

er1646v2XEfmPppOEIpIMRedirect OBJECT-TYPE
   SYNTAX      INTEGER
               {
               disabled (0),
               enabled (1)
               }
   MAX-ACCESS  read-write
   STATUS      current
   DESCRIPTION
      "Path: efm.editConf.pppoEClient.ip.icmpMessages.redirect

       Possibilities:
               disabled   (0)
               enabled   (1)"
   ::= {er1646v2XEfmPppOEEntry 53413888}

er1646v2XEfmPppOEIpV6VrfRouter OBJECT-TYPE
   SYNTAX      DisplayString
   MAX-ACCESS  read-write
   STATUS      current
   DESCRIPTION
      "Path: efm.editConf.pppoEClient.ipV6.vrfRouter"
   ::= {er1646v2XEfmPppOEEntry 704708608}

er1646v2XEfmPppOEIpV6AddrAutoConfigNrDupAddrDetects OBJECT-TYPE
   SYNTAX      Integer32
   MAX-ACCESS  read-write
   STATUS      current
   DESCRIPTION
      "Path: efm.editConf.pppoEClient.ipV6.addrAutoConfig.nrDupAddrDetects"
   ::= {er1646v2XEfmPppOEEntry 704905472}

er1646v2XEfmPppOEIpV6AddrAutoConfigAcceptRa OBJECT-TYPE
   SYNTAX      INTEGER
               {
               disabled (0),
               enabled (1)
               }
   MAX-ACCESS  read-write
   STATUS      current
   DESCRIPTION
      "Path: efm.editConf.pppoEClient.ipV6.addrAutoConfig.acceptRa

       Possibilities:
               disabled   (0)
               enabled   (1)"
   ::= {er1646v2XEfmPppOEEntry 704905728}

er1646v2XEfmPppOEIpV6AddrAutoConfigAcceptRaRdnss OBJECT-TYPE
   SYNTAX      INTEGER
               {
               disabled (0),
               enabled (1)
               }
   MAX-ACCESS  read-write
   STATUS      current
   DESCRIPTION
      "Path: efm.editConf.pppoEClient.ipV6.addrAutoConfig.acceptRaRdnss

       Possibilities:
               disabled   (0)
               enabled   (1)"
   ::= {er1646v2XEfmPppOEEntry 704905984}

er1646v2XEfmPppOEIpV6AddrAutoConfigAcceptRaDnssl OBJECT-TYPE
   SYNTAX      INTEGER
               {
               disabled (0),
               enabled (1)
               }
   MAX-ACCESS  read-write
   STATUS      current
   DESCRIPTION
      "Path: efm.editConf.pppoEClient.ipV6.addrAutoConfig.acceptRaDnssl

       Possibilities:
               disabled   (0)
               enabled   (1)"
   ::= {er1646v2XEfmPppOEEntry 704906240}

er1646v2XEfmPppOEIpV6DefaultRoute OBJECT-TYPE
   SYNTAX      INTEGER
               {
               disabled (0),
               enabled (1)
               }
   MAX-ACCESS  read-write
   STATUS      current
   DESCRIPTION
      "Path: efm.editConf.pppoEClient.ipV6.defaultRoute

       Possibilities:
               disabled   (0)
               enabled   (1)"
   ::= {er1646v2XEfmPppOEEntry 704970752}

er1646v2XEfmPppOEIpV6RaSend OBJECT-TYPE
   SYNTAX      INTEGER
               {
               disabled (0),
               enabled (1)
               }
   MAX-ACCESS  read-write
   STATUS      current
   DESCRIPTION
      "Path: efm.editConf.pppoEClient.ipV6.ra.send

       Possibilities:
               disabled   (0)
               enabled   (1)"
   ::= {er1646v2XEfmPppOEEntry 705036544}

er1646v2XEfmPppOEIpV6RaMinInterval OBJECT-TYPE
   SYNTAX      TimeTicks
   MAX-ACCESS  read-write
   STATUS      current
   DESCRIPTION
      "Path: efm.editConf.pppoEClient.ipV6.ra.minInterval

       Time in centi-second."
   ::= {er1646v2XEfmPppOEEntry 705036800}

er1646v2XEfmPppOEIpV6RaMaxInterval OBJECT-TYPE
   SYNTAX      TimeTicks
   MAX-ACCESS  read-write
   STATUS      current
   DESCRIPTION
      "Path: efm.editConf.pppoEClient.ipV6.ra.maxInterval

       Time in centi-second."
   ::= {er1646v2XEfmPppOEEntry 705037056}

er1646v2XEfmPppOEIpV6RaManagedFlag OBJECT-TYPE
   SYNTAX      INTEGER
               {
               disabled (0),
               enabled (1)
               }
   MAX-ACCESS  read-write
   STATUS      current
   DESCRIPTION
      "Path: efm.editConf.pppoEClient.ipV6.ra.managedFlag

       Possibilities:
               disabled   (0)
               enabled   (1)"
   ::= {er1646v2XEfmPppOEEntry 705037312}

er1646v2XEfmPppOEIpV6RaOtherConfFlag OBJECT-TYPE
   SYNTAX      INTEGER
               {
               disabled (0),
               enabled (1)
               }
   MAX-ACCESS  read-write
   STATUS      current
   DESCRIPTION
      "Path: efm.editConf.pppoEClient.ipV6.ra.otherConfFlag

       Possibilities:
               disabled   (0)
               enabled   (1)"
   ::= {er1646v2XEfmPppOEEntry 705037568}

er1646v2XEfmPppOEIpV6RaLinkMtu OBJECT-TYPE
   SYNTAX      Integer32
   MAX-ACCESS  read-write
   STATUS      current
   DESCRIPTION
      "Path: efm.editConf.pppoEClient.ipV6.ra.linkMtu"
   ::= {er1646v2XEfmPppOEEntry 705037824}

er1646v2XEfmPppOEIpV6RaReachableTime OBJECT-TYPE
   SYNTAX      TimeTicks
   MAX-ACCESS  read-write
   STATUS      current
   DESCRIPTION
      "Path: efm.editConf.pppoEClient.ipV6.ra.reachableTime

       Time in centi-second."
   ::= {er1646v2XEfmPppOEEntry 705038080}

er1646v2XEfmPppOEIpV6RaRetransmitTime OBJECT-TYPE
   SYNTAX      TimeTicks
   MAX-ACCESS  read-write
   STATUS      current
   DESCRIPTION
      "Path: efm.editConf.pppoEClient.ipV6.ra.retransmitTime

       Time in centi-second."
   ::= {er1646v2XEfmPppOEEntry 705038336}

er1646v2XEfmPppOEIpV6RaHopLimit OBJECT-TYPE
   SYNTAX      Integer32
   MAX-ACCESS  read-write
   STATUS      current
   DESCRIPTION
      "Path: efm.editConf.pppoEClient.ipV6.ra.hopLimit"
   ::= {er1646v2XEfmPppOEEntry 705038592}

er1646v2XEfmPppOEIpV6RaDefaultLifeTime OBJECT-TYPE
   SYNTAX      TimeTicks
   MAX-ACCESS  read-write
   STATUS      current
   DESCRIPTION
      "Path: efm.editConf.pppoEClient.ipV6.ra.defaultLifeTime

       Time in centi-second."
   ::= {er1646v2XEfmPppOEEntry 705038848}

er1646v2XEfmPppOEIpV6RaDnsOptionsRdnssLifeTime OBJECT-TYPE
   SYNTAX      TimeTicks
   MAX-ACCESS  read-write
   STATUS      current
   DESCRIPTION
      "Path: efm.editConf.pppoEClient.ipV6.ra.dnsOptions.rdnss.lifeTime

       Time in centi-second."
   ::= {er1646v2XEfmPppOEEntry 705039140}

er1646v2XEfmPppOEIpV6RaDnsOptionsRdnssImportServers OBJECT-TYPE
   SYNTAX      INTEGER
               {
               disabled (0),
               enabled (1)
               }
   MAX-ACCESS  read-write
   STATUS      current
   DESCRIPTION
      "Path: efm.editConf.pppoEClient.ipV6.ra.dnsOptions.rdnss.importServers

       Possibilities:
               disabled   (0)
               enabled   (1)"
   ::= {er1646v2XEfmPppOEEntry 705039148}

er1646v2XEfmPppOEIpV6RaDnsOptionsDnsslLifeTime OBJECT-TYPE
   SYNTAX      TimeTicks
   MAX-ACCESS  read-write
   STATUS      current
   DESCRIPTION
      "Path: efm.editConf.pppoEClient.ipV6.ra.dnsOptions.dnssl.lifeTime

       Time in centi-second."
   ::= {er1646v2XEfmPppOEEntry 705039172}

er1646v2XEfmPppOEIpV6RaDnsOptionsDnsslImportDomains OBJECT-TYPE
   SYNTAX      INTEGER
               {
               disabled (0),
               enabled (1)
               }
   MAX-ACCESS  read-write
   STATUS      current
   DESCRIPTION
      "Path: efm.editConf.pppoEClient.ipV6.ra.dnsOptions.dnssl.importDomains

       Possibilities:
               disabled   (0)
               enabled   (1)"
   ::= {er1646v2XEfmPppOEEntry 705039180}

er1646v2XEfmPppOEIpV6RsSend OBJECT-TYPE
   SYNTAX      INTEGER
               {
               disabled (0),
               enabled (1)
               }
   MAX-ACCESS  read-write
   STATUS      current
   DESCRIPTION
      "Path: efm.editConf.pppoEClient.ipV6.rs.send

       Possibilities:
               disabled   (0)
               enabled   (1)"
   ::= {er1646v2XEfmPppOEEntry 705954048}

er1646v2XEfmPppOEIpV6RsMaxRandomDelay OBJECT-TYPE
   SYNTAX      TimeTicks
   MAX-ACCESS  read-write
   STATUS      current
   DESCRIPTION
      "Path: efm.editConf.pppoEClient.ipV6.rs.maxRandomDelay

       Time in centi-second."
   ::= {er1646v2XEfmPppOEEntry 705954304}

er1646v2XEfmPppOEIpV6RsInterval OBJECT-TYPE
   SYNTAX      TimeTicks
   MAX-ACCESS  read-write
   STATUS      current
   DESCRIPTION
      "Path: efm.editConf.pppoEClient.ipV6.rs.interval

       Time in centi-second."
   ::= {er1646v2XEfmPppOEEntry 705954560}

er1646v2XEfmPppOEIpV6RsMaxSolicitations OBJECT-TYPE
   SYNTAX      Integer32
   MAX-ACCESS  read-write
   STATUS      current
   DESCRIPTION
      "Path: efm.editConf.pppoEClient.ipV6.rs.maxSolicitations"
   ::= {er1646v2XEfmPppOEEntry 705954816}

er1646v2XEfmPppOEIpV6TrafficPolicyInbound OBJECT-TYPE
   SYNTAX      DisplayString
   MAX-ACCESS  read-write
   STATUS      current
   DESCRIPTION
      "Path: efm.editConf.pppoEClient.ipV6.trafficPolicy.inbound"
   ::= {er1646v2XEfmPppOEEntry 705364224}

er1646v2XEfmPppOEIpV6TrafficPolicyOutbound OBJECT-TYPE
   SYNTAX      DisplayString
   MAX-ACCESS  read-write
   STATUS      current
   DESCRIPTION
      "Path: efm.editConf.pppoEClient.ipV6.trafficPolicy.outbound"
   ::= {er1646v2XEfmPppOEEntry 705364480}

er1646v2XEfmPppOEIpV6FirewallZone OBJECT-TYPE
   SYNTAX      DisplayString
   MAX-ACCESS  read-write
   STATUS      current
   DESCRIPTION
      "Path: efm.editConf.pppoEClient.ipV6.firewall.zone"
   ::= {er1646v2XEfmPppOEEntry 705429760}

er1646v2XEfmPppOEIpV6DhcpClientAddrAC OBJECT-TYPE
   SYNTAX      INTEGER
               {
               disabled (0),
               enabled (1)
               }
   MAX-ACCESS  read-write
   STATUS      current
   DESCRIPTION
      "Path: efm.editConf.pppoEClient.ipV6.dhcp.client.addrAutoConfig

       Possibilities:
               disabled   (0)
               enabled   (1)"
   ::= {er1646v2XEfmPppOEEntry 705307648}

er1646v2XEfmPppOEIpV6DhcpClientPrDelMode OBJECT-TYPE
   SYNTAX      INTEGER
               {
               disabled (0),
               enabled (1)
               }
   MAX-ACCESS  read-write
   STATUS      current
   DESCRIPTION
      "Path: efm.editConf.pppoEClient.ipV6.dhcp.client.pd.mode

       Possibilities:
               disabled   (0)
               enabled   (1)"
   ::= {er1646v2XEfmPppOEEntry 705308676}

er1646v2XEfmPppOEIpV6DhcpClientPrDelPool OBJECT-TYPE
   SYNTAX      DisplayString
   MAX-ACCESS  read-write
   STATUS      current
   DESCRIPTION
      "Path: efm.editConf.pppoEClient.ipV6.dhcp.client.pd.pool"
   ::= {er1646v2XEfmPppOEEntry 705308680}

er1646v2XEfmPppOEIpV6DhcpClientPrDelPdExclOpt OBJECT-TYPE
   SYNTAX      INTEGER
               {
               disabled (0),
               enabled (1)
               }
   MAX-ACCESS  read-write
   STATUS      current
   DESCRIPTION
      "Path: efm.editConf.pppoEClient.ipV6.dhcp.client.pd.pdExclOpt

       Possibilities:
               disabled   (0)
               enabled   (1)"
   ::= {er1646v2XEfmPppOEEntry 705308684}

er1646v2XEfmPppOEIpV6DhcpClientDnsServerPref OBJECT-TYPE
   SYNTAX      Integer32
   MAX-ACCESS  read-write
   STATUS      current
   DESCRIPTION
      "Path: efm.editConf.pppoEClient.ipV6.dhcp.client.dns.serverPref"
   ::= {er1646v2XEfmPppOEEntry 705310724}

er1646v2XEfmPppOEIpV6DhcpClientRapidCommit OBJECT-TYPE
   SYNTAX      INTEGER
               {
               disabled (0),
               enabled (1)
               }
   MAX-ACCESS  read-write
   STATUS      current
   DESCRIPTION
      "Path: efm.editConf.pppoEClient.ipV6.dhcp.client.rapidCommit

       Possibilities:
               disabled   (0)
               enabled   (1)"
   ::= {er1646v2XEfmPppOEEntry 705309696}

er1646v2XEfmPppOEIpV6DhcpClientTimersSolTimeOut OBJECT-TYPE
   SYNTAX      TimeTicks
   MAX-ACCESS  read-write
   STATUS      current
   DESCRIPTION
      "Path: efm.editConf.pppoEClient.ipV6.dhcp.client.timers.solTimeOut

       Time in centi-second."
   ::= {er1646v2XEfmPppOEEntry 705311748}

er1646v2XEfmPppOEIpV6DhcpClientTimersSolMaxRt OBJECT-TYPE
   SYNTAX      TimeTicks
   MAX-ACCESS  read-write
   STATUS      current
   DESCRIPTION
      "Path: efm.editConf.pppoEClient.ipV6.dhcp.client.timers.solMaxRt

       Time in centi-second."
   ::= {er1646v2XEfmPppOEEntry 705311752}

er1646v2XEfmPppOEIpV6DhcpClientTimersInfoRefresh OBJECT-TYPE
   SYNTAX      TimeTicks
   MAX-ACCESS  read-write
   STATUS      current
   DESCRIPTION
      "Path: efm.editConf.pppoEClient.ipV6.dhcp.client.timers.infoRefresh

       Time in centi-second."
   ::= {er1646v2XEfmPppOEEntry 705311756}

er1646v2XEfmPppOEIpV6DhcpServerMode OBJECT-TYPE
   SYNTAX      INTEGER
               {
               disabled (0),
               enabled (1)
               }
   MAX-ACCESS  read-write
   STATUS      current
   DESCRIPTION
      "Path: efm.editConf.pppoEClient.ipV6.dhcp.server.mode

       Possibilities:
               disabled   (0)
               enabled   (1)"
   ::= {er1646v2XEfmPppOEEntry 705315840}

er1646v2XEfmPppOEIpV6DhcpServerPreference OBJECT-TYPE
   SYNTAX      Integer32
   MAX-ACCESS  read-write
   STATUS      current
   DESCRIPTION
      "Path: efm.editConf.pppoEClient.ipV6.dhcp.server.preference"
   ::= {er1646v2XEfmPppOEEntry 705316864}

er1646v2XEfmPppOEIpV6DhcpServerPool OBJECT-TYPE
   SYNTAX      DisplayString
   MAX-ACCESS  read-write
   STATUS      current
   DESCRIPTION
      "Path: efm.editConf.pppoEClient.ipV6.dhcp.server.pool"
   ::= {er1646v2XEfmPppOEEntry 705317888}

er1646v2XEfmPppOEIpV6DhcpServerRapidCommit OBJECT-TYPE
   SYNTAX      INTEGER
               {
               disabled (0),
               enabled (1)
               }
   MAX-ACCESS  read-write
   STATUS      current
   DESCRIPTION
      "Path: efm.editConf.pppoEClient.ipV6.dhcp.server.rapidCommit

       Possibilities:
               disabled   (0)
               enabled   (1)"
   ::= {er1646v2XEfmPppOEEntry 705318912}

er1646v2XEfmPppOEIpV6DhcpServerTimersInfoRefresh OBJECT-TYPE
   SYNTAX      TimeTicks
   MAX-ACCESS  read-write
   STATUS      current
   DESCRIPTION
      "Path: efm.editConf.pppoEClient.ipV6.dhcp.server.timers.infoRefresh

       Time in centi-second."
   ::= {er1646v2XEfmPppOEEntry 705319940}

er1646v2XEfmPppOEIpV6DhcpRelayMode OBJECT-TYPE
   SYNTAX      INTEGER
               {
               disabled (0),
               enabled (1)
               }
   MAX-ACCESS  read-write
   STATUS      current
   DESCRIPTION
      "Path: efm.editConf.pppoEClient.ipV6.dhcp.relay.mode

       Possibilities:
               disabled   (0)
               enabled   (1)"
   ::= {er1646v2XEfmPppOEEntry 705323040}

er1646v2XEfmPppOEIpV6SendRedirect OBJECT-TYPE
   SYNTAX      INTEGER
               {
               disabled (0),
               enabled (1)
               }
   MAX-ACCESS  read-write
   STATUS      current
   DESCRIPTION
      "Path: efm.editConf.pppoEClient.ipV6.sendRedirect

       Possibilities:
               disabled   (0)
               enabled   (1)"
   ::= {er1646v2XEfmPppOEEntry 705101824}

er1646v2XEfmPppOEIpV6LinkMtu OBJECT-TYPE
   SYNTAX      Integer32
   MAX-ACCESS  read-write
   STATUS      current
   DESCRIPTION
      "Path: efm.editConf.pppoEClient.ipV6.linkMtu"
   ::= {er1646v2XEfmPppOEEntry 705167360}

er1646v2XEfmPppOEIpV6InterfaceId OBJECT-TYPE
   SYNTAX      OCTET STRING
   MAX-ACCESS  read-write
   STATUS      current
   DESCRIPTION
      "Path: efm.editConf.pppoEClient.ipV6.interfaceId"
   ::= {er1646v2XEfmPppOEEntry 705232896}

er1646v2XEfmPppOEIpV6MF OBJECT-TYPE
   SYNTAX      Integer32
   MAX-ACCESS  read-write
   STATUS      current
   DESCRIPTION
      "Path: efm.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2XEfmPppOEEntry 705757184}

er1646v2XEfmPppOEIpV6IcmpMessagesNoRoute OBJECT-TYPE
   SYNTAX      INTEGER
               {
               disabled (0),
               enabled (1)
               }
   MAX-ACCESS  read-write
   STATUS      current
   DESCRIPTION
      "Path: efm.editConf.pppoEClient.ipV6.icmpMessages.noRoute

       Possibilities:
               disabled   (0)
               enabled   (1)"
   ::= {er1646v2XEfmPppOEEntry 705822976}

er1646v2XEfmPppOEIpV6IcmpMessagesBeyondScope OBJECT-TYPE
   SYNTAX      INTEGER
               {
               disabled (0),
               enabled (1)
               }
   MAX-ACCESS  read-write
   STATUS      current
   DESCRIPTION
      "Path: efm.editConf.pppoEClient.ipV6.icmpMessages.beyondScope

       Possibilities:
               disabled   (0)
               enabled   (1)"
   ::= {er1646v2XEfmPppOEEntry 705823488}

er1646v2XEfmPppOEIpV6IcmpMessagesAddressUnreachable OBJECT-TYPE
   SYNTAX      INTEGER
               {
               disabled (0),
               enabled (1)
               }
   MAX-ACCESS  read-write
   STATUS      current
   DESCRIPTION
      "Path: efm.editConf.pppoEClient.ipV6.icmpMessages.addressUnreachable

       Possibilities:
               disabled   (0)
               enabled   (1)"
   ::= {er1646v2XEfmPppOEEntry 705823744}

er1646v2XEfmPppOEIpV6IcmpMessagesPortUnreachable OBJECT-TYPE
   SYNTAX      INTEGER
               {
               disabled (0),
               enabled (1)
               }
   MAX-ACCESS  read-write
   STATUS      current
   DESCRIPTION
      "Path: efm.editConf.pppoEClient.ipV6.icmpMessages.portUnreachable

       Possibilities:
               disabled   (0)
               enabled   (1)"
   ::= {er1646v2XEfmPppOEEntry 705824000}

er1646v2XEfmPppOEIpV6IcmpMessagesPacketTooBig OBJECT-TYPE
   SYNTAX      INTEGER
               {
               disabled (0),
               enabled (1)
               }
   MAX-ACCESS  read-write
   STATUS      current
   DESCRIPTION
      "Path: efm.editConf.pppoEClient.ipV6.icmpMessages.packetTooBig

       Possibilities:
               disabled   (0)
               enabled   (1)"
   ::= {er1646v2XEfmPppOEEntry 705825280}

er1646v2XEfmPppOEIpV6IcmpMessagesHopLimitExceeded OBJECT-TYPE
   SYNTAX      INTEGER
               {
               disabled (0),
               enabled (1)
               }
   MAX-ACCESS  read-write
   STATUS      current
   DESCRIPTION
      "Path: efm.editConf.pppoEClient.ipV6.icmpMessages.hopLimitExceeded

       Possibilities:
               disabled   (0)
               enabled   (1)"
   ::= {er1646v2XEfmPppOEEntry 705827840}

er1646v2XEfmPppOEIpV6IcmpMessagesFragTimeExceeded OBJECT-TYPE
   SYNTAX      INTEGER
               {
               disabled (0),
               enabled (1)
               }
   MAX-ACCESS  read-write
   STATUS      current
   DESCRIPTION
      "Path: efm.editConf.pppoEClient.ipV6.icmpMessages.fragTimeExceeded

       Possibilities:
               disabled   (0)
               enabled   (1)"
   ::= {er1646v2XEfmPppOEEntry 705828096}

er1646v2XEfmPppOEIpV6IcmpMessagesHeaderFieldErr OBJECT-TYPE
   SYNTAX      INTEGER
               {
               disabled (0),
               enabled (1)
               }
   MAX-ACCESS  read-write
   STATUS      current
   DESCRIPTION
      "Path: efm.editConf.pppoEClient.ipV6.icmpMessages.headerFieldErr

       Possibilities:
               disabled   (0)
               enabled   (1)"
   ::= {er1646v2XEfmPppOEEntry 705830400}

er1646v2XEfmPppOEIpV6IcmpMessagesOptionUnrecognized OBJECT-TYPE
   SYNTAX      INTEGER
               {
               disabled (0),
               enabled (1)
               }
   MAX-ACCESS  read-write
   STATUS      current
   DESCRIPTION
      "Path: efm.editConf.pppoEClient.ipV6.icmpMessages.optionUnrecognized

       Possibilities:
               disabled   (0)
               enabled   (1)"
   ::= {er1646v2XEfmPppOEEntry 705830912}

er1646v2XEfmPppOEIpV6IcmpMessagesRedirect OBJECT-TYPE
   SYNTAX      INTEGER
               {
               disabled (0),
               enabled (1)
               }
   MAX-ACCESS  read-write
   STATUS      current
   DESCRIPTION
      "Path: efm.editConf.pppoEClient.ipV6.icmpMessages.redirect

       Possibilities:
               disabled   (0)
               enabled   (1)"
   ::= {er1646v2XEfmPppOEEntry 705832960}

er1646v2XEfmPppOEPppLnkMOperation OBJECT-TYPE
   SYNTAX      INTEGER
               {
               disabled (0),
               enabled (1)
               }
   MAX-ACCESS  read-write
   STATUS      current
   DESCRIPTION
      "Path: efm.editConf.pppoEClient.ppp.linkMonitoring.operation

       Possibilities:
               disabled   (0)
               enabled   (1)"
   ::= {er1646v2XEfmPppOEEntry 251724032}

er1646v2XEfmPppOEPppLnkMInterval OBJECT-TYPE
   SYNTAX      TimeTicks
   MAX-ACCESS  read-write
   STATUS      current
   DESCRIPTION
      "Path: efm.editConf.pppoEClient.ppp.linkMonitoring.interval

       Time in centi-second."
   ::= {er1646v2XEfmPppOEEntry 251724288}

er1646v2XEfmPppOEPppLnkMRepTimeOut OBJECT-TYPE
   SYNTAX      TimeTicks
   MAX-ACCESS  read-write
   STATUS      current
   DESCRIPTION
      "Path: efm.editConf.pppoEClient.ppp.linkMonitoring.replyTimeOut

       Time in centi-second."
   ::= {er1646v2XEfmPppOEEntry 251724544}

er1646v2XEfmPppOEPppLnkMFailsPrmt OBJECT-TYPE
   SYNTAX      Integer32
   MAX-ACCESS  read-write
   STATUS      current
   DESCRIPTION
      "Path: efm.editConf.pppoEClient.ppp.linkMonitoring.failsPermitted"
   ::= {er1646v2XEfmPppOEEntry 251724800}

er1646v2XEfmPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: efm.editConf.pppoEClient.ppp.authentication

       Possibilities:
               disabled   (0)
               chap   (1)
               pap   (2)
               chapOrPap   (3)
               msChap   (4)
               msChapV2   (5)"
   ::= {er1646v2XEfmPppOEEntry 251789312}

er1646v2XEfmPppOEPppAuthenPeriod OBJECT-TYPE
   SYNTAX      TimeTicks
   MAX-ACCESS  read-write
   STATUS      current
   DESCRIPTION
      "Path: efm.editConf.pppoEClient.ppp.authenPeriod

       Time in centi-second."
   ::= {er1646v2XEfmPppOEEntry 251854848}

er1646v2XEfmPppOEPppSessionName OBJECT-TYPE
   SYNTAX      DisplayString
   MAX-ACCESS  read-write
   STATUS      current
   DESCRIPTION
      "Path: efm.editConf.pppoEClient.ppp.sessionName"
   ::= {er1646v2XEfmPppOEEntry 251985920}

er1646v2XEfmPppOEPppSessionSecret OBJECT-TYPE
   SYNTAX      DisplayString
   MAX-ACCESS  read-write
   STATUS      current
   DESCRIPTION
      "Path: efm.editConf.pppoEClient.ppp.sessionSecret"
   ::= {er1646v2XEfmPppOEEntry 252051456}

er1646v2XEfmPppOEPppEncModeSessionSecret OBJECT-TYPE
   SYNTAX      INTEGER
               {
               none (1),
               encrypt (2),
               encType1 (3),
               invalid (128)
               }
   MAX-ACCESS  read-write
   STATUS      current
   DESCRIPTION
      "Path: efm.editConf.pppoEClient.ppp.encModeSessionSecret

       Possibilities:
               none   (1)
               encrypt   (2)
               encType1   (3)
               invalid   (128)"
   ::= {er1646v2XEfmPppOEEntry 252182528}

er1646v2XEfmPppOEPppEncSessionSecret OBJECT-TYPE
   SYNTAX      DisplayString
   MAX-ACCESS  read-write
   STATUS      current
   DESCRIPTION
      "Path: efm.editConf.pppoEClient.ppp.encSessionSecret"
   ::= {er1646v2XEfmPppOEEntry 252248064}

er1646v2XEfmPppOEPppServiceName OBJECT-TYPE
   SYNTAX      DisplayString
   MAX-ACCESS  read-write
   STATUS      current
   DESCRIPTION
      "Path: efm.editConf.pppoEClient.ppp.serviceName"
   ::= {er1646v2XEfmPppOEEntry 252116992}

er1646v2XEfmPppOEIpH OBJECT-TYPE
   SYNTAX      SEQUENCE OF Er1646v2XEfmPppOEIpHEntry
   MAX-ACCESS  not-accessible
   STATUS      current
   DESCRIPTION
      ""
   ::= {er1646v2XEfmPppOE 51314688}

er1646v2XEfmPppOEIpHEntry OBJECT-TYPE
   SYNTAX      Er1646v2XEfmPppOEIpHEntry
   MAX-ACCESS  not-accessible
   STATUS      current
   DESCRIPTION
      ""
   INDEX      { er1646v2XEfmPppOETableIx,
                er1646v2XEfmPppOEIpHTableIx }
   ::= {er1646v2XEfmPppOEIpH 1}

Er1646v2XEfmPppOEIpHEntry ::=
   SEQUENCE
      {
      er1646v2XEfmPppOEIpHActions
         VariableLengthTableActions,
      er1646v2XEfmPppOEIpHTableIx
         TableIndex,
      er1646v2XEfmPppOEIpHAddress
         IpAddress,
      er1646v2XEfmPppOEIpHDhcpRelayOptionSubscriberId
         DisplayString
      }

er1646v2XEfmPppOEIpHActions OBJECT-TYPE
   SYNTAX      VariableLengthTableActions
   MAX-ACCESS  read-write
   STATUS      current
   DESCRIPTION
      "By way of this field, some manipulations
       on this table may be performed."
   ::= {er1646v2XEfmPppOEIpHEntry 2}

er1646v2XEfmPppOEIpHTableIx OBJECT-TYPE
   SYNTAX      TableIndex
   MAX-ACCESS  not-accessible
   STATUS      current
   DESCRIPTION
      ""
   ::= {er1646v2XEfmPppOEIpHEntry 11}

er1646v2XEfmPppOEIpHAddress OBJECT-TYPE
   SYNTAX      IpAddress
   MAX-ACCESS  read-write
   STATUS      current
   DESCRIPTION
      "Path: efm.editConf.pppoEClient.ip.helpers.address"
   ::= {er1646v2XEfmPppOEIpHEntry 16777216}

er1646v2XEfmPppOEIpHDhcpRelayOptionSubscriberId OBJECT-TYPE
   SYNTAX      DisplayString
   MAX-ACCESS  read-write
   STATUS      current
   DESCRIPTION
      "Path: efm.editConf.pppoEClient.ip.helpers.dhcpRelayOption.subscriberId"
   ::= {er1646v2XEfmPppOEIpHEntry 33947648}

er1646v2XEfmPppOEIpV6Addresses OBJECT-TYPE
   SYNTAX      SEQUENCE OF Er1646v2XEfmPppOEIpV6AddressesEntry
   MAX-ACCESS  not-accessible
   STATUS      current
   DESCRIPTION
      ""
   ::= {er1646v2XEfmPppOE 704839680}

er1646v2XEfmPppOEIpV6AddressesEntry OBJECT-TYPE
   SYNTAX      Er1646v2XEfmPppOEIpV6AddressesEntry
   MAX-ACCESS  not-accessible
   STATUS      current
   DESCRIPTION
      ""
   INDEX      { er1646v2XEfmPppOETableIx,
                er1646v2XEfmPppOEIpV6AddressesTableIx }
   ::= {er1646v2XEfmPppOEIpV6Addresses 1}

Er1646v2XEfmPppOEIpV6AddressesEntry ::=
   SEQUENCE
      {
      er1646v2XEfmPppOEIpV6AddressesActions
         VariableLengthTableActions,
      er1646v2XEfmPppOEIpV6AddressesTableIx
         TableIndex,
      er1646v2XEfmPppOEIpV6AddressesType
         INTEGER,
      er1646v2XEfmPppOEIpV6AddressesAddress
         Ipv6Address,
      er1646v2XEfmPppOEIpV6AddressesPrefixLength
         Integer32,
      er1646v2XEfmPppOEIpV6AddressesGeneralPrefix
         DisplayString,
      er1646v2XEfmPppOEIpV6AddressesRaSend
         INTEGER,
      er1646v2XEfmPppOEIpV6AddressesRaOnLinkFlag
         INTEGER,
      er1646v2XEfmPppOEIpV6AddressesRaAutoFlag
         INTEGER,
      er1646v2XEfmPppOEIpV6AddressesRaValidLifeTime
         TimeTicks,
      er1646v2XEfmPppOEIpV6AddressesRaValidLTMode
         INTEGER,
      er1646v2XEfmPppOEIpV6AddressesRaPrefLifeTime
         TimeTicks,
      er1646v2XEfmPppOEIpV6AddressesRaPrefLTMode
         INTEGER
      }

er1646v2XEfmPppOEIpV6AddressesActions OBJECT-TYPE
   SYNTAX      VariableLengthTableActions
   MAX-ACCESS  read-write
   STATUS      current
   DESCRIPTION
      "By way of this field, some manipulations
       on this table may be performed."
   ::= {er1646v2XEfmPppOEIpV6AddressesEntry 2}

er1646v2XEfmPppOEIpV6AddressesTableIx OBJECT-TYPE
   SYNTAX      TableIndex
   MAX-ACCESS  not-accessible
   STATUS      current
   DESCRIPTION
      ""
   ::= {er1646v2XEfmPppOEIpV6AddressesEntry 11}

er1646v2XEfmPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.pppoEClient.ipV6.addresses.type

       Possibilities:
               unicast   (0)
               eui64   (1)
               anycast   (2)
               linkLocal   (3)
               generalPrefix   (4)"
   ::= {er1646v2XEfmPppOEIpV6AddressesEntry 50331648}

er1646v2XEfmPppOEIpV6AddressesAddress OBJECT-TYPE
   SYNTAX      Ipv6Address
   MAX-ACCESS  read-write
   STATUS      current
   DESCRIPTION
      "Path: efm.editConf.pppoEClient.ipV6.addresses.address

       ipv6 address"
   ::= {er1646v2XEfmPppOEIpV6AddressesEntry 16777216}

er1646v2XEfmPppOEIpV6AddressesPrefixLength OBJECT-TYPE
   SYNTAX      Integer32
   MAX-ACCESS  read-write
   STATUS      current
   DESCRIPTION
      "Path: efm.editConf.pppoEClient.ipV6.addresses.prefixLength"
   ::= {er1646v2XEfmPppOEIpV6AddressesEntry 33554432}

er1646v2XEfmPppOEIpV6AddressesGeneralPrefix OBJECT-TYPE
   SYNTAX      DisplayString
   MAX-ACCESS  read-write
   STATUS      current
   DESCRIPTION
      "Path: efm.editConf.pppoEClient.ipV6.addresses.generalPrefix"
   ::= {er1646v2XEfmPppOEIpV6AddressesEntry 83886080}

er1646v2XEfmPppOEIpV6AddressesRaSend OBJECT-TYPE
   SYNTAX      INTEGER
               {
               disabled (0),
               enabled (1)
               }
   MAX-ACCESS  read-write
   STATUS      current
   DESCRIPTION
      "Path: efm.editConf.pppoEClient.ipV6.addresses.ra.send

       Possibilities:
               disabled   (0)
               enabled   (1)"
   ::= {er1646v2XEfmPppOEIpV6AddressesEntry 67174400}

er1646v2XEfmPppOEIpV6AddressesRaOnLinkFlag OBJECT-TYPE
   SYNTAX      INTEGER
               {
               disabled (0),
               enabled (1)
               }
   MAX-ACCESS  read-write
   STATUS      current
   DESCRIPTION
      "Path: efm.editConf.pppoEClient.ipV6.addresses.ra.onLinkFlag

       Possibilities:
               disabled   (0)
               enabled   (1)"
   ::= {er1646v2XEfmPppOEIpV6AddressesEntry 67371008}

er1646v2XEfmPppOEIpV6AddressesRaAutoFlag OBJECT-TYPE
   SYNTAX      INTEGER
               {
               disabled (0),
               enabled (1)
               }
   MAX-ACCESS  read-write
   STATUS      current
   DESCRIPTION
      "Path: efm.editConf.pppoEClient.ipV6.addresses.ra.autonomousFlag

       Possibilities:
               disabled   (0)
               enabled   (1)"
   ::= {er1646v2XEfmPppOEIpV6AddressesEntry 67567616}

er1646v2XEfmPppOEIpV6AddressesRaValidLifeTime OBJECT-TYPE
   SYNTAX      TimeTicks
   MAX-ACCESS  read-write
   STATUS      current
   DESCRIPTION
      "Path: efm.editConf.pppoEClient.ipV6.addresses.ra.validLifeTime

       Time in centi-second."
   ::= {er1646v2XEfmPppOEIpV6AddressesEntry 67239936}

er1646v2XEfmPppOEIpV6AddressesRaValidLTMode OBJECT-TYPE
   SYNTAX      INTEGER
               {
               fixed (0),
               infinite (2)
               }
   MAX-ACCESS  read-write
   STATUS      current
   DESCRIPTION
      "Path: efm.editConf.pppoEClient.ipV6.addresses.ra.validLifeTimeMode

       Possibilities:
               fixed   (0)
               infinite   (2)"
   ::= {er1646v2XEfmPppOEIpV6AddressesEntry 67305472}

er1646v2XEfmPppOEIpV6AddressesRaPrefLifeTime OBJECT-TYPE
   SYNTAX      TimeTicks
   MAX-ACCESS  read-write
   STATUS      current
   DESCRIPTION
      "Path: efm.editConf.pppoEClient.ipV6.addresses.ra.prefLifeTime

       Time in centi-second."
   ::= {er1646v2XEfmPppOEIpV6AddressesEntry 67436544}

er1646v2XEfmPppOEIpV6AddressesRaPrefLTMode OBJECT-TYPE
   SYNTAX      INTEGER
               {
               fixed (0),
               infinite (2)
               }
   MAX-ACCESS  read-write
   STATUS      current
   DESCRIPTION
      "Path: efm.editConf.pppoEClient.ipV6.addresses.ra.prefLifeTimeMode

       Possibilities:
               fixed   (0)
               infinite   (2)"
   ::= {er1646v2XEfmPppOEIpV6AddressesEntry 67502080}

er1646v2XEfmPppOEIpV6RaDnsOptionsRdnssServers OBJECT-TYPE
   SYNTAX      SEQUENCE OF Er1646v2XEfmPppOEIpV6RaDnsOptionsRdnssServersEntry
   MAX-ACCESS  not-accessible
   STATUS      current
   DESCRIPTION
      ""
   ::= {er1646v2XEfmPppOE 705039144}

er1646v2XEfmPppOEIpV6RaDnsOptionsRdnssServersEntry OBJECT-TYPE
   SYNTAX      Er1646v2XEfmPppOEIpV6RaDnsOptionsRdnssServersEntry
   MAX-ACCESS  not-accessible
   STATUS      current
   DESCRIPTION
      ""
   INDEX      { er1646v2XEfmPppOETableIx,
                er1646v2XEfmPppOEIpV6RaDnsOptionsRdnssServersTableIx }
   ::= {er1646v2XEfmPppOEIpV6RaDnsOptionsRdnssServers 1}

Er1646v2XEfmPppOEIpV6RaDnsOptionsRdnssServersEntry ::=
   SEQUENCE
      {
      er1646v2XEfmPppOEIpV6RaDnsOptionsRdnssServersActions
         VariableLengthTableActions,
      er1646v2XEfmPppOEIpV6RaDnsOptionsRdnssServersTableIx
         TableIndex,
      er1646v2XEfmPppOEIpV6RaDnsOptionsRdnssServersAddress
         Ipv6Address
      }

er1646v2XEfmPppOEIpV6RaDnsOptionsRdnssServersActions OBJECT-TYPE
   SYNTAX      VariableLengthTableActions
   MAX-ACCESS  read-write
   STATUS      current
   DESCRIPTION
      "By way of this field, some manipulations
       on this table may be performed."
   ::= {er1646v2XEfmPppOEIpV6RaDnsOptionsRdnssServersEntry 2}

er1646v2XEfmPppOEIpV6RaDnsOptionsRdnssServersTableIx OBJECT-TYPE
   SYNTAX      TableIndex
   MAX-ACCESS  not-accessible
   STATUS      current
   DESCRIPTION
      ""
   ::= {er1646v2XEfmPppOEIpV6RaDnsOptionsRdnssServersEntry 11}

er1646v2XEfmPppOEIpV6RaDnsOptionsRdnssServersAddress OBJECT-TYPE
   SYNTAX      Ipv6Address
   MAX-ACCESS  read-write
   STATUS      current
   DESCRIPTION
      "Path: efm.editConf.pppoEClient.ipV6.ra.dnsOptions.rdnss.servers.address

       ipv6 address"
   ::= {er1646v2XEfmPppOEIpV6RaDnsOptionsRdnssServersEntry 16777216}

er1646v2XEfmPppOEIpV6RaDnsOptionsDnsslDomains OBJECT-TYPE
   SYNTAX      SEQUENCE OF Er1646v2XEfmPppOEIpV6RaDnsOptionsDnsslDomainsEntry
   MAX-ACCESS  not-accessible
   STATUS      current
   DESCRIPTION
      ""
   ::= {er1646v2XEfmPppOE 705039176}

er1646v2XEfmPppOEIpV6RaDnsOptionsDnsslDomainsEntry OBJECT-TYPE
   SYNTAX      Er1646v2XEfmPppOEIpV6RaDnsOptionsDnsslDomainsEntry
   MAX-ACCESS  not-accessible
   STATUS      current
   DESCRIPTION
      ""
   INDEX      { er1646v2XEfmPppOETableIx,
                er1646v2XEfmPppOEIpV6RaDnsOptionsDnsslDomainsTableIx }
   ::= {er1646v2XEfmPppOEIpV6RaDnsOptionsDnsslDomains 1}

Er1646v2XEfmPppOEIpV6RaDnsOptionsDnsslDomainsEntry ::=
   SEQUENCE
      {
      er1646v2XEfmPppOEIpV6RaDnsOptionsDnsslDomainsActions
         VariableLengthTableActions,
      er1646v2XEfmPppOEIpV6RaDnsOptionsDnsslDomainsTableIx
         TableIndex,
      er1646v2XEfmPppOEIpV6RaDnsOptionsDnsslDomainsName
         DisplayString
      }

er1646v2XEfmPppOEIpV6RaDnsOptionsDnsslDomainsActions OBJECT-TYPE
   SYNTAX      VariableLengthTableActions
   MAX-ACCESS  read-write
   STATUS      current
   DESCRIPTION
      "By way of this field, some manipulations
       on this table may be performed."
   ::= {er1646v2XEfmPppOEIpV6RaDnsOptionsDnsslDomainsEntry 2}

er1646v2XEfmPppOEIpV6RaDnsOptionsDnsslDomainsTableIx OBJECT-TYPE
   SYNTAX      TableIndex
   MAX-ACCESS  not-accessible
   STATUS      current
   DESCRIPTION
      ""
   ::= {er1646v2XEfmPppOEIpV6RaDnsOptionsDnsslDomainsEntry 11}

er1646v2XEfmPppOEIpV6RaDnsOptionsDnsslDomainsName OBJECT-TYPE
   SYNTAX      DisplayString
   MAX-ACCESS  read-write
   STATUS      current
   DESCRIPTION
      "Path: efm.editConf.pppoEClient.ipV6.ra.dnsOptions.dnssl.domains.name"
   ::= {er1646v2XEfmPppOEIpV6RaDnsOptionsDnsslDomainsEntry 16777216}

er1646v2XEfmPppOEIpV6DhcpClientUserClassOpt OBJECT-TYPE
   SYNTAX      SEQUENCE OF Er1646v2XEfmPppOEIpV6DhcpClientUserClassOptEntry
   MAX-ACCESS  not-accessible
   STATUS      current
   DESCRIPTION
      ""
   ::= {er1646v2XEfmPppOE 705312768}

er1646v2XEfmPppOEIpV6DhcpClientUserClassOptEntry OBJECT-TYPE
   SYNTAX      Er1646v2XEfmPppOEIpV6DhcpClientUserClassOptEntry
   MAX-ACCESS  not-accessible
   STATUS      current
   DESCRIPTION
      ""
   INDEX      { er1646v2XEfmPppOETableIx,
                er1646v2XEfmPppOEIpV6DhcpClientUserClassOptTableIx }
   ::= {er1646v2XEfmPppOEIpV6DhcpClientUserClassOpt 1}

Er1646v2XEfmPppOEIpV6DhcpClientUserClassOptEntry ::=
   SEQUENCE
      {
      er1646v2XEfmPppOEIpV6DhcpClientUserClassOptActions
         VariableLengthTableActions,
      er1646v2XEfmPppOEIpV6DhcpClientUserClassOptTableIx
         TableIndex,
      er1646v2XEfmPppOEIpV6DhcpClientUserClassOptValueAscii
         DisplayString,
      er1646v2XEfmPppOEIpV6DhcpClientUserClassOptValueDecimal
         Integer32,
      er1646v2XEfmPppOEIpV6DhcpClientUserClassOptValueHexData
         OCTET STRING
      }

er1646v2XEfmPppOEIpV6DhcpClientUserClassOptActions OBJECT-TYPE
   SYNTAX      VariableLengthTableActions
   MAX-ACCESS  read-write
   STATUS      current
   DESCRIPTION
      "By way of this field, some manipulations
       on this table may be performed."
   ::= {er1646v2XEfmPppOEIpV6DhcpClientUserClassOptEntry 2}

er1646v2XEfmPppOEIpV6DhcpClientUserClassOptTableIx OBJECT-TYPE
   SYNTAX      TableIndex
   MAX-ACCESS  not-accessible
   STATUS      current
   DESCRIPTION
      ""
   ::= {er1646v2XEfmPppOEIpV6DhcpClientUserClassOptEntry 11}

er1646v2XEfmPppOEIpV6DhcpClientUserClassOptValueAscii OBJECT-TYPE
   SYNTAX      DisplayString
   MAX-ACCESS  read-write
   STATUS      current
   DESCRIPTION
      "Path: efm.editConf.pppoEClient.ipV6.dhcp.client.userClassOpt.value.ascii"
   ::= {er1646v2XEfmPppOEIpV6DhcpClientUserClassOptEntry 16842752}

er1646v2XEfmPppOEIpV6DhcpClientUserClassOptValueDecimal OBJECT-TYPE
   SYNTAX      Integer32
   MAX-ACCESS  read-write
   STATUS      current
   DESCRIPTION
      "Path: efm.editConf.pppoEClient.ipV6.dhcp.client.userClassOpt.value.decimal"
   ::= {er1646v2XEfmPppOEIpV6DhcpClientUserClassOptEntry 16908288}

er1646v2XEfmPppOEIpV6DhcpClientUserClassOptValueHexData OBJECT-TYPE
   SYNTAX      OCTET STRING
   MAX-ACCESS  read-write
   STATUS      current
   DESCRIPTION
      "Path: efm.editConf.pppoEClient.ipV6.dhcp.client.userClassOpt.value.hexData"
   ::= {er1646v2XEfmPppOEIpV6DhcpClientUserClassOptEntry 16973824}

er1646v2XEfmPppOEIpV6DhcpClientVendorCl OBJECT-TYPE
   SYNTAX      SEQUENCE OF Er1646v2XEfmPppOEIpV6DhcpClientVendorClEntry
   MAX-ACCESS  not-accessible
   STATUS      current
   DESCRIPTION
      ""
   ::= {er1646v2XEfmPppOE 705313792}

er1646v2XEfmPppOEIpV6DhcpClientVendorClEntry OBJECT-TYPE
   SYNTAX      Er1646v2XEfmPppOEIpV6DhcpClientVendorClEntry
   MAX-ACCESS  not-accessible
   STATUS      current
   DESCRIPTION
      ""
   INDEX      { er1646v2XEfmPppOETableIx,
                er1646v2XEfmPppOEIpV6DhcpClientVendorClTableIx }
   ::= {er1646v2XEfmPppOEIpV6DhcpClientVendorCl 1}

Er1646v2XEfmPppOEIpV6DhcpClientVendorClEntry ::=
   SEQUENCE
      {
      er1646v2XEfmPppOEIpV6DhcpClientVendorClActions
         VariableLengthTableActions,
      er1646v2XEfmPppOEIpV6DhcpClientVendorClTableIx
         TableIndex,
      er1646v2XEfmPppOEIpV6DhcpClientVendorClValueAscii
         DisplayString,
      er1646v2XEfmPppOEIpV6DhcpClientVendorClValueDecimal
         Integer32,
      er1646v2XEfmPppOEIpV6DhcpClientVendorClValueHexData
         OCTET STRING
      }

er1646v2XEfmPppOEIpV6DhcpClientVendorClActions OBJECT-TYPE
   SYNTAX      VariableLengthTableActions
   MAX-ACCESS  read-write
   STATUS      current
   DESCRIPTION
      "By way of this field, some manipulations
       on this table may be performed."
   ::= {er1646v2XEfmPppOEIpV6DhcpClientVendorClEntry 2}

er1646v2XEfmPppOEIpV6DhcpClientVendorClTableIx OBJECT-TYPE
   SYNTAX      TableIndex
   MAX-ACCESS  not-accessible
   STATUS      current
   DESCRIPTION
      ""
   ::= {er1646v2XEfmPppOEIpV6DhcpClientVendorClEntry 11}

er1646v2XEfmPppOEIpV6DhcpClientVendorClValueAscii OBJECT-TYPE
   SYNTAX      DisplayString
   MAX-ACCESS  read-write
   STATUS      current
   DESCRIPTION
      "Path: efm.editConf.pppoEClient.ipV6.dhcp.client.vendorClassOpt.value.ascii"
   ::= {er1646v2XEfmPppOEIpV6DhcpClientVendorClEntry 16842752}

er1646v2XEfmPppOEIpV6DhcpClientVendorClValueDecimal OBJECT-TYPE
   SYNTAX      Integer32
   MAX-ACCESS  read-write
   STATUS      current
   DESCRIPTION
      "Path: efm.editConf.pppoEClient.ipV6.dhcp.client.vendorClassOpt.value.decimal"
   ::= {er1646v2XEfmPppOEIpV6DhcpClientVendorClEntry 16908288}

er1646v2XEfmPppOEIpV6DhcpClientVendorClValueHexData OBJECT-TYPE
   SYNTAX      OCTET STRING
   MAX-ACCESS  read-write
   STATUS      current
   DESCRIPTION
      "Path: efm.editConf.pppoEClient.ipV6.dhcp.client.vendorClassOpt.value.hexData"
   ::= {er1646v2XEfmPppOEIpV6DhcpClientVendorClEntry 16973824}

er1646v2XEfmPppOEIpV6DhcpRelayDestinations OBJECT-TYPE
   SYNTAX      SEQUENCE OF Er1646v2XEfmPppOEIpV6DhcpRelayDestinationsEntry
   MAX-ACCESS  not-accessible
   STATUS      current
   DESCRIPTION
      ""
   ::= {er1646v2XEfmPppOE 705323072}

er1646v2XEfmPppOEIpV6DhcpRelayDestinationsEntry OBJECT-TYPE
   SYNTAX      Er1646v2XEfmPppOEIpV6DhcpRelayDestinationsEntry
   MAX-ACCESS  not-accessible
   STATUS      current
   DESCRIPTION
      ""
   INDEX      { er1646v2XEfmPppOETableIx,
                er1646v2XEfmPppOEIpV6DhcpRelayDestinationsTableIx }
   ::= {er1646v2XEfmPppOEIpV6DhcpRelayDestinations 1}

Er1646v2XEfmPppOEIpV6DhcpRelayDestinationsEntry ::=
   SEQUENCE
      {
      er1646v2XEfmPppOEIpV6DhcpRelayDestinationsActions
         VariableLengthTableActions,
      er1646v2XEfmPppOEIpV6DhcpRelayDestinationsTableIx
         TableIndex,
      er1646v2XEfmPppOEIpV6DhcpRelayDestinationsAddress
         Ipv6Address,
      er1646v2XEfmPppOEIpV6DhcpRelayDestinationsInterface
         DisplayString
      }

er1646v2XEfmPppOEIpV6DhcpRelayDestinationsActions OBJECT-TYPE
   SYNTAX      VariableLengthTableActions
   MAX-ACCESS  read-write
   STATUS      current
   DESCRIPTION
      "By way of this field, some manipulations
       on this table may be performed."
   ::= {er1646v2XEfmPppOEIpV6DhcpRelayDestinationsEntry 2}

er1646v2XEfmPppOEIpV6DhcpRelayDestinationsTableIx OBJECT-TYPE
   SYNTAX      TableIndex
   MAX-ACCESS  not-accessible
   STATUS      current
   DESCRIPTION
      ""
   ::= {er1646v2XEfmPppOEIpV6DhcpRelayDestinationsEntry 11}

er1646v2XEfmPppOEIpV6DhcpRelayDestinationsAddress OBJECT-TYPE
   SYNTAX      Ipv6Address
   MAX-ACCESS  read-write
   STATUS      current
   DESCRIPTION
      "Path: efm.editConf.pppoEClient.ipV6.dhcp.relay.destinations.address

       ipv6 address"
   ::= {er1646v2XEfmPppOEIpV6DhcpRelayDestinationsEntry 16777216}

er1646v2XEfmPppOEIpV6DhcpRelayDestinationsInterface OBJECT-TYPE
   SYNTAX      DisplayString
   MAX-ACCESS  read-write
   STATUS      current
   DESCRIPTION
      "Path: efm.editConf.pppoEClient.ipV6.dhcp.relay.destinations.interface"
   ::= {er1646v2XEfmPppOEIpV6DhcpRelayDestinationsEntry 33554432}


er1646v2XEfmDot1x OBJECT IDENTIFIER ::= {er1646v2XEfm 191}

er1646v2XEfmDot1xSSC OBJECT IDENTIFIER ::= {er1646v2XEfmDot1x 1}

er1646v2XEfmDot1xEntry OBJECT IDENTIFIER ::= {er1646v2XEfmDot1xSSC 1}

er1646v2XEfmDot1xMode OBJECT-TYPE
   SYNTAX      INTEGER
               {
               inactive (0),
               auto (1)
               }
   MAX-ACCESS  read-write
   STATUS      current
   DESCRIPTION
      "Path: efm.editConf.dot1x.mode

       Possibilities:
               inactive   (0)
               auto   (1)"
   ::= {er1646v2XEfmDot1xEntry 16777216}

er1646v2XEfmDot1xMaxHosts OBJECT-TYPE
   SYNTAX      Integer32
   MAX-ACCESS  read-write
   STATUS      current
   DESCRIPTION
      "Path: efm.editConf.dot1x.maxHosts"
   ::= {er1646v2XEfmDot1xEntry 33554432}

er1646v2XEfmDot1xReAuthentication OBJECT-TYPE
   SYNTAX      INTEGER
               {
               disabled (0),
               enabled (1)
               }
   MAX-ACCESS  read-write
   STATUS      current
   DESCRIPTION
      "Path: efm.editConf.dot1x.reAuthentication

       Possibilities:
               disabled   (0)
               enabled   (1)"
   ::= {er1646v2XEfmDot1xEntry 50331648}

er1646v2XEfmDot1xReAuthPeriod OBJECT-TYPE
   SYNTAX      TimeTicks
   MAX-ACCESS  read-write
   STATUS      current
   DESCRIPTION
      "Path: efm.editConf.dot1x.reAuthPeriod

       Time in centi-second."
   ::= {er1646v2XEfmDot1xEntry 67108864}

er1646v2XEfmDot1xQuietPeriod OBJECT-TYPE
   SYNTAX      TimeTicks
   MAX-ACCESS  read-write
   STATUS      current
   DESCRIPTION
      "Path: efm.editConf.dot1x.quietPeriod

       Time in centi-second."
   ::= {er1646v2XEfmDot1xEntry 83886080}

er1646v2XEfmDot1xSupplTimeout OBJECT-TYPE
   SYNTAX      TimeTicks
   MAX-ACCESS  read-write
   STATUS      current
   DESCRIPTION
      "Path: efm.editConf.dot1x.supplTimeout

       Time in centi-second."
   ::= {er1646v2XEfmDot1xEntry 100663296}

er1646v2XEfmDot1xServerTimeout OBJECT-TYPE
   SYNTAX      TimeTicks
   MAX-ACCESS  read-write
   STATUS      current
   DESCRIPTION
      "Path: efm.editConf.dot1x.serverTimeout

       Time in centi-second."
   ::= {er1646v2XEfmDot1xEntry 117440512}

er1646v2XEfmDot1xMaxReqCount OBJECT-TYPE
   SYNTAX      Integer32
   MAX-ACCESS  read-write
   STATUS      current
   DESCRIPTION
      "Path: efm.editConf.dot1x.maxReqCount"
   ::= {er1646v2XEfmDot1xEntry 134217728}


er1646v2XEfmName OBJECT-TYPE
   SYNTAX      DisplayString
   MAX-ACCESS  read-write
   STATUS      current
   DESCRIPTION
      "Path: efm.editConf.name
       Info: config interface name"
   ::= {er1646v2XEfm 2}


er1646v2XEfmMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: efm.editConf.mode
       Info: routing and/or bridging or ipV6 or multilink selection

       Possibilities:
               bridging   (0)
               routing   (1)
               routingAndBridging   (2)
               ipV6   (3)
               ipV6/ipV4   (4)
               multilink   (5)"
   ::= {er1646v2XEfm 29}


er1646v2XEfmIpV6 OBJECT IDENTIFIER ::= {er1646v2XEfm 15}

er1646v2XEfmIpV6SSC OBJECT IDENTIFIER ::= {er1646v2XEfmIpV6 1}

er1646v2XEfmIpV6Entry OBJECT IDENTIFIER ::= {er1646v2XEfmIpV6SSC 1}

er1646v2XEfmIpV6VrfRouter OBJECT-TYPE
   SYNTAX      DisplayString
   MAX-ACCESS  read-write
   STATUS      current
   DESCRIPTION
      "Path: efm.editConf.ipV6.vrfRouter"
   ::= {er1646v2XEfmIpV6Entry 16777216}

er1646v2XEfmIpV6AddrAutoConfigNrDupAddrDetects OBJECT-TYPE
   SYNTAX      Integer32
   MAX-ACCESS  read-write
   STATUS      current
   DESCRIPTION
      "Path: efm.editConf.ipV6.addrAutoConfig.nrDupAddrDetects"
   ::= {er1646v2XEfmIpV6Entry 67174400}

er1646v2XEfmIpV6AddrAutoConfigAcceptRa OBJECT-TYPE
   SYNTAX      INTEGER
               {
               disabled (0),
               enabled (1)
               }
   MAX-ACCESS  read-write
   STATUS      current
   DESCRIPTION
      "Path: efm.editConf.ipV6.addrAutoConfig.acceptRa

       Possibilities:
               disabled   (0)
               enabled   (1)"
   ::= {er1646v2XEfmIpV6Entry 67239936}

er1646v2XEfmIpV6AddrAutoConfigAcceptRaRdnss OBJECT-TYPE
   SYNTAX      INTEGER
               {
               disabled (0),
               enabled (1)
               }
   MAX-ACCESS  read-write
   STATUS      current
   DESCRIPTION
      "Path: efm.editConf.ipV6.addrAutoConfig.acceptRaRdnss

       Possibilities:
               disabled   (0)
               enabled   (1)"
   ::= {er1646v2XEfmIpV6Entry 67305472}

er1646v2XEfmIpV6AddrAutoConfigAcceptRaDnssl OBJECT-TYPE
   SYNTAX      INTEGER
               {
               disabled (0),
               enabled (1)
               }
   MAX-ACCESS  read-write
   STATUS      current
   DESCRIPTION
      "Path: efm.editConf.ipV6.addrAutoConfig.acceptRaDnssl

       Possibilities:
               disabled   (0)
               enabled   (1)"
   ::= {er1646v2XEfmIpV6Entry 67371008}

er1646v2XEfmIpV6DefaultRoute OBJECT-TYPE
   SYNTAX      INTEGER
               {
               disabled (0),
               enabled (1)
               }
   MAX-ACCESS  read-write
   STATUS      current
   DESCRIPTION
      "Path: efm.editConf.ipV6.defaultRoute

       Possibilities:
               disabled   (0)
               enabled   (1)"
   ::= {er1646v2XEfmIpV6Entry 83886080}

er1646v2XEfmIpV6RaSend OBJECT-TYPE
   SYNTAX      INTEGER
               {
               disabled (0),
               enabled (1)
               }
   MAX-ACCESS  read-write
   STATUS      current
   DESCRIPTION
      "Path: efm.editConf.ipV6.ra.send

       Possibilities:
               disabled   (0)
               enabled   (1)"
   ::= {er1646v2XEfmIpV6Entry 100728832}

er1646v2XEfmIpV6RaMinInterval OBJECT-TYPE
   SYNTAX      TimeTicks
   MAX-ACCESS  read-write
   STATUS      current
   DESCRIPTION
      "Path: efm.editConf.ipV6.ra.minInterval

       Time in centi-second."
   ::= {er1646v2XEfmIpV6Entry 100794368}

er1646v2XEfmIpV6RaMaxInterval OBJECT-TYPE
   SYNTAX      TimeTicks
   MAX-ACCESS  read-write
   STATUS      current
   DESCRIPTION
      "Path: efm.editConf.ipV6.ra.maxInterval

       Time in centi-second."
   ::= {er1646v2XEfmIpV6Entry 100859904}

er1646v2XEfmIpV6RaManagedFlag OBJECT-TYPE
   SYNTAX      INTEGER
               {
               disabled (0),
               enabled (1)
               }
   MAX-ACCESS  read-write
   STATUS      current
   DESCRIPTION
      "Path: efm.editConf.ipV6.ra.managedFlag

       Possibilities:
               disabled   (0)
               enabled   (1)"
   ::= {er1646v2XEfmIpV6Entry 100925440}

er1646v2XEfmIpV6RaOtherConfFlag OBJECT-TYPE
   SYNTAX      INTEGER
               {
               disabled (0),
               enabled (1)
               }
   MAX-ACCESS  read-write
   STATUS      current
   DESCRIPTION
      "Path: efm.editConf.ipV6.ra.otherConfFlag

       Possibilities:
               disabled   (0)
               enabled   (1)"
   ::= {er1646v2XEfmIpV6Entry 100990976}

er1646v2XEfmIpV6RaLinkMtu OBJECT-TYPE
   SYNTAX      Integer32
   MAX-ACCESS  read-write
   STATUS      current
   DESCRIPTION
      "Path: efm.editConf.ipV6.ra.linkMtu"
   ::= {er1646v2XEfmIpV6Entry 101056512}

er1646v2XEfmIpV6RaReachableTime OBJECT-TYPE
   SYNTAX      TimeTicks
   MAX-ACCESS  read-write
   STATUS      current
   DESCRIPTION
      "Path: efm.editConf.ipV6.ra.reachableTime

       Time in centi-second."
   ::= {er1646v2XEfmIpV6Entry 101122048}

er1646v2XEfmIpV6RaRetransmitTime OBJECT-TYPE
   SYNTAX      TimeTicks
   MAX-ACCESS  read-write
   STATUS      current
   DESCRIPTION
      "Path: efm.editConf.ipV6.ra.retransmitTime

       Time in centi-second."
   ::= {er1646v2XEfmIpV6Entry 101187584}

er1646v2XEfmIpV6RaHopLimit OBJECT-TYPE
   SYNTAX      Integer32
   MAX-ACCESS  read-write
   STATUS      current
   DESCRIPTION
      "Path: efm.editConf.ipV6.ra.hopLimit"
   ::= {er1646v2XEfmIpV6Entry 101253120}

er1646v2XEfmIpV6RaDefaultLifeTime OBJECT-TYPE
   SYNTAX      TimeTicks
   MAX-ACCESS  read-write
   STATUS      current
   DESCRIPTION
      "Path: efm.editConf.ipV6.ra.defaultLifeTime

       Time in centi-second."
   ::= {er1646v2XEfmIpV6Entry 101318656}

er1646v2XEfmIpV6RaDnsOptionsRdnssLifeTime OBJECT-TYPE
   SYNTAX      TimeTicks
   MAX-ACCESS  read-write
   STATUS      current
   DESCRIPTION
      "Path: efm.editConf.ipV6.ra.dnsOptions.rdnss.lifeTime

       Time in centi-second."
   ::= {er1646v2XEfmIpV6Entry 101393408}

er1646v2XEfmIpV6RaDnsOptionsRdnssImportServers OBJECT-TYPE
   SYNTAX      INTEGER
               {
               disabled (0),
               enabled (1)
               }
   MAX-ACCESS  read-write
   STATUS      current
   DESCRIPTION
      "Path: efm.editConf.ipV6.ra.dnsOptions.rdnss.importServers

       Possibilities:
               disabled   (0)
               enabled   (1)"
   ::= {er1646v2XEfmIpV6Entry 101395456}

er1646v2XEfmIpV6RaDnsOptionsDnsslLifeTime OBJECT-TYPE
   SYNTAX      TimeTicks
   MAX-ACCESS  read-write
   STATUS      current
   DESCRIPTION
      "Path: efm.editConf.ipV6.ra.dnsOptions.dnssl.lifeTime

       Time in centi-second."
   ::= {er1646v2XEfmIpV6Entry 101401600}

er1646v2XEfmIpV6RaDnsOptionsDnsslImportDomains OBJECT-TYPE
   SYNTAX      INTEGER
               {
               disabled (0),
               enabled (1)
               }
   MAX-ACCESS  read-write
   STATUS      current
   DESCRIPTION
      "Path: efm.editConf.ipV6.ra.dnsOptions.dnssl.importDomains

       Possibilities:
               disabled   (0)
               enabled   (1)"
   ::= {er1646v2XEfmIpV6Entry 101403648}

er1646v2XEfmIpV6RsSend OBJECT-TYPE
   SYNTAX      INTEGER
               {
               disabled (0),
               enabled (1)
               }
   MAX-ACCESS  read-write
   STATUS      current
   DESCRIPTION
      "Path: efm.editConf.ipV6.rs.send

       Possibilities:
               disabled   (0)
               enabled   (1)"
   ::= {er1646v2XEfmIpV6Entry 335609856}

er1646v2XEfmIpV6RsMaxRandomDelay OBJECT-TYPE
   SYNTAX      TimeTicks
   MAX-ACCESS  read-write
   STATUS      current
   DESCRIPTION
      "Path: efm.editConf.ipV6.rs.maxRandomDelay

       Time in centi-second."
   ::= {er1646v2XEfmIpV6Entry 335675392}

er1646v2XEfmIpV6RsInterval OBJECT-TYPE
   SYNTAX      TimeTicks
   MAX-ACCESS  read-write
   STATUS      current
   DESCRIPTION
      "Path: efm.editConf.ipV6.rs.interval

       Time in centi-second."
   ::= {er1646v2XEfmIpV6Entry 335740928}

er1646v2XEfmIpV6RsMaxSolicitations OBJECT-TYPE
   SYNTAX      Integer32
   MAX-ACCESS  read-write
   STATUS      current
   DESCRIPTION
      "Path: efm.editConf.ipV6.rs.maxSolicitations"
   ::= {er1646v2XEfmIpV6Entry 335806464}

er1646v2XEfmIpV6TrafficPolicyInbound OBJECT-TYPE
   SYNTAX      DisplayString
   MAX-ACCESS  read-write
   STATUS      current
   DESCRIPTION
      "Path: efm.editConf.ipV6.trafficPolicy.inbound"
   ::= {er1646v2XEfmIpV6Entry 184614912}

er1646v2XEfmIpV6TrafficPolicyOutbound OBJECT-TYPE
   SYNTAX      DisplayString
   MAX-ACCESS  read-write
   STATUS      current
   DESCRIPTION
      "Path: efm.editConf.ipV6.trafficPolicy.outbound"
   ::= {er1646v2XEfmIpV6Entry 184680448}

er1646v2XEfmIpV6FirewallZone OBJECT-TYPE
   SYNTAX      DisplayString
   MAX-ACCESS  read-write
   STATUS      current
   DESCRIPTION
      "Path: efm.editConf.ipV6.firewall.zone"
   ::= {er1646v2XEfmIpV6Entry 201392128}

er1646v2XEfmIpV6DhcpClientAddrAC OBJECT-TYPE
   SYNTAX      INTEGER
               {
               disabled (0),
               enabled (1)
               }
   MAX-ACCESS  read-write
   STATUS      current
   DESCRIPTION
      "Path: efm.editConf.ipV6.dhcp.client.addrAutoConfig

       Possibilities:
               disabled   (0)
               enabled   (1)"
   ::= {er1646v2XEfmIpV6Entry 170131456}

er1646v2XEfmIpV6DhcpClientPrDelMode OBJECT-TYPE
   SYNTAX      INTEGER
               {
               disabled (0),
               enabled (1)
               }
   MAX-ACCESS  read-write
   STATUS      current
   DESCRIPTION
      "Path: efm.editConf.ipV6.dhcp.client.pd.mode

       Possibilities:
               disabled   (0)
               enabled   (1)"
   ::= {er1646v2XEfmIpV6Entry 170394624}

er1646v2XEfmIpV6DhcpClientPrDelPool OBJECT-TYPE
   SYNTAX      DisplayString
   MAX-ACCESS  read-write
   STATUS      current
   DESCRIPTION
      "Path: efm.editConf.ipV6.dhcp.client.pd.pool"
   ::= {er1646v2XEfmIpV6Entry 170395648}

er1646v2XEfmIpV6DhcpClientPrDelPdExclOpt OBJECT-TYPE
   SYNTAX      INTEGER
               {
               disabled (0),
               enabled (1)
               }
   MAX-ACCESS  read-write
   STATUS      current
   DESCRIPTION
      "Path: efm.editConf.ipV6.dhcp.client.pd.pdExclOpt

       Possibilities:
               disabled   (0)
               enabled   (1)"
   ::= {er1646v2XEfmIpV6Entry 170396672}

er1646v2XEfmIpV6DhcpClientDnsServerPref OBJECT-TYPE
   SYNTAX      Integer32
   MAX-ACCESS  read-write
   STATUS      current
   DESCRIPTION
      "Path: efm.editConf.ipV6.dhcp.client.dns.serverPref"
   ::= {er1646v2XEfmIpV6Entry 170918912}

er1646v2XEfmIpV6DhcpClientRapidCommit OBJECT-TYPE
   SYNTAX      INTEGER
               {
               disabled (0),
               enabled (1)
               }
   MAX-ACCESS  read-write
   STATUS      current
   DESCRIPTION
      "Path: efm.editConf.ipV6.dhcp.client.rapidCommit

       Possibilities:
               disabled   (0)
               enabled   (1)"
   ::= {er1646v2XEfmIpV6Entry 170655744}

er1646v2XEfmIpV6DhcpClientTimersSolTimeOut OBJECT-TYPE
   SYNTAX      TimeTicks
   MAX-ACCESS  read-write
   STATUS      current
   DESCRIPTION
      "Path: efm.editConf.ipV6.dhcp.client.timers.solTimeOut

       Time in centi-second."
   ::= {er1646v2XEfmIpV6Entry 171181056}

er1646v2XEfmIpV6DhcpClientTimersSolMaxRt OBJECT-TYPE
   SYNTAX      TimeTicks
   MAX-ACCESS  read-write
   STATUS      current
   DESCRIPTION
      "Path: efm.editConf.ipV6.dhcp.client.timers.solMaxRt

       Time in centi-second."
   ::= {er1646v2XEfmIpV6Entry 171182080}

er1646v2XEfmIpV6DhcpClientTimersInfoRefresh OBJECT-TYPE
   SYNTAX      TimeTicks
   MAX-ACCESS  read-write
   STATUS      current
   DESCRIPTION
      "Path: efm.editConf.ipV6.dhcp.client.timers.infoRefresh

       Time in centi-second."
   ::= {er1646v2XEfmIpV6Entry 171183104}

er1646v2XEfmIpV6DhcpServerMode OBJECT-TYPE
   SYNTAX      INTEGER
               {
               disabled (0),
               enabled (1)
               }
   MAX-ACCESS  read-write
   STATUS      current
   DESCRIPTION
      "Path: efm.editConf.ipV6.dhcp.server.mode

       Possibilities:
               disabled   (0)
               enabled   (1)"
   ::= {er1646v2XEfmIpV6Entry 172228608}

er1646v2XEfmIpV6DhcpServerPreference OBJECT-TYPE
   SYNTAX      Integer32
   MAX-ACCESS  read-write
   STATUS      current
   DESCRIPTION
      "Path: efm.editConf.ipV6.dhcp.server.preference"
   ::= {er1646v2XEfmIpV6Entry 172490752}

er1646v2XEfmIpV6DhcpServerPool OBJECT-TYPE
   SYNTAX      DisplayString
   MAX-ACCESS  read-write
   STATUS      current
   DESCRIPTION
      "Path: efm.editConf.ipV6.dhcp.server.pool"
   ::= {er1646v2XEfmIpV6Entry 172752896}

er1646v2XEfmIpV6DhcpServerRapidCommit OBJECT-TYPE
   SYNTAX      INTEGER
               {
               disabled (0),
               enabled (1)
               }
   MAX-ACCESS  read-write
   STATUS      current
   DESCRIPTION
      "Path: efm.editConf.ipV6.dhcp.server.rapidCommit

       Possibilities:
               disabled   (0)
               enabled   (1)"
   ::= {er1646v2XEfmIpV6Entry 173015040}

er1646v2XEfmIpV6DhcpServerTimersInfoRefresh OBJECT-TYPE
   SYNTAX      TimeTicks
   MAX-ACCESS  read-write
   STATUS      current
   DESCRIPTION
      "Path: efm.editConf.ipV6.dhcp.server.timers.infoRefresh

       Time in centi-second."
   ::= {er1646v2XEfmIpV6Entry 173278208}

er1646v2XEfmIpV6DhcpRelayMode OBJECT-TYPE
   SYNTAX      INTEGER
               {
               disabled (0),
               enabled (1)
               }
   MAX-ACCESS  read-write
   STATUS      current
   DESCRIPTION
      "Path: efm.editConf.ipV6.dhcp.relay.mode

       Possibilities:
               disabled   (0)
               enabled   (1)"
   ::= {er1646v2XEfmIpV6Entry 174071808}

er1646v2XEfmIpV6SendRedirect OBJECT-TYPE
   SYNTAX      INTEGER
               {
               disabled (0),
               enabled (1)
               }
   MAX-ACCESS  read-write
   STATUS      current
   DESCRIPTION
      "Path: efm.editConf.ipV6.sendRedirect

       Possibilities:
               disabled   (0)
               enabled   (1)"
   ::= {er1646v2XEfmIpV6Entry 117440512}

er1646v2XEfmIpV6LinkMtu OBJECT-TYPE
   SYNTAX      Integer32
   MAX-ACCESS  read-write
   STATUS      current
   DESCRIPTION
      "Path: efm.editConf.ipV6.linkMtu"
   ::= {er1646v2XEfmIpV6Entry 134217728}

er1646v2XEfmIpV6InterfaceId OBJECT-TYPE
   SYNTAX      OCTET STRING
   MAX-ACCESS  read-write
   STATUS      current
   DESCRIPTION
      "Path: efm.editConf.ipV6.interfaceId"
   ::= {er1646v2XEfmIpV6Entry 150994944}

er1646v2XEfmIpV6MF OBJECT-TYPE
   SYNTAX      Integer32
   MAX-ACCESS  read-write
   STATUS      current
   DESCRIPTION
      "Path: efm.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2XEfmIpV6Entry 285212672}

er1646v2XEfmIpV6IcmpMessagesNoRoute OBJECT-TYPE
   SYNTAX      INTEGER
               {
               disabled (0),
               enabled (1)
               }
   MAX-ACCESS  read-write
   STATUS      current
   DESCRIPTION
      "Path: efm.editConf.ipV6.icmpMessages.noRoute

       Possibilities:
               disabled   (0)
               enabled   (1)"
   ::= {er1646v2XEfmIpV6Entry 302055424}

er1646v2XEfmIpV6IcmpMessagesBeyondScope OBJECT-TYPE
   SYNTAX      INTEGER
               {
               disabled (0),
               enabled (1)
               }
   MAX-ACCESS  read-write
   STATUS      current
   DESCRIPTION
      "Path: efm.editConf.ipV6.icmpMessages.beyondScope

       Possibilities:
               disabled   (0)
               enabled   (1)"
   ::= {er1646v2XEfmIpV6Entry 302186496}

er1646v2XEfmIpV6IcmpMessagesAddressUnreachable OBJECT-TYPE
   SYNTAX      INTEGER
               {
               disabled (0),
               enabled (1)
               }
   MAX-ACCESS  read-write
   STATUS      current
   DESCRIPTION
      "Path: efm.editConf.ipV6.icmpMessages.addressUnreachable

       Possibilities:
               disabled   (0)
               enabled   (1)"
   ::= {er1646v2XEfmIpV6Entry 302252032}

er1646v2XEfmIpV6IcmpMessagesPortUnreachable OBJECT-TYPE
   SYNTAX      INTEGER
               {
               disabled (0),
               enabled (1)
               }
   MAX-ACCESS  read-write
   STATUS      current
   DESCRIPTION
      "Path: efm.editConf.ipV6.icmpMessages.portUnreachable

       Possibilities:
               disabled   (0)
               enabled   (1)"
   ::= {er1646v2XEfmIpV6Entry 302317568}

er1646v2XEfmIpV6IcmpMessagesPacketTooBig OBJECT-TYPE
   SYNTAX      INTEGER
               {
               disabled (0),
               enabled (1)
               }
   MAX-ACCESS  read-write
   STATUS      current
   DESCRIPTION
      "Path: efm.editConf.ipV6.icmpMessages.packetTooBig

       Possibilities:
               disabled   (0)
               enabled   (1)"
   ::= {er1646v2XEfmIpV6Entry 302645248}

er1646v2XEfmIpV6IcmpMessagesHopLimitExceeded OBJECT-TYPE
   SYNTAX      INTEGER
               {
               disabled (0),
               enabled (1)
               }
   MAX-ACCESS  read-write
   STATUS      current
   DESCRIPTION
      "Path: efm.editConf.ipV6.icmpMessages.hopLimitExceeded

       Possibilities:
               disabled   (0)
               enabled   (1)"
   ::= {er1646v2XEfmIpV6Entry 303300608}

er1646v2XEfmIpV6IcmpMessagesFragTimeExceeded OBJECT-TYPE
   SYNTAX      INTEGER
               {
               disabled (0),
               enabled (1)
               }
   MAX-ACCESS  read-write
   STATUS      current
   DESCRIPTION
      "Path: efm.editConf.ipV6.icmpMessages.fragTimeExceeded

       Possibilities:
               disabled   (0)
               enabled   (1)"
   ::= {er1646v2XEfmIpV6Entry 303366144}

er1646v2XEfmIpV6IcmpMessagesHeaderFieldErr OBJECT-TYPE
   SYNTAX      INTEGER
               {
               disabled (0),
               enabled (1)
               }
   MAX-ACCESS  read-write
   STATUS      current
   DESCRIPTION
      "Path: efm.editConf.ipV6.icmpMessages.headerFieldErr

       Possibilities:
               disabled   (0)
               enabled   (1)"
   ::= {er1646v2XEfmIpV6Entry 303955968}

er1646v2XEfmIpV6IcmpMessagesOptionUnrecognized OBJECT-TYPE
   SYNTAX      INTEGER
               {
               disabled (0),
               enabled (1)
               }
   MAX-ACCESS  read-write
   STATUS      current
   DESCRIPTION
      "Path: efm.editConf.ipV6.icmpMessages.optionUnrecognized

       Possibilities:
               disabled   (0)
               enabled   (1)"
   ::= {er1646v2XEfmIpV6Entry 304087040}

er1646v2XEfmIpV6IcmpMessagesRedirect OBJECT-TYPE
   SYNTAX      INTEGER
               {
               disabled (0),
               enabled (1)
               }
   MAX-ACCESS  read-write
   STATUS      current
   DESCRIPTION
      "Path: efm.editConf.ipV6.icmpMessages.redirect

       Possibilities:
               disabled   (0)
               enabled   (1)"
   ::= {er1646v2XEfmIpV6Entry 304611328}

er1646v2XEfmIpV6Addresses OBJECT-TYPE
   SYNTAX      SEQUENCE OF Er1646v2XEfmIpV6AddressesEntry
   MAX-ACCESS  not-accessible
   STATUS      current
   DESCRIPTION
      ""
   ::= {er1646v2XEfmIpV6 50331648}

er1646v2XEfmIpV6AddressesEntry OBJECT-TYPE
   SYNTAX      Er1646v2XEfmIpV6AddressesEntry
   MAX-ACCESS  not-accessible
   STATUS      current
   DESCRIPTION
      ""
   INDEX      { er1646v2XEfmIpV6AddressesTableIx }
   ::= {er1646v2XEfmIpV6Addresses 1}

Er1646v2XEfmIpV6AddressesEntry ::=
   SEQUENCE
      {
      er1646v2XEfmIpV6AddressesActions
         VariableLengthTableActions,
      er1646v2XEfmIpV6AddressesTableIx
         TableIndex,
      er1646v2XEfmIpV6AddressesType
         INTEGER,
      er1646v2XEfmIpV6AddressesAddress
         Ipv6Address,
      er1646v2XEfmIpV6AddressesPrefixLength
         Integer32,
      er1646v2XEfmIpV6AddressesGeneralPrefix
         DisplayString,
      er1646v2XEfmIpV6AddressesRaSend
         INTEGER,
      er1646v2XEfmIpV6AddressesRaOnLinkFlag
         INTEGER,
      er1646v2XEfmIpV6AddressesRaAutoFlag
         INTEGER,
      er1646v2XEfmIpV6AddressesRaValidLifeTime
         TimeTicks,
      er1646v2XEfmIpV6AddressesRaValidLTMode
         INTEGER,
      er1646v2XEfmIpV6AddressesRaPrefLifeTime
         TimeTicks,
      er1646v2XEfmIpV6AddressesRaPrefLTMode
         INTEGER
      }

er1646v2XEfmIpV6AddressesActions OBJECT-TYPE
   SYNTAX      VariableLengthTableActions
   MAX-ACCESS  read-write
   STATUS      current
   DESCRIPTION
      "By way of this field, some manipulations
       on this table may be performed."
   ::= {er1646v2XEfmIpV6AddressesEntry 2}

er1646v2XEfmIpV6AddressesTableIx OBJECT-TYPE
   SYNTAX      TableIndex
   MAX-ACCESS  not-accessible
   STATUS      current
   DESCRIPTION
      ""
   ::= {er1646v2XEfmIpV6AddressesEntry 11}

er1646v2XEfmIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.ipV6.addresses.type

       Possibilities:
               unicast   (0)
               eui64   (1)
               anycast   (2)
               linkLocal   (3)
               generalPrefix   (4)"
   ::= {er1646v2XEfmIpV6AddressesEntry 50331648}

er1646v2XEfmIpV6AddressesAddress OBJECT-TYPE
   SYNTAX      Ipv6Address
   MAX-ACCESS  read-write
   STATUS      current
   DESCRIPTION
      "Path: efm.editConf.ipV6.addresses.address

       ipv6 address"
   ::= {er1646v2XEfmIpV6AddressesEntry 16777216}

er1646v2XEfmIpV6AddressesPrefixLength OBJECT-TYPE
   SYNTAX      Integer32
   MAX-ACCESS  read-write
   STATUS      current
   DESCRIPTION
      "Path: efm.editConf.ipV6.addresses.prefixLength"
   ::= {er1646v2XEfmIpV6AddressesEntry 33554432}

er1646v2XEfmIpV6AddressesGeneralPrefix OBJECT-TYPE
   SYNTAX      DisplayString
   MAX-ACCESS  read-write
   STATUS      current
   DESCRIPTION
      "Path: efm.editConf.ipV6.addresses.generalPrefix"
   ::= {er1646v2XEfmIpV6AddressesEntry 83886080}

er1646v2XEfmIpV6AddressesRaSend OBJECT-TYPE
   SYNTAX      INTEGER
               {
               disabled (0),
               enabled (1)
               }
   MAX-ACCESS  read-write
   STATUS      current
   DESCRIPTION
      "Path: efm.editConf.ipV6.addresses.ra.send

       Possibilities:
               disabled   (0)
               enabled   (1)"
   ::= {er1646v2XEfmIpV6AddressesEntry 67174400}

er1646v2XEfmIpV6AddressesRaOnLinkFlag OBJECT-TYPE
   SYNTAX      INTEGER
               {
               disabled (0),
               enabled (1)
               }
   MAX-ACCESS  read-write
   STATUS      current
   DESCRIPTION
      "Path: efm.editConf.ipV6.addresses.ra.onLinkFlag

       Possibilities:
               disabled   (0)
               enabled   (1)"
   ::= {er1646v2XEfmIpV6AddressesEntry 67371008}

er1646v2XEfmIpV6AddressesRaAutoFlag OBJECT-TYPE
   SYNTAX      INTEGER
               {
               disabled (0),
               enabled (1)
               }
   MAX-ACCESS  read-write
   STATUS      current
   DESCRIPTION
      "Path: efm.editConf.ipV6.addresses.ra.autonomousFlag

       Possibilities:
               disabled   (0)
               enabled   (1)"
   ::= {er1646v2XEfmIpV6AddressesEntry 67567616}

er1646v2XEfmIpV6AddressesRaValidLifeTime OBJECT-TYPE
   SYNTAX      TimeTicks
   MAX-ACCESS  read-write
   STATUS      current
   DESCRIPTION
      "Path: efm.editConf.ipV6.addresses.ra.validLifeTime

       Time in centi-second."
   ::= {er1646v2XEfmIpV6AddressesEntry 67239936}

er1646v2XEfmIpV6AddressesRaValidLTMode OBJECT-TYPE
   SYNTAX      INTEGER
               {
               fixed (0),
               infinite (2)
               }
   MAX-ACCESS  read-write
   STATUS      current
   DESCRIPTION
      "Path: efm.editConf.ipV6.addresses.ra.validLifeTimeMode

       Possibilities:
               fixed   (0)
               infinite   (2)"
   ::= {er1646v2XEfmIpV6AddressesEntry 67305472}

er1646v2XEfmIpV6AddressesRaPrefLifeTime OBJECT-TYPE
   SYNTAX      TimeTicks
   MAX-ACCESS  read-write
   STATUS      current
   DESCRIPTION
      "Path: efm.editConf.ipV6.addresses.ra.prefLifeTime

       Time in centi-second."
   ::= {er1646v2XEfmIpV6AddressesEntry 67436544}

er1646v2XEfmIpV6AddressesRaPrefLTMode OBJECT-TYPE
   SYNTAX      INTEGER
               {
               fixed (0),
               infinite (2)
               }
   MAX-ACCESS  read-write
   STATUS      current
   DESCRIPTION
      "Path: efm.editConf.ipV6.addresses.ra.prefLifeTimeMode

       Possibilities:
               fixed   (0)
               infinite   (2)"
   ::= {er1646v2XEfmIpV6AddressesEntry 67502080}

er1646v2XEfmIpV6RaDnsOptionsRdnssServers OBJECT-TYPE
   SYNTAX      SEQUENCE OF Er1646v2XEfmIpV6RaDnsOptionsRdnssServersEntry
   MAX-ACCESS  not-accessible
   STATUS      current
   DESCRIPTION
      ""
   ::= {er1646v2XEfmIpV6 101394432}

er1646v2XEfmIpV6RaDnsOptionsRdnssServersEntry OBJECT-TYPE
   SYNTAX      Er1646v2XEfmIpV6RaDnsOptionsRdnssServersEntry
   MAX-ACCESS  not-accessible
   STATUS      current
   DESCRIPTION
      ""
   INDEX      { er1646v2XEfmIpV6RaDnsOptionsRdnssServersTableIx }
   ::= {er1646v2XEfmIpV6RaDnsOptionsRdnssServers 1}

Er1646v2XEfmIpV6RaDnsOptionsRdnssServersEntry ::=
   SEQUENCE
      {
      er1646v2XEfmIpV6RaDnsOptionsRdnssServersActions
         VariableLengthTableActions,
      er1646v2XEfmIpV6RaDnsOptionsRdnssServersTableIx
         TableIndex,
      er1646v2XEfmIpV6RaDnsOptionsRdnssServersAddress
         Ipv6Address
      }

er1646v2XEfmIpV6RaDnsOptionsRdnssServersActions OBJECT-TYPE
   SYNTAX      VariableLengthTableActions
   MAX-ACCESS  read-write
   STATUS      current
   DESCRIPTION
      "By way of this field, some manipulations
       on this table may be performed."
   ::= {er1646v2XEfmIpV6RaDnsOptionsRdnssServersEntry 2}

er1646v2XEfmIpV6RaDnsOptionsRdnssServersTableIx OBJECT-TYPE
   SYNTAX      TableIndex
   MAX-ACCESS  not-accessible
   STATUS      current
   DESCRIPTION
      ""
   ::= {er1646v2XEfmIpV6RaDnsOptionsRdnssServersEntry 11}

er1646v2XEfmIpV6RaDnsOptionsRdnssServersAddress OBJECT-TYPE
   SYNTAX      Ipv6Address
   MAX-ACCESS  read-write
   STATUS      current
   DESCRIPTION
      "Path: efm.editConf.ipV6.ra.dnsOptions.rdnss.servers.address

       ipv6 address"
   ::= {er1646v2XEfmIpV6RaDnsOptionsRdnssServersEntry 16777216}

er1646v2XEfmIpV6RaDnsOptionsDnsslDomains OBJECT-TYPE
   SYNTAX      SEQUENCE OF Er1646v2XEfmIpV6RaDnsOptionsDnsslDomainsEntry
   MAX-ACCESS  not-accessible
   STATUS      current
   DESCRIPTION
      ""
   ::= {er1646v2XEfmIpV6 101402624}

er1646v2XEfmIpV6RaDnsOptionsDnsslDomainsEntry OBJECT-TYPE
   SYNTAX      Er1646v2XEfmIpV6RaDnsOptionsDnsslDomainsEntry
   MAX-ACCESS  not-accessible
   STATUS      current
   DESCRIPTION
      ""
   INDEX      { er1646v2XEfmIpV6RaDnsOptionsDnsslDomainsTableIx }
   ::= {er1646v2XEfmIpV6RaDnsOptionsDnsslDomains 1}

Er1646v2XEfmIpV6RaDnsOptionsDnsslDomainsEntry ::=
   SEQUENCE
      {
      er1646v2XEfmIpV6RaDnsOptionsDnsslDomainsActions
         VariableLengthTableActions,
      er1646v2XEfmIpV6RaDnsOptionsDnsslDomainsTableIx
         TableIndex,
      er1646v2XEfmIpV6RaDnsOptionsDnsslDomainsName
         DisplayString
      }

er1646v2XEfmIpV6RaDnsOptionsDnsslDomainsActions OBJECT-TYPE
   SYNTAX      VariableLengthTableActions
   MAX-ACCESS  read-write
   STATUS      current
   DESCRIPTION
      "By way of this field, some manipulations
       on this table may be performed."
   ::= {er1646v2XEfmIpV6RaDnsOptionsDnsslDomainsEntry 2}

er1646v2XEfmIpV6RaDnsOptionsDnsslDomainsTableIx OBJECT-TYPE
   SYNTAX      TableIndex
   MAX-ACCESS  not-accessible
   STATUS      current
   DESCRIPTION
      ""
   ::= {er1646v2XEfmIpV6RaDnsOptionsDnsslDomainsEntry 11}

er1646v2XEfmIpV6RaDnsOptionsDnsslDomainsName OBJECT-TYPE
   SYNTAX      DisplayString
   MAX-ACCESS  read-write
   STATUS      current
   DESCRIPTION
      "Path: efm.editConf.ipV6.ra.dnsOptions.dnssl.domains.name"
   ::= {er1646v2XEfmIpV6RaDnsOptionsDnsslDomainsEntry 16777216}

er1646v2XEfmIpV6DhcpClientUserClassOpt OBJECT-TYPE
   SYNTAX      SEQUENCE OF Er1646v2XEfmIpV6DhcpClientUserClassOptEntry
   MAX-ACCESS  not-accessible
   STATUS      current
   DESCRIPTION
      ""
   ::= {er1646v2XEfmIpV6 171442176}

er1646v2XEfmIpV6DhcpClientUserClassOptEntry OBJECT-TYPE
   SYNTAX      Er1646v2XEfmIpV6DhcpClientUserClassOptEntry
   MAX-ACCESS  not-accessible
   STATUS      current
   DESCRIPTION
      ""
   INDEX      { er1646v2XEfmIpV6DhcpClientUserClassOptTableIx }
   ::= {er1646v2XEfmIpV6DhcpClientUserClassOpt 1}

Er1646v2XEfmIpV6DhcpClientUserClassOptEntry ::=
   SEQUENCE
      {
      er1646v2XEfmIpV6DhcpClientUserClassOptActions
         VariableLengthTableActions,
      er1646v2XEfmIpV6DhcpClientUserClassOptTableIx
         TableIndex,
      er1646v2XEfmIpV6DhcpClientUserClassOptValueAscii
         DisplayString,
      er1646v2XEfmIpV6DhcpClientUserClassOptValueDecimal
         Integer32,
      er1646v2XEfmIpV6DhcpClientUserClassOptValueHexData
         OCTET STRING
      }

er1646v2XEfmIpV6DhcpClientUserClassOptActions OBJECT-TYPE
   SYNTAX      VariableLengthTableActions
   MAX-ACCESS  read-write
   STATUS      current
   DESCRIPTION
      "By way of this field, some manipulations
       on this table may be performed."
   ::= {er1646v2XEfmIpV6DhcpClientUserClassOptEntry 2}

er1646v2XEfmIpV6DhcpClientUserClassOptTableIx OBJECT-TYPE
   SYNTAX      TableIndex
   MAX-ACCESS  not-accessible
   STATUS      current
   DESCRIPTION
      ""
   ::= {er1646v2XEfmIpV6DhcpClientUserClassOptEntry 11}

er1646v2XEfmIpV6DhcpClientUserClassOptValueAscii OBJECT-TYPE
   SYNTAX      DisplayString
   MAX-ACCESS  read-write
   STATUS      current
   DESCRIPTION
      "Path: efm.editConf.ipV6.dhcp.client.userClassOpt.value.ascii"
   ::= {er1646v2XEfmIpV6DhcpClientUserClassOptEntry 16842752}

er1646v2XEfmIpV6DhcpClientUserClassOptValueDecimal OBJECT-TYPE
   SYNTAX      Integer32
   MAX-ACCESS  read-write
   STATUS      current
   DESCRIPTION
      "Path: efm.editConf.ipV6.dhcp.client.userClassOpt.value.decimal"
   ::= {er1646v2XEfmIpV6DhcpClientUserClassOptEntry 16908288}

er1646v2XEfmIpV6DhcpClientUserClassOptValueHexData OBJECT-TYPE
   SYNTAX      OCTET STRING
   MAX-ACCESS  read-write
   STATUS      current
   DESCRIPTION
      "Path: efm.editConf.ipV6.dhcp.client.userClassOpt.value.hexData"
   ::= {er1646v2XEfmIpV6DhcpClientUserClassOptEntry 16973824}

er1646v2XEfmIpV6DhcpClientVendorCl OBJECT-TYPE
   SYNTAX      SEQUENCE OF Er1646v2XEfmIpV6DhcpClientVendorClEntry
   MAX-ACCESS  not-accessible
   STATUS      current
   DESCRIPTION
      ""
   ::= {er1646v2XEfmIpV6 171704320}

er1646v2XEfmIpV6DhcpClientVendorClEntry OBJECT-TYPE
   SYNTAX      Er1646v2XEfmIpV6DhcpClientVendorClEntry
   MAX-ACCESS  not-accessible
   STATUS      current
   DESCRIPTION
      ""
   INDEX      { er1646v2XEfmIpV6DhcpClientVendorClTableIx }
   ::= {er1646v2XEfmIpV6DhcpClientVendorCl 1}

Er1646v2XEfmIpV6DhcpClientVendorClEntry ::=
   SEQUENCE
      {
      er1646v2XEfmIpV6DhcpClientVendorClActions
         VariableLengthTableActions,
      er1646v2XEfmIpV6DhcpClientVendorClTableIx
         TableIndex,
      er1646v2XEfmIpV6DhcpClientVendorClValueAscii
         DisplayString,
      er1646v2XEfmIpV6DhcpClientVendorClValueDecimal
         Integer32,
      er1646v2XEfmIpV6DhcpClientVendorClValueHexData
         OCTET STRING
      }

er1646v2XEfmIpV6DhcpClientVendorClActions OBJECT-TYPE
   SYNTAX      VariableLengthTableActions
   MAX-ACCESS  read-write
   STATUS      current
   DESCRIPTION
      "By way of this field, some manipulations
       on this table may be performed."
   ::= {er1646v2XEfmIpV6DhcpClientVendorClEntry 2}

er1646v2XEfmIpV6DhcpClientVendorClTableIx OBJECT-TYPE
   SYNTAX      TableIndex
   MAX-ACCESS  not-accessible
   STATUS      current
   DESCRIPTION
      ""
   ::= {er1646v2XEfmIpV6DhcpClientVendorClEntry 11}

er1646v2XEfmIpV6DhcpClientVendorClValueAscii OBJECT-TYPE
   SYNTAX      DisplayString
   MAX-ACCESS  read-write
   STATUS      current
   DESCRIPTION
      "Path: efm.editConf.ipV6.dhcp.client.vendorClassOpt.value.ascii"
   ::= {er1646v2XEfmIpV6DhcpClientVendorClEntry 16842752}

er1646v2XEfmIpV6DhcpClientVendorClValueDecimal OBJECT-TYPE
   SYNTAX      Integer32
   MAX-ACCESS  read-write
   STATUS      current
   DESCRIPTION
      "Path: efm.editConf.ipV6.dhcp.client.vendorClassOpt.value.decimal"
   ::= {er1646v2XEfmIpV6DhcpClientVendorClEntry 16908288}

er1646v2XEfmIpV6DhcpClientVendorClValueHexData OBJECT-TYPE
   SYNTAX      OCTET STRING
   MAX-ACCESS  read-write
   STATUS      current
   DESCRIPTION
      "Path: efm.editConf.ipV6.dhcp.client.vendorClassOpt.value.hexData"
   ::= {er1646v2XEfmIpV6DhcpClientVendorClEntry 16973824}

er1646v2XEfmIpV6DhcpRelayDestinations OBJECT-TYPE
   SYNTAX      SEQUENCE OF Er1646v2XEfmIpV6DhcpRelayDestinationsEntry
   MAX-ACCESS  not-accessible
   STATUS      current
   DESCRIPTION
      ""
   ::= {er1646v2XEfmIpV6 174080000}

er1646v2XEfmIpV6DhcpRelayDestinationsEntry OBJECT-TYPE
   SYNTAX      Er1646v2XEfmIpV6DhcpRelayDestinationsEntry
   MAX-ACCESS  not-accessible
   STATUS      current
   DESCRIPTION
      ""
   INDEX      { er1646v2XEfmIpV6DhcpRelayDestinationsTableIx }
   ::= {er1646v2XEfmIpV6DhcpRelayDestinations 1}

Er1646v2XEfmIpV6DhcpRelayDestinationsEntry ::=
   SEQUENCE
      {
      er1646v2XEfmIpV6DhcpRelayDestinationsActions
         VariableLengthTableActions,
      er1646v2XEfmIpV6DhcpRelayDestinationsTableIx
         TableIndex,
      er1646v2XEfmIpV6DhcpRelayDestinationsAddress
         Ipv6Address,
      er1646v2XEfmIpV6DhcpRelayDestinationsInterface
         DisplayString
      }

er1646v2XEfmIpV6DhcpRelayDestinationsActions OBJECT-TYPE
   SYNTAX      VariableLengthTableActions
   MAX-ACCESS  read-write
   STATUS      current
   DESCRIPTION
      "By way of this field, some manipulations
       on this table may be performed."
   ::= {er1646v2XEfmIpV6DhcpRelayDestinationsEntry 2}

er1646v2XEfmIpV6DhcpRelayDestinationsTableIx OBJECT-TYPE
   SYNTAX      TableIndex
   MAX-ACCESS  not-accessible
   STATUS      current
   DESCRIPTION
      ""
   ::= {er1646v2XEfmIpV6DhcpRelayDestinationsEntry 11}

er1646v2XEfmIpV6DhcpRelayDestinationsAddress OBJECT-TYPE
   SYNTAX      Ipv6Address
   MAX-ACCESS  read-write
   STATUS      current
   DESCRIPTION
      "Path: efm.editConf.ipV6.dhcp.relay.destinations.address

       ipv6 address"
   ::= {er1646v2XEfmIpV6DhcpRelayDestinationsEntry 16777216}

er1646v2XEfmIpV6DhcpRelayDestinationsInterface OBJECT-TYPE
   SYNTAX      DisplayString
   MAX-ACCESS  read-write
   STATUS      current
   DESCRIPTION
      "Path: efm.editConf.ipV6.dhcp.relay.destinations.interface"
   ::= {er1646v2XEfmIpV6DhcpRelayDestinationsEntry 33554432}


er1646v2XEfmIbw OBJECT IDENTIFIER ::= {er1646v2XEfm 13}

er1646v2XEfmIbwSSC OBJECT IDENTIFIER ::= {er1646v2XEfmIbw 1}

er1646v2XEfmIbwEntry OBJECT IDENTIFIER ::= {er1646v2XEfmIbwSSC 1}

er1646v2XEfmIbwMode OBJECT-TYPE
   SYNTAX      INTEGER
               {
               reshaping (1),
               policing (2)
               }
   MAX-ACCESS  read-write
   STATUS      current
   DESCRIPTION
      "Path: efm.editConf.inboundBandwidth.mode

       Possibilities:
               reshaping   (1)
               policing   (2)"
   ::= {er1646v2XEfmIbwEntry 3758096384}

er1646v2XEfmIbwCir OBJECT-TYPE
   SYNTAX      Integer32
   MAX-ACCESS  read-write
   STATUS      current
   DESCRIPTION
      "Path: efm.editConf.inboundBandwidth.cir"
   ::= {er1646v2XEfmIbwEntry 268435456}

er1646v2XEfmIbwEir OBJECT-TYPE
   SYNTAX      Integer32
   MAX-ACCESS  read-write
   STATUS      current
   DESCRIPTION
      "Path: efm.editConf.inboundBandwidth.eir"
   ::= {er1646v2XEfmIbwEntry 1879048192}

er1646v2XEfmIbwUnit OBJECT-TYPE
   SYNTAX      INTEGER
               {
               bitssec (1),
               percent (2)
               }
   MAX-ACCESS  read-write
   STATUS      current
   DESCRIPTION
      "Path: efm.editConf.inboundBandwidth.unit

       Possibilities:
               bits/sec   (1)
               percent   (2)"
   ::= {er1646v2XEfmIbwEntry 1342177280}

er1646v2XEfmIbwTc OBJECT-TYPE
   SYNTAX      INTEGER
               {
               auto (0)
               }
   MAX-ACCESS  read-write
   STATUS      current
   DESCRIPTION
      "Path: efm.editConf.inboundBandwidth.tc

       Possibilities:
               auto   (0)"
   ::= {er1646v2XEfmIbwEntry 1610612736}

er1646v2XEfmIbwTcFactor OBJECT-TYPE
   SYNTAX      INTEGER
               {
               ms (10),
               s100us (1)
               }
   MAX-ACCESS  read-write
   STATUS      current
   DESCRIPTION
      "Path: efm.editConf.inboundBandwidth.tcFactor

       Possibilities:
               ms   (10)
               *100us   (1)"
   ::= {er1646v2XEfmIbwEntry 2147483648}

er1646v2XEfmIbwCorrType OBJECT-TYPE
   SYNTAX      INTEGER
               {
               noCorrection (0),
               predefined (1),
               manual (2)
               }
   MAX-ACCESS  read-write
   STATUS      current
   DESCRIPTION
      "Path: efm.editConf.inboundBandwidth.correction.type

       Possibilities:
               noCorrection   (0)
               predefined   (1)
               manual   (2)"
   ::= {er1646v2XEfmIbwEntry 570425344}

er1646v2XEfmIbwCorrPredefEncapsFrameRelay OBJECT-TYPE
   SYNTAX      DisplayString
   MAX-ACCESS  read-write
   STATUS      current
   DESCRIPTION
      "Path: efm.editConf.inboundBandwidth.correction.predefined.encapsulation.frameRelay"
   ::= {er1646v2XEfmIbwEntry 608436224}

er1646v2XEfmIbwCorrPredefEncapsPpp OBJECT-TYPE
   SYNTAX      DisplayString
   MAX-ACCESS  read-write
   STATUS      current
   DESCRIPTION
      "Path: efm.editConf.inboundBandwidth.correction.predefined.encapsulation.ppp"
   ::= {er1646v2XEfmIbwEntry 608698368}

er1646v2XEfmIbwCorrPredefEncapsAtmHl OBJECT-TYPE
   SYNTAX      INTEGER
               {
               rfc2684 (0),
               ppp (1),
               pppOverEthernet (2)
               }
   MAX-ACCESS  read-write
   STATUS      current
   DESCRIPTION
      "Path: efm.editConf.inboundBandwidth.correction.predefined.encapsulation.atm.higherLayer

       Possibilities:
               rfc2684   (0)
               ppp   (1)
               pppOverEthernet   (2)"
   ::= {er1646v2XEfmIbwEntry 608993280}

er1646v2XEfmIbwCorrPredefEncapsAtmMp OBJECT-TYPE
   SYNTAX      INTEGER
               {
               llcEncapsulation (0),
               vcMultiplexing (1)
               }
   MAX-ACCESS  read-write
   STATUS      current
   DESCRIPTION
      "Path: efm.editConf.inboundBandwidth.correction.predefined.encapsulation.atm.multiProtocol

       Possibilities:
               llcEncapsulation   (0)
               vcMultiplexing   (1)"
   ::= {er1646v2XEfmIbwEntry 609026048}

er1646v2XEfmIbwCorrPredefEncapsHdlc OBJECT-TYPE
   SYNTAX      DisplayString
   MAX-ACCESS  read-write
   STATUS      current
   DESCRIPTION
      "Path: efm.editConf.inboundBandwidth.correction.predefined.encapsulation.hdlc"
   ::= {er1646v2XEfmIbwEntry 609222656}

er1646v2XEfmIbwCorrPredefEncapsEfmFs OBJECT-TYPE
   SYNTAX      Integer32
   MAX-ACCESS  read-write
   STATUS      current
   DESCRIPTION
      "Path: efm.editConf.inboundBandwidth.correction.predefined.encapsulation.efm.fragmentSize"
   ::= {er1646v2XEfmIbwEntry 609517568}

er1646v2XEfmIbwCorrPredefEncapsEfmIb OBJECT-TYPE
   SYNTAX      Integer32
   MAX-ACCESS  read-write
   STATUS      current
   DESCRIPTION
      "Path: efm.editConf.inboundBandwidth.correction.predefined.encapsulation.efm.idleBytes"
   ::= {er1646v2XEfmIbwEntry 609550336}

er1646v2XEfmIbwCorrPredefMode OBJECT-TYPE
   SYNTAX      INTEGER
               {
               routing (0),
               bridging (1)
               }
   MAX-ACCESS  read-write
   STATUS      current
   DESCRIPTION
      "Path: efm.editConf.inboundBandwidth.correction.predefined.mode

       Possibilities:
               routing   (0)
               bridging   (1)"
   ::= {er1646v2XEfmIbwEntry 612368384}

er1646v2XEfmIbwCorrManualOverhead OBJECT-TYPE
   SYNTAX      Integer32
   MAX-ACCESS  read-write
   STATUS      current
   DESCRIPTION
      "Path: efm.editConf.inboundBandwidth.correction.manual.overhead"
   ::= {er1646v2XEfmIbwEntry 637665280}

er1646v2XEfmIbwCorrManualFrameData OBJECT-TYPE
   SYNTAX      Counter32
   MAX-ACCESS  read-write
   STATUS      current
   DESCRIPTION
      "Path: efm.editConf.inboundBandwidth.correction.manual.frameData

       32 bit unsigned wrappable counter."
   ::= {er1646v2XEfmIbwEntry 637796352}

er1646v2XEfmIbwCorrManualFrameHeader OBJECT-TYPE
   SYNTAX      Counter32
   MAX-ACCESS  read-write
   STATUS      current
   DESCRIPTION
      "Path: efm.editConf.inboundBandwidth.correction.manual.frameHeader

       32 bit unsigned wrappable counter."
   ::= {er1646v2XEfmIbwEntry 637927424}

er1646v2XEfmIbwMaxFifoQLen OBJECT-TYPE
   SYNTAX      Integer32
   MAX-ACCESS  read-write
   STATUS      current
   DESCRIPTION
      "Path: efm.editConf.inboundBandwidth.maxFifoQLen"
   ::= {er1646v2XEfmIbwEntry 805306368}

er1646v2XEfmIbwPriorityPolicy OBJECT-TYPE
   SYNTAX      DisplayString
   MAX-ACCESS  read-write
   STATUS      current
   DESCRIPTION
      "Path: efm.editConf.inboundBandwidth.priorityPolicy"
   ::= {er1646v2XEfmIbwEntry 1073741824}

er1646v2XEfmIbwDeFlagCir OBJECT-TYPE
   SYNTAX      INTEGER
               {
               allowed (1),
               notAllowed (2)
               }
   MAX-ACCESS  read-write
   STATUS      current
   DESCRIPTION
      "Path: efm.editConf.inboundBandwidth.deFlag.cir

       Possibilities:
               allowed   (1)
               notAllowed   (2)"
   ::= {er1646v2XEfmIbwEntry 3490709504}

er1646v2XEfmIbwDeFlagEir OBJECT-TYPE
   SYNTAX      INTEGER
               {
               allowed (1),
               notAllowed (2)
               }
   MAX-ACCESS  read-write
   STATUS      current
   DESCRIPTION
      "Path: efm.editConf.inboundBandwidth.deFlag.eir

       Possibilities:
               allowed   (1)
               notAllowed   (2)"
   ::= {er1646v2XEfmIbwEntry 3491758080}

er1646v2XEfmIbwDeFlagViolate OBJECT-TYPE
   SYNTAX      INTEGER
               {
               allowed (1),
               notAllowed (2)
               }
   MAX-ACCESS  read-write
   STATUS      current
   DESCRIPTION
      "Path: efm.editConf.inboundBandwidth.deFlag.violate

       Possibilities:
               allowed   (1)
               notAllowed   (2)"
   ::= {er1646v2XEfmIbwEntry 3492806656}

er1646v2XEfmIbwActCirActNone OBJECT-TYPE
   SYNTAX      OCTET STRING
   MAX-ACCESS  read-write
   STATUS      current
   DESCRIPTION
      "Path: efm.editConf.inboundBandwidth.action.cirAction.none"
   ::= {er1646v2XEfmIbwEntry 4062183424}

er1646v2XEfmIbwActCirActEthCos1 OBJECT-TYPE
   SYNTAX      INTEGER
               {
               unchanged (256)
               }
   MAX-ACCESS  read-write
   STATUS      current
   DESCRIPTION
      "Path: efm.editConf.inboundBandwidth.action.cirAction.ethernet.cosDepth1

       Possibilities:
               unchanged   (256)"
   ::= {er1646v2XEfmIbwEntry 4064346112}

er1646v2XEfmIbwActCirActEthDei1 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth1

       Possibilities:
               unchanged   (255)
               clear   (0)
               set   (1)"
   ::= {er1646v2XEfmIbwEntry 4065656832}

er1646v2XEfmIbwActCirActEthCos2 OBJECT-TYPE
   SYNTAX      INTEGER
               {
               unchanged (256)
               }
   MAX-ACCESS  read-write
   STATUS      current
   DESCRIPTION
      "Path: efm.editConf.inboundBandwidth.action.cirAction.ethernet.cosDepth2

       Possibilities:
               unchanged   (256)"
   ::= {er1646v2XEfmIbwEntry 4064411648}

er1646v2XEfmIbwActCirActEthDei2 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth2

       Possibilities:
               unchanged   (255)
               clear   (0)
               set   (1)"
   ::= {er1646v2XEfmIbwEntry 4065722368}

er1646v2XEfmIbwActCirActEthCos3 OBJECT-TYPE
   SYNTAX      INTEGER
               {
               unchanged (256)
               }
   MAX-ACCESS  read-write
   STATUS      current
   DESCRIPTION
      "Path: efm.editConf.inboundBandwidth.action.cirAction.ethernet.cosDepth3

       Possibilities:
               unchanged   (256)"
   ::= {er1646v2XEfmIbwEntry 4064477184}

er1646v2XEfmIbwActCirActEthDei3 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth3

       Possibilities:
               unchanged   (255)
               clear   (0)
               set   (1)"
   ::= {er1646v2XEfmIbwEntry 4065787904}

er1646v2XEfmIbwActCirActEthCos4 OBJECT-TYPE
   SYNTAX      INTEGER
               {
               unchanged (256)
               }
   MAX-ACCESS  read-write
   STATUS      current
   DESCRIPTION
      "Path: efm.editConf.inboundBandwidth.action.cirAction.ethernet.cosDepth4

       Possibilities:
               unchanged   (256)"
   ::= {er1646v2XEfmIbwEntry 4064542720}

er1646v2XEfmIbwActCirActEthDei4 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth4

       Possibilities:
               unchanged   (255)
               clear   (0)
               set   (1)"
   ::= {er1646v2XEfmIbwEntry 4065853440}

er1646v2XEfmIbwActCirActEthCos5 OBJECT-TYPE
   SYNTAX      INTEGER
               {
               unchanged (256)
               }
   MAX-ACCESS  read-write
   STATUS      current
   DESCRIPTION
      "Path: efm.editConf.inboundBandwidth.action.cirAction.ethernet.cosDepth5

       Possibilities:
               unchanged   (256)"
   ::= {er1646v2XEfmIbwEntry 4064608256}

er1646v2XEfmIbwActCirActEthDei5 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth5

       Possibilities:
               unchanged   (255)
               clear   (0)
               set   (1)"
   ::= {er1646v2XEfmIbwEntry 4065918976}

er1646v2XEfmIbwActCirActEthCos6 OBJECT-TYPE
   SYNTAX      INTEGER
               {
               unchanged (256)
               }
   MAX-ACCESS  read-write
   STATUS      current
   DESCRIPTION
      "Path: efm.editConf.inboundBandwidth.action.cirAction.ethernet.cosDepth6

       Possibilities:
               unchanged   (256)"
   ::= {er1646v2XEfmIbwEntry 4064673792}

er1646v2XEfmIbwActCirActEthDei6 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth6

       Possibilities:
               unchanged   (255)
               clear   (0)
               set   (1)"
   ::= {er1646v2XEfmIbwEntry 4065984512}

er1646v2XEfmIbwActCirActEthCos7 OBJECT-TYPE
   SYNTAX      INTEGER
               {
               unchanged (256)
               }
   MAX-ACCESS  read-write
   STATUS      current
   DESCRIPTION
      "Path: efm.editConf.inboundBandwidth.action.cirAction.ethernet.cosDepth7

       Possibilities:
               unchanged   (256)"
   ::= {er1646v2XEfmIbwEntry 4064739328}

er1646v2XEfmIbwActCirActEthDei7 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth7

       Possibilities:
               unchanged   (255)
               clear   (0)
               set   (1)"
   ::= {er1646v2XEfmIbwEntry 4066050048}

er1646v2XEfmIbwActCirActEthCos8 OBJECT-TYPE
   SYNTAX      INTEGER
               {
               unchanged (256)
               }
   MAX-ACCESS  read-write
   STATUS      current
   DESCRIPTION
      "Path: efm.editConf.inboundBandwidth.action.cirAction.ethernet.cosDepth8

       Possibilities:
               unchanged   (256)"
   ::= {er1646v2XEfmIbwEntry 4064804864}

er1646v2XEfmIbwActCirActEthDei8 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth8

       Possibilities:
               unchanged   (255)
               clear   (0)
               set   (1)"
   ::= {er1646v2XEfmIbwEntry 4066115584}

er1646v2XEfmIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4064870400}

er1646v2XEfmIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4064935936}

er1646v2XEfmIbwActCirActEthDrpLev OBJECT-TYPE
   SYNTAX      INTEGER
               {
               unchanged (0)
               }
   MAX-ACCESS  read-write
   STATUS      current
   DESCRIPTION
      "Path: efm.editConf.inboundBandwidth.action.cirAction.ethernet.dropLevel

       Possibilities:
               unchanged   (0)"
   ::= {er1646v2XEfmIbwEntry 4065001472}

er1646v2XEfmIbwActCirActEthDeFlag OBJECT-TYPE
   SYNTAX      INTEGER
               {
               unchanged (255),
               clear (0),
               set (1)
               }
   MAX-ACCESS  read-write
   STATUS      current
   DESCRIPTION
      "Path: efm.editConf.inboundBandwidth.action.cirAction.ethernet.deFlag

       Possibilities:
               unchanged   (255)
               clear   (0)
               set   (1)"
   ::= {er1646v2XEfmIbwEntry 4065198080}

er1646v2XEfmIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4071161856}

er1646v2XEfmIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4071227392}

er1646v2XEfmIbwActCirActIpDrpLev OBJECT-TYPE
   SYNTAX      INTEGER
               {
               unchanged (0)
               }
   MAX-ACCESS  read-write
   STATUS      current
   DESCRIPTION
      "Path: efm.editConf.inboundBandwidth.action.cirAction.ip.dropLevel

       Possibilities:
               unchanged   (0)"
   ::= {er1646v2XEfmIbwEntry 4071292928}

er1646v2XEfmIbwActCirActIpDeFlag OBJECT-TYPE
   SYNTAX      INTEGER
               {
               unchanged (255),
               clear (0),
               set (1)
               }
   MAX-ACCESS  read-write
   STATUS      current
   DESCRIPTION
      "Path: efm.editConf.inboundBandwidth.action.cirAction.ip.deFlag

       Possibilities:
               unchanged   (255)
               clear   (0)
               set   (1)"
   ::= {er1646v2XEfmIbwEntry 4071489536}

er1646v2XEfmIbwActEirActNone OBJECT-TYPE
   SYNTAX      OCTET STRING
   MAX-ACCESS  read-write
   STATUS      current
   DESCRIPTION
      "Path: efm.editConf.inboundBandwidth.action.eirAction.none"
   ::= {er1646v2XEfmIbwEntry 4095737856}

er1646v2XEfmIbwActEirActEthCos1 OBJECT-TYPE
   SYNTAX      INTEGER
               {
               unchanged (256)
               }
   MAX-ACCESS  read-write
   STATUS      current
   DESCRIPTION
      "Path: efm.editConf.inboundBandwidth.action.eirAction.ethernet.cosDepth1

       Possibilities:
               unchanged   (256)"
   ::= {er1646v2XEfmIbwEntry 4097900544}

er1646v2XEfmIbwActEirActEthDei1 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth1

       Possibilities:
               unchanged   (255)
               clear   (0)
               set   (1)"
   ::= {er1646v2XEfmIbwEntry 4099211264}

er1646v2XEfmIbwActEirActEthCos2 OBJECT-TYPE
   SYNTAX      INTEGER
               {
               unchanged (256)
               }
   MAX-ACCESS  read-write
   STATUS      current
   DESCRIPTION
      "Path: efm.editConf.inboundBandwidth.action.eirAction.ethernet.cosDepth2

       Possibilities:
               unchanged   (256)"
   ::= {er1646v2XEfmIbwEntry 4097966080}

er1646v2XEfmIbwActEirActEthDei2 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth2

       Possibilities:
               unchanged   (255)
               clear   (0)
               set   (1)"
   ::= {er1646v2XEfmIbwEntry 4099276800}

er1646v2XEfmIbwActEirActEthCos3 OBJECT-TYPE
   SYNTAX      INTEGER
               {
               unchanged (256)
               }
   MAX-ACCESS  read-write
   STATUS      current
   DESCRIPTION
      "Path: efm.editConf.inboundBandwidth.action.eirAction.ethernet.cosDepth3

       Possibilities:
               unchanged   (256)"
   ::= {er1646v2XEfmIbwEntry 4098031616}

er1646v2XEfmIbwActEirActEthDei3 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth3

       Possibilities:
               unchanged   (255)
               clear   (0)
               set   (1)"
   ::= {er1646v2XEfmIbwEntry 4099342336}

er1646v2XEfmIbwActEirActEthCos4 OBJECT-TYPE
   SYNTAX      INTEGER
               {
               unchanged (256)
               }
   MAX-ACCESS  read-write
   STATUS      current
   DESCRIPTION
      "Path: efm.editConf.inboundBandwidth.action.eirAction.ethernet.cosDepth4

       Possibilities:
               unchanged   (256)"
   ::= {er1646v2XEfmIbwEntry 4098097152}

er1646v2XEfmIbwActEirActEthDei4 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth4

       Possibilities:
               unchanged   (255)
               clear   (0)
               set   (1)"
   ::= {er1646v2XEfmIbwEntry 4099407872}

er1646v2XEfmIbwActEirActEthCos5 OBJECT-TYPE
   SYNTAX      INTEGER
               {
               unchanged (256)
               }
   MAX-ACCESS  read-write
   STATUS      current
   DESCRIPTION
      "Path: efm.editConf.inboundBandwidth.action.eirAction.ethernet.cosDepth5

       Possibilities:
               unchanged   (256)"
   ::= {er1646v2XEfmIbwEntry 4098162688}

er1646v2XEfmIbwActEirActEthDei5 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth5

       Possibilities:
               unchanged   (255)
               clear   (0)
               set   (1)"
   ::= {er1646v2XEfmIbwEntry 4099473408}

er1646v2XEfmIbwActEirActEthCos6 OBJECT-TYPE
   SYNTAX      INTEGER
               {
               unchanged (256)
               }
   MAX-ACCESS  read-write
   STATUS      current
   DESCRIPTION
      "Path: efm.editConf.inboundBandwidth.action.eirAction.ethernet.cosDepth6

       Possibilities:
               unchanged   (256)"
   ::= {er1646v2XEfmIbwEntry 4098228224}

er1646v2XEfmIbwActEirActEthDei6 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth6

       Possibilities:
               unchanged   (255)
               clear   (0)
               set   (1)"
   ::= {er1646v2XEfmIbwEntry 4099538944}

er1646v2XEfmIbwActEirActEthCos7 OBJECT-TYPE
   SYNTAX      INTEGER
               {
               unchanged (256)
               }
   MAX-ACCESS  read-write
   STATUS      current
   DESCRIPTION
      "Path: efm.editConf.inboundBandwidth.action.eirAction.ethernet.cosDepth7

       Possibilities:
               unchanged   (256)"
   ::= {er1646v2XEfmIbwEntry 4098293760}

er1646v2XEfmIbwActEirActEthDei7 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth7

       Possibilities:
               unchanged   (255)
               clear   (0)
               set   (1)"
   ::= {er1646v2XEfmIbwEntry 4099604480}

er1646v2XEfmIbwActEirActEthCos8 OBJECT-TYPE
   SYNTAX      INTEGER
               {
               unchanged (256)
               }
   MAX-ACCESS  read-write
   STATUS      current
   DESCRIPTION
      "Path: efm.editConf.inboundBandwidth.action.eirAction.ethernet.cosDepth8

       Possibilities:
               unchanged   (256)"
   ::= {er1646v2XEfmIbwEntry 4098359296}

er1646v2XEfmIbwActEirActEthDei8 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth8

       Possibilities:
               unchanged   (255)
               clear   (0)
               set   (1)"
   ::= {er1646v2XEfmIbwEntry 4099670016}

er1646v2XEfmIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4098424832}

er1646v2XEfmIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4098490368}

er1646v2XEfmIbwActEirActEthDrpLev OBJECT-TYPE
   SYNTAX      INTEGER
               {
               unchanged (0)
               }
   MAX-ACCESS  read-write
   STATUS      current
   DESCRIPTION
      "Path: efm.editConf.inboundBandwidth.action.eirAction.ethernet.dropLevel

       Possibilities:
               unchanged   (0)"
   ::= {er1646v2XEfmIbwEntry 4098555904}

er1646v2XEfmIbwActEirActEthDeFlag OBJECT-TYPE
   SYNTAX      INTEGER
               {
               unchanged (255),
               clear (0),
               set (1)
               }
   MAX-ACCESS  read-write
   STATUS      current
   DESCRIPTION
      "Path: efm.editConf.inboundBandwidth.action.eirAction.ethernet.deFlag

       Possibilities:
               unchanged   (255)
               clear   (0)
               set   (1)"
   ::= {er1646v2XEfmIbwEntry 4098752512}

er1646v2XEfmIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4104716288}

er1646v2XEfmIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4104781824}

er1646v2XEfmIbwActEirActIpDrpLev OBJECT-TYPE
   SYNTAX      INTEGER
               {
               unchanged (0)
               }
   MAX-ACCESS  read-write
   STATUS      current
   DESCRIPTION
      "Path: efm.editConf.inboundBandwidth.action.eirAction.ip.dropLevel

       Possibilities:
               unchanged   (0)"
   ::= {er1646v2XEfmIbwEntry 4104847360}

er1646v2XEfmIbwActEirActIpDeFlag OBJECT-TYPE
   SYNTAX      INTEGER
               {
               unchanged (255),
               clear (0),
               set (1)
               }
   MAX-ACCESS  read-write
   STATUS      current
   DESCRIPTION
      "Path: efm.editConf.inboundBandwidth.action.eirAction.ip.deFlag

       Possibilities:
               unchanged   (255)
               clear   (0)
               set   (1)"
   ::= {er1646v2XEfmIbwEntry 4105043968}

er1646v2XEfmIbwActViolActNone OBJECT-TYPE
   SYNTAX      OCTET STRING
   MAX-ACCESS  read-write
   STATUS      current
   DESCRIPTION
      "Path: efm.editConf.inboundBandwidth.action.violateAction.none"
   ::= {er1646v2XEfmIbwEntry 4129292288}

er1646v2XEfmIbwActViolActDrop OBJECT-TYPE
   SYNTAX      OCTET STRING
   MAX-ACCESS  read-write
   STATUS      current
   DESCRIPTION
      "Path: efm.editConf.inboundBandwidth.action.violateAction.drop"
   ::= {er1646v2XEfmIbwEntry 4133486592}

er1646v2XEfmIbwActViolActEthCos1 OBJECT-TYPE
   SYNTAX      INTEGER
               {
               unchanged (256)
               }
   MAX-ACCESS  read-write
   STATUS      current
   DESCRIPTION
      "Path: efm.editConf.inboundBandwidth.action.violateAction.ethernet.cosDepth1

       Possibilities:
               unchanged   (256)"
   ::= {er1646v2XEfmIbwEntry 4131454976}

er1646v2XEfmIbwActViolActEthDei1 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth1

       Possibilities:
               unchanged   (255)
               clear   (0)
               set   (1)"
   ::= {er1646v2XEfmIbwEntry 4132765696}

er1646v2XEfmIbwActViolActEthCos2 OBJECT-TYPE
   SYNTAX      INTEGER
               {
               unchanged (256)
               }
   MAX-ACCESS  read-write
   STATUS      current
   DESCRIPTION
      "Path: efm.editConf.inboundBandwidth.action.violateAction.ethernet.cosDepth2

       Possibilities:
               unchanged   (256)"
   ::= {er1646v2XEfmIbwEntry 4131520512}

er1646v2XEfmIbwActViolActEthDei2 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth2

       Possibilities:
               unchanged   (255)
               clear   (0)
               set   (1)"
   ::= {er1646v2XEfmIbwEntry 4132831232}

er1646v2XEfmIbwActViolActEthCos3 OBJECT-TYPE
   SYNTAX      INTEGER
               {
               unchanged (256)
               }
   MAX-ACCESS  read-write
   STATUS      current
   DESCRIPTION
      "Path: efm.editConf.inboundBandwidth.action.violateAction.ethernet.cosDepth3

       Possibilities:
               unchanged   (256)"
   ::= {er1646v2XEfmIbwEntry 4131586048}

er1646v2XEfmIbwActViolActEthDei3 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth3

       Possibilities:
               unchanged   (255)
               clear   (0)
               set   (1)"
   ::= {er1646v2XEfmIbwEntry 4132896768}

er1646v2XEfmIbwActViolActEthCos4 OBJECT-TYPE
   SYNTAX      INTEGER
               {
               unchanged (256)
               }
   MAX-ACCESS  read-write
   STATUS      current
   DESCRIPTION
      "Path: efm.editConf.inboundBandwidth.action.violateAction.ethernet.cosDepth4

       Possibilities:
               unchanged   (256)"
   ::= {er1646v2XEfmIbwEntry 4131651584}

er1646v2XEfmIbwActViolActEthDei4 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth4

       Possibilities:
               unchanged   (255)
               clear   (0)
               set   (1)"
   ::= {er1646v2XEfmIbwEntry 4132962304}

er1646v2XEfmIbwActViolActEthCos5 OBJECT-TYPE
   SYNTAX      INTEGER
               {
               unchanged (256)
               }
   MAX-ACCESS  read-write
   STATUS      current
   DESCRIPTION
      "Path: efm.editConf.inboundBandwidth.action.violateAction.ethernet.cosDepth5

       Possibilities:
               unchanged   (256)"
   ::= {er1646v2XEfmIbwEntry 4131717120}

er1646v2XEfmIbwActViolActEthDei5 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth5

       Possibilities:
               unchanged   (255)
               clear   (0)
               set   (1)"
   ::= {er1646v2XEfmIbwEntry 4133027840}

er1646v2XEfmIbwActViolActEthCos6 OBJECT-TYPE
   SYNTAX      INTEGER
               {
               unchanged (256)
               }
   MAX-ACCESS  read-write
   STATUS      current
   DESCRIPTION
      "Path: efm.editConf.inboundBandwidth.action.violateAction.ethernet.cosDepth6

       Possibilities:
               unchanged   (256)"
   ::= {er1646v2XEfmIbwEntry 4131782656}

er1646v2XEfmIbwActViolActEthDei6 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth6

       Possibilities:
               unchanged   (255)
               clear   (0)
               set   (1)"
   ::= {er1646v2XEfmIbwEntry 4133093376}

er1646v2XEfmIbwActViolActEthCos7 OBJECT-TYPE
   SYNTAX      INTEGER
               {
               unchanged (256)
               }
   MAX-ACCESS  read-write
   STATUS      current
   DESCRIPTION
      "Path: efm.editConf.inboundBandwidth.action.violateAction.ethernet.cosDepth7

       Possibilities:
               unchanged   (256)"
   ::= {er1646v2XEfmIbwEntry 4131848192}

er1646v2XEfmIbwActViolActEthDei7 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth7

       Possibilities:
               unchanged   (255)
               clear   (0)
               set   (1)"
   ::= {er1646v2XEfmIbwEntry 4133158912}

er1646v2XEfmIbwActViolActEthCos8 OBJECT-TYPE
   SYNTAX      INTEGER
               {
               unchanged (256)
               }
   MAX-ACCESS  read-write
   STATUS      current
   DESCRIPTION
      "Path: efm.editConf.inboundBandwidth.action.violateAction.ethernet.cosDepth8

       Possibilities:
               unchanged   (256)"
   ::= {er1646v2XEfmIbwEntry 4131913728}

er1646v2XEfmIbwActViolActEthDei8 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth8

       Possibilities:
               unchanged   (255)
               clear   (0)
               set   (1)"
   ::= {er1646v2XEfmIbwEntry 4133224448}

er1646v2XEfmIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4131979264}

er1646v2XEfmIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4132044800}

er1646v2XEfmIbwActViolActEthDrpLev OBJECT-TYPE
   SYNTAX      INTEGER
               {
               unchanged (0)
               }
   MAX-ACCESS  read-write
   STATUS      current
   DESCRIPTION
      "Path: efm.editConf.inboundBandwidth.action.violateAction.ethernet.dropLevel

       Possibilities:
               unchanged   (0)"
   ::= {er1646v2XEfmIbwEntry 4132110336}

er1646v2XEfmIbwActViolActEthDeFlag OBJECT-TYPE
   SYNTAX      INTEGER
               {
               unchanged (255),
               clear (0),
               set (1)
               }
   MAX-ACCESS  read-write
   STATUS      current
   DESCRIPTION
      "Path: efm.editConf.inboundBandwidth.action.violateAction.ethernet.deFlag

       Possibilities:
               unchanged   (255)
               clear   (0)
               set   (1)"
   ::= {er1646v2XEfmIbwEntry 4132306944}

er1646v2XEfmIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2XEfmIbwEntry 4138270720}

er1646v2XEfmIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2XEfmIbwEntry 4138336256}

er1646v2XEfmIbwActViolActIpDrpLev OBJECT-TYPE
   SYNTAX      INTEGER
               {
               unchanged (0)
               }
   MAX-ACCESS  read-write
   STATUS      current
   DESCRIPTION
      "Path: efm.editConf.inboundBandwidth.action.violateAction.ip.dropLevel

       Possibilities:
               unchanged   (0)"
   ::= {er1646v2XEfmIbwEntry 4138401792}

er1646v2XEfmIbwActViolActIpDeFlag OBJECT-TYPE
   SYNTAX      INTEGER
               {
               unchanged (255),
               clear (0),
               set (1)
               }
   MAX-ACCESS  read-write
   STATUS      current
   DESCRIPTION
      "Path: efm.editConf.inboundBandwidth.action.violateAction.ip.deFlag

       Possibilities:
               unchanged   (255)
               clear   (0)
               set   (1)"
   ::= {er1646v2XEfmIbwEntry 4138598400}

er1646v2XEfmIbwSubInterfacesExcluded OBJECT-TYPE
   SYNTAX      INTEGER
               {
               s (1)
               }
   MAX-ACCESS  read-write
   STATUS      current
   DESCRIPTION
      "Path: efm.editConf.inboundBandwidth.subInterfaces.excluded

       Possibilities:
                  (1)"
   ::= {er1646v2XEfmIbwEntry 2416967680}

er1646v2XEfmIbwSubInterfacesIncludedInAccessList OBJECT-TYPE
   SYNTAX      DisplayString
   MAX-ACCESS  read-write
   STATUS      current
   DESCRIPTION
      "Path: efm.editConf.inboundBandwidth.subInterfaces.included.inAccessList"
   ::= {er1646v2XEfmIbwEntry 2418020352}



sr1646v2XEfm OBJECT IDENTIFIER ::= {r1646v2XEfm 14}


sr1646v2XEfmDescr OBJECT-TYPE
   SYNTAX      DisplayString
   MAX-ACCESS  read-only
   STATUS      current
   DESCRIPTION
      "Path: efm.status.ifDescr
       Info: ifDescr"
   ::= {sr1646v2XEfm 101}


sr1646v2XEfmType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: efm.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2XEfm 102}


sr1646v2XEfmMtu OBJECT-TYPE
   SYNTAX      Integer32
   MAX-ACCESS  read-only
   STATUS      current
   DESCRIPTION
      "Path: efm.status.ifMtu
       Info: ifMtu"
   ::= {sr1646v2XEfm 103}


sr1646v2XEfmOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.ifOperStatus
       Info: ifOperStatus

       Possibilities:
               up   (1)
               down   (2)
               testing   (3)
               unknown   (4)
               dormant   (5)
               notPresent   (6)
               lowerLayerDown   (7)"
   ::= {sr1646v2XEfm 107}


sr1646v2XEfmLastChange OBJECT-TYPE
   SYNTAX      TimeTicks
   MAX-ACCESS  read-only
   STATUS      current
   DESCRIPTION
      "Path: efm.status.ifLastChange
       Info: ifLastChange

       Time in centi-second."
   ::= {sr1646v2XEfm 108}


sr1646v2XEfmLastChangeD OBJECT-TYPE
   SYNTAX      DisplayString
   MAX-ACCESS  read-only
   STATUS      current
   DESCRIPTION
      "Path: efm.status.ifLastChangeDate
       Info: ifLastChangeDate"
   ::= {sr1646v2XEfm 183}


sr1646v2XEfmSpeed OBJECT-TYPE
   SYNTAX      Gauge32
   MAX-ACCESS  read-only
   STATUS      current
   DESCRIPTION
      "Path: efm.status.ifSpeed
       Info: ifSpeed

       32 bit unsigned gauge value."
   ::= {sr1646v2XEfm 104}


sr1646v2XEfmIp OBJECT IDENTIFIER ::= {sr1646v2XEfm 16}

sr1646v2XEfmIpSSC OBJECT IDENTIFIER ::= {sr1646v2XEfmIp 1}

sr1646v2XEfmIpEntry OBJECT IDENTIFIER ::= {sr1646v2XEfmIpSSC 1}

sr1646v2XEfmIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.ip.status

       Possibilities:
               up   (1)
               down   (2)
               testing   (3)
               unknown   (4)
               dormant   (5)
               notPresent   (6)
               lowerLayerDown   (7)"
   ::= {sr1646v2XEfmIpEntry 1795162112}

sr1646v2XEfmIpAddress OBJECT-TYPE
   SYNTAX      IpAddress
   MAX-ACCESS  read-only
   STATUS      current
   DESCRIPTION
      "Path: efm.status.ip.address"
   ::= {sr1646v2XEfmIpEntry 2030043136}

sr1646v2XEfmIpNetMask OBJECT-TYPE
   SYNTAX      IpAddress
   MAX-ACCESS  read-only
   STATUS      current
   DESCRIPTION
      "Path: efm.status.ip.netMask"
   ::= {sr1646v2XEfmIpEntry 2063597568}

sr1646v2XEfmIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: efm.status.ip.dhcp.status

       Possibilities:
               none   (0)
               selecting   (1)
               requesting   (2)
               rebinding   (3)
               bound   (4)
               renewing   (5)
               rebooting   (6)
               initreboot   (7)"
   ::= {sr1646v2XEfmIpEntry 402718720}

sr1646v2XEfmIpDhcpLeaseTime OBJECT-TYPE
   SYNTAX      TimeTicks
   MAX-ACCESS  read-only
   STATUS      current
   DESCRIPTION
      "Path: efm.status.ip.dhcp.leaseTime

       Time in centi-second."
   ::= {sr1646v2XEfmIpEntry 402784256}

sr1646v2XEfmIpSecondaryIp OBJECT-TYPE
   SYNTAX      SEQUENCE OF Sr1646v2XEfmIpSecondaryIpEntry
   MAX-ACCESS  not-accessible
   STATUS      current
   DESCRIPTION
      ""
   ::= {sr1646v2XEfmIp 385875968}

sr1646v2XEfmIpSecondaryIpEntry OBJECT-TYPE
   SYNTAX      Sr1646v2XEfmIpSecondaryIpEntry
   MAX-ACCESS  not-accessible
   STATUS      current
   DESCRIPTION
      ""
   INDEX      { sr1646v2XEfmIpSecondaryIpTableIx }
   ::= {sr1646v2XEfmIpSecondaryIp 1}

Sr1646v2XEfmIpSecondaryIpEntry ::=
   SEQUENCE
      {
      sr1646v2XEfmIpSecondaryIpTableIx
         TableIndex,
      sr1646v2XEfmIpSecondaryIpAddress
         IpAddress,
      sr1646v2XEfmIpSecondaryIpNetMask
         IpAddress
      }

sr1646v2XEfmIpSecondaryIpTableIx OBJECT-TYPE
   SYNTAX      TableIndex
   MAX-ACCESS  not-accessible
   STATUS      current
   DESCRIPTION
      ""
   ::= {sr1646v2XEfmIpSecondaryIpEntry 11}

sr1646v2XEfmIpSecondaryIpAddress OBJECT-TYPE
   SYNTAX      IpAddress
   MAX-ACCESS  read-only
   STATUS      current
   DESCRIPTION
      "Path: efm.status.ip.secondaryIp.address"
   ::= {sr1646v2XEfmIpSecondaryIpEntry 2030043136}

sr1646v2XEfmIpSecondaryIpNetMask OBJECT-TYPE
   SYNTAX      IpAddress
   MAX-ACCESS  read-only
   STATUS      current
   DESCRIPTION
      "Path: efm.status.ip.secondaryIp.netMask"
   ::= {sr1646v2XEfmIpSecondaryIpEntry 2063597568}


sr1646v2XEfmArpCache OBJECT IDENTIFIER ::= {sr1646v2XEfm 11}

sr1646v2XEfmArpCacheSSCTable OBJECT-TYPE
   SYNTAX      SEQUENCE OF Sr1646v2XEfmArpCacheEntry
   MAX-ACCESS  not-accessible
   STATUS      current
   DESCRIPTION
      "arp cache of ethernet interface"
   ::= {sr1646v2XEfmArpCache 1}

sr1646v2XEfmArpCacheEntry OBJECT-TYPE
   SYNTAX      Sr1646v2XEfmArpCacheEntry
   MAX-ACCESS  not-accessible
   STATUS      current
   DESCRIPTION
      ""
   INDEX      { sr1646v2XEfmArpCacheTableIx }
   ::= {sr1646v2XEfmArpCacheSSCTable 1}

Sr1646v2XEfmArpCacheEntry ::=
   SEQUENCE
      {
      sr1646v2XEfmArpCacheTableIx
         TableIndex,
      sr1646v2XEfmArpCacheMacAddress
         OCTET STRING,
      sr1646v2XEfmArpCacheIpAddress
         IpAddress,
      sr1646v2XEfmArpCacheType
         INTEGER,
      sr1646v2XEfmArpCacheTimeOut
         TimeTicks
      }

sr1646v2XEfmArpCacheTableIx OBJECT-TYPE
   SYNTAX      TableIndex
   MAX-ACCESS  not-accessible
   STATUS      current
   DESCRIPTION
      ""
   ::= {sr1646v2XEfmArpCacheEntry 11}

sr1646v2XEfmArpCacheMacAddress OBJECT-TYPE
   SYNTAX      OCTET STRING
   MAX-ACCESS  read-only
   STATUS      current
   DESCRIPTION
      "Path: efm.status.arpCache.macAddress

       MAC address."
   ::= {sr1646v2XEfmArpCacheEntry 16777216}

sr1646v2XEfmArpCacheIpAddress OBJECT-TYPE
   SYNTAX      IpAddress
   MAX-ACCESS  read-only
   STATUS      current
   DESCRIPTION
      "Path: efm.status.arpCache.ipAddress"
   ::= {sr1646v2XEfmArpCacheEntry 33554432}

sr1646v2XEfmArpCacheType OBJECT-TYPE
   SYNTAX      INTEGER
               {
               static (0),
               dynamic (1)
               }
   MAX-ACCESS  read-only
   STATUS      current
   DESCRIPTION
      "Path: efm.status.arpCache.type

       Possibilities:
               static   (0)
               dynamic   (1)"
   ::= {sr1646v2XEfmArpCacheEntry 50331648}

sr1646v2XEfmArpCacheTimeOut OBJECT-TYPE
   SYNTAX      TimeTicks
   MAX-ACCESS  read-only
   STATUS      current
   DESCRIPTION
      "Path: efm.status.arpCache.timeOut

       Time in centi-second."
   ::= {sr1646v2XEfmArpCacheEntry 67108864}


sr1646v2XEfmBrS OBJECT IDENTIFIER ::= {sr1646v2XEfm 28}

sr1646v2XEfmBrSSSC OBJECT IDENTIFIER ::= {sr1646v2XEfmBrS 1}

sr1646v2XEfmBrSEntry OBJECT IDENTIFIER ::= {sr1646v2XEfmBrSSSC 1}

sr1646v2XEfmBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: efm.status.bridging.status

       Possibilities:
               disabled   (0)
               discarding   (1)
               learning   (2)
               forwarding   (3)
               backupBlockedIntfDown   (256)
               backupBlockedIntfUp   (259)
               shutdown   (255)"
   ::= {sr1646v2XEfmBrSEntry 16777216}

sr1646v2XEfmBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: efm.status.bridging.spanningTree.portRole

       Possibilities:
               none   (0)
               root   (1)
               designated   (2)
               alternate   (3)
               backup   (4)
               disabled   (5)
               master   (6)"
   ::= {sr1646v2XEfmBrSEntry 33619968}

sr1646v2XEfmBrSStPortId OBJECT-TYPE
   SYNTAX      Integer32
   MAX-ACCESS  read-only
   STATUS      current
   DESCRIPTION
      "Path: efm.status.bridging.spanningTree.portId"
   ::= {sr1646v2XEfmBrSEntry 33685504}

sr1646v2XEfmBrSStPpCostExtPathCost OBJECT-TYPE
   SYNTAX      Integer32
   MAX-ACCESS  read-only
   STATUS      current
   DESCRIPTION
      "Path: efm.status.bridging.spanningTree.portPathCosts.extPathCost"
   ::= {sr1646v2XEfmBrSEntry 33751296}

sr1646v2XEfmBrSStPpCostIntPathCost OBJECT-TYPE
   SYNTAX      Integer32
   MAX-ACCESS  read-only
   STATUS      current
   DESCRIPTION
      "Path: efm.status.bridging.spanningTree.portPathCosts.intPathCost"
   ::= {sr1646v2XEfmBrSEntry 33751552}

sr1646v2XEfmBrSStExtRpCost OBJECT-TYPE
   SYNTAX      Integer32
   MAX-ACCESS  read-only
   STATUS      current
   DESCRIPTION
      "Path: efm.status.bridging.spanningTree.extRootPathCost"
   ::= {sr1646v2XEfmBrSEntry 33816576}

sr1646v2XEfmBrSStIntRpCost OBJECT-TYPE
   SYNTAX      Integer32
   MAX-ACCESS  read-only
   STATUS      current
   DESCRIPTION
      "Path: efm.status.bridging.spanningTree.intRootPathCost"
   ::= {sr1646v2XEfmBrSEntry 33882112}

sr1646v2XEfmBrSStDesBrIdPriority OBJECT-TYPE
   SYNTAX      Integer32
   MAX-ACCESS  read-only
   STATUS      current
   DESCRIPTION
      "Path: efm.status.bridging.spanningTree.designatedBridgeId.priority"
   ::= {sr1646v2XEfmBrSEntry 33947904}

sr1646v2XEfmBrSStDesBrIdMacAddress OBJECT-TYPE
   SYNTAX      OCTET STRING
   MAX-ACCESS  read-only
   STATUS      current
   DESCRIPTION
      "Path: efm.status.bridging.spanningTree.designatedBridgeId.macAddress

       MAC address."
   ::= {sr1646v2XEfmBrSEntry 33948160}

sr1646v2XEfmBrSStDesPrtId OBJECT-TYPE
   SYNTAX      Integer32
   MAX-ACCESS  read-only
   STATUS      current
   DESCRIPTION
      "Path: efm.status.bridging.spanningTree.designatedPortId"
   ::= {sr1646v2XEfmBrSEntry 34013184}

sr1646v2XEfmBrSStDesInt OBJECT-TYPE
   SYNTAX      INTEGER
               {
               no (0),
               yes (1)
               }
   MAX-ACCESS  read-only
   STATUS      current
   DESCRIPTION
      "Path: efm.status.bridging.spanningTree.designatedOrInternal

       Possibilities:
               no   (0)
               yes   (1)"
   ::= {sr1646v2XEfmBrSEntry 34078720}

sr1646v2XEfmBrSStEdgeDetection OBJECT-TYPE
   SYNTAX      INTEGER
               {
               none (0),
               edge (1),
               notEdge (2)
               }
   MAX-ACCESS  read-only
   STATUS      current
   DESCRIPTION
      "Path: efm.status.bridging.spanningTree.edgeDetection

       Possibilities:
               none   (0)
               edge   (1)
               notEdge   (2)"
   ::= {sr1646v2XEfmBrSEntry 34144256}


sr1646v2XEfmMacAddress OBJECT-TYPE
   SYNTAX      OCTET STRING
   MAX-ACCESS  read-only
   STATUS      current
   DESCRIPTION
      "Path: efm.status.macAddress
       Info: ifPhysAddress

       MAC address."
   ::= {sr1646v2XEfm 105}


sr1646v2XEfmIpAdEntBcastAddr OBJECT-TYPE
   SYNTAX      Integer32
   MAX-ACCESS  read-only
   STATUS      current
   DESCRIPTION
      "Path: efm.status.ipAdEntBcastAddr
       Info: ipAdEntBcastAddr"
   ::= {sr1646v2XEfm 124}


sr1646v2XEfmIpAdEntReasmMaxSize OBJECT-TYPE
   SYNTAX      Integer32
   MAX-ACCESS  read-only
   STATUS      current
   DESCRIPTION
      "Path: efm.status.ipAdEntReasmMaxSize
       Info: ipAdEntReasmMaxSize"
   ::= {sr1646v2XEfm 125}


sr1646v2XEfmOam OBJECT IDENTIFIER ::= {sr1646v2XEfm 901}

sr1646v2XEfmOamSSC OBJECT IDENTIFIER ::= {sr1646v2XEfmOam 1}

sr1646v2XEfmOamEntry OBJECT IDENTIFIER ::= {sr1646v2XEfmOamSSC 1}

sr1646v2XEfmOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: efm.status.oam.discovery

       Possibilities:
               fault   (0)
               sendLocal   (1)
               passiveWait   (2)
               sendLocalRemote   (3)
               sendLocalRemoteOk   (4)
               sendAny   (5)"
   ::= {sr1646v2XEfmOamEntry 16777216}

sr1646v2XEfmOamLoopback OBJECT-TYPE
   SYNTAX      INTEGER
               {
               idle (0),
               waiting (1),
               localRunning (2),
               remoteRunning (3)
               }
   MAX-ACCESS  read-only
   STATUS      current
   DESCRIPTION
      "Path: efm.status.oam.loopback

       Possibilities:
               idle   (0)
               waiting   (1)
               localRunning   (2)
               remoteRunning   (3)"
   ::= {sr1646v2XEfmOamEntry 33554432}

sr1646v2XEfmOamLocalInfoVersion OBJECT-TYPE
   SYNTAX      Integer32
   MAX-ACCESS  read-only
   STATUS      current
   DESCRIPTION
      "Path: efm.status.oam.localInfo.version"
   ::= {sr1646v2XEfmOamEntry 50397184}

sr1646v2XEfmOamLocalInfoRevision OBJECT-TYPE
   SYNTAX      Integer32
   MAX-ACCESS  read-only
   STATUS      current
   DESCRIPTION
      "Path: efm.status.oam.localInfo.revision"
   ::= {sr1646v2XEfmOamEntry 50462720}

sr1646v2XEfmOamLocalInfoStateMuxAction OBJECT-TYPE
   SYNTAX      INTEGER
               {
               forwarding (0),
               discarding (1)
               }
   MAX-ACCESS  read-only
   STATUS      current
   DESCRIPTION
      "Path: efm.status.oam.localInfo.state.muxAction

       Possibilities:
               forwarding   (0)
               discarding   (1)"
   ::= {sr1646v2XEfmOamEntry 50528512}

sr1646v2XEfmOamLocalInfoStateParserAction OBJECT-TYPE
   SYNTAX      INTEGER
               {
               forwarding (0),
               loopback (1),
               discarding (2),
               reserved (3)
               }
   MAX-ACCESS  read-only
   STATUS      current
   DESCRIPTION
      "Path: efm.status.oam.localInfo.state.parserAction

       Possibilities:
               forwarding   (0)
               loopback   (1)
               discarding   (2)
               reserved   (3)"
   ::= {sr1646v2XEfmOamEntry 50528768}

sr1646v2XEfmOamLocalInfoOui OBJECT-TYPE
   SYNTAX      OCTET STRING
   MAX-ACCESS  read-only
   STATUS      current
   DESCRIPTION
      "Path: efm.status.oam.localInfo.oui"
   ::= {sr1646v2XEfmOamEntry 50593792}

sr1646v2XEfmOamLocalInfoVendorInfo OBJECT-TYPE
   SYNTAX      OCTET STRING
   MAX-ACCESS  read-only
   STATUS      current
   DESCRIPTION
      "Path: efm.status.oam.localInfo.vendorInfo"
   ::= {sr1646v2XEfmOamEntry 50659328}

sr1646v2XEfmOamLocalInfoVarRetrieval OBJECT-TYPE
   SYNTAX      INTEGER
               {
               notSupported (0),
               supported (1)
               }
   MAX-ACCESS  read-only
   STATUS      current
   DESCRIPTION
      "Path: efm.status.oam.localInfo.varRetrieval

       Possibilities:
               notSupported   (0)
               supported   (1)"
   ::= {sr1646v2XEfmOamEntry 50724864}

sr1646v2XEfmOamLocalInfoLinkEvents OBJECT-TYPE
   SYNTAX      INTEGER
               {
               ignored (0),
               interpreted (1)
               }
   MAX-ACCESS  read-only
   STATUS      current
   DESCRIPTION
      "Path: efm.status.oam.localInfo.linkEvents

       Possibilities:
               ignored   (0)
               interpreted   (1)"
   ::= {sr1646v2XEfmOamEntry 50790400}

sr1646v2XEfmOamLocalInfoLoopback OBJECT-TYPE
   SYNTAX      INTEGER
               {
               notSupported (0),
               supported (1)
               }
   MAX-ACCESS  read-only
   STATUS      current
   DESCRIPTION
      "Path: efm.status.oam.localInfo.loopback

       Possibilities:
               notSupported   (0)
               supported   (1)"
   ::= {sr1646v2XEfmOamEntry 50855936}

sr1646v2XEfmOamLocalInfoUnidirectional OBJECT-TYPE
   SYNTAX      INTEGER
               {
               notSupported (0),
               supported (1)
               }
   MAX-ACCESS  read-only
   STATUS      current
   DESCRIPTION
      "Path: efm.status.oam.localInfo.unidirectional

       Possibilities:
               notSupported   (0)
               supported   (1)"
   ::= {sr1646v2XEfmOamEntry 50921472}

sr1646v2XEfmOamLocalInfoMode OBJECT-TYPE
   SYNTAX      INTEGER
               {
               passive (0),
               active (1)
               }
   MAX-ACCESS  read-only
   STATUS      current
   DESCRIPTION
      "Path: efm.status.oam.localInfo.mode

       Possibilities:
               passive   (0)
               active   (1)"
   ::= {sr1646v2XEfmOamEntry 50987008}

sr1646v2XEfmOamLocalInfoMaxPduSize OBJECT-TYPE
   SYNTAX      Integer32
   MAX-ACCESS  read-only
   STATUS      current
   DESCRIPTION
      "Path: efm.status.oam.localInfo.maxPduSize"
   ::= {sr1646v2XEfmOamEntry 51052544}

sr1646v2XEfmOamRemoteInfoVersion OBJECT-TYPE
   SYNTAX      Integer32
   MAX-ACCESS  read-only
   STATUS      current
   DESCRIPTION
      "Path: efm.status.oam.remoteInfo.version"
   ::= {sr1646v2XEfmOamEntry 67174400}

sr1646v2XEfmOamRemoteInfoRevision OBJECT-TYPE
   SYNTAX      Integer32
   MAX-ACCESS  read-only
   STATUS      current
   DESCRIPTION
      "Path: efm.status.oam.remoteInfo.revision"
   ::= {sr1646v2XEfmOamEntry 67239936}

sr1646v2XEfmOamRemoteInfoStateMuxAction OBJECT-TYPE
   SYNTAX      INTEGER
               {
               forwarding (0),
               discarding (1)
               }
   MAX-ACCESS  read-only
   STATUS      current
   DESCRIPTION
      "Path: efm.status.oam.remoteInfo.state.muxAction

       Possibilities:
               forwarding   (0)
               discarding   (1)"
   ::= {sr1646v2XEfmOamEntry 67305728}

sr1646v2XEfmOamRemoteInfoStateParserAction OBJECT-TYPE
   SYNTAX      INTEGER
               {
               forwarding (0),
               loopback (1),
               discarding (2),
               reserved (3)
               }
   MAX-ACCESS  read-only
   STATUS      current
   DESCRIPTION
      "Path: efm.status.oam.remoteInfo.state.parserAction

       Possibilities:
               forwarding   (0)
               loopback   (1)
               discarding   (2)
               reserved   (3)"
   ::= {sr1646v2XEfmOamEntry 67305984}

sr1646v2XEfmOamRemoteInfoOui OBJECT-TYPE
   SYNTAX      OCTET STRING
   MAX-ACCESS  read-only
   STATUS      current
   DESCRIPTION
      "Path: efm.status.oam.remoteInfo.oui"
   ::= {sr1646v2XEfmOamEntry 67371008}

sr1646v2XEfmOamRemoteInfoVendorInfo OBJECT-TYPE
   SYNTAX      OCTET STRING
   MAX-ACCESS  read-only
   STATUS      current
   DESCRIPTION
      "Path: efm.status.oam.remoteInfo.vendorInfo"
   ::= {sr1646v2XEfmOamEntry 67436544}

sr1646v2XEfmOamRemoteInfoVarRetrieval OBJECT-TYPE
   SYNTAX      INTEGER
               {
               notSupported (0),
               supported (1)
               }
   MAX-ACCESS  read-only
   STATUS      current
   DESCRIPTION
      "Path: efm.status.oam.remoteInfo.varRetrieval

       Possibilities:
               notSupported   (0)
               supported   (1)"
   ::= {sr1646v2XEfmOamEntry 67502080}

sr1646v2XEfmOamRemoteInfoLinkEvents OBJECT-TYPE
   SYNTAX      INTEGER
               {
               ignored (0),
               interpreted (1)
               }
   MAX-ACCESS  read-only
   STATUS      current
   DESCRIPTION
      "Path: efm.status.oam.remoteInfo.linkEvents

       Possibilities:
               ignored   (0)
               interpreted   (1)"
   ::= {sr1646v2XEfmOamEntry 67567616}

sr1646v2XEfmOamRemoteInfoLoopback OBJECT-TYPE
   SYNTAX      INTEGER
               {
               notSupported (0),
               supported (1)
               }
   MAX-ACCESS  read-only
   STATUS      current
   DESCRIPTION
      "Path: efm.status.oam.remoteInfo.loopback

       Possibilities:
               notSupported   (0)
               supported   (1)"
   ::= {sr1646v2XEfmOamEntry 67633152}

sr1646v2XEfmOamRemoteInfoUnidirectional OBJECT-TYPE
   SYNTAX      INTEGER
               {
               notSupported (0),
               supported (1)
               }
   MAX-ACCESS  read-only
   STATUS      current
   DESCRIPTION
      "Path: efm.status.oam.remoteInfo.unidirectional

       Possibilities:
               notSupported   (0)
               supported   (1)"
   ::= {sr1646v2XEfmOamEntry 67698688}

sr1646v2XEfmOamRemoteInfoMode OBJECT-TYPE
   SYNTAX      INTEGER
               {
               passive (0),
               active (1)
               }
   MAX-ACCESS  read-only
   STATUS      current
   DESCRIPTION
      "Path: efm.status.oam.remoteInfo.mode

       Possibilities:
               passive   (0)
               active   (1)"
   ::= {sr1646v2XEfmOamEntry 67764224}

sr1646v2XEfmOamRemoteInfoMaxPduSize OBJECT-TYPE
   SYNTAX      Integer32
   MAX-ACCESS  read-only
   STATUS      current
   DESCRIPTION
      "Path: efm.status.oam.remoteInfo.maxPduSize"
   ::= {sr1646v2XEfmOamEntry 67829760}

sr1646v2XEfmOamEventsErroredSymbolWindow OBJECT-TYPE
   SYNTAX      Integer32
   UNITS       "symbols"
   MAX-ACCESS  read-only
   STATUS      current
   DESCRIPTION
      "Path: efm.status.oam.events.erroredSymbol.window

       unit name = symbols"
   ::= {sr1646v2XEfmOamEntry 83951872}

sr1646v2XEfmOamEventsErroredSymbolThreshold OBJECT-TYPE
   SYNTAX      OCTET STRING
   UNITS       "symbols"
   MAX-ACCESS  read-only
   STATUS      current
   DESCRIPTION
      "Path: efm.status.oam.events.erroredSymbol.threshold

       unit name = symbols"
   ::= {sr1646v2XEfmOamEntry 83952128}

sr1646v2XEfmOamEventsErroredFramePeriodWindow OBJECT-TYPE
   SYNTAX      INTEGER
               {
               default (0)
               }
   UNITS       "frames"
   MAX-ACCESS  read-only
   STATUS      current
   DESCRIPTION
      "Path: efm.status.oam.events.erroredFramePeriod.window

       unit name = frames

       Possibilities:
               default   (0)"
   ::= {sr1646v2XEfmOamEntry 84017408}

sr1646v2XEfmOamEventsErroredFramePeriodThreshold OBJECT-TYPE
   SYNTAX      Integer32
   UNITS       "frames"
   MAX-ACCESS  read-only
   STATUS      current
   DESCRIPTION
      "Path: efm.status.oam.events.erroredFramePeriod.threshold

       unit name = frames"
   ::= {sr1646v2XEfmOamEntry 84017664}

sr1646v2XEfmOamEventsErroredFrameWindow OBJECT-TYPE
   SYNTAX      Integer32
   UNITS       "100msec"
   MAX-ACCESS  read-only
   STATUS      current
   DESCRIPTION
      "Path: efm.status.oam.events.erroredFrame.window

       unit name = 100msec"
   ::= {sr1646v2XEfmOamEntry 84082944}

sr1646v2XEfmOamEventsErroredFrameThreshold OBJECT-TYPE
   SYNTAX      Integer32
   UNITS       "frames"
   MAX-ACCESS  read-only
   STATUS      current
   DESCRIPTION
      "Path: efm.status.oam.events.erroredFrame.threshold

       unit name = frames"
   ::= {sr1646v2XEfmOamEntry 84083200}

sr1646v2XEfmOamEventsErroredFrameSecondsWindow OBJECT-TYPE
   SYNTAX      Integer32
   UNITS       "100msec"
   MAX-ACCESS  read-only
   STATUS      current
   DESCRIPTION
      "Path: efm.status.oam.events.erroredFrameSeconds.window

       unit name = 100msec"
   ::= {sr1646v2XEfmOamEntry 84148480}

sr1646v2XEfmOamEventsErroredFrameSecondsThreshold OBJECT-TYPE
   SYNTAX      Integer32
   UNITS       "frames"
   MAX-ACCESS  read-only
   STATUS      current
   DESCRIPTION
      "Path: efm.status.oam.events.erroredFrameSeconds.threshold

       unit name = frames"
   ::= {sr1646v2XEfmOamEntry 84148736}


sr1646v2XEfmOamEventLog OBJECT IDENTIFIER ::= {sr1646v2XEfm 911}

sr1646v2XEfmOamEventLogSSCTable OBJECT-TYPE
   SYNTAX      SEQUENCE OF Sr1646v2XEfmOamEventLogEntry
   MAX-ACCESS  not-accessible
   STATUS      current
   DESCRIPTION
      "OAM event log"
   ::= {sr1646v2XEfmOamEventLog 1}

sr1646v2XEfmOamEventLogEntry OBJECT-TYPE
   SYNTAX      Sr1646v2XEfmOamEventLogEntry
   MAX-ACCESS  not-accessible
   STATUS      current
   DESCRIPTION
      ""
   INDEX      { sr1646v2XEfmOamEventLogTableIx }
   ::= {sr1646v2XEfmOamEventLogSSCTable 1}

Sr1646v2XEfmOamEventLogEntry ::=
   SEQUENCE
      {
      sr1646v2XEfmOamEventLogTableIx
         TableIndex,
      sr1646v2XEfmOamEventLogSysUpTime
         TimeTicks,
      sr1646v2XEfmOamEventLogLocation
         INTEGER,
      sr1646v2XEfmOamEventLogType
         INTEGER,
      sr1646v2XEfmOamEventLogOui
         OCTET STRING,
      sr1646v2XEfmOamEventLogWindow
         Counter64,
      sr1646v2XEfmOamEventLogThreshold
         Counter64,
      sr1646v2XEfmOamEventLogTotal
         Counter32,
      sr1646v2XEfmOamEventLogValue
         Counter64,
      sr1646v2XEfmOamEventLogRunningTotal
         Counter64
      }

sr1646v2XEfmOamEventLogTableIx OBJECT-TYPE
   SYNTAX      TableIndex
   MAX-ACCESS  not-accessible
   STATUS      current
   DESCRIPTION
      ""
   ::= {sr1646v2XEfmOamEventLogEntry 11}

sr1646v2XEfmOamEventLogSysUpTime OBJECT-TYPE
   SYNTAX      TimeTicks
   MAX-ACCESS  read-only
   STATUS      current
   DESCRIPTION
      "Path: efm.status.oamEventLog.sysUpTime

       Time in centi-second."
   ::= {sr1646v2XEfmOamEventLogEntry 16777216}

sr1646v2XEfmOamEventLogLocation OBJECT-TYPE
   SYNTAX      INTEGER
               {
               local (1),
               remote (2)
               }
   MAX-ACCESS  read-only
   STATUS      current
   DESCRIPTION
      "Path: efm.status.oamEventLog.location

       Possibilities:
               local   (1)
               remote   (2)"
   ::= {sr1646v2XEfmOamEventLogEntry 33554432}

sr1646v2XEfmOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: efm.status.oamEventLog.type

       Possibilities:
               erroredSymbols   (1)
               erroredFramePeriod   (2)
               erroredFrame   (3)
               erroredFrameSeconds   (4)
               linkFault   (256)
               dyingGasp   (257)
               criticalLink   (258)"
   ::= {sr1646v2XEfmOamEventLogEntry 50331648}

sr1646v2XEfmOamEventLogOui OBJECT-TYPE
   SYNTAX      OCTET STRING
   MAX-ACCESS  read-only
   STATUS      current
   DESCRIPTION
      "Path: efm.status.oamEventLog.oui"
   ::= {sr1646v2XEfmOamEventLogEntry 67108864}

sr1646v2XEfmOamEventLogWindow OBJECT-TYPE
   SYNTAX      Counter64
   MAX-ACCESS  read-only
   STATUS      current
   DESCRIPTION
      "Path: efm.status.oamEventLog.window

       64 bit unsigned wrappable counter."
   ::= {sr1646v2XEfmOamEventLogEntry 83886080}

sr1646v2XEfmOamEventLogThreshold OBJECT-TYPE
   SYNTAX      Counter64
   MAX-ACCESS  read-only
   STATUS      current
   DESCRIPTION
      "Path: efm.status.oamEventLog.threshold

       64 bit unsigned wrappable counter."
   ::= {sr1646v2XEfmOamEventLogEntry 100663296}

sr1646v2XEfmOamEventLogTotal OBJECT-TYPE
   SYNTAX      Counter32
   MAX-ACCESS  read-only
   STATUS      current
   DESCRIPTION
      "Path: efm.status.oamEventLog.total

       32 bit unsigned wrappable counter."
   ::= {sr1646v2XEfmOamEventLogEntry 117440512}

sr1646v2XEfmOamEventLogValue OBJECT-TYPE
   SYNTAX      Counter64
   MAX-ACCESS  read-only
   STATUS      current
   DESCRIPTION
      "Path: efm.status.oamEventLog.value

       64 bit unsigned wrappable counter."
   ::= {sr1646v2XEfmOamEventLogEntry 134217728}

sr1646v2XEfmOamEventLogRunningTotal OBJECT-TYPE
   SYNTAX      Counter64
   MAX-ACCESS  read-only
   STATUS      current
   DESCRIPTION
      "Path: efm.status.oamEventLog.runningTotal

       64 bit unsigned wrappable counter."
   ::= {sr1646v2XEfmOamEventLogEntry 150994944}


sr1646v2XEfmIpV6 OBJECT IDENTIFIER ::= {sr1646v2XEfm 17}

sr1646v2XEfmIpV6SSC OBJECT IDENTIFIER ::= {sr1646v2XEfmIpV6 1}

sr1646v2XEfmIpV6Entry OBJECT IDENTIFIER ::= {sr1646v2XEfmIpV6SSC 1}

sr1646v2XEfmIpV6State OBJECT-TYPE
   SYNTAX      INTEGER
               {
               disabled (0),
               enabled (1)
               }
   MAX-ACCESS  read-only
   STATUS      current
   DESCRIPTION
      "Path: efm.status.ipV6.state

       Possibilities:
               disabled   (0)
               enabled   (1)"
   ::= {sr1646v2XEfmIpV6Entry 16777216}

sr1646v2XEfmIpV6InterfaceId OBJECT-TYPE
   SYNTAX      OCTET STRING
   MAX-ACCESS  read-only
   STATUS      current
   DESCRIPTION
      "Path: efm.status.ipV6.interfaceId"
   ::= {sr1646v2XEfmIpV6Entry 33554432}

sr1646v2XEfmIpV6LinkMtu OBJECT-TYPE
   SYNTAX      Integer32
   MAX-ACCESS  read-only
   STATUS      current
   DESCRIPTION
      "Path: efm.status.ipV6.linkMtu"
   ::= {sr1646v2XEfmIpV6Entry 67108864}

sr1646v2XEfmIpV6HopLimit OBJECT-TYPE
   SYNTAX      Integer32
   MAX-ACCESS  read-only
   STATUS      current
   DESCRIPTION
      "Path: efm.status.ipV6.hopLimit"
   ::= {sr1646v2XEfmIpV6Entry 83886080}

sr1646v2XEfmIpV6DhcpIaid OBJECT-TYPE
   SYNTAX      Counter32
   MAX-ACCESS  read-only
   STATUS      current
   DESCRIPTION
      "Path: efm.status.ipV6.dhcp.iaid

       32 bit unsigned wrappable counter."
   ::= {sr1646v2XEfmIpV6Entry 100728832}

sr1646v2XEfmIpV6RaRcvOption OBJECT-TYPE
   SYNTAX      Integer32
   MAX-ACCESS  read-only
   STATUS      current
   DESCRIPTION
      "Path: efm.status.ipV6.raRcvOption

       Bit meanings:
               bit 0 = linkMtu,
               bit 1 = srcLinkLayer,
               bit 2 = prefixInfo,
               bit 3 = rdnss,
               bit 4 = dnssl"
   ::= {sr1646v2XEfmIpV6Entry 117440512}

sr1646v2XEfmIpV6Addresses OBJECT-TYPE
   SYNTAX      SEQUENCE OF Sr1646v2XEfmIpV6AddressesEntry
   MAX-ACCESS  not-accessible
   STATUS      current
   DESCRIPTION
      ""
   ::= {sr1646v2XEfmIpV6 50331648}

sr1646v2XEfmIpV6AddressesEntry OBJECT-TYPE
   SYNTAX      Sr1646v2XEfmIpV6AddressesEntry
   MAX-ACCESS  not-accessible
   STATUS      current
   DESCRIPTION
      ""
   INDEX      { sr1646v2XEfmIpV6AddressesTableIx }
   ::= {sr1646v2XEfmIpV6Addresses 1}

Sr1646v2XEfmIpV6AddressesEntry ::=
   SEQUENCE
      {
      sr1646v2XEfmIpV6AddressesTableIx
         TableIndex,
      sr1646v2XEfmIpV6AddressesAddress
         Ipv6Address,
      sr1646v2XEfmIpV6AddressesPrefixLength
         Integer32,
      sr1646v2XEfmIpV6AddressesStatus
         INTEGER,
      sr1646v2XEfmIpV6AddressesOrigin
         INTEGER,
      sr1646v2XEfmIpV6AddressesFlagsInterfaceId
         INTEGER,
      sr1646v2XEfmIpV6AddressesFlagsAnycast
         INTEGER,
      sr1646v2XEfmIpV6AddressesTimersValidLifeTime
         TimeTicks,
      sr1646v2XEfmIpV6AddressesTimersPrefLifeTime
         TimeTicks
      }

sr1646v2XEfmIpV6AddressesTableIx OBJECT-TYPE
   SYNTAX      TableIndex
   MAX-ACCESS  not-accessible
   STATUS      current
   DESCRIPTION
      ""
   ::= {sr1646v2XEfmIpV6AddressesEntry 11}

sr1646v2XEfmIpV6AddressesAddress OBJECT-TYPE
   SYNTAX      Ipv6Address
   MAX-ACCESS  read-only
   STATUS      current
   DESCRIPTION
      "Path: efm.status.ipV6.addresses.address

       ipv6 address"
   ::= {sr1646v2XEfmIpV6AddressesEntry 16777216}

sr1646v2XEfmIpV6AddressesPrefixLength OBJECT-TYPE
   SYNTAX      Integer32
   MAX-ACCESS  read-only
   STATUS      current
   DESCRIPTION
      "Path: efm.status.ipV6.addresses.prefixLength"
   ::= {sr1646v2XEfmIpV6AddressesEntry 33554432}

sr1646v2XEfmIpV6AddressesStatus OBJECT-TYPE
   SYNTAX      INTEGER
               {
               invalid (0),
               tentative (1),
               deprecated (2),
               preferred (3)
               }
   MAX-ACCESS  read-only
   STATUS      current
   DESCRIPTION
      "Path: efm.status.ipV6.addresses.status

       Possibilities:
               invalid   (0)
               tentative   (1)
               deprecated   (2)
               preferred   (3)"
   ::= {sr1646v2XEfmIpV6AddressesEntry 50331648}

sr1646v2XEfmIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.ipV6.addresses.origin

       Possibilities:
               unknown   (0)
               manual   (1)
               generalPrefix   (2)
               statelessAuto   (3)
               statefullAuto   (4)"
   ::= {sr1646v2XEfmIpV6AddressesEntry 67108864}

sr1646v2XEfmIpV6AddressesFlagsInterfaceId OBJECT-TYPE
   SYNTAX      INTEGER
               {
               no (0),
               yes (1)
               }
   MAX-ACCESS  read-only
   STATUS      current
   DESCRIPTION
      "Path: efm.status.ipV6.addresses.flags.interfaceId

       Possibilities:
               no   (0)
               yes   (1)"
   ::= {sr1646v2XEfmIpV6AddressesEntry 83951616}

sr1646v2XEfmIpV6AddressesFlagsAnycast OBJECT-TYPE
   SYNTAX      INTEGER
               {
               no (0),
               yes (1)
               }
   MAX-ACCESS  read-only
   STATUS      current
   DESCRIPTION
      "Path: efm.status.ipV6.addresses.flags.anycast

       Possibilities:
               no   (0)
               yes   (1)"
   ::= {sr1646v2XEfmIpV6AddressesEntry 84017152}

sr1646v2XEfmIpV6AddressesTimersValidLifeTime OBJECT-TYPE
   SYNTAX      TimeTicks
   MAX-ACCESS  read-only
   STATUS      current
   DESCRIPTION
      "Path: efm.status.ipV6.addresses.timers.validLifeTime

       Time in centi-second."
   ::= {sr1646v2XEfmIpV6AddressesEntry 100794368}

sr1646v2XEfmIpV6AddressesTimersPrefLifeTime OBJECT-TYPE
   SYNTAX      TimeTicks
   MAX-ACCESS  read-only
   STATUS      current
   DESCRIPTION
      "Path: efm.status.ipV6.addresses.timers.prefLifeTime

       Time in centi-second."
   ::= {sr1646v2XEfmIpV6AddressesEntry 100728832}


sr1646v2XEfmVlan OBJECT IDENTIFIER ::= {sr1646v2XEfm 34}

sr1646v2XEfmVlanSSCTable OBJECT-TYPE
   SYNTAX      SEQUENCE OF Sr1646v2XEfmVlanEntry
   MAX-ACCESS  not-accessible
   STATUS      current
   DESCRIPTION
      ""
   ::= {sr1646v2XEfmVlan 1}

sr1646v2XEfmVlanEntry OBJECT-TYPE
   SYNTAX      Sr1646v2XEfmVlanEntry
   MAX-ACCESS  not-accessible
   STATUS      current
   DESCRIPTION
      ""
   INDEX      { sr1646v2XEfmVlanTableIx }
   ::= {sr1646v2XEfmVlanSSCTable 1}

Sr1646v2XEfmVlanEntry ::=
   SEQUENCE
      {
      sr1646v2XEfmVlanTableIx
         TableIndex,
      sr1646v2XEfmVlanName
         DisplayString,
      sr1646v2XEfmVlanMode
         INTEGER,
      sr1646v2XEfmVlanIfOperStatus
         INTEGER,
      sr1646v2XEfmVlanIfLastChange
         TimeTicks,
      sr1646v2XEfmVlanIfLastChangeDate
         DisplayString,
      sr1646v2XEfmVlanIpAddress
         IpAddress,
      sr1646v2XEfmVlanIpNetMask
         IpAddress,
      sr1646v2XEfmVlanIpRemote
         IpAddress,
      sr1646v2XEfmVlanIpDhcpStatus
         INTEGER,
      sr1646v2XEfmVlanIpDhcpLeaseTime
         TimeTicks,
      sr1646v2XEfmVlanIpV6State
         INTEGER,
      sr1646v2XEfmVlanIpV6InterfaceId
         OCTET STRING,
      sr1646v2XEfmVlanIpV6LinkMtu
         Integer32,
      sr1646v2XEfmVlanIpV6HopLimit
         Integer32,
      sr1646v2XEfmVlanIpV6DhcpIaid
         Counter32,
      sr1646v2XEfmVlanIpV6RaRcvOption
         Integer32,
      sr1646v2XEfmVlanBridgingStatus
         INTEGER,
      sr1646v2XEfmVlanBridgingSpanningTreePortRole
         INTEGER,
      sr1646v2XEfmVlanBridgingSpanningTreePortId
         Integer32,
      sr1646v2XEfmVlanBridgingSpanningTreePpCostExtPathCost
         Integer32,
      sr1646v2XEfmVlanBridgingSpanningTreePpCostIntPathCost
         Integer32,
      sr1646v2XEfmVlanBridgingSpanningTreeExtRpCost
         Integer32,
      sr1646v2XEfmVlanBridgingSpanningTreeIntRpCost
         Integer32,
      sr1646v2XEfmVlanBridgingSpanningTreeDesBrIdPriority
         Integer32,
      sr1646v2XEfmVlanBridgingSpanningTreeDesBrIdMacAddress
         OCTET STRING,
      sr1646v2XEfmVlanBridgingSpanningTreeDesPrtId
         Integer32,
      sr1646v2XEfmVlanBridgingSpanningTreeDesInt
         INTEGER,
      sr1646v2XEfmVlanBridgingSpanningTreeEdgeDetection
         INTEGER,
      sr1646v2XEfmVlanVlanVid
         Integer32,
      sr1646v2XEfmVlanPppOEthDiscState
         INTEGER,
      sr1646v2XEfmVlanPppOEthPeerMac
         OCTET STRING,
      sr1646v2XEfmVlanPppOEthServiceName
         DisplayString,
      sr1646v2XEfmVlanPppLcpState
         INTEGER,
      sr1646v2XEfmVlanPppIpcpState
         INTEGER,
      sr1646v2XEfmVlanPppIp6cpState
         INTEGER,
      sr1646v2XEfmVlanPppMyAutSt
         INTEGER,
      sr1646v2XEfmVlanPppHisAutSt
         INTEGER,
      sr1646v2XEfmVlanPppMru
         Integer32
      }

sr1646v2XEfmVlanTableIx OBJECT-TYPE
   SYNTAX      TableIndex
   MAX-ACCESS  not-accessible
   STATUS      current
   DESCRIPTION
      ""
   ::= {sr1646v2XEfmVlanEntry 11}

sr1646v2XEfmVlanName OBJECT-TYPE
   SYNTAX      DisplayString
   MAX-ACCESS  read-only
   STATUS      current
   DESCRIPTION
      "Path: efm.status.vlan.name"
   ::= {sr1646v2XEfmVlanEntry 16777216}

sr1646v2XEfmVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: efm.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2XEfmVlanEntry 335544320}

sr1646v2XEfmVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.vlan.ifOperStatus

       Possibilities:
               up   (1)
               down   (2)
               testing   (3)
               unknown   (4)
               dormant   (5)
               notPresent   (6)
               lowerLayerDown   (7)"
   ::= {sr1646v2XEfmVlanEntry 1795162112}

sr1646v2XEfmVlanIfLastChange OBJECT-TYPE
   SYNTAX      TimeTicks
   MAX-ACCESS  read-only
   STATUS      current
   DESCRIPTION
      "Path: efm.status.vlan.ifLastChange

       Time in centi-second."
   ::= {sr1646v2XEfmVlanEntry 1811939328}

sr1646v2XEfmVlanIfLastChangeDate OBJECT-TYPE
   SYNTAX      DisplayString
   MAX-ACCESS  read-only
   STATUS      current
   DESCRIPTION
      "Path: efm.status.vlan.ifLastChangeDate"
   ::= {sr1646v2XEfmVlanEntry 3070230528}

sr1646v2XEfmVlanIpAddress OBJECT-TYPE
   SYNTAX      IpAddress
   MAX-ACCESS  read-only
   STATUS      current
   DESCRIPTION
      "Path: efm.status.vlan.ip.address"
   ::= {sr1646v2XEfmVlanEntry 51380224}

sr1646v2XEfmVlanIpNetMask OBJECT-TYPE
   SYNTAX      IpAddress
   MAX-ACCESS  read-only
   STATUS      current
   DESCRIPTION
      "Path: efm.status.vlan.ip.netMask"
   ::= {sr1646v2XEfmVlanEntry 51445760}

sr1646v2XEfmVlanIpRemote OBJECT-TYPE
   SYNTAX      IpAddress
   MAX-ACCESS  read-only
   STATUS      current
   DESCRIPTION
      "Path: efm.status.vlan.ip.remote"
   ::= {sr1646v2XEfmVlanEntry 51511296}

sr1646v2XEfmVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: efm.status.vlan.ip.dhcp.status

       Possibilities:
               none   (0)
               selecting   (1)
               requesting   (2)
               rebinding   (3)
               bound   (4)
               renewing   (5)
               rebooting   (6)
               initreboot   (7)"
   ::= {sr1646v2XEfmVlanEntry 51904768}

sr1646v2XEfmVlanIpDhcpLeaseTime OBJECT-TYPE
   SYNTAX      TimeTicks
   MAX-ACCESS  read-only
   STATUS      current
   DESCRIPTION
      "Path: efm.status.vlan.ip.dhcp.leaseTime

       Time in centi-second."
   ::= {sr1646v2XEfmVlanEntry 51905024}

sr1646v2XEfmVlanIpV6State OBJECT-TYPE
   SYNTAX      INTEGER
               {
               disabled (0),
               enabled (1)
               }
   MAX-ACCESS  read-only
   STATUS      current
   DESCRIPTION
      "Path: efm.status.vlan.ipV6.state

       Possibilities:
               disabled   (0)
               enabled   (1)"
   ::= {sr1646v2XEfmVlanEntry 100728832}

sr1646v2XEfmVlanIpV6InterfaceId OBJECT-TYPE
   SYNTAX      OCTET STRING
   MAX-ACCESS  read-only
   STATUS      current
   DESCRIPTION
      "Path: efm.status.vlan.ipV6.interfaceId"
   ::= {sr1646v2XEfmVlanEntry 100794368}

sr1646v2XEfmVlanIpV6LinkMtu OBJECT-TYPE
   SYNTAX      Integer32
   MAX-ACCESS  read-only
   STATUS      current
   DESCRIPTION
      "Path: efm.status.vlan.ipV6.linkMtu"
   ::= {sr1646v2XEfmVlanEntry 100925440}

sr1646v2XEfmVlanIpV6HopLimit OBJECT-TYPE
   SYNTAX      Integer32
   MAX-ACCESS  read-only
   STATUS      current
   DESCRIPTION
      "Path: efm.status.vlan.ipV6.hopLimit"
   ::= {sr1646v2XEfmVlanEntry 100990976}

sr1646v2XEfmVlanIpV6DhcpIaid OBJECT-TYPE
   SYNTAX      Counter32
   MAX-ACCESS  read-only
   STATUS      current
   DESCRIPTION
      "Path: efm.status.vlan.ipV6.dhcp.iaid

       32 bit unsigned wrappable counter."
   ::= {sr1646v2XEfmVlanEntry 101056768}

sr1646v2XEfmVlanIpV6RaRcvOption OBJECT-TYPE
   SYNTAX      Integer32
   MAX-ACCESS  read-only
   STATUS      current
   DESCRIPTION
      "Path: efm.status.vlan.ipV6.raRcvOption

       Bit meanings:
               bit 0 = linkMtu,
               bit 1 = srcLinkLayer,
               bit 2 = prefixInfo,
               bit 3 = rdnss,
               bit 4 = dnssl"
   ::= {sr1646v2XEfmVlanEntry 101122048}

sr1646v2XEfmVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: efm.status.vlan.bridging.status

       Possibilities:
               disabled   (0)
               discarding   (1)
               learning   (2)
               forwarding   (3)
               backupBlockedIntfDown   (256)
               backupBlockedIntfUp   (259)
               shutdown   (255)"
   ::= {sr1646v2XEfmVlanEntry 453050368}

sr1646v2XEfmVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: efm.status.vlan.bridging.spanningTree.portRole

       Possibilities:
               none   (0)
               root   (1)
               designated   (2)
               alternate   (3)
               backup   (4)
               disabled   (5)
               master   (6)"
   ::= {sr1646v2XEfmVlanEntry 453116160}

sr1646v2XEfmVlanBridgingSpanningTreePortId OBJECT-TYPE
   SYNTAX      Integer32
   MAX-ACCESS  read-only
   STATUS      current
   DESCRIPTION
      "Path: efm.status.vlan.bridging.spanningTree.portId"
   ::= {sr1646v2XEfmVlanEntry 453116416}

sr1646v2XEfmVlanBridgingSpanningTreePpCostExtPathCost OBJECT-TYPE
   SYNTAX      Integer32
   MAX-ACCESS  read-only
   STATUS      current
   DESCRIPTION
      "Path: efm.status.vlan.bridging.spanningTree.portPathCosts.extPathCost"
   ::= {sr1646v2XEfmVlanEntry 453116673}

sr1646v2XEfmVlanBridgingSpanningTreePpCostIntPathCost OBJECT-TYPE
   SYNTAX      Integer32
   MAX-ACCESS  read-only
   STATUS      current
   DESCRIPTION
      "Path: efm.status.vlan.bridging.spanningTree.portPathCosts.intPathCost"
   ::= {sr1646v2XEfmVlanEntry 453116674}

sr1646v2XEfmVlanBridgingSpanningTreeExtRpCost OBJECT-TYPE
   SYNTAX      Integer32
   MAX-ACCESS  read-only
   STATUS      current
   DESCRIPTION
      "Path: efm.status.vlan.bridging.spanningTree.extRootPathCost"
   ::= {sr1646v2XEfmVlanEntry 453116928}

sr1646v2XEfmVlanBridgingSpanningTreeIntRpCost OBJECT-TYPE
   SYNTAX      Integer32
   MAX-ACCESS  read-only
   STATUS      current
   DESCRIPTION
      "Path: efm.status.vlan.bridging.spanningTree.intRootPathCost"
   ::= {sr1646v2XEfmVlanEntry 453117184}

sr1646v2XEfmVlanBridgingSpanningTreeDesBrIdPriority OBJECT-TYPE
   SYNTAX      Integer32
   MAX-ACCESS  read-only
   STATUS      current
   DESCRIPTION
      "Path: efm.status.vlan.bridging.spanningTree.designatedBridgeId.priority"
   ::= {sr1646v2XEfmVlanEntry 453117441}

sr1646v2XEfmVlanBridgingSpanningTreeDesBrIdMacAddress OBJECT-TYPE
   SYNTAX      OCTET STRING
   MAX-ACCESS  read-only
   STATUS      current
   DESCRIPTION
      "Path: efm.status.vlan.bridging.spanningTree.designatedBridgeId.macAddress

       MAC address."
   ::= {sr1646v2XEfmVlanEntry 453117442}

sr1646v2XEfmVlanBridgingSpanningTreeDesPrtId OBJECT-TYPE
   SYNTAX      Integer32
   MAX-ACCESS  read-only
   STATUS      current
   DESCRIPTION
      "Path: efm.status.vlan.bridging.spanningTree.designatedPortId"
   ::= {sr1646v2XEfmVlanEntry 453117696}

sr1646v2XEfmVlanBridgingSpanningTreeDesInt OBJECT-TYPE
   SYNTAX      INTEGER
               {
               no (0),
               yes (1)
               }
   MAX-ACCESS  read-only
   STATUS      current
   DESCRIPTION
      "Path: efm.status.vlan.bridging.spanningTree.designatedOrInternal

       Possibilities:
               no   (0)
               yes   (1)"
   ::= {sr1646v2XEfmVlanEntry 453117952}

sr1646v2XEfmVlanBridgingSpanningTreeEdgeDetection OBJECT-TYPE
   SYNTAX      INTEGER
               {
               none (0),
               edge (1),
               notEdge (2)
               }
   MAX-ACCESS  read-only
   STATUS      current
   DESCRIPTION
      "Path: efm.status.vlan.bridging.spanningTree.edgeDetection

       Possibilities:
               none   (0)
               edge   (1)
               notEdge   (2)"
   ::= {sr1646v2XEfmVlanEntry 453118208}

sr1646v2XEfmVlanVlanVid OBJECT-TYPE
   SYNTAX      Integer32
   MAX-ACCESS  read-only
   STATUS      current
   DESCRIPTION
      "Path: efm.status.vlan.vlan.vid"
   ::= {sr1646v2XEfmVlanEntry 234946560}

sr1646v2XEfmVlanPppOEthDiscState OBJECT-TYPE
   SYNTAX      INTEGER
               {
               idle (0),
               waitForPADO (1),
               waitForPADS (2),
               established (3)
               }
   MAX-ACCESS  read-only
   STATUS      current
   DESCRIPTION
      "Path: efm.status.vlan.pppOverEth.discState

       Possibilities:
               idle   (0)
               waitForPADO   (1)
               waitForPADS   (2)
               established   (3)"
   ::= {sr1646v2XEfmVlanEntry 67174400}

sr1646v2XEfmVlanPppOEthPeerMac OBJECT-TYPE
   SYNTAX      OCTET STRING
   MAX-ACCESS  read-only
   STATUS      current
   DESCRIPTION
      "Path: efm.status.vlan.pppOverEth.remoteMacAddress

       MAC address."
   ::= {sr1646v2XEfmVlanEntry 67239936}

sr1646v2XEfmVlanPppOEthServiceName OBJECT-TYPE
   SYNTAX      DisplayString
   MAX-ACCESS  read-only
   STATUS      current
   DESCRIPTION
      "Path: efm.status.vlan.pppOverEth.serviceName"
   ::= {sr1646v2XEfmVlanEntry 67305472}

sr1646v2XEfmVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmVlanEntry 83951616}

sr1646v2XEfmVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmVlanEntry 84017152}

sr1646v2XEfmVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmVlanEntry 84869120}

sr1646v2XEfmVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: efm.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2XEfmVlanEntry 84541440}

sr1646v2XEfmVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: efm.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2XEfmVlanEntry 84606976}

sr1646v2XEfmVlanPppMru OBJECT-TYPE
   SYNTAX      Integer32
   MAX-ACCESS  read-only
   STATUS      current
   DESCRIPTION
      "Path: efm.status.vlan.ppp.mru"
   ::= {sr1646v2XEfmVlanEntry 84934656}

sr1646v2XEfmVlanIpSecondaryIp OBJECT-TYPE
   SYNTAX      SEQUENCE OF Sr1646v2XEfmVlanIpSecondaryIpEntry
   MAX-ACCESS  not-accessible
   STATUS      current
   DESCRIPTION
      ""
   ::= {sr1646v2XEfmVlan 51838976}

sr1646v2XEfmVlanIpSecondaryIpEntry OBJECT-TYPE
   SYNTAX      Sr1646v2XEfmVlanIpSecondaryIpEntry
   MAX-ACCESS  not-accessible
   STATUS      current
   DESCRIPTION
      ""
   INDEX      { sr1646v2XEfmVlanTableIx,
                sr1646v2XEfmVlanIpSecondaryIpTableIx }
   ::= {sr1646v2XEfmVlanIpSecondaryIp 1}

Sr1646v2XEfmVlanIpSecondaryIpEntry ::=
   SEQUENCE
      {
      sr1646v2XEfmVlanIpSecondaryIpTableIx
         TableIndex,
      sr1646v2XEfmVlanIpSecondaryIpAddress
         IpAddress,
      sr1646v2XEfmVlanIpSecondaryIpNetMask
         IpAddress
      }

sr1646v2XEfmVlanIpSecondaryIpTableIx OBJECT-TYPE
   SYNTAX      TableIndex
   MAX-ACCESS  not-accessible
   STATUS      current
   DESCRIPTION
      ""
   ::= {sr1646v2XEfmVlanIpSecondaryIpEntry 11}

sr1646v2XEfmVlanIpSecondaryIpAddress OBJECT-TYPE
   SYNTAX      IpAddress
   MAX-ACCESS  read-only
   STATUS      current
   DESCRIPTION
      "Path: efm.status.vlan.ip.secondaryIp.address"
   ::= {sr1646v2XEfmVlanIpSecondaryIpEntry 2030043136}

sr1646v2XEfmVlanIpSecondaryIpNetMask OBJECT-TYPE
   SYNTAX      IpAddress
   MAX-ACCESS  read-only
   STATUS      current
   DESCRIPTION
      "Path: efm.status.vlan.ip.secondaryIp.netMask"
   ::= {sr1646v2XEfmVlanIpSecondaryIpEntry 2063597568}

sr1646v2XEfmVlanIpV6Addresses OBJECT-TYPE
   SYNTAX      SEQUENCE OF Sr1646v2XEfmVlanIpV6AddressesEntry
   MAX-ACCESS  not-accessible
   STATUS      current
   DESCRIPTION
      ""
   ::= {sr1646v2XEfmVlan 100859904}

sr1646v2XEfmVlanIpV6AddressesEntry OBJECT-TYPE
   SYNTAX      Sr1646v2XEfmVlanIpV6AddressesEntry
   MAX-ACCESS  not-accessible
   STATUS      current
   DESCRIPTION
      ""
   INDEX      { sr1646v2XEfmVlanTableIx,
                sr1646v2XEfmVlanIpV6AddressesTableIx }
   ::= {sr1646v2XEfmVlanIpV6Addresses 1}

Sr1646v2XEfmVlanIpV6AddressesEntry ::=
   SEQUENCE
      {
      sr1646v2XEfmVlanIpV6AddressesTableIx
         TableIndex,
      sr1646v2XEfmVlanIpV6AddressesAddress
         Ipv6Address,
      sr1646v2XEfmVlanIpV6AddressesPrefixLength
         Integer32,
      sr1646v2XEfmVlanIpV6AddressesStatus
         INTEGER,
      sr1646v2XEfmVlanIpV6AddressesOrigin
         INTEGER,
      sr1646v2XEfmVlanIpV6AddressesFlagsInterfaceId
         INTEGER,
      sr1646v2XEfmVlanIpV6AddressesFlagsAnycast
         INTEGER,
      sr1646v2XEfmVlanIpV6AddressesTimersValidLifeTime
         TimeTicks,
      sr1646v2XEfmVlanIpV6AddressesTimersPrefLifeTime
         TimeTicks
      }

sr1646v2XEfmVlanIpV6AddressesTableIx OBJECT-TYPE
   SYNTAX      TableIndex
   MAX-ACCESS  not-accessible
   STATUS      current
   DESCRIPTION
      ""
   ::= {sr1646v2XEfmVlanIpV6AddressesEntry 11}

sr1646v2XEfmVlanIpV6AddressesAddress OBJECT-TYPE
   SYNTAX      Ipv6Address
   MAX-ACCESS  read-only
   STATUS      current
   DESCRIPTION
      "Path: efm.status.vlan.ipV6.addresses.address

       ipv6 address"
   ::= {sr1646v2XEfmVlanIpV6AddressesEntry 16777216}

sr1646v2XEfmVlanIpV6AddressesPrefixLength OBJECT-TYPE
   SYNTAX      Integer32
   MAX-ACCESS  read-only
   STATUS      current
   DESCRIPTION
      "Path: efm.status.vlan.ipV6.addresses.prefixLength"
   ::= {sr1646v2XEfmVlanIpV6AddressesEntry 33554432}

sr1646v2XEfmVlanIpV6AddressesStatus OBJECT-TYPE
   SYNTAX      INTEGER
               {
               invalid (0),
               tentative (1),
               deprecated (2),
               preferred (3)
               }
   MAX-ACCESS  read-only
   STATUS      current
   DESCRIPTION
      "Path: efm.status.vlan.ipV6.addresses.status

       Possibilities:
               invalid   (0)
               tentative   (1)
               deprecated   (2)
               preferred   (3)"
   ::= {sr1646v2XEfmVlanIpV6AddressesEntry 50331648}

sr1646v2XEfmVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.vlan.ipV6.addresses.origin

       Possibilities:
               unknown   (0)
               manual   (1)
               generalPrefix   (2)
               statelessAuto   (3)
               statefullAuto   (4)"
   ::= {sr1646v2XEfmVlanIpV6AddressesEntry 67108864}

sr1646v2XEfmVlanIpV6AddressesFlagsInterfaceId OBJECT-TYPE
   SYNTAX      INTEGER
               {
               no (0),
               yes (1)
               }
   MAX-ACCESS  read-only
   STATUS      current
   DESCRIPTION
      "Path: efm.status.vlan.ipV6.addresses.flags.interfaceId

       Possibilities:
               no   (0)
               yes   (1)"
   ::= {sr1646v2XEfmVlanIpV6AddressesEntry 83951616}

sr1646v2XEfmVlanIpV6AddressesFlagsAnycast OBJECT-TYPE
   SYNTAX      INTEGER
               {
               no (0),
               yes (1)
               }
   MAX-ACCESS  read-only
   STATUS      current
   DESCRIPTION
      "Path: efm.status.vlan.ipV6.addresses.flags.anycast

       Possibilities:
               no   (0)
               yes   (1)"
   ::= {sr1646v2XEfmVlanIpV6AddressesEntry 84017152}

sr1646v2XEfmVlanIpV6AddressesTimersValidLifeTime OBJECT-TYPE
   SYNTAX      TimeTicks
   MAX-ACCESS  read-only
   STATUS      current
   DESCRIPTION
      "Path: efm.status.vlan.ipV6.addresses.timers.validLifeTime

       Time in centi-second."
   ::= {sr1646v2XEfmVlanIpV6AddressesEntry 100794368}

sr1646v2XEfmVlanIpV6AddressesTimersPrefLifeTime OBJECT-TYPE
   SYNTAX      TimeTicks
   MAX-ACCESS  read-only
   STATUS      current
   DESCRIPTION
      "Path: efm.status.vlan.ipV6.addresses.timers.prefLifeTime

       Time in centi-second."
   ::= {sr1646v2XEfmVlanIpV6AddressesEntry 100728832}

sr1646v2XEfmVlanVlanArpCache OBJECT-TYPE
   SYNTAX      SEQUENCE OF Sr1646v2XEfmVlanVlanArpCacheEntry
   MAX-ACCESS  not-accessible
   STATUS      current
   DESCRIPTION
      ""
   ::= {sr1646v2XEfmVlan 235601920}

sr1646v2XEfmVlanVlanArpCacheEntry OBJECT-TYPE
   SYNTAX      Sr1646v2XEfmVlanVlanArpCacheEntry
   MAX-ACCESS  not-accessible
   STATUS      current
   DESCRIPTION
      ""
   INDEX      { sr1646v2XEfmVlanTableIx,
                sr1646v2XEfmVlanVlanArpCacheTableIx }
   ::= {sr1646v2XEfmVlanVlanArpCache 1}

Sr1646v2XEfmVlanVlanArpCacheEntry ::=
   SEQUENCE
      {
      sr1646v2XEfmVlanVlanArpCacheTableIx
         TableIndex,
      sr1646v2XEfmVlanVlanArpCacheMacAddress
         OCTET STRING,
      sr1646v2XEfmVlanVlanArpCacheIpAddress
         IpAddress,
      sr1646v2XEfmVlanVlanArpCacheType
         INTEGER,
      sr1646v2XEfmVlanVlanArpCacheTimeOut
         TimeTicks
      }

sr1646v2XEfmVlanVlanArpCacheTableIx OBJECT-TYPE
   SYNTAX      TableIndex
   MAX-ACCESS  not-accessible
   STATUS      current
   DESCRIPTION
      ""
   ::= {sr1646v2XEfmVlanVlanArpCacheEntry 11}

sr1646v2XEfmVlanVlanArpCacheMacAddress OBJECT-TYPE
   SYNTAX      OCTET STRING
   MAX-ACCESS  read-only
   STATUS      current
   DESCRIPTION
      "Path: efm.status.vlan.vlan.arpCache.macAddress

       MAC address."
   ::= {sr1646v2XEfmVlanVlanArpCacheEntry 16777216}

sr1646v2XEfmVlanVlanArpCacheIpAddress OBJECT-TYPE
   SYNTAX      IpAddress
   MAX-ACCESS  read-only
   STATUS      current
   DESCRIPTION
      "Path: efm.status.vlan.vlan.arpCache.ipAddress"
   ::= {sr1646v2XEfmVlanVlanArpCacheEntry 33554432}

sr1646v2XEfmVlanVlanArpCacheType OBJECT-TYPE
   SYNTAX      INTEGER
               {
               static (0),
               dynamic (1)
               }
   MAX-ACCESS  read-only
   STATUS      current
   DESCRIPTION
      "Path: efm.status.vlan.vlan.arpCache.type

       Possibilities:
               static   (0)
               dynamic   (1)"
   ::= {sr1646v2XEfmVlanVlanArpCacheEntry 50331648}

sr1646v2XEfmVlanVlanArpCacheTimeOut OBJECT-TYPE
   SYNTAX      TimeTicks
   MAX-ACCESS  read-only
   STATUS      current
   DESCRIPTION
      "Path: efm.status.vlan.vlan.arpCache.timeOut

       Time in centi-second."
   ::= {sr1646v2XEfmVlanVlanArpCacheEntry 67108864}


sr1646v2XEfmPppOE OBJECT IDENTIFIER ::= {sr1646v2XEfm 36}

sr1646v2XEfmPppOESSCTable OBJECT-TYPE
   SYNTAX      SEQUENCE OF Sr1646v2XEfmPppOEEntry
   MAX-ACCESS  not-accessible
   STATUS      current
   DESCRIPTION
      ""
   ::= {sr1646v2XEfmPppOE 1}

sr1646v2XEfmPppOEEntry OBJECT-TYPE
   SYNTAX      Sr1646v2XEfmPppOEEntry
   MAX-ACCESS  not-accessible
   STATUS      current
   DESCRIPTION
      ""
   INDEX      { sr1646v2XEfmPppOETableIx }
   ::= {sr1646v2XEfmPppOESSCTable 1}

Sr1646v2XEfmPppOEEntry ::=
   SEQUENCE
      {
      sr1646v2XEfmPppOETableIx
         TableIndex,
      sr1646v2XEfmPppOEName
         DisplayString,
      sr1646v2XEfmPppOEMode
         INTEGER,
      sr1646v2XEfmPppOEIfOperStatus
         INTEGER,
      sr1646v2XEfmPppOEIfLastChange
         TimeTicks,
      sr1646v2XEfmPppOEIfLastChangeDate
         DisplayString,
      sr1646v2XEfmPppOEIpAddress
         IpAddress,
      sr1646v2XEfmPppOEIpNetMask
         IpAddress,
      sr1646v2XEfmPppOEIpRemote
         IpAddress,
      sr1646v2XEfmPppOEPppOEthDiscState
         INTEGER,
      sr1646v2XEfmPppOEPppOEthPeerMac
         OCTET STRING,
      sr1646v2XEfmPppOEPppOEthServiceName
         DisplayString,
      sr1646v2XEfmPppOEPppLcpState
         INTEGER,
      sr1646v2XEfmPppOEPppIpcpState
         INTEGER,
      sr1646v2XEfmPppOEPppIp6cpState
         INTEGER,
      sr1646v2XEfmPppOEPppMyAutSt
         INTEGER,
      sr1646v2XEfmPppOEPppHisAutSt
         INTEGER,
      sr1646v2XEfmPppOEPppMru
         Integer32,
      sr1646v2XEfmPppOEIpV6State
         INTEGER,
      sr1646v2XEfmPppOEIpV6InterfaceId
         OCTET STRING,
      sr1646v2XEfmPppOEIpV6LinkMtu
         Integer32,
      sr1646v2XEfmPppOEIpV6HopLimit
         Integer32,
      sr1646v2XEfmPppOEIpV6DhcpIaid
         Counter32,
      sr1646v2XEfmPppOEIpV6RaRcvOption
         Integer32
      }

sr1646v2XEfmPppOETableIx OBJECT-TYPE
   SYNTAX      TableIndex
   MAX-ACCESS  not-accessible
   STATUS      current
   DESCRIPTION
      ""
   ::= {sr1646v2XEfmPppOEEntry 11}

sr1646v2XEfmPppOEName OBJECT-TYPE
   SYNTAX      DisplayString
   MAX-ACCESS  read-only
   STATUS      current
   DESCRIPTION
      "Path: efm.status.pppoEClient.name"
   ::= {sr1646v2XEfmPppOEEntry 16777216}

sr1646v2XEfmPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: efm.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2XEfmPppOEEntry 335544320}

sr1646v2XEfmPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.pppoEClient.ifOperStatus

       Possibilities:
               up   (1)
               down   (2)
               testing   (3)
               unknown   (4)
               dormant   (5)
               notPresent   (6)
               lowerLayerDown   (7)"
   ::= {sr1646v2XEfmPppOEEntry 1795162112}

sr1646v2XEfmPppOEIfLastChange OBJECT-TYPE
   SYNTAX      TimeTicks
   MAX-ACCESS  read-only
   STATUS      current
   DESCRIPTION
      "Path: efm.status.pppoEClient.ifLastChange

       Time in centi-second."
   ::= {sr1646v2XEfmPppOEEntry 1811939328}

sr1646v2XEfmPppOEIfLastChangeDate OBJECT-TYPE
   SYNTAX      DisplayString
   MAX-ACCESS  read-only
   STATUS      current
   DESCRIPTION
      "Path: efm.status.pppoEClient.ifLastChangeDate"
   ::= {sr1646v2XEfmPppOEEntry 3070230528}

sr1646v2XEfmPppOEIpAddress OBJECT-TYPE
   SYNTAX      IpAddress
   MAX-ACCESS  read-only
   STATUS      current
   DESCRIPTION
      "Path: efm.status.pppoEClient.ip.address"
   ::= {sr1646v2XEfmPppOEEntry 51380224}

sr1646v2XEfmPppOEIpNetMask OBJECT-TYPE
   SYNTAX      IpAddress
   MAX-ACCESS  read-only
   STATUS      current
   DESCRIPTION
      "Path: efm.status.pppoEClient.ip.netMask"
   ::= {sr1646v2XEfmPppOEEntry 51445760}

sr1646v2XEfmPppOEIpRemote OBJECT-TYPE
   SYNTAX      IpAddress
   MAX-ACCESS  read-only
   STATUS      current
   DESCRIPTION
      "Path: efm.status.pppoEClient.ip.remote"
   ::= {sr1646v2XEfmPppOEEntry 51511296}

sr1646v2XEfmPppOEPppOEthDiscState OBJECT-TYPE
   SYNTAX      INTEGER
               {
               idle (0),
               waitForPADO (1),
               waitForPADS (2),
               established (3)
               }
   MAX-ACCESS  read-only
   STATUS      current
   DESCRIPTION
      "Path: efm.status.pppoEClient.pppOverEth.discState

       Possibilities:
               idle   (0)
               waitForPADO   (1)
               waitForPADS   (2)
               established   (3)"
   ::= {sr1646v2XEfmPppOEEntry 67174400}

sr1646v2XEfmPppOEPppOEthPeerMac OBJECT-TYPE
   SYNTAX      OCTET STRING
   MAX-ACCESS  read-only
   STATUS      current
   DESCRIPTION
      "Path: efm.status.pppoEClient.pppOverEth.remoteMacAddress

       MAC address."
   ::= {sr1646v2XEfmPppOEEntry 67239936}

sr1646v2XEfmPppOEPppOEthServiceName OBJECT-TYPE
   SYNTAX      DisplayString
   MAX-ACCESS  read-only
   STATUS      current
   DESCRIPTION
      "Path: efm.status.pppoEClient.pppOverEth.serviceName"
   ::= {sr1646v2XEfmPppOEEntry 67305472}

sr1646v2XEfmPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmPppOEEntry 83951616}

sr1646v2XEfmPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmPppOEEntry 84017152}

sr1646v2XEfmPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2XEfmPppOEEntry 84869120}

sr1646v2XEfmPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: efm.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2XEfmPppOEEntry 84541440}

sr1646v2XEfmPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: efm.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2XEfmPppOEEntry 84606976}

sr1646v2XEfmPppOEPppMru OBJECT-TYPE
   SYNTAX      Integer32
   MAX-ACCESS  read-only
   STATUS      current
   DESCRIPTION
      "Path: efm.status.pppoEClient.ppp.mru"
   ::= {sr1646v2XEfmPppOEEntry 84934656}

sr1646v2XEfmPppOEIpV6State OBJECT-TYPE
   SYNTAX      INTEGER
               {
               disabled (0),
               enabled (1)
               }
   MAX-ACCESS  read-only
   STATUS      current
   DESCRIPTION
      "Path: efm.status.pppoEClient.ipV6.state

       Possibilities:
               disabled   (0)
               enabled   (1)"
   ::= {sr1646v2XEfmPppOEEntry 100728832}

sr1646v2XEfmPppOEIpV6InterfaceId OBJECT-TYPE
   SYNTAX      OCTET STRING
   MAX-ACCESS  read-only
   STATUS      current
   DESCRIPTION
      "Path: efm.status.pppoEClient.ipV6.interfaceId"
   ::= {sr1646v2XEfmPppOEEntry 100794368}

sr1646v2XEfmPppOEIpV6LinkMtu OBJECT-TYPE
   SYNTAX      Integer32
   MAX-ACCESS  read-only
   STATUS      current
   DESCRIPTION
      "Path: efm.status.pppoEClient.ipV6.linkMtu"
   ::= {sr1646v2XEfmPppOEEntry 100925440}

sr1646v2XEfmPppOEIpV6HopLimit OBJECT-TYPE
   SYNTAX      Integer32
   MAX-ACCESS  read-only
   STATUS      current
   DESCRIPTION
      "Path: efm.status.pppoEClient.ipV6.hopLimit"
   ::= {sr1646v2XEfmPppOEEntry 100990976}

sr1646v2XEfmPppOEIpV6DhcpIaid OBJECT-TYPE
   SYNTAX      Counter32
   MAX-ACCESS  read-only
   STATUS      current
   DESCRIPTION
      "Path: efm.status.pppoEClient.ipV6.dhcp.iaid

       32 bit unsigned wrappable counter."
   ::= {sr1646v2XEfmPppOEEntry 101056768}

sr1646v2XEfmPppOEIpV6RaRcvOption OBJECT-TYPE
   SYNTAX      Integer32
   MAX-ACCESS  read-only
   STATUS      current
   DESCRIPTION
      "Path: efm.status.pppoEClient.ipV6.raRcvOption

       Bit meanings:
               bit 0 = linkMtu,
               bit 1 = srcLinkLayer,
               bit 2 = prefixInfo,
               bit 3 = rdnss,
               bit 4 = dnssl"
   ::= {sr1646v2XEfmPppOEEntry 101122048}

sr1646v2XEfmPppOEIpV6Addresses OBJECT-TYPE
   SYNTAX      SEQUENCE OF Sr1646v2XEfmPppOEIpV6AddressesEntry
   MAX-ACCESS  not-accessible
   STATUS      current
   DESCRIPTION
      ""
   ::= {sr1646v2XEfmPppOE 100859904}

sr1646v2XEfmPppOEIpV6AddressesEntry OBJECT-TYPE
   SYNTAX      Sr1646v2XEfmPppOEIpV6AddressesEntry
   MAX-ACCESS  not-accessible
   STATUS      current
   DESCRIPTION
      ""
   INDEX      { sr1646v2XEfmPppOETableIx,
                sr1646v2XEfmPppOEIpV6AddressesTableIx }
   ::= {sr1646v2XEfmPppOEIpV6Addresses 1}

Sr1646v2XEfmPppOEIpV6AddressesEntry ::=
   SEQUENCE
      {
      sr1646v2XEfmPppOEIpV6AddressesTableIx
         TableIndex,
      sr1646v2XEfmPppOEIpV6AddressesAddress
         Ipv6Address,
      sr1646v2XEfmPppOEIpV6AddressesPrefixLength
         Integer32,
      sr1646v2XEfmPppOEIpV6AddressesStatus
         INTEGER,
      sr1646v2XEfmPppOEIpV6AddressesOrigin
         INTEGER,
      sr1646v2XEfmPppOEIpV6AddressesFlagsInterfaceId
         INTEGER,
      sr1646v2XEfmPppOEIpV6AddressesFlagsAnycast
         INTEGER,
      sr1646v2XEfmPppOEIpV6AddressesTimersValidLifeTime
         TimeTicks,
      sr1646v2XEfmPppOEIpV6AddressesTimersPrefLifeTime
         TimeTicks
      }

sr1646v2XEfmPppOEIpV6AddressesTableIx OBJECT-TYPE
   SYNTAX      TableIndex
   MAX-ACCESS  not-accessible
   STATUS      current
   DESCRIPTION
      ""
   ::= {sr1646v2XEfmPppOEIpV6AddressesEntry 11}

sr1646v2XEfmPppOEIpV6AddressesAddress OBJECT-TYPE
   SYNTAX      Ipv6Address
   MAX-ACCESS  read-only
   STATUS      current
   DESCRIPTION
      "Path: efm.status.pppoEClient.ipV6.addresses.address

       ipv6 address"
   ::= {sr1646v2XEfmPppOEIpV6AddressesEntry 16777216}

sr1646v2XEfmPppOEIpV6AddressesPrefixLength OBJECT-TYPE
   SYNTAX      Integer32
   MAX-ACCESS  read-only
   STATUS      current
   DESCRIPTION
      "Path: efm.status.pppoEClient.ipV6.addresses.prefixLength"
   ::= {sr1646v2XEfmPppOEIpV6AddressesEntry 33554432}

sr1646v2XEfmPppOEIpV6AddressesStatus OBJECT-TYPE
   SYNTAX      INTEGER
               {
               invalid (0),
               tentative (1),
               deprecated (2),
               preferred (3)
               }
   MAX-ACCESS  read-only
   STATUS      current
   DESCRIPTION
      "Path: efm.status.pppoEClient.ipV6.addresses.status

       Possibilities:
               invalid   (0)
               tentative   (1)
               deprecated   (2)
               preferred   (3)"
   ::= {sr1646v2XEfmPppOEIpV6AddressesEntry 50331648}

sr1646v2XEfmPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.pppoEClient.ipV6.addresses.origin

       Possibilities:
               unknown   (0)
               manual   (1)
               generalPrefix   (2)
               statelessAuto   (3)
               statefullAuto   (4)"
   ::= {sr1646v2XEfmPppOEIpV6AddressesEntry 67108864}

sr1646v2XEfmPppOEIpV6AddressesFlagsInterfaceId OBJECT-TYPE
   SYNTAX      INTEGER
               {
               no (0),
               yes (1)
               }
   MAX-ACCESS  read-only
   STATUS      current
   DESCRIPTION
      "Path: efm.status.pppoEClient.ipV6.addresses.flags.interfaceId

       Possibilities:
               no   (0)
               yes   (1)"
   ::= {sr1646v2XEfmPppOEIpV6AddressesEntry 83951616}

sr1646v2XEfmPppOEIpV6AddressesFlagsAnycast OBJECT-TYPE
   SYNTAX      INTEGER
               {
               no (0),
               yes (1)
               }
   MAX-ACCESS  read-only
   STATUS      current
   DESCRIPTION
      "Path: efm.status.pppoEClient.ipV6.addresses.flags.anycast

       Possibilities:
               no   (0)
               yes   (1)"
   ::= {sr1646v2XEfmPppOEIpV6AddressesEntry 84017152}

sr1646v2XEfmPppOEIpV6AddressesTimersValidLifeTime OBJECT-TYPE
   SYNTAX      TimeTicks
   MAX-ACCESS  read-only
   STATUS      current
   DESCRIPTION
      "Path: efm.status.pppoEClient.ipV6.addresses.timers.validLifeTime

       Time in centi-second."
   ::= {sr1646v2XEfmPppOEIpV6AddressesEntry 100794368}

sr1646v2XEfmPppOEIpV6AddressesTimersPrefLifeTime OBJECT-TYPE
   SYNTAX      TimeTicks
   MAX-ACCESS  read-only
   STATUS      current
   DESCRIPTION
      "Path: efm.status.pppoEClient.ipV6.addresses.timers.prefLifeTime

       Time in centi-second."
   ::= {sr1646v2XEfmPppOEIpV6AddressesEntry 100728832}


sr1646v2XEfmDot1x OBJECT IDENTIFIER ::= {sr1646v2XEfm 190}

sr1646v2XEfmDot1xSSCTable OBJECT-TYPE
   SYNTAX      SEQUENCE OF Sr1646v2XEfmDot1xEntry
   MAX-ACCESS  not-accessible
   STATUS      current
   DESCRIPTION
      "Ethernet Switch VLAN Table"
   ::= {sr1646v2XEfmDot1x 1}

sr1646v2XEfmDot1xEntry OBJECT-TYPE
   SYNTAX      Sr1646v2XEfmDot1xEntry
   MAX-ACCESS  not-accessible
   STATUS      current
   DESCRIPTION
      ""
   INDEX      { sr1646v2XEfmDot1xTableIx }
   ::= {sr1646v2XEfmDot1xSSCTable 1}

Sr1646v2XEfmDot1xEntry ::=
   SEQUENCE
      {
      sr1646v2XEfmDot1xTableIx
         TableIndex,
      sr1646v2XEfmDot1xRemote
         OCTET STRING,
      sr1646v2XEfmDot1xAuthorized
         INTEGER,
      sr1646v2XEfmDot1xAuthenticator
         INTEGER,
      sr1646v2XEfmDot1xBackEnd
         INTEGER,
      sr1646v2XEfmDot1xRetries
         Integer32,
      sr1646v2XEfmDot1xReAuthTime
         TimeTicks,
      sr1646v2XEfmDot1xHoldTime
         TimeTicks
      }

sr1646v2XEfmDot1xTableIx OBJECT-TYPE
   SYNTAX      TableIndex
   MAX-ACCESS  not-accessible
   STATUS      current
   DESCRIPTION
      ""
   ::= {sr1646v2XEfmDot1xEntry 11}

sr1646v2XEfmDot1xRemote OBJECT-TYPE
   SYNTAX      OCTET STRING
   MAX-ACCESS  read-only
   STATUS      current
   DESCRIPTION
      "Path: efm.status.dot1x.remote

       MAC address."
   ::= {sr1646v2XEfmDot1xEntry 16777216}

sr1646v2XEfmDot1xAuthorized OBJECT-TYPE
   SYNTAX      INTEGER
               {
               no (0),
               yes (1)
               }
   MAX-ACCESS  read-only
   STATUS      current
   DESCRIPTION
      "Path: efm.status.dot1x.authorized

       Possibilities:
               no   (0)
               yes   (1)"
   ::= {sr1646v2XEfmDot1xEntry 33554432}

sr1646v2XEfmDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: efm.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2XEfmDot1xEntry 50331648}

sr1646v2XEfmDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: efm.status.dot1x.backEnd

       Possibilities:
               preInit   (0)
               initialize   (1)
               idle   (2)
               request   (3)
               response   (4)
               success   (5)
               failure   (6)
               radiusTimeout   (7)
               timeout   (8)"
   ::= {sr1646v2XEfmDot1xEntry 67108864}

sr1646v2XEfmDot1xRetries OBJECT-TYPE
   SYNTAX      Integer32
   MAX-ACCESS  read-only
   STATUS      current
   DESCRIPTION
      "Path: efm.status.dot1x.retries"
   ::= {sr1646v2XEfmDot1xEntry 83886080}

sr1646v2XEfmDot1xReAuthTime OBJECT-TYPE
   SYNTAX      TimeTicks
   MAX-ACCESS  read-only
   STATUS      current
   DESCRIPTION
      "Path: efm.status.dot1x.reAuthTime

       Time in centi-second."
   ::= {sr1646v2XEfmDot1xEntry 100663296}

sr1646v2XEfmDot1xHoldTime OBJECT-TYPE
   SYNTAX      TimeTicks
   MAX-ACCESS  read-only
   STATUS      current
   DESCRIPTION
      "Path: efm.status.dot1x.holdTime

       Time in centi-second."
   ::= {sr1646v2XEfmDot1xEntry 117440512}


sr1646v2XEfmSnmpIndex OBJECT-TYPE
   SYNTAX      Integer32
   MAX-ACCESS  read-only
   STATUS      current
   DESCRIPTION
      "Path: efm.status.snmpIndex
       Info: SNMP index assigned to this object"
   ::= {sr1646v2XEfm 269}



pr1646v2XEfm OBJECT IDENTIFIER ::= {r1646v2XEfm 12}


pr1646v2XEfmInOctets OBJECT-TYPE
   SYNTAX      Counter64
   MAX-ACCESS  read-only
   STATUS      current
   DESCRIPTION
      "Path: efm.performance.ifInOctets
       Info: ifInOctets

       64 bit unsigned wrappable counter."
   ::= {pr1646v2XEfm 109}


pr1646v2XEfmInUcast OBJECT-TYPE
   SYNTAX      Counter64
   MAX-ACCESS  read-only
   STATUS      current
   DESCRIPTION
      "Path: efm.performance.ifInUcastPkts
       Info: ifInUcastPkts

       64 bit unsigned wrappable counter."
   ::= {pr1646v2XEfm 110}


pr1646v2XEfmInNUcastPkts OBJECT-TYPE
   SYNTAX      Counter64
   MAX-ACCESS  read-only
   STATUS      current
   DESCRIPTION
      "Path: efm.performance.ifInNUcastPkts
       Info: ifInNUcastPkts

       64 bit unsigned wrappable counter."
   ::= {pr1646v2XEfm 111}


pr1646v2XEfmInBcastPkts OBJECT-TYPE
   SYNTAX      Counter64
   MAX-ACCESS  read-only
   STATUS      current
   DESCRIPTION
      "Path: efm.performance.ifInBcastPkts
       Info: ifInBcastPkts

       64 bit unsigned wrappable counter."
   ::= {pr1646v2XEfm 211}


pr1646v2XEfmInMcastPkts OBJECT-TYPE
   SYNTAX      Counter64
   MAX-ACCESS  read-only
   STATUS      current
   DESCRIPTION
      "Path: efm.performance.ifInMcastPkts
       Info: ifInNUcastPkts

       64 bit unsigned wrappable counter."
   ::= {pr1646v2XEfm 221}


pr1646v2XEfmInDiscards OBJECT-TYPE
   SYNTAX      Counter64
   MAX-ACCESS  read-only
   STATUS      current
   DESCRIPTION
      "Path: efm.performance.ifInDiscards
       Info: ifInDiscards

       64 bit unsigned wrappable counter."
   ::= {pr1646v2XEfm 112}


pr1646v2XEfmInErrors OBJECT-TYPE
   SYNTAX      Counter64
   MAX-ACCESS  read-only
   STATUS      current
   DESCRIPTION
      "Path: efm.performance.ifInErrors
       Info: ifInErrors

       64 bit unsigned wrappable counter."
   ::= {pr1646v2XEfm 113}


pr1646v2XEfmInUnknownProtos OBJECT-TYPE
   SYNTAX      Counter64
   MAX-ACCESS  read-only
   STATUS      current
   DESCRIPTION
      "Path: efm.performance.ifInUnknownProtos
       Info: ifInUnknownprotos

       64 bit unsigned wrappable counter."
   ::= {pr1646v2XEfm 114}


pr1646v2XEfmInQLen OBJECT-TYPE
   SYNTAX      Gauge32
   MAX-ACCESS  read-only
   STATUS      current
   DESCRIPTION
      "Path: efm.performance.ifInQLen
       Info: ifInQLen

       32 bit unsigned gauge value."
   ::= {pr1646v2XEfm 128}


pr1646v2XEfmInDropEx OBJECT-TYPE
   SYNTAX      Counter64
   MAX-ACCESS  read-only
   STATUS      current
   DESCRIPTION
      "Path: efm.performance.ifInDropLevelExceeded
       Info: ifInDiscards

       64 bit unsigned wrappable counter."
   ::= {pr1646v2XEfm 130}


pr1646v2XEfmInDropNoMac OBJECT-TYPE
   SYNTAX      Counter64
   MAX-ACCESS  read-only
   STATUS      current
   DESCRIPTION
      "Path: efm.performance.ifInDiscardsNoMacFit
       Info: ifInDiscards

       64 bit unsigned wrappable counter."
   ::= {pr1646v2XEfm 133}


pr1646v2XEfmInDropNUCast OBJECT-TYPE
   SYNTAX      Counter64
   MAX-ACCESS  read-only
   STATUS      current
   DESCRIPTION
      "Path: efm.performance.ifInDiscardsNUCast
       Info: ifInDiscards

       64 bit unsigned wrappable counter."
   ::= {pr1646v2XEfm 136}


pr1646v2XEfmInDropFilter OBJECT-TYPE
   SYNTAX      Counter64
   MAX-ACCESS  read-only
   STATUS      current
   DESCRIPTION
      "Path: efm.performance.ifInDiscardsFilter
       Info: ifInDiscards

       64 bit unsigned wrappable counter."
   ::= {pr1646v2XEfm 137}


pr1646v2XEfmInQueues OBJECT IDENTIFIER ::= {pr1646v2XEfm 131}

pr1646v2XEfmInQueuesSSCTable OBJECT-TYPE
   SYNTAX      SEQUENCE OF Pr1646v2XEfmInQueuesEntry
   MAX-ACCESS  not-accessible
   STATUS      current
   DESCRIPTION
      "Queue Lengths"
   ::= {pr1646v2XEfmInQueues 1}

pr1646v2XEfmInQueuesEntry OBJECT-TYPE
   SYNTAX      Pr1646v2XEfmInQueuesEntry
   MAX-ACCESS  not-accessible
   STATUS      current
   DESCRIPTION
      ""
   INDEX      { pr1646v2XEfmInQueuesTableIx }
   ::= {pr1646v2XEfmInQueuesSSCTable 1}

Pr1646v2XEfmInQueuesEntry ::=
   SEQUENCE
      {
      pr1646v2XEfmInQueuesTableIx
         TableIndex,
      pr1646v2XEfmInQueuesName
         INTEGER,
      pr1646v2XEfmInQueuesLength
         Integer32,
      pr1646v2XEfmInQueuesOctetLength
         Integer32,
      pr1646v2XEfmInQueuesRedLength
         Integer32,
      pr1646v2XEfmInQueuesPacketsTotal
         Counter64,
      pr1646v2XEfmInQueuesPacketsDirectTx
         Counter64,
      pr1646v2XEfmInQueuesPacketsQueued
         Counter64,
      pr1646v2XEfmInQueuesPacketsDropped
         Counter64,
      pr1646v2XEfmInQueuesPacketsRedDropped
         Counter64,
      pr1646v2XEfmInQueuesPacketsCirTx
         Counter64,
      pr1646v2XEfmInQueuesPacketsEirTx
         Counter64,
      pr1646v2XEfmInQueuesPacketsViolateTx
         Counter64,
      pr1646v2XEfmInQueuesOctetsTotal
         Counter64,
      pr1646v2XEfmInQueuesOctetsDirectTx
         Counter64,
      pr1646v2XEfmInQueuesOctetsQueued
         Counter64,
      pr1646v2XEfmInQueuesOctetsDropped
         Counter64,
      pr1646v2XEfmInQueuesOctetsRedDropped
         Counter64,
      pr1646v2XEfmInQueuesOctetsCirTx
         Counter64,
      pr1646v2XEfmInQueuesOctetsEirTx
         Counter64,
      pr1646v2XEfmInQueuesOctetsViolateTx
         Counter64,
      pr1646v2XEfmInQueuesOctetsBandwidth15sec
         Integer32,
      pr1646v2XEfmInQueuesOctetsBandwidth30sec
         Integer32,
      pr1646v2XEfmInQueuesOctetsBandwidth1min
         Integer32,
      pr1646v2XEfmInQueuesOctetsBandwidth2min
         Integer32,
      pr1646v2XEfmInQueuesOctetsBandwidth5min
         Integer32
      }

pr1646v2XEfmInQueuesTableIx OBJECT-TYPE
   SYNTAX      TableIndex
   MAX-ACCESS  not-accessible
   STATUS      current
   DESCRIPTION
      ""
   ::= {pr1646v2XEfmInQueuesEntry 11}

pr1646v2XEfmInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2XEfmInQueuesEntry 16777216}

pr1646v2XEfmInQueuesLength OBJECT-TYPE
   SYNTAX      Integer32
   MAX-ACCESS  read-only
   STATUS      current
   DESCRIPTION
      "Path: efm.performance.ifInPriorityQueues.length"
   ::= {pr1646v2XEfmInQueuesEntry 33554432}

pr1646v2XEfmInQueuesOctetLength OBJECT-TYPE
   SYNTAX      Integer32
   MAX-ACCESS  read-only
   STATUS      current
   DESCRIPTION
      "Path: efm.performance.ifInPriorityQueues.octetLength"
   ::= {pr1646v2XEfmInQueuesEntry 150994944}

pr1646v2XEfmInQueuesRedLength OBJECT-TYPE
   SYNTAX      Integer32
   MAX-ACCESS  read-only
   STATUS      current
   DESCRIPTION
      "Path: efm.performance.ifInPriorityQueues.redLength"
   ::= {pr1646v2XEfmInQueuesEntry 134217728}

pr1646v2XEfmInQueuesPacketsTotal OBJECT-TYPE
   SYNTAX      Counter64
   MAX-ACCESS  read-only
   STATUS      current
   DESCRIPTION
      "Path: efm.performance.ifInPriorityQueues.packets.total

       64 bit unsigned wrappable counter."
   ::= {pr1646v2XEfmInQueuesEntry 50790400}

pr1646v2XEfmInQueuesPacketsDirectTx OBJECT-TYPE
   SYNTAX      Counter64
   MAX-ACCESS  read-only
   STATUS      current
   DESCRIPTION
      "Path: efm.performance.ifInPriorityQueues.packets.directTx

       64 bit unsigned wrappable counter."
   ::= {pr1646v2XEfmInQueuesEntry 50397184}

pr1646v2XEfmInQueuesPacketsQueued OBJECT-TYPE
   SYNTAX      Counter64
   MAX-ACCESS  read-only
   STATUS      current
   DESCRIPTION
      "Path: efm.performance.ifInPriorityQueues.packets.queued

       64 bit unsigned wrappable counter."
   ::= {pr1646v2XEfmInQueuesEntry 50462720}

pr1646v2XEfmInQueuesPacketsDropped OBJECT-TYPE
   SYNTAX      Counter64
   MAX-ACCESS  read-only
   STATUS      current
   DESCRIPTION
      "Path: efm.performance.ifInPriorityQueues.packets.dropped

       64 bit unsigned wrappable counter."
   ::= {pr1646v2XEfmInQueuesEntry 50528256}

pr1646v2XEfmInQueuesPacketsRedDropped OBJECT-TYPE
   SYNTAX      Counter64
   MAX-ACCESS  read-only
   STATUS      current
   DESCRIPTION
      "Path: efm.performance.ifInPriorityQueues.packets.redDropped

       64 bit unsigned wrappable counter."
   ::= {pr1646v2XEfmInQueuesEntry 50724864}

pr1646v2XEfmInQueuesPacketsCirTx OBJECT-TYPE
   SYNTAX      Counter64
   MAX-ACCESS  read-only
   STATUS      current
   DESCRIPTION
      "Path: efm.performance.ifInPriorityQueues.packets.cirTx

       64 bit unsigned wrappable counter."
   ::= {pr1646v2XEfmInQueuesEntry 50593792}

pr1646v2XEfmInQueuesPacketsEirTx OBJECT-TYPE
   SYNTAX      Counter64
   MAX-ACCESS  read-only
   STATUS      current
   DESCRIPTION
      "Path: efm.performance.ifInPriorityQueues.packets.eirTx

       64 bit unsigned wrappable counter."
   ::= {pr1646v2XEfmInQueuesEntry 50659328}

pr1646v2XEfmInQueuesPacketsViolateTx OBJECT-TYPE
   SYNTAX      Counter64
   MAX-ACCESS  read-only
   STATUS      current
   DESCRIPTION
      "Path: efm.performance.ifInPriorityQueues.packets.violateTx

       64 bit unsigned wrappable counter."
   ::= {pr1646v2XEfmInQueuesEntry 50855936}

pr1646v2XEfmInQueuesOctetsTotal OBJECT-TYPE
   SYNTAX      Counter64
   MAX-ACCESS  read-only
   STATUS      current
   DESCRIPTION
      "Path: efm.performance.ifInPriorityQueues.octets.total

       64 bit unsigned wrappable counter."
   ::= {pr1646v2XEfmInQueuesEntry 67567616}

pr1646v2XEfmInQueuesOctetsDirectTx OBJECT-TYPE
   SYNTAX      Counter64
   MAX-ACCESS  read-only
   STATUS      current
   DESCRIPTION
      "Path: efm.performance.ifInPriorityQueues.octets.directTx

       64 bit unsigned wrappable counter."
   ::= {pr1646v2XEfmInQueuesEntry 67174400}

pr1646v2XEfmInQueuesOctetsQueued OBJECT-TYPE
   SYNTAX      Counter64
   MAX-ACCESS  read-only
   STATUS      current
   DESCRIPTION
      "Path: efm.performance.ifInPriorityQueues.octets.queued

       64 bit unsigned wrappable counter."
   ::= {pr1646v2XEfmInQueuesEntry 67239936}

pr1646v2XEfmInQueuesOctetsDropped OBJECT-TYPE
   SYNTAX      Counter64
   MAX-ACCESS  read-only
   STATUS      current
   DESCRIPTION
      "Path: efm.performance.ifInPriorityQueues.octets.dropped

       64 bit unsigned wrappable counter."
   ::= {pr1646v2XEfmInQueuesEntry 67305472}

pr1646v2XEfmInQueuesOctetsRedDropped OBJECT-TYPE
   SYNTAX      Counter64
   MAX-ACCESS  read-only
   STATUS      current
   DESCRIPTION
      "Path: efm.performance.ifInPriorityQueues.octets.redDropped

       64 bit unsigned wrappable counter."
   ::= {pr1646v2XEfmInQueuesEntry 67502080}

pr1646v2XEfmInQueuesOctetsCirTx OBJECT-TYPE
   SYNTAX      Counter64
   MAX-ACCESS  read-only
   STATUS      current
   DESCRIPTION
      "Path: efm.performance.ifInPriorityQueues.octets.cirTx

       64 bit unsigned wrappable counter."
   ::= {pr1646v2XEfmInQueuesEntry 67371008}

pr1646v2XEfmInQueuesOctetsEirTx OBJECT-TYPE
   SYNTAX      Counter64
   MAX-ACCESS  read-only
   STATUS      current
   DESCRIPTION
      "Path: efm.performance.ifInPriorityQueues.octets.eirTx

       64 bit unsigned wrappable counter."
   ::= {pr1646v2XEfmInQueuesEntry 67436544}

pr1646v2XEfmInQueuesOctetsViolateTx OBJECT-TYPE
   SYNTAX      Counter64
   MAX-ACCESS  read-only
   STATUS      current
   DESCRIPTION
      "Path: efm.performance.ifInPriorityQueues.octets.violateTx

       64 bit unsigned wrappable counter."
   ::= {pr1646v2XEfmInQueuesEntry 67633152}

pr1646v2XEfmInQueuesOctetsBandwidth15sec OBJECT-TYPE
   SYNTAX      Integer32
   MAX-ACCESS  read-only
   STATUS      current
   DESCRIPTION
      "Path: efm.performance.ifInPriorityQueues.octets.bandwidth.15sec

       unit name = bps
       formula = 8 * ; 8 /"
   ::= {pr1646v2XEfmInQueuesEntry 70386944}

pr1646v2XEfmInQueuesOctetsBandwidth30sec OBJECT-TYPE
   SYNTAX      Integer32
   MAX-ACCESS  read-only
   STATUS      current
   DESCRIPTION
      "Path: efm.performance.ifInPriorityQueues.octets.bandwidth.30sec

       unit name = bps
       formula = 8 * ; 8 /"
   ::= {pr1646v2XEfmInQueuesEntry 70388224}

pr1646v2XEfmInQueuesOctetsBandwidth1min OBJECT-TYPE
   SYNTAX      Integer32
   MAX-ACCESS  read-only
   STATUS      current
   DESCRIPTION
      "Path: efm.performance.ifInPriorityQueues.octets.bandwidth.1min

       unit name = bps
       formula = 8 * ; 8 /"
   ::= {pr1646v2XEfmInQueuesEntry 70390784}

pr1646v2XEfmInQueuesOctetsBandwidth2min OBJECT-TYPE
   SYNTAX      Integer32
   MAX-ACCESS  read-only
   STATUS      current
   DESCRIPTION
      "Path: efm.performance.ifInPriorityQueues.octets.bandwidth.2min

       unit name = bps
       formula = 8 * ; 8 /"
   ::= {pr1646v2XEfmInQueuesEntry 70395904}

pr1646v2XEfmInQueuesOctetsBandwidth5min OBJECT-TYPE
   SYNTAX      Integer32
   MAX-ACCESS  read-only
   STATUS      current
   DESCRIPTION
      "Path: efm.performance.ifInPriorityQueues.octets.bandwidth.5min

       unit name = bps
       formula = 8 * ; 8 /"
   ::= {pr1646v2XEfmInQueuesEntry 70411264}

pr1646v2XEfmInQueuesH2Performance OBJECT-TYPE
   SYNTAX      SEQUENCE OF Pr1646v2XEfmInQueuesH2PerformanceEntry
   MAX-ACCESS  not-accessible
   STATUS      current
   DESCRIPTION
      ""
   ::= {pr1646v2XEfmInQueues 83886080}

pr1646v2XEfmInQueuesH2PerformanceEntry OBJECT-TYPE
   SYNTAX      Pr1646v2XEfmInQueuesH2PerformanceEntry
   MAX-ACCESS  not-accessible
   STATUS      current
   DESCRIPTION
      ""
   INDEX      { pr1646v2XEfmInQueuesTableIx,
                pr1646v2XEfmInQueuesH2PerformanceTableIx }
   ::= {pr1646v2XEfmInQueuesH2Performance 1}

Pr1646v2XEfmInQueuesH2PerformanceEntry ::=
   SEQUENCE
      {
      pr1646v2XEfmInQueuesH2PerformanceTableIx
         TableIndex,
      pr1646v2XEfmInQueuesH2PerformanceSysUpTime
         TimeTicks,
      pr1646v2XEfmInQueuesH2PerformanceTotPkts
         Counter64,
      pr1646v2XEfmInQueuesH2PerformanceDirTxPkts
         Counter64,
      pr1646v2XEfmInQueuesH2PerformanceQdPkts
         Counter64,
      pr1646v2XEfmInQueuesH2PerformanceDropPkts
         Counter64,
      pr1646v2XEfmInQueuesH2PerformanceRDropPkts
         Counter64,
      pr1646v2XEfmInQueuesH2PerformanceCirTxPkts
         Counter64,
      pr1646v2XEfmInQueuesH2PerformanceEirTxPkts
         Counter64,
      pr1646v2XEfmInQueuesH2PerformanceViolTxPkts
         Counter64,
      pr1646v2XEfmInQueuesH2PerformanceTotOcts
         Counter64,
      pr1646v2XEfmInQueuesH2PerformanceDirTxOcts
         Counter64,
      pr1646v2XEfmInQueuesH2PerformanceQdOcts
         Counter64,
      pr1646v2XEfmInQueuesH2PerformanceDropOcts
         Counter64,
      pr1646v2XEfmInQueuesH2PerformanceRDropOcts
         Counter64,
      pr1646v2XEfmInQueuesH2PerformanceCirTxOcts
         Counter64,
      pr1646v2XEfmInQueuesH2PerformanceEirTxOcts
         Counter64,
      pr1646v2XEfmInQueuesH2PerformanceViolTxOcts
         Counter64,
      pr1646v2XEfmInQueuesH2PerformanceBandwidth
         Integer32
      }

pr1646v2XEfmInQueuesH2PerformanceTableIx OBJECT-TYPE
   SYNTAX      TableIndex
   MAX-ACCESS  not-accessible
   STATUS      current
   DESCRIPTION
      ""
   ::= {pr1646v2XEfmInQueuesH2PerformanceEntry 11}

pr1646v2XEfmInQueuesH2PerformanceSysUpTime OBJECT-TYPE
   SYNTAX      TimeTicks
   MAX-ACCESS  read-only
   STATUS      current
   DESCRIPTION
      "Path: efm.performance.ifInPriorityQueues.h2Performance.sysUpTime

       Time in centi-second."
   ::= {pr1646v2XEfmInQueuesH2PerformanceEntry 16777216}

pr1646v2XEfmInQueuesH2PerformanceTotPkts OBJECT-TYPE
   SYNTAX      Counter64
   MAX-ACCESS  read-only
   STATUS      current
   DESCRIPTION
      "Path: efm.performance.ifInPriorityQueues.h2Performance.totalPkts

       64 bit unsigned wrappable counter."
   ::= {pr1646v2XEfmInQueuesH2PerformanceEntry 234881024}

pr1646v2XEfmInQueuesH2PerformanceDirTxPkts OBJECT-TYPE
   SYNTAX      Counter64
   MAX-ACCESS  read-only
   STATUS      current
   DESCRIPTION
      "Path: efm.performance.ifInPriorityQueues.h2Performance.directTxPkts

       64 bit unsigned wrappable counter."
   ::= {pr1646v2XEfmInQueuesH2PerformanceEntry 33554432}

pr1646v2XEfmInQueuesH2PerformanceQdPkts OBJECT-TYPE
   SYNTAX      Counter64
   MAX-ACCESS  read-only
   STATUS      current
   DESCRIPTION
      "Path: efm.performance.ifInPriorityQueues.h2Performance.queuedPkts

       64 bit unsigned wrappable counter."
   ::= {pr1646v2XEfmInQueuesH2PerformanceEntry 50331648}

pr1646v2XEfmInQueuesH2PerformanceDropPkts OBJECT-TYPE
   SYNTAX      Counter64
   MAX-ACCESS  read-only
   STATUS      current
   DESCRIPTION
      "Path: efm.performance.ifInPriorityQueues.h2Performance.droppedPkts

       64 bit unsigned wrappable counter."
   ::= {pr1646v2XEfmInQueuesH2PerformanceEntry 67108864}

pr1646v2XEfmInQueuesH2PerformanceRDropPkts OBJECT-TYPE
   SYNTAX      Counter64
   MAX-ACCESS  read-only
   STATUS      current
   DESCRIPTION
      "Path: efm.performance.ifInPriorityQueues.h2Performance.redDroppedPkts

       64 bit unsigned wrappable counter."
   ::= {pr1646v2XEfmInQueuesH2PerformanceEntry 201326592}

pr1646v2XEfmInQueuesH2PerformanceCirTxPkts OBJECT-TYPE
   SYNTAX      Counter64
   MAX-ACCESS  read-only
   STATUS      current
   DESCRIPTION
      "Path: efm.performance.ifInPriorityQueues.h2Performance.cirTxPkts

       64 bit unsigned wrappable counter."
   ::= {pr1646v2XEfmInQueuesH2PerformanceEntry 83886080}

pr1646v2XEfmInQueuesH2PerformanceEirTxPkts OBJECT-TYPE
   SYNTAX      Counter64
   MAX-ACCESS  read-only
   STATUS      current
   DESCRIPTION
      "Path: efm.performance.ifInPriorityQueues.h2Performance.eirTxPkts

       64 bit unsigned wrappable counter."
   ::= {pr1646v2XEfmInQueuesH2PerformanceEntry 100663296}

pr1646v2XEfmInQueuesH2PerformanceViolTxPkts OBJECT-TYPE
   SYNTAX      Counter64
   MAX-ACCESS  read-only
   STATUS      current
   DESCRIPTION
      "Path: efm.performance.ifInPriorityQueues.h2Performance.violateTxPkts

       64 bit unsigned wrappable counter."
   ::= {pr1646v2XEfmInQueuesH2PerformanceEntry 301989888}

pr1646v2XEfmInQueuesH2PerformanceTotOcts OBJECT-TYPE
   SYNTAX      Counter64
   MAX-ACCESS  read-only
   STATUS      current
   DESCRIPTION
      "Path: efm.performance.ifInPriorityQueues.h2Performance.totalOctets

       64 bit unsigned wrappable counter."
   ::= {pr1646v2XEfmInQueuesH2PerformanceEntry 251658240}

pr1646v2XEfmInQueuesH2PerformanceDirTxOcts OBJECT-TYPE
   SYNTAX      Counter64
   MAX-ACCESS  read-only
   STATUS      current
   DESCRIPTION
      "Path: efm.performance.ifInPriorityQueues.h2Performance.directTxOctets

       64 bit unsigned wrappable counter."
   ::= {pr1646v2XEfmInQueuesH2PerformanceEntry 117440512}

pr1646v2XEfmInQueuesH2PerformanceQdOcts OBJECT-TYPE
   SYNTAX      Counter64
   MAX-ACCESS  read-only
   STATUS      current
   DESCRIPTION
      "Path: efm.performance.ifInPriorityQueues.h2Performance.queuedOctets

       64 bit unsigned wrappable counter."
   ::= {pr1646v2XEfmInQueuesH2PerformanceEntry 134217728}

pr1646v2XEfmInQueuesH2PerformanceDropOcts OBJECT-TYPE
   SYNTAX      Counter64
   MAX-ACCESS  read-only
   STATUS      current
   DESCRIPTION
      "Path: efm.performance.ifInPriorityQueues.h2Performance.droppedOctets

       64 bit unsigned wrappable counter."
   ::= {pr1646v2XEfmInQueuesH2PerformanceEntry 150994944}

pr1646v2XEfmInQueuesH2PerformanceRDropOcts OBJECT-TYPE
   SYNTAX      Counter64
   MAX-ACCESS  read-only
   STATUS      current
   DESCRIPTION
      "Path: efm.performance.ifInPriorityQueues.h2Performance.redDroppedOctets

       64 bit unsigned wrappable counter."
   ::= {pr1646v2XEfmInQueuesH2PerformanceEntry 218103808}

pr1646v2XEfmInQueuesH2PerformanceCirTxOcts OBJECT-TYPE
   SYNTAX      Counter64
   MAX-ACCESS  read-only
   STATUS      current
   DESCRIPTION
      "Path: efm.performance.ifInPriorityQueues.h2Performance.cirTxOctets

       64 bit unsigned wrappable counter."
   ::= {pr1646v2XEfmInQueuesH2PerformanceEntry 167772160}

pr1646v2XEfmInQueuesH2PerformanceEirTxOcts OBJECT-TYPE
   SYNTAX      Counter64
   MAX-ACCESS  read-only
   STATUS      current
   DESCRIPTION
      "Path: efm.performance.ifInPriorityQueues.h2Performance.eirTxOctets

       64 bit unsigned wrappable counter."
   ::= {pr1646v2XEfmInQueuesH2PerformanceEntry 184549376}

pr1646v2XEfmInQueuesH2PerformanceViolTxOcts OBJECT-TYPE
   SYNTAX      Counter64
   MAX-ACCESS  read-only
   STATUS      current
   DESCRIPTION
      "Path: efm.performance.ifInPriorityQueues.h2Performance.violateTxOctets

       64 bit unsigned wrappable counter."
   ::= {pr1646v2XEfmInQueuesH2PerformanceEntry 318767104}

pr1646v2XEfmInQueuesH2PerformanceBandwidth OBJECT-TYPE
   SYNTAX      Integer32
   MAX-ACCESS  read-only
   STATUS      current
   DESCRIPTION
      "Path: efm.performance.ifInPriorityQueues.h2Performance.bandwidth

       unit name = bps
       formula = 8 * ; 8 /"
   ::= {pr1646v2XEfmInQueuesH2PerformanceEntry 268435456}

pr1646v2XEfmInQueuesH24Performance OBJECT-TYPE
   SYNTAX      SEQUENCE OF Pr1646v2XEfmInQueuesH24PerformanceEntry
   MAX-ACCESS  not-accessible
   STATUS      current
   DESCRIPTION
      ""
   ::= {pr1646v2XEfmInQueues 100663296}

pr1646v2XEfmInQueuesH24PerformanceEntry OBJECT-TYPE
   SYNTAX      Pr1646v2XEfmInQueuesH24PerformanceEntry
   MAX-ACCESS  not-accessible
   STATUS      current
   DESCRIPTION
      ""
   INDEX      { pr1646v2XEfmInQueuesTableIx,
                pr1646v2XEfmInQueuesH24PerformanceTableIx }
   ::= {pr1646v2XEfmInQueuesH24Performance 1}

Pr1646v2XEfmInQueuesH24PerformanceEntry ::=
   SEQUENCE
      {
      pr1646v2XEfmInQueuesH24PerformanceTableIx
         TableIndex,
      pr1646v2XEfmInQueuesH24PerformanceSysUpTime
         TimeTicks,
      pr1646v2XEfmInQueuesH24PerformanceTotPkts
         Counter64,
      pr1646v2XEfmInQueuesH24PerformanceDirTxPkts
         Counter64,
      pr1646v2XEfmInQueuesH24PerformanceQdPkts
         Counter64,
      pr1646v2XEfmInQueuesH24PerformanceDropPkts
         Counter64,
      pr1646v2XEfmInQueuesH24PerformanceRDropPkts
         Counter64,
      pr1646v2XEfmInQueuesH24PerformanceCirTxPkts
         Counter64,
      pr1646v2XEfmInQueuesH24PerformanceEirTxPkts
         Counter64,
      pr1646v2XEfmInQueuesH24PerformanceViolTxPkts
         Counter64,
      pr1646v2XEfmInQueuesH24PerformanceTotOcts
         Counter64,
      pr1646v2XEfmInQueuesH24PerformanceDirTxOcts
         Counter64,
      pr1646v2XEfmInQueuesH24PerformanceQdOcts
         Counter64,
      pr1646v2XEfmInQueuesH24PerformanceDropOcts
         Counter64,
      pr1646v2XEfmInQueuesH24PerformanceRDropOcts
         Counter64,
      pr1646v2XEfmInQueuesH24PerformanceCirTxOcts
         Counter64,
      pr1646v2XEfmInQueuesH24PerformanceEirTxOcts
         Counter64,
      pr1646v2XEfmInQueuesH24PerformanceViolTxOcts
         Counter64,
      pr1646v2XEfmInQueuesH24PerformanceBandwidth
         Integer32
      }

pr1646v2XEfmInQueuesH24PerformanceTableIx OBJECT-TYPE
   SYNTAX      TableIndex
   MAX-ACCESS  not-accessible
   STATUS      current
   DESCRIPTION
      ""
   ::= {pr1646v2XEfmInQueuesH24PerformanceEntry 11}

pr1646v2XEfmInQueuesH24PerformanceSysUpTime OBJECT-TYPE
   SYNTAX      TimeTicks
   MAX-ACCESS  read-only
   STATUS      current
   DESCRIPTION
      "Path: efm.performance.ifInPriorityQueues.h24Performance.sysUpTime

       Time in centi-second."
   ::= {pr1646v2XEfmInQueuesH24PerformanceEntry 16777216}

pr1646v2XEfmInQueuesH24PerformanceTotPkts OBJECT-TYPE
   SYNTAX      Counter64
   MAX-ACCESS  read-only
   STATUS      current
   DESCRIPTION
      "Path: efm.performance.ifInPriorityQueues.h24Performance.totalPkts

       64 bit unsigned wrappable counter."
   ::= {pr1646v2XEfmInQueuesH24PerformanceEntry 234881024}

pr1646v2XEfmInQueuesH24PerformanceDirTxPkts OBJECT-TYPE
   SYNTAX      Counter64
   MAX-ACCESS  read-only
   STATUS      current
   DESCRIPTION
      "Path: efm.performance.ifInPriorityQueues.h24Performance.directTxPkts

       64 bit unsigned wrappable counter."
   ::= {pr1646v2XEfmInQueuesH24PerformanceEntry 33554432}

pr1646v2XEfmInQueuesH24PerformanceQdPkts OBJECT-TYPE
   SYNTAX      Counter64
   MAX-ACCESS  read-only
   STATUS      current
   DESCRIPTION
      "Path: efm.performance.ifInPriorityQueues.h24Performance.queuedPkts

       64 bit unsigned wrappable counter."
   ::= {pr1646v2XEfmInQueuesH24PerformanceEntry 50331648}

pr1646v2XEfmInQueuesH24PerformanceDropPkts OBJECT-TYPE
   SYNTAX      Counter64
   MAX-ACCESS  read-only
   STATUS      current
   DESCRIPTION
      "Path: efm.performance.ifInPriorityQueues.h24Performance.droppedPkts

       64 bit unsigned wrappable counter."
   ::= {pr1646v2XEfmInQueuesH24PerformanceEntry 67108864}

pr1646v2XEfmInQueuesH24PerformanceRDropPkts OBJECT-TYPE
   SYNTAX      Counter64
   MAX-ACCESS  read-only
   STATUS      current
   DESCRIPTION
      "Path: efm.performance.ifInPriorityQueues.h24Performance.redDroppedPkts

       64 bit unsigned wrappable counter."
   ::= {pr1646v2XEfmInQueuesH24PerformanceEntry 201326592}

pr1646v2XEfmInQueuesH24PerformanceCirTxPkts OBJECT-TYPE
   SYNTAX      Counter64
   MAX-ACCESS  read-only
   STATUS      current
   DESCRIPTION
      "Path: efm.performance.ifInPriorityQueues.h24Performance.cirTxPkts

       64 bit unsigned wrappable counter."
   ::= {pr1646v2XEfmInQueuesH24PerformanceEntry 83886080}

pr1646v2XEfmInQueuesH24PerformanceEirTxPkts OBJECT-TYPE
   SYNTAX      Counter64
   MAX-ACCESS  read-only
   STATUS      current
   DESCRIPTION
      "Path: efm.performance.ifInPriorityQueues.h24Performance.eirTxPkts

       64 bit unsigned wrappable counter."
   ::= {pr1646v2XEfmInQueuesH24PerformanceEntry 100663296}

pr1646v2XEfmInQueuesH24PerformanceViolTxPkts OBJECT-TYPE
   SYNTAX      Counter64
   MAX-ACCESS  read-only
   STATUS      current
   DESCRIPTION
      "Path: efm.performance.ifInPriorityQueues.h24Performance.violateTxPkts

       64 bit unsigned wrappable counter."
   ::= {pr1646v2XEfmInQueuesH24PerformanceEntry 301989888}

pr1646v2XEfmInQueuesH24PerformanceTotOcts OBJECT-TYPE
   SYNTAX      Counter64
   MAX-ACCESS  read-only
   STATUS      current
   DESCRIPTION
      "Path: efm.performance.ifInPriorityQueues.h24Performance.totalOctets

       64 bit unsigned wrappable counter."
   ::= {pr1646v2XEfmInQueuesH24PerformanceEntry 251658240}

pr1646v2XEfmInQueuesH24PerformanceDirTxOcts OBJECT-TYPE
   SYNTAX      Counter64
   MAX-ACCESS  read-only
   STATUS      current
   DESCRIPTION
      "Path: efm.performance.ifInPriorityQueues.h24Performance.directTxOctets

       64 bit unsigned wrappable counter."
   ::= {pr1646v2XEfmInQueuesH24PerformanceEntry 117440512}

pr1646v2XEfmInQueuesH24PerformanceQdOcts OBJECT-TYPE
   SYNTAX      Counter64
   MAX-ACCESS  read-only
   STATUS      current
   DESCRIPTION
      "Path: efm.performance.ifInPriorityQueues.h24Performance.queuedOctets

       64 bit unsigned wrappable counter."
   ::= {pr1646v2XEfmInQueuesH24PerformanceEntry 134217728}

pr1646v2XEfmInQueuesH24PerformanceDropOcts OBJECT-TYPE
   SYNTAX      Counter64
   MAX-ACCESS  read-only
   STATUS      current
   DESCRIPTION
      "Path: efm.performance.ifInPriorityQueues.h24Performance.droppedOctets

       64 bit unsigned wrappable counter."
   ::= {pr1646v2XEfmInQueuesH24PerformanceEntry 150994944}

pr1646v2XEfmInQueuesH24PerformanceRDropOcts OBJECT-TYPE
   SYNTAX      Counter64
   MAX-ACCESS  read-only
   STATUS      current
   DESCRIPTION
      "Path: efm.performance.ifInPriorityQueues.h24Performance.redDroppedOctets

       64 bit unsigned wrappable counter."
   ::= {pr1646v2XEfmInQueuesH24PerformanceEntry 218103808}

pr1646v2XEfmInQueuesH24PerformanceCirTxOcts OBJECT-TYPE
   SYNTAX      Counter64
   MAX-ACCESS  read-only
   STATUS      current
   DESCRIPTION
      "Path: efm.performance.ifInPriorityQueues.h24Performance.cirTxOctets

       64 bit unsigned wrappable counter."
   ::= {pr1646v2XEfmInQueuesH24PerformanceEntry 167772160}

pr1646v2XEfmInQueuesH24PerformanceEirTxOcts OBJECT-TYPE
   SYNTAX      Counter64
   MAX-ACCESS  read-only
   STATUS      current
   DESCRIPTION
      "Path: efm.performance.ifInPriorityQueues.h24Performance.eirTxOctets

       64 bit unsigned wrappable counter."
   ::= {pr1646v2XEfmInQueuesH24PerformanceEntry 184549376}

pr1646v2XEfmInQueuesH24PerformanceViolTxOcts OBJECT-TYPE
   SYNTAX      Counter64
   MAX-ACCESS  read-only
   STATUS      current
   DESCRIPTION
      "Path: efm.performance.ifInPriorityQueues.h24Performance.violateTxOctets

       64 bit unsigned wrappable counter."
   ::= {pr1646v2XEfmInQueuesH24PerformanceEntry 318767104}

pr1646v2XEfmInQueuesH24PerformanceBandwidth OBJECT-TYPE
   SYNTAX      Integer32
   MAX-ACCESS  read-only
   STATUS      current
   DESCRIPTION
      "Path: efm.performance.ifInPriorityQueues.h24Performance.bandwidth

       unit name = bps
       formula = 8 * ; 8 /"
   ::= {pr1646v2XEfmInQueuesH24PerformanceEntry 268435456}

pr1646v2XEfmInQueuesD7Performance OBJECT-TYPE
   SYNTAX      SEQUENCE OF Pr1646v2XEfmInQueuesD7PerformanceEntry
   MAX-ACCESS  not-accessible
   STATUS      current
   DESCRIPTION
      ""
   ::= {pr1646v2XEfmInQueues 117440512}

pr1646v2XEfmInQueuesD7PerformanceEntry OBJECT-TYPE
   SYNTAX      Pr1646v2XEfmInQueuesD7PerformanceEntry
   MAX-ACCESS  not-accessible
   STATUS      current
   DESCRIPTION
      ""
   INDEX      { pr1646v2XEfmInQueuesTableIx,
                pr1646v2XEfmInQueuesD7PerformanceTableIx }
   ::= {pr1646v2XEfmInQueuesD7Performance 1}

Pr1646v2XEfmInQueuesD7PerformanceEntry ::=
   SEQUENCE
      {
      pr1646v2XEfmInQueuesD7PerformanceTableIx
         TableIndex,
      pr1646v2XEfmInQueuesD7PerformanceSysUpTime
         TimeTicks,
      pr1646v2XEfmInQueuesD7PerformanceTotPkts
         Counter64,
      pr1646v2XEfmInQueuesD7PerformanceDirTxPkts
         Counter64,
      pr1646v2XEfmInQueuesD7PerformanceQdPkts
         Counter64,
      pr1646v2XEfmInQueuesD7PerformanceDropPkts
         Counter64,
      pr1646v2XEfmInQueuesD7PerformanceRDropPkts
         Counter64,
      pr1646v2XEfmInQueuesD7PerformanceCirTxPkts
         Counter64,
      pr1646v2XEfmInQueuesD7PerformanceEirTxPkts
         Counter64,
      pr1646v2XEfmInQueuesD7PerformanceViolTxPkts
         Counter64,
      pr1646v2XEfmInQueuesD7PerformanceTotOcts
         Counter64,
      pr1646v2XEfmInQueuesD7PerformanceDirTxOcts
         Counter64,
      pr1646v2XEfmInQueuesD7PerformanceQdOcts
         Counter64,
      pr1646v2XEfmInQueuesD7PerformanceDropOcts
         Counter64,
      pr1646v2XEfmInQueuesD7PerformanceRDropOcts
         Counter64,
      pr1646v2XEfmInQueuesD7PerformanceCirTxOcts
         Counter64,
      pr1646v2XEfmInQueuesD7PerformanceEirTxOcts
         Counter64,
      pr1646v2XEfmInQueuesD7PerformanceViolTxOcts
         Counter64,
      pr1646v2XEfmInQueuesD7PerformanceBandwidth
         Integer32
      }

pr1646v2XEfmInQueuesD7PerformanceTableIx OBJECT-TYPE
   SYNTAX      TableIndex
   MAX-ACCESS  not-accessible
   STATUS      current
   DESCRIPTION
      ""
   ::= {pr1646v2XEfmInQueuesD7PerformanceEntry 11}

pr1646v2XEfmInQueuesD7PerformanceSysUpTime OBJECT-TYPE
   SYNTAX      TimeTicks
   MAX-ACCESS  read-only
   STATUS      current
   DESCRIPTION
      "Path: efm.performance.ifInPriorityQueues.d7Performance.sysUpTime

       Time in centi-second."
   ::= {pr1646v2XEfmInQueuesD7PerformanceEntry 16777216}

pr1646v2XEfmInQueuesD7PerformanceTotPkts OBJECT-TYPE
   SYNTAX      Counter64
   MAX-ACCESS  read-only
   STATUS      current
   DESCRIPTION
      "Path: efm.performance.ifInPriorityQueues.d7Performance.totalPkts

       64 bit unsigned wrappable counter."
   ::= {pr1646v2XEfmInQueuesD7PerformanceEntry 234881024}

pr1646v2XEfmInQueuesD7PerformanceDirTxPkts OBJECT-TYPE
   SYNTAX      Counter64
   MAX-ACCESS  read-only
   STATUS      current
   DESCRIPTION
      "Path: efm.performance.ifInPriorityQueues.d7Performance.directTxPkts

       64 bit unsigned wrappable counter."
   ::= {pr1646v2XEfmInQueuesD7PerformanceEntry 33554432}

pr1646v2XEfmInQueuesD7PerformanceQdPkts OBJECT-TYPE
   SYNTAX      Counter64
   MAX-ACCESS  read-only
   STATUS      current
   DESCRIPTION
      "Path: efm.performance.ifInPriorityQueues.d7Performance.queuedPkts

       64 bit unsigned wrappable counter."
   ::= {pr1646v2XEfmInQueuesD7PerformanceEntry 50331648}

pr1646v2XEfmInQueuesD7PerformanceDropPkts OBJECT-TYPE
   SYNTAX      Counter64
   MAX-ACCESS  read-only
   STATUS      current
   DESCRIPTION
      "Path: efm.performance.ifInPriorityQueues.d7Performance.droppedPkts

       64 bit unsigned wrappable counter."
   ::= {pr1646v2XEfmInQueuesD7PerformanceEntry 67108864}

pr1646v2XEfmInQueuesD7PerformanceRDropPkts OBJECT-TYPE
   SYNTAX      Counter64
   MAX-ACCESS  read-only
   STATUS      current
   DESCRIPTION
      "Path: efm.performance.ifInPriorityQueues.d7Performance.redDroppedPkts

       64 bit unsigned wrappable counter."
   ::= {pr1646v2XEfmInQueuesD7PerformanceEntry 201326592}

pr1646v2XEfmInQueuesD7PerformanceCirTxPkts OBJECT-TYPE
   SYNTAX      Counter64
   MAX-ACCESS  read-only
   STATUS      current
   DESCRIPTION
      "Path: efm.performance.ifInPriorityQueues.d7Performance.cirTxPkts

       64 bit unsigned wrappable counter."
   ::= {pr1646v2XEfmInQueuesD7PerformanceEntry 83886080}

pr1646v2XEfmInQueuesD7PerformanceEirTxPkts OBJECT-TYPE
   SYNTAX      Counter64
   MAX-ACCESS  read-only
   STATUS      current
   DESCRIPTION
      "Path: efm.performance.ifInPriorityQueues.d7Performance.eirTxPkts

       64 bit unsigned wrappable counter."
   ::= {pr1646v2XEfmInQueuesD7PerformanceEntry 100663296}

pr1646v2XEfmInQueuesD7PerformanceViolTxPkts OBJECT-TYPE
   SYNTAX      Counter64
   MAX-ACCESS  read-only
   STATUS      current
   DESCRIPTION
      "Path: efm.performance.ifInPriorityQueues.d7Performance.violateTxPkts

       64 bit unsigned wrappable counter."
   ::= {pr1646v2XEfmInQueuesD7PerformanceEntry 301989888}

pr1646v2XEfmInQueuesD7PerformanceTotOcts OBJECT-TYPE
   SYNTAX      Counter64
   MAX-ACCESS  read-only
   STATUS      current
   DESCRIPTION
      "Path: efm.performance.ifInPriorityQueues.d7Performance.totalOctets

       64 bit unsigned wrappable counter."
   ::= {pr1646v2XEfmInQueuesD7PerformanceEntry 251658240}

pr1646v2XEfmInQueuesD7PerformanceDirTxOcts OBJECT-TYPE
   SYNTAX      Counter64
   MAX-ACCESS  read-only
   STATUS      current
   DESCRIPTION
      "Path: efm.performance.ifInPriorityQueues.d7Performance.directTxOctets

       64 bit unsigned wrappable counter."
   ::= {pr1646v2XEfmInQueuesD7PerformanceEntry 117440512}

pr1646v2XEfmInQueuesD7PerformanceQdOcts OBJECT-TYPE
   SYNTAX      Counter64
   MAX-ACCESS  read-only
   STATUS      current
   DESCRIPTION
      "Path: efm.performance.ifInPriorityQueues.d7Performance.queuedOctets

       64 bit unsigned wrappable counter."
   ::= {pr1646v2XEfmInQueuesD7PerformanceEntry 134217728}

pr1646v2XEfmInQueuesD7PerformanceDropOcts OBJECT-TYPE
   SYNTAX      Counter64
   MAX-ACCESS  read-only
   STATUS      current
   DESCRIPTION
      "Path: efm.performance.ifInPriorityQueues.d7Performance.droppedOctets

       64 bit unsigned wrappable counter."
   ::= {pr1646v2XEfmInQueuesD7PerformanceEntry 150994944}

pr1646v2XEfmInQueuesD7PerformanceRDropOcts OBJECT-TYPE
   SYNTAX      Counter64
   MAX-ACCESS  read-only
   STATUS      current
   DESCRIPTION
      "Path: efm.performance.ifInPriorityQueues.d7Performance.redDroppedOctets

       64 bit unsigned wrappable counter."
   ::= {pr1646v2XEfmInQueuesD7PerformanceEntry 218103808}

pr1646v2XEfmInQueuesD7PerformanceCirTxOcts OBJECT-TYPE
   SYNTAX      Counter64
   MAX-ACCESS  read-only
   STATUS      current
   DESCRIPTION
      "Path: efm.performance.ifInPriorityQueues.d7Performance.cirTxOctets

       64 bit unsigned wrappable counter."
   ::= {pr1646v2XEfmInQueuesD7PerformanceEntry 167772160}

pr1646v2XEfmInQueuesD7PerformanceEirTxOcts OBJECT-TYPE
   SYNTAX      Counter64
   MAX-ACCESS  read-only
   STATUS      current
   DESCRIPTION
      "Path: efm.performance.ifInPriorityQueues.d7Performance.eirTxOctets

       64 bit unsigned wrappable counter."
   ::= {pr1646v2XEfmInQueuesD7PerformanceEntry 184549376}

pr1646v2XEfmInQueuesD7PerformanceViolTxOcts OBJECT-TYPE
   SYNTAX      Counter64
   MAX-ACCESS  read-only
   STATUS      current
   DESCRIPTION
      "Path: efm.performance.ifInPriorityQueues.d7Performance.violateTxOctets

       64 bit unsigned wrappable counter."
   ::= {pr1646v2XEfmInQueuesD7PerformanceEntry 318767104}

pr1646v2XEfmInQueuesD7PerformanceBandwidth OBJECT-TYPE
   SYNTAX      Integer32
   MAX-ACCESS  read-only
   STATUS      current
   DESCRIPTION
      "Path: efm.performance.ifInPriorityQueues.d7Performance.bandwidth

       unit name = bps
       formula = 8 * ; 8 /"
   ::= {pr1646v2XEfmInQueuesD7PerformanceEntry 268435456}


pr1646v2XEfmInBandwidth OBJECT IDENTIFIER ::= {pr1646v2XEfm 181}

pr1646v2XEfmInBandwidthSSC OBJECT IDENTIFIER ::= {pr1646v2XEfmInBandwidth 1}

pr1646v2XEfmInBandwidthEntry OBJECT IDENTIFIER ::= {pr1646v2XEfmInBandwidthSSC 1}

pr1646v2XEfmInBandwidth15sec OBJECT-TYPE
   SYNTAX      Integer32
   MAX-ACCESS  read-only
   STATUS      current
   DESCRIPTION
      "Path: efm.performance.ifInBandwidth.15sec

       unit name = bps
       formula = 8 * ; 8 /"
   ::= {pr1646v2XEfmInBandwidthEntry 83886080}

pr1646v2XEfmInBandwidth30sec OBJECT-TYPE
   SYNTAX      Integer32
   MAX-ACCESS  read-only
   STATUS      current
   DESCRIPTION
      "Path: efm.performance.ifInBandwidth.30sec

       unit name = bps
       formula = 8 * ; 8 /"
   ::= {pr1646v2XEfmInBandwidthEntry 167772160}

pr1646v2XEfmInBandwidth1min OBJECT-TYPE
   SYNTAX      Integer32
   MAX-ACCESS  read-only
   STATUS      current
   DESCRIPTION
      "Path: efm.performance.ifInBandwidth.1min

       unit name = bps
       formula = 8 * ; 8 /"
   ::= {pr1646v2XEfmInBandwidthEntry 335544320}

pr1646v2XEfmInBandwidth2min OBJECT-TYPE
   SYNTAX      Integer32
   MAX-ACCESS  read-only
   STATUS      current
   DESCRIPTION
      "Path: efm.performance.ifInBandwidth.2min

       unit name = bps
       formula = 8 * ; 8 /"
   ::= {pr1646v2XEfmInBandwidthEntry 671088640}

pr1646v2XEfmInBandwidth5min OBJECT-TYPE
   SYNTAX      Integer32
   MAX-ACCESS  read-only
   STATUS      current
   DESCRIPTION
      "Path: efm.performance.ifInBandwidth.5min

       unit name = bps
       formula = 8 * ; 8 /"
   ::= {pr1646v2XEfmInBandwidthEntry 1677721600}


pr1646v2XEfmOutOctets OBJECT-TYPE
   SYNTAX      Counter64
   MAX-ACCESS  read-only
   STATUS      current
   DESCRIPTION
      "Path: efm.performance.ifOutOctets
       Info: ifOutOctets

       64 bit unsigned wrappable counter."
   ::= {pr1646v2XEfm 115}


pr1646v2XEfmOutUcastPkts OBJECT-TYPE
   SYNTAX      Counter64
   MAX-ACCESS  read-only
   STATUS      current
   DESCRIPTION
      "Path: efm.performance.ifOutUcastPkts
       Info: ifOutUcastPkts

       64 bit unsigned wrappable counter."
   ::= {pr1646v2XEfm 116}


pr1646v2XEfmOutNUcastPkts OBJECT-TYPE
   SYNTAX      Counter64
   MAX-ACCESS  read-only
   STATUS      current
   DESCRIPTION
      "Path: efm.performance.ifOutNUcastPkts
       Info: ifOutNUcastPkts

       64 bit unsigned wrappable counter."
   ::= {pr1646v2XEfm 117}


pr1646v2XEfmOutBcastPkts OBJECT-TYPE
   SYNTAX      Counter64
   MAX-ACCESS  read-only
   STATUS      current
   DESCRIPTION
      "Path: efm.performance.ifOutBcastPkts
       Info: ifOutBcastPkts

       64 bit unsigned wrappable counter."
   ::= {pr1646v2XEfm 217}


pr1646v2XEfmOutMcastPkts OBJECT-TYPE
   SYNTAX      Counter64
   MAX-ACCESS  read-only
   STATUS      current
   DESCRIPTION
      "Path: efm.performance.ifOutMcastPkts
       Info: ifOutMcastPkts

       64 bit unsigned wrappable counter."
   ::= {pr1646v2XEfm 227}


pr1646v2XEfmOutDiscards OBJECT-TYPE
   SYNTAX      Counter64
   MAX-ACCESS  read-only
   STATUS      current
   DESCRIPTION
      "Path: efm.performance.ifOutDiscards
       Info: ifOutDiscards

       64 bit unsigned wrappable counter."
   ::= {pr1646v2XEfm 118}


pr1646v2XEfmOutErrors OBJECT-TYPE
   SYNTAX      Counter64
   MAX-ACCESS  read-only
   STATUS      current
   DESCRIPTION
      "Path: efm.performance.ifOutErrors
       Info: ifOutErrors

       64 bit unsigned wrappable counter."
   ::= {pr1646v2XEfm 119}


pr1646v2XEfmOutQLen OBJECT-TYPE
   SYNTAX      Gauge32
   MAX-ACCESS  read-only
   STATUS      current
   DESCRIPTION
      "Path: efm.performance.ifOutQLen
       Info: ifOutQLen

       32 bit unsigned gauge value."
   ::= {pr1646v2XEfm 120}


pr1646v2XEfmOutDropEx OBJECT-TYPE
   SYNTAX      Counter64
   MAX-ACCESS  read-only
   STATUS      current
   DESCRIPTION
      "Path: efm.performance.ifOutDropLevelExceeded
       Info: ifOutDiscards

       64 bit unsigned wrappable counter."
   ::= {pr1646v2XEfm 127}


pr1646v2XEfmOutDropNoArp OBJECT-TYPE
   SYNTAX      Counter64
   MAX-ACCESS  read-only
   STATUS      current
   DESCRIPTION
      "Path: efm.performance.ifOutDiscardsNoArp
       Info: ifOutDiscards

       64 bit unsigned wrappable counter."
   ::= {pr1646v2XEfm 134}


pr1646v2XEfmOutDropFilter OBJECT-TYPE
   SYNTAX      Counter64
   MAX-ACCESS  read-only
   STATUS      current
   DESCRIPTION
      "Path: efm.performance.ifOutDiscardsFilter
       Info: ifOutDiscards

       64 bit unsigned wrappable counter."
   ::= {pr1646v2XEfm 138}


pr1646v2XEfmOutQueues OBJECT IDENTIFIER ::= {pr1646v2XEfm 129}

pr1646v2XEfmOutQueuesSSCTable OBJECT-TYPE
   SYNTAX      SEQUENCE OF Pr1646v2XEfmOutQueuesEntry
   MAX-ACCESS  not-accessible
   STATUS      current
   DESCRIPTION
      "Queue Lengths"
   ::= {pr1646v2XEfmOutQueues 1}

pr1646v2XEfmOutQueuesEntry OBJECT-TYPE
   SYNTAX      Pr1646v2XEfmOutQueuesEntry
   MAX-ACCESS  not-accessible
   STATUS      current
   DESCRIPTION
      ""
   INDEX      { pr1646v2XEfmOutQueuesTableIx }
   ::= {pr1646v2XEfmOutQueuesSSCTable 1}

Pr1646v2XEfmOutQueuesEntry ::=
   SEQUENCE
      {
      pr1646v2XEfmOutQueuesTableIx
         TableIndex,
      pr1646v2XEfmOutQueuesName
         INTEGER,
      pr1646v2XEfmOutQueuesLength
         Integer32,
      pr1646v2XEfmOutQueuesOctetLength
         Integer32,
      pr1646v2XEfmOutQueuesRedLength
         Integer32,
      pr1646v2XEfmOutQueuesPacketsTotal
         Counter64,
      pr1646v2XEfmOutQueuesPacketsDirectTx
         Counter64,
      pr1646v2XEfmOutQueuesPacketsQueued
         Counter64,
      pr1646v2XEfmOutQueuesPacketsDropped
         Counter64,
      pr1646v2XEfmOutQueuesPacketsRedDropped
         Counter64,
      pr1646v2XEfmOutQueuesPacketsCirTx
         Counter64,
      pr1646v2XEfmOutQueuesPacketsEirTx
         Counter64,
      pr1646v2XEfmOutQueuesPacketsViolateTx
         Counter64,
      pr1646v2XEfmOutQueuesOctetsTotal
         Counter64,
      pr1646v2XEfmOutQueuesOctetsDirectTx
         Counter64,
      pr1646v2XEfmOutQueuesOctetsQueued
         Counter64,
      pr1646v2XEfmOutQueuesOctetsDropped
         Counter64,
      pr1646v2XEfmOutQueuesOctetsRedDropped
         Counter64,
      pr1646v2XEfmOutQueuesOctetsCirTx
         Counter64,
      pr1646v2XEfmOutQueuesOctetsEirTx
         Counter64,
      pr1646v2XEfmOutQueuesOctetsViolateTx
         Counter64,
      pr1646v2XEfmOutQueuesOctetsBandwidth15sec
         Integer32,
      pr1646v2XEfmOutQueuesOctetsBandwidth30sec
         Integer32,
      pr1646v2XEfmOutQueuesOctetsBandwidth1min
         Integer32,
      pr1646v2XEfmOutQueuesOctetsBandwidth2min
         Integer32,
      pr1646v2XEfmOutQueuesOctetsBandwidth5min
         Integer32
      }

pr1646v2XEfmOutQueuesTableIx OBJECT-TYPE
   SYNTAX      TableIndex
   MAX-ACCESS  not-accessible
   STATUS      current
   DESCRIPTION
      ""
   ::= {pr1646v2XEfmOutQueuesEntry 11}

pr1646v2XEfmOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2XEfmOutQueuesEntry 16777216}

pr1646v2XEfmOutQueuesLength OBJECT-TYPE
   SYNTAX      Integer32
   MAX-ACCESS  read-only
   STATUS      current
   DESCRIPTION
      "Path: efm.performance.ifOutPriorityQueues.length"
   ::= {pr1646v2XEfmOutQueuesEntry 33554432}

pr1646v2XEfmOutQueuesOctetLength OBJECT-TYPE
   SYNTAX      Integer32
   MAX-ACCESS  read-only
   STATUS      current
   DESCRIPTION
      "Path: efm.performance.ifOutPriorityQueues.octetLength"
   ::= {pr1646v2XEfmOutQueuesEntry 150994944}

pr1646v2XEfmOutQueuesRedLength OBJECT-TYPE
   SYNTAX      Integer32
   MAX-ACCESS  read-only
   STATUS      current
   DESCRIPTION
      "Path: efm.performance.ifOutPriorityQueues.redLength"
   ::= {pr1646v2XEfmOutQueuesEntry 134217728}

pr1646v2XEfmOutQueuesPacketsTotal OBJECT-TYPE
   SYNTAX      Counter64
   MAX-ACCESS  read-only
   STATUS      current
   DESCRIPTION
      "Path: efm.performance.ifOutPriorityQueues.packets.total

       64 bit unsigned wrappable counter."
   ::= {pr1646v2XEfmOutQueuesEntry 50790400}

pr1646v2XEfmOutQueuesPacketsDirectTx OBJECT-TYPE
   SYNTAX      Counter64
   MAX-ACCESS  read-only
   STATUS      current
   DESCRIPTION
      "Path: efm.performance.ifOutPriorityQueues.packets.directTx

       64 bit unsigned wrappable counter."
   ::= {pr1646v2XEfmOutQueuesEntry 50397184}

pr1646v2XEfmOutQueuesPacketsQueued OBJECT-TYPE
   SYNTAX      Counter64
   MAX-ACCESS  read-only
   STATUS      current
   DESCRIPTION
      "Path: efm.performance.ifOutPriorityQueues.packets.queued

       64 bit unsigned wrappable counter."
   ::= {pr1646v2XEfmOutQueuesEntry 50462720}

pr1646v2XEfmOutQueuesPacketsDropped OBJECT-TYPE
   SYNTAX      Counter64
   MAX-ACCESS  read-only
   STATUS      current
   DESCRIPTION
      "Path: efm.performance.ifOutPriorityQueues.packets.dropped

       64 bit unsigned wrappable counter."
   ::= {pr1646v2XEfmOutQueuesEntry 50528256}

pr1646v2XEfmOutQueuesPacketsRedDropped OBJECT-TYPE
   SYNTAX      Counter64
   MAX-ACCESS  read-only
   STATUS      current
   DESCRIPTION
      "Path: efm.performance.ifOutPriorityQueues.packets.redDropped

       64 bit unsigned wrappable counter."
   ::= {pr1646v2XEfmOutQueuesEntry 50724864}

pr1646v2XEfmOutQueuesPacketsCirTx OBJECT-TYPE
   SYNTAX      Counter64
   MAX-ACCESS  read-only
   STATUS      current
   DESCRIPTION
      "Path: efm.performance.ifOutPriorityQueues.packets.cirTx

       64 bit unsigned wrappable counter."
   ::= {pr1646v2XEfmOutQueuesEntry 50593792}

pr1646v2XEfmOutQueuesPacketsEirTx OBJECT-TYPE
   SYNTAX      Counter64
   MAX-ACCESS  read-only
   STATUS      current
   DESCRIPTION
      "Path: efm.performance.ifOutPriorityQueues.packets.eirTx

       64 bit unsigned wrappable counter."
   ::= {pr1646v2XEfmOutQueuesEntry 50659328}

pr1646v2XEfmOutQueuesPacketsViolateTx OBJECT-TYPE
   SYNTAX      Counter64
   MAX-ACCESS  read-only
   STATUS      current
   DESCRIPTION
      "Path: efm.performance.ifOutPriorityQueues.packets.violateTx

       64 bit unsigned wrappable counter."
   ::= {pr1646v2XEfmOutQueuesEntry 50855936}

pr1646v2XEfmOutQueuesOctetsTotal OBJECT-TYPE
   SYNTAX      Counter64
   MAX-ACCESS  read-only
   STATUS      current
   DESCRIPTION
      "Path: efm.performance.ifOutPriorityQueues.octets.total

       64 bit unsigned wrappable counter."
   ::= {pr1646v2XEfmOutQueuesEntry 67567616}

pr1646v2XEfmOutQueuesOctetsDirectTx OBJECT-TYPE
   SYNTAX      Counter64
   MAX-ACCESS  read-only
   STATUS      current
   DESCRIPTION
      "Path: efm.performance.ifOutPriorityQueues.octets.directTx

       64 bit unsigned wrappable counter."
   ::= {pr1646v2XEfmOutQueuesEntry 67174400}

pr1646v2XEfmOutQueuesOctetsQueued OBJECT-TYPE
   SYNTAX      Counter64
   MAX-ACCESS  read-only
   STATUS      current
   DESCRIPTION
      "Path: efm.performance.ifOutPriorityQueues.octets.queued

       64 bit unsigned wrappable counter."
   ::= {pr1646v2XEfmOutQueuesEntry 67239936}

pr1646v2XEfmOutQueuesOctetsDropped OBJECT-TYPE
   SYNTAX      Counter64
   MAX-ACCESS  read-only
   STATUS      current
   DESCRIPTION
      "Path: efm.performance.ifOutPriorityQueues.octets.dropped

       64 bit unsigned wrappable counter."
   ::= {pr1646v2XEfmOutQueuesEntry 67305472}

pr1646v2XEfmOutQueuesOctetsRedDropped OBJECT-TYPE
   SYNTAX      Counter64
   MAX-ACCESS  read-only
   STATUS      current
   DESCRIPTION
      "Path: efm.performance.ifOutPriorityQueues.octets.redDropped

       64 bit unsigned wrappable counter."
   ::= {pr1646v2XEfmOutQueuesEntry 67502080}

pr1646v2XEfmOutQueuesOctetsCirTx OBJECT-TYPE
   SYNTAX      Counter64
   MAX-ACCESS  read-only
   STATUS      current
   DESCRIPTION
      "Path: efm.performance.ifOutPriorityQueues.octets.cirTx

       64 bit unsigned wrappable counter."
   ::= {pr1646v2XEfmOutQueuesEntry 67371008}

pr1646v2XEfmOutQueuesOctetsEirTx OBJECT-TYPE
   SYNTAX      Counter64
   MAX-ACCESS  read-only
   STATUS      current
   DESCRIPTION
      "Path: efm.performance.ifOutPriorityQueues.octets.eirTx

       64 bit unsigned wrappable counter."
   ::= {pr1646v2XEfmOutQueuesEntry 67436544}

pr1646v2XEfmOutQueuesOctetsViolateTx OBJECT-TYPE
   SYNTAX      Counter64
   MAX-ACCESS  read-only
   STATUS      current
   DESCRIPTION
      "Path: efm.performance.ifOutPriorityQueues.octets.violateTx

       64 bit unsigned wrappable counter."
   ::= {pr1646v2XEfmOutQueuesEntry 67633152}

pr1646v2XEfmOutQueuesOctetsBandwidth15sec OBJECT-TYPE
   SYNTAX      Integer32
   MAX-ACCESS  read-only
   STATUS      current
   DESCRIPTION
      "Path: efm.performance.ifOutPriorityQueues.octets.bandwidth.15sec

       unit name = bps
       formula = 8 * ; 8 /"
   ::= {pr1646v2XEfmOutQueuesEntry 70386944}

pr1646v2XEfmOutQueuesOctetsBandwidth30sec OBJECT-TYPE
   SYNTAX      Integer32
   MAX-ACCESS  read-only
   STATUS      current
   DESCRIPTION
      "Path: efm.performance.ifOutPriorityQueues.octets.bandwidth.30sec

       unit name = bps
       formula = 8 * ; 8 /"
   ::= {pr1646v2XEfmOutQueuesEntry 70388224}

pr1646v2XEfmOutQueuesOctetsBandwidth1min OBJECT-TYPE
   SYNTAX      Integer32
   MAX-ACCESS  read-only
   STATUS      current
   DESCRIPTION
      "Path: efm.performance.ifOutPriorityQueues.octets.bandwidth.1min

       unit name = bps
       formula = 8 * ; 8 /"
   ::= {pr1646v2XEfmOutQueuesEntry 70390784}

pr1646v2XEfmOutQueuesOctetsBandwidth2min OBJECT-TYPE
   SYNTAX      Integer32
   MAX-ACCESS  read-only
   STATUS      current
   DESCRIPTION
      "Path: efm.performance.ifOutPriorityQueues.octets.bandwidth.2min

       unit name = bps
       formula = 8 * ; 8 /"
   ::= {pr1646v2XEfmOutQueuesEntry 70395904}

pr1646v2XEfmOutQueuesOctetsBandwidth5min OBJECT-TYPE
   SYNTAX      Integer32
   MAX-ACCESS  read-only
   STATUS      current
   DESCRIPTION
      "Path: efm.performance.ifOutPriorityQueues.octets.bandwidth.5min

       unit name = bps
       formula = 8 * ; 8 /"
   ::= {pr1646v2XEfmOutQueuesEntry 70411264}

pr1646v2XEfmOutQueuesH2Performance OBJECT-TYPE
   SYNTAX      SEQUENCE OF Pr1646v2XEfmOutQueuesH2PerformanceEntry
   MAX-ACCESS  not-accessible
   STATUS      current
   DESCRIPTION
      ""
   ::= {pr1646v2XEfmOutQueues 83886080}

pr1646v2XEfmOutQueuesH2PerformanceEntry OBJECT-TYPE
   SYNTAX      Pr1646v2XEfmOutQueuesH2PerformanceEntry
   MAX-ACCESS  not-accessible
   STATUS      current
   DESCRIPTION
      ""
   INDEX      { pr1646v2XEfmOutQueuesTableIx,
                pr1646v2XEfmOutQueuesH2PerformanceTableIx }
   ::= {pr1646v2XEfmOutQueuesH2Performance 1}

Pr1646v2XEfmOutQueuesH2PerformanceEntry ::=
   SEQUENCE
      {
      pr1646v2XEfmOutQueuesH2PerformanceTableIx
         TableIndex,
      pr1646v2XEfmOutQueuesH2PerformanceSysUpTime
         TimeTicks,
      pr1646v2XEfmOutQueuesH2PerformanceTotPkts
         Counter64,
      pr1646v2XEfmOutQueuesH2PerformanceDirTxPkts
         Counter64,
      pr1646v2XEfmOutQueuesH2PerformanceQdPkts
         Counter64,
      pr1646v2XEfmOutQueuesH2PerformanceDropPkts
         Counter64,
      pr1646v2XEfmOutQueuesH2PerformanceRDropPkts
         Counter64,
      pr1646v2XEfmOutQueuesH2PerformanceCirTxPkts
         Counter64,
      pr1646v2XEfmOutQueuesH2PerformanceEirTxPkts
         Counter64,
      pr1646v2XEfmOutQueuesH2PerformanceViolTxPkts
         Counter64,
      pr1646v2XEfmOutQueuesH2PerformanceTotOcts
         Counter64,
      pr1646v2XEfmOutQueuesH2PerformanceDirTxOcts
         Counter64,
      pr1646v2XEfmOutQueuesH2PerformanceQdOcts
         Counter64,
      pr1646v2XEfmOutQueuesH2PerformanceDropOcts
         Counter64,
      pr1646v2XEfmOutQueuesH2PerformanceRDropOcts
         Counter64,
      pr1646v2XEfmOutQueuesH2PerformanceCirTxOcts
         Counter64,
      pr1646v2XEfmOutQueuesH2PerformanceEirTxOcts
         Counter64,
      pr1646v2XEfmOutQueuesH2PerformanceViolTxOcts
         Counter64,
      pr1646v2XEfmOutQueuesH2PerformanceBandwidth
         Integer32
      }

pr1646v2XEfmOutQueuesH2PerformanceTableIx OBJECT-TYPE
   SYNTAX      TableIndex
   MAX-ACCESS  not-accessible
   STATUS      current
   DESCRIPTION
      ""
   ::= {pr1646v2XEfmOutQueuesH2PerformanceEntry 11}

pr1646v2XEfmOutQueuesH2PerformanceSysUpTime OBJECT-TYPE
   SYNTAX      TimeTicks
   MAX-ACCESS  read-only
   STATUS      current
   DESCRIPTION
      "Path: efm.performance.ifOutPriorityQueues.h2Performance.sysUpTime

       Time in centi-second."
   ::= {pr1646v2XEfmOutQueuesH2PerformanceEntry 16777216}

pr1646v2XEfmOutQueuesH2PerformanceTotPkts OBJECT-TYPE
   SYNTAX      Counter64
   MAX-ACCESS  read-only
   STATUS      current
   DESCRIPTION
      "Path: efm.performance.ifOutPriorityQueues.h2Performance.totalPkts

       64 bit unsigned wrappable counter."
   ::= {pr1646v2XEfmOutQueuesH2PerformanceEntry 234881024}

pr1646v2XEfmOutQueuesH2PerformanceDirTxPkts OBJECT-TYPE
   SYNTAX      Counter64
   MAX-ACCESS  read-only
   STATUS      current
   DESCRIPTION
      "Path: efm.performance.ifOutPriorityQueues.h2Performance.directTxPkts

       64 bit unsigned wrappable counter."
   ::= {pr1646v2XEfmOutQueuesH2PerformanceEntry 33554432}

pr1646v2XEfmOutQueuesH2PerformanceQdPkts OBJECT-TYPE
   SYNTAX      Counter64
   MAX-ACCESS  read-only
   STATUS      current
   DESCRIPTION
      "Path: efm.performance.ifOutPriorityQueues.h2Performance.queuedPkts

       64 bit unsigned wrappable counter."
   ::= {pr1646v2XEfmOutQueuesH2PerformanceEntry 50331648}

pr1646v2XEfmOutQueuesH2PerformanceDropPkts OBJECT-TYPE
   SYNTAX      Counter64
   MAX-ACCESS  read-only
   STATUS      current
   DESCRIPTION
      "Path: efm.performance.ifOutPriorityQueues.h2Performance.droppedPkts

       64 bit unsigned wrappable counter."
   ::= {pr1646v2XEfmOutQueuesH2PerformanceEntry 67108864}

pr1646v2XEfmOutQueuesH2PerformanceRDropPkts OBJECT-TYPE
   SYNTAX      Counter64
   MAX-ACCESS  read-only
   STATUS      current
   DESCRIPTION
      "Path: efm.performance.ifOutPriorityQueues.h2Performance.redDroppedPkts

       64 bit unsigned wrappable counter."
   ::= {pr1646v2XEfmOutQueuesH2PerformanceEntry 201326592}

pr1646v2XEfmOutQueuesH2PerformanceCirTxPkts OBJECT-TYPE
   SYNTAX      Counter64
   MAX-ACCESS  read-only
   STATUS      current
   DESCRIPTION
      "Path: efm.performance.ifOutPriorityQueues.h2Performance.cirTxPkts

       64 bit unsigned wrappable counter."
   ::= {pr1646v2XEfmOutQueuesH2PerformanceEntry 83886080}

pr1646v2XEfmOutQueuesH2PerformanceEirTxPkts OBJECT-TYPE
   SYNTAX      Counter64
   MAX-ACCESS  read-only
   STATUS      current
   DESCRIPTION
      "Path: efm.performance.ifOutPriorityQueues.h2Performance.eirTxPkts

       64 bit unsigned wrappable counter."
   ::= {pr1646v2XEfmOutQueuesH2PerformanceEntry 100663296}

pr1646v2XEfmOutQueuesH2PerformanceViolTxPkts OBJECT-TYPE
   SYNTAX      Counter64
   MAX-ACCESS  read-only
   STATUS      current
   DESCRIPTION
      "Path: efm.performance.ifOutPriorityQueues.h2Performance.violateTxPkts

       64 bit unsigned wrappable counter."
   ::= {pr1646v2XEfmOutQueuesH2PerformanceEntry 301989888}

pr1646v2XEfmOutQueuesH2PerformanceTotOcts OBJECT-TYPE
   SYNTAX      Counter64
   MAX-ACCESS  read-only
   STATUS      current
   DESCRIPTION
      "Path: efm.performance.ifOutPriorityQueues.h2Performance.totalOctets

       64 bit unsigned wrappable counter."
   ::= {pr1646v2XEfmOutQueuesH2PerformanceEntry 251658240}

pr1646v2XEfmOutQueuesH2PerformanceDirTxOcts OBJECT-TYPE
   SYNTAX      Counter64
   MAX-ACCESS  read-only
   STATUS      current
   DESCRIPTION
      "Path: efm.performance.ifOutPriorityQueues.h2Performance.directTxOctets

       64 bit unsigned wrappable counter."
   ::= {pr1646v2XEfmOutQueuesH2PerformanceEntry 117440512}

pr1646v2XEfmOutQueuesH2PerformanceQdOcts OBJECT-TYPE
   SYNTAX      Counter64
   MAX-ACCESS  read-only
   STATUS      current
   DESCRIPTION
      "Path: efm.performance.ifOutPriorityQueues.h2Performance.queuedOctets

       64 bit unsigned wrappable counter."
   ::= {pr1646v2XEfmOutQueuesH2PerformanceEntry 134217728}

pr1646v2XEfmOutQueuesH2PerformanceDropOcts OBJECT-TYPE
   SYNTAX      Counter64
   MAX-ACCESS  read-only
   STATUS      current
   DESCRIPTION
      "Path: efm.performance.ifOutPriorityQueues.h2Performance.droppedOctets

       64 bit unsigned wrappable counter."
   ::= {pr1646v2XEfmOutQueuesH2PerformanceEntry 150994944}

pr1646v2XEfmOutQueuesH2PerformanceRDropOcts OBJECT-TYPE
   SYNTAX      Counter64
   MAX-ACCESS  read-only
   STATUS      current
   DESCRIPTION
      "Path: efm.performance.ifOutPriorityQueues.h2Performance.redDroppedOctets

       64 bit unsigned wrappable counter."
   ::= {pr1646v2XEfmOutQueuesH2PerformanceEntry 218103808}

pr1646v2XEfmOutQueuesH2PerformanceCirTxOcts OBJECT-TYPE
   SYNTAX      Counter64
   MAX-ACCESS  read-only
   STATUS      current
   DESCRIPTION
      "Path: efm.performance.ifOutPriorityQueues.h2Performance.cirTxOctets

       64 bit unsigned wrappable counter."
   ::= {pr1646v2XEfmOutQueuesH2PerformanceEntry 167772160}

pr1646v2XEfmOutQueuesH2PerformanceEirTxOcts OBJECT-TYPE
   SYNTAX      Counter64
   MAX-ACCESS  read-only
   STATUS      current
   DESCRIPTION
      "Path: efm.performance.ifOutPriorityQueues.h2Performance.eirTxOctets

       64 bit unsigned wrappable counter."
   ::= {pr1646v2XEfmOutQueuesH2PerformanceEntry 184549376}

pr1646v2XEfmOutQueuesH2PerformanceViolTxOcts OBJECT-TYPE
   SYNTAX      Counter64
   MAX-ACCESS  read-only
   STATUS      current
   DESCRIPTION
      "Path: efm.performance.ifOutPriorityQueues.h2Performance.violateTxOctets

       64 bit unsigned wrappable counter."
   ::= {pr1646v2XEfmOutQueuesH2PerformanceEntry 318767104}

pr1646v2XEfmOutQueuesH2PerformanceBandwidth OBJECT-TYPE
   SYNTAX      Integer32
   MAX-ACCESS  read-only
   STATUS      current
   DESCRIPTION
      "Path: efm.performance.ifOutPriorityQueues.h2Performance.bandwidth

       unit name = bps
       formula = 8 * ; 8 /"
   ::= {pr1646v2XEfmOutQueuesH2PerformanceEntry 268435456}

pr1646v2XEfmOutQueuesH24Performance OBJECT-TYPE
   SYNTAX      SEQUENCE OF Pr1646v2XEfmOutQueuesH24PerformanceEntry
   MAX-ACCESS  not-accessible
   STATUS      current
   DESCRIPTION
      ""
   ::= {pr1646v2XEfmOutQueues 100663296}

pr1646v2XEfmOutQueuesH24PerformanceEntry OBJECT-TYPE
   SYNTAX      Pr1646v2XEfmOutQueuesH24PerformanceEntry
   MAX-ACCESS  not-accessible
   STATUS      current
   DESCRIPTION
      ""
   INDEX      { pr1646v2XEfmOutQueuesTableIx,
                pr1646v2XEfmOutQueuesH24PerformanceTableIx }
   ::= {pr1646v2XEfmOutQueuesH24Performance 1}

Pr1646v2XEfmOutQueuesH24PerformanceEntry ::=
   SEQUENCE
      {
      pr1646v2XEfmOutQueuesH24PerformanceTableIx
         TableIndex,
      pr1646v2XEfmOutQueuesH24PerformanceSysUpTime
         TimeTicks,
      pr1646v2XEfmOutQueuesH24PerformanceTotPkts
         Counter64,
      pr1646v2XEfmOutQueuesH24PerformanceDirTxPkts
         Counter64,
      pr1646v2XEfmOutQueuesH24PerformanceQdPkts
         Counter64,
      pr1646v2XEfmOutQueuesH24PerformanceDropPkts
         Counter64,
      pr1646v2XEfmOutQueuesH24PerformanceRDropPkts
         Counter64,
      pr1646v2XEfmOutQueuesH24PerformanceCirTxPkts
         Counter64,
      pr1646v2XEfmOutQueuesH24PerformanceEirTxPkts
         Counter64,
      pr1646v2XEfmOutQueuesH24PerformanceViolTxPkts
         Counter64,
      pr1646v2XEfmOutQueuesH24PerformanceTotOcts
         Counter64,
      pr1646v2XEfmOutQueuesH24PerformanceDirTxOcts
         Counter64,
      pr1646v2XEfmOutQueuesH24PerformanceQdOcts
         Counter64,
      pr1646v2XEfmOutQueuesH24PerformanceDropOcts
         Counter64,
      pr1646v2XEfmOutQueuesH24PerformanceRDropOcts
         Counter64,
      pr1646v2XEfmOutQueuesH24PerformanceCirTxOcts
         Counter64,
      pr1646v2XEfmOutQueuesH24PerformanceEirTxOcts
         Counter64,
      pr1646v2XEfmOutQueuesH24PerformanceViolTxOcts
         Counter64,
      pr1646v2XEfmOutQueuesH24PerformanceBandwidth
         Integer32
      }

pr1646v2XEfmOutQueuesH24PerformanceTableIx OBJECT-TYPE
   SYNTAX      TableIndex
   MAX-ACCESS  not-accessible
   STATUS      current
   DESCRIPTION
      ""
   ::= {pr1646v2XEfmOutQueuesH24PerformanceEntry 11}

pr1646v2XEfmOutQueuesH24PerformanceSysUpTime OBJECT-TYPE
   SYNTAX      TimeTicks
   MAX-ACCESS  read-only
   STATUS      current
   DESCRIPTION
      "Path: efm.performance.ifOutPriorityQueues.h24Performance.sysUpTime

       Time in centi-second."
   ::= {pr1646v2XEfmOutQueuesH24PerformanceEntry 16777216}

pr1646v2XEfmOutQueuesH24PerformanceTotPkts OBJECT-TYPE
   SYNTAX      Counter64
   MAX-ACCESS  read-only
   STATUS      current
   DESCRIPTION
      "Path: efm.performance.ifOutPriorityQueues.h24Performance.totalPkts

       64 bit unsigned wrappable counter."
   ::= {pr1646v2XEfmOutQueuesH24PerformanceEntry 234881024}

pr1646v2XEfmOutQueuesH24PerformanceDirTxPkts OBJECT-TYPE
   SYNTAX      Counter64
   MAX-ACCESS  read-only
   STATUS      current
   DESCRIPTION
      "Path: efm.performance.ifOutPriorityQueues.h24Performance.directTxPkts

       64 bit unsigned wrappable counter."
   ::= {pr1646v2XEfmOutQueuesH24PerformanceEntry 33554432}

pr1646v2XEfmOutQueuesH24PerformanceQdPkts OBJECT-TYPE
   SYNTAX      Counter64
   MAX-ACCESS  read-only
   STATUS      current
   DESCRIPTION
      "Path: efm.performance.ifOutPriorityQueues.h24Performance.queuedPkts

       64 bit unsigned wrappable counter."
   ::= {pr1646v2XEfmOutQueuesH24PerformanceEntry 50331648}

pr1646v2XEfmOutQueuesH24PerformanceDropPkts OBJECT-TYPE
   SYNTAX      Counter64
   MAX-ACCESS  read-only
   STATUS      current
   DESCRIPTION
      "Path: efm.performance.ifOutPriorityQueues.h24Performance.droppedPkts

       64 bit unsigned wrappable counter."
   ::= {pr1646v2XEfmOutQueuesH24PerformanceEntry 67108864}

pr1646v2XEfmOutQueuesH24PerformanceRDropPkts OBJECT-TYPE
   SYNTAX      Counter64
   MAX-ACCESS  read-only
   STATUS      current
   DESCRIPTION
      "Path: efm.performance.ifOutPriorityQueues.h24Performance.redDroppedPkts

       64 bit unsigned wrappable counter."
   ::= {pr1646v2XEfmOutQueuesH24PerformanceEntry 201326592}

pr1646v2XEfmOutQueuesH24PerformanceCirTxPkts OBJECT-TYPE
   SYNTAX      Counter64
   MAX-ACCESS  read-only
   STATUS      current
   DESCRIPTION
      "Path: efm.performance.ifOutPriorityQueues.h24Performance.cirTxPkts

       64 bit unsigned wrappable counter."
   ::= {pr1646v2XEfmOutQueuesH24PerformanceEntry 83886080}

pr1646v2XEfmOutQueuesH24PerformanceEirTxPkts OBJECT-TYPE
   SYNTAX      Counter64
   MAX-ACCESS  read-only
   STATUS      current
   DESCRIPTION
      "Path: efm.performance.ifOutPriorityQueues.h24Performance.eirTxPkts

       64 bit unsigned wrappable counter."
   ::= {pr1646v2XEfmOutQueuesH24PerformanceEntry 100663296}

pr1646v2XEfmOutQueuesH24PerformanceViolTxPkts OBJECT-TYPE
   SYNTAX      Counter64
   MAX-ACCESS  read-only
   STATUS      current
   DESCRIPTION
      "Path: efm.performance.ifOutPriorityQueues.h24Performance.violateTxPkts

       64 bit unsigned wrappable counter."
   ::= {pr1646v2XEfmOutQueuesH24PerformanceEntry 301989888}

pr1646v2XEfmOutQueuesH24PerformanceTotOcts OBJECT-TYPE
   SYNTAX      Counter64
   MAX-ACCESS  read-only
   STATUS      current
   DESCRIPTION
      "Path: efm.performance.ifOutPriorityQueues.h24Performance.totalOctets

       64 bit unsigned wrappable counter."
   ::= {pr1646v2XEfmOutQueuesH24PerformanceEntry 251658240}

pr1646v2XEfmOutQueuesH24PerformanceDirTxOcts OBJECT-TYPE
   SYNTAX      Counter64
   MAX-ACCESS  read-only
   STATUS      current
   DESCRIPTION
      "Path: efm.performance.ifOutPriorityQueues.h24Performance.directTxOctets

       64 bit unsigned wrappable counter."
   ::= {pr1646v2XEfmOutQueuesH24PerformanceEntry 117440512}

pr1646v2XEfmOutQueuesH24PerformanceQdOcts OBJECT-TYPE
   SYNTAX      Counter64
   MAX-ACCESS  read-only
   STATUS      current
   DESCRIPTION
      "Path: efm.performance.ifOutPriorityQueues.h24Performance.queuedOctets

       64 bit unsigned wrappable counter."
   ::= {pr1646v2XEfmOutQueuesH24PerformanceEntry 134217728}

pr1646v2XEfmOutQueuesH24PerformanceDropOcts OBJECT-TYPE
   SYNTAX      Counter64
   MAX-ACCESS  read-only
   STATUS      current
   DESCRIPTION
      "Path: efm.performance.ifOutPriorityQueues.h24Performance.droppedOctets

       64 bit unsigned wrappable counter."
   ::= {pr1646v2XEfmOutQueuesH24PerformanceEntry 150994944}

pr1646v2XEfmOutQueuesH24PerformanceRDropOcts OBJECT-TYPE
   SYNTAX      Counter64
   MAX-ACCESS  read-only
   STATUS      current
   DESCRIPTION
      "Path: efm.performance.ifOutPriorityQueues.h24Performance.redDroppedOctets

       64 bit unsigned wrappable counter."
   ::= {pr1646v2XEfmOutQueuesH24PerformanceEntry 218103808}

pr1646v2XEfmOutQueuesH24PerformanceCirTxOcts OBJECT-TYPE
   SYNTAX      Counter64
   MAX-ACCESS  read-only
   STATUS      current
   DESCRIPTION
      "Path: efm.performance.ifOutPriorityQueues.h24Performance.cirTxOctets

       64 bit unsigned wrappable counter."
   ::= {pr1646v2XEfmOutQueuesH24PerformanceEntry 167772160}

pr1646v2XEfmOutQueuesH24PerformanceEirTxOcts OBJECT-TYPE
   SYNTAX      Counter64
   MAX-ACCESS  read-only
   STATUS      current
   DESCRIPTION
      "Path: efm.performance.ifOutPriorityQueues.h24Performance.eirTxOctets

       64 bit unsigned wrappable counter."
   ::= {pr1646v2XEfmOutQueuesH24PerformanceEntry 184549376}

pr1646v2XEfmOutQueuesH24PerformanceViolTxOcts OBJECT-TYPE
   SYNTAX      Counter64
   MAX-ACCESS  read-only
   STATUS      current
   DESCRIPTION
      "Path: efm.performance.ifOutPriorityQueues.h24Performance.violateTxOctets

       64 bit unsigned wrappable counter."
   ::= {pr1646v2XEfmOutQueuesH24PerformanceEntry 318767104}

pr1646v2XEfmOutQueuesH24PerformanceBandwidth OBJECT-TYPE
   SYNTAX      Integer32
   MAX-ACCESS  read-only
   STATUS      current
   DESCRIPTION
      "Path: efm.performance.ifOutPriorityQueues.h24Performance.bandwidth

       unit name = bps
       formula = 8 * ; 8 /"
   ::= {pr1646v2XEfmOutQueuesH24PerformanceEntry 268435456}

pr1646v2XEfmOutQueuesD7Performance OBJECT-TYPE
   SYNTAX      SEQUENCE OF Pr1646v2XEfmOutQueuesD7PerformanceEntry
   MAX-ACCESS  not-accessible
   STATUS      current
   DESCRIPTION
      ""
   ::= {pr1646v2XEfmOutQueues 117440512}

pr1646v2XEfmOutQueuesD7PerformanceEntry OBJECT-TYPE
   SYNTAX      Pr1646v2XEfmOutQueuesD7PerformanceEntry
   MAX-ACCESS  not-accessible
   STATUS      current
   DESCRIPTION
      ""
   INDEX      { pr1646v2XEfmOutQueuesTableIx,
                pr1646v2XEfmOutQueuesD7PerformanceTableIx }
   ::= {pr1646v2XEfmOutQueuesD7Performance 1}

Pr1646v2XEfmOutQueuesD7PerformanceEntry ::=
   SEQUENCE
      {
      pr1646v2XEfmOutQueuesD7PerformanceTableIx
         TableIndex,
      pr1646v2XEfmOutQueuesD7PerformanceSysUpTime
         TimeTicks,
      pr1646v2XEfmOutQueuesD7PerformanceTotPkts
         Counter64,
      pr1646v2XEfmOutQueuesD7PerformanceDirTxPkts
         Counter64,
      pr1646v2XEfmOutQueuesD7PerformanceQdPkts
         Counter64,
      pr1646v2XEfmOutQueuesD7PerformanceDropPkts
         Counter64,
      pr1646v2XEfmOutQueuesD7PerformanceRDropPkts
         Counter64,
      pr1646v2XEfmOutQueuesD7PerformanceCirTxPkts
         Counter64,
      pr1646v2XEfmOutQueuesD7PerformanceEirTxPkts
         Counter64,
      pr1646v2XEfmOutQueuesD7PerformanceViolTxPkts
         Counter64,
      pr1646v2XEfmOutQueuesD7PerformanceTotOcts
         Counter64,
      pr1646v2XEfmOutQueuesD7PerformanceDirTxOcts
         Counter64,
      pr1646v2XEfmOutQueuesD7PerformanceQdOcts
         Counter64,
      pr1646v2XEfmOutQueuesD7PerformanceDropOcts
         Counter64,
      pr1646v2XEfmOutQueuesD7PerformanceRDropOcts
         Counter64,
      pr1646v2XEfmOutQueuesD7PerformanceCirTxOcts
         Counter64,
      pr1646v2XEfmOutQueuesD7PerformanceEirTxOcts
         Counter64,
      pr1646v2XEfmOutQueuesD7PerformanceViolTxOcts
         Counter64,
      pr1646v2XEfmOutQueuesD7PerformanceBandwidth
         Integer32
      }

pr1646v2XEfmOutQueuesD7PerformanceTableIx OBJECT-TYPE
   SYNTAX      TableIndex
   MAX-ACCESS  not-accessible
   STATUS      current
   DESCRIPTION
      ""
   ::= {pr1646v2XEfmOutQueuesD7PerformanceEntry 11}

pr1646v2XEfmOutQueuesD7PerformanceSysUpTime OBJECT-TYPE
   SYNTAX      TimeTicks
   MAX-ACCESS  read-only
   STATUS      current
   DESCRIPTION
      "Path: efm.performance.ifOutPriorityQueues.d7Performance.sysUpTime

       Time in centi-second."
   ::= {pr1646v2XEfmOutQueuesD7PerformanceEntry 16777216}

pr1646v2XEfmOutQueuesD7PerformanceTotPkts OBJECT-TYPE
   SYNTAX      Counter64
   MAX-ACCESS  read-only
   STATUS      current
   DESCRIPTION
      "Path: efm.performance.ifOutPriorityQueues.d7Performance.totalPkts

       64 bit unsigned wrappable counter."
   ::= {pr1646v2XEfmOutQueuesD7PerformanceEntry 234881024}

pr1646v2XEfmOutQueuesD7PerformanceDirTxPkts OBJECT-TYPE
   SYNTAX      Counter64
   MAX-ACCESS  read-only
   STATUS      current
   DESCRIPTION
      "Path: efm.performance.ifOutPriorityQueues.d7Performance.directTxPkts

       64 bit unsigned wrappable counter."
   ::= {pr1646v2XEfmOutQueuesD7PerformanceEntry 33554432}

pr1646v2XEfmOutQueuesD7PerformanceQdPkts OBJECT-TYPE
   SYNTAX      Counter64
   MAX-ACCESS  read-only
   STATUS      current
   DESCRIPTION
      "Path: efm.performance.ifOutPriorityQueues.d7Performance.queuedPkts

       64 bit unsigned wrappable counter."
   ::= {pr1646v2XEfmOutQueuesD7PerformanceEntry 50331648}

pr1646v2XEfmOutQueuesD7PerformanceDropPkts OBJECT-TYPE
   SYNTAX      Counter64
   MAX-ACCESS  read-only
   STATUS      current
   DESCRIPTION
      "Path: efm.performance.ifOutPriorityQueues.d7Performance.droppedPkts

       64 bit unsigned wrappable counter."
   ::= {pr1646v2XEfmOutQueuesD7PerformanceEntry 67108864}

pr1646v2XEfmOutQueuesD7PerformanceRDropPkts OBJECT-TYPE
   SYNTAX      Counter64
   MAX-ACCESS  read-only
   STATUS      current
   DESCRIPTION
      "Path: efm.performance.ifOutPriorityQueues.d7Performance.redDroppedPkts

       64 bit unsigned wrappable counter."
   ::= {pr1646v2XEfmOutQueuesD7PerformanceEntry 201326592}

pr1646v2XEfmOutQueuesD7PerformanceCirTxPkts OBJECT-TYPE
   SYNTAX      Counter64
   MAX-ACCESS  read-only
   STATUS      current
   DESCRIPTION
      "Path: efm.performance.ifOutPriorityQueues.d7Performance.cirTxPkts

       64 bit unsigned wrappable counter."
   ::= {pr1646v2XEfmOutQueuesD7PerformanceEntry 83886080}

pr1646v2XEfmOutQueuesD7PerformanceEirTxPkts OBJECT-TYPE
   SYNTAX      Counter64
   MAX-ACCESS  read-only
   STATUS      current
   DESCRIPTION
      "Path: efm.performance.ifOutPriorityQueues.d7Performance.eirTxPkts

       64 bit unsigned wrappable counter."
   ::= {pr1646v2XEfmOutQueuesD7PerformanceEntry 100663296}

pr1646v2XEfmOutQueuesD7PerformanceViolTxPkts OBJECT-TYPE
   SYNTAX      Counter64
   MAX-ACCESS  read-only
   STATUS      current
   DESCRIPTION
      "Path: efm.performance.ifOutPriorityQueues.d7Performance.violateTxPkts

       64 bit unsigned wrappable counter."
   ::= {pr1646v2XEfmOutQueuesD7PerformanceEntry 301989888}

pr1646v2XEfmOutQueuesD7PerformanceTotOcts OBJECT-TYPE
   SYNTAX      Counter64
   MAX-ACCESS  read-only
   STATUS      current
   DESCRIPTION
      "Path: efm.performance.ifOutPriorityQueues.d7Performance.totalOctets

       64 bit unsigned wrappable counter."
   ::= {pr1646v2XEfmOutQueuesD7PerformanceEntry 251658240}

pr1646v2XEfmOutQueuesD7PerformanceDirTxOcts OBJECT-TYPE
   SYNTAX      Counter64
   MAX-ACCESS  read-only
   STATUS      current
   DESCRIPTION
      "Path: efm.performance.ifOutPriorityQueues.d7Performance.directTxOctets

       64 bit unsigned wrappable counter."
   ::= {pr1646v2XEfmOutQueuesD7PerformanceEntry 117440512}

pr1646v2XEfmOutQueuesD7PerformanceQdOcts OBJECT-TYPE
   SYNTAX      Counter64
   MAX-ACCESS  read-only
   STATUS      current
   DESCRIPTION
      "Path: efm.performance.ifOutPriorityQueues.d7Performance.queuedOctets

       64 bit unsigned wrappable counter."
   ::= {pr1646v2XEfmOutQueuesD7PerformanceEntry 134217728}

pr1646v2XEfmOutQueuesD7PerformanceDropOcts OBJECT-TYPE
   SYNTAX      Counter64
   MAX-ACCESS  read-only
   STATUS      current
   DESCRIPTION
      "Path: efm.performance.ifOutPriorityQueues.d7Performance.droppedOctets

       64 bit unsigned wrappable counter."
   ::= {pr1646v2XEfmOutQueuesD7PerformanceEntry 150994944}

pr1646v2XEfmOutQueuesD7PerformanceRDropOcts OBJECT-TYPE
   SYNTAX      Counter64
   MAX-ACCESS  read-only
   STATUS      current
   DESCRIPTION
      "Path: efm.performance.ifOutPriorityQueues.d7Performance.redDroppedOctets

       64 bit unsigned wrappable counter."
   ::= {pr1646v2XEfmOutQueuesD7PerformanceEntry 218103808}

pr1646v2XEfmOutQueuesD7PerformanceCirTxOcts OBJECT-TYPE
   SYNTAX      Counter64
   MAX-ACCESS  read-only
   STATUS      current
   DESCRIPTION
      "Path: efm.performance.ifOutPriorityQueues.d7Performance.cirTxOctets

       64 bit unsigned wrappable counter."
   ::= {pr1646v2XEfmOutQueuesD7PerformanceEntry 167772160}

pr1646v2XEfmOutQueuesD7PerformanceEirTxOcts OBJECT-TYPE
   SYNTAX      Counter64
   MAX-ACCESS  read-only
   STATUS      current
   DESCRIPTION
      "Path: efm.performance.ifOutPriorityQueues.d7Performance.eirTxOctets

       64 bit unsigned wrappable counter."
   ::= {pr1646v2XEfmOutQueuesD7PerformanceEntry 184549376}

pr1646v2XEfmOutQueuesD7PerformanceViolTxOcts OBJECT-TYPE
   SYNTAX      Counter64
   MAX-ACCESS  read-only
   STATUS      current
   DESCRIPTION
      "Path: efm.performance.ifOutPriorityQueues.d7Performance.violateTxOctets

       64 bit unsigned wrappable counter."
   ::= {pr1646v2XEfmOutQueuesD7PerformanceEntry 318767104}

pr1646v2XEfmOutQueuesD7PerformanceBandwidth OBJECT-TYPE
   SYNTAX      Integer32
   MAX-ACCESS  read-only
   STATUS      current
   DESCRIPTION
      "Path: efm.performance.ifOutPriorityQueues.d7Performance.bandwidth

       unit name = bps
       formula = 8 * ; 8 /"
   ::= {pr1646v2XEfmOutQueuesD7PerformanceEntry 268435456}


pr1646v2XEfmOutBandwidth OBJECT IDENTIFIER ::= {pr1646v2XEfm 182}

pr1646v2XEfmOutBandwidthSSC OBJECT IDENTIFIER ::= {pr1646v2XEfmOutBandwidth 1}

pr1646v2XEfmOutBandwidthEntry OBJECT IDENTIFIER ::= {pr1646v2XEfmOutBandwidthSSC 1}

pr1646v2XEfmOutBandwidth15sec OBJECT-TYPE
   SYNTAX      Integer32
   MAX-ACCESS  read-only
   STATUS      current
   DESCRIPTION
      "Path: efm.performance.ifOutBandwidth.15sec

       unit name = bps
       formula = 8 * ; 8 /"
   ::= {pr1646v2XEfmOutBandwidthEntry 83886080}

pr1646v2XEfmOutBandwidth30sec OBJECT-TYPE
   SYNTAX      Integer32
   MAX-ACCESS  read-only
   STATUS      current
   DESCRIPTION
      "Path: efm.performance.ifOutBandwidth.30sec

       unit name = bps
       formula = 8 * ; 8 /"
   ::= {pr1646v2XEfmOutBandwidthEntry 167772160}

pr1646v2XEfmOutBandwidth1min OBJECT-TYPE
   SYNTAX      Integer32
   MAX-ACCESS  read-only
   STATUS      current
   DESCRIPTION
      "Path: efm.performance.ifOutBandwidth.1min

       unit name = bps
       formula = 8 * ; 8 /"
   ::= {pr1646v2XEfmOutBandwidthEntry 335544320}

pr1646v2XEfmOutBandwidth2min OBJECT-TYPE
   SYNTAX      Integer32
   MAX-ACCESS  read-only
   STATUS      current
   DESCRIPTION
      "Path: efm.performance.ifOutBandwidth.2min

       unit name = bps
       formula = 8 * ; 8 /"
   ::= {pr1646v2XEfmOutBandwidthEntry 671088640}

pr1646v2XEfmOutBandwidth5min OBJECT-TYPE
   SYNTAX      Integer32
   MAX-ACCESS  read-only
   STATUS      current
   DESCRIPTION
      "Path: efm.performance.ifOutBandwidth.5min

       unit name = bps
       formula = 8 * ; 8 /"
   ::= {pr1646v2XEfmOutBandwidthEntry 1677721600}


pr1646v2XEfmInP OBJECT IDENTIFIER ::= {pr1646v2XEfm 307}

pr1646v2XEfmInPSSCTable OBJECT-TYPE
   SYNTAX      SEQUENCE OF Pr1646v2XEfmInPEntry
   MAX-ACCESS  not-accessible
   STATUS      current
   DESCRIPTION
      "h2IfInPerformance"
   ::= {pr1646v2XEfmInP 1}

pr1646v2XEfmInPEntry OBJECT-TYPE
   SYNTAX      Pr1646v2XEfmInPEntry
   MAX-ACCESS  not-accessible
   STATUS      current
   DESCRIPTION
      ""
   INDEX      { pr1646v2XEfmInPTableIx }
   ::= {pr1646v2XEfmInPSSCTable 1}

Pr1646v2XEfmInPEntry ::=
   SEQUENCE
      {
      pr1646v2XEfmInPTableIx
         TableIndex,
      pr1646v2XEfmInPSysUpTime
         TimeTicks,
      pr1646v2XEfmInPIfUpTime
         TimeTicks,
      pr1646v2XEfmInPIfStatChanges
         Counter32,
      pr1646v2XEfmInPIfInOctets
         Counter64,
      pr1646v2XEfmInPIfInUCPkts
         Counter64,
      pr1646v2XEfmInPIfInNUCPkts
         Counter64,
      pr1646v2XEfmInPIfInBCPkts
         Counter64,
      pr1646v2XEfmInPIfInMCPkts
         Counter64,
      pr1646v2XEfmInPIfInDiscards
         Counter64,
      pr1646v2XEfmInPIfInErrors
         Counter64,
      pr1646v2XEfmInPIfInUnkwn
         Counter64,
      pr1646v2XEfmInPInDropEx
         Counter64,
      pr1646v2XEfmInPInDropNoMac
         Counter64,
      pr1646v2XEfmInPInDropNUCast
         Counter64,
      pr1646v2XEfmInPInDropFilter
         Counter64,
      pr1646v2XEfmInPIfInBandwidth
         Integer32,
      pr1646v2XEfmInPIfOutOctets
         Counter64,
      pr1646v2XEfmInPIfOutUCPkts
         Counter64,
      pr1646v2XEfmInPIfOutNUCPkts
         Counter64,
      pr1646v2XEfmInPIfOutBCPkts
         Counter64,
      pr1646v2XEfmInPIfOutMCPkts
         Counter64,
      pr1646v2XEfmInPIfOutDiscards
         Counter64,
      pr1646v2XEfmInPIfOutErrors
         Counter64,
      pr1646v2XEfmInPOutDropEx
         Counter64,
      pr1646v2XEfmInPOutDropNoArp
         Counter64,
      pr1646v2XEfmInPOutDropFilter
         Counter64,
      pr1646v2XEfmInPIfOutBandwidth
         Integer32,
      pr1646v2XEfmInPIfErrSec
         Counter32
      }

pr1646v2XEfmInPTableIx OBJECT-TYPE
   SYNTAX      TableIndex
   MAX-ACCESS  not-accessible
   STATUS      current
   DESCRIPTION
      ""
   ::= {pr1646v2XEfmInPEntry 11}

pr1646v2XEfmInPSysUpTime OBJECT-TYPE
   SYNTAX      TimeTicks
   MAX-ACCESS  read-only
   STATUS      current
   DESCRIPTION
      "Path: efm.performance.h2Performance.sysUpTime

       Time in centi-second."
   ::= {pr1646v2XEfmInPEntry 16777216}

pr1646v2XEfmInPIfUpTime OBJECT-TYPE
   SYNTAX      TimeTicks
   MAX-ACCESS  read-only
   STATUS      current
   DESCRIPTION
      "Path: efm.performance.h2Performance.ifUpTime

       Time in centi-second."
   ::= {pr1646v2XEfmInPEntry 33554432}

pr1646v2XEfmInPIfStatChanges OBJECT-TYPE
   SYNTAX      Counter32
   MAX-ACCESS  read-only
   STATUS      current
   DESCRIPTION
      "Path: efm.performance.h2Performance.ifStatusChanges

       32 bit unsigned wrappable counter."
   ::= {pr1646v2XEfmInPEntry 50331648}

pr1646v2XEfmInPIfInOctets OBJECT-TYPE
   SYNTAX      Counter64
   MAX-ACCESS  read-only
   STATUS      current
   DESCRIPTION
      "Path: efm.performance.h2Performance.ifInOctets

       64 bit unsigned wrappable counter."
   ::= {pr1646v2XEfmInPEntry 67108864}

pr1646v2XEfmInPIfInUCPkts OBJECT-TYPE
   SYNTAX      Counter64
   MAX-ACCESS  read-only
   STATUS      current
   DESCRIPTION
      "Path: efm.performance.h2Performance.ifInUcastPkts

       64 bit unsigned wrappable counter."
   ::= {pr1646v2XEfmInPEntry 83886080}

pr1646v2XEfmInPIfInNUCPkts OBJECT-TYPE
   SYNTAX      Counter64
   MAX-ACCESS  read-only
   STATUS      current
   DESCRIPTION
      "Path: efm.performance.h2Performance.ifInNUcastPkts

       64 bit unsigned wrappable counter."
   ::= {pr1646v2XEfmInPEntry 100663296}

pr1646v2XEfmInPIfInBCPkts OBJECT-TYPE
   SYNTAX      Counter64
   MAX-ACCESS  read-only
   STATUS      current
   DESCRIPTION
      "Path: efm.performance.h2Performance.ifInBcastPkts

       64 bit unsigned wrappable counter."
   ::= {pr1646v2XEfmInPEntry 419430400}

pr1646v2XEfmInPIfInMCPkts OBJECT-TYPE
   SYNTAX      Counter64
   MAX-ACCESS  read-only
   STATUS      current
   DESCRIPTION
      "Path: efm.performance.h2Performance.ifInMcastPkts

       64 bit unsigned wrappable counter."
   ::= {pr1646v2XEfmInPEntry 436207616}

pr1646v2XEfmInPIfInDiscards OBJECT-TYPE
   SYNTAX      Counter64
   MAX-ACCESS  read-only
   STATUS      current
   DESCRIPTION
      "Path: efm.performance.h2Performance.ifInDiscards

       64 bit unsigned wrappable counter."
   ::= {pr1646v2XEfmInPEntry 117440512}

pr1646v2XEfmInPIfInErrors OBJECT-TYPE
   SYNTAX      Counter64
   MAX-ACCESS  read-only
   STATUS      current
   DESCRIPTION
      "Path: efm.performance.h2Performance.ifInErrors

       64 bit unsigned wrappable counter."
   ::= {pr1646v2XEfmInPEntry 134217728}

pr1646v2XEfmInPIfInUnkwn OBJECT-TYPE
   SYNTAX      Counter64
   MAX-ACCESS  read-only
   STATUS      current
   DESCRIPTION
      "Path: efm.performance.h2Performance.ifInUnknownProtos

       64 bit unsigned wrappable counter."
   ::= {pr1646v2XEfmInPEntry 150994944}

pr1646v2XEfmInPInDropEx OBJECT-TYPE
   SYNTAX      Counter64
   MAX-ACCESS  read-only
   STATUS      current
   DESCRIPTION
      "Path: efm.performance.h2Performance.ifInDropLevelExceeded

       64 bit unsigned wrappable counter."
   ::= {pr1646v2XEfmInPEntry 335544320}

pr1646v2XEfmInPInDropNoMac OBJECT-TYPE
   SYNTAX      Counter64
   MAX-ACCESS  read-only
   STATUS      current
   DESCRIPTION
      "Path: efm.performance.h2Performance.fInDiscardsNoMacFit

       64 bit unsigned wrappable counter."
   ::= {pr1646v2XEfmInPEntry 301989888}

pr1646v2XEfmInPInDropNUCast OBJECT-TYPE
   SYNTAX      Counter64
   MAX-ACCESS  read-only
   STATUS      current
   DESCRIPTION
      "Path: efm.performance.h2Performance.fInDiscardsNUCast

       64 bit unsigned wrappable counter."
   ::= {pr1646v2XEfmInPEntry 318767104}

pr1646v2XEfmInPInDropFilter OBJECT-TYPE
   SYNTAX      Counter64
   MAX-ACCESS  read-only
   STATUS      current
   DESCRIPTION
      "Path: efm.performance.h2Performance.fInDiscardsFilter

       64 bit unsigned wrappable counter."
   ::= {pr1646v2XEfmInPEntry 385875968}

pr1646v2XEfmInPIfInBandwidth OBJECT-TYPE
   SYNTAX      Integer32
   MAX-ACCESS  read-only
   STATUS      current
   DESCRIPTION
      "Path: efm.performance.h2Performance.ifInBandwidth

       unit name = bps
       formula = 8 * ; 8 /"
   ::= {pr1646v2XEfmInPEntry 268435456}

pr1646v2XEfmInPIfOutOctets OBJECT-TYPE
   SYNTAX      Counter64
   MAX-ACCESS  read-only
   STATUS      current
   DESCRIPTION
      "Path: efm.performance.h2Performance.ifOutOctets

       64 bit unsigned wrappable counter."
   ::= {pr1646v2XEfmInPEntry 167772160}

pr1646v2XEfmInPIfOutUCPkts OBJECT-TYPE
   SYNTAX      Counter64
   MAX-ACCESS  read-only
   STATUS      current
   DESCRIPTION
      "Path: efm.performance.h2Performance.ifOutUcastPkts

       64 bit unsigned wrappable counter."
   ::= {pr1646v2XEfmInPEntry 184549376}

pr1646v2XEfmInPIfOutNUCPkts OBJECT-TYPE
   SYNTAX      Counter64
   MAX-ACCESS  read-only
   STATUS      current
   DESCRIPTION
      "Path: efm.performance.h2Performance.ifOutNUcastPkts

       64 bit unsigned wrappable counter."
   ::= {pr1646v2XEfmInPEntry 201326592}

pr1646v2XEfmInPIfOutBCPkts OBJECT-TYPE
   SYNTAX      Counter64
   MAX-ACCESS  read-only
   STATUS      current
   DESCRIPTION
      "Path: efm.performance.h2Performance.ifOutBcastPkts

       64 bit unsigned wrappable counter."
   ::= {pr1646v2XEfmInPEntry 452984832}

pr1646v2XEfmInPIfOutMCPkts OBJECT-TYPE
   SYNTAX      Counter64
   MAX-ACCESS  read-only
   STATUS      current
   DESCRIPTION
      "Path: efm.performance.h2Performance.ifOutMcastPkts

       64 bit unsigned wrappable counter."
   ::= {pr1646v2XEfmInPEntry 469762048}

pr1646v2XEfmInPIfOutDiscards OBJECT-TYPE
   SYNTAX      Counter64
   MAX-ACCESS  read-only
   STATUS      current
   DESCRIPTION
      "Path: efm.performance.h2Performance.ifOutDiscards

       64 bit unsigned wrappable counter."
   ::= {pr1646v2XEfmInPEntry 218103808}

pr1646v2XEfmInPIfOutErrors OBJECT-TYPE
   SYNTAX      Counter64
   MAX-ACCESS  read-only
   STATUS      current
   DESCRIPTION
      "Path: efm.performance.h2Performance.ifOutErrors

       64 bit unsigned wrappable counter."
   ::= {pr1646v2XEfmInPEntry 234881024}

pr1646v2XEfmInPOutDropEx OBJECT-TYPE
   SYNTAX      Counter64
   MAX-ACCESS  read-only
   STATUS      current
   DESCRIPTION
      "Path: efm.performance.h2Performance.ifOutDropLevelExceeded

       64 bit unsigned wrappable counter."
   ::= {pr1646v2XEfmInPEntry 352321536}

pr1646v2XEfmInPOutDropNoArp OBJECT-TYPE
   SYNTAX      Counter64
   MAX-ACCESS  read-only
   STATUS      current
   DESCRIPTION
      "Path: efm.performance.h2Performance.ifOutDiscardsNoArp

       64 bit unsigned wrappable counter."
   ::= {pr1646v2XEfmInPEntry 369098752}

pr1646v2XEfmInPOutDropFilter OBJECT-TYPE
   SYNTAX      Counter64
   MAX-ACCESS  read-only
   STATUS      current
   DESCRIPTION
      "Path: efm.performance.h2Performance.ifOutDiscardsFilter

       64 bit unsigned wrappable counter."
   ::= {pr1646v2XEfmInPEntry 402653184}

pr1646v2XEfmInPIfOutBandwidth OBJECT-TYPE
   SYNTAX      Integer32
   MAX-ACCESS  read-only
   STATUS      current
   DESCRIPTION
      "Path: efm.performance.h2Performance.ifOutBandwidth

       unit name = bps
       formula = 8 * ; 8 /"
   ::= {pr1646v2XEfmInPEntry 285212672}

pr1646v2XEfmInPIfErrSec OBJECT-TYPE
   SYNTAX      Counter32
   MAX-ACCESS  read-only
   STATUS      current
   DESCRIPTION
      "Path: efm.performance.h2Performance.ifErrSec

       32 bit unsigned wrappable counter."
   ::= {pr1646v2XEfmInPEntry 251658240}


pr1646v2XEfmH24InP OBJECT IDENTIFIER ::= {pr1646v2XEfm 308}

pr1646v2XEfmH24InPSSCTable OBJECT-TYPE
   SYNTAX      SEQUENCE OF Pr1646v2XEfmH24InPEntry
   MAX-ACCESS  not-accessible
   STATUS      current
   DESCRIPTION
      "h24IfInPerformance"
   ::= {pr1646v2XEfmH24InP 1}

pr1646v2XEfmH24InPEntry OBJECT-TYPE
   SYNTAX      Pr1646v2XEfmH24InPEntry
   MAX-ACCESS  not-accessible
   STATUS      current
   DESCRIPTION
      ""
   INDEX      { pr1646v2XEfmH24InPTableIx }
   ::= {pr1646v2XEfmH24InPSSCTable 1}

Pr1646v2XEfmH24InPEntry ::=
   SEQUENCE
      {
      pr1646v2XEfmH24InPTableIx
         TableIndex,
      pr1646v2XEfmH24InPSysUpTime
         TimeTicks,
      pr1646v2XEfmH24InPIfUpTime
         TimeTicks,
      pr1646v2XEfmH24InPIfStatChanges
         Counter32,
      pr1646v2XEfmH24InPIfInOctets
         Counter64,
      pr1646v2XEfmH24InPIfInUCPkts
         Counter64,
      pr1646v2XEfmH24InPIfInNUCPkts
         Counter64,
      pr1646v2XEfmH24InPIfInBCPkts
         Counter64,
      pr1646v2XEfmH24InPIfInMCPkts
         Counter64,
      pr1646v2XEfmH24InPIfInDiscards
         Counter64,
      pr1646v2XEfmH24InPIfInErrors
         Counter64,
      pr1646v2XEfmH24InPIfInUnkwn
         Counter64,
      pr1646v2XEfmH24InPInDropEx
         Counter64,
      pr1646v2XEfmH24InPInDropNoMac
         Counter64,
      pr1646v2XEfmH24InPInDropNUCast
         Counter64,
      pr1646v2XEfmH24InPInDropFilter
         Counter64,
      pr1646v2XEfmH24InPIfInBandwidth
         Integer32,
      pr1646v2XEfmH24InPIfOutOctets
         Counter64,
      pr1646v2XEfmH24InPIfOutUCPkts
         Counter64,
      pr1646v2XEfmH24InPIfOutNUCPkts
         Counter64,
      pr1646v2XEfmH24InPIfOutBCPkts
         Counter64,
      pr1646v2XEfmH24InPIfOutMCPkts
         Counter64,
      pr1646v2XEfmH24InPIfOutDiscards
         Counter64,
      pr1646v2XEfmH24InPIfOutErrors
         Counter64,
      pr1646v2XEfmH24InPOutDropEx
         Counter64,
      pr1646v2XEfmH24InPOutDropNoArp
         Counter64,
      pr1646v2XEfmH24InPOutDropFilter
         Counter64,
      pr1646v2XEfmH24InPIfOutBandwidth
         Integer32,
      pr1646v2XEfmH24InPIfErrSec
         Counter32
      }

pr1646v2XEfmH24InPTableIx OBJECT-TYPE
   SYNTAX      TableIndex
   MAX-ACCESS  not-accessible
   STATUS      current
   DESCRIPTION
      ""
   ::= {pr1646v2XEfmH24InPEntry 11}

pr1646v2XEfmH24InPSysUpTime OBJECT-TYPE
   SYNTAX      TimeTicks
   MAX-ACCESS  read-only
   STATUS      current
   DESCRIPTION
      "Path: efm.performance.h24Performance.sysUpTime

       Time in centi-second."
   ::= {pr1646v2XEfmH24InPEntry 16777216}

pr1646v2XEfmH24InPIfUpTime OBJECT-TYPE
   SYNTAX      TimeTicks
   MAX-ACCESS  read-only
   STATUS      current
   DESCRIPTION
      "Path: efm.performance.h24Performance.ifUpTime

       Time in centi-second."
   ::= {pr1646v2XEfmH24InPEntry 33554432}

pr1646v2XEfmH24InPIfStatChanges OBJECT-TYPE
   SYNTAX      Counter32
   MAX-ACCESS  read-only
   STATUS      current
   DESCRIPTION
      "Path: efm.performance.h24Performance.ifStatusChanges

       32 bit unsigned wrappable counter."
   ::= {pr1646v2XEfmH24InPEntry 50331648}

pr1646v2XEfmH24InPIfInOctets OBJECT-TYPE
   SYNTAX      Counter64
   MAX-ACCESS  read-only
   STATUS      current
   DESCRIPTION
      "Path: efm.performance.h24Performance.ifInOctets

       64 bit unsigned wrappable counter."
   ::= {pr1646v2XEfmH24InPEntry 67108864}

pr1646v2XEfmH24InPIfInUCPkts OBJECT-TYPE
   SYNTAX      Counter64
   MAX-ACCESS  read-only
   STATUS      current
   DESCRIPTION
      "Path: efm.performance.h24Performance.ifInUcastPkts

       64 bit unsigned wrappable counter."
   ::= {pr1646v2XEfmH24InPEntry 83886080}

pr1646v2XEfmH24InPIfInNUCPkts OBJECT-TYPE
   SYNTAX      Counter64
   MAX-ACCESS  read-only
   STATUS      current
   DESCRIPTION
      "Path: efm.performance.h24Performance.ifInNUcastPkts

       64 bit unsigned wrappable counter."
   ::= {pr1646v2XEfmH24InPEntry 100663296}

pr1646v2XEfmH24InPIfInBCPkts OBJECT-TYPE
   SYNTAX      Counter64
   MAX-ACCESS  read-only
   STATUS      current
   DESCRIPTION
      "Path: efm.performance.h24Performance.ifInBcastPkts

       64 bit unsigned wrappable counter."
   ::= {pr1646v2XEfmH24InPEntry 419430400}

pr1646v2XEfmH24InPIfInMCPkts OBJECT-TYPE
   SYNTAX      Counter64
   MAX-ACCESS  read-only
   STATUS      current
   DESCRIPTION
      "Path: efm.performance.h24Performance.ifInMcastPkts

       64 bit unsigned wrappable counter."
   ::= {pr1646v2XEfmH24InPEntry 436207616}

pr1646v2XEfmH24InPIfInDiscards OBJECT-TYPE
   SYNTAX      Counter64
   MAX-ACCESS  read-only
   STATUS      current
   DESCRIPTION
      "Path: efm.performance.h24Performance.ifInDiscards

       64 bit unsigned wrappable counter."
   ::= {pr1646v2XEfmH24InPEntry 117440512}

pr1646v2XEfmH24InPIfInErrors OBJECT-TYPE
   SYNTAX      Counter64
   MAX-ACCESS  read-only
   STATUS      current
   DESCRIPTION
      "Path: efm.performance.h24Performance.ifInErrors

       64 bit unsigned wrappable counter."
   ::= {pr1646v2XEfmH24InPEntry 134217728}

pr1646v2XEfmH24InPIfInUnkwn OBJECT-TYPE
   SYNTAX      Counter64
   MAX-ACCESS  read-only
   STATUS      current
   DESCRIPTION
      "Path: efm.performance.h24Performance.ifInUnknownProtos

       64 bit unsigned wrappable counter."
   ::= {pr1646v2XEfmH24InPEntry 150994944}

pr1646v2XEfmH24InPInDropEx OBJECT-TYPE
   SYNTAX      Counter64
   MAX-ACCESS  read-only
   STATUS      current
   DESCRIPTION
      "Path: efm.performance.h24Performance.ifInDropLevelExceeded

       64 bit unsigned wrappable counter."
   ::= {pr1646v2XEfmH24InPEntry 335544320}

pr1646v2XEfmH24InPInDropNoMac OBJECT-TYPE
   SYNTAX      Counter64
   MAX-ACCESS  read-only
   STATUS      current
   DESCRIPTION
      "Path: efm.performance.h24Performance.fInDiscardsNoMacFit

       64 bit unsigned wrappable counter."
   ::= {pr1646v2XEfmH24InPEntry 301989888}

pr1646v2XEfmH24InPInDropNUCast OBJECT-TYPE
   SYNTAX      Counter64
   MAX-ACCESS  read-only
   STATUS      current
   DESCRIPTION
      "Path: efm.performance.h24Performance.fInDiscardsNUCast

       64 bit unsigned wrappable counter."
   ::= {pr1646v2XEfmH24InPEntry 318767104}

pr1646v2XEfmH24InPInDropFilter OBJECT-TYPE
   SYNTAX      Counter64
   MAX-ACCESS  read-only
   STATUS      current
   DESCRIPTION
      "Path: efm.performance.h24Performance.fInDiscardsFilter

       64 bit unsigned wrappable counter."
   ::= {pr1646v2XEfmH24InPEntry 385875968}

pr1646v2XEfmH24InPIfInBandwidth OBJECT-TYPE
   SYNTAX      Integer32
   MAX-ACCESS  read-only
   STATUS      current
   DESCRIPTION
      "Path: efm.performance.h24Performance.ifInBandwidth

       unit name = bps
       formula = 8 * ; 8 /"
   ::= {pr1646v2XEfmH24InPEntry 268435456}

pr1646v2XEfmH24InPIfOutOctets OBJECT-TYPE
   SYNTAX      Counter64
   MAX-ACCESS  read-only
   STATUS      current
   DESCRIPTION
      "Path: efm.performance.h24Performance.ifOutOctets

       64 bit unsigned wrappable counter."
   ::= {pr1646v2XEfmH24InPEntry 167772160}

pr1646v2XEfmH24InPIfOutUCPkts OBJECT-TYPE
   SYNTAX      Counter64
   MAX-ACCESS  read-only
   STATUS      current
   DESCRIPTION
      "Path: efm.performance.h24Performance.ifOutUcastPkts

       64 bit unsigned wrappable counter."
   ::= {pr1646v2XEfmH24InPEntry 184549376}

pr1646v2XEfmH24InPIfOutNUCPkts OBJECT-TYPE
   SYNTAX      Counter64
   MAX-ACCESS  read-only
   STATUS      current
   DESCRIPTION
      "Path: efm.performance.h24Performance.ifOutNUcastPkts

       64 bit unsigned wrappable counter."
   ::= {pr1646v2XEfmH24InPEntry 201326592}

pr1646v2XEfmH24InPIfOutBCPkts OBJECT-TYPE
   SYNTAX      Counter64
   MAX-ACCESS  read-only
   STATUS      current
   DESCRIPTION
      "Path: efm.performance.h24Performance.ifOutBcastPkts

       64 bit unsigned wrappable counter."
   ::= {pr1646v2XEfmH24InPEntry 452984832}

pr1646v2XEfmH24InPIfOutMCPkts OBJECT-TYPE
   SYNTAX      Counter64
   MAX-ACCESS  read-only
   STATUS      current
   DESCRIPTION
      "Path: efm.performance.h24Performance.ifOutMcastPkts

       64 bit unsigned wrappable counter."
   ::= {pr1646v2XEfmH24InPEntry 469762048}

pr1646v2XEfmH24InPIfOutDiscards OBJECT-TYPE
   SYNTAX      Counter64
   MAX-ACCESS  read-only
   STATUS      current
   DESCRIPTION
      "Path: efm.performance.h24Performance.ifOutDiscards

       64 bit unsigned wrappable counter."
   ::= {pr1646v2XEfmH24InPEntry 218103808}

pr1646v2XEfmH24InPIfOutErrors OBJECT-TYPE
   SYNTAX      Counter64
   MAX-ACCESS  read-only
   STATUS      current
   DESCRIPTION
      "Path: efm.performance.h24Performance.ifOutErrors

       64 bit unsigned wrappable counter."
   ::= {pr1646v2XEfmH24InPEntry 234881024}

pr1646v2XEfmH24InPOutDropEx OBJECT-TYPE
   SYNTAX      Counter64
   MAX-ACCESS  read-only
   STATUS      current
   DESCRIPTION
      "Path: efm.performance.h24Performance.ifOutDropLevelExceeded

       64 bit unsigned wrappable counter."
   ::= {pr1646v2XEfmH24InPEntry 352321536}

pr1646v2XEfmH24InPOutDropNoArp OBJECT-TYPE
   SYNTAX      Counter64
   MAX-ACCESS  read-only
   STATUS      current
   DESCRIPTION
      "Path: efm.performance.h24Performance.ifOutDiscardsNoArp

       64 bit unsigned wrappable counter."
   ::= {pr1646v2XEfmH24InPEntry 369098752}

pr1646v2XEfmH24InPOutDropFilter OBJECT-TYPE
   SYNTAX      Counter64
   MAX-ACCESS  read-only
   STATUS      current
   DESCRIPTION
      "Path: efm.performance.h24Performance.ifOutDiscardsFilter

       64 bit unsigned wrappable counter."
   ::= {pr1646v2XEfmH24InPEntry 402653184}

pr1646v2XEfmH24InPIfOutBandwidth OBJECT-TYPE
   SYNTAX      Integer32
   MAX-ACCESS  read-only
   STATUS      current
   DESCRIPTION
      "Path: efm.performance.h24Performance.ifOutBandwidth

       unit name = bps
       formula = 8 * ; 8 /"
   ::= {pr1646v2XEfmH24InPEntry 285212672}

pr1646v2XEfmH24InPIfErrSec OBJECT-TYPE
   SYNTAX      Counter32
   MAX-ACCESS  read-only
   STATUS      current
   DESCRIPTION
      "Path: efm.performance.h24Performance.ifErrSec

       32 bit unsigned wrappable counter."
   ::= {pr1646v2XEfmH24InPEntry 251658240}


pr1646v2XEfmD7InP OBJECT IDENTIFIER ::= {pr1646v2XEfm 309}

pr1646v2XEfmD7InPSSCTable OBJECT-TYPE
   SYNTAX      SEQUENCE OF Pr1646v2XEfmD7InPEntry
   MAX-ACCESS  not-accessible
   STATUS      current
   DESCRIPTION
      "d7IfInPerformance"
   ::= {pr1646v2XEfmD7InP 1}

pr1646v2XEfmD7InPEntry OBJECT-TYPE
   SYNTAX      Pr1646v2XEfmD7InPEntry
   MAX-ACCESS  not-accessible
   STATUS      current
   DESCRIPTION
      ""
   INDEX      { pr1646v2XEfmD7InPTableIx }
   ::= {pr1646v2XEfmD7InPSSCTable 1}

Pr1646v2XEfmD7InPEntry ::=
   SEQUENCE
      {
      pr1646v2XEfmD7InPTableIx
         TableIndex,
      pr1646v2XEfmD7InPSysUpTime
         TimeTicks,
      pr1646v2XEfmD7InPIfUpTime
         TimeTicks,
      pr1646v2XEfmD7InPIfStatChanges
         Counter32,
      pr1646v2XEfmD7InPIfInOctets
         Counter64,
      pr1646v2XEfmD7InPIfInUCPkts
         Counter64,
      pr1646v2XEfmD7InPIfInNUCPkts
         Counter64,
      pr1646v2XEfmD7InPIfInBCPkts
         Counter64,
      pr1646v2XEfmD7InPIfInMCPkts
         Counter64,
      pr1646v2XEfmD7InPIfInDiscards
         Counter64,
      pr1646v2XEfmD7InPIfInErrors
         Counter64,
      pr1646v2XEfmD7InPIfInUnkwn
         Counter64,
      pr1646v2XEfmD7InPInDropEx
         Counter64,
      pr1646v2XEfmD7InPInDropNoMac
         Counter64,
      pr1646v2XEfmD7InPInDropNUCast
         Counter64,
      pr1646v2XEfmD7InPInDropFilter
         Counter64,
      pr1646v2XEfmD7InPIfInBandwidth
         Integer32,
      pr1646v2XEfmD7InPIfOutOctets
         Counter64,
      pr1646v2XEfmD7InPIfOutUCPkts
         Counter64,
      pr1646v2XEfmD7InPIfOutNUCPkts
         Counter64,
      pr1646v2XEfmD7InPIfOutBCPkts
         Counter64,
      pr1646v2XEfmD7InPIfOutMCPkts
         Counter64,
      pr1646v2XEfmD7InPIfOutDiscards
         Counter64,
      pr1646v2XEfmD7InPIfOutErrors
         Counter64,
      pr1646v2XEfmD7InPOutDropEx
         Counter64,
      pr1646v2XEfmD7InPOutDropNoArp
         Counter64,
      pr1646v2XEfmD7InPOutDropFilter
         Counter64,
      pr1646v2XEfmD7InPIfOutBandwidth
         Integer32,
      pr1646v2XEfmD7InPIfErrSec
         Counter32
      }

pr1646v2XEfmD7InPTableIx OBJECT-TYPE
   SYNTAX      TableIndex
   MAX-ACCESS  not-accessible
   STATUS      current
   DESCRIPTION
      ""
   ::= {pr1646v2XEfmD7InPEntry 11}

pr1646v2XEfmD7InPSysUpTime OBJECT-TYPE
   SYNTAX      TimeTicks
   MAX-ACCESS  read-only
   STATUS      current
   DESCRIPTION
      "Path: efm.performance.d7Performance.sysUpTime

       Time in centi-second."
   ::= {pr1646v2XEfmD7InPEntry 16777216}

pr1646v2XEfmD7InPIfUpTime OBJECT-TYPE
   SYNTAX      TimeTicks
   MAX-ACCESS  read-only
   STATUS      current
   DESCRIPTION
      "Path: efm.performance.d7Performance.ifUpTime

       Time in centi-second."
   ::= {pr1646v2XEfmD7InPEntry 33554432}

pr1646v2XEfmD7InPIfStatChanges OBJECT-TYPE
   SYNTAX      Counter32
   MAX-ACCESS  read-only
   STATUS      current
   DESCRIPTION
      "Path: efm.performance.d7Performance.ifStatusChanges

       32 bit unsigned wrappable counter."
   ::= {pr1646v2XEfmD7InPEntry 50331648}

pr1646v2XEfmD7InPIfInOctets OBJECT-TYPE
   SYNTAX      Counter64
   MAX-ACCESS  read-only
   STATUS      current
   DESCRIPTION
      "Path: efm.performance.d7Performance.ifInOctets

       64 bit unsigned wrappable counter."
   ::= {pr1646v2XEfmD7InPEntry 67108864}

pr1646v2XEfmD7InPIfInUCPkts OBJECT-TYPE
   SYNTAX      Counter64
   MAX-ACCESS  read-only
   STATUS      current
   DESCRIPTION
      "Path: efm.performance.d7Performance.ifInUcastPkts

       64 bit unsigned wrappable counter."
   ::= {pr1646v2XEfmD7InPEntry 83886080}

pr1646v2XEfmD7InPIfInNUCPkts OBJECT-TYPE
   SYNTAX      Counter64
   MAX-ACCESS  read-only
   STATUS      current
   DESCRIPTION
      "Path: efm.performance.d7Performance.ifInNUcastPkts

       64 bit unsigned wrappable counter."
   ::= {pr1646v2XEfmD7InPEntry 100663296}

pr1646v2XEfmD7InPIfInBCPkts OBJECT-TYPE
   SYNTAX      Counter64
   MAX-ACCESS  read-only
   STATUS      current
   DESCRIPTION
      "Path: efm.performance.d7Performance.ifInBcastPkts

       64 bit unsigned wrappable counter."
   ::= {pr1646v2XEfmD7InPEntry 419430400}

pr1646v2XEfmD7InPIfInMCPkts OBJECT-TYPE
   SYNTAX      Counter64
   MAX-ACCESS  read-only
   STATUS      current
   DESCRIPTION
      "Path: efm.performance.d7Performance.ifInMcastPkts

       64 bit unsigned wrappable counter."
   ::= {pr1646v2XEfmD7InPEntry 436207616}

pr1646v2XEfmD7InPIfInDiscards OBJECT-TYPE
   SYNTAX      Counter64
   MAX-ACCESS  read-only
   STATUS      current
   DESCRIPTION
      "Path: efm.performance.d7Performance.ifInDiscards

       64 bit unsigned wrappable counter."
   ::= {pr1646v2XEfmD7InPEntry 117440512}

pr1646v2XEfmD7InPIfInErrors OBJECT-TYPE
   SYNTAX      Counter64
   MAX-ACCESS  read-only
   STATUS      current
   DESCRIPTION
      "Path: efm.performance.d7Performance.ifInErrors

       64 bit unsigned wrappable counter."
   ::= {pr1646v2XEfmD7InPEntry 134217728}

pr1646v2XEfmD7InPIfInUnkwn OBJECT-TYPE
   SYNTAX      Counter64
   MAX-ACCESS  read-only
   STATUS      current
   DESCRIPTION
      "Path: efm.performance.d7Performance.ifInUnknownProtos

       64 bit unsigned wrappable counter."
   ::= {pr1646v2XEfmD7InPEntry 150994944}

pr1646v2XEfmD7InPInDropEx OBJECT-TYPE
   SYNTAX      Counter64
   MAX-ACCESS  read-only
   STATUS      current
   DESCRIPTION
      "Path: efm.performance.d7Performance.ifInDropLevelExceeded

       64 bit unsigned wrappable counter."
   ::= {pr1646v2XEfmD7InPEntry 335544320}

pr1646v2XEfmD7InPInDropNoMac OBJECT-TYPE
   SYNTAX      Counter64
   MAX-ACCESS  read-only
   STATUS      current
   DESCRIPTION
      "Path: efm.performance.d7Performance.fInDiscardsNoMacFit

       64 bit unsigned wrappable counter."
   ::= {pr1646v2XEfmD7InPEntry 301989888}

pr1646v2XEfmD7InPInDropNUCast OBJECT-TYPE
   SYNTAX      Counter64
   MAX-ACCESS  read-only
   STATUS      current
   DESCRIPTION
      "Path: efm.performance.d7Performance.fInDiscardsNUCast

       64 bit unsigned wrappable counter."
   ::= {pr1646v2XEfmD7InPEntry 318767104}

pr1646v2XEfmD7InPInDropFilter OBJECT-TYPE
   SYNTAX      Counter64
   MAX-ACCESS  read-only
   STATUS      current
   DESCRIPTION
      "Path: efm.performance.d7Performance.fInDiscardsFilter

       64 bit unsigned wrappable counter."
   ::= {pr1646v2XEfmD7InPEntry 385875968}

pr1646v2XEfmD7InPIfInBandwidth OBJECT-TYPE
   SYNTAX      Integer32
   MAX-ACCESS  read-only
   STATUS      current
   DESCRIPTION
      "Path: efm.performance.d7Performance.ifInBandwidth

       unit name = bps
       formula = 8 * ; 8 /"
   ::= {pr1646v2XEfmD7InPEntry 268435456}

pr1646v2XEfmD7InPIfOutOctets OBJECT-TYPE
   SYNTAX      Counter64
   MAX-ACCESS  read-only
   STATUS      current
   DESCRIPTION
      "Path: efm.performance.d7Performance.ifOutOctets

       64 bit unsigned wrappable counter."
   ::= {pr1646v2XEfmD7InPEntry 167772160}

pr1646v2XEfmD7InPIfOutUCPkts OBJECT-TYPE
   SYNTAX      Counter64
   MAX-ACCESS  read-only
   STATUS      current
   DESCRIPTION
      "Path: efm.performance.d7Performance.ifOutUcastPkts

       64 bit unsigned wrappable counter."
   ::= {pr1646v2XEfmD7InPEntry 184549376}

pr1646v2XEfmD7InPIfOutNUCPkts OBJECT-TYPE
   SYNTAX      Counter64
   MAX-ACCESS  read-only
   STATUS      current
   DESCRIPTION
      "Path: efm.performance.d7Performance.ifOutNUcastPkts

       64 bit unsigned wrappable counter."
   ::= {pr1646v2XEfmD7InPEntry 201326592}

pr1646v2XEfmD7InPIfOutBCPkts OBJECT-TYPE
   SYNTAX      Counter64
   MAX-ACCESS  read-only
   STATUS      current
   DESCRIPTION
      "Path: efm.performance.d7Performance.ifOutBcastPkts

       64 bit unsigned wrappable counter."
   ::= {pr1646v2XEfmD7InPEntry 452984832}

pr1646v2XEfmD7InPIfOutMCPkts OBJECT-TYPE
   SYNTAX      Counter64
   MAX-ACCESS  read-only
   STATUS      current
   DESCRIPTION
      "Path: efm.performance.d7Performance.ifOutMcastPkts

       64 bit unsigned wrappable counter."
   ::= {pr1646v2XEfmD7InPEntry 469762048}

pr1646v2XEfmD7InPIfOutDiscards OBJECT-TYPE
   SYNTAX      Counter64
   MAX-ACCESS  read-only
   STATUS      current
   DESCRIPTION
      "Path: efm.performance.d7Performance.ifOutDiscards

       64 bit unsigned wrappable counter."
   ::= {pr1646v2XEfmD7InPEntry 218103808}

pr1646v2XEfmD7InPIfOutErrors OBJECT-TYPE
   SYNTAX      Counter64
   MAX-ACCESS  read-only
   STATUS      current
   DESCRIPTION
      "Path: efm.performance.d7Performance.ifOutErrors

       64 bit unsigned wrappable counter."
   ::= {pr1646v2XEfmD7InPEntry 234881024}

pr1646v2XEfmD7InPOutDropEx OBJECT-TYPE
   SYNTAX      Counter64
   MAX-ACCESS  read-only
   STATUS      current
   DESCRIPTION
      "Path: efm.performance.d7Performance.ifOutDropLevelExceeded

       64 bit unsigned wrappable counter."
   ::= {pr1646v2XEfmD7InPEntry 352321536}

pr1646v2XEfmD7InPOutDropNoArp OBJECT-TYPE
   SYNTAX      Counter64
   MAX-ACCESS  read-only
   STATUS      current
   DESCRIPTION
      "Path: efm.performance.d7Performance.ifOutDiscardsNoArp

       64 bit unsigned wrappable counter."
   ::= {pr1646v2XEfmD7InPEntry 369098752}

pr1646v2XEfmD7InPOutDropFilter OBJECT-TYPE
   SYNTAX      Counter64
   MAX-ACCESS  read-only
   STATUS      current
   DESCRIPTION
      "Path: efm.performance.d7Performance.ifOutDiscardsFilter

       64 bit unsigned wrappable counter."
   ::= {pr1646v2XEfmD7InPEntry 402653184}

pr1646v2XEfmD7InPIfOutBandwidth OBJECT-TYPE
   SYNTAX      Integer32
   MAX-ACCESS  read-only
   STATUS      current
   DESCRIPTION
      "Path: efm.performance.d7Performance.ifOutBandwidth

       unit name = bps
       formula = 8 * ; 8 /"
   ::= {pr1646v2XEfmD7InPEntry 285212672}

pr1646v2XEfmD7InPIfErrSec OBJECT-TYPE
   SYNTAX      Counter32
   MAX-ACCESS  read-only
   STATUS      current
   DESCRIPTION
      "Path: efm.performance.d7Performance.ifErrSec

       32 bit unsigned wrappable counter."
   ::= {pr1646v2XEfmD7InPEntry 251658240}


pr1646v2XEfmOam OBJECT IDENTIFIER ::= {pr1646v2XEfm 910}

pr1646v2XEfmOamSSC OBJECT IDENTIFIER ::= {pr1646v2XEfmOam 1}

pr1646v2XEfmOamEntry OBJECT IDENTIFIER ::= {pr1646v2XEfmOamSSC 1}

pr1646v2XEfmOamInformationTx OBJECT-TYPE
   SYNTAX      Counter32
   MAX-ACCESS  read-only
   STATUS      current
   DESCRIPTION
      "Path: efm.performance.oam.informationTx

       32 bit unsigned wrappable counter."
   ::= {pr1646v2XEfmOamEntry 16777216}

pr1646v2XEfmOamInformationRx OBJECT-TYPE
   SYNTAX      Counter32
   MAX-ACCESS  read-only
   STATUS      current
   DESCRIPTION
      "Path: efm.performance.oam.informationRx

       32 bit unsigned wrappable counter."
   ::= {pr1646v2XEfmOamEntry 33554432}

pr1646v2XEfmOamUniqueEventNotifTx OBJECT-TYPE
   SYNTAX      Counter32
   MAX-ACCESS  read-only
   STATUS      current
   DESCRIPTION
      "Path: efm.performance.oam.uniqueEventNotifTx

       32 bit unsigned wrappable counter."
   ::= {pr1646v2XEfmOamEntry 50331648}

pr1646v2XEfmOamUniqueEventNotifRx OBJECT-TYPE
   SYNTAX      Counter32
   MAX-ACCESS  read-only
   STATUS      current
   DESCRIPTION
      "Path: efm.performance.oam.uniqueEventNotifRx

       32 bit unsigned wrappable counter."
   ::= {pr1646v2XEfmOamEntry 67108864}

pr1646v2XEfmOamLoopbackCtrlTx OBJECT-TYPE
   SYNTAX      Counter32
   MAX-ACCESS  read-only
   STATUS      current
   DESCRIPTION
      "Path: efm.performance.oam.loopbackCtrlTx

       32 bit unsigned wrappable counter."
   ::= {pr1646v2XEfmOamEntry 117440512}

pr1646v2XEfmOamLoopbackCtrlRx OBJECT-TYPE
   SYNTAX      Counter32
   MAX-ACCESS  read-only
   STATUS      current
   DESCRIPTION
      "Path: efm.performance.oam.loopbackCtrlRx

       32 bit unsigned wrappable counter."
   ::= {pr1646v2XEfmOamEntry 134217728}

pr1646v2XEfmOamVarReqTx OBJECT-TYPE
   SYNTAX      Counter32
   MAX-ACCESS  read-only
   STATUS      current
   DESCRIPTION
      "Path: efm.performance.oam.varReqTx

       32 bit unsigned wrappable counter."
   ::= {pr1646v2XEfmOamEntry 150994944}

pr1646v2XEfmOamVarReqRx OBJECT-TYPE
   SYNTAX      Counter32
   MAX-ACCESS  read-only
   STATUS      current
   DESCRIPTION
      "Path: efm.performance.oam.varReqRx

       32 bit unsigned wrappable counter."
   ::= {pr1646v2XEfmOamEntry 167772160}

pr1646v2XEfmOamVarRespTx OBJECT-TYPE
   SYNTAX      Counter32
   MAX-ACCESS  read-only
   STATUS      current
   DESCRIPTION
      "Path: efm.performance.oam.varRespTx

       32 bit unsigned wrappable counter."
   ::= {pr1646v2XEfmOamEntry 184549376}

pr1646v2XEfmOamVarRespRx OBJECT-TYPE
   SYNTAX      Counter32
   MAX-ACCESS  read-only
   STATUS      current
   DESCRIPTION
      "Path: efm.performance.oam.varRespRx

       32 bit unsigned wrappable counter."
   ::= {pr1646v2XEfmOamEntry 201326592}

pr1646v2XEfmOamOrgSpecificTx OBJECT-TYPE
   SYNTAX      Counter32
   MAX-ACCESS  read-only
   STATUS      current
   DESCRIPTION
      "Path: efm.performance.oam.orgSpecificTx

       32 bit unsigned wrappable counter."
   ::= {pr1646v2XEfmOamEntry 218103808}

pr1646v2XEfmOamOrgSpecificRx OBJECT-TYPE
   SYNTAX      Counter32
   MAX-ACCESS  read-only
   STATUS      current
   DESCRIPTION
      "Path: efm.performance.oam.orgSpecificRx

       32 bit unsigned wrappable counter."
   ::= {pr1646v2XEfmOamEntry 234881024}

pr1646v2XEfmOamUnsupportedCodesTx OBJECT-TYPE
   SYNTAX      Counter32
   MAX-ACCESS  read-only
   STATUS      current
   DESCRIPTION
      "Path: efm.performance.oam.unsupportedCodesTx

       32 bit unsigned wrappable counter."
   ::= {pr1646v2XEfmOamEntry 251658240}

pr1646v2XEfmOamUnsupportedCodesRx OBJECT-TYPE
   SYNTAX      Counter32
   MAX-ACCESS  read-only
   STATUS      current
   DESCRIPTION
      "Path: efm.performance.oam.unsupportedCodesRx

       32 bit unsigned wrappable counter."
   ::= {pr1646v2XEfmOamEntry 268435456}

pr1646v2XEfmOamPduDiscardRx OBJECT-TYPE
   SYNTAX      Counter32
   MAX-ACCESS  read-only
   STATUS      current
   DESCRIPTION
      "Path: efm.performance.oam.pduDiscardRx

       32 bit unsigned wrappable counter."
   ::= {pr1646v2XEfmOamEntry 1694498816}

pr1646v2XEfmOamDataDiscardTx OBJECT-TYPE
   SYNTAX      Counter32
   MAX-ACCESS  read-only
   STATUS      current
   DESCRIPTION
      "Path: efm.performance.oam.dataDiscardTx

       32 bit unsigned wrappable counter."
   ::= {pr1646v2XEfmOamEntry 1711276032}

pr1646v2XEfmOamDataDiscardRx OBJECT-TYPE
   SYNTAX      Counter32
   MAX-ACCESS  read-only
   STATUS      current
   DESCRIPTION
      "Path: efm.performance.oam.dataDiscardRx

       32 bit unsigned wrappable counter."
   ::= {pr1646v2XEfmOamEntry 1728053248}


pr1646v2XEfmVlan OBJECT IDENTIFIER ::= {pr1646v2XEfm 310}

pr1646v2XEfmVlanSSCTable OBJECT-TYPE
   SYNTAX      SEQUENCE OF Pr1646v2XEfmVlanEntry
   MAX-ACCESS  not-accessible
   STATUS      current
   DESCRIPTION
      ""
   ::= {pr1646v2XEfmVlan 1}

pr1646v2XEfmVlanEntry OBJECT-TYPE
   SYNTAX      Pr1646v2XEfmVlanEntry
   MAX-ACCESS  not-accessible
   STATUS      current
   DESCRIPTION
      ""
   INDEX      { pr1646v2XEfmVlanTableIx }
   ::= {pr1646v2XEfmVlanSSCTable 1}

Pr1646v2XEfmVlanEntry ::=
   SEQUENCE
      {
      pr1646v2XEfmVlanTableIx
         TableIndex,
      pr1646v2XEfmVlanName
         DisplayString,
      pr1646v2XEfmVlanMCInOctets
         Counter64,
      pr1646v2XEfmVlanMCInUcast
         Counter64,
      pr1646v2XEfmVlanMCInNUcastPkts
         Counter64,
      pr1646v2XEfmVlanMCInBcastPkts
         Counter64,
      pr1646v2XEfmVlanMCInMcastPkts
         Counter64,
      pr1646v2XEfmVlanMCInDiscards
         Counter64,
      pr1646v2XEfmVlanMCInErrors
         Counter64,
      pr1646v2XEfmVlanMCInUnknownProtos
         Counter64,
      pr1646v2XEfmVlanMCInDropEx
         Counter64,
      pr1646v2XEfmVlanMCInDropNoMac
         Counter64,
      pr1646v2XEfmVlanMCInDropNUCast
         Counter64,
      pr1646v2XEfmVlanMCInDropFilter
         Counter64,
      pr1646v2XEfmVlanMCInBandwidth15sec
         Integer32,
      pr1646v2XEfmVlanMCInBandwidth30sec
         Integer32,
      pr1646v2XEfmVlanMCInBandwidth1min
         Integer32,
      pr1646v2XEfmVlanMCInBandwidth2min
         Integer32,
      pr1646v2XEfmVlanMCInBandwidth5min
         Integer32,
      pr1646v2XEfmVlanMCOutOctets
         Counter64,
      pr1646v2XEfmVlanMCOutUcastPkts
         Counter64,
      pr1646v2XEfmVlanMCOutNUcastPkts
         Counter64,
      pr1646v2XEfmVlanMCOutBcastPkts
         Counter64,
      pr1646v2XEfmVlanMCOutMcastPkts
         Counter64,
      pr1646v2XEfmVlanMCOutDiscards
         Counter64,
      pr1646v2XEfmVlanMCOutErrors
         Counter64,
      pr1646v2XEfmVlanMCOutQLen
         Counter32,
      pr1646v2XEfmVlanMCOutDropEx
         Counter64,
      pr1646v2XEfmVlanMCOutDropNoArp
         Counter64,
      pr1646v2XEfmVlanMCOutDropFilter
         Counter64,
      pr1646v2XEfmVlanMCOutBandwidth15sec
         Integer32,
      pr1646v2XEfmVlanMCOutBandwidth30sec
         Integer32,
      pr1646v2XEfmVlanMCOutBandwidth1min
         Integer32,
      pr1646v2XEfmVlanMCOutBandwidth2min
         Integer32,
      pr1646v2XEfmVlanMCOutBandwidth5min
         Integer32,
      pr1646v2XEfmVlanVlanVid
         Integer32,
      pr1646v2XEfmVlanPppLinkMonitoringRequestsSent
         Gauge32,
      pr1646v2XEfmVlanPppLinkMonitoringRepliesRcvd
         Gauge32,
      pr1646v2XEfmVlanPppLinkMonitoringRequestsRcvd
         Gauge32,
      pr1646v2XEfmVlanPppLinkMonitoringRepliesSent
         Gauge32
      }

pr1646v2XEfmVlanTableIx OBJECT-TYPE
   SYNTAX      TableIndex
   MAX-ACCESS  not-accessible
   STATUS      current
   DESCRIPTION
      ""
   ::= {pr1646v2XEfmVlanEntry 11}

pr1646v2XEfmVlanName OBJECT-TYPE
   SYNTAX      DisplayString
   MAX-ACCESS  read-only
   STATUS      current
   DESCRIPTION
      "Path: efm.performance.vlan.name"
   ::= {pr1646v2XEfmVlanEntry 16777216}

pr1646v2XEfmVlanMCInOctets OBJECT-TYPE
   SYNTAX      Counter64
   MAX-ACCESS  read-only
   STATUS      current
   DESCRIPTION
      "Path: efm.performance.vlan.mibCounters.ifInOctets

       64 bit unsigned wrappable counter."
   ::= {pr1646v2XEfmVlanEntry 40697856}

pr1646v2XEfmVlanMCInUcast OBJECT-TYPE
   SYNTAX      Counter64
   MAX-ACCESS  read-only
   STATUS      current
   DESCRIPTION
      "Path: efm.performance.vlan.mibCounters.ifInUcastPkts

       64 bit unsigned wrappable counter."
   ::= {pr1646v2XEfmVlanEntry 40763392}

pr1646v2XEfmVlanMCInNUcastPkts OBJECT-TYPE
   SYNTAX      Counter64
   MAX-ACCESS  read-only
   STATUS      current
   DESCRIPTION
      "Path: efm.performance.vlan.mibCounters.ifInNUcastPkts

       64 bit unsigned wrappable counter."
   ::= {pr1646v2XEfmVlanEntry 40828928}

pr1646v2XEfmVlanMCInBcastPkts OBJECT-TYPE
   SYNTAX      Counter64
   MAX-ACCESS  read-only
   STATUS      current
   DESCRIPTION
      "Path: efm.performance.vlan.mibCounters.ifInBcastPkts

       64 bit unsigned wrappable counter."
   ::= {pr1646v2XEfmVlanEntry 47382528}

pr1646v2XEfmVlanMCInMcastPkts OBJECT-TYPE
   SYNTAX      Counter64
   MAX-ACCESS  read-only
   STATUS      current
   DESCRIPTION
      "Path: efm.performance.vlan.mibCounters.ifInMcastPkts

       64 bit unsigned wrappable counter."
   ::= {pr1646v2XEfmVlanEntry 48037888}

pr1646v2XEfmVlanMCInDiscards OBJECT-TYPE
   SYNTAX      Counter64
   MAX-ACCESS  read-only
   STATUS      current
   DESCRIPTION
      "Path: efm.performance.vlan.mibCounters.ifInDiscards

       64 bit unsigned wrappable counter."
   ::= {pr1646v2XEfmVlanEntry 40894464}

pr1646v2XEfmVlanMCInErrors OBJECT-TYPE
   SYNTAX      Counter64
   MAX-ACCESS  read-only
   STATUS      current
   DESCRIPTION
      "Path: efm.performance.vlan.mibCounters.ifInErrors

       64 bit unsigned wrappable counter."
   ::= {pr1646v2XEfmVlanEntry 40960000}

pr1646v2XEfmVlanMCInUnknownProtos OBJECT-TYPE
   SYNTAX      Counter64
   MAX-ACCESS  read-only
   STATUS      current
   DESCRIPTION
      "Path: efm.performance.vlan.mibCounters.ifInUnknownProtos

       64 bit unsigned wrappable counter."
   ::= {pr1646v2XEfmVlanEntry 41025536}

pr1646v2XEfmVlanMCInDropEx OBJECT-TYPE
   SYNTAX      Counter64
   MAX-ACCESS  read-only
   STATUS      current
   DESCRIPTION
      "Path: efm.performance.vlan.mibCounters.ifInDropLevelExceeded

       64 bit unsigned wrappable counter."
   ::= {pr1646v2XEfmVlanEntry 42074112}

pr1646v2XEfmVlanMCInDropNoMac OBJECT-TYPE
   SYNTAX      Counter64
   MAX-ACCESS  read-only
   STATUS      current
   DESCRIPTION
      "Path: efm.performance.vlan.mibCounters.ifInDiscardsNoMacFit

       64 bit unsigned wrappable counter."
   ::= {pr1646v2XEfmVlanEntry 42270720}

pr1646v2XEfmVlanMCInDropNUCast OBJECT-TYPE
   SYNTAX      Counter64
   MAX-ACCESS  read-only
   STATUS      current
   DESCRIPTION
      "Path: efm.performance.vlan.mibCounters.ifInDiscardsNUCast

       64 bit unsigned wrappable counter."
   ::= {pr1646v2XEfmVlanEntry 42467328}

pr1646v2XEfmVlanMCInDropFilter OBJECT-TYPE
   SYNTAX      Counter64
   MAX-ACCESS  read-only
   STATUS      current
   DESCRIPTION
      "Path: efm.performance.vlan.mibCounters.ifInDiscardsFilter

       64 bit unsigned wrappable counter."
   ::= {pr1646v2XEfmVlanEntry 42532864}

pr1646v2XEfmVlanMCInBandwidth15sec OBJECT-TYPE
   SYNTAX      Integer32
   MAX-ACCESS  read-only
   STATUS      current
   DESCRIPTION
      "Path: efm.performance.vlan.mibCounters.ifInBandwidth.15sec

       unit name = bps
       formula = 8 * ; 8 /"
   ::= {pr1646v2XEfmVlanEntry 45417728}

pr1646v2XEfmVlanMCInBandwidth30sec OBJECT-TYPE
   SYNTAX      Integer32
   MAX-ACCESS  read-only
   STATUS      current
   DESCRIPTION
      "Path: efm.performance.vlan.mibCounters.ifInBandwidth.30sec

       unit name = bps
       formula = 8 * ; 8 /"
   ::= {pr1646v2XEfmVlanEntry 45419008}

pr1646v2XEfmVlanMCInBandwidth1min OBJECT-TYPE
   SYNTAX      Integer32
   MAX-ACCESS  read-only
   STATUS      current
   DESCRIPTION
      "Path: efm.performance.vlan.mibCounters.ifInBandwidth.1min

       unit name = bps
       formula = 8 * ; 8 /"
   ::= {pr1646v2XEfmVlanEntry 45421568}

pr1646v2XEfmVlanMCInBandwidth2min OBJECT-TYPE
   SYNTAX      Integer32
   MAX-ACCESS  read-only
   STATUS      current
   DESCRIPTION
      "Path: efm.performance.vlan.mibCounters.ifInBandwidth.2min

       unit name = bps
       formula = 8 * ; 8 /"
   ::= {pr1646v2XEfmVlanEntry 45426688}

pr1646v2XEfmVlanMCInBandwidth5min OBJECT-TYPE
   SYNTAX      Integer32
   MAX-ACCESS  read-only
   STATUS      current
   DESCRIPTION
      "Path: efm.performance.vlan.mibCounters.ifInBandwidth.5min

       unit name = bps
       formula = 8 * ; 8 /"
   ::= {pr1646v2XEfmVlanEntry 45442048}

pr1646v2XEfmVlanMCOutOctets OBJECT-TYPE
   SYNTAX      Counter64
   MAX-ACCESS  read-only
   STATUS      current
   DESCRIPTION
      "Path: efm.performance.vlan.mibCounters.ifOutOctets

       64 bit unsigned wrappable counter."
   ::= {pr1646v2XEfmVlanEntry 41091072}

pr1646v2XEfmVlanMCOutUcastPkts OBJECT-TYPE
   SYNTAX      Counter64
   MAX-ACCESS  read-only
   STATUS      current
   DESCRIPTION
      "Path: efm.performance.vlan.mibCounters.ifOutUcastPkts

       64 bit unsigned wrappable counter."
   ::= {pr1646v2XEfmVlanEntry 41156608}

pr1646v2XEfmVlanMCOutNUcastPkts OBJECT-TYPE
   SYNTAX      Counter64
   MAX-ACCESS  read-only
   STATUS      current
   DESCRIPTION
      "Path: efm.performance.vlan.mibCounters.ifOutNUcastPkts

       64 bit unsigned wrappable counter."
   ::= {pr1646v2XEfmVlanEntry 41222144}

pr1646v2XEfmVlanMCOutBcastPkts OBJECT-TYPE
   SYNTAX      Counter64
   MAX-ACCESS  read-only
   STATUS      current
   DESCRIPTION
      "Path: efm.performance.vlan.mibCounters.ifOutBcastPkts

       64 bit unsigned wrappable counter."
   ::= {pr1646v2XEfmVlanEntry 47775744}

pr1646v2XEfmVlanMCOutMcastPkts OBJECT-TYPE
   SYNTAX      Counter64
   MAX-ACCESS  read-only
   STATUS      current
   DESCRIPTION
      "Path: efm.performance.vlan.mibCounters.ifOutMcastPkts

       64 bit unsigned wrappable counter."
   ::= {pr1646v2XEfmVlanEntry 48431104}

pr1646v2XEfmVlanMCOutDiscards OBJECT-TYPE
   SYNTAX      Counter64
   MAX-ACCESS  read-only
   STATUS      current
   DESCRIPTION
      "Path: efm.performance.vlan.mibCounters.ifOutDiscards

       64 bit unsigned wrappable counter."
   ::= {pr1646v2XEfmVlanEntry 41287680}

pr1646v2XEfmVlanMCOutErrors OBJECT-TYPE
   SYNTAX      Counter64
   MAX-ACCESS  read-only
   STATUS      current
   DESCRIPTION
      "Path: efm.performance.vlan.mibCounters.ifOutErrors

       64 bit unsigned wrappable counter."
   ::= {pr1646v2XEfmVlanEntry 41353216}

pr1646v2XEfmVlanMCOutQLen OBJECT-TYPE
   SYNTAX      Counter32
   MAX-ACCESS  read-only
   STATUS      current
   DESCRIPTION
      "Path: efm.performance.vlan.mibCounters.ifOutQLen

       32 bit unsigned wrappable counter."
   ::= {pr1646v2XEfmVlanEntry 41418752}

pr1646v2XEfmVlanMCOutDropEx OBJECT-TYPE
   SYNTAX      Counter64
   MAX-ACCESS  read-only
   STATUS      current
   DESCRIPTION
      "Path: efm.performance.vlan.mibCounters.ifOutDropLevelExceeded

       64 bit unsigned wrappable counter."
   ::= {pr1646v2XEfmVlanEntry 41484288}

pr1646v2XEfmVlanMCOutDropNoArp OBJECT-TYPE
   SYNTAX      Counter64
   MAX-ACCESS  read-only
   STATUS      current
   DESCRIPTION
      "Path: efm.performance.vlan.mibCounters.ifOutDiscardsNoArp

       64 bit unsigned wrappable counter."
   ::= {pr1646v2XEfmVlanEntry 42336256}

pr1646v2XEfmVlanMCOutDropFilter OBJECT-TYPE
   SYNTAX      Counter64
   MAX-ACCESS  read-only
   STATUS      current
   DESCRIPTION
      "Path: efm.performance.vlan.mibCounters.ifOutDiscardsFilter

       64 bit unsigned wrappable counter."
   ::= {pr1646v2XEfmVlanEntry 42598400}

pr1646v2XEfmVlanMCOutBandwidth15sec OBJECT-TYPE
   SYNTAX      Integer32
   MAX-ACCESS  read-only
   STATUS      current
   DESCRIPTION
      "Path: efm.performance.vlan.mibCounters.ifOutBandwidth.15sec

       unit name = bps
       formula = 8 * ; 8 /"
   ::= {pr1646v2XEfmVlanEntry 45483264}

pr1646v2XEfmVlanMCOutBandwidth30sec OBJECT-TYPE
   SYNTAX      Integer32
   MAX-ACCESS  read-only
   STATUS      current
   DESCRIPTION
      "Path: efm.performance.vlan.mibCounters.ifOutBandwidth.30sec

       unit name = bps
       formula = 8 * ; 8 /"
   ::= {pr1646v2XEfmVlanEntry 45484544}

pr1646v2XEfmVlanMCOutBandwidth1min OBJECT-TYPE
   SYNTAX      Integer32
   MAX-ACCESS  read-only
   STATUS      current
   DESCRIPTION
      "Path: efm.performance.vlan.mibCounters.ifOutBandwidth.1min

       unit name = bps
       formula = 8 * ; 8 /"
   ::= {pr1646v2XEfmVlanEntry 45487104}

pr1646v2XEfmVlanMCOutBandwidth2min OBJECT-TYPE
   SYNTAX      Integer32
   MAX-ACCESS  read-only
   STATUS      current
   DESCRIPTION
      "Path: efm.performance.vlan.mibCounters.ifOutBandwidth.2min

       unit name = bps
       formula = 8 * ; 8 /"
   ::= {pr1646v2XEfmVlanEntry 45492224}

pr1646v2XEfmVlanMCOutBandwidth5min OBJECT-TYPE
   SYNTAX      Integer32
   MAX-ACCESS  read-only
   STATUS      current
   DESCRIPTION
      "Path: efm.performance.vlan.mibCounters.ifOutBandwidth.5min

       unit name = bps
       formula = 8 * ; 8 /"
   ::= {pr1646v2XEfmVlanEntry 45507584}

pr1646v2XEfmVlanVlanVid OBJECT-TYPE
   SYNTAX      Integer32
   MAX-ACCESS  read-only
   STATUS      current
   DESCRIPTION
      "Path: efm.performance.vlan.vlan.vid"
   ::= {pr1646v2XEfmVlanEntry 234946560}

pr1646v2XEfmVlanPppLinkMonitoringRequestsSent OBJECT-TYPE
   SYNTAX      Gauge32
   MAX-ACCESS  read-only
   STATUS      current
   DESCRIPTION
      "Path: efm.performance.vlan.ppp.linkMonitoring.requestsSent

       32 bit unsigned gauge value."
   ::= {pr1646v2XEfmVlanEntry 50397440}

pr1646v2XEfmVlanPppLinkMonitoringRepliesRcvd OBJECT-TYPE
   SYNTAX      Gauge32
   MAX-ACCESS  read-only
   STATUS      current
   DESCRIPTION
      "Path: efm.performance.vlan.ppp.linkMonitoring.repliesRcvd

       32 bit unsigned gauge value."
   ::= {pr1646v2XEfmVlanEntry 50397696}

pr1646v2XEfmVlanPppLinkMonitoringRequestsRcvd OBJECT-TYPE
   SYNTAX      Gauge32
   MAX-ACCESS  read-only
   STATUS      current
   DESCRIPTION
      "Path: efm.performance.vlan.ppp.linkMonitoring.requestsRcvd

       32 bit unsigned gauge value."
   ::= {pr1646v2XEfmVlanEntry 50397952}

pr1646v2XEfmVlanPppLinkMonitoringRepliesSent OBJECT-TYPE
   SYNTAX      Gauge32
   MAX-ACCESS  read-only
   STATUS      current
   DESCRIPTION
      "Path: efm.performance.vlan.ppp.linkMonitoring.repliesSent

       32 bit unsigned gauge value."
   ::= {pr1646v2XEfmVlanEntry 50398208}

pr1646v2XEfmVlanMCH2P OBJECT-TYPE
   SYNTAX      SEQUENCE OF Pr1646v2XEfmVlanMCH2PEntry
   MAX-ACCESS  not-accessible
   STATUS      current
   DESCRIPTION
      ""
   ::= {pr1646v2XEfmVlan 41549824}

pr1646v2XEfmVlanMCH2PEntry OBJECT-TYPE
   SYNTAX      Pr1646v2XEfmVlanMCH2PEntry
   MAX-ACCESS  not-accessible
   STATUS      current
   DESCRIPTION
      ""
   INDEX      { pr1646v2XEfmVlanTableIx,
                pr1646v2XEfmVlanMCH2PTableIx }
   ::= {pr1646v2XEfmVlanMCH2P 1}

Pr1646v2XEfmVlanMCH2PEntry ::=
   SEQUENCE
      {
      pr1646v2XEfmVlanMCH2PTableIx
         TableIndex,
      pr1646v2XEfmVlanMCH2PSysUpTime
         TimeTicks,
      pr1646v2XEfmVlanMCH2PIfUpTime
         TimeTicks,
      pr1646v2XEfmVlanMCH2PIfStatChanges
         Counter32,
      pr1646v2XEfmVlanMCH2PIfInOctets
         Counter64,
      pr1646v2XEfmVlanMCH2PIfInUCPkts
         Counter64,
      pr1646v2XEfmVlanMCH2PIfInNUCPkts
         Counter64,
      pr1646v2XEfmVlanMCH2PIfInBCPkts
         Counter64,
      pr1646v2XEfmVlanMCH2PIfInMCPkts
         Counter64,
      pr1646v2XEfmVlanMCH2PIfInDiscards
         Counter64,
      pr1646v2XEfmVlanMCH2PIfInErrors
         Counter64,
      pr1646v2XEfmVlanMCH2PIfInUnkwn
         Counter64,
      pr1646v2XEfmVlanMCH2PInDropEx
         Counter64,
      pr1646v2XEfmVlanMCH2PInDropNoMac
         Counter64,
      pr1646v2XEfmVlanMCH2PInDropNUCast
         Counter64,
      pr1646v2XEfmVlanMCH2PInDropFilter
         Counter64,
      pr1646v2XEfmVlanMCH2PIfInBandwidth
         Integer32,
      pr1646v2XEfmVlanMCH2PIfOutOctets
         Counter64,
      pr1646v2XEfmVlanMCH2PIfOutUCPkts
         Counter64,
      pr1646v2XEfmVlanMCH2PIfOutNUCPkts
         Counter64,
      pr1646v2XEfmVlanMCH2PIfOutBCPkts
         Counter64,
      pr1646v2XEfmVlanMCH2PIfOutMCPkts
         Counter64,
      pr1646v2XEfmVlanMCH2PIfOutDiscards
         Counter64,
      pr1646v2XEfmVlanMCH2PIfOutErrors
         Counter64,
      pr1646v2XEfmVlanMCH2POutDropEx
         Counter64,
      pr1646v2XEfmVlanMCH2POutDropNoArp
         Counter64,
      pr1646v2XEfmVlanMCH2POutDropFilter
         Counter64,
      pr1646v2XEfmVlanMCH2PIfOutBandwidth
         Integer32,
      pr1646v2XEfmVlanMCH2PIfErrSec
         Counter32
      }

pr1646v2XEfmVlanMCH2PTableIx OBJECT-TYPE
   SYNTAX      TableIndex
   MAX-ACCESS  not-accessible
   STATUS      current
   DESCRIPTION
      ""
   ::= {pr1646v2XEfmVlanMCH2PEntry 11}

pr1646v2XEfmVlanMCH2PSysUpTime OBJECT-TYPE
   SYNTAX      TimeTicks
   MAX-ACCESS  read-only
   STATUS      current
   DESCRIPTION
      "Path: efm.performance.vlan.mibCounters.h2Performance.sysUpTime

       Time in centi-second."
   ::= {pr1646v2XEfmVlanMCH2PEntry 16777216}

pr1646v2XEfmVlanMCH2PIfUpTime OBJECT-TYPE
   SYNTAX      TimeTicks
   MAX-ACCESS  read-only
   STATUS      current
   DESCRIPTION
      "Path: efm.performance.vlan.mibCounters.h2Performance.ifUpTime

       Time in centi-second."
   ::= {pr1646v2XEfmVlanMCH2PEntry 33554432}

pr1646v2XEfmVlanMCH2PIfStatChanges OBJECT-TYPE
   SYNTAX      Counter32
   MAX-ACCESS  read-only
   STATUS      current
   DESCRIPTION
      "Path: efm.performance.vlan.mibCounters.h2Performance.ifStatusChanges

       32 bit unsigned wrappable counter."
   ::= {pr1646v2XEfmVlanMCH2PEntry 50331648}

pr1646v2XEfmVlanMCH2PIfInOctets OBJECT-TYPE
   SYNTAX      Counter64
   MAX-ACCESS  read-only
   STATUS      current
   DESCRIPTION
      "Path: efm.performance.vlan.mibCounters.h2Performance.ifInOctets

       64 bit unsigned wrappable counter."
   ::= {pr1646v2XEfmVlanMCH2PEntry 67108864}

pr1646v2XEfmVlanMCH2PIfInUCPkts OBJECT-TYPE
   SYNTAX      Counter64
   MAX-ACCESS  read-only
   STATUS      current
   DESCRIPTION
      "Path: efm.performance.vlan.mibCounters.h2Performance.ifInUcastPkts

       64 bit unsigned wrappable counter."
   ::= {pr1646v2XEfmVlanMCH2PEntry 83886080}

pr1646v2XEfmVlanMCH2PIfInNUCPkts OBJECT-TYPE
   SYNTAX      Counter64
   MAX-ACCESS  read-only
   STATUS      current
   DESCRIPTION
      "Path: efm.performance.vlan.mibCounters.h2Performance.ifInNUcastPkts

       64 bit unsigned wrappable counter."
   ::= {pr1646v2XEfmVlanMCH2PEntry 100663296}

pr1646v2XEfmVlanMCH2PIfInBCPkts OBJECT-TYPE
   SYNTAX      Counter64
   MAX-ACCESS  read-only
   STATUS      current
   DESCRIPTION
      "Path: efm.performance.vlan.mibCounters.h2Performance.ifInBcastPkts

       64 bit unsigned wrappable counter."
   ::= {pr1646v2XEfmVlanMCH2PEntry 419430400}

pr1646v2XEfmVlanMCH2PIfInMCPkts OBJECT-TYPE
   SYNTAX      Counter64
   MAX-ACCESS  read-only
   STATUS      current
   DESCRIPTION
      "Path: efm.performance.vlan.mibCounters.h2Performance.ifInMcastPkts

       64 bit unsigned wrappable counter."
   ::= {pr1646v2XEfmVlanMCH2PEntry 436207616}

pr1646v2XEfmVlanMCH2PIfInDiscards OBJECT-TYPE
   SYNTAX      Counter64
   MAX-ACCESS  read-only
   STATUS      current
   DESCRIPTION
      "Path: efm.performance.vlan.mibCounters.h2Performance.ifInDiscards

       64 bit unsigned wrappable counter."
   ::= {pr1646v2XEfmVlanMCH2PEntry 117440512}

pr1646v2XEfmVlanMCH2PIfInErrors OBJECT-TYPE
   SYNTAX      Counter64
   MAX-ACCESS  read-only
   STATUS      current
   DESCRIPTION
      "Path: efm.performance.vlan.mibCounters.h2Performance.ifInErrors

       64 bit unsigned wrappable counter."
   ::= {pr1646v2XEfmVlanMCH2PEntry 134217728}

pr1646v2XEfmVlanMCH2PIfInUnkwn OBJECT-TYPE
   SYNTAX      Counter64
   MAX-ACCESS  read-only
   STATUS      current
   DESCRIPTION
      "Path: efm.performance.vlan.mibCounters.h2Performance.ifInUnknownProtos

       64 bit unsigned wrappable counter."
   ::= {pr1646v2XEfmVlanMCH2PEntry 150994944}

pr1646v2XEfmVlanMCH2PInDropEx OBJECT-TYPE
   SYNTAX      Counter64
   MAX-ACCESS  read-only
   STATUS      current
   DESCRIPTION
      "Path: efm.performance.vlan.mibCounters.h2Performance.ifInDropLevelExceeded

       64 bit unsigned wrappable counter."
   ::= {pr1646v2XEfmVlanMCH2PEntry 335544320}

pr1646v2XEfmVlanMCH2PInDropNoMac OBJECT-TYPE
   SYNTAX      Counter64
   MAX-ACCESS  read-only
   STATUS      current
   DESCRIPTION
      "Path: efm.performance.vlan.mibCounters.h2Performance.fInDiscardsNoMacFit

       64 bit unsigned wrappable counter."
   ::= {pr1646v2XEfmVlanMCH2PEntry 301989888}

pr1646v2XEfmVlanMCH2PInDropNUCast OBJECT-TYPE
   SYNTAX      Counter64
   MAX-ACCESS  read-only
   STATUS      current
   DESCRIPTION
      "Path: efm.performance.vlan.mibCounters.h2Performance.fInDiscardsNUCast

       64 bit unsigned wrappable counter."
   ::= {pr1646v2XEfmVlanMCH2PEntry 318767104}

pr1646v2XEfmVlanMCH2PInDropFilter OBJECT-TYPE
   SYNTAX      Counter64
   MAX-ACCESS  read-only
   STATUS      current
   DESCRIPTION
      "Path: efm.performance.vlan.mibCounters.h2Performance.fInDiscardsFilter

       64 bit unsigned wrappable counter."
   ::= {pr1646v2XEfmVlanMCH2PEntry 385875968}

pr1646v2XEfmVlanMCH2PIfInBandwidth OBJECT-TYPE
   SYNTAX      Integer32
   MAX-ACCESS  read-only
   STATUS      current
   DESCRIPTION
      "Path: efm.performance.vlan.mibCounters.h2Performance.ifInBandwidth

       unit name = bps
       formula = 8 * ; 8 /"
   ::= {pr1646v2XEfmVlanMCH2PEntry 268435456}

pr1646v2XEfmVlanMCH2PIfOutOctets OBJECT-TYPE
   SYNTAX      Counter64
   MAX-ACCESS  read-only
   STATUS      current
   DESCRIPTION
      "Path: efm.performance.vlan.mibCounters.h2Performance.ifOutOctets

       64 bit unsigned wrappable counter."
   ::= {pr1646v2XEfmVlanMCH2PEntry 167772160}

pr1646v2XEfmVlanMCH2PIfOutUCPkts OBJECT-TYPE
   SYNTAX      Counter64
   MAX-ACCESS  read-only
   STATUS      current
   DESCRIPTION
      "Path: efm.performance.vlan.mibCounters.h2Performance.ifOutUcastPkts

       64 bit unsigned wrappable counter."
   ::= {pr1646v2XEfmVlanMCH2PEntry 184549376}

pr1646v2XEfmVlanMCH2PIfOutNUCPkts OBJECT-TYPE
   SYNTAX      Counter64
   MAX-ACCESS  read-only
   STATUS      current
   DESCRIPTION
      "Path: efm.performance.vlan.mibCounters.h2Performance.ifOutNUcastPkts

       64 bit unsigned wrappable counter."
   ::= {pr1646v2XEfmVlanMCH2PEntry 201326592}

pr1646v2XEfmVlanMCH2PIfOutBCPkts OBJECT-TYPE
   SYNTAX      Counter64
   MAX-ACCESS  read-only
   STATUS      current
   DESCRIPTION
      "Path: efm.performance.vlan.mibCounters.h2Performance.ifOutBcastPkts

       64 bit unsigned wrappable counter."
   ::= {pr1646v2XEfmVlanMCH2PEntry 452984832}

pr1646v2XEfmVlanMCH2PIfOutMCPkts OBJECT-TYPE
   SYNTAX      Counter64
   MAX-ACCESS  read-only
   STATUS      current
   DESCRIPTION
      "Path: efm.performance.vlan.mibCounters.h2Performance.ifOutMcastPkts

       64 bit unsigned wrappable counter."
   ::= {pr1646v2XEfmVlanMCH2PEntry 469762048}

pr1646v2XEfmVlanMCH2PIfOutDiscards OBJECT-TYPE
   SYNTAX      Counter64
   MAX-ACCESS  read-only
   STATUS      current
   DESCRIPTION
      "Path: efm.performance.vlan.mibCounters.h2Performance.ifOutDiscards

       64 bit unsigned wrappable counter."
   ::= {pr1646v2XEfmVlanMCH2PEntry 218103808}

pr1646v2XEfmVlanMCH2PIfOutErrors OBJECT-TYPE
   SYNTAX      Counter64
   MAX-ACCESS  read-only
   STATUS      current
   DESCRIPTION
      "Path: efm.performance.vlan.mibCounters.h2Performance.ifOutErrors

       64 bit unsigned wrappable counter."
   ::= {pr1646v2XEfmVlanMCH2PEntry 234881024}

pr1646v2XEfmVlanMCH2POutDropEx OBJECT-TYPE
   SYNTAX      Counter64
   MAX-ACCESS  read-only
   STATUS      current
   DESCRIPTION
      "Path: efm.performance.vlan.mibCounters.h2Performance.ifOutDropLevelExceeded

       64 bit unsigned wrappable counter."
   ::= {pr1646v2XEfmVlanMCH2PEntry 352321536}

pr1646v2XEfmVlanMCH2POutDropNoArp OBJECT-TYPE
   SYNTAX      Counter64
   MAX-ACCESS  read-only
   STATUS      current
   DESCRIPTION
      "Path: efm.performance.vlan.mibCounters.h2Performance.ifOutDiscardsNoArp

       64 bit unsigned wrappable counter."
   ::= {pr1646v2XEfmVlanMCH2PEntry 369098752}

pr1646v2XEfmVlanMCH2POutDropFilter OBJECT-TYPE
   SYNTAX      Counter64
   MAX-ACCESS  read-only
   STATUS      current
   DESCRIPTION
      "Path: efm.performance.vlan.mibCounters.h2Performance.ifOutDiscardsFilter

       64 bit unsigned wrappable counter."
   ::= {pr1646v2XEfmVlanMCH2PEntry 402653184}

pr1646v2XEfmVlanMCH2PIfOutBandwidth OBJECT-TYPE
   SYNTAX      Integer32
   MAX-ACCESS  read-only
   STATUS      current
   DESCRIPTION
      "Path: efm.performance.vlan.mibCounters.h2Performance.ifOutBandwidth

       unit name = bps
       formula = 8 * ; 8 /"
   ::= {pr1646v2XEfmVlanMCH2PEntry 285212672}

pr1646v2XEfmVlanMCH2PIfErrSec OBJECT-TYPE
   SYNTAX      Counter32
   MAX-ACCESS  read-only
   STATUS      current
   DESCRIPTION
      "Path: efm.performance.vlan.mibCounters.h2Performance.ifErrSec

       32 bit unsigned wrappable counter."
   ::= {pr1646v2XEfmVlanMCH2PEntry 251658240}

pr1646v2XEfmVlanMCH24P OBJECT-TYPE
   SYNTAX      SEQUENCE OF Pr1646v2XEfmVlanMCH24PEntry
   MAX-ACCESS  not-accessible
   STATUS      current
   DESCRIPTION
      ""
   ::= {pr1646v2XEfmVlan 41615360}

pr1646v2XEfmVlanMCH24PEntry OBJECT-TYPE
   SYNTAX      Pr1646v2XEfmVlanMCH24PEntry
   MAX-ACCESS  not-accessible
   STATUS      current
   DESCRIPTION
      ""
   INDEX      { pr1646v2XEfmVlanTableIx,
                pr1646v2XEfmVlanMCH24PTableIx }
   ::= {pr1646v2XEfmVlanMCH24P 1}

Pr1646v2XEfmVlanMCH24PEntry ::=
   SEQUENCE
      {
      pr1646v2XEfmVlanMCH24PTableIx
         TableIndex,
      pr1646v2XEfmVlanMCH24PSysUpTime
         TimeTicks,
      pr1646v2XEfmVlanMCH24PIfUpTime
         TimeTicks,
      pr1646v2XEfmVlanMCH24PIfStatChanges
         Counter32,
      pr1646v2XEfmVlanMCH24PIfInOctets
         Counter64,
      pr1646v2XEfmVlanMCH24PIfInUCPkts
         Counter64,
      pr1646v2XEfmVlanMCH24PIfInNUCPkts
         Counter64,
      pr1646v2XEfmVlanMCH24PIfInBCPkts
         Counter64,
      pr1646v2XEfmVlanMCH24PIfInMCPkts
         Counter64,
      pr1646v2XEfmVlanMCH24PIfInDiscards
         Counter64,
      pr1646v2XEfmVlanMCH24PIfInErrors
         Counter64,
      pr1646v2XEfmVlanMCH24PIfInUnkwn
         Counter64,
      pr1646v2XEfmVlanMCH24PInDropEx
         Counter64,
      pr1646v2XEfmVlanMCH24PInDropNoMac
         Counter64,
      pr1646v2XEfmVlanMCH24PInDropNUCast
         Counter64,
      pr1646v2XEfmVlanMCH24PInDropFilter
         Counter64,
      pr1646v2XEfmVlanMCH24PIfInBandwidth
         Integer32,
      pr1646v2XEfmVlanMCH24PIfOutOctets
         Counter64,
      pr1646v2XEfmVlanMCH24PIfOutUCPkts
         Counter64,
      pr1646v2XEfmVlanMCH24PIfOutNUCPkts
         Counter64,
      pr1646v2XEfmVlanMCH24PIfOutBCPkts
         Counter64,
      pr1646v2XEfmVlanMCH24PIfOutMCPkts
         Counter64,
      pr1646v2XEfmVlanMCH24PIfOutDiscards
         Counter64,
      pr1646v2XEfmVlanMCH24PIfOutErrors
         Counter64,
      pr1646v2XEfmVlanMCH24POutDropEx
         Counter64,
      pr1646v2XEfmVlanMCH24POutDropNoArp
         Counter64,
      pr1646v2XEfmVlanMCH24POutDropFilter
         Counter64,
      pr1646v2XEfmVlanMCH24PIfOutBandwidth
         Integer32,
      pr1646v2XEfmVlanMCH24PIfErrSec
         Counter32
      }

pr1646v2XEfmVlanMCH24PTableIx OBJECT-TYPE
   SYNTAX      TableIndex
   MAX-ACCESS  not-accessible
   STATUS      current
   DESCRIPTION
      ""
   ::= {pr1646v2XEfmVlanMCH24PEntry 11}

pr1646v2XEfmVlanMCH24PSysUpTime OBJECT-TYPE
   SYNTAX      TimeTicks
   MAX-ACCESS  read-only
   STATUS      current
   DESCRIPTION
      "Path: efm.performance.vlan.mibCounters.h24Performance.sysUpTime

       Time in centi-second."
   ::= {pr1646v2XEfmVlanMCH24PEntry 16777216}

pr1646v2XEfmVlanMCH24PIfUpTime OBJECT-TYPE
   SYNTAX      TimeTicks
   MAX-ACCESS  read-only
   STATUS      current
   DESCRIPTION
      "Path: efm.performance.vlan.mibCounters.h24Performance.ifUpTime

       Time in centi-second."
   ::= {pr1646v2XEfmVlanMCH24PEntry 33554432}

pr1646v2XEfmVlanMCH24PIfStatChanges OBJECT-TYPE
   SYNTAX      Counter32
   MAX-ACCESS  read-only
   STATUS      current
   DESCRIPTION
      "Path: efm.performance.vlan.mibCounters.h24Performance.ifStatusChanges

       32 bit unsigned wrappable counter."
   ::= {pr1646v2XEfmVlanMCH24PEntry 50331648}

pr1646v2XEfmVlanMCH24PIfInOctets OBJECT-TYPE
   SYNTAX      Counter64
   MAX-ACCESS  read-only
   STATUS      current
   DESCRIPTION
      "Path: efm.performance.vlan.mibCounters.h24Performance.ifInOctets

       64 bit unsigned wrappable counter."
   ::= {pr1646v2XEfmVlanMCH24PEntry 67108864}

pr1646v2XEfmVlanMCH24PIfInUCPkts OBJECT-TYPE
   SYNTAX      Counter64
   MAX-ACCESS  read-only
   STATUS      current
   DESCRIPTION
      "Path: efm.performance.vlan.mibCounters.h24Performance.ifInUcastPkts

       64 bit unsigned wrappable counter."
   ::= {pr1646v2XEfmVlanMCH24PEntry 83886080}

pr1646v2XEfmVlanMCH24PIfInNUCPkts OBJECT-TYPE
   SYNTAX      Counter64
   MAX-ACCESS  read-only
   STATUS      current
   DESCRIPTION
      "Path: efm.performance.vlan.mibCounters.h24Performance.ifInNUcastPkts

       64 bit unsigned wrappable counter."
   ::= {pr1646v2XEfmVlanMCH24PEntry 100663296}

pr1646v2XEfmVlanMCH24PIfInBCPkts OBJECT-TYPE
   SYNTAX      Counter64
   MAX-ACCESS  read-only
   STATUS      current
   DESCRIPTION
      "Path: efm.performance.vlan.mibCounters.h24Performance.ifInBcastPkts

       64 bit unsigned wrappable counter."
   ::= {pr1646v2XEfmVlanMCH24PEntry 419430400}

pr1646v2XEfmVlanMCH24PIfInMCPkts OBJECT-TYPE
   SYNTAX      Counter64
   MAX-ACCESS  read-only
   STATUS      current
   DESCRIPTION
      "Path: efm.performance.vlan.mibCounters.h24Performance.ifInMcastPkts

       64 bit unsigned wrappable counter."
   ::= {pr1646v2XEfmVlanMCH24PEntry 436207616}

pr1646v2XEfmVlanMCH24PIfInDiscards OBJECT-TYPE
   SYNTAX      Counter64
   MAX-ACCESS  read-only
   STATUS      current
   DESCRIPTION
      "Path: efm.performance.vlan.mibCounters.h24Performance.ifInDiscards

       64 bit unsigned wrappable counter."
   ::= {pr1646v2XEfmVlanMCH24PEntry 117440512}

pr1646v2XEfmVlanMCH24PIfInErrors OBJECT-TYPE
   SYNTAX      Counter64
   MAX-ACCESS  read-only
   STATUS      current
   DESCRIPTION
      "Path: efm.performance.vlan.mibCounters.h24Performance.ifInErrors

       64 bit unsigned wrappable counter."
   ::= {pr1646v2XEfmVlanMCH24PEntry 134217728}

pr1646v2XEfmVlanMCH24PIfInUnkwn OBJECT-TYPE
   SYNTAX      Counter64
   MAX-ACCESS  read-only
   STATUS      current
   DESCRIPTION
      "Path: efm.performance.vlan.mibCounters.h24Performance.ifInUnknownProtos

       64 bit unsigned wrappable counter."
   ::= {pr1646v2XEfmVlanMCH24PEntry 150994944}

pr1646v2XEfmVlanMCH24PInDropEx OBJECT-TYPE
   SYNTAX      Counter64
   MAX-ACCESS  read-only
   STATUS      current
   DESCRIPTION
      "Path: efm.performance.vlan.mibCounters.h24Performance.ifInDropLevelExceeded

       64 bit unsigned wrappable counter."
   ::= {pr1646v2XEfmVlanMCH24PEntry 335544320}

pr1646v2XEfmVlanMCH24PInDropNoMac OBJECT-TYPE
   SYNTAX      Counter64
   MAX-ACCESS  read-only
   STATUS      current
   DESCRIPTION
      "Path: efm.performance.vlan.mibCounters.h24Performance.fInDiscardsNoMacFit

       64 bit unsigned wrappable counter."
   ::= {pr1646v2XEfmVlanMCH24PEntry 301989888}

pr1646v2XEfmVlanMCH24PInDropNUCast OBJECT-TYPE
   SYNTAX      Counter64
   MAX-ACCESS  read-only
   STATUS      current
   DESCRIPTION
      "Path: efm.performance.vlan.mibCounters.h24Performance.fInDiscardsNUCast

       64 bit unsigned wrappable counter."
   ::= {pr1646v2XEfmVlanMCH24PEntry 318767104}

pr1646v2XEfmVlanMCH24PInDropFilter OBJECT-TYPE
   SYNTAX      Counter64
   MAX-ACCESS  read-only
   STATUS      current
   DESCRIPTION
      "Path: efm.performance.vlan.mibCounters.h24Performance.fInDiscardsFilter

       64 bit unsigned wrappable counter."
   ::= {pr1646v2XEfmVlanMCH24PEntry 385875968}

pr1646v2XEfmVlanMCH24PIfInBandwidth OBJECT-TYPE
   SYNTAX      Integer32
   MAX-ACCESS  read-only
   STATUS      current
   DESCRIPTION
      "Path: efm.performance.vlan.mibCounters.h24Performance.ifInBandwidth

       unit name = bps
       formula = 8 * ; 8 /"
   ::= {pr1646v2XEfmVlanMCH24PEntry 268435456}

pr1646v2XEfmVlanMCH24PIfOutOctets OBJECT-TYPE
   SYNTAX      Counter64
   MAX-ACCESS  read-only
   STATUS      current
   DESCRIPTION
      "Path: efm.performance.vlan.mibCounters.h24Performance.ifOutOctets

       64 bit unsigned wrappable counter."
   ::= {pr1646v2XEfmVlanMCH24PEntry 167772160}

pr1646v2XEfmVlanMCH24PIfOutUCPkts OBJECT-TYPE
   SYNTAX      Counter64
   MAX-ACCESS  read-only
   STATUS      current
   DESCRIPTION
      "Path: efm.performance.vlan.mibCounters.h24Performance.ifOutUcastPkts

       64 bit unsigned wrappable counter."
   ::= {pr1646v2XEfmVlanMCH24PEntry 184549376}

pr1646v2XEfmVlanMCH24PIfOutNUCPkts OBJECT-TYPE
   SYNTAX      Counter64
   MAX-ACCESS  read-only
   STATUS      current
   DESCRIPTION
      "Path: efm.performance.vlan.mibCounters.h24Performance.ifOutNUcastPkts

       64 bit unsigned wrappable counter."
   ::= {pr1646v2XEfmVlanMCH24PEntry 201326592}

pr1646v2XEfmVlanMCH24PIfOutBCPkts OBJECT-TYPE
   SYNTAX      Counter64
   MAX-ACCESS  read-only
   STATUS      current
   DESCRIPTION
      "Path: efm.performance.vlan.mibCounters.h24Performance.ifOutBcastPkts

       64 bit unsigned wrappable counter."
   ::= {pr1646v2XEfmVlanMCH24PEntry 452984832}

pr1646v2XEfmVlanMCH24PIfOutMCPkts OBJECT-TYPE
   SYNTAX      Counter64
   MAX-ACCESS  read-only
   STATUS      current
   DESCRIPTION
      "Path: efm.performance.vlan.mibCounters.h24Performance.ifOutMcastPkts

       64 bit unsigned wrappable counter."
   ::= {pr1646v2XEfmVlanMCH24PEntry 469762048}

pr1646v2XEfmVlanMCH24PIfOutDiscards OBJECT-TYPE
   SYNTAX      Counter64
   MAX-ACCESS  read-only
   STATUS      current
   DESCRIPTION
      "Path: efm.performance.vlan.mibCounters.h24Performance.ifOutDiscards

       64 bit unsigned wrappable counter."
   ::= {pr1646v2XEfmVlanMCH24PEntry 218103808}

pr1646v2XEfmVlanMCH24PIfOutErrors OBJECT-TYPE
   SYNTAX      Counter64
   MAX-ACCESS  read-only
   STATUS      current
   DESCRIPTION
      "Path: efm.performance.vlan.mibCounters.h24Performance.ifOutErrors

       64 bit unsigned wrappable counter."
   ::= {pr1646v2XEfmVlanMCH24PEntry 234881024}

pr1646v2XEfmVlanMCH24POutDropEx OBJECT-TYPE
   SYNTAX      Counter64
   MAX-ACCESS  read-only
   STATUS      current
   DESCRIPTION
      "Path: efm.performance.vlan.mibCounters.h24Performance.ifOutDropLevelExceeded

       64 bit unsigned wrappable counter."
   ::= {pr1646v2XEfmVlanMCH24PEntry 352321536}

pr1646v2XEfmVlanMCH24POutDropNoArp OBJECT-TYPE
   SYNTAX      Counter64
   MAX-ACCESS  read-only
   STATUS      current
   DESCRIPTION
      "Path: efm.performance.vlan.mibCounters.h24Performance.ifOutDiscardsNoArp

       64 bit unsigned wrappable counter."
   ::= {pr1646v2XEfmVlanMCH24PEntry 369098752}

pr1646v2XEfmVlanMCH24POutDropFilter OBJECT-TYPE
   SYNTAX      Counter64
   MAX-ACCESS  read-only
   STATUS      current
   DESCRIPTION
      "Path: efm.performance.vlan.mibCounters.h24Performance.ifOutDiscardsFilter

       64 bit unsigned wrappable counter."
   ::= {pr1646v2XEfmVlanMCH24PEntry 402653184}

pr1646v2XEfmVlanMCH24PIfOutBandwidth OBJECT-TYPE
   SYNTAX      Integer32
   MAX-ACCESS  read-only
   STATUS      current
   DESCRIPTION
      "Path: efm.performance.vlan.mibCounters.h24Performance.ifOutBandwidth

       unit name = bps
       formula = 8 * ; 8 /"
   ::= {pr1646v2XEfmVlanMCH24PEntry 285212672}

pr1646v2XEfmVlanMCH24PIfErrSec OBJECT-TYPE
   SYNTAX      Counter32
   MAX-ACCESS  read-only
   STATUS      current
   DESCRIPTION
      "Path: efm.performance.vlan.mibCounters.h24Performance.ifErrSec

       32 bit unsigned wrappable counter."
   ::= {pr1646v2XEfmVlanMCH24PEntry 251658240}

pr1646v2XEfmVlanMCD7P OBJECT-TYPE
   SYNTAX      SEQUENCE OF Pr1646v2XEfmVlanMCD7PEntry
   MAX-ACCESS  not-accessible
   STATUS      current
   DESCRIPTION
      ""
   ::= {pr1646v2XEfmVlan 41680896}

pr1646v2XEfmVlanMCD7PEntry OBJECT-TYPE
   SYNTAX      Pr1646v2XEfmVlanMCD7PEntry
   MAX-ACCESS  not-accessible
   STATUS      current
   DESCRIPTION
      ""
   INDEX      { pr1646v2XEfmVlanTableIx,
                pr1646v2XEfmVlanMCD7PTableIx }
   ::= {pr1646v2XEfmVlanMCD7P 1}

Pr1646v2XEfmVlanMCD7PEntry ::=
   SEQUENCE
      {
      pr1646v2XEfmVlanMCD7PTableIx
         TableIndex,
      pr1646v2XEfmVlanMCD7PSysUpTime
         TimeTicks,
      pr1646v2XEfmVlanMCD7PIfUpTime
         TimeTicks,
      pr1646v2XEfmVlanMCD7PIfStatChanges
         Counter32,
      pr1646v2XEfmVlanMCD7PIfInOctets
         Counter64,
      pr1646v2XEfmVlanMCD7PIfInUCPkts
         Counter64,
      pr1646v2XEfmVlanMCD7PIfInNUCPkts
         Counter64,
      pr1646v2XEfmVlanMCD7PIfInBCPkts
         Counter64,
      pr1646v2XEfmVlanMCD7PIfInMCPkts
         Counter64,
      pr1646v2XEfmVlanMCD7PIfInDiscards
         Counter64,
      pr1646v2XEfmVlanMCD7PIfInErrors
         Counter64,
      pr1646v2XEfmVlanMCD7PIfInUnkwn
         Counter64,
      pr1646v2XEfmVlanMCD7PInDropEx
         Counter64,
      pr1646v2XEfmVlanMCD7PInDropNoMac
         Counter64,
      pr1646v2XEfmVlanMCD7PInDropNUCast
         Counter64,
      pr1646v2XEfmVlanMCD7PInDropFilter
         Counter64,
      pr1646v2XEfmVlanMCD7PIfInBandwidth
         Integer32,
      pr1646v2XEfmVlanMCD7PIfOutOctets
         Counter64,
      pr1646v2XEfmVlanMCD7PIfOutUCPkts
         Counter64,
      pr1646v2XEfmVlanMCD7PIfOutNUCPkts
         Counter64,
      pr1646v2XEfmVlanMCD7PIfOutBCPkts
         Counter64,
      pr1646v2XEfmVlanMCD7PIfOutMCPkts
         Counter64,
      pr1646v2XEfmVlanMCD7PIfOutDiscards
         Counter64,
      pr1646v2XEfmVlanMCD7PIfOutErrors
         Counter64,
      pr1646v2XEfmVlanMCD7POutDropEx
         Counter64,
      pr1646v2XEfmVlanMCD7POutDropNoArp
         Counter64,
      pr1646v2XEfmVlanMCD7POutDropFilter
         Counter64,
      pr1646v2XEfmVlanMCD7PIfOutBandwidth
         Integer32,
      pr1646v2XEfmVlanMCD7PIfErrSec
         Counter32
      }

pr1646v2XEfmVlanMCD7PTableIx OBJECT-TYPE
   SYNTAX      TableIndex
   MAX-ACCESS  not-accessible
   STATUS      current
   DESCRIPTION
      ""
   ::= {pr1646v2XEfmVlanMCD7PEntry 11}

pr1646v2XEfmVlanMCD7PSysUpTime OBJECT-TYPE
   SYNTAX      TimeTicks
   MAX-ACCESS  read-only
   STATUS      current
   DESCRIPTION
      "Path: efm.performance.vlan.mibCounters.d7Performance.sysUpTime

       Time in centi-second."
   ::= {pr1646v2XEfmVlanMCD7PEntry 16777216}

pr1646v2XEfmVlanMCD7PIfUpTime OBJECT-TYPE
   SYNTAX      TimeTicks
   MAX-ACCESS  read-only
   STATUS      current
   DESCRIPTION
      "Path: efm.performance.vlan.mibCounters.d7Performance.ifUpTime

       Time in centi-second."
   ::= {pr1646v2XEfmVlanMCD7PEntry 33554432}

pr1646v2XEfmVlanMCD7PIfStatChanges OBJECT-TYPE
   SYNTAX      Counter32
   MAX-ACCESS  read-only
   STATUS      current
   DESCRIPTION
      "Path: efm.performance.vlan.mibCounters.d7Performance.ifStatusChanges

       32 bit unsigned wrappable counter."
   ::= {pr1646v2XEfmVlanMCD7PEntry 50331648}

pr1646v2XEfmVlanMCD7PIfInOctets OBJECT-TYPE
   SYNTAX      Counter64
   MAX-ACCESS  read-only
   STATUS      current
   DESCRIPTION
      "Path: efm.performance.vlan.mibCounters.d7Performance.ifInOctets

       64 bit unsigned wrappable counter."
   ::= {pr1646v2XEfmVlanMCD7PEntry 67108864}

pr1646v2XEfmVlanMCD7PIfInUCPkts OBJECT-TYPE
   SYNTAX      Counter64
   MAX-ACCESS  read-only
   STATUS      current
   DESCRIPTION
      "Path: efm.performance.vlan.mibCounters.d7Performance.ifInUcastPkts

       64 bit unsigned wrappable counter."
   ::= {pr1646v2XEfmVlanMCD7PEntry 83886080}

pr1646v2XEfmVlanMCD7PIfInNUCPkts OBJECT-TYPE
   SYNTAX      Counter64
   MAX-ACCESS  read-only
   STATUS      current
   DESCRIPTION
      "Path: efm.performance.vlan.mibCounters.d7Performance.ifInNUcastPkts

       64 bit unsigned wrappable counter."
   ::= {pr1646v2XEfmVlanMCD7PEntry 100663296}

pr1646v2XEfmVlanMCD7PIfInBCPkts OBJECT-TYPE
   SYNTAX      Counter64
   MAX-ACCESS  read-only
   STATUS      current
   DESCRIPTION
      "Path: efm.performance.vlan.mibCounters.d7Performance.ifInBcastPkts

       64 bit unsigned wrappable counter."
   ::= {pr1646v2XEfmVlanMCD7PEntry 419430400}

pr1646v2XEfmVlanMCD7PIfInMCPkts OBJECT-TYPE
   SYNTAX      Counter64
   MAX-ACCESS  read-only
   STATUS      current
   DESCRIPTION
      "Path: efm.performance.vlan.mibCounters.d7Performance.ifInMcastPkts

       64 bit unsigned wrappable counter."
   ::= {pr1646v2XEfmVlanMCD7PEntry 436207616}

pr1646v2XEfmVlanMCD7PIfInDiscards OBJECT-TYPE
   SYNTAX      Counter64
   MAX-ACCESS  read-only
   STATUS      current
   DESCRIPTION
      "Path: efm.performance.vlan.mibCounters.d7Performance.ifInDiscards

       64 bit unsigned wrappable counter."
   ::= {pr1646v2XEfmVlanMCD7PEntry 117440512}

pr1646v2XEfmVlanMCD7PIfInErrors OBJECT-TYPE
   SYNTAX      Counter64
   MAX-ACCESS  read-only
   STATUS      current
   DESCRIPTION
      "Path: efm.performance.vlan.mibCounters.d7Performance.ifInErrors

       64 bit unsigned wrappable counter."
   ::= {pr1646v2XEfmVlanMCD7PEntry 134217728}

pr1646v2XEfmVlanMCD7PIfInUnkwn OBJECT-TYPE
   SYNTAX      Counter64
   MAX-ACCESS  read-only
   STATUS      current
   DESCRIPTION
      "Path: efm.performance.vlan.mibCounters.d7Performance.ifInUnknownProtos

       64 bit unsigned wrappable counter."
   ::= {pr1646v2XEfmVlanMCD7PEntry 150994944}

pr1646v2XEfmVlanMCD7PInDropEx OBJECT-TYPE
   SYNTAX      Counter64
   MAX-ACCESS  read-only
   STATUS      current
   DESCRIPTION
      "Path: efm.performance.vlan.mibCounters.d7Performance.ifInDropLevelExceeded

       64 bit unsigned wrappable counter."
   ::= {pr1646v2XEfmVlanMCD7PEntry 335544320}

pr1646v2XEfmVlanMCD7PInDropNoMac OBJECT-TYPE
   SYNTAX      Counter64
   MAX-ACCESS  read-only
   STATUS      current
   DESCRIPTION
      "Path: efm.performance.vlan.mibCounters.d7Performance.fInDiscardsNoMacFit

       64 bit unsigned wrappable counter."
   ::= {pr1646v2XEfmVlanMCD7PEntry 301989888}

pr1646v2XEfmVlanMCD7PInDropNUCast OBJECT-TYPE
   SYNTAX      Counter64
   MAX-ACCESS  read-only
   STATUS      current
   DESCRIPTION
      "Path: efm.performance.vlan.mibCounters.d7Performance.fInDiscardsNUCast

       64 bit unsigned wrappable counter."
   ::= {pr1646v2XEfmVlanMCD7PEntry 318767104}

pr1646v2XEfmVlanMCD7PInDropFilter OBJECT-TYPE
   SYNTAX      Counter64
   MAX-ACCESS  read-only
   STATUS      current
   DESCRIPTION
      "Path: efm.performance.vlan.mibCounters.d7Performance.fInDiscardsFilter

       64 bit unsigned wrappable counter."
   ::= {pr1646v2XEfmVlanMCD7PEntry 385875968}

pr1646v2XEfmVlanMCD7PIfInBandwidth OBJECT-TYPE
   SYNTAX      Integer32
   MAX-ACCESS  read-only
   STATUS      current
   DESCRIPTION
      "Path: efm.performance.vlan.mibCounters.d7Performance.ifInBandwidth

       unit name = bps
       formula = 8 * ; 8 /"
   ::= {pr1646v2XEfmVlanMCD7PEntry 268435456}

pr1646v2XEfmVlanMCD7PIfOutOctets OBJECT-TYPE
   SYNTAX      Counter64
   MAX-ACCESS  read-only
   STATUS      current
   DESCRIPTION
      "Path: efm.performance.vlan.mibCounters.d7Performance.ifOutOctets

       64 bit unsigned wrappable counter."
   ::= {pr1646v2XEfmVlanMCD7PEntry 167772160}

pr1646v2XEfmVlanMCD7PIfOutUCPkts OBJECT-TYPE
   SYNTAX      Counter64
   MAX-ACCESS  read-only
   STATUS      current
   DESCRIPTION
      "Path: efm.performance.vlan.mibCounters.d7Performance.ifOutUcastPkts

       64 bit unsigned wrappable counter."
   ::= {pr1646v2XEfmVlanMCD7PEntry 184549376}

pr1646v2XEfmVlanMCD7PIfOutNUCPkts OBJECT-TYPE
   SYNTAX      Counter64
   MAX-ACCESS  read-only
   STATUS      current
   DESCRIPTION
      "Path: efm.performance.vlan.mibCounters.d7Performance.ifOutNUcastPkts

       64 bit unsigned wrappable counter."
   ::= {pr1646v2XEfmVlanMCD7PEntry 201326592}

pr1646v2XEfmVlanMCD7PIfOutBCPkts OBJECT-TYPE
   SYNTAX      Counter64
   MAX-ACCESS  read-only
   STATUS      current
   DESCRIPTION
      "Path: efm.performance.vlan.mibCounters.d7Performance.ifOutBcastPkts

       64 bit unsigned wrappable counter."
   ::= {pr1646v2XEfmVlanMCD7PEntry 452984832}

pr1646v2XEfmVlanMCD7PIfOutMCPkts OBJECT-TYPE
   SYNTAX      Counter64
   MAX-ACCESS  read-only
   STATUS      current
   DESCRIPTION
      "Path: efm.performance.vlan.mibCounters.d7Performance.ifOutMcastPkts

       64 bit unsigned wrappable counter."
   ::= {pr1646v2XEfmVlanMCD7PEntry 469762048}

pr1646v2XEfmVlanMCD7PIfOutDiscards OBJECT-TYPE
   SYNTAX      Counter64
   MAX-ACCESS  read-only
   STATUS      current
   DESCRIPTION
      "Path: efm.performance.vlan.mibCounters.d7Performance.ifOutDiscards

       64 bit unsigned wrappable counter."
   ::= {pr1646v2XEfmVlanMCD7PEntry 218103808}

pr1646v2XEfmVlanMCD7PIfOutErrors OBJECT-TYPE
   SYNTAX      Counter64
   MAX-ACCESS  read-only
   STATUS      current
   DESCRIPTION
      "Path: efm.performance.vlan.mibCounters.d7Performance.ifOutErrors

       64 bit unsigned wrappable counter."
   ::= {pr1646v2XEfmVlanMCD7PEntry 234881024}

pr1646v2XEfmVlanMCD7POutDropEx OBJECT-TYPE
   SYNTAX      Counter64
   MAX-ACCESS  read-only
   STATUS      current
   DESCRIPTION
      "Path: efm.performance.vlan.mibCounters.d7Performance.ifOutDropLevelExceeded

       64 bit unsigned wrappable counter."
   ::= {pr1646v2XEfmVlanMCD7PEntry 352321536}

pr1646v2XEfmVlanMCD7POutDropNoArp OBJECT-TYPE
   SYNTAX      Counter64
   MAX-ACCESS  read-only
   STATUS      current
   DESCRIPTION
      "Path: efm.performance.vlan.mibCounters.d7Performance.ifOutDiscardsNoArp

       64 bit unsigned wrappable counter."
   ::= {pr1646v2XEfmVlanMCD7PEntry 369098752}

pr1646v2XEfmVlanMCD7POutDropFilter OBJECT-TYPE
   SYNTAX      Counter64
   MAX-ACCESS  read-only
   STATUS      current
   DESCRIPTION
      "Path: efm.performance.vlan.mibCounters.d7Performance.ifOutDiscardsFilter

       64 bit unsigned wrappable counter."
   ::= {pr1646v2XEfmVlanMCD7PEntry 402653184}

pr1646v2XEfmVlanMCD7PIfOutBandwidth OBJECT-TYPE
   SYNTAX      Integer32
   MAX-ACCESS  read-only
   STATUS      current
   DESCRIPTION
      "Path: efm.performance.vlan.mibCounters.d7Performance.ifOutBandwidth

       unit name = bps
       formula = 8 * ; 8 /"
   ::= {pr1646v2XEfmVlanMCD7PEntry 285212672}

pr1646v2XEfmVlanMCD7PIfErrSec OBJECT-TYPE
   SYNTAX      Counter32
   MAX-ACCESS  read-only
   STATUS      current
   DESCRIPTION
      "Path: efm.performance.vlan.mibCounters.d7Performance.ifErrSec

       32 bit unsigned wrappable counter."
   ::= {pr1646v2XEfmVlanMCD7PEntry 251658240}

pr1646v2XEfmVlanInPQs OBJECT-TYPE
   SYNTAX      SEQUENCE OF Pr1646v2XEfmVlanInPQsEntry
   MAX-ACCESS  not-accessible
   STATUS      current
   DESCRIPTION
      ""
   ::= {pr1646v2XEfmVlan 100663296}

pr1646v2XEfmVlanInPQsEntry OBJECT-TYPE
   SYNTAX      Pr1646v2XEfmVlanInPQsEntry
   MAX-ACCESS  not-accessible
   STATUS      current
   DESCRIPTION
      ""
   INDEX      { pr1646v2XEfmVlanTableIx,
                pr1646v2XEfmVlanInPQsTableIx }
   ::= {pr1646v2XEfmVlanInPQs 1}

Pr1646v2XEfmVlanInPQsEntry ::=
   SEQUENCE
      {
      pr1646v2XEfmVlanInPQsTableIx
         TableIndex,
      pr1646v2XEfmVlanInPQsName
         INTEGER,
      pr1646v2XEfmVlanInPQsLength
         Integer32,
      pr1646v2XEfmVlanInPQsOctetLength
         Integer32,
      pr1646v2XEfmVlanInPQsRedLength
         Integer32,
      pr1646v2XEfmVlanInPQsPacketsTotal
         Counter64,
      pr1646v2XEfmVlanInPQsPacketsDirectTx
         Counter64,
      pr1646v2XEfmVlanInPQsPacketsQueued
         Counter64,
      pr1646v2XEfmVlanInPQsPacketsDropped
         Counter64,
      pr1646v2XEfmVlanInPQsPacketsRedDropped
         Counter64,
      pr1646v2XEfmVlanInPQsPacketsCirTx
         Counter64,
      pr1646v2XEfmVlanInPQsPacketsEirTx
         Counter64,
      pr1646v2XEfmVlanInPQsPacketsViolateTx
         Counter64,
      pr1646v2XEfmVlanInPQsOctetsTotal
         Counter64,
      pr1646v2XEfmVlanInPQsOctetsDirectTx
         Counter64,
      pr1646v2XEfmVlanInPQsOctetsQueued
         Counter64,
      pr1646v2XEfmVlanInPQsOctetsDropped
         Counter64,
      pr1646v2XEfmVlanInPQsOctetsRedDropped
         Counter64,
      pr1646v2XEfmVlanInPQsOctetsCirTx
         Counter64,
      pr1646v2XEfmVlanInPQsOctetsEirTx
         Counter64,
      pr1646v2XEfmVlanInPQsOctetsViolateTx
         Counter64,
      pr1646v2XEfmVlanInPQsOctetsBandwidth15sec
         Integer32,
      pr1646v2XEfmVlanInPQsOctetsBandwidth30sec
         Integer32,
      pr1646v2XEfmVlanInPQsOctetsBandwidth1min
         Integer32,
      pr1646v2XEfmVlanInPQsOctetsBandwidth2min
         Integer32,
      pr1646v2XEfmVlanInPQsOctetsBandwidth5min
         Integer32
      }

pr1646v2XEfmVlanInPQsTableIx OBJECT-TYPE
   SYNTAX      TableIndex
   MAX-ACCESS  not-accessible
   STATUS      current
   DESCRIPTION
      ""
   ::= {pr1646v2XEfmVlanInPQsEntry 11}

pr1646v2XEfmVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2XEfmVlanInPQsEntry 16777216}

pr1646v2XEfmVlanInPQsLength OBJECT-TYPE
   SYNTAX      Integer32
   MAX-ACCESS  read-only
   STATUS      current
   DESCRIPTION
      "Path: efm.performance.vlan.inPriorityQueues.length"
   ::= {pr1646v2XEfmVlanInPQsEntry 33554432}

pr1646v2XEfmVlanInPQsOctetLength OBJECT-TYPE
   SYNTAX      Integer32
   MAX-ACCESS  read-only
   STATUS      current
   DESCRIPTION
      "Path: efm.performance.vlan.inPriorityQueues.octetLength"
   ::= {pr1646v2XEfmVlanInPQsEntry 150994944}

pr1646v2XEfmVlanInPQsRedLength OBJECT-TYPE
   SYNTAX      Integer32
   MAX-ACCESS  read-only
   STATUS      current
   DESCRIPTION
      "Path: efm.performance.vlan.inPriorityQueues.redLength"
   ::= {pr1646v2XEfmVlanInPQsEntry 134217728}

pr1646v2XEfmVlanInPQsPacketsTotal OBJECT-TYPE
   SYNTAX      Counter64
   MAX-ACCESS  read-only
   STATUS      current
   DESCRIPTION
      "Path: efm.performance.vlan.inPriorityQueues.packets.total

       64 bit unsigned wrappable counter."
   ::= {pr1646v2XEfmVlanInPQsEntry 50790400}

pr1646v2XEfmVlanInPQsPacketsDirectTx OBJECT-TYPE
   SYNTAX      Counter64
   MAX-ACCESS  read-only
   STATUS      current
   DESCRIPTION
      "Path: efm.performance.vlan.inPriorityQueues.packets.directTx

       64 bit unsigned wrappable counter."
   ::= {pr1646v2XEfmVlanInPQsEntry 50397184}

pr1646v2XEfmVlanInPQsPacketsQueued OBJECT-TYPE
   SYNTAX      Counter64
   MAX-ACCESS  read-only
   STATUS      current
   DESCRIPTION
      "Path: efm.performance.vlan.inPriorityQueues.packets.queued

       64 bit unsigned wrappable counter."
   ::= {pr1646v2XEfmVlanInPQsEntry 50462720}

pr1646v2XEfmVlanInPQsPacketsDropped OBJECT-TYPE
   SYNTAX      Counter64
   MAX-ACCESS  read-only
   STATUS      current
   DESCRIPTION
      "Path: efm.performance.vlan.inPriorityQueues.packets.dropped

       64 bit unsigned wrappable counter."
   ::= {pr1646v2XEfmVlanInPQsEntry 50528256}

pr1646v2XEfmVlanInPQsPacketsRedDropped OBJECT-TYPE
   SYNTAX      Counter64
   MAX-ACCESS  read-only
   STATUS      current
   DESCRIPTION
      "Path: efm.performance.vlan.inPriorityQueues.packets.redDropped

       64 bit unsigned wrappable counter."
   ::= {pr1646v2XEfmVlanInPQsEntry 50724864}

pr1646v2XEfmVlanInPQsPacketsCirTx OBJECT-TYPE
   SYNTAX      Counter64
   MAX-ACCESS  read-only
   STATUS      current
   DESCRIPTION
      "Path: efm.performance.vlan.inPriorityQueues.packets.cirTx

       64 bit unsigned wrappable counter."
   ::= {pr1646v2XEfmVlanInPQsEntry 50593792}

pr1646v2XEfmVlanInPQsPacketsEirTx OBJECT-TYPE
   SYNTAX      Counter64
   MAX-ACCESS  read-only
   STATUS      current
   DESCRIPTION
      "Path: efm.performance.vlan.inPriorityQueues.packets.eirTx

       64 bit unsigned wrappable counter."
   ::= {pr1646v2XEfmVlanInPQsEntry 50659328}

pr1646v2XEfmVlanInPQsPacketsViolateTx OBJECT-TYPE
   SYNTAX      Counter64
   MAX-ACCESS  read-only
   STATUS      current
   DESCRIPTION
      "Path: efm.performance.vlan.inPriorityQueues.packets.violateTx

       64 bit unsigned wrappable counter."
   ::= {pr1646v2XEfmVlanInPQsEntry 50855936}

pr1646v2XEfmVlanInPQsOctetsTotal OBJECT-TYPE
   SYNTAX      Counter64
   MAX-ACCESS  read-only
   STATUS      current
   DESCRIPTION
      "Path: efm.performance.vlan.inPriorityQueues.octets.total

       64 bit unsigned wrappable counter."
   ::= {pr1646v2XEfmVlanInPQsEntry 67567616}

pr1646v2XEfmVlanInPQsOctetsDirectTx OBJECT-TYPE
   SYNTAX      Counter64
   MAX-ACCESS  read-only
   STATUS      current
   DESCRIPTION
      "Path: efm.performance.vlan.inPriorityQueues.octets.directTx

       64 bit unsigned wrappable counter."
   ::= {pr1646v2XEfmVlanInPQsEntry 67174400}

pr1646v2XEfmVlanInPQsOctetsQueued OBJECT-TYPE
   SYNTAX      Counter64
   MAX-ACCESS  read-only
   STATUS      current
   DESCRIPTION
      "Path: efm.performance.vlan.inPriorityQueues.octets.queued

       64 bit unsigned wrappable counter."
   ::= {pr1646v2XEfmVlanInPQsEntry 67239936}

pr1646v2XEfmVlanInPQsOctetsDropped OBJECT-TYPE
   SYNTAX      Counter64
   MAX-ACCESS  read-only
   STATUS      current
   DESCRIPTION
      "Path: efm.performance.vlan.inPriorityQueues.octets.dropped

       64 bit unsigned wrappable counter."
   ::= {pr1646v2XEfmVlanInPQsEntry 67305472}

pr1646v2XEfmVlanInPQsOctetsRedDropped OBJECT-TYPE
   SYNTAX      Counter64
   MAX-ACCESS  read-only
   STATUS      current
   DESCRIPTION
      "Path: efm.performance.vlan.inPriorityQueues.octets.redDropped

       64 bit unsigned wrappable counter."
   ::= {pr1646v2XEfmVlanInPQsEntry 67502080}

pr1646v2XEfmVlanInPQsOctetsCirTx OBJECT-TYPE
   SYNTAX      Counter64
   MAX-ACCESS  read-only
   STATUS      current
   DESCRIPTION
      "Path: efm.performance.vlan.inPriorityQueues.octets.cirTx

       64 bit unsigned wrappable counter."
   ::= {pr1646v2XEfmVlanInPQsEntry 67371008}

pr1646v2XEfmVlanInPQsOctetsEirTx OBJECT-TYPE
   SYNTAX      Counter64
   MAX-ACCESS  read-only
   STATUS      current
   DESCRIPTION
      "Path: efm.performance.vlan.inPriorityQueues.octets.eirTx

       64 bit unsigned wrappable counter."
   ::= {pr1646v2XEfmVlanInPQsEntry 67436544}

pr1646v2XEfmVlanInPQsOctetsViolateTx OBJECT-TYPE
   SYNTAX      Counter64
   MAX-ACCESS  read-only
   STATUS      current
   DESCRIPTION
      "Path: efm.performance.vlan.inPriorityQueues.octets.violateTx

       64 bit unsigned wrappable counter."
   ::= {pr1646v2XEfmVlanInPQsEntry 67633152}

pr1646v2XEfmVlanInPQsOctetsBandwidth15sec OBJECT-TYPE
   SYNTAX      Integer32
   MAX-ACCESS  read-only
   STATUS      current
   DESCRIPTION
      "Path: efm.performance.vlan.inPriorityQueues.octets.bandwidth.15sec

       unit name = bps
       formula = 8 * ; 8 /"
   ::= {pr1646v2XEfmVlanInPQsEntry 70386944}

pr1646v2XEfmVlanInPQsOctetsBandwidth30sec OBJECT-TYPE
   SYNTAX      Integer32
   MAX-ACCESS  read-only
   STATUS      current
   DESCRIPTION
      "Path: efm.performance.vlan.inPriorityQueues.octets.bandwidth.30sec

       unit name = bps
       formula = 8 * ; 8 /"
   ::= {pr1646v2XEfmVlanInPQsEntry 70388224}

pr1646v2XEfmVlanInPQsOctetsBandwidth1min OBJECT-TYPE
   SYNTAX      Integer32
   MAX-ACCESS  read-only
   STATUS      current
   DESCRIPTION
      "Path: efm.performance.vlan.inPriorityQueues.octets.bandwidth.1min

       unit name = bps
       formula = 8 * ; 8 /"
   ::= {pr1646v2XEfmVlanInPQsEntry 70390784}

pr1646v2XEfmVlanInPQsOctetsBandwidth2min OBJECT-TYPE
   SYNTAX      Integer32
   MAX-ACCESS  read-only
   STATUS      current
   DESCRIPTION
      "Path: efm.performance.vlan.inPriorityQueues.octets.bandwidth.2min

       unit name = bps
       formula = 8 * ; 8 /"
   ::= {pr1646v2XEfmVlanInPQsEntry 70395904}

pr1646v2XEfmVlanInPQsOctetsBandwidth5min OBJECT-TYPE
   SYNTAX      Integer32
   MAX-ACCESS  read-only
   STATUS      current
   DESCRIPTION
      "Path: efm.performance.vlan.inPriorityQueues.octets.bandwidth.5min

       unit name = bps
       formula = 8 * ; 8 /"
   ::= {pr1646v2XEfmVlanInPQsEntry 70411264}

pr1646v2XEfmVlanInPQsH2Performance OBJECT-TYPE
   SYNTAX      SEQUENCE OF Pr1646v2XEfmVlanInPQsH2PerformanceEntry
   MAX-ACCESS  not-accessible
   STATUS      current
   DESCRIPTION
      ""
   ::= {pr1646v2XEfmVlan 100990976}

pr1646v2XEfmVlanInPQsH2PerformanceEntry OBJECT-TYPE
   SYNTAX      Pr1646v2XEfmVlanInPQsH2PerformanceEntry
   MAX-ACCESS  not-accessible
   STATUS      current
   DESCRIPTION
      ""
   INDEX      { pr1646v2XEfmVlanTableIx,
                pr1646v2XEfmVlanInPQsTableIx,
                pr1646v2XEfmVlanInPQsH2PerformanceTableIx }
   ::= {pr1646v2XEfmVlanInPQsH2Performance 1}

Pr1646v2XEfmVlanInPQsH2PerformanceEntry ::=
   SEQUENCE
      {
      pr1646v2XEfmVlanInPQsH2PerformanceTableIx
         TableIndex,
      pr1646v2XEfmVlanInPQsH2PerformanceSysUpTime
         TimeTicks,
      pr1646v2XEfmVlanInPQsH2PerformanceTotPkts
         Counter64,
      pr1646v2XEfmVlanInPQsH2PerformanceDirTxPkts
         Counter64,
      pr1646v2XEfmVlanInPQsH2PerformanceQdPkts
         Counter64,
      pr1646v2XEfmVlanInPQsH2PerformanceDropPkts
         Counter64,
      pr1646v2XEfmVlanInPQsH2PerformanceRDropPkts
         Counter64,
      pr1646v2XEfmVlanInPQsH2PerformanceCirTxPkts
         Counter64,
      pr1646v2XEfmVlanInPQsH2PerformanceEirTxPkts
         Counter64,
      pr1646v2XEfmVlanInPQsH2PerformanceViolTxPkts
         Counter64,
      pr1646v2XEfmVlanInPQsH2PerformanceTotOcts
         Counter64,
      pr1646v2XEfmVlanInPQsH2PerformanceDirTxOcts
         Counter64,
      pr1646v2XEfmVlanInPQsH2PerformanceQdOcts
         Counter64,
      pr1646v2XEfmVlanInPQsH2PerformanceDropOcts
         Counter64,
      pr1646v2XEfmVlanInPQsH2PerformanceRDropOcts
         Counter64,
      pr1646v2XEfmVlanInPQsH2PerformanceCirTxOcts
         Counter64,
      pr1646v2XEfmVlanInPQsH2PerformanceEirTxOcts
         Counter64,
      pr1646v2XEfmVlanInPQsH2PerformanceViolTxOcts
         Counter64,
      pr1646v2XEfmVlanInPQsH2PerformanceBandwidth
         Integer32
      }

pr1646v2XEfmVlanInPQsH2PerformanceTableIx OBJECT-TYPE
   SYNTAX      TableIndex
   MAX-ACCESS  not-accessible
   STATUS      current
   DESCRIPTION
      ""
   ::= {pr1646v2XEfmVlanInPQsH2PerformanceEntry 11}

pr1646v2XEfmVlanInPQsH2PerformanceSysUpTime OBJECT-TYPE
   SYNTAX      TimeTicks
   MAX-ACCESS  read-only
   STATUS      current
   DESCRIPTION
      "Path: efm.performance.vlan.inPriorityQueues.h2Performance.sysUpTime

       Time in centi-second."
   ::= {pr1646v2XEfmVlanInPQsH2PerformanceEntry 16777216}

pr1646v2XEfmVlanInPQsH2PerformanceTotPkts OBJECT-TYPE
   SYNTAX      Counter64
   MAX-ACCESS  read-only
   STATUS      current
   DESCRIPTION
      "Path: efm.performance.vlan.inPriorityQueues.h2Performance.totalPkts

       64 bit unsigned wrappable counter."
   ::= {pr1646v2XEfmVlanInPQsH2PerformanceEntry 234881024}

pr1646v2XEfmVlanInPQsH2PerformanceDirTxPkts OBJECT-TYPE
   SYNTAX      Counter64
   MAX-ACCESS  read-only
   STATUS      current
   DESCRIPTION
      "Path: efm.performance.vlan.inPriorityQueues.h2Performance.directTxPkts

       64 bit unsigned wrappable counter."
   ::= {pr1646v2XEfmVlanInPQsH2PerformanceEntry 33554432}

pr1646v2XEfmVlanInPQsH2PerformanceQdPkts OBJECT-TYPE
   SYNTAX      Counter64
   MAX-ACCESS  read-only
   STATUS      current
   DESCRIPTION
      "Path: efm.performance.vlan.inPriorityQueues.h2Performance.queuedPkts

       64 bit unsigned wrappable counter."
   ::= {pr1646v2XEfmVlanInPQsH2PerformanceEntry 50331648}

pr1646v2XEfmVlanInPQsH2PerformanceDropPkts OBJECT-TYPE
   SYNTAX      Counter64
   MAX-ACCESS  read-only
   STATUS      current
   DESCRIPTION
      "Path: efm.performance.vlan.inPriorityQueues.h2Performance.droppedPkts

       64 bit unsigned wrappable counter."
   ::= {pr1646v2XEfmVlanInPQsH2PerformanceEntry 67108864}

pr1646v2XEfmVlanInPQsH2PerformanceRDropPkts OBJECT-TYPE
   SYNTAX      Counter64
   MAX-ACCESS  read-only
   STATUS      current
   DESCRIPTION
      "Path: efm.performance.vlan.inPriorityQueues.h2Performance.redDroppedPkts

       64 bit unsigned wrappable counter."
   ::= {pr1646v2XEfmVlanInPQsH2PerformanceEntry 201326592}

pr1646v2XEfmVlanInPQsH2PerformanceCirTxPkts OBJECT-TYPE
   SYNTAX      Counter64
   MAX-ACCESS  read-only
   STATUS      current
   DESCRIPTION
      "Path: efm.performance.vlan.inPriorityQueues.h2Performance.cirTxPkts

       64 bit unsigned wrappable counter."
   ::= {pr1646v2XEfmVlanInPQsH2PerformanceEntry 83886080}

pr1646v2XEfmVlanInPQsH2PerformanceEirTxPkts OBJECT-TYPE
   SYNTAX      Counter64
   MAX-ACCESS  read-only
   STATUS      current
   DESCRIPTION
      "Path: efm.performance.vlan.inPriorityQueues.h2Performance.eirTxPkts

       64 bit unsigned wrappable counter."
   ::= {pr1646v2XEfmVlanInPQsH2PerformanceEntry 100663296}

pr1646v2XEfmVlanInPQsH2PerformanceViolTxPkts OBJECT-TYPE
   SYNTAX      Counter64
   MAX-ACCESS  read-only
   STATUS      current
   DESCRIPTION
      "Path: efm.performance.vlan.inPriorityQueues.h2Performance.violateTxPkts

       64 bit unsigned wrappable counter."
   ::= {pr1646v2XEfmVlanInPQsH2PerformanceEntry 301989888}

pr1646v2XEfmVlanInPQsH2PerformanceTotOcts OBJECT-TYPE
   SYNTAX      Counter64
   MAX-ACCESS  read-only
   STATUS      current
   DESCRIPTION
      "Path: efm.performance.vlan.inPriorityQueues.h2Performance.totalOctets

       64 bit unsigned wrappable counter."
   ::= {pr1646v2XEfmVlanInPQsH2PerformanceEntry 251658240}

pr1646v2XEfmVlanInPQsH2PerformanceDirTxOcts OBJECT-TYPE
   SYNTAX      Counter64
   MAX-ACCESS  read-only
   STATUS      current
   DESCRIPTION
      "Path: efm.performance.vlan.inPriorityQueues.h2Performance.directTxOctets

       64 bit unsigned wrappable counter."
   ::= {pr1646v2XEfmVlanInPQsH2PerformanceEntry 117440512}

pr1646v2XEfmVlanInPQsH2PerformanceQdOcts OBJECT-TYPE
   SYNTAX      Counter64
   MAX-ACCESS  read-only
   STATUS      current
   DESCRIPTION
      "Path: efm.performance.vlan.inPriorityQueues.h2Performance.queuedOctets

       64 bit unsigned wrappable counter."
   ::= {pr1646v2XEfmVlanInPQsH2PerformanceEntry 134217728}

pr1646v2XEfmVlanInPQsH2PerformanceDropOcts OBJECT-TYPE
   SYNTAX      Counter64
   MAX-ACCESS  read-only
   STATUS      current
   DESCRIPTION
      "Path: efm.performance.vlan.inPriorityQueues.h2Performance.droppedOctets

       64 bit unsigned wrappable counter."
   ::= {pr1646v2XEfmVlanInPQsH2PerformanceEntry 150994944}

pr1646v2XEfmVlanInPQsH2PerformanceRDropOcts OBJECT-TYPE
   SYNTAX      Counter64
   MAX-ACCESS  read-only
   STATUS      current
   DESCRIPTION
      "Path: efm.performance.vlan.inPriorityQueues.h2Performance.redDroppedOctets

       64 bit unsigned wrappable counter."
   ::= {pr1646v2XEfmVlanInPQsH2PerformanceEntry 218103808}

pr1646v2XEfmVlanInPQsH2PerformanceCirTxOcts OBJECT-TYPE
   SYNTAX      Counter64
   MAX-ACCESS  read-only
   STATUS      current
   DESCRIPTION
      "Path: efm.performance.vlan.inPriorityQueues.h2Performance.cirTxOctets

       64 bit unsigned wrappable counter."
   ::= {pr1646v2XEfmVlanInPQsH2PerformanceEntry 167772160}

pr1646v2XEfmVlanInPQsH2PerformanceEirTxOcts OBJECT-TYPE
   SYNTAX      Counter64
   MAX-ACCESS  read-only
   STATUS      current
   DESCRIPTION
      "Path: efm.performance.vlan.inPriorityQueues.h2Performance.eirTxOctets

       64 bit unsigned wrappable counter."
   ::= {pr1646v2XEfmVlanInPQsH2PerformanceEntry 184549376}

pr1646v2XEfmVlanInPQsH2PerformanceViolTxOcts OBJECT-TYPE
   SYNTAX      Counter64
   MAX-ACCESS  read-only
   STATUS      current
   DESCRIPTION
      "Path: efm.performance.vlan.inPriorityQueues.h2Performance.violateTxOctets

       64 bit unsigned wrappable counter."
   ::= {pr1646v2XEfmVlanInPQsH2PerformanceEntry 318767104}

pr1646v2XEfmVlanInPQsH2PerformanceBandwidth OBJECT-TYPE
   SYNTAX      Integer32
   MAX-ACCESS  read-only
   STATUS      current
   DESCRIPTION
      "Path: efm.performance.vlan.inPriorityQueues.h2Performance.bandwidth

       unit name = bps
       formula = 8 * ; 8 /"
   ::= {pr1646v2XEfmVlanInPQsH2PerformanceEntry 268435456}

pr1646v2XEfmVlanInPQsH24Performance OBJECT-TYPE
   SYNTAX      SEQUENCE OF Pr1646v2XEfmVlanInPQsH24PerformanceEntry
   MAX-ACCESS  not-accessible
   STATUS      current
   DESCRIPTION
      ""
   ::= {pr1646v2XEfmVlan 101056512}

pr1646v2XEfmVlanInPQsH24PerformanceEntry OBJECT-TYPE
   SYNTAX      Pr1646v2XEfmVlanInPQsH24PerformanceEntry
   MAX-ACCESS  not-accessible
   STATUS      current
   DESCRIPTION
      ""
   INDEX      { pr1646v2XEfmVlanTableIx,
                pr1646v2XEfmVlanInPQsTableIx,
                pr1646v2XEfmVlanInPQsH24PerformanceTableIx }
   ::= {pr1646v2XEfmVlanInPQsH24Performance 1}

Pr1646v2XEfmVlanInPQsH24PerformanceEntry ::=
   SEQUENCE
      {
      pr1646v2XEfmVlanInPQsH24PerformanceTableIx
         TableIndex,
      pr1646v2XEfmVlanInPQsH24PerformanceSysUpTime
         TimeTicks,
      pr1646v2XEfmVlanInPQsH24PerformanceTotPkts
         Counter64,
      pr1646v2XEfmVlanInPQsH24PerformanceDirTxPkts
         Counter64,
      pr1646v2XEfmVlanInPQsH24PerformanceQdPkts
         Counter64,
      pr1646v2XEfmVlanInPQsH24PerformanceDropPkts
         Counter64,
      pr1646v2XEfmVlanInPQsH24PerformanceRDropPkts
         Counter64,
      pr1646v2XEfmVlanInPQsH24PerformanceCirTxPkts
         Counter64,
      pr1646v2XEfmVlanInPQsH24PerformanceEirTxPkts
         Counter64,
      pr1646v2XEfmVlanInPQsH24PerformanceViolTxPkts
         Counter64,
      pr1646v2XEfmVlanInPQsH24PerformanceTotOcts
         Counter64,
      pr1646v2XEfmVlanInPQsH24PerformanceDirTxOcts
         Counter64,
      pr1646v2XEfmVlanInPQsH24PerformanceQdOcts
         Counter64,
      pr1646v2XEfmVlanInPQsH24PerformanceDropOcts
         Counter64,
      pr1646v2XEfmVlanInPQsH24PerformanceRDropOcts
         Counter64,
      pr1646v2XEfmVlanInPQsH24PerformanceCirTxOcts
         Counter64,
      pr1646v2XEfmVlanInPQsH24PerformanceEirTxOcts
         Counter64,
      pr1646v2XEfmVlanInPQsH24PerformanceViolTxOcts
         Counter64,
      pr1646v2XEfmVlanInPQsH24PerformanceBandwidth
         Integer32
      }

pr1646v2XEfmVlanInPQsH24PerformanceTableIx OBJECT-TYPE
   SYNTAX      TableIndex
   MAX-ACCESS  not-accessible
   STATUS      current
   DESCRIPTION
      ""
   ::= {pr1646v2XEfmVlanInPQsH24PerformanceEntry 11}

pr1646v2XEfmVlanInPQsH24PerformanceSysUpTime OBJECT-TYPE
   SYNTAX      TimeTicks
   MAX-ACCESS  read-only
   STATUS      current
   DESCRIPTION
      "Path: efm.performance.vlan.inPriorityQueues.h24Performance.sysUpTime

       Time in centi-second."
   ::= {pr1646v2XEfmVlanInPQsH24PerformanceEntry 16777216}

pr1646v2XEfmVlanInPQsH24PerformanceTotPkts OBJECT-TYPE
   SYNTAX      Counter64
   MAX-ACCESS  read-only
   STATUS      current
   DESCRIPTION
      "Path: efm.performance.vlan.inPriorityQueues.h24Performance.totalPkts

       64 bit unsigned wrappable counter."
   ::= {pr1646v2XEfmVlanInPQsH24PerformanceEntry 234881024}

pr1646v2XEfmVlanInPQsH24PerformanceDirTxPkts OBJECT-TYPE
   SYNTAX      Counter64
   MAX-ACCESS  read-only
   STATUS      current
   DESCRIPTION
      "Path: efm.performance.vlan.inPriorityQueues.h24Performance.directTxPkts

       64 bit unsigned wrappable counter."
   ::= {pr1646v2XEfmVlanInPQsH24PerformanceEntry 33554432}

pr1646v2XEfmVlanInPQsH24PerformanceQdPkts OBJECT-TYPE
   SYNTAX      Counter64
   MAX-ACCESS  read-only
   STATUS      current
   DESCRIPTION
      "Path: efm.performance.vlan.inPriorityQueues.h24Performance.queuedPkts

       64 bit unsigned wrappable counter."
   ::= {pr1646v2XEfmVlanInPQsH24PerformanceEntry 50331648}

pr1646v2XEfmVlanInPQsH24PerformanceDropPkts OBJECT-TYPE
   SYNTAX      Counter64
   MAX-ACCESS  read-only
   STATUS      current
   DESCRIPTION
      "Path: efm.performance.vlan.inPriorityQueues.h24Performance.droppedPkts

       64 bit unsigned wrappable counter."
   ::= {pr1646v2XEfmVlanInPQsH24PerformanceEntry 67108864}

pr1646v2XEfmVlanInPQsH24PerformanceRDropPkts OBJECT-TYPE
   SYNTAX      Counter64
   MAX-ACCESS  read-only
   STATUS      current
   DESCRIPTION
      "Path: efm.performance.vlan.inPriorityQueues.h24Performance.redDroppedPkts

       64 bit unsigned wrappable counter."
   ::= {pr1646v2XEfmVlanInPQsH24PerformanceEntry 201326592}

pr1646v2XEfmVlanInPQsH24PerformanceCirTxPkts OBJECT-TYPE
   SYNTAX      Counter64
   MAX-ACCESS  read-only
   STATUS      current
   DESCRIPTION
      "Path: efm.performance.vlan.inPriorityQueues.h24Performance.cirTxPkts

       64 bit unsigned wrappable counter."
   ::= {pr1646v2XEfmVlanInPQsH24PerformanceEntry 83886080}

pr1646v2XEfmVlanInPQsH24PerformanceEirTxPkts OBJECT-TYPE
   SYNTAX      Counter64
   MAX-ACCESS  read-only
   STATUS      current
   DESCRIPTION
      "Path: efm.performance.vlan.inPriorityQueues.h24Performance.eirTxPkts

       64 bit unsigned wrappable counter."
   ::= {pr1646v2XEfmVlanInPQsH24PerformanceEntry 100663296}

pr1646v2XEfmVlanInPQsH24PerformanceViolTxPkts OBJECT-TYPE
   SYNTAX      Counter64
   MAX-ACCESS  read-only
   STATUS      current
   DESCRIPTION
      "Path: efm.performance.vlan.inPriorityQueues.h24Performance.violateTxPkts

       64 bit unsigned wrappable counter."
   ::= {pr1646v2XEfmVlanInPQsH24PerformanceEntry 301989888}

pr1646v2XEfmVlanInPQsH24PerformanceTotOcts OBJECT-TYPE
   SYNTAX      Counter64
   MAX-ACCESS  read-only
   STATUS      current
   DESCRIPTION
      "Path: efm.performance.vlan.inPriorityQueues.h24Performance.totalOctets

       64 bit unsigned wrappable counter."
   ::= {pr1646v2XEfmVlanInPQsH24PerformanceEntry 251658240}

pr1646v2XEfmVlanInPQsH24PerformanceDirTxOcts OBJECT-TYPE
   SYNTAX      Counter64
   MAX-ACCESS  read-only
   STATUS      current
   DESCRIPTION
      "Path: efm.performance.vlan.inPriorityQueues.h24Performance.directTxOctets

       64 bit unsigned wrappable counter."
   ::= {pr1646v2XEfmVlanInPQsH24PerformanceEntry 117440512}

pr1646v2XEfmVlanInPQsH24PerformanceQdOcts OBJECT-TYPE
   SYNTAX      Counter64
   MAX-ACCESS  read-only
   STATUS      current
   DESCRIPTION
      "Path: efm.performance.vlan.inPriorityQueues.h24Performance.queuedOctets

       64 bit unsigned wrappable counter."
   ::= {pr1646v2XEfmVlanInPQsH24PerformanceEntry 134217728}

pr1646v2XEfmVlanInPQsH24PerformanceDropOcts OBJECT-TYPE
   SYNTAX      Counter64
   MAX-ACCESS  read-only
   STATUS      current
   DESCRIPTION
      "Path: efm.performance.vlan.inPriorityQueues.h24Performance.droppedOctets

       64 bit unsigned wrappable counter."
   ::= {pr1646v2XEfmVlanInPQsH24PerformanceEntry 150994944}

pr1646v2XEfmVlanInPQsH24PerformanceRDropOcts OBJECT-TYPE
   SYNTAX      Counter64
   MAX-ACCESS  read-only
   STATUS      current
   DESCRIPTION
      "Path: efm.performance.vlan.inPriorityQueues.h24Performance.redDroppedOctets

       64 bit unsigned wrappable counter."
   ::= {pr1646v2XEfmVlanInPQsH24PerformanceEntry 218103808}

pr1646v2XEfmVlanInPQsH24PerformanceCirTxOcts OBJECT-TYPE
   SYNTAX      Counter64
   MAX-ACCESS  read-only
   STATUS      current
   DESCRIPTION
      "Path: efm.performance.vlan.inPriorityQueues.h24Performance.cirTxOctets

       64 bit unsigned wrappable counter."
   ::= {pr1646v2XEfmVlanInPQsH24PerformanceEntry 167772160}

pr1646v2XEfmVlanInPQsH24PerformanceEirTxOcts OBJECT-TYPE
   SYNTAX      Counter64
   MAX-ACCESS  read-only
   STATUS      current
   DESCRIPTION
      "Path: efm.performance.vlan.inPriorityQueues.h24Performance.eirTxOctets

       64 bit unsigned wrappable counter."
   ::= {pr1646v2XEfmVlanInPQsH24PerformanceEntry 184549376}

pr1646v2XEfmVlanInPQsH24PerformanceViolTxOcts OBJECT-TYPE
   SYNTAX      Counter64
   MAX-ACCESS  read-only
   STATUS      current
   DESCRIPTION
      "Path: efm.performance.vlan.inPriorityQueues.h24Performance.violateTxOctets

       64 bit unsigned wrappable counter."
   ::= {pr1646v2XEfmVlanInPQsH24PerformanceEntry 318767104}

pr1646v2XEfmVlanInPQsH24PerformanceBandwidth OBJECT-TYPE
   SYNTAX      Integer32
   MAX-ACCESS  read-only
   STATUS      current
   DESCRIPTION
      "Path: efm.performance.vlan.inPriorityQueues.h24Performance.bandwidth

       unit name = bps
       formula = 8 * ; 8 /"
   ::= {pr1646v2XEfmVlanInPQsH24PerformanceEntry 268435456}

pr1646v2XEfmVlanInPQsD7Performance OBJECT-TYPE
   SYNTAX      SEQUENCE OF Pr1646v2XEfmVlanInPQsD7PerformanceEntry
   MAX-ACCESS  not-accessible
   STATUS      current
   DESCRIPTION
      ""
   ::= {pr1646v2XEfmVlan 101122048}

pr1646v2XEfmVlanInPQsD7PerformanceEntry OBJECT-TYPE
   SYNTAX      Pr1646v2XEfmVlanInPQsD7PerformanceEntry
   MAX-ACCESS  not-accessible
   STATUS      current
   DESCRIPTION
      ""
   INDEX      { pr1646v2XEfmVlanTableIx,
                pr1646v2XEfmVlanInPQsTableIx,
                pr1646v2XEfmVlanInPQsD7PerformanceTableIx }
   ::= {pr1646v2XEfmVlanInPQsD7Performance 1}

Pr1646v2XEfmVlanInPQsD7PerformanceEntry ::=
   SEQUENCE
      {
      pr1646v2XEfmVlanInPQsD7PerformanceTableIx
         TableIndex,
      pr1646v2XEfmVlanInPQsD7PerformanceSysUpTime
         TimeTicks,
      pr1646v2XEfmVlanInPQsD7PerformanceTotPkts
         Counter64,
      pr1646v2XEfmVlanInPQsD7PerformanceDirTxPkts
         Counter64,
      pr1646v2XEfmVlanInPQsD7PerformanceQdPkts
         Counter64,
      pr1646v2XEfmVlanInPQsD7PerformanceDropPkts
         Counter64,
      pr1646v2XEfmVlanInPQsD7PerformanceRDropPkts
         Counter64,
      pr1646v2XEfmVlanInPQsD7PerformanceCirTxPkts
         Counter64,
      pr1646v2XEfmVlanInPQsD7PerformanceEirTxPkts
         Counter64,
      pr1646v2XEfmVlanInPQsD7PerformanceViolTxPkts
         Counter64,
      pr1646v2XEfmVlanInPQsD7PerformanceTotOcts
         Counter64,
      pr1646v2XEfmVlanInPQsD7PerformanceDirTxOcts
         Counter64,
      pr1646v2XEfmVlanInPQsD7PerformanceQdOcts
         Counter64,
      pr1646v2XEfmVlanInPQsD7PerformanceDropOcts
         Counter64,
      pr1646v2XEfmVlanInPQsD7PerformanceRDropOcts
         Counter64,
      pr1646v2XEfmVlanInPQsD7PerformanceCirTxOcts
         Counter64,
      pr1646v2XEfmVlanInPQsD7PerformanceEirTxOcts
         Counter64,
      pr1646v2XEfmVlanInPQsD7PerformanceViolTxOcts
         Counter64,
      pr1646v2XEfmVlanInPQsD7PerformanceBandwidth
         Integer32
      }

pr1646v2XEfmVlanInPQsD7PerformanceTableIx OBJECT-TYPE
   SYNTAX      TableIndex
   MAX-ACCESS  not-accessible
   STATUS      current
   DESCRIPTION
      ""
   ::= {pr1646v2XEfmVlanInPQsD7PerformanceEntry 11}

pr1646v2XEfmVlanInPQsD7PerformanceSysUpTime OBJECT-TYPE
   SYNTAX      TimeTicks
   MAX-ACCESS  read-only
   STATUS      current
   DESCRIPTION
      "Path: efm.performance.vlan.inPriorityQueues.d7Performance.sysUpTime

       Time in centi-second."
   ::= {pr1646v2XEfmVlanInPQsD7PerformanceEntry 16777216}

pr1646v2XEfmVlanInPQsD7PerformanceTotPkts OBJECT-TYPE
   SYNTAX      Counter64
   MAX-ACCESS  read-only
   STATUS      current
   DESCRIPTION
      "Path: efm.performance.vlan.inPriorityQueues.d7Performance.totalPkts

       64 bit unsigned wrappable counter."
   ::= {pr1646v2XEfmVlanInPQsD7PerformanceEntry 234881024}

pr1646v2XEfmVlanInPQsD7PerformanceDirTxPkts OBJECT-TYPE
   SYNTAX      Counter64
   MAX-ACCESS  read-only
   STATUS      current
   DESCRIPTION
      "Path: efm.performance.vlan.inPriorityQueues.d7Performance.directTxPkts

       64 bit unsigned wrappable counter."
   ::= {pr1646v2XEfmVlanInPQsD7PerformanceEntry 33554432}

pr1646v2XEfmVlanInPQsD7PerformanceQdPkts OBJECT-TYPE
   SYNTAX      Counter64
   MAX-ACCESS  read-only
   STATUS      current
   DESCRIPTION
      "Path: efm.performance.vlan.inPriorityQueues.d7Performance.queuedPkts

       64 bit unsigned wrappable counter."
   ::= {pr1646v2XEfmVlanInPQsD7PerformanceEntry 50331648}

pr1646v2XEfmVlanInPQsD7PerformanceDropPkts OBJECT-TYPE
   SYNTAX      Counter64
   MAX-ACCESS  read-only
   STATUS      current
   DESCRIPTION
      "Path: efm.performance.vlan.inPriorityQueues.d7Performance.droppedPkts

       64 bit unsigned wrappable counter."
   ::= {pr1646v2XEfmVlanInPQsD7PerformanceEntry 67108864}

pr1646v2XEfmVlanInPQsD7PerformanceRDropPkts OBJECT-TYPE
   SYNTAX      Counter64
   MAX-ACCESS  read-only
   STATUS      current
   DESCRIPTION
      "Path: efm.performance.vlan.inPriorityQueues.d7Performance.redDroppedPkts

       64 bit unsigned wrappable counter."
   ::= {pr1646v2XEfmVlanInPQsD7PerformanceEntry 201326592}

pr1646v2XEfmVlanInPQsD7PerformanceCirTxPkts OBJECT-TYPE
   SYNTAX      Counter64
   MAX-ACCESS  read-only
   STATUS      current
   DESCRIPTION
      "Path: efm.performance.vlan.inPriorityQueues.d7Performance.cirTxPkts

       64 bit unsigned wrappable counter."
   ::= {pr1646v2XEfmVlanInPQsD7PerformanceEntry 83886080}

pr1646v2XEfmVlanInPQsD7PerformanceEirTxPkts OBJECT-TYPE
   SYNTAX      Counter64
   MAX-ACCESS  read-only
   STATUS      current
   DESCRIPTION
      "Path: efm.performance.vlan.inPriorityQueues.d7Performance.eirTxPkts

       64 bit unsigned wrappable counter."
   ::= {pr1646v2XEfmVlanInPQsD7PerformanceEntry 100663296}

pr1646v2XEfmVlanInPQsD7PerformanceViolTxPkts OBJECT-TYPE
   SYNTAX      Counter64
   MAX-ACCESS  read-only
   STATUS      current
   DESCRIPTION
      "Path: efm.performance.vlan.inPriorityQueues.d7Performance.violateTxPkts

       64 bit unsigned wrappable counter."
   ::= {pr1646v2XEfmVlanInPQsD7PerformanceEntry 301989888}

pr1646v2XEfmVlanInPQsD7PerformanceTotOcts OBJECT-TYPE
   SYNTAX      Counter64
   MAX-ACCESS  read-only
   STATUS      current
   DESCRIPTION
      "Path: efm.performance.vlan.inPriorityQueues.d7Performance.totalOctets

       64 bit unsigned wrappable counter."
   ::= {pr1646v2XEfmVlanInPQsD7PerformanceEntry 251658240}

pr1646v2XEfmVlanInPQsD7PerformanceDirTxOcts OBJECT-TYPE
   SYNTAX      Counter64
   MAX-ACCESS  read-only
   STATUS      current
   DESCRIPTION
      "Path: efm.performance.vlan.inPriorityQueues.d7Performance.directTxOctets

       64 bit unsigned wrappable counter."
   ::= {pr1646v2XEfmVlanInPQsD7PerformanceEntry 117440512}

pr1646v2XEfmVlanInPQsD7PerformanceQdOcts OBJECT-TYPE
   SYNTAX      Counter64
   MAX-ACCESS  read-only
   STATUS      current
   DESCRIPTION
      "Path: efm.performance.vlan.inPriorityQueues.d7Performance.queuedOctets

       64 bit unsigned wrappable counter."
   ::= {pr1646v2XEfmVlanInPQsD7PerformanceEntry 134217728}

pr1646v2XEfmVlanInPQsD7PerformanceDropOcts OBJECT-TYPE
   SYNTAX      Counter64
   MAX-ACCESS  read-only
   STATUS      current
   DESCRIPTION
      "Path: efm.performance.vlan.inPriorityQueues.d7Performance.droppedOctets

       64 bit unsigned wrappable counter."
   ::= {pr1646v2XEfmVlanInPQsD7PerformanceEntry 150994944}

pr1646v2XEfmVlanInPQsD7PerformanceRDropOcts OBJECT-TYPE
   SYNTAX      Counter64
   MAX-ACCESS  read-only
   STATUS      current
   DESCRIPTION
      "Path: efm.performance.vlan.inPriorityQueues.d7Performance.redDroppedOctets

       64 bit unsigned wrappable counter."
   ::= {pr1646v2XEfmVlanInPQsD7PerformanceEntry 218103808}

pr1646v2XEfmVlanInPQsD7PerformanceCirTxOcts OBJECT-TYPE
   SYNTAX      Counter64
   MAX-ACCESS  read-only
   STATUS      current
   DESCRIPTION
      "Path: efm.performance.vlan.inPriorityQueues.d7Performance.cirTxOctets

       64 bit unsigned wrappable counter."
   ::= {pr1646v2XEfmVlanInPQsD7PerformanceEntry 167772160}

pr1646v2XEfmVlanInPQsD7PerformanceEirTxOcts OBJECT-TYPE
   SYNTAX      Counter64
   MAX-ACCESS  read-only
   STATUS      current
   DESCRIPTION
      "Path: efm.performance.vlan.inPriorityQueues.d7Performance.eirTxOctets

       64 bit unsigned wrappable counter."
   ::= {pr1646v2XEfmVlanInPQsD7PerformanceEntry 184549376}

pr1646v2XEfmVlanInPQsD7PerformanceViolTxOcts OBJECT-TYPE
   SYNTAX      Counter64
   MAX-ACCESS  read-only
   STATUS      current
   DESCRIPTION
      "Path: efm.performance.vlan.inPriorityQueues.d7Performance.violateTxOctets

       64 bit unsigned wrappable counter."
   ::= {pr1646v2XEfmVlanInPQsD7PerformanceEntry 318767104}

pr1646v2XEfmVlanInPQsD7PerformanceBandwidth OBJECT-TYPE
   SYNTAX      Integer32
   MAX-ACCESS  read-only
   STATUS      current
   DESCRIPTION
      "Path: efm.performance.vlan.inPriorityQueues.d7Performance.bandwidth

       unit name = bps
       formula = 8 * ; 8 /"
   ::= {pr1646v2XEfmVlanInPQsD7PerformanceEntry 268435456}

pr1646v2XEfmVlanOutPQs OBJECT-TYPE
   SYNTAX      SEQUENCE OF Pr1646v2XEfmVlanOutPQsEntry
   MAX-ACCESS  not-accessible
   STATUS      current
   DESCRIPTION
      ""
   ::= {pr1646v2XEfmVlan 83886080}

pr1646v2XEfmVlanOutPQsEntry OBJECT-TYPE
   SYNTAX      Pr1646v2XEfmVlanOutPQsEntry
   MAX-ACCESS  not-accessible
   STATUS      current
   DESCRIPTION
      ""
   INDEX      { pr1646v2XEfmVlanTableIx,
                pr1646v2XEfmVlanOutPQsTableIx }
   ::= {pr1646v2XEfmVlanOutPQs 1}

Pr1646v2XEfmVlanOutPQsEntry ::=
   SEQUENCE
      {
      pr1646v2XEfmVlanOutPQsTableIx
         TableIndex,
      pr1646v2XEfmVlanOutPQsName
         INTEGER,
      pr1646v2XEfmVlanOutPQsLength
         Integer32,
      pr1646v2XEfmVlanOutPQsOctetLength
         Integer32,
      pr1646v2XEfmVlanOutPQsRedLength
         Integer32,
      pr1646v2XEfmVlanOutPQsPacketsTotal
         Counter64,
      pr1646v2XEfmVlanOutPQsPacketsDirectTx
         Counter64,
      pr1646v2XEfmVlanOutPQsPacketsQueued
         Counter64,
      pr1646v2XEfmVlanOutPQsPacketsDropped
         Counter64,
      pr1646v2XEfmVlanOutPQsPacketsRedDropped
         Counter64,
      pr1646v2XEfmVlanOutPQsPacketsCirTx
         Counter64,
      pr1646v2XEfmVlanOutPQsPacketsEirTx
         Counter64,
      pr1646v2XEfmVlanOutPQsPacketsViolateTx
         Counter64,
      pr1646v2XEfmVlanOutPQsOctetsTotal
         Counter64,
      pr1646v2XEfmVlanOutPQsOctetsDirectTx
         Counter64,
      pr1646v2XEfmVlanOutPQsOctetsQueued
         Counter64,
      pr1646v2XEfmVlanOutPQsOctetsDropped
         Counter64,
      pr1646v2XEfmVlanOutPQsOctetsRedDropped
         Counter64,
      pr1646v2XEfmVlanOutPQsOctetsCirTx
         Counter64,
      pr1646v2XEfmVlanOutPQsOctetsEirTx
         Counter64,
      pr1646v2XEfmVlanOutPQsOctetsViolateTx
         Counter64,
      pr1646v2XEfmVlanOutPQsOctetsBandwidth15sec
         Integer32,
      pr1646v2XEfmVlanOutPQsOctetsBandwidth30sec
         Integer32,
      pr1646v2XEfmVlanOutPQsOctetsBandwidth1min
         Integer32,
      pr1646v2XEfmVlanOutPQsOctetsBandwidth2min
         Integer32,
      pr1646v2XEfmVlanOutPQsOctetsBandwidth5min
         Integer32
      }

pr1646v2XEfmVlanOutPQsTableIx OBJECT-TYPE
   SYNTAX      TableIndex
   MAX-ACCESS  not-accessible
   STATUS      current
   DESCRIPTION
      ""
   ::= {pr1646v2XEfmVlanOutPQsEntry 11}

pr1646v2XEfmVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2XEfmVlanOutPQsEntry 16777216}

pr1646v2XEfmVlanOutPQsLength OBJECT-TYPE
   SYNTAX      Integer32
   MAX-ACCESS  read-only
   STATUS      current
   DESCRIPTION
      "Path: efm.performance.vlan.outPriorityQueues.length"
   ::= {pr1646v2XEfmVlanOutPQsEntry 33554432}

pr1646v2XEfmVlanOutPQsOctetLength OBJECT-TYPE
   SYNTAX      Integer32
   MAX-ACCESS  read-only
   STATUS      current
   DESCRIPTION
      "Path: efm.performance.vlan.outPriorityQueues.octetLength"
   ::= {pr1646v2XEfmVlanOutPQsEntry 150994944}

pr1646v2XEfmVlanOutPQsRedLength OBJECT-TYPE
   SYNTAX      Integer32
   MAX-ACCESS  read-only
   STATUS      current
   DESCRIPTION
      "Path: efm.performance.vlan.outPriorityQueues.redLength"
   ::= {pr1646v2XEfmVlanOutPQsEntry 134217728}

pr1646v2XEfmVlanOutPQsPacketsTotal OBJECT-TYPE
   SYNTAX      Counter64
   MAX-ACCESS  read-only
   STATUS      current
   DESCRIPTION
      "Path: efm.performance.vlan.outPriorityQueues.packets.total

       64 bit unsigned wrappable counter."
   ::= {pr1646v2XEfmVlanOutPQsEntry 50790400}

pr1646v2XEfmVlanOutPQsPacketsDirectTx OBJECT-TYPE
   SYNTAX      Counter64
   MAX-ACCESS  read-only
   STATUS      current
   DESCRIPTION
      "Path: efm.performance.vlan.outPriorityQueues.packets.directTx

       64 bit unsigned wrappable counter."
   ::= {pr1646v2XEfmVlanOutPQsEntry 50397184}

pr1646v2XEfmVlanOutPQsPacketsQueued OBJECT-TYPE
   SYNTAX      Counter64
   MAX-ACCESS  read-only
   STATUS      current
   DESCRIPTION
      "Path: efm.performance.vlan.outPriorityQueues.packets.queued

       64 bit unsigned wrappable counter."
   ::= {pr1646v2XEfmVlanOutPQsEntry 50462720}

pr1646v2XEfmVlanOutPQsPacketsDropped OBJECT-TYPE
   SYNTAX      Counter64
   MAX-ACCESS  read-only
   STATUS      current
   DESCRIPTION
      "Path: efm.performance.vlan.outPriorityQueues.packets.dropped

       64 bit unsigned wrappable counter."
   ::= {pr1646v2XEfmVlanOutPQsEntry 50528256}

pr1646v2XEfmVlanOutPQsPacketsRedDropped OBJECT-TYPE
   SYNTAX      Counter64
   MAX-ACCESS  read-only
   STATUS      current
   DESCRIPTION
      "Path: efm.performance.vlan.outPriorityQueues.packets.redDropped

       64 bit unsigned wrappable counter."
   ::= {pr1646v2XEfmVlanOutPQsEntry 50724864}

pr1646v2XEfmVlanOutPQsPacketsCirTx OBJECT-TYPE
   SYNTAX      Counter64
   MAX-ACCESS  read-only
   STATUS      current
   DESCRIPTION
      "Path: efm.performance.vlan.outPriorityQueues.packets.cirTx

       64 bit unsigned wrappable counter."
   ::= {pr1646v2XEfmVlanOutPQsEntry 50593792}

pr1646v2XEfmVlanOutPQsPacketsEirTx OBJECT-TYPE
   SYNTAX      Counter64
   MAX-ACCESS  read-only
   STATUS      current
   DESCRIPTION
      "Path: efm.performance.vlan.outPriorityQueues.packets.eirTx

       64 bit unsigned wrappable counter."
   ::= {pr1646v2XEfmVlanOutPQsEntry 50659328}

pr1646v2XEfmVlanOutPQsPacketsViolateTx OBJECT-TYPE
   SYNTAX      Counter64
   MAX-ACCESS  read-only
   STATUS      current
   DESCRIPTION
      "Path: efm.performance.vlan.outPriorityQueues.packets.violateTx

       64 bit unsigned wrappable counter."
   ::= {pr1646v2XEfmVlanOutPQsEntry 50855936}

pr1646v2XEfmVlanOutPQsOctetsTotal OBJECT-TYPE
   SYNTAX      Counter64
   MAX-ACCESS  read-only
   STATUS      current
   DESCRIPTION
      "Path: efm.performance.vlan.outPriorityQueues.octets.total

       64 bit unsigned wrappable counter."
   ::= {pr1646v2XEfmVlanOutPQsEntry 67567616}

pr1646v2XEfmVlanOutPQsOctetsDirectTx OBJECT-TYPE
   SYNTAX      Counter64
   MAX-ACCESS  read-only
   STATUS      current
   DESCRIPTION
      "Path: efm.performance.vlan.outPriorityQueues.octets.directTx

       64 bit unsigned wrappable counter."
   ::= {pr1646v2XEfmVlanOutPQsEntry 67174400}

pr1646v2XEfmVlanOutPQsOctetsQueued OBJECT-TYPE
   SYNTAX      Counter64
   MAX-ACCESS  read-only
   STATUS      current
   DESCRIPTION
      "Path: efm.performance.vlan.outPriorityQueues.octets.queued

       64 bit unsigned wrappable counter."
   ::= {pr1646v2XEfmVlanOutPQsEntry 67239936}

pr1646v2XEfmVlanOutPQsOctetsDropped OBJECT-TYPE
   SYNTAX      Counter64
   MAX-ACCESS  read-only
   STATUS      current
   DESCRIPTION
      "Path: efm.performance.vlan.outPriorityQueues.octets.dropped

       64 bit unsigned wrappable counter."
   ::= {pr1646v2XEfmVlanOutPQsEntry 67305472}

pr1646v2XEfmVlanOutPQsOctetsRedDropped OBJECT-TYPE
   SYNTAX      Counter64
   MAX-ACCESS  read-only
   STATUS      current
   DESCRIPTION
      "Path: efm.performance.vlan.outPriorityQueues.octets.redDropped

       64 bit unsigned wrappable counter."
   ::= {pr1646v2XEfmVlanOutPQsEntry 67502080}

pr1646v2XEfmVlanOutPQsOctetsCirTx OBJECT-TYPE
   SYNTAX      Counter64
   MAX-ACCESS  read-only
   STATUS      current
   DESCRIPTION
      "Path: efm.performance.vlan.outPriorityQueues.octets.cirTx

       64 bit unsigned wrappable counter."
   ::= {pr1646v2XEfmVlanOutPQsEntry 67371008}

pr1646v2XEfmVlanOutPQsOctetsEirTx OBJECT-TYPE
   SYNTAX      Counter64
   MAX-ACCESS  read-only
   STATUS      current
   DESCRIPTION
      "Path: efm.performance.vlan.outPriorityQueues.octets.eirTx

       64 bit unsigned wrappable counter."
   ::= {pr1646v2XEfmVlanOutPQsEntry 67436544}

pr1646v2XEfmVlanOutPQsOctetsViolateTx OBJECT-TYPE
   SYNTAX      Counter64
   MAX-ACCESS  read-only
   STATUS      current
   DESCRIPTION
      "Path: efm.performance.vlan.outPriorityQueues.octets.violateTx

       64 bit unsigned wrappable counter."
   ::= {pr1646v2XEfmVlanOutPQsEntry 67633152}

pr1646v2XEfmVlanOutPQsOctetsBandwidth15sec OBJECT-TYPE
   SYNTAX      Integer32
   MAX-ACCESS  read-only
   STATUS      current
   DESCRIPTION
      "Path: efm.performance.vlan.outPriorityQueues.octets.bandwidth.15sec

       unit name = bps
       formula = 8 * ; 8 /"
   ::= {pr1646v2XEfmVlanOutPQsEntry 70386944}

pr1646v2XEfmVlanOutPQsOctetsBandwidth30sec OBJECT-TYPE
   SYNTAX      Integer32
   MAX-ACCESS  read-only
   STATUS      current
   DESCRIPTION
      "Path: efm.performance.vlan.outPriorityQueues.octets.bandwidth.30sec

       unit name = bps
       formula = 8 * ; 8 /"
   ::= {pr1646v2XEfmVlanOutPQsEntry 70388224}

pr1646v2XEfmVlanOutPQsOctetsBandwidth1min OBJECT-TYPE
   SYNTAX      Integer32
   MAX-ACCESS  read-only
   STATUS      current
   DESCRIPTION
      "Path: efm.performance.vlan.outPriorityQueues.octets.bandwidth.1min

       unit name = bps
       formula = 8 * ; 8 /"
   ::= {pr1646v2XEfmVlanOutPQsEntry 70390784}

pr1646v2XEfmVlanOutPQsOctetsBandwidth2min OBJECT-TYPE
   SYNTAX      Integer32
   MAX-ACCESS  read-only
   STATUS      current
   DESCRIPTION
      "Path: efm.performance.vlan.outPriorityQueues.octets.bandwidth.2min

       unit name = bps
       formula = 8 * ; 8 /"
   ::= {pr1646v2XEfmVlanOutPQsEntry 70395904}

pr1646v2XEfmVlanOutPQsOctetsBandwidth5min OBJECT-TYPE
   SYNTAX      Integer32
   MAX-ACCESS  read-only
   STATUS      current
   DESCRIPTION
      "Path: efm.performance.vlan.outPriorityQueues.octets.bandwidth.5min

       unit name = bps
       formula = 8 * ; 8 /"
   ::= {pr1646v2XEfmVlanOutPQsEntry 70411264}

pr1646v2XEfmVlanOutPQsH2Performance OBJECT-TYPE
   SYNTAX      SEQUENCE OF Pr1646v2XEfmVlanOutPQsH2PerformanceEntry
   MAX-ACCESS  not-accessible
   STATUS      current
   DESCRIPTION
      ""
   ::= {pr1646v2XEfmVlan 84213760}

pr1646v2XEfmVlanOutPQsH2PerformanceEntry OBJECT-TYPE
   SYNTAX      Pr1646v2XEfmVlanOutPQsH2PerformanceEntry
   MAX-ACCESS  not-accessible
   STATUS      current
   DESCRIPTION
      ""
   INDEX      { pr1646v2XEfmVlanTableIx,
                pr1646v2XEfmVlanOutPQsTableIx,
                pr1646v2XEfmVlanOutPQsH2PerformanceTableIx }
   ::= {pr1646v2XEfmVlanOutPQsH2Performance 1}

Pr1646v2XEfmVlanOutPQsH2PerformanceEntry ::=
   SEQUENCE
      {
      pr1646v2XEfmVlanOutPQsH2PerformanceTableIx
         TableIndex,
      pr1646v2XEfmVlanOutPQsH2PerformanceSysUpTime
         TimeTicks,
      pr1646v2XEfmVlanOutPQsH2PerformanceTotPkts
         Counter64,
      pr1646v2XEfmVlanOutPQsH2PerformanceDirTxPkts
         Counter64,
      pr1646v2XEfmVlanOutPQsH2PerformanceQdPkts
         Counter64,
      pr1646v2XEfmVlanOutPQsH2PerformanceDropPkts
         Counter64,
      pr1646v2XEfmVlanOutPQsH2PerformanceRDropPkts
         Counter64,
      pr1646v2XEfmVlanOutPQsH2PerformanceCirTxPkts
         Counter64,
      pr1646v2XEfmVlanOutPQsH2PerformanceEirTxPkts
         Counter64,
      pr1646v2XEfmVlanOutPQsH2PerformanceViolTxPkts
         Counter64,
      pr1646v2XEfmVlanOutPQsH2PerformanceTotOcts
         Counter64,
      pr1646v2XEfmVlanOutPQsH2PerformanceDirTxOcts
         Counter64,
      pr1646v2XEfmVlanOutPQsH2PerformanceQdOcts
         Counter64,
      pr1646v2XEfmVlanOutPQsH2PerformanceDropOcts
         Counter64,
      pr1646v2XEfmVlanOutPQsH2PerformanceRDropOcts
         Counter64,
      pr1646v2XEfmVlanOutPQsH2PerformanceCirTxOcts
         Counter64,
      pr1646v2XEfmVlanOutPQsH2PerformanceEirTxOcts
         Counter64,
      pr1646v2XEfmVlanOutPQsH2PerformanceViolTxOcts
         Counter64,
      pr1646v2XEfmVlanOutPQsH2PerformanceBandwidth
         Integer32
      }

pr1646v2XEfmVlanOutPQsH2PerformanceTableIx OBJECT-TYPE
   SYNTAX      TableIndex
   MAX-ACCESS  not-accessible
   STATUS      current
   DESCRIPTION
      ""
   ::= {pr1646v2XEfmVlanOutPQsH2PerformanceEntry 11}

pr1646v2XEfmVlanOutPQsH2PerformanceSysUpTime OBJECT-TYPE
   SYNTAX      TimeTicks
   MAX-ACCESS  read-only
   STATUS      current
   DESCRIPTION
      "Path: efm.performance.vlan.outPriorityQueues.h2Performance.sysUpTime

       Time in centi-second."
   ::= {pr1646v2XEfmVlanOutPQsH2PerformanceEntry 16777216}

pr1646v2XEfmVlanOutPQsH2PerformanceTotPkts OBJECT-TYPE
   SYNTAX      Counter64
   MAX-ACCESS  read-only
   STATUS      current
   DESCRIPTION
      "Path: efm.performance.vlan.outPriorityQueues.h2Performance.totalPkts

       64 bit unsigned wrappable counter."
   ::= {pr1646v2XEfmVlanOutPQsH2PerformanceEntry 234881024}

pr1646v2XEfmVlanOutPQsH2PerformanceDirTxPkts OBJECT-TYPE
   SYNTAX      Counter64
   MAX-ACCESS  read-only
   STATUS      current
   DESCRIPTION
      "Path: efm.performance.vlan.outPriorityQueues.h2Performance.directTxPkts

       64 bit unsigned wrappable counter."
   ::= {pr1646v2XEfmVlanOutPQsH2PerformanceEntry 33554432}

pr1646v2XEfmVlanOutPQsH2PerformanceQdPkts OBJECT-TYPE
   SYNTAX      Counter64
   MAX-ACCESS  read-only
   STATUS      current
   DESCRIPTION
      "Path: efm.performance.vlan.outPriorityQueues.h2Performance.queuedPkts

       64 bit unsigned wrappable counter."
   ::= {pr1646v2XEfmVlanOutPQsH2PerformanceEntry 50331648}

pr1646v2XEfmVlanOutPQsH2PerformanceDropPkts OBJECT-TYPE
   SYNTAX      Counter64
   MAX-ACCESS  read-only
   STATUS      current
   DESCRIPTION
      "Path: efm.performance.vlan.outPriorityQueues.h2Performance.droppedPkts

       64 bit unsigned wrappable counter."
   ::= {pr1646v2XEfmVlanOutPQsH2PerformanceEntry 67108864}

pr1646v2XEfmVlanOutPQsH2PerformanceRDropPkts OBJECT-TYPE
   SYNTAX      Counter64
   MAX-ACCESS  read-only
   STATUS      current
   DESCRIPTION
      "Path: efm.performance.vlan.outPriorityQueues.h2Performance.redDroppedPkts

       64 bit unsigned wrappable counter."
   ::= {pr1646v2XEfmVlanOutPQsH2PerformanceEntry 201326592}

pr1646v2XEfmVlanOutPQsH2PerformanceCirTxPkts OBJECT-TYPE
   SYNTAX      Counter64
   MAX-ACCESS  read-only
   STATUS      current
   DESCRIPTION
      "Path: efm.performance.vlan.outPriorityQueues.h2Performance.cirTxPkts

       64 bit unsigned wrappable counter."
   ::= {pr1646v2XEfmVlanOutPQsH2PerformanceEntry 83886080}

pr1646v2XEfmVlanOutPQsH2PerformanceEirTxPkts OBJECT-TYPE
   SYNTAX      Counter64
   MAX-ACCESS  read-only
   STATUS      current
   DESCRIPTION
      "Path: efm.performance.vlan.outPriorityQueues.h2Performance.eirTxPkts

       64 bit unsigned wrappable counter."
   ::= {pr1646v2XEfmVlanOutPQsH2PerformanceEntry 100663296}

pr1646v2XEfmVlanOutPQsH2PerformanceViolTxPkts OBJECT-TYPE
   SYNTAX      Counter64
   MAX-ACCESS  read-only
   STATUS      current
   DESCRIPTION
      "Path: efm.performance.vlan.outPriorityQueues.h2Performance.violateTxPkts

       64 bit unsigned wrappable counter."
   ::= {pr1646v2XEfmVlanOutPQsH2PerformanceEntry 301989888}

pr1646v2XEfmVlanOutPQsH2PerformanceTotOcts OBJECT-TYPE
   SYNTAX      Counter64
   MAX-ACCESS  read-only
   STATUS      current
   DESCRIPTION
      "Path: efm.performance.vlan.outPriorityQueues.h2Performance.totalOctets

       64 bit unsigned wrappable counter."
   ::= {pr1646v2XEfmVlanOutPQsH2PerformanceEntry 251658240}

pr1646v2XEfmVlanOutPQsH2PerformanceDirTxOcts OBJECT-TYPE
   SYNTAX      Counter64
   MAX-ACCESS  read-only
   STATUS      current
   DESCRIPTION
      "Path: efm.performance.vlan.outPriorityQueues.h2Performance.directTxOctets

       64 bit unsigned wrappable counter."
   ::= {pr1646v2XEfmVlanOutPQsH2PerformanceEntry 117440512}

pr1646v2XEfmVlanOutPQsH2PerformanceQdOcts OBJECT-TYPE
   SYNTAX      Counter64
   MAX-ACCESS  read-only
   STATUS      current
   DESCRIPTION
      "Path: efm.performance.vlan.outPriorityQueues.h2Performance.queuedOctets

       64 bit unsigned wrappable counter."
   ::= {pr1646v2XEfmVlanOutPQsH2PerformanceEntry 134217728}

pr1646v2XEfmVlanOutPQsH2PerformanceDropOcts OBJECT-TYPE
   SYNTAX      Counter64
   MAX-ACCESS  read-only
   STATUS      current
   DESCRIPTION
      "Path: efm.performance.vlan.outPriorityQueues.h2Performance.droppedOctets

       64 bit unsigned wrappable counter."
   ::= {pr1646v2XEfmVlanOutPQsH2PerformanceEntry 150994944}

pr1646v2XEfmVlanOutPQsH2PerformanceRDropOcts OBJECT-TYPE
   SYNTAX      Counter64
   MAX-ACCESS  read-only
   STATUS      current
   DESCRIPTION
      "Path: efm.performance.vlan.outPriorityQueues.h2Performance.redDroppedOctets

       64 bit unsigned wrappable counter."
   ::= {pr1646v2XEfmVlanOutPQsH2PerformanceEntry 218103808}

pr1646v2XEfmVlanOutPQsH2PerformanceCirTxOcts OBJECT-TYPE
   SYNTAX      Counter64
   MAX-ACCESS  read-only
   STATUS      current
   DESCRIPTION
      "Path: efm.performance.vlan.outPriorityQueues.h2Performance.cirTxOctets

       64 bit unsigned wrappable counter."
   ::= {pr1646v2XEfmVlanOutPQsH2PerformanceEntry 167772160}

pr1646v2XEfmVlanOutPQsH2PerformanceEirTxOcts OBJECT-TYPE
   SYNTAX      Counter64
   MAX-ACCESS  read-only
   STATUS      current
   DESCRIPTION
      "Path: efm.performance.vlan.outPriorityQueues.h2Performance.eirTxOctets

       64 bit unsigned wrappable counter."
   ::= {pr1646v2XEfmVlanOutPQsH2PerformanceEntry 184549376}

pr1646v2XEfmVlanOutPQsH2PerformanceViolTxOcts OBJECT-TYPE
   SYNTAX      Counter64
   MAX-ACCESS  read-only
   STATUS      current
   DESCRIPTION
      "Path: efm.performance.vlan.outPriorityQueues.h2Performance.violateTxOctets

       64 bit unsigned wrappable counter."
   ::= {pr1646v2XEfmVlanOutPQsH2PerformanceEntry 318767104}

pr1646v2XEfmVlanOutPQsH2PerformanceBandwidth OBJECT-TYPE
   SYNTAX      Integer32
   MAX-ACCESS  read-only
   STATUS      current
   DESCRIPTION
      "Path: efm.performance.vlan.outPriorityQueues.h2Performance.bandwidth

       unit name = bps
       formula = 8 * ; 8 /"
   ::= {pr1646v2XEfmVlanOutPQsH2PerformanceEntry 268435456}

pr1646v2XEfmVlanOutPQsH24Performance OBJECT-TYPE
   SYNTAX      SEQUENCE OF Pr1646v2XEfmVlanOutPQsH24PerformanceEntry
   MAX-ACCESS  not-accessible
   STATUS      current
   DESCRIPTION
      ""
   ::= {pr1646v2XEfmVlan 84279296}

pr1646v2XEfmVlanOutPQsH24PerformanceEntry OBJECT-TYPE
   SYNTAX      Pr1646v2XEfmVlanOutPQsH24PerformanceEntry
   MAX-ACCESS  not-accessible
   STATUS      current
   DESCRIPTION
      ""
   INDEX      { pr1646v2XEfmVlanTableIx,
                pr1646v2XEfmVlanOutPQsTableIx,
                pr1646v2XEfmVlanOutPQsH24PerformanceTableIx }
   ::= {pr1646v2XEfmVlanOutPQsH24Performance 1}

Pr1646v2XEfmVlanOutPQsH24PerformanceEntry ::=
   SEQUENCE
      {
      pr1646v2XEfmVlanOutPQsH24PerformanceTableIx
         TableIndex,
      pr1646v2XEfmVlanOutPQsH24PerformanceSysUpTime
         TimeTicks,
      pr1646v2XEfmVlanOutPQsH24PerformanceTotPkts
         Counter64,
      pr1646v2XEfmVlanOutPQsH24PerformanceDirTxPkts
         Counter64,
      pr1646v2XEfmVlanOutPQsH24PerformanceQdPkts
         Counter64,
      pr1646v2XEfmVlanOutPQsH24PerformanceDropPkts
         Counter64,
      pr1646v2XEfmVlanOutPQsH24PerformanceRDropPkts
         Counter64,
      pr1646v2XEfmVlanOutPQsH24PerformanceCirTxPkts
         Counter64,
      pr1646v2XEfmVlanOutPQsH24PerformanceEirTxPkts
         Counter64,
      pr1646v2XEfmVlanOutPQsH24PerformanceViolTxPkts
         Counter64,
      pr1646v2XEfmVlanOutPQsH24PerformanceTotOcts
         Counter64,
      pr1646v2XEfmVlanOutPQsH24PerformanceDirTxOcts
         Counter64,
      pr1646v2XEfmVlanOutPQsH24PerformanceQdOcts
         Counter64,
      pr1646v2XEfmVlanOutPQsH24PerformanceDropOcts
         Counter64,
      pr1646v2XEfmVlanOutPQsH24PerformanceRDropOcts
         Counter64,
      pr1646v2XEfmVlanOutPQsH24PerformanceCirTxOcts
         Counter64,
      pr1646v2XEfmVlanOutPQsH24PerformanceEirTxOcts
         Counter64,
      pr1646v2XEfmVlanOutPQsH24PerformanceViolTxOcts
         Counter64,
      pr1646v2XEfmVlanOutPQsH24PerformanceBandwidth
         Integer32
      }

pr1646v2XEfmVlanOutPQsH24PerformanceTableIx OBJECT-TYPE
   SYNTAX      TableIndex
   MAX-ACCESS  not-accessible
   STATUS      current
   DESCRIPTION
      ""
   ::= {pr1646v2XEfmVlanOutPQsH24PerformanceEntry 11}

pr1646v2XEfmVlanOutPQsH24PerformanceSysUpTime OBJECT-TYPE
   SYNTAX      TimeTicks
   MAX-ACCESS  read-only
   STATUS      current
   DESCRIPTION
      "Path: efm.performance.vlan.outPriorityQueues.h24Performance.sysUpTime

       Time in centi-second."
   ::= {pr1646v2XEfmVlanOutPQsH24PerformanceEntry 16777216}

pr1646v2XEfmVlanOutPQsH24PerformanceTotPkts OBJECT-TYPE
   SYNTAX      Counter64
   MAX-ACCESS  read-only
   STATUS      current
   DESCRIPTION
      "Path: efm.performance.vlan.outPriorityQueues.h24Performance.totalPkts

       64 bit unsigned wrappable counter."
   ::= {pr1646v2XEfmVlanOutPQsH24PerformanceEntry 234881024}

pr1646v2XEfmVlanOutPQsH24PerformanceDirTxPkts OBJECT-TYPE
   SYNTAX      Counter64
   MAX-ACCESS  read-only
   STATUS      current
   DESCRIPTION
      "Path: efm.performance.vlan.outPriorityQueues.h24Performance.directTxPkts

       64 bit unsigned wrappable counter."
   ::= {pr1646v2XEfmVlanOutPQsH24PerformanceEntry 33554432}

pr1646v2XEfmVlanOutPQsH24PerformanceQdPkts OBJECT-TYPE
   SYNTAX      Counter64
   MAX-ACCESS  read-only
   STATUS      current
   DESCRIPTION
      "Path: efm.performance.vlan.outPriorityQueues.h24Performance.queuedPkts

       64 bit unsigned wrappable counter."
   ::= {pr1646v2XEfmVlanOutPQsH24PerformanceEntry 50331648}

pr1646v2XEfmVlanOutPQsH24PerformanceDropPkts OBJECT-TYPE
   SYNTAX      Counter64
   MAX-ACCESS  read-only
   STATUS      current
   DESCRIPTION
      "Path: efm.performance.vlan.outPriorityQueues.h24Performance.droppedPkts

       64 bit unsigned wrappable counter."
   ::= {pr1646v2XEfmVlanOutPQsH24PerformanceEntry 67108864}

pr1646v2XEfmVlanOutPQsH24PerformanceRDropPkts OBJECT-TYPE
   SYNTAX      Counter64
   MAX-ACCESS  read-only
   STATUS      current
   DESCRIPTION
      "Path: efm.performance.vlan.outPriorityQueues.h24Performance.redDroppedPkts

       64 bit unsigned wrappable counter."
   ::= {pr1646v2XEfmVlanOutPQsH24PerformanceEntry 201326592}

pr1646v2XEfmVlanOutPQsH24PerformanceCirTxPkts OBJECT-TYPE
   SYNTAX      Counter64
   MAX-ACCESS  read-only
   STATUS      current
   DESCRIPTION
      "Path: efm.performance.vlan.outPriorityQueues.h24Performance.cirTxPkts

       64 bit unsigned wrappable counter."
   ::= {pr1646v2XEfmVlanOutPQsH24PerformanceEntry 83886080}

pr1646v2XEfmVlanOutPQsH24PerformanceEirTxPkts OBJECT-TYPE
   SYNTAX      Counter64
   MAX-ACCESS  read-only
   STATUS      current
   DESCRIPTION
      "Path: efm.performance.vlan.outPriorityQueues.h24Performance.eirTxPkts

       64 bit unsigned wrappable counter."
   ::= {pr1646v2XEfmVlanOutPQsH24PerformanceEntry 100663296}

pr1646v2XEfmVlanOutPQsH24PerformanceViolTxPkts OBJECT-TYPE
   SYNTAX      Counter64
   MAX-ACCESS  read-only
   STATUS      current
   DESCRIPTION
      "Path: efm.performance.vlan.outPriorityQueues.h24Performance.violateTxPkts

       64 bit unsigned wrappable counter."
   ::= {pr1646v2XEfmVlanOutPQsH24PerformanceEntry 301989888}

pr1646v2XEfmVlanOutPQsH24PerformanceTotOcts OBJECT-TYPE
   SYNTAX      Counter64
   MAX-ACCESS  read-only
   STATUS      current
   DESCRIPTION
      "Path: efm.performance.vlan.outPriorityQueues.h24Performance.totalOctets

       64 bit unsigned wrappable counter."
   ::= {pr1646v2XEfmVlanOutPQsH24PerformanceEntry 251658240}

pr1646v2XEfmVlanOutPQsH24PerformanceDirTxOcts OBJECT-TYPE
   SYNTAX      Counter64
   MAX-ACCESS  read-only
   STATUS      current
   DESCRIPTION
      "Path: efm.performance.vlan.outPriorityQueues.h24Performance.directTxOctets

       64 bit unsigned wrappable counter."
   ::= {pr1646v2XEfmVlanOutPQsH24PerformanceEntry 117440512}

pr1646v2XEfmVlanOutPQsH24PerformanceQdOcts OBJECT-TYPE
   SYNTAX      Counter64
   MAX-ACCESS  read-only
   STATUS      current
   DESCRIPTION
      "Path: efm.performance.vlan.outPriorityQueues.h24Performance.queuedOctets

       64 bit unsigned wrappable counter."
   ::= {pr1646v2XEfmVlanOutPQsH24PerformanceEntry 134217728}

pr1646v2XEfmVlanOutPQsH24PerformanceDropOcts OBJECT-TYPE
   SYNTAX      Counter64
   MAX-ACCESS  read-only
   STATUS      current
   DESCRIPTION
      "Path: efm.performance.vlan.outPriorityQueues.h24Performance.droppedOctets

       64 bit unsigned wrappable counter."
   ::= {pr1646v2XEfmVlanOutPQsH24PerformanceEntry 150994944}

pr1646v2XEfmVlanOutPQsH24PerformanceRDropOcts OBJECT-TYPE
   SYNTAX      Counter64
   MAX-ACCESS  read-only
   STATUS      current
   DESCRIPTION
      "Path: efm.performance.vlan.outPriorityQueues.h24Performance.redDroppedOctets

       64 bit unsigned wrappable counter."
   ::= {pr1646v2XEfmVlanOutPQsH24PerformanceEntry 218103808}

pr1646v2XEfmVlanOutPQsH24PerformanceCirTxOcts OBJECT-TYPE
   SYNTAX      Counter64
   MAX-ACCESS  read-only
   STATUS      current
   DESCRIPTION
      "Path: efm.performance.vlan.outPriorityQueues.h24Performance.cirTxOctets

       64 bit unsigned wrappable counter."
   ::= {pr1646v2XEfmVlanOutPQsH24PerformanceEntry 167772160}

pr1646v2XEfmVlanOutPQsH24PerformanceEirTxOcts OBJECT-TYPE
   SYNTAX      Counter64
   MAX-ACCESS  read-only
   STATUS      current
   DESCRIPTION
      "Path: efm.performance.vlan.outPriorityQueues.h24Performance.eirTxOctets

       64 bit unsigned wrappable counter."
   ::= {pr1646v2XEfmVlanOutPQsH24PerformanceEntry 184549376}

pr1646v2XEfmVlanOutPQsH24PerformanceViolTxOcts OBJECT-TYPE
   SYNTAX      Counter64
   MAX-ACCESS  read-only
   STATUS      current
   DESCRIPTION
      "Path: efm.performance.vlan.outPriorityQueues.h24Performance.violateTxOctets

       64 bit unsigned wrappable counter."
   ::= {pr1646v2XEfmVlanOutPQsH24PerformanceEntry 318767104}

pr1646v2XEfmVlanOutPQsH24PerformanceBandwidth OBJECT-TYPE
   SYNTAX      Integer32
   MAX-ACCESS  read-only
   STATUS      current
   DESCRIPTION
      "Path: efm.performance.vlan.outPriorityQueues.h24Performance.bandwidth

       unit name = bps
       formula = 8 * ; 8 /"
   ::= {pr1646v2XEfmVlanOutPQsH24PerformanceEntry 268435456}

pr1646v2XEfmVlanOutPQsD7Performance OBJECT-TYPE
   SYNTAX      SEQUENCE OF Pr1646v2XEfmVlanOutPQsD7PerformanceEntry
   MAX-ACCESS  not-accessible
   STATUS      current
   DESCRIPTION
      ""
   ::= {pr1646v2XEfmVlan 84344832}

pr1646v2XEfmVlanOutPQsD7PerformanceEntry OBJECT-TYPE
   SYNTAX      Pr1646v2XEfmVlanOutPQsD7PerformanceEntry
   MAX-ACCESS  not-accessible
   STATUS      current
   DESCRIPTION
      ""
   INDEX      { pr1646v2XEfmVlanTableIx,
                pr1646v2XEfmVlanOutPQsTableIx,
                pr1646v2XEfmVlanOutPQsD7PerformanceTableIx }
   ::= {pr1646v2XEfmVlanOutPQsD7Performance 1}

Pr1646v2XEfmVlanOutPQsD7PerformanceEntry ::=
   SEQUENCE
      {
      pr1646v2XEfmVlanOutPQsD7PerformanceTableIx
         TableIndex,
      pr1646v2XEfmVlanOutPQsD7PerformanceSysUpTime
         TimeTicks,
      pr1646v2XEfmVlanOutPQsD7PerformanceTotPkts
         Counter64,
      pr1646v2XEfmVlanOutPQsD7PerformanceDirTxPkts
         Counter64,
      pr1646v2XEfmVlanOutPQsD7PerformanceQdPkts
         Counter64,
      pr1646v2XEfmVlanOutPQsD7PerformanceDropPkts
         Counter64,
      pr1646v2XEfmVlanOutPQsD7PerformanceRDropPkts
         Counter64,
      pr1646v2XEfmVlanOutPQsD7PerformanceCirTxPkts
         Counter64,
      pr1646v2XEfmVlanOutPQsD7PerformanceEirTxPkts
         Counter64,
      pr1646v2XEfmVlanOutPQsD7PerformanceViolTxPkts
         Counter64,
      pr1646v2XEfmVlanOutPQsD7PerformanceTotOcts
         Counter64,
      pr1646v2XEfmVlanOutPQsD7PerformanceDirTxOcts
         Counter64,
      pr1646v2XEfmVlanOutPQsD7PerformanceQdOcts
         Counter64,
      pr1646v2XEfmVlanOutPQsD7PerformanceDropOcts
         Counter64,
      pr1646v2XEfmVlanOutPQsD7PerformanceRDropOcts
         Counter64,
      pr1646v2XEfmVlanOutPQsD7PerformanceCirTxOcts
         Counter64,
      pr1646v2XEfmVlanOutPQsD7PerformanceEirTxOcts
         Counter64,
      pr1646v2XEfmVlanOutPQsD7PerformanceViolTxOcts
         Counter64,
      pr1646v2XEfmVlanOutPQsD7PerformanceBandwidth
         Integer32
      }

pr1646v2XEfmVlanOutPQsD7PerformanceTableIx OBJECT-TYPE
   SYNTAX      TableIndex
   MAX-ACCESS  not-accessible
   STATUS      current
   DESCRIPTION
      ""
   ::= {pr1646v2XEfmVlanOutPQsD7PerformanceEntry 11}

pr1646v2XEfmVlanOutPQsD7PerformanceSysUpTime OBJECT-TYPE
   SYNTAX      TimeTicks
   MAX-ACCESS  read-only
   STATUS      current
   DESCRIPTION
      "Path: efm.performance.vlan.outPriorityQueues.d7Performance.sysUpTime

       Time in centi-second."
   ::= {pr1646v2XEfmVlanOutPQsD7PerformanceEntry 16777216}

pr1646v2XEfmVlanOutPQsD7PerformanceTotPkts OBJECT-TYPE
   SYNTAX      Counter64
   MAX-ACCESS  read-only
   STATUS      current
   DESCRIPTION
      "Path: efm.performance.vlan.outPriorityQueues.d7Performance.totalPkts

       64 bit unsigned wrappable counter."
   ::= {pr1646v2XEfmVlanOutPQsD7PerformanceEntry 234881024}

pr1646v2XEfmVlanOutPQsD7PerformanceDirTxPkts OBJECT-TYPE
   SYNTAX      Counter64
   MAX-ACCESS  read-only
   STATUS      current
   DESCRIPTION
      "Path: efm.performance.vlan.outPriorityQueues.d7Performance.directTxPkts

       64 bit unsigned wrappable counter."
   ::= {pr1646v2XEfmVlanOutPQsD7PerformanceEntry 33554432}

pr1646v2XEfmVlanOutPQsD7PerformanceQdPkts OBJECT-TYPE
   SYNTAX      Counter64
   MAX-ACCESS  read-only
   STATUS      current
   DESCRIPTION
      "Path: efm.performance.vlan.outPriorityQueues.d7Performance.queuedPkts

       64 bit unsigned wrappable counter."
   ::= {pr1646v2XEfmVlanOutPQsD7PerformanceEntry 50331648}

pr1646v2XEfmVlanOutPQsD7PerformanceDropPkts OBJECT-TYPE
   SYNTAX      Counter64
   MAX-ACCESS  read-only
   STATUS      current
   DESCRIPTION
      "Path: efm.performance.vlan.outPriorityQueues.d7Performance.droppedPkts

       64 bit unsigned wrappable counter."
   ::= {pr1646v2XEfmVlanOutPQsD7PerformanceEntry 67108864}

pr1646v2XEfmVlanOutPQsD7PerformanceRDropPkts OBJECT-TYPE
   SYNTAX      Counter64
   MAX-ACCESS  read-only
   STATUS      current
   DESCRIPTION
      "Path: efm.performance.vlan.outPriorityQueues.d7Performance.redDroppedPkts

       64 bit unsigned wrappable counter."
   ::= {pr1646v2XEfmVlanOutPQsD7PerformanceEntry 201326592}

pr1646v2XEfmVlanOutPQsD7PerformanceCirTxPkts OBJECT-TYPE
   SYNTAX      Counter64
   MAX-ACCESS  read-only
   STATUS      current
   DESCRIPTION
      "Path: efm.performance.vlan.outPriorityQueues.d7Performance.cirTxPkts

       64 bit unsigned wrappable counter."
   ::= {pr1646v2XEfmVlanOutPQsD7PerformanceEntry 83886080}

pr1646v2XEfmVlanOutPQsD7PerformanceEirTxPkts OBJECT-TYPE
   SYNTAX      Counter64
   MAX-ACCESS  read-only
   STATUS      current
   DESCRIPTION
      "Path: efm.performance.vlan.outPriorityQueues.d7Performance.eirTxPkts

       64 bit unsigned wrappable counter."
   ::= {pr1646v2XEfmVlanOutPQsD7PerformanceEntry 100663296}

pr1646v2XEfmVlanOutPQsD7PerformanceViolTxPkts OBJECT-TYPE
   SYNTAX      Counter64
   MAX-ACCESS  read-only
   STATUS      current
   DESCRIPTION
      "Path: efm.performance.vlan.outPriorityQueues.d7Performance.violateTxPkts

       64 bit unsigned wrappable counter."
   ::= {pr1646v2XEfmVlanOutPQsD7PerformanceEntry 301989888}

pr1646v2XEfmVlanOutPQsD7PerformanceTotOcts OBJECT-TYPE
   SYNTAX      Counter64
   MAX-ACCESS  read-only
   STATUS      current
   DESCRIPTION
      "Path: efm.performance.vlan.outPriorityQueues.d7Performance.totalOctets

       64 bit unsigned wrappable counter."
   ::= {pr1646v2XEfmVlanOutPQsD7PerformanceEntry 251658240}

pr1646v2XEfmVlanOutPQsD7PerformanceDirTxOcts OBJECT-TYPE
   SYNTAX      Counter64
   MAX-ACCESS  read-only
   STATUS      current
   DESCRIPTION
      "Path: efm.performance.vlan.outPriorityQueues.d7Performance.directTxOctets

       64 bit unsigned wrappable counter."
   ::= {pr1646v2XEfmVlanOutPQsD7PerformanceEntry 117440512}

pr1646v2XEfmVlanOutPQsD7PerformanceQdOcts OBJECT-TYPE
   SYNTAX      Counter64
   MAX-ACCESS  read-only
   STATUS      current
   DESCRIPTION
      "Path: efm.performance.vlan.outPriorityQueues.d7Performance.queuedOctets

       64 bit unsigned wrappable counter."
   ::= {pr1646v2XEfmVlanOutPQsD7PerformanceEntry 134217728}

pr1646v2XEfmVlanOutPQsD7PerformanceDropOcts OBJECT-TYPE
   SYNTAX      Counter64
   MAX-ACCESS  read-only
   STATUS      current
   DESCRIPTION
      "Path: efm.performance.vlan.outPriorityQueues.d7Performance.droppedOctets

       64 bit unsigned wrappable counter."
   ::= {pr1646v2XEfmVlanOutPQsD7PerformanceEntry 150994944}

pr1646v2XEfmVlanOutPQsD7PerformanceRDropOcts OBJECT-TYPE
   SYNTAX      Counter64
   MAX-ACCESS  read-only
   STATUS      current
   DESCRIPTION
      "Path: efm.performance.vlan.outPriorityQueues.d7Performance.redDroppedOctets

       64 bit unsigned wrappable counter."
   ::= {pr1646v2XEfmVlanOutPQsD7PerformanceEntry 218103808}

pr1646v2XEfmVlanOutPQsD7PerformanceCirTxOcts OBJECT-TYPE
   SYNTAX      Counter64
   MAX-ACCESS  read-only
   STATUS      current
   DESCRIPTION
      "Path: efm.performance.vlan.outPriorityQueues.d7Performance.cirTxOctets

       64 bit unsigned wrappable counter."
   ::= {pr1646v2XEfmVlanOutPQsD7PerformanceEntry 167772160}

pr1646v2XEfmVlanOutPQsD7PerformanceEirTxOcts OBJECT-TYPE
   SYNTAX      Counter64
   MAX-ACCESS  read-only
   STATUS      current
   DESCRIPTION
      "Path: efm.performance.vlan.outPriorityQueues.d7Performance.eirTxOctets

       64 bit unsigned wrappable counter."
   ::= {pr1646v2XEfmVlanOutPQsD7PerformanceEntry 184549376}

pr1646v2XEfmVlanOutPQsD7PerformanceViolTxOcts OBJECT-TYPE
   SYNTAX      Counter64
   MAX-ACCESS  read-only
   STATUS      current
   DESCRIPTION
      "Path: efm.performance.vlan.outPriorityQueues.d7Performance.violateTxOctets

       64 bit unsigned wrappable counter."
   ::= {pr1646v2XEfmVlanOutPQsD7PerformanceEntry 318767104}

pr1646v2XEfmVlanOutPQsD7PerformanceBandwidth OBJECT-TYPE
   SYNTAX      Integer32
   MAX-ACCESS  read-only
   STATUS      current
   DESCRIPTION
      "Path: efm.performance.vlan.outPriorityQueues.d7Performance.bandwidth

       unit name = bps
       formula = 8 * ; 8 /"
   ::= {pr1646v2XEfmVlanOutPQsD7PerformanceEntry 268435456}


pr1646v2XEfmPPPoE OBJECT IDENTIFIER ::= {pr1646v2XEfm 53}

pr1646v2XEfmPPPoESSCTable OBJECT-TYPE
   SYNTAX      SEQUENCE OF Pr1646v2XEfmPPPoEEntry
   MAX-ACCESS  not-accessible
   STATUS      current
   DESCRIPTION
      ""
   ::= {pr1646v2XEfmPPPoE 1}

pr1646v2XEfmPPPoEEntry OBJECT-TYPE
   SYNTAX      Pr1646v2XEfmPPPoEEntry
   MAX-ACCESS  not-accessible
   STATUS      current
   DESCRIPTION
      ""
   INDEX      { pr1646v2XEfmPPPoETableIx }
   ::= {pr1646v2XEfmPPPoESSCTable 1}

Pr1646v2XEfmPPPoEEntry ::=
   SEQUENCE
      {
      pr1646v2XEfmPPPoETableIx
         TableIndex,
      pr1646v2XEfmPPPoEName
         DisplayString,
      pr1646v2XEfmPPPoEMCInOctets
         Counter64,
      pr1646v2XEfmPPPoEMCInUcast
         Counter64,
      pr1646v2XEfmPPPoEMCInNUcastPkts
         Counter64,
      pr1646v2XEfmPPPoEMCInBcastPkts
         Counter64,
      pr1646v2XEfmPPPoEMCInMcastPkts
         Counter64,
      pr1646v2XEfmPPPoEMCInDiscards
         Counter64,
      pr1646v2XEfmPPPoEMCInErrors
         Counter64,
      pr1646v2XEfmPPPoEMCInUnknownProtos
         Counter64,
      pr1646v2XEfmPPPoEMCInDropEx
         Counter64,
      pr1646v2XEfmPPPoEMCInDropNoMac
         Counter64,
      pr1646v2XEfmPPPoEMCInDropNUCast
         Counter64,
      pr1646v2XEfmPPPoEMCInDropFilter
         Counter64,
      pr1646v2XEfmPPPoEMCInBandwidth15sec
         Integer32,
      pr1646v2XEfmPPPoEMCInBandwidth30sec
         Integer32,
      pr1646v2XEfmPPPoEMCInBandwidth1min
         Integer32,
      pr1646v2XEfmPPPoEMCInBandwidth2min
         Integer32,
      pr1646v2XEfmPPPoEMCInBandwidth5min
         Integer32,
      pr1646v2XEfmPPPoEMCOutOctets
         Counter64,
      pr1646v2XEfmPPPoEMCOutUcastPkts
         Counter64,
      pr1646v2XEfmPPPoEMCOutNUcastPkts
         Counter64,
      pr1646v2XEfmPPPoEMCOutBcastPkts
         Counter64,
      pr1646v2XEfmPPPoEMCOutMcastPkts
         Counter64,
      pr1646v2XEfmPPPoEMCOutDiscards
         Counter64,
      pr1646v2XEfmPPPoEMCOutErrors
         Counter64,
      pr1646v2XEfmPPPoEMCOutQLen
         Counter32,
      pr1646v2XEfmPPPoEMCOutDropEx
         Counter64,
      pr1646v2XEfmPPPoEMCOutDropNoArp
         Counter64,
      pr1646v2XEfmPPPoEMCOutDropFilter
         Counter64,
      pr1646v2XEfmPPPoEMCOutBandwidth15sec
         Integer32,
      pr1646v2XEfmPPPoEMCOutBandwidth30sec
         Integer32,
      pr1646v2XEfmPPPoEMCOutBandwidth1min
         Integer32,
      pr1646v2XEfmPPPoEMCOutBandwidth2min
         Integer32,
      pr1646v2XEfmPPPoEMCOutBandwidth5min
         Integer32,
      pr1646v2XEfmPPPoEPppLinkMonitoringRequestsSent
         Gauge32,
      pr1646v2XEfmPPPoEPppLinkMonitoringRepliesRcvd
         Gauge32,
      pr1646v2XEfmPPPoEPppLinkMonitoringRequestsRcvd
         Gauge32,
      pr1646v2XEfmPPPoEPppLinkMonitoringRepliesSent
         Gauge32
      }

pr1646v2XEfmPPPoETableIx OBJECT-TYPE
   SYNTAX      TableIndex
   MAX-ACCESS  not-accessible
   STATUS      current
   DESCRIPTION
      ""
   ::= {pr1646v2XEfmPPPoEEntry 11}

pr1646v2XEfmPPPoEName OBJECT-TYPE
   SYNTAX      DisplayString
   MAX-ACCESS  read-only
   STATUS      current
   DESCRIPTION
      "Path: efm.performance.pppoEClient.name"
   ::= {pr1646v2XEfmPPPoEEntry 16777216}

pr1646v2XEfmPPPoEMCInOctets OBJECT-TYPE
   SYNTAX      Counter64
   MAX-ACCESS  read-only
   STATUS      current
   DESCRIPTION
      "Path: efm.performance.pppoEClient.mibCounters.ifInOctets

       64 bit unsigned wrappable counter."
   ::= {pr1646v2XEfmPPPoEEntry 40697856}

pr1646v2XEfmPPPoEMCInUcast OBJECT-TYPE
   SYNTAX      Counter64
   MAX-ACCESS  read-only
   STATUS      current
   DESCRIPTION
      "Path: efm.performance.pppoEClient.mibCounters.ifInUcastPkts

       64 bit unsigned wrappable counter."
   ::= {pr1646v2XEfmPPPoEEntry 40763392}

pr1646v2XEfmPPPoEMCInNUcastPkts OBJECT-TYPE
   SYNTAX      Counter64
   MAX-ACCESS  read-only
   STATUS      current
   DESCRIPTION
      "Path: efm.performance.pppoEClient.mibCounters.ifInNUcastPkts

       64 bit unsigned wrappable counter."
   ::= {pr1646v2XEfmPPPoEEntry 40828928}

pr1646v2XEfmPPPoEMCInBcastPkts OBJECT-TYPE
   SYNTAX      Counter64
   MAX-ACCESS  read-only
   STATUS      current
   DESCRIPTION
      "Path: efm.performance.pppoEClient.mibCounters.ifInBcastPkts

       64 bit unsigned wrappable counter."
   ::= {pr1646v2XEfmPPPoEEntry 47382528}

pr1646v2XEfmPPPoEMCInMcastPkts OBJECT-TYPE
   SYNTAX      Counter64
   MAX-ACCESS  read-only
   STATUS      current
   DESCRIPTION
      "Path: efm.performance.pppoEClient.mibCounters.ifInMcastPkts

       64 bit unsigned wrappable counter."
   ::= {pr1646v2XEfmPPPoEEntry 48037888}

pr1646v2XEfmPPPoEMCInDiscards OBJECT-TYPE
   SYNTAX      Counter64
   MAX-ACCESS  read-only
   STATUS      current
   DESCRIPTION
      "Path: efm.performance.pppoEClient.mibCounters.ifInDiscards

       64 bit unsigned wrappable counter."
   ::= {pr1646v2XEfmPPPoEEntry 40894464}

pr1646v2XEfmPPPoEMCInErrors OBJECT-TYPE
   SYNTAX      Counter64
   MAX-ACCESS  read-only
   STATUS      current
   DESCRIPTION
      "Path: efm.performance.pppoEClient.mibCounters.ifInErrors

       64 bit unsigned wrappable counter."
   ::= {pr1646v2XEfmPPPoEEntry 40960000}

pr1646v2XEfmPPPoEMCInUnknownProtos OBJECT-TYPE
   SYNTAX      Counter64
   MAX-ACCESS  read-only
   STATUS      current
   DESCRIPTION
      "Path: efm.performance.pppoEClient.mibCounters.ifInUnknownProtos

       64 bit unsigned wrappable counter."
   ::= {pr1646v2XEfmPPPoEEntry 41025536}

pr1646v2XEfmPPPoEMCInDropEx OBJECT-TYPE
   SYNTAX      Counter64
   MAX-ACCESS  read-only
   STATUS      current
   DESCRIPTION
      "Path: efm.performance.pppoEClient.mibCounters.ifInDropLevelExceeded

       64 bit unsigned wrappable counter."
   ::= {pr1646v2XEfmPPPoEEntry 42074112}

pr1646v2XEfmPPPoEMCInDropNoMac OBJECT-TYPE
   SYNTAX      Counter64
   MAX-ACCESS  read-only
   STATUS      current
   DESCRIPTION
      "Path: efm.performance.pppoEClient.mibCounters.ifInDiscardsNoMacFit

       64 bit unsigned wrappable counter."
   ::= {pr1646v2XEfmPPPoEEntry 42270720}

pr1646v2XEfmPPPoEMCInDropNUCast OBJECT-TYPE
   SYNTAX      Counter64
   MAX-ACCESS  read-only
   STATUS      current
   DESCRIPTION
      "Path: efm.performance.pppoEClient.mibCounters.ifInDiscardsNUCast

       64 bit unsigned wrappable counter."
   ::= {pr1646v2XEfmPPPoEEntry 42467328}

pr1646v2XEfmPPPoEMCInDropFilter OBJECT-TYPE
   SYNTAX      Counter64
   MAX-ACCESS  read-only
   STATUS      current
   DESCRIPTION
      "Path: efm.performance.pppoEClient.mibCounters.ifInDiscardsFilter

       64 bit unsigned wrappable counter."
   ::= {pr1646v2XEfmPPPoEEntry 42532864}

pr1646v2XEfmPPPoEMCInBandwidth15sec OBJECT-TYPE
   SYNTAX      Integer32
   MAX-ACCESS  read-only
   STATUS      current
   DESCRIPTION
      "Path: efm.performance.pppoEClient.mibCounters.ifInBandwidth.15sec

       unit name = bps
       formula = 8 * ; 8 /"
   ::= {pr1646v2XEfmPPPoEEntry 45417728}

pr1646v2XEfmPPPoEMCInBandwidth30sec OBJECT-TYPE
   SYNTAX      Integer32
   MAX-ACCESS  read-only
   STATUS      current
   DESCRIPTION
      "Path: efm.performance.pppoEClient.mibCounters.ifInBandwidth.30sec

       unit name = bps
       formula = 8 * ; 8 /"
   ::= {pr1646v2XEfmPPPoEEntry 45419008}

pr1646v2XEfmPPPoEMCInBandwidth1min OBJECT-TYPE
   SYNTAX      Integer32
   MAX-ACCESS  read-only
   STATUS      current
   DESCRIPTION
      "Path: efm.performance.pppoEClient.mibCounters.ifInBandwidth.1min

       unit name = bps
       formula = 8 * ; 8 /"
   ::= {pr1646v2XEfmPPPoEEntry 45421568}

pr1646v2XEfmPPPoEMCInBandwidth2min OBJECT-TYPE
   SYNTAX      Integer32
   MAX-ACCESS  read-only
   STATUS      current
   DESCRIPTION
      "Path: efm.performance.pppoEClient.mibCounters.ifInBandwidth.2min

       unit name = bps
       formula = 8 * ; 8 /"
   ::= {pr1646v2XEfmPPPoEEntry 45426688}

pr1646v2XEfmPPPoEMCInBandwidth5min OBJECT-TYPE
   SYNTAX      Integer32
   MAX-ACCESS  read-only
   STATUS      current
   DESCRIPTION
      "Path: efm.performance.pppoEClient.mibCounters.ifInBandwidth.5min

       unit name = bps
       formula = 8 * ; 8 /"
   ::= {pr1646v2XEfmPPPoEEntry 45442048}

pr1646v2XEfmPPPoEMCOutOctets OBJECT-TYPE
   SYNTAX      Counter64
   MAX-ACCESS  read-only
   STATUS      current
   DESCRIPTION
      "Path: efm.performance.pppoEClient.mibCounters.ifOutOctets

       64 bit unsigned wrappable counter."
   ::= {pr1646v2XEfmPPPoEEntry 41091072}

pr1646v2XEfmPPPoEMCOutUcastPkts OBJECT-TYPE
   SYNTAX      Counter64
   MAX-ACCESS  read-only
   STATUS      current
   DESCRIPTION
      "Path: efm.performance.pppoEClient.mibCounters.ifOutUcastPkts

       64 bit unsigned wrappable counter."
   ::= {pr1646v2XEfmPPPoEEntry 41156608}

pr1646v2XEfmPPPoEMCOutNUcastPkts OBJECT-TYPE
   SYNTAX      Counter64
   MAX-ACCESS  read-only
   STATUS      current
   DESCRIPTION
      "Path: efm.performance.pppoEClient.mibCounters.ifOutNUcastPkts

       64 bit unsigned wrappable counter."
   ::= {pr1646v2XEfmPPPoEEntry 41222144}

pr1646v2XEfmPPPoEMCOutBcastPkts OBJECT-TYPE
   SYNTAX      Counter64
   MAX-ACCESS  read-only
   STATUS      current
   DESCRIPTION
      "Path: efm.performance.pppoEClient.mibCounters.ifOutBcastPkts

       64 bit unsigned wrappable counter."
   ::= {pr1646v2XEfmPPPoEEntry 47775744}

pr1646v2XEfmPPPoEMCOutMcastPkts OBJECT-TYPE
   SYNTAX      Counter64
   MAX-ACCESS  read-only
   STATUS      current
   DESCRIPTION
      "Path: efm.performance.pppoEClient.mibCounters.ifOutMcastPkts

       64 bit unsigned wrappable counter."
   ::= {pr1646v2XEfmPPPoEEntry 48431104}

pr1646v2XEfmPPPoEMCOutDiscards OBJECT-TYPE
   SYNTAX      Counter64
   MAX-ACCESS  read-only
   STATUS      current
   DESCRIPTION
      "Path: efm.performance.pppoEClient.mibCounters.ifOutDiscards

       64 bit unsigned wrappable counter."
   ::= {pr1646v2XEfmPPPoEEntry 41287680}

pr1646v2XEfmPPPoEMCOutErrors OBJECT-TYPE
   SYNTAX      Counter64
   MAX-ACCESS  read-only
   STATUS      current
   DESCRIPTION
      "Path: efm.performance.pppoEClient.mibCounters.ifOutErrors

       64 bit unsigned wrappable counter."
   ::= {pr1646v2XEfmPPPoEEntry 41353216}

pr1646v2XEfmPPPoEMCOutQLen OBJECT-TYPE
   SYNTAX      Counter32
   MAX-ACCESS  read-only
   STATUS      current
   DESCRIPTION
      "Path: efm.performance.pppoEClient.mibCounters.ifOutQLen

       32 bit unsigned wrappable counter."
   ::= {pr1646v2XEfmPPPoEEntry 41418752}

pr1646v2XEfmPPPoEMCOutDropEx OBJECT-TYPE
   SYNTAX      Counter64
   MAX-ACCESS  read-only
   STATUS      current
   DESCRIPTION
      "Path: efm.performance.pppoEClient.mibCounters.ifOutDropLevelExceeded

       64 bit unsigned wrappable counter."
   ::= {pr1646v2XEfmPPPoEEntry 41484288}

pr1646v2XEfmPPPoEMCOutDropNoArp OBJECT-TYPE
   SYNTAX      Counter64
   MAX-ACCESS  read-only
   STATUS      current
   DESCRIPTION
      "Path: efm.performance.pppoEClient.mibCounters.ifOutDiscardsNoArp

       64 bit unsigned wrappable counter."
   ::= {pr1646v2XEfmPPPoEEntry 42336256}

pr1646v2XEfmPPPoEMCOutDropFilter OBJECT-TYPE
   SYNTAX      Counter64
   MAX-ACCESS  read-only
   STATUS      current
   DESCRIPTION
      "Path: efm.performance.pppoEClient.mibCounters.ifOutDiscardsFilter

       64 bit unsigned wrappable counter."
   ::= {pr1646v2XEfmPPPoEEntry 42598400}

pr1646v2XEfmPPPoEMCOutBandwidth15sec OBJECT-TYPE
   SYNTAX      Integer32
   MAX-ACCESS  read-only
   STATUS      current
   DESCRIPTION
      "Path: efm.performance.pppoEClient.mibCounters.ifOutBandwidth.15sec

       unit name = bps
       formula = 8 * ; 8 /"
   ::= {pr1646v2XEfmPPPoEEntry 45483264}

pr1646v2XEfmPPPoEMCOutBandwidth30sec OBJECT-TYPE
   SYNTAX      Integer32
   MAX-ACCESS  read-only
   STATUS      current
   DESCRIPTION
      "Path: efm.performance.pppoEClient.mibCounters.ifOutBandwidth.30sec

       unit name = bps
       formula = 8 * ; 8 /"
   ::= {pr1646v2XEfmPPPoEEntry 45484544}

pr1646v2XEfmPPPoEMCOutBandwidth1min OBJECT-TYPE
   SYNTAX      Integer32
   MAX-ACCESS  read-only
   STATUS      current
   DESCRIPTION
      "Path: efm.performance.pppoEClient.mibCounters.ifOutBandwidth.1min

       unit name = bps
       formula = 8 * ; 8 /"
   ::= {pr1646v2XEfmPPPoEEntry 45487104}

pr1646v2XEfmPPPoEMCOutBandwidth2min OBJECT-TYPE
   SYNTAX      Integer32
   MAX-ACCESS  read-only
   STATUS      current
   DESCRIPTION
      "Path: efm.performance.pppoEClient.mibCounters.ifOutBandwidth.2min

       unit name = bps
       formula = 8 * ; 8 /"
   ::= {pr1646v2XEfmPPPoEEntry 45492224}

pr1646v2XEfmPPPoEMCOutBandwidth5min OBJECT-TYPE
   SYNTAX      Integer32
   MAX-ACCESS  read-only
   STATUS      current
   DESCRIPTION
      "Path: efm.performance.pppoEClient.mibCounters.ifOutBandwidth.5min

       unit name = bps
       formula = 8 * ; 8 /"
   ::= {pr1646v2XEfmPPPoEEntry 45507584}

pr1646v2XEfmPPPoEPppLinkMonitoringRequestsSent OBJECT-TYPE
   SYNTAX      Gauge32
   MAX-ACCESS  read-only
   STATUS      current
   DESCRIPTION
      "Path: efm.performance.pppoEClient.ppp.linkMonitoring.requestsSent

       32 bit unsigned gauge value."
   ::= {pr1646v2XEfmPPPoEEntry 50397440}

pr1646v2XEfmPPPoEPppLinkMonitoringRepliesRcvd OBJECT-TYPE
   SYNTAX      Gauge32
   MAX-ACCESS  read-only
   STATUS      current
   DESCRIPTION
      "Path: efm.performance.pppoEClient.ppp.linkMonitoring.repliesRcvd

       32 bit unsigned gauge value."
   ::= {pr1646v2XEfmPPPoEEntry 50397696}

pr1646v2XEfmPPPoEPppLinkMonitoringRequestsRcvd OBJECT-TYPE
   SYNTAX      Gauge32
   MAX-ACCESS  read-only
   STATUS      current
   DESCRIPTION
      "Path: efm.performance.pppoEClient.ppp.linkMonitoring.requestsRcvd

       32 bit unsigned gauge value."
   ::= {pr1646v2XEfmPPPoEEntry 50397952}

pr1646v2XEfmPPPoEPppLinkMonitoringRepliesSent OBJECT-TYPE
   SYNTAX      Gauge32
   MAX-ACCESS  read-only
   STATUS      current
   DESCRIPTION
      "Path: efm.performance.pppoEClient.ppp.linkMonitoring.repliesSent

       32 bit unsigned gauge value."
   ::= {pr1646v2XEfmPPPoEEntry 50398208}

pr1646v2XEfmPPPoEMCH2P OBJECT-TYPE
   SYNTAX      SEQUENCE OF Pr1646v2XEfmPPPoEMCH2PEntry
   MAX-ACCESS  not-accessible
   STATUS      current
   DESCRIPTION
      ""
   ::= {pr1646v2XEfmPPPoE 41549824}

pr1646v2XEfmPPPoEMCH2PEntry OBJECT-TYPE
   SYNTAX      Pr1646v2XEfmPPPoEMCH2PEntry
   MAX-ACCESS  not-accessible
   STATUS      current
   DESCRIPTION
      ""
   INDEX      { pr1646v2XEfmPPPoETableIx,
                pr1646v2XEfmPPPoEMCH2PTableIx }
   ::= {pr1646v2XEfmPPPoEMCH2P 1}

Pr1646v2XEfmPPPoEMCH2PEntry ::=
   SEQUENCE
      {
      pr1646v2XEfmPPPoEMCH2PTableIx
         TableIndex,
      pr1646v2XEfmPPPoEMCH2PSysUpTime
         TimeTicks,
      pr1646v2XEfmPPPoEMCH2PIfUpTime
         TimeTicks,
      pr1646v2XEfmPPPoEMCH2PIfStatChanges
         Counter32,
      pr1646v2XEfmPPPoEMCH2PIfInOctets
         Counter64,
      pr1646v2XEfmPPPoEMCH2PIfInUCPkts
         Counter64,
      pr1646v2XEfmPPPoEMCH2PIfInNUCPkts
         Counter64,
      pr1646v2XEfmPPPoEMCH2PIfInBCPkts
         Counter64,
      pr1646v2XEfmPPPoEMCH2PIfInMCPkts
         Counter64,
      pr1646v2XEfmPPPoEMCH2PIfInDiscards
         Counter64,
      pr1646v2XEfmPPPoEMCH2PIfInErrors
         Counter64,
      pr1646v2XEfmPPPoEMCH2PIfInUnkwn
         Counter64,
      pr1646v2XEfmPPPoEMCH2PInDropEx
         Counter64,
      pr1646v2XEfmPPPoEMCH2PInDropNoMac
         Counter64,
      pr1646v2XEfmPPPoEMCH2PInDropNUCast
         Counter64,
      pr1646v2XEfmPPPoEMCH2PInDropFilter
         Counter64,
      pr1646v2XEfmPPPoEMCH2PIfInBandwidth
         Integer32,
      pr1646v2XEfmPPPoEMCH2PIfOutOctets
         Counter64,
      pr1646v2XEfmPPPoEMCH2PIfOutUCPkts
         Counter64,
      pr1646v2XEfmPPPoEMCH2PIfOutNUCPkts
         Counter64,
      pr1646v2XEfmPPPoEMCH2PIfOutBCPkts
         Counter64,
      pr1646v2XEfmPPPoEMCH2PIfOutMCPkts
         Counter64,
      pr1646v2XEfmPPPoEMCH2PIfOutDiscards
         Counter64,
      pr1646v2XEfmPPPoEMCH2PIfOutErrors
         Counter64,
      pr1646v2XEfmPPPoEMCH2POutDropEx
         Counter64,
      pr1646v2XEfmPPPoEMCH2POutDropNoArp
         Counter64,
      pr1646v2XEfmPPPoEMCH2POutDropFilter
         Counter64,
      pr1646v2XEfmPPPoEMCH2PIfOutBandwidth
         Integer32,
      pr1646v2XEfmPPPoEMCH2PIfErrSec
         Counter32
      }

pr1646v2XEfmPPPoEMCH2PTableIx OBJECT-TYPE
   SYNTAX      TableIndex
   MAX-ACCESS  not-accessible
   STATUS      current
   DESCRIPTION
      ""
   ::= {pr1646v2XEfmPPPoEMCH2PEntry 11}

pr1646v2XEfmPPPoEMCH2PSysUpTime OBJECT-TYPE
   SYNTAX      TimeTicks
   MAX-ACCESS  read-only
   STATUS      current
   DESCRIPTION
      "Path: efm.performance.pppoEClient.mibCounters.h2Performance.sysUpTime

       Time in centi-second."
   ::= {pr1646v2XEfmPPPoEMCH2PEntry 16777216}

pr1646v2XEfmPPPoEMCH2PIfUpTime OBJECT-TYPE
   SYNTAX      TimeTicks
   MAX-ACCESS  read-only
   STATUS      current
   DESCRIPTION
      "Path: efm.performance.pppoEClient.mibCounters.h2Performance.ifUpTime

       Time in centi-second."
   ::= {pr1646v2XEfmPPPoEMCH2PEntry 33554432}

pr1646v2XEfmPPPoEMCH2PIfStatChanges OBJECT-TYPE
   SYNTAX      Counter32
   MAX-ACCESS  read-only
   STATUS      current
   DESCRIPTION
      "Path: efm.performance.pppoEClient.mibCounters.h2Performance.ifStatusChanges

       32 bit unsigned wrappable counter."
   ::= {pr1646v2XEfmPPPoEMCH2PEntry 50331648}

pr1646v2XEfmPPPoEMCH2PIfInOctets OBJECT-TYPE
   SYNTAX      Counter64
   MAX-ACCESS  read-only
   STATUS      current
   DESCRIPTION
      "Path: efm.performance.pppoEClient.mibCounters.h2Performance.ifInOctets

       64 bit unsigned wrappable counter."
   ::= {pr1646v2XEfmPPPoEMCH2PEntry 67108864}

pr1646v2XEfmPPPoEMCH2PIfInUCPkts OBJECT-TYPE
   SYNTAX      Counter64
   MAX-ACCESS  read-only
   STATUS      current
   DESCRIPTION
      "Path: efm.performance.pppoEClient.mibCounters.h2Performance.ifInUcastPkts

       64 bit unsigned wrappable counter."
   ::= {pr1646v2XEfmPPPoEMCH2PEntry 83886080}

pr1646v2XEfmPPPoEMCH2PIfInNUCPkts OBJECT-TYPE
   SYNTAX      Counter64
   MAX-ACCESS  read-only
   STATUS      current
   DESCRIPTION
      "Path: efm.performance.pppoEClient.mibCounters.h2Performance.ifInNUcastPkts

       64 bit unsigned wrappable counter."
   ::= {pr1646v2XEfmPPPoEMCH2PEntry 100663296}

pr1646v2XEfmPPPoEMCH2PIfInBCPkts OBJECT-TYPE
   SYNTAX      Counter64
   MAX-ACCESS  read-only
   STATUS      current
   DESCRIPTION
      "Path: efm.performance.pppoEClient.mibCounters.h2Performance.ifInBcastPkts

       64 bit unsigned wrappable counter."
   ::= {pr1646v2XEfmPPPoEMCH2PEntry 419430400}

pr1646v2XEfmPPPoEMCH2PIfInMCPkts OBJECT-TYPE
   SYNTAX      Counter64
   MAX-ACCESS  read-only
   STATUS      current
   DESCRIPTION
      "Path: efm.performance.pppoEClient.mibCounters.h2Performance.ifInMcastPkts

       64 bit unsigned wrappable counter."
   ::= {pr1646v2XEfmPPPoEMCH2PEntry 436207616}

pr1646v2XEfmPPPoEMCH2PIfInDiscards OBJECT-TYPE
   SYNTAX      Counter64
   MAX-ACCESS  read-only
   STATUS      current
   DESCRIPTION
      "Path: efm.performance.pppoEClient.mibCounters.h2Performance.ifInDiscards

       64 bit unsigned wrappable counter."
   ::= {pr1646v2XEfmPPPoEMCH2PEntry 117440512}

pr1646v2XEfmPPPoEMCH2PIfInErrors OBJECT-TYPE
   SYNTAX      Counter64
   MAX-ACCESS  read-only
   STATUS      current
   DESCRIPTION
      "Path: efm.performance.pppoEClient.mibCounters.h2Performance.ifInErrors

       64 bit unsigned wrappable counter."
   ::= {pr1646v2XEfmPPPoEMCH2PEntry 134217728}

pr1646v2XEfmPPPoEMCH2PIfInUnkwn OBJECT-TYPE
   SYNTAX      Counter64
   MAX-ACCESS  read-only
   STATUS      current
   DESCRIPTION
      "Path: efm.performance.pppoEClient.mibCounters.h2Performance.ifInUnknownProtos

       64 bit unsigned wrappable counter."
   ::= {pr1646v2XEfmPPPoEMCH2PEntry 150994944}

pr1646v2XEfmPPPoEMCH2PInDropEx OBJECT-TYPE
   SYNTAX      Counter64
   MAX-ACCESS  read-only
   STATUS      current
   DESCRIPTION
      "Path: efm.performance.pppoEClient.mibCounters.h2Performance.ifInDropLevelExceeded

       64 bit unsigned wrappable counter."
   ::= {pr1646v2XEfmPPPoEMCH2PEntry 335544320}

pr1646v2XEfmPPPoEMCH2PInDropNoMac OBJECT-TYPE
   SYNTAX      Counter64
   MAX-ACCESS  read-only
   STATUS      current
   DESCRIPTION
      "Path: efm.performance.pppoEClient.mibCounters.h2Performance.fInDiscardsNoMacFit

       64 bit unsigned wrappable counter."
   ::= {pr1646v2XEfmPPPoEMCH2PEntry 301989888}

pr1646v2XEfmPPPoEMCH2PInDropNUCast OBJECT-TYPE
   SYNTAX      Counter64
   MAX-ACCESS  read-only
   STATUS      current
   DESCRIPTION
      "Path: efm.performance.pppoEClient.mibCounters.h2Performance.fInDiscardsNUCast

       64 bit unsigned wrappable counter."
   ::= {pr1646v2XEfmPPPoEMCH2PEntry 318767104}

pr1646v2XEfmPPPoEMCH2PInDropFilter OBJECT-TYPE
   SYNTAX      Counter64
   MAX-ACCESS  read-only
   STATUS      current
   DESCRIPTION
      "Path: efm.performance.pppoEClient.mibCounters.h2Performance.fInDiscardsFilter

       64 bit unsigned wrappable counter."
   ::= {pr1646v2XEfmPPPoEMCH2PEntry 385875968}

pr1646v2XEfmPPPoEMCH2PIfInBandwidth OBJECT-TYPE
   SYNTAX      Integer32
   MAX-ACCESS  read-only
   STATUS      current
   DESCRIPTION
      "Path: efm.performance.pppoEClient.mibCounters.h2Performance.ifInBandwidth

       unit name = bps
       formula = 8 * ; 8 /"
   ::= {pr1646v2XEfmPPPoEMCH2PEntry 268435456}

pr1646v2XEfmPPPoEMCH2PIfOutOctets OBJECT-TYPE
   SYNTAX      Counter64
   MAX-ACCESS  read-only
   STATUS      current
   DESCRIPTION
      "Path: efm.performance.pppoEClient.mibCounters.h2Performance.ifOutOctets

       64 bit unsigned wrappable counter."
   ::= {pr1646v2XEfmPPPoEMCH2PEntry 167772160}

pr1646v2XEfmPPPoEMCH2PIfOutUCPkts OBJECT-TYPE
   SYNTAX      Counter64
   MAX-ACCESS  read-only
   STATUS      current
   DESCRIPTION
      "Path: efm.performance.pppoEClient.mibCounters.h2Performance.ifOutUcastPkts

       64 bit unsigned wrappable counter."
   ::= {pr1646v2XEfmPPPoEMCH2PEntry 184549376}

pr1646v2XEfmPPPoEMCH2PIfOutNUCPkts OBJECT-TYPE
   SYNTAX      Counter64
   MAX-ACCESS  read-only
   STATUS      current
   DESCRIPTION
      "Path: efm.performance.pppoEClient.mibCounters.h2Performance.ifOutNUcastPkts

       64 bit unsigned wrappable counter."
   ::= {pr1646v2XEfmPPPoEMCH2PEntry 201326592}

pr1646v2XEfmPPPoEMCH2PIfOutBCPkts OBJECT-TYPE
   SYNTAX      Counter64
   MAX-ACCESS  read-only
   STATUS      current
   DESCRIPTION
      "Path: efm.performance.pppoEClient.mibCounters.h2Performance.ifOutBcastPkts

       64 bit unsigned wrappable counter."
   ::= {pr1646v2XEfmPPPoEMCH2PEntry 452984832}

pr1646v2XEfmPPPoEMCH2PIfOutMCPkts OBJECT-TYPE
   SYNTAX      Counter64
   MAX-ACCESS  read-only
   STATUS      current
   DESCRIPTION
      "Path: efm.performance.pppoEClient.mibCounters.h2Performance.ifOutMcastPkts

       64 bit unsigned wrappable counter."
   ::= {pr1646v2XEfmPPPoEMCH2PEntry 469762048}

pr1646v2XEfmPPPoEMCH2PIfOutDiscards OBJECT-TYPE
   SYNTAX      Counter64
   MAX-ACCESS  read-only
   STATUS      current
   DESCRIPTION
      "Path: efm.performance.pppoEClient.mibCounters.h2Performance.ifOutDiscards

       64 bit unsigned wrappable counter."
   ::= {pr1646v2XEfmPPPoEMCH2PEntry 218103808}

pr1646v2XEfmPPPoEMCH2PIfOutErrors OBJECT-TYPE
   SYNTAX      Counter64
   MAX-ACCESS  read-only
   STATUS      current
   DESCRIPTION
      "Path: efm.performance.pppoEClient.mibCounters.h2Performance.ifOutErrors

       64 bit unsigned wrappable counter."
   ::= {pr1646v2XEfmPPPoEMCH2PEntry 234881024}

pr1646v2XEfmPPPoEMCH2POutDropEx OBJECT-TYPE
   SYNTAX      Counter64
   MAX-ACCESS  read-only
   STATUS      current
   DESCRIPTION
      "Path: efm.performance.pppoEClient.mibCounters.h2Performance.ifOutDropLevelExceeded

       64 bit unsigned wrappable counter."
   ::= {pr1646v2XEfmPPPoEMCH2PEntry 352321536}

pr1646v2XEfmPPPoEMCH2POutDropNoArp OBJECT-TYPE
   SYNTAX      Counter64
   MAX-ACCESS  read-only
   STATUS      current
   DESCRIPTION
      "Path: efm.performance.pppoEClient.mibCounters.h2Performance.ifOutDiscardsNoArp

       64 bit unsigned wrappable counter."
   ::= {pr1646v2XEfmPPPoEMCH2PEntry 369098752}

pr1646v2XEfmPPPoEMCH2POutDropFilter OBJECT-TYPE
   SYNTAX      Counter64
   MAX-ACCESS  read-only
   STATUS      current
   DESCRIPTION
      "Path: efm.performance.pppoEClient.mibCounters.h2Performance.ifOutDiscardsFilter

       64 bit unsigned wrappable counter."
   ::= {pr1646v2XEfmPPPoEMCH2PEntry 402653184}

pr1646v2XEfmPPPoEMCH2PIfOutBandwidth OBJECT-TYPE
   SYNTAX      Integer32
   MAX-ACCESS  read-only
   STATUS      current
   DESCRIPTION
      "Path: efm.performance.pppoEClient.mibCounters.h2Performance.ifOutBandwidth

       unit name = bps
       formula = 8 * ; 8 /"
   ::= {pr1646v2XEfmPPPoEMCH2PEntry 285212672}

pr1646v2XEfmPPPoEMCH2PIfErrSec OBJECT-TYPE
   SYNTAX      Counter32
   MAX-ACCESS  read-only
   STATUS      current
   DESCRIPTION
      "Path: efm.performance.pppoEClient.mibCounters.h2Performance.ifErrSec

       32 bit unsigned wrappable counter."
   ::= {pr1646v2XEfmPPPoEMCH2PEntry 251658240}

pr1646v2XEfmPPPoEMCH24P OBJECT-TYPE
   SYNTAX      SEQUENCE OF Pr1646v2XEfmPPPoEMCH24PEntry
   MAX-ACCESS  not-accessible
   STATUS      current
   DESCRIPTION
      ""
   ::= {pr1646v2XEfmPPPoE 41615360}

pr1646v2XEfmPPPoEMCH24PEntry OBJECT-TYPE
   SYNTAX      Pr1646v2XEfmPPPoEMCH24PEntry
   MAX-ACCESS  not-accessible
   STATUS      current
   DESCRIPTION
      ""
   INDEX      { pr1646v2XEfmPPPoETableIx,
                pr1646v2XEfmPPPoEMCH24PTableIx }
   ::= {pr1646v2XEfmPPPoEMCH24P 1}

Pr1646v2XEfmPPPoEMCH24PEntry ::=
   SEQUENCE
      {
      pr1646v2XEfmPPPoEMCH24PTableIx
         TableIndex,
      pr1646v2XEfmPPPoEMCH24PSysUpTime
         TimeTicks,
      pr1646v2XEfmPPPoEMCH24PIfUpTime
         TimeTicks,
      pr1646v2XEfmPPPoEMCH24PIfStatChanges
         Counter32,
      pr1646v2XEfmPPPoEMCH24PIfInOctets
         Counter64,
      pr1646v2XEfmPPPoEMCH24PIfInUCPkts
         Counter64,
      pr1646v2XEfmPPPoEMCH24PIfInNUCPkts
         Counter64,
      pr1646v2XEfmPPPoEMCH24PIfInBCPkts
         Counter64,
      pr1646v2XEfmPPPoEMCH24PIfInMCPkts
         Counter64,
      pr1646v2XEfmPPPoEMCH24PIfInDiscards
         Counter64,
      pr1646v2XEfmPPPoEMCH24PIfInErrors
         Counter64,
      pr1646v2XEfmPPPoEMCH24PIfInUnkwn
         Counter64,
      pr1646v2XEfmPPPoEMCH24PInDropEx
         Counter64,
      pr1646v2XEfmPPPoEMCH24PInDropNoMac
         Counter64,
      pr1646v2XEfmPPPoEMCH24PInDropNUCast
         Counter64,
      pr1646v2XEfmPPPoEMCH24PInDropFilter
         Counter64,
      pr1646v2XEfmPPPoEMCH24PIfInBandwidth
         Integer32,
      pr1646v2XEfmPPPoEMCH24PIfOutOctets
         Counter64,
      pr1646v2XEfmPPPoEMCH24PIfOutUCPkts
         Counter64,
      pr1646v2XEfmPPPoEMCH24PIfOutNUCPkts
         Counter64,
      pr1646v2XEfmPPPoEMCH24PIfOutBCPkts
         Counter64,
      pr1646v2XEfmPPPoEMCH24PIfOutMCPkts
         Counter64,
      pr1646v2XEfmPPPoEMCH24PIfOutDiscards
         Counter64,
      pr1646v2XEfmPPPoEMCH24PIfOutErrors
         Counter64,
      pr1646v2XEfmPPPoEMCH24POutDropEx
         Counter64,
      pr1646v2XEfmPPPoEMCH24POutDropNoArp
         Counter64,
      pr1646v2XEfmPPPoEMCH24POutDropFilter
         Counter64,
      pr1646v2XEfmPPPoEMCH24PIfOutBandwidth
         Integer32,
      pr1646v2XEfmPPPoEMCH24PIfErrSec
         Counter32
      }

pr1646v2XEfmPPPoEMCH24PTableIx OBJECT-TYPE
   SYNTAX      TableIndex
   MAX-ACCESS  not-accessible
   STATUS      current
   DESCRIPTION
      ""
   ::= {pr1646v2XEfmPPPoEMCH24PEntry 11}

pr1646v2XEfmPPPoEMCH24PSysUpTime OBJECT-TYPE
   SYNTAX      TimeTicks
   MAX-ACCESS  read-only
   STATUS      current
   DESCRIPTION
      "Path: efm.performance.pppoEClient.mibCounters.h24Performance.sysUpTime

       Time in centi-second."
   ::= {pr1646v2XEfmPPPoEMCH24PEntry 16777216}

pr1646v2XEfmPPPoEMCH24PIfUpTime OBJECT-TYPE
   SYNTAX      TimeTicks
   MAX-ACCESS  read-only
   STATUS      current
   DESCRIPTION
      "Path: efm.performance.pppoEClient.mibCounters.h24Performance.ifUpTime

       Time in centi-second."
   ::= {pr1646v2XEfmPPPoEMCH24PEntry 33554432}

pr1646v2XEfmPPPoEMCH24PIfStatChanges OBJECT-TYPE
   SYNTAX      Counter32
   MAX-ACCESS  read-only
   STATUS      current
   DESCRIPTION
      "Path: efm.performance.pppoEClient.mibCounters.h24Performance.ifStatusChanges

       32 bit unsigned wrappable counter."
   ::= {pr1646v2XEfmPPPoEMCH24PEntry 50331648}

pr1646v2XEfmPPPoEMCH24PIfInOctets OBJECT-TYPE
   SYNTAX      Counter64
   MAX-ACCESS  read-only
   STATUS      current
   DESCRIPTION
      "Path: efm.performance.pppoEClient.mibCounters.h24Performance.ifInOctets

       64 bit unsigned wrappable counter."
   ::= {pr1646v2XEfmPPPoEMCH24PEntry 67108864}

pr1646v2XEfmPPPoEMCH24PIfInUCPkts OBJECT-TYPE
   SYNTAX      Counter64
   MAX-ACCESS  read-only
   STATUS      current
   DESCRIPTION
      "Path: efm.performance.pppoEClient.mibCounters.h24Performance.ifInUcastPkts

       64 bit unsigned wrappable counter."
   ::= {pr1646v2XEfmPPPoEMCH24PEntry 83886080}

pr1646v2XEfmPPPoEMCH24PIfInNUCPkts OBJECT-TYPE
   SYNTAX      Counter64
   MAX-ACCESS  read-only
   STATUS      current
   DESCRIPTION
      "Path: efm.performance.pppoEClient.mibCounters.h24Performance.ifInNUcastPkts

       64 bit unsigned wrappable counter."
   ::= {pr1646v2XEfmPPPoEMCH24PEntry 100663296}

pr1646v2XEfmPPPoEMCH24PIfInBCPkts OBJECT-TYPE
   SYNTAX      Counter64
   MAX-ACCESS  read-only
   STATUS      current
   DESCRIPTION
      "Path: efm.performance.pppoEClient.mibCounters.h24Performance.ifInBcastPkts

       64 bit unsigned wrappable counter."
   ::= {pr1646v2XEfmPPPoEMCH24PEntry 419430400}

pr1646v2XEfmPPPoEMCH24PIfInMCPkts OBJECT-TYPE
   SYNTAX      Counter64
   MAX-ACCESS  read-only
   STATUS      current
   DESCRIPTION
      "Path: efm.performance.pppoEClient.mibCounters.h24Performance.ifInMcastPkts

       64 bit unsigned wrappable counter."
   ::= {pr1646v2XEfmPPPoEMCH24PEntry 436207616}

pr1646v2XEfmPPPoEMCH24PIfInDiscards OBJECT-TYPE
   SYNTAX      Counter64
   MAX-ACCESS  read-only
   STATUS      current
   DESCRIPTION
      "Path: efm.performance.pppoEClient.mibCounters.h24Performance.ifInDiscards

       64 bit unsigned wrappable counter."
   ::= {pr1646v2XEfmPPPoEMCH24PEntry 117440512}

pr1646v2XEfmPPPoEMCH24PIfInErrors OBJECT-TYPE
   SYNTAX      Counter64
   MAX-ACCESS  read-only
   STATUS      current
   DESCRIPTION
      "Path: efm.performance.pppoEClient.mibCounters.h24Performance.ifInErrors

       64 bit unsigned wrappable counter."
   ::= {pr1646v2XEfmPPPoEMCH24PEntry 134217728}

pr1646v2XEfmPPPoEMCH24PIfInUnkwn OBJECT-TYPE
   SYNTAX      Counter64
   MAX-ACCESS  read-only
   STATUS      current
   DESCRIPTION
      "Path: efm.performance.pppoEClient.mibCounters.h24Performance.ifInUnknownProtos

       64 bit unsigned wrappable counter."
   ::= {pr1646v2XEfmPPPoEMCH24PEntry 150994944}

pr1646v2XEfmPPPoEMCH24PInDropEx OBJECT-TYPE
   SYNTAX      Counter64
   MAX-ACCESS  read-only
   STATUS      current
   DESCRIPTION
      "Path: efm.performance.pppoEClient.mibCounters.h24Performance.ifInDropLevelExceeded

       64 bit unsigned wrappable counter."
   ::= {pr1646v2XEfmPPPoEMCH24PEntry 335544320}

pr1646v2XEfmPPPoEMCH24PInDropNoMac OBJECT-TYPE
   SYNTAX      Counter64
   MAX-ACCESS  read-only
   STATUS      current
   DESCRIPTION
      "Path: efm.performance.pppoEClient.mibCounters.h24Performance.fInDiscardsNoMacFit

       64 bit unsigned wrappable counter."
   ::= {pr1646v2XEfmPPPoEMCH24PEntry 301989888}

pr1646v2XEfmPPPoEMCH24PInDropNUCast OBJECT-TYPE
   SYNTAX      Counter64
   MAX-ACCESS  read-only
   STATUS      current
   DESCRIPTION
      "Path: efm.performance.pppoEClient.mibCounters.h24Performance.fInDiscardsNUCast

       64 bit unsigned wrappable counter."
   ::= {pr1646v2XEfmPPPoEMCH24PEntry 318767104}

pr1646v2XEfmPPPoEMCH24PInDropFilter OBJECT-TYPE
   SYNTAX      Counter64
   MAX-ACCESS  read-only
   STATUS      current
   DESCRIPTION
      "Path: efm.performance.pppoEClient.mibCounters.h24Performance.fInDiscardsFilter

       64 bit unsigned wrappable counter."
   ::= {pr1646v2XEfmPPPoEMCH24PEntry 385875968}

pr1646v2XEfmPPPoEMCH24PIfInBandwidth OBJECT-TYPE
   SYNTAX      Integer32
   MAX-ACCESS  read-only
   STATUS      current
   DESCRIPTION
      "Path: efm.performance.pppoEClient.mibCounters.h24Performance.ifInBandwidth

       unit name = bps
       formula = 8 * ; 8 /"
   ::= {pr1646v2XEfmPPPoEMCH24PEntry 268435456}

pr1646v2XEfmPPPoEMCH24PIfOutOctets OBJECT-TYPE
   SYNTAX      Counter64
   MAX-ACCESS  read-only
   STATUS      current
   DESCRIPTION
      "Path: efm.performance.pppoEClient.mibCounters.h24Performance.ifOutOctets

       64 bit unsigned wrappable counter."
   ::= {pr1646v2XEfmPPPoEMCH24PEntry 167772160}

pr1646v2XEfmPPPoEMCH24PIfOutUCPkts OBJECT-TYPE
   SYNTAX      Counter64
   MAX-ACCESS  read-only
   STATUS      current
   DESCRIPTION
      "Path: efm.performance.pppoEClient.mibCounters.h24Performance.ifOutUcastPkts

       64 bit unsigned wrappable counter."
   ::= {pr1646v2XEfmPPPoEMCH24PEntry 184549376}

pr1646v2XEfmPPPoEMCH24PIfOutNUCPkts OBJECT-TYPE
   SYNTAX      Counter64
   MAX-ACCESS  read-only
   STATUS      current
   DESCRIPTION
      "Path: efm.performance.pppoEClient.mibCounters.h24Performance.ifOutNUcastPkts

       64 bit unsigned wrappable counter."
   ::= {pr1646v2XEfmPPPoEMCH24PEntry 201326592}

pr1646v2XEfmPPPoEMCH24PIfOutBCPkts OBJECT-TYPE
   SYNTAX      Counter64
   MAX-ACCESS  read-only
   STATUS      current
   DESCRIPTION
      "Path: efm.performance.pppoEClient.mibCounters.h24Performance.ifOutBcastPkts

       64 bit unsigned wrappable counter."
   ::= {pr1646v2XEfmPPPoEMCH24PEntry 452984832}

pr1646v2XEfmPPPoEMCH24PIfOutMCPkts OBJECT-TYPE
   SYNTAX      Counter64
   MAX-ACCESS  read-only
   STATUS      current
   DESCRIPTION
      "Path: efm.performance.pppoEClient.mibCounters.h24Performance.ifOutMcastPkts

       64 bit unsigned wrappable counter."
   ::= {pr1646v2XEfmPPPoEMCH24PEntry 469762048}

pr1646v2XEfmPPPoEMCH24PIfOutDiscards OBJECT-TYPE
   SYNTAX      Counter64
   MAX-ACCESS  read-only
   STATUS      current
   DESCRIPTION
      "Path: efm.performance.pppoEClient.mibCounters.h24Performance.ifOutDiscards

       64 bit unsigned wrappable counter."
   ::= {pr1646v2XEfmPPPoEMCH24PEntry 218103808}

pr1646v2XEfmPPPoEMCH24PIfOutErrors OBJECT-TYPE
   SYNTAX      Counter64
   MAX-ACCESS  read-only
   STATUS      current
   DESCRIPTION
      "Path: efm.performance.pppoEClient.mibCounters.h24Performance.ifOutErrors

       64 bit unsigned wrappable counter."
   ::= {pr1646v2XEfmPPPoEMCH24PEntry 234881024}

pr1646v2XEfmPPPoEMCH24POutDropEx OBJECT-TYPE
   SYNTAX      Counter64
   MAX-ACCESS  read-only
   STATUS      current
   DESCRIPTION
      "Path: efm.performance.pppoEClient.mibCounters.h24Performance.ifOutDropLevelExceeded

       64 bit unsigned wrappable counter."
   ::= {pr1646v2XEfmPPPoEMCH24PEntry 352321536}

pr1646v2XEfmPPPoEMCH24POutDropNoArp OBJECT-TYPE
   SYNTAX      Counter64
   MAX-ACCESS  read-only
   STATUS      current
   DESCRIPTION
      "Path: efm.performance.pppoEClient.mibCounters.h24Performance.ifOutDiscardsNoArp

       64 bit unsigned wrappable counter."
   ::= {pr1646v2XEfmPPPoEMCH24PEntry 369098752}

pr1646v2XEfmPPPoEMCH24POutDropFilter OBJECT-TYPE
   SYNTAX      Counter64
   MAX-ACCESS  read-only
   STATUS      current
   DESCRIPTION
      "Path: efm.performance.pppoEClient.mibCounters.h24Performance.ifOutDiscardsFilter

       64 bit unsigned wrappable counter."
   ::= {pr1646v2XEfmPPPoEMCH24PEntry 402653184}

pr1646v2XEfmPPPoEMCH24PIfOutBandwidth OBJECT-TYPE
   SYNTAX      Integer32
   MAX-ACCESS  read-only
   STATUS      current
   DESCRIPTION
      "Path: efm.performance.pppoEClient.mibCounters.h24Performance.ifOutBandwidth

       unit name = bps
       formula = 8 * ; 8 /"
   ::= {pr1646v2XEfmPPPoEMCH24PEntry 285212672}

pr1646v2XEfmPPPoEMCH24PIfErrSec OBJECT-TYPE
   SYNTAX      Counter32
   MAX-ACCESS  read-only
   STATUS      current
   DESCRIPTION
      "Path: efm.performance.pppoEClient.mibCounters.h24Performance.ifErrSec

       32 bit unsigned wrappable counter."
   ::= {pr1646v2XEfmPPPoEMCH24PEntry 251658240}

pr1646v2XEfmPPPoEMCD7P OBJECT-TYPE
   SYNTAX      SEQUENCE OF Pr1646v2XEfmPPPoEMCD7PEntry
   MAX-ACCESS  not-accessible
   STATUS      current
   DESCRIPTION
      ""
   ::= {pr1646v2XEfmPPPoE 41680896}

pr1646v2XEfmPPPoEMCD7PEntry OBJECT-TYPE
   SYNTAX      Pr1646v2XEfmPPPoEMCD7PEntry
   MAX-ACCESS  not-accessible
   STATUS      current
   DESCRIPTION
      ""
   INDEX      { pr1646v2XEfmPPPoETableIx,
                pr1646v2XEfmPPPoEMCD7PTableIx }
   ::= {pr1646v2XEfmPPPoEMCD7P 1}

Pr1646v2XEfmPPPoEMCD7PEntry ::=
   SEQUENCE
      {
      pr1646v2XEfmPPPoEMCD7PTableIx
         TableIndex,
      pr1646v2XEfmPPPoEMCD7PSysUpTime
         TimeTicks,
      pr1646v2XEfmPPPoEMCD7PIfUpTime
         TimeTicks,
      pr1646v2XEfmPPPoEMCD7PIfStatChanges
         Counter32,
      pr1646v2XEfmPPPoEMCD7PIfInOctets
         Counter64,
      pr1646v2XEfmPPPoEMCD7PIfInUCPkts
         Counter64,
      pr1646v2XEfmPPPoEMCD7PIfInNUCPkts
         Counter64,
      pr1646v2XEfmPPPoEMCD7PIfInBCPkts
         Counter64,
      pr1646v2XEfmPPPoEMCD7PIfInMCPkts
         Counter64,
      pr1646v2XEfmPPPoEMCD7PIfInDiscards
         Counter64,
      pr1646v2XEfmPPPoEMCD7PIfInErrors
         Counter64,
      pr1646v2XEfmPPPoEMCD7PIfInUnkwn
         Counter64,
      pr1646v2XEfmPPPoEMCD7PInDropEx
         Counter64,
      pr1646v2XEfmPPPoEMCD7PInDropNoMac
         Counter64,
      pr1646v2XEfmPPPoEMCD7PInDropNUCast
         Counter64,
      pr1646v2XEfmPPPoEMCD7PInDropFilter
         Counter64,
      pr1646v2XEfmPPPoEMCD7PIfInBandwidth
         Integer32,
      pr1646v2XEfmPPPoEMCD7PIfOutOctets
         Counter64,
      pr1646v2XEfmPPPoEMCD7PIfOutUCPkts
         Counter64,
      pr1646v2XEfmPPPoEMCD7PIfOutNUCPkts
         Counter64,
      pr1646v2XEfmPPPoEMCD7PIfOutBCPkts
         Counter64,
      pr1646v2XEfmPPPoEMCD7PIfOutMCPkts
         Counter64,
      pr1646v2XEfmPPPoEMCD7PIfOutDiscards
         Counter64,
      pr1646v2XEfmPPPoEMCD7PIfOutErrors
         Counter64,
      pr1646v2XEfmPPPoEMCD7POutDropEx
         Counter64,
      pr1646v2XEfmPPPoEMCD7POutDropNoArp
         Counter64,
      pr1646v2XEfmPPPoEMCD7POutDropFilter
         Counter64,
      pr1646v2XEfmPPPoEMCD7PIfOutBandwidth
         Integer32,
      pr1646v2XEfmPPPoEMCD7PIfErrSec
         Counter32
      }

pr1646v2XEfmPPPoEMCD7PTableIx OBJECT-TYPE
   SYNTAX      TableIndex
   MAX-ACCESS  not-accessible
   STATUS      current
   DESCRIPTION
      ""
   ::= {pr1646v2XEfmPPPoEMCD7PEntry 11}

pr1646v2XEfmPPPoEMCD7PSysUpTime OBJECT-TYPE
   SYNTAX      TimeTicks
   MAX-ACCESS  read-only
   STATUS      current
   DESCRIPTION
      "Path: efm.performance.pppoEClient.mibCounters.d7Performance.sysUpTime

       Time in centi-second."
   ::= {pr1646v2XEfmPPPoEMCD7PEntry 16777216}

pr1646v2XEfmPPPoEMCD7PIfUpTime OBJECT-TYPE
   SYNTAX      TimeTicks
   MAX-ACCESS  read-only
   STATUS      current
   DESCRIPTION
      "Path: efm.performance.pppoEClient.mibCounters.d7Performance.ifUpTime

       Time in centi-second."
   ::= {pr1646v2XEfmPPPoEMCD7PEntry 33554432}

pr1646v2XEfmPPPoEMCD7PIfStatChanges OBJECT-TYPE
   SYNTAX      Counter32
   MAX-ACCESS  read-only
   STATUS      current
   DESCRIPTION
      "Path: efm.performance.pppoEClient.mibCounters.d7Performance.ifStatusChanges

       32 bit unsigned wrappable counter."
   ::= {pr1646v2XEfmPPPoEMCD7PEntry 50331648}

pr1646v2XEfmPPPoEMCD7PIfInOctets OBJECT-TYPE
   SYNTAX      Counter64
   MAX-ACCESS  read-only
   STATUS      current
   DESCRIPTION
      "Path: efm.performance.pppoEClient.mibCounters.d7Performance.ifInOctets

       64 bit unsigned wrappable counter."
   ::= {pr1646v2XEfmPPPoEMCD7PEntry 67108864}

pr1646v2XEfmPPPoEMCD7PIfInUCPkts OBJECT-TYPE
   SYNTAX      Counter64
   MAX-ACCESS  read-only
   STATUS      current
   DESCRIPTION
      "Path: efm.performance.pppoEClient.mibCounters.d7Performance.ifInUcastPkts

       64 bit unsigned wrappable counter."
   ::= {pr1646v2XEfmPPPoEMCD7PEntry 83886080}

pr1646v2XEfmPPPoEMCD7PIfInNUCPkts OBJECT-TYPE
   SYNTAX      Counter64
   MAX-ACCESS  read-only
   STATUS      current
   DESCRIPTION
      "Path: efm.performance.pppoEClient.mibCounters.d7Performance.ifInNUcastPkts

       64 bit unsigned wrappable counter."
   ::= {pr1646v2XEfmPPPoEMCD7PEntry 100663296}

pr1646v2XEfmPPPoEMCD7PIfInBCPkts OBJECT-TYPE
   SYNTAX      Counter64
   MAX-ACCESS  read-only
   STATUS      current
   DESCRIPTION
      "Path: efm.performance.pppoEClient.mibCounters.d7Performance.ifInBcastPkts

       64 bit unsigned wrappable counter."
   ::= {pr1646v2XEfmPPPoEMCD7PEntry 419430400}

pr1646v2XEfmPPPoEMCD7PIfInMCPkts OBJECT-TYPE
   SYNTAX      Counter64
   MAX-ACCESS  read-only
   STATUS      current
   DESCRIPTION
      "Path: efm.performance.pppoEClient.mibCounters.d7Performance.ifInMcastPkts

       64 bit unsigned wrappable counter."
   ::= {pr1646v2XEfmPPPoEMCD7PEntry 436207616}

pr1646v2XEfmPPPoEMCD7PIfInDiscards OBJECT-TYPE
   SYNTAX      Counter64
   MAX-ACCESS  read-only
   STATUS      current
   DESCRIPTION
      "Path: efm.performance.pppoEClient.mibCounters.d7Performance.ifInDiscards

       64 bit unsigned wrappable counter."
   ::= {pr1646v2XEfmPPPoEMCD7PEntry 117440512}

pr1646v2XEfmPPPoEMCD7PIfInErrors OBJECT-TYPE
   SYNTAX      Counter64
   MAX-ACCESS  read-only
   STATUS      current
   DESCRIPTION
      "Path: efm.performance.pppoEClient.mibCounters.d7Performance.ifInErrors

       64 bit unsigned wrappable counter."
   ::= {pr1646v2XEfmPPPoEMCD7PEntry 134217728}

pr1646v2XEfmPPPoEMCD7PIfInUnkwn OBJECT-TYPE
   SYNTAX      Counter64
   MAX-ACCESS  read-only
   STATUS      current
   DESCRIPTION
      "Path: efm.performance.pppoEClient.mibCounters.d7Performance.ifInUnknownProtos

       64 bit unsigned wrappable counter."
   ::= {pr1646v2XEfmPPPoEMCD7PEntry 150994944}

pr1646v2XEfmPPPoEMCD7PInDropEx OBJECT-TYPE
   SYNTAX      Counter64
   MAX-ACCESS  read-only
   STATUS      current
   DESCRIPTION
      "Path: efm.performance.pppoEClient.mibCounters.d7Performance.ifInDropLevelExceeded

       64 bit unsigned wrappable counter."
   ::= {pr1646v2XEfmPPPoEMCD7PEntry 335544320}

pr1646v2XEfmPPPoEMCD7PInDropNoMac OBJECT-TYPE
   SYNTAX      Counter64
   MAX-ACCESS  read-only
   STATUS      current
   DESCRIPTION
      "Path: efm.performance.pppoEClient.mibCounters.d7Performance.fInDiscardsNoMacFit

       64 bit unsigned wrappable counter."
   ::= {pr1646v2XEfmPPPoEMCD7PEntry 301989888}

pr1646v2XEfmPPPoEMCD7PInDropNUCast OBJECT-TYPE
   SYNTAX      Counter64
   MAX-ACCESS  read-only
   STATUS      current
   DESCRIPTION
      "Path: efm.performance.pppoEClient.mibCounters.d7Performance.fInDiscardsNUCast

       64 bit unsigned wrappable counter."
   ::= {pr1646v2XEfmPPPoEMCD7PEntry 318767104}

pr1646v2XEfmPPPoEMCD7PInDropFilter OBJECT-TYPE
   SYNTAX      Counter64
   MAX-ACCESS  read-only
   STATUS      current
   DESCRIPTION
      "Path: efm.performance.pppoEClient.mibCounters.d7Performance.fInDiscardsFilter

       64 bit unsigned wrappable counter."
   ::= {pr1646v2XEfmPPPoEMCD7PEntry 385875968}

pr1646v2XEfmPPPoEMCD7PIfInBandwidth OBJECT-TYPE
   SYNTAX      Integer32
   MAX-ACCESS  read-only
   STATUS      current
   DESCRIPTION
      "Path: efm.performance.pppoEClient.mibCounters.d7Performance.ifInBandwidth

       unit name = bps
       formula = 8 * ; 8 /"
   ::= {pr1646v2XEfmPPPoEMCD7PEntry 268435456}

pr1646v2XEfmPPPoEMCD7PIfOutOctets OBJECT-TYPE
   SYNTAX      Counter64
   MAX-ACCESS  read-only
   STATUS      current
   DESCRIPTION
      "Path: efm.performance.pppoEClient.mibCounters.d7Performance.ifOutOctets

       64 bit unsigned wrappable counter."
   ::= {pr1646v2XEfmPPPoEMCD7PEntry 167772160}

pr1646v2XEfmPPPoEMCD7PIfOutUCPkts OBJECT-TYPE
   SYNTAX      Counter64
   MAX-ACCESS  read-only
   STATUS      current
   DESCRIPTION
      "Path: efm.performance.pppoEClient.mibCounters.d7Performance.ifOutUcastPkts

       64 bit unsigned wrappable counter."
   ::= {pr1646v2XEfmPPPoEMCD7PEntry 184549376}

pr1646v2XEfmPPPoEMCD7PIfOutNUCPkts OBJECT-TYPE
   SYNTAX      Counter64
   MAX-ACCESS  read-only
   STATUS      current
   DESCRIPTION
      "Path: efm.performance.pppoEClient.mibCounters.d7Performance.ifOutNUcastPkts

       64 bit unsigned wrappable counter."
   ::= {pr1646v2XEfmPPPoEMCD7PEntry 201326592}

pr1646v2XEfmPPPoEMCD7PIfOutBCPkts OBJECT-TYPE
   SYNTAX      Counter64
   MAX-ACCESS  read-only
   STATUS      current
   DESCRIPTION
      "Path: efm.performance.pppoEClient.mibCounters.d7Performance.ifOutBcastPkts

       64 bit unsigned wrappable counter."
   ::= {pr1646v2XEfmPPPoEMCD7PEntry 452984832}

pr1646v2XEfmPPPoEMCD7PIfOutMCPkts OBJECT-TYPE
   SYNTAX      Counter64
   MAX-ACCESS  read-only
   STATUS      current
   DESCRIPTION
      "Path: efm.performance.pppoEClient.mibCounters.d7Performance.ifOutMcastPkts

       64 bit unsigned wrappable counter."
   ::= {pr1646v2XEfmPPPoEMCD7PEntry 469762048}

pr1646v2XEfmPPPoEMCD7PIfOutDiscards OBJECT-TYPE
   SYNTAX      Counter64
   MAX-ACCESS  read-only
   STATUS      current
   DESCRIPTION
      "Path: efm.performance.pppoEClient.mibCounters.d7Performance.ifOutDiscards

       64 bit unsigned wrappable counter."
   ::= {pr1646v2XEfmPPPoEMCD7PEntry 218103808}

pr1646v2XEfmPPPoEMCD7PIfOutErrors OBJECT-TYPE
   SYNTAX      Counter64
   MAX-ACCESS  read-only
   STATUS      current
   DESCRIPTION
      "Path: efm.performance.pppoEClient.mibCounters.d7Performance.ifOutErrors

       64 bit unsigned wrappable counter."
   ::= {pr1646v2XEfmPPPoEMCD7PEntry 234881024}

pr1646v2XEfmPPPoEMCD7POutDropEx OBJECT-TYPE
   SYNTAX      Counter64
   MAX-ACCESS  read-only
   STATUS      current
   DESCRIPTION
      "Path: efm.performance.pppoEClient.mibCounters.d7Performance.ifOutDropLevelExceeded

       64 bit unsigned wrappable counter."
   ::= {pr1646v2XEfmPPPoEMCD7PEntry 352321536}

pr1646v2XEfmPPPoEMCD7POutDropNoArp OBJECT-TYPE
   SYNTAX      Counter64
   MAX-ACCESS  read-only
   STATUS      current
   DESCRIPTION
      "Path: efm.performance.pppoEClient.mibCounters.d7Performance.ifOutDiscardsNoArp

       64 bit unsigned wrappable counter."
   ::= {pr1646v2XEfmPPPoEMCD7PEntry 369098752}

pr1646v2XEfmPPPoEMCD7POutDropFilter OBJECT-TYPE
   SYNTAX      Counter64
   MAX-ACCESS  read-only
   STATUS      current
   DESCRIPTION
      "Path: efm.performance.pppoEClient.mibCounters.d7Performance.ifOutDiscardsFilter

       64 bit unsigned wrappable counter."
   ::= {pr1646v2XEfmPPPoEMCD7PEntry 402653184}

pr1646v2XEfmPPPoEMCD7PIfOutBandwidth OBJECT-TYPE
   SYNTAX      Integer32
   MAX-ACCESS  read-only
   STATUS      current
   DESCRIPTION
      "Path: efm.performance.pppoEClient.mibCounters.d7Performance.ifOutBandwidth

       unit name = bps
       formula = 8 * ; 8 /"
   ::= {pr1646v2XEfmPPPoEMCD7PEntry 285212672}

pr1646v2XEfmPPPoEMCD7PIfErrSec OBJECT-TYPE
   SYNTAX      Counter32
   MAX-ACCESS  read-only
   STATUS      current
   DESCRIPTION
      "Path: efm.performance.pppoEClient.mibCounters.d7Performance.ifErrSec

       32 bit unsigned wrappable counter."
   ::= {pr1646v2XEfmPPPoEMCD7PEntry 251658240}



ar1646v2XEfm OBJECT IDENTIFIER ::= {r1646v2XEfm 16}


ar1646v2XEfmClearCounters OBJECT-TYPE
   SYNTAX      Integer32
   MAX-ACCESS  read-write
   STATUS      current
   DESCRIPTION
      "Path: efm.actions.clearCounters
       Info: reset counters"
   ::= {ar1646v2XEfm 263}


ar1646v2XEfmPowerToggle OBJECT-TYPE
   SYNTAX      Integer32
   MAX-ACCESS  read-write
   STATUS      current
   DESCRIPTION
      "Path: efm.actions.powerToggle
       Info: action in the debug group"
   ::= {ar1646v2XEfm 68}


ar1646v2XEfmStopAutoNeg OBJECT-TYPE
   SYNTAX      Integer32
   MAX-ACCESS  read-write
   STATUS      current
   DESCRIPTION
      "Path: efm.actions.stopAutoNeg
       Info: action in the debug group"
   ::= {ar1646v2XEfm 79}


ar1646v2XEfmRestartIntf OBJECT-TYPE
   SYNTAX      Integer32
   MAX-ACCESS  read-write
   STATUS      current
   DESCRIPTION
      "Path: efm.actions.restartIntf
       Info: action in the debug group"
   ::= {ar1646v2XEfm 67}


ar1646v2XEfmClearOamEventLog OBJECT-TYPE
   SYNTAX      Integer32
   MAX-ACCESS  read-write
   STATUS      current
   DESCRIPTION
      "Path: efm.actions.clearOamEventLog
       Info: clear the OAM event log"
   ::= {ar1646v2XEfm 916}


ar1646v2XEfmLoopback OBJECT-TYPE
   SYNTAX      Integer32
   MAX-ACCESS  read-write
   STATUS      current
   DESCRIPTION
      "Path: efm.actions.loopback
       Info: ethernet loopback"
   ::= {ar1646v2XEfm 914}


ar1646v2XEfmLoop OBJECT IDENTIFIER ::= {ar1646v2XEfm 915}

ar1646v2XEfmLoopSSC OBJECT IDENTIFIER ::= {ar1646v2XEfmLoop 1}

ar1646v2XEfmLoopEntry OBJECT IDENTIFIER ::= {ar1646v2XEfmLoopSSC 1}

ar1646v2XEfmLoopAction OBJECT-TYPE
   SYNTAX      INTEGER
               {
               start (1),
               stop (2)
               }
   MAX-ACCESS  read-write
   STATUS      current
   DESCRIPTION
      "Path: efm.actions.loop.action

       Possibilities:
               start   (1)
               stop   (2)"
   ::= {ar1646v2XEfmLoopEntry 16777216}

ar1646v2XEfmLoopTime OBJECT-TYPE
   SYNTAX      TimeTicks
   MAX-ACCESS  read-write
   STATUS      current
   DESCRIPTION
      "Path: efm.actions.loop.time

       Time in centi-second."
   ::= {ar1646v2XEfmLoopEntry 50331648}

ar1646v2XEfmLoopIntfName OBJECT-TYPE
   SYNTAX      DisplayString
   MAX-ACCESS  read-write
   STATUS      current
   DESCRIPTION
      "Path: efm.actions.loop.intfName"
   ::= {ar1646v2XEfmLoopEntry 67108864}


ar1646v2XEfmOamRemLoopback OBJECT-TYPE
   SYNTAX      Integer32
   MAX-ACCESS  read-write
   STATUS      current
   DESCRIPTION
      "Path: efm.actions.oamRemLoopback
       Info: OAM Remote Loopback"
   ::= {ar1646v2XEfm 912}


ar1646v2XEfmType OBJECT-TYPE
   SYNTAX      INTEGER
               {
               start (0),
               stop (1)
               }
   MAX-ACCESS  read-write
   STATUS      current
   DESCRIPTION
      "Path: efm.actions.type
       Info: OAM Remote Loopback type

       Possibilities:
               start   (0)
               stop   (1)"
   ::= {ar1646v2XEfm 913}


ar1646v2XEfmSendWOL OBJECT-TYPE
   SYNTAX      Integer32
   MAX-ACCESS  read-write
   STATUS      current
   DESCRIPTION
      "Path: efm.actions.sendWOL
       Info: send a WakeOnLan message on this interface"
   ::= {ar1646v2XEfm 333}


ar1646v2XEfmWolInfo OBJECT IDENTIFIER ::= {ar1646v2XEfm 332}

ar1646v2XEfmWolInfoSSC OBJECT IDENTIFIER ::= {ar1646v2XEfmWolInfo 1}

ar1646v2XEfmWolInfoEntry OBJECT IDENTIFIER ::= {ar1646v2XEfmWolInfoSSC 1}

ar1646v2XEfmWolInfoTargetMAC OBJECT-TYPE
   SYNTAX      OCTET STRING
   MAX-ACCESS  read-write
   STATUS      current
   DESCRIPTION
      "Path: efm.actions.wolInfo.targetMAC

       MAC address."
   ::= {ar1646v2XEfmWolInfoEntry 16777216}

ar1646v2XEfmWolInfoPassword OBJECT-TYPE
   SYNTAX      OCTET STRING
   MAX-ACCESS  read-write
   STATUS      current
   DESCRIPTION
      "Path: efm.actions.wolInfo.password"
   ::= {ar1646v2XEfmWolInfoEntry 33554432}


ar1646v2XEfmClearArpCache OBJECT-TYPE
   SYNTAX      Integer32
   MAX-ACCESS  read-write
   STATUS      current
   DESCRIPTION
      "Path: efm.actions.clearArpCache
       Info: clear all dynamic enties in ARP cache table"
   ::= {ar1646v2XEfm 25}



END
