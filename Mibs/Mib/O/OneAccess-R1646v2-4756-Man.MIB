OneAccess-R1646v2-4756-Man DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Man OBJECT IDENTIFIER ::= {r1646Rootv2 4756}

r1646v2ManMOProp OBJECT IDENTIFIER ::= {r1646v2Man 1}

r1646v2ManMOPropEntry OBJECT IDENTIFIER ::= {r1646v2ManMOProp 1}

r1646v2ManMOPropPath OBJECT-TYPE
   SYNTAX      ContainmentPath
   MAX-ACCESS  read-only
   STATUS      current
   DESCRIPTION
      "Textual description of the containment tree from the instance of
       the root object down to the instance of the current object."
   ::= {r1646v2ManMOPropEntry 3}

r1646v2ManMOPropRev OBJECT-TYPE
   SYNTAX      ObjectRevision
   MAX-ACCESS  read-only
   STATUS      current
   DESCRIPTION
      "This value corresponds with the revision of the MANAGED OBJECT."
   ::= {r1646v2ManMOPropEntry 4}



er1646v2Man OBJECT IDENTIFIER ::= {r1646v2Man 11}


er1646v2ManCms2Address OBJECT-TYPE
   SYNTAX      Integer32
   MAX-ACCESS  read-write
   STATUS      current
   DESCRIPTION
      "Path: management.editConf.cms2Address
       Info: cms2Address"
   ::= {er1646v2Man 1}


er1646v2ManElementManSecrets OBJECT IDENTIFIER ::= {er1646v2Man 33}

er1646v2ManElementManSecretsSSCTable OBJECT-TYPE
   SYNTAX      SEQUENCE OF Er1646v2ManElementManSecretsEntry
   MAX-ACCESS  not-accessible
   STATUS      current
   DESCRIPTION
      ""
   ::= {er1646v2ManElementManSecrets 1}

er1646v2ManElementManSecretsEntry OBJECT-TYPE
   SYNTAX      Er1646v2ManElementManSecretsEntry
   MAX-ACCESS  not-accessible
   STATUS      current
   DESCRIPTION
      ""
   INDEX      { er1646v2ManElementManSecretsTableIx }
   ::= {er1646v2ManElementManSecretsSSCTable 1}

Er1646v2ManElementManSecretsEntry ::=
   SEQUENCE
      {
      er1646v2ManElementManSecretsActions
         VariableLengthTableActions,
      er1646v2ManElementManSecretsTableIx
         TableIndex,
      er1646v2ManElementManSecretsRemark
         DisplayString,
      er1646v2ManElementManSecretsPassword
         DisplayString,
      er1646v2ManElementManSecretsEncModePassw
         INTEGER,
      er1646v2ManElementManSecretsEncPassword
         DisplayString
      }

er1646v2ManElementManSecretsActions OBJECT-TYPE
   SYNTAX      VariableLengthTableActions
   MAX-ACCESS  read-write
   STATUS      current
   DESCRIPTION
      "By way of this field, some manipulations
       on this table may be performed."
   ::= {er1646v2ManElementManSecretsEntry 2}

er1646v2ManElementManSecretsTableIx OBJECT-TYPE
   SYNTAX      TableIndex
   MAX-ACCESS  not-accessible
   STATUS      current
   DESCRIPTION
      ""
   ::= {er1646v2ManElementManSecretsEntry 11}

er1646v2ManElementManSecretsRemark OBJECT-TYPE
   SYNTAX      DisplayString
   MAX-ACCESS  read-write
   STATUS      current
   DESCRIPTION
      "Path: management.editConf.elementManSecrets.remark"
   ::= {er1646v2ManElementManSecretsEntry 67108864}

er1646v2ManElementManSecretsPassword OBJECT-TYPE
   SYNTAX      DisplayString
   MAX-ACCESS  read-write
   STATUS      current
   DESCRIPTION
      "Path: management.editConf.elementManSecrets.password"
   ::= {er1646v2ManElementManSecretsEntry 16777216}

er1646v2ManElementManSecretsEncModePassw OBJECT-TYPE
   SYNTAX      INTEGER
               {
               none (1),
               encrypt (2),
               encType1 (3),
               invalid (128)
               }
   MAX-ACCESS  read-write
   STATUS      current
   DESCRIPTION
      "Path: management.editConf.elementManSecrets.encModePassw

       Possibilities:
               none   (1)
               encrypt   (2)
               encType1   (3)
               invalid   (128)"
   ::= {er1646v2ManElementManSecretsEntry 100663296}

er1646v2ManElementManSecretsEncPassword OBJECT-TYPE
   SYNTAX      DisplayString
   MAX-ACCESS  read-write
   STATUS      current
   DESCRIPTION
      "Path: management.editConf.elementManSecrets.encPassword"
   ::= {er1646v2ManElementManSecretsEntry 83886080}


er1646v2ManElementManDetect OBJECT IDENTIFIER ::= {er1646v2Man 48}

er1646v2ManElementManDetectSSCTable OBJECT-TYPE
   SYNTAX      SEQUENCE OF Er1646v2ManElementManDetectEntry
   MAX-ACCESS  not-accessible
   STATUS      current
   DESCRIPTION
      ""
   ::= {er1646v2ManElementManDetect 1}

er1646v2ManElementManDetectEntry OBJECT-TYPE
   SYNTAX      Er1646v2ManElementManDetectEntry
   MAX-ACCESS  not-accessible
   STATUS      current
   DESCRIPTION
      ""
   INDEX      { er1646v2ManElementManDetectTableIx }
   ::= {er1646v2ManElementManDetectSSCTable 1}

Er1646v2ManElementManDetectEntry ::=
   SEQUENCE
      {
      er1646v2ManElementManDetectActions
         VariableLengthTableActions,
      er1646v2ManElementManDetectTableIx
         TableIndex,
      er1646v2ManElementManDetectRemark
         DisplayString,
      er1646v2ManElementManDetectDiscoverState
         INTEGER,
      er1646v2ManElementManDetectServer
         DisplayString,
      er1646v2ManElementManDetectSource
         DisplayString,
      er1646v2ManElementManDetectUdpPort
         Integer32,
      er1646v2ManElementManDetectVrfRouter
         DisplayString,
      er1646v2ManElementManDetectPassword
         DisplayString,
      er1646v2ManElementManDetectEncModePassw
         INTEGER,
      er1646v2ManElementManDetectEncPassword
         DisplayString,
      er1646v2ManElementManDetectPath
         DisplayString
      }

er1646v2ManElementManDetectActions OBJECT-TYPE
   SYNTAX      VariableLengthTableActions
   MAX-ACCESS  read-write
   STATUS      current
   DESCRIPTION
      "By way of this field, some manipulations
       on this table may be performed."
   ::= {er1646v2ManElementManDetectEntry 2}

er1646v2ManElementManDetectTableIx OBJECT-TYPE
   SYNTAX      TableIndex
   MAX-ACCESS  not-accessible
   STATUS      current
   DESCRIPTION
      ""
   ::= {er1646v2ManElementManDetectEntry 11}

er1646v2ManElementManDetectRemark OBJECT-TYPE
   SYNTAX      DisplayString
   MAX-ACCESS  read-write
   STATUS      current
   DESCRIPTION
      "Path: management.editConf.elementManDetect.remark"
   ::= {er1646v2ManElementManDetectEntry 67108864}

er1646v2ManElementManDetectDiscoverState OBJECT-TYPE
   SYNTAX      INTEGER
               {
               disabled (1),
               enabled (2)
               }
   MAX-ACCESS  read-write
   STATUS      current
   DESCRIPTION
      "Path: management.editConf.elementManDetect.discoverState

       Possibilities:
               disabled   (1)
               enabled   (2)"
   ::= {er1646v2ManElementManDetectEntry 285212672}

er1646v2ManElementManDetectServer OBJECT-TYPE
   SYNTAX      DisplayString
   MAX-ACCESS  read-write
   STATUS      current
   DESCRIPTION
      "Path: management.editConf.elementManDetect.server"
   ::= {er1646v2ManElementManDetectEntry 218103808}

er1646v2ManElementManDetectSource OBJECT-TYPE
   SYNTAX      DisplayString
   MAX-ACCESS  read-write
   STATUS      current
   DESCRIPTION
      "Path: management.editConf.elementManDetect.source"
   ::= {er1646v2ManElementManDetectEntry 234881024}

er1646v2ManElementManDetectUdpPort OBJECT-TYPE
   SYNTAX      Integer32
   MAX-ACCESS  read-write
   STATUS      current
   DESCRIPTION
      "Path: management.editConf.elementManDetect.udpPort"
   ::= {er1646v2ManElementManDetectEntry 251658240}

er1646v2ManElementManDetectVrfRouter OBJECT-TYPE
   SYNTAX      DisplayString
   MAX-ACCESS  read-write
   STATUS      current
   DESCRIPTION
      "Path: management.editConf.elementManDetect.vrfRouter"
   ::= {er1646v2ManElementManDetectEntry 201326592}

er1646v2ManElementManDetectPassword OBJECT-TYPE
   SYNTAX      DisplayString
   MAX-ACCESS  read-write
   STATUS      current
   DESCRIPTION
      "Path: management.editConf.elementManDetect.password"
   ::= {er1646v2ManElementManDetectEntry 16777216}

er1646v2ManElementManDetectEncModePassw OBJECT-TYPE
   SYNTAX      INTEGER
               {
               none (1),
               encrypt (2),
               encType1 (3),
               invalid (128)
               }
   MAX-ACCESS  read-write
   STATUS      current
   DESCRIPTION
      "Path: management.editConf.elementManDetect.encModePassw

       Possibilities:
               none   (1)
               encrypt   (2)
               encType1   (3)
               invalid   (128)"
   ::= {er1646v2ManElementManDetectEntry 100663296}

er1646v2ManElementManDetectEncPassword OBJECT-TYPE
   SYNTAX      DisplayString
   MAX-ACCESS  read-write
   STATUS      current
   DESCRIPTION
      "Path: management.editConf.elementManDetect.encPassword"
   ::= {er1646v2ManElementManDetectEntry 83886080}

er1646v2ManElementManDetectPath OBJECT-TYPE
   SYNTAX      DisplayString
   MAX-ACCESS  read-write
   STATUS      current
   DESCRIPTION
      "Path: management.editConf.elementManDetect.path"
   ::= {er1646v2ManElementManDetectEntry 268435456}


er1646v2ManElementManSaveStatFiles OBJECT IDENTIFIER ::= {er1646v2Man 49}

er1646v2ManElementManSaveStatFilesSSCTable OBJECT-TYPE
   SYNTAX      SEQUENCE OF Er1646v2ManElementManSaveStatFilesEntry
   MAX-ACCESS  not-accessible
   STATUS      current
   DESCRIPTION
      ""
   ::= {er1646v2ManElementManSaveStatFiles 1}

er1646v2ManElementManSaveStatFilesEntry OBJECT-TYPE
   SYNTAX      Er1646v2ManElementManSaveStatFilesEntry
   MAX-ACCESS  not-accessible
   STATUS      current
   DESCRIPTION
      ""
   INDEX      { er1646v2ManElementManSaveStatFilesTableIx }
   ::= {er1646v2ManElementManSaveStatFilesSSCTable 1}

Er1646v2ManElementManSaveStatFilesEntry ::=
   SEQUENCE
      {
      er1646v2ManElementManSaveStatFilesActions
         VariableLengthTableActions,
      er1646v2ManElementManSaveStatFilesTableIx
         TableIndex,
      er1646v2ManElementManSaveStatFilesRemark
         DisplayString,
      er1646v2ManElementManSaveStatFilesServer
         DisplayString,
      er1646v2ManElementManSaveStatFilesSource
         DisplayString,
      er1646v2ManElementManSaveStatFilesUdpPort
         Integer32,
      er1646v2ManElementManSaveStatFilesVrfRouter
         DisplayString,
      er1646v2ManElementManSaveStatFilesPassword
         DisplayString,
      er1646v2ManElementManSaveStatFilesEncModePassw
         INTEGER,
      er1646v2ManElementManSaveStatFilesEncPassword
         DisplayString
      }

er1646v2ManElementManSaveStatFilesActions OBJECT-TYPE
   SYNTAX      VariableLengthTableActions
   MAX-ACCESS  read-write
   STATUS      current
   DESCRIPTION
      "By way of this field, some manipulations
       on this table may be performed."
   ::= {er1646v2ManElementManSaveStatFilesEntry 2}

er1646v2ManElementManSaveStatFilesTableIx OBJECT-TYPE
   SYNTAX      TableIndex
   MAX-ACCESS  not-accessible
   STATUS      current
   DESCRIPTION
      ""
   ::= {er1646v2ManElementManSaveStatFilesEntry 11}

er1646v2ManElementManSaveStatFilesRemark OBJECT-TYPE
   SYNTAX      DisplayString
   MAX-ACCESS  read-write
   STATUS      current
   DESCRIPTION
      "Path: management.editConf.elementManSaveStatFiles.remark"
   ::= {er1646v2ManElementManSaveStatFilesEntry 67108864}

er1646v2ManElementManSaveStatFilesServer OBJECT-TYPE
   SYNTAX      DisplayString
   MAX-ACCESS  read-write
   STATUS      current
   DESCRIPTION
      "Path: management.editConf.elementManSaveStatFiles.server"
   ::= {er1646v2ManElementManSaveStatFilesEntry 218103808}

er1646v2ManElementManSaveStatFilesSource OBJECT-TYPE
   SYNTAX      DisplayString
   MAX-ACCESS  read-write
   STATUS      current
   DESCRIPTION
      "Path: management.editConf.elementManSaveStatFiles.source"
   ::= {er1646v2ManElementManSaveStatFilesEntry 234881024}

er1646v2ManElementManSaveStatFilesUdpPort OBJECT-TYPE
   SYNTAX      Integer32
   MAX-ACCESS  read-write
   STATUS      current
   DESCRIPTION
      "Path: management.editConf.elementManSaveStatFiles.udpPort"
   ::= {er1646v2ManElementManSaveStatFilesEntry 251658240}

er1646v2ManElementManSaveStatFilesVrfRouter OBJECT-TYPE
   SYNTAX      DisplayString
   MAX-ACCESS  read-write
   STATUS      current
   DESCRIPTION
      "Path: management.editConf.elementManSaveStatFiles.vrfRouter"
   ::= {er1646v2ManElementManSaveStatFilesEntry 201326592}

er1646v2ManElementManSaveStatFilesPassword OBJECT-TYPE
   SYNTAX      DisplayString
   MAX-ACCESS  read-write
   STATUS      current
   DESCRIPTION
      "Path: management.editConf.elementManSaveStatFiles.password"
   ::= {er1646v2ManElementManSaveStatFilesEntry 16777216}

er1646v2ManElementManSaveStatFilesEncModePassw OBJECT-TYPE
   SYNTAX      INTEGER
               {
               none (1),
               encrypt (2),
               encType1 (3),
               invalid (128)
               }
   MAX-ACCESS  read-write
   STATUS      current
   DESCRIPTION
      "Path: management.editConf.elementManSaveStatFiles.encModePassw

       Possibilities:
               none   (1)
               encrypt   (2)
               encType1   (3)
               invalid   (128)"
   ::= {er1646v2ManElementManSaveStatFilesEntry 100663296}

er1646v2ManElementManSaveStatFilesEncPassword OBJECT-TYPE
   SYNTAX      DisplayString
   MAX-ACCESS  read-write
   STATUS      current
   DESCRIPTION
      "Path: management.editConf.elementManSaveStatFiles.encPassword"
   ::= {er1646v2ManElementManSaveStatFilesEntry 83886080}


er1646v2ManAccList OBJECT IDENTIFIER ::= {er1646v2Man 17}

er1646v2ManAccListSSCTable OBJECT-TYPE
   SYNTAX      SEQUENCE OF Er1646v2ManAccListEntry
   MAX-ACCESS  not-accessible
   STATUS      current
   DESCRIPTION
      "simple access list based on source IP address only"
   ::= {er1646v2ManAccList 1}

er1646v2ManAccListEntry OBJECT-TYPE
   SYNTAX      Er1646v2ManAccListEntry
   MAX-ACCESS  not-accessible
   STATUS      current
   DESCRIPTION
      ""
   INDEX      { er1646v2ManAccListTableIx }
   ::= {er1646v2ManAccListSSCTable 1}

Er1646v2ManAccListEntry ::=
   SEQUENCE
      {
      er1646v2ManAccListActions
         VariableLengthTableActions,
      er1646v2ManAccListTableIx
         TableIndex,
      er1646v2ManAccListSourceAddress
         IpAddress,
      er1646v2ManAccListMask
         IpAddress,
      er1646v2ManAccListAction
         INTEGER
      }

er1646v2ManAccListActions OBJECT-TYPE
   SYNTAX      VariableLengthTableActions
   MAX-ACCESS  read-write
   STATUS      current
   DESCRIPTION
      "By way of this field, some manipulations
       on this table may be performed."
   ::= {er1646v2ManAccListEntry 2}

er1646v2ManAccListTableIx OBJECT-TYPE
   SYNTAX      TableIndex
   MAX-ACCESS  not-accessible
   STATUS      current
   DESCRIPTION
      ""
   ::= {er1646v2ManAccListEntry 11}

er1646v2ManAccListSourceAddress OBJECT-TYPE
   SYNTAX      IpAddress
   MAX-ACCESS  read-write
   STATUS      current
   DESCRIPTION
      "Path: management.editConf.accessList.sourceAddress"
   ::= {er1646v2ManAccListEntry 16777216}

er1646v2ManAccListMask OBJECT-TYPE
   SYNTAX      IpAddress
   MAX-ACCESS  read-write
   STATUS      current
   DESCRIPTION
      "Path: management.editConf.accessList.mask"
   ::= {er1646v2ManAccListEntry 33554432}

er1646v2ManAccListAction OBJECT-TYPE
   SYNTAX      INTEGER
               {
               deny (0),
               allow (1)
               }
   MAX-ACCESS  read-write
   STATUS      current
   DESCRIPTION
      "Path: management.editConf.accessList.action

       Possibilities:
               deny   (0)
               allow   (1)"
   ::= {er1646v2ManAccListEntry 50331648}


er1646v2ManTma OBJECT-TYPE
   SYNTAX      INTEGER
               {
               disabled (0),
               enabled (1)
               }
   MAX-ACCESS  read-write
   STATUS      current
   DESCRIPTION
      "Path: management.editConf.tma
       Info: Attribute that controls the orchid how to treat the UDP packets for the TMA port
                         enabled:    act on UDP packets destined for the TMA port
                         disabled:   discard UDP packets destined for the TMA port

       Possibilities:
               disabled   (0)
               enabled   (1)"
   ::= {er1646v2Man 36}


er1646v2ManSnmp OBJECT-TYPE
   SYNTAX      INTEGER
               {
               disabled (0),
               enabled (1)
               }
   MAX-ACCESS  read-write
   STATUS      current
   DESCRIPTION
      "Path: management.editConf.snmp
       Info: Attribute that controls the orchid how to treat the UDP packets for the SNMP port (161)
                         enabled:    act on UDP packets destined for the SNMP port
                         disabled:   discard UDP packets destined for the SNMP port

       Possibilities:
               disabled   (0)
               enabled   (1)"
   ::= {er1646v2Man 18}


er1646v2ManTelnet OBJECT-TYPE
   SYNTAX      INTEGER
               {
               disabled (0),
               enabled (1)
               }
   MAX-ACCESS  read-write
   STATUS      current
   DESCRIPTION
      "Path: management.editConf.telnet
       Info: Attribute that controls the orchid how to treat the TCP packets for the TELNET port
                         enabled:    act on TCP packets destined for the TELNET port
                         disabled:   discard TCP packets destined for the TELNET port

       Possibilities:
               disabled   (0)
               enabled   (1)"
   ::= {er1646v2Man 19}


er1646v2ManTftp OBJECT-TYPE
   SYNTAX      INTEGER
               {
               disabled (0),
               enabled (1)
               }
   MAX-ACCESS  read-write
   STATUS      current
   DESCRIPTION
      "Path: management.editConf.tftp
       Info: Attribute that controls the orchid how to treat the UDP packets for the TFTP port
                         enabled:    act on UDP packets destined for the TFTP port
                         disabled:   discard UDP packets destined for the TFTP port

       Possibilities:
               disabled   (0)
               enabled   (1)"
   ::= {er1646v2Man 20}


er1646v2ManFtp OBJECT-TYPE
   SYNTAX      INTEGER
               {
               disabled (0),
               enabled (1)
               }
   MAX-ACCESS  read-write
   STATUS      current
   DESCRIPTION
      "Path: management.editConf.ftp
       Info: Attribute that controls the orchid how to treat the TCP packets for FTP
                         enabled:    act on TCP packets destined FTP
                         disabled:   discard TCP packets destined FTP

       Possibilities:
               disabled   (0)
               enabled   (1)"
   ::= {er1646v2Man 23}


er1646v2ManTcp OBJECT IDENTIFIER ::= {er1646v2Man 34}

er1646v2ManTcpSSC OBJECT IDENTIFIER ::= {er1646v2ManTcp 1}

er1646v2ManTcpEntry OBJECT IDENTIFIER ::= {er1646v2ManTcpSSC 1}

er1646v2ManTcpMaxReceiveWindow OBJECT-TYPE
   SYNTAX      Integer32
   MAX-ACCESS  read-write
   STATUS      current
   DESCRIPTION
      "Path: management.editConf.tcp.maxReceiveWindow"
   ::= {er1646v2ManTcpEntry 16777216}

er1646v2ManTcpMaxSegmentSize OBJECT-TYPE
   SYNTAX      Integer32
   MAX-ACCESS  read-write
   STATUS      current
   DESCRIPTION
      "Path: management.editConf.tcp.maxSegmentSize"
   ::= {er1646v2ManTcpEntry 33554432}


er1646v2ManBanner OBJECT IDENTIFIER ::= {er1646v2Man 37}

er1646v2ManBannerMotd OBJECT-TYPE
   SYNTAX      SEQUENCE OF Er1646v2ManBannerMotdEntry
   MAX-ACCESS  not-accessible
   STATUS      current
   DESCRIPTION
      ""
   ::= {er1646v2ManBanner 16777216}

er1646v2ManBannerMotdEntry OBJECT-TYPE
   SYNTAX      Er1646v2ManBannerMotdEntry
   MAX-ACCESS  not-accessible
   STATUS      current
   DESCRIPTION
      ""
   INDEX      { er1646v2ManBannerMotdTableIx }
   ::= {er1646v2ManBannerMotd 1}

Er1646v2ManBannerMotdEntry ::=
   SEQUENCE
      {
      er1646v2ManBannerMotdActions
         VariableLengthTableActions,
      er1646v2ManBannerMotdTableIx
         TableIndex,
      er1646v2ManBannerMotdText
         DisplayString
      }

er1646v2ManBannerMotdActions OBJECT-TYPE
   SYNTAX      VariableLengthTableActions
   MAX-ACCESS  read-write
   STATUS      current
   DESCRIPTION
      "By way of this field, some manipulations
       on this table may be performed."
   ::= {er1646v2ManBannerMotdEntry 2}

er1646v2ManBannerMotdTableIx OBJECT-TYPE
   SYNTAX      TableIndex
   MAX-ACCESS  not-accessible
   STATUS      current
   DESCRIPTION
      ""
   ::= {er1646v2ManBannerMotdEntry 11}

er1646v2ManBannerMotdText OBJECT-TYPE
   SYNTAX      DisplayString
   MAX-ACCESS  read-write
   STATUS      current
   DESCRIPTION
      "Path: management.editConf.banner.motd.text"
   ::= {er1646v2ManBannerMotdEntry 16777216}

er1646v2ManBannerExec OBJECT-TYPE
   SYNTAX      SEQUENCE OF Er1646v2ManBannerExecEntry
   MAX-ACCESS  not-accessible
   STATUS      current
   DESCRIPTION
      ""
   ::= {er1646v2ManBanner 33554432}

er1646v2ManBannerExecEntry OBJECT-TYPE
   SYNTAX      Er1646v2ManBannerExecEntry
   MAX-ACCESS  not-accessible
   STATUS      current
   DESCRIPTION
      ""
   INDEX      { er1646v2ManBannerExecTableIx }
   ::= {er1646v2ManBannerExec 1}

Er1646v2ManBannerExecEntry ::=
   SEQUENCE
      {
      er1646v2ManBannerExecActions
         VariableLengthTableActions,
      er1646v2ManBannerExecTableIx
         TableIndex,
      er1646v2ManBannerExecText
         DisplayString
      }

er1646v2ManBannerExecActions OBJECT-TYPE
   SYNTAX      VariableLengthTableActions
   MAX-ACCESS  read-write
   STATUS      current
   DESCRIPTION
      "By way of this field, some manipulations
       on this table may be performed."
   ::= {er1646v2ManBannerExecEntry 2}

er1646v2ManBannerExecTableIx OBJECT-TYPE
   SYNTAX      TableIndex
   MAX-ACCESS  not-accessible
   STATUS      current
   DESCRIPTION
      ""
   ::= {er1646v2ManBannerExecEntry 11}

er1646v2ManBannerExecText OBJECT-TYPE
   SYNTAX      DisplayString
   MAX-ACCESS  read-write
   STATUS      current
   DESCRIPTION
      "Path: management.editConf.banner.exec.text"
   ::= {er1646v2ManBannerExecEntry 16777216}


er1646v2ManAutoConfigure OBJECT-TYPE
   SYNTAX      INTEGER
               {
               enabled (0),
               onTftpServer (1),
               onBootFile (2),
               onTftpServerAndBootFile (3),
               disabled (4)
               }
   MAX-ACCESS  read-write
   STATUS      current
   DESCRIPTION
      "Path: management.editConf.autoConfigure
       Info: set restrictions to auto configuration using TFTP

       Possibilities:
               enabled   (0)
               onTftpServer   (1)
               onBootFile   (2)
               onTftpServerAndBootFile   (3)
               disabled   (4)"
   ::= {er1646v2Man 35}


er1646v2ManAlignStatsToRtc OBJECT-TYPE
   SYNTAX      INTEGER
               {
               enabled (1),
               disabled (2)
               }
   MAX-ACCESS  read-write
   STATUS      current
   DESCRIPTION
      "Path: management.editConf.alignStatsToRtc
       Info: align statistics to real-time clock

       Possibilities:
               enabled   (1)
               disabled   (2)"
   ::= {er1646v2Man 214}


er1646v2ManStatisticTable OBJECT IDENTIFIER ::= {er1646v2Man 38}

er1646v2ManStatisticTableSSC OBJECT IDENTIFIER ::= {er1646v2ManStatisticTable 1}

er1646v2ManStatisticTableEntry OBJECT IDENTIFIER ::= {er1646v2ManStatisticTableSSC 1}

er1646v2ManStatisticTableOrder OBJECT-TYPE
   SYNTAX      INTEGER
               {
               oldestFirst (1),
               recentFirst (2)
               }
   MAX-ACCESS  read-write
   STATUS      current
   DESCRIPTION
      "Path: management.editConf.statisticTable.order

       Possibilities:
               oldestFirst   (1)
               recentFirst   (2)"
   ::= {er1646v2ManStatisticTableEntry 16777216}

er1646v2ManStatisticTableIncompleteLine OBJECT-TYPE
   SYNTAX      INTEGER
               {
               present (1),
               notPresent (2)
               }
   MAX-ACCESS  read-write
   STATUS      current
   DESCRIPTION
      "Path: management.editConf.statisticTable.incompleteLine

       Possibilities:
               present   (1)
               notPresent   (2)"
   ::= {er1646v2ManStatisticTableEntry 33554432}


er1646v2ManLogStatsToFile OBJECT IDENTIFIER ::= {er1646v2Man 215}

er1646v2ManLogStatsToFileSSCTable OBJECT-TYPE
   SYNTAX      SEQUENCE OF Er1646v2ManLogStatsToFileEntry
   MAX-ACCESS  not-accessible
   STATUS      current
   DESCRIPTION
      "specify logging of performance tables"
   ::= {er1646v2ManLogStatsToFile 1}

er1646v2ManLogStatsToFileEntry OBJECT-TYPE
   SYNTAX      Er1646v2ManLogStatsToFileEntry
   MAX-ACCESS  not-accessible
   STATUS      current
   DESCRIPTION
      ""
   INDEX      { er1646v2ManLogStatsToFileTableIx }
   ::= {er1646v2ManLogStatsToFileSSCTable 1}

Er1646v2ManLogStatsToFileEntry ::=
   SEQUENCE
      {
      er1646v2ManLogStatsToFileActions
         VariableLengthTableActions,
      er1646v2ManLogStatsToFileTableIx
         TableIndex,
      er1646v2ManLogStatsToFileInterval
         INTEGER,
      er1646v2ManLogStatsToFileTypeTableName
         DisplayString,
      er1646v2ManLogStatsToFileTypeTableElement
         DisplayString,
      er1646v2ManLogStatsToFileTypeTableSamples
         Integer32,
      er1646v2ManLogStatsToFileTypeTableAddHeader
         INTEGER,
      er1646v2ManLogStatsToFileTypeTableConversion
         Integer32,
      er1646v2ManLogStatsToFileTypeTableColumnFilter
         Integer32,
      er1646v2ManLogStatsToFileTypeTableHeaderFilter
         DisplayString,
      er1646v2ManLogStatsToFileTypeTableSaveToServerPathFileName
         DisplayString,
      er1646v2ManLogStatsToFileTypeTablesSamples
         Integer32,
      er1646v2ManLogStatsToFileTypeTablesAddHeader
         INTEGER,
      er1646v2ManLogStatsToFileTypeTablesSaveToServerPathFileName
         DisplayString,
      er1646v2ManLogStatsToFileTypeElmInterval
         TimeTicks,
      er1646v2ManLogStatsToFileTypeElmAddHeader
         INTEGER,
      er1646v2ManLogStatsToFileTypeElmSaveToServerPathFileName
         DisplayString,
      er1646v2ManLogStatsToFileTypeElmSaveToServerUpdate
         INTEGER,
      er1646v2ManLogStatsToFileTypeElmSaveToServerFastTime
         Integer32,
      er1646v2ManLogStatsToFileFileType
         INTEGER,
      er1646v2ManLogStatsToFileFileName
         DisplayString
      }

er1646v2ManLogStatsToFileActions OBJECT-TYPE
   SYNTAX      VariableLengthTableActions
   MAX-ACCESS  read-write
   STATUS      current
   DESCRIPTION
      "By way of this field, some manipulations
       on this table may be performed."
   ::= {er1646v2ManLogStatsToFileEntry 2}

er1646v2ManLogStatsToFileTableIx OBJECT-TYPE
   SYNTAX      TableIndex
   MAX-ACCESS  not-accessible
   STATUS      current
   DESCRIPTION
      ""
   ::= {er1646v2ManLogStatsToFileEntry 11}

er1646v2ManLogStatsToFileInterval OBJECT-TYPE
   SYNTAX      INTEGER
               {
               s30min (30),
               s1h (60),
               s2h (120),
               s1d (1440)
               }
   MAX-ACCESS  read-write
   STATUS      current
   DESCRIPTION
      "Path: management.editConf.logStatsToFile.interval

       Possibilities:
               30min   (30)
               1h   (60)
               2h   (120)
               1d   (1440)"
   ::= {er1646v2ManLogStatsToFileEntry 16777216}

er1646v2ManLogStatsToFileTypeTableName OBJECT-TYPE
   SYNTAX      DisplayString
   MAX-ACCESS  read-write
   STATUS      current
   DESCRIPTION
      "Path: management.editConf.logStatsToFile.type.table.name"
   ::= {er1646v2ManLogStatsToFileEntry 33621504}

er1646v2ManLogStatsToFileTypeTableElement OBJECT-TYPE
   SYNTAX      DisplayString
   MAX-ACCESS  read-write
   STATUS      current
   DESCRIPTION
      "Path: management.editConf.logStatsToFile.type.table.element"
   ::= {er1646v2ManLogStatsToFileEntry 33620224}

er1646v2ManLogStatsToFileTypeTableSamples OBJECT-TYPE
   SYNTAX      Integer32
   MAX-ACCESS  read-write
   STATUS      current
   DESCRIPTION
      "Path: management.editConf.logStatsToFile.type.table.samples"
   ::= {er1646v2ManLogStatsToFileEntry 33620480}

er1646v2ManLogStatsToFileTypeTableAddHeader OBJECT-TYPE
   SYNTAX      INTEGER
               {
               no (1),
               yes (2)
               }
   MAX-ACCESS  read-write
   STATUS      current
   DESCRIPTION
      "Path: management.editConf.logStatsToFile.type.table.addHeader

       Possibilities:
               no   (1)
               yes   (2)"
   ::= {er1646v2ManLogStatsToFileEntry 33621248}

er1646v2ManLogStatsToFileTypeTableConversion OBJECT-TYPE
   SYNTAX      Integer32
   MAX-ACCESS  read-write
   STATUS      current
   DESCRIPTION
      "Path: management.editConf.logStatsToFile.type.table.conversion

       Bit meanings:
               bit 0 = removeQuotes,
               bit 1 = dateToSeconds,
               bit 2 = removeUnits,
               bit 3 = changeDecimalPnt"
   ::= {er1646v2ManLogStatsToFileEntry 33620736}

er1646v2ManLogStatsToFileTypeTableColumnFilter OBJECT-TYPE
   SYNTAX      Integer32
   MAX-ACCESS  read-write
   STATUS      current
   DESCRIPTION
      "Path: management.editConf.logStatsToFile.type.table.columnFilter

       Bit meanings:
               bit 1 = column02,
               bit 2 = column03,
               bit 3 = column04,
               bit 4 = column05,
               bit 5 = column06,
               bit 6 = column07,
               bit 7 = column08,
               bit 8 = column09,
               bit 9 = column10,
               bit 10 = column11,
               bit 11 = column12,
               bit 12 = column13,
               bit 13 = column14,
               bit 14 = column15,
               bit 15 = column16,
               bit 16 = column17,
               bit 17 = column18,
               bit 18 = column19,
               bit 19 = column20,
               bit 20 = column21,
               bit 21 = column22,
               bit 22 = column23,
               bit 23 = column24,
               bit 24 = column25,
               bit 25 = column26,
               bit 26 = column27,
               bit 27 = column28,
               bit 28 = column29,
               bit 29 = column30,
               bit 30 = column31,
               bit 31 = column32"
   ::= {er1646v2ManLogStatsToFileEntry 33620992}

er1646v2ManLogStatsToFileTypeTableHeaderFilter OBJECT-TYPE
   SYNTAX      DisplayString
   MAX-ACCESS  read-write
   STATUS      current
   DESCRIPTION
      "Path: management.editConf.logStatsToFile.type.table.headerFilter"
   ::= {er1646v2ManLogStatsToFileEntry 33621760}

er1646v2ManLogStatsToFileTypeTableSaveToServerPathFileName OBJECT-TYPE
   SYNTAX      DisplayString
   MAX-ACCESS  read-write
   STATUS      current
   DESCRIPTION
      "Path: management.editConf.logStatsToFile.type.table.saveToServer.pathFileName"
   ::= {er1646v2ManLogStatsToFileEntry 33622017}

er1646v2ManLogStatsToFileTypeTablesSamples OBJECT-TYPE
   SYNTAX      Integer32
   MAX-ACCESS  read-write
   STATUS      current
   DESCRIPTION
      "Path: management.editConf.logStatsToFile.type.tables.samples"
   ::= {er1646v2ManLogStatsToFileEntry 33686016}

er1646v2ManLogStatsToFileTypeTablesAddHeader OBJECT-TYPE
   SYNTAX      INTEGER
               {
               no (1),
               yes (2)
               }
   MAX-ACCESS  read-write
   STATUS      current
   DESCRIPTION
      "Path: management.editConf.logStatsToFile.type.tables.addHeader

       Possibilities:
               no   (1)
               yes   (2)"
   ::= {er1646v2ManLogStatsToFileEntry 33686784}

er1646v2ManLogStatsToFileTypeTablesSaveToServerPathFileName OBJECT-TYPE
   SYNTAX      DisplayString
   MAX-ACCESS  read-write
   STATUS      current
   DESCRIPTION
      "Path: management.editConf.logStatsToFile.type.tables.saveToServer.pathFileName"
   ::= {er1646v2ManLogStatsToFileEntry 33687553}

er1646v2ManLogStatsToFileTypeElmInterval OBJECT-TYPE
   SYNTAX      TimeTicks
   MAX-ACCESS  read-write
   STATUS      current
   DESCRIPTION
      "Path: management.editConf.logStatsToFile.type.elements.interval

       Time in centi-second."
   ::= {er1646v2ManLogStatsToFileEntry 33751552}

er1646v2ManLogStatsToFileTypeElmAddHeader OBJECT-TYPE
   SYNTAX      INTEGER
               {
               no (1),
               yes (2)
               }
   MAX-ACCESS  read-write
   STATUS      current
   DESCRIPTION
      "Path: management.editConf.logStatsToFile.type.elements.addHeader

       Possibilities:
               no   (1)
               yes   (2)"
   ::= {er1646v2ManLogStatsToFileEntry 33752320}

er1646v2ManLogStatsToFileTypeElmSaveToServerPathFileName OBJECT-TYPE
   SYNTAX      DisplayString
   MAX-ACCESS  read-write
   STATUS      current
   DESCRIPTION
      "Path: management.editConf.logStatsToFile.type.elements.saveToServer.pathFileName"
   ::= {er1646v2ManLogStatsToFileEntry 33753089}

er1646v2ManLogStatsToFileTypeElmSaveToServerUpdate OBJECT-TYPE
   SYNTAX      INTEGER
               {
               slow (1),
               fast (2)
               }
   MAX-ACCESS  read-write
   STATUS      current
   DESCRIPTION
      "Path: management.editConf.logStatsToFile.type.elements.saveToServer.update

       Possibilities:
               slow   (1)
               fast   (2)"
   ::= {er1646v2ManLogStatsToFileEntry 33753090}

er1646v2ManLogStatsToFileTypeElmSaveToServerFastTime OBJECT-TYPE
   SYNTAX      Integer32
   UNITS       "minutes"
   MAX-ACCESS  read-write
   STATUS      current
   DESCRIPTION
      "Path: management.editConf.logStatsToFile.type.elements.saveToServer.updateFastTime

       unit name = minutes"
   ::= {er1646v2ManLogStatsToFileEntry 33753091}

er1646v2ManLogStatsToFileFileType OBJECT-TYPE
   SYNTAX      INTEGER
               {
               day (4),
               week (1),
               month (2)
               }
   MAX-ACCESS  read-write
   STATUS      current
   DESCRIPTION
      "Path: management.editConf.logStatsToFile.fileType

       Possibilities:
               day   (4)
               week   (1)
               month   (2)"
   ::= {er1646v2ManLogStatsToFileEntry 67108864}

er1646v2ManLogStatsToFileFileName OBJECT-TYPE
   SYNTAX      DisplayString
   MAX-ACCESS  read-write
   STATUS      current
   DESCRIPTION
      "Path: management.editConf.logStatsToFile.fileName"
   ::= {er1646v2ManLogStatsToFileEntry 50331648}

er1646v2ManLogStatsToFileTypeTablesElements OBJECT-TYPE
   SYNTAX      SEQUENCE OF Er1646v2ManLogStatsToFileTypeTablesElementsEntry
   MAX-ACCESS  not-accessible
   STATUS      current
   DESCRIPTION
      ""
   ::= {er1646v2ManLogStatsToFile 33685760}

er1646v2ManLogStatsToFileTypeTablesElementsEntry OBJECT-TYPE
   SYNTAX      Er1646v2ManLogStatsToFileTypeTablesElementsEntry
   MAX-ACCESS  not-accessible
   STATUS      current
   DESCRIPTION
      ""
   INDEX      { er1646v2ManLogStatsToFileTableIx,
                er1646v2ManLogStatsToFileTypeTablesElementsTableIx }
   ::= {er1646v2ManLogStatsToFileTypeTablesElements 1}

Er1646v2ManLogStatsToFileTypeTablesElementsEntry ::=
   SEQUENCE
      {
      er1646v2ManLogStatsToFileTypeTablesElementsActions
         VariableLengthTableActions,
      er1646v2ManLogStatsToFileTypeTablesElementsTableIx
         TableIndex,
      er1646v2ManLogStatsToFileTypeTablesElementsName
         DisplayString,
      er1646v2ManLogStatsToFileTypeTablesElementsElement
         DisplayString,
      er1646v2ManLogStatsToFileTypeTablesElementsConversion
         Integer32,
      er1646v2ManLogStatsToFileTypeTablesElementsColumnFilter
         Integer32,
      er1646v2ManLogStatsToFileTypeTablesElementsNrOfColumns
         Integer32,
      er1646v2ManLogStatsToFileTypeTablesElementsHeaderFilter
         DisplayString
      }

er1646v2ManLogStatsToFileTypeTablesElementsActions OBJECT-TYPE
   SYNTAX      VariableLengthTableActions
   MAX-ACCESS  read-write
   STATUS      current
   DESCRIPTION
      "By way of this field, some manipulations
       on this table may be performed."
   ::= {er1646v2ManLogStatsToFileTypeTablesElementsEntry 2}

er1646v2ManLogStatsToFileTypeTablesElementsTableIx OBJECT-TYPE
   SYNTAX      TableIndex
   MAX-ACCESS  not-accessible
   STATUS      current
   DESCRIPTION
      ""
   ::= {er1646v2ManLogStatsToFileTypeTablesElementsEntry 11}

er1646v2ManLogStatsToFileTypeTablesElementsName OBJECT-TYPE
   SYNTAX      DisplayString
   MAX-ACCESS  read-write
   STATUS      current
   DESCRIPTION
      "Path: management.editConf.logStatsToFile.type.tables.elements.name"
   ::= {er1646v2ManLogStatsToFileTypeTablesElementsEntry 100663296}

er1646v2ManLogStatsToFileTypeTablesElementsElement OBJECT-TYPE
   SYNTAX      DisplayString
   MAX-ACCESS  read-write
   STATUS      current
   DESCRIPTION
      "Path: management.editConf.logStatsToFile.type.tables.elements.element"
   ::= {er1646v2ManLogStatsToFileTypeTablesElementsEntry 16777216}

er1646v2ManLogStatsToFileTypeTablesElementsConversion OBJECT-TYPE
   SYNTAX      Integer32
   MAX-ACCESS  read-write
   STATUS      current
   DESCRIPTION
      "Path: management.editConf.logStatsToFile.type.tables.elements.conversion

       Bit meanings:
               bit 0 = removeQuotes,
               bit 1 = dateToSeconds,
               bit 2 = removeUnits,
               bit 3 = changeDecimalPnt"
   ::= {er1646v2ManLogStatsToFileTypeTablesElementsEntry 50331648}

er1646v2ManLogStatsToFileTypeTablesElementsColumnFilter OBJECT-TYPE
   SYNTAX      Integer32
   MAX-ACCESS  read-write
   STATUS      current
   DESCRIPTION
      "Path: management.editConf.logStatsToFile.type.tables.elements.columnFilter

       Bit meanings:
               bit 1 = column02,
               bit 2 = column03,
               bit 3 = column04,
               bit 4 = column05,
               bit 5 = column06,
               bit 6 = column07,
               bit 7 = column08,
               bit 8 = column09,
               bit 9 = column10,
               bit 10 = column11,
               bit 11 = column12,
               bit 12 = column13,
               bit 13 = column14,
               bit 14 = column15,
               bit 15 = column16,
               bit 16 = column17,
               bit 17 = column18,
               bit 18 = column19,
               bit 19 = column20,
               bit 20 = column21,
               bit 21 = column22,
               bit 22 = column23,
               bit 23 = column24,
               bit 24 = column25,
               bit 25 = column26,
               bit 26 = column27,
               bit 27 = column28,
               bit 28 = column29,
               bit 29 = column30,
               bit 30 = column31,
               bit 31 = column32"
   ::= {er1646v2ManLogStatsToFileTypeTablesElementsEntry 67108864}

er1646v2ManLogStatsToFileTypeTablesElementsNrOfColumns OBJECT-TYPE
   SYNTAX      Integer32
   MAX-ACCESS  read-write
   STATUS      current
   DESCRIPTION
      "Path: management.editConf.logStatsToFile.type.tables.elements.nrOfColumns"
   ::= {er1646v2ManLogStatsToFileTypeTablesElementsEntry 83886080}

er1646v2ManLogStatsToFileTypeTablesElementsHeaderFilter OBJECT-TYPE
   SYNTAX      DisplayString
   MAX-ACCESS  read-write
   STATUS      current
   DESCRIPTION
      "Path: management.editConf.logStatsToFile.type.tables.elements.headerFilter"
   ::= {er1646v2ManLogStatsToFileTypeTablesElementsEntry 117440512}

er1646v2ManLogStatsToFileTypeElmElements OBJECT-TYPE
   SYNTAX      SEQUENCE OF Er1646v2ManLogStatsToFileTypeElmElementsEntry
   MAX-ACCESS  not-accessible
   STATUS      current
   DESCRIPTION
      ""
   ::= {er1646v2ManLogStatsToFile 33751296}

er1646v2ManLogStatsToFileTypeElmElementsEntry OBJECT-TYPE
   SYNTAX      Er1646v2ManLogStatsToFileTypeElmElementsEntry
   MAX-ACCESS  not-accessible
   STATUS      current
   DESCRIPTION
      ""
   INDEX      { er1646v2ManLogStatsToFileTableIx,
                er1646v2ManLogStatsToFileTypeElmElementsTableIx }
   ::= {er1646v2ManLogStatsToFileTypeElmElements 1}

Er1646v2ManLogStatsToFileTypeElmElementsEntry ::=
   SEQUENCE
      {
      er1646v2ManLogStatsToFileTypeElmElementsActions
         VariableLengthTableActions,
      er1646v2ManLogStatsToFileTypeElmElementsTableIx
         TableIndex,
      er1646v2ManLogStatsToFileTypeElmElementsName
         DisplayString,
      er1646v2ManLogStatsToFileTypeElmElementsElement
         DisplayString,
      er1646v2ManLogStatsToFileTypeElmElementsConversion
         Integer32,
      er1646v2ManLogStatsToFileTypeElmElementsNrOfColumns
         Integer32
      }

er1646v2ManLogStatsToFileTypeElmElementsActions OBJECT-TYPE
   SYNTAX      VariableLengthTableActions
   MAX-ACCESS  read-write
   STATUS      current
   DESCRIPTION
      "By way of this field, some manipulations
       on this table may be performed."
   ::= {er1646v2ManLogStatsToFileTypeElmElementsEntry 2}

er1646v2ManLogStatsToFileTypeElmElementsTableIx OBJECT-TYPE
   SYNTAX      TableIndex
   MAX-ACCESS  not-accessible
   STATUS      current
   DESCRIPTION
      ""
   ::= {er1646v2ManLogStatsToFileTypeElmElementsEntry 11}

er1646v2ManLogStatsToFileTypeElmElementsName OBJECT-TYPE
   SYNTAX      DisplayString
   MAX-ACCESS  read-write
   STATUS      current
   DESCRIPTION
      "Path: management.editConf.logStatsToFile.type.elements.elements.name"
   ::= {er1646v2ManLogStatsToFileTypeElmElementsEntry 100663296}

er1646v2ManLogStatsToFileTypeElmElementsElement OBJECT-TYPE
   SYNTAX      DisplayString
   MAX-ACCESS  read-write
   STATUS      current
   DESCRIPTION
      "Path: management.editConf.logStatsToFile.type.elements.elements.element"
   ::= {er1646v2ManLogStatsToFileTypeElmElementsEntry 16777216}

er1646v2ManLogStatsToFileTypeElmElementsConversion OBJECT-TYPE
   SYNTAX      Integer32
   MAX-ACCESS  read-write
   STATUS      current
   DESCRIPTION
      "Path: management.editConf.logStatsToFile.type.elements.elements.conversion

       Bit meanings:
               bit 0 = removeQuotes,
               bit 1 = dateToSeconds,
               bit 2 = removeUnits,
               bit 3 = changeDecimalPnt,
               bit 4 = difference"
   ::= {er1646v2ManLogStatsToFileTypeElmElementsEntry 50331648}

er1646v2ManLogStatsToFileTypeElmElementsNrOfColumns OBJECT-TYPE
   SYNTAX      Integer32
   MAX-ACCESS  read-write
   STATUS      current
   DESCRIPTION
      "Path: management.editConf.logStatsToFile.type.elements.elements.nrOfColumns"
   ::= {er1646v2ManLogStatsToFileTypeElmElementsEntry 83886080}


er1646v2ManLogStatsToFileLimit OBJECT IDENTIFIER ::= {er1646v2Man 219}

er1646v2ManLogStatsToFileLimitSSC OBJECT IDENTIFIER ::= {er1646v2ManLogStatsToFileLimit 1}

er1646v2ManLogStatsToFileLimitEntry OBJECT IDENTIFIER ::= {er1646v2ManLogStatsToFileLimitSSC 1}

er1646v2ManLogStatsToFileLimitDays OBJECT-TYPE
   SYNTAX      Integer32
   MAX-ACCESS  read-write
   STATUS      current
   DESCRIPTION
      "Path: management.editConf.logStatsToFileLimit.days"
   ::= {er1646v2ManLogStatsToFileLimitEntry 16777216}

er1646v2ManLogStatsToFileLimitWeeks OBJECT-TYPE
   SYNTAX      Integer32
   MAX-ACCESS  read-write
   STATUS      current
   DESCRIPTION
      "Path: management.editConf.logStatsToFileLimit.weeks"
   ::= {er1646v2ManLogStatsToFileLimitEntry 33554432}

er1646v2ManLogStatsToFileLimitMonths OBJECT-TYPE
   SYNTAX      Integer32
   MAX-ACCESS  read-write
   STATUS      current
   DESCRIPTION
      "Path: management.editConf.logStatsToFileLimit.months"
   ::= {er1646v2ManLogStatsToFileLimitEntry 50331648}

er1646v2ManLogStatsToFileLimitDiskSpace OBJECT-TYPE
   SYNTAX      Integer32
   UNITS       "%"
   MAX-ACCESS  read-write
   STATUS      current
   DESCRIPTION
      "Path: management.editConf.logStatsToFileLimit.diskSpace

       unit name = %"
   ::= {er1646v2ManLogStatsToFileLimitEntry 67108864}


er1646v2ManExecManager OBJECT IDENTIFIER ::= {er1646v2Man 216}

er1646v2ManExecManagerSSCTable OBJECT-TYPE
   SYNTAX      SEQUENCE OF Er1646v2ManExecManagerEntry
   MAX-ACCESS  not-accessible
   STATUS      current
   DESCRIPTION
      "follow up tasks, test and execute"
   ::= {er1646v2ManExecManager 1}

er1646v2ManExecManagerEntry OBJECT-TYPE
   SYNTAX      Er1646v2ManExecManagerEntry
   MAX-ACCESS  not-accessible
   STATUS      current
   DESCRIPTION
      ""
   INDEX      { er1646v2ManExecManagerTableIx }
   ::= {er1646v2ManExecManagerSSCTable 1}

Er1646v2ManExecManagerEntry ::=
   SEQUENCE
      {
      er1646v2ManExecManagerActions
         VariableLengthTableActions,
      er1646v2ManExecManagerTableIx
         TableIndex,
      er1646v2ManExecManagerName
         DisplayString,
      er1646v2ManExecManagerAdminStatus
         INTEGER
      }

er1646v2ManExecManagerActions OBJECT-TYPE
   SYNTAX      VariableLengthTableActions
   MAX-ACCESS  read-write
   STATUS      current
   DESCRIPTION
      "By way of this field, some manipulations
       on this table may be performed."
   ::= {er1646v2ManExecManagerEntry 2}

er1646v2ManExecManagerTableIx OBJECT-TYPE
   SYNTAX      TableIndex
   MAX-ACCESS  not-accessible
   STATUS      current
   DESCRIPTION
      ""
   ::= {er1646v2ManExecManagerEntry 11}

er1646v2ManExecManagerName OBJECT-TYPE
   SYNTAX      DisplayString
   MAX-ACCESS  read-write
   STATUS      current
   DESCRIPTION
      "Path: management.editConf.execManager.name"
   ::= {er1646v2ManExecManagerEntry 16777216}

er1646v2ManExecManagerAdminStatus OBJECT-TYPE
   SYNTAX      INTEGER
               {
               enabled (1),
               onDemand (2)
               }
   MAX-ACCESS  read-write
   STATUS      current
   DESCRIPTION
      "Path: management.editConf.execManager.adminStatus

       Possibilities:
               enabled   (1)
               onDemand   (2)"
   ::= {er1646v2ManExecManagerEntry 33554432}

er1646v2ManExecManagerTask OBJECT-TYPE
   SYNTAX      SEQUENCE OF Er1646v2ManExecManagerTaskEntry
   MAX-ACCESS  not-accessible
   STATUS      current
   DESCRIPTION
      ""
   ::= {er1646v2ManExecManager 50331648}

er1646v2ManExecManagerTaskEntry OBJECT-TYPE
   SYNTAX      Er1646v2ManExecManagerTaskEntry
   MAX-ACCESS  not-accessible
   STATUS      current
   DESCRIPTION
      ""
   INDEX      { er1646v2ManExecManagerTableIx,
                er1646v2ManExecManagerTaskTableIx }
   ::= {er1646v2ManExecManagerTask 1}

Er1646v2ManExecManagerTaskEntry ::=
   SEQUENCE
      {
      er1646v2ManExecManagerTaskActions
         VariableLengthTableActions,
      er1646v2ManExecManagerTaskTableIx
         TableIndex,
      er1646v2ManExecManagerTaskName
         DisplayString,
      er1646v2ManExecManagerTaskAction
         INTEGER,
      er1646v2ManExecManagerTaskSingleAction
         DisplayString,
      er1646v2ManExecManagerTaskVar
         INTEGER,
      er1646v2ManExecManagerTaskTest
         INTEGER,
      er1646v2ManExecManagerTaskTestValueValue
         DisplayString,
      er1646v2ManExecManagerTaskTestValueVar
         Integer32,
      er1646v2ManExecManagerTaskJumpToIfTrue
         DisplayString,
      er1646v2ManExecManagerTaskJumpToIfFalse
         DisplayString
      }

er1646v2ManExecManagerTaskActions OBJECT-TYPE
   SYNTAX      VariableLengthTableActions
   MAX-ACCESS  read-write
   STATUS      current
   DESCRIPTION
      "By way of this field, some manipulations
       on this table may be performed."
   ::= {er1646v2ManExecManagerTaskEntry 2}

er1646v2ManExecManagerTaskTableIx OBJECT-TYPE
   SYNTAX      TableIndex
   MAX-ACCESS  not-accessible
   STATUS      current
   DESCRIPTION
      ""
   ::= {er1646v2ManExecManagerTaskEntry 11}

er1646v2ManExecManagerTaskName OBJECT-TYPE
   SYNTAX      DisplayString
   MAX-ACCESS  read-write
   STATUS      current
   DESCRIPTION
      "Path: management.editConf.execManager.task.name"
   ::= {er1646v2ManExecManagerTaskEntry 16777216}

er1646v2ManExecManagerTaskAction OBJECT-TYPE
   SYNTAX      INTEGER
               {
               calculate (28),
               counterGet (3),
               counterSet (4),
               counterInc (5),
               counterDec (6),
               execCommand (2),
               globalStringGet (25),
               globalStringSet (24),
               globalVarGet (8),
               globalVarSet (7),
               localStringGet (23),
               localStringSet (27),
               localVarGet (22),
               localVarSet (26),
               numberGet (18),
               numberSet (19),
               print (29),
               remark (1),
               sendEvent (30),
               scan (31),
               start (20),
               stop (21),
               stringGet (16),
               stringSet (17),
               timerGet (9),
               timerSet (10),
               timerStart (11),
               timerStop (12),
               wait (13),
               waitTime (15),
               waitWeekDayTime (14)
               }
   MAX-ACCESS  read-write
   STATUS      current
   DESCRIPTION
      "Path: management.editConf.execManager.task.action

       Possibilities:
               calculate   (28)
               counterGet   (3)
               counterSet   (4)
               counterInc   (5)
               counterDec   (6)
               execCommand   (2)
               globalStringGet   (25)
               globalStringSet   (24)
               globalVarGet   (8)
               globalVarSet   (7)
               localStringGet   (23)
               localStringSet   (27)
               localVarGet   (22)
               localVarSet   (26)
               numberGet   (18)
               numberSet   (19)
               print   (29)
               remark   (1)
               sendEvent   (30)
               scan   (31)
               start   (20)
               stop   (21)
               stringGet   (16)
               stringSet   (17)
               timerGet   (9)
               timerSet   (10)
               timerStart   (11)
               timerStop   (12)
               wait   (13)
               waitTime   (15)
               waitWeekDayTime   (14)"
   ::= {er1646v2ManExecManagerTaskEntry 33554432}

er1646v2ManExecManagerTaskSingleAction OBJECT-TYPE
   SYNTAX      DisplayString
   MAX-ACCESS  read-write
   STATUS      current
   DESCRIPTION
      "Path: management.editConf.execManager.task.singleAction"
   ::= {er1646v2ManExecManagerTaskEntry 50331648}

er1646v2ManExecManagerTaskVar OBJECT-TYPE
   SYNTAX      INTEGER
               {
               none (0)
               }
   MAX-ACCESS  read-write
   STATUS      current
   DESCRIPTION
      "Path: management.editConf.execManager.task.var

       Possibilities:
               none   (0)"
   ::= {er1646v2ManExecManagerTaskEntry 150994944}

er1646v2ManExecManagerTaskTest OBJECT-TYPE
   SYNTAX      INTEGER
               {
               true (1),
               equal (2),
               greater (3),
               less (4)
               }
   MAX-ACCESS  read-write
   STATUS      current
   DESCRIPTION
      "Path: management.editConf.execManager.task.test

       Possibilities:
               true   (1)
               equal   (2)
               greater   (3)
               less   (4)"
   ::= {er1646v2ManExecManagerTaskEntry 83886080}

er1646v2ManExecManagerTaskTestValueValue OBJECT-TYPE
   SYNTAX      DisplayString
   MAX-ACCESS  read-write
   STATUS      current
   DESCRIPTION
      "Path: management.editConf.execManager.task.testValue.value"
   ::= {er1646v2ManExecManagerTaskEntry 134283264}

er1646v2ManExecManagerTaskTestValueVar OBJECT-TYPE
   SYNTAX      Integer32
   MAX-ACCESS  read-write
   STATUS      current
   DESCRIPTION
      "Path: management.editConf.execManager.task.testValue.var"
   ::= {er1646v2ManExecManagerTaskEntry 134348800}

er1646v2ManExecManagerTaskJumpToIfTrue OBJECT-TYPE
   SYNTAX      DisplayString
   MAX-ACCESS  read-write
   STATUS      current
   DESCRIPTION
      "Path: management.editConf.execManager.task.jumpToIfTrue"
   ::= {er1646v2ManExecManagerTaskEntry 100663296}

er1646v2ManExecManagerTaskJumpToIfFalse OBJECT-TYPE
   SYNTAX      DisplayString
   MAX-ACCESS  read-write
   STATUS      current
   DESCRIPTION
      "Path: management.editConf.execManager.task.jumpToIfFalse"
   ::= {er1646v2ManExecManagerTaskEntry 117440512}

er1646v2ManExecManagerTaskMultipleActions OBJECT-TYPE
   SYNTAX      SEQUENCE OF Er1646v2ManExecManagerTaskMultipleActionsEntry
   MAX-ACCESS  not-accessible
   STATUS      current
   DESCRIPTION
      ""
   ::= {er1646v2ManExecManager 50593792}

er1646v2ManExecManagerTaskMultipleActionsEntry OBJECT-TYPE
   SYNTAX      Er1646v2ManExecManagerTaskMultipleActionsEntry
   MAX-ACCESS  not-accessible
   STATUS      current
   DESCRIPTION
      ""
   INDEX      { er1646v2ManExecManagerTableIx,
                er1646v2ManExecManagerTaskTableIx,
                er1646v2ManExecManagerTaskMultipleActionsTableIx }
   ::= {er1646v2ManExecManagerTaskMultipleActions 1}

Er1646v2ManExecManagerTaskMultipleActionsEntry ::=
   SEQUENCE
      {
      er1646v2ManExecManagerTaskMultipleActionsActions
         VariableLengthTableActions,
      er1646v2ManExecManagerTaskMultipleActionsTableIx
         TableIndex,
      er1646v2ManExecManagerTaskMultipleActionsRemark
         DisplayString,
      er1646v2ManExecManagerTaskMultipleActionsData
         DisplayString
      }

er1646v2ManExecManagerTaskMultipleActionsActions OBJECT-TYPE
   SYNTAX      VariableLengthTableActions
   MAX-ACCESS  read-write
   STATUS      current
   DESCRIPTION
      "By way of this field, some manipulations
       on this table may be performed."
   ::= {er1646v2ManExecManagerTaskMultipleActionsEntry 2}

er1646v2ManExecManagerTaskMultipleActionsTableIx OBJECT-TYPE
   SYNTAX      TableIndex
   MAX-ACCESS  not-accessible
   STATUS      current
   DESCRIPTION
      ""
   ::= {er1646v2ManExecManagerTaskMultipleActionsEntry 11}

er1646v2ManExecManagerTaskMultipleActionsRemark OBJECT-TYPE
   SYNTAX      DisplayString
   MAX-ACCESS  read-write
   STATUS      current
   DESCRIPTION
      "Path: management.editConf.execManager.task.multipleActions.remark"
   ::= {er1646v2ManExecManagerTaskMultipleActionsEntry 16777216}

er1646v2ManExecManagerTaskMultipleActionsData OBJECT-TYPE
   SYNTAX      DisplayString
   MAX-ACCESS  read-write
   STATUS      current
   DESCRIPTION
      "Path: management.editConf.execManager.task.multipleActions.data"
   ::= {er1646v2ManExecManagerTaskMultipleActionsEntry 33554432}


er1646v2ManUserInfo OBJECT IDENTIFIER ::= {er1646v2Man 59}

er1646v2ManUserInfoSSCTable OBJECT-TYPE
   SYNTAX      SEQUENCE OF Er1646v2ManUserInfoEntry
   MAX-ACCESS  not-accessible
   STATUS      current
   DESCRIPTION
      ""
   ::= {er1646v2ManUserInfo 1}

er1646v2ManUserInfoEntry OBJECT-TYPE
   SYNTAX      Er1646v2ManUserInfoEntry
   MAX-ACCESS  not-accessible
   STATUS      current
   DESCRIPTION
      ""
   INDEX      { er1646v2ManUserInfoTableIx }
   ::= {er1646v2ManUserInfoSSCTable 1}

Er1646v2ManUserInfoEntry ::=
   SEQUENCE
      {
      er1646v2ManUserInfoActions
         VariableLengthTableActions,
      er1646v2ManUserInfoTableIx
         TableIndex,
      er1646v2ManUserInfoInfo
         DisplayString
      }

er1646v2ManUserInfoActions OBJECT-TYPE
   SYNTAX      VariableLengthTableActions
   MAX-ACCESS  read-write
   STATUS      current
   DESCRIPTION
      "By way of this field, some manipulations
       on this table may be performed."
   ::= {er1646v2ManUserInfoEntry 2}

er1646v2ManUserInfoTableIx OBJECT-TYPE
   SYNTAX      TableIndex
   MAX-ACCESS  not-accessible
   STATUS      current
   DESCRIPTION
      ""
   ::= {er1646v2ManUserInfoEntry 11}

er1646v2ManUserInfoInfo OBJECT-TYPE
   SYNTAX      DisplayString
   MAX-ACCESS  read-write
   STATUS      current
   DESCRIPTION
      "Path: management.editConf.userInfo.info"
   ::= {er1646v2ManUserInfoEntry 16777216}


er1646v2ManAlarmFilter OBJECT-TYPE
   SYNTAX      Integer32
   MAX-ACCESS  read-write
   STATUS      current
   DESCRIPTION
      "Path: management.editConf.alarmFilter
       Info: Attribute used in the TMA alarm manager for filtering of alarms."
   ::= {er1646v2Man 400}


er1646v2ManConsoleNoTrafficTimeOut OBJECT-TYPE
   SYNTAX      TimeTicks
   MAX-ACCESS  read-write
   STATUS      current
   DESCRIPTION
      "Path: management.editConf.consoleNoTrafficTimeOut
       Info: consoleNoTrafficTimeout

       Time in centi-second."
   ::= {er1646v2Man 21}


er1646v2ManAtwinGraphics OBJECT-TYPE
   SYNTAX      INTEGER
               {
               disabled (0),
               enabled (1)
               }
   MAX-ACCESS  read-write
   STATUS      current
   DESCRIPTION
      "Path: management.editConf.atwinGraphics
       Info: graphics in atwin enabled or not

       Possibilities:
               disabled   (0)
               enabled   (1)"
   ::= {er1646v2Man 24}


er1646v2ManPrompt OBJECT-TYPE
   SYNTAX      INTEGER
               {
               empty (1),
               sysName (2)
               }
   MAX-ACCESS  read-write
   STATUS      current
   DESCRIPTION
      "Path: management.editConf.prompt
       Info: Attribute that controls the cli prompt will look

       Possibilities:
               empty   (1)
               sysName   (2)"
   ::= {er1646v2Man 39}


er1646v2ManAccessPolicy OBJECT-TYPE
   SYNTAX      DisplayString
   MAX-ACCESS  read-write
   STATUS      current
   DESCRIPTION
      "Path: management.editConf.accessPolicy
       Info: access policy name"
   ::= {er1646v2Man 25}


er1646v2ManTrafficPolicy OBJECT-TYPE
   SYNTAX      DisplayString
   MAX-ACCESS  read-write
   STATUS      current
   DESCRIPTION
      "Path: management.editConf.trafficPolicy
       Info: access policy name"
   ::= {er1646v2Man 73}


er1646v2ManMaxPingReplies OBJECT-TYPE
   SYNTAX      INTEGER
               {
               disabled (0)
               }
   MAX-ACCESS  read-write
   STATUS      current
   DESCRIPTION
      "Path: management.editConf.maxPingReplies
       Info: max nr of ping replies per second

       Possibilities:
               disabled   (0)"
   ::= {er1646v2Man 26}


er1646v2ManHttp OBJECT-TYPE
   SYNTAX      INTEGER
               {
               disabled (0),
               enabled (1)
               }
   MAX-ACCESS  read-write
   STATUS      current
   DESCRIPTION
      "Path: management.editConf.http
       Info: Attribute that controls the orchid how to treat the TCP packets for the TELNET port
                         enabled:    act on TCP packets destined for the TELNET port
                         disabled:   discard TCP packets destined for the TELNET port

       Possibilities:
               disabled   (0)
               enabled   (1)"
   ::= {er1646v2Man 77}


er1646v2ManHttps OBJECT-TYPE
   SYNTAX      INTEGER
               {
               disabled (0),
               enabled (1)
               }
   MAX-ACCESS  read-write
   STATUS      current
   DESCRIPTION
      "Path: management.editConf.https
       Info: Attribute that controls the orchid how to treat the TCP packets for the TELNET port
                         enabled:    act on TCP packets destined for the TELNET port
                         disabled:   discard TCP packets destined for the TELNET port

       Possibilities:
               disabled   (0)
               enabled   (1)"
   ::= {er1646v2Man 27}


er1646v2ManSsh OBJECT-TYPE
   SYNTAX      INTEGER
               {
               disabled (0),
               enabled (1)
               }
   MAX-ACCESS  read-write
   STATUS      current
   DESCRIPTION
      "Path: management.editConf.ssh
       Info: Attribute that controls the orchid how to treat the TCP packets for the TELNET port
                         enabled:    act on TCP packets destined for the TELNET port
                         disabled:   discard TCP packets destined for the TELNET port

       Possibilities:
               disabled   (0)
               enabled   (1)"
   ::= {er1646v2Man 30}


er1646v2ManEcho OBJECT-TYPE
   SYNTAX      INTEGER
               {
               disabled (0),
               enabled (1)
               }
   MAX-ACCESS  read-write
   STATUS      current
   DESCRIPTION
      "Path: management.editConf.echo
       Info: Attribute that controls the orchid how to treat the TCP packets for the TELNET port
                         enabled:    act on TCP packets destined for the TELNET port
                         disabled:   discard TCP packets destined for the TELNET port

       Possibilities:
               disabled   (0)
               enabled   (1)"
   ::= {er1646v2Man 7}


er1646v2ManDiscard OBJECT-TYPE
   SYNTAX      INTEGER
               {
               disabled (0),
               enabled (1)
               }
   MAX-ACCESS  read-write
   STATUS      current
   DESCRIPTION
      "Path: management.editConf.discard
       Info: Attribute that controls the orchid how to treat the TCP packets for the TELNET port
                         enabled:    act on TCP packets destined for the TELNET port
                         disabled:   discard TCP packets destined for the TELNET port

       Possibilities:
               disabled   (0)
               enabled   (1)"
   ::= {er1646v2Man 9}


er1646v2ManCwmp OBJECT IDENTIFIER ::= {er1646v2Man 74}

er1646v2ManCwmpSSC OBJECT IDENTIFIER ::= {er1646v2ManCwmp 1}

er1646v2ManCwmpEntry OBJECT IDENTIFIER ::= {er1646v2ManCwmpSSC 1}

er1646v2ManCwmpVrfRouter OBJECT-TYPE
   SYNTAX      DisplayString
   MAX-ACCESS  read-write
   STATUS      current
   DESCRIPTION
      "Path: management.editConf.cwmp.vrfRouter"
   ::= {er1646v2ManCwmpEntry 167772160}

er1646v2ManCwmpRouterType OBJECT-TYPE
   SYNTAX      INTEGER
               {
               ipV4 (1),
               ipV6 (2)
               }
   MAX-ACCESS  read-write
   STATUS      current
   DESCRIPTION
      "Path: management.editConf.cwmp.routerType

       Possibilities:
               ipV4   (1)
               ipV6   (2)"
   ::= {er1646v2ManCwmpEntry 251658240}

er1646v2ManCwmpSource OBJECT-TYPE
   SYNTAX      DisplayString
   MAX-ACCESS  read-write
   STATUS      current
   DESCRIPTION
      "Path: management.editConf.cwmp.source"
   ::= {er1646v2ManCwmpEntry 150994944}

er1646v2ManCwmpAcsUrl OBJECT-TYPE
   SYNTAX      DisplayString
   MAX-ACCESS  read-write
   STATUS      current
   DESCRIPTION
      "Path: management.editConf.cwmp.acsUrl"
   ::= {er1646v2ManCwmpEntry 16777216}

er1646v2ManCwmpDhcpAcsUrl OBJECT-TYPE
   SYNTAX      INTEGER
               {
               disabled (0),
               dslforum (1),
               custom1 (2)
               }
   MAX-ACCESS  read-write
   STATUS      current
   DESCRIPTION
      "Path: management.editConf.cwmp.dhcpAcsUrl

       Possibilities:
               disabled   (0)
               dslforum   (1)
               custom1   (2)"
   ::= {er1646v2ManCwmpEntry 117440512}

er1646v2ManCwmpAuthenticationDefaultUsername OBJECT-TYPE
   SYNTAX      INTEGER
               {
               empty (0),
               ouiClassSerial (1),
               ouiSerial (2)
               }
   MAX-ACCESS  read-write
   STATUS      current
   DESCRIPTION
      "Path: management.editConf.cwmp.authentication.defaultUsername

       Possibilities:
               empty   (0)
               ouiClassSerial   (1)
               ouiSerial   (2)"
   ::= {er1646v2ManCwmpEntry 34144256}

er1646v2ManCwmpAuthenticationUsername OBJECT-TYPE
   SYNTAX      DisplayString
   MAX-ACCESS  read-write
   STATUS      current
   DESCRIPTION
      "Path: management.editConf.cwmp.authentication.username"
   ::= {er1646v2ManCwmpEntry 33619968}

er1646v2ManCwmpAuthenticationDefaultPassword OBJECT-TYPE
   SYNTAX      INTEGER
               {
               empty (0),
               serial (1)
               }
   MAX-ACCESS  read-write
   STATUS      current
   DESCRIPTION
      "Path: management.editConf.cwmp.authentication.defaultPassword

       Possibilities:
               empty   (0)
               serial   (1)"
   ::= {er1646v2ManCwmpEntry 34209792}

er1646v2ManCwmpAuthenticationPassword OBJECT-TYPE
   SYNTAX      DisplayString
   MAX-ACCESS  read-write
   STATUS      current
   DESCRIPTION
      "Path: management.editConf.cwmp.authentication.password"
   ::= {er1646v2ManCwmpEntry 33685504}

er1646v2ManCwmpAuthenticationEncModePassword OBJECT-TYPE
   SYNTAX      INTEGER
               {
               none (1),
               encrypt (2),
               encType1 (3),
               invalid (128)
               }
   MAX-ACCESS  read-write
   STATUS      current
   DESCRIPTION
      "Path: management.editConf.cwmp.authentication.encModePassword

       Possibilities:
               none   (1)
               encrypt   (2)
               encType1   (3)
               invalid   (128)"
   ::= {er1646v2ManCwmpEntry 33882112}

er1646v2ManCwmpAuthenticationEncPassword OBJECT-TYPE
   SYNTAX      DisplayString
   MAX-ACCESS  read-write
   STATUS      current
   DESCRIPTION
      "Path: management.editConf.cwmp.authentication.encPassword"
   ::= {er1646v2ManCwmpEntry 33947648}

er1646v2ManCwmpAuthenticationConnectionRequestUsername OBJECT-TYPE
   SYNTAX      DisplayString
   MAX-ACCESS  read-write
   STATUS      current
   DESCRIPTION
      "Path: management.editConf.cwmp.authentication.connectionRequestUsername"
   ::= {er1646v2ManCwmpEntry 33751040}

er1646v2ManCwmpAuthenticationConnectionRequestPassword OBJECT-TYPE
   SYNTAX      DisplayString
   MAX-ACCESS  read-write
   STATUS      current
   DESCRIPTION
      "Path: management.editConf.cwmp.authentication.connectionRequestPassword"
   ::= {er1646v2ManCwmpEntry 33816576}

er1646v2ManCwmpAuthenticationEncModeConnectionRequestPassword OBJECT-TYPE
   SYNTAX      INTEGER
               {
               none (1),
               encrypt (2),
               encType1 (3),
               invalid (128)
               }
   MAX-ACCESS  read-write
   STATUS      current
   DESCRIPTION
      "Path: management.editConf.cwmp.authentication.encModeConnectionRequestPassword

       Possibilities:
               none   (1)
               encrypt   (2)
               encType1   (3)
               invalid   (128)"
   ::= {er1646v2ManCwmpEntry 34013184}

er1646v2ManCwmpAuthenticationEncConnectionRequestPassword OBJECT-TYPE
   SYNTAX      DisplayString
   MAX-ACCESS  read-write
   STATUS      current
   DESCRIPTION
      "Path: management.editConf.cwmp.authentication.encConnectionRequestPassword"
   ::= {er1646v2ManCwmpEntry 34078720}

er1646v2ManCwmpAcsVerificationCaCertificate OBJECT-TYPE
   SYNTAX      INTEGER
               {
               optional (1),
               enabled (2),
               disabled (3)
               }
   MAX-ACCESS  read-write
   STATUS      current
   DESCRIPTION
      "Path: management.editConf.cwmp.acsVerification.caCertificate

       Possibilities:
               optional   (1)
               enabled   (2)
               disabled   (3)"
   ::= {er1646v2ManCwmpEntry 268500992}

er1646v2ManCwmpAcsVerificationHostname OBJECT-TYPE
   SYNTAX      INTEGER
               {
               disabled (1),
               enabled (2)
               }
   MAX-ACCESS  read-write
   STATUS      current
   DESCRIPTION
      "Path: management.editConf.cwmp.acsVerification.hostname

       Possibilities:
               disabled   (1)
               enabled   (2)"
   ::= {er1646v2ManCwmpEntry 268566528}

er1646v2ManCwmpAcsVerificationValidFrom OBJECT-TYPE
   SYNTAX      INTEGER
               {
               auto (1),
               enabled (2),
               disabled (3)
               }
   MAX-ACCESS  read-write
   STATUS      current
   DESCRIPTION
      "Path: management.editConf.cwmp.acsVerification.validFrom

       Possibilities:
               auto   (1)
               enabled   (2)
               disabled   (3)"
   ::= {er1646v2ManCwmpEntry 268632064}

er1646v2ManCwmpAcsVerificationValidUntil OBJECT-TYPE
   SYNTAX      INTEGER
               {
               auto (1),
               enabled (2),
               disabled (3)
               }
   MAX-ACCESS  read-write
   STATUS      current
   DESCRIPTION
      "Path: management.editConf.cwmp.acsVerification.validUntil

       Possibilities:
               auto   (1)
               enabled   (2)
               disabled   (3)"
   ::= {er1646v2ManCwmpEntry 268697600}

er1646v2ManCwmpHardwareVersion OBJECT-TYPE
   SYNTAX      DisplayString
   MAX-ACCESS  read-write
   STATUS      current
   DESCRIPTION
      "Path: management.editConf.cwmp.hardwareVersion"
   ::= {er1646v2ManCwmpEntry 50331648}

er1646v2ManCwmpMacAddress OBJECT-TYPE
   SYNTAX      INTEGER
               {
               default (0),
               lowest (1)
               }
   MAX-ACCESS  read-write
   STATUS      current
   DESCRIPTION
      "Path: management.editConf.cwmp.macAddress

       Possibilities:
               default   (0)
               lowest   (1)"
   ::= {er1646v2ManCwmpEntry 201326592}

er1646v2ManCwmpConfigVersionUpdate OBJECT-TYPE
   SYNTAX      INTEGER
               {
               manual (0),
               automatic (1)
               }
   MAX-ACCESS  read-write
   STATUS      current
   DESCRIPTION
      "Path: management.editConf.cwmp.configVersionUpdate

       Possibilities:
               manual   (0)
               automatic   (1)"
   ::= {er1646v2ManCwmpEntry 184549376}

er1646v2ManCwmpConfigVersion OBJECT-TYPE
   SYNTAX      DisplayString
   MAX-ACCESS  read-write
   STATUS      current
   DESCRIPTION
      "Path: management.editConf.cwmp.configVersion"
   ::= {er1646v2ManCwmpEntry 67108864}

er1646v2ManCwmpProvisioningCode OBJECT-TYPE
   SYNTAX      DisplayString
   MAX-ACCESS  read-write
   STATUS      current
   DESCRIPTION
      "Path: management.editConf.cwmp.provisioningCode"
   ::= {er1646v2ManCwmpEntry 83886080}

er1646v2ManCwmpInformTime OBJECT-TYPE
   SYNTAX      DisplayString
   MAX-ACCESS  read-write
   STATUS      current
   DESCRIPTION
      "Path: management.editConf.cwmp.informTime"
   ::= {er1646v2ManCwmpEntry 234881024}

er1646v2ManCwmpInformInterval OBJECT-TYPE
   SYNTAX      TimeTicks
   MAX-ACCESS  read-write
   STATUS      current
   DESCRIPTION
      "Path: management.editConf.cwmp.informInterval

       Time in centi-second."
   ::= {er1646v2ManCwmpEntry 100663296}

er1646v2ManCwmpInformEnabled OBJECT-TYPE
   SYNTAX      INTEGER
               {
               disabled (0),
               enabled (1)
               }
   MAX-ACCESS  read-write
   STATUS      current
   DESCRIPTION
      "Path: management.editConf.cwmp.informEnabled

       Possibilities:
               disabled   (0)
               enabled   (1)"
   ::= {er1646v2ManCwmpEntry 134217728}

er1646v2ManCwmpConnectionRequestPort OBJECT-TYPE
   SYNTAX      INTEGER
               {
               auto (0)
               }
   MAX-ACCESS  read-write
   STATUS      current
   DESCRIPTION
      "Path: management.editConf.cwmp.connectionRequestPort

       Possibilities:
               auto   (0)"
   ::= {er1646v2ManCwmpEntry 218103808}


er1646v2ManRadius OBJECT IDENTIFIER ::= {er1646v2Man 80}

er1646v2ManRadiusSSC OBJECT IDENTIFIER ::= {er1646v2ManRadius 1}

er1646v2ManRadiusEntry OBJECT IDENTIFIER ::= {er1646v2ManRadiusSSC 1}

er1646v2ManRadiusAcctServerVrfRouter OBJECT-TYPE
   SYNTAX      DisplayString
   MAX-ACCESS  read-write
   STATUS      current
   DESCRIPTION
      "Path: management.editConf.radius.acctServer.vrfRouter"
   ::= {er1646v2ManRadiusEntry 1694826496}

er1646v2ManRadiusAcctServerAddress OBJECT-TYPE
   SYNTAX      IpAddress
   MAX-ACCESS  read-write
   STATUS      current
   DESCRIPTION
      "Path: management.editConf.radius.acctServer.address"
   ::= {er1646v2ManRadiusEntry 1694564352}

er1646v2ManRadiusAcctServerPort OBJECT-TYPE
   SYNTAX      Integer32
   MAX-ACCESS  read-write
   STATUS      current
   DESCRIPTION
      "Path: management.editConf.radius.acctServer.port"
   ::= {er1646v2ManRadiusEntry 1695023104}

er1646v2ManRadiusAcctServerSource OBJECT-TYPE
   SYNTAX      DisplayString
   MAX-ACCESS  read-write
   STATUS      current
   DESCRIPTION
      "Path: management.editConf.radius.acctServer.source"
   ::= {er1646v2ManRadiusEntry 1694760960}

er1646v2ManRadiusAcctServerSecret OBJECT-TYPE
   SYNTAX      DisplayString
   MAX-ACCESS  read-write
   STATUS      current
   DESCRIPTION
      "Path: management.editConf.radius.acctServer.secret"
   ::= {er1646v2ManRadiusEntry 1694629888}

er1646v2ManRadiusAcctServerEncModeSecret OBJECT-TYPE
   SYNTAX      INTEGER
               {
               none (1),
               encrypt (2),
               encType1 (3),
               invalid (128)
               }
   MAX-ACCESS  read-write
   STATUS      current
   DESCRIPTION
      "Path: management.editConf.radius.acctServer.encModeSecret

       Possibilities:
               none   (1)
               encrypt   (2)
               encType1   (3)
               invalid   (128)"
   ::= {er1646v2ManRadiusEntry 1694892032}

er1646v2ManRadiusAcctServerEncSecret OBJECT-TYPE
   SYNTAX      DisplayString
   MAX-ACCESS  read-write
   STATUS      current
   DESCRIPTION
      "Path: management.editConf.radius.acctServer.encSecret"
   ::= {er1646v2ManRadiusEntry 1694957568}

er1646v2ManRadiusAcctServerTimeOut OBJECT-TYPE
   SYNTAX      TimeTicks
   MAX-ACCESS  read-write
   STATUS      current
   DESCRIPTION
      "Path: management.editConf.radius.acctServer.timeOut

       Time in centi-second."
   ::= {er1646v2ManRadiusEntry 1694695424}

er1646v2ManRadiusRetries OBJECT-TYPE
   SYNTAX      Integer32
   MAX-ACCESS  read-write
   STATUS      current
   DESCRIPTION
      "Path: management.editConf.radius.retries"
   ::= {er1646v2ManRadiusEntry 16777216}

er1646v2ManRadiusAcctUpdate OBJECT-TYPE
   SYNTAX      TimeTicks
   MAX-ACCESS  read-write
   STATUS      current
   DESCRIPTION
      "Path: management.editConf.radius.acctUpdate

       Time in centi-second."
   ::= {er1646v2ManRadiusEntry 33554432}

er1646v2ManRadiusLogin OBJECT-TYPE
   SYNTAX      INTEGER
               {
               disabled (0),
               enabled (1),
               fallback (2),
               reverseFallback (3)
               }
   MAX-ACCESS  read-write
   STATUS      current
   DESCRIPTION
      "Path: management.editConf.radius.login

       Possibilities:
               disabled   (0)
               enabled   (1)
               fallback   (2)
               reverseFallback   (3)"
   ::= {er1646v2ManRadiusEntry 50331648}

er1646v2ManRadiusPpp OBJECT-TYPE
   SYNTAX      INTEGER
               {
               disabled (0),
               enabled (1),
               fallback (2),
               reverseFallback (3)
               }
   MAX-ACCESS  read-write
   STATUS      current
   DESCRIPTION
      "Path: management.editConf.radius.ppp

       Possibilities:
               disabled   (0)
               enabled   (1)
               fallback   (2)
               reverseFallback   (3)"
   ::= {er1646v2ManRadiusEntry 67108864}

er1646v2ManRadiusAuthServers OBJECT-TYPE
   SYNTAX      SEQUENCE OF Er1646v2ManRadiusAuthServersEntry
   MAX-ACCESS  not-accessible
   STATUS      current
   DESCRIPTION
      ""
   ::= {er1646v2ManRadius 1677721600}

er1646v2ManRadiusAuthServersEntry OBJECT-TYPE
   SYNTAX      Er1646v2ManRadiusAuthServersEntry
   MAX-ACCESS  not-accessible
   STATUS      current
   DESCRIPTION
      ""
   INDEX      { er1646v2ManRadiusAuthServersTableIx }
   ::= {er1646v2ManRadiusAuthServers 1}

Er1646v2ManRadiusAuthServersEntry ::=
   SEQUENCE
      {
      er1646v2ManRadiusAuthServersActions
         VariableLengthTableActions,
      er1646v2ManRadiusAuthServersTableIx
         TableIndex,
      er1646v2ManRadiusAuthServersVrfRouter
         DisplayString,
      er1646v2ManRadiusAuthServersAddress
         IpAddress,
      er1646v2ManRadiusAuthServersPort
         Integer32,
      er1646v2ManRadiusAuthServersSource
         DisplayString,
      er1646v2ManRadiusAuthServersSecret
         DisplayString,
      er1646v2ManRadiusAuthServersEncModeSecret
         INTEGER,
      er1646v2ManRadiusAuthServersEncSecret
         DisplayString,
      er1646v2ManRadiusAuthServersTimeOut
         TimeTicks
      }

er1646v2ManRadiusAuthServersActions OBJECT-TYPE
   SYNTAX      VariableLengthTableActions
   MAX-ACCESS  read-write
   STATUS      current
   DESCRIPTION
      "By way of this field, some manipulations
       on this table may be performed."
   ::= {er1646v2ManRadiusAuthServersEntry 2}

er1646v2ManRadiusAuthServersTableIx OBJECT-TYPE
   SYNTAX      TableIndex
   MAX-ACCESS  not-accessible
   STATUS      current
   DESCRIPTION
      ""
   ::= {er1646v2ManRadiusAuthServersEntry 11}

er1646v2ManRadiusAuthServersVrfRouter OBJECT-TYPE
   SYNTAX      DisplayString
   MAX-ACCESS  read-write
   STATUS      current
   DESCRIPTION
      "Path: management.editConf.radius.authServers.vrfRouter"
   ::= {er1646v2ManRadiusAuthServersEntry 83886080}

er1646v2ManRadiusAuthServersAddress OBJECT-TYPE
   SYNTAX      IpAddress
   MAX-ACCESS  read-write
   STATUS      current
   DESCRIPTION
      "Path: management.editConf.radius.authServers.address"
   ::= {er1646v2ManRadiusAuthServersEntry 16777216}

er1646v2ManRadiusAuthServersPort OBJECT-TYPE
   SYNTAX      Integer32
   MAX-ACCESS  read-write
   STATUS      current
   DESCRIPTION
      "Path: management.editConf.radius.authServers.port"
   ::= {er1646v2ManRadiusAuthServersEntry 134217728}

er1646v2ManRadiusAuthServersSource OBJECT-TYPE
   SYNTAX      DisplayString
   MAX-ACCESS  read-write
   STATUS      current
   DESCRIPTION
      "Path: management.editConf.radius.authServers.source"
   ::= {er1646v2ManRadiusAuthServersEntry 67108864}

er1646v2ManRadiusAuthServersSecret OBJECT-TYPE
   SYNTAX      DisplayString
   MAX-ACCESS  read-write
   STATUS      current
   DESCRIPTION
      "Path: management.editConf.radius.authServers.secret"
   ::= {er1646v2ManRadiusAuthServersEntry 33554432}

er1646v2ManRadiusAuthServersEncModeSecret OBJECT-TYPE
   SYNTAX      INTEGER
               {
               none (1),
               encrypt (2),
               encType1 (3),
               invalid (128)
               }
   MAX-ACCESS  read-write
   STATUS      current
   DESCRIPTION
      "Path: management.editConf.radius.authServers.encModeSecret

       Possibilities:
               none   (1)
               encrypt   (2)
               encType1   (3)
               invalid   (128)"
   ::= {er1646v2ManRadiusAuthServersEntry 100663296}

er1646v2ManRadiusAuthServersEncSecret OBJECT-TYPE
   SYNTAX      DisplayString
   MAX-ACCESS  read-write
   STATUS      current
   DESCRIPTION
      "Path: management.editConf.radius.authServers.encSecret"
   ::= {er1646v2ManRadiusAuthServersEntry 117440512}

er1646v2ManRadiusAuthServersTimeOut OBJECT-TYPE
   SYNTAX      TimeTicks
   MAX-ACCESS  read-write
   STATUS      current
   DESCRIPTION
      "Path: management.editConf.radius.authServers.timeOut

       Time in centi-second."
   ::= {er1646v2ManRadiusAuthServersEntry 50331648}


er1646v2ManTacacs OBJECT IDENTIFIER ::= {er1646v2Man 81}

er1646v2ManTacacsSSC OBJECT IDENTIFIER ::= {er1646v2ManTacacs 1}

er1646v2ManTacacsEntry OBJECT IDENTIFIER ::= {er1646v2ManTacacsSSC 1}

er1646v2ManTacacsLogin OBJECT-TYPE
   SYNTAX      INTEGER
               {
               disabled (0),
               enabled (1),
               fallback (2),
               reverseFallback (3)
               }
   MAX-ACCESS  read-write
   STATUS      current
   DESCRIPTION
      "Path: management.editConf.tacacs.login

       Possibilities:
               disabled   (0)
               enabled   (1)
               fallback   (2)
               reverseFallback   (3)"
   ::= {er1646v2ManTacacsEntry 83886080}

er1646v2ManTacacsAuthServers OBJECT-TYPE
   SYNTAX      SEQUENCE OF Er1646v2ManTacacsAuthServersEntry
   MAX-ACCESS  not-accessible
   STATUS      current
   DESCRIPTION
      ""
   ::= {er1646v2ManTacacs 16777216}

er1646v2ManTacacsAuthServersEntry OBJECT-TYPE
   SYNTAX      Er1646v2ManTacacsAuthServersEntry
   MAX-ACCESS  not-accessible
   STATUS      current
   DESCRIPTION
      ""
   INDEX      { er1646v2ManTacacsAuthServersTableIx }
   ::= {er1646v2ManTacacsAuthServers 1}

Er1646v2ManTacacsAuthServersEntry ::=
   SEQUENCE
      {
      er1646v2ManTacacsAuthServersActions
         VariableLengthTableActions,
      er1646v2ManTacacsAuthServersTableIx
         TableIndex,
      er1646v2ManTacacsAuthServersVrfRouter
         DisplayString,
      er1646v2ManTacacsAuthServersAddress
         IpAddress,
      er1646v2ManTacacsAuthServersSource
         DisplayString,
      er1646v2ManTacacsAuthServersSecret
         DisplayString,
      er1646v2ManTacacsAuthServersEncModeSecret
         INTEGER,
      er1646v2ManTacacsAuthServersEncSecret
         DisplayString,
      er1646v2ManTacacsAuthServersTimeOut
         TimeTicks
      }

er1646v2ManTacacsAuthServersActions OBJECT-TYPE
   SYNTAX      VariableLengthTableActions
   MAX-ACCESS  read-write
   STATUS      current
   DESCRIPTION
      "By way of this field, some manipulations
       on this table may be performed."
   ::= {er1646v2ManTacacsAuthServersEntry 2}

er1646v2ManTacacsAuthServersTableIx OBJECT-TYPE
   SYNTAX      TableIndex
   MAX-ACCESS  not-accessible
   STATUS      current
   DESCRIPTION
      ""
   ::= {er1646v2ManTacacsAuthServersEntry 11}

er1646v2ManTacacsAuthServersVrfRouter OBJECT-TYPE
   SYNTAX      DisplayString
   MAX-ACCESS  read-write
   STATUS      current
   DESCRIPTION
      "Path: management.editConf.tacacs.authServers.vrfRouter"
   ::= {er1646v2ManTacacsAuthServersEntry 117440512}

er1646v2ManTacacsAuthServersAddress OBJECT-TYPE
   SYNTAX      IpAddress
   MAX-ACCESS  read-write
   STATUS      current
   DESCRIPTION
      "Path: management.editConf.tacacs.authServers.address"
   ::= {er1646v2ManTacacsAuthServersEntry 16777216}

er1646v2ManTacacsAuthServersSource OBJECT-TYPE
   SYNTAX      DisplayString
   MAX-ACCESS  read-write
   STATUS      current
   DESCRIPTION
      "Path: management.editConf.tacacs.authServers.source"
   ::= {er1646v2ManTacacsAuthServersEntry 33554432}

er1646v2ManTacacsAuthServersSecret OBJECT-TYPE
   SYNTAX      DisplayString
   MAX-ACCESS  read-write
   STATUS      current
   DESCRIPTION
      "Path: management.editConf.tacacs.authServers.secret"
   ::= {er1646v2ManTacacsAuthServersEntry 50331648}

er1646v2ManTacacsAuthServersEncModeSecret OBJECT-TYPE
   SYNTAX      INTEGER
               {
               none (1),
               encrypt (2),
               encType1 (3),
               invalid (128)
               }
   MAX-ACCESS  read-write
   STATUS      current
   DESCRIPTION
      "Path: management.editConf.tacacs.authServers.encModeSecret

       Possibilities:
               none   (1)
               encrypt   (2)
               encType1   (3)
               invalid   (128)"
   ::= {er1646v2ManTacacsAuthServersEntry 134217728}

er1646v2ManTacacsAuthServersEncSecret OBJECT-TYPE
   SYNTAX      DisplayString
   MAX-ACCESS  read-write
   STATUS      current
   DESCRIPTION
      "Path: management.editConf.tacacs.authServers.encSecret"
   ::= {er1646v2ManTacacsAuthServersEntry 150994944}

er1646v2ManTacacsAuthServersTimeOut OBJECT-TYPE
   SYNTAX      TimeTicks
   MAX-ACCESS  read-write
   STATUS      current
   DESCRIPTION
      "Path: management.editConf.tacacs.authServers.timeOut

       Time in centi-second."
   ::= {er1646v2ManTacacsAuthServersEntry 67108864}


er1646v2ManTimeWindows OBJECT IDENTIFIER ::= {er1646v2Man 93}

er1646v2ManTimeWindowsSSCTable OBJECT-TYPE
   SYNTAX      SEQUENCE OF Er1646v2ManTimeWindowsEntry
   MAX-ACCESS  not-accessible
   STATUS      current
   DESCRIPTION
      "ranges with time intervals"
   ::= {er1646v2ManTimeWindows 1}

er1646v2ManTimeWindowsEntry OBJECT-TYPE
   SYNTAX      Er1646v2ManTimeWindowsEntry
   MAX-ACCESS  not-accessible
   STATUS      current
   DESCRIPTION
      ""
   INDEX      { er1646v2ManTimeWindowsTableIx }
   ::= {er1646v2ManTimeWindowsSSCTable 1}

Er1646v2ManTimeWindowsEntry ::=
   SEQUENCE
      {
      er1646v2ManTimeWindowsActions
         VariableLengthTableActions,
      er1646v2ManTimeWindowsTableIx
         TableIndex,
      er1646v2ManTimeWindowsName
         DisplayString
      }

er1646v2ManTimeWindowsActions OBJECT-TYPE
   SYNTAX      VariableLengthTableActions
   MAX-ACCESS  read-write
   STATUS      current
   DESCRIPTION
      "By way of this field, some manipulations
       on this table may be performed."
   ::= {er1646v2ManTimeWindowsEntry 2}

er1646v2ManTimeWindowsTableIx OBJECT-TYPE
   SYNTAX      TableIndex
   MAX-ACCESS  not-accessible
   STATUS      current
   DESCRIPTION
      ""
   ::= {er1646v2ManTimeWindowsEntry 11}

er1646v2ManTimeWindowsName OBJECT-TYPE
   SYNTAX      DisplayString
   MAX-ACCESS  read-write
   STATUS      current
   DESCRIPTION
      "Path: management.editConf.timeWindows.name"
   ::= {er1646v2ManTimeWindowsEntry 16777216}

er1646v2ManTimeWindowsPeriods OBJECT-TYPE
   SYNTAX      SEQUENCE OF Er1646v2ManTimeWindowsPeriodsEntry
   MAX-ACCESS  not-accessible
   STATUS      current
   DESCRIPTION
      ""
   ::= {er1646v2ManTimeWindows 33554432}

er1646v2ManTimeWindowsPeriodsEntry OBJECT-TYPE
   SYNTAX      Er1646v2ManTimeWindowsPeriodsEntry
   MAX-ACCESS  not-accessible
   STATUS      current
   DESCRIPTION
      ""
   INDEX      { er1646v2ManTimeWindowsTableIx,
                er1646v2ManTimeWindowsPeriodsTableIx }
   ::= {er1646v2ManTimeWindowsPeriods 1}

Er1646v2ManTimeWindowsPeriodsEntry ::=
   SEQUENCE
      {
      er1646v2ManTimeWindowsPeriodsActions
         VariableLengthTableActions,
      er1646v2ManTimeWindowsPeriodsTableIx
         TableIndex,
      er1646v2ManTimeWindowsPeriodsDay
         Integer32,
      er1646v2ManTimeWindowsPeriodsFrom
         DisplayString,
      er1646v2ManTimeWindowsPeriodsTo
         DisplayString
      }

er1646v2ManTimeWindowsPeriodsActions OBJECT-TYPE
   SYNTAX      VariableLengthTableActions
   MAX-ACCESS  read-write
   STATUS      current
   DESCRIPTION
      "By way of this field, some manipulations
       on this table may be performed."
   ::= {er1646v2ManTimeWindowsPeriodsEntry 2}

er1646v2ManTimeWindowsPeriodsTableIx OBJECT-TYPE
   SYNTAX      TableIndex
   MAX-ACCESS  not-accessible
   STATUS      current
   DESCRIPTION
      ""
   ::= {er1646v2ManTimeWindowsPeriodsEntry 11}

er1646v2ManTimeWindowsPeriodsDay OBJECT-TYPE
   SYNTAX      Integer32
   MAX-ACCESS  read-write
   STATUS      current
   DESCRIPTION
      "Path: management.editConf.timeWindows.periods.day

       Bit meanings:
               bit 0 = sunday,
               bit 1 = monday,
               bit 2 = tuesday,
               bit 3 = wednesday,
               bit 4 = thursday,
               bit 5 = friday,
               bit 6 = saturday"
   ::= {er1646v2ManTimeWindowsPeriodsEntry 16777216}

er1646v2ManTimeWindowsPeriodsFrom OBJECT-TYPE
   SYNTAX      DisplayString
   MAX-ACCESS  read-write
   STATUS      current
   DESCRIPTION
      "Path: management.editConf.timeWindows.periods.from"
   ::= {er1646v2ManTimeWindowsPeriodsEntry 33554432}

er1646v2ManTimeWindowsPeriodsTo OBJECT-TYPE
   SYNTAX      DisplayString
   MAX-ACCESS  read-write
   STATUS      current
   DESCRIPTION
      "Path: management.editConf.timeWindows.periods.to"
   ::= {er1646v2ManTimeWindowsPeriodsEntry 50331648}


er1646v2ManAlarmMask OBJECT-TYPE
   SYNTAX      Integer32
   MAX-ACCESS  read-write
   STATUS      current
   DESCRIPTION
      "Path: management.editConf.alarmMask
       Info: managementAlarmMask

       Bit meanings:
               bit 1 = ntpSyncLoss"
   ::= {er1646v2Man 28}


er1646v2ManAlarmLev OBJECT IDENTIFIER ::= {er1646v2Man 29}

er1646v2ManAlarmLevSSC OBJECT IDENTIFIER ::= {er1646v2ManAlarmLev 1}

er1646v2ManAlarmLevEntry OBJECT IDENTIFIER ::= {er1646v2ManAlarmLevSSC 1}

er1646v2ManAlarmLevNtpSyncLoss OBJECT-TYPE
   SYNTAX      Integer32
   MAX-ACCESS  read-write
   STATUS      current
   DESCRIPTION
      "Path: management.editConf.alarmLevel.ntpSyncLoss"
   ::= {er1646v2ManAlarmLevEntry 33554432}


er1646v2ManTimeServer OBJECT-TYPE
   SYNTAX      IpAddress
   MAX-ACCESS  read-write
   STATUS      current
   DESCRIPTION
      "Path: management.editConf.timeServer
       Info: ipAdEntAddr"
   ::= {er1646v2Man 50}


er1646v2ManTimeAdvService OBJECT IDENTIFIER ::= {er1646v2Man 65}

er1646v2ManTimeAdvServiceSSC OBJECT IDENTIFIER ::= {er1646v2ManTimeAdvService 1}

er1646v2ManTimeAdvServiceEntry OBJECT IDENTIFIER ::= {er1646v2ManTimeAdvServiceSSC 1}

er1646v2ManTimeAdvServicePreferredServer OBJECT-TYPE
   SYNTAX      DisplayString
   MAX-ACCESS  read-write
   STATUS      current
   DESCRIPTION
      "Path: management.editConf.timeAdvService.preferredServer"
   ::= {er1646v2ManTimeAdvServiceEntry 16777216}

er1646v2ManTimeAdvServiceSourceIp OBJECT-TYPE
   SYNTAX      DisplayString
   MAX-ACCESS  read-write
   STATUS      current
   DESCRIPTION
      "Path: management.editConf.timeAdvService.sourceIp"
   ::= {er1646v2ManTimeAdvServiceEntry 50331648}

er1646v2ManTimeAdvServiceRouterType OBJECT-TYPE
   SYNTAX      INTEGER
               {
               ipV4 (1),
               ipV6 (2)
               }
   MAX-ACCESS  read-write
   STATUS      current
   DESCRIPTION
      "Path: management.editConf.timeAdvService.routerType

       Possibilities:
               ipV4   (1)
               ipV6   (2)"
   ::= {er1646v2ManTimeAdvServiceEntry 167772160}

er1646v2ManTimeAdvServicePriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: management.editConf.timeAdvService.priority

       Possibilities:
               queue1   (0)
               queue2   (1)
               queue3   (2)
               queue4   (3)
               queue5   (4)
               lowDelayQueue   (5)
               lowDelay2Queue   (6)
               systemQueue   (7)"
   ::= {er1646v2ManTimeAdvServiceEntry 117440512}

er1646v2ManTimeAdvServiceTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: management.editConf.timeAdvService.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2ManTimeAdvServiceEntry 134217728}

er1646v2ManTimeAdvServiceVrfRouter OBJECT-TYPE
   SYNTAX      DisplayString
   MAX-ACCESS  read-write
   STATUS      current
   DESCRIPTION
      "Path: management.editConf.timeAdvService.vrfRouter"
   ::= {er1646v2ManTimeAdvServiceEntry 67108864}

er1646v2ManTimeAdvServiceAccept OBJECT-TYPE
   SYNTAX      INTEGER
               {
               allUnicasts (1),
               serverUnicast (2)
               }
   MAX-ACCESS  read-write
   STATUS      current
   DESCRIPTION
      "Path: management.editConf.timeAdvService.accept

       Possibilities:
               allUnicasts   (1)
               serverUnicast   (2)"
   ::= {er1646v2ManTimeAdvServiceEntry 33554432}

er1646v2ManTimeAdvServicePrecision OBJECT-TYPE
   SYNTAX      INTEGER
               {
               s10exp0 (1),
               s10expm3 (2)
               }
   MAX-ACCESS  read-write
   STATUS      current
   DESCRIPTION
      "Path: management.editConf.timeAdvService.precision

       Possibilities:
               10exp0   (1)
               10exp-3   (2)"
   ::= {er1646v2ManTimeAdvServiceEntry 83886080}

er1646v2ManTimeAdvServiceMode OBJECT-TYPE
   SYNTAX      INTEGER
               {
               client (1),
               clientServer (2)
               }
   MAX-ACCESS  read-write
   STATUS      current
   DESCRIPTION
      "Path: management.editConf.timeAdvService.mode

       Possibilities:
               client   (1)
               clientServer   (2)"
   ::= {er1646v2ManTimeAdvServiceEntry 100663296}

er1646v2ManTimeAdvServiceBackupServers OBJECT-TYPE
   SYNTAX      SEQUENCE OF Er1646v2ManTimeAdvServiceBackupServersEntry
   MAX-ACCESS  not-accessible
   STATUS      current
   DESCRIPTION
      ""
   ::= {er1646v2ManTimeAdvService 150994944}

er1646v2ManTimeAdvServiceBackupServersEntry OBJECT-TYPE
   SYNTAX      Er1646v2ManTimeAdvServiceBackupServersEntry
   MAX-ACCESS  not-accessible
   STATUS      current
   DESCRIPTION
      ""
   INDEX      { er1646v2ManTimeAdvServiceBackupServersTableIx }
   ::= {er1646v2ManTimeAdvServiceBackupServers 1}

Er1646v2ManTimeAdvServiceBackupServersEntry ::=
   SEQUENCE
      {
      er1646v2ManTimeAdvServiceBackupServersActions
         VariableLengthTableActions,
      er1646v2ManTimeAdvServiceBackupServersTableIx
         TableIndex,
      er1646v2ManTimeAdvServiceBackupServersServerIp
         DisplayString,
      er1646v2ManTimeAdvServiceBackupServersSourceIp
         DisplayString,
      er1646v2ManTimeAdvServiceBackupServersRouterType
         INTEGER,
      er1646v2ManTimeAdvServiceBackupServersVrfRouter
         DisplayString
      }

er1646v2ManTimeAdvServiceBackupServersActions OBJECT-TYPE
   SYNTAX      VariableLengthTableActions
   MAX-ACCESS  read-write
   STATUS      current
   DESCRIPTION
      "By way of this field, some manipulations
       on this table may be performed."
   ::= {er1646v2ManTimeAdvServiceBackupServersEntry 2}

er1646v2ManTimeAdvServiceBackupServersTableIx OBJECT-TYPE
   SYNTAX      TableIndex
   MAX-ACCESS  not-accessible
   STATUS      current
   DESCRIPTION
      ""
   ::= {er1646v2ManTimeAdvServiceBackupServersEntry 11}

er1646v2ManTimeAdvServiceBackupServersServerIp OBJECT-TYPE
   SYNTAX      DisplayString
   MAX-ACCESS  read-write
   STATUS      current
   DESCRIPTION
      "Path: management.editConf.timeAdvService.backupServers.serverIp"
   ::= {er1646v2ManTimeAdvServiceBackupServersEntry 536870912}

er1646v2ManTimeAdvServiceBackupServersSourceIp OBJECT-TYPE
   SYNTAX      DisplayString
   MAX-ACCESS  read-write
   STATUS      current
   DESCRIPTION
      "Path: management.editConf.timeAdvService.backupServers.sourceIp"
   ::= {er1646v2ManTimeAdvServiceBackupServersEntry 1073741824}

er1646v2ManTimeAdvServiceBackupServersRouterType OBJECT-TYPE
   SYNTAX      INTEGER
               {
               ipV4 (1),
               ipV6 (2)
               }
   MAX-ACCESS  read-write
   STATUS      current
   DESCRIPTION
      "Path: management.editConf.timeAdvService.backupServers.routerType

       Possibilities:
               ipV4   (1)
               ipV6   (2)"
   ::= {er1646v2ManTimeAdvServiceBackupServersEntry 1610612736}

er1646v2ManTimeAdvServiceBackupServersVrfRouter OBJECT-TYPE
   SYNTAX      DisplayString
   MAX-ACCESS  read-write
   STATUS      current
   DESCRIPTION
      "Path: management.editConf.timeAdvService.backupServers.vrfRouter"
   ::= {er1646v2ManTimeAdvServiceBackupServersEntry 2147483648}


er1646v2ManTimeZone OBJECT IDENTIFIER ::= {er1646v2Man 51}

er1646v2ManTimeZoneSSC OBJECT IDENTIFIER ::= {er1646v2ManTimeZone 1}

er1646v2ManTimeZoneEntry OBJECT IDENTIFIER ::= {er1646v2ManTimeZoneSSC 1}

er1646v2ManTimeZoneTimeZone OBJECT-TYPE
   SYNTAX      INTEGER
               {
               utcm12 (0),
               utcm11 (1),
               utcm10 (2),
               utcm9 (3),
               utcm8 (4),
               utcm7 (5),
               utcm6 (6),
               utcm5 (7),
               utcm4 (8),
               utcm3 (9),
               utcm2 (10),
               utcm1 (11),
               utc (12),
               utcp1 (13),
               utcp2 (14),
               utcp3 (15),
               utcp4 (16),
               utcp5 (17),
               utcp6 (18),
               utcp7 (19),
               utcp8 (20),
               utcp9 (21),
               utcp10 (22),
               utcp11 (23),
               utcp12 (24)
               }
   MAX-ACCESS  read-write
   STATUS      current
   DESCRIPTION
      "Path: management.editConf.timeZone.timeZone

       Possibilities:
               utc-12   (0)
               utc-11   (1)
               utc-10   (2)
               utc-9   (3)
               utc-8   (4)
               utc-7   (5)
               utc-6   (6)
               utc-5   (7)
               utc-4   (8)
               utc-3   (9)
               utc-2   (10)
               utc-1   (11)
               utc   (12)
               utc+1   (13)
               utc+2   (14)
               utc+3   (15)
               utc+4   (16)
               utc+5   (17)
               utc+6   (18)
               utc+7   (19)
               utc+8   (20)
               utc+9   (21)
               utc+10   (22)
               utc+11   (23)
               utc+12   (24)"
   ::= {er1646v2ManTimeZoneEntry 16777216}

er1646v2ManTimeZoneTimeZoneOffset OBJECT-TYPE
   SYNTAX      INTEGER
               {
               sm45min (14),
               sm30min (29),
               sm15min (44),
               s0min (59),
               sp15min (74),
               sp30min (89),
               sp45min (104)
               }
   MAX-ACCESS  read-write
   STATUS      current
   DESCRIPTION
      "Path: management.editConf.timeZone.timeZoneOffset

       Possibilities:
               -45min   (14)
               -30min   (29)
               -15min   (44)
               0min   (59)
               +15min   (74)
               +30min   (89)
               +45min   (104)"
   ::= {er1646v2ManTimeZoneEntry 50331648}

er1646v2ManTimeZoneDaylightSaving OBJECT-TYPE
   SYNTAX      INTEGER
               {
               none (0),
               manual (100),
               australia (3),
               europeanUnion (1),
               newZealand (4),
               uSA (2)
               }
   MAX-ACCESS  read-write
   STATUS      current
   DESCRIPTION
      "Path: management.editConf.timeZone.daylightSaving

       Possibilities:
               none   (0)
               manual   (100)
               australia   (3)
               europeanUnion   (1)
               newZealand   (4)
               uSA   (2)"
   ::= {er1646v2ManTimeZoneEntry 33554432}

er1646v2ManTimeZoneDaylightSavingManualRuleStartSummerDay OBJECT-TYPE
   SYNTAX      INTEGER
               {
               firstSunday (2),
               secondSunday (3),
               thirdSunday (4),
               fourthSunday (5),
               lastSunday (1),
               firstFriday (52),
               secondFriday (53),
               thirdFriday (54),
               fourthFriday (55),
               lastFriday (51)
               }
   MAX-ACCESS  read-write
   STATUS      current
   DESCRIPTION
      "Path: management.editConf.timeZone.daylightSavingManual.rule.startSummerDay

       Possibilities:
               firstSunday   (2)
               secondSunday   (3)
               thirdSunday   (4)
               fourthSunday   (5)
               lastSunday   (1)
               firstFriday   (52)
               secondFriday   (53)
               thirdFriday   (54)
               fourthFriday   (55)
               lastFriday   (51)"
   ::= {er1646v2ManTimeZoneEntry 67174656}

er1646v2ManTimeZoneDaylightSavingManualRuleStartSummerMonth OBJECT-TYPE
   SYNTAX      INTEGER
               {
               jan (1),
               feb (2),
               mar (3),
               apr (4),
               may (5),
               jun (6),
               jul (7),
               aug (8),
               sep (9),
               oct (10),
               nov (11),
               dec (12)
               }
   MAX-ACCESS  read-write
   STATUS      current
   DESCRIPTION
      "Path: management.editConf.timeZone.daylightSavingManual.rule.startSummerMonth

       Possibilities:
               jan   (1)
               feb   (2)
               mar   (3)
               apr   (4)
               may   (5)
               jun   (6)
               jul   (7)
               aug   (8)
               sep   (9)
               oct   (10)
               nov   (11)
               dec   (12)"
   ::= {er1646v2ManTimeZoneEntry 67174912}

er1646v2ManTimeZoneDaylightSavingManualRuleStartSummerHour OBJECT-TYPE
   SYNTAX      Integer32
   MAX-ACCESS  read-write
   STATUS      current
   DESCRIPTION
      "Path: management.editConf.timeZone.daylightSavingManual.rule.startSummerHour"
   ::= {er1646v2ManTimeZoneEntry 67175680}

er1646v2ManTimeZoneDaylightSavingManualRuleEndSummerDay OBJECT-TYPE
   SYNTAX      INTEGER
               {
               firstSunday (2),
               secondSunday (3),
               thirdSunday (4),
               fourthSunday (5),
               lastSunday (1),
               firstFriday (52),
               secondFriday (53),
               thirdFriday (54),
               fourthFriday (55),
               lastFriday (51)
               }
   MAX-ACCESS  read-write
   STATUS      current
   DESCRIPTION
      "Path: management.editConf.timeZone.daylightSavingManual.rule.endSummerDay

       Possibilities:
               firstSunday   (2)
               secondSunday   (3)
               thirdSunday   (4)
               fourthSunday   (5)
               lastSunday   (1)
               firstFriday   (52)
               secondFriday   (53)
               thirdFriday   (54)
               fourthFriday   (55)
               lastFriday   (51)"
   ::= {er1646v2ManTimeZoneEntry 67175168}

er1646v2ManTimeZoneDaylightSavingManualRuleEndSummerMonth OBJECT-TYPE
   SYNTAX      INTEGER
               {
               jan (1),
               feb (2),
               mar (3),
               apr (4),
               may (5),
               jun (6),
               jul (7),
               aug (8),
               sep (9),
               oct (10),
               nov (11),
               dec (12)
               }
   MAX-ACCESS  read-write
   STATUS      current
   DESCRIPTION
      "Path: management.editConf.timeZone.daylightSavingManual.rule.endSummerMonth

       Possibilities:
               jan   (1)
               feb   (2)
               mar   (3)
               apr   (4)
               may   (5)
               jun   (6)
               jul   (7)
               aug   (8)
               sep   (9)
               oct   (10)
               nov   (11)
               dec   (12)"
   ::= {er1646v2ManTimeZoneEntry 67175424}

er1646v2ManTimeZoneDaylightSavingManualRuleEndSummerHour OBJECT-TYPE
   SYNTAX      Integer32
   MAX-ACCESS  read-write
   STATUS      current
   DESCRIPTION
      "Path: management.editConf.timeZone.daylightSavingManual.rule.endSummerHour"
   ::= {er1646v2ManTimeZoneEntry 67175936}


er1646v2ManSyslog OBJECT IDENTIFIER ::= {er1646v2Man 53}

er1646v2ManSyslogSSC OBJECT IDENTIFIER ::= {er1646v2ManSyslog 1}

er1646v2ManSyslogEntry OBJECT IDENTIFIER ::= {er1646v2ManSyslogSSC 1}

er1646v2ManSyslogSeparator OBJECT-TYPE
   SYNTAX      DisplayString
   MAX-ACCESS  read-write
   STATUS      current
   DESCRIPTION
      "Path: management.editConf.syslog.separator"
   ::= {er1646v2ManSyslogEntry 16777216}

er1646v2ManSyslogFacilityAlarms OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.alarms

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50397184}

er1646v2ManSyslogFacilityAlarmEvents OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.alarmEvents

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50462720}

er1646v2ManSyslogFacilityAccess OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.access

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50528256}

er1646v2ManSyslogFacilityDbase OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.dbase

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50593792}

er1646v2ManSyslogFacilityMessage OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.message

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50659328}

er1646v2ManSyslogFacilityTracing OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.tracing

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50724864}

er1646v2ManSyslogFacilityDhcpServer OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.dhcpServer

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50790400}

er1646v2ManSyslogFacilityNat OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.nat

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50855936}

er1646v2ManSyslogFacilityExecManager OBJECT-TYPE
   SYNTAX      INTEGER
               {
               kernel (0),
               user (1),
               mail (2),
               daemon (3),
               auth (4),
               syslog (5),
               lpr (6),
               news (7),
               uucp (8),
               sys9 (9),
               sys10 (10),
               sys11 (11),
               sys12 (12),
               sys13 (13),
               sys14 (14),
               cron (15),
               local0 (16),
               local1 (17),
               local2 (18),
               local3 (19),
               local4 (20),
               local5 (21),
               local6 (22),
               local7 (23)
               }
   MAX-ACCESS  read-write
   STATUS      current
   DESCRIPTION
      "Path: management.editConf.syslog.facility.execManager

       Possibilities:
               kernel   (0)
               user   (1)
               mail   (2)
               daemon   (3)
               auth   (4)
               syslog   (5)
               lpr   (6)
               news   (7)
               uucp   (8)
               sys9   (9)
               sys10   (10)
               sys11   (11)
               sys12   (12)
               sys13   (13)
               sys14   (14)
               cron   (15)
               local0   (16)
               local1   (17)
               local2   (18)
               local3   (19)
               local4   (20)
               local5   (21)
               local6   (22)
               local7   (23)"
   ::= {er1646v2ManSyslogEntry 50987008}

er1646v2ManSyslogDestinations OBJECT-TYPE
   SYNTAX      SEQUENCE OF Er1646v2ManSyslogDestinationsEntry
   MAX-ACCESS  not-accessible
   STATUS      current
   DESCRIPTION
      ""
   ::= {er1646v2ManSyslog 33554432}

er1646v2ManSyslogDestinationsEntry OBJECT-TYPE
   SYNTAX      Er1646v2ManSyslogDestinationsEntry
   MAX-ACCESS  not-accessible
   STATUS      current
   DESCRIPTION
      ""
   INDEX      { er1646v2ManSyslogDestinationsTableIx }
   ::= {er1646v2ManSyslogDestinations 1}

Er1646v2ManSyslogDestinationsEntry ::=
   SEQUENCE
      {
      er1646v2ManSyslogDestinationsActions
         VariableLengthTableActions,
      er1646v2ManSyslogDestinationsTableIx
         TableIndex,
      er1646v2ManSyslogDestinationsSourceIp
         IpAddress,
      er1646v2ManSyslogDestinationsSource
         DisplayString,
      er1646v2ManSyslogDestinationsAddress
         IpAddress,
      er1646v2ManSyslogDestinationsVrfRouter
         DisplayString,
      er1646v2ManSyslogDestinationsApplicationsAlarms
         INTEGER,
      er1646v2ManSyslogDestinationsApplicationsAlarmEvents
         INTEGER,
      er1646v2ManSyslogDestinationsApplicationsAccess
         INTEGER,
      er1646v2ManSyslogDestinationsApplicationsDbase
         INTEGER,
      er1646v2ManSyslogDestinationsApplicationsMessage
         INTEGER,
      er1646v2ManSyslogDestinationsApplicationsTracing
         INTEGER,
      er1646v2ManSyslogDestinationsApplicationsDhcpServer
         INTEGER,
      er1646v2ManSyslogDestinationsApplicationsNat
         INTEGER,
      er1646v2ManSyslogDestinationsApplicationsZbFirewall
         INTEGER,
      er1646v2ManSyslogDestinationsApplicationsExecManager
         INTEGER
      }

er1646v2ManSyslogDestinationsActions OBJECT-TYPE
   SYNTAX      VariableLengthTableActions
   MAX-ACCESS  read-write
   STATUS      current
   DESCRIPTION
      "By way of this field, some manipulations
       on this table may be performed."
   ::= {er1646v2ManSyslogDestinationsEntry 2}

er1646v2ManSyslogDestinationsTableIx OBJECT-TYPE
   SYNTAX      TableIndex
   MAX-ACCESS  not-accessible
   STATUS      current
   DESCRIPTION
      ""
   ::= {er1646v2ManSyslogDestinationsEntry 11}

er1646v2ManSyslogDestinationsSourceIp OBJECT-TYPE
   SYNTAX      IpAddress
   MAX-ACCESS  read-write
   STATUS      current
   DESCRIPTION
      "Path: management.editConf.syslog.destinations.sourceIp"
   ::= {er1646v2ManSyslogDestinationsEntry 33554432}

er1646v2ManSyslogDestinationsSource OBJECT-TYPE
   SYNTAX      DisplayString
   MAX-ACCESS  read-write
   STATUS      current
   DESCRIPTION
      "Path: management.editConf.syslog.destinations.source"
   ::= {er1646v2ManSyslogDestinationsEntry 83886080}

er1646v2ManSyslogDestinationsAddress OBJECT-TYPE
   SYNTAX      IpAddress
   MAX-ACCESS  read-write
   STATUS      current
   DESCRIPTION
      "Path: management.editConf.syslog.destinations.address"
   ::= {er1646v2ManSyslogDestinationsEntry 16777216}

er1646v2ManSyslogDestinationsVrfRouter OBJECT-TYPE
   SYNTAX      DisplayString
   MAX-ACCESS  read-write
   STATUS      current
   DESCRIPTION
      "Path: management.editConf.syslog.destinations.vrfRouter"
   ::= {er1646v2ManSyslogDestinationsEntry 50331648}

er1646v2ManSyslogDestinationsApplicationsAlarms OBJECT-TYPE
   SYNTAX      INTEGER
               {
               disabled (0),
               enabled (1)
               }
   MAX-ACCESS  read-write
   STATUS      current
   DESCRIPTION
      "Path: management.editConf.syslog.destinations.applications.alarms

       Possibilities:
               disabled   (0)
               enabled   (1)"
   ::= {er1646v2ManSyslogDestinationsEntry 67174400}

er1646v2ManSyslogDestinationsApplicationsAlarmEvents OBJECT-TYPE
   SYNTAX      INTEGER
               {
               disabled (0),
               enabled (1)
               }
   MAX-ACCESS  read-write
   STATUS      current
   DESCRIPTION
      "Path: management.editConf.syslog.destinations.applications.alarmEvents

       Possibilities:
               disabled   (0)
               enabled   (1)"
   ::= {er1646v2ManSyslogDestinationsEntry 67239936}

er1646v2ManSyslogDestinationsApplicationsAccess OBJECT-TYPE
   SYNTAX      INTEGER
               {
               disabled (0),
               enabled (1)
               }
   MAX-ACCESS  read-write
   STATUS      current
   DESCRIPTION
      "Path: management.editConf.syslog.destinations.applications.access

       Possibilities:
               disabled   (0)
               enabled   (1)"
   ::= {er1646v2ManSyslogDestinationsEntry 67305472}

er1646v2ManSyslogDestinationsApplicationsDbase OBJECT-TYPE
   SYNTAX      INTEGER
               {
               disabled (0),
               enabled (1)
               }
   MAX-ACCESS  read-write
   STATUS      current
   DESCRIPTION
      "Path: management.editConf.syslog.destinations.applications.dbase

       Possibilities:
               disabled   (0)
               enabled   (1)"
   ::= {er1646v2ManSyslogDestinationsEntry 67371008}

er1646v2ManSyslogDestinationsApplicationsMessage OBJECT-TYPE
   SYNTAX      INTEGER
               {
               disabled (0),
               enabled (1)
               }
   MAX-ACCESS  read-write
   STATUS      current
   DESCRIPTION
      "Path: management.editConf.syslog.destinations.applications.message

       Possibilities:
               disabled   (0)
               enabled   (1)"
   ::= {er1646v2ManSyslogDestinationsEntry 67436544}

er1646v2ManSyslogDestinationsApplicationsTracing OBJECT-TYPE
   SYNTAX      INTEGER
               {
               disabled (0),
               enabled (1)
               }
   MAX-ACCESS  read-write
   STATUS      current
   DESCRIPTION
      "Path: management.editConf.syslog.destinations.applications.tracing

       Possibilities:
               disabled   (0)
               enabled   (1)"
   ::= {er1646v2ManSyslogDestinationsEntry 67502080}

er1646v2ManSyslogDestinationsApplicationsDhcpServer OBJECT-TYPE
   SYNTAX      INTEGER
               {
               disabled (0),
               enabled (1)
               }
   MAX-ACCESS  read-write
   STATUS      current
   DESCRIPTION
      "Path: management.editConf.syslog.destinations.applications.dhcpServer

       Possibilities:
               disabled   (0)
               enabled   (1)"
   ::= {er1646v2ManSyslogDestinationsEntry 67567616}

er1646v2ManSyslogDestinationsApplicationsNat OBJECT-TYPE
   SYNTAX      INTEGER
               {
               disabled (0),
               enabled (1)
               }
   MAX-ACCESS  read-write
   STATUS      current
   DESCRIPTION
      "Path: management.editConf.syslog.destinations.applications.nat

       Possibilities:
               disabled   (0)
               enabled   (1)"
   ::= {er1646v2ManSyslogDestinationsEntry 67633152}

er1646v2ManSyslogDestinationsApplicationsZbFirewall OBJECT-TYPE
   SYNTAX      INTEGER
               {
               disabled (0),
               enabled (1)
               }
   MAX-ACCESS  read-write
   STATUS      current
   DESCRIPTION
      "Path: management.editConf.syslog.destinations.applications.zbFirewall

       Possibilities:
               disabled   (0)
               enabled   (1)"
   ::= {er1646v2ManSyslogDestinationsEntry 67698688}

er1646v2ManSyslogDestinationsApplicationsExecManager OBJECT-TYPE
   SYNTAX      INTEGER
               {
               disabled (0),
               enabled (1)
               }
   MAX-ACCESS  read-write
   STATUS      current
   DESCRIPTION
      "Path: management.editConf.syslog.destinations.applications.execManager

       Possibilities:
               disabled   (0)
               enabled   (1)"
   ::= {er1646v2ManSyslogDestinationsEntry 67764224}


er1646v2ManAccessControl OBJECT IDENTIFIER ::= {er1646v2Man 56}

er1646v2ManAccessControlSSC OBJECT IDENTIFIER ::= {er1646v2ManAccessControl 1}

er1646v2ManAccessControlEntry OBJECT IDENTIFIER ::= {er1646v2ManAccessControlSSC 1}

er1646v2ManAccessControlAlarmMaxFail OBJECT-TYPE
   SYNTAX      Integer32
   MAX-ACCESS  read-write
   STATUS      current
   DESCRIPTION
      "Path: management.editConf.accessControl.alarm.maxFailCnt"
   ::= {er1646v2ManAccessControlEntry 16842752}

er1646v2ManAccessControlAlarmPeriod OBJECT-TYPE
   SYNTAX      TimeTicks
   MAX-ACCESS  read-write
   STATUS      current
   DESCRIPTION
      "Path: management.editConf.accessControl.alarm.period

       Time in centi-second."
   ::= {er1646v2ManAccessControlEntry 16908288}

er1646v2ManAccessControlLogClearPeriod OBJECT-TYPE
   SYNTAX      TimeTicks
   MAX-ACCESS  read-write
   STATUS      current
   DESCRIPTION
      "Path: management.editConf.accessControl.log.clearPeriod

       Time in centi-second."
   ::= {er1646v2ManAccessControlEntry 33685504}


er1646v2ManCtrlPortProtocol OBJECT-TYPE
   SYNTAX      INTEGER
               {
               console (1),
               disabled (2)
               }
   MAX-ACCESS  read-write
   STATUS      current
   DESCRIPTION
      "Path: management.editConf.ctrlPortProtocol
       Info: ctrlPortProtocol

       Possibilities:
               console   (1)
               disabled   (2)"
   ::= {er1646v2Man 22}



sr1646v2Man OBJECT IDENTIFIER ::= {r1646v2Man 14}


sr1646v2ManCms2Address OBJECT-TYPE
   SYNTAX      Integer32
   MAX-ACCESS  read-only
   STATUS      current
   DESCRIPTION
      "Path: management.status.cms2Address
       Info: cms2Address"
   ::= {sr1646v2Man 31}


sr1646v2ManLogStats OBJECT IDENTIFIER ::= {sr1646v2Man 58}

sr1646v2ManLogStatsSSCTable OBJECT-TYPE
   SYNTAX      SEQUENCE OF Sr1646v2ManLogStatsEntry
   MAX-ACCESS  not-accessible
   STATUS      current
   DESCRIPTION
      "Table about saving statistics."
   ::= {sr1646v2ManLogStats 1}

sr1646v2ManLogStatsEntry OBJECT-TYPE
   SYNTAX      Sr1646v2ManLogStatsEntry
   MAX-ACCESS  not-accessible
   STATUS      current
   DESCRIPTION
      ""
   INDEX      { sr1646v2ManLogStatsTableIx }
   ::= {sr1646v2ManLogStatsSSCTable 1}

Sr1646v2ManLogStatsEntry ::=
   SEQUENCE
      {
      sr1646v2ManLogStatsTableIx
         TableIndex,
      sr1646v2ManLogStatsName
         DisplayString,
      sr1646v2ManLogStatsFileName
         DisplayString,
      sr1646v2ManLogStatsError
         DisplayString,
      sr1646v2ManLogStatsColumnsHeader
         DisplayString
      }

sr1646v2ManLogStatsTableIx OBJECT-TYPE
   SYNTAX      TableIndex
   MAX-ACCESS  not-accessible
   STATUS      current
   DESCRIPTION
      ""
   ::= {sr1646v2ManLogStatsEntry 11}

sr1646v2ManLogStatsName OBJECT-TYPE
   SYNTAX      DisplayString
   MAX-ACCESS  read-only
   STATUS      current
   DESCRIPTION
      "Path: management.status.logStats.name"
   ::= {sr1646v2ManLogStatsEntry 50331648}

sr1646v2ManLogStatsFileName OBJECT-TYPE
   SYNTAX      DisplayString
   MAX-ACCESS  read-only
   STATUS      current
   DESCRIPTION
      "Path: management.status.logStats.fileName"
   ::= {sr1646v2ManLogStatsEntry 16777216}

sr1646v2ManLogStatsError OBJECT-TYPE
   SYNTAX      DisplayString
   MAX-ACCESS  read-only
   STATUS      current
   DESCRIPTION
      "Path: management.status.logStats.error"
   ::= {sr1646v2ManLogStatsEntry 33554432}

sr1646v2ManLogStatsColumnsHeader OBJECT-TYPE
   SYNTAX      DisplayString
   MAX-ACCESS  read-only
   STATUS      current
   DESCRIPTION
      "Path: management.status.logStats.columnsHeader"
   ::= {sr1646v2ManLogStatsEntry 67108864}


sr1646v2ManExecManager OBJECT IDENTIFIER ::= {sr1646v2Man 217}

sr1646v2ManExecManagerSSCTable OBJECT-TYPE
   SYNTAX      SEQUENCE OF Sr1646v2ManExecManagerEntry
   MAX-ACCESS  not-accessible
   STATUS      current
   DESCRIPTION
      "follow up tasks, test and execute"
   ::= {sr1646v2ManExecManager 1}

sr1646v2ManExecManagerEntry OBJECT-TYPE
   SYNTAX      Sr1646v2ManExecManagerEntry
   MAX-ACCESS  not-accessible
   STATUS      current
   DESCRIPTION
      ""
   INDEX      { sr1646v2ManExecManagerTableIx }
   ::= {sr1646v2ManExecManagerSSCTable 1}

Sr1646v2ManExecManagerEntry ::=
   SEQUENCE
      {
      sr1646v2ManExecManagerTableIx
         TableIndex,
      sr1646v2ManExecManagerName
         DisplayString,
      sr1646v2ManExecManagerStatus
         INTEGER,
      sr1646v2ManExecManagerLastActivity
         DisplayString,
      sr1646v2ManExecManagerLastActivityLineNumber
         Integer32,
      sr1646v2ManExecManagerError
         DisplayString
      }

sr1646v2ManExecManagerTableIx OBJECT-TYPE
   SYNTAX      TableIndex
   MAX-ACCESS  not-accessible
   STATUS      current
   DESCRIPTION
      ""
   ::= {sr1646v2ManExecManagerEntry 11}

sr1646v2ManExecManagerName OBJECT-TYPE
   SYNTAX      DisplayString
   MAX-ACCESS  read-only
   STATUS      current
   DESCRIPTION
      "Path: management.status.execManager.name"
   ::= {sr1646v2ManExecManagerEntry 16777216}

sr1646v2ManExecManagerStatus OBJECT-TYPE
   SYNTAX      INTEGER
               {
               disabled (1),
               waitForStart (2),
               running (3),
               error (4)
               }
   MAX-ACCESS  read-only
   STATUS      current
   DESCRIPTION
      "Path: management.status.execManager.status

       Possibilities:
               disabled   (1)
               waitForStart   (2)
               running   (3)
               error   (4)"
   ::= {sr1646v2ManExecManagerEntry 33554432}

sr1646v2ManExecManagerLastActivity OBJECT-TYPE
   SYNTAX      DisplayString
   MAX-ACCESS  read-only
   STATUS      current
   DESCRIPTION
      "Path: management.status.execManager.lastActivity"
   ::= {sr1646v2ManExecManagerEntry 83886080}

sr1646v2ManExecManagerLastActivityLineNumber OBJECT-TYPE
   SYNTAX      Integer32
   MAX-ACCESS  read-only
   STATUS      current
   DESCRIPTION
      "Path: management.status.execManager.lastActivityLineNumber"
   ::= {sr1646v2ManExecManagerEntry 100663296}

sr1646v2ManExecManagerError OBJECT-TYPE
   SYNTAX      DisplayString
   MAX-ACCESS  read-only
   STATUS      current
   DESCRIPTION
      "Path: management.status.execManager.error"
   ::= {sr1646v2ManExecManagerEntry 67108864}

sr1646v2ManExecManagerTask OBJECT-TYPE
   SYNTAX      SEQUENCE OF Sr1646v2ManExecManagerTaskEntry
   MAX-ACCESS  not-accessible
   STATUS      current
   DESCRIPTION
      ""
   ::= {sr1646v2ManExecManager 50331648}

sr1646v2ManExecManagerTaskEntry OBJECT-TYPE
   SYNTAX      Sr1646v2ManExecManagerTaskEntry
   MAX-ACCESS  not-accessible
   STATUS      current
   DESCRIPTION
      ""
   INDEX      { sr1646v2ManExecManagerTableIx,
                sr1646v2ManExecManagerTaskTableIx }
   ::= {sr1646v2ManExecManagerTask 1}

Sr1646v2ManExecManagerTaskEntry ::=
   SEQUENCE
      {
      sr1646v2ManExecManagerTaskTableIx
         TableIndex,
      sr1646v2ManExecManagerTaskName
         DisplayString,
      sr1646v2ManExecManagerTaskAction
         INTEGER,
      sr1646v2ManExecManagerTaskSingleAction
         DisplayString,
      sr1646v2ManExecManagerTaskLastActivity
         DisplayString,
      sr1646v2ManExecManagerTaskLastInfo
         DisplayString
      }

sr1646v2ManExecManagerTaskTableIx OBJECT-TYPE
   SYNTAX      TableIndex
   MAX-ACCESS  not-accessible
   STATUS      current
   DESCRIPTION
      ""
   ::= {sr1646v2ManExecManagerTaskEntry 11}

sr1646v2ManExecManagerTaskName OBJECT-TYPE
   SYNTAX      DisplayString
   MAX-ACCESS  read-only
   STATUS      current
   DESCRIPTION
      "Path: management.status.execManager.task.name"
   ::= {sr1646v2ManExecManagerTaskEntry 16777216}

sr1646v2ManExecManagerTaskAction OBJECT-TYPE
   SYNTAX      INTEGER
               {
               calculate (28),
               counterGet (3),
               counterSet (4),
               counterInc (5),
               counterDec (6),
               execCommand (2),
               globalStringGet (25),
               globalStringSet (24),
               globalVarGet (8),
               globalVarSet (7),
               localStringGet (23),
               localStringSet (27),
               localVarGet (22),
               localVarSet (26),
               numberGet (18),
               numberSet (19),
               print (29),
               remark (1),
               sendEvent (30),
               scan (31),
               start (20),
               stop (21),
               stringGet (16),
               stringSet (17),
               timerGet (9),
               timerSet (10),
               timerStart (11),
               timerStop (12),
               wait (13),
               waitTime (15),
               waitWeekDayTime (14)
               }
   MAX-ACCESS  read-only
   STATUS      current
   DESCRIPTION
      "Path: management.status.execManager.task.action

       Possibilities:
               calculate   (28)
               counterGet   (3)
               counterSet   (4)
               counterInc   (5)
               counterDec   (6)
               execCommand   (2)
               globalStringGet   (25)
               globalStringSet   (24)
               globalVarGet   (8)
               globalVarSet   (7)
               localStringGet   (23)
               localStringSet   (27)
               localVarGet   (22)
               localVarSet   (26)
               numberGet   (18)
               numberSet   (19)
               print   (29)
               remark   (1)
               sendEvent   (30)
               scan   (31)
               start   (20)
               stop   (21)
               stringGet   (16)
               stringSet   (17)
               timerGet   (9)
               timerSet   (10)
               timerStart   (11)
               timerStop   (12)
               wait   (13)
               waitTime   (15)
               waitWeekDayTime   (14)"
   ::= {sr1646v2ManExecManagerTaskEntry 33554432}

sr1646v2ManExecManagerTaskSingleAction OBJECT-TYPE
   SYNTAX      DisplayString
   MAX-ACCESS  read-only
   STATUS      current
   DESCRIPTION
      "Path: management.status.execManager.task.singleAction"
   ::= {sr1646v2ManExecManagerTaskEntry 50331648}

sr1646v2ManExecManagerTaskLastActivity OBJECT-TYPE
   SYNTAX      DisplayString
   MAX-ACCESS  read-only
   STATUS      current
   DESCRIPTION
      "Path: management.status.execManager.task.lastActivity"
   ::= {sr1646v2ManExecManagerTaskEntry 83886080}

sr1646v2ManExecManagerTaskLastInfo OBJECT-TYPE
   SYNTAX      DisplayString
   MAX-ACCESS  read-only
   STATUS      current
   DESCRIPTION
      "Path: management.status.execManager.task.lastInfo"
   ::= {sr1646v2ManExecManagerTaskEntry 67108864}


sr1646v2ManTcpSession OBJECT IDENTIFIER ::= {sr1646v2Man 45}

sr1646v2ManTcpSessionSSCTable OBJECT-TYPE
   SYNTAX      SEQUENCE OF Sr1646v2ManTcpSessionEntry
   MAX-ACCESS  not-accessible
   STATUS      current
   DESCRIPTION
      "TCP session overview"
   ::= {sr1646v2ManTcpSession 1}

sr1646v2ManTcpSessionEntry OBJECT-TYPE
   SYNTAX      Sr1646v2ManTcpSessionEntry
   MAX-ACCESS  not-accessible
   STATUS      current
   DESCRIPTION
      ""
   INDEX      { sr1646v2ManTcpSessionTableIx }
   ::= {sr1646v2ManTcpSessionSSCTable 1}

Sr1646v2ManTcpSessionEntry ::=
   SEQUENCE
      {
      sr1646v2ManTcpSessionTableIx
         TableIndex,
      sr1646v2ManTcpSessionLocalIp
         IpAddress,
      sr1646v2ManTcpSessionLocalPort
         INTEGER,
      sr1646v2ManTcpSessionRemoteIp
         IpAddress,
      sr1646v2ManTcpSessionRemotePort
         INTEGER,
      sr1646v2ManTcpSessionState
         INTEGER,
      sr1646v2ManTcpSessionType
         INTEGER,
      sr1646v2ManTcpSessionInOctets
         Counter32,
      sr1646v2ManTcpSessionOutOctets
         Counter32,
      sr1646v2ManTcpSessionOutQLen
         Gauge32,
      sr1646v2ManTcpSessionOutQOctets
         Counter32,
      sr1646v2ManTcpSessionOutOfOrder
         Counter32,
      sr1646v2ManTcpSessionLastActivity
         TimeTicks,
      sr1646v2ManTcpSessionDuration
         TimeTicks
      }

sr1646v2ManTcpSessionTableIx OBJECT-TYPE
   SYNTAX      TableIndex
   MAX-ACCESS  not-accessible
   STATUS      current
   DESCRIPTION
      ""
   ::= {sr1646v2ManTcpSessionEntry 11}

sr1646v2ManTcpSessionLocalIp OBJECT-TYPE
   SYNTAX      IpAddress
   MAX-ACCESS  read-only
   STATUS      current
   DESCRIPTION
      "Path: management.status.tcpSession.localIp"
   ::= {sr1646v2ManTcpSessionEntry 16777216}

sr1646v2ManTcpSessionLocalPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: management.status.tcpSession.localPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1646v2ManTcpSessionEntry 33554432}

sr1646v2ManTcpSessionRemoteIp OBJECT-TYPE
   SYNTAX      IpAddress
   MAX-ACCESS  read-only
   STATUS      current
   DESCRIPTION
      "Path: management.status.tcpSession.remoteIp"
   ::= {sr1646v2ManTcpSessionEntry 50331648}

sr1646v2ManTcpSessionRemotePort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: management.status.tcpSession.remotePort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1646v2ManTcpSessionEntry 67108864}

sr1646v2ManTcpSessionState OBJECT-TYPE
   SYNTAX      INTEGER
               {
               closed (0),
               listen (1),
               synSent (2),
               synReceived (3),
               established (4),
               finWait1 (5),
               finWait2 (6),
               closing (7),
               timeWait (8),
               closeWait (9),
               lastAck (10),
               notFound (11),
               dnsReqSent (12)
               }
   MAX-ACCESS  read-only
   STATUS      current
   DESCRIPTION
      "Path: management.status.tcpSession.state

       Possibilities:
               closed   (0)
               listen   (1)
               synSent   (2)
               synReceived   (3)
               established   (4)
               finWait1   (5)
               finWait2   (6)
               closing   (7)
               timeWait   (8)
               closeWait   (9)
               lastAck   (10)
               notFound   (11)
               dnsReqSent   (12)"
   ::= {sr1646v2ManTcpSessionEntry 83886080}

sr1646v2ManTcpSessionType OBJECT-TYPE
   SYNTAX      INTEGER
               {
               passivesstatic (1),
               active (2),
               passivesdynamic (3)
               }
   MAX-ACCESS  read-only
   STATUS      current
   DESCRIPTION
      "Path: management.status.tcpSession.type

       Possibilities:
               passive static   (1)
               active   (2)
               passive dynamic   (3)"
   ::= {sr1646v2ManTcpSessionEntry 117440512}

sr1646v2ManTcpSessionInOctets OBJECT-TYPE
   SYNTAX      Counter32
   MAX-ACCESS  read-only
   STATUS      current
   DESCRIPTION
      "Path: management.status.tcpSession.inOctets

       32 bit unsigned wrappable counter."
   ::= {sr1646v2ManTcpSessionEntry 134217728}

sr1646v2ManTcpSessionOutOctets OBJECT-TYPE
   SYNTAX      Counter32
   MAX-ACCESS  read-only
   STATUS      current
   DESCRIPTION
      "Path: management.status.tcpSession.outOctets

       32 bit unsigned wrappable counter."
   ::= {sr1646v2ManTcpSessionEntry 150994944}

sr1646v2ManTcpSessionOutQLen OBJECT-TYPE
   SYNTAX      Gauge32
   MAX-ACCESS  read-only
   STATUS      current
   DESCRIPTION
      "Path: management.status.tcpSession.outQLen

       32 bit unsigned gauge value."
   ::= {sr1646v2ManTcpSessionEntry 167772160}

sr1646v2ManTcpSessionOutQOctets OBJECT-TYPE
   SYNTAX      Counter32
   MAX-ACCESS  read-only
   STATUS      current
   DESCRIPTION
      "Path: management.status.tcpSession.outQOctets

       32 bit unsigned wrappable counter."
   ::= {sr1646v2ManTcpSessionEntry 184549376}

sr1646v2ManTcpSessionOutOfOrder OBJECT-TYPE
   SYNTAX      Counter32
   MAX-ACCESS  read-only
   STATUS      current
   DESCRIPTION
      "Path: management.status.tcpSession.outOfOrder

       32 bit unsigned wrappable counter."
   ::= {sr1646v2ManTcpSessionEntry 201326592}

sr1646v2ManTcpSessionLastActivity OBJECT-TYPE
   SYNTAX      TimeTicks
   MAX-ACCESS  read-only
   STATUS      current
   DESCRIPTION
      "Path: management.status.tcpSession.lastActivity

       Time in centi-second."
   ::= {sr1646v2ManTcpSessionEntry 234881024}

sr1646v2ManTcpSessionDuration OBJECT-TYPE
   SYNTAX      TimeTicks
   MAX-ACCESS  read-only
   STATUS      current
   DESCRIPTION
      "Path: management.status.tcpSession.duration

       Time in centi-second."
   ::= {sr1646v2ManTcpSessionEntry 218103808}


sr1646v2ManCwmp OBJECT IDENTIFIER ::= {sr1646v2Man 75}

sr1646v2ManCwmpSSC OBJECT IDENTIFIER ::= {sr1646v2ManCwmp 1}

sr1646v2ManCwmpEntry OBJECT IDENTIFIER ::= {sr1646v2ManCwmpSSC 1}

sr1646v2ManCwmpRunning OBJECT-TYPE
   SYNTAX      INTEGER
               {
               no (0),
               yes (1)
               }
   MAX-ACCESS  read-only
   STATUS      current
   DESCRIPTION
      "Path: management.status.cwmp.running

       Possibilities:
               no   (0)
               yes   (1)"
   ::= {sr1646v2ManCwmpEntry 16777216}

sr1646v2ManCwmpSessionState OBJECT-TYPE
   SYNTAX      INTEGER
               {
               inactive (0),
               resolvingsacsIp (1),
               searchingsextIp (2),
               initialising (3),
               connecting (4),
               authenticating (5),
               active (6),
               succesfull (7),
               searchingsvrf (8),
               resolvingssource (9)
               }
   MAX-ACCESS  read-only
   STATUS      current
   DESCRIPTION
      "Path: management.status.cwmp.sessionState

       Possibilities:
               inactive   (0)
               resolving acsIp   (1)
               searching extIp   (2)
               initialising   (3)
               connecting   (4)
               authenticating   (5)
               active   (6)
               succesfull   (7)
               searching vrf   (8)
               resolving source   (9)"
   ::= {sr1646v2ManCwmpEntry 33554432}

sr1646v2ManCwmpAcsIpAddress OBJECT-TYPE
   SYNTAX      IpAddress
   MAX-ACCESS  read-only
   STATUS      current
   DESCRIPTION
      "Path: management.status.cwmp.acsIpAddress"
   ::= {sr1646v2ManCwmpEntry 50331648}

sr1646v2ManCwmpAcsIpV6Address OBJECT-TYPE
   SYNTAX      Ipv6Address
   MAX-ACCESS  read-only
   STATUS      current
   DESCRIPTION
      "Path: management.status.cwmp.acsIpV6Address

       ipv6 address"
   ::= {sr1646v2ManCwmpEntry 234881024}

sr1646v2ManCwmpAcsUrl OBJECT-TYPE
   SYNTAX      DisplayString
   MAX-ACCESS  read-only
   STATUS      current
   DESCRIPTION
      "Path: management.status.cwmp.acsUrl"
   ::= {sr1646v2ManCwmpEntry 167772160}

sr1646v2ManCwmpConnectionRequestUrl OBJECT-TYPE
   SYNTAX      DisplayString
   MAX-ACCESS  read-only
   STATUS      current
   DESCRIPTION
      "Path: management.status.cwmp.connectionRequestUrl"
   ::= {sr1646v2ManCwmpEntry 67108864}

sr1646v2ManCwmpTimeSinceLastSession OBJECT-TYPE
   SYNTAX      TimeTicks
   MAX-ACCESS  read-only
   STATUS      current
   DESCRIPTION
      "Path: management.status.cwmp.timeSinceLastSession

       Time in centi-second."
   ::= {sr1646v2ManCwmpEntry 83886080}

sr1646v2ManCwmpTimeUntilNextSession OBJECT-TYPE
   SYNTAX      TimeTicks
   MAX-ACCESS  read-only
   STATUS      current
   DESCRIPTION
      "Path: management.status.cwmp.timeUntilNextSession

       Time in centi-second."
   ::= {sr1646v2ManCwmpEntry 100663296}

sr1646v2ManCwmpLastSession OBJECT-TYPE
   SYNTAX      INTEGER
               {
               inactive (0),
               acsIpsnotsresolved (1),
               extIpsnotsfound (2),
               initialisationsfailed (3),
               connectionsfailed (4),
               authenticationsfailed (5),
               exchangesfailed (6),
               successful (7),
               vrfRoutersnotsresolved (8),
               sourcesnotsresolved (9)
               }
   MAX-ACCESS  read-only
   STATUS      current
   DESCRIPTION
      "Path: management.status.cwmp.lastSession

       Possibilities:
               inactive   (0)
               acsIp not resolved   (1)
               extIp not found   (2)
               initialisation failed   (3)
               connection failed   (4)
               authentication failed   (5)
               exchange failed   (6)
               successful   (7)
               vrfRouter not resolved   (8)
               source not resolved   (9)"
   ::= {sr1646v2ManCwmpEntry 117440512}

sr1646v2ManCwmpLastError OBJECT-TYPE
   SYNTAX      DisplayString
   MAX-ACCESS  read-only
   STATUS      current
   DESCRIPTION
      "Path: management.status.cwmp.lastError"
   ::= {sr1646v2ManCwmpEntry 184549376}

sr1646v2ManCwmpTimeUntilNextRetry OBJECT-TYPE
   SYNTAX      TimeTicks
   MAX-ACCESS  read-only
   STATUS      current
   DESCRIPTION
      "Path: management.status.cwmp.timeUntilNextRetry

       Time in centi-second."
   ::= {sr1646v2ManCwmpEntry 134217728}

sr1646v2ManCwmpConfigVersion OBJECT-TYPE
   SYNTAX      DisplayString
   MAX-ACCESS  read-only
   STATUS      current
   DESCRIPTION
      "Path: management.status.cwmp.configVersion"
   ::= {sr1646v2ManCwmpEntry 150994944}

sr1646v2ManCwmpInformTimeUtc OBJECT-TYPE
   SYNTAX      DisplayString
   MAX-ACCESS  read-only
   STATUS      current
   DESCRIPTION
      "Path: management.status.cwmp.informTimeUtc"
   ::= {sr1646v2ManCwmpEntry 201326592}

sr1646v2ManCwmpCurrentUtc OBJECT-TYPE
   SYNTAX      DisplayString
   MAX-ACCESS  read-only
   STATUS      current
   DESCRIPTION
      "Path: management.status.cwmp.currentUtc"
   ::= {sr1646v2ManCwmpEntry 218103808}


sr1646v2ManRadius OBJECT IDENTIFIER ::= {sr1646v2Man 61}

sr1646v2ManRadiusSSC OBJECT IDENTIFIER ::= {sr1646v2ManRadius 1}

sr1646v2ManRadiusEntry OBJECT IDENTIFIER ::= {sr1646v2ManRadiusSSC 1}

sr1646v2ManRadiusAuthServer OBJECT-TYPE
   SYNTAX      IpAddress
   MAX-ACCESS  read-only
   STATUS      current
   DESCRIPTION
      "Path: management.status.radius.authServer"
   ::= {sr1646v2ManRadiusEntry 16777216}

sr1646v2ManRadiusAcctServer OBJECT-TYPE
   SYNTAX      IpAddress
   MAX-ACCESS  read-only
   STATUS      current
   DESCRIPTION
      "Path: management.status.radius.acctServer"
   ::= {sr1646v2ManRadiusEntry 50331648}

sr1646v2ManRadiusPendingRequests OBJECT-TYPE
   SYNTAX      Integer32
   MAX-ACCESS  read-only
   STATUS      current
   DESCRIPTION
      "Path: management.status.radius.pendingRequests"
   ::= {sr1646v2ManRadiusEntry 33554432}


sr1646v2ManTimeWindows OBJECT IDENTIFIER ::= {sr1646v2Man 94}

sr1646v2ManTimeWindowsSSCTable OBJECT-TYPE
   SYNTAX      SEQUENCE OF Sr1646v2ManTimeWindowsEntry
   MAX-ACCESS  not-accessible
   STATUS      current
   DESCRIPTION
      "ranges with time intervals"
   ::= {sr1646v2ManTimeWindows 1}

sr1646v2ManTimeWindowsEntry OBJECT-TYPE
   SYNTAX      Sr1646v2ManTimeWindowsEntry
   MAX-ACCESS  not-accessible
   STATUS      current
   DESCRIPTION
      ""
   INDEX      { sr1646v2ManTimeWindowsTableIx }
   ::= {sr1646v2ManTimeWindowsSSCTable 1}

Sr1646v2ManTimeWindowsEntry ::=
   SEQUENCE
      {
      sr1646v2ManTimeWindowsTableIx
         TableIndex,
      sr1646v2ManTimeWindowsName
         DisplayString,
      sr1646v2ManTimeWindowsState
         INTEGER
      }

sr1646v2ManTimeWindowsTableIx OBJECT-TYPE
   SYNTAX      TableIndex
   MAX-ACCESS  not-accessible
   STATUS      current
   DESCRIPTION
      ""
   ::= {sr1646v2ManTimeWindowsEntry 11}

sr1646v2ManTimeWindowsName OBJECT-TYPE
   SYNTAX      DisplayString
   MAX-ACCESS  read-only
   STATUS      current
   DESCRIPTION
      "Path: management.status.timeWindows.name"
   ::= {sr1646v2ManTimeWindowsEntry 16777216}

sr1646v2ManTimeWindowsState OBJECT-TYPE
   SYNTAX      INTEGER
               {
               disabled (0),
               enabled (1)
               }
   MAX-ACCESS  read-only
   STATUS      current
   DESCRIPTION
      "Path: management.status.timeWindows.state

       Possibilities:
               disabled   (0)
               enabled   (1)"
   ::= {sr1646v2ManTimeWindowsEntry 33554432}


sr1646v2ManTimeServer OBJECT IDENTIFIER ::= {sr1646v2Man 52}

sr1646v2ManTimeServerSSC OBJECT IDENTIFIER ::= {sr1646v2ManTimeServer 1}

sr1646v2ManTimeServerEntry OBJECT IDENTIFIER ::= {sr1646v2ManTimeServerSSC 1}

sr1646v2ManTimeServerState OBJECT-TYPE
   SYNTAX      INTEGER
               {
               noContact (0),
               notSynchronised (1),
               synchronised (2),
               notConfigured (3),
               waitForResponse (4),
               synchronisedStart (5),
               synchronised10expm0 (6),
               synchronised10expm1 (7),
               synchronised10expm2 (8),
               synchronised10expm3 (9),
               noSync10expm0 (10),
               noSync10expm1 (11),
               noSync10expm2 (12),
               noSync10expm3 (13)
               }
   MAX-ACCESS  read-only
   STATUS      current
   DESCRIPTION
      "Path: management.status.timeServer.state

       Possibilities:
               noContact   (0)
               notSynchronised   (1)
               synchronised   (2)
               notConfigured   (3)
               waitForResponse   (4)
               synchronisedStart   (5)
               synchronised10exp-0   (6)
               synchronised10exp-1   (7)
               synchronised10exp-2   (8)
               synchronised10exp-3   (9)
               noSync10exp-0   (10)
               noSync10exp-1   (11)
               noSync10exp-2   (12)
               noSync10exp-3   (13)"
   ::= {sr1646v2ManTimeServerEntry 16777216}

sr1646v2ManTimeServerConnection OBJECT-TYPE
   SYNTAX      INTEGER
               {
               noContact (0),
               notSynchronised (1),
               synchronised (2),
               notConfigured (3),
               waitForResponse (4),
               synchronisedStart (5),
               synchronised10expm0 (6),
               synchronised10expm1 (7),
               synchronised10expm2 (8),
               synchronised10expm3 (9),
               noSync10expm0 (10),
               noSync10expm1 (11),
               noSync10expm2 (12),
               noSync10expm3 (13)
               }
   MAX-ACCESS  read-only
   STATUS      current
   DESCRIPTION
      "Path: management.status.timeServer.connection

       Possibilities:
               noContact   (0)
               notSynchronised   (1)
               synchronised   (2)
               notConfigured   (3)
               waitForResponse   (4)
               synchronisedStart   (5)
               synchronised10exp-0   (6)
               synchronised10exp-1   (7)
               synchronised10exp-2   (8)
               synchronised10exp-3   (9)
               noSync10exp-0   (10)
               noSync10exp-1   (11)
               noSync10exp-2   (12)
               noSync10exp-3   (13)"
   ::= {sr1646v2ManTimeServerEntry 67108864}

sr1646v2ManTimeServerServer OBJECT-TYPE
   SYNTAX      IpAddress
   MAX-ACCESS  read-only
   STATUS      current
   DESCRIPTION
      "Path: management.status.timeServer.server"
   ::= {sr1646v2ManTimeServerEntry 83886080}

sr1646v2ManTimeServerSourceIp OBJECT-TYPE
   SYNTAX      IpAddress
   MAX-ACCESS  read-only
   STATUS      current
   DESCRIPTION
      "Path: management.status.timeServer.sourceIp"
   ::= {sr1646v2ManTimeServerEntry 117440512}

sr1646v2ManTimeServerServerIpV6 OBJECT-TYPE
   SYNTAX      Ipv6Address
   MAX-ACCESS  read-only
   STATUS      current
   DESCRIPTION
      "Path: management.status.timeServer.serverIpV6

       ipv6 address"
   ::= {sr1646v2ManTimeServerEntry 150994944}

sr1646v2ManTimeServerSourceIpV6 OBJECT-TYPE
   SYNTAX      Ipv6Address
   MAX-ACCESS  read-only
   STATUS      current
   DESCRIPTION
      "Path: management.status.timeServer.sourceIpV6

       ipv6 address"
   ::= {sr1646v2ManTimeServerEntry 167772160}

sr1646v2ManTimeServerStratum OBJECT-TYPE
   SYNTAX      INTEGER
               {
               unknown (0)
               }
   MAX-ACCESS  read-only
   STATUS      current
   DESCRIPTION
      "Path: management.status.timeServer.stratum

       Possibilities:
               unknown   (0)"
   ::= {sr1646v2ManTimeServerEntry 33554432}

sr1646v2ManTimeServerDelay OBJECT-TYPE
   SYNTAX      TimeTicks
   MAX-ACCESS  read-only
   STATUS      current
   DESCRIPTION
      "Path: management.status.timeServer.delay

       Time in centi-second."
   ::= {sr1646v2ManTimeServerEntry 50331648}

sr1646v2ManTimeServerTimeSinceLastUpdate OBJECT-TYPE
   SYNTAX      TimeTicks
   MAX-ACCESS  read-only
   STATUS      current
   DESCRIPTION
      "Path: management.status.timeServer.timeSinceLastUpdate

       Time in centi-second."
   ::= {sr1646v2ManTimeServerEntry 100663296}

sr1646v2ManTimeServerLastDifference OBJECT-TYPE
   SYNTAX      TimeTicks
   MAX-ACCESS  read-only
   STATUS      current
   DESCRIPTION
      "Path: management.status.timeServer.lastDifference

       Time in centi-second."
   ::= {sr1646v2ManTimeServerEntry 134217728}


sr1646v2ManSessions OBJECT IDENTIFIER ::= {sr1646v2Man 32}

sr1646v2ManSessionsSSCTable OBJECT-TYPE
   SYNTAX      SEQUENCE OF Sr1646v2ManSessionsEntry
   MAX-ACCESS  not-accessible
   STATUS      current
   DESCRIPTION
      ""
   ::= {sr1646v2ManSessions 1}

sr1646v2ManSessionsEntry OBJECT-TYPE
   SYNTAX      Sr1646v2ManSessionsEntry
   MAX-ACCESS  not-accessible
   STATUS      current
   DESCRIPTION
      ""
   INDEX      { sr1646v2ManSessionsTableIx }
   ::= {sr1646v2ManSessionsSSCTable 1}

Sr1646v2ManSessionsEntry ::=
   SEQUENCE
      {
      sr1646v2ManSessionsTableIx
         TableIndex,
      sr1646v2ManSessionsUser
         DisplayString,
      sr1646v2ManSessionsSource
         DisplayString,
      sr1646v2ManSessionsApplication
         INTEGER,
      sr1646v2ManSessionsInfo
         DisplayString,
      sr1646v2ManSessionsAccessRights
         Integer32,
      sr1646v2ManSessionsDuration
         TimeTicks
      }

sr1646v2ManSessionsTableIx OBJECT-TYPE
   SYNTAX      TableIndex
   MAX-ACCESS  not-accessible
   STATUS      current
   DESCRIPTION
      ""
   ::= {sr1646v2ManSessionsEntry 11}

sr1646v2ManSessionsUser OBJECT-TYPE
   SYNTAX      DisplayString
   MAX-ACCESS  read-only
   STATUS      current
   DESCRIPTION
      "Path: management.status.sessions.user"
   ::= {sr1646v2ManSessionsEntry 16777216}

sr1646v2ManSessionsSource OBJECT-TYPE
   SYNTAX      DisplayString
   MAX-ACCESS  read-only
   STATUS      current
   DESCRIPTION
      "Path: management.status.sessions.source"
   ::= {sr1646v2ManSessionsEntry 33554432}

sr1646v2ManSessionsApplication OBJECT-TYPE
   SYNTAX      INTEGER
               {
               none (0),
               cms2 (1),
               consolemcli (3),
               consolemcms2 (4),
               snmp (5),
               tftp (6),
               ftp (7),
               telnet (8),
               ssh (9),
               snmpv3 (10),
               httpmclassic (13),
               httpmtma (14),
               httpmeasyConfig (15),
               httpsmclassic (21),
               httpsmtma (22),
               httpsmeasyConfig (23)
               }
   MAX-ACCESS  read-only
   STATUS      current
   DESCRIPTION
      "Path: management.status.sessions.application

       Possibilities:
               none   (0)
               cms2   (1)
               console-cli   (3)
               console-cms2   (4)
               snmp   (5)
               tftp   (6)
               ftp   (7)
               telnet   (8)
               ssh   (9)
               snmpv3   (10)
               http-classic   (13)
               http-tma   (14)
               http-easyConfig   (15)
               https-classic   (21)
               https-tma   (22)
               https-easyConfig   (23)"
   ::= {sr1646v2ManSessionsEntry 50331648}

sr1646v2ManSessionsInfo OBJECT-TYPE
   SYNTAX      DisplayString
   MAX-ACCESS  read-only
   STATUS      current
   DESCRIPTION
      "Path: management.status.sessions.info"
   ::= {sr1646v2ManSessionsEntry 100663296}

sr1646v2ManSessionsAccessRights OBJECT-TYPE
   SYNTAX      Integer32
   MAX-ACCESS  read-only
   STATUS      current
   DESCRIPTION
      "Path: management.status.sessions.accessRights

       Bit meanings:
               bit 0 = readAccess,
               bit 1 = writeAccess,
               bit 2 = securityAccess,
               bit 4 = fileSystemAccess,
               bit 5 = testAccess"
   ::= {sr1646v2ManSessionsEntry 67108864}

sr1646v2ManSessionsDuration OBJECT-TYPE
   SYNTAX      TimeTicks
   MAX-ACCESS  read-only
   STATUS      current
   DESCRIPTION
      "Path: management.status.sessions.duration

       Time in centi-second."
   ::= {sr1646v2ManSessionsEntry 83886080}


sr1646v2ManAlarmLog OBJECT IDENTIFIER ::= {sr1646v2Man 54}

sr1646v2ManAlarmLogSSCTable OBJECT-TYPE
   SYNTAX      SEQUENCE OF Sr1646v2ManAlarmLogEntry
   MAX-ACCESS  not-accessible
   STATUS      current
   DESCRIPTION
      "Table containing string representation of alarm history."
   ::= {sr1646v2ManAlarmLog 1}

sr1646v2ManAlarmLogEntry OBJECT-TYPE
   SYNTAX      Sr1646v2ManAlarmLogEntry
   MAX-ACCESS  not-accessible
   STATUS      current
   DESCRIPTION
      ""
   INDEX      { sr1646v2ManAlarmLogTableIx }
   ::= {sr1646v2ManAlarmLogSSCTable 1}

Sr1646v2ManAlarmLogEntry ::=
   SEQUENCE
      {
      sr1646v2ManAlarmLogTableIx
         TableIndex,
      sr1646v2ManAlarmLogTimeStamp
         DisplayString,
      sr1646v2ManAlarmLogSysUpTime
         TimeTicks,
      sr1646v2ManAlarmLogTotalAlarmLevel
         Integer32,
      sr1646v2ManAlarmLogAlarmLevel
         Integer32,
      sr1646v2ManAlarmLogAlarm
         DisplayString
      }

sr1646v2ManAlarmLogTableIx OBJECT-TYPE
   SYNTAX      TableIndex
   MAX-ACCESS  not-accessible
   STATUS      current
   DESCRIPTION
      ""
   ::= {sr1646v2ManAlarmLogEntry 11}

sr1646v2ManAlarmLogTimeStamp OBJECT-TYPE
   SYNTAX      DisplayString
   MAX-ACCESS  read-only
   STATUS      current
   DESCRIPTION
      "Path: management.status.alarmLog.timeStamp"
   ::= {sr1646v2ManAlarmLogEntry 16777216}

sr1646v2ManAlarmLogSysUpTime OBJECT-TYPE
   SYNTAX      TimeTicks
   MAX-ACCESS  read-only
   STATUS      current
   DESCRIPTION
      "Path: management.status.alarmLog.sysUpTime

       Time in centi-second."
   ::= {sr1646v2ManAlarmLogEntry 33554432}

sr1646v2ManAlarmLogTotalAlarmLevel OBJECT-TYPE
   SYNTAX      Integer32
   MAX-ACCESS  read-only
   STATUS      current
   DESCRIPTION
      "Path: management.status.alarmLog.totalAlarmLevel"
   ::= {sr1646v2ManAlarmLogEntry 50331648}

sr1646v2ManAlarmLogAlarmLevel OBJECT-TYPE
   SYNTAX      Integer32
   MAX-ACCESS  read-only
   STATUS      current
   DESCRIPTION
      "Path: management.status.alarmLog.alarmLevel"
   ::= {sr1646v2ManAlarmLogEntry 67108864}

sr1646v2ManAlarmLogAlarm OBJECT-TYPE
   SYNTAX      DisplayString
   MAX-ACCESS  read-only
   STATUS      current
   DESCRIPTION
      "Path: management.status.alarmLog.alarm"
   ::= {sr1646v2ManAlarmLogEntry 83886080}


sr1646v2ManAccessLog OBJECT IDENTIFIER ::= {sr1646v2Man 55}

sr1646v2ManAccessLogSSCTable OBJECT-TYPE
   SYNTAX      SEQUENCE OF Sr1646v2ManAccessLogEntry
   MAX-ACCESS  not-accessible
   STATUS      current
   DESCRIPTION
      "Table containing logging information about device accesses."
   ::= {sr1646v2ManAccessLog 1}

sr1646v2ManAccessLogEntry OBJECT-TYPE
   SYNTAX      Sr1646v2ManAccessLogEntry
   MAX-ACCESS  not-accessible
   STATUS      current
   DESCRIPTION
      ""
   INDEX      { sr1646v2ManAccessLogTableIx }
   ::= {sr1646v2ManAccessLogSSCTable 1}

Sr1646v2ManAccessLogEntry ::=
   SEQUENCE
      {
      sr1646v2ManAccessLogTableIx
         TableIndex,
      sr1646v2ManAccessLogTimeStamp
         DisplayString,
      sr1646v2ManAccessLogSysUpTime
         TimeTicks,
      sr1646v2ManAccessLogType
         INTEGER,
      sr1646v2ManAccessLogUser
         DisplayString,
      sr1646v2ManAccessLogApplication
         INTEGER,
      sr1646v2ManAccessLogAccessRights
         Integer32,
      sr1646v2ManAccessLogSource
         DisplayString,
      sr1646v2ManAccessLogInfo
         DisplayString
      }

sr1646v2ManAccessLogTableIx OBJECT-TYPE
   SYNTAX      TableIndex
   MAX-ACCESS  not-accessible
   STATUS      current
   DESCRIPTION
      ""
   ::= {sr1646v2ManAccessLogEntry 11}

sr1646v2ManAccessLogTimeStamp OBJECT-TYPE
   SYNTAX      DisplayString
   MAX-ACCESS  read-only
   STATUS      current
   DESCRIPTION
      "Path: management.status.accessLog.timeStamp"
   ::= {sr1646v2ManAccessLogEntry 16777216}

sr1646v2ManAccessLogSysUpTime OBJECT-TYPE
   SYNTAX      TimeTicks
   MAX-ACCESS  read-only
   STATUS      current
   DESCRIPTION
      "Path: management.status.accessLog.sysUpTime

       Time in centi-second."
   ::= {sr1646v2ManAccessLogEntry 33554432}

sr1646v2ManAccessLogType OBJECT-TYPE
   SYNTAX      INTEGER
               {
               login (1),
               loginFailure (2),
               accessFailureOn (3),
               accessFailureOff (4)
               }
   MAX-ACCESS  read-only
   STATUS      current
   DESCRIPTION
      "Path: management.status.accessLog.type

       Possibilities:
               login   (1)
               loginFailure   (2)
               accessFailureOn   (3)
               accessFailureOff   (4)"
   ::= {sr1646v2ManAccessLogEntry 50331648}

sr1646v2ManAccessLogUser OBJECT-TYPE
   SYNTAX      DisplayString
   MAX-ACCESS  read-only
   STATUS      current
   DESCRIPTION
      "Path: management.status.accessLog.user"
   ::= {sr1646v2ManAccessLogEntry 67108864}

sr1646v2ManAccessLogApplication OBJECT-TYPE
   SYNTAX      INTEGER
               {
               none (0),
               cms2 (1),
               consolemcli (3),
               consolemcms2 (4),
               snmp (5),
               tftp (6),
               ftp (7),
               telnet (8),
               ssh (9),
               snmpv3 (10),
               httpmclassic (13),
               httpmtma (14),
               httpmeasyConfig (15),
               httpsmclassic (21),
               httpsmtma (22),
               httpsmeasyConfig (23)
               }
   MAX-ACCESS  read-only
   STATUS      current
   DESCRIPTION
      "Path: management.status.accessLog.application

       Possibilities:
               none   (0)
               cms2   (1)
               console-cli   (3)
               console-cms2   (4)
               snmp   (5)
               tftp   (6)
               ftp   (7)
               telnet   (8)
               ssh   (9)
               snmpv3   (10)
               http-classic   (13)
               http-tma   (14)
               http-easyConfig   (15)
               https-classic   (21)
               https-tma   (22)
               https-easyConfig   (23)"
   ::= {sr1646v2ManAccessLogEntry 83886080}

sr1646v2ManAccessLogAccessRights OBJECT-TYPE
   SYNTAX      Integer32
   MAX-ACCESS  read-only
   STATUS      current
   DESCRIPTION
      "Path: management.status.accessLog.accessRights

       Bit meanings:
               bit 0 = readAccess,
               bit 1 = writeAccess,
               bit 2 = securityAccess,
               bit 4 = fileSystemAccess,
               bit 5 = testAccess"
   ::= {sr1646v2ManAccessLogEntry 100663296}

sr1646v2ManAccessLogSource OBJECT-TYPE
   SYNTAX      DisplayString
   MAX-ACCESS  read-only
   STATUS      current
   DESCRIPTION
      "Path: management.status.accessLog.source"
   ::= {sr1646v2ManAccessLogEntry 134217728}

sr1646v2ManAccessLogInfo OBJECT-TYPE
   SYNTAX      DisplayString
   MAX-ACCESS  read-only
   STATUS      current
   DESCRIPTION
      "Path: management.status.accessLog.info"
   ::= {sr1646v2ManAccessLogEntry 150994944}


sr1646v2ManSyslog OBJECT IDENTIFIER ::= {sr1646v2Man 57}

sr1646v2ManSyslogSSCTable OBJECT-TYPE
   SYNTAX      SEQUENCE OF Sr1646v2ManSyslogEntry
   MAX-ACCESS  not-accessible
   STATUS      current
   DESCRIPTION
      "Contains a list of each syslog destination as
                        specified in the configuration and the state
                        for each destination."
   ::= {sr1646v2ManSyslog 1}

sr1646v2ManSyslogEntry OBJECT-TYPE
   SYNTAX      Sr1646v2ManSyslogEntry
   MAX-ACCESS  not-accessible
   STATUS      current
   DESCRIPTION
      ""
   INDEX      { sr1646v2ManSyslogTableIx }
   ::= {sr1646v2ManSyslogSSCTable 1}

Sr1646v2ManSyslogEntry ::=
   SEQUENCE
      {
      sr1646v2ManSyslogTableIx
         TableIndex,
      sr1646v2ManSyslogAddress
         IpAddress,
      sr1646v2ManSyslogState
         INTEGER
      }

sr1646v2ManSyslogTableIx OBJECT-TYPE
   SYNTAX      TableIndex
   MAX-ACCESS  not-accessible
   STATUS      current
   DESCRIPTION
      ""
   ::= {sr1646v2ManSyslogEntry 11}

sr1646v2ManSyslogAddress OBJECT-TYPE
   SYNTAX      IpAddress
   MAX-ACCESS  read-only
   STATUS      current
   DESCRIPTION
      "Path: management.status.syslog.address"
   ::= {sr1646v2ManSyslogEntry 16777216}

sr1646v2ManSyslogState OBJECT-TYPE
   SYNTAX      INTEGER
               {
               ok (0),
               badSource (1),
               badIntfName (2),
               badVrfName (3)
               }
   MAX-ACCESS  read-only
   STATUS      current
   DESCRIPTION
      "Path: management.status.syslog.state

       Possibilities:
               ok   (0)
               badSource   (1)
               badIntfName   (2)
               badVrfName   (3)"
   ::= {sr1646v2ManSyslogEntry 33554432}



pr1646v2Man OBJECT IDENTIFIER ::= {r1646v2Man 12}


pr1646v2ManCms2SessionCount OBJECT-TYPE
   SYNTAX      Gauge32
   MAX-ACCESS  read-only
   STATUS      current
   DESCRIPTION
      "Path: management.performance.cms2SessionCount
       Info: Number of sessions currently in use.

       32 bit unsigned gauge value."
   ::= {pr1646v2Man 40}


pr1646v2ManTftpSessionCount OBJECT-TYPE
   SYNTAX      Gauge32
   MAX-ACCESS  read-only
   STATUS      current
   DESCRIPTION
      "Path: management.performance.tftpSessionCount
       Info: Number of sessions currently in use.

       32 bit unsigned gauge value."
   ::= {pr1646v2Man 41}


pr1646v2ManCliSessionCount OBJECT-TYPE
   SYNTAX      Gauge32
   MAX-ACCESS  read-only
   STATUS      current
   DESCRIPTION
      "Path: management.performance.cliSessionCount
       Info: Number of sessions currently in use.

       32 bit unsigned gauge value."
   ::= {pr1646v2Man 42}


pr1646v2ManTcpSessionCount OBJECT-TYPE
   SYNTAX      Gauge32
   MAX-ACCESS  read-only
   STATUS      current
   DESCRIPTION
      "Path: management.performance.tcpSessionCount
       Info: Number of sessions currently in use.

       32 bit unsigned gauge value."
   ::= {pr1646v2Man 43}


pr1646v2ManTcpSession OBJECT IDENTIFIER ::= {pr1646v2Man 47}

pr1646v2ManTcpSessionSSC OBJECT IDENTIFIER ::= {pr1646v2ManTcpSession 1}

pr1646v2ManTcpSessionEntry OBJECT IDENTIFIER ::= {pr1646v2ManTcpSessionSSC 1}

pr1646v2ManTcpSessionIncomingHttp OBJECT-TYPE
   SYNTAX      Counter32
   MAX-ACCESS  read-only
   STATUS      current
   DESCRIPTION
      "Path: management.performance.tcpSession.incoming.http

       32 bit unsigned wrappable counter."
   ::= {pr1646v2ManTcpSessionEntry 16842752}

pr1646v2ManTcpSessionIncomingHttps OBJECT-TYPE
   SYNTAX      Counter32
   MAX-ACCESS  read-only
   STATUS      current
   DESCRIPTION
      "Path: management.performance.tcpSession.incoming.https

       32 bit unsigned wrappable counter."
   ::= {pr1646v2ManTcpSessionEntry 17170432}

pr1646v2ManTcpSessionIncomingTelnet OBJECT-TYPE
   SYNTAX      Counter32
   MAX-ACCESS  read-only
   STATUS      current
   DESCRIPTION
      "Path: management.performance.tcpSession.incoming.telnet

       32 bit unsigned wrappable counter."
   ::= {pr1646v2ManTcpSessionEntry 16908288}

pr1646v2ManTcpSessionIncomingSsh OBJECT-TYPE
   SYNTAX      Counter32
   MAX-ACCESS  read-only
   STATUS      current
   DESCRIPTION
      "Path: management.performance.tcpSession.incoming.ssh

       32 bit unsigned wrappable counter."
   ::= {pr1646v2ManTcpSessionEntry 16973824}

pr1646v2ManTcpSessionIncomingFtpCtrl OBJECT-TYPE
   SYNTAX      Counter32
   MAX-ACCESS  read-only
   STATUS      current
   DESCRIPTION
      "Path: management.performance.tcpSession.incoming.ftpCtrl

       32 bit unsigned wrappable counter."
   ::= {pr1646v2ManTcpSessionEntry 17039360}

pr1646v2ManTcpSessionIncomingFtpData OBJECT-TYPE
   SYNTAX      Counter32
   MAX-ACCESS  read-only
   STATUS      current
   DESCRIPTION
      "Path: management.performance.tcpSession.incoming.ftpData

       32 bit unsigned wrappable counter."
   ::= {pr1646v2ManTcpSessionEntry 17104896}


pr1646v2ManTcpSyn OBJECT IDENTIFIER ::= {pr1646v2Man 76}

pr1646v2ManTcpSynSSC OBJECT IDENTIFIER ::= {pr1646v2ManTcpSyn 1}

pr1646v2ManTcpSynEntry OBJECT IDENTIFIER ::= {pr1646v2ManTcpSynSSC 1}

pr1646v2ManTcpSynTotalRxSyn OBJECT-TYPE
   SYNTAX      Counter32
   MAX-ACCESS  read-only
   STATUS      current
   DESCRIPTION
      "Path: management.performance.tcpSyn.total.rxSyn

       32 bit unsigned wrappable counter."
   ::= {pr1646v2ManTcpSynEntry 16842752}

pr1646v2ManTcpSynTotalMaxSynRate OBJECT-TYPE
   SYNTAX      Gauge32
   MAX-ACCESS  read-only
   STATUS      current
   DESCRIPTION
      "Path: management.performance.tcpSyn.total.maxSynRate

       32 bit unsigned gauge value."
   ::= {pr1646v2ManTcpSynEntry 16908288}

pr1646v2ManTcpSynTotalDropped OBJECT-TYPE
   SYNTAX      Counter32
   MAX-ACCESS  read-only
   STATUS      current
   DESCRIPTION
      "Path: management.performance.tcpSyn.total.dropped

       32 bit unsigned wrappable counter."
   ::= {pr1646v2ManTcpSynEntry 16973824}

pr1646v2ManTcpSynKnownPortsRxSyn OBJECT-TYPE
   SYNTAX      Counter32
   MAX-ACCESS  read-only
   STATUS      current
   DESCRIPTION
      "Path: management.performance.tcpSyn.knownPorts.rxSyn

       32 bit unsigned wrappable counter."
   ::= {pr1646v2ManTcpSynEntry 33619968}

pr1646v2ManTcpSynKnownPortsMaxSynRate OBJECT-TYPE
   SYNTAX      Gauge32
   MAX-ACCESS  read-only
   STATUS      current
   DESCRIPTION
      "Path: management.performance.tcpSyn.knownPorts.maxSynRate

       32 bit unsigned gauge value."
   ::= {pr1646v2ManTcpSynEntry 33685504}

pr1646v2ManTcpSynKnownPortsDropped OBJECT-TYPE
   SYNTAX      Counter32
   MAX-ACCESS  read-only
   STATUS      current
   DESCRIPTION
      "Path: management.performance.tcpSyn.knownPorts.dropped

       32 bit unsigned wrappable counter."
   ::= {pr1646v2ManTcpSynEntry 33751040}


pr1646v2ManLogStats OBJECT IDENTIFIER ::= {pr1646v2Man 78}

pr1646v2ManLogStatsSSC OBJECT IDENTIFIER ::= {pr1646v2ManLogStats 1}

pr1646v2ManLogStatsEntry OBJECT IDENTIFIER ::= {pr1646v2ManLogStatsSSC 1}

pr1646v2ManLogStatsWrites OBJECT-TYPE
   SYNTAX      Counter64
   MAX-ACCESS  read-only
   STATUS      current
   DESCRIPTION
      "Path: management.performance.logStats.writes

       64 bit unsigned wrappable counter."
   ::= {pr1646v2ManLogStatsEntry 16777216}

pr1646v2ManLogStatsWriteErrors OBJECT-TYPE
   SYNTAX      Integer32
   MAX-ACCESS  read-only
   STATUS      current
   DESCRIPTION
      "Path: management.performance.logStats.writeErrors"
   ::= {pr1646v2ManLogStatsEntry 33554432}

pr1646v2ManLogStatsCreateErrors OBJECT-TYPE
   SYNTAX      Integer32
   MAX-ACCESS  read-only
   STATUS      current
   DESCRIPTION
      "Path: management.performance.logStats.createErrors"
   ::= {pr1646v2ManLogStatsEntry 50331648}

pr1646v2ManLogStatsDiskSpaceErrors OBJECT-TYPE
   SYNTAX      Integer32
   MAX-ACCESS  read-only
   STATUS      current
   DESCRIPTION
      "Path: management.performance.logStats.diskSpaceErrors"
   ::= {pr1646v2ManLogStatsEntry 67108864}

pr1646v2ManLogStatsCleanUps OBJECT-TYPE
   SYNTAX      Integer32
   MAX-ACCESS  read-only
   STATUS      current
   DESCRIPTION
      "Path: management.performance.logStats.cleanUps"
   ::= {pr1646v2ManLogStatsEntry 83886080}

pr1646v2ManLogStatsHeavyCleanUps OBJECT-TYPE
   SYNTAX      Integer32
   MAX-ACCESS  read-only
   STATUS      current
   DESCRIPTION
      "Path: management.performance.logStats.heavyCleanUps"
   ::= {pr1646v2ManLogStatsEntry 100663296}


pr1646v2ManIpStackEvents OBJECT IDENTIFIER ::= {pr1646v2Man 44}

pr1646v2ManIpStackEventsSSC OBJECT IDENTIFIER ::= {pr1646v2ManIpStackEvents 1}

pr1646v2ManIpStackEventsEntry OBJECT IDENTIFIER ::= {pr1646v2ManIpStackEventsSSC 1}

pr1646v2ManIpStackEventsProtStack OBJECT-TYPE
   SYNTAX      Counter32
   MAX-ACCESS  read-only
   STATUS      current
   DESCRIPTION
      "Path: management.performance.ipStackEvents.protocolStack

       32 bit unsigned wrappable counter."
   ::= {pr1646v2ManIpStackEventsEntry 16777216}

pr1646v2ManIpStackEventsMulticast OBJECT-TYPE
   SYNTAX      Counter32
   MAX-ACCESS  read-only
   STATUS      current
   DESCRIPTION
      "Path: management.performance.ipStackEvents.multicast

       32 bit unsigned wrappable counter."
   ::= {pr1646v2ManIpStackEventsEntry 33554432}

pr1646v2ManIpStackEventsDelPckts OBJECT-TYPE
   SYNTAX      Counter32
   MAX-ACCESS  read-only
   STATUS      current
   DESCRIPTION
      "Path: management.performance.ipStackEvents.delayedPackets

       32 bit unsigned wrappable counter."
   ::= {pr1646v2ManIpStackEventsEntry 50331648}

pr1646v2ManIpStackEventsIgmp OBJECT-TYPE
   SYNTAX      Counter32
   MAX-ACCESS  read-only
   STATUS      current
   DESCRIPTION
      "Path: management.performance.ipStackEvents.igmp

       32 bit unsigned wrappable counter."
   ::= {pr1646v2ManIpStackEventsEntry 67108864}

pr1646v2ManIpStackEventsTcp OBJECT-TYPE
   SYNTAX      Counter32
   MAX-ACCESS  read-only
   STATUS      current
   DESCRIPTION
      "Path: management.performance.ipStackEvents.tcp

       32 bit unsigned wrappable counter."
   ::= {pr1646v2ManIpStackEventsEntry 83886080}

pr1646v2ManIpStackEventsTelnet OBJECT-TYPE
   SYNTAX      Counter32
   MAX-ACCESS  read-only
   STATUS      current
   DESCRIPTION
      "Path: management.performance.ipStackEvents.telnet

       32 bit unsigned wrappable counter."
   ::= {pr1646v2ManIpStackEventsEntry 100663296}

pr1646v2ManIpStackEventsFtp OBJECT-TYPE
   SYNTAX      Counter32
   MAX-ACCESS  read-only
   STATUS      current
   DESCRIPTION
      "Path: management.performance.ipStackEvents.ftp

       32 bit unsigned wrappable counter."
   ::= {pr1646v2ManIpStackEventsEntry 117440512}

pr1646v2ManIpStackEventsSntp OBJECT-TYPE
   SYNTAX      Counter32
   MAX-ACCESS  read-only
   STATUS      current
   DESCRIPTION
      "Path: management.performance.ipStackEvents.sntp

       32 bit unsigned wrappable counter."
   ::= {pr1646v2ManIpStackEventsEntry 134217728}

pr1646v2ManIpStackEventsRadius OBJECT-TYPE
   SYNTAX      Counter32
   MAX-ACCESS  read-only
   STATUS      current
   DESCRIPTION
      "Path: management.performance.ipStackEvents.radius

       32 bit unsigned wrappable counter."
   ::= {pr1646v2ManIpStackEventsEntry 150994944}

pr1646v2ManIpStackEventsTacacs OBJECT-TYPE
   SYNTAX      Counter32
   MAX-ACCESS  read-only
   STATUS      current
   DESCRIPTION
      "Path: management.performance.ipStackEvents.tacacs

       32 bit unsigned wrappable counter."
   ::= {pr1646v2ManIpStackEventsEntry 419430400}

pr1646v2ManIpStackEventsTimer OBJECT-TYPE
   SYNTAX      Counter32
   MAX-ACCESS  read-only
   STATUS      current
   DESCRIPTION
      "Path: management.performance.ipStackEvents.timer

       32 bit unsigned wrappable counter."
   ::= {pr1646v2ManIpStackEventsEntry 167772160}

pr1646v2ManIpStackEventsCms2 OBJECT-TYPE
   SYNTAX      Counter32
   MAX-ACCESS  read-only
   STATUS      current
   DESCRIPTION
      "Path: management.performance.ipStackEvents.cms2

       32 bit unsigned wrappable counter."
   ::= {pr1646v2ManIpStackEventsEntry 184549376}

pr1646v2ManIpStackEventsBootp OBJECT-TYPE
   SYNTAX      Counter32
   MAX-ACCESS  read-only
   STATUS      current
   DESCRIPTION
      "Path: management.performance.ipStackEvents.bootp

       32 bit unsigned wrappable counter."
   ::= {pr1646v2ManIpStackEventsEntry 201326592}

pr1646v2ManIpStackEventsDns OBJECT-TYPE
   SYNTAX      Counter32
   MAX-ACCESS  read-only
   STATUS      current
   DESCRIPTION
      "Path: management.performance.ipStackEvents.dns

       32 bit unsigned wrappable counter."
   ::= {pr1646v2ManIpStackEventsEntry 218103808}

pr1646v2ManIpStackEventsDnsUpdCl OBJECT-TYPE
   SYNTAX      Counter32
   MAX-ACCESS  read-only
   STATUS      current
   DESCRIPTION
      "Path: management.performance.ipStackEvents.dnsUpdateClient

       32 bit unsigned wrappable counter."
   ::= {pr1646v2ManIpStackEventsEntry 234881024}

pr1646v2ManIpStackEventsDnsConfig OBJECT-TYPE
   SYNTAX      Counter32
   MAX-ACCESS  read-only
   STATUS      current
   DESCRIPTION
      "Path: management.performance.ipStackEvents.dnsConfig

       32 bit unsigned wrappable counter."
   ::= {pr1646v2ManIpStackEventsEntry 436207616}

pr1646v2ManIpStackEventsNat OBJECT-TYPE
   SYNTAX      Counter32
   MAX-ACCESS  read-only
   STATUS      current
   DESCRIPTION
      "Path: management.performance.ipStackEvents.nat

       32 bit unsigned wrappable counter."
   ::= {pr1646v2ManIpStackEventsEntry 251658240}

pr1646v2ManIpStackEventsRipTxPackets OBJECT-TYPE
   SYNTAX      Counter32
   MAX-ACCESS  read-only
   STATUS      current
   DESCRIPTION
      "Path: management.performance.ipStackEvents.ripTxPackets

       32 bit unsigned wrappable counter."
   ::= {pr1646v2ManIpStackEventsEntry 268435456}

pr1646v2ManIpStackEventsUnreachable OBJECT-TYPE
   SYNTAX      Counter32
   MAX-ACCESS  read-only
   STATUS      current
   DESCRIPTION
      "Path: management.performance.ipStackEvents.unreachable

       32 bit unsigned wrappable counter."
   ::= {pr1646v2ManIpStackEventsEntry 285212672}

pr1646v2ManIpStackEventsRouteUpdate OBJECT-TYPE
   SYNTAX      Counter32
   MAX-ACCESS  read-only
   STATUS      current
   DESCRIPTION
      "Path: management.performance.ipStackEvents.routeUpdate

       32 bit unsigned wrappable counter."
   ::= {pr1646v2ManIpStackEventsEntry 301989888}

pr1646v2ManIpStackEventsTftp OBJECT-TYPE
   SYNTAX      Counter32
   MAX-ACCESS  read-only
   STATUS      current
   DESCRIPTION
      "Path: management.performance.ipStackEvents.tftp

       32 bit unsigned wrappable counter."
   ::= {pr1646v2ManIpStackEventsEntry 318767104}

pr1646v2ManIpStackEventsDhcp OBJECT-TYPE
   SYNTAX      Counter32
   MAX-ACCESS  read-only
   STATUS      current
   DESCRIPTION
      "Path: management.performance.ipStackEvents.dhcp

       32 bit unsigned wrappable counter."
   ::= {pr1646v2ManIpStackEventsEntry 335544320}

pr1646v2ManIpStackEventsDnsLookup OBJECT-TYPE
   SYNTAX      Counter32
   MAX-ACCESS  read-only
   STATUS      current
   DESCRIPTION
      "Path: management.performance.ipStackEvents.dnsLookup

       32 bit unsigned wrappable counter."
   ::= {pr1646v2ManIpStackEventsEntry 352321536}

pr1646v2ManIpStackEventsPing OBJECT-TYPE
   SYNTAX      Counter32
   MAX-ACCESS  read-only
   STATUS      current
   DESCRIPTION
      "Path: management.performance.ipStackEvents.ping

       32 bit unsigned wrappable counter."
   ::= {pr1646v2ManIpStackEventsEntry 369098752}

pr1646v2ManIpStackEventsOspfTxPckts OBJECT-TYPE
   SYNTAX      Counter32
   MAX-ACCESS  read-only
   STATUS      current
   DESCRIPTION
      "Path: management.performance.ipStackEvents.ospfTxPackets

       32 bit unsigned wrappable counter."
   ::= {pr1646v2ManIpStackEventsEntry 385875968}

pr1646v2ManIpStackEventsUdpTxPackets OBJECT-TYPE
   SYNTAX      Counter32
   MAX-ACCESS  read-only
   STATUS      current
   DESCRIPTION
      "Path: management.performance.ipStackEvents.udpTxPackets

       32 bit unsigned wrappable counter."
   ::= {pr1646v2ManIpStackEventsEntry 402653184}

pr1646v2ManIpStackEventsClearCounters OBJECT-TYPE
   SYNTAX      Counter32
   MAX-ACCESS  read-only
   STATUS      current
   DESCRIPTION
      "Path: management.performance.ipStackEvents.clearCounters

       32 bit unsigned wrappable counter."
   ::= {pr1646v2ManIpStackEventsEntry 452984832}

pr1646v2ManIpStackEventsTracert OBJECT-TYPE
   SYNTAX      Counter32
   MAX-ACCESS  read-only
   STATUS      current
   DESCRIPTION
      "Path: management.performance.ipStackEvents.tracert

       32 bit unsigned wrappable counter."
   ::= {pr1646v2ManIpStackEventsEntry 469762048}

pr1646v2ManIpStackEventsCapture OBJECT-TYPE
   SYNTAX      Counter32
   MAX-ACCESS  read-only
   STATUS      current
   DESCRIPTION
      "Path: management.performance.ipStackEvents.capture

       32 bit unsigned wrappable counter."
   ::= {pr1646v2ManIpStackEventsEntry 486539264}

pr1646v2ManIpStackEventsSsh OBJECT-TYPE
   SYNTAX      Counter32
   MAX-ACCESS  read-only
   STATUS      current
   DESCRIPTION
      "Path: management.performance.ipStackEvents.ssh

       32 bit unsigned wrappable counter."
   ::= {pr1646v2ManIpStackEventsEntry 503316480}

pr1646v2ManIpStackEventsSocket OBJECT-TYPE
   SYNTAX      Counter32
   MAX-ACCESS  read-only
   STATUS      current
   DESCRIPTION
      "Path: management.performance.ipStackEvents.socket

       32 bit unsigned wrappable counter."
   ::= {pr1646v2ManIpStackEventsEntry 520093696}

pr1646v2ManIpStackEventsTimeWindow OBJECT-TYPE
   SYNTAX      Counter32
   MAX-ACCESS  read-only
   STATUS      current
   DESCRIPTION
      "Path: management.performance.ipStackEvents.timeWindow

       32 bit unsigned wrappable counter."
   ::= {pr1646v2ManIpStackEventsEntry 536870912}

pr1646v2ManIpStackEventsUnknown OBJECT-TYPE
   SYNTAX      Counter32
   MAX-ACCESS  read-only
   STATUS      current
   DESCRIPTION
      "Path: management.performance.ipStackEvents.unknown

       32 bit unsigned wrappable counter."
   ::= {pr1646v2ManIpStackEventsEntry 553648128}


pr1646v2ManQueuesDepth OBJECT IDENTIFIER ::= {pr1646v2Man 46}

pr1646v2ManQueuesDepthSSC OBJECT IDENTIFIER ::= {pr1646v2ManQueuesDepth 1}

pr1646v2ManQueuesDepthEntry OBJECT IDENTIFIER ::= {pr1646v2ManQueuesDepthSSC 1}

pr1646v2ManQueuesDepthData OBJECT-TYPE
   SYNTAX      Gauge32
   MAX-ACCESS  read-only
   STATUS      current
   DESCRIPTION
      "Path: management.performance.queuesDepth.data

       32 bit unsigned gauge value."
   ::= {pr1646v2ManQueuesDepthEntry 16777216}

pr1646v2ManQueuesDepthDataDropLevelExceeded OBJECT-TYPE
   SYNTAX      Counter32
   MAX-ACCESS  read-only
   STATUS      current
   DESCRIPTION
      "Path: management.performance.queuesDepth.dataDropLevelExceeded

       32 bit unsigned wrappable counter."
   ::= {pr1646v2ManQueuesDepthEntry 67108864}

pr1646v2ManQueuesDepthTma OBJECT-TYPE
   SYNTAX      Gauge32
   MAX-ACCESS  read-only
   STATUS      current
   DESCRIPTION
      "Path: management.performance.queuesDepth.tma

       32 bit unsigned gauge value."
   ::= {pr1646v2ManQueuesDepthEntry 33554432}

pr1646v2ManQueuesDepthEvent OBJECT-TYPE
   SYNTAX      Gauge32
   MAX-ACCESS  read-only
   STATUS      current
   DESCRIPTION
      "Path: management.performance.queuesDepth.event

       32 bit unsigned gauge value."
   ::= {pr1646v2ManQueuesDepthEntry 50331648}


pr1646v2ManRadiusAuth OBJECT IDENTIFIER ::= {pr1646v2Man 63}

pr1646v2ManRadiusAuthSSCTable OBJECT-TYPE
   SYNTAX      SEQUENCE OF Pr1646v2ManRadiusAuthEntry
   MAX-ACCESS  not-accessible
   STATUS      current
   DESCRIPTION
      "radius statistics"
   ::= {pr1646v2ManRadiusAuth 1}

pr1646v2ManRadiusAuthEntry OBJECT-TYPE
   SYNTAX      Pr1646v2ManRadiusAuthEntry
   MAX-ACCESS  not-accessible
   STATUS      current
   DESCRIPTION
      ""
   INDEX      { pr1646v2ManRadiusAuthTableIx }
   ::= {pr1646v2ManRadiusAuthSSCTable 1}

Pr1646v2ManRadiusAuthEntry ::=
   SEQUENCE
      {
      pr1646v2ManRadiusAuthTableIx
         TableIndex,
      pr1646v2ManRadiusAuthServer
         IpAddress,
      pr1646v2ManRadiusAuthVrfRouter
         DisplayString,
      pr1646v2ManRadiusAuthRequests
         Integer32,
      pr1646v2ManRadiusAuthAccepts
         Integer32,
      pr1646v2ManRadiusAuthRejects
         Integer32,
      pr1646v2ManRadiusAuthChallenges
         Integer32,
      pr1646v2ManRadiusAuthBadAuth
         Integer32,
      pr1646v2ManRadiusAuthTimeOuts
         Integer32,
      pr1646v2ManRadiusAuthDroppedPackets
         Integer32
      }

pr1646v2ManRadiusAuthTableIx OBJECT-TYPE
   SYNTAX      TableIndex
   MAX-ACCESS  not-accessible
   STATUS      current
   DESCRIPTION
      ""
   ::= {pr1646v2ManRadiusAuthEntry 11}

pr1646v2ManRadiusAuthServer OBJECT-TYPE
   SYNTAX      IpAddress
   MAX-ACCESS  read-only
   STATUS      current
   DESCRIPTION
      "Path: management.performance.radiusAuth.server"
   ::= {pr1646v2ManRadiusAuthEntry 1677721600}

pr1646v2ManRadiusAuthVrfRouter OBJECT-TYPE
   SYNTAX      DisplayString
   MAX-ACCESS  read-only
   STATUS      current
   DESCRIPTION
      "Path: management.performance.radiusAuth.vrfRouter"
   ::= {pr1646v2ManRadiusAuthEntry 134217728}

pr1646v2ManRadiusAuthRequests OBJECT-TYPE
   SYNTAX      Integer32
   MAX-ACCESS  read-only
   STATUS      current
   DESCRIPTION
      "Path: management.performance.radiusAuth.requests"
   ::= {pr1646v2ManRadiusAuthEntry 16777216}

pr1646v2ManRadiusAuthAccepts OBJECT-TYPE
   SYNTAX      Integer32
   MAX-ACCESS  read-only
   STATUS      current
   DESCRIPTION
      "Path: management.performance.radiusAuth.accepts"
   ::= {pr1646v2ManRadiusAuthEntry 33554432}

pr1646v2ManRadiusAuthRejects OBJECT-TYPE
   SYNTAX      Integer32
   MAX-ACCESS  read-only
   STATUS      current
   DESCRIPTION
      "Path: management.performance.radiusAuth.rejects"
   ::= {pr1646v2ManRadiusAuthEntry 50331648}

pr1646v2ManRadiusAuthChallenges OBJECT-TYPE
   SYNTAX      Integer32
   MAX-ACCESS  read-only
   STATUS      current
   DESCRIPTION
      "Path: management.performance.radiusAuth.challenges"
   ::= {pr1646v2ManRadiusAuthEntry 67108864}

pr1646v2ManRadiusAuthBadAuth OBJECT-TYPE
   SYNTAX      Integer32
   MAX-ACCESS  read-only
   STATUS      current
   DESCRIPTION
      "Path: management.performance.radiusAuth.badAuthenticators"
   ::= {pr1646v2ManRadiusAuthEntry 83886080}

pr1646v2ManRadiusAuthTimeOuts OBJECT-TYPE
   SYNTAX      Integer32
   MAX-ACCESS  read-only
   STATUS      current
   DESCRIPTION
      "Path: management.performance.radiusAuth.timeOuts"
   ::= {pr1646v2ManRadiusAuthEntry 100663296}

pr1646v2ManRadiusAuthDroppedPackets OBJECT-TYPE
   SYNTAX      Integer32
   MAX-ACCESS  read-only
   STATUS      current
   DESCRIPTION
      "Path: management.performance.radiusAuth.droppedPackets"
   ::= {pr1646v2ManRadiusAuthEntry 117440512}


pr1646v2ManRadiusAcct OBJECT IDENTIFIER ::= {pr1646v2Man 62}

pr1646v2ManRadiusAcctSSC OBJECT IDENTIFIER ::= {pr1646v2ManRadiusAcct 1}

pr1646v2ManRadiusAcctEntry OBJECT IDENTIFIER ::= {pr1646v2ManRadiusAcctSSC 1}

pr1646v2ManRadiusAcctServer OBJECT-TYPE
   SYNTAX      IpAddress
   MAX-ACCESS  read-only
   STATUS      current
   DESCRIPTION
      "Path: management.performance.radiusAcct.server"
   ::= {pr1646v2ManRadiusAcctEntry 1677721600}

pr1646v2ManRadiusAcctVrfRouter OBJECT-TYPE
   SYNTAX      DisplayString
   MAX-ACCESS  read-only
   STATUS      current
   DESCRIPTION
      "Path: management.performance.radiusAcct.vrfRouter"
   ::= {pr1646v2ManRadiusAcctEntry 16777216}

pr1646v2ManRadiusAcctRequests OBJECT-TYPE
   SYNTAX      Integer32
   MAX-ACCESS  read-only
   STATUS      current
   DESCRIPTION
      "Path: management.performance.radiusAcct.requests"
   ::= {pr1646v2ManRadiusAcctEntry 134217728}

pr1646v2ManRadiusAcctResponses OBJECT-TYPE
   SYNTAX      Integer32
   MAX-ACCESS  read-only
   STATUS      current
   DESCRIPTION
      "Path: management.performance.radiusAcct.responses"
   ::= {pr1646v2ManRadiusAcctEntry 150994944}

pr1646v2ManRadiusAcctBadAuth OBJECT-TYPE
   SYNTAX      Integer32
   MAX-ACCESS  read-only
   STATUS      current
   DESCRIPTION
      "Path: management.performance.radiusAcct.badAuthenticators"
   ::= {pr1646v2ManRadiusAcctEntry 83886080}

pr1646v2ManRadiusAcctTimeOuts OBJECT-TYPE
   SYNTAX      Integer32
   MAX-ACCESS  read-only
   STATUS      current
   DESCRIPTION
      "Path: management.performance.radiusAcct.timeOuts"
   ::= {pr1646v2ManRadiusAcctEntry 100663296}

pr1646v2ManRadiusAcctDroppedPackets OBJECT-TYPE
   SYNTAX      Integer32
   MAX-ACCESS  read-only
   STATUS      current
   DESCRIPTION
      "Path: management.performance.radiusAcct.droppedPackets"
   ::= {pr1646v2ManRadiusAcctEntry 117440512}


pr1646v2ManTacacsAuth OBJECT IDENTIFIER ::= {pr1646v2Man 68}

pr1646v2ManTacacsAuthSSCTable OBJECT-TYPE
   SYNTAX      SEQUENCE OF Pr1646v2ManTacacsAuthEntry
   MAX-ACCESS  not-accessible
   STATUS      current
   DESCRIPTION
      "tacacs auth server perf table"
   ::= {pr1646v2ManTacacsAuth 1}

pr1646v2ManTacacsAuthEntry OBJECT-TYPE
   SYNTAX      Pr1646v2ManTacacsAuthEntry
   MAX-ACCESS  not-accessible
   STATUS      current
   DESCRIPTION
      ""
   INDEX      { pr1646v2ManTacacsAuthTableIx }
   ::= {pr1646v2ManTacacsAuthSSCTable 1}

Pr1646v2ManTacacsAuthEntry ::=
   SEQUENCE
      {
      pr1646v2ManTacacsAuthTableIx
         TableIndex,
      pr1646v2ManTacacsAuthServer
         IpAddress,
      pr1646v2ManTacacsAuthPort
         Integer32,
      pr1646v2ManTacacsAuthVrfRouter
         DisplayString,
      pr1646v2ManTacacsAuthRequests
         Counter32,
      pr1646v2ManTacacsAuthAccepts
         Counter32,
      pr1646v2ManTacacsAuthFails
         Counter32,
      pr1646v2ManTacacsAuthTimeOuts
         Counter32,
      pr1646v2ManTacacsAuthAuthenticationStartPkts
         Counter32,
      pr1646v2ManTacacsAuthAuthenticationContinuePkts
         Counter32,
      pr1646v2ManTacacsAuthAuthenticationReplyPkts
         Counter32,
      pr1646v2ManTacacsAuthAuthorizationRequestPkts
         Counter32,
      pr1646v2ManTacacsAuthAuthorizationResponsePkts
         Counter32,
      pr1646v2ManTacacsAuthDrops
         Counter32,
      pr1646v2ManTacacsAuthErrors
         Counter32
      }

pr1646v2ManTacacsAuthTableIx OBJECT-TYPE
   SYNTAX      TableIndex
   MAX-ACCESS  not-accessible
   STATUS      current
   DESCRIPTION
      ""
   ::= {pr1646v2ManTacacsAuthEntry 11}

pr1646v2ManTacacsAuthServer OBJECT-TYPE
   SYNTAX      IpAddress
   MAX-ACCESS  read-only
   STATUS      current
   DESCRIPTION
      "Path: management.performance.tacacsAuth.server"
   ::= {pr1646v2ManTacacsAuthEntry 16777216}

pr1646v2ManTacacsAuthPort OBJECT-TYPE
   SYNTAX      Integer32
   MAX-ACCESS  read-only
   STATUS      current
   DESCRIPTION
      "Path: management.performance.tacacsAuth.port"
   ::= {pr1646v2ManTacacsAuthEntry 33554432}

pr1646v2ManTacacsAuthVrfRouter OBJECT-TYPE
   SYNTAX      DisplayString
   MAX-ACCESS  read-only
   STATUS      current
   DESCRIPTION
      "Path: management.performance.tacacsAuth.vrfRouter"
   ::= {pr1646v2ManTacacsAuthEntry 184549376}

pr1646v2ManTacacsAuthRequests OBJECT-TYPE
   SYNTAX      Counter32
   MAX-ACCESS  read-only
   STATUS      current
   DESCRIPTION
      "Path: management.performance.tacacsAuth.requests

       32 bit unsigned wrappable counter."
   ::= {pr1646v2ManTacacsAuthEntry 50331648}

pr1646v2ManTacacsAuthAccepts OBJECT-TYPE
   SYNTAX      Counter32
   MAX-ACCESS  read-only
   STATUS      current
   DESCRIPTION
      "Path: management.performance.tacacsAuth.accepts

       32 bit unsigned wrappable counter."
   ::= {pr1646v2ManTacacsAuthEntry 67108864}

pr1646v2ManTacacsAuthFails OBJECT-TYPE
   SYNTAX      Counter32
   MAX-ACCESS  read-only
   STATUS      current
   DESCRIPTION
      "Path: management.performance.tacacsAuth.fails

       32 bit unsigned wrappable counter."
   ::= {pr1646v2ManTacacsAuthEntry 83886080}

pr1646v2ManTacacsAuthTimeOuts OBJECT-TYPE
   SYNTAX      Counter32
   MAX-ACCESS  read-only
   STATUS      current
   DESCRIPTION
      "Path: management.performance.tacacsAuth.timeOuts

       32 bit unsigned wrappable counter."
   ::= {pr1646v2ManTacacsAuthEntry 100663296}

pr1646v2ManTacacsAuthAuthenticationStartPkts OBJECT-TYPE
   SYNTAX      Counter32
   MAX-ACCESS  read-only
   STATUS      current
   DESCRIPTION
      "Path: management.performance.tacacsAuth.authentication.startPkts

       32 bit unsigned wrappable counter."
   ::= {pr1646v2ManTacacsAuthEntry 117506048}

pr1646v2ManTacacsAuthAuthenticationContinuePkts OBJECT-TYPE
   SYNTAX      Counter32
   MAX-ACCESS  read-only
   STATUS      current
   DESCRIPTION
      "Path: management.performance.tacacsAuth.authentication.continuePkts

       32 bit unsigned wrappable counter."
   ::= {pr1646v2ManTacacsAuthEntry 117571584}

pr1646v2ManTacacsAuthAuthenticationReplyPkts OBJECT-TYPE
   SYNTAX      Counter32
   MAX-ACCESS  read-only
   STATUS      current
   DESCRIPTION
      "Path: management.performance.tacacsAuth.authentication.replyPkts

       32 bit unsigned wrappable counter."
   ::= {pr1646v2ManTacacsAuthEntry 117637120}

pr1646v2ManTacacsAuthAuthorizationRequestPkts OBJECT-TYPE
   SYNTAX      Counter32
   MAX-ACCESS  read-only
   STATUS      current
   DESCRIPTION
      "Path: management.performance.tacacsAuth.authorization.requestPkts

       32 bit unsigned wrappable counter."
   ::= {pr1646v2ManTacacsAuthEntry 134283264}

pr1646v2ManTacacsAuthAuthorizationResponsePkts OBJECT-TYPE
   SYNTAX      Counter32
   MAX-ACCESS  read-only
   STATUS      current
   DESCRIPTION
      "Path: management.performance.tacacsAuth.authorization.responsePkts

       32 bit unsigned wrappable counter."
   ::= {pr1646v2ManTacacsAuthEntry 134348800}

pr1646v2ManTacacsAuthDrops OBJECT-TYPE
   SYNTAX      Counter32
   MAX-ACCESS  read-only
   STATUS      current
   DESCRIPTION
      "Path: management.performance.tacacsAuth.drops

       32 bit unsigned wrappable counter."
   ::= {pr1646v2ManTacacsAuthEntry 150994944}

pr1646v2ManTacacsAuthErrors OBJECT-TYPE
   SYNTAX      Counter32
   MAX-ACCESS  read-only
   STATUS      current
   DESCRIPTION
      "Path: management.performance.tacacsAuth.errors

       32 bit unsigned wrappable counter."
   ::= {pr1646v2ManTacacsAuthEntry 167772160}



ar1646v2Man OBJECT IDENTIFIER ::= {r1646v2Man 16}


ar1646v2ManSendEMDetect OBJECT-TYPE
   SYNTAX      Integer32
   MAX-ACCESS  read-write
   STATUS      current
   DESCRIPTION
      "Path: management.actions.sendEMDetect
       Info: lower the timer for the CWMP connection"
   ::= {ar1646v2Man 1280}


ar1646v2ManExecManStop OBJECT-TYPE
   SYNTAX      Integer32
   MAX-ACCESS  read-write
   STATUS      current
   DESCRIPTION
      "Path: management.actions.execManStop
       Info: stop task"
   ::= {ar1646v2Man 502}


ar1646v2ManTaskToStop OBJECT-TYPE
   SYNTAX      DisplayString
   MAX-ACCESS  read-write
   STATUS      current
   DESCRIPTION
      "Path: management.actions.taskToStop
       Info: filename"
   ::= {ar1646v2Man 503}


ar1646v2ManExecManStart OBJECT-TYPE
   SYNTAX      Integer32
   MAX-ACCESS  read-write
   STATUS      current
   DESCRIPTION
      "Path: management.actions.execManStart
       Info: start task"
   ::= {ar1646v2Man 500}


ar1646v2ManTask OBJECT-TYPE
   SYNTAX      DisplayString
   MAX-ACCESS  read-write
   STATUS      current
   DESCRIPTION
      "Path: management.actions.task
       Info: filename"
   ::= {ar1646v2Man 501}


ar1646v2ManFakeCWMPFactReset OBJECT-TYPE
   SYNTAX      Integer32
   MAX-ACCESS  read-write
   STATUS      current
   DESCRIPTION
      "Path: management.actions.fakeCWMPFactReset
       Info: action in the debug group"
   ::= {ar1646v2Man 1266}


ar1646v2ManForceCWMPextip OBJECT-TYPE
   SYNTAX      Integer32
   MAX-ACCESS  read-write
   STATUS      current
   DESCRIPTION
      "Path: management.actions.forceCWMPextip
       Info: action in the debug group"
   ::= {ar1646v2Man 1265}


ar1646v2ManFakeCWMPSetParamVal OBJECT-TYPE
   SYNTAX      Integer32
   MAX-ACCESS  read-write
   STATUS      current
   DESCRIPTION
      "Path: management.actions.fakeCWMPSetParamVal
       Info: action in the debug group"
   ::= {ar1646v2Man 1264}


ar1646v2ManFakeCWMPdownload OBJECT-TYPE
   SYNTAX      Integer32
   MAX-ACCESS  read-write
   STATUS      current
   DESCRIPTION
      "Path: management.actions.fakeCWMPdownload
       Info: action in the debug group"
   ::= {ar1646v2Man 1263}


ar1646v2ManForceCWMPBStrap OBJECT-TYPE
   SYNTAX      Integer32
   MAX-ACCESS  read-write
   STATUS      current
   DESCRIPTION
      "Path: management.actions.forceCWMPBStrap
       Info: lower the timer for the CWMP connection"
   ::= {ar1646v2Man 1268}


ar1646v2ManForceCWMPInform OBJECT-TYPE
   SYNTAX      Integer32
   MAX-ACCESS  read-write
   STATUS      current
   DESCRIPTION
      "Path: management.actions.forceCWMPInform
       Info: lower the timer for the CWMP connection"
   ::= {ar1646v2Man 1267}


ar1646v2ManClearCounters OBJECT-TYPE
   SYNTAX      Integer32
   MAX-ACCESS  read-write
   STATUS      current
   DESCRIPTION
      "Path: management.actions.clearCounters
       Info: reset counters"
   ::= {ar1646v2Man 263}


ar1646v2ManClearAccessLog OBJECT-TYPE
   SYNTAX      Integer32
   MAX-ACCESS  read-write
   STATUS      current
   DESCRIPTION
      "Path: management.actions.clearAccessLog
       Info: clear the accessLog table"
   ::= {ar1646v2Man 60}



fr1646v2Man OBJECT IDENTIFIER ::= {r1646v2Man 13}


fr1646v2ManAlarm OBJECT IDENTIFIER ::= {fr1646v2Man 202}

fr1646v2ManAlarmSSC OBJECT IDENTIFIER ::= {fr1646v2ManAlarm 1}

fr1646v2ManAlarmEntry OBJECT IDENTIFIER ::= {fr1646v2ManAlarmSSC 1}

fr1646v2ManAlarmDiscriminator OBJECT-TYPE
   SYNTAX      Integer32
   MAX-ACCESS  read-only
   STATUS      current
   DESCRIPTION
      "Path: management.alarms.alarmInfo.discriminator"
   ::= {fr1646v2ManAlarmEntry 16777216}

fr1646v2ManAlarmCurrent OBJECT-TYPE
   SYNTAX      Integer32
   MAX-ACCESS  read-only
   STATUS      current
   DESCRIPTION
      "Path: management.alarms.alarmInfo.currentAlarms

       Bit meanings:
               bit 1 = ntpSyncLoss"
   ::= {fr1646v2ManAlarmEntry 33554432}

fr1646v2ManAlarmPrevious OBJECT-TYPE
   SYNTAX      Integer32
   MAX-ACCESS  read-only
   STATUS      current
   DESCRIPTION
      "Path: management.alarms.alarmInfo.previousAlarms

       Bit meanings:
               bit 1 = ntpSyncLoss"
   ::= {fr1646v2ManAlarmEntry 50331648}

fr1646v2ManAlarmMask OBJECT-TYPE
   SYNTAX      Integer32
   MAX-ACCESS  read-only
   STATUS      current
   DESCRIPTION
      "Path: management.alarms.alarmInfo.alarmMask

       Bit meanings:
               bit 1 = ntpSyncLoss"
   ::= {fr1646v2ManAlarmEntry 67108864}

fr1646v2ManAlarmLevNtpSyncLoss OBJECT-TYPE
   SYNTAX      Integer32
   MAX-ACCESS  read-only
   STATUS      current
   DESCRIPTION
      "Path: management.alarms.alarmInfo.alarmLevel.ntpSyncLoss"
   ::= {fr1646v2ManAlarmEntry 84017152}


fr1646v2ManAlarmE2 OBJECT IDENTIFIER ::= {fr1646v2ManAlarm 2}

fr1646v2ManAlarmE2Entry OBJECT IDENTIFIER ::= {fr1646v2ManAlarmE2 1}

fr1646v2ManAlarmE2NtpSyncLoss OBJECT IDENTIFIER ::= {fr1646v2ManAlarmE2Entry 11}

fr1646v2ManAlarmE2NtpSyncLossPfx OBJECT IDENTIFIER ::= {fr1646v2ManAlarmE2NtpSyncLoss 0}

fr1646v2ManAlarmE2NtpSyncLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ntpSyncLoss'
                representing an alarm condition in the alarm word
                of attribute 'alarmInfo' of managed object 'managementNoO10'
                (root='router1646') has changed from the ON to the OFF state."
   ::= {fr1646v2ManAlarmE2NtpSyncLossPfx 1}

fr1646v2ManAlarmE2NtpSyncLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ntpSyncLoss'
                representing an alarm condition in the alarm word
                of attribute 'alarmInfo' of managed object 'managementNoO10'
                (root='router1646') has changed from the OFF to the ON state."
   ::= {fr1646v2ManAlarmE2NtpSyncLossPfx 2}



END
