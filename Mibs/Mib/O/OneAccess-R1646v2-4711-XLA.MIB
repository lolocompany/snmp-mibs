OneAccess-R1646v2-4711-XLA DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2XLA OBJECT IDENTIFIER ::= {r1646Rootv2 4711}

r1646v2XLAMOProp OBJECT IDENTIFIER ::= {r1646v2XLA 1}

r1646v2XLAMOPropEntry OBJECT IDENTIFIER ::= {r1646v2XLAMOProp 1}

r1646v2XLAMOPropPath OBJECT-TYPE
   SYNTAX      ContainmentPath
   MAX-ACCESS  read-only
   STATUS      current
   DESCRIPTION
      "Textual description of the containment tree from the instance of
       the root object down to the instance of the current object."
   ::= {r1646v2XLAMOPropEntry 3}

r1646v2XLAMOPropRev OBJECT-TYPE
   SYNTAX      ObjectRevision
   MAX-ACCESS  read-only
   STATUS      current
   DESCRIPTION
      "This value corresponds with the revision of the MANAGED OBJECT."
   ::= {r1646v2XLAMOPropEntry 4}



er1646v2XLA OBJECT IDENTIFIER ::= {r1646v2XLA 11}


er1646v2XLAPowerManagementControl OBJECT-TYPE
   SYNTAX      INTEGER
               {
               g997mpmsmL0 (0),
               g997mpmsmL3 (3)
               }
   MAX-ACCESS  read-write
   STATUS      current
   DESCRIPTION
      "Path: line.editConf.powerManagementControl
       Info: Power Management Control

       Possibilities:
               g997-pms-L0   (0)
               g997-pms-L3   (3)"
   ::= {er1646v2XLA 2}


er1646v2XLALinAlmMsk OBJECT-TYPE
   SYNTAX      Integer32
   MAX-ACCESS  read-write
   STATUS      current
   DESCRIPTION
      "Path: line.editConf.alarmMask
       Info: lineAlarmMask

       Bit meanings:
               bit 0 = linkDown"
   ::= {er1646v2XLA 70}


er1646v2XLALinAlmLev OBJECT IDENTIFIER ::= {er1646v2XLA 71}

er1646v2XLALinAlmLevSSC OBJECT IDENTIFIER ::= {er1646v2XLALinAlmLev 1}

er1646v2XLALinAlmLevEntry OBJECT IDENTIFIER ::= {er1646v2XLALinAlmLevSSC 1}

er1646v2XLALinAlmLevLnkDwn OBJECT-TYPE
   SYNTAX      Integer32
   MAX-ACCESS  read-write
   STATUS      current
   DESCRIPTION
      "Path: line.editConf.alarmLevel.linkDown"
   ::= {er1646v2XLALinAlmLevEntry 16777216}


er1646v2XLAFirmwareAlt OBJECT-TYPE
   SYNTAX      INTEGER
               {
               latest (0)
               }
   MAX-ACCESS  read-write
   STATUS      current
   DESCRIPTION
      "Path: line.editConf.firmwareAlt
       Info: To select an alternative bitpump DSP firmware

       Possibilities:
               latest   (0)"
   ::= {er1646v2XLA 717}


er1646v2XLASubCarriersInfo OBJECT-TYPE
   SYNTAX      INTEGER
               {
               invisible (1),
               visible (2)
               }
   MAX-ACCESS  read-write
   STATUS      current
   DESCRIPTION
      "Path: line.editConf.subCarriersInfo
       Info: subcarrier info

       Possibilities:
               invisible   (1)
               visible   (2)"
   ::= {er1646v2XLA 720}


er1646v2XLAHsCarrierSet OBJECT IDENTIFIER ::= {er1646v2XLA 724}

er1646v2XLAHsCarrierSetSSC OBJECT IDENTIFIER ::= {er1646v2XLAHsCarrierSet 1}

er1646v2XLAHsCarrierSetEntry OBJECT IDENTIFIER ::= {er1646v2XLAHsCarrierSetSSC 1}

er1646v2XLAHsCarrierSetAuto OBJECT-TYPE
   SYNTAX      OCTET STRING
   MAX-ACCESS  read-write
   STATUS      current
   DESCRIPTION
      "Path: line.editConf.hsCarrierSet.auto"
   ::= {er1646v2XLAHsCarrierSetEntry 16777216}

er1646v2XLAHsCarrierSetDisable OBJECT-TYPE
   SYNTAX      Integer32
   MAX-ACCESS  read-write
   STATUS      current
   DESCRIPTION
      "Path: line.editConf.hsCarrierSet.disable

       Bit meanings:
               bit 0 = B43,
               bit 1 = A43,
               bit 2 = V43,
               bit 5 = C43,
               bit 6 = J43,
               bit 7 = B43C,
               bit 8 = A43C"
   ::= {er1646v2XLAHsCarrierSetEntry 33554432}


er1646v2XLAAdslInteropCmds OBJECT IDENTIFIER ::= {er1646v2XLA 726}

er1646v2XLAAdslInteropCmdsSSCTable OBJECT-TYPE
   SYNTAX      SEQUENCE OF Er1646v2XLAAdslInteropCmdsEntry
   MAX-ACCESS  not-accessible
   STATUS      current
   DESCRIPTION
      "to set the interop commands manually"
   ::= {er1646v2XLAAdslInteropCmds 1}

er1646v2XLAAdslInteropCmdsEntry OBJECT-TYPE
   SYNTAX      Er1646v2XLAAdslInteropCmdsEntry
   MAX-ACCESS  not-accessible
   STATUS      current
   DESCRIPTION
      ""
   INDEX      { er1646v2XLAAdslInteropCmdsTableIx }
   ::= {er1646v2XLAAdslInteropCmdsSSCTable 1}

Er1646v2XLAAdslInteropCmdsEntry ::=
   SEQUENCE
      {
      er1646v2XLAAdslInteropCmdsActions
         VariableLengthTableActions,
      er1646v2XLAAdslInteropCmdsTableIx
         TableIndex,
      er1646v2XLAAdslInteropCmdsSection
         INTEGER,
      er1646v2XLAAdslInteropCmdsCommand
         DisplayString
      }

er1646v2XLAAdslInteropCmdsActions OBJECT-TYPE
   SYNTAX      VariableLengthTableActions
   MAX-ACCESS  read-write
   STATUS      current
   DESCRIPTION
      "By way of this field, some manipulations
       on this table may be performed."
   ::= {er1646v2XLAAdslInteropCmdsEntry 2}

er1646v2XLAAdslInteropCmdsTableIx OBJECT-TYPE
   SYNTAX      TableIndex
   MAX-ACCESS  not-accessible
   STATUS      current
   DESCRIPTION
      ""
   ::= {er1646v2XLAAdslInteropCmdsEntry 11}

er1646v2XLAAdslInteropCmdsSection OBJECT-TYPE
   SYNTAX      INTEGER
               {
               waitForConfiguration (0),
               waitForLinkActivate (1)
               }
   MAX-ACCESS  read-write
   STATUS      current
   DESCRIPTION
      "Path: line.editConf.adslInteropCmds.section

       Possibilities:
               waitForConfiguration   (0)
               waitForLinkActivate   (1)"
   ::= {er1646v2XLAAdslInteropCmdsEntry 16777216}

er1646v2XLAAdslInteropCmdsCommand OBJECT-TYPE
   SYNTAX      DisplayString
   MAX-ACCESS  read-write
   STATUS      current
   DESCRIPTION
      "Path: line.editConf.adslInteropCmds.command"
   ::= {er1646v2XLAAdslInteropCmdsEntry 33554432}


er1646v2XLAVdslInteropCmds OBJECT IDENTIFIER ::= {er1646v2XLA 727}

er1646v2XLAVdslInteropCmdsSSCTable OBJECT-TYPE
   SYNTAX      SEQUENCE OF Er1646v2XLAVdslInteropCmdsEntry
   MAX-ACCESS  not-accessible
   STATUS      current
   DESCRIPTION
      "to set the interop commands manually"
   ::= {er1646v2XLAVdslInteropCmds 1}

er1646v2XLAVdslInteropCmdsEntry OBJECT-TYPE
   SYNTAX      Er1646v2XLAVdslInteropCmdsEntry
   MAX-ACCESS  not-accessible
   STATUS      current
   DESCRIPTION
      ""
   INDEX      { er1646v2XLAVdslInteropCmdsTableIx }
   ::= {er1646v2XLAVdslInteropCmdsSSCTable 1}

Er1646v2XLAVdslInteropCmdsEntry ::=
   SEQUENCE
      {
      er1646v2XLAVdslInteropCmdsActions
         VariableLengthTableActions,
      er1646v2XLAVdslInteropCmdsTableIx
         TableIndex,
      er1646v2XLAVdslInteropCmdsSection
         INTEGER,
      er1646v2XLAVdslInteropCmdsCommand
         DisplayString
      }

er1646v2XLAVdslInteropCmdsActions OBJECT-TYPE
   SYNTAX      VariableLengthTableActions
   MAX-ACCESS  read-write
   STATUS      current
   DESCRIPTION
      "By way of this field, some manipulations
       on this table may be performed."
   ::= {er1646v2XLAVdslInteropCmdsEntry 2}

er1646v2XLAVdslInteropCmdsTableIx OBJECT-TYPE
   SYNTAX      TableIndex
   MAX-ACCESS  not-accessible
   STATUS      current
   DESCRIPTION
      ""
   ::= {er1646v2XLAVdslInteropCmdsEntry 11}

er1646v2XLAVdslInteropCmdsSection OBJECT-TYPE
   SYNTAX      INTEGER
               {
               waitForConfiguration (0),
               waitForLinkActivate (1)
               }
   MAX-ACCESS  read-write
   STATUS      current
   DESCRIPTION
      "Path: line.editConf.vdslInteropCmds.section

       Possibilities:
               waitForConfiguration   (0)
               waitForLinkActivate   (1)"
   ::= {er1646v2XLAVdslInteropCmdsEntry 16777216}

er1646v2XLAVdslInteropCmdsCommand OBJECT-TYPE
   SYNTAX      DisplayString
   MAX-ACCESS  read-write
   STATUS      current
   DESCRIPTION
      "Path: line.editConf.vdslInteropCmds.command"
   ::= {er1646v2XLAVdslInteropCmdsEntry 33554432}


er1646v2XLAAdslDsLineFeatures OBJECT IDENTIFIER ::= {er1646v2XLA 728}

er1646v2XLAAdslDsLineFeaturesSSC OBJECT IDENTIFIER ::= {er1646v2XLAAdslDsLineFeatures 1}

er1646v2XLAAdslDsLineFeaturesEntry OBJECT IDENTIFIER ::= {er1646v2XLAAdslDsLineFeaturesSSC 1}

er1646v2XLAAdslDsLineFeaturesTrellis OBJECT-TYPE
   SYNTAX      INTEGER
               {
               disabled (0),
               enabled (1)
               }
   MAX-ACCESS  read-write
   STATUS      current
   DESCRIPTION
      "Path: line.editConf.adslDsLineFeatures.trellis

       Possibilities:
               disabled   (0)
               enabled   (1)"
   ::= {er1646v2XLAAdslDsLineFeaturesEntry 16777216}

er1646v2XLAAdslDsLineFeaturesBitSwap OBJECT-TYPE
   SYNTAX      INTEGER
               {
               disabled (0),
               enabled (1)
               }
   MAX-ACCESS  read-write
   STATUS      current
   DESCRIPTION
      "Path: line.editConf.adslDsLineFeatures.bitSwap

       Possibilities:
               disabled   (0)
               enabled   (1)"
   ::= {er1646v2XLAAdslDsLineFeaturesEntry 33554432}

er1646v2XLAAdslDsLineFeaturesReTx OBJECT-TYPE
   SYNTAX      INTEGER
               {
               disabled (0),
               enabled (1)
               }
   MAX-ACCESS  read-write
   STATUS      current
   DESCRIPTION
      "Path: line.editConf.adslDsLineFeatures.reTx

       Possibilities:
               disabled   (0)
               enabled   (1)"
   ::= {er1646v2XLAAdslDsLineFeaturesEntry 50331648}

er1646v2XLAAdslDsLineFeaturesVirtualNoiseSupport OBJECT-TYPE
   SYNTAX      INTEGER
               {
               disabled (0),
               enabled (1)
               }
   MAX-ACCESS  read-write
   STATUS      current
   DESCRIPTION
      "Path: line.editConf.adslDsLineFeatures.virtualNoiseSupport

       Possibilities:
               disabled   (0)
               enabled   (1)"
   ::= {er1646v2XLAAdslDsLineFeaturesEntry 67108864}


er1646v2XLAVdslDsLineFeatures OBJECT IDENTIFIER ::= {er1646v2XLA 729}

er1646v2XLAVdslDsLineFeaturesSSC OBJECT IDENTIFIER ::= {er1646v2XLAVdslDsLineFeatures 1}

er1646v2XLAVdslDsLineFeaturesEntry OBJECT IDENTIFIER ::= {er1646v2XLAVdslDsLineFeaturesSSC 1}

er1646v2XLAVdslDsLineFeaturesTrellis OBJECT-TYPE
   SYNTAX      INTEGER
               {
               disabled (0),
               enabled (1)
               }
   MAX-ACCESS  read-write
   STATUS      current
   DESCRIPTION
      "Path: line.editConf.vdslDsLineFeatures.trellis

       Possibilities:
               disabled   (0)
               enabled   (1)"
   ::= {er1646v2XLAVdslDsLineFeaturesEntry 16777216}

er1646v2XLAVdslDsLineFeaturesBitSwap OBJECT-TYPE
   SYNTAX      INTEGER
               {
               disabled (0),
               enabled (1)
               }
   MAX-ACCESS  read-write
   STATUS      current
   DESCRIPTION
      "Path: line.editConf.vdslDsLineFeatures.bitSwap

       Possibilities:
               disabled   (0)
               enabled   (1)"
   ::= {er1646v2XLAVdslDsLineFeaturesEntry 33554432}

er1646v2XLAVdslDsLineFeaturesReTx OBJECT-TYPE
   SYNTAX      INTEGER
               {
               disabled (0),
               enabled (1)
               }
   MAX-ACCESS  read-write
   STATUS      current
   DESCRIPTION
      "Path: line.editConf.vdslDsLineFeatures.reTx

       Possibilities:
               disabled   (0)
               enabled   (1)"
   ::= {er1646v2XLAVdslDsLineFeaturesEntry 50331648}

er1646v2XLAVdslDsLineFeaturesVirtualNoiseSupport OBJECT-TYPE
   SYNTAX      INTEGER
               {
               disabled (0),
               enabled (1)
               }
   MAX-ACCESS  read-write
   STATUS      current
   DESCRIPTION
      "Path: line.editConf.vdslDsLineFeatures.virtualNoiseSupport

       Possibilities:
               disabled   (0)
               enabled   (1)"
   ::= {er1646v2XLAVdslDsLineFeaturesEntry 67108864}


er1646v2XLAVdslUsLineFeatures OBJECT IDENTIFIER ::= {er1646v2XLA 738}

er1646v2XLAVdslUsLineFeaturesSSC OBJECT IDENTIFIER ::= {er1646v2XLAVdslUsLineFeatures 1}

er1646v2XLAVdslUsLineFeaturesEntry OBJECT IDENTIFIER ::= {er1646v2XLAVdslUsLineFeaturesSSC 1}

er1646v2XLAVdslUsLineFeaturesReTx OBJECT-TYPE
   SYNTAX      INTEGER
               {
               disabled (0),
               enabled (1)
               }
   MAX-ACCESS  read-write
   STATUS      current
   DESCRIPTION
      "Path: line.editConf.vdslUsLineFeatures.reTx

       Possibilities:
               disabled   (0)
               enabled   (1)"
   ::= {er1646v2XLAVdslUsLineFeaturesEntry 50331648}


er1646v2XLAAdslDsSraMode OBJECT-TYPE
   SYNTAX      INTEGER
               {
               atInit (2),
               dynamic (3),
               dynamicSOS (4)
               }
   MAX-ACCESS  read-write
   STATUS      current
   DESCRIPTION
      "Path: line.editConf.adslDsSraMode
       Info: specify downstream rate adaption

       Possibilities:
               atInit   (2)
               dynamic   (3)
               dynamicSOS   (4)"
   ::= {er1646v2XLA 730}


er1646v2XLAVdslDsSraMode OBJECT-TYPE
   SYNTAX      INTEGER
               {
               atInit (2),
               dynamic (3),
               dynamicSOS (4)
               }
   MAX-ACCESS  read-write
   STATUS      current
   DESCRIPTION
      "Path: line.editConf.vdslDsSraMode
       Info: specify downstream rate adaption

       Possibilities:
               atInit   (2)
               dynamic   (3)
               dynamicSOS   (4)"
   ::= {er1646v2XLA 731}


er1646v2XLAVectoringMode OBJECT-TYPE
   SYNTAX      INTEGER
               {
               off (0),
               on (1),
               friendly (2)
               }
   MAX-ACCESS  read-write
   STATUS      current
   DESCRIPTION
      "Path: line.editConf.vectoringMode
       Info: vectoring with fixed MAC

       Possibilities:
               off   (0)
               on   (1)
               friendly   (2)"
   ::= {er1646v2XLA 732}


er1646v2XLALinkAlarmThresholds OBJECT IDENTIFIER ::= {er1646v2XLA 65}

er1646v2XLALinkAlarmThresholdsSSC OBJECT IDENTIFIER ::= {er1646v2XLALinkAlarmThresholds 1}

er1646v2XLALinkAlarmThresholdsEntry OBJECT IDENTIFIER ::= {er1646v2XLALinkAlarmThresholdsSSC 1}

er1646v2XLALinkAlarmThresholdsLineAtt OBJECT-TYPE
   SYNTAX      Integer32
   UNITS       "dB"
   MAX-ACCESS  read-write
   STATUS      current
   DESCRIPTION
      "Path: line.editConf.linkAlarmThresholds.lineAttenuation

       unit name = dB"
   ::= {er1646v2XLALinkAlarmThresholdsEntry 16777216}

er1646v2XLALinkAlarmThresholdsNoiseMrgn OBJECT-TYPE
   SYNTAX      Integer32
   UNITS       "dB"
   MAX-ACCESS  read-write
   STATUS      current
   DESCRIPTION
      "Path: line.editConf.linkAlarmThresholds.noiseMargin

       unit name = dB"
   ::= {er1646v2XLALinkAlarmThresholdsEntry 33554432}

er1646v2XLALinkAlarmThresholdsEsrExc OBJECT-TYPE
   SYNTAX      Integer32
   MAX-ACCESS  read-write
   STATUS      current
   DESCRIPTION
      "Path: line.editConf.linkAlarmThresholds.errSecRatioExceeded

       unit name = ratio
       formula = 1000 / ; 1000 *"
   ::= {er1646v2XLALinkAlarmThresholdsEntry 83886080}

er1646v2XLALinkAlarmThresholdsSesrExc OBJECT-TYPE
   SYNTAX      Integer32
   MAX-ACCESS  read-write
   STATUS      current
   DESCRIPTION
      "Path: line.editConf.linkAlarmThresholds.sevErrSecRatioExceeded

       unit name = ratio
       formula = 1000 / ; 1000 *"
   ::= {er1646v2XLALinkAlarmThresholdsEntry 100663296}

er1646v2XLALinkAlarmThresholdsIfDsSpeed OBJECT-TYPE
   SYNTAX      INTEGER
               {
               disabled (0)
               }
   UNITS       "bps"
   MAX-ACCESS  read-write
   STATUS      current
   DESCRIPTION
      "Path: line.editConf.linkAlarmThresholds.ifDsSpeed

       unit name = bps

       Possibilities:
               disabled   (0)"
   ::= {er1646v2XLALinkAlarmThresholdsEntry 117440512}

er1646v2XLALinkAlarmThresholdsIfUsSpeed OBJECT-TYPE
   SYNTAX      INTEGER
               {
               disabled (0)
               }
   UNITS       "bps"
   MAX-ACCESS  read-write
   STATUS      current
   DESCRIPTION
      "Path: line.editConf.linkAlarmThresholds.ifUsSpeed

       unit name = bps

       Possibilities:
               disabled   (0)"
   ::= {er1646v2XLALinkAlarmThresholdsEntry 134217728}


er1646v2XLAAdslMode OBJECT-TYPE
   SYNTAX      Integer32
   MAX-ACCESS  read-write
   STATUS      current
   DESCRIPTION
      "Path: line.editConf.adslMode
       Info: Configuration of ADSL ATU transmission system (POTS)

       Bit meanings:
               bit 0 = t1.413,
               bit 1 = g992.1 adsl annex A,
               bit 2 = g992.2 adsl lite,
               bit 3 = g992.3 adsl2 annex A,
               bit 4 = g992.3 adsl2 annex I,
               bit 5 = g992.3 adsl2 annex L,
               bit 6 = g992.3 adsl2 annex M,
               bit 7 = g992.4 adsl2 lite,
               bit 8 = g992.4 adsl2 lite annex I,
               bit 9 = g992.5 adsl2Plus annex A,
               bit 10 = g992.5 adsl2Plus annex I,
               bit 11 = g992.5 adsl2Plus annex M"
   ::= {er1646v2XLA 52}


er1646v2XLAVdslMode OBJECT-TYPE
   SYNTAX      Integer32
   MAX-ACCESS  read-write
   STATUS      current
   DESCRIPTION
      "Path: line.editConf.vdslMode
       Info: Configuration of VDSL ATU transmission system

       Bit meanings:
               bit 0 = g993.2 vdsl annex A,
               bit 1 = g993.2 vdsl annex B,
               bit 2 = g993.2 vdsl annex C"
   ::= {er1646v2XLA 53}



sr1646v2XLA OBJECT IDENTIFIER ::= {r1646v2XLA 14}


sr1646v2XLAIfDescr OBJECT-TYPE
   SYNTAX      DisplayString
   MAX-ACCESS  read-only
   STATUS      current
   DESCRIPTION
      "Path: line.status.ifDescr
       Info: ifDescr"
   ::= {sr1646v2XLA 101}


sr1646v2XLAIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: line.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2XLA 102}


sr1646v2XLAIfUsSpeed OBJECT-TYPE
   SYNTAX      Gauge32
   MAX-ACCESS  read-only
   STATUS      current
   DESCRIPTION
      "Path: line.status.ifUsSpeed
       Info: ifSpeed

       32 bit unsigned gauge value."
   ::= {sr1646v2XLA 104}


sr1646v2XLAIfDsSpeed OBJECT-TYPE
   SYNTAX      Gauge32
   MAX-ACCESS  read-only
   STATUS      current
   DESCRIPTION
      "Path: line.status.ifDsSpeed
       Info: ifSpeed

       32 bit unsigned gauge value."
   ::= {sr1646v2XLA 127}


sr1646v2XLAIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: line.status.ifOperStatus
       Info: ifOperStatus

       Possibilities:
               up   (1)
               down   (2)
               testing   (3)
               unknown   (4)
               dormant   (5)
               notPresent   (6)
               lowerLayerDown   (7)"
   ::= {sr1646v2XLA 107}


sr1646v2XLAMode OBJECT-TYPE
   SYNTAX      INTEGER
               {
               t1d413 (0),
               g992d1sadslsannexsA (1),
               g992d2sadslslite (2),
               g992d3sadsl2sannexsA (3),
               g992d3sadsl2sannexsI (4),
               g992d3sadsl2sannexsL (5),
               g992d3sadsl2sannexsM (6),
               g992d4sadsl2slite (7),
               g992d4sadsl2slitesannexsI (8),
               g992d5sadsl2PlussannexsA (9),
               g992d5sadsl2PlussannexsI (10),
               g992d5sadsl2PlussannexsM (11),
               g992d1sadslsannexsB (16),
               g992d3sadsl2sannexsB (17),
               g992d3sadsl2sannexsJ (18),
               g992d5sadsl2PlussannexsB (19),
               g992d5sadsl2PlussannexsJ (20),
               g993d2svdslsannexsA (30),
               g993d2svdslsannexsB (31),
               g993d2svdslsannexsC (32),
               unknown (99)
               }
   MAX-ACCESS  read-only
   STATUS      current
   DESCRIPTION
      "Path: line.status.mode
       Info: The ADSL mode selected

       Possibilities:
               t1.413   (0)
               g992.1 adsl annex A   (1)
               g992.2 adsl lite   (2)
               g992.3 adsl2 annex A   (3)
               g992.3 adsl2 annex I   (4)
               g992.3 adsl2 annex L   (5)
               g992.3 adsl2 annex M   (6)
               g992.4 adsl2 lite   (7)
               g992.4 adsl2 lite annex I   (8)
               g992.5 adsl2Plus annex A   (9)
               g992.5 adsl2Plus annex I   (10)
               g992.5 adsl2Plus annex M   (11)
               g992.1 adsl annex B   (16)
               g992.3 adsl2 annex B   (17)
               g992.3 adsl2 annex J   (18)
               g992.5 adsl2Plus annex B   (19)
               g992.5 adsl2Plus annex J   (20)
               g993.2 vdsl annex A   (30)
               g993.2 vdsl annex B   (31)
               g993.2 vdsl annex C   (32)
               unknown   (99)"
   ::= {sr1646v2XLA 126}


sr1646v2XLAPowerManagementMode OBJECT-TYPE
   SYNTAX      INTEGER
               {
               g997mpmsmL0 (0),
               g997mpmsmL3 (3)
               }
   MAX-ACCESS  read-only
   STATUS      current
   DESCRIPTION
      "Path: line.status.powerManagementMode
       Info: Power Management Mode

       Possibilities:
               g997-pms-L0   (0)
               g997-pms-L3   (3)"
   ::= {sr1646v2XLA 128}


sr1646v2XLADsLatency OBJECT-TYPE
   SYNTAX      INTEGER
               {
               fast (0),
               interleaved (1)
               }
   MAX-ACCESS  read-only
   STATUS      current
   DESCRIPTION
      "Path: line.status.dsLatency
       Info: Latency type

       Possibilities:
               fast   (0)
               interleaved   (1)"
   ::= {sr1646v2XLA 130}


sr1646v2XLAUsLatency OBJECT-TYPE
   SYNTAX      INTEGER
               {
               fast (0),
               interleaved (1)
               }
   MAX-ACCESS  read-only
   STATUS      current
   DESCRIPTION
      "Path: line.status.usLatency
       Info: Latency type

       Possibilities:
               fast   (0)
               interleaved   (1)"
   ::= {sr1646v2XLA 230}


sr1646v2XLAFirmwareVersion OBJECT-TYPE
   SYNTAX      DisplayString
   MAX-ACCESS  read-only
   STATUS      current
   DESCRIPTION
      "Path: line.status.firmwareVersion
       Info: Amazon firmware release"
   ::= {sr1646v2XLA 131}


sr1646v2XLAEocInfo OBJECT IDENTIFIER ::= {sr1646v2XLA 132}

sr1646v2XLAEocInfoSSC OBJECT IDENTIFIER ::= {sr1646v2XLAEocInfo 1}

sr1646v2XLAEocInfoEntry OBJECT IDENTIFIER ::= {sr1646v2XLAEocInfoSSC 1}

sr1646v2XLAEocInfoVendorID OBJECT-TYPE
   SYNTAX      OCTET STRING
   MAX-ACCESS  read-only
   STATUS      current
   DESCRIPTION
      "Path: line.status.eocInfo.vendorID"
   ::= {sr1646v2XLAEocInfoEntry 16777216}

sr1646v2XLAEocInfoVendorVersionNumber OBJECT-TYPE
   SYNTAX      OCTET STRING
   MAX-ACCESS  read-only
   STATUS      current
   DESCRIPTION
      "Path: line.status.eocInfo.vendorVersionNumber"
   ::= {sr1646v2XLAEocInfoEntry 33554432}

sr1646v2XLAEocInfoVendorSerialNumber OBJECT-TYPE
   SYNTAX      OCTET STRING
   MAX-ACCESS  read-only
   STATUS      current
   DESCRIPTION
      "Path: line.status.eocInfo.vendorSerialNumber"
   ::= {sr1646v2XLAEocInfoEntry 50331648}


sr1646v2XLAIfUsNetSpeed OBJECT-TYPE
   SYNTAX      Gauge32
   MAX-ACCESS  read-only
   STATUS      current
   DESCRIPTION
      "Path: line.status.ifUsNetSpeed
       Info: ifSpeed

       32 bit unsigned gauge value."
   ::= {sr1646v2XLA 156}


sr1646v2XLAIfDsNetSpeed OBJECT-TYPE
   SYNTAX      Gauge32
   MAX-ACCESS  read-only
   STATUS      current
   DESCRIPTION
      "Path: line.status.ifDsNetSpeed
       Info: ifSpeed

       32 bit unsigned gauge value."
   ::= {sr1646v2XLA 157}


sr1646v2XLAIfUsPrevSpeed OBJECT-TYPE
   SYNTAX      Gauge32
   MAX-ACCESS  read-only
   STATUS      current
   DESCRIPTION
      "Path: line.status.ifUsPrevSpeed
       Info: ifSpeed

       32 bit unsigned gauge value."
   ::= {sr1646v2XLA 137}


sr1646v2XLAIfDsPrevSpeed OBJECT-TYPE
   SYNTAX      Gauge32
   MAX-ACCESS  read-only
   STATUS      current
   DESCRIPTION
      "Path: line.status.ifDsPrevSpeed
       Info: ifSpeed

       32 bit unsigned gauge value."
   ::= {sr1646v2XLA 138}


sr1646v2XLAIfMaxCellRate OBJECT-TYPE
   SYNTAX      Integer32
   MAX-ACCESS  read-only
   STATUS      current
   DESCRIPTION
      "Path: line.status.ifMaxCellRate
       Info: line max cell rate"
   ::= {sr1646v2XLA 139}


sr1646v2XLAG994VendorID OBJECT-TYPE
   SYNTAX      OCTET STRING
   MAX-ACCESS  read-only
   STATUS      current
   DESCRIPTION
      "Path: line.status.g994VendorID
       Info: G994 vendor id"
   ::= {sr1646v2XLA 133}


sr1646v2XLAG997Capabilities OBJECT-TYPE
   SYNTAX      OCTET STRING
   MAX-ACCESS  read-only
   STATUS      current
   DESCRIPTION
      "Path: line.status.g997Capabilities
       Info: G997 XTSE Capabilities"
   ::= {sr1646v2XLA 134}


sr1646v2XLALtqVersionInfo OBJECT IDENTIFIER ::= {sr1646v2XLA 142}

sr1646v2XLALtqVersionInfoSSC OBJECT IDENTIFIER ::= {sr1646v2XLALtqVersionInfo 1}

sr1646v2XLALtqVersionInfoEntry OBJECT IDENTIFIER ::= {sr1646v2XLALtqVersionInfoSSC 1}

sr1646v2XLALtqVersionInfoDriverVersionApi OBJECT-TYPE
   SYNTAX      DisplayString
   MAX-ACCESS  read-only
   STATUS      current
   DESCRIPTION
      "Path: line.status.ltqVersionInfo.driverVersionApi"
   ::= {sr1646v2XLALtqVersionInfoEntry 16777216}

sr1646v2XLALtqVersionInfoDriverVersionMeiBsp OBJECT-TYPE
   SYNTAX      DisplayString
   MAX-ACCESS  read-only
   STATUS      current
   DESCRIPTION
      "Path: line.status.ltqVersionInfo.driverVersionMeiBsp"
   ::= {sr1646v2XLALtqVersionInfoEntry 33554432}

sr1646v2XLALtqVersionInfoChipSetFWVersion OBJECT-TYPE
   SYNTAX      DisplayString
   MAX-ACCESS  read-only
   STATUS      current
   DESCRIPTION
      "Path: line.status.ltqVersionInfo.chipSetFWVersion"
   ::= {sr1646v2XLALtqVersionInfoEntry 50331648}

sr1646v2XLALtqVersionInfoChipSetHWVersion OBJECT-TYPE
   SYNTAX      DisplayString
   MAX-ACCESS  read-only
   STATUS      current
   DESCRIPTION
      "Path: line.status.ltqVersionInfo.chipSetHWVersion"
   ::= {sr1646v2XLALtqVersionInfoEntry 67108864}

sr1646v2XLALtqVersionInfoChipSetType OBJECT-TYPE
   SYNTAX      DisplayString
   MAX-ACCESS  read-only
   STATUS      current
   DESCRIPTION
      "Path: line.status.ltqVersionInfo.chipSetType"
   ::= {sr1646v2XLALtqVersionInfoEntry 83886080}

sr1646v2XLALtqVersionInfoHybridType OBJECT-TYPE
   SYNTAX      INTEGER
               {
               unknown (-1),
               na (0),
               pots (1),
               isdn (2),
               invalid (3)
               }
   MAX-ACCESS  read-only
   STATUS      current
   DESCRIPTION
      "Path: line.status.ltqVersionInfo.hybridType

       Possibilities:
               unknown   (-1)
               n/a   (0)
               pots   (1)
               isdn   (2)
               invalid   (3)"
   ::= {sr1646v2XLALtqVersionInfoEntry 100663296}

sr1646v2XLALtqVersionInfoLoadedFW OBJECT-TYPE
   SYNTAX      DisplayString
   MAX-ACCESS  read-only
   STATUS      current
   DESCRIPTION
      "Path: line.status.ltqVersionInfo.loadedFW"
   ::= {sr1646v2XLALtqVersionInfoEntry 117440512}


sr1646v2XLALtqAutoBoot OBJECT IDENTIFIER ::= {sr1646v2XLA 146}

sr1646v2XLALtqAutoBootSSC OBJECT IDENTIFIER ::= {sr1646v2XLALtqAutoBoot 1}

sr1646v2XLALtqAutoBootEntry OBJECT IDENTIFIER ::= {sr1646v2XLALtqAutoBootSSC 1}

sr1646v2XLALtqAutoBootLinuxDriver OBJECT-TYPE
   SYNTAX      INTEGER
               {
               unknown (0),
               atm (1),
               ptm (2),
               ptmForced (3)
               }
   MAX-ACCESS  read-only
   STATUS      current
   DESCRIPTION
      "Path: line.status.ltqAutoBoot.linuxDriver

       Possibilities:
               unknown   (0)
               atm   (1)
               ptm   (2)
               ptmForced   (3)"
   ::= {sr1646v2XLALtqAutoBootEntry 16777216}

sr1646v2XLALtqAutoBootNextMode OBJECT-TYPE
   SYNTAX      INTEGER
               {
               na (0),
               adsl (1),
               vdsl (2)
               }
   MAX-ACCESS  read-only
   STATUS      current
   DESCRIPTION
      "Path: line.status.ltqAutoBoot.nextMode

       Possibilities:
               n/a   (0)
               adsl   (1)
               vdsl   (2)"
   ::= {sr1646v2XLALtqAutoBootEntry 33554432}

sr1646v2XLALtqAutoBootTcLayer OBJECT-TYPE
   SYNTAX      INTEGER
               {
               unknown (0),
               atm (1),
               ptm (2),
               ptmForced (3)
               }
   MAX-ACCESS  read-only
   STATUS      current
   DESCRIPTION
      "Path: line.status.ltqAutoBoot.tcLayer

       Possibilities:
               unknown   (0)
               atm   (1)
               ptm   (2)
               ptmForced   (3)"
   ::= {sr1646v2XLALtqAutoBootEntry 50331648}

sr1646v2XLALtqAutoBootInitStatus OBJECT-TYPE
   SYNTAX      INTEGER
               {
               successful (0),
               configserror (1),
               configsnotsfeasible (2),
               communicationsproblem (3),
               nospeersxtu (4),
               unknown (5)
               }
   MAX-ACCESS  read-only
   STATUS      current
   DESCRIPTION
      "Path: line.status.ltqAutoBoot.initStatus

       Possibilities:
               successful   (0)
               config error   (1)
               config not feasible   (2)
               communication problem   (3)
               no peer xtu   (4)
               unknown   (5)"
   ::= {sr1646v2XLALtqAutoBootEntry 67108864}

sr1646v2XLALtqAutoBootInitSubStatus OBJECT-TYPE
   SYNTAX      INTEGER
               {
               none (0),
               unknown (1),
               noscommonsmode (2),
               oppositesmode (3),
               retry (4),
               hybrid (5),
               portsmode (6),
               ppsdriver (7),
               localsshutdown (8),
               timeout (9),
               fastslos (10)
               }
   MAX-ACCESS  read-only
   STATUS      current
   DESCRIPTION
      "Path: line.status.ltqAutoBoot.initSubStatus

       Possibilities:
               none   (0)
               unknown   (1)
               no common mode   (2)
               opposite mode   (3)
               retry   (4)
               hybrid   (5)
               port mode   (6)
               pp driver   (7)
               local shutdown   (8)
               timeout   (9)
               fast los   (10)"
   ::= {sr1646v2XLALtqAutoBootEntry 83886080}


sr1646v2XLABandPlanProfile OBJECT-TYPE
   SYNTAX      INTEGER
               {
               profiles8a (0),
               profiles8b (1),
               profiles8c (2),
               profiles8d (3),
               profiles12a (4),
               profiles12b (5),
               profiles17a (6),
               profiles30a (7),
               profiles17b (8),
               unknown (99)
               }
   MAX-ACCESS  read-only
   STATUS      current
   DESCRIPTION
      "Path: line.status.bandPlanProfile
       Info: VDSL band plan profile

       Possibilities:
               profile 8a   (0)
               profile 8b   (1)
               profile 8c   (2)
               profile 8d   (3)
               profile 12a   (4)
               profile 12b   (5)
               profile 17a   (6)
               profile 30a   (7)
               profile 17b   (8)
               unknown   (99)"
   ::= {sr1646v2XLA 145}


sr1646v2XLAVectoring OBJECT IDENTIFIER ::= {sr1646v2XLA 741}

sr1646v2XLAVectoringSSC OBJECT IDENTIFIER ::= {sr1646v2XLAVectoring 1}

sr1646v2XLAVectoringEntry OBJECT IDENTIFIER ::= {sr1646v2XLAVectoringSSC 1}

sr1646v2XLAVectoringVector OBJECT-TYPE
   SYNTAX      INTEGER
               {
               off (0),
               onDs (1),
               onDsUs (2)
               }
   MAX-ACCESS  read-only
   STATUS      current
   DESCRIPTION
      "Path: line.status.vectoring.vector

       Possibilities:
               off   (0)
               onDs   (1)
               onDsUs   (2)"
   ::= {sr1646v2XLAVectoringEntry 16777216}

sr1646v2XLAVectoringVectorFriendly OBJECT-TYPE
   SYNTAX      INTEGER
               {
               off (0),
               onDs (1),
               onDsUs (2)
               }
   MAX-ACCESS  read-only
   STATUS      current
   DESCRIPTION
      "Path: line.status.vectoring.vectorFriendly

       Possibilities:
               off   (0)
               onDs   (1)
               onDsUs   (2)"
   ::= {sr1646v2XLAVectoringEntry 33554432}


sr1646v2XLATestMode OBJECT-TYPE
   SYNTAX      INTEGER
               {
               disable (0),
               showtimeLock (1),
               quiet (2),
               trainingLock (3),
               lock (4),
               unlock (5),
               sleep (6)
               }
   MAX-ACCESS  read-only
   STATUS      current
   DESCRIPTION
      "Path: line.status.testMode
       Info: testmode

       Possibilities:
               disable   (0)
               showtimeLock   (1)
               quiet   (2)
               trainingLock   (3)
               lock   (4)
               unlock   (5)
               sleep   (6)"
   ::= {sr1646v2XLA 735}


sr1646v2XLADsLineFeatures OBJECT IDENTIFIER ::= {sr1646v2XLA 739}

sr1646v2XLADsLineFeaturesSSC OBJECT IDENTIFIER ::= {sr1646v2XLADsLineFeatures 1}

sr1646v2XLADsLineFeaturesEntry OBJECT IDENTIFIER ::= {sr1646v2XLADsLineFeaturesSSC 1}

sr1646v2XLADsLineFeaturesTrellis OBJECT-TYPE
   SYNTAX      INTEGER
               {
               disabled (0),
               enabled (1)
               }
   MAX-ACCESS  read-only
   STATUS      current
   DESCRIPTION
      "Path: line.status.dsLineFeatures.trellis

       Possibilities:
               disabled   (0)
               enabled   (1)"
   ::= {sr1646v2XLADsLineFeaturesEntry 16777216}

sr1646v2XLADsLineFeaturesBitSwap OBJECT-TYPE
   SYNTAX      INTEGER
               {
               disabled (0),
               enabled (1)
               }
   MAX-ACCESS  read-only
   STATUS      current
   DESCRIPTION
      "Path: line.status.dsLineFeatures.bitSwap

       Possibilities:
               disabled   (0)
               enabled   (1)"
   ::= {sr1646v2XLADsLineFeaturesEntry 33554432}

sr1646v2XLADsLineFeaturesReTx OBJECT-TYPE
   SYNTAX      INTEGER
               {
               disabled (0),
               enabled (1)
               }
   MAX-ACCESS  read-only
   STATUS      current
   DESCRIPTION
      "Path: line.status.dsLineFeatures.reTx

       Possibilities:
               disabled   (0)
               enabled   (1)"
   ::= {sr1646v2XLADsLineFeaturesEntry 50331648}

sr1646v2XLADsLineFeaturesVirtualNoiseSupport OBJECT-TYPE
   SYNTAX      INTEGER
               {
               disabled (0),
               enabled (1)
               }
   MAX-ACCESS  read-only
   STATUS      current
   DESCRIPTION
      "Path: line.status.dsLineFeatures.virtualNoiseSupport

       Possibilities:
               disabled   (0)
               enabled   (1)"
   ::= {sr1646v2XLADsLineFeaturesEntry 67108864}


sr1646v2XLAUsLineFeatures OBJECT IDENTIFIER ::= {sr1646v2XLA 740}

sr1646v2XLAUsLineFeaturesSSC OBJECT IDENTIFIER ::= {sr1646v2XLAUsLineFeatures 1}

sr1646v2XLAUsLineFeaturesEntry OBJECT IDENTIFIER ::= {sr1646v2XLAUsLineFeaturesSSC 1}

sr1646v2XLAUsLineFeaturesTrellis OBJECT-TYPE
   SYNTAX      INTEGER
               {
               disabled (0),
               enabled (1)
               }
   MAX-ACCESS  read-only
   STATUS      current
   DESCRIPTION
      "Path: line.status.usLineFeatures.trellis

       Possibilities:
               disabled   (0)
               enabled   (1)"
   ::= {sr1646v2XLAUsLineFeaturesEntry 16777216}

sr1646v2XLAUsLineFeaturesBitSwap OBJECT-TYPE
   SYNTAX      INTEGER
               {
               disabled (0),
               enabled (1)
               }
   MAX-ACCESS  read-only
   STATUS      current
   DESCRIPTION
      "Path: line.status.usLineFeatures.bitSwap

       Possibilities:
               disabled   (0)
               enabled   (1)"
   ::= {sr1646v2XLAUsLineFeaturesEntry 33554432}

sr1646v2XLAUsLineFeaturesReTx OBJECT-TYPE
   SYNTAX      INTEGER
               {
               disabled (0),
               enabled (1)
               }
   MAX-ACCESS  read-only
   STATUS      current
   DESCRIPTION
      "Path: line.status.usLineFeatures.reTx

       Possibilities:
               disabled   (0)
               enabled   (1)"
   ::= {sr1646v2XLAUsLineFeaturesEntry 50331648}

sr1646v2XLAUsLineFeaturesVirtualNoiseSupport OBJECT-TYPE
   SYNTAX      INTEGER
               {
               disabled (0),
               enabled (1)
               }
   MAX-ACCESS  read-only
   STATUS      current
   DESCRIPTION
      "Path: line.status.usLineFeatures.virtualNoiseSupport

       Possibilities:
               disabled   (0)
               enabled   (1)"
   ::= {sr1646v2XLAUsLineFeaturesEntry 67108864}


sr1646v2XLASnmpIndex OBJECT-TYPE
   SYNTAX      Integer32
   MAX-ACCESS  read-only
   STATUS      current
   DESCRIPTION
      "Path: line.status.snmpIndex
       Info: SNMP index assigned to this object"
   ::= {sr1646v2XLA 269}



pr1646v2XLA OBJECT IDENTIFIER ::= {r1646v2XLA 12}


pr1646v2XLAH2 OBJECT IDENTIFIER ::= {pr1646v2XLA 21}

pr1646v2XLAH2SSCTable OBJECT-TYPE
   SYNTAX      SEQUENCE OF Pr1646v2XLAH2Entry
   MAX-ACCESS  not-accessible
   STATUS      current
   DESCRIPTION
      "h2Line"
   ::= {pr1646v2XLAH2 1}

pr1646v2XLAH2Entry OBJECT-TYPE
   SYNTAX      Pr1646v2XLAH2Entry
   MAX-ACCESS  not-accessible
   STATUS      current
   DESCRIPTION
      ""
   INDEX      { pr1646v2XLAH2TableIx }
   ::= {pr1646v2XLAH2SSCTable 1}

Pr1646v2XLAH2Entry ::=
   SEQUENCE
      {
      pr1646v2XLAH2TableIx
         TableIndex,
      pr1646v2XLAH2SysUpTime
         TimeTicks,
      pr1646v2XLAH2LDownCnt
         Counter32,
      pr1646v2XLAH2LDownTme
         TimeTicks,
      pr1646v2XLAH2UsSpdMin
         Integer32,
      pr1646v2XLAH2UsSpdAvrg
         Integer32,
      pr1646v2XLAH2UsSpdMax
         Integer32,
      pr1646v2XLAH2DsSpdMin
         Integer32,
      pr1646v2XLAH2DsSpdAvrg
         Integer32,
      pr1646v2XLAH2DsSpdMax
         Integer32
      }

pr1646v2XLAH2TableIx OBJECT-TYPE
   SYNTAX      TableIndex
   MAX-ACCESS  not-accessible
   STATUS      current
   DESCRIPTION
      ""
   ::= {pr1646v2XLAH2Entry 11}

pr1646v2XLAH2SysUpTime OBJECT-TYPE
   SYNTAX      TimeTicks
   MAX-ACCESS  read-only
   STATUS      current
   DESCRIPTION
      "Path: line.performance.h2Line.sysUpTime

       Time in centi-second."
   ::= {pr1646v2XLAH2Entry 16777216}

pr1646v2XLAH2LDownCnt OBJECT-TYPE
   SYNTAX      Counter32
   MAX-ACCESS  read-only
   STATUS      current
   DESCRIPTION
      "Path: line.performance.h2Line.linkDownCount

       32 bit unsigned wrappable counter."
   ::= {pr1646v2XLAH2Entry 33554432}

pr1646v2XLAH2LDownTme OBJECT-TYPE
   SYNTAX      TimeTicks
   MAX-ACCESS  read-only
   STATUS      current
   DESCRIPTION
      "Path: line.performance.h2Line.linkDownTime

       Time in centi-second."
   ::= {pr1646v2XLAH2Entry 50331648}

pr1646v2XLAH2UsSpdMin OBJECT-TYPE
   SYNTAX      Integer32
   MAX-ACCESS  read-only
   STATUS      current
   DESCRIPTION
      "Path: line.performance.h2Line.usSpeedMin

       formula = 32000 * ; 32000 /"
   ::= {pr1646v2XLAH2Entry 67108864}

pr1646v2XLAH2UsSpdAvrg OBJECT-TYPE
   SYNTAX      Integer32
   MAX-ACCESS  read-only
   STATUS      current
   DESCRIPTION
      "Path: line.performance.h2Line.usSpeedAvrg

       formula = 32000 * ; 32000 /"
   ::= {pr1646v2XLAH2Entry 83886080}

pr1646v2XLAH2UsSpdMax OBJECT-TYPE
   SYNTAX      Integer32
   MAX-ACCESS  read-only
   STATUS      current
   DESCRIPTION
      "Path: line.performance.h2Line.usSpeedMax

       formula = 32000 * ; 32000 /"
   ::= {pr1646v2XLAH2Entry 100663296}

pr1646v2XLAH2DsSpdMin OBJECT-TYPE
   SYNTAX      Integer32
   MAX-ACCESS  read-only
   STATUS      current
   DESCRIPTION
      "Path: line.performance.h2Line.dsSpeedMin

       formula = 32000 * ; 32000 /"
   ::= {pr1646v2XLAH2Entry 117440512}

pr1646v2XLAH2DsSpdAvrg OBJECT-TYPE
   SYNTAX      Integer32
   MAX-ACCESS  read-only
   STATUS      current
   DESCRIPTION
      "Path: line.performance.h2Line.dsSpeedAvrg

       formula = 32000 * ; 32000 /"
   ::= {pr1646v2XLAH2Entry 134217728}

pr1646v2XLAH2DsSpdMax OBJECT-TYPE
   SYNTAX      Integer32
   MAX-ACCESS  read-only
   STATUS      current
   DESCRIPTION
      "Path: line.performance.h2Line.dsSpeedMax

       formula = 32000 * ; 32000 /"
   ::= {pr1646v2XLAH2Entry 150994944}


pr1646v2XLAH24 OBJECT IDENTIFIER ::= {pr1646v2XLA 23}

pr1646v2XLAH24SSCTable OBJECT-TYPE
   SYNTAX      SEQUENCE OF Pr1646v2XLAH24Entry
   MAX-ACCESS  not-accessible
   STATUS      current
   DESCRIPTION
      "h24Line"
   ::= {pr1646v2XLAH24 1}

pr1646v2XLAH24Entry OBJECT-TYPE
   SYNTAX      Pr1646v2XLAH24Entry
   MAX-ACCESS  not-accessible
   STATUS      current
   DESCRIPTION
      ""
   INDEX      { pr1646v2XLAH24TableIx }
   ::= {pr1646v2XLAH24SSCTable 1}

Pr1646v2XLAH24Entry ::=
   SEQUENCE
      {
      pr1646v2XLAH24TableIx
         TableIndex,
      pr1646v2XLAH24SysUpTime
         TimeTicks,
      pr1646v2XLAH24LDownCnt
         Counter32,
      pr1646v2XLAH24LDownTme
         TimeTicks,
      pr1646v2XLAH24UsSpdMin
         Integer32,
      pr1646v2XLAH24UsSpdAvrg
         Integer32,
      pr1646v2XLAH24UsSpdMax
         Integer32,
      pr1646v2XLAH24DsSpdMin
         Integer32,
      pr1646v2XLAH24DsSpdAvrg
         Integer32,
      pr1646v2XLAH24DsSpdMax
         Integer32
      }

pr1646v2XLAH24TableIx OBJECT-TYPE
   SYNTAX      TableIndex
   MAX-ACCESS  not-accessible
   STATUS      current
   DESCRIPTION
      ""
   ::= {pr1646v2XLAH24Entry 11}

pr1646v2XLAH24SysUpTime OBJECT-TYPE
   SYNTAX      TimeTicks
   MAX-ACCESS  read-only
   STATUS      current
   DESCRIPTION
      "Path: line.performance.h24Line.sysUpTime

       Time in centi-second."
   ::= {pr1646v2XLAH24Entry 16777216}

pr1646v2XLAH24LDownCnt OBJECT-TYPE
   SYNTAX      Counter32
   MAX-ACCESS  read-only
   STATUS      current
   DESCRIPTION
      "Path: line.performance.h24Line.linkDownCount

       32 bit unsigned wrappable counter."
   ::= {pr1646v2XLAH24Entry 33554432}

pr1646v2XLAH24LDownTme OBJECT-TYPE
   SYNTAX      TimeTicks
   MAX-ACCESS  read-only
   STATUS      current
   DESCRIPTION
      "Path: line.performance.h24Line.linkDownTime

       Time in centi-second."
   ::= {pr1646v2XLAH24Entry 50331648}

pr1646v2XLAH24UsSpdMin OBJECT-TYPE
   SYNTAX      Integer32
   MAX-ACCESS  read-only
   STATUS      current
   DESCRIPTION
      "Path: line.performance.h24Line.usSpeedMin

       formula = 32000 * ; 32000 /"
   ::= {pr1646v2XLAH24Entry 67108864}

pr1646v2XLAH24UsSpdAvrg OBJECT-TYPE
   SYNTAX      Integer32
   MAX-ACCESS  read-only
   STATUS      current
   DESCRIPTION
      "Path: line.performance.h24Line.usSpeedAvrg

       formula = 32000 * ; 32000 /"
   ::= {pr1646v2XLAH24Entry 83886080}

pr1646v2XLAH24UsSpdMax OBJECT-TYPE
   SYNTAX      Integer32
   MAX-ACCESS  read-only
   STATUS      current
   DESCRIPTION
      "Path: line.performance.h24Line.usSpeedMax

       formula = 32000 * ; 32000 /"
   ::= {pr1646v2XLAH24Entry 100663296}

pr1646v2XLAH24DsSpdMin OBJECT-TYPE
   SYNTAX      Integer32
   MAX-ACCESS  read-only
   STATUS      current
   DESCRIPTION
      "Path: line.performance.h24Line.dsSpeedMin

       formula = 32000 * ; 32000 /"
   ::= {pr1646v2XLAH24Entry 117440512}

pr1646v2XLAH24DsSpdAvrg OBJECT-TYPE
   SYNTAX      Integer32
   MAX-ACCESS  read-only
   STATUS      current
   DESCRIPTION
      "Path: line.performance.h24Line.dsSpeedAvrg

       formula = 32000 * ; 32000 /"
   ::= {pr1646v2XLAH24Entry 134217728}

pr1646v2XLAH24DsSpdMax OBJECT-TYPE
   SYNTAX      Integer32
   MAX-ACCESS  read-only
   STATUS      current
   DESCRIPTION
      "Path: line.performance.h24Line.dsSpeedMax

       formula = 32000 * ; 32000 /"
   ::= {pr1646v2XLAH24Entry 150994944}


pr1646v2XLAD7 OBJECT IDENTIFIER ::= {pr1646v2XLA 26}

pr1646v2XLAD7SSCTable OBJECT-TYPE
   SYNTAX      SEQUENCE OF Pr1646v2XLAD7Entry
   MAX-ACCESS  not-accessible
   STATUS      current
   DESCRIPTION
      "d7Line"
   ::= {pr1646v2XLAD7 1}

pr1646v2XLAD7Entry OBJECT-TYPE
   SYNTAX      Pr1646v2XLAD7Entry
   MAX-ACCESS  not-accessible
   STATUS      current
   DESCRIPTION
      ""
   INDEX      { pr1646v2XLAD7TableIx }
   ::= {pr1646v2XLAD7SSCTable 1}

Pr1646v2XLAD7Entry ::=
   SEQUENCE
      {
      pr1646v2XLAD7TableIx
         TableIndex,
      pr1646v2XLAD7SysUpTime
         TimeTicks,
      pr1646v2XLAD7LDownCnt
         Counter32,
      pr1646v2XLAD7LDownTme
         TimeTicks,
      pr1646v2XLAD7UsSpdMin
         Integer32,
      pr1646v2XLAD7UsSpdAvrg
         Integer32,
      pr1646v2XLAD7UsSpdMax
         Integer32,
      pr1646v2XLAD7DsSpdMin
         Integer32,
      pr1646v2XLAD7DsSpdAvrg
         Integer32,
      pr1646v2XLAD7DsSpdMax
         Integer32
      }

pr1646v2XLAD7TableIx OBJECT-TYPE
   SYNTAX      TableIndex
   MAX-ACCESS  not-accessible
   STATUS      current
   DESCRIPTION
      ""
   ::= {pr1646v2XLAD7Entry 11}

pr1646v2XLAD7SysUpTime OBJECT-TYPE
   SYNTAX      TimeTicks
   MAX-ACCESS  read-only
   STATUS      current
   DESCRIPTION
      "Path: line.performance.d7Line.sysUpTime

       Time in centi-second."
   ::= {pr1646v2XLAD7Entry 16777216}

pr1646v2XLAD7LDownCnt OBJECT-TYPE
   SYNTAX      Counter32
   MAX-ACCESS  read-only
   STATUS      current
   DESCRIPTION
      "Path: line.performance.d7Line.linkDownCount

       32 bit unsigned wrappable counter."
   ::= {pr1646v2XLAD7Entry 33554432}

pr1646v2XLAD7LDownTme OBJECT-TYPE
   SYNTAX      TimeTicks
   MAX-ACCESS  read-only
   STATUS      current
   DESCRIPTION
      "Path: line.performance.d7Line.linkDownTime

       Time in centi-second."
   ::= {pr1646v2XLAD7Entry 50331648}

pr1646v2XLAD7UsSpdMin OBJECT-TYPE
   SYNTAX      Integer32
   MAX-ACCESS  read-only
   STATUS      current
   DESCRIPTION
      "Path: line.performance.d7Line.usSpeedMin

       formula = 32000 * ; 32000 /"
   ::= {pr1646v2XLAD7Entry 67108864}

pr1646v2XLAD7UsSpdAvrg OBJECT-TYPE
   SYNTAX      Integer32
   MAX-ACCESS  read-only
   STATUS      current
   DESCRIPTION
      "Path: line.performance.d7Line.usSpeedAvrg

       formula = 32000 * ; 32000 /"
   ::= {pr1646v2XLAD7Entry 83886080}

pr1646v2XLAD7UsSpdMax OBJECT-TYPE
   SYNTAX      Integer32
   MAX-ACCESS  read-only
   STATUS      current
   DESCRIPTION
      "Path: line.performance.d7Line.usSpeedMax

       formula = 32000 * ; 32000 /"
   ::= {pr1646v2XLAD7Entry 100663296}

pr1646v2XLAD7DsSpdMin OBJECT-TYPE
   SYNTAX      Integer32
   MAX-ACCESS  read-only
   STATUS      current
   DESCRIPTION
      "Path: line.performance.d7Line.dsSpeedMin

       formula = 32000 * ; 32000 /"
   ::= {pr1646v2XLAD7Entry 117440512}

pr1646v2XLAD7DsSpdAvrg OBJECT-TYPE
   SYNTAX      Integer32
   MAX-ACCESS  read-only
   STATUS      current
   DESCRIPTION
      "Path: line.performance.d7Line.dsSpeedAvrg

       formula = 32000 * ; 32000 /"
   ::= {pr1646v2XLAD7Entry 134217728}

pr1646v2XLAD7DsSpdMax OBJECT-TYPE
   SYNTAX      Integer32
   MAX-ACCESS  read-only
   STATUS      current
   DESCRIPTION
      "Path: line.performance.d7Line.dsSpeedMax

       formula = 32000 * ; 32000 /"
   ::= {pr1646v2XLAD7Entry 150994944}


pr1646v2XLARel OBJECT IDENTIFIER ::= {pr1646v2XLA 30}

pr1646v2XLARelSSC OBJECT IDENTIFIER ::= {pr1646v2XLARel 1}

pr1646v2XLARelEntry OBJECT IDENTIFIER ::= {pr1646v2XLARelSSC 1}

pr1646v2XLARelLDownCnt OBJECT-TYPE
   SYNTAX      Counter32
   MAX-ACCESS  read-only
   STATUS      current
   DESCRIPTION
      "Path: line.performance.line.linkDownCount

       32 bit unsigned wrappable counter."
   ::= {pr1646v2XLARelEntry 16777216}

pr1646v2XLARelLDownTme OBJECT-TYPE
   SYNTAX      TimeTicks
   MAX-ACCESS  read-only
   STATUS      current
   DESCRIPTION
      "Path: line.performance.line.linkDownTime

       Time in centi-second."
   ::= {pr1646v2XLARelEntry 33554432}



fr1646v2XLA OBJECT IDENTIFIER ::= {r1646v2XLA 13}


fr1646v2XLAAlInfo OBJECT IDENTIFIER ::= {fr1646v2XLA 207}

fr1646v2XLAAlInfoSSC OBJECT IDENTIFIER ::= {fr1646v2XLAAlInfo 1}

fr1646v2XLAAlInfoEntry OBJECT IDENTIFIER ::= {fr1646v2XLAAlInfoSSC 1}

fr1646v2XLAAlInfoDiscr OBJECT-TYPE
   SYNTAX      Integer32
   MAX-ACCESS  read-only
   STATUS      current
   DESCRIPTION
      "Path: line.alarms.alarmInfo.discriminator"
   ::= {fr1646v2XLAAlInfoEntry 16777216}

fr1646v2XLAAlInfoCurrAlms OBJECT-TYPE
   SYNTAX      Integer32
   MAX-ACCESS  read-only
   STATUS      current
   DESCRIPTION
      "Path: line.alarms.alarmInfo.currentAlarms

       Bit meanings:
               bit 0 = linkDown"
   ::= {fr1646v2XLAAlInfoEntry 33554432}

fr1646v2XLAAlInfoPrevAlms OBJECT-TYPE
   SYNTAX      Integer32
   MAX-ACCESS  read-only
   STATUS      current
   DESCRIPTION
      "Path: line.alarms.alarmInfo.previousAlarms

       Bit meanings:
               bit 0 = linkDown"
   ::= {fr1646v2XLAAlInfoEntry 50331648}

fr1646v2XLAAlInfoAlMask OBJECT-TYPE
   SYNTAX      Integer32
   MAX-ACCESS  read-only
   STATUS      current
   DESCRIPTION
      "Path: line.alarms.alarmInfo.alarmMask

       Bit meanings:
               bit 0 = linkDown"
   ::= {fr1646v2XLAAlInfoEntry 67108864}

fr1646v2XLAAlInfoAlLvlLnkDwn OBJECT-TYPE
   SYNTAX      Integer32
   MAX-ACCESS  read-only
   STATUS      current
   DESCRIPTION
      "Path: line.alarms.alarmInfo.alarmLevel.linkDown"
   ::= {fr1646v2XLAAlInfoEntry 83951616}


fr1646v2XLAAlInfoE2 OBJECT IDENTIFIER ::= {fr1646v2XLAAlInfo 2}

fr1646v2XLAAlInfoE2Entry OBJECT IDENTIFIER ::= {fr1646v2XLAAlInfoE2 1}

fr1646v2XLAAlInfoE2LnkDwn OBJECT IDENTIFIER ::= {fr1646v2XLAAlInfoE2Entry 10}

fr1646v2XLAAlInfoE2LnkDwnPfx OBJECT IDENTIFIER ::= {fr1646v2XLAAlInfoE2LnkDwn 0}

fr1646v2XLAAlInfoE2LnkDwnOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'xdslLineAnnexA'
                (root='router1646') has changed from the ON to the OFF state."
   ::= {fr1646v2XLAAlInfoE2LnkDwnPfx 1}

fr1646v2XLAAlInfoE2LnkDwnOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'xdslLineAnnexA'
                (root='router1646') has changed from the OFF to the ON state."
   ::= {fr1646v2XLAAlInfoE2LnkDwnPfx 2}



ar1646v2XLA OBJECT IDENTIFIER ::= {r1646v2XLA 16}


ar1646v2XLASendDebugCmd OBJECT-TYPE
   SYNTAX      Integer32
   MAX-ACCESS  read-write
   STATUS      current
   DESCRIPTION
      "Path: line.actions.sendDebugCmd
       Info: send debug command to Amazon"
   ::= {ar1646v2XLA 714}


ar1646v2XLADebugCmd OBJECT-TYPE
   SYNTAX      DisplayString
   MAX-ACCESS  read-write
   STATUS      current
   DESCRIPTION
      "Path: line.actions.debugCmd
       Info: debug command"
   ::= {ar1646v2XLA 715}


ar1646v2XLAForceUBoot OBJECT-TYPE
   SYNTAX      Integer32
   MAX-ACCESS  read-write
   STATUS      current
   DESCRIPTION
      "Path: line.actions.forceUBoot
       Info: force DSL device in UBoot state"
   ::= {ar1646v2XLA 713}


ar1646v2XLAUpgradeAmazonFile OBJECT-TYPE
   SYNTAX      Integer32
   MAX-ACCESS  read-write
   STATUS      current
   DESCRIPTION
      "Path: line.actions.upgradeAmazonFile
       Info: upgrade file to Amazon"
   ::= {ar1646v2XLA 704}


ar1646v2XLAUpgradeFilename OBJECT IDENTIFIER ::= {ar1646v2XLA 705}

ar1646v2XLAUpgradeFilenameSSC OBJECT IDENTIFIER ::= {ar1646v2XLAUpgradeFilename 1}

ar1646v2XLAUpgradeFilenameEntry OBJECT IDENTIFIER ::= {ar1646v2XLAUpgradeFilenameSSC 1}

ar1646v2XLAUpgradeFilenameName OBJECT-TYPE
   SYNTAX      DisplayString
   MAX-ACCESS  read-write
   STATUS      current
   DESCRIPTION
      "Path: line.actions.upgradeFilename.name"
   ::= {ar1646v2XLAUpgradeFilenameEntry 16777216}


ar1646v2XLADownloadAmazonFile OBJECT-TYPE
   SYNTAX      Integer32
   MAX-ACCESS  read-write
   STATUS      current
   DESCRIPTION
      "Path: line.actions.downloadAmazonFile
       Info: download file to Amazon"
   ::= {ar1646v2XLA 702}


ar1646v2XLADownloadFilename OBJECT IDENTIFIER ::= {ar1646v2XLA 703}

ar1646v2XLADownloadFilenameSSC OBJECT IDENTIFIER ::= {ar1646v2XLADownloadFilename 1}

ar1646v2XLADownloadFilenameEntry OBJECT IDENTIFIER ::= {ar1646v2XLADownloadFilenameSSC 1}

ar1646v2XLADownloadFilenameSrcName OBJECT-TYPE
   SYNTAX      DisplayString
   MAX-ACCESS  read-write
   STATUS      current
   DESCRIPTION
      "Path: line.actions.downloadFilename.srcName"
   ::= {ar1646v2XLADownloadFilenameEntry 16777216}

ar1646v2XLADownloadFilenameDstName OBJECT-TYPE
   SYNTAX      DisplayString
   MAX-ACCESS  read-write
   STATUS      current
   DESCRIPTION
      "Path: line.actions.downloadFilename.dstName"
   ::= {ar1646v2XLADownloadFilenameEntry 33554432}

ar1646v2XLADownloadFilenameOffset OBJECT-TYPE
   SYNTAX      Integer32
   MAX-ACCESS  read-write
   STATUS      current
   DESCRIPTION
      "Path: line.actions.downloadFilename.offset"
   ::= {ar1646v2XLADownloadFilenameEntry 50331648}


ar1646v2XLACacheResume OBJECT-TYPE
   SYNTAX      Integer32
   MAX-ACCESS  read-write
   STATUS      current
   DESCRIPTION
      "Path: line.actions.cacheResume
       Info: resume DSL cache"
   ::= {ar1646v2XLA 708}


ar1646v2XLACacheSuspend OBJECT-TYPE
   SYNTAX      Integer32
   MAX-ACCESS  read-write
   STATUS      current
   DESCRIPTION
      "Path: line.actions.cacheSuspend
       Info: suspend DSL cache"
   ::= {ar1646v2XLA 707}


ar1646v2XLAResetAfterFailure OBJECT-TYPE
   SYNTAX      Integer32
   MAX-ACCESS  read-write
   STATUS      current
   DESCRIPTION
      "Path: line.actions.resetAfterFailure
       Info: enabled or disabled reset of Amazon"
   ::= {ar1646v2XLA 710}


ar1646v2XLAValue OBJECT-TYPE
   SYNTAX      INTEGER
               {
               disabled (0),
               enabled (1)
               }
   MAX-ACCESS  read-write
   STATUS      current
   DESCRIPTION
      "Path: line.actions.value
       Info: enabled or disabled reset of Amazon

       Possibilities:
               disabled   (0)
               enabled   (1)"
   ::= {ar1646v2XLA 711}


ar1646v2XLAForceUnReset OBJECT-TYPE
   SYNTAX      Integer32
   MAX-ACCESS  read-write
   STATUS      current
   DESCRIPTION
      "Path: line.actions.forceUnReset
       Info: reset DSL device"
   ::= {ar1646v2XLA 751}


ar1646v2XLAForceResetOnly OBJECT-TYPE
   SYNTAX      Integer32
   MAX-ACCESS  read-write
   STATUS      current
   DESCRIPTION
      "Path: line.actions.forceResetOnly
       Info: reset DSL device"
   ::= {ar1646v2XLA 750}


ar1646v2XLAForceReset OBJECT-TYPE
   SYNTAX      Integer32
   MAX-ACCESS  read-write
   STATUS      current
   DESCRIPTION
      "Path: line.actions.forceReset
       Info: reset DSL device"
   ::= {ar1646v2XLA 709}


ar1646v2XLAForceResyncCoreDump OBJECT-TYPE
   SYNTAX      Integer32
   MAX-ACCESS  read-write
   STATUS      current
   DESCRIPTION
      "Path: line.actions.forceResyncCoreDump
       Info: resync Amazon Core Dump"
   ::= {ar1646v2XLA 712}


ar1646v2XLAForceResync OBJECT-TYPE
   SYNTAX      Integer32
   MAX-ACCESS  read-write
   STATUS      current
   DESCRIPTION
      "Path: line.actions.forceResync
       Info: resync DSL cache"
   ::= {ar1646v2XLA 706}


ar1646v2XLAForceRetrain OBJECT-TYPE
   SYNTAX      Integer32
   MAX-ACCESS  read-write
   STATUS      current
   DESCRIPTION
      "Path: line.actions.forceRetrain
       Info: retrain DSL"
   ::= {ar1646v2XLA 143}


ar1646v2XLAClearCounters OBJECT-TYPE
   SYNTAX      Integer32
   MAX-ACCESS  read-write
   STATUS      current
   DESCRIPTION
      "Path: line.actions.clearCounters
       Info: reset counters"
   ::= {ar1646v2XLA 263}


ar1646v2XLATestModeAction OBJECT-TYPE
   SYNTAX      Integer32
   MAX-ACCESS  read-write
   STATUS      current
   DESCRIPTION
      "Path: line.actions.testModeAction
       Info: set testMode"
   ::= {ar1646v2XLA 736}


ar1646v2XLATestActivationType OBJECT-TYPE
   SYNTAX      INTEGER
               {
               disable (0),
               showtimeLock (1),
               quiet (2),
               trainingLock (3),
               lock (4),
               unlock (5),
               sleep (6)
               }
   MAX-ACCESS  read-write
   STATUS      current
   DESCRIPTION
      "Path: line.actions.testActivationType
       Info: testmode

       Possibilities:
               disable   (0)
               showtimeLock   (1)
               quiet   (2)
               trainingLock   (3)
               lock   (4)
               unlock   (5)
               sleep   (6)"
   ::= {ar1646v2XLA 737}



END
