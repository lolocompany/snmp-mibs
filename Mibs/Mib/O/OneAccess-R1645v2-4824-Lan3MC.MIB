OneAccess-R1645v2-4824-Lan3MC DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Lan3MC OBJECT IDENTIFIER ::= {r1645Rootv2 4824}

r1645v2Lan3MCMOProp OBJECT IDENTIFIER ::= {r1645v2Lan3MC 1}

r1645v2Lan3MCMOPropEntry OBJECT IDENTIFIER ::= {r1645v2Lan3MCMOProp 1}

r1645v2Lan3MCMOPropPath OBJECT-TYPE
   SYNTAX      ContainmentPath
   MAX-ACCESS  read-only
   STATUS      current
   DESCRIPTION
      "Textual description of the containment tree from the instance of
       the root object down to the instance of the current object."
   ::= {r1645v2Lan3MCMOPropEntry 3}

r1645v2Lan3MCMOPropRev OBJECT-TYPE
   SYNTAX      ObjectRevision
   MAX-ACCESS  read-only
   STATUS      current
   DESCRIPTION
      "This value corresponds with the revision of the MANAGED OBJECT."
   ::= {r1645v2Lan3MCMOPropEntry 4}



er1645v2Lan3MC OBJECT IDENTIFIER ::= {r1645v2Lan3MC 11}


er1645v2Lan3MCRemark OBJECT-TYPE
   SYNTAX      DisplayString
   MAX-ACCESS  read-write
   STATUS      current
   DESCRIPTION
      "Path: ethernet3.editConf.remark
       Info: intfRemark"
   ::= {er1645v2Lan3MC 321}


er1645v2Lan3MCAdminStatus OBJECT-TYPE
   SYNTAX      INTEGER
               {
               up (1),
               down (2)
               }
   MAX-ACCESS  read-write
   STATUS      current
   DESCRIPTION
      "Path: ethernet3.editConf.adminStatus
       Info: ifAdminStatus

       Possibilities:
               up   (1)
               down   (2)"
   ::= {er1645v2Lan3MC 106}


er1645v2Lan3MCBw OBJECT IDENTIFIER ::= {er1645v2Lan3MC 5}

er1645v2Lan3MCBwSSC OBJECT IDENTIFIER ::= {er1645v2Lan3MCBw 1}

er1645v2Lan3MCBwEntry OBJECT IDENTIFIER ::= {er1645v2Lan3MCBwSSC 1}

er1645v2Lan3MCBwMode OBJECT-TYPE
   SYNTAX      INTEGER
               {
               reshaping (1),
               policing (2),
               policingReshape (3)
               }
   MAX-ACCESS  read-write
   STATUS      current
   DESCRIPTION
      "Path: ethernet3.editConf.bandwidth.mode

       Possibilities:
               reshaping   (1)
               policing   (2)
               policingReshape   (3)"
   ::= {er1645v2Lan3MCBwEntry 3758096384}

er1645v2Lan3MCBwCir OBJECT-TYPE
   SYNTAX      Integer32
   MAX-ACCESS  read-write
   STATUS      current
   DESCRIPTION
      "Path: ethernet3.editConf.bandwidth.cir"
   ::= {er1645v2Lan3MCBwEntry 268435456}

er1645v2Lan3MCBwEir OBJECT-TYPE
   SYNTAX      Integer32
   MAX-ACCESS  read-write
   STATUS      current
   DESCRIPTION
      "Path: ethernet3.editConf.bandwidth.eir"
   ::= {er1645v2Lan3MCBwEntry 1879048192}

er1645v2Lan3MCBwUnit OBJECT-TYPE
   SYNTAX      INTEGER
               {
               bitssec (1),
               percent (2)
               }
   MAX-ACCESS  read-write
   STATUS      current
   DESCRIPTION
      "Path: ethernet3.editConf.bandwidth.unit

       Possibilities:
               bits/sec   (1)
               percent   (2)"
   ::= {er1645v2Lan3MCBwEntry 1342177280}

er1645v2Lan3MCBwTc OBJECT-TYPE
   SYNTAX      INTEGER
               {
               auto (0)
               }
   MAX-ACCESS  read-write
   STATUS      current
   DESCRIPTION
      "Path: ethernet3.editConf.bandwidth.tc

       Possibilities:
               auto   (0)"
   ::= {er1645v2Lan3MCBwEntry 1610612736}

er1645v2Lan3MCBwTcFactor OBJECT-TYPE
   SYNTAX      INTEGER
               {
               ms (10),
               s100us (1)
               }
   MAX-ACCESS  read-write
   STATUS      current
   DESCRIPTION
      "Path: ethernet3.editConf.bandwidth.tcFactor

       Possibilities:
               ms   (10)
               *100us   (1)"
   ::= {er1645v2Lan3MCBwEntry 2147483648}

er1645v2Lan3MCBwCorrType OBJECT-TYPE
   SYNTAX      INTEGER
               {
               noCorrection (0),
               predefined (1),
               manual (2)
               }
   MAX-ACCESS  read-write
   STATUS      current
   DESCRIPTION
      "Path: ethernet3.editConf.bandwidth.correction.type

       Possibilities:
               noCorrection   (0)
               predefined   (1)
               manual   (2)"
   ::= {er1645v2Lan3MCBwEntry 570425344}

er1645v2Lan3MCBwCorrPredefEncapsFrameRelay OBJECT-TYPE
   SYNTAX      DisplayString
   MAX-ACCESS  read-write
   STATUS      current
   DESCRIPTION
      "Path: ethernet3.editConf.bandwidth.correction.predefined.encapsulation.frameRelay"
   ::= {er1645v2Lan3MCBwEntry 608436224}

er1645v2Lan3MCBwCorrPredefEncapsPpp OBJECT-TYPE
   SYNTAX      DisplayString
   MAX-ACCESS  read-write
   STATUS      current
   DESCRIPTION
      "Path: ethernet3.editConf.bandwidth.correction.predefined.encapsulation.ppp"
   ::= {er1645v2Lan3MCBwEntry 608698368}

er1645v2Lan3MCBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.bandwidth.correction.predefined.encapsulation.atm.higherLayer

       Possibilities:
               rfc2684   (0)
               ppp   (1)
               pppOverEthernet   (2)"
   ::= {er1645v2Lan3MCBwEntry 608993280}

er1645v2Lan3MCBwCorrPredefEncapsAtmMp OBJECT-TYPE
   SYNTAX      INTEGER
               {
               llcEncapsulation (0),
               vcMultiplexing (1)
               }
   MAX-ACCESS  read-write
   STATUS      current
   DESCRIPTION
      "Path: ethernet3.editConf.bandwidth.correction.predefined.encapsulation.atm.multiProtocol

       Possibilities:
               llcEncapsulation   (0)
               vcMultiplexing   (1)"
   ::= {er1645v2Lan3MCBwEntry 609026048}

er1645v2Lan3MCBwCorrPredefEncapsHdlc OBJECT-TYPE
   SYNTAX      DisplayString
   MAX-ACCESS  read-write
   STATUS      current
   DESCRIPTION
      "Path: ethernet3.editConf.bandwidth.correction.predefined.encapsulation.hdlc"
   ::= {er1645v2Lan3MCBwEntry 609222656}

er1645v2Lan3MCBwCorrPredefEncapsEfmFs OBJECT-TYPE
   SYNTAX      Integer32
   MAX-ACCESS  read-write
   STATUS      current
   DESCRIPTION
      "Path: ethernet3.editConf.bandwidth.correction.predefined.encapsulation.efm.fragmentSize"
   ::= {er1645v2Lan3MCBwEntry 609517568}

er1645v2Lan3MCBwCorrPredefEncapsEfmIb OBJECT-TYPE
   SYNTAX      Integer32
   MAX-ACCESS  read-write
   STATUS      current
   DESCRIPTION
      "Path: ethernet3.editConf.bandwidth.correction.predefined.encapsulation.efm.idleBytes"
   ::= {er1645v2Lan3MCBwEntry 609550336}

er1645v2Lan3MCBwCorrPredefMode OBJECT-TYPE
   SYNTAX      INTEGER
               {
               routing (0),
               bridging (1)
               }
   MAX-ACCESS  read-write
   STATUS      current
   DESCRIPTION
      "Path: ethernet3.editConf.bandwidth.correction.predefined.mode

       Possibilities:
               routing   (0)
               bridging   (1)"
   ::= {er1645v2Lan3MCBwEntry 612368384}

er1645v2Lan3MCBwCorrManualOverhead OBJECT-TYPE
   SYNTAX      Integer32
   MAX-ACCESS  read-write
   STATUS      current
   DESCRIPTION
      "Path: ethernet3.editConf.bandwidth.correction.manual.overhead"
   ::= {er1645v2Lan3MCBwEntry 637665280}

er1645v2Lan3MCBwCorrManualFrameData OBJECT-TYPE
   SYNTAX      Counter32
   MAX-ACCESS  read-write
   STATUS      current
   DESCRIPTION
      "Path: ethernet3.editConf.bandwidth.correction.manual.frameData

       32 bit unsigned wrappable counter."
   ::= {er1645v2Lan3MCBwEntry 637796352}

er1645v2Lan3MCBwCorrManualFrameHeader OBJECT-TYPE
   SYNTAX      Counter32
   MAX-ACCESS  read-write
   STATUS      current
   DESCRIPTION
      "Path: ethernet3.editConf.bandwidth.correction.manual.frameHeader

       32 bit unsigned wrappable counter."
   ::= {er1645v2Lan3MCBwEntry 637927424}

er1645v2Lan3MCBwMaxFifoQLen OBJECT-TYPE
   SYNTAX      Integer32
   MAX-ACCESS  read-write
   STATUS      current
   DESCRIPTION
      "Path: ethernet3.editConf.bandwidth.maxFifoQLen"
   ::= {er1645v2Lan3MCBwEntry 805306368}

er1645v2Lan3MCBwDeFlagCir OBJECT-TYPE
   SYNTAX      INTEGER
               {
               allowed (1),
               notAllowed (2)
               }
   MAX-ACCESS  read-write
   STATUS      current
   DESCRIPTION
      "Path: ethernet3.editConf.bandwidth.deFlag.cir

       Possibilities:
               allowed   (1)
               notAllowed   (2)"
   ::= {er1645v2Lan3MCBwEntry 3490709504}

er1645v2Lan3MCBwDeFlagEir OBJECT-TYPE
   SYNTAX      INTEGER
               {
               allowed (1),
               notAllowed (2)
               }
   MAX-ACCESS  read-write
   STATUS      current
   DESCRIPTION
      "Path: ethernet3.editConf.bandwidth.deFlag.eir

       Possibilities:
               allowed   (1)
               notAllowed   (2)"
   ::= {er1645v2Lan3MCBwEntry 3491758080}

er1645v2Lan3MCBwDeFlagViolate OBJECT-TYPE
   SYNTAX      INTEGER
               {
               allowed (1),
               notAllowed (2)
               }
   MAX-ACCESS  read-write
   STATUS      current
   DESCRIPTION
      "Path: ethernet3.editConf.bandwidth.deFlag.violate

       Possibilities:
               allowed   (1)
               notAllowed   (2)"
   ::= {er1645v2Lan3MCBwEntry 3492806656}

er1645v2Lan3MCBwActCirActNone OBJECT-TYPE
   SYNTAX      OCTET STRING
   MAX-ACCESS  read-write
   STATUS      current
   DESCRIPTION
      "Path: ethernet3.editConf.bandwidth.action.cirAction.none"
   ::= {er1645v2Lan3MCBwEntry 4062183424}

er1645v2Lan3MCBwActCirActEthCos1 OBJECT-TYPE
   SYNTAX      INTEGER
               {
               unchanged (256)
               }
   MAX-ACCESS  read-write
   STATUS      current
   DESCRIPTION
      "Path: ethernet3.editConf.bandwidth.action.cirAction.ethernet.cosDepth1

       Possibilities:
               unchanged   (256)"
   ::= {er1645v2Lan3MCBwEntry 4064346112}

er1645v2Lan3MCBwActCirActEthDei1 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth1

       Possibilities:
               unchanged   (255)
               clear   (0)
               set   (1)"
   ::= {er1645v2Lan3MCBwEntry 4065656832}

er1645v2Lan3MCBwActCirActEthCos2 OBJECT-TYPE
   SYNTAX      INTEGER
               {
               unchanged (256)
               }
   MAX-ACCESS  read-write
   STATUS      current
   DESCRIPTION
      "Path: ethernet3.editConf.bandwidth.action.cirAction.ethernet.cosDepth2

       Possibilities:
               unchanged   (256)"
   ::= {er1645v2Lan3MCBwEntry 4064411648}

er1645v2Lan3MCBwActCirActEthDei2 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth2

       Possibilities:
               unchanged   (255)
               clear   (0)
               set   (1)"
   ::= {er1645v2Lan3MCBwEntry 4065722368}

er1645v2Lan3MCBwActCirActEthCos3 OBJECT-TYPE
   SYNTAX      INTEGER
               {
               unchanged (256)
               }
   MAX-ACCESS  read-write
   STATUS      current
   DESCRIPTION
      "Path: ethernet3.editConf.bandwidth.action.cirAction.ethernet.cosDepth3

       Possibilities:
               unchanged   (256)"
   ::= {er1645v2Lan3MCBwEntry 4064477184}

er1645v2Lan3MCBwActCirActEthDei3 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth3

       Possibilities:
               unchanged   (255)
               clear   (0)
               set   (1)"
   ::= {er1645v2Lan3MCBwEntry 4065787904}

er1645v2Lan3MCBwActCirActEthCos4 OBJECT-TYPE
   SYNTAX      INTEGER
               {
               unchanged (256)
               }
   MAX-ACCESS  read-write
   STATUS      current
   DESCRIPTION
      "Path: ethernet3.editConf.bandwidth.action.cirAction.ethernet.cosDepth4

       Possibilities:
               unchanged   (256)"
   ::= {er1645v2Lan3MCBwEntry 4064542720}

er1645v2Lan3MCBwActCirActEthDei4 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth4

       Possibilities:
               unchanged   (255)
               clear   (0)
               set   (1)"
   ::= {er1645v2Lan3MCBwEntry 4065853440}

er1645v2Lan3MCBwActCirActEthCos5 OBJECT-TYPE
   SYNTAX      INTEGER
               {
               unchanged (256)
               }
   MAX-ACCESS  read-write
   STATUS      current
   DESCRIPTION
      "Path: ethernet3.editConf.bandwidth.action.cirAction.ethernet.cosDepth5

       Possibilities:
               unchanged   (256)"
   ::= {er1645v2Lan3MCBwEntry 4064608256}

er1645v2Lan3MCBwActCirActEthDei5 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth5

       Possibilities:
               unchanged   (255)
               clear   (0)
               set   (1)"
   ::= {er1645v2Lan3MCBwEntry 4065918976}

er1645v2Lan3MCBwActCirActEthCos6 OBJECT-TYPE
   SYNTAX      INTEGER
               {
               unchanged (256)
               }
   MAX-ACCESS  read-write
   STATUS      current
   DESCRIPTION
      "Path: ethernet3.editConf.bandwidth.action.cirAction.ethernet.cosDepth6

       Possibilities:
               unchanged   (256)"
   ::= {er1645v2Lan3MCBwEntry 4064673792}

er1645v2Lan3MCBwActCirActEthDei6 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth6

       Possibilities:
               unchanged   (255)
               clear   (0)
               set   (1)"
   ::= {er1645v2Lan3MCBwEntry 4065984512}

er1645v2Lan3MCBwActCirActEthCos7 OBJECT-TYPE
   SYNTAX      INTEGER
               {
               unchanged (256)
               }
   MAX-ACCESS  read-write
   STATUS      current
   DESCRIPTION
      "Path: ethernet3.editConf.bandwidth.action.cirAction.ethernet.cosDepth7

       Possibilities:
               unchanged   (256)"
   ::= {er1645v2Lan3MCBwEntry 4064739328}

er1645v2Lan3MCBwActCirActEthDei7 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth7

       Possibilities:
               unchanged   (255)
               clear   (0)
               set   (1)"
   ::= {er1645v2Lan3MCBwEntry 4066050048}

er1645v2Lan3MCBwActCirActEthCos8 OBJECT-TYPE
   SYNTAX      INTEGER
               {
               unchanged (256)
               }
   MAX-ACCESS  read-write
   STATUS      current
   DESCRIPTION
      "Path: ethernet3.editConf.bandwidth.action.cirAction.ethernet.cosDepth8

       Possibilities:
               unchanged   (256)"
   ::= {er1645v2Lan3MCBwEntry 4064804864}

er1645v2Lan3MCBwActCirActEthDei8 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth8

       Possibilities:
               unchanged   (255)
               clear   (0)
               set   (1)"
   ::= {er1645v2Lan3MCBwEntry 4066115584}

er1645v2Lan3MCBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4064870400}

er1645v2Lan3MCBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4064935936}

er1645v2Lan3MCBwActCirActEthDrpLev OBJECT-TYPE
   SYNTAX      INTEGER
               {
               unchanged (0)
               }
   MAX-ACCESS  read-write
   STATUS      current
   DESCRIPTION
      "Path: ethernet3.editConf.bandwidth.action.cirAction.ethernet.dropLevel

       Possibilities:
               unchanged   (0)"
   ::= {er1645v2Lan3MCBwEntry 4065001472}

er1645v2Lan3MCBwActCirActEthDeFlag OBJECT-TYPE
   SYNTAX      INTEGER
               {
               unchanged (255),
               clear (0),
               set (1)
               }
   MAX-ACCESS  read-write
   STATUS      current
   DESCRIPTION
      "Path: ethernet3.editConf.bandwidth.action.cirAction.ethernet.deFlag

       Possibilities:
               unchanged   (255)
               clear   (0)
               set   (1)"
   ::= {er1645v2Lan3MCBwEntry 4065198080}

er1645v2Lan3MCBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4071161856}

er1645v2Lan3MCBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4071227392}

er1645v2Lan3MCBwActCirActIpDrpLev OBJECT-TYPE
   SYNTAX      INTEGER
               {
               unchanged (0)
               }
   MAX-ACCESS  read-write
   STATUS      current
   DESCRIPTION
      "Path: ethernet3.editConf.bandwidth.action.cirAction.ip.dropLevel

       Possibilities:
               unchanged   (0)"
   ::= {er1645v2Lan3MCBwEntry 4071292928}

er1645v2Lan3MCBwActCirActIpDeFlag OBJECT-TYPE
   SYNTAX      INTEGER
               {
               unchanged (255),
               clear (0),
               set (1)
               }
   MAX-ACCESS  read-write
   STATUS      current
   DESCRIPTION
      "Path: ethernet3.editConf.bandwidth.action.cirAction.ip.deFlag

       Possibilities:
               unchanged   (255)
               clear   (0)
               set   (1)"
   ::= {er1645v2Lan3MCBwEntry 4071489536}

er1645v2Lan3MCBwActEirActNone OBJECT-TYPE
   SYNTAX      OCTET STRING
   MAX-ACCESS  read-write
   STATUS      current
   DESCRIPTION
      "Path: ethernet3.editConf.bandwidth.action.eirAction.none"
   ::= {er1645v2Lan3MCBwEntry 4095737856}

er1645v2Lan3MCBwActEirActEthCos1 OBJECT-TYPE
   SYNTAX      INTEGER
               {
               unchanged (256)
               }
   MAX-ACCESS  read-write
   STATUS      current
   DESCRIPTION
      "Path: ethernet3.editConf.bandwidth.action.eirAction.ethernet.cosDepth1

       Possibilities:
               unchanged   (256)"
   ::= {er1645v2Lan3MCBwEntry 4097900544}

er1645v2Lan3MCBwActEirActEthDei1 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth1

       Possibilities:
               unchanged   (255)
               clear   (0)
               set   (1)"
   ::= {er1645v2Lan3MCBwEntry 4099211264}

er1645v2Lan3MCBwActEirActEthCos2 OBJECT-TYPE
   SYNTAX      INTEGER
               {
               unchanged (256)
               }
   MAX-ACCESS  read-write
   STATUS      current
   DESCRIPTION
      "Path: ethernet3.editConf.bandwidth.action.eirAction.ethernet.cosDepth2

       Possibilities:
               unchanged   (256)"
   ::= {er1645v2Lan3MCBwEntry 4097966080}

er1645v2Lan3MCBwActEirActEthDei2 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth2

       Possibilities:
               unchanged   (255)
               clear   (0)
               set   (1)"
   ::= {er1645v2Lan3MCBwEntry 4099276800}

er1645v2Lan3MCBwActEirActEthCos3 OBJECT-TYPE
   SYNTAX      INTEGER
               {
               unchanged (256)
               }
   MAX-ACCESS  read-write
   STATUS      current
   DESCRIPTION
      "Path: ethernet3.editConf.bandwidth.action.eirAction.ethernet.cosDepth3

       Possibilities:
               unchanged   (256)"
   ::= {er1645v2Lan3MCBwEntry 4098031616}

er1645v2Lan3MCBwActEirActEthDei3 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth3

       Possibilities:
               unchanged   (255)
               clear   (0)
               set   (1)"
   ::= {er1645v2Lan3MCBwEntry 4099342336}

er1645v2Lan3MCBwActEirActEthCos4 OBJECT-TYPE
   SYNTAX      INTEGER
               {
               unchanged (256)
               }
   MAX-ACCESS  read-write
   STATUS      current
   DESCRIPTION
      "Path: ethernet3.editConf.bandwidth.action.eirAction.ethernet.cosDepth4

       Possibilities:
               unchanged   (256)"
   ::= {er1645v2Lan3MCBwEntry 4098097152}

er1645v2Lan3MCBwActEirActEthDei4 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth4

       Possibilities:
               unchanged   (255)
               clear   (0)
               set   (1)"
   ::= {er1645v2Lan3MCBwEntry 4099407872}

er1645v2Lan3MCBwActEirActEthCos5 OBJECT-TYPE
   SYNTAX      INTEGER
               {
               unchanged (256)
               }
   MAX-ACCESS  read-write
   STATUS      current
   DESCRIPTION
      "Path: ethernet3.editConf.bandwidth.action.eirAction.ethernet.cosDepth5

       Possibilities:
               unchanged   (256)"
   ::= {er1645v2Lan3MCBwEntry 4098162688}

er1645v2Lan3MCBwActEirActEthDei5 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth5

       Possibilities:
               unchanged   (255)
               clear   (0)
               set   (1)"
   ::= {er1645v2Lan3MCBwEntry 4099473408}

er1645v2Lan3MCBwActEirActEthCos6 OBJECT-TYPE
   SYNTAX      INTEGER
               {
               unchanged (256)
               }
   MAX-ACCESS  read-write
   STATUS      current
   DESCRIPTION
      "Path: ethernet3.editConf.bandwidth.action.eirAction.ethernet.cosDepth6

       Possibilities:
               unchanged   (256)"
   ::= {er1645v2Lan3MCBwEntry 4098228224}

er1645v2Lan3MCBwActEirActEthDei6 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth6

       Possibilities:
               unchanged   (255)
               clear   (0)
               set   (1)"
   ::= {er1645v2Lan3MCBwEntry 4099538944}

er1645v2Lan3MCBwActEirActEthCos7 OBJECT-TYPE
   SYNTAX      INTEGER
               {
               unchanged (256)
               }
   MAX-ACCESS  read-write
   STATUS      current
   DESCRIPTION
      "Path: ethernet3.editConf.bandwidth.action.eirAction.ethernet.cosDepth7

       Possibilities:
               unchanged   (256)"
   ::= {er1645v2Lan3MCBwEntry 4098293760}

er1645v2Lan3MCBwActEirActEthDei7 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth7

       Possibilities:
               unchanged   (255)
               clear   (0)
               set   (1)"
   ::= {er1645v2Lan3MCBwEntry 4099604480}

er1645v2Lan3MCBwActEirActEthCos8 OBJECT-TYPE
   SYNTAX      INTEGER
               {
               unchanged (256)
               }
   MAX-ACCESS  read-write
   STATUS      current
   DESCRIPTION
      "Path: ethernet3.editConf.bandwidth.action.eirAction.ethernet.cosDepth8

       Possibilities:
               unchanged   (256)"
   ::= {er1645v2Lan3MCBwEntry 4098359296}

er1645v2Lan3MCBwActEirActEthDei8 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth8

       Possibilities:
               unchanged   (255)
               clear   (0)
               set   (1)"
   ::= {er1645v2Lan3MCBwEntry 4099670016}

er1645v2Lan3MCBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4098424832}

er1645v2Lan3MCBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4098490368}

er1645v2Lan3MCBwActEirActEthDrpLev OBJECT-TYPE
   SYNTAX      INTEGER
               {
               unchanged (0)
               }
   MAX-ACCESS  read-write
   STATUS      current
   DESCRIPTION
      "Path: ethernet3.editConf.bandwidth.action.eirAction.ethernet.dropLevel

       Possibilities:
               unchanged   (0)"
   ::= {er1645v2Lan3MCBwEntry 4098555904}

er1645v2Lan3MCBwActEirActEthDeFlag OBJECT-TYPE
   SYNTAX      INTEGER
               {
               unchanged (255),
               clear (0),
               set (1)
               }
   MAX-ACCESS  read-write
   STATUS      current
   DESCRIPTION
      "Path: ethernet3.editConf.bandwidth.action.eirAction.ethernet.deFlag

       Possibilities:
               unchanged   (255)
               clear   (0)
               set   (1)"
   ::= {er1645v2Lan3MCBwEntry 4098752512}

er1645v2Lan3MCBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4104716288}

er1645v2Lan3MCBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4104781824}

er1645v2Lan3MCBwActEirActIpDrpLev OBJECT-TYPE
   SYNTAX      INTEGER
               {
               unchanged (0)
               }
   MAX-ACCESS  read-write
   STATUS      current
   DESCRIPTION
      "Path: ethernet3.editConf.bandwidth.action.eirAction.ip.dropLevel

       Possibilities:
               unchanged   (0)"
   ::= {er1645v2Lan3MCBwEntry 4104847360}

er1645v2Lan3MCBwActEirActIpDeFlag OBJECT-TYPE
   SYNTAX      INTEGER
               {
               unchanged (255),
               clear (0),
               set (1)
               }
   MAX-ACCESS  read-write
   STATUS      current
   DESCRIPTION
      "Path: ethernet3.editConf.bandwidth.action.eirAction.ip.deFlag

       Possibilities:
               unchanged   (255)
               clear   (0)
               set   (1)"
   ::= {er1645v2Lan3MCBwEntry 4105043968}

er1645v2Lan3MCBwActViolActNone OBJECT-TYPE
   SYNTAX      OCTET STRING
   MAX-ACCESS  read-write
   STATUS      current
   DESCRIPTION
      "Path: ethernet3.editConf.bandwidth.action.violateAction.none"
   ::= {er1645v2Lan3MCBwEntry 4129292288}

er1645v2Lan3MCBwActViolActDrop OBJECT-TYPE
   SYNTAX      OCTET STRING
   MAX-ACCESS  read-write
   STATUS      current
   DESCRIPTION
      "Path: ethernet3.editConf.bandwidth.action.violateAction.drop"
   ::= {er1645v2Lan3MCBwEntry 4133486592}

er1645v2Lan3MCBwActViolActEthCos1 OBJECT-TYPE
   SYNTAX      INTEGER
               {
               unchanged (256)
               }
   MAX-ACCESS  read-write
   STATUS      current
   DESCRIPTION
      "Path: ethernet3.editConf.bandwidth.action.violateAction.ethernet.cosDepth1

       Possibilities:
               unchanged   (256)"
   ::= {er1645v2Lan3MCBwEntry 4131454976}

er1645v2Lan3MCBwActViolActEthDei1 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth1

       Possibilities:
               unchanged   (255)
               clear   (0)
               set   (1)"
   ::= {er1645v2Lan3MCBwEntry 4132765696}

er1645v2Lan3MCBwActViolActEthCos2 OBJECT-TYPE
   SYNTAX      INTEGER
               {
               unchanged (256)
               }
   MAX-ACCESS  read-write
   STATUS      current
   DESCRIPTION
      "Path: ethernet3.editConf.bandwidth.action.violateAction.ethernet.cosDepth2

       Possibilities:
               unchanged   (256)"
   ::= {er1645v2Lan3MCBwEntry 4131520512}

er1645v2Lan3MCBwActViolActEthDei2 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth2

       Possibilities:
               unchanged   (255)
               clear   (0)
               set   (1)"
   ::= {er1645v2Lan3MCBwEntry 4132831232}

er1645v2Lan3MCBwActViolActEthCos3 OBJECT-TYPE
   SYNTAX      INTEGER
               {
               unchanged (256)
               }
   MAX-ACCESS  read-write
   STATUS      current
   DESCRIPTION
      "Path: ethernet3.editConf.bandwidth.action.violateAction.ethernet.cosDepth3

       Possibilities:
               unchanged   (256)"
   ::= {er1645v2Lan3MCBwEntry 4131586048}

er1645v2Lan3MCBwActViolActEthDei3 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth3

       Possibilities:
               unchanged   (255)
               clear   (0)
               set   (1)"
   ::= {er1645v2Lan3MCBwEntry 4132896768}

er1645v2Lan3MCBwActViolActEthCos4 OBJECT-TYPE
   SYNTAX      INTEGER
               {
               unchanged (256)
               }
   MAX-ACCESS  read-write
   STATUS      current
   DESCRIPTION
      "Path: ethernet3.editConf.bandwidth.action.violateAction.ethernet.cosDepth4

       Possibilities:
               unchanged   (256)"
   ::= {er1645v2Lan3MCBwEntry 4131651584}

er1645v2Lan3MCBwActViolActEthDei4 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth4

       Possibilities:
               unchanged   (255)
               clear   (0)
               set   (1)"
   ::= {er1645v2Lan3MCBwEntry 4132962304}

er1645v2Lan3MCBwActViolActEthCos5 OBJECT-TYPE
   SYNTAX      INTEGER
               {
               unchanged (256)
               }
   MAX-ACCESS  read-write
   STATUS      current
   DESCRIPTION
      "Path: ethernet3.editConf.bandwidth.action.violateAction.ethernet.cosDepth5

       Possibilities:
               unchanged   (256)"
   ::= {er1645v2Lan3MCBwEntry 4131717120}

er1645v2Lan3MCBwActViolActEthDei5 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth5

       Possibilities:
               unchanged   (255)
               clear   (0)
               set   (1)"
   ::= {er1645v2Lan3MCBwEntry 4133027840}

er1645v2Lan3MCBwActViolActEthCos6 OBJECT-TYPE
   SYNTAX      INTEGER
               {
               unchanged (256)
               }
   MAX-ACCESS  read-write
   STATUS      current
   DESCRIPTION
      "Path: ethernet3.editConf.bandwidth.action.violateAction.ethernet.cosDepth6

       Possibilities:
               unchanged   (256)"
   ::= {er1645v2Lan3MCBwEntry 4131782656}

er1645v2Lan3MCBwActViolActEthDei6 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth6

       Possibilities:
               unchanged   (255)
               clear   (0)
               set   (1)"
   ::= {er1645v2Lan3MCBwEntry 4133093376}

er1645v2Lan3MCBwActViolActEthCos7 OBJECT-TYPE
   SYNTAX      INTEGER
               {
               unchanged (256)
               }
   MAX-ACCESS  read-write
   STATUS      current
   DESCRIPTION
      "Path: ethernet3.editConf.bandwidth.action.violateAction.ethernet.cosDepth7

       Possibilities:
               unchanged   (256)"
   ::= {er1645v2Lan3MCBwEntry 4131848192}

er1645v2Lan3MCBwActViolActEthDei7 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth7

       Possibilities:
               unchanged   (255)
               clear   (0)
               set   (1)"
   ::= {er1645v2Lan3MCBwEntry 4133158912}

er1645v2Lan3MCBwActViolActEthCos8 OBJECT-TYPE
   SYNTAX      INTEGER
               {
               unchanged (256)
               }
   MAX-ACCESS  read-write
   STATUS      current
   DESCRIPTION
      "Path: ethernet3.editConf.bandwidth.action.violateAction.ethernet.cosDepth8

       Possibilities:
               unchanged   (256)"
   ::= {er1645v2Lan3MCBwEntry 4131913728}

er1645v2Lan3MCBwActViolActEthDei8 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth8

       Possibilities:
               unchanged   (255)
               clear   (0)
               set   (1)"
   ::= {er1645v2Lan3MCBwEntry 4133224448}

er1645v2Lan3MCBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4131979264}

er1645v2Lan3MCBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4132044800}

er1645v2Lan3MCBwActViolActEthDrpLev OBJECT-TYPE
   SYNTAX      INTEGER
               {
               unchanged (0)
               }
   MAX-ACCESS  read-write
   STATUS      current
   DESCRIPTION
      "Path: ethernet3.editConf.bandwidth.action.violateAction.ethernet.dropLevel

       Possibilities:
               unchanged   (0)"
   ::= {er1645v2Lan3MCBwEntry 4132110336}

er1645v2Lan3MCBwActViolActEthDeFlag OBJECT-TYPE
   SYNTAX      INTEGER
               {
               unchanged (255),
               clear (0),
               set (1)
               }
   MAX-ACCESS  read-write
   STATUS      current
   DESCRIPTION
      "Path: ethernet3.editConf.bandwidth.action.violateAction.ethernet.deFlag

       Possibilities:
               unchanged   (255)
               clear   (0)
               set   (1)"
   ::= {er1645v2Lan3MCBwEntry 4132306944}

er1645v2Lan3MCBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCBwEntry 4138270720}

er1645v2Lan3MCBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCBwEntry 4138336256}

er1645v2Lan3MCBwActViolActIpDrpLev OBJECT-TYPE
   SYNTAX      INTEGER
               {
               unchanged (0)
               }
   MAX-ACCESS  read-write
   STATUS      current
   DESCRIPTION
      "Path: ethernet3.editConf.bandwidth.action.violateAction.ip.dropLevel

       Possibilities:
               unchanged   (0)"
   ::= {er1645v2Lan3MCBwEntry 4138401792}

er1645v2Lan3MCBwActViolActIpDeFlag OBJECT-TYPE
   SYNTAX      INTEGER
               {
               unchanged (255),
               clear (0),
               set (1)
               }
   MAX-ACCESS  read-write
   STATUS      current
   DESCRIPTION
      "Path: ethernet3.editConf.bandwidth.action.violateAction.ip.deFlag

       Possibilities:
               unchanged   (255)
               clear   (0)
               set   (1)"
   ::= {er1645v2Lan3MCBwEntry 4138598400}


er1645v2Lan3MCIbw OBJECT IDENTIFIER ::= {er1645v2Lan3MC 13}

er1645v2Lan3MCIbwSSC OBJECT IDENTIFIER ::= {er1645v2Lan3MCIbw 1}

er1645v2Lan3MCIbwEntry OBJECT IDENTIFIER ::= {er1645v2Lan3MCIbwSSC 1}

er1645v2Lan3MCIbwMode OBJECT-TYPE
   SYNTAX      INTEGER
               {
               reshaping (1),
               policing (2)
               }
   MAX-ACCESS  read-write
   STATUS      current
   DESCRIPTION
      "Path: ethernet3.editConf.inboundBandwidth.mode

       Possibilities:
               reshaping   (1)
               policing   (2)"
   ::= {er1645v2Lan3MCIbwEntry 3758096384}

er1645v2Lan3MCIbwCir OBJECT-TYPE
   SYNTAX      Integer32
   MAX-ACCESS  read-write
   STATUS      current
   DESCRIPTION
      "Path: ethernet3.editConf.inboundBandwidth.cir"
   ::= {er1645v2Lan3MCIbwEntry 268435456}

er1645v2Lan3MCIbwEir OBJECT-TYPE
   SYNTAX      Integer32
   MAX-ACCESS  read-write
   STATUS      current
   DESCRIPTION
      "Path: ethernet3.editConf.inboundBandwidth.eir"
   ::= {er1645v2Lan3MCIbwEntry 1879048192}

er1645v2Lan3MCIbwUnit OBJECT-TYPE
   SYNTAX      INTEGER
               {
               bitssec (1),
               percent (2)
               }
   MAX-ACCESS  read-write
   STATUS      current
   DESCRIPTION
      "Path: ethernet3.editConf.inboundBandwidth.unit

       Possibilities:
               bits/sec   (1)
               percent   (2)"
   ::= {er1645v2Lan3MCIbwEntry 1342177280}

er1645v2Lan3MCIbwTc OBJECT-TYPE
   SYNTAX      INTEGER
               {
               auto (0)
               }
   MAX-ACCESS  read-write
   STATUS      current
   DESCRIPTION
      "Path: ethernet3.editConf.inboundBandwidth.tc

       Possibilities:
               auto   (0)"
   ::= {er1645v2Lan3MCIbwEntry 1610612736}

er1645v2Lan3MCIbwTcFactor OBJECT-TYPE
   SYNTAX      INTEGER
               {
               ms (10),
               s100us (1)
               }
   MAX-ACCESS  read-write
   STATUS      current
   DESCRIPTION
      "Path: ethernet3.editConf.inboundBandwidth.tcFactor

       Possibilities:
               ms   (10)
               *100us   (1)"
   ::= {er1645v2Lan3MCIbwEntry 2147483648}

er1645v2Lan3MCIbwCorrType OBJECT-TYPE
   SYNTAX      INTEGER
               {
               noCorrection (0),
               predefined (1),
               manual (2)
               }
   MAX-ACCESS  read-write
   STATUS      current
   DESCRIPTION
      "Path: ethernet3.editConf.inboundBandwidth.correction.type

       Possibilities:
               noCorrection   (0)
               predefined   (1)
               manual   (2)"
   ::= {er1645v2Lan3MCIbwEntry 570425344}

er1645v2Lan3MCIbwCorrPredefEncapsFrameRelay OBJECT-TYPE
   SYNTAX      DisplayString
   MAX-ACCESS  read-write
   STATUS      current
   DESCRIPTION
      "Path: ethernet3.editConf.inboundBandwidth.correction.predefined.encapsulation.frameRelay"
   ::= {er1645v2Lan3MCIbwEntry 608436224}

er1645v2Lan3MCIbwCorrPredefEncapsPpp OBJECT-TYPE
   SYNTAX      DisplayString
   MAX-ACCESS  read-write
   STATUS      current
   DESCRIPTION
      "Path: ethernet3.editConf.inboundBandwidth.correction.predefined.encapsulation.ppp"
   ::= {er1645v2Lan3MCIbwEntry 608698368}

er1645v2Lan3MCIbwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.inboundBandwidth.correction.predefined.encapsulation.atm.higherLayer

       Possibilities:
               rfc2684   (0)
               ppp   (1)
               pppOverEthernet   (2)"
   ::= {er1645v2Lan3MCIbwEntry 608993280}

er1645v2Lan3MCIbwCorrPredefEncapsAtmMp OBJECT-TYPE
   SYNTAX      INTEGER
               {
               llcEncapsulation (0),
               vcMultiplexing (1)
               }
   MAX-ACCESS  read-write
   STATUS      current
   DESCRIPTION
      "Path: ethernet3.editConf.inboundBandwidth.correction.predefined.encapsulation.atm.multiProtocol

       Possibilities:
               llcEncapsulation   (0)
               vcMultiplexing   (1)"
   ::= {er1645v2Lan3MCIbwEntry 609026048}

er1645v2Lan3MCIbwCorrPredefEncapsHdlc OBJECT-TYPE
   SYNTAX      DisplayString
   MAX-ACCESS  read-write
   STATUS      current
   DESCRIPTION
      "Path: ethernet3.editConf.inboundBandwidth.correction.predefined.encapsulation.hdlc"
   ::= {er1645v2Lan3MCIbwEntry 609222656}

er1645v2Lan3MCIbwCorrPredefEncapsEfmFs OBJECT-TYPE
   SYNTAX      Integer32
   MAX-ACCESS  read-write
   STATUS      current
   DESCRIPTION
      "Path: ethernet3.editConf.inboundBandwidth.correction.predefined.encapsulation.efm.fragmentSize"
   ::= {er1645v2Lan3MCIbwEntry 609517568}

er1645v2Lan3MCIbwCorrPredefEncapsEfmIb OBJECT-TYPE
   SYNTAX      Integer32
   MAX-ACCESS  read-write
   STATUS      current
   DESCRIPTION
      "Path: ethernet3.editConf.inboundBandwidth.correction.predefined.encapsulation.efm.idleBytes"
   ::= {er1645v2Lan3MCIbwEntry 609550336}

er1645v2Lan3MCIbwCorrPredefMode OBJECT-TYPE
   SYNTAX      INTEGER
               {
               routing (0),
               bridging (1)
               }
   MAX-ACCESS  read-write
   STATUS      current
   DESCRIPTION
      "Path: ethernet3.editConf.inboundBandwidth.correction.predefined.mode

       Possibilities:
               routing   (0)
               bridging   (1)"
   ::= {er1645v2Lan3MCIbwEntry 612368384}

er1645v2Lan3MCIbwCorrManualOverhead OBJECT-TYPE
   SYNTAX      Integer32
   MAX-ACCESS  read-write
   STATUS      current
   DESCRIPTION
      "Path: ethernet3.editConf.inboundBandwidth.correction.manual.overhead"
   ::= {er1645v2Lan3MCIbwEntry 637665280}

er1645v2Lan3MCIbwCorrManualFrameData OBJECT-TYPE
   SYNTAX      Counter32
   MAX-ACCESS  read-write
   STATUS      current
   DESCRIPTION
      "Path: ethernet3.editConf.inboundBandwidth.correction.manual.frameData

       32 bit unsigned wrappable counter."
   ::= {er1645v2Lan3MCIbwEntry 637796352}

er1645v2Lan3MCIbwCorrManualFrameHeader OBJECT-TYPE
   SYNTAX      Counter32
   MAX-ACCESS  read-write
   STATUS      current
   DESCRIPTION
      "Path: ethernet3.editConf.inboundBandwidth.correction.manual.frameHeader

       32 bit unsigned wrappable counter."
   ::= {er1645v2Lan3MCIbwEntry 637927424}

er1645v2Lan3MCIbwMaxFifoQLen OBJECT-TYPE
   SYNTAX      Integer32
   MAX-ACCESS  read-write
   STATUS      current
   DESCRIPTION
      "Path: ethernet3.editConf.inboundBandwidth.maxFifoQLen"
   ::= {er1645v2Lan3MCIbwEntry 805306368}

er1645v2Lan3MCIbwPriorityPolicy OBJECT-TYPE
   SYNTAX      DisplayString
   MAX-ACCESS  read-write
   STATUS      current
   DESCRIPTION
      "Path: ethernet3.editConf.inboundBandwidth.priorityPolicy"
   ::= {er1645v2Lan3MCIbwEntry 1073741824}

er1645v2Lan3MCIbwDeFlagCir OBJECT-TYPE
   SYNTAX      INTEGER
               {
               allowed (1),
               notAllowed (2)
               }
   MAX-ACCESS  read-write
   STATUS      current
   DESCRIPTION
      "Path: ethernet3.editConf.inboundBandwidth.deFlag.cir

       Possibilities:
               allowed   (1)
               notAllowed   (2)"
   ::= {er1645v2Lan3MCIbwEntry 3490709504}

er1645v2Lan3MCIbwDeFlagEir OBJECT-TYPE
   SYNTAX      INTEGER
               {
               allowed (1),
               notAllowed (2)
               }
   MAX-ACCESS  read-write
   STATUS      current
   DESCRIPTION
      "Path: ethernet3.editConf.inboundBandwidth.deFlag.eir

       Possibilities:
               allowed   (1)
               notAllowed   (2)"
   ::= {er1645v2Lan3MCIbwEntry 3491758080}

er1645v2Lan3MCIbwDeFlagViolate OBJECT-TYPE
   SYNTAX      INTEGER
               {
               allowed (1),
               notAllowed (2)
               }
   MAX-ACCESS  read-write
   STATUS      current
   DESCRIPTION
      "Path: ethernet3.editConf.inboundBandwidth.deFlag.violate

       Possibilities:
               allowed   (1)
               notAllowed   (2)"
   ::= {er1645v2Lan3MCIbwEntry 3492806656}

er1645v2Lan3MCIbwActCirActNone OBJECT-TYPE
   SYNTAX      OCTET STRING
   MAX-ACCESS  read-write
   STATUS      current
   DESCRIPTION
      "Path: ethernet3.editConf.inboundBandwidth.action.cirAction.none"
   ::= {er1645v2Lan3MCIbwEntry 4062183424}

er1645v2Lan3MCIbwActCirActEthCos1 OBJECT-TYPE
   SYNTAX      INTEGER
               {
               unchanged (256)
               }
   MAX-ACCESS  read-write
   STATUS      current
   DESCRIPTION
      "Path: ethernet3.editConf.inboundBandwidth.action.cirAction.ethernet.cosDepth1

       Possibilities:
               unchanged   (256)"
   ::= {er1645v2Lan3MCIbwEntry 4064346112}

er1645v2Lan3MCIbwActCirActEthDei1 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth1

       Possibilities:
               unchanged   (255)
               clear   (0)
               set   (1)"
   ::= {er1645v2Lan3MCIbwEntry 4065656832}

er1645v2Lan3MCIbwActCirActEthCos2 OBJECT-TYPE
   SYNTAX      INTEGER
               {
               unchanged (256)
               }
   MAX-ACCESS  read-write
   STATUS      current
   DESCRIPTION
      "Path: ethernet3.editConf.inboundBandwidth.action.cirAction.ethernet.cosDepth2

       Possibilities:
               unchanged   (256)"
   ::= {er1645v2Lan3MCIbwEntry 4064411648}

er1645v2Lan3MCIbwActCirActEthDei2 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth2

       Possibilities:
               unchanged   (255)
               clear   (0)
               set   (1)"
   ::= {er1645v2Lan3MCIbwEntry 4065722368}

er1645v2Lan3MCIbwActCirActEthCos3 OBJECT-TYPE
   SYNTAX      INTEGER
               {
               unchanged (256)
               }
   MAX-ACCESS  read-write
   STATUS      current
   DESCRIPTION
      "Path: ethernet3.editConf.inboundBandwidth.action.cirAction.ethernet.cosDepth3

       Possibilities:
               unchanged   (256)"
   ::= {er1645v2Lan3MCIbwEntry 4064477184}

er1645v2Lan3MCIbwActCirActEthDei3 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth3

       Possibilities:
               unchanged   (255)
               clear   (0)
               set   (1)"
   ::= {er1645v2Lan3MCIbwEntry 4065787904}

er1645v2Lan3MCIbwActCirActEthCos4 OBJECT-TYPE
   SYNTAX      INTEGER
               {
               unchanged (256)
               }
   MAX-ACCESS  read-write
   STATUS      current
   DESCRIPTION
      "Path: ethernet3.editConf.inboundBandwidth.action.cirAction.ethernet.cosDepth4

       Possibilities:
               unchanged   (256)"
   ::= {er1645v2Lan3MCIbwEntry 4064542720}

er1645v2Lan3MCIbwActCirActEthDei4 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth4

       Possibilities:
               unchanged   (255)
               clear   (0)
               set   (1)"
   ::= {er1645v2Lan3MCIbwEntry 4065853440}

er1645v2Lan3MCIbwActCirActEthCos5 OBJECT-TYPE
   SYNTAX      INTEGER
               {
               unchanged (256)
               }
   MAX-ACCESS  read-write
   STATUS      current
   DESCRIPTION
      "Path: ethernet3.editConf.inboundBandwidth.action.cirAction.ethernet.cosDepth5

       Possibilities:
               unchanged   (256)"
   ::= {er1645v2Lan3MCIbwEntry 4064608256}

er1645v2Lan3MCIbwActCirActEthDei5 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth5

       Possibilities:
               unchanged   (255)
               clear   (0)
               set   (1)"
   ::= {er1645v2Lan3MCIbwEntry 4065918976}

er1645v2Lan3MCIbwActCirActEthCos6 OBJECT-TYPE
   SYNTAX      INTEGER
               {
               unchanged (256)
               }
   MAX-ACCESS  read-write
   STATUS      current
   DESCRIPTION
      "Path: ethernet3.editConf.inboundBandwidth.action.cirAction.ethernet.cosDepth6

       Possibilities:
               unchanged   (256)"
   ::= {er1645v2Lan3MCIbwEntry 4064673792}

er1645v2Lan3MCIbwActCirActEthDei6 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth6

       Possibilities:
               unchanged   (255)
               clear   (0)
               set   (1)"
   ::= {er1645v2Lan3MCIbwEntry 4065984512}

er1645v2Lan3MCIbwActCirActEthCos7 OBJECT-TYPE
   SYNTAX      INTEGER
               {
               unchanged (256)
               }
   MAX-ACCESS  read-write
   STATUS      current
   DESCRIPTION
      "Path: ethernet3.editConf.inboundBandwidth.action.cirAction.ethernet.cosDepth7

       Possibilities:
               unchanged   (256)"
   ::= {er1645v2Lan3MCIbwEntry 4064739328}

er1645v2Lan3MCIbwActCirActEthDei7 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth7

       Possibilities:
               unchanged   (255)
               clear   (0)
               set   (1)"
   ::= {er1645v2Lan3MCIbwEntry 4066050048}

er1645v2Lan3MCIbwActCirActEthCos8 OBJECT-TYPE
   SYNTAX      INTEGER
               {
               unchanged (256)
               }
   MAX-ACCESS  read-write
   STATUS      current
   DESCRIPTION
      "Path: ethernet3.editConf.inboundBandwidth.action.cirAction.ethernet.cosDepth8

       Possibilities:
               unchanged   (256)"
   ::= {er1645v2Lan3MCIbwEntry 4064804864}

er1645v2Lan3MCIbwActCirActEthDei8 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth8

       Possibilities:
               unchanged   (255)
               clear   (0)
               set   (1)"
   ::= {er1645v2Lan3MCIbwEntry 4066115584}

er1645v2Lan3MCIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4064870400}

er1645v2Lan3MCIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4064935936}

er1645v2Lan3MCIbwActCirActEthDrpLev OBJECT-TYPE
   SYNTAX      INTEGER
               {
               unchanged (0)
               }
   MAX-ACCESS  read-write
   STATUS      current
   DESCRIPTION
      "Path: ethernet3.editConf.inboundBandwidth.action.cirAction.ethernet.dropLevel

       Possibilities:
               unchanged   (0)"
   ::= {er1645v2Lan3MCIbwEntry 4065001472}

er1645v2Lan3MCIbwActCirActEthDeFlag OBJECT-TYPE
   SYNTAX      INTEGER
               {
               unchanged (255),
               clear (0),
               set (1)
               }
   MAX-ACCESS  read-write
   STATUS      current
   DESCRIPTION
      "Path: ethernet3.editConf.inboundBandwidth.action.cirAction.ethernet.deFlag

       Possibilities:
               unchanged   (255)
               clear   (0)
               set   (1)"
   ::= {er1645v2Lan3MCIbwEntry 4065198080}

er1645v2Lan3MCIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4071161856}

er1645v2Lan3MCIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4071227392}

er1645v2Lan3MCIbwActCirActIpDrpLev OBJECT-TYPE
   SYNTAX      INTEGER
               {
               unchanged (0)
               }
   MAX-ACCESS  read-write
   STATUS      current
   DESCRIPTION
      "Path: ethernet3.editConf.inboundBandwidth.action.cirAction.ip.dropLevel

       Possibilities:
               unchanged   (0)"
   ::= {er1645v2Lan3MCIbwEntry 4071292928}

er1645v2Lan3MCIbwActCirActIpDeFlag OBJECT-TYPE
   SYNTAX      INTEGER
               {
               unchanged (255),
               clear (0),
               set (1)
               }
   MAX-ACCESS  read-write
   STATUS      current
   DESCRIPTION
      "Path: ethernet3.editConf.inboundBandwidth.action.cirAction.ip.deFlag

       Possibilities:
               unchanged   (255)
               clear   (0)
               set   (1)"
   ::= {er1645v2Lan3MCIbwEntry 4071489536}

er1645v2Lan3MCIbwActEirActNone OBJECT-TYPE
   SYNTAX      OCTET STRING
   MAX-ACCESS  read-write
   STATUS      current
   DESCRIPTION
      "Path: ethernet3.editConf.inboundBandwidth.action.eirAction.none"
   ::= {er1645v2Lan3MCIbwEntry 4095737856}

er1645v2Lan3MCIbwActEirActEthCos1 OBJECT-TYPE
   SYNTAX      INTEGER
               {
               unchanged (256)
               }
   MAX-ACCESS  read-write
   STATUS      current
   DESCRIPTION
      "Path: ethernet3.editConf.inboundBandwidth.action.eirAction.ethernet.cosDepth1

       Possibilities:
               unchanged   (256)"
   ::= {er1645v2Lan3MCIbwEntry 4097900544}

er1645v2Lan3MCIbwActEirActEthDei1 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth1

       Possibilities:
               unchanged   (255)
               clear   (0)
               set   (1)"
   ::= {er1645v2Lan3MCIbwEntry 4099211264}

er1645v2Lan3MCIbwActEirActEthCos2 OBJECT-TYPE
   SYNTAX      INTEGER
               {
               unchanged (256)
               }
   MAX-ACCESS  read-write
   STATUS      current
   DESCRIPTION
      "Path: ethernet3.editConf.inboundBandwidth.action.eirAction.ethernet.cosDepth2

       Possibilities:
               unchanged   (256)"
   ::= {er1645v2Lan3MCIbwEntry 4097966080}

er1645v2Lan3MCIbwActEirActEthDei2 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth2

       Possibilities:
               unchanged   (255)
               clear   (0)
               set   (1)"
   ::= {er1645v2Lan3MCIbwEntry 4099276800}

er1645v2Lan3MCIbwActEirActEthCos3 OBJECT-TYPE
   SYNTAX      INTEGER
               {
               unchanged (256)
               }
   MAX-ACCESS  read-write
   STATUS      current
   DESCRIPTION
      "Path: ethernet3.editConf.inboundBandwidth.action.eirAction.ethernet.cosDepth3

       Possibilities:
               unchanged   (256)"
   ::= {er1645v2Lan3MCIbwEntry 4098031616}

er1645v2Lan3MCIbwActEirActEthDei3 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth3

       Possibilities:
               unchanged   (255)
               clear   (0)
               set   (1)"
   ::= {er1645v2Lan3MCIbwEntry 4099342336}

er1645v2Lan3MCIbwActEirActEthCos4 OBJECT-TYPE
   SYNTAX      INTEGER
               {
               unchanged (256)
               }
   MAX-ACCESS  read-write
   STATUS      current
   DESCRIPTION
      "Path: ethernet3.editConf.inboundBandwidth.action.eirAction.ethernet.cosDepth4

       Possibilities:
               unchanged   (256)"
   ::= {er1645v2Lan3MCIbwEntry 4098097152}

er1645v2Lan3MCIbwActEirActEthDei4 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth4

       Possibilities:
               unchanged   (255)
               clear   (0)
               set   (1)"
   ::= {er1645v2Lan3MCIbwEntry 4099407872}

er1645v2Lan3MCIbwActEirActEthCos5 OBJECT-TYPE
   SYNTAX      INTEGER
               {
               unchanged (256)
               }
   MAX-ACCESS  read-write
   STATUS      current
   DESCRIPTION
      "Path: ethernet3.editConf.inboundBandwidth.action.eirAction.ethernet.cosDepth5

       Possibilities:
               unchanged   (256)"
   ::= {er1645v2Lan3MCIbwEntry 4098162688}

er1645v2Lan3MCIbwActEirActEthDei5 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth5

       Possibilities:
               unchanged   (255)
               clear   (0)
               set   (1)"
   ::= {er1645v2Lan3MCIbwEntry 4099473408}

er1645v2Lan3MCIbwActEirActEthCos6 OBJECT-TYPE
   SYNTAX      INTEGER
               {
               unchanged (256)
               }
   MAX-ACCESS  read-write
   STATUS      current
   DESCRIPTION
      "Path: ethernet3.editConf.inboundBandwidth.action.eirAction.ethernet.cosDepth6

       Possibilities:
               unchanged   (256)"
   ::= {er1645v2Lan3MCIbwEntry 4098228224}

er1645v2Lan3MCIbwActEirActEthDei6 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth6

       Possibilities:
               unchanged   (255)
               clear   (0)
               set   (1)"
   ::= {er1645v2Lan3MCIbwEntry 4099538944}

er1645v2Lan3MCIbwActEirActEthCos7 OBJECT-TYPE
   SYNTAX      INTEGER
               {
               unchanged (256)
               }
   MAX-ACCESS  read-write
   STATUS      current
   DESCRIPTION
      "Path: ethernet3.editConf.inboundBandwidth.action.eirAction.ethernet.cosDepth7

       Possibilities:
               unchanged   (256)"
   ::= {er1645v2Lan3MCIbwEntry 4098293760}

er1645v2Lan3MCIbwActEirActEthDei7 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth7

       Possibilities:
               unchanged   (255)
               clear   (0)
               set   (1)"
   ::= {er1645v2Lan3MCIbwEntry 4099604480}

er1645v2Lan3MCIbwActEirActEthCos8 OBJECT-TYPE
   SYNTAX      INTEGER
               {
               unchanged (256)
               }
   MAX-ACCESS  read-write
   STATUS      current
   DESCRIPTION
      "Path: ethernet3.editConf.inboundBandwidth.action.eirAction.ethernet.cosDepth8

       Possibilities:
               unchanged   (256)"
   ::= {er1645v2Lan3MCIbwEntry 4098359296}

er1645v2Lan3MCIbwActEirActEthDei8 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth8

       Possibilities:
               unchanged   (255)
               clear   (0)
               set   (1)"
   ::= {er1645v2Lan3MCIbwEntry 4099670016}

er1645v2Lan3MCIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4098424832}

er1645v2Lan3MCIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4098490368}

er1645v2Lan3MCIbwActEirActEthDrpLev OBJECT-TYPE
   SYNTAX      INTEGER
               {
               unchanged (0)
               }
   MAX-ACCESS  read-write
   STATUS      current
   DESCRIPTION
      "Path: ethernet3.editConf.inboundBandwidth.action.eirAction.ethernet.dropLevel

       Possibilities:
               unchanged   (0)"
   ::= {er1645v2Lan3MCIbwEntry 4098555904}

er1645v2Lan3MCIbwActEirActEthDeFlag OBJECT-TYPE
   SYNTAX      INTEGER
               {
               unchanged (255),
               clear (0),
               set (1)
               }
   MAX-ACCESS  read-write
   STATUS      current
   DESCRIPTION
      "Path: ethernet3.editConf.inboundBandwidth.action.eirAction.ethernet.deFlag

       Possibilities:
               unchanged   (255)
               clear   (0)
               set   (1)"
   ::= {er1645v2Lan3MCIbwEntry 4098752512}

er1645v2Lan3MCIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4104716288}

er1645v2Lan3MCIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4104781824}

er1645v2Lan3MCIbwActEirActIpDrpLev OBJECT-TYPE
   SYNTAX      INTEGER
               {
               unchanged (0)
               }
   MAX-ACCESS  read-write
   STATUS      current
   DESCRIPTION
      "Path: ethernet3.editConf.inboundBandwidth.action.eirAction.ip.dropLevel

       Possibilities:
               unchanged   (0)"
   ::= {er1645v2Lan3MCIbwEntry 4104847360}

er1645v2Lan3MCIbwActEirActIpDeFlag OBJECT-TYPE
   SYNTAX      INTEGER
               {
               unchanged (255),
               clear (0),
               set (1)
               }
   MAX-ACCESS  read-write
   STATUS      current
   DESCRIPTION
      "Path: ethernet3.editConf.inboundBandwidth.action.eirAction.ip.deFlag

       Possibilities:
               unchanged   (255)
               clear   (0)
               set   (1)"
   ::= {er1645v2Lan3MCIbwEntry 4105043968}

er1645v2Lan3MCIbwActViolActNone OBJECT-TYPE
   SYNTAX      OCTET STRING
   MAX-ACCESS  read-write
   STATUS      current
   DESCRIPTION
      "Path: ethernet3.editConf.inboundBandwidth.action.violateAction.none"
   ::= {er1645v2Lan3MCIbwEntry 4129292288}

er1645v2Lan3MCIbwActViolActDrop OBJECT-TYPE
   SYNTAX      OCTET STRING
   MAX-ACCESS  read-write
   STATUS      current
   DESCRIPTION
      "Path: ethernet3.editConf.inboundBandwidth.action.violateAction.drop"
   ::= {er1645v2Lan3MCIbwEntry 4133486592}

er1645v2Lan3MCIbwActViolActEthCos1 OBJECT-TYPE
   SYNTAX      INTEGER
               {
               unchanged (256)
               }
   MAX-ACCESS  read-write
   STATUS      current
   DESCRIPTION
      "Path: ethernet3.editConf.inboundBandwidth.action.violateAction.ethernet.cosDepth1

       Possibilities:
               unchanged   (256)"
   ::= {er1645v2Lan3MCIbwEntry 4131454976}

er1645v2Lan3MCIbwActViolActEthDei1 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth1

       Possibilities:
               unchanged   (255)
               clear   (0)
               set   (1)"
   ::= {er1645v2Lan3MCIbwEntry 4132765696}

er1645v2Lan3MCIbwActViolActEthCos2 OBJECT-TYPE
   SYNTAX      INTEGER
               {
               unchanged (256)
               }
   MAX-ACCESS  read-write
   STATUS      current
   DESCRIPTION
      "Path: ethernet3.editConf.inboundBandwidth.action.violateAction.ethernet.cosDepth2

       Possibilities:
               unchanged   (256)"
   ::= {er1645v2Lan3MCIbwEntry 4131520512}

er1645v2Lan3MCIbwActViolActEthDei2 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth2

       Possibilities:
               unchanged   (255)
               clear   (0)
               set   (1)"
   ::= {er1645v2Lan3MCIbwEntry 4132831232}

er1645v2Lan3MCIbwActViolActEthCos3 OBJECT-TYPE
   SYNTAX      INTEGER
               {
               unchanged (256)
               }
   MAX-ACCESS  read-write
   STATUS      current
   DESCRIPTION
      "Path: ethernet3.editConf.inboundBandwidth.action.violateAction.ethernet.cosDepth3

       Possibilities:
               unchanged   (256)"
   ::= {er1645v2Lan3MCIbwEntry 4131586048}

er1645v2Lan3MCIbwActViolActEthDei3 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth3

       Possibilities:
               unchanged   (255)
               clear   (0)
               set   (1)"
   ::= {er1645v2Lan3MCIbwEntry 4132896768}

er1645v2Lan3MCIbwActViolActEthCos4 OBJECT-TYPE
   SYNTAX      INTEGER
               {
               unchanged (256)
               }
   MAX-ACCESS  read-write
   STATUS      current
   DESCRIPTION
      "Path: ethernet3.editConf.inboundBandwidth.action.violateAction.ethernet.cosDepth4

       Possibilities:
               unchanged   (256)"
   ::= {er1645v2Lan3MCIbwEntry 4131651584}

er1645v2Lan3MCIbwActViolActEthDei4 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth4

       Possibilities:
               unchanged   (255)
               clear   (0)
               set   (1)"
   ::= {er1645v2Lan3MCIbwEntry 4132962304}

er1645v2Lan3MCIbwActViolActEthCos5 OBJECT-TYPE
   SYNTAX      INTEGER
               {
               unchanged (256)
               }
   MAX-ACCESS  read-write
   STATUS      current
   DESCRIPTION
      "Path: ethernet3.editConf.inboundBandwidth.action.violateAction.ethernet.cosDepth5

       Possibilities:
               unchanged   (256)"
   ::= {er1645v2Lan3MCIbwEntry 4131717120}

er1645v2Lan3MCIbwActViolActEthDei5 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth5

       Possibilities:
               unchanged   (255)
               clear   (0)
               set   (1)"
   ::= {er1645v2Lan3MCIbwEntry 4133027840}

er1645v2Lan3MCIbwActViolActEthCos6 OBJECT-TYPE
   SYNTAX      INTEGER
               {
               unchanged (256)
               }
   MAX-ACCESS  read-write
   STATUS      current
   DESCRIPTION
      "Path: ethernet3.editConf.inboundBandwidth.action.violateAction.ethernet.cosDepth6

       Possibilities:
               unchanged   (256)"
   ::= {er1645v2Lan3MCIbwEntry 4131782656}

er1645v2Lan3MCIbwActViolActEthDei6 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth6

       Possibilities:
               unchanged   (255)
               clear   (0)
               set   (1)"
   ::= {er1645v2Lan3MCIbwEntry 4133093376}

er1645v2Lan3MCIbwActViolActEthCos7 OBJECT-TYPE
   SYNTAX      INTEGER
               {
               unchanged (256)
               }
   MAX-ACCESS  read-write
   STATUS      current
   DESCRIPTION
      "Path: ethernet3.editConf.inboundBandwidth.action.violateAction.ethernet.cosDepth7

       Possibilities:
               unchanged   (256)"
   ::= {er1645v2Lan3MCIbwEntry 4131848192}

er1645v2Lan3MCIbwActViolActEthDei7 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth7

       Possibilities:
               unchanged   (255)
               clear   (0)
               set   (1)"
   ::= {er1645v2Lan3MCIbwEntry 4133158912}

er1645v2Lan3MCIbwActViolActEthCos8 OBJECT-TYPE
   SYNTAX      INTEGER
               {
               unchanged (256)
               }
   MAX-ACCESS  read-write
   STATUS      current
   DESCRIPTION
      "Path: ethernet3.editConf.inboundBandwidth.action.violateAction.ethernet.cosDepth8

       Possibilities:
               unchanged   (256)"
   ::= {er1645v2Lan3MCIbwEntry 4131913728}

er1645v2Lan3MCIbwActViolActEthDei8 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth8

       Possibilities:
               unchanged   (255)
               clear   (0)
               set   (1)"
   ::= {er1645v2Lan3MCIbwEntry 4133224448}

er1645v2Lan3MCIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4131979264}

er1645v2Lan3MCIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4132044800}

er1645v2Lan3MCIbwActViolActEthDrpLev OBJECT-TYPE
   SYNTAX      INTEGER
               {
               unchanged (0)
               }
   MAX-ACCESS  read-write
   STATUS      current
   DESCRIPTION
      "Path: ethernet3.editConf.inboundBandwidth.action.violateAction.ethernet.dropLevel

       Possibilities:
               unchanged   (0)"
   ::= {er1645v2Lan3MCIbwEntry 4132110336}

er1645v2Lan3MCIbwActViolActEthDeFlag OBJECT-TYPE
   SYNTAX      INTEGER
               {
               unchanged (255),
               clear (0),
               set (1)
               }
   MAX-ACCESS  read-write
   STATUS      current
   DESCRIPTION
      "Path: ethernet3.editConf.inboundBandwidth.action.violateAction.ethernet.deFlag

       Possibilities:
               unchanged   (255)
               clear   (0)
               set   (1)"
   ::= {er1645v2Lan3MCIbwEntry 4132306944}

er1645v2Lan3MCIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCIbwEntry 4138270720}

er1645v2Lan3MCIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCIbwEntry 4138336256}

er1645v2Lan3MCIbwActViolActIpDrpLev OBJECT-TYPE
   SYNTAX      INTEGER
               {
               unchanged (0)
               }
   MAX-ACCESS  read-write
   STATUS      current
   DESCRIPTION
      "Path: ethernet3.editConf.inboundBandwidth.action.violateAction.ip.dropLevel

       Possibilities:
               unchanged   (0)"
   ::= {er1645v2Lan3MCIbwEntry 4138401792}

er1645v2Lan3MCIbwActViolActIpDeFlag OBJECT-TYPE
   SYNTAX      INTEGER
               {
               unchanged (255),
               clear (0),
               set (1)
               }
   MAX-ACCESS  read-write
   STATUS      current
   DESCRIPTION
      "Path: ethernet3.editConf.inboundBandwidth.action.violateAction.ip.deFlag

       Possibilities:
               unchanged   (255)
               clear   (0)
               set   (1)"
   ::= {er1645v2Lan3MCIbwEntry 4138598400}

er1645v2Lan3MCIbwSubInterfacesExcluded OBJECT-TYPE
   SYNTAX      INTEGER
               {
               s (1)
               }
   MAX-ACCESS  read-write
   STATUS      current
   DESCRIPTION
      "Path: ethernet3.editConf.inboundBandwidth.subInterfaces.excluded

       Possibilities:
                  (1)"
   ::= {er1645v2Lan3MCIbwEntry 2416967680}

er1645v2Lan3MCIbwSubInterfacesIncludedInAccessList OBJECT-TYPE
   SYNTAX      DisplayString
   MAX-ACCESS  read-write
   STATUS      current
   DESCRIPTION
      "Path: ethernet3.editConf.inboundBandwidth.subInterfaces.included.inAccessList"
   ::= {er1645v2Lan3MCIbwEntry 2418020352}


er1645v2Lan3MCPriorityPolicy OBJECT-TYPE
   SYNTAX      DisplayString
   MAX-ACCESS  read-write
   STATUS      current
   DESCRIPTION
      "Path: ethernet3.editConf.priorityPolicy
       Info: Preferred Policy"
   ::= {er1645v2Lan3MC 39}


er1645v2Lan3MCMru OBJECT-TYPE
   SYNTAX      Integer32
   MAX-ACCESS  read-write
   STATUS      current
   DESCRIPTION
      "Path: ethernet3.editConf.mru"
   ::= {er1645v2Lan3MC 43}


er1645v2Lan3MCDelayOptimisation OBJECT-TYPE
   SYNTAX      INTEGER
               {
               disabled (0),
               enabled (1)
               }
   MAX-ACCESS  read-write
   STATUS      current
   DESCRIPTION
      "Path: ethernet3.editConf.delayOptimisation
       Info: optimise delay

       Possibilities:
               disabled   (0)
               enabled   (1)"
   ::= {er1645v2Lan3MC 80}


er1645v2Lan3MCAlarmMask OBJECT-TYPE
   SYNTAX      Integer32
   MAX-ACCESS  read-write
   STATUS      current
   DESCRIPTION
      "Path: ethernet3.editConf.alarmMask
       Info: ifAlarmMask

       Bit meanings:
               bit 0 = linkDown,
               bit 9 = pppoEDown"
   ::= {er1645v2Lan3MC 135}


er1645v2Lan3MCAlarmLev OBJECT IDENTIFIER ::= {er1645v2Lan3MC 170}

er1645v2Lan3MCAlarmLevSSC OBJECT IDENTIFIER ::= {er1645v2Lan3MCAlarmLev 1}

er1645v2Lan3MCAlarmLevEntry OBJECT IDENTIFIER ::= {er1645v2Lan3MCAlarmLevSSC 1}

er1645v2Lan3MCAlarmLevLinkDown OBJECT-TYPE
   SYNTAX      Integer32
   MAX-ACCESS  read-write
   STATUS      current
   DESCRIPTION
      "Path: ethernet3.editConf.alarmLevel.linkDown"
   ::= {er1645v2Lan3MCAlarmLevEntry 16777216}

er1645v2Lan3MCAlarmLevPppoEDown OBJECT-TYPE
   SYNTAX      Integer32
   MAX-ACCESS  read-write
   STATUS      current
   DESCRIPTION
      "Path: ethernet3.editConf.alarmLevel.pppoEDown"
   ::= {er1645v2Lan3MCAlarmLevEntry 167772160}


er1645v2Lan3MCArp OBJECT IDENTIFIER ::= {er1645v2Lan3MC 19}

er1645v2Lan3MCArpSSC OBJECT IDENTIFIER ::= {er1645v2Lan3MCArp 1}

er1645v2Lan3MCArpEntry OBJECT IDENTIFIER ::= {er1645v2Lan3MCArpSSC 1}

er1645v2Lan3MCArpTimeOut OBJECT-TYPE
   SYNTAX      TimeTicks
   MAX-ACCESS  read-write
   STATUS      current
   DESCRIPTION
      "Path: ethernet3.editConf.arp.timeOut

       Time in centi-second."
   ::= {er1645v2Lan3MCArpEntry 201326592}

er1645v2Lan3MCArpProxyArp OBJECT-TYPE
   SYNTAX      INTEGER
               {
               disabled (0),
               enabled (1)
               }
   MAX-ACCESS  read-write
   STATUS      current
   DESCRIPTION
      "Path: ethernet3.editConf.arp.proxyArp

       Possibilities:
               disabled   (0)
               enabled   (1)"
   ::= {er1645v2Lan3MCArpEntry 838860800}

er1645v2Lan3MCArpStaticArp OBJECT-TYPE
   SYNTAX      SEQUENCE OF Er1645v2Lan3MCArpStaticArpEntry
   MAX-ACCESS  not-accessible
   STATUS      current
   DESCRIPTION
      ""
   ::= {er1645v2Lan3MCArp 50331648}

er1645v2Lan3MCArpStaticArpEntry OBJECT-TYPE
   SYNTAX      Er1645v2Lan3MCArpStaticArpEntry
   MAX-ACCESS  not-accessible
   STATUS      current
   DESCRIPTION
      ""
   INDEX      { er1645v2Lan3MCArpStaticArpTableIx }
   ::= {er1645v2Lan3MCArpStaticArp 1}

Er1645v2Lan3MCArpStaticArpEntry ::=
   SEQUENCE
      {
      er1645v2Lan3MCArpStaticArpActions
         VariableLengthTableActions,
      er1645v2Lan3MCArpStaticArpTableIx
         TableIndex,
      er1645v2Lan3MCArpStaticArpMacAddress
         OCTET STRING,
      er1645v2Lan3MCArpStaticArpIpAddress
         IpAddress
      }

er1645v2Lan3MCArpStaticArpActions OBJECT-TYPE
   SYNTAX      VariableLengthTableActions
   MAX-ACCESS  read-write
   STATUS      current
   DESCRIPTION
      "By way of this field, some manipulations
       on this table may be performed."
   ::= {er1645v2Lan3MCArpStaticArpEntry 2}

er1645v2Lan3MCArpStaticArpTableIx OBJECT-TYPE
   SYNTAX      TableIndex
   MAX-ACCESS  not-accessible
   STATUS      current
   DESCRIPTION
      ""
   ::= {er1645v2Lan3MCArpStaticArpEntry 11}

er1645v2Lan3MCArpStaticArpMacAddress OBJECT-TYPE
   SYNTAX      OCTET STRING
   MAX-ACCESS  read-write
   STATUS      current
   DESCRIPTION
      "Path: ethernet3.editConf.arp.staticArp.macAddress

       MAC address."
   ::= {er1645v2Lan3MCArpStaticArpEntry 16777216}

er1645v2Lan3MCArpStaticArpIpAddress OBJECT-TYPE
   SYNTAX      IpAddress
   MAX-ACCESS  read-write
   STATUS      current
   DESCRIPTION
      "Path: ethernet3.editConf.arp.staticArp.ipAddress"
   ::= {er1645v2Lan3MCArpStaticArpEntry 33554432}


er1645v2Lan3MCBrC OBJECT IDENTIFIER ::= {er1645v2Lan3MC 27}

er1645v2Lan3MCBrCSSC OBJECT IDENTIFIER ::= {er1645v2Lan3MCBrC 1}

er1645v2Lan3MCBrCEntry OBJECT IDENTIFIER ::= {er1645v2Lan3MCBrCSSC 1}

er1645v2Lan3MCBrCAccessList OBJECT-TYPE
   SYNTAX      DisplayString
   MAX-ACCESS  read-write
   STATUS      current
   DESCRIPTION
      "Path: ethernet3.editConf.bridging.accessList"
   ::= {er1645v2Lan3MCBrCEntry 83886080}

er1645v2Lan3MCBrCInAccessList OBJECT-TYPE
   SYNTAX      DisplayString
   MAX-ACCESS  read-write
   STATUS      current
   DESCRIPTION
      "Path: ethernet3.editConf.bridging.inAccessList"
   ::= {er1645v2Lan3MCBrCEntry 251658240}

er1645v2Lan3MCBrCTp OBJECT-TYPE
   SYNTAX      DisplayString
   MAX-ACCESS  read-write
   STATUS      current
   DESCRIPTION
      "Path: ethernet3.editConf.bridging.trafficPolicy"
   ::= {er1645v2Lan3MCBrCEntry 100663296}

er1645v2Lan3MCBrCBridgeGroup OBJECT-TYPE
   SYNTAX      DisplayString
   MAX-ACCESS  read-write
   STATUS      current
   DESCRIPTION
      "Path: ethernet3.editConf.bridging.bridgeGroup"
   ::= {er1645v2Lan3MCBrCEntry 117440512}

er1645v2Lan3MCBrCLimBC OBJECT-TYPE
   SYNTAX      INTEGER
               {
               disabled (0),
               enabled (1)
               }
   MAX-ACCESS  read-write
   STATUS      current
   DESCRIPTION
      "Path: ethernet3.editConf.bridging.limitBroadcasts

       Possibilities:
               disabled   (0)
               enabled   (1)"
   ::= {er1645v2Lan3MCBrCEntry 134217728}

er1645v2Lan3MCBrCPrivateMode OBJECT-TYPE
   SYNTAX      INTEGER
               {
               disabled (0),
               enabled (1)
               }
   MAX-ACCESS  read-write
   STATUS      current
   DESCRIPTION
      "Path: ethernet3.editConf.bridging.privateMode

       Possibilities:
               disabled   (0)
               enabled   (1)"
   ::= {er1645v2Lan3MCBrCEntry 419430400}

er1645v2Lan3MCBrCLearning OBJECT-TYPE
   SYNTAX      INTEGER
               {
               disabled (0),
               enabled (1)
               }
   MAX-ACCESS  read-write
   STATUS      current
   DESCRIPTION
      "Path: ethernet3.editConf.bridging.learning

       Possibilities:
               disabled   (0)
               enabled   (1)"
   ::= {er1645v2Lan3MCBrCEntry 201326592}

er1645v2Lan3MCBrCMaxCacheSize OBJECT-TYPE
   SYNTAX      INTEGER
               {
               unlimited (0)
               }
   MAX-ACCESS  read-write
   STATUS      current
   DESCRIPTION
      "Path: ethernet3.editConf.bridging.maxCacheSize

       Possibilities:
               unlimited   (0)"
   ::= {er1645v2Lan3MCBrCEntry 218103808}

er1645v2Lan3MCBrCRelearnDropOnRelearn OBJECT-TYPE
   SYNTAX      INTEGER
               {
               disabled (0),
               enabled (1)
               }
   MAX-ACCESS  read-write
   STATUS      current
   DESCRIPTION
      "Path: ethernet3.editConf.bridging.relearn.dropOnRelearn

       Possibilities:
               disabled   (0)
               enabled   (1)"
   ::= {er1645v2Lan3MCBrCEntry 234946560}

er1645v2Lan3MCBrCRelearnShutdownThreshold OBJECT-TYPE
   SYNTAX      Integer32
   MAX-ACCESS  read-write
   STATUS      current
   DESCRIPTION
      "Path: ethernet3.editConf.bridging.relearn.shutdownThreshold"
   ::= {er1645v2Lan3MCBrCEntry 235012096}

er1645v2Lan3MCBrCRelearnShutdownTime OBJECT-TYPE
   SYNTAX      TimeTicks
   MAX-ACCESS  read-write
   STATUS      current
   DESCRIPTION
      "Path: ethernet3.editConf.bridging.relearn.shutdownTime

       Time in centi-second."
   ::= {er1645v2Lan3MCBrCEntry 235077632}

er1645v2Lan3MCBrCRelearnLoopDetection OBJECT-TYPE
   SYNTAX      INTEGER
               {
               disabled (0),
               passive (1),
               active (2)
               }
   MAX-ACCESS  read-write
   STATUS      current
   DESCRIPTION
      "Path: ethernet3.editConf.bridging.relearn.loopDetection

       Possibilities:
               disabled   (0)
               passive   (1)
               active   (2)"
   ::= {er1645v2Lan3MCBrCEntry 235143168}

er1645v2Lan3MCBrCRelearnLoopDetectionInterval OBJECT-TYPE
   SYNTAX      TimeTicks
   MAX-ACCESS  read-write
   STATUS      current
   DESCRIPTION
      "Path: ethernet3.editConf.bridging.relearn.loopDetectionInterval

       Time in centi-second."
   ::= {er1645v2Lan3MCBrCEntry 235208704}

er1645v2Lan3MCBrCVlanMemberShip OBJECT-TYPE
   SYNTAX      INTEGER
               {
               all (0),
               none (1),
               grouped (2)
               }
   MAX-ACCESS  read-write
   STATUS      current
   DESCRIPTION
      "Path: ethernet3.editConf.bridging.vlanMemberShip

       Possibilities:
               all   (0)
               none   (1)
               grouped   (2)"
   ::= {er1645v2Lan3MCBrCEntry 318767104}

er1645v2Lan3MCBrCDot1adType OBJECT-TYPE
   SYNTAX      INTEGER
               {
               slOPTg (0),
               cPort (4),
               sPort (1),
               nni (2)
               }
   MAX-ACCESS  read-write
   STATUS      current
   DESCRIPTION
      "Path: ethernet3.editConf.bridging.dot1ad.type

       Possibilities:
               <OPT>   (0)
               cPort   (4)
               sPort   (1)
               nni   (2)"
   ::= {er1645v2Lan3MCBrCEntry 503382016}

er1645v2Lan3MCBrCPriority OBJECT-TYPE
   SYNTAX      Integer32
   MAX-ACCESS  read-write
   STATUS      current
   DESCRIPTION
      "Path: ethernet3.editConf.bridging.priority"
   ::= {er1645v2Lan3MCBrCEntry 33554432}

er1645v2Lan3MCBrCPathCost OBJECT-TYPE
   SYNTAX      Integer32
   MAX-ACCESS  read-write
   STATUS      current
   DESCRIPTION
      "Path: ethernet3.editConf.bridging.pathCost"
   ::= {er1645v2Lan3MCBrCEntry 50331648}

er1645v2Lan3MCBrCInternalPathCost OBJECT-TYPE
   SYNTAX      Integer32
   MAX-ACCESS  read-write
   STATUS      current
   DESCRIPTION
      "Path: ethernet3.editConf.bridging.internalPathCost"
   ::= {er1645v2Lan3MCBrCEntry 301989888}

er1645v2Lan3MCBrCTCD OBJECT-TYPE
   SYNTAX      INTEGER
               {
               disabled (0),
               enabled (1)
               }
   MAX-ACCESS  read-write
   STATUS      current
   DESCRIPTION
      "Path: ethernet3.editConf.bridging.topologyChangeDetection

       Possibilities:
               disabled   (0)
               enabled   (1)"
   ::= {er1645v2Lan3MCBrCEntry 67108864}

er1645v2Lan3MCBrCRestrictedRole OBJECT-TYPE
   SYNTAX      INTEGER
               {
               disabled (0),
               enabled (1)
               }
   MAX-ACCESS  read-write
   STATUS      current
   DESCRIPTION
      "Path: ethernet3.editConf.bridging.restrictedRole

       Possibilities:
               disabled   (0)
               enabled   (1)"
   ::= {er1645v2Lan3MCBrCEntry 335544320}

er1645v2Lan3MCBrCAdminEdge OBJECT-TYPE
   SYNTAX      INTEGER
               {
               disabled (0),
               enabled (1)
               }
   MAX-ACCESS  read-write
   STATUS      current
   DESCRIPTION
      "Path: ethernet3.editConf.bridging.adminEdge

       Possibilities:
               disabled   (0)
               enabled   (1)"
   ::= {er1645v2Lan3MCBrCEntry 268435456}

er1645v2Lan3MCBrCMgmtInline OBJECT-TYPE
   SYNTAX      INTEGER
               {
               disabled (0),
               enabled (1)
               }
   MAX-ACCESS  read-write
   STATUS      current
   DESCRIPTION
      "Path: ethernet3.editConf.bridging.mgmtInline

       Possibilities:
               disabled   (0)
               enabled   (1)"
   ::= {er1645v2Lan3MCBrCEntry 369098752}

er1645v2Lan3MCBrCL2ptMode OBJECT-TYPE
   SYNTAX      INTEGER
               {
               disabled (0),
               enabled (1)
               }
   MAX-ACCESS  read-write
   STATUS      current
   DESCRIPTION
      "Path: ethernet3.editConf.bridging.l2ProtTunnel.mode

       Possibilities:
               disabled   (0)
               enabled   (1)"
   ::= {er1645v2Lan3MCBrCEntry 403701760}

er1645v2Lan3MCBrCL2ptProtocols OBJECT-TYPE
   SYNTAX      Integer32
   MAX-ACCESS  read-write
   STATUS      current
   DESCRIPTION
      "Path: ethernet3.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan3MCBrCEntry 404750336}

er1645v2Lan3MCBrCL2ptDestMac OBJECT-TYPE
   SYNTAX      OCTET STRING
   MAX-ACCESS  read-write
   STATUS      current
   DESCRIPTION
      "Path: ethernet3.editConf.bridging.l2ProtTunnel.destinationMac

       MAC address."
   ::= {er1645v2Lan3MCBrCEntry 405798912}

er1645v2Lan3MCBrCL2ptCos OBJECT-TYPE
   SYNTAX      INTEGER
               {
               unchanged (255)
               }
   MAX-ACCESS  read-write
   STATUS      current
   DESCRIPTION
      "Path: ethernet3.editConf.bridging.l2ProtTunnel.cos

       Possibilities:
               unchanged   (255)"
   ::= {er1645v2Lan3MCBrCEntry 406847488}

er1645v2Lan3MCBrCL2ptDropThrStp OBJECT-TYPE
   SYNTAX      INTEGER
               {
               unlimited (0)
               }
   UNITS       "packets/sec"
   MAX-ACCESS  read-write
   STATUS      current
   DESCRIPTION
      "Path: ethernet3.editConf.bridging.l2ProtTunnel.dropThresholds.stp

       unit name = packets/sec

       Possibilities:
               unlimited   (0)"
   ::= {er1645v2Lan3MCBrCEntry 407900160}

er1645v2Lan3MCBrCL2ptDropThrLldp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lldp

       unit name = packets/sec

       Possibilities:
               unlimited   (0)"
   ::= {er1645v2Lan3MCBrCEntry 407904256}

er1645v2Lan3MCBrCL2ptDropThrOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.oam

       unit name = packets/sec

       Possibilities:
               unlimited   (0)"
   ::= {er1645v2Lan3MCBrCEntry 407908352}

er1645v2Lan3MCBrCL2ptDropThrCdp OBJECT-TYPE
   SYNTAX      INTEGER
               {
               unlimited (0)
               }
   UNITS       "packets/sec"
   MAX-ACCESS  read-write
   STATUS      current
   DESCRIPTION
      "Path: ethernet3.editConf.bridging.l2ProtTunnel.dropThresholds.cdp

       unit name = packets/sec

       Possibilities:
               unlimited   (0)"
   ::= {er1645v2Lan3MCBrCEntry 407912448}

er1645v2Lan3MCBrCL2ptDropThrVtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.vtp

       unit name = packets/sec

       Possibilities:
               unlimited   (0)"
   ::= {er1645v2Lan3MCBrCEntry 407916544}

er1645v2Lan3MCBrCL2ptDropThrLacp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lacp

       unit name = packets/sec

       Possibilities:
               unlimited   (0)"
   ::= {er1645v2Lan3MCBrCEntry 407920640}

er1645v2Lan3MCBrCL2ptDropThrEfmOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.efmOam

       unit name = packets/sec

       Possibilities:
               unlimited   (0)"
   ::= {er1645v2Lan3MCBrCEntry 407924736}

er1645v2Lan3MCBrCL2ptDropThrPvst OBJECT-TYPE
   SYNTAX      INTEGER
               {
               unlimited (0)
               }
   UNITS       "packets/sec"
   MAX-ACCESS  read-write
   STATUS      current
   DESCRIPTION
      "Path: ethernet3.editConf.bridging.l2ProtTunnel.dropThresholds.pvst

       unit name = packets/sec

       Possibilities:
               unlimited   (0)"
   ::= {er1645v2Lan3MCBrCEntry 407928832}

er1645v2Lan3MCBrCL2ptDropThrMmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mmrp

       unit name = packets/sec

       Possibilities:
               unlimited   (0)"
   ::= {er1645v2Lan3MCBrCEntry 407932928}

er1645v2Lan3MCBrCL2ptDropThrMvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mvrp

       unit name = packets/sec

       Possibilities:
               unlimited   (0)"
   ::= {er1645v2Lan3MCBrCEntry 407937024}

er1645v2Lan3MCBrCL2ptDropThrGvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gvrp

       unit name = packets/sec

       Possibilities:
               unlimited   (0)"
   ::= {er1645v2Lan3MCBrCEntry 407941120}

er1645v2Lan3MCBrCL2ptDropThrGmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gmrp

       unit name = packets/sec

       Possibilities:
               unlimited   (0)"
   ::= {er1645v2Lan3MCBrCEntry 407945216}

er1645v2Lan3MCBrCL2ptDropThrDtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.dtp

       unit name = packets/sec

       Possibilities:
               unlimited   (0)"
   ::= {er1645v2Lan3MCBrCEntry 407949312}

er1645v2Lan3MCBrCL2ptDropThrPagp OBJECT-TYPE
   SYNTAX      INTEGER
               {
               unlimited (0)
               }
   UNITS       "packets/sec"
   MAX-ACCESS  read-write
   STATUS      current
   DESCRIPTION
      "Path: ethernet3.editConf.bridging.l2ProtTunnel.dropThresholds.pagp

       unit name = packets/sec

       Possibilities:
               unlimited   (0)"
   ::= {er1645v2Lan3MCBrCEntry 407953408}

er1645v2Lan3MCBrCL2ptDropThrUdld OBJECT-TYPE
   SYNTAX      INTEGER
               {
               unlimited (0)
               }
   UNITS       "packets/sec"
   MAX-ACCESS  read-write
   STATUS      current
   DESCRIPTION
      "Path: ethernet3.editConf.bridging.l2ProtTunnel.dropThresholds.udld

       unit name = packets/sec

       Possibilities:
               unlimited   (0)"
   ::= {er1645v2Lan3MCBrCEntry 407957504}


er1645v2Lan3MCVlanTagging OBJECT IDENTIFIER ::= {er1645v2Lan3MC 14}

er1645v2Lan3MCVlanTaggingSSC OBJECT IDENTIFIER ::= {er1645v2Lan3MCVlanTagging 1}

er1645v2Lan3MCVlanTaggingEntry OBJECT IDENTIFIER ::= {er1645v2Lan3MCVlanTaggingSSC 1}

er1645v2Lan3MCVlanTaggingUntaggedAction OBJECT-TYPE
   SYNTAX      INTEGER
               {
               discard (0),
               accept (1),
               tag (2)
               }
   MAX-ACCESS  read-write
   STATUS      current
   DESCRIPTION
      "Path: ethernet3.editConf.vlanTagging.untagged.action

       Possibilities:
               discard   (0)
               accept   (1)
               tag   (2)"
   ::= {er1645v2Lan3MCVlanTaggingEntry 671088640}

er1645v2Lan3MCVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.untagged.tagInfo.tpid

       Possibilities:
               dot1Q   (33024)
               dot1ad   (34984)
               0x9100   (37120)
               0x9200   (37376)
               0x9300   (37632)"
   ::= {er1645v2Lan3MCVlanTaggingEntry 746586112}

er1645v2Lan3MCVlanTaggingUntaggedTagInfoVid OBJECT-TYPE
   SYNTAX      Integer32
   MAX-ACCESS  read-write
   STATUS      current
   DESCRIPTION
      "Path: ethernet3.editConf.vlanTagging.untagged.tagInfo.vid"
   ::= {er1645v2Lan3MCVlanTaggingEntry 754974720}

er1645v2Lan3MCVlanTaggingUnknownVlansAction OBJECT-TYPE
   SYNTAX      INTEGER
               {
               discard (0),
               accept (1),
               tag (2)
               }
   MAX-ACCESS  read-write
   STATUS      current
   DESCRIPTION
      "Path: ethernet3.editConf.vlanTagging.unknownVlans.action

       Possibilities:
               discard   (0)
               accept   (1)
               tag   (2)"
   ::= {er1645v2Lan3MCVlanTaggingEntry 1744830464}

er1645v2Lan3MCVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.unknownVlans.tagInfo.tpid

       Possibilities:
               dot1Q   (33024)
               dot1ad   (34984)
               0x9100   (37120)
               0x9200   (37376)
               0x9300   (37632)"
   ::= {er1645v2Lan3MCVlanTaggingEntry 1820327936}

er1645v2Lan3MCVlanTaggingUnknownVlansTagInfoVid OBJECT-TYPE
   SYNTAX      Integer32
   MAX-ACCESS  read-write
   STATUS      current
   DESCRIPTION
      "Path: ethernet3.editConf.vlanTagging.unknownVlans.tagInfo.vid"
   ::= {er1645v2Lan3MCVlanTaggingEntry 1828716544}

er1645v2Lan3MCVlanTaggingVlans OBJECT-TYPE
   SYNTAX      SEQUENCE OF Er1645v2Lan3MCVlanTaggingVlansEntry
   MAX-ACCESS  not-accessible
   STATUS      current
   DESCRIPTION
      ""
   ::= {er1645v2Lan3MCVlanTagging 1073741824}

er1645v2Lan3MCVlanTaggingVlansEntry OBJECT-TYPE
   SYNTAX      Er1645v2Lan3MCVlanTaggingVlansEntry
   MAX-ACCESS  not-accessible
   STATUS      current
   DESCRIPTION
      ""
   INDEX      { er1645v2Lan3MCVlanTaggingVlansTableIx }
   ::= {er1645v2Lan3MCVlanTaggingVlans 1}

Er1645v2Lan3MCVlanTaggingVlansEntry ::=
   SEQUENCE
      {
      er1645v2Lan3MCVlanTaggingVlansActions
         VariableLengthTableActions,
      er1645v2Lan3MCVlanTaggingVlansTableIx
         TableIndex,
      er1645v2Lan3MCVlanTaggingVlansVid
         Integer32,
      er1645v2Lan3MCVlanTaggingVlansEndVid
         Integer32,
      er1645v2Lan3MCVlanTaggingVlansAction
         INTEGER,
      er1645v2Lan3MCVlanTaggingVlansTagInfoTpid
         INTEGER,
      er1645v2Lan3MCVlanTaggingVlansTagInfoVid
         Integer32
      }

er1645v2Lan3MCVlanTaggingVlansActions OBJECT-TYPE
   SYNTAX      VariableLengthTableActions
   MAX-ACCESS  read-write
   STATUS      current
   DESCRIPTION
      "By way of this field, some manipulations
       on this table may be performed."
   ::= {er1645v2Lan3MCVlanTaggingVlansEntry 2}

er1645v2Lan3MCVlanTaggingVlansTableIx OBJECT-TYPE
   SYNTAX      TableIndex
   MAX-ACCESS  not-accessible
   STATUS      current
   DESCRIPTION
      ""
   ::= {er1645v2Lan3MCVlanTaggingVlansEntry 11}

er1645v2Lan3MCVlanTaggingVlansVid OBJECT-TYPE
   SYNTAX      Integer32
   MAX-ACCESS  read-write
   STATUS      current
   DESCRIPTION
      "Path: ethernet3.editConf.vlanTagging.vlans.vid"
   ::= {er1645v2Lan3MCVlanTaggingVlansEntry 536870912}

er1645v2Lan3MCVlanTaggingVlansEndVid OBJECT-TYPE
   SYNTAX      Integer32
   MAX-ACCESS  read-write
   STATUS      current
   DESCRIPTION
      "Path: ethernet3.editConf.vlanTagging.vlans.endVid"
   ::= {er1645v2Lan3MCVlanTaggingVlansEntry 2147483648}

er1645v2Lan3MCVlanTaggingVlansAction OBJECT-TYPE
   SYNTAX      INTEGER
               {
               discard (0),
               accept (1),
               tag (2)
               }
   MAX-ACCESS  read-write
   STATUS      current
   DESCRIPTION
      "Path: ethernet3.editConf.vlanTagging.vlans.action

       Possibilities:
               discard   (0)
               accept   (1)
               tag   (2)"
   ::= {er1645v2Lan3MCVlanTaggingVlansEntry 1073741824}

er1645v2Lan3MCVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.vlans.tagInfo.tpid

       Possibilities:
               dot1Q   (33024)
               dot1ad   (34984)
               0x9100   (37120)
               0x9200   (37376)
               0x9300   (37632)"
   ::= {er1645v2Lan3MCVlanTaggingVlansEntry 1677721600}

er1645v2Lan3MCVlanTaggingVlansTagInfoVid OBJECT-TYPE
   SYNTAX      Integer32
   MAX-ACCESS  read-write
   STATUS      current
   DESCRIPTION
      "Path: ethernet3.editConf.vlanTagging.vlans.tagInfo.vid"
   ::= {er1645v2Lan3MCVlanTaggingVlansEntry 1744830464}


er1645v2Lan3MCOam OBJECT IDENTIFIER ::= {er1645v2Lan3MC 900}

er1645v2Lan3MCOamSSC OBJECT IDENTIFIER ::= {er1645v2Lan3MCOam 1}

er1645v2Lan3MCOamEntry OBJECT IDENTIFIER ::= {er1645v2Lan3MCOamSSC 1}

er1645v2Lan3MCOamMode OBJECT-TYPE
   SYNTAX      INTEGER
               {
               disabled (0),
               passive (3),
               active (2)
               }
   MAX-ACCESS  read-write
   STATUS      current
   DESCRIPTION
      "Path: ethernet3.editConf.oam.mode

       Possibilities:
               disabled   (0)
               passive   (3)
               active   (2)"
   ::= {er1645v2Lan3MCOamEntry 16777216}

er1645v2Lan3MCOamLpbkLocalParAction OBJECT-TYPE
   SYNTAX      INTEGER
               {
               discard (0),
               forward (1)
               }
   MAX-ACCESS  read-write
   STATUS      current
   DESCRIPTION
      "Path: ethernet3.editConf.oam.loopbackLocalParserAction

       Possibilities:
               discard   (0)
               forward   (1)"
   ::= {er1645v2Lan3MCOamEntry 33554432}

er1645v2Lan3MCOamLpbkSwapMacAddr OBJECT-TYPE
   SYNTAX      INTEGER
               {
               disabled (0),
               enabled (1)
               }
   MAX-ACCESS  read-write
   STATUS      current
   DESCRIPTION
      "Path: ethernet3.editConf.oam.loopbackSwapMacAddresses

       Possibilities:
               disabled   (0)
               enabled   (1)"
   ::= {er1645v2Lan3MCOamEntry 50331648}

er1645v2Lan3MCOamLoopbackIgnoreRx OBJECT-TYPE
   SYNTAX      INTEGER
               {
               no (0),
               yes (1)
               }
   MAX-ACCESS  read-write
   STATUS      current
   DESCRIPTION
      "Path: ethernet3.editConf.oam.loopbackIgnoreRx

       Possibilities:
               no   (0)
               yes   (1)"
   ::= {er1645v2Lan3MCOamEntry 67108864}

er1645v2Lan3MCOamEventsErroredSymbolEnabled OBJECT-TYPE
   SYNTAX      INTEGER
               {
               no (0),
               yes (1)
               }
   MAX-ACCESS  read-write
   STATUS      current
   DESCRIPTION
      "Path: ethernet3.editConf.oam.events.erroredSymbol.enabled

       Possibilities:
               no   (0)
               yes   (1)"
   ::= {er1645v2Lan3MCOamEntry 83951872}

er1645v2Lan3MCOamEventsErroredSymbolWindowHi OBJECT-TYPE
   SYNTAX      INTEGER
               {
               default (0)
               }
   UNITS       "symbols"
   MAX-ACCESS  read-write
   STATUS      current
   DESCRIPTION
      "Path: ethernet3.editConf.oam.events.erroredSymbol.windowHi

       unit name = symbols

       Possibilities:
               default   (0)"
   ::= {er1645v2Lan3MCOamEntry 83952128}

er1645v2Lan3MCOamEventsErroredSymbolWindowLo OBJECT-TYPE
   SYNTAX      INTEGER
               {
               default (0)
               }
   UNITS       "symbols"
   MAX-ACCESS  read-write
   STATUS      current
   DESCRIPTION
      "Path: ethernet3.editConf.oam.events.erroredSymbol.windowLo

       unit name = symbols

       Possibilities:
               default   (0)"
   ::= {er1645v2Lan3MCOamEntry 83952384}

er1645v2Lan3MCOamEventsErroredSymbolThresholdHi OBJECT-TYPE
   SYNTAX      Integer32
   UNITS       "symbols"
   MAX-ACCESS  read-write
   STATUS      current
   DESCRIPTION
      "Path: ethernet3.editConf.oam.events.erroredSymbol.thresholdHi

       unit name = symbols"
   ::= {er1645v2Lan3MCOamEntry 83952640}

er1645v2Lan3MCOamEventsErroredSymbolThresholdLo OBJECT-TYPE
   SYNTAX      Integer32
   UNITS       "symbols"
   MAX-ACCESS  read-write
   STATUS      current
   DESCRIPTION
      "Path: ethernet3.editConf.oam.events.erroredSymbol.thresholdLo

       unit name = symbols"
   ::= {er1645v2Lan3MCOamEntry 83952896}

er1645v2Lan3MCOamEventsErroredFramePeriodEnabled OBJECT-TYPE
   SYNTAX      INTEGER
               {
               no (0),
               yes (1)
               }
   MAX-ACCESS  read-write
   STATUS      current
   DESCRIPTION
      "Path: ethernet3.editConf.oam.events.erroredFramePeriod.enabled

       Possibilities:
               no   (0)
               yes   (1)"
   ::= {er1645v2Lan3MCOamEntry 84017408}

er1645v2Lan3MCOamEventsErroredFramePeriodWindow OBJECT-TYPE
   SYNTAX      INTEGER
               {
               default (0)
               }
   UNITS       "frames"
   MAX-ACCESS  read-write
   STATUS      current
   DESCRIPTION
      "Path: ethernet3.editConf.oam.events.erroredFramePeriod.window

       unit name = frames

       Possibilities:
               default   (0)"
   ::= {er1645v2Lan3MCOamEntry 84017664}

er1645v2Lan3MCOamEventsErroredFramePeriodThreshold OBJECT-TYPE
   SYNTAX      Integer32
   UNITS       "frames"
   MAX-ACCESS  read-write
   STATUS      current
   DESCRIPTION
      "Path: ethernet3.editConf.oam.events.erroredFramePeriod.threshold

       unit name = frames"
   ::= {er1645v2Lan3MCOamEntry 84017920}

er1645v2Lan3MCOamEventsErroredFrameEnabled OBJECT-TYPE
   SYNTAX      INTEGER
               {
               no (0),
               yes (1)
               }
   MAX-ACCESS  read-write
   STATUS      current
   DESCRIPTION
      "Path: ethernet3.editConf.oam.events.erroredFrame.enabled

       Possibilities:
               no   (0)
               yes   (1)"
   ::= {er1645v2Lan3MCOamEntry 84082944}

er1645v2Lan3MCOamEventsErroredFrameWindow OBJECT-TYPE
   SYNTAX      Integer32
   UNITS       "100msec"
   MAX-ACCESS  read-write
   STATUS      current
   DESCRIPTION
      "Path: ethernet3.editConf.oam.events.erroredFrame.window

       unit name = 100msec"
   ::= {er1645v2Lan3MCOamEntry 84083200}

er1645v2Lan3MCOamEventsErroredFrameThreshold OBJECT-TYPE
   SYNTAX      Integer32
   UNITS       "frames"
   MAX-ACCESS  read-write
   STATUS      current
   DESCRIPTION
      "Path: ethernet3.editConf.oam.events.erroredFrame.threshold

       unit name = frames"
   ::= {er1645v2Lan3MCOamEntry 84083456}

er1645v2Lan3MCOamEventsErroredFrameSecondsEnabled OBJECT-TYPE
   SYNTAX      INTEGER
               {
               no (0),
               yes (1)
               }
   MAX-ACCESS  read-write
   STATUS      current
   DESCRIPTION
      "Path: ethernet3.editConf.oam.events.erroredFrameSeconds.enabled

       Possibilities:
               no   (0)
               yes   (1)"
   ::= {er1645v2Lan3MCOamEntry 84148480}

er1645v2Lan3MCOamEventsErroredFrameSecondsWindow OBJECT-TYPE
   SYNTAX      Integer32
   UNITS       "100msec"
   MAX-ACCESS  read-write
   STATUS      current
   DESCRIPTION
      "Path: ethernet3.editConf.oam.events.erroredFrameSeconds.window

       unit name = 100msec"
   ::= {er1645v2Lan3MCOamEntry 84148736}

er1645v2Lan3MCOamEventsErroredFrameSecondsThreshold OBJECT-TYPE
   SYNTAX      Integer32
   UNITS       "frames"
   MAX-ACCESS  read-write
   STATUS      current
   DESCRIPTION
      "Path: ethernet3.editConf.oam.events.erroredFrameSeconds.threshold

       unit name = frames"
   ::= {er1645v2Lan3MCOamEntry 84148992}

er1645v2Lan3MCOamEventsDyingGasp OBJECT-TYPE
   SYNTAX      INTEGER
               {
               disabled (0),
               enabled (1)
               }
   MAX-ACCESS  read-write
   STATUS      current
   DESCRIPTION
      "Path: ethernet3.editConf.oam.events.dyingGasp

       Possibilities:
               disabled   (0)
               enabled   (1)"
   ::= {er1645v2Lan3MCOamEntry 84213760}

er1645v2Lan3MCOamEventsCriticalEvent OBJECT-TYPE
   SYNTAX      INTEGER
               {
               disabled (0),
               enabled (1)
               }
   MAX-ACCESS  read-write
   STATUS      current
   DESCRIPTION
      "Path: ethernet3.editConf.oam.events.criticalEvent

       Possibilities:
               disabled   (0)
               enabled   (1)"
   ::= {er1645v2Lan3MCOamEntry 84279296}


er1645v2Lan3MCLst OBJECT IDENTIFIER ::= {er1645v2Lan3MC 12}

er1645v2Lan3MCLstSSC OBJECT IDENTIFIER ::= {er1645v2Lan3MCLst 1}

er1645v2Lan3MCLstEntry OBJECT IDENTIFIER ::= {er1645v2Lan3MCLstSSC 1}

er1645v2Lan3MCLstTrackedInterface OBJECT-TYPE
   SYNTAX      DisplayString
   MAX-ACCESS  read-write
   STATUS      current
   DESCRIPTION
      "Path: ethernet3.editConf.linkStateTracking.trackedInterface"
   ::= {er1645v2Lan3MCLstEntry 16777216}


er1645v2Lan3MCDot1x OBJECT IDENTIFIER ::= {er1645v2Lan3MC 191}

er1645v2Lan3MCDot1xSSC OBJECT IDENTIFIER ::= {er1645v2Lan3MCDot1x 1}

er1645v2Lan3MCDot1xEntry OBJECT IDENTIFIER ::= {er1645v2Lan3MCDot1xSSC 1}

er1645v2Lan3MCDot1xMode OBJECT-TYPE
   SYNTAX      INTEGER
               {
               inactive (0),
               auto (1)
               }
   MAX-ACCESS  read-write
   STATUS      current
   DESCRIPTION
      "Path: ethernet3.editConf.dot1x.mode

       Possibilities:
               inactive   (0)
               auto   (1)"
   ::= {er1645v2Lan3MCDot1xEntry 16777216}

er1645v2Lan3MCDot1xMaxHosts OBJECT-TYPE
   SYNTAX      Integer32
   MAX-ACCESS  read-write
   STATUS      current
   DESCRIPTION
      "Path: ethernet3.editConf.dot1x.maxHosts"
   ::= {er1645v2Lan3MCDot1xEntry 33554432}

er1645v2Lan3MCDot1xReAuthentication OBJECT-TYPE
   SYNTAX      INTEGER
               {
               disabled (0),
               enabled (1)
               }
   MAX-ACCESS  read-write
   STATUS      current
   DESCRIPTION
      "Path: ethernet3.editConf.dot1x.reAuthentication

       Possibilities:
               disabled   (0)
               enabled   (1)"
   ::= {er1645v2Lan3MCDot1xEntry 50331648}

er1645v2Lan3MCDot1xReAuthPeriod OBJECT-TYPE
   SYNTAX      TimeTicks
   MAX-ACCESS  read-write
   STATUS      current
   DESCRIPTION
      "Path: ethernet3.editConf.dot1x.reAuthPeriod

       Time in centi-second."
   ::= {er1645v2Lan3MCDot1xEntry 67108864}

er1645v2Lan3MCDot1xQuietPeriod OBJECT-TYPE
   SYNTAX      TimeTicks
   MAX-ACCESS  read-write
   STATUS      current
   DESCRIPTION
      "Path: ethernet3.editConf.dot1x.quietPeriod

       Time in centi-second."
   ::= {er1645v2Lan3MCDot1xEntry 83886080}

er1645v2Lan3MCDot1xSupplTimeout OBJECT-TYPE
   SYNTAX      TimeTicks
   MAX-ACCESS  read-write
   STATUS      current
   DESCRIPTION
      "Path: ethernet3.editConf.dot1x.supplTimeout

       Time in centi-second."
   ::= {er1645v2Lan3MCDot1xEntry 100663296}

er1645v2Lan3MCDot1xServerTimeout OBJECT-TYPE
   SYNTAX      TimeTicks
   MAX-ACCESS  read-write
   STATUS      current
   DESCRIPTION
      "Path: ethernet3.editConf.dot1x.serverTimeout

       Time in centi-second."
   ::= {er1645v2Lan3MCDot1xEntry 117440512}

er1645v2Lan3MCDot1xMaxReqCount OBJECT-TYPE
   SYNTAX      Integer32
   MAX-ACCESS  read-write
   STATUS      current
   DESCRIPTION
      "Path: ethernet3.editConf.dot1x.maxReqCount"
   ::= {er1645v2Lan3MCDot1xEntry 134217728}


er1645v2Lan3MCMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet3.editConf.mode
       Info: routing and/or bridging or ipV6 or multilink selection

       Possibilities:
               bridging   (0)
               routing   (1)
               routingAndBridging   (2)
               ipV6   (3)
               ipV6/ipV4   (4)
               multilink   (5)"
   ::= {er1645v2Lan3MC 29}


er1645v2Lan3MCIpV6 OBJECT IDENTIFIER ::= {er1645v2Lan3MC 15}

er1645v2Lan3MCIpV6SSC OBJECT IDENTIFIER ::= {er1645v2Lan3MCIpV6 1}

er1645v2Lan3MCIpV6Entry OBJECT IDENTIFIER ::= {er1645v2Lan3MCIpV6SSC 1}

er1645v2Lan3MCIpV6VrfRouter OBJECT-TYPE
   SYNTAX      DisplayString
   MAX-ACCESS  read-write
   STATUS      current
   DESCRIPTION
      "Path: ethernet3.editConf.ipV6.vrfRouter"
   ::= {er1645v2Lan3MCIpV6Entry 16777216}

er1645v2Lan3MCIpV6AddrAutoConfigNrDupAddrDetects OBJECT-TYPE
   SYNTAX      Integer32
   MAX-ACCESS  read-write
   STATUS      current
   DESCRIPTION
      "Path: ethernet3.editConf.ipV6.addrAutoConfig.nrDupAddrDetects"
   ::= {er1645v2Lan3MCIpV6Entry 67174400}

er1645v2Lan3MCIpV6AddrAutoConfigAcceptRa OBJECT-TYPE
   SYNTAX      INTEGER
               {
               disabled (0),
               enabled (1)
               }
   MAX-ACCESS  read-write
   STATUS      current
   DESCRIPTION
      "Path: ethernet3.editConf.ipV6.addrAutoConfig.acceptRa

       Possibilities:
               disabled   (0)
               enabled   (1)"
   ::= {er1645v2Lan3MCIpV6Entry 67239936}

er1645v2Lan3MCIpV6AddrAutoConfigAcceptRaRdnss OBJECT-TYPE
   SYNTAX      INTEGER
               {
               disabled (0),
               enabled (1)
               }
   MAX-ACCESS  read-write
   STATUS      current
   DESCRIPTION
      "Path: ethernet3.editConf.ipV6.addrAutoConfig.acceptRaRdnss

       Possibilities:
               disabled   (0)
               enabled   (1)"
   ::= {er1645v2Lan3MCIpV6Entry 67305472}

er1645v2Lan3MCIpV6AddrAutoConfigAcceptRaDnssl OBJECT-TYPE
   SYNTAX      INTEGER
               {
               disabled (0),
               enabled (1)
               }
   MAX-ACCESS  read-write
   STATUS      current
   DESCRIPTION
      "Path: ethernet3.editConf.ipV6.addrAutoConfig.acceptRaDnssl

       Possibilities:
               disabled   (0)
               enabled   (1)"
   ::= {er1645v2Lan3MCIpV6Entry 67371008}

er1645v2Lan3MCIpV6DefaultRoute OBJECT-TYPE
   SYNTAX      INTEGER
               {
               disabled (0),
               enabled (1)
               }
   MAX-ACCESS  read-write
   STATUS      current
   DESCRIPTION
      "Path: ethernet3.editConf.ipV6.defaultRoute

       Possibilities:
               disabled   (0)
               enabled   (1)"
   ::= {er1645v2Lan3MCIpV6Entry 83886080}

er1645v2Lan3MCIpV6RaSend OBJECT-TYPE
   SYNTAX      INTEGER
               {
               disabled (0),
               enabled (1)
               }
   MAX-ACCESS  read-write
   STATUS      current
   DESCRIPTION
      "Path: ethernet3.editConf.ipV6.ra.send

       Possibilities:
               disabled   (0)
               enabled   (1)"
   ::= {er1645v2Lan3MCIpV6Entry 100728832}

er1645v2Lan3MCIpV6RaMinInterval OBJECT-TYPE
   SYNTAX      TimeTicks
   MAX-ACCESS  read-write
   STATUS      current
   DESCRIPTION
      "Path: ethernet3.editConf.ipV6.ra.minInterval

       Time in centi-second."
   ::= {er1645v2Lan3MCIpV6Entry 100794368}

er1645v2Lan3MCIpV6RaMaxInterval OBJECT-TYPE
   SYNTAX      TimeTicks
   MAX-ACCESS  read-write
   STATUS      current
   DESCRIPTION
      "Path: ethernet3.editConf.ipV6.ra.maxInterval

       Time in centi-second."
   ::= {er1645v2Lan3MCIpV6Entry 100859904}

er1645v2Lan3MCIpV6RaManagedFlag OBJECT-TYPE
   SYNTAX      INTEGER
               {
               disabled (0),
               enabled (1)
               }
   MAX-ACCESS  read-write
   STATUS      current
   DESCRIPTION
      "Path: ethernet3.editConf.ipV6.ra.managedFlag

       Possibilities:
               disabled   (0)
               enabled   (1)"
   ::= {er1645v2Lan3MCIpV6Entry 100925440}

er1645v2Lan3MCIpV6RaOtherConfFlag OBJECT-TYPE
   SYNTAX      INTEGER
               {
               disabled (0),
               enabled (1)
               }
   MAX-ACCESS  read-write
   STATUS      current
   DESCRIPTION
      "Path: ethernet3.editConf.ipV6.ra.otherConfFlag

       Possibilities:
               disabled   (0)
               enabled   (1)"
   ::= {er1645v2Lan3MCIpV6Entry 100990976}

er1645v2Lan3MCIpV6RaLinkMtu OBJECT-TYPE
   SYNTAX      Integer32
   MAX-ACCESS  read-write
   STATUS      current
   DESCRIPTION
      "Path: ethernet3.editConf.ipV6.ra.linkMtu"
   ::= {er1645v2Lan3MCIpV6Entry 101056512}

er1645v2Lan3MCIpV6RaReachableTime OBJECT-TYPE
   SYNTAX      TimeTicks
   MAX-ACCESS  read-write
   STATUS      current
   DESCRIPTION
      "Path: ethernet3.editConf.ipV6.ra.reachableTime

       Time in centi-second."
   ::= {er1645v2Lan3MCIpV6Entry 101122048}

er1645v2Lan3MCIpV6RaRetransmitTime OBJECT-TYPE
   SYNTAX      TimeTicks
   MAX-ACCESS  read-write
   STATUS      current
   DESCRIPTION
      "Path: ethernet3.editConf.ipV6.ra.retransmitTime

       Time in centi-second."
   ::= {er1645v2Lan3MCIpV6Entry 101187584}

er1645v2Lan3MCIpV6RaHopLimit OBJECT-TYPE
   SYNTAX      Integer32
   MAX-ACCESS  read-write
   STATUS      current
   DESCRIPTION
      "Path: ethernet3.editConf.ipV6.ra.hopLimit"
   ::= {er1645v2Lan3MCIpV6Entry 101253120}

er1645v2Lan3MCIpV6RaDefaultLifeTime OBJECT-TYPE
   SYNTAX      TimeTicks
   MAX-ACCESS  read-write
   STATUS      current
   DESCRIPTION
      "Path: ethernet3.editConf.ipV6.ra.defaultLifeTime

       Time in centi-second."
   ::= {er1645v2Lan3MCIpV6Entry 101318656}

er1645v2Lan3MCIpV6RaDnsOptionsRdnssLifeTime OBJECT-TYPE
   SYNTAX      TimeTicks
   MAX-ACCESS  read-write
   STATUS      current
   DESCRIPTION
      "Path: ethernet3.editConf.ipV6.ra.dnsOptions.rdnss.lifeTime

       Time in centi-second."
   ::= {er1645v2Lan3MCIpV6Entry 101393408}

er1645v2Lan3MCIpV6RaDnsOptionsRdnssImportServers OBJECT-TYPE
   SYNTAX      INTEGER
               {
               disabled (0),
               enabled (1)
               }
   MAX-ACCESS  read-write
   STATUS      current
   DESCRIPTION
      "Path: ethernet3.editConf.ipV6.ra.dnsOptions.rdnss.importServers

       Possibilities:
               disabled   (0)
               enabled   (1)"
   ::= {er1645v2Lan3MCIpV6Entry 101395456}

er1645v2Lan3MCIpV6RaDnsOptionsDnsslLifeTime OBJECT-TYPE
   SYNTAX      TimeTicks
   MAX-ACCESS  read-write
   STATUS      current
   DESCRIPTION
      "Path: ethernet3.editConf.ipV6.ra.dnsOptions.dnssl.lifeTime

       Time in centi-second."
   ::= {er1645v2Lan3MCIpV6Entry 101401600}

er1645v2Lan3MCIpV6RaDnsOptionsDnsslImportDomains OBJECT-TYPE
   SYNTAX      INTEGER
               {
               disabled (0),
               enabled (1)
               }
   MAX-ACCESS  read-write
   STATUS      current
   DESCRIPTION
      "Path: ethernet3.editConf.ipV6.ra.dnsOptions.dnssl.importDomains

       Possibilities:
               disabled   (0)
               enabled   (1)"
   ::= {er1645v2Lan3MCIpV6Entry 101403648}

er1645v2Lan3MCIpV6RsSend OBJECT-TYPE
   SYNTAX      INTEGER
               {
               disabled (0),
               enabled (1)
               }
   MAX-ACCESS  read-write
   STATUS      current
   DESCRIPTION
      "Path: ethernet3.editConf.ipV6.rs.send

       Possibilities:
               disabled   (0)
               enabled   (1)"
   ::= {er1645v2Lan3MCIpV6Entry 335609856}

er1645v2Lan3MCIpV6RsMaxRandomDelay OBJECT-TYPE
   SYNTAX      TimeTicks
   MAX-ACCESS  read-write
   STATUS      current
   DESCRIPTION
      "Path: ethernet3.editConf.ipV6.rs.maxRandomDelay

       Time in centi-second."
   ::= {er1645v2Lan3MCIpV6Entry 335675392}

er1645v2Lan3MCIpV6RsInterval OBJECT-TYPE
   SYNTAX      TimeTicks
   MAX-ACCESS  read-write
   STATUS      current
   DESCRIPTION
      "Path: ethernet3.editConf.ipV6.rs.interval

       Time in centi-second."
   ::= {er1645v2Lan3MCIpV6Entry 335740928}

er1645v2Lan3MCIpV6RsMaxSolicitations OBJECT-TYPE
   SYNTAX      Integer32
   MAX-ACCESS  read-write
   STATUS      current
   DESCRIPTION
      "Path: ethernet3.editConf.ipV6.rs.maxSolicitations"
   ::= {er1645v2Lan3MCIpV6Entry 335806464}

er1645v2Lan3MCIpV6TrafficPolicyInbound OBJECT-TYPE
   SYNTAX      DisplayString
   MAX-ACCESS  read-write
   STATUS      current
   DESCRIPTION
      "Path: ethernet3.editConf.ipV6.trafficPolicy.inbound"
   ::= {er1645v2Lan3MCIpV6Entry 184614912}

er1645v2Lan3MCIpV6TrafficPolicyOutbound OBJECT-TYPE
   SYNTAX      DisplayString
   MAX-ACCESS  read-write
   STATUS      current
   DESCRIPTION
      "Path: ethernet3.editConf.ipV6.trafficPolicy.outbound"
   ::= {er1645v2Lan3MCIpV6Entry 184680448}

er1645v2Lan3MCIpV6FirewallZone OBJECT-TYPE
   SYNTAX      DisplayString
   MAX-ACCESS  read-write
   STATUS      current
   DESCRIPTION
      "Path: ethernet3.editConf.ipV6.firewall.zone"
   ::= {er1645v2Lan3MCIpV6Entry 201392128}

er1645v2Lan3MCIpV6DhcpClientAddrAC OBJECT-TYPE
   SYNTAX      INTEGER
               {
               disabled (0),
               enabled (1)
               }
   MAX-ACCESS  read-write
   STATUS      current
   DESCRIPTION
      "Path: ethernet3.editConf.ipV6.dhcp.client.addrAutoConfig

       Possibilities:
               disabled   (0)
               enabled   (1)"
   ::= {er1645v2Lan3MCIpV6Entry 170131456}

er1645v2Lan3MCIpV6DhcpClientPrDelMode OBJECT-TYPE
   SYNTAX      INTEGER
               {
               disabled (0),
               enabled (1)
               }
   MAX-ACCESS  read-write
   STATUS      current
   DESCRIPTION
      "Path: ethernet3.editConf.ipV6.dhcp.client.pd.mode

       Possibilities:
               disabled   (0)
               enabled   (1)"
   ::= {er1645v2Lan3MCIpV6Entry 170394624}

er1645v2Lan3MCIpV6DhcpClientPrDelPool OBJECT-TYPE
   SYNTAX      DisplayString
   MAX-ACCESS  read-write
   STATUS      current
   DESCRIPTION
      "Path: ethernet3.editConf.ipV6.dhcp.client.pd.pool"
   ::= {er1645v2Lan3MCIpV6Entry 170395648}

er1645v2Lan3MCIpV6DhcpClientPrDelPdExclOpt OBJECT-TYPE
   SYNTAX      INTEGER
               {
               disabled (0),
               enabled (1)
               }
   MAX-ACCESS  read-write
   STATUS      current
   DESCRIPTION
      "Path: ethernet3.editConf.ipV6.dhcp.client.pd.pdExclOpt

       Possibilities:
               disabled   (0)
               enabled   (1)"
   ::= {er1645v2Lan3MCIpV6Entry 170396672}

er1645v2Lan3MCIpV6DhcpClientDnsServerPref OBJECT-TYPE
   SYNTAX      Integer32
   MAX-ACCESS  read-write
   STATUS      current
   DESCRIPTION
      "Path: ethernet3.editConf.ipV6.dhcp.client.dns.serverPref"
   ::= {er1645v2Lan3MCIpV6Entry 170918912}

er1645v2Lan3MCIpV6DhcpClientRapidCommit OBJECT-TYPE
   SYNTAX      INTEGER
               {
               disabled (0),
               enabled (1)
               }
   MAX-ACCESS  read-write
   STATUS      current
   DESCRIPTION
      "Path: ethernet3.editConf.ipV6.dhcp.client.rapidCommit

       Possibilities:
               disabled   (0)
               enabled   (1)"
   ::= {er1645v2Lan3MCIpV6Entry 170655744}

er1645v2Lan3MCIpV6DhcpClientTimersSolTimeOut OBJECT-TYPE
   SYNTAX      TimeTicks
   MAX-ACCESS  read-write
   STATUS      current
   DESCRIPTION
      "Path: ethernet3.editConf.ipV6.dhcp.client.timers.solTimeOut

       Time in centi-second."
   ::= {er1645v2Lan3MCIpV6Entry 171181056}

er1645v2Lan3MCIpV6DhcpClientTimersSolMaxRt OBJECT-TYPE
   SYNTAX      TimeTicks
   MAX-ACCESS  read-write
   STATUS      current
   DESCRIPTION
      "Path: ethernet3.editConf.ipV6.dhcp.client.timers.solMaxRt

       Time in centi-second."
   ::= {er1645v2Lan3MCIpV6Entry 171182080}

er1645v2Lan3MCIpV6DhcpClientTimersInfoRefresh OBJECT-TYPE
   SYNTAX      TimeTicks
   MAX-ACCESS  read-write
   STATUS      current
   DESCRIPTION
      "Path: ethernet3.editConf.ipV6.dhcp.client.timers.infoRefresh

       Time in centi-second."
   ::= {er1645v2Lan3MCIpV6Entry 171183104}

er1645v2Lan3MCIpV6DhcpServerMode OBJECT-TYPE
   SYNTAX      INTEGER
               {
               disabled (0),
               enabled (1)
               }
   MAX-ACCESS  read-write
   STATUS      current
   DESCRIPTION
      "Path: ethernet3.editConf.ipV6.dhcp.server.mode

       Possibilities:
               disabled   (0)
               enabled   (1)"
   ::= {er1645v2Lan3MCIpV6Entry 172228608}

er1645v2Lan3MCIpV6DhcpServerPreference OBJECT-TYPE
   SYNTAX      Integer32
   MAX-ACCESS  read-write
   STATUS      current
   DESCRIPTION
      "Path: ethernet3.editConf.ipV6.dhcp.server.preference"
   ::= {er1645v2Lan3MCIpV6Entry 172490752}

er1645v2Lan3MCIpV6DhcpServerPool OBJECT-TYPE
   SYNTAX      DisplayString
   MAX-ACCESS  read-write
   STATUS      current
   DESCRIPTION
      "Path: ethernet3.editConf.ipV6.dhcp.server.pool"
   ::= {er1645v2Lan3MCIpV6Entry 172752896}

er1645v2Lan3MCIpV6DhcpServerRapidCommit OBJECT-TYPE
   SYNTAX      INTEGER
               {
               disabled (0),
               enabled (1)
               }
   MAX-ACCESS  read-write
   STATUS      current
   DESCRIPTION
      "Path: ethernet3.editConf.ipV6.dhcp.server.rapidCommit

       Possibilities:
               disabled   (0)
               enabled   (1)"
   ::= {er1645v2Lan3MCIpV6Entry 173015040}

er1645v2Lan3MCIpV6DhcpServerTimersInfoRefresh OBJECT-TYPE
   SYNTAX      TimeTicks
   MAX-ACCESS  read-write
   STATUS      current
   DESCRIPTION
      "Path: ethernet3.editConf.ipV6.dhcp.server.timers.infoRefresh

       Time in centi-second."
   ::= {er1645v2Lan3MCIpV6Entry 173278208}

er1645v2Lan3MCIpV6DhcpRelayMode OBJECT-TYPE
   SYNTAX      INTEGER
               {
               disabled (0),
               enabled (1)
               }
   MAX-ACCESS  read-write
   STATUS      current
   DESCRIPTION
      "Path: ethernet3.editConf.ipV6.dhcp.relay.mode

       Possibilities:
               disabled   (0)
               enabled   (1)"
   ::= {er1645v2Lan3MCIpV6Entry 174071808}

er1645v2Lan3MCIpV6SendRedirect OBJECT-TYPE
   SYNTAX      INTEGER
               {
               disabled (0),
               enabled (1)
               }
   MAX-ACCESS  read-write
   STATUS      current
   DESCRIPTION
      "Path: ethernet3.editConf.ipV6.sendRedirect

       Possibilities:
               disabled   (0)
               enabled   (1)"
   ::= {er1645v2Lan3MCIpV6Entry 117440512}

er1645v2Lan3MCIpV6LinkMtu OBJECT-TYPE
   SYNTAX      Integer32
   MAX-ACCESS  read-write
   STATUS      current
   DESCRIPTION
      "Path: ethernet3.editConf.ipV6.linkMtu"
   ::= {er1645v2Lan3MCIpV6Entry 134217728}

er1645v2Lan3MCIpV6InterfaceId OBJECT-TYPE
   SYNTAX      OCTET STRING
   MAX-ACCESS  read-write
   STATUS      current
   DESCRIPTION
      "Path: ethernet3.editConf.ipV6.interfaceId"
   ::= {er1645v2Lan3MCIpV6Entry 150994944}

er1645v2Lan3MCIpV6MF OBJECT-TYPE
   SYNTAX      Integer32
   MAX-ACCESS  read-write
   STATUS      current
   DESCRIPTION
      "Path: ethernet3.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3MCIpV6Entry 285212672}

er1645v2Lan3MCIpV6IcmpMessagesNoRoute OBJECT-TYPE
   SYNTAX      INTEGER
               {
               disabled (0),
               enabled (1)
               }
   MAX-ACCESS  read-write
   STATUS      current
   DESCRIPTION
      "Path: ethernet3.editConf.ipV6.icmpMessages.noRoute

       Possibilities:
               disabled   (0)
               enabled   (1)"
   ::= {er1645v2Lan3MCIpV6Entry 302055424}

er1645v2Lan3MCIpV6IcmpMessagesBeyondScope OBJECT-TYPE
   SYNTAX      INTEGER
               {
               disabled (0),
               enabled (1)
               }
   MAX-ACCESS  read-write
   STATUS      current
   DESCRIPTION
      "Path: ethernet3.editConf.ipV6.icmpMessages.beyondScope

       Possibilities:
               disabled   (0)
               enabled   (1)"
   ::= {er1645v2Lan3MCIpV6Entry 302186496}

er1645v2Lan3MCIpV6IcmpMessagesAddressUnreachable OBJECT-TYPE
   SYNTAX      INTEGER
               {
               disabled (0),
               enabled (1)
               }
   MAX-ACCESS  read-write
   STATUS      current
   DESCRIPTION
      "Path: ethernet3.editConf.ipV6.icmpMessages.addressUnreachable

       Possibilities:
               disabled   (0)
               enabled   (1)"
   ::= {er1645v2Lan3MCIpV6Entry 302252032}

er1645v2Lan3MCIpV6IcmpMessagesPortUnreachable OBJECT-TYPE
   SYNTAX      INTEGER
               {
               disabled (0),
               enabled (1)
               }
   MAX-ACCESS  read-write
   STATUS      current
   DESCRIPTION
      "Path: ethernet3.editConf.ipV6.icmpMessages.portUnreachable

       Possibilities:
               disabled   (0)
               enabled   (1)"
   ::= {er1645v2Lan3MCIpV6Entry 302317568}

er1645v2Lan3MCIpV6IcmpMessagesPacketTooBig OBJECT-TYPE
   SYNTAX      INTEGER
               {
               disabled (0),
               enabled (1)
               }
   MAX-ACCESS  read-write
   STATUS      current
   DESCRIPTION
      "Path: ethernet3.editConf.ipV6.icmpMessages.packetTooBig

       Possibilities:
               disabled   (0)
               enabled   (1)"
   ::= {er1645v2Lan3MCIpV6Entry 302645248}

er1645v2Lan3MCIpV6IcmpMessagesHopLimitExceeded OBJECT-TYPE
   SYNTAX      INTEGER
               {
               disabled (0),
               enabled (1)
               }
   MAX-ACCESS  read-write
   STATUS      current
   DESCRIPTION
      "Path: ethernet3.editConf.ipV6.icmpMessages.hopLimitExceeded

       Possibilities:
               disabled   (0)
               enabled   (1)"
   ::= {er1645v2Lan3MCIpV6Entry 303300608}

er1645v2Lan3MCIpV6IcmpMessagesFragTimeExceeded OBJECT-TYPE
   SYNTAX      INTEGER
               {
               disabled (0),
               enabled (1)
               }
   MAX-ACCESS  read-write
   STATUS      current
   DESCRIPTION
      "Path: ethernet3.editConf.ipV6.icmpMessages.fragTimeExceeded

       Possibilities:
               disabled   (0)
               enabled   (1)"
   ::= {er1645v2Lan3MCIpV6Entry 303366144}

er1645v2Lan3MCIpV6IcmpMessagesHeaderFieldErr OBJECT-TYPE
   SYNTAX      INTEGER
               {
               disabled (0),
               enabled (1)
               }
   MAX-ACCESS  read-write
   STATUS      current
   DESCRIPTION
      "Path: ethernet3.editConf.ipV6.icmpMessages.headerFieldErr

       Possibilities:
               disabled   (0)
               enabled   (1)"
   ::= {er1645v2Lan3MCIpV6Entry 303955968}

er1645v2Lan3MCIpV6IcmpMessagesOptionUnrecognized OBJECT-TYPE
   SYNTAX      INTEGER
               {
               disabled (0),
               enabled (1)
               }
   MAX-ACCESS  read-write
   STATUS      current
   DESCRIPTION
      "Path: ethernet3.editConf.ipV6.icmpMessages.optionUnrecognized

       Possibilities:
               disabled   (0)
               enabled   (1)"
   ::= {er1645v2Lan3MCIpV6Entry 304087040}

er1645v2Lan3MCIpV6IcmpMessagesRedirect OBJECT-TYPE
   SYNTAX      INTEGER
               {
               disabled (0),
               enabled (1)
               }
   MAX-ACCESS  read-write
   STATUS      current
   DESCRIPTION
      "Path: ethernet3.editConf.ipV6.icmpMessages.redirect

       Possibilities:
               disabled   (0)
               enabled   (1)"
   ::= {er1645v2Lan3MCIpV6Entry 304611328}

er1645v2Lan3MCIpV6Addresses OBJECT-TYPE
   SYNTAX      SEQUENCE OF Er1645v2Lan3MCIpV6AddressesEntry
   MAX-ACCESS  not-accessible
   STATUS      current
   DESCRIPTION
      ""
   ::= {er1645v2Lan3MCIpV6 50331648}

er1645v2Lan3MCIpV6AddressesEntry OBJECT-TYPE
   SYNTAX      Er1645v2Lan3MCIpV6AddressesEntry
   MAX-ACCESS  not-accessible
   STATUS      current
   DESCRIPTION
      ""
   INDEX      { er1645v2Lan3MCIpV6AddressesTableIx }
   ::= {er1645v2Lan3MCIpV6Addresses 1}

Er1645v2Lan3MCIpV6AddressesEntry ::=
   SEQUENCE
      {
      er1645v2Lan3MCIpV6AddressesActions
         VariableLengthTableActions,
      er1645v2Lan3MCIpV6AddressesTableIx
         TableIndex,
      er1645v2Lan3MCIpV6AddressesType
         INTEGER,
      er1645v2Lan3MCIpV6AddressesAddress
         Ipv6Address,
      er1645v2Lan3MCIpV6AddressesPrefixLength
         Integer32,
      er1645v2Lan3MCIpV6AddressesGeneralPrefix
         DisplayString,
      er1645v2Lan3MCIpV6AddressesRaSend
         INTEGER,
      er1645v2Lan3MCIpV6AddressesRaOnLinkFlag
         INTEGER,
      er1645v2Lan3MCIpV6AddressesRaAutoFlag
         INTEGER,
      er1645v2Lan3MCIpV6AddressesRaValidLifeTime
         TimeTicks,
      er1645v2Lan3MCIpV6AddressesRaValidLTMode
         INTEGER,
      er1645v2Lan3MCIpV6AddressesRaPrefLifeTime
         TimeTicks,
      er1645v2Lan3MCIpV6AddressesRaPrefLTMode
         INTEGER
      }

er1645v2Lan3MCIpV6AddressesActions OBJECT-TYPE
   SYNTAX      VariableLengthTableActions
   MAX-ACCESS  read-write
   STATUS      current
   DESCRIPTION
      "By way of this field, some manipulations
       on this table may be performed."
   ::= {er1645v2Lan3MCIpV6AddressesEntry 2}

er1645v2Lan3MCIpV6AddressesTableIx OBJECT-TYPE
   SYNTAX      TableIndex
   MAX-ACCESS  not-accessible
   STATUS      current
   DESCRIPTION
      ""
   ::= {er1645v2Lan3MCIpV6AddressesEntry 11}

er1645v2Lan3MCIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.ipV6.addresses.type

       Possibilities:
               unicast   (0)
               eui64   (1)
               anycast   (2)
               linkLocal   (3)
               generalPrefix   (4)"
   ::= {er1645v2Lan3MCIpV6AddressesEntry 50331648}

er1645v2Lan3MCIpV6AddressesAddress OBJECT-TYPE
   SYNTAX      Ipv6Address
   MAX-ACCESS  read-write
   STATUS      current
   DESCRIPTION
      "Path: ethernet3.editConf.ipV6.addresses.address

       ipv6 address"
   ::= {er1645v2Lan3MCIpV6AddressesEntry 16777216}

er1645v2Lan3MCIpV6AddressesPrefixLength OBJECT-TYPE
   SYNTAX      Integer32
   MAX-ACCESS  read-write
   STATUS      current
   DESCRIPTION
      "Path: ethernet3.editConf.ipV6.addresses.prefixLength"
   ::= {er1645v2Lan3MCIpV6AddressesEntry 33554432}

er1645v2Lan3MCIpV6AddressesGeneralPrefix OBJECT-TYPE
   SYNTAX      DisplayString
   MAX-ACCESS  read-write
   STATUS      current
   DESCRIPTION
      "Path: ethernet3.editConf.ipV6.addresses.generalPrefix"
   ::= {er1645v2Lan3MCIpV6AddressesEntry 83886080}

er1645v2Lan3MCIpV6AddressesRaSend OBJECT-TYPE
   SYNTAX      INTEGER
               {
               disabled (0),
               enabled (1)
               }
   MAX-ACCESS  read-write
   STATUS      current
   DESCRIPTION
      "Path: ethernet3.editConf.ipV6.addresses.ra.send

       Possibilities:
               disabled   (0)
               enabled   (1)"
   ::= {er1645v2Lan3MCIpV6AddressesEntry 67174400}

er1645v2Lan3MCIpV6AddressesRaOnLinkFlag OBJECT-TYPE
   SYNTAX      INTEGER
               {
               disabled (0),
               enabled (1)
               }
   MAX-ACCESS  read-write
   STATUS      current
   DESCRIPTION
      "Path: ethernet3.editConf.ipV6.addresses.ra.onLinkFlag

       Possibilities:
               disabled   (0)
               enabled   (1)"
   ::= {er1645v2Lan3MCIpV6AddressesEntry 67371008}

er1645v2Lan3MCIpV6AddressesRaAutoFlag OBJECT-TYPE
   SYNTAX      INTEGER
               {
               disabled (0),
               enabled (1)
               }
   MAX-ACCESS  read-write
   STATUS      current
   DESCRIPTION
      "Path: ethernet3.editConf.ipV6.addresses.ra.autonomousFlag

       Possibilities:
               disabled   (0)
               enabled   (1)"
   ::= {er1645v2Lan3MCIpV6AddressesEntry 67567616}

er1645v2Lan3MCIpV6AddressesRaValidLifeTime OBJECT-TYPE
   SYNTAX      TimeTicks
   MAX-ACCESS  read-write
   STATUS      current
   DESCRIPTION
      "Path: ethernet3.editConf.ipV6.addresses.ra.validLifeTime

       Time in centi-second."
   ::= {er1645v2Lan3MCIpV6AddressesEntry 67239936}

er1645v2Lan3MCIpV6AddressesRaValidLTMode OBJECT-TYPE
   SYNTAX      INTEGER
               {
               fixed (0),
               infinite (2)
               }
   MAX-ACCESS  read-write
   STATUS      current
   DESCRIPTION
      "Path: ethernet3.editConf.ipV6.addresses.ra.validLifeTimeMode

       Possibilities:
               fixed   (0)
               infinite   (2)"
   ::= {er1645v2Lan3MCIpV6AddressesEntry 67305472}

er1645v2Lan3MCIpV6AddressesRaPrefLifeTime OBJECT-TYPE
   SYNTAX      TimeTicks
   MAX-ACCESS  read-write
   STATUS      current
   DESCRIPTION
      "Path: ethernet3.editConf.ipV6.addresses.ra.prefLifeTime

       Time in centi-second."
   ::= {er1645v2Lan3MCIpV6AddressesEntry 67436544}

er1645v2Lan3MCIpV6AddressesRaPrefLTMode OBJECT-TYPE
   SYNTAX      INTEGER
               {
               fixed (0),
               infinite (2)
               }
   MAX-ACCESS  read-write
   STATUS      current
   DESCRIPTION
      "Path: ethernet3.editConf.ipV6.addresses.ra.prefLifeTimeMode

       Possibilities:
               fixed   (0)
               infinite   (2)"
   ::= {er1645v2Lan3MCIpV6AddressesEntry 67502080}

er1645v2Lan3MCIpV6RaDnsOptionsRdnssServers OBJECT-TYPE
   SYNTAX      SEQUENCE OF Er1645v2Lan3MCIpV6RaDnsOptionsRdnssServersEntry
   MAX-ACCESS  not-accessible
   STATUS      current
   DESCRIPTION
      ""
   ::= {er1645v2Lan3MCIpV6 101394432}

er1645v2Lan3MCIpV6RaDnsOptionsRdnssServersEntry OBJECT-TYPE
   SYNTAX      Er1645v2Lan3MCIpV6RaDnsOptionsRdnssServersEntry
   MAX-ACCESS  not-accessible
   STATUS      current
   DESCRIPTION
      ""
   INDEX      { er1645v2Lan3MCIpV6RaDnsOptionsRdnssServersTableIx }
   ::= {er1645v2Lan3MCIpV6RaDnsOptionsRdnssServers 1}

Er1645v2Lan3MCIpV6RaDnsOptionsRdnssServersEntry ::=
   SEQUENCE
      {
      er1645v2Lan3MCIpV6RaDnsOptionsRdnssServersActions
         VariableLengthTableActions,
      er1645v2Lan3MCIpV6RaDnsOptionsRdnssServersTableIx
         TableIndex,
      er1645v2Lan3MCIpV6RaDnsOptionsRdnssServersAddress
         Ipv6Address
      }

er1645v2Lan3MCIpV6RaDnsOptionsRdnssServersActions OBJECT-TYPE
   SYNTAX      VariableLengthTableActions
   MAX-ACCESS  read-write
   STATUS      current
   DESCRIPTION
      "By way of this field, some manipulations
       on this table may be performed."
   ::= {er1645v2Lan3MCIpV6RaDnsOptionsRdnssServersEntry 2}

er1645v2Lan3MCIpV6RaDnsOptionsRdnssServersTableIx OBJECT-TYPE
   SYNTAX      TableIndex
   MAX-ACCESS  not-accessible
   STATUS      current
   DESCRIPTION
      ""
   ::= {er1645v2Lan3MCIpV6RaDnsOptionsRdnssServersEntry 11}

er1645v2Lan3MCIpV6RaDnsOptionsRdnssServersAddress OBJECT-TYPE
   SYNTAX      Ipv6Address
   MAX-ACCESS  read-write
   STATUS      current
   DESCRIPTION
      "Path: ethernet3.editConf.ipV6.ra.dnsOptions.rdnss.servers.address

       ipv6 address"
   ::= {er1645v2Lan3MCIpV6RaDnsOptionsRdnssServersEntry 16777216}

er1645v2Lan3MCIpV6RaDnsOptionsDnsslDomains OBJECT-TYPE
   SYNTAX      SEQUENCE OF Er1645v2Lan3MCIpV6RaDnsOptionsDnsslDomainsEntry
   MAX-ACCESS  not-accessible
   STATUS      current
   DESCRIPTION
      ""
   ::= {er1645v2Lan3MCIpV6 101402624}

er1645v2Lan3MCIpV6RaDnsOptionsDnsslDomainsEntry OBJECT-TYPE
   SYNTAX      Er1645v2Lan3MCIpV6RaDnsOptionsDnsslDomainsEntry
   MAX-ACCESS  not-accessible
   STATUS      current
   DESCRIPTION
      ""
   INDEX      { er1645v2Lan3MCIpV6RaDnsOptionsDnsslDomainsTableIx }
   ::= {er1645v2Lan3MCIpV6RaDnsOptionsDnsslDomains 1}

Er1645v2Lan3MCIpV6RaDnsOptionsDnsslDomainsEntry ::=
   SEQUENCE
      {
      er1645v2Lan3MCIpV6RaDnsOptionsDnsslDomainsActions
         VariableLengthTableActions,
      er1645v2Lan3MCIpV6RaDnsOptionsDnsslDomainsTableIx
         TableIndex,
      er1645v2Lan3MCIpV6RaDnsOptionsDnsslDomainsName
         DisplayString
      }

er1645v2Lan3MCIpV6RaDnsOptionsDnsslDomainsActions OBJECT-TYPE
   SYNTAX      VariableLengthTableActions
   MAX-ACCESS  read-write
   STATUS      current
   DESCRIPTION
      "By way of this field, some manipulations
       on this table may be performed."
   ::= {er1645v2Lan3MCIpV6RaDnsOptionsDnsslDomainsEntry 2}

er1645v2Lan3MCIpV6RaDnsOptionsDnsslDomainsTableIx OBJECT-TYPE
   SYNTAX      TableIndex
   MAX-ACCESS  not-accessible
   STATUS      current
   DESCRIPTION
      ""
   ::= {er1645v2Lan3MCIpV6RaDnsOptionsDnsslDomainsEntry 11}

er1645v2Lan3MCIpV6RaDnsOptionsDnsslDomainsName OBJECT-TYPE
   SYNTAX      DisplayString
   MAX-ACCESS  read-write
   STATUS      current
   DESCRIPTION
      "Path: ethernet3.editConf.ipV6.ra.dnsOptions.dnssl.domains.name"
   ::= {er1645v2Lan3MCIpV6RaDnsOptionsDnsslDomainsEntry 16777216}

er1645v2Lan3MCIpV6DhcpClientUserClassOpt OBJECT-TYPE
   SYNTAX      SEQUENCE OF Er1645v2Lan3MCIpV6DhcpClientUserClassOptEntry
   MAX-ACCESS  not-accessible
   STATUS      current
   DESCRIPTION
      ""
   ::= {er1645v2Lan3MCIpV6 171442176}

er1645v2Lan3MCIpV6DhcpClientUserClassOptEntry OBJECT-TYPE
   SYNTAX      Er1645v2Lan3MCIpV6DhcpClientUserClassOptEntry
   MAX-ACCESS  not-accessible
   STATUS      current
   DESCRIPTION
      ""
   INDEX      { er1645v2Lan3MCIpV6DhcpClientUserClassOptTableIx }
   ::= {er1645v2Lan3MCIpV6DhcpClientUserClassOpt 1}

Er1645v2Lan3MCIpV6DhcpClientUserClassOptEntry ::=
   SEQUENCE
      {
      er1645v2Lan3MCIpV6DhcpClientUserClassOptActions
         VariableLengthTableActions,
      er1645v2Lan3MCIpV6DhcpClientUserClassOptTableIx
         TableIndex,
      er1645v2Lan3MCIpV6DhcpClientUserClassOptValueAscii
         DisplayString,
      er1645v2Lan3MCIpV6DhcpClientUserClassOptValueDecimal
         Integer32,
      er1645v2Lan3MCIpV6DhcpClientUserClassOptValueHexData
         OCTET STRING
      }

er1645v2Lan3MCIpV6DhcpClientUserClassOptActions OBJECT-TYPE
   SYNTAX      VariableLengthTableActions
   MAX-ACCESS  read-write
   STATUS      current
   DESCRIPTION
      "By way of this field, some manipulations
       on this table may be performed."
   ::= {er1645v2Lan3MCIpV6DhcpClientUserClassOptEntry 2}

er1645v2Lan3MCIpV6DhcpClientUserClassOptTableIx OBJECT-TYPE
   SYNTAX      TableIndex
   MAX-ACCESS  not-accessible
   STATUS      current
   DESCRIPTION
      ""
   ::= {er1645v2Lan3MCIpV6DhcpClientUserClassOptEntry 11}

er1645v2Lan3MCIpV6DhcpClientUserClassOptValueAscii OBJECT-TYPE
   SYNTAX      DisplayString
   MAX-ACCESS  read-write
   STATUS      current
   DESCRIPTION
      "Path: ethernet3.editConf.ipV6.dhcp.client.userClassOpt.value.ascii"
   ::= {er1645v2Lan3MCIpV6DhcpClientUserClassOptEntry 16842752}

er1645v2Lan3MCIpV6DhcpClientUserClassOptValueDecimal OBJECT-TYPE
   SYNTAX      Integer32
   MAX-ACCESS  read-write
   STATUS      current
   DESCRIPTION
      "Path: ethernet3.editConf.ipV6.dhcp.client.userClassOpt.value.decimal"
   ::= {er1645v2Lan3MCIpV6DhcpClientUserClassOptEntry 16908288}

er1645v2Lan3MCIpV6DhcpClientUserClassOptValueHexData OBJECT-TYPE
   SYNTAX      OCTET STRING
   MAX-ACCESS  read-write
   STATUS      current
   DESCRIPTION
      "Path: ethernet3.editConf.ipV6.dhcp.client.userClassOpt.value.hexData"
   ::= {er1645v2Lan3MCIpV6DhcpClientUserClassOptEntry 16973824}

er1645v2Lan3MCIpV6DhcpClientVendorCl OBJECT-TYPE
   SYNTAX      SEQUENCE OF Er1645v2Lan3MCIpV6DhcpClientVendorClEntry
   MAX-ACCESS  not-accessible
   STATUS      current
   DESCRIPTION
      ""
   ::= {er1645v2Lan3MCIpV6 171704320}

er1645v2Lan3MCIpV6DhcpClientVendorClEntry OBJECT-TYPE
   SYNTAX      Er1645v2Lan3MCIpV6DhcpClientVendorClEntry
   MAX-ACCESS  not-accessible
   STATUS      current
   DESCRIPTION
      ""
   INDEX      { er1645v2Lan3MCIpV6DhcpClientVendorClTableIx }
   ::= {er1645v2Lan3MCIpV6DhcpClientVendorCl 1}

Er1645v2Lan3MCIpV6DhcpClientVendorClEntry ::=
   SEQUENCE
      {
      er1645v2Lan3MCIpV6DhcpClientVendorClActions
         VariableLengthTableActions,
      er1645v2Lan3MCIpV6DhcpClientVendorClTableIx
         TableIndex,
      er1645v2Lan3MCIpV6DhcpClientVendorClValueAscii
         DisplayString,
      er1645v2Lan3MCIpV6DhcpClientVendorClValueDecimal
         Integer32,
      er1645v2Lan3MCIpV6DhcpClientVendorClValueHexData
         OCTET STRING
      }

er1645v2Lan3MCIpV6DhcpClientVendorClActions OBJECT-TYPE
   SYNTAX      VariableLengthTableActions
   MAX-ACCESS  read-write
   STATUS      current
   DESCRIPTION
      "By way of this field, some manipulations
       on this table may be performed."
   ::= {er1645v2Lan3MCIpV6DhcpClientVendorClEntry 2}

er1645v2Lan3MCIpV6DhcpClientVendorClTableIx OBJECT-TYPE
   SYNTAX      TableIndex
   MAX-ACCESS  not-accessible
   STATUS      current
   DESCRIPTION
      ""
   ::= {er1645v2Lan3MCIpV6DhcpClientVendorClEntry 11}

er1645v2Lan3MCIpV6DhcpClientVendorClValueAscii OBJECT-TYPE
   SYNTAX      DisplayString
   MAX-ACCESS  read-write
   STATUS      current
   DESCRIPTION
      "Path: ethernet3.editConf.ipV6.dhcp.client.vendorClassOpt.value.ascii"
   ::= {er1645v2Lan3MCIpV6DhcpClientVendorClEntry 16842752}

er1645v2Lan3MCIpV6DhcpClientVendorClValueDecimal OBJECT-TYPE
   SYNTAX      Integer32
   MAX-ACCESS  read-write
   STATUS      current
   DESCRIPTION
      "Path: ethernet3.editConf.ipV6.dhcp.client.vendorClassOpt.value.decimal"
   ::= {er1645v2Lan3MCIpV6DhcpClientVendorClEntry 16908288}

er1645v2Lan3MCIpV6DhcpClientVendorClValueHexData OBJECT-TYPE
   SYNTAX      OCTET STRING
   MAX-ACCESS  read-write
   STATUS      current
   DESCRIPTION
      "Path: ethernet3.editConf.ipV6.dhcp.client.vendorClassOpt.value.hexData"
   ::= {er1645v2Lan3MCIpV6DhcpClientVendorClEntry 16973824}

er1645v2Lan3MCIpV6DhcpRelayDestinations OBJECT-TYPE
   SYNTAX      SEQUENCE OF Er1645v2Lan3MCIpV6DhcpRelayDestinationsEntry
   MAX-ACCESS  not-accessible
   STATUS      current
   DESCRIPTION
      ""
   ::= {er1645v2Lan3MCIpV6 174080000}

er1645v2Lan3MCIpV6DhcpRelayDestinationsEntry OBJECT-TYPE
   SYNTAX      Er1645v2Lan3MCIpV6DhcpRelayDestinationsEntry
   MAX-ACCESS  not-accessible
   STATUS      current
   DESCRIPTION
      ""
   INDEX      { er1645v2Lan3MCIpV6DhcpRelayDestinationsTableIx }
   ::= {er1645v2Lan3MCIpV6DhcpRelayDestinations 1}

Er1645v2Lan3MCIpV6DhcpRelayDestinationsEntry ::=
   SEQUENCE
      {
      er1645v2Lan3MCIpV6DhcpRelayDestinationsActions
         VariableLengthTableActions,
      er1645v2Lan3MCIpV6DhcpRelayDestinationsTableIx
         TableIndex,
      er1645v2Lan3MCIpV6DhcpRelayDestinationsAddress
         Ipv6Address,
      er1645v2Lan3MCIpV6DhcpRelayDestinationsInterface
         DisplayString
      }

er1645v2Lan3MCIpV6DhcpRelayDestinationsActions OBJECT-TYPE
   SYNTAX      VariableLengthTableActions
   MAX-ACCESS  read-write
   STATUS      current
   DESCRIPTION
      "By way of this field, some manipulations
       on this table may be performed."
   ::= {er1645v2Lan3MCIpV6DhcpRelayDestinationsEntry 2}

er1645v2Lan3MCIpV6DhcpRelayDestinationsTableIx OBJECT-TYPE
   SYNTAX      TableIndex
   MAX-ACCESS  not-accessible
   STATUS      current
   DESCRIPTION
      ""
   ::= {er1645v2Lan3MCIpV6DhcpRelayDestinationsEntry 11}

er1645v2Lan3MCIpV6DhcpRelayDestinationsAddress OBJECT-TYPE
   SYNTAX      Ipv6Address
   MAX-ACCESS  read-write
   STATUS      current
   DESCRIPTION
      "Path: ethernet3.editConf.ipV6.dhcp.relay.destinations.address

       ipv6 address"
   ::= {er1645v2Lan3MCIpV6DhcpRelayDestinationsEntry 16777216}

er1645v2Lan3MCIpV6DhcpRelayDestinationsInterface OBJECT-TYPE
   SYNTAX      DisplayString
   MAX-ACCESS  read-write
   STATUS      current
   DESCRIPTION
      "Path: ethernet3.editConf.ipV6.dhcp.relay.destinations.interface"
   ::= {er1645v2Lan3MCIpV6DhcpRelayDestinationsEntry 33554432}


er1645v2Lan3MCFlowControl OBJECT-TYPE
   SYNTAX      INTEGER
               {
               disabled (1),
               rx (2),
               tx (3),
               rxAndTx (4)
               }
   MAX-ACCESS  read-write
   STATUS      current
   DESCRIPTION
      "Path: ethernet3.editConf.flowControl
       Info: LAN flow control

       Possibilities:
               disabled   (1)
               rx   (2)
               tx   (3)
               rxAndTx   (4)"
   ::= {er1645v2Lan3MC 7}


er1645v2Lan3MCInboundNUcastPriority OBJECT IDENTIFIER ::= {er1645v2Lan3MC 230}

er1645v2Lan3MCInboundNUcastPrioritySSC OBJECT IDENTIFIER ::= {er1645v2Lan3MCInboundNUcastPriority 1}

er1645v2Lan3MCInboundNUcastPriorityEntry OBJECT IDENTIFIER ::= {er1645v2Lan3MCInboundNUcastPrioritySSC 1}

er1645v2Lan3MCInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2Lan3MCInboundNUcastPriorityEntry 16777216}

er1645v2Lan3MCInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.multicast

       Possibilities:
               queue1   (0)
               queue2   (1)
               queue3   (2)
               queue4   (3)
               queue5   (4)
               lowDelayQueue   (5)
               lowDelay2Queue   (6)
               systemQueue   (7)"
   ::= {er1645v2Lan3MCInboundNUcastPriorityEntry 33554432}


er1645v2Lan3MCIp OBJECT IDENTIFIER ::= {er1645v2Lan3MC 1}

er1645v2Lan3MCIpSSC OBJECT IDENTIFIER ::= {er1645v2Lan3MCIp 1}

er1645v2Lan3MCIpEntry OBJECT IDENTIFIER ::= {er1645v2Lan3MCIpSSC 1}

er1645v2Lan3MCIpVrfRouter OBJECT-TYPE
   SYNTAX      DisplayString
   MAX-ACCESS  read-write
   STATUS      current
   DESCRIPTION
      "Path: ethernet3.editConf.ip.vrfRouter"
   ::= {er1645v2Lan3MCIpEntry 738197504}

er1645v2Lan3MCIpAdr OBJECT-TYPE
   SYNTAX      IpAddress
   MAX-ACCESS  read-write
   STATUS      current
   DESCRIPTION
      "Path: ethernet3.editConf.ip.address"
   ::= {er1645v2Lan3MCIpEntry 2030043136}

er1645v2Lan3MCIpNetm OBJECT-TYPE
   SYNTAX      IpAddress
   MAX-ACCESS  read-write
   STATUS      current
   DESCRIPTION
      "Path: ethernet3.editConf.ip.netMask"
   ::= {er1645v2Lan3MCIpEntry 2063597568}

er1645v2Lan3MCIpSNetName OBJECT-TYPE
   SYNTAX      INTEGER
               {
               slOPTg (0),
               corp (2),
               dmz (3),
               internet (1)
               }
   MAX-ACCESS  read-write
   STATUS      current
   DESCRIPTION
      "Path: ethernet3.editConf.ip.sNet.name

       Possibilities:
               <OPT>   (0)
               corp   (2)
               dmz   (3)
               internet   (1)"
   ::= {er1645v2Lan3MCIpEntry 855703552}

er1645v2Lan3MCIpSNetCust OBJECT-TYPE
   SYNTAX      DisplayString
   MAX-ACCESS  read-write
   STATUS      current
   DESCRIPTION
      "Path: ethernet3.editConf.ip.sNet.custom"
   ::= {er1645v2Lan3MCIpEntry 855769088}

er1645v2Lan3MCIpDhcpC OBJECT-TYPE
   SYNTAX      INTEGER
               {
               disabled (0),
               enabled (1)
               }
   MAX-ACCESS  read-write
   STATUS      current
   DESCRIPTION
      "Path: ethernet3.editConf.ip.dhcpClient

       Possibilities:
               disabled   (0)
               enabled   (1)"
   ::= {er1645v2Lan3MCIpEntry 838860800}

er1645v2Lan3MCIpDhcpGatewayPreference OBJECT-TYPE
   SYNTAX      Integer32
   MAX-ACCESS  read-write
   STATUS      current
   DESCRIPTION
      "Path: ethernet3.editConf.ip.dhcp.gatewayPreference"
   ::= {er1645v2Lan3MCIpEntry 872480768}

er1645v2Lan3MCIpDhcpRoutePreference OBJECT-TYPE
   SYNTAX      Integer32
   MAX-ACCESS  read-write
   STATUS      current
   DESCRIPTION
      "Path: ethernet3.editConf.ip.dhcp.routePreference"
   ::= {er1645v2Lan3MCIpEntry 872546304}

er1645v2Lan3MCIpDhcpDnsPreference OBJECT-TYPE
   SYNTAX      Integer32
   MAX-ACCESS  read-write
   STATUS      current
   DESCRIPTION
      "Path: ethernet3.editConf.ip.dhcp.dnsPreference"
   ::= {er1645v2Lan3MCIpEntry 872611840}

er1645v2Lan3MCIpMtu OBJECT-TYPE
   SYNTAX      Integer32
   MAX-ACCESS  read-write
   STATUS      current
   DESCRIPTION
      "Path: ethernet3.editConf.ip.mtu"
   ::= {er1645v2Lan3MCIpEntry 671088640}

er1645v2Lan3MCIpMssAdjust OBJECT-TYPE
   SYNTAX      INTEGER
               {
               disabled (0),
               auto (65536)
               }
   MAX-ACCESS  read-write
   STATUS      current
   DESCRIPTION
      "Path: ethernet3.editConf.ip.mssAdjust

       Possibilities:
               disabled   (0)
               auto   (65536)"
   ::= {er1645v2Lan3MCIpEntry 754974720}

er1645v2Lan3MCIpRipMetric OBJECT-TYPE
   SYNTAX      Integer32
   MAX-ACCESS  read-write
   STATUS      current
   DESCRIPTION
      "Path: ethernet3.editConf.ip.rip.metric"
   ::= {er1645v2Lan3MCIpEntry 353566720}

er1645v2Lan3MCIpRipMetricOut OBJECT-TYPE
   SYNTAX      Integer32
   MAX-ACCESS  read-write
   STATUS      current
   DESCRIPTION
      "Path: ethernet3.editConf.ip.rip.metricOut"
   ::= {er1645v2Lan3MCIpEntry 353632256}

er1645v2Lan3MCIpRipMode OBJECT-TYPE
   SYNTAX      INTEGER
               {
               disabled (0),
               passive (1),
               active (2)
               }
   MAX-ACCESS  read-write
   STATUS      current
   DESCRIPTION
      "Path: ethernet3.editConf.ip.rip.mode

       Possibilities:
               disabled   (0)
               passive   (1)
               active   (2)"
   ::= {er1645v2Lan3MCIpEntry 353697792}

er1645v2Lan3MCIpRipTxVer OBJECT-TYPE
   SYNTAX      INTEGER
               {
               rip1 (0),
               rip2 (1),
               rip1mcompatible (2)
               }
   MAX-ACCESS  read-write
   STATUS      current
   DESCRIPTION
      "Path: ethernet3.editConf.ip.rip.txVersion

       Possibilities:
               rip1   (0)
               rip2   (1)
               rip1-compatible   (2)"
   ::= {er1645v2Lan3MCIpEntry 354615296}

er1645v2Lan3MCIpRipRxVer OBJECT-TYPE
   SYNTAX      INTEGER
               {
               rip1only (0),
               rip2only (1),
               rip12 (2)
               }
   MAX-ACCESS  read-write
   STATUS      current
   DESCRIPTION
      "Path: ethernet3.editConf.ip.rip.rxVersion

       Possibilities:
               rip1only   (0)
               rip2only   (1)
               rip1&2   (2)"
   ::= {er1645v2Lan3MCIpEntry 354680832}

er1645v2Lan3MCIpRipSplitH OBJECT-TYPE
   SYNTAX      INTEGER
               {
               disabled (0),
               enabled (1),
               poisonedReverse (2)
               }
   MAX-ACCESS  read-write
   STATUS      current
   DESCRIPTION
      "Path: ethernet3.editConf.ip.rip.splitHorizon

       Possibilities:
               disabled   (0)
               enabled   (1)
               poisonedReverse   (2)"
   ::= {er1645v2Lan3MCIpEntry 353828864}

er1645v2Lan3MCIpRipAuth OBJECT-TYPE
   SYNTAX      INTEGER
               {
               disabled (0),
               texts (1),
               md5 (2)
               }
   MAX-ACCESS  read-write
   STATUS      current
   DESCRIPTION
      "Path: ethernet3.editConf.ip.rip.authentication

       Possibilities:
               disabled   (0)
               text    (1)
               md5   (2)"
   ::= {er1645v2Lan3MCIpEntry 353501184}

er1645v2Lan3MCIpRipFilter OBJECT-TYPE
   SYNTAX      DisplayString
   MAX-ACCESS  read-write
   STATUS      current
   DESCRIPTION
      "Path: ethernet3.editConf.ip.rip.filter"
   ::= {er1645v2Lan3MCIpEntry 354418688}

er1645v2Lan3MCIpRipFilterIn OBJECT-TYPE
   SYNTAX      DisplayString
   MAX-ACCESS  read-write
   STATUS      current
   DESCRIPTION
      "Path: ethernet3.editConf.ip.rip.filterIn"
   ::= {er1645v2Lan3MCIpEntry 354484224}

er1645v2Lan3MCIpRipClearNextHop OBJECT-TYPE
   SYNTAX      INTEGER
               {
               disabled (0),
               enabled (1)
               }
   MAX-ACCESS  read-write
   STATUS      current
   DESCRIPTION
      "Path: ethernet3.editConf.ip.rip.clearNextHop

       Possibilities:
               disabled   (0)
               enabled   (1)"
   ::= {er1645v2Lan3MCIpEntry 352452608}

er1645v2Lan3MCIpAccPol OBJECT-TYPE
   SYNTAX      DisplayString
   MAX-ACCESS  read-write
   STATUS      current
   DESCRIPTION
      "Path: ethernet3.editConf.ip.accessPolicy"
   ::= {er1645v2Lan3MCIpEntry 704643072}

er1645v2Lan3MCIpAB OBJECT-TYPE
   SYNTAX      DisplayString
   MAX-ACCESS  read-write
   STATUS      current
   DESCRIPTION
      "Path: ethernet3.editConf.ip.trafficPolicy"
   ::= {er1645v2Lan3MCIpEntry 234881024}

er1645v2Lan3MCIpMA OBJECT-TYPE
   SYNTAX      INTEGER
               {
               disabled (0),
               enabled (1)
               }
   MAX-ACCESS  read-write
   STATUS      current
   DESCRIPTION
      "Path: ethernet3.editConf.ip.mgmtAccess

       Possibilities:
               disabled   (0)
               enabled   (1)"
   ::= {er1645v2Lan3MCIpEntry 268435456}

er1645v2Lan3MCIpMF OBJECT-TYPE
   SYNTAX      Integer32
   MAX-ACCESS  read-write
   STATUS      current
   DESCRIPTION
      "Path: ethernet3.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3MCIpEntry 285212672}

er1645v2Lan3MCIpDB OBJECT-TYPE
   SYNTAX      INTEGER
               {
               disabled (0),
               enabled (1)
               }
   MAX-ACCESS  read-write
   STATUS      current
   DESCRIPTION
      "Path: ethernet3.editConf.ip.directedBroadcasts

       Possibilities:
               disabled   (0)
               enabled   (1)"
   ::= {er1645v2Lan3MCIpEntry 369098752}

er1645v2Lan3MCIpIR OBJECT-TYPE
   SYNTAX      INTEGER
               {
               disabled (0),
               enabled (1)
               }
   MAX-ACCESS  read-write
   STATUS      current
   DESCRIPTION
      "Path: ethernet3.editConf.ip.icmpRedirects

       Possibilities:
               disabled   (0)
               enabled   (1)"
   ::= {er1645v2Lan3MCIpEntry 436207616}

er1645v2Lan3MCIpIgmp OBJECT-TYPE
   SYNTAX      INTEGER
               {
               disabled (0),
               proxy (1),
               router (2),
               v3Router (5)
               }
   MAX-ACCESS  read-write
   STATUS      current
   DESCRIPTION
      "Path: ethernet3.editConf.ip.igmp

       Possibilities:
               disabled   (0)
               proxy   (1)
               router   (2)
               v3Router   (5)"
   ::= {er1645v2Lan3MCIpEntry 536870912}

er1645v2Lan3MCIpNN OBJECT-TYPE
   SYNTAX      DisplayString
   MAX-ACCESS  read-write
   STATUS      current
   DESCRIPTION
      "Path: ethernet3.editConf.ip.nat"
   ::= {er1645v2Lan3MCIpEntry 452984832}

er1645v2Lan3MCIpVrrp OBJECT-TYPE
   SYNTAX      INTEGER
               {
               disabled (0),
               enabled (1)
               }
   MAX-ACCESS  read-write
   STATUS      current
   DESCRIPTION
      "Path: ethernet3.editConf.ip.vrrp

       Possibilities:
               disabled   (0)
               enabled   (1)"
   ::= {er1645v2Lan3MCIpEntry 721420288}

er1645v2Lan3MCIpPimMode OBJECT-TYPE
   SYNTAX      INTEGER
               {
               disabled (0),
               sparse (1),
               passive (2)
               }
   MAX-ACCESS  read-write
   STATUS      current
   DESCRIPTION
      "Path: ethernet3.editConf.ip.pim.mode

       Possibilities:
               disabled   (0)
               sparse   (1)
               passive   (2)"
   ::= {er1645v2Lan3MCIpEntry 771817472}

er1645v2Lan3MCIpPimDrPriority OBJECT-TYPE
   SYNTAX      Counter32
   MAX-ACCESS  read-write
   STATUS      current
   DESCRIPTION
      "Path: ethernet3.editConf.ip.pim.drPriority

       32 bit unsigned wrappable counter."
   ::= {er1645v2Lan3MCIpEntry 771883008}

er1645v2Lan3MCIpPimHelloTime OBJECT-TYPE
   SYNTAX      TimeTicks
   MAX-ACCESS  read-write
   STATUS      current
   DESCRIPTION
      "Path: ethernet3.editConf.ip.pim.helloTime

       Time in centi-second."
   ::= {er1645v2Lan3MCIpEntry 771948544}

er1645v2Lan3MCIpPimPropagationDelay OBJECT-TYPE
   SYNTAX      TimeTicks
   MAX-ACCESS  read-write
   STATUS      current
   DESCRIPTION
      "Path: ethernet3.editConf.ip.pim.propagationDelay

       Time in centi-second."
   ::= {er1645v2Lan3MCIpEntry 772014080}

er1645v2Lan3MCIpPimOverrideInterval OBJECT-TYPE
   SYNTAX      TimeTicks
   MAX-ACCESS  read-write
   STATUS      current
   DESCRIPTION
      "Path: ethernet3.editConf.ip.pim.overrideInterval

       Time in centi-second."
   ::= {er1645v2Lan3MCIpEntry 772079616}

er1645v2Lan3MCIpPimBsrBorder OBJECT-TYPE
   SYNTAX      INTEGER
               {
               disabled (0),
               enabled (1)
               }
   MAX-ACCESS  read-write
   STATUS      current
   DESCRIPTION
      "Path: ethernet3.editConf.ip.pim.bsrBorder

       Possibilities:
               disabled   (0)
               enabled   (1)"
   ::= {er1645v2Lan3MCIpEntry 772145152}

er1645v2Lan3MCIpPimTtlThreshold OBJECT-TYPE
   SYNTAX      Integer32
   MAX-ACCESS  read-write
   STATUS      current
   DESCRIPTION
      "Path: ethernet3.editConf.ip.pim.ttlThreshold"
   ::= {er1645v2Lan3MCIpEntry 772210688}

er1645v2Lan3MCIpIMNetworkUnreachable OBJECT-TYPE
   SYNTAX      INTEGER
               {
               disabled (0),
               enabled (1)
               }
   MAX-ACCESS  read-write
   STATUS      current
   DESCRIPTION
      "Path: ethernet3.editConf.ip.icmpMessages.networkUnreachable

       Possibilities:
               disabled   (0)
               enabled   (1)"
   ::= {er1645v2Lan3MCIpEntry 788594688}

er1645v2Lan3MCIpIMHostUnreachable OBJECT-TYPE
   SYNTAX      INTEGER
               {
               disabled (0),
               enabled (1)
               }
   MAX-ACCESS  read-write
   STATUS      current
   DESCRIPTION
      "Path: ethernet3.editConf.ip.icmpMessages.hostUnreachable

       Possibilities:
               disabled   (0)
               enabled   (1)"
   ::= {er1645v2Lan3MCIpEntry 788660224}

er1645v2Lan3MCIpIMProtocolUnreachable OBJECT-TYPE
   SYNTAX      INTEGER
               {
               disabled (0),
               enabled (1)
               }
   MAX-ACCESS  read-write
   STATUS      current
   DESCRIPTION
      "Path: ethernet3.editConf.ip.icmpMessages.protocolUnreachable

       Possibilities:
               disabled   (0)
               enabled   (1)"
   ::= {er1645v2Lan3MCIpEntry 788725760}

er1645v2Lan3MCIpIMPortUnreachable OBJECT-TYPE
   SYNTAX      INTEGER
               {
               disabled (0),
               enabled (1)
               }
   MAX-ACCESS  read-write
   STATUS      current
   DESCRIPTION
      "Path: ethernet3.editConf.ip.icmpMessages.portUnreachable

       Possibilities:
               disabled   (0)
               enabled   (1)"
   ::= {er1645v2Lan3MCIpEntry 788791296}

er1645v2Lan3MCIpIMMtuExceeded OBJECT-TYPE
   SYNTAX      INTEGER
               {
               disabled (0),
               enabled (1)
               }
   MAX-ACCESS  read-write
   STATUS      current
   DESCRIPTION
      "Path: ethernet3.editConf.ip.icmpMessages.mtuExceeded

       Possibilities:
               disabled   (0)
               enabled   (1)"
   ::= {er1645v2Lan3MCIpEntry 788856832}

er1645v2Lan3MCIpIMAdminProhibited OBJECT-TYPE
   SYNTAX      INTEGER
               {
               disabled (0),
               enabled (1)
               }
   MAX-ACCESS  read-write
   STATUS      current
   DESCRIPTION
      "Path: ethernet3.editConf.ip.icmpMessages.adminProhibited

       Possibilities:
               disabled   (0)
               enabled   (1)"
   ::= {er1645v2Lan3MCIpEntry 788922368}

er1645v2Lan3MCIpIMTtlExceeded OBJECT-TYPE
   SYNTAX      INTEGER
               {
               disabled (0),
               enabled (1)
               }
   MAX-ACCESS  read-write
   STATUS      current
   DESCRIPTION
      "Path: ethernet3.editConf.ip.icmpMessages.ttlExceeded

       Possibilities:
               disabled   (0)
               enabled   (1)"
   ::= {er1645v2Lan3MCIpEntry 788987904}

er1645v2Lan3MCIpIMRedirect OBJECT-TYPE
   SYNTAX      INTEGER
               {
               disabled (0),
               enabled (1)
               }
   MAX-ACCESS  read-write
   STATUS      current
   DESCRIPTION
      "Path: ethernet3.editConf.ip.icmpMessages.redirect

       Possibilities:
               disabled   (0)
               enabled   (1)"
   ::= {er1645v2Lan3MCIpEntry 789053440}

er1645v2Lan3MCIpSaddr OBJECT-TYPE
   SYNTAX      SEQUENCE OF Er1645v2Lan3MCIpSaddrEntry
   MAX-ACCESS  not-accessible
   STATUS      current
   DESCRIPTION
      ""
   ::= {er1645v2Lan3MCIp 385875968}

er1645v2Lan3MCIpSaddrEntry OBJECT-TYPE
   SYNTAX      Er1645v2Lan3MCIpSaddrEntry
   MAX-ACCESS  not-accessible
   STATUS      current
   DESCRIPTION
      ""
   INDEX      { er1645v2Lan3MCIpSaddrTableIx }
   ::= {er1645v2Lan3MCIpSaddr 1}

Er1645v2Lan3MCIpSaddrEntry ::=
   SEQUENCE
      {
      er1645v2Lan3MCIpSaddrActions
         VariableLengthTableActions,
      er1645v2Lan3MCIpSaddrTableIx
         TableIndex,
      er1645v2Lan3MCIpSaddrAddress
         IpAddress,
      er1645v2Lan3MCIpSaddrNetMask
         IpAddress
      }

er1645v2Lan3MCIpSaddrActions OBJECT-TYPE
   SYNTAX      VariableLengthTableActions
   MAX-ACCESS  read-write
   STATUS      current
   DESCRIPTION
      "By way of this field, some manipulations
       on this table may be performed."
   ::= {er1645v2Lan3MCIpSaddrEntry 2}

er1645v2Lan3MCIpSaddrTableIx OBJECT-TYPE
   SYNTAX      TableIndex
   MAX-ACCESS  not-accessible
   STATUS      current
   DESCRIPTION
      ""
   ::= {er1645v2Lan3MCIpSaddrEntry 11}

er1645v2Lan3MCIpSaddrAddress OBJECT-TYPE
   SYNTAX      IpAddress
   MAX-ACCESS  read-write
   STATUS      current
   DESCRIPTION
      "Path: ethernet3.editConf.ip.secondaryIp.address"
   ::= {er1645v2Lan3MCIpSaddrEntry 2030043136}

er1645v2Lan3MCIpSaddrNetMask OBJECT-TYPE
   SYNTAX      IpAddress
   MAX-ACCESS  read-write
   STATUS      current
   DESCRIPTION
      "Path: ethernet3.editConf.ip.secondaryIp.netMask"
   ::= {er1645v2Lan3MCIpSaddrEntry 2063597568}

er1645v2Lan3MCIpH OBJECT-TYPE
   SYNTAX      SEQUENCE OF Er1645v2Lan3MCIpHEntry
   MAX-ACCESS  not-accessible
   STATUS      current
   DESCRIPTION
      ""
   ::= {er1645v2Lan3MCIp 251658240}

er1645v2Lan3MCIpHEntry OBJECT-TYPE
   SYNTAX      Er1645v2Lan3MCIpHEntry
   MAX-ACCESS  not-accessible
   STATUS      current
   DESCRIPTION
      ""
   INDEX      { er1645v2Lan3MCIpHTableIx }
   ::= {er1645v2Lan3MCIpH 1}

Er1645v2Lan3MCIpHEntry ::=
   SEQUENCE
      {
      er1645v2Lan3MCIpHActions
         VariableLengthTableActions,
      er1645v2Lan3MCIpHTableIx
         TableIndex,
      er1645v2Lan3MCIpHAddress
         IpAddress,
      er1645v2Lan3MCIpHDhcpRelayOptionSubscriberId
         DisplayString
      }

er1645v2Lan3MCIpHActions OBJECT-TYPE
   SYNTAX      VariableLengthTableActions
   MAX-ACCESS  read-write
   STATUS      current
   DESCRIPTION
      "By way of this field, some manipulations
       on this table may be performed."
   ::= {er1645v2Lan3MCIpHEntry 2}

er1645v2Lan3MCIpHTableIx OBJECT-TYPE
   SYNTAX      TableIndex
   MAX-ACCESS  not-accessible
   STATUS      current
   DESCRIPTION
      ""
   ::= {er1645v2Lan3MCIpHEntry 11}

er1645v2Lan3MCIpHAddress OBJECT-TYPE
   SYNTAX      IpAddress
   MAX-ACCESS  read-write
   STATUS      current
   DESCRIPTION
      "Path: ethernet3.editConf.ip.helpers.address"
   ::= {er1645v2Lan3MCIpHEntry 16777216}

er1645v2Lan3MCIpHDhcpRelayOptionSubscriberId OBJECT-TYPE
   SYNTAX      DisplayString
   MAX-ACCESS  read-write
   STATUS      current
   DESCRIPTION
      "Path: ethernet3.editConf.ip.helpers.dhcpRelayOption.subscriberId"
   ::= {er1645v2Lan3MCIpHEntry 33947648}


er1645v2Lan3MCAdapter OBJECT-TYPE
   SYNTAX      INTEGER
               {
               autoDetect (0),
               s10MbhalfDuplex (1),
               s10MbfullDuplex (2),
               s100MbhalfDuplex (3),
               s100MbfullDuplex (4),
               s1000MbfullDuplex (6)
               }
   MAX-ACCESS  read-write
   STATUS      current
   DESCRIPTION
      "Path: ethernet3.editConf.adapter

       Possibilities:
               autoDetect   (0)
               10Mb/halfDuplex   (1)
               10Mb/fullDuplex   (2)
               100Mb/halfDuplex   (3)
               100Mb/fullDuplex   (4)
               1000Mb/fullDuplex   (6)"
   ::= {er1645v2Lan3MC 32}


er1645v2Lan3MCVlan OBJECT IDENTIFIER ::= {er1645v2Lan3MC 33}

er1645v2Lan3MCVlanSSCTable OBJECT-TYPE
   SYNTAX      SEQUENCE OF Er1645v2Lan3MCVlanEntry
   MAX-ACCESS  not-accessible
   STATUS      current
   DESCRIPTION
      ""
   ::= {er1645v2Lan3MCVlan 1}

er1645v2Lan3MCVlanEntry OBJECT-TYPE
   SYNTAX      Er1645v2Lan3MCVlanEntry
   MAX-ACCESS  not-accessible
   STATUS      current
   DESCRIPTION
      ""
   INDEX      { er1645v2Lan3MCVlanTableIx }
   ::= {er1645v2Lan3MCVlanSSCTable 1}

Er1645v2Lan3MCVlanEntry ::=
   SEQUENCE
      {
      er1645v2Lan3MCVlanActions
         VariableLengthTableActions,
      er1645v2Lan3MCVlanTableIx
         TableIndex,
      er1645v2Lan3MCVlanName
         DisplayString,
      er1645v2Lan3MCVlanRemark
         DisplayString,
      er1645v2Lan3MCVlanAdminStatus
         INTEGER,
      er1645v2Lan3MCVlanMode
         INTEGER,
      er1645v2Lan3MCVlanPriorityPolicy
         DisplayString,
      er1645v2Lan3MCVlanIpVrfRouter
         DisplayString,
      er1645v2Lan3MCVlanIpAdr
         IpAddress,
      er1645v2Lan3MCVlanIpNetm
         IpAddress,
      er1645v2Lan3MCVlanIpSNetName
         INTEGER,
      er1645v2Lan3MCVlanIpSNetCust
         DisplayString,
      er1645v2Lan3MCVlanIpDhcpC
         INTEGER,
      er1645v2Lan3MCVlanIpDhcpGatewayPreference
         Integer32,
      er1645v2Lan3MCVlanIpDhcpRoutePreference
         Integer32,
      er1645v2Lan3MCVlanIpDhcpDnsPreference
         Integer32,
      er1645v2Lan3MCVlanIpMtu
         Integer32,
      er1645v2Lan3MCVlanIpMssAdjust
         INTEGER,
      er1645v2Lan3MCVlanIpRipMetric
         Integer32,
      er1645v2Lan3MCVlanIpRipMetricOut
         Integer32,
      er1645v2Lan3MCVlanIpRipMode
         INTEGER,
      er1645v2Lan3MCVlanIpRipTxVer
         INTEGER,
      er1645v2Lan3MCVlanIpRipRxVer
         INTEGER,
      er1645v2Lan3MCVlanIpRipSplitH
         INTEGER,
      er1645v2Lan3MCVlanIpRipAuth
         INTEGER,
      er1645v2Lan3MCVlanIpRipFilter
         DisplayString,
      er1645v2Lan3MCVlanIpRipFilterIn
         DisplayString,
      er1645v2Lan3MCVlanIpRipClearNextHop
         INTEGER,
      er1645v2Lan3MCVlanIpAccPol
         DisplayString,
      er1645v2Lan3MCVlanIpAB
         DisplayString,
      er1645v2Lan3MCVlanIpMA
         INTEGER,
      er1645v2Lan3MCVlanIpMF
         Integer32,
      er1645v2Lan3MCVlanIpDB
         INTEGER,
      er1645v2Lan3MCVlanIpIR
         INTEGER,
      er1645v2Lan3MCVlanIpIgmp
         INTEGER,
      er1645v2Lan3MCVlanIpNN
         DisplayString,
      er1645v2Lan3MCVlanIpVrrp
         INTEGER,
      er1645v2Lan3MCVlanIpPimMode
         INTEGER,
      er1645v2Lan3MCVlanIpPimDrPriority
         Counter32,
      er1645v2Lan3MCVlanIpPimHelloTime
         TimeTicks,
      er1645v2Lan3MCVlanIpPimPropagationDelay
         TimeTicks,
      er1645v2Lan3MCVlanIpPimOverrideInterval
         TimeTicks,
      er1645v2Lan3MCVlanIpPimBsrBorder
         INTEGER,
      er1645v2Lan3MCVlanIpPimTtlThreshold
         Integer32,
      er1645v2Lan3MCVlanIpIMNetworkUnreachable
         INTEGER,
      er1645v2Lan3MCVlanIpIMHostUnreachable
         INTEGER,
      er1645v2Lan3MCVlanIpIMProtocolUnreachable
         INTEGER,
      er1645v2Lan3MCVlanIpIMPortUnreachable
         INTEGER,
      er1645v2Lan3MCVlanIpIMMtuExceeded
         INTEGER,
      er1645v2Lan3MCVlanIpIMAdminProhibited
         INTEGER,
      er1645v2Lan3MCVlanIpIMTtlExceeded
         INTEGER,
      er1645v2Lan3MCVlanIpIMRedirect
         INTEGER,
      er1645v2Lan3MCVlanIpV6VrfRouter
         DisplayString,
      er1645v2Lan3MCVlanIpV6AddrAutoConfigNrDupAddrDetects
         Integer32,
      er1645v2Lan3MCVlanIpV6AddrAutoConfigAcceptRa
         INTEGER,
      er1645v2Lan3MCVlanIpV6AddrAutoConfigAcceptRaRdnss
         INTEGER,
      er1645v2Lan3MCVlanIpV6AddrAutoConfigAcceptRaDnssl
         INTEGER,
      er1645v2Lan3MCVlanIpV6DefaultRoute
         INTEGER,
      er1645v2Lan3MCVlanIpV6RaSend
         INTEGER,
      er1645v2Lan3MCVlanIpV6RaMinInterval
         TimeTicks,
      er1645v2Lan3MCVlanIpV6RaMaxInterval
         TimeTicks,
      er1645v2Lan3MCVlanIpV6RaManagedFlag
         INTEGER,
      er1645v2Lan3MCVlanIpV6RaOtherConfFlag
         INTEGER,
      er1645v2Lan3MCVlanIpV6RaLinkMtu
         Integer32,
      er1645v2Lan3MCVlanIpV6RaReachableTime
         TimeTicks,
      er1645v2Lan3MCVlanIpV6RaRetransmitTime
         TimeTicks,
      er1645v2Lan3MCVlanIpV6RaHopLimit
         Integer32,
      er1645v2Lan3MCVlanIpV6RaDefaultLifeTime
         TimeTicks,
      er1645v2Lan3MCVlanIpV6RaDnsOptionsRdnssLifeTime
         TimeTicks,
      er1645v2Lan3MCVlanIpV6RaDnsOptionsRdnssImportServers
         INTEGER,
      er1645v2Lan3MCVlanIpV6RaDnsOptionsDnsslLifeTime
         TimeTicks,
      er1645v2Lan3MCVlanIpV6RaDnsOptionsDnsslImportDomains
         INTEGER,
      er1645v2Lan3MCVlanIpV6RsSend
         INTEGER,
      er1645v2Lan3MCVlanIpV6RsMaxRandomDelay
         TimeTicks,
      er1645v2Lan3MCVlanIpV6RsInterval
         TimeTicks,
      er1645v2Lan3MCVlanIpV6RsMaxSolicitations
         Integer32,
      er1645v2Lan3MCVlanIpV6TrafficPolicyInbound
         DisplayString,
      er1645v2Lan3MCVlanIpV6TrafficPolicyOutbound
         DisplayString,
      er1645v2Lan3MCVlanIpV6FirewallZone
         DisplayString,
      er1645v2Lan3MCVlanIpV6DhcpClientAddrAC
         INTEGER,
      er1645v2Lan3MCVlanIpV6DhcpClientPrDelMode
         INTEGER,
      er1645v2Lan3MCVlanIpV6DhcpClientPrDelPool
         DisplayString,
      er1645v2Lan3MCVlanIpV6DhcpClientPrDelPdExclOpt
         INTEGER,
      er1645v2Lan3MCVlanIpV6DhcpClientDnsServerPref
         Integer32,
      er1645v2Lan3MCVlanIpV6DhcpClientRapidCommit
         INTEGER,
      er1645v2Lan3MCVlanIpV6DhcpClientTimersSolTimeOut
         TimeTicks,
      er1645v2Lan3MCVlanIpV6DhcpClientTimersSolMaxRt
         TimeTicks,
      er1645v2Lan3MCVlanIpV6DhcpClientTimersInfoRefresh
         TimeTicks,
      er1645v2Lan3MCVlanIpV6DhcpServerMode
         INTEGER,
      er1645v2Lan3MCVlanIpV6DhcpServerPreference
         Integer32,
      er1645v2Lan3MCVlanIpV6DhcpServerPool
         DisplayString,
      er1645v2Lan3MCVlanIpV6DhcpServerRapidCommit
         INTEGER,
      er1645v2Lan3MCVlanIpV6DhcpServerTimersInfoRefresh
         TimeTicks,
      er1645v2Lan3MCVlanIpV6DhcpRelayMode
         INTEGER,
      er1645v2Lan3MCVlanIpV6SendRedirect
         INTEGER,
      er1645v2Lan3MCVlanIpV6LinkMtu
         Integer32,
      er1645v2Lan3MCVlanIpV6InterfaceId
         OCTET STRING,
      er1645v2Lan3MCVlanIpV6MF
         Integer32,
      er1645v2Lan3MCVlanIpV6IcmpMessagesNoRoute
         INTEGER,
      er1645v2Lan3MCVlanIpV6IcmpMessagesBeyondScope
         INTEGER,
      er1645v2Lan3MCVlanIpV6IcmpMessagesAddressUnreachable
         INTEGER,
      er1645v2Lan3MCVlanIpV6IcmpMessagesPortUnreachable
         INTEGER,
      er1645v2Lan3MCVlanIpV6IcmpMessagesPacketTooBig
         INTEGER,
      er1645v2Lan3MCVlanIpV6IcmpMessagesHopLimitExceeded
         INTEGER,
      er1645v2Lan3MCVlanIpV6IcmpMessagesFragTimeExceeded
         INTEGER,
      er1645v2Lan3MCVlanIpV6IcmpMessagesHeaderFieldErr
         INTEGER,
      er1645v2Lan3MCVlanIpV6IcmpMessagesOptionUnrecognized
         INTEGER,
      er1645v2Lan3MCVlanIpV6IcmpMessagesRedirect
         INTEGER,
      er1645v2Lan3MCVlanBridgingAccList
         DisplayString,
      er1645v2Lan3MCVlanBridgingInACL
         DisplayString,
      er1645v2Lan3MCVlanBridgingTp
         DisplayString,
      er1645v2Lan3MCVlanBridgingBrGrp
         DisplayString,
      er1645v2Lan3MCVlanBridgingLimBC
         INTEGER,
      er1645v2Lan3MCVlanBridgingPrivateMode
         INTEGER,
      er1645v2Lan3MCVlanBridgingLearning
         INTEGER,
      er1645v2Lan3MCVlanBridgingMaxCacheSize
         INTEGER,
      er1645v2Lan3MCVlanBridgingRelearnDropOnRelearn
         INTEGER,
      er1645v2Lan3MCVlanBridgingRelearnShutdownThreshold
         Integer32,
      er1645v2Lan3MCVlanBridgingRelearnShutdownTime
         TimeTicks,
      er1645v2Lan3MCVlanBridgingRelearnLoopDetection
         INTEGER,
      er1645v2Lan3MCVlanBridgingRelearnLoopDetectionInterval
         TimeTicks,
      er1645v2Lan3MCVlanBridgingVlanMemberShip
         INTEGER,
      er1645v2Lan3MCVlanBridgingVlTUntaggedAction
         INTEGER,
      er1645v2Lan3MCVlanBridgingVlTUntaggedTagInfoTpid
         INTEGER,
      er1645v2Lan3MCVlanBridgingVlTUntaggedTagInfoVid
         Integer32,
      er1645v2Lan3MCVlanBridgingVlTUnknownVlansAction
         INTEGER,
      er1645v2Lan3MCVlanBridgingVlTUnknownVlansTagInfoTpid
         INTEGER,
      er1645v2Lan3MCVlanBridgingVlTUnknownVlansTagInfoVid
         Integer32,
      er1645v2Lan3MCVlanBridgingDot1adType
         INTEGER,
      er1645v2Lan3MCVlanBridgingPriority
         Integer32,
      er1645v2Lan3MCVlanBridgingPathCost
         Integer32,
      er1645v2Lan3MCVlanBridgingInternalPathCost
         Integer32,
      er1645v2Lan3MCVlanBridgingTCD
         INTEGER,
      er1645v2Lan3MCVlanBridgingRestrictedRole
         INTEGER,
      er1645v2Lan3MCVlanBridgingAdminEdge
         INTEGER,
      er1645v2Lan3MCVlanBridgingOamMacDeviceMac
         DisplayString,
      er1645v2Lan3MCVlanBridgingOamMacUserMac
         OCTET STRING,
      er1645v2Lan3MCVlanBridgingOamMacBridgeMac
         DisplayString,
      er1645v2Lan3MCVlanBridgingMgmtInline
         INTEGER,
      er1645v2Lan3MCVlanBridgingL2ptMode
         INTEGER,
      er1645v2Lan3MCVlanBridgingL2ptProtocols
         Integer32,
      er1645v2Lan3MCVlanBridgingL2ptDestMac
         OCTET STRING,
      er1645v2Lan3MCVlanBridgingL2ptCos
         INTEGER,
      er1645v2Lan3MCVlanBridgingL2ptDropThrStp
         INTEGER,
      er1645v2Lan3MCVlanBridgingL2ptDropThrLldp
         INTEGER,
      er1645v2Lan3MCVlanBridgingL2ptDropThrOam
         INTEGER,
      er1645v2Lan3MCVlanBridgingL2ptDropThrCdp
         INTEGER,
      er1645v2Lan3MCVlanBridgingL2ptDropThrVtp
         INTEGER,
      er1645v2Lan3MCVlanBridgingL2ptDropThrLacp
         INTEGER,
      er1645v2Lan3MCVlanBridgingL2ptDropThrEfmOam
         INTEGER,
      er1645v2Lan3MCVlanBridgingL2ptDropThrPvst
         INTEGER,
      er1645v2Lan3MCVlanBridgingL2ptDropThrMmrp
         INTEGER,
      er1645v2Lan3MCVlanBridgingL2ptDropThrMvrp
         INTEGER,
      er1645v2Lan3MCVlanBridgingL2ptDropThrGvrp
         INTEGER,
      er1645v2Lan3MCVlanBridgingL2ptDropThrGmrp
         INTEGER,
      er1645v2Lan3MCVlanBridgingL2ptDropThrDtp
         INTEGER,
      er1645v2Lan3MCVlanBridgingL2ptDropThrPagp
         INTEGER,
      er1645v2Lan3MCVlanBridgingL2ptDropThrUdld
         INTEGER,
      er1645v2Lan3MCVlanVlanVid
         INTEGER,
      er1645v2Lan3MCVlanVlanVidExtensionSingle
         OCTET STRING,
      er1645v2Lan3MCVlanVlanVidExtensionEndVid
         Integer32,
      er1645v2Lan3MCVlanVlanTpid
         INTEGER,
      er1645v2Lan3MCVlanVlanTagSign
         INTEGER,
      er1645v2Lan3MCVlanVlanChTos
         INTEGER,
      er1645v2Lan3MCVlanVlanCTMapP0
         INTEGER,
      er1645v2Lan3MCVlanVlanCTMapP1
         INTEGER,
      er1645v2Lan3MCVlanVlanCTMapP2
         INTEGER,
      er1645v2Lan3MCVlanVlanCTMapP3
         INTEGER,
      er1645v2Lan3MCVlanVlanCTMapP4
         INTEGER,
      er1645v2Lan3MCVlanVlanCTMapP5
         INTEGER,
      er1645v2Lan3MCVlanVlanCTMapP6
         INTEGER,
      er1645v2Lan3MCVlanVlanCTMapP7
         INTEGER,
      er1645v2Lan3MCVlanVlanTxCos
         INTEGER,
      er1645v2Lan3MCVlanVlanCCMapP0
         Integer32,
      er1645v2Lan3MCVlanVlanCCMapP1
         Integer32,
      er1645v2Lan3MCVlanVlanCCMapP2
         Integer32,
      er1645v2Lan3MCVlanVlanCCMapP3
         Integer32,
      er1645v2Lan3MCVlanVlanCCMapP4
         Integer32,
      er1645v2Lan3MCVlanVlanCCMapP5
         Integer32,
      er1645v2Lan3MCVlanVlanCCMapP6
         Integer32,
      er1645v2Lan3MCVlanVlanCCMapP7
         Integer32,
      er1645v2Lan3MCVlanVlanQCMapQueue1
         Integer32,
      er1645v2Lan3MCVlanVlanQCMapQueue2
         Integer32,
      er1645v2Lan3MCVlanVlanQCMapQueue3
         Integer32,
      er1645v2Lan3MCVlanVlanQCMapQueue4
         Integer32,
      er1645v2Lan3MCVlanVlanQCMapQueue5
         Integer32,
      er1645v2Lan3MCVlanVlanQCMapLowDelayQueue
         Integer32,
      er1645v2Lan3MCVlanVlanQCMapLowDelay2Queue
         Integer32,
      er1645v2Lan3MCVlanVlanQCMapSystemQueue
         Integer32,
      er1645v2Lan3MCVlanVlanQinQSVid
         Integer32,
      er1645v2Lan3MCVlanVlanQinQSTpid
         INTEGER,
      er1645v2Lan3MCVlanVlanArpTimeOut
         TimeTicks,
      er1645v2Lan3MCVlanVlanArpProxyArp
         INTEGER,
      er1645v2Lan3MCVlanBandwidthMode
         INTEGER,
      er1645v2Lan3MCVlanBandwidthCir
         Integer32,
      er1645v2Lan3MCVlanBandwidthEir
         Integer32,
      er1645v2Lan3MCVlanBandwidthUnit
         INTEGER,
      er1645v2Lan3MCVlanBandwidthTc
         INTEGER,
      er1645v2Lan3MCVlanBandwidthTcFactor
         INTEGER,
      er1645v2Lan3MCVlanBandwidthCorrType
         INTEGER,
      er1645v2Lan3MCVlanBandwidthCorrPredefEncapsFrameRelay
         DisplayString,
      er1645v2Lan3MCVlanBandwidthCorrPredefEncapsPpp
         DisplayString,
      er1645v2Lan3MCVlanBandwidthCorrPredefEncapsAtmHl
         INTEGER,
      er1645v2Lan3MCVlanBandwidthCorrPredefEncapsAtmMp
         INTEGER,
      er1645v2Lan3MCVlanBandwidthCorrPredefEncapsHdlc
         DisplayString,
      er1645v2Lan3MCVlanBandwidthCorrPredefEncapsEfmFs
         Integer32,
      er1645v2Lan3MCVlanBandwidthCorrPredefEncapsEfmIb
         Integer32,
      er1645v2Lan3MCVlanBandwidthCorrPredefMode
         INTEGER,
      er1645v2Lan3MCVlanBandwidthCorrManualOverhead
         Integer32,
      er1645v2Lan3MCVlanBandwidthCorrManualFrameData
         Counter32,
      er1645v2Lan3MCVlanBandwidthCorrManualFrameHeader
         Counter32,
      er1645v2Lan3MCVlanBandwidthMaxFifoQLen
         Integer32,
      er1645v2Lan3MCVlanBandwidthDeFlagCir
         INTEGER,
      er1645v2Lan3MCVlanBandwidthDeFlagEir
         INTEGER,
      er1645v2Lan3MCVlanBandwidthDeFlagViolate
         INTEGER,
      er1645v2Lan3MCVlanBandwidthActCirActNone
         OCTET STRING,
      er1645v2Lan3MCVlanBandwidthActCirActEthCos1
         INTEGER,
      er1645v2Lan3MCVlanBandwidthActCirActEthDei1
         INTEGER,
      er1645v2Lan3MCVlanBandwidthActCirActEthCos2
         INTEGER,
      er1645v2Lan3MCVlanBandwidthActCirActEthDei2
         INTEGER,
      er1645v2Lan3MCVlanBandwidthActCirActEthCos3
         INTEGER,
      er1645v2Lan3MCVlanBandwidthActCirActEthDei3
         INTEGER,
      er1645v2Lan3MCVlanBandwidthActCirActEthCos4
         INTEGER,
      er1645v2Lan3MCVlanBandwidthActCirActEthDei4
         INTEGER,
      er1645v2Lan3MCVlanBandwidthActCirActEthCos5
         INTEGER,
      er1645v2Lan3MCVlanBandwidthActCirActEthDei5
         INTEGER,
      er1645v2Lan3MCVlanBandwidthActCirActEthCos6
         INTEGER,
      er1645v2Lan3MCVlanBandwidthActCirActEthDei6
         INTEGER,
      er1645v2Lan3MCVlanBandwidthActCirActEthCos7
         INTEGER,
      er1645v2Lan3MCVlanBandwidthActCirActEthDei7
         INTEGER,
      er1645v2Lan3MCVlanBandwidthActCirActEthCos8
         INTEGER,
      er1645v2Lan3MCVlanBandwidthActCirActEthDei8
         INTEGER,
      er1645v2Lan3MCVlanBandwidthActCirActEthTos
         INTEGER,
      er1645v2Lan3MCVlanBandwidthActCirActEthQueue
         INTEGER,
      er1645v2Lan3MCVlanBandwidthActCirActEthDrpLev
         INTEGER,
      er1645v2Lan3MCVlanBandwidthActCirActEthDeFlag
         INTEGER,
      er1645v2Lan3MCVlanBandwidthActCirActIpTos
         INTEGER,
      er1645v2Lan3MCVlanBandwidthActCirActIpQueue
         INTEGER,
      er1645v2Lan3MCVlanBandwidthActCirActIpDrpLev
         INTEGER,
      er1645v2Lan3MCVlanBandwidthActCirActIpDeFlag
         INTEGER,
      er1645v2Lan3MCVlanBandwidthActEirActNone
         OCTET STRING,
      er1645v2Lan3MCVlanBandwidthActEirActEthCos1
         INTEGER,
      er1645v2Lan3MCVlanBandwidthActEirActEthDei1
         INTEGER,
      er1645v2Lan3MCVlanBandwidthActEirActEthCos2
         INTEGER,
      er1645v2Lan3MCVlanBandwidthActEirActEthDei2
         INTEGER,
      er1645v2Lan3MCVlanBandwidthActEirActEthCos3
         INTEGER,
      er1645v2Lan3MCVlanBandwidthActEirActEthDei3
         INTEGER,
      er1645v2Lan3MCVlanBandwidthActEirActEthCos4
         INTEGER,
      er1645v2Lan3MCVlanBandwidthActEirActEthDei4
         INTEGER,
      er1645v2Lan3MCVlanBandwidthActEirActEthCos5
         INTEGER,
      er1645v2Lan3MCVlanBandwidthActEirActEthDei5
         INTEGER,
      er1645v2Lan3MCVlanBandwidthActEirActEthCos6
         INTEGER,
      er1645v2Lan3MCVlanBandwidthActEirActEthDei6
         INTEGER,
      er1645v2Lan3MCVlanBandwidthActEirActEthCos7
         INTEGER,
      er1645v2Lan3MCVlanBandwidthActEirActEthDei7
         INTEGER,
      er1645v2Lan3MCVlanBandwidthActEirActEthCos8
         INTEGER,
      er1645v2Lan3MCVlanBandwidthActEirActEthDei8
         INTEGER,
      er1645v2Lan3MCVlanBandwidthActEirActEthTos
         INTEGER,
      er1645v2Lan3MCVlanBandwidthActEirActEthQueue
         INTEGER,
      er1645v2Lan3MCVlanBandwidthActEirActEthDrpLev
         INTEGER,
      er1645v2Lan3MCVlanBandwidthActEirActEthDeFlag
         INTEGER,
      er1645v2Lan3MCVlanBandwidthActEirActIpTos
         INTEGER,
      er1645v2Lan3MCVlanBandwidthActEirActIpQueue
         INTEGER,
      er1645v2Lan3MCVlanBandwidthActEirActIpDrpLev
         INTEGER,
      er1645v2Lan3MCVlanBandwidthActEirActIpDeFlag
         INTEGER,
      er1645v2Lan3MCVlanBandwidthActViolActNone
         OCTET STRING,
      er1645v2Lan3MCVlanBandwidthActViolActDrop
         OCTET STRING,
      er1645v2Lan3MCVlanBandwidthActViolActEthCos1
         INTEGER,
      er1645v2Lan3MCVlanBandwidthActViolActEthDei1
         INTEGER,
      er1645v2Lan3MCVlanBandwidthActViolActEthCos2
         INTEGER,
      er1645v2Lan3MCVlanBandwidthActViolActEthDei2
         INTEGER,
      er1645v2Lan3MCVlanBandwidthActViolActEthCos3
         INTEGER,
      er1645v2Lan3MCVlanBandwidthActViolActEthDei3
         INTEGER,
      er1645v2Lan3MCVlanBandwidthActViolActEthCos4
         INTEGER,
      er1645v2Lan3MCVlanBandwidthActViolActEthDei4
         INTEGER,
      er1645v2Lan3MCVlanBandwidthActViolActEthCos5
         INTEGER,
      er1645v2Lan3MCVlanBandwidthActViolActEthDei5
         INTEGER,
      er1645v2Lan3MCVlanBandwidthActViolActEthCos6
         INTEGER,
      er1645v2Lan3MCVlanBandwidthActViolActEthDei6
         INTEGER,
      er1645v2Lan3MCVlanBandwidthActViolActEthCos7
         INTEGER,
      er1645v2Lan3MCVlanBandwidthActViolActEthDei7
         INTEGER,
      er1645v2Lan3MCVlanBandwidthActViolActEthCos8
         INTEGER,
      er1645v2Lan3MCVlanBandwidthActViolActEthDei8
         INTEGER,
      er1645v2Lan3MCVlanBandwidthActViolActEthTos
         INTEGER,
      er1645v2Lan3MCVlanBandwidthActViolActEthQueue
         INTEGER,
      er1645v2Lan3MCVlanBandwidthActViolActEthDrpLev
         INTEGER,
      er1645v2Lan3MCVlanBandwidthActViolActEthDeFlag
         INTEGER,
      er1645v2Lan3MCVlanBandwidthActViolActIpTos
         INTEGER,
      er1645v2Lan3MCVlanBandwidthActViolActIpQueue
         INTEGER,
      er1645v2Lan3MCVlanBandwidthActViolActIpDrpLev
         INTEGER,
      er1645v2Lan3MCVlanBandwidthActViolActIpDeFlag
         INTEGER,
      er1645v2Lan3MCVlanInbBwMode
         INTEGER,
      er1645v2Lan3MCVlanInbBwCir
         Integer32,
      er1645v2Lan3MCVlanInbBwEir
         Integer32,
      er1645v2Lan3MCVlanInbBwUnit
         INTEGER,
      er1645v2Lan3MCVlanInbBwTc
         INTEGER,
      er1645v2Lan3MCVlanInbBwTcFactor
         INTEGER,
      er1645v2Lan3MCVlanInbBwCorrType
         INTEGER,
      er1645v2Lan3MCVlanInbBwCorrPredefEncapsFrameRelay
         DisplayString,
      er1645v2Lan3MCVlanInbBwCorrPredefEncapsPpp
         DisplayString,
      er1645v2Lan3MCVlanInbBwCorrPredefEncapsAtmHl
         INTEGER,
      er1645v2Lan3MCVlanInbBwCorrPredefEncapsAtmMp
         INTEGER,
      er1645v2Lan3MCVlanInbBwCorrPredefEncapsHdlc
         DisplayString,
      er1645v2Lan3MCVlanInbBwCorrPredefEncapsEfmFs
         Integer32,
      er1645v2Lan3MCVlanInbBwCorrPredefEncapsEfmIb
         Integer32,
      er1645v2Lan3MCVlanInbBwCorrPredefMode
         INTEGER,
      er1645v2Lan3MCVlanInbBwCorrManualOverhead
         Integer32,
      er1645v2Lan3MCVlanInbBwCorrManualFrameData
         Counter32,
      er1645v2Lan3MCVlanInbBwCorrManualFrameHeader
         Counter32,
      er1645v2Lan3MCVlanInbBwMaxFifoQLen
         Integer32,
      er1645v2Lan3MCVlanInbBwPriorityPolicy
         DisplayString,
      er1645v2Lan3MCVlanInbBwDeFlagCir
         INTEGER,
      er1645v2Lan3MCVlanInbBwDeFlagEir
         INTEGER,
      er1645v2Lan3MCVlanInbBwDeFlagViolate
         INTEGER,
      er1645v2Lan3MCVlanInbBwActCirActNone
         OCTET STRING,
      er1645v2Lan3MCVlanInbBwActCirActEthCos1
         INTEGER,
      er1645v2Lan3MCVlanInbBwActCirActEthDei1
         INTEGER,
      er1645v2Lan3MCVlanInbBwActCirActEthCos2
         INTEGER,
      er1645v2Lan3MCVlanInbBwActCirActEthDei2
         INTEGER,
      er1645v2Lan3MCVlanInbBwActCirActEthCos3
         INTEGER,
      er1645v2Lan3MCVlanInbBwActCirActEthDei3
         INTEGER,
      er1645v2Lan3MCVlanInbBwActCirActEthCos4
         INTEGER,
      er1645v2Lan3MCVlanInbBwActCirActEthDei4
         INTEGER,
      er1645v2Lan3MCVlanInbBwActCirActEthCos5
         INTEGER,
      er1645v2Lan3MCVlanInbBwActCirActEthDei5
         INTEGER,
      er1645v2Lan3MCVlanInbBwActCirActEthCos6
         INTEGER,
      er1645v2Lan3MCVlanInbBwActCirActEthDei6
         INTEGER,
      er1645v2Lan3MCVlanInbBwActCirActEthCos7
         INTEGER,
      er1645v2Lan3MCVlanInbBwActCirActEthDei7
         INTEGER,
      er1645v2Lan3MCVlanInbBwActCirActEthCos8
         INTEGER,
      er1645v2Lan3MCVlanInbBwActCirActEthDei8
         INTEGER,
      er1645v2Lan3MCVlanInbBwActCirActEthTos
         INTEGER,
      er1645v2Lan3MCVlanInbBwActCirActEthQueue
         INTEGER,
      er1645v2Lan3MCVlanInbBwActCirActEthDrpLev
         INTEGER,
      er1645v2Lan3MCVlanInbBwActCirActEthDeFlag
         INTEGER,
      er1645v2Lan3MCVlanInbBwActCirActIpTos
         INTEGER,
      er1645v2Lan3MCVlanInbBwActCirActIpQueue
         INTEGER,
      er1645v2Lan3MCVlanInbBwActCirActIpDrpLev
         INTEGER,
      er1645v2Lan3MCVlanInbBwActCirActIpDeFlag
         INTEGER,
      er1645v2Lan3MCVlanInbBwActEirActNone
         OCTET STRING,
      er1645v2Lan3MCVlanInbBwActEirActEthCos1
         INTEGER,
      er1645v2Lan3MCVlanInbBwActEirActEthDei1
         INTEGER,
      er1645v2Lan3MCVlanInbBwActEirActEthCos2
         INTEGER,
      er1645v2Lan3MCVlanInbBwActEirActEthDei2
         INTEGER,
      er1645v2Lan3MCVlanInbBwActEirActEthCos3
         INTEGER,
      er1645v2Lan3MCVlanInbBwActEirActEthDei3
         INTEGER,
      er1645v2Lan3MCVlanInbBwActEirActEthCos4
         INTEGER,
      er1645v2Lan3MCVlanInbBwActEirActEthDei4
         INTEGER,
      er1645v2Lan3MCVlanInbBwActEirActEthCos5
         INTEGER,
      er1645v2Lan3MCVlanInbBwActEirActEthDei5
         INTEGER,
      er1645v2Lan3MCVlanInbBwActEirActEthCos6
         INTEGER,
      er1645v2Lan3MCVlanInbBwActEirActEthDei6
         INTEGER,
      er1645v2Lan3MCVlanInbBwActEirActEthCos7
         INTEGER,
      er1645v2Lan3MCVlanInbBwActEirActEthDei7
         INTEGER,
      er1645v2Lan3MCVlanInbBwActEirActEthCos8
         INTEGER,
      er1645v2Lan3MCVlanInbBwActEirActEthDei8
         INTEGER,
      er1645v2Lan3MCVlanInbBwActEirActEthTos
         INTEGER,
      er1645v2Lan3MCVlanInbBwActEirActEthQueue
         INTEGER,
      er1645v2Lan3MCVlanInbBwActEirActEthDrpLev
         INTEGER,
      er1645v2Lan3MCVlanInbBwActEirActEthDeFlag
         INTEGER,
      er1645v2Lan3MCVlanInbBwActEirActIpTos
         INTEGER,
      er1645v2Lan3MCVlanInbBwActEirActIpQueue
         INTEGER,
      er1645v2Lan3MCVlanInbBwActEirActIpDrpLev
         INTEGER,
      er1645v2Lan3MCVlanInbBwActEirActIpDeFlag
         INTEGER,
      er1645v2Lan3MCVlanInbBwActViolActNone
         OCTET STRING,
      er1645v2Lan3MCVlanInbBwActViolActDrop
         OCTET STRING,
      er1645v2Lan3MCVlanInbBwActViolActEthCos1
         INTEGER,
      er1645v2Lan3MCVlanInbBwActViolActEthDei1
         INTEGER,
      er1645v2Lan3MCVlanInbBwActViolActEthCos2
         INTEGER,
      er1645v2Lan3MCVlanInbBwActViolActEthDei2
         INTEGER,
      er1645v2Lan3MCVlanInbBwActViolActEthCos3
         INTEGER,
      er1645v2Lan3MCVlanInbBwActViolActEthDei3
         INTEGER,
      er1645v2Lan3MCVlanInbBwActViolActEthCos4
         INTEGER,
      er1645v2Lan3MCVlanInbBwActViolActEthDei4
         INTEGER,
      er1645v2Lan3MCVlanInbBwActViolActEthCos5
         INTEGER,
      er1645v2Lan3MCVlanInbBwActViolActEthDei5
         INTEGER,
      er1645v2Lan3MCVlanInbBwActViolActEthCos6
         INTEGER,
      er1645v2Lan3MCVlanInbBwActViolActEthDei6
         INTEGER,
      er1645v2Lan3MCVlanInbBwActViolActEthCos7
         INTEGER,
      er1645v2Lan3MCVlanInbBwActViolActEthDei7
         INTEGER,
      er1645v2Lan3MCVlanInbBwActViolActEthCos8
         INTEGER,
      er1645v2Lan3MCVlanInbBwActViolActEthDei8
         INTEGER,
      er1645v2Lan3MCVlanInbBwActViolActEthTos
         INTEGER,
      er1645v2Lan3MCVlanInbBwActViolActEthQueue
         INTEGER,
      er1645v2Lan3MCVlanInbBwActViolActEthDrpLev
         INTEGER,
      er1645v2Lan3MCVlanInbBwActViolActEthDeFlag
         INTEGER,
      er1645v2Lan3MCVlanInbBwActViolActIpTos
         INTEGER,
      er1645v2Lan3MCVlanInbBwActViolActIpQueue
         INTEGER,
      er1645v2Lan3MCVlanInbBwActViolActIpDrpLev
         INTEGER,
      er1645v2Lan3MCVlanInbBwActViolActIpDeFlag
         INTEGER,
      er1645v2Lan3MCVlanPppoE
         INTEGER,
      er1645v2Lan3MCVlanPppLnkMOperation
         INTEGER,
      er1645v2Lan3MCVlanPppLnkMInterval
         TimeTicks,
      er1645v2Lan3MCVlanPppLnkMRepTimeOut
         TimeTicks,
      er1645v2Lan3MCVlanPppLnkMFailsPrmt
         Integer32,
      er1645v2Lan3MCVlanPppAuthentication
         INTEGER,
      er1645v2Lan3MCVlanPppAuthenPeriod
         TimeTicks,
      er1645v2Lan3MCVlanPppSessionName
         DisplayString,
      er1645v2Lan3MCVlanPppSessionSecret
         DisplayString,
      er1645v2Lan3MCVlanPppEncModeSessionSecret
         INTEGER,
      er1645v2Lan3MCVlanPppEncSessionSecret
         DisplayString,
      er1645v2Lan3MCVlanPppServiceName
         DisplayString,
      er1645v2Lan3MCVlanPbbMode
         INTEGER,
      er1645v2Lan3MCVlanPbbTxCos
         Integer32,
      er1645v2Lan3MCVlanPbbIsid
         Integer32,
      er1645v2Lan3MCVlanPbbDestMac
         OCTET STRING,
      er1645v2Lan3MCVlanPbbCustomGroupMac
         OCTET STRING
      }

er1645v2Lan3MCVlanActions OBJECT-TYPE
   SYNTAX      VariableLengthTableActions
   MAX-ACCESS  read-write
   STATUS      current
   DESCRIPTION
      "By way of this field, some manipulations
       on this table may be performed."
   ::= {er1645v2Lan3MCVlanEntry 2}

er1645v2Lan3MCVlanTableIx OBJECT-TYPE
   SYNTAX      TableIndex
   MAX-ACCESS  not-accessible
   STATUS      current
   DESCRIPTION
      ""
   ::= {er1645v2Lan3MCVlanEntry 11}

er1645v2Lan3MCVlanName OBJECT-TYPE
   SYNTAX      DisplayString
   MAX-ACCESS  read-write
   STATUS      current
   DESCRIPTION
      "Path: ethernet3.editConf.vlan.name"
   ::= {er1645v2Lan3MCVlanEntry 16777216}

er1645v2Lan3MCVlanRemark OBJECT-TYPE
   SYNTAX      DisplayString
   MAX-ACCESS  read-write
   STATUS      current
   DESCRIPTION
      "Path: ethernet3.editConf.vlan.remark"
   ::= {er1645v2Lan3MCVlanEntry 1157627904}

er1645v2Lan3MCVlanAdminStatus OBJECT-TYPE
   SYNTAX      INTEGER
               {
               up (1),
               down (2)
               }
   MAX-ACCESS  read-write
   STATUS      current
   DESCRIPTION
      "Path: ethernet3.editConf.vlan.adminStatus

       Possibilities:
               up   (1)
               down   (2)"
   ::= {er1645v2Lan3MCVlanEntry 33554432}

er1645v2Lan3MCVlanMode OBJECT-TYPE
   SYNTAX      INTEGER
               {
               routing (1),
               bridging (2),
               ipV6 (16),
               ipV6ipV4 (17),
               multilink (8)
               }
   MAX-ACCESS  read-write
   STATUS      current
   DESCRIPTION
      "Path: ethernet3.editConf.vlan.mode

       Possibilities:
               routing   (1)
               bridging   (2)
               ipV6   (16)
               ipV6/ipV4   (17)
               multilink   (8)"
   ::= {er1645v2Lan3MCVlanEntry 67108864}

er1645v2Lan3MCVlanPriorityPolicy OBJECT-TYPE
   SYNTAX      DisplayString
   MAX-ACCESS  read-write
   STATUS      current
   DESCRIPTION
      "Path: ethernet3.editConf.vlan.priorityPolicy"
   ::= {er1645v2Lan3MCVlanEntry 83886080}

er1645v2Lan3MCVlanIpVrfRouter OBJECT-TYPE
   SYNTAX      DisplayString
   MAX-ACCESS  read-write
   STATUS      current
   DESCRIPTION
      "Path: ethernet3.editConf.vlan.ip.vrfRouter"
   ::= {er1645v2Lan3MCVlanEntry 53215232}

er1645v2Lan3MCVlanIpAdr OBJECT-TYPE
   SYNTAX      IpAddress
   MAX-ACCESS  read-write
   STATUS      current
   DESCRIPTION
      "Path: ethernet3.editConf.vlan.ip.address"
   ::= {er1645v2Lan3MCVlanEntry 58261504}

er1645v2Lan3MCVlanIpNetm OBJECT-TYPE
   SYNTAX      IpAddress
   MAX-ACCESS  read-write
   STATUS      current
   DESCRIPTION
      "Path: ethernet3.editConf.vlan.ip.netMask"
   ::= {er1645v2Lan3MCVlanEntry 58392576}

er1645v2Lan3MCVlanIpSNetName OBJECT-TYPE
   SYNTAX      INTEGER
               {
               slOPTg (0),
               corp (2),
               dmz (3),
               internet (1)
               }
   MAX-ACCESS  read-write
   STATUS      current
   DESCRIPTION
      "Path: ethernet3.editConf.vlan.ip.sNet.name

       Possibilities:
               <OPT>   (0)
               corp   (2)
               dmz   (3)
               internet   (1)"
   ::= {er1645v2Lan3MCVlanEntry 53674240}

er1645v2Lan3MCVlanIpSNetCust OBJECT-TYPE
   SYNTAX      DisplayString
   MAX-ACCESS  read-write
   STATUS      current
   DESCRIPTION
      "Path: ethernet3.editConf.vlan.ip.sNet.custom"
   ::= {er1645v2Lan3MCVlanEntry 53674496}

er1645v2Lan3MCVlanIpDhcpC OBJECT-TYPE
   SYNTAX      INTEGER
               {
               disabled (0),
               enabled (1)
               }
   MAX-ACCESS  read-write
   STATUS      current
   DESCRIPTION
      "Path: ethernet3.editConf.vlan.ip.dhcpClient

       Possibilities:
               disabled   (0)
               enabled   (1)"
   ::= {er1645v2Lan3MCVlanEntry 53608448}

er1645v2Lan3MCVlanIpDhcpGatewayPreference OBJECT-TYPE
   SYNTAX      Integer32
   MAX-ACCESS  read-write
   STATUS      current
   DESCRIPTION
      "Path: ethernet3.editConf.vlan.ip.dhcp.gatewayPreference"
   ::= {er1645v2Lan3MCVlanEntry 53739776}

er1645v2Lan3MCVlanIpDhcpRoutePreference OBJECT-TYPE
   SYNTAX      Integer32
   MAX-ACCESS  read-write
   STATUS      current
   DESCRIPTION
      "Path: ethernet3.editConf.vlan.ip.dhcp.routePreference"
   ::= {er1645v2Lan3MCVlanEntry 53740032}

er1645v2Lan3MCVlanIpDhcpDnsPreference OBJECT-TYPE
   SYNTAX      Integer32
   MAX-ACCESS  read-write
   STATUS      current
   DESCRIPTION
      "Path: ethernet3.editConf.vlan.ip.dhcp.dnsPreference"
   ::= {er1645v2Lan3MCVlanEntry 53740288}

er1645v2Lan3MCVlanIpMtu OBJECT-TYPE
   SYNTAX      Integer32
   MAX-ACCESS  read-write
   STATUS      current
   DESCRIPTION
      "Path: ethernet3.editConf.vlan.ip.mtu"
   ::= {er1645v2Lan3MCVlanEntry 52953088}

er1645v2Lan3MCVlanIpMssAdjust OBJECT-TYPE
   SYNTAX      INTEGER
               {
               disabled (0),
               auto (65536)
               }
   MAX-ACCESS  read-write
   STATUS      current
   DESCRIPTION
      "Path: ethernet3.editConf.vlan.ip.mssAdjust

       Possibilities:
               disabled   (0)
               auto   (65536)"
   ::= {er1645v2Lan3MCVlanEntry 53280768}

er1645v2Lan3MCVlanIpRipMetric OBJECT-TYPE
   SYNTAX      Integer32
   MAX-ACCESS  read-write
   STATUS      current
   DESCRIPTION
      "Path: ethernet3.editConf.vlan.ip.rip.metric"
   ::= {er1645v2Lan3MCVlanEntry 51712768}

er1645v2Lan3MCVlanIpRipMetricOut OBJECT-TYPE
   SYNTAX      Integer32
   MAX-ACCESS  read-write
   STATUS      current
   DESCRIPTION
      "Path: ethernet3.editConf.vlan.ip.rip.metricOut"
   ::= {er1645v2Lan3MCVlanEntry 51713024}

er1645v2Lan3MCVlanIpRipMode OBJECT-TYPE
   SYNTAX      INTEGER
               {
               disabled (0),
               passive (1),
               active (2)
               }
   MAX-ACCESS  read-write
   STATUS      current
   DESCRIPTION
      "Path: ethernet3.editConf.vlan.ip.rip.mode

       Possibilities:
               disabled   (0)
               passive   (1)
               active   (2)"
   ::= {er1645v2Lan3MCVlanEntry 51713280}

er1645v2Lan3MCVlanIpRipTxVer OBJECT-TYPE
   SYNTAX      INTEGER
               {
               rip1 (0),
               rip2 (1),
               rip1mcompatible (2)
               }
   MAX-ACCESS  read-write
   STATUS      current
   DESCRIPTION
      "Path: ethernet3.editConf.vlan.ip.rip.txVersion

       Possibilities:
               rip1   (0)
               rip2   (1)
               rip1-compatible   (2)"
   ::= {er1645v2Lan3MCVlanEntry 51716864}

er1645v2Lan3MCVlanIpRipRxVer OBJECT-TYPE
   SYNTAX      INTEGER
               {
               rip1only (0),
               rip2only (1),
               rip12 (2)
               }
   MAX-ACCESS  read-write
   STATUS      current
   DESCRIPTION
      "Path: ethernet3.editConf.vlan.ip.rip.rxVersion

       Possibilities:
               rip1only   (0)
               rip2only   (1)
               rip1&2   (2)"
   ::= {er1645v2Lan3MCVlanEntry 51717120}

er1645v2Lan3MCVlanIpRipSplitH OBJECT-TYPE
   SYNTAX      INTEGER
               {
               disabled (0),
               enabled (1),
               poisonedReverse (2)
               }
   MAX-ACCESS  read-write
   STATUS      current
   DESCRIPTION
      "Path: ethernet3.editConf.vlan.ip.rip.splitHorizon

       Possibilities:
               disabled   (0)
               enabled   (1)
               poisonedReverse   (2)"
   ::= {er1645v2Lan3MCVlanEntry 51713792}

er1645v2Lan3MCVlanIpRipAuth OBJECT-TYPE
   SYNTAX      INTEGER
               {
               disabled (0),
               texts (1),
               md5 (2)
               }
   MAX-ACCESS  read-write
   STATUS      current
   DESCRIPTION
      "Path: ethernet3.editConf.vlan.ip.rip.authentication

       Possibilities:
               disabled   (0)
               text    (1)
               md5   (2)"
   ::= {er1645v2Lan3MCVlanEntry 51712512}

er1645v2Lan3MCVlanIpRipFilter OBJECT-TYPE
   SYNTAX      DisplayString
   MAX-ACCESS  read-write
   STATUS      current
   DESCRIPTION
      "Path: ethernet3.editConf.vlan.ip.rip.filter"
   ::= {er1645v2Lan3MCVlanEntry 51716096}

er1645v2Lan3MCVlanIpRipFilterIn OBJECT-TYPE
   SYNTAX      DisplayString
   MAX-ACCESS  read-write
   STATUS      current
   DESCRIPTION
      "Path: ethernet3.editConf.vlan.ip.rip.filterIn"
   ::= {er1645v2Lan3MCVlanEntry 51716352}

er1645v2Lan3MCVlanIpRipClearNextHop OBJECT-TYPE
   SYNTAX      INTEGER
               {
               disabled (0),
               enabled (1)
               }
   MAX-ACCESS  read-write
   STATUS      current
   DESCRIPTION
      "Path: ethernet3.editConf.vlan.ip.rip.clearNextHop

       Possibilities:
               disabled   (0)
               enabled   (1)"
   ::= {er1645v2Lan3MCVlanEntry 51708416}

er1645v2Lan3MCVlanIpAccPol OBJECT-TYPE
   SYNTAX      DisplayString
   MAX-ACCESS  read-write
   STATUS      current
   DESCRIPTION
      "Path: ethernet3.editConf.vlan.ip.accessPolicy"
   ::= {er1645v2Lan3MCVlanEntry 53084160}

er1645v2Lan3MCVlanIpAB OBJECT-TYPE
   SYNTAX      DisplayString
   MAX-ACCESS  read-write
   STATUS      current
   DESCRIPTION
      "Path: ethernet3.editConf.vlan.ip.trafficPolicy"
   ::= {er1645v2Lan3MCVlanEntry 51249152}

er1645v2Lan3MCVlanIpMA OBJECT-TYPE
   SYNTAX      INTEGER
               {
               disabled (0),
               enabled (1)
               }
   MAX-ACCESS  read-write
   STATUS      current
   DESCRIPTION
      "Path: ethernet3.editConf.vlan.ip.mgmtAccess

       Possibilities:
               disabled   (0)
               enabled   (1)"
   ::= {er1645v2Lan3MCVlanEntry 51380224}

er1645v2Lan3MCVlanIpMF OBJECT-TYPE
   SYNTAX      Integer32
   MAX-ACCESS  read-write
   STATUS      current
   DESCRIPTION
      "Path: ethernet3.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3MCVlanEntry 51445760}

er1645v2Lan3MCVlanIpDB OBJECT-TYPE
   SYNTAX      INTEGER
               {
               disabled (0),
               enabled (1)
               }
   MAX-ACCESS  read-write
   STATUS      current
   DESCRIPTION
      "Path: ethernet3.editConf.vlan.ip.directedBroadcasts

       Possibilities:
               disabled   (0)
               enabled   (1)"
   ::= {er1645v2Lan3MCVlanEntry 51773440}

er1645v2Lan3MCVlanIpIR OBJECT-TYPE
   SYNTAX      INTEGER
               {
               disabled (0),
               enabled (1)
               }
   MAX-ACCESS  read-write
   STATUS      current
   DESCRIPTION
      "Path: ethernet3.editConf.vlan.ip.icmpRedirects

       Possibilities:
               disabled   (0)
               enabled   (1)"
   ::= {er1645v2Lan3MCVlanEntry 52035584}

er1645v2Lan3MCVlanIpIgmp OBJECT-TYPE
   SYNTAX      INTEGER
               {
               disabled (0),
               proxy (1),
               router (2),
               v3Router (5)
               }
   MAX-ACCESS  read-write
   STATUS      current
   DESCRIPTION
      "Path: ethernet3.editConf.vlan.ip.igmp

       Possibilities:
               disabled   (0)
               proxy   (1)
               router   (2)
               v3Router   (5)"
   ::= {er1645v2Lan3MCVlanEntry 52428800}

er1645v2Lan3MCVlanIpNN OBJECT-TYPE
   SYNTAX      DisplayString
   MAX-ACCESS  read-write
   STATUS      current
   DESCRIPTION
      "Path: ethernet3.editConf.vlan.ip.nat"
   ::= {er1645v2Lan3MCVlanEntry 52101120}

er1645v2Lan3MCVlanIpVrrp OBJECT-TYPE
   SYNTAX      INTEGER
               {
               disabled (0),
               enabled (1)
               }
   MAX-ACCESS  read-write
   STATUS      current
   DESCRIPTION
      "Path: ethernet3.editConf.vlan.ip.vrrp

       Possibilities:
               disabled   (0)
               enabled   (1)"
   ::= {er1645v2Lan3MCVlanEntry 53149696}

er1645v2Lan3MCVlanIpPimMode OBJECT-TYPE
   SYNTAX      INTEGER
               {
               disabled (0),
               sparse (1),
               passive (2)
               }
   MAX-ACCESS  read-write
   STATUS      current
   DESCRIPTION
      "Path: ethernet3.editConf.vlan.ip.pim.mode

       Possibilities:
               disabled   (0)
               sparse   (1)
               passive   (2)"
   ::= {er1645v2Lan3MCVlanEntry 53346560}

er1645v2Lan3MCVlanIpPimDrPriority OBJECT-TYPE
   SYNTAX      Counter32
   MAX-ACCESS  read-write
   STATUS      current
   DESCRIPTION
      "Path: ethernet3.editConf.vlan.ip.pim.drPriority

       32 bit unsigned wrappable counter."
   ::= {er1645v2Lan3MCVlanEntry 53346816}

er1645v2Lan3MCVlanIpPimHelloTime OBJECT-TYPE
   SYNTAX      TimeTicks
   MAX-ACCESS  read-write
   STATUS      current
   DESCRIPTION
      "Path: ethernet3.editConf.vlan.ip.pim.helloTime

       Time in centi-second."
   ::= {er1645v2Lan3MCVlanEntry 53347072}

er1645v2Lan3MCVlanIpPimPropagationDelay OBJECT-TYPE
   SYNTAX      TimeTicks
   MAX-ACCESS  read-write
   STATUS      current
   DESCRIPTION
      "Path: ethernet3.editConf.vlan.ip.pim.propagationDelay

       Time in centi-second."
   ::= {er1645v2Lan3MCVlanEntry 53347328}

er1645v2Lan3MCVlanIpPimOverrideInterval OBJECT-TYPE
   SYNTAX      TimeTicks
   MAX-ACCESS  read-write
   STATUS      current
   DESCRIPTION
      "Path: ethernet3.editConf.vlan.ip.pim.overrideInterval

       Time in centi-second."
   ::= {er1645v2Lan3MCVlanEntry 53347584}

er1645v2Lan3MCVlanIpPimBsrBorder OBJECT-TYPE
   SYNTAX      INTEGER
               {
               disabled (0),
               enabled (1)
               }
   MAX-ACCESS  read-write
   STATUS      current
   DESCRIPTION
      "Path: ethernet3.editConf.vlan.ip.pim.bsrBorder

       Possibilities:
               disabled   (0)
               enabled   (1)"
   ::= {er1645v2Lan3MCVlanEntry 53347840}

er1645v2Lan3MCVlanIpPimTtlThreshold OBJECT-TYPE
   SYNTAX      Integer32
   MAX-ACCESS  read-write
   STATUS      current
   DESCRIPTION
      "Path: ethernet3.editConf.vlan.ip.pim.ttlThreshold"
   ::= {er1645v2Lan3MCVlanEntry 53348096}

er1645v2Lan3MCVlanIpIMNetworkUnreachable OBJECT-TYPE
   SYNTAX      INTEGER
               {
               disabled (0),
               enabled (1)
               }
   MAX-ACCESS  read-write
   STATUS      current
   DESCRIPTION
      "Path: ethernet3.editConf.vlan.ip.icmpMessages.networkUnreachable

       Possibilities:
               disabled   (0)
               enabled   (1)"
   ::= {er1645v2Lan3MCVlanEntry 53412096}

er1645v2Lan3MCVlanIpIMHostUnreachable OBJECT-TYPE
   SYNTAX      INTEGER
               {
               disabled (0),
               enabled (1)
               }
   MAX-ACCESS  read-write
   STATUS      current
   DESCRIPTION
      "Path: ethernet3.editConf.vlan.ip.icmpMessages.hostUnreachable

       Possibilities:
               disabled   (0)
               enabled   (1)"
   ::= {er1645v2Lan3MCVlanEntry 53412352}

er1645v2Lan3MCVlanIpIMProtocolUnreachable OBJECT-TYPE
   SYNTAX      INTEGER
               {
               disabled (0),
               enabled (1)
               }
   MAX-ACCESS  read-write
   STATUS      current
   DESCRIPTION
      "Path: ethernet3.editConf.vlan.ip.icmpMessages.protocolUnreachable

       Possibilities:
               disabled   (0)
               enabled   (1)"
   ::= {er1645v2Lan3MCVlanEntry 53412608}

er1645v2Lan3MCVlanIpIMPortUnreachable OBJECT-TYPE
   SYNTAX      INTEGER
               {
               disabled (0),
               enabled (1)
               }
   MAX-ACCESS  read-write
   STATUS      current
   DESCRIPTION
      "Path: ethernet3.editConf.vlan.ip.icmpMessages.portUnreachable

       Possibilities:
               disabled   (0)
               enabled   (1)"
   ::= {er1645v2Lan3MCVlanEntry 53412864}

er1645v2Lan3MCVlanIpIMMtuExceeded OBJECT-TYPE
   SYNTAX      INTEGER
               {
               disabled (0),
               enabled (1)
               }
   MAX-ACCESS  read-write
   STATUS      current
   DESCRIPTION
      "Path: ethernet3.editConf.vlan.ip.icmpMessages.mtuExceeded

       Possibilities:
               disabled   (0)
               enabled   (1)"
   ::= {er1645v2Lan3MCVlanEntry 53413120}

er1645v2Lan3MCVlanIpIMAdminProhibited OBJECT-TYPE
   SYNTAX      INTEGER
               {
               disabled (0),
               enabled (1)
               }
   MAX-ACCESS  read-write
   STATUS      current
   DESCRIPTION
      "Path: ethernet3.editConf.vlan.ip.icmpMessages.adminProhibited

       Possibilities:
               disabled   (0)
               enabled   (1)"
   ::= {er1645v2Lan3MCVlanEntry 53413376}

er1645v2Lan3MCVlanIpIMTtlExceeded OBJECT-TYPE
   SYNTAX      INTEGER
               {
               disabled (0),
               enabled (1)
               }
   MAX-ACCESS  read-write
   STATUS      current
   DESCRIPTION
      "Path: ethernet3.editConf.vlan.ip.icmpMessages.ttlExceeded

       Possibilities:
               disabled   (0)
               enabled   (1)"
   ::= {er1645v2Lan3MCVlanEntry 53413632}

er1645v2Lan3MCVlanIpIMRedirect OBJECT-TYPE
   SYNTAX      INTEGER
               {
               disabled (0),
               enabled (1)
               }
   MAX-ACCESS  read-write
   STATUS      current
   DESCRIPTION
      "Path: ethernet3.editConf.vlan.ip.icmpMessages.redirect

       Possibilities:
               disabled   (0)
               enabled   (1)"
   ::= {er1645v2Lan3MCVlanEntry 53413888}

er1645v2Lan3MCVlanIpV6VrfRouter OBJECT-TYPE
   SYNTAX      DisplayString
   MAX-ACCESS  read-write
   STATUS      current
   DESCRIPTION
      "Path: ethernet3.editConf.vlan.ipV6.vrfRouter"
   ::= {er1645v2Lan3MCVlanEntry 704708608}

er1645v2Lan3MCVlanIpV6AddrAutoConfigNrDupAddrDetects OBJECT-TYPE
   SYNTAX      Integer32
   MAX-ACCESS  read-write
   STATUS      current
   DESCRIPTION
      "Path: ethernet3.editConf.vlan.ipV6.addrAutoConfig.nrDupAddrDetects"
   ::= {er1645v2Lan3MCVlanEntry 704905472}

er1645v2Lan3MCVlanIpV6AddrAutoConfigAcceptRa OBJECT-TYPE
   SYNTAX      INTEGER
               {
               disabled (0),
               enabled (1)
               }
   MAX-ACCESS  read-write
   STATUS      current
   DESCRIPTION
      "Path: ethernet3.editConf.vlan.ipV6.addrAutoConfig.acceptRa

       Possibilities:
               disabled   (0)
               enabled   (1)"
   ::= {er1645v2Lan3MCVlanEntry 704905728}

er1645v2Lan3MCVlanIpV6AddrAutoConfigAcceptRaRdnss OBJECT-TYPE
   SYNTAX      INTEGER
               {
               disabled (0),
               enabled (1)
               }
   MAX-ACCESS  read-write
   STATUS      current
   DESCRIPTION
      "Path: ethernet3.editConf.vlan.ipV6.addrAutoConfig.acceptRaRdnss

       Possibilities:
               disabled   (0)
               enabled   (1)"
   ::= {er1645v2Lan3MCVlanEntry 704905984}

er1645v2Lan3MCVlanIpV6AddrAutoConfigAcceptRaDnssl OBJECT-TYPE
   SYNTAX      INTEGER
               {
               disabled (0),
               enabled (1)
               }
   MAX-ACCESS  read-write
   STATUS      current
   DESCRIPTION
      "Path: ethernet3.editConf.vlan.ipV6.addrAutoConfig.acceptRaDnssl

       Possibilities:
               disabled   (0)
               enabled   (1)"
   ::= {er1645v2Lan3MCVlanEntry 704906240}

er1645v2Lan3MCVlanIpV6DefaultRoute OBJECT-TYPE
   SYNTAX      INTEGER
               {
               disabled (0),
               enabled (1)
               }
   MAX-ACCESS  read-write
   STATUS      current
   DESCRIPTION
      "Path: ethernet3.editConf.vlan.ipV6.defaultRoute

       Possibilities:
               disabled   (0)
               enabled   (1)"
   ::= {er1645v2Lan3MCVlanEntry 704970752}

er1645v2Lan3MCVlanIpV6RaSend OBJECT-TYPE
   SYNTAX      INTEGER
               {
               disabled (0),
               enabled (1)
               }
   MAX-ACCESS  read-write
   STATUS      current
   DESCRIPTION
      "Path: ethernet3.editConf.vlan.ipV6.ra.send

       Possibilities:
               disabled   (0)
               enabled   (1)"
   ::= {er1645v2Lan3MCVlanEntry 705036544}

er1645v2Lan3MCVlanIpV6RaMinInterval OBJECT-TYPE
   SYNTAX      TimeTicks
   MAX-ACCESS  read-write
   STATUS      current
   DESCRIPTION
      "Path: ethernet3.editConf.vlan.ipV6.ra.minInterval

       Time in centi-second."
   ::= {er1645v2Lan3MCVlanEntry 705036800}

er1645v2Lan3MCVlanIpV6RaMaxInterval OBJECT-TYPE
   SYNTAX      TimeTicks
   MAX-ACCESS  read-write
   STATUS      current
   DESCRIPTION
      "Path: ethernet3.editConf.vlan.ipV6.ra.maxInterval

       Time in centi-second."
   ::= {er1645v2Lan3MCVlanEntry 705037056}

er1645v2Lan3MCVlanIpV6RaManagedFlag OBJECT-TYPE
   SYNTAX      INTEGER
               {
               disabled (0),
               enabled (1)
               }
   MAX-ACCESS  read-write
   STATUS      current
   DESCRIPTION
      "Path: ethernet3.editConf.vlan.ipV6.ra.managedFlag

       Possibilities:
               disabled   (0)
               enabled   (1)"
   ::= {er1645v2Lan3MCVlanEntry 705037312}

er1645v2Lan3MCVlanIpV6RaOtherConfFlag OBJECT-TYPE
   SYNTAX      INTEGER
               {
               disabled (0),
               enabled (1)
               }
   MAX-ACCESS  read-write
   STATUS      current
   DESCRIPTION
      "Path: ethernet3.editConf.vlan.ipV6.ra.otherConfFlag

       Possibilities:
               disabled   (0)
               enabled   (1)"
   ::= {er1645v2Lan3MCVlanEntry 705037568}

er1645v2Lan3MCVlanIpV6RaLinkMtu OBJECT-TYPE
   SYNTAX      Integer32
   MAX-ACCESS  read-write
   STATUS      current
   DESCRIPTION
      "Path: ethernet3.editConf.vlan.ipV6.ra.linkMtu"
   ::= {er1645v2Lan3MCVlanEntry 705037824}

er1645v2Lan3MCVlanIpV6RaReachableTime OBJECT-TYPE
   SYNTAX      TimeTicks
   MAX-ACCESS  read-write
   STATUS      current
   DESCRIPTION
      "Path: ethernet3.editConf.vlan.ipV6.ra.reachableTime

       Time in centi-second."
   ::= {er1645v2Lan3MCVlanEntry 705038080}

er1645v2Lan3MCVlanIpV6RaRetransmitTime OBJECT-TYPE
   SYNTAX      TimeTicks
   MAX-ACCESS  read-write
   STATUS      current
   DESCRIPTION
      "Path: ethernet3.editConf.vlan.ipV6.ra.retransmitTime

       Time in centi-second."
   ::= {er1645v2Lan3MCVlanEntry 705038336}

er1645v2Lan3MCVlanIpV6RaHopLimit OBJECT-TYPE
   SYNTAX      Integer32
   MAX-ACCESS  read-write
   STATUS      current
   DESCRIPTION
      "Path: ethernet3.editConf.vlan.ipV6.ra.hopLimit"
   ::= {er1645v2Lan3MCVlanEntry 705038592}

er1645v2Lan3MCVlanIpV6RaDefaultLifeTime OBJECT-TYPE
   SYNTAX      TimeTicks
   MAX-ACCESS  read-write
   STATUS      current
   DESCRIPTION
      "Path: ethernet3.editConf.vlan.ipV6.ra.defaultLifeTime

       Time in centi-second."
   ::= {er1645v2Lan3MCVlanEntry 705038848}

er1645v2Lan3MCVlanIpV6RaDnsOptionsRdnssLifeTime OBJECT-TYPE
   SYNTAX      TimeTicks
   MAX-ACCESS  read-write
   STATUS      current
   DESCRIPTION
      "Path: ethernet3.editConf.vlan.ipV6.ra.dnsOptions.rdnss.lifeTime

       Time in centi-second."
   ::= {er1645v2Lan3MCVlanEntry 705039140}

er1645v2Lan3MCVlanIpV6RaDnsOptionsRdnssImportServers OBJECT-TYPE
   SYNTAX      INTEGER
               {
               disabled (0),
               enabled (1)
               }
   MAX-ACCESS  read-write
   STATUS      current
   DESCRIPTION
      "Path: ethernet3.editConf.vlan.ipV6.ra.dnsOptions.rdnss.importServers

       Possibilities:
               disabled   (0)
               enabled   (1)"
   ::= {er1645v2Lan3MCVlanEntry 705039148}

er1645v2Lan3MCVlanIpV6RaDnsOptionsDnsslLifeTime OBJECT-TYPE
   SYNTAX      TimeTicks
   MAX-ACCESS  read-write
   STATUS      current
   DESCRIPTION
      "Path: ethernet3.editConf.vlan.ipV6.ra.dnsOptions.dnssl.lifeTime

       Time in centi-second."
   ::= {er1645v2Lan3MCVlanEntry 705039172}

er1645v2Lan3MCVlanIpV6RaDnsOptionsDnsslImportDomains OBJECT-TYPE
   SYNTAX      INTEGER
               {
               disabled (0),
               enabled (1)
               }
   MAX-ACCESS  read-write
   STATUS      current
   DESCRIPTION
      "Path: ethernet3.editConf.vlan.ipV6.ra.dnsOptions.dnssl.importDomains

       Possibilities:
               disabled   (0)
               enabled   (1)"
   ::= {er1645v2Lan3MCVlanEntry 705039180}

er1645v2Lan3MCVlanIpV6RsSend OBJECT-TYPE
   SYNTAX      INTEGER
               {
               disabled (0),
               enabled (1)
               }
   MAX-ACCESS  read-write
   STATUS      current
   DESCRIPTION
      "Path: ethernet3.editConf.vlan.ipV6.rs.send

       Possibilities:
               disabled   (0)
               enabled   (1)"
   ::= {er1645v2Lan3MCVlanEntry 705954048}

er1645v2Lan3MCVlanIpV6RsMaxRandomDelay OBJECT-TYPE
   SYNTAX      TimeTicks
   MAX-ACCESS  read-write
   STATUS      current
   DESCRIPTION
      "Path: ethernet3.editConf.vlan.ipV6.rs.maxRandomDelay

       Time in centi-second."
   ::= {er1645v2Lan3MCVlanEntry 705954304}

er1645v2Lan3MCVlanIpV6RsInterval OBJECT-TYPE
   SYNTAX      TimeTicks
   MAX-ACCESS  read-write
   STATUS      current
   DESCRIPTION
      "Path: ethernet3.editConf.vlan.ipV6.rs.interval

       Time in centi-second."
   ::= {er1645v2Lan3MCVlanEntry 705954560}

er1645v2Lan3MCVlanIpV6RsMaxSolicitations OBJECT-TYPE
   SYNTAX      Integer32
   MAX-ACCESS  read-write
   STATUS      current
   DESCRIPTION
      "Path: ethernet3.editConf.vlan.ipV6.rs.maxSolicitations"
   ::= {er1645v2Lan3MCVlanEntry 705954816}

er1645v2Lan3MCVlanIpV6TrafficPolicyInbound OBJECT-TYPE
   SYNTAX      DisplayString
   MAX-ACCESS  read-write
   STATUS      current
   DESCRIPTION
      "Path: ethernet3.editConf.vlan.ipV6.trafficPolicy.inbound"
   ::= {er1645v2Lan3MCVlanEntry 705364224}

er1645v2Lan3MCVlanIpV6TrafficPolicyOutbound OBJECT-TYPE
   SYNTAX      DisplayString
   MAX-ACCESS  read-write
   STATUS      current
   DESCRIPTION
      "Path: ethernet3.editConf.vlan.ipV6.trafficPolicy.outbound"
   ::= {er1645v2Lan3MCVlanEntry 705364480}

er1645v2Lan3MCVlanIpV6FirewallZone OBJECT-TYPE
   SYNTAX      DisplayString
   MAX-ACCESS  read-write
   STATUS      current
   DESCRIPTION
      "Path: ethernet3.editConf.vlan.ipV6.firewall.zone"
   ::= {er1645v2Lan3MCVlanEntry 705429760}

er1645v2Lan3MCVlanIpV6DhcpClientAddrAC OBJECT-TYPE
   SYNTAX      INTEGER
               {
               disabled (0),
               enabled (1)
               }
   MAX-ACCESS  read-write
   STATUS      current
   DESCRIPTION
      "Path: ethernet3.editConf.vlan.ipV6.dhcp.client.addrAutoConfig

       Possibilities:
               disabled   (0)
               enabled   (1)"
   ::= {er1645v2Lan3MCVlanEntry 705307648}

er1645v2Lan3MCVlanIpV6DhcpClientPrDelMode OBJECT-TYPE
   SYNTAX      INTEGER
               {
               disabled (0),
               enabled (1)
               }
   MAX-ACCESS  read-write
   STATUS      current
   DESCRIPTION
      "Path: ethernet3.editConf.vlan.ipV6.dhcp.client.pd.mode

       Possibilities:
               disabled   (0)
               enabled   (1)"
   ::= {er1645v2Lan3MCVlanEntry 705308676}

er1645v2Lan3MCVlanIpV6DhcpClientPrDelPool OBJECT-TYPE
   SYNTAX      DisplayString
   MAX-ACCESS  read-write
   STATUS      current
   DESCRIPTION
      "Path: ethernet3.editConf.vlan.ipV6.dhcp.client.pd.pool"
   ::= {er1645v2Lan3MCVlanEntry 705308680}

er1645v2Lan3MCVlanIpV6DhcpClientPrDelPdExclOpt OBJECT-TYPE
   SYNTAX      INTEGER
               {
               disabled (0),
               enabled (1)
               }
   MAX-ACCESS  read-write
   STATUS      current
   DESCRIPTION
      "Path: ethernet3.editConf.vlan.ipV6.dhcp.client.pd.pdExclOpt

       Possibilities:
               disabled   (0)
               enabled   (1)"
   ::= {er1645v2Lan3MCVlanEntry 705308684}

er1645v2Lan3MCVlanIpV6DhcpClientDnsServerPref OBJECT-TYPE
   SYNTAX      Integer32
   MAX-ACCESS  read-write
   STATUS      current
   DESCRIPTION
      "Path: ethernet3.editConf.vlan.ipV6.dhcp.client.dns.serverPref"
   ::= {er1645v2Lan3MCVlanEntry 705310724}

er1645v2Lan3MCVlanIpV6DhcpClientRapidCommit OBJECT-TYPE
   SYNTAX      INTEGER
               {
               disabled (0),
               enabled (1)
               }
   MAX-ACCESS  read-write
   STATUS      current
   DESCRIPTION
      "Path: ethernet3.editConf.vlan.ipV6.dhcp.client.rapidCommit

       Possibilities:
               disabled   (0)
               enabled   (1)"
   ::= {er1645v2Lan3MCVlanEntry 705309696}

er1645v2Lan3MCVlanIpV6DhcpClientTimersSolTimeOut OBJECT-TYPE
   SYNTAX      TimeTicks
   MAX-ACCESS  read-write
   STATUS      current
   DESCRIPTION
      "Path: ethernet3.editConf.vlan.ipV6.dhcp.client.timers.solTimeOut

       Time in centi-second."
   ::= {er1645v2Lan3MCVlanEntry 705311748}

er1645v2Lan3MCVlanIpV6DhcpClientTimersSolMaxRt OBJECT-TYPE
   SYNTAX      TimeTicks
   MAX-ACCESS  read-write
   STATUS      current
   DESCRIPTION
      "Path: ethernet3.editConf.vlan.ipV6.dhcp.client.timers.solMaxRt

       Time in centi-second."
   ::= {er1645v2Lan3MCVlanEntry 705311752}

er1645v2Lan3MCVlanIpV6DhcpClientTimersInfoRefresh OBJECT-TYPE
   SYNTAX      TimeTicks
   MAX-ACCESS  read-write
   STATUS      current
   DESCRIPTION
      "Path: ethernet3.editConf.vlan.ipV6.dhcp.client.timers.infoRefresh

       Time in centi-second."
   ::= {er1645v2Lan3MCVlanEntry 705311756}

er1645v2Lan3MCVlanIpV6DhcpServerMode OBJECT-TYPE
   SYNTAX      INTEGER
               {
               disabled (0),
               enabled (1)
               }
   MAX-ACCESS  read-write
   STATUS      current
   DESCRIPTION
      "Path: ethernet3.editConf.vlan.ipV6.dhcp.server.mode

       Possibilities:
               disabled   (0)
               enabled   (1)"
   ::= {er1645v2Lan3MCVlanEntry 705315840}

er1645v2Lan3MCVlanIpV6DhcpServerPreference OBJECT-TYPE
   SYNTAX      Integer32
   MAX-ACCESS  read-write
   STATUS      current
   DESCRIPTION
      "Path: ethernet3.editConf.vlan.ipV6.dhcp.server.preference"
   ::= {er1645v2Lan3MCVlanEntry 705316864}

er1645v2Lan3MCVlanIpV6DhcpServerPool OBJECT-TYPE
   SYNTAX      DisplayString
   MAX-ACCESS  read-write
   STATUS      current
   DESCRIPTION
      "Path: ethernet3.editConf.vlan.ipV6.dhcp.server.pool"
   ::= {er1645v2Lan3MCVlanEntry 705317888}

er1645v2Lan3MCVlanIpV6DhcpServerRapidCommit OBJECT-TYPE
   SYNTAX      INTEGER
               {
               disabled (0),
               enabled (1)
               }
   MAX-ACCESS  read-write
   STATUS      current
   DESCRIPTION
      "Path: ethernet3.editConf.vlan.ipV6.dhcp.server.rapidCommit

       Possibilities:
               disabled   (0)
               enabled   (1)"
   ::= {er1645v2Lan3MCVlanEntry 705318912}

er1645v2Lan3MCVlanIpV6DhcpServerTimersInfoRefresh OBJECT-TYPE
   SYNTAX      TimeTicks
   MAX-ACCESS  read-write
   STATUS      current
   DESCRIPTION
      "Path: ethernet3.editConf.vlan.ipV6.dhcp.server.timers.infoRefresh

       Time in centi-second."
   ::= {er1645v2Lan3MCVlanEntry 705319940}

er1645v2Lan3MCVlanIpV6DhcpRelayMode OBJECT-TYPE
   SYNTAX      INTEGER
               {
               disabled (0),
               enabled (1)
               }
   MAX-ACCESS  read-write
   STATUS      current
   DESCRIPTION
      "Path: ethernet3.editConf.vlan.ipV6.dhcp.relay.mode

       Possibilities:
               disabled   (0)
               enabled   (1)"
   ::= {er1645v2Lan3MCVlanEntry 705323040}

er1645v2Lan3MCVlanIpV6SendRedirect OBJECT-TYPE
   SYNTAX      INTEGER
               {
               disabled (0),
               enabled (1)
               }
   MAX-ACCESS  read-write
   STATUS      current
   DESCRIPTION
      "Path: ethernet3.editConf.vlan.ipV6.sendRedirect

       Possibilities:
               disabled   (0)
               enabled   (1)"
   ::= {er1645v2Lan3MCVlanEntry 705101824}

er1645v2Lan3MCVlanIpV6LinkMtu OBJECT-TYPE
   SYNTAX      Integer32
   MAX-ACCESS  read-write
   STATUS      current
   DESCRIPTION
      "Path: ethernet3.editConf.vlan.ipV6.linkMtu"
   ::= {er1645v2Lan3MCVlanEntry 705167360}

er1645v2Lan3MCVlanIpV6InterfaceId OBJECT-TYPE
   SYNTAX      OCTET STRING
   MAX-ACCESS  read-write
   STATUS      current
   DESCRIPTION
      "Path: ethernet3.editConf.vlan.ipV6.interfaceId"
   ::= {er1645v2Lan3MCVlanEntry 705232896}

er1645v2Lan3MCVlanIpV6MF OBJECT-TYPE
   SYNTAX      Integer32
   MAX-ACCESS  read-write
   STATUS      current
   DESCRIPTION
      "Path: ethernet3.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3MCVlanEntry 705757184}

er1645v2Lan3MCVlanIpV6IcmpMessagesNoRoute OBJECT-TYPE
   SYNTAX      INTEGER
               {
               disabled (0),
               enabled (1)
               }
   MAX-ACCESS  read-write
   STATUS      current
   DESCRIPTION
      "Path: ethernet3.editConf.vlan.ipV6.icmpMessages.noRoute

       Possibilities:
               disabled   (0)
               enabled   (1)"
   ::= {er1645v2Lan3MCVlanEntry 705822976}

er1645v2Lan3MCVlanIpV6IcmpMessagesBeyondScope OBJECT-TYPE
   SYNTAX      INTEGER
               {
               disabled (0),
               enabled (1)
               }
   MAX-ACCESS  read-write
   STATUS      current
   DESCRIPTION
      "Path: ethernet3.editConf.vlan.ipV6.icmpMessages.beyondScope

       Possibilities:
               disabled   (0)
               enabled   (1)"
   ::= {er1645v2Lan3MCVlanEntry 705823488}

er1645v2Lan3MCVlanIpV6IcmpMessagesAddressUnreachable OBJECT-TYPE
   SYNTAX      INTEGER
               {
               disabled (0),
               enabled (1)
               }
   MAX-ACCESS  read-write
   STATUS      current
   DESCRIPTION
      "Path: ethernet3.editConf.vlan.ipV6.icmpMessages.addressUnreachable

       Possibilities:
               disabled   (0)
               enabled   (1)"
   ::= {er1645v2Lan3MCVlanEntry 705823744}

er1645v2Lan3MCVlanIpV6IcmpMessagesPortUnreachable OBJECT-TYPE
   SYNTAX      INTEGER
               {
               disabled (0),
               enabled (1)
               }
   MAX-ACCESS  read-write
   STATUS      current
   DESCRIPTION
      "Path: ethernet3.editConf.vlan.ipV6.icmpMessages.portUnreachable

       Possibilities:
               disabled   (0)
               enabled   (1)"
   ::= {er1645v2Lan3MCVlanEntry 705824000}

er1645v2Lan3MCVlanIpV6IcmpMessagesPacketTooBig OBJECT-TYPE
   SYNTAX      INTEGER
               {
               disabled (0),
               enabled (1)
               }
   MAX-ACCESS  read-write
   STATUS      current
   DESCRIPTION
      "Path: ethernet3.editConf.vlan.ipV6.icmpMessages.packetTooBig

       Possibilities:
               disabled   (0)
               enabled   (1)"
   ::= {er1645v2Lan3MCVlanEntry 705825280}

er1645v2Lan3MCVlanIpV6IcmpMessagesHopLimitExceeded OBJECT-TYPE
   SYNTAX      INTEGER
               {
               disabled (0),
               enabled (1)
               }
   MAX-ACCESS  read-write
   STATUS      current
   DESCRIPTION
      "Path: ethernet3.editConf.vlan.ipV6.icmpMessages.hopLimitExceeded

       Possibilities:
               disabled   (0)
               enabled   (1)"
   ::= {er1645v2Lan3MCVlanEntry 705827840}

er1645v2Lan3MCVlanIpV6IcmpMessagesFragTimeExceeded OBJECT-TYPE
   SYNTAX      INTEGER
               {
               disabled (0),
               enabled (1)
               }
   MAX-ACCESS  read-write
   STATUS      current
   DESCRIPTION
      "Path: ethernet3.editConf.vlan.ipV6.icmpMessages.fragTimeExceeded

       Possibilities:
               disabled   (0)
               enabled   (1)"
   ::= {er1645v2Lan3MCVlanEntry 705828096}

er1645v2Lan3MCVlanIpV6IcmpMessagesHeaderFieldErr OBJECT-TYPE
   SYNTAX      INTEGER
               {
               disabled (0),
               enabled (1)
               }
   MAX-ACCESS  read-write
   STATUS      current
   DESCRIPTION
      "Path: ethernet3.editConf.vlan.ipV6.icmpMessages.headerFieldErr

       Possibilities:
               disabled   (0)
               enabled   (1)"
   ::= {er1645v2Lan3MCVlanEntry 705830400}

er1645v2Lan3MCVlanIpV6IcmpMessagesOptionUnrecognized OBJECT-TYPE
   SYNTAX      INTEGER
               {
               disabled (0),
               enabled (1)
               }
   MAX-ACCESS  read-write
   STATUS      current
   DESCRIPTION
      "Path: ethernet3.editConf.vlan.ipV6.icmpMessages.optionUnrecognized

       Possibilities:
               disabled   (0)
               enabled   (1)"
   ::= {er1645v2Lan3MCVlanEntry 705830912}

er1645v2Lan3MCVlanIpV6IcmpMessagesRedirect OBJECT-TYPE
   SYNTAX      INTEGER
               {
               disabled (0),
               enabled (1)
               }
   MAX-ACCESS  read-write
   STATUS      current
   DESCRIPTION
      "Path: ethernet3.editConf.vlan.ipV6.icmpMessages.redirect

       Possibilities:
               disabled   (0)
               enabled   (1)"
   ::= {er1645v2Lan3MCVlanEntry 705832960}

er1645v2Lan3MCVlanBridgingAccList OBJECT-TYPE
   SYNTAX      DisplayString
   MAX-ACCESS  read-write
   STATUS      current
   DESCRIPTION
      "Path: ethernet3.editConf.vlan.bridging.accessList"
   ::= {er1645v2Lan3MCVlanEntry 453246976}

er1645v2Lan3MCVlanBridgingInACL OBJECT-TYPE
   SYNTAX      DisplayString
   MAX-ACCESS  read-write
   STATUS      current
   DESCRIPTION
      "Path: ethernet3.editConf.vlan.bridging.inAccessList"
   ::= {er1645v2Lan3MCVlanEntry 456916992}

er1645v2Lan3MCVlanBridgingTp OBJECT-TYPE
   SYNTAX      DisplayString
   MAX-ACCESS  read-write
   STATUS      current
   DESCRIPTION
      "Path: ethernet3.editConf.vlan.bridging.trafficPolicy"
   ::= {er1645v2Lan3MCVlanEntry 454295552}

er1645v2Lan3MCVlanBridgingBrGrp OBJECT-TYPE
   SYNTAX      DisplayString
   MAX-ACCESS  read-write
   STATUS      current
   DESCRIPTION
      "Path: ethernet3.editConf.vlan.bridging.bridgeGroup"
   ::= {er1645v2Lan3MCVlanEntry 454819840}

er1645v2Lan3MCVlanBridgingLimBC OBJECT-TYPE
   SYNTAX      INTEGER
               {
               disabled (0),
               enabled (1)
               }
   MAX-ACCESS  read-write
   STATUS      current
   DESCRIPTION
      "Path: ethernet3.editConf.vlan.bridging.limitBroadcasts

       Possibilities:
               disabled   (0)
               enabled   (1)"
   ::= {er1645v2Lan3MCVlanEntry 455081984}

er1645v2Lan3MCVlanBridgingPrivateMode OBJECT-TYPE
   SYNTAX      INTEGER
               {
               disabled (0),
               enabled (1)
               }
   MAX-ACCESS  read-write
   STATUS      current
   DESCRIPTION
      "Path: ethernet3.editConf.vlan.bridging.privateMode

       Possibilities:
               disabled   (0)
               enabled   (1)"
   ::= {er1645v2Lan3MCVlanEntry 459538432}

er1645v2Lan3MCVlanBridgingLearning OBJECT-TYPE
   SYNTAX      INTEGER
               {
               disabled (0),
               enabled (1)
               }
   MAX-ACCESS  read-write
   STATUS      current
   DESCRIPTION
      "Path: ethernet3.editConf.vlan.bridging.learning

       Possibilities:
               disabled   (0)
               enabled   (1)"
   ::= {er1645v2Lan3MCVlanEntry 456130560}

er1645v2Lan3MCVlanBridgingMaxCacheSize OBJECT-TYPE
   SYNTAX      INTEGER
               {
               unlimited (0)
               }
   MAX-ACCESS  read-write
   STATUS      current
   DESCRIPTION
      "Path: ethernet3.editConf.vlan.bridging.maxCacheSize

       Possibilities:
               unlimited   (0)"
   ::= {er1645v2Lan3MCVlanEntry 456392704}

er1645v2Lan3MCVlanBridgingRelearnDropOnRelearn OBJECT-TYPE
   SYNTAX      INTEGER
               {
               disabled (0),
               enabled (1)
               }
   MAX-ACCESS  read-write
   STATUS      current
   DESCRIPTION
      "Path: ethernet3.editConf.vlan.bridging.relearn.dropOnRelearn

       Possibilities:
               disabled   (0)
               enabled   (1)"
   ::= {er1645v2Lan3MCVlanEntry 456655872}

er1645v2Lan3MCVlanBridgingRelearnShutdownThreshold OBJECT-TYPE
   SYNTAX      Integer32
   MAX-ACCESS  read-write
   STATUS      current
   DESCRIPTION
      "Path: ethernet3.editConf.vlan.bridging.relearn.shutdownThreshold"
   ::= {er1645v2Lan3MCVlanEntry 456656896}

er1645v2Lan3MCVlanBridgingRelearnShutdownTime OBJECT-TYPE
   SYNTAX      TimeTicks
   MAX-ACCESS  read-write
   STATUS      current
   DESCRIPTION
      "Path: ethernet3.editConf.vlan.bridging.relearn.shutdownTime

       Time in centi-second."
   ::= {er1645v2Lan3MCVlanEntry 456657920}

er1645v2Lan3MCVlanBridgingRelearnLoopDetection OBJECT-TYPE
   SYNTAX      INTEGER
               {
               disabled (0),
               passive (1),
               active (2)
               }
   MAX-ACCESS  read-write
   STATUS      current
   DESCRIPTION
      "Path: ethernet3.editConf.vlan.bridging.relearn.loopDetection

       Possibilities:
               disabled   (0)
               passive   (1)
               active   (2)"
   ::= {er1645v2Lan3MCVlanEntry 456658944}

er1645v2Lan3MCVlanBridgingRelearnLoopDetectionInterval OBJECT-TYPE
   SYNTAX      TimeTicks
   MAX-ACCESS  read-write
   STATUS      current
   DESCRIPTION
      "Path: ethernet3.editConf.vlan.bridging.relearn.loopDetectionInterval

       Time in centi-second."
   ::= {er1645v2Lan3MCVlanEntry 456659968}

er1645v2Lan3MCVlanBridgingVlanMemberShip OBJECT-TYPE
   SYNTAX      INTEGER
               {
               all (0),
               none (1),
               grouped (2)
               }
   MAX-ACCESS  read-write
   STATUS      current
   DESCRIPTION
      "Path: ethernet3.editConf.vlan.bridging.vlanMemberShip

       Possibilities:
               all   (0)
               none   (1)
               grouped   (2)"
   ::= {er1645v2Lan3MCVlanEntry 457965568}

er1645v2Lan3MCVlanBridgingVlTUntaggedAction OBJECT-TYPE
   SYNTAX      INTEGER
               {
               discard (0),
               accept (1),
               tag (2)
               }
   MAX-ACCESS  read-write
   STATUS      current
   DESCRIPTION
      "Path: ethernet3.editConf.vlan.bridging.vlanTagging.untagged.action

       Possibilities:
               discard   (0)
               accept   (1)
               tag   (2)"
   ::= {er1645v2Lan3MCVlanEntry 459055104}

er1645v2Lan3MCVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.untagged.tagInfo.tpid

       Possibilities:
               dot1Q   (33024)
               dot1ad   (34984)
               0x9100   (37120)
               0x9200   (37376)
               0x9300   (37632)"
   ::= {er1645v2Lan3MCVlanEntry 459059712}

er1645v2Lan3MCVlanBridgingVlTUntaggedTagInfoVid OBJECT-TYPE
   SYNTAX      Integer32
   MAX-ACCESS  read-write
   STATUS      current
   DESCRIPTION
      "Path: ethernet3.editConf.vlan.bridging.vlanTagging.untagged.tagInfo.vid"
   ::= {er1645v2Lan3MCVlanEntry 459060224}

er1645v2Lan3MCVlanBridgingVlTUnknownVlansAction OBJECT-TYPE
   SYNTAX      INTEGER
               {
               discard (0),
               accept (1),
               tag (2)
               }
   MAX-ACCESS  read-write
   STATUS      current
   DESCRIPTION
      "Path: ethernet3.editConf.vlan.bridging.vlanTagging.unknownVlans.action

       Possibilities:
               discard   (0)
               accept   (1)
               tag   (2)"
   ::= {er1645v2Lan3MCVlanEntry 459120640}

er1645v2Lan3MCVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.unknownVlans.tagInfo.tpid

       Possibilities:
               dot1Q   (33024)
               dot1ad   (34984)
               0x9100   (37120)
               0x9200   (37376)
               0x9300   (37632)"
   ::= {er1645v2Lan3MCVlanEntry 459125248}

er1645v2Lan3MCVlanBridgingVlTUnknownVlansTagInfoVid OBJECT-TYPE
   SYNTAX      Integer32
   MAX-ACCESS  read-write
   STATUS      current
   DESCRIPTION
      "Path: ethernet3.editConf.vlan.bridging.vlanTagging.unknownVlans.tagInfo.vid"
   ::= {er1645v2Lan3MCVlanEntry 459125760}

er1645v2Lan3MCVlanBridgingDot1adType OBJECT-TYPE
   SYNTAX      INTEGER
               {
               slOPTg (0),
               cPort (4),
               sPort (1),
               nni (2)
               }
   MAX-ACCESS  read-write
   STATUS      current
   DESCRIPTION
      "Path: ethernet3.editConf.vlan.bridging.dot1ad.type

       Possibilities:
               <OPT>   (0)
               cPort   (4)
               sPort   (1)
               nni   (2)"
   ::= {er1645v2Lan3MCVlanEntry 460850176}

er1645v2Lan3MCVlanBridgingPriority OBJECT-TYPE
   SYNTAX      Integer32
   MAX-ACCESS  read-write
   STATUS      current
   DESCRIPTION
      "Path: ethernet3.editConf.vlan.bridging.priority"
   ::= {er1645v2Lan3MCVlanEntry 453509120}

er1645v2Lan3MCVlanBridgingPathCost OBJECT-TYPE
   SYNTAX      Integer32
   MAX-ACCESS  read-write
   STATUS      current
   DESCRIPTION
      "Path: ethernet3.editConf.vlan.bridging.pathCost"
   ::= {er1645v2Lan3MCVlanEntry 453771264}

er1645v2Lan3MCVlanBridgingInternalPathCost OBJECT-TYPE
   SYNTAX      Integer32
   MAX-ACCESS  read-write
   STATUS      current
   DESCRIPTION
      "Path: ethernet3.editConf.vlan.bridging.internalPathCost"
   ::= {er1645v2Lan3MCVlanEntry 457703424}

er1645v2Lan3MCVlanBridgingTCD OBJECT-TYPE
   SYNTAX      INTEGER
               {
               disabled (0),
               enabled (1)
               }
   MAX-ACCESS  read-write
   STATUS      current
   DESCRIPTION
      "Path: ethernet3.editConf.vlan.bridging.topologyChangeDetection

       Possibilities:
               disabled   (0)
               enabled   (1)"
   ::= {er1645v2Lan3MCVlanEntry 454033408}

er1645v2Lan3MCVlanBridgingRestrictedRole OBJECT-TYPE
   SYNTAX      INTEGER
               {
               disabled (0),
               enabled (1)
               }
   MAX-ACCESS  read-write
   STATUS      current
   DESCRIPTION
      "Path: ethernet3.editConf.vlan.bridging.restrictedRole

       Possibilities:
               disabled   (0)
               enabled   (1)"
   ::= {er1645v2Lan3MCVlanEntry 458227712}

er1645v2Lan3MCVlanBridgingAdminEdge OBJECT-TYPE
   SYNTAX      INTEGER
               {
               disabled (0),
               enabled (1)
               }
   MAX-ACCESS  read-write
   STATUS      current
   DESCRIPTION
      "Path: ethernet3.editConf.vlan.bridging.adminEdge

       Possibilities:
               disabled   (0)
               enabled   (1)"
   ::= {er1645v2Lan3MCVlanEntry 457179136}

er1645v2Lan3MCVlanBridgingOamMacDeviceMac OBJECT-TYPE
   SYNTAX      DisplayString
   MAX-ACCESS  read-write
   STATUS      current
   DESCRIPTION
      "Path: ethernet3.editConf.vlan.bridging.ethOam.macAddress.deviceMac"
   ::= {er1645v2Lan3MCVlanEntry 458506496}

er1645v2Lan3MCVlanBridgingOamMacUserMac OBJECT-TYPE
   SYNTAX      OCTET STRING
   MAX-ACCESS  read-write
   STATUS      current
   DESCRIPTION
      "Path: ethernet3.editConf.vlan.bridging.ethOam.macAddress.userMac

       MAC address."
   ::= {er1645v2Lan3MCVlanEntry 458506368}

er1645v2Lan3MCVlanBridgingOamMacBridgeMac OBJECT-TYPE
   SYNTAX      DisplayString
   MAX-ACCESS  read-write
   STATUS      current
   DESCRIPTION
      "Path: ethernet3.editConf.vlan.bridging.ethOam.macAddress.bridgeMac"
   ::= {er1645v2Lan3MCVlanEntry 458506432}

er1645v2Lan3MCVlanBridgingMgmtInline OBJECT-TYPE
   SYNTAX      INTEGER
               {
               disabled (0),
               enabled (1)
               }
   MAX-ACCESS  read-write
   STATUS      current
   DESCRIPTION
      "Path: ethernet3.editConf.vlan.bridging.mgmtInline

       Possibilities:
               disabled   (0)
               enabled   (1)"
   ::= {er1645v2Lan3MCVlanEntry 458752000}

er1645v2Lan3MCVlanBridgingL2ptMode OBJECT-TYPE
   SYNTAX      INTEGER
               {
               disabled (0),
               enabled (1)
               }
   MAX-ACCESS  read-write
   STATUS      current
   DESCRIPTION
      "Path: ethernet3.editConf.vlan.bridging.l2ProtTunnel.mode

       Possibilities:
               disabled   (0)
               enabled   (1)"
   ::= {er1645v2Lan3MCVlanEntry 459292672}

er1645v2Lan3MCVlanBridgingL2ptProtocols OBJECT-TYPE
   SYNTAX      Integer32
   MAX-ACCESS  read-write
   STATUS      current
   DESCRIPTION
      "Path: ethernet3.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan3MCVlanEntry 459309056}

er1645v2Lan3MCVlanBridgingL2ptDestMac OBJECT-TYPE
   SYNTAX      OCTET STRING
   MAX-ACCESS  read-write
   STATUS      current
   DESCRIPTION
      "Path: ethernet3.editConf.vlan.bridging.l2ProtTunnel.destinationMac

       MAC address."
   ::= {er1645v2Lan3MCVlanEntry 459325440}

er1645v2Lan3MCVlanBridgingL2ptCos OBJECT-TYPE
   SYNTAX      INTEGER
               {
               unchanged (255)
               }
   MAX-ACCESS  read-write
   STATUS      current
   DESCRIPTION
      "Path: ethernet3.editConf.vlan.bridging.l2ProtTunnel.cos

       Possibilities:
               unchanged   (255)"
   ::= {er1645v2Lan3MCVlanEntry 459341824}

er1645v2Lan3MCVlanBridgingL2ptDropThrStp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.stp

       unit name = packets/sec

       Possibilities:
               unlimited   (0)"
   ::= {er1645v2Lan3MCVlanEntry 459358272}

er1645v2Lan3MCVlanBridgingL2ptDropThrLldp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lldp

       unit name = packets/sec

       Possibilities:
               unlimited   (0)"
   ::= {er1645v2Lan3MCVlanEntry 459358336}

er1645v2Lan3MCVlanBridgingL2ptDropThrOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.oam

       unit name = packets/sec

       Possibilities:
               unlimited   (0)"
   ::= {er1645v2Lan3MCVlanEntry 459358400}

er1645v2Lan3MCVlanBridgingL2ptDropThrCdp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.cdp

       unit name = packets/sec

       Possibilities:
               unlimited   (0)"
   ::= {er1645v2Lan3MCVlanEntry 459358464}

er1645v2Lan3MCVlanBridgingL2ptDropThrVtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.vtp

       unit name = packets/sec

       Possibilities:
               unlimited   (0)"
   ::= {er1645v2Lan3MCVlanEntry 459358528}

er1645v2Lan3MCVlanBridgingL2ptDropThrLacp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lacp

       unit name = packets/sec

       Possibilities:
               unlimited   (0)"
   ::= {er1645v2Lan3MCVlanEntry 459358592}

er1645v2Lan3MCVlanBridgingL2ptDropThrEfmOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.efmOam

       unit name = packets/sec

       Possibilities:
               unlimited   (0)"
   ::= {er1645v2Lan3MCVlanEntry 459358656}

er1645v2Lan3MCVlanBridgingL2ptDropThrPvst OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pvst

       unit name = packets/sec

       Possibilities:
               unlimited   (0)"
   ::= {er1645v2Lan3MCVlanEntry 459358720}

er1645v2Lan3MCVlanBridgingL2ptDropThrMmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mmrp

       unit name = packets/sec

       Possibilities:
               unlimited   (0)"
   ::= {er1645v2Lan3MCVlanEntry 459358784}

er1645v2Lan3MCVlanBridgingL2ptDropThrMvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mvrp

       unit name = packets/sec

       Possibilities:
               unlimited   (0)"
   ::= {er1645v2Lan3MCVlanEntry 459358848}

er1645v2Lan3MCVlanBridgingL2ptDropThrGvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gvrp

       unit name = packets/sec

       Possibilities:
               unlimited   (0)"
   ::= {er1645v2Lan3MCVlanEntry 459358912}

er1645v2Lan3MCVlanBridgingL2ptDropThrGmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gmrp

       unit name = packets/sec

       Possibilities:
               unlimited   (0)"
   ::= {er1645v2Lan3MCVlanEntry 459358976}

er1645v2Lan3MCVlanBridgingL2ptDropThrDtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.dtp

       unit name = packets/sec

       Possibilities:
               unlimited   (0)"
   ::= {er1645v2Lan3MCVlanEntry 459359040}

er1645v2Lan3MCVlanBridgingL2ptDropThrPagp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pagp

       unit name = packets/sec

       Possibilities:
               unlimited   (0)"
   ::= {er1645v2Lan3MCVlanEntry 459359104}

er1645v2Lan3MCVlanBridgingL2ptDropThrUdld OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.udld

       unit name = packets/sec

       Possibilities:
               unlimited   (0)"
   ::= {er1645v2Lan3MCVlanEntry 459359168}

er1645v2Lan3MCVlanVlanVid OBJECT-TYPE
   SYNTAX      INTEGER
               {
               untagged (0),
               prioTagged (4096),
               notUsed (4097)
               }
   MAX-ACCESS  read-write
   STATUS      current
   DESCRIPTION
      "Path: ethernet3.editConf.vlan.vlan.vid

       Possibilities:
               untagged   (0)
               prioTagged   (4096)
               notUsed   (4097)"
   ::= {er1645v2Lan3MCVlanEntry 234946560}

er1645v2Lan3MCVlanVlanVidExtensionSingle OBJECT-TYPE
   SYNTAX      OCTET STRING
   MAX-ACCESS  read-write
   STATUS      current
   DESCRIPTION
      "Path: ethernet3.editConf.vlan.vlan.vidExtension.single"
   ::= {er1645v2Lan3MCVlanEntry 235340032}

er1645v2Lan3MCVlanVlanVidExtensionEndVid OBJECT-TYPE
   SYNTAX      Integer32
   MAX-ACCESS  read-write
   STATUS      current
   DESCRIPTION
      "Path: ethernet3.editConf.vlan.vlan.vidExtension.endVid"
   ::= {er1645v2Lan3MCVlanEntry 235340288}

er1645v2Lan3MCVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tpid

       Possibilities:
               dot1Q   (33024)
               dot1ad   (34984)
               0x9100   (37120)
               0x9200   (37376)
               0x9300   (37632)"
   ::= {er1645v2Lan3MCVlanEntry 241238016}

er1645v2Lan3MCVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet3.editConf.vlan.vlan.tagSignificance

       Possibilities:
               global   (0)
               local   (1)
               sVlan   (2)
               sVlanGlobal   (6)
               cVlan   (3)
               scVlan   (5)
               cVlanLocal   (4)"
   ::= {er1645v2Lan3MCVlanEntry 235012096}

er1645v2Lan3MCVlanVlanChTos OBJECT-TYPE
   SYNTAX      INTEGER
               {
               disabled (0),
               enabled (1)
               }
   MAX-ACCESS  read-write
   STATUS      current
   DESCRIPTION
      "Path: ethernet3.editConf.vlan.vlan.changeTos

       Possibilities:
               disabled   (0)
               enabled   (1)"
   ::= {er1645v2Lan3MCVlanEntry 235208704}

er1645v2Lan3MCVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235143424}

er1645v2Lan3MCVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235143680}

er1645v2Lan3MCVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235143936}

er1645v2Lan3MCVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235144192}

er1645v2Lan3MCVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235144448}

er1645v2Lan3MCVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235144704}

er1645v2Lan3MCVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235144960}

er1645v2Lan3MCVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan3MCVlanEntry 235145216}

er1645v2Lan3MCVlanVlanTxCos OBJECT-TYPE
   SYNTAX      INTEGER
               {
               tosCosMap (8),
               queueCosMap (16)
               }
   MAX-ACCESS  read-write
   STATUS      current
   DESCRIPTION
      "Path: ethernet3.editConf.vlan.vlan.txCos

       Possibilities:
               tosCosMap   (8)
               queueCosMap   (16)"
   ::= {er1645v2Lan3MCVlanEntry 235077632}

er1645v2Lan3MCVlanVlanCCMapP0 OBJECT-TYPE
   SYNTAX      Integer32
   MAX-ACCESS  read-write
   STATUS      current
   DESCRIPTION
      "Path: ethernet3.editConf.vlan.vlan.cosCosMap.p0"
   ::= {er1645v2Lan3MCVlanEntry 241303808}

er1645v2Lan3MCVlanVlanCCMapP1 OBJECT-TYPE
   SYNTAX      Integer32
   MAX-ACCESS  read-write
   STATUS      current
   DESCRIPTION
      "Path: ethernet3.editConf.vlan.vlan.cosCosMap.p1"
   ::= {er1645v2Lan3MCVlanEntry 241304064}

er1645v2Lan3MCVlanVlanCCMapP2 OBJECT-TYPE
   SYNTAX      Integer32
   MAX-ACCESS  read-write
   STATUS      current
   DESCRIPTION
      "Path: ethernet3.editConf.vlan.vlan.cosCosMap.p2"
   ::= {er1645v2Lan3MCVlanEntry 241304320}

er1645v2Lan3MCVlanVlanCCMapP3 OBJECT-TYPE
   SYNTAX      Integer32
   MAX-ACCESS  read-write
   STATUS      current
   DESCRIPTION
      "Path: ethernet3.editConf.vlan.vlan.cosCosMap.p3"
   ::= {er1645v2Lan3MCVlanEntry 241304576}

er1645v2Lan3MCVlanVlanCCMapP4 OBJECT-TYPE
   SYNTAX      Integer32
   MAX-ACCESS  read-write
   STATUS      current
   DESCRIPTION
      "Path: ethernet3.editConf.vlan.vlan.cosCosMap.p4"
   ::= {er1645v2Lan3MCVlanEntry 241304832}

er1645v2Lan3MCVlanVlanCCMapP5 OBJECT-TYPE
   SYNTAX      Integer32
   MAX-ACCESS  read-write
   STATUS      current
   DESCRIPTION
      "Path: ethernet3.editConf.vlan.vlan.cosCosMap.p5"
   ::= {er1645v2Lan3MCVlanEntry 241305088}

er1645v2Lan3MCVlanVlanCCMapP6 OBJECT-TYPE
   SYNTAX      Integer32
   MAX-ACCESS  read-write
   STATUS      current
   DESCRIPTION
      "Path: ethernet3.editConf.vlan.vlan.cosCosMap.p6"
   ::= {er1645v2Lan3MCVlanEntry 241305344}

er1645v2Lan3MCVlanVlanCCMapP7 OBJECT-TYPE
   SYNTAX      Integer32
   MAX-ACCESS  read-write
   STATUS      current
   DESCRIPTION
      "Path: ethernet3.editConf.vlan.vlan.cosCosMap.p7"
   ::= {er1645v2Lan3MCVlanEntry 241305600}

er1645v2Lan3MCVlanVlanQCMapQueue1 OBJECT-TYPE
   SYNTAX      Integer32
   MAX-ACCESS  read-write
   STATUS      current
   DESCRIPTION
      "Path: ethernet3.editConf.vlan.vlan.queueCosMap.queue1"
   ::= {er1645v2Lan3MCVlanEntry 241434880}

er1645v2Lan3MCVlanVlanQCMapQueue2 OBJECT-TYPE
   SYNTAX      Integer32
   MAX-ACCESS  read-write
   STATUS      current
   DESCRIPTION
      "Path: ethernet3.editConf.vlan.vlan.queueCosMap.queue2"
   ::= {er1645v2Lan3MCVlanEntry 241435136}

er1645v2Lan3MCVlanVlanQCMapQueue3 OBJECT-TYPE
   SYNTAX      Integer32
   MAX-ACCESS  read-write
   STATUS      current
   DESCRIPTION
      "Path: ethernet3.editConf.vlan.vlan.queueCosMap.queue3"
   ::= {er1645v2Lan3MCVlanEntry 241435392}

er1645v2Lan3MCVlanVlanQCMapQueue4 OBJECT-TYPE
   SYNTAX      Integer32
   MAX-ACCESS  read-write
   STATUS      current
   DESCRIPTION
      "Path: ethernet3.editConf.vlan.vlan.queueCosMap.queue4"
   ::= {er1645v2Lan3MCVlanEntry 241435648}

er1645v2Lan3MCVlanVlanQCMapQueue5 OBJECT-TYPE
   SYNTAX      Integer32
   MAX-ACCESS  read-write
   STATUS      current
   DESCRIPTION
      "Path: ethernet3.editConf.vlan.vlan.queueCosMap.queue5"
   ::= {er1645v2Lan3MCVlanEntry 241435904}

er1645v2Lan3MCVlanVlanQCMapLowDelayQueue OBJECT-TYPE
   SYNTAX      Integer32
   MAX-ACCESS  read-write
   STATUS      current
   DESCRIPTION
      "Path: ethernet3.editConf.vlan.vlan.queueCosMap.lowDelayQueue"
   ::= {er1645v2Lan3MCVlanEntry 241436160}

er1645v2Lan3MCVlanVlanQCMapLowDelay2Queue OBJECT-TYPE
   SYNTAX      Integer32
   MAX-ACCESS  read-write
   STATUS      current
   DESCRIPTION
      "Path: ethernet3.editConf.vlan.vlan.queueCosMap.lowDelay2Queue"
   ::= {er1645v2Lan3MCVlanEntry 241436416}

er1645v2Lan3MCVlanVlanQCMapSystemQueue OBJECT-TYPE
   SYNTAX      Integer32
   MAX-ACCESS  read-write
   STATUS      current
   DESCRIPTION
      "Path: ethernet3.editConf.vlan.vlan.queueCosMap.systemQueue"
   ::= {er1645v2Lan3MCVlanEntry 241436672}

er1645v2Lan3MCVlanVlanQinQSVid OBJECT-TYPE
   SYNTAX      Integer32
   MAX-ACCESS  read-write
   STATUS      current
   DESCRIPTION
      "Path: ethernet3.editConf.vlan.vlan.tunnel.sVid"
   ::= {er1645v2Lan3MCVlanEntry 241172736}

er1645v2Lan3MCVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tunnel.sTpid

       Possibilities:
               dot1Q   (33024)
               dot1ad   (34984)
               0x9100   (37120)
               0x9200   (37376)
               0x9300   (37632)"
   ::= {er1645v2Lan3MCVlanEntry 241172992}

er1645v2Lan3MCVlanVlanArpTimeOut OBJECT-TYPE
   SYNTAX      TimeTicks
   MAX-ACCESS  read-write
   STATUS      current
   DESCRIPTION
      "Path: ethernet3.editConf.vlan.vlan.arp.timeOut

       Time in centi-second."
   ::= {er1645v2Lan3MCVlanEntry 235277312}

er1645v2Lan3MCVlanVlanArpProxyArp OBJECT-TYPE
   SYNTAX      INTEGER
               {
               disabled (0),
               enabled (1)
               }
   MAX-ACCESS  read-write
   STATUS      current
   DESCRIPTION
      "Path: ethernet3.editConf.vlan.vlan.arp.proxyArp

       Possibilities:
               disabled   (0)
               enabled   (1)"
   ::= {er1645v2Lan3MCVlanEntry 235287040}

er1645v2Lan3MCVlanBandwidthMode OBJECT-TYPE
   SYNTAX      INTEGER
               {
               reshaping (1),
               policing (2),
               policingReshape (3)
               }
   MAX-ACCESS  read-write
   STATUS      current
   DESCRIPTION
      "Path: ethernet3.editConf.vlan.bandwidth.mode

       Possibilities:
               reshaping   (1)
               policing   (2)
               policingReshape   (3)"
   ::= {er1645v2Lan3MCVlanEntry 148897792}

er1645v2Lan3MCVlanBandwidthCir OBJECT-TYPE
   SYNTAX      Integer32
   MAX-ACCESS  read-write
   STATUS      current
   DESCRIPTION
      "Path: ethernet3.editConf.vlan.bandwidth.cir"
   ::= {er1645v2Lan3MCVlanEntry 135266304}

er1645v2Lan3MCVlanBandwidthEir OBJECT-TYPE
   SYNTAX      Integer32
   MAX-ACCESS  read-write
   STATUS      current
   DESCRIPTION
      "Path: ethernet3.editConf.vlan.bandwidth.eir"
   ::= {er1645v2Lan3MCVlanEntry 141557760}

er1645v2Lan3MCVlanBandwidthUnit OBJECT-TYPE
   SYNTAX      INTEGER
               {
               bitssec (1),
               percent (2)
               }
   MAX-ACCESS  read-write
   STATUS      current
   DESCRIPTION
      "Path: ethernet3.editConf.vlan.bandwidth.unit

       Possibilities:
               bits/sec   (1)
               percent   (2)"
   ::= {er1645v2Lan3MCVlanEntry 139460608}

er1645v2Lan3MCVlanBandwidthTc OBJECT-TYPE
   SYNTAX      INTEGER
               {
               auto (0)
               }
   MAX-ACCESS  read-write
   STATUS      current
   DESCRIPTION
      "Path: ethernet3.editConf.vlan.bandwidth.tc

       Possibilities:
               auto   (0)"
   ::= {er1645v2Lan3MCVlanEntry 140509184}

er1645v2Lan3MCVlanBandwidthTcFactor OBJECT-TYPE
   SYNTAX      INTEGER
               {
               ms (10),
               s100us (1)
               }
   MAX-ACCESS  read-write
   STATUS      current
   DESCRIPTION
      "Path: ethernet3.editConf.vlan.bandwidth.tcFactor

       Possibilities:
               ms   (10)
               *100us   (1)"
   ::= {er1645v2Lan3MCVlanEntry 142606336}

er1645v2Lan3MCVlanBandwidthCorrType OBJECT-TYPE
   SYNTAX      INTEGER
               {
               noCorrection (0),
               predefined (1),
               manual (2)
               }
   MAX-ACCESS  read-write
   STATUS      current
   DESCRIPTION
      "Path: ethernet3.editConf.vlan.bandwidth.correction.type

       Possibilities:
               noCorrection   (0)
               predefined   (1)
               manual   (2)"
   ::= {er1645v2Lan3MCVlanEntry 136445952}

er1645v2Lan3MCVlanBandwidthCorrPredefEncapsFrameRelay OBJECT-TYPE
   SYNTAX      DisplayString
   MAX-ACCESS  read-write
   STATUS      current
   DESCRIPTION
      "Path: ethernet3.editConf.vlan.bandwidth.correction.predefined.encapsulation.frameRelay"
   ::= {er1645v2Lan3MCVlanEntry 136594432}

er1645v2Lan3MCVlanBandwidthCorrPredefEncapsPpp OBJECT-TYPE
   SYNTAX      DisplayString
   MAX-ACCESS  read-write
   STATUS      current
   DESCRIPTION
      "Path: ethernet3.editConf.vlan.bandwidth.correction.predefined.encapsulation.ppp"
   ::= {er1645v2Lan3MCVlanEntry 136595456}

er1645v2Lan3MCVlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.bandwidth.correction.predefined.encapsulation.atm.higherLayer

       Possibilities:
               rfc2684   (0)
               ppp   (1)
               pppOverEthernet   (2)"
   ::= {er1645v2Lan3MCVlanEntry 136596608}

er1645v2Lan3MCVlanBandwidthCorrPredefEncapsAtmMp OBJECT-TYPE
   SYNTAX      INTEGER
               {
               llcEncapsulation (0),
               vcMultiplexing (1)
               }
   MAX-ACCESS  read-write
   STATUS      current
   DESCRIPTION
      "Path: ethernet3.editConf.vlan.bandwidth.correction.predefined.encapsulation.atm.multiProtocol

       Possibilities:
               llcEncapsulation   (0)
               vcMultiplexing   (1)"
   ::= {er1645v2Lan3MCVlanEntry 136596736}

er1645v2Lan3MCVlanBandwidthCorrPredefEncapsHdlc OBJECT-TYPE
   SYNTAX      DisplayString
   MAX-ACCESS  read-write
   STATUS      current
   DESCRIPTION
      "Path: ethernet3.editConf.vlan.bandwidth.correction.predefined.encapsulation.hdlc"
   ::= {er1645v2Lan3MCVlanEntry 136597504}

er1645v2Lan3MCVlanBandwidthCorrPredefEncapsEfmFs OBJECT-TYPE
   SYNTAX      Integer32
   MAX-ACCESS  read-write
   STATUS      current
   DESCRIPTION
      "Path: ethernet3.editConf.vlan.bandwidth.correction.predefined.encapsulation.efm.fragmentSize"
   ::= {er1645v2Lan3MCVlanEntry 136598656}

er1645v2Lan3MCVlanBandwidthCorrPredefEncapsEfmIb OBJECT-TYPE
   SYNTAX      Integer32
   MAX-ACCESS  read-write
   STATUS      current
   DESCRIPTION
      "Path: ethernet3.editConf.vlan.bandwidth.correction.predefined.encapsulation.efm.idleBytes"
   ::= {er1645v2Lan3MCVlanEntry 136598784}

er1645v2Lan3MCVlanBandwidthCorrPredefMode OBJECT-TYPE
   SYNTAX      INTEGER
               {
               routing (0),
               bridging (1)
               }
   MAX-ACCESS  read-write
   STATUS      current
   DESCRIPTION
      "Path: ethernet3.editConf.vlan.bandwidth.correction.predefined.mode

       Possibilities:
               routing   (0)
               bridging   (1)"
   ::= {er1645v2Lan3MCVlanEntry 136609792}

er1645v2Lan3MCVlanBandwidthCorrManualOverhead OBJECT-TYPE
   SYNTAX      Integer32
   MAX-ACCESS  read-write
   STATUS      current
   DESCRIPTION
      "Path: ethernet3.editConf.vlan.bandwidth.correction.manual.overhead"
   ::= {er1645v2Lan3MCVlanEntry 136708608}

er1645v2Lan3MCVlanBandwidthCorrManualFrameData OBJECT-TYPE
   SYNTAX      Counter32
   MAX-ACCESS  read-write
   STATUS      current
   DESCRIPTION
      "Path: ethernet3.editConf.vlan.bandwidth.correction.manual.frameData

       32 bit unsigned wrappable counter."
   ::= {er1645v2Lan3MCVlanEntry 136709120}

er1645v2Lan3MCVlanBandwidthCorrManualFrameHeader OBJECT-TYPE
   SYNTAX      Counter32
   MAX-ACCESS  read-write
   STATUS      current
   DESCRIPTION
      "Path: ethernet3.editConf.vlan.bandwidth.correction.manual.frameHeader

       32 bit unsigned wrappable counter."
   ::= {er1645v2Lan3MCVlanEntry 136709632}

er1645v2Lan3MCVlanBandwidthMaxFifoQLen OBJECT-TYPE
   SYNTAX      Integer32
   MAX-ACCESS  read-write
   STATUS      current
   DESCRIPTION
      "Path: ethernet3.editConf.vlan.bandwidth.maxFifoQLen"
   ::= {er1645v2Lan3MCVlanEntry 137363456}

er1645v2Lan3MCVlanBandwidthDeFlagCir OBJECT-TYPE
   SYNTAX      INTEGER
               {
               allowed (1),
               notAllowed (2)
               }
   MAX-ACCESS  read-write
   STATUS      current
   DESCRIPTION
      "Path: ethernet3.editConf.vlan.bandwidth.deFlag.cir

       Possibilities:
               allowed   (1)
               notAllowed   (2)"
   ::= {er1645v2Lan3MCVlanEntry 147853312}

er1645v2Lan3MCVlanBandwidthDeFlagEir OBJECT-TYPE
   SYNTAX      INTEGER
               {
               allowed (1),
               notAllowed (2)
               }
   MAX-ACCESS  read-write
   STATUS      current
   DESCRIPTION
      "Path: ethernet3.editConf.vlan.bandwidth.deFlag.eir

       Possibilities:
               allowed   (1)
               notAllowed   (2)"
   ::= {er1645v2Lan3MCVlanEntry 147857408}

er1645v2Lan3MCVlanBandwidthDeFlagViolate OBJECT-TYPE
   SYNTAX      INTEGER
               {
               allowed (1),
               notAllowed (2)
               }
   MAX-ACCESS  read-write
   STATUS      current
   DESCRIPTION
      "Path: ethernet3.editConf.vlan.bandwidth.deFlag.violate

       Possibilities:
               allowed   (1)
               notAllowed   (2)"
   ::= {er1645v2Lan3MCVlanEntry 147861504}

er1645v2Lan3MCVlanBandwidthActCirActNone OBJECT-TYPE
   SYNTAX      OCTET STRING
   MAX-ACCESS  read-write
   STATUS      current
   DESCRIPTION
      "Path: ethernet3.editConf.vlan.bandwidth.action.cirAction.none"
   ::= {er1645v2Lan3MCVlanEntry 150085632}

er1645v2Lan3MCVlanBandwidthActCirActEthCos1 OBJECT-TYPE
   SYNTAX      INTEGER
               {
               unchanged (256)
               }
   MAX-ACCESS  read-write
   STATUS      current
   DESCRIPTION
      "Path: ethernet3.editConf.vlan.bandwidth.action.cirAction.ethernet.cosDepth1

       Possibilities:
               unchanged   (256)"
   ::= {er1645v2Lan3MCVlanEntry 150094080}

er1645v2Lan3MCVlanBandwidthActCirActEthDei1 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth1

       Possibilities:
               unchanged   (255)
               clear   (0)
               set   (1)"
   ::= {er1645v2Lan3MCVlanEntry 150099200}

er1645v2Lan3MCVlanBandwidthActCirActEthCos2 OBJECT-TYPE
   SYNTAX      INTEGER
               {
               unchanged (256)
               }
   MAX-ACCESS  read-write
   STATUS      current
   DESCRIPTION
      "Path: ethernet3.editConf.vlan.bandwidth.action.cirAction.ethernet.cosDepth2

       Possibilities:
               unchanged   (256)"
   ::= {er1645v2Lan3MCVlanEntry 150094336}

er1645v2Lan3MCVlanBandwidthActCirActEthDei2 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth2

       Possibilities:
               unchanged   (255)
               clear   (0)
               set   (1)"
   ::= {er1645v2Lan3MCVlanEntry 150099456}

er1645v2Lan3MCVlanBandwidthActCirActEthCos3 OBJECT-TYPE
   SYNTAX      INTEGER
               {
               unchanged (256)
               }
   MAX-ACCESS  read-write
   STATUS      current
   DESCRIPTION
      "Path: ethernet3.editConf.vlan.bandwidth.action.cirAction.ethernet.cosDepth3

       Possibilities:
               unchanged   (256)"
   ::= {er1645v2Lan3MCVlanEntry 150094592}

er1645v2Lan3MCVlanBandwidthActCirActEthDei3 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth3

       Possibilities:
               unchanged   (255)
               clear   (0)
               set   (1)"
   ::= {er1645v2Lan3MCVlanEntry 150099712}

er1645v2Lan3MCVlanBandwidthActCirActEthCos4 OBJECT-TYPE
   SYNTAX      INTEGER
               {
               unchanged (256)
               }
   MAX-ACCESS  read-write
   STATUS      current
   DESCRIPTION
      "Path: ethernet3.editConf.vlan.bandwidth.action.cirAction.ethernet.cosDepth4

       Possibilities:
               unchanged   (256)"
   ::= {er1645v2Lan3MCVlanEntry 150094848}

er1645v2Lan3MCVlanBandwidthActCirActEthDei4 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth4

       Possibilities:
               unchanged   (255)
               clear   (0)
               set   (1)"
   ::= {er1645v2Lan3MCVlanEntry 150099968}

er1645v2Lan3MCVlanBandwidthActCirActEthCos5 OBJECT-TYPE
   SYNTAX      INTEGER
               {
               unchanged (256)
               }
   MAX-ACCESS  read-write
   STATUS      current
   DESCRIPTION
      "Path: ethernet3.editConf.vlan.bandwidth.action.cirAction.ethernet.cosDepth5

       Possibilities:
               unchanged   (256)"
   ::= {er1645v2Lan3MCVlanEntry 150095104}

er1645v2Lan3MCVlanBandwidthActCirActEthDei5 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth5

       Possibilities:
               unchanged   (255)
               clear   (0)
               set   (1)"
   ::= {er1645v2Lan3MCVlanEntry 150100224}

er1645v2Lan3MCVlanBandwidthActCirActEthCos6 OBJECT-TYPE
   SYNTAX      INTEGER
               {
               unchanged (256)
               }
   MAX-ACCESS  read-write
   STATUS      current
   DESCRIPTION
      "Path: ethernet3.editConf.vlan.bandwidth.action.cirAction.ethernet.cosDepth6

       Possibilities:
               unchanged   (256)"
   ::= {er1645v2Lan3MCVlanEntry 150095360}

er1645v2Lan3MCVlanBandwidthActCirActEthDei6 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth6

       Possibilities:
               unchanged   (255)
               clear   (0)
               set   (1)"
   ::= {er1645v2Lan3MCVlanEntry 150100480}

er1645v2Lan3MCVlanBandwidthActCirActEthCos7 OBJECT-TYPE
   SYNTAX      INTEGER
               {
               unchanged (256)
               }
   MAX-ACCESS  read-write
   STATUS      current
   DESCRIPTION
      "Path: ethernet3.editConf.vlan.bandwidth.action.cirAction.ethernet.cosDepth7

       Possibilities:
               unchanged   (256)"
   ::= {er1645v2Lan3MCVlanEntry 150095616}

er1645v2Lan3MCVlanBandwidthActCirActEthDei7 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth7

       Possibilities:
               unchanged   (255)
               clear   (0)
               set   (1)"
   ::= {er1645v2Lan3MCVlanEntry 150100736}

er1645v2Lan3MCVlanBandwidthActCirActEthCos8 OBJECT-TYPE
   SYNTAX      INTEGER
               {
               unchanged (256)
               }
   MAX-ACCESS  read-write
   STATUS      current
   DESCRIPTION
      "Path: ethernet3.editConf.vlan.bandwidth.action.cirAction.ethernet.cosDepth8

       Possibilities:
               unchanged   (256)"
   ::= {er1645v2Lan3MCVlanEntry 150095872}

er1645v2Lan3MCVlanBandwidthActCirActEthDei8 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth8

       Possibilities:
               unchanged   (255)
               clear   (0)
               set   (1)"
   ::= {er1645v2Lan3MCVlanEntry 150100992}

er1645v2Lan3MCVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150096128}

er1645v2Lan3MCVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150096384}

er1645v2Lan3MCVlanBandwidthActCirActEthDrpLev OBJECT-TYPE
   SYNTAX      INTEGER
               {
               unchanged (0)
               }
   MAX-ACCESS  read-write
   STATUS      current
   DESCRIPTION
      "Path: ethernet3.editConf.vlan.bandwidth.action.cirAction.ethernet.dropLevel

       Possibilities:
               unchanged   (0)"
   ::= {er1645v2Lan3MCVlanEntry 150096640}

er1645v2Lan3MCVlanBandwidthActCirActEthDeFlag OBJECT-TYPE
   SYNTAX      INTEGER
               {
               unchanged (255),
               clear (0),
               set (1)
               }
   MAX-ACCESS  read-write
   STATUS      current
   DESCRIPTION
      "Path: ethernet3.editConf.vlan.bandwidth.action.cirAction.ethernet.deFlag

       Possibilities:
               unchanged   (255)
               clear   (0)
               set   (1)"
   ::= {er1645v2Lan3MCVlanEntry 150097408}

er1645v2Lan3MCVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150120704}

er1645v2Lan3MCVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150120960}

er1645v2Lan3MCVlanBandwidthActCirActIpDrpLev OBJECT-TYPE
   SYNTAX      INTEGER
               {
               unchanged (0)
               }
   MAX-ACCESS  read-write
   STATUS      current
   DESCRIPTION
      "Path: ethernet3.editConf.vlan.bandwidth.action.cirAction.ip.dropLevel

       Possibilities:
               unchanged   (0)"
   ::= {er1645v2Lan3MCVlanEntry 150121216}

er1645v2Lan3MCVlanBandwidthActCirActIpDeFlag OBJECT-TYPE
   SYNTAX      INTEGER
               {
               unchanged (255),
               clear (0),
               set (1)
               }
   MAX-ACCESS  read-write
   STATUS      current
   DESCRIPTION
      "Path: ethernet3.editConf.vlan.bandwidth.action.cirAction.ip.deFlag

       Possibilities:
               unchanged   (255)
               clear   (0)
               set   (1)"
   ::= {er1645v2Lan3MCVlanEntry 150121984}

er1645v2Lan3MCVlanBandwidthActEirActNone OBJECT-TYPE
   SYNTAX      OCTET STRING
   MAX-ACCESS  read-write
   STATUS      current
   DESCRIPTION
      "Path: ethernet3.editConf.vlan.bandwidth.action.eirAction.none"
   ::= {er1645v2Lan3MCVlanEntry 150216704}

er1645v2Lan3MCVlanBandwidthActEirActEthCos1 OBJECT-TYPE
   SYNTAX      INTEGER
               {
               unchanged (256)
               }
   MAX-ACCESS  read-write
   STATUS      current
   DESCRIPTION
      "Path: ethernet3.editConf.vlan.bandwidth.action.eirAction.ethernet.cosDepth1

       Possibilities:
               unchanged   (256)"
   ::= {er1645v2Lan3MCVlanEntry 150225152}

er1645v2Lan3MCVlanBandwidthActEirActEthDei1 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth1

       Possibilities:
               unchanged   (255)
               clear   (0)
               set   (1)"
   ::= {er1645v2Lan3MCVlanEntry 150230272}

er1645v2Lan3MCVlanBandwidthActEirActEthCos2 OBJECT-TYPE
   SYNTAX      INTEGER
               {
               unchanged (256)
               }
   MAX-ACCESS  read-write
   STATUS      current
   DESCRIPTION
      "Path: ethernet3.editConf.vlan.bandwidth.action.eirAction.ethernet.cosDepth2

       Possibilities:
               unchanged   (256)"
   ::= {er1645v2Lan3MCVlanEntry 150225408}

er1645v2Lan3MCVlanBandwidthActEirActEthDei2 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth2

       Possibilities:
               unchanged   (255)
               clear   (0)
               set   (1)"
   ::= {er1645v2Lan3MCVlanEntry 150230528}

er1645v2Lan3MCVlanBandwidthActEirActEthCos3 OBJECT-TYPE
   SYNTAX      INTEGER
               {
               unchanged (256)
               }
   MAX-ACCESS  read-write
   STATUS      current
   DESCRIPTION
      "Path: ethernet3.editConf.vlan.bandwidth.action.eirAction.ethernet.cosDepth3

       Possibilities:
               unchanged   (256)"
   ::= {er1645v2Lan3MCVlanEntry 150225664}

er1645v2Lan3MCVlanBandwidthActEirActEthDei3 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth3

       Possibilities:
               unchanged   (255)
               clear   (0)
               set   (1)"
   ::= {er1645v2Lan3MCVlanEntry 150230784}

er1645v2Lan3MCVlanBandwidthActEirActEthCos4 OBJECT-TYPE
   SYNTAX      INTEGER
               {
               unchanged (256)
               }
   MAX-ACCESS  read-write
   STATUS      current
   DESCRIPTION
      "Path: ethernet3.editConf.vlan.bandwidth.action.eirAction.ethernet.cosDepth4

       Possibilities:
               unchanged   (256)"
   ::= {er1645v2Lan3MCVlanEntry 150225920}

er1645v2Lan3MCVlanBandwidthActEirActEthDei4 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth4

       Possibilities:
               unchanged   (255)
               clear   (0)
               set   (1)"
   ::= {er1645v2Lan3MCVlanEntry 150231040}

er1645v2Lan3MCVlanBandwidthActEirActEthCos5 OBJECT-TYPE
   SYNTAX      INTEGER
               {
               unchanged (256)
               }
   MAX-ACCESS  read-write
   STATUS      current
   DESCRIPTION
      "Path: ethernet3.editConf.vlan.bandwidth.action.eirAction.ethernet.cosDepth5

       Possibilities:
               unchanged   (256)"
   ::= {er1645v2Lan3MCVlanEntry 150226176}

er1645v2Lan3MCVlanBandwidthActEirActEthDei5 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth5

       Possibilities:
               unchanged   (255)
               clear   (0)
               set   (1)"
   ::= {er1645v2Lan3MCVlanEntry 150231296}

er1645v2Lan3MCVlanBandwidthActEirActEthCos6 OBJECT-TYPE
   SYNTAX      INTEGER
               {
               unchanged (256)
               }
   MAX-ACCESS  read-write
   STATUS      current
   DESCRIPTION
      "Path: ethernet3.editConf.vlan.bandwidth.action.eirAction.ethernet.cosDepth6

       Possibilities:
               unchanged   (256)"
   ::= {er1645v2Lan3MCVlanEntry 150226432}

er1645v2Lan3MCVlanBandwidthActEirActEthDei6 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth6

       Possibilities:
               unchanged   (255)
               clear   (0)
               set   (1)"
   ::= {er1645v2Lan3MCVlanEntry 150231552}

er1645v2Lan3MCVlanBandwidthActEirActEthCos7 OBJECT-TYPE
   SYNTAX      INTEGER
               {
               unchanged (256)
               }
   MAX-ACCESS  read-write
   STATUS      current
   DESCRIPTION
      "Path: ethernet3.editConf.vlan.bandwidth.action.eirAction.ethernet.cosDepth7

       Possibilities:
               unchanged   (256)"
   ::= {er1645v2Lan3MCVlanEntry 150226688}

er1645v2Lan3MCVlanBandwidthActEirActEthDei7 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth7

       Possibilities:
               unchanged   (255)
               clear   (0)
               set   (1)"
   ::= {er1645v2Lan3MCVlanEntry 150231808}

er1645v2Lan3MCVlanBandwidthActEirActEthCos8 OBJECT-TYPE
   SYNTAX      INTEGER
               {
               unchanged (256)
               }
   MAX-ACCESS  read-write
   STATUS      current
   DESCRIPTION
      "Path: ethernet3.editConf.vlan.bandwidth.action.eirAction.ethernet.cosDepth8

       Possibilities:
               unchanged   (256)"
   ::= {er1645v2Lan3MCVlanEntry 150226944}

er1645v2Lan3MCVlanBandwidthActEirActEthDei8 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth8

       Possibilities:
               unchanged   (255)
               clear   (0)
               set   (1)"
   ::= {er1645v2Lan3MCVlanEntry 150232064}

er1645v2Lan3MCVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150227200}

er1645v2Lan3MCVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150227456}

er1645v2Lan3MCVlanBandwidthActEirActEthDrpLev OBJECT-TYPE
   SYNTAX      INTEGER
               {
               unchanged (0)
               }
   MAX-ACCESS  read-write
   STATUS      current
   DESCRIPTION
      "Path: ethernet3.editConf.vlan.bandwidth.action.eirAction.ethernet.dropLevel

       Possibilities:
               unchanged   (0)"
   ::= {er1645v2Lan3MCVlanEntry 150227712}

er1645v2Lan3MCVlanBandwidthActEirActEthDeFlag OBJECT-TYPE
   SYNTAX      INTEGER
               {
               unchanged (255),
               clear (0),
               set (1)
               }
   MAX-ACCESS  read-write
   STATUS      current
   DESCRIPTION
      "Path: ethernet3.editConf.vlan.bandwidth.action.eirAction.ethernet.deFlag

       Possibilities:
               unchanged   (255)
               clear   (0)
               set   (1)"
   ::= {er1645v2Lan3MCVlanEntry 150228480}

er1645v2Lan3MCVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150251776}

er1645v2Lan3MCVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150252032}

er1645v2Lan3MCVlanBandwidthActEirActIpDrpLev OBJECT-TYPE
   SYNTAX      INTEGER
               {
               unchanged (0)
               }
   MAX-ACCESS  read-write
   STATUS      current
   DESCRIPTION
      "Path: ethernet3.editConf.vlan.bandwidth.action.eirAction.ip.dropLevel

       Possibilities:
               unchanged   (0)"
   ::= {er1645v2Lan3MCVlanEntry 150252288}

er1645v2Lan3MCVlanBandwidthActEirActIpDeFlag OBJECT-TYPE
   SYNTAX      INTEGER
               {
               unchanged (255),
               clear (0),
               set (1)
               }
   MAX-ACCESS  read-write
   STATUS      current
   DESCRIPTION
      "Path: ethernet3.editConf.vlan.bandwidth.action.eirAction.ip.deFlag

       Possibilities:
               unchanged   (255)
               clear   (0)
               set   (1)"
   ::= {er1645v2Lan3MCVlanEntry 150253056}

er1645v2Lan3MCVlanBandwidthActViolActNone OBJECT-TYPE
   SYNTAX      OCTET STRING
   MAX-ACCESS  read-write
   STATUS      current
   DESCRIPTION
      "Path: ethernet3.editConf.vlan.bandwidth.action.violateAction.none"
   ::= {er1645v2Lan3MCVlanEntry 150347776}

er1645v2Lan3MCVlanBandwidthActViolActDrop OBJECT-TYPE
   SYNTAX      OCTET STRING
   MAX-ACCESS  read-write
   STATUS      current
   DESCRIPTION
      "Path: ethernet3.editConf.vlan.bandwidth.action.violateAction.drop"
   ::= {er1645v2Lan3MCVlanEntry 150364160}

er1645v2Lan3MCVlanBandwidthActViolActEthCos1 OBJECT-TYPE
   SYNTAX      INTEGER
               {
               unchanged (256)
               }
   MAX-ACCESS  read-write
   STATUS      current
   DESCRIPTION
      "Path: ethernet3.editConf.vlan.bandwidth.action.violateAction.ethernet.cosDepth1

       Possibilities:
               unchanged   (256)"
   ::= {er1645v2Lan3MCVlanEntry 150356224}

er1645v2Lan3MCVlanBandwidthActViolActEthDei1 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth1

       Possibilities:
               unchanged   (255)
               clear   (0)
               set   (1)"
   ::= {er1645v2Lan3MCVlanEntry 150361344}

er1645v2Lan3MCVlanBandwidthActViolActEthCos2 OBJECT-TYPE
   SYNTAX      INTEGER
               {
               unchanged (256)
               }
   MAX-ACCESS  read-write
   STATUS      current
   DESCRIPTION
      "Path: ethernet3.editConf.vlan.bandwidth.action.violateAction.ethernet.cosDepth2

       Possibilities:
               unchanged   (256)"
   ::= {er1645v2Lan3MCVlanEntry 150356480}

er1645v2Lan3MCVlanBandwidthActViolActEthDei2 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth2

       Possibilities:
               unchanged   (255)
               clear   (0)
               set   (1)"
   ::= {er1645v2Lan3MCVlanEntry 150361600}

er1645v2Lan3MCVlanBandwidthActViolActEthCos3 OBJECT-TYPE
   SYNTAX      INTEGER
               {
               unchanged (256)
               }
   MAX-ACCESS  read-write
   STATUS      current
   DESCRIPTION
      "Path: ethernet3.editConf.vlan.bandwidth.action.violateAction.ethernet.cosDepth3

       Possibilities:
               unchanged   (256)"
   ::= {er1645v2Lan3MCVlanEntry 150356736}

er1645v2Lan3MCVlanBandwidthActViolActEthDei3 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth3

       Possibilities:
               unchanged   (255)
               clear   (0)
               set   (1)"
   ::= {er1645v2Lan3MCVlanEntry 150361856}

er1645v2Lan3MCVlanBandwidthActViolActEthCos4 OBJECT-TYPE
   SYNTAX      INTEGER
               {
               unchanged (256)
               }
   MAX-ACCESS  read-write
   STATUS      current
   DESCRIPTION
      "Path: ethernet3.editConf.vlan.bandwidth.action.violateAction.ethernet.cosDepth4

       Possibilities:
               unchanged   (256)"
   ::= {er1645v2Lan3MCVlanEntry 150356992}

er1645v2Lan3MCVlanBandwidthActViolActEthDei4 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth4

       Possibilities:
               unchanged   (255)
               clear   (0)
               set   (1)"
   ::= {er1645v2Lan3MCVlanEntry 150362112}

er1645v2Lan3MCVlanBandwidthActViolActEthCos5 OBJECT-TYPE
   SYNTAX      INTEGER
               {
               unchanged (256)
               }
   MAX-ACCESS  read-write
   STATUS      current
   DESCRIPTION
      "Path: ethernet3.editConf.vlan.bandwidth.action.violateAction.ethernet.cosDepth5

       Possibilities:
               unchanged   (256)"
   ::= {er1645v2Lan3MCVlanEntry 150357248}

er1645v2Lan3MCVlanBandwidthActViolActEthDei5 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth5

       Possibilities:
               unchanged   (255)
               clear   (0)
               set   (1)"
   ::= {er1645v2Lan3MCVlanEntry 150362368}

er1645v2Lan3MCVlanBandwidthActViolActEthCos6 OBJECT-TYPE
   SYNTAX      INTEGER
               {
               unchanged (256)
               }
   MAX-ACCESS  read-write
   STATUS      current
   DESCRIPTION
      "Path: ethernet3.editConf.vlan.bandwidth.action.violateAction.ethernet.cosDepth6

       Possibilities:
               unchanged   (256)"
   ::= {er1645v2Lan3MCVlanEntry 150357504}

er1645v2Lan3MCVlanBandwidthActViolActEthDei6 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth6

       Possibilities:
               unchanged   (255)
               clear   (0)
               set   (1)"
   ::= {er1645v2Lan3MCVlanEntry 150362624}

er1645v2Lan3MCVlanBandwidthActViolActEthCos7 OBJECT-TYPE
   SYNTAX      INTEGER
               {
               unchanged (256)
               }
   MAX-ACCESS  read-write
   STATUS      current
   DESCRIPTION
      "Path: ethernet3.editConf.vlan.bandwidth.action.violateAction.ethernet.cosDepth7

       Possibilities:
               unchanged   (256)"
   ::= {er1645v2Lan3MCVlanEntry 150357760}

er1645v2Lan3MCVlanBandwidthActViolActEthDei7 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth7

       Possibilities:
               unchanged   (255)
               clear   (0)
               set   (1)"
   ::= {er1645v2Lan3MCVlanEntry 150362880}

er1645v2Lan3MCVlanBandwidthActViolActEthCos8 OBJECT-TYPE
   SYNTAX      INTEGER
               {
               unchanged (256)
               }
   MAX-ACCESS  read-write
   STATUS      current
   DESCRIPTION
      "Path: ethernet3.editConf.vlan.bandwidth.action.violateAction.ethernet.cosDepth8

       Possibilities:
               unchanged   (256)"
   ::= {er1645v2Lan3MCVlanEntry 150358016}

er1645v2Lan3MCVlanBandwidthActViolActEthDei8 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth8

       Possibilities:
               unchanged   (255)
               clear   (0)
               set   (1)"
   ::= {er1645v2Lan3MCVlanEntry 150363136}

er1645v2Lan3MCVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150358272}

er1645v2Lan3MCVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150358528}

er1645v2Lan3MCVlanBandwidthActViolActEthDrpLev OBJECT-TYPE
   SYNTAX      INTEGER
               {
               unchanged (0)
               }
   MAX-ACCESS  read-write
   STATUS      current
   DESCRIPTION
      "Path: ethernet3.editConf.vlan.bandwidth.action.violateAction.ethernet.dropLevel

       Possibilities:
               unchanged   (0)"
   ::= {er1645v2Lan3MCVlanEntry 150358784}

er1645v2Lan3MCVlanBandwidthActViolActEthDeFlag OBJECT-TYPE
   SYNTAX      INTEGER
               {
               unchanged (255),
               clear (0),
               set (1)
               }
   MAX-ACCESS  read-write
   STATUS      current
   DESCRIPTION
      "Path: ethernet3.editConf.vlan.bandwidth.action.violateAction.ethernet.deFlag

       Possibilities:
               unchanged   (255)
               clear   (0)
               set   (1)"
   ::= {er1645v2Lan3MCVlanEntry 150359552}

er1645v2Lan3MCVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 150382848}

er1645v2Lan3MCVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 150383104}

er1645v2Lan3MCVlanBandwidthActViolActIpDrpLev OBJECT-TYPE
   SYNTAX      INTEGER
               {
               unchanged (0)
               }
   MAX-ACCESS  read-write
   STATUS      current
   DESCRIPTION
      "Path: ethernet3.editConf.vlan.bandwidth.action.violateAction.ip.dropLevel

       Possibilities:
               unchanged   (0)"
   ::= {er1645v2Lan3MCVlanEntry 150383360}

er1645v2Lan3MCVlanBandwidthActViolActIpDeFlag OBJECT-TYPE
   SYNTAX      INTEGER
               {
               unchanged (255),
               clear (0),
               set (1)
               }
   MAX-ACCESS  read-write
   STATUS      current
   DESCRIPTION
      "Path: ethernet3.editConf.vlan.bandwidth.action.violateAction.ip.deFlag

       Possibilities:
               unchanged   (255)
               clear   (0)
               set   (1)"
   ::= {er1645v2Lan3MCVlanEntry 150384128}

er1645v2Lan3MCVlanInbBwMode OBJECT-TYPE
   SYNTAX      INTEGER
               {
               reshaping (1),
               policing (2)
               }
   MAX-ACCESS  read-write
   STATUS      current
   DESCRIPTION
      "Path: ethernet3.editConf.vlan.inboundBandwidth.mode

       Possibilities:
               reshaping   (1)
               policing   (2)"
   ::= {er1645v2Lan3MCVlanEntry 132120576}

er1645v2Lan3MCVlanInbBwCir OBJECT-TYPE
   SYNTAX      Integer32
   MAX-ACCESS  read-write
   STATUS      current
   DESCRIPTION
      "Path: ethernet3.editConf.vlan.inboundBandwidth.cir"
   ::= {er1645v2Lan3MCVlanEntry 118489088}

er1645v2Lan3MCVlanInbBwEir OBJECT-TYPE
   SYNTAX      Integer32
   MAX-ACCESS  read-write
   STATUS      current
   DESCRIPTION
      "Path: ethernet3.editConf.vlan.inboundBandwidth.eir"
   ::= {er1645v2Lan3MCVlanEntry 124780544}

er1645v2Lan3MCVlanInbBwUnit OBJECT-TYPE
   SYNTAX      INTEGER
               {
               bitssec (1),
               percent (2)
               }
   MAX-ACCESS  read-write
   STATUS      current
   DESCRIPTION
      "Path: ethernet3.editConf.vlan.inboundBandwidth.unit

       Possibilities:
               bits/sec   (1)
               percent   (2)"
   ::= {er1645v2Lan3MCVlanEntry 122683392}

er1645v2Lan3MCVlanInbBwTc OBJECT-TYPE
   SYNTAX      INTEGER
               {
               auto (0)
               }
   MAX-ACCESS  read-write
   STATUS      current
   DESCRIPTION
      "Path: ethernet3.editConf.vlan.inboundBandwidth.tc

       Possibilities:
               auto   (0)"
   ::= {er1645v2Lan3MCVlanEntry 123731968}

er1645v2Lan3MCVlanInbBwTcFactor OBJECT-TYPE
   SYNTAX      INTEGER
               {
               ms (10),
               s100us (1)
               }
   MAX-ACCESS  read-write
   STATUS      current
   DESCRIPTION
      "Path: ethernet3.editConf.vlan.inboundBandwidth.tcFactor

       Possibilities:
               ms   (10)
               *100us   (1)"
   ::= {er1645v2Lan3MCVlanEntry 125829120}

er1645v2Lan3MCVlanInbBwCorrType OBJECT-TYPE
   SYNTAX      INTEGER
               {
               noCorrection (0),
               predefined (1),
               manual (2)
               }
   MAX-ACCESS  read-write
   STATUS      current
   DESCRIPTION
      "Path: ethernet3.editConf.vlan.inboundBandwidth.correction.type

       Possibilities:
               noCorrection   (0)
               predefined   (1)
               manual   (2)"
   ::= {er1645v2Lan3MCVlanEntry 119668736}

er1645v2Lan3MCVlanInbBwCorrPredefEncapsFrameRelay OBJECT-TYPE
   SYNTAX      DisplayString
   MAX-ACCESS  read-write
   STATUS      current
   DESCRIPTION
      "Path: ethernet3.editConf.vlan.inboundBandwidth.correction.predefined.encapsulation.frameRelay"
   ::= {er1645v2Lan3MCVlanEntry 119817216}

er1645v2Lan3MCVlanInbBwCorrPredefEncapsPpp OBJECT-TYPE
   SYNTAX      DisplayString
   MAX-ACCESS  read-write
   STATUS      current
   DESCRIPTION
      "Path: ethernet3.editConf.vlan.inboundBandwidth.correction.predefined.encapsulation.ppp"
   ::= {er1645v2Lan3MCVlanEntry 119818240}

er1645v2Lan3MCVlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.inboundBandwidth.correction.predefined.encapsulation.atm.higherLayer

       Possibilities:
               rfc2684   (0)
               ppp   (1)
               pppOverEthernet   (2)"
   ::= {er1645v2Lan3MCVlanEntry 119819392}

er1645v2Lan3MCVlanInbBwCorrPredefEncapsAtmMp OBJECT-TYPE
   SYNTAX      INTEGER
               {
               llcEncapsulation (0),
               vcMultiplexing (1)
               }
   MAX-ACCESS  read-write
   STATUS      current
   DESCRIPTION
      "Path: ethernet3.editConf.vlan.inboundBandwidth.correction.predefined.encapsulation.atm.multiProtocol

       Possibilities:
               llcEncapsulation   (0)
               vcMultiplexing   (1)"
   ::= {er1645v2Lan3MCVlanEntry 119819520}

er1645v2Lan3MCVlanInbBwCorrPredefEncapsHdlc OBJECT-TYPE
   SYNTAX      DisplayString
   MAX-ACCESS  read-write
   STATUS      current
   DESCRIPTION
      "Path: ethernet3.editConf.vlan.inboundBandwidth.correction.predefined.encapsulation.hdlc"
   ::= {er1645v2Lan3MCVlanEntry 119820288}

er1645v2Lan3MCVlanInbBwCorrPredefEncapsEfmFs OBJECT-TYPE
   SYNTAX      Integer32
   MAX-ACCESS  read-write
   STATUS      current
   DESCRIPTION
      "Path: ethernet3.editConf.vlan.inboundBandwidth.correction.predefined.encapsulation.efm.fragmentSize"
   ::= {er1645v2Lan3MCVlanEntry 119821440}

er1645v2Lan3MCVlanInbBwCorrPredefEncapsEfmIb OBJECT-TYPE
   SYNTAX      Integer32
   MAX-ACCESS  read-write
   STATUS      current
   DESCRIPTION
      "Path: ethernet3.editConf.vlan.inboundBandwidth.correction.predefined.encapsulation.efm.idleBytes"
   ::= {er1645v2Lan3MCVlanEntry 119821568}

er1645v2Lan3MCVlanInbBwCorrPredefMode OBJECT-TYPE
   SYNTAX      INTEGER
               {
               routing (0),
               bridging (1)
               }
   MAX-ACCESS  read-write
   STATUS      current
   DESCRIPTION
      "Path: ethernet3.editConf.vlan.inboundBandwidth.correction.predefined.mode

       Possibilities:
               routing   (0)
               bridging   (1)"
   ::= {er1645v2Lan3MCVlanEntry 119832576}

er1645v2Lan3MCVlanInbBwCorrManualOverhead OBJECT-TYPE
   SYNTAX      Integer32
   MAX-ACCESS  read-write
   STATUS      current
   DESCRIPTION
      "Path: ethernet3.editConf.vlan.inboundBandwidth.correction.manual.overhead"
   ::= {er1645v2Lan3MCVlanEntry 119931392}

er1645v2Lan3MCVlanInbBwCorrManualFrameData OBJECT-TYPE
   SYNTAX      Counter32
   MAX-ACCESS  read-write
   STATUS      current
   DESCRIPTION
      "Path: ethernet3.editConf.vlan.inboundBandwidth.correction.manual.frameData

       32 bit unsigned wrappable counter."
   ::= {er1645v2Lan3MCVlanEntry 119931904}

er1645v2Lan3MCVlanInbBwCorrManualFrameHeader OBJECT-TYPE
   SYNTAX      Counter32
   MAX-ACCESS  read-write
   STATUS      current
   DESCRIPTION
      "Path: ethernet3.editConf.vlan.inboundBandwidth.correction.manual.frameHeader

       32 bit unsigned wrappable counter."
   ::= {er1645v2Lan3MCVlanEntry 119932416}

er1645v2Lan3MCVlanInbBwMaxFifoQLen OBJECT-TYPE
   SYNTAX      Integer32
   MAX-ACCESS  read-write
   STATUS      current
   DESCRIPTION
      "Path: ethernet3.editConf.vlan.inboundBandwidth.maxFifoQLen"
   ::= {er1645v2Lan3MCVlanEntry 120586240}

er1645v2Lan3MCVlanInbBwPriorityPolicy OBJECT-TYPE
   SYNTAX      DisplayString
   MAX-ACCESS  read-write
   STATUS      current
   DESCRIPTION
      "Path: ethernet3.editConf.vlan.inboundBandwidth.priorityPolicy"
   ::= {er1645v2Lan3MCVlanEntry 121634816}

er1645v2Lan3MCVlanInbBwDeFlagCir OBJECT-TYPE
   SYNTAX      INTEGER
               {
               allowed (1),
               notAllowed (2)
               }
   MAX-ACCESS  read-write
   STATUS      current
   DESCRIPTION
      "Path: ethernet3.editConf.vlan.inboundBandwidth.deFlag.cir

       Possibilities:
               allowed   (1)
               notAllowed   (2)"
   ::= {er1645v2Lan3MCVlanEntry 131076096}

er1645v2Lan3MCVlanInbBwDeFlagEir OBJECT-TYPE
   SYNTAX      INTEGER
               {
               allowed (1),
               notAllowed (2)
               }
   MAX-ACCESS  read-write
   STATUS      current
   DESCRIPTION
      "Path: ethernet3.editConf.vlan.inboundBandwidth.deFlag.eir

       Possibilities:
               allowed   (1)
               notAllowed   (2)"
   ::= {er1645v2Lan3MCVlanEntry 131080192}

er1645v2Lan3MCVlanInbBwDeFlagViolate OBJECT-TYPE
   SYNTAX      INTEGER
               {
               allowed (1),
               notAllowed (2)
               }
   MAX-ACCESS  read-write
   STATUS      current
   DESCRIPTION
      "Path: ethernet3.editConf.vlan.inboundBandwidth.deFlag.violate

       Possibilities:
               allowed   (1)
               notAllowed   (2)"
   ::= {er1645v2Lan3MCVlanEntry 131084288}

er1645v2Lan3MCVlanInbBwActCirActNone OBJECT-TYPE
   SYNTAX      OCTET STRING
   MAX-ACCESS  read-write
   STATUS      current
   DESCRIPTION
      "Path: ethernet3.editConf.vlan.inboundBandwidth.action.cirAction.none"
   ::= {er1645v2Lan3MCVlanEntry 133308416}

er1645v2Lan3MCVlanInbBwActCirActEthCos1 OBJECT-TYPE
   SYNTAX      INTEGER
               {
               unchanged (256)
               }
   MAX-ACCESS  read-write
   STATUS      current
   DESCRIPTION
      "Path: ethernet3.editConf.vlan.inboundBandwidth.action.cirAction.ethernet.cosDepth1

       Possibilities:
               unchanged   (256)"
   ::= {er1645v2Lan3MCVlanEntry 133316864}

er1645v2Lan3MCVlanInbBwActCirActEthDei1 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth1

       Possibilities:
               unchanged   (255)
               clear   (0)
               set   (1)"
   ::= {er1645v2Lan3MCVlanEntry 133321984}

er1645v2Lan3MCVlanInbBwActCirActEthCos2 OBJECT-TYPE
   SYNTAX      INTEGER
               {
               unchanged (256)
               }
   MAX-ACCESS  read-write
   STATUS      current
   DESCRIPTION
      "Path: ethernet3.editConf.vlan.inboundBandwidth.action.cirAction.ethernet.cosDepth2

       Possibilities:
               unchanged   (256)"
   ::= {er1645v2Lan3MCVlanEntry 133317120}

er1645v2Lan3MCVlanInbBwActCirActEthDei2 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth2

       Possibilities:
               unchanged   (255)
               clear   (0)
               set   (1)"
   ::= {er1645v2Lan3MCVlanEntry 133322240}

er1645v2Lan3MCVlanInbBwActCirActEthCos3 OBJECT-TYPE
   SYNTAX      INTEGER
               {
               unchanged (256)
               }
   MAX-ACCESS  read-write
   STATUS      current
   DESCRIPTION
      "Path: ethernet3.editConf.vlan.inboundBandwidth.action.cirAction.ethernet.cosDepth3

       Possibilities:
               unchanged   (256)"
   ::= {er1645v2Lan3MCVlanEntry 133317376}

er1645v2Lan3MCVlanInbBwActCirActEthDei3 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth3

       Possibilities:
               unchanged   (255)
               clear   (0)
               set   (1)"
   ::= {er1645v2Lan3MCVlanEntry 133322496}

er1645v2Lan3MCVlanInbBwActCirActEthCos4 OBJECT-TYPE
   SYNTAX      INTEGER
               {
               unchanged (256)
               }
   MAX-ACCESS  read-write
   STATUS      current
   DESCRIPTION
      "Path: ethernet3.editConf.vlan.inboundBandwidth.action.cirAction.ethernet.cosDepth4

       Possibilities:
               unchanged   (256)"
   ::= {er1645v2Lan3MCVlanEntry 133317632}

er1645v2Lan3MCVlanInbBwActCirActEthDei4 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth4

       Possibilities:
               unchanged   (255)
               clear   (0)
               set   (1)"
   ::= {er1645v2Lan3MCVlanEntry 133322752}

er1645v2Lan3MCVlanInbBwActCirActEthCos5 OBJECT-TYPE
   SYNTAX      INTEGER
               {
               unchanged (256)
               }
   MAX-ACCESS  read-write
   STATUS      current
   DESCRIPTION
      "Path: ethernet3.editConf.vlan.inboundBandwidth.action.cirAction.ethernet.cosDepth5

       Possibilities:
               unchanged   (256)"
   ::= {er1645v2Lan3MCVlanEntry 133317888}

er1645v2Lan3MCVlanInbBwActCirActEthDei5 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth5

       Possibilities:
               unchanged   (255)
               clear   (0)
               set   (1)"
   ::= {er1645v2Lan3MCVlanEntry 133323008}

er1645v2Lan3MCVlanInbBwActCirActEthCos6 OBJECT-TYPE
   SYNTAX      INTEGER
               {
               unchanged (256)
               }
   MAX-ACCESS  read-write
   STATUS      current
   DESCRIPTION
      "Path: ethernet3.editConf.vlan.inboundBandwidth.action.cirAction.ethernet.cosDepth6

       Possibilities:
               unchanged   (256)"
   ::= {er1645v2Lan3MCVlanEntry 133318144}

er1645v2Lan3MCVlanInbBwActCirActEthDei6 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth6

       Possibilities:
               unchanged   (255)
               clear   (0)
               set   (1)"
   ::= {er1645v2Lan3MCVlanEntry 133323264}

er1645v2Lan3MCVlanInbBwActCirActEthCos7 OBJECT-TYPE
   SYNTAX      INTEGER
               {
               unchanged (256)
               }
   MAX-ACCESS  read-write
   STATUS      current
   DESCRIPTION
      "Path: ethernet3.editConf.vlan.inboundBandwidth.action.cirAction.ethernet.cosDepth7

       Possibilities:
               unchanged   (256)"
   ::= {er1645v2Lan3MCVlanEntry 133318400}

er1645v2Lan3MCVlanInbBwActCirActEthDei7 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth7

       Possibilities:
               unchanged   (255)
               clear   (0)
               set   (1)"
   ::= {er1645v2Lan3MCVlanEntry 133323520}

er1645v2Lan3MCVlanInbBwActCirActEthCos8 OBJECT-TYPE
   SYNTAX      INTEGER
               {
               unchanged (256)
               }
   MAX-ACCESS  read-write
   STATUS      current
   DESCRIPTION
      "Path: ethernet3.editConf.vlan.inboundBandwidth.action.cirAction.ethernet.cosDepth8

       Possibilities:
               unchanged   (256)"
   ::= {er1645v2Lan3MCVlanEntry 133318656}

er1645v2Lan3MCVlanInbBwActCirActEthDei8 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth8

       Possibilities:
               unchanged   (255)
               clear   (0)
               set   (1)"
   ::= {er1645v2Lan3MCVlanEntry 133323776}

er1645v2Lan3MCVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133318912}

er1645v2Lan3MCVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133319168}

er1645v2Lan3MCVlanInbBwActCirActEthDrpLev OBJECT-TYPE
   SYNTAX      INTEGER
               {
               unchanged (0)
               }
   MAX-ACCESS  read-write
   STATUS      current
   DESCRIPTION
      "Path: ethernet3.editConf.vlan.inboundBandwidth.action.cirAction.ethernet.dropLevel

       Possibilities:
               unchanged   (0)"
   ::= {er1645v2Lan3MCVlanEntry 133319424}

er1645v2Lan3MCVlanInbBwActCirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deFlag

       Possibilities:
               unchanged   (255)
               clear   (0)
               set   (1)"
   ::= {er1645v2Lan3MCVlanEntry 133320192}

er1645v2Lan3MCVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133343488}

er1645v2Lan3MCVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133343744}

er1645v2Lan3MCVlanInbBwActCirActIpDrpLev OBJECT-TYPE
   SYNTAX      INTEGER
               {
               unchanged (0)
               }
   MAX-ACCESS  read-write
   STATUS      current
   DESCRIPTION
      "Path: ethernet3.editConf.vlan.inboundBandwidth.action.cirAction.ip.dropLevel

       Possibilities:
               unchanged   (0)"
   ::= {er1645v2Lan3MCVlanEntry 133344000}

er1645v2Lan3MCVlanInbBwActCirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ip.deFlag

       Possibilities:
               unchanged   (255)
               clear   (0)
               set   (1)"
   ::= {er1645v2Lan3MCVlanEntry 133344768}

er1645v2Lan3MCVlanInbBwActEirActNone OBJECT-TYPE
   SYNTAX      OCTET STRING
   MAX-ACCESS  read-write
   STATUS      current
   DESCRIPTION
      "Path: ethernet3.editConf.vlan.inboundBandwidth.action.eirAction.none"
   ::= {er1645v2Lan3MCVlanEntry 133439488}

er1645v2Lan3MCVlanInbBwActEirActEthCos1 OBJECT-TYPE
   SYNTAX      INTEGER
               {
               unchanged (256)
               }
   MAX-ACCESS  read-write
   STATUS      current
   DESCRIPTION
      "Path: ethernet3.editConf.vlan.inboundBandwidth.action.eirAction.ethernet.cosDepth1

       Possibilities:
               unchanged   (256)"
   ::= {er1645v2Lan3MCVlanEntry 133447936}

er1645v2Lan3MCVlanInbBwActEirActEthDei1 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth1

       Possibilities:
               unchanged   (255)
               clear   (0)
               set   (1)"
   ::= {er1645v2Lan3MCVlanEntry 133453056}

er1645v2Lan3MCVlanInbBwActEirActEthCos2 OBJECT-TYPE
   SYNTAX      INTEGER
               {
               unchanged (256)
               }
   MAX-ACCESS  read-write
   STATUS      current
   DESCRIPTION
      "Path: ethernet3.editConf.vlan.inboundBandwidth.action.eirAction.ethernet.cosDepth2

       Possibilities:
               unchanged   (256)"
   ::= {er1645v2Lan3MCVlanEntry 133448192}

er1645v2Lan3MCVlanInbBwActEirActEthDei2 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth2

       Possibilities:
               unchanged   (255)
               clear   (0)
               set   (1)"
   ::= {er1645v2Lan3MCVlanEntry 133453312}

er1645v2Lan3MCVlanInbBwActEirActEthCos3 OBJECT-TYPE
   SYNTAX      INTEGER
               {
               unchanged (256)
               }
   MAX-ACCESS  read-write
   STATUS      current
   DESCRIPTION
      "Path: ethernet3.editConf.vlan.inboundBandwidth.action.eirAction.ethernet.cosDepth3

       Possibilities:
               unchanged   (256)"
   ::= {er1645v2Lan3MCVlanEntry 133448448}

er1645v2Lan3MCVlanInbBwActEirActEthDei3 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth3

       Possibilities:
               unchanged   (255)
               clear   (0)
               set   (1)"
   ::= {er1645v2Lan3MCVlanEntry 133453568}

er1645v2Lan3MCVlanInbBwActEirActEthCos4 OBJECT-TYPE
   SYNTAX      INTEGER
               {
               unchanged (256)
               }
   MAX-ACCESS  read-write
   STATUS      current
   DESCRIPTION
      "Path: ethernet3.editConf.vlan.inboundBandwidth.action.eirAction.ethernet.cosDepth4

       Possibilities:
               unchanged   (256)"
   ::= {er1645v2Lan3MCVlanEntry 133448704}

er1645v2Lan3MCVlanInbBwActEirActEthDei4 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth4

       Possibilities:
               unchanged   (255)
               clear   (0)
               set   (1)"
   ::= {er1645v2Lan3MCVlanEntry 133453824}

er1645v2Lan3MCVlanInbBwActEirActEthCos5 OBJECT-TYPE
   SYNTAX      INTEGER
               {
               unchanged (256)
               }
   MAX-ACCESS  read-write
   STATUS      current
   DESCRIPTION
      "Path: ethernet3.editConf.vlan.inboundBandwidth.action.eirAction.ethernet.cosDepth5

       Possibilities:
               unchanged   (256)"
   ::= {er1645v2Lan3MCVlanEntry 133448960}

er1645v2Lan3MCVlanInbBwActEirActEthDei5 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth5

       Possibilities:
               unchanged   (255)
               clear   (0)
               set   (1)"
   ::= {er1645v2Lan3MCVlanEntry 133454080}

er1645v2Lan3MCVlanInbBwActEirActEthCos6 OBJECT-TYPE
   SYNTAX      INTEGER
               {
               unchanged (256)
               }
   MAX-ACCESS  read-write
   STATUS      current
   DESCRIPTION
      "Path: ethernet3.editConf.vlan.inboundBandwidth.action.eirAction.ethernet.cosDepth6

       Possibilities:
               unchanged   (256)"
   ::= {er1645v2Lan3MCVlanEntry 133449216}

er1645v2Lan3MCVlanInbBwActEirActEthDei6 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth6

       Possibilities:
               unchanged   (255)
               clear   (0)
               set   (1)"
   ::= {er1645v2Lan3MCVlanEntry 133454336}

er1645v2Lan3MCVlanInbBwActEirActEthCos7 OBJECT-TYPE
   SYNTAX      INTEGER
               {
               unchanged (256)
               }
   MAX-ACCESS  read-write
   STATUS      current
   DESCRIPTION
      "Path: ethernet3.editConf.vlan.inboundBandwidth.action.eirAction.ethernet.cosDepth7

       Possibilities:
               unchanged   (256)"
   ::= {er1645v2Lan3MCVlanEntry 133449472}

er1645v2Lan3MCVlanInbBwActEirActEthDei7 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth7

       Possibilities:
               unchanged   (255)
               clear   (0)
               set   (1)"
   ::= {er1645v2Lan3MCVlanEntry 133454592}

er1645v2Lan3MCVlanInbBwActEirActEthCos8 OBJECT-TYPE
   SYNTAX      INTEGER
               {
               unchanged (256)
               }
   MAX-ACCESS  read-write
   STATUS      current
   DESCRIPTION
      "Path: ethernet3.editConf.vlan.inboundBandwidth.action.eirAction.ethernet.cosDepth8

       Possibilities:
               unchanged   (256)"
   ::= {er1645v2Lan3MCVlanEntry 133449728}

er1645v2Lan3MCVlanInbBwActEirActEthDei8 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth8

       Possibilities:
               unchanged   (255)
               clear   (0)
               set   (1)"
   ::= {er1645v2Lan3MCVlanEntry 133454848}

er1645v2Lan3MCVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133449984}

er1645v2Lan3MCVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133450240}

er1645v2Lan3MCVlanInbBwActEirActEthDrpLev OBJECT-TYPE
   SYNTAX      INTEGER
               {
               unchanged (0)
               }
   MAX-ACCESS  read-write
   STATUS      current
   DESCRIPTION
      "Path: ethernet3.editConf.vlan.inboundBandwidth.action.eirAction.ethernet.dropLevel

       Possibilities:
               unchanged   (0)"
   ::= {er1645v2Lan3MCVlanEntry 133450496}

er1645v2Lan3MCVlanInbBwActEirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deFlag

       Possibilities:
               unchanged   (255)
               clear   (0)
               set   (1)"
   ::= {er1645v2Lan3MCVlanEntry 133451264}

er1645v2Lan3MCVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133474560}

er1645v2Lan3MCVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133474816}

er1645v2Lan3MCVlanInbBwActEirActIpDrpLev OBJECT-TYPE
   SYNTAX      INTEGER
               {
               unchanged (0)
               }
   MAX-ACCESS  read-write
   STATUS      current
   DESCRIPTION
      "Path: ethernet3.editConf.vlan.inboundBandwidth.action.eirAction.ip.dropLevel

       Possibilities:
               unchanged   (0)"
   ::= {er1645v2Lan3MCVlanEntry 133475072}

er1645v2Lan3MCVlanInbBwActEirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ip.deFlag

       Possibilities:
               unchanged   (255)
               clear   (0)
               set   (1)"
   ::= {er1645v2Lan3MCVlanEntry 133475840}

er1645v2Lan3MCVlanInbBwActViolActNone OBJECT-TYPE
   SYNTAX      OCTET STRING
   MAX-ACCESS  read-write
   STATUS      current
   DESCRIPTION
      "Path: ethernet3.editConf.vlan.inboundBandwidth.action.violateAction.none"
   ::= {er1645v2Lan3MCVlanEntry 133570560}

er1645v2Lan3MCVlanInbBwActViolActDrop OBJECT-TYPE
   SYNTAX      OCTET STRING
   MAX-ACCESS  read-write
   STATUS      current
   DESCRIPTION
      "Path: ethernet3.editConf.vlan.inboundBandwidth.action.violateAction.drop"
   ::= {er1645v2Lan3MCVlanEntry 133586944}

er1645v2Lan3MCVlanInbBwActViolActEthCos1 OBJECT-TYPE
   SYNTAX      INTEGER
               {
               unchanged (256)
               }
   MAX-ACCESS  read-write
   STATUS      current
   DESCRIPTION
      "Path: ethernet3.editConf.vlan.inboundBandwidth.action.violateAction.ethernet.cosDepth1

       Possibilities:
               unchanged   (256)"
   ::= {er1645v2Lan3MCVlanEntry 133579008}

er1645v2Lan3MCVlanInbBwActViolActEthDei1 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth1

       Possibilities:
               unchanged   (255)
               clear   (0)
               set   (1)"
   ::= {er1645v2Lan3MCVlanEntry 133584128}

er1645v2Lan3MCVlanInbBwActViolActEthCos2 OBJECT-TYPE
   SYNTAX      INTEGER
               {
               unchanged (256)
               }
   MAX-ACCESS  read-write
   STATUS      current
   DESCRIPTION
      "Path: ethernet3.editConf.vlan.inboundBandwidth.action.violateAction.ethernet.cosDepth2

       Possibilities:
               unchanged   (256)"
   ::= {er1645v2Lan3MCVlanEntry 133579264}

er1645v2Lan3MCVlanInbBwActViolActEthDei2 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth2

       Possibilities:
               unchanged   (255)
               clear   (0)
               set   (1)"
   ::= {er1645v2Lan3MCVlanEntry 133584384}

er1645v2Lan3MCVlanInbBwActViolActEthCos3 OBJECT-TYPE
   SYNTAX      INTEGER
               {
               unchanged (256)
               }
   MAX-ACCESS  read-write
   STATUS      current
   DESCRIPTION
      "Path: ethernet3.editConf.vlan.inboundBandwidth.action.violateAction.ethernet.cosDepth3

       Possibilities:
               unchanged   (256)"
   ::= {er1645v2Lan3MCVlanEntry 133579520}

er1645v2Lan3MCVlanInbBwActViolActEthDei3 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth3

       Possibilities:
               unchanged   (255)
               clear   (0)
               set   (1)"
   ::= {er1645v2Lan3MCVlanEntry 133584640}

er1645v2Lan3MCVlanInbBwActViolActEthCos4 OBJECT-TYPE
   SYNTAX      INTEGER
               {
               unchanged (256)
               }
   MAX-ACCESS  read-write
   STATUS      current
   DESCRIPTION
      "Path: ethernet3.editConf.vlan.inboundBandwidth.action.violateAction.ethernet.cosDepth4

       Possibilities:
               unchanged   (256)"
   ::= {er1645v2Lan3MCVlanEntry 133579776}

er1645v2Lan3MCVlanInbBwActViolActEthDei4 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth4

       Possibilities:
               unchanged   (255)
               clear   (0)
               set   (1)"
   ::= {er1645v2Lan3MCVlanEntry 133584896}

er1645v2Lan3MCVlanInbBwActViolActEthCos5 OBJECT-TYPE
   SYNTAX      INTEGER
               {
               unchanged (256)
               }
   MAX-ACCESS  read-write
   STATUS      current
   DESCRIPTION
      "Path: ethernet3.editConf.vlan.inboundBandwidth.action.violateAction.ethernet.cosDepth5

       Possibilities:
               unchanged   (256)"
   ::= {er1645v2Lan3MCVlanEntry 133580032}

er1645v2Lan3MCVlanInbBwActViolActEthDei5 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth5

       Possibilities:
               unchanged   (255)
               clear   (0)
               set   (1)"
   ::= {er1645v2Lan3MCVlanEntry 133585152}

er1645v2Lan3MCVlanInbBwActViolActEthCos6 OBJECT-TYPE
   SYNTAX      INTEGER
               {
               unchanged (256)
               }
   MAX-ACCESS  read-write
   STATUS      current
   DESCRIPTION
      "Path: ethernet3.editConf.vlan.inboundBandwidth.action.violateAction.ethernet.cosDepth6

       Possibilities:
               unchanged   (256)"
   ::= {er1645v2Lan3MCVlanEntry 133580288}

er1645v2Lan3MCVlanInbBwActViolActEthDei6 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth6

       Possibilities:
               unchanged   (255)
               clear   (0)
               set   (1)"
   ::= {er1645v2Lan3MCVlanEntry 133585408}

er1645v2Lan3MCVlanInbBwActViolActEthCos7 OBJECT-TYPE
   SYNTAX      INTEGER
               {
               unchanged (256)
               }
   MAX-ACCESS  read-write
   STATUS      current
   DESCRIPTION
      "Path: ethernet3.editConf.vlan.inboundBandwidth.action.violateAction.ethernet.cosDepth7

       Possibilities:
               unchanged   (256)"
   ::= {er1645v2Lan3MCVlanEntry 133580544}

er1645v2Lan3MCVlanInbBwActViolActEthDei7 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth7

       Possibilities:
               unchanged   (255)
               clear   (0)
               set   (1)"
   ::= {er1645v2Lan3MCVlanEntry 133585664}

er1645v2Lan3MCVlanInbBwActViolActEthCos8 OBJECT-TYPE
   SYNTAX      INTEGER
               {
               unchanged (256)
               }
   MAX-ACCESS  read-write
   STATUS      current
   DESCRIPTION
      "Path: ethernet3.editConf.vlan.inboundBandwidth.action.violateAction.ethernet.cosDepth8

       Possibilities:
               unchanged   (256)"
   ::= {er1645v2Lan3MCVlanEntry 133580800}

er1645v2Lan3MCVlanInbBwActViolActEthDei8 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth8

       Possibilities:
               unchanged   (255)
               clear   (0)
               set   (1)"
   ::= {er1645v2Lan3MCVlanEntry 133585920}

er1645v2Lan3MCVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133581056}

er1645v2Lan3MCVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133581312}

er1645v2Lan3MCVlanInbBwActViolActEthDrpLev OBJECT-TYPE
   SYNTAX      INTEGER
               {
               unchanged (0)
               }
   MAX-ACCESS  read-write
   STATUS      current
   DESCRIPTION
      "Path: ethernet3.editConf.vlan.inboundBandwidth.action.violateAction.ethernet.dropLevel

       Possibilities:
               unchanged   (0)"
   ::= {er1645v2Lan3MCVlanEntry 133581568}

er1645v2Lan3MCVlanInbBwActViolActEthDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deFlag

       Possibilities:
               unchanged   (255)
               clear   (0)
               set   (1)"
   ::= {er1645v2Lan3MCVlanEntry 133582336}

er1645v2Lan3MCVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanEntry 133605632}

er1645v2Lan3MCVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanEntry 133605888}

er1645v2Lan3MCVlanInbBwActViolActIpDrpLev OBJECT-TYPE
   SYNTAX      INTEGER
               {
               unchanged (0)
               }
   MAX-ACCESS  read-write
   STATUS      current
   DESCRIPTION
      "Path: ethernet3.editConf.vlan.inboundBandwidth.action.violateAction.ip.dropLevel

       Possibilities:
               unchanged   (0)"
   ::= {er1645v2Lan3MCVlanEntry 133606144}

er1645v2Lan3MCVlanInbBwActViolActIpDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ip.deFlag

       Possibilities:
               unchanged   (255)
               clear   (0)
               set   (1)"
   ::= {er1645v2Lan3MCVlanEntry 133606912}

er1645v2Lan3MCVlanPppoE OBJECT-TYPE
   SYNTAX      INTEGER
               {
               disabled (0),
               enabled (1)
               }
   MAX-ACCESS  read-write
   STATUS      current
   DESCRIPTION
      "Path: ethernet3.editConf.vlan.pppoE

       Possibilities:
               disabled   (0)
               enabled   (1)"
   ::= {er1645v2Lan3MCVlanEntry 838860800}

er1645v2Lan3MCVlanPppLnkMOperation OBJECT-TYPE
   SYNTAX      INTEGER
               {
               disabled (0),
               enabled (1)
               }
   MAX-ACCESS  read-write
   STATUS      current
   DESCRIPTION
      "Path: ethernet3.editConf.vlan.ppp.linkMonitoring.operation

       Possibilities:
               disabled   (0)
               enabled   (1)"
   ::= {er1645v2Lan3MCVlanEntry 251724032}

er1645v2Lan3MCVlanPppLnkMInterval OBJECT-TYPE
   SYNTAX      TimeTicks
   MAX-ACCESS  read-write
   STATUS      current
   DESCRIPTION
      "Path: ethernet3.editConf.vlan.ppp.linkMonitoring.interval

       Time in centi-second."
   ::= {er1645v2Lan3MCVlanEntry 251724288}

er1645v2Lan3MCVlanPppLnkMRepTimeOut OBJECT-TYPE
   SYNTAX      TimeTicks
   MAX-ACCESS  read-write
   STATUS      current
   DESCRIPTION
      "Path: ethernet3.editConf.vlan.ppp.linkMonitoring.replyTimeOut

       Time in centi-second."
   ::= {er1645v2Lan3MCVlanEntry 251724544}

er1645v2Lan3MCVlanPppLnkMFailsPrmt OBJECT-TYPE
   SYNTAX      Integer32
   MAX-ACCESS  read-write
   STATUS      current
   DESCRIPTION
      "Path: ethernet3.editConf.vlan.ppp.linkMonitoring.failsPermitted"
   ::= {er1645v2Lan3MCVlanEntry 251724800}

er1645v2Lan3MCVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.vlan.ppp.authentication

       Possibilities:
               disabled   (0)
               chap   (1)
               pap   (2)
               chapOrPap   (3)
               msChap   (4)
               msChapV2   (5)"
   ::= {er1645v2Lan3MCVlanEntry 251789312}

er1645v2Lan3MCVlanPppAuthenPeriod OBJECT-TYPE
   SYNTAX      TimeTicks
   MAX-ACCESS  read-write
   STATUS      current
   DESCRIPTION
      "Path: ethernet3.editConf.vlan.ppp.authenPeriod

       Time in centi-second."
   ::= {er1645v2Lan3MCVlanEntry 251854848}

er1645v2Lan3MCVlanPppSessionName OBJECT-TYPE
   SYNTAX      DisplayString
   MAX-ACCESS  read-write
   STATUS      current
   DESCRIPTION
      "Path: ethernet3.editConf.vlan.ppp.sessionName"
   ::= {er1645v2Lan3MCVlanEntry 251985920}

er1645v2Lan3MCVlanPppSessionSecret OBJECT-TYPE
   SYNTAX      DisplayString
   MAX-ACCESS  read-write
   STATUS      current
   DESCRIPTION
      "Path: ethernet3.editConf.vlan.ppp.sessionSecret"
   ::= {er1645v2Lan3MCVlanEntry 252051456}

er1645v2Lan3MCVlanPppEncModeSessionSecret OBJECT-TYPE
   SYNTAX      INTEGER
               {
               none (1),
               encrypt (2),
               encType1 (3),
               invalid (128)
               }
   MAX-ACCESS  read-write
   STATUS      current
   DESCRIPTION
      "Path: ethernet3.editConf.vlan.ppp.encModeSessionSecret

       Possibilities:
               none   (1)
               encrypt   (2)
               encType1   (3)
               invalid   (128)"
   ::= {er1645v2Lan3MCVlanEntry 252182528}

er1645v2Lan3MCVlanPppEncSessionSecret OBJECT-TYPE
   SYNTAX      DisplayString
   MAX-ACCESS  read-write
   STATUS      current
   DESCRIPTION
      "Path: ethernet3.editConf.vlan.ppp.encSessionSecret"
   ::= {er1645v2Lan3MCVlanEntry 252248064}

er1645v2Lan3MCVlanPppServiceName OBJECT-TYPE
   SYNTAX      DisplayString
   MAX-ACCESS  read-write
   STATUS      current
   DESCRIPTION
      "Path: ethernet3.editConf.vlan.ppp.serviceName"
   ::= {er1645v2Lan3MCVlanEntry 252116992}

er1645v2Lan3MCVlanPbbMode OBJECT-TYPE
   SYNTAX      INTEGER
               {
               disabled (0),
               static (1),
               dynamicPtp (2),
               dynamicPtmp (3)
               }
   MAX-ACCESS  read-write
   STATUS      current
   DESCRIPTION
      "Path: ethernet3.editConf.vlan.pbb.mode

       Possibilities:
               disabled   (0)
               static   (1)
               dynamicPtp   (2)
               dynamicPtmp   (3)"
   ::= {er1645v2Lan3MCVlanEntry 1174667264}

er1645v2Lan3MCVlanPbbTxCos OBJECT-TYPE
   SYNTAX      Integer32
   MAX-ACCESS  read-write
   STATUS      current
   DESCRIPTION
      "Path: ethernet3.editConf.vlan.pbb.txCos"
   ::= {er1645v2Lan3MCVlanEntry 1175191552}

er1645v2Lan3MCVlanPbbIsid OBJECT-TYPE
   SYNTAX      Integer32
   MAX-ACCESS  read-write
   STATUS      current
   DESCRIPTION
      "Path: ethernet3.editConf.vlan.pbb.isid"
   ::= {er1645v2Lan3MCVlanEntry 1175453696}

er1645v2Lan3MCVlanPbbDestMac OBJECT-TYPE
   SYNTAX      OCTET STRING
   MAX-ACCESS  read-write
   STATUS      current
   DESCRIPTION
      "Path: ethernet3.editConf.vlan.pbb.destMac

       MAC address."
   ::= {er1645v2Lan3MCVlanEntry 1175715840}

er1645v2Lan3MCVlanPbbCustomGroupMac OBJECT-TYPE
   SYNTAX      OCTET STRING
   MAX-ACCESS  read-write
   STATUS      current
   DESCRIPTION
      "Path: ethernet3.editConf.vlan.pbb.customGroupMac

       MAC address."
   ::= {er1645v2Lan3MCVlanEntry 1175977984}

er1645v2Lan3MCVlanIpSaddr OBJECT-TYPE
   SYNTAX      SEQUENCE OF Er1645v2Lan3MCVlanIpSaddrEntry
   MAX-ACCESS  not-accessible
   STATUS      current
   DESCRIPTION
      ""
   ::= {er1645v2Lan3MCVlan 51838976}

er1645v2Lan3MCVlanIpSaddrEntry OBJECT-TYPE
   SYNTAX      Er1645v2Lan3MCVlanIpSaddrEntry
   MAX-ACCESS  not-accessible
   STATUS      current
   DESCRIPTION
      ""
   INDEX      { er1645v2Lan3MCVlanTableIx,
                er1645v2Lan3MCVlanIpSaddrTableIx }
   ::= {er1645v2Lan3MCVlanIpSaddr 1}

Er1645v2Lan3MCVlanIpSaddrEntry ::=
   SEQUENCE
      {
      er1645v2Lan3MCVlanIpSaddrActions
         VariableLengthTableActions,
      er1645v2Lan3MCVlanIpSaddrTableIx
         TableIndex,
      er1645v2Lan3MCVlanIpSaddrAddress
         IpAddress,
      er1645v2Lan3MCVlanIpSaddrNetMask
         IpAddress
      }

er1645v2Lan3MCVlanIpSaddrActions OBJECT-TYPE
   SYNTAX      VariableLengthTableActions
   MAX-ACCESS  read-write
   STATUS      current
   DESCRIPTION
      "By way of this field, some manipulations
       on this table may be performed."
   ::= {er1645v2Lan3MCVlanIpSaddrEntry 2}

er1645v2Lan3MCVlanIpSaddrTableIx OBJECT-TYPE
   SYNTAX      TableIndex
   MAX-ACCESS  not-accessible
   STATUS      current
   DESCRIPTION
      ""
   ::= {er1645v2Lan3MCVlanIpSaddrEntry 11}

er1645v2Lan3MCVlanIpSaddrAddress OBJECT-TYPE
   SYNTAX      IpAddress
   MAX-ACCESS  read-write
   STATUS      current
   DESCRIPTION
      "Path: ethernet3.editConf.vlan.ip.secondaryIp.address"
   ::= {er1645v2Lan3MCVlanIpSaddrEntry 2030043136}

er1645v2Lan3MCVlanIpSaddrNetMask OBJECT-TYPE
   SYNTAX      IpAddress
   MAX-ACCESS  read-write
   STATUS      current
   DESCRIPTION
      "Path: ethernet3.editConf.vlan.ip.secondaryIp.netMask"
   ::= {er1645v2Lan3MCVlanIpSaddrEntry 2063597568}

er1645v2Lan3MCVlanIpH OBJECT-TYPE
   SYNTAX      SEQUENCE OF Er1645v2Lan3MCVlanIpHEntry
   MAX-ACCESS  not-accessible
   STATUS      current
   DESCRIPTION
      ""
   ::= {er1645v2Lan3MCVlan 51314688}

er1645v2Lan3MCVlanIpHEntry OBJECT-TYPE
   SYNTAX      Er1645v2Lan3MCVlanIpHEntry
   MAX-ACCESS  not-accessible
   STATUS      current
   DESCRIPTION
      ""
   INDEX      { er1645v2Lan3MCVlanTableIx,
                er1645v2Lan3MCVlanIpHTableIx }
   ::= {er1645v2Lan3MCVlanIpH 1}

Er1645v2Lan3MCVlanIpHEntry ::=
   SEQUENCE
      {
      er1645v2Lan3MCVlanIpHActions
         VariableLengthTableActions,
      er1645v2Lan3MCVlanIpHTableIx
         TableIndex,
      er1645v2Lan3MCVlanIpHAddress
         IpAddress,
      er1645v2Lan3MCVlanIpHDhcpRelayOptionSubscriberId
         DisplayString
      }

er1645v2Lan3MCVlanIpHActions OBJECT-TYPE
   SYNTAX      VariableLengthTableActions
   MAX-ACCESS  read-write
   STATUS      current
   DESCRIPTION
      "By way of this field, some manipulations
       on this table may be performed."
   ::= {er1645v2Lan3MCVlanIpHEntry 2}

er1645v2Lan3MCVlanIpHTableIx OBJECT-TYPE
   SYNTAX      TableIndex
   MAX-ACCESS  not-accessible
   STATUS      current
   DESCRIPTION
      ""
   ::= {er1645v2Lan3MCVlanIpHEntry 11}

er1645v2Lan3MCVlanIpHAddress OBJECT-TYPE
   SYNTAX      IpAddress
   MAX-ACCESS  read-write
   STATUS      current
   DESCRIPTION
      "Path: ethernet3.editConf.vlan.ip.helpers.address"
   ::= {er1645v2Lan3MCVlanIpHEntry 16777216}

er1645v2Lan3MCVlanIpHDhcpRelayOptionSubscriberId OBJECT-TYPE
   SYNTAX      DisplayString
   MAX-ACCESS  read-write
   STATUS      current
   DESCRIPTION
      "Path: ethernet3.editConf.vlan.ip.helpers.dhcpRelayOption.subscriberId"
   ::= {er1645v2Lan3MCVlanIpHEntry 33947648}

er1645v2Lan3MCVlanIpV6Addresses OBJECT-TYPE
   SYNTAX      SEQUENCE OF Er1645v2Lan3MCVlanIpV6AddressesEntry
   MAX-ACCESS  not-accessible
   STATUS      current
   DESCRIPTION
      ""
   ::= {er1645v2Lan3MCVlan 704839680}

er1645v2Lan3MCVlanIpV6AddressesEntry OBJECT-TYPE
   SYNTAX      Er1645v2Lan3MCVlanIpV6AddressesEntry
   MAX-ACCESS  not-accessible
   STATUS      current
   DESCRIPTION
      ""
   INDEX      { er1645v2Lan3MCVlanTableIx,
                er1645v2Lan3MCVlanIpV6AddressesTableIx }
   ::= {er1645v2Lan3MCVlanIpV6Addresses 1}

Er1645v2Lan3MCVlanIpV6AddressesEntry ::=
   SEQUENCE
      {
      er1645v2Lan3MCVlanIpV6AddressesActions
         VariableLengthTableActions,
      er1645v2Lan3MCVlanIpV6AddressesTableIx
         TableIndex,
      er1645v2Lan3MCVlanIpV6AddressesType
         INTEGER,
      er1645v2Lan3MCVlanIpV6AddressesAddress
         Ipv6Address,
      er1645v2Lan3MCVlanIpV6AddressesPrefixLength
         Integer32,
      er1645v2Lan3MCVlanIpV6AddressesGeneralPrefix
         DisplayString,
      er1645v2Lan3MCVlanIpV6AddressesRaSend
         INTEGER,
      er1645v2Lan3MCVlanIpV6AddressesRaOnLinkFlag
         INTEGER,
      er1645v2Lan3MCVlanIpV6AddressesRaAutoFlag
         INTEGER,
      er1645v2Lan3MCVlanIpV6AddressesRaValidLifeTime
         TimeTicks,
      er1645v2Lan3MCVlanIpV6AddressesRaValidLTMode
         INTEGER,
      er1645v2Lan3MCVlanIpV6AddressesRaPrefLifeTime
         TimeTicks,
      er1645v2Lan3MCVlanIpV6AddressesRaPrefLTMode
         INTEGER
      }

er1645v2Lan3MCVlanIpV6AddressesActions OBJECT-TYPE
   SYNTAX      VariableLengthTableActions
   MAX-ACCESS  read-write
   STATUS      current
   DESCRIPTION
      "By way of this field, some manipulations
       on this table may be performed."
   ::= {er1645v2Lan3MCVlanIpV6AddressesEntry 2}

er1645v2Lan3MCVlanIpV6AddressesTableIx OBJECT-TYPE
   SYNTAX      TableIndex
   MAX-ACCESS  not-accessible
   STATUS      current
   DESCRIPTION
      ""
   ::= {er1645v2Lan3MCVlanIpV6AddressesEntry 11}

er1645v2Lan3MCVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.vlan.ipV6.addresses.type

       Possibilities:
               unicast   (0)
               eui64   (1)
               anycast   (2)
               linkLocal   (3)
               generalPrefix   (4)"
   ::= {er1645v2Lan3MCVlanIpV6AddressesEntry 50331648}

er1645v2Lan3MCVlanIpV6AddressesAddress OBJECT-TYPE
   SYNTAX      Ipv6Address
   MAX-ACCESS  read-write
   STATUS      current
   DESCRIPTION
      "Path: ethernet3.editConf.vlan.ipV6.addresses.address

       ipv6 address"
   ::= {er1645v2Lan3MCVlanIpV6AddressesEntry 16777216}

er1645v2Lan3MCVlanIpV6AddressesPrefixLength OBJECT-TYPE
   SYNTAX      Integer32
   MAX-ACCESS  read-write
   STATUS      current
   DESCRIPTION
      "Path: ethernet3.editConf.vlan.ipV6.addresses.prefixLength"
   ::= {er1645v2Lan3MCVlanIpV6AddressesEntry 33554432}

er1645v2Lan3MCVlanIpV6AddressesGeneralPrefix OBJECT-TYPE
   SYNTAX      DisplayString
   MAX-ACCESS  read-write
   STATUS      current
   DESCRIPTION
      "Path: ethernet3.editConf.vlan.ipV6.addresses.generalPrefix"
   ::= {er1645v2Lan3MCVlanIpV6AddressesEntry 83886080}

er1645v2Lan3MCVlanIpV6AddressesRaSend OBJECT-TYPE
   SYNTAX      INTEGER
               {
               disabled (0),
               enabled (1)
               }
   MAX-ACCESS  read-write
   STATUS      current
   DESCRIPTION
      "Path: ethernet3.editConf.vlan.ipV6.addresses.ra.send

       Possibilities:
               disabled   (0)
               enabled   (1)"
   ::= {er1645v2Lan3MCVlanIpV6AddressesEntry 67174400}

er1645v2Lan3MCVlanIpV6AddressesRaOnLinkFlag OBJECT-TYPE
   SYNTAX      INTEGER
               {
               disabled (0),
               enabled (1)
               }
   MAX-ACCESS  read-write
   STATUS      current
   DESCRIPTION
      "Path: ethernet3.editConf.vlan.ipV6.addresses.ra.onLinkFlag

       Possibilities:
               disabled   (0)
               enabled   (1)"
   ::= {er1645v2Lan3MCVlanIpV6AddressesEntry 67371008}

er1645v2Lan3MCVlanIpV6AddressesRaAutoFlag OBJECT-TYPE
   SYNTAX      INTEGER
               {
               disabled (0),
               enabled (1)
               }
   MAX-ACCESS  read-write
   STATUS      current
   DESCRIPTION
      "Path: ethernet3.editConf.vlan.ipV6.addresses.ra.autonomousFlag

       Possibilities:
               disabled   (0)
               enabled   (1)"
   ::= {er1645v2Lan3MCVlanIpV6AddressesEntry 67567616}

er1645v2Lan3MCVlanIpV6AddressesRaValidLifeTime OBJECT-TYPE
   SYNTAX      TimeTicks
   MAX-ACCESS  read-write
   STATUS      current
   DESCRIPTION
      "Path: ethernet3.editConf.vlan.ipV6.addresses.ra.validLifeTime

       Time in centi-second."
   ::= {er1645v2Lan3MCVlanIpV6AddressesEntry 67239936}

er1645v2Lan3MCVlanIpV6AddressesRaValidLTMode OBJECT-TYPE
   SYNTAX      INTEGER
               {
               fixed (0),
               infinite (2)
               }
   MAX-ACCESS  read-write
   STATUS      current
   DESCRIPTION
      "Path: ethernet3.editConf.vlan.ipV6.addresses.ra.validLifeTimeMode

       Possibilities:
               fixed   (0)
               infinite   (2)"
   ::= {er1645v2Lan3MCVlanIpV6AddressesEntry 67305472}

er1645v2Lan3MCVlanIpV6AddressesRaPrefLifeTime OBJECT-TYPE
   SYNTAX      TimeTicks
   MAX-ACCESS  read-write
   STATUS      current
   DESCRIPTION
      "Path: ethernet3.editConf.vlan.ipV6.addresses.ra.prefLifeTime

       Time in centi-second."
   ::= {er1645v2Lan3MCVlanIpV6AddressesEntry 67436544}

er1645v2Lan3MCVlanIpV6AddressesRaPrefLTMode OBJECT-TYPE
   SYNTAX      INTEGER
               {
               fixed (0),
               infinite (2)
               }
   MAX-ACCESS  read-write
   STATUS      current
   DESCRIPTION
      "Path: ethernet3.editConf.vlan.ipV6.addresses.ra.prefLifeTimeMode

       Possibilities:
               fixed   (0)
               infinite   (2)"
   ::= {er1645v2Lan3MCVlanIpV6AddressesEntry 67502080}

er1645v2Lan3MCVlanIpV6RaDnsOptionsRdnssServers OBJECT-TYPE
   SYNTAX      SEQUENCE OF Er1645v2Lan3MCVlanIpV6RaDnsOptionsRdnssServersEntry
   MAX-ACCESS  not-accessible
   STATUS      current
   DESCRIPTION
      ""
   ::= {er1645v2Lan3MCVlan 705039144}

er1645v2Lan3MCVlanIpV6RaDnsOptionsRdnssServersEntry OBJECT-TYPE
   SYNTAX      Er1645v2Lan3MCVlanIpV6RaDnsOptionsRdnssServersEntry
   MAX-ACCESS  not-accessible
   STATUS      current
   DESCRIPTION
      ""
   INDEX      { er1645v2Lan3MCVlanTableIx,
                er1645v2Lan3MCVlanIpV6RaDnsOptionsRdnssServersTableIx }
   ::= {er1645v2Lan3MCVlanIpV6RaDnsOptionsRdnssServers 1}

Er1645v2Lan3MCVlanIpV6RaDnsOptionsRdnssServersEntry ::=
   SEQUENCE
      {
      er1645v2Lan3MCVlanIpV6RaDnsOptionsRdnssServersActions
         VariableLengthTableActions,
      er1645v2Lan3MCVlanIpV6RaDnsOptionsRdnssServersTableIx
         TableIndex,
      er1645v2Lan3MCVlanIpV6RaDnsOptionsRdnssServersAddress
         Ipv6Address
      }

er1645v2Lan3MCVlanIpV6RaDnsOptionsRdnssServersActions OBJECT-TYPE
   SYNTAX      VariableLengthTableActions
   MAX-ACCESS  read-write
   STATUS      current
   DESCRIPTION
      "By way of this field, some manipulations
       on this table may be performed."
   ::= {er1645v2Lan3MCVlanIpV6RaDnsOptionsRdnssServersEntry 2}

er1645v2Lan3MCVlanIpV6RaDnsOptionsRdnssServersTableIx OBJECT-TYPE
   SYNTAX      TableIndex
   MAX-ACCESS  not-accessible
   STATUS      current
   DESCRIPTION
      ""
   ::= {er1645v2Lan3MCVlanIpV6RaDnsOptionsRdnssServersEntry 11}

er1645v2Lan3MCVlanIpV6RaDnsOptionsRdnssServersAddress OBJECT-TYPE
   SYNTAX      Ipv6Address
   MAX-ACCESS  read-write
   STATUS      current
   DESCRIPTION
      "Path: ethernet3.editConf.vlan.ipV6.ra.dnsOptions.rdnss.servers.address

       ipv6 address"
   ::= {er1645v2Lan3MCVlanIpV6RaDnsOptionsRdnssServersEntry 16777216}

er1645v2Lan3MCVlanIpV6RaDnsOptionsDnsslDomains OBJECT-TYPE
   SYNTAX      SEQUENCE OF Er1645v2Lan3MCVlanIpV6RaDnsOptionsDnsslDomainsEntry
   MAX-ACCESS  not-accessible
   STATUS      current
   DESCRIPTION
      ""
   ::= {er1645v2Lan3MCVlan 705039176}

er1645v2Lan3MCVlanIpV6RaDnsOptionsDnsslDomainsEntry OBJECT-TYPE
   SYNTAX      Er1645v2Lan3MCVlanIpV6RaDnsOptionsDnsslDomainsEntry
   MAX-ACCESS  not-accessible
   STATUS      current
   DESCRIPTION
      ""
   INDEX      { er1645v2Lan3MCVlanTableIx,
                er1645v2Lan3MCVlanIpV6RaDnsOptionsDnsslDomainsTableIx }
   ::= {er1645v2Lan3MCVlanIpV6RaDnsOptionsDnsslDomains 1}

Er1645v2Lan3MCVlanIpV6RaDnsOptionsDnsslDomainsEntry ::=
   SEQUENCE
      {
      er1645v2Lan3MCVlanIpV6RaDnsOptionsDnsslDomainsActions
         VariableLengthTableActions,
      er1645v2Lan3MCVlanIpV6RaDnsOptionsDnsslDomainsTableIx
         TableIndex,
      er1645v2Lan3MCVlanIpV6RaDnsOptionsDnsslDomainsName
         DisplayString
      }

er1645v2Lan3MCVlanIpV6RaDnsOptionsDnsslDomainsActions OBJECT-TYPE
   SYNTAX      VariableLengthTableActions
   MAX-ACCESS  read-write
   STATUS      current
   DESCRIPTION
      "By way of this field, some manipulations
       on this table may be performed."
   ::= {er1645v2Lan3MCVlanIpV6RaDnsOptionsDnsslDomainsEntry 2}

er1645v2Lan3MCVlanIpV6RaDnsOptionsDnsslDomainsTableIx OBJECT-TYPE
   SYNTAX      TableIndex
   MAX-ACCESS  not-accessible
   STATUS      current
   DESCRIPTION
      ""
   ::= {er1645v2Lan3MCVlanIpV6RaDnsOptionsDnsslDomainsEntry 11}

er1645v2Lan3MCVlanIpV6RaDnsOptionsDnsslDomainsName OBJECT-TYPE
   SYNTAX      DisplayString
   MAX-ACCESS  read-write
   STATUS      current
   DESCRIPTION
      "Path: ethernet3.editConf.vlan.ipV6.ra.dnsOptions.dnssl.domains.name"
   ::= {er1645v2Lan3MCVlanIpV6RaDnsOptionsDnsslDomainsEntry 16777216}

er1645v2Lan3MCVlanIpV6DhcpClientUserClassOpt OBJECT-TYPE
   SYNTAX      SEQUENCE OF Er1645v2Lan3MCVlanIpV6DhcpClientUserClassOptEntry
   MAX-ACCESS  not-accessible
   STATUS      current
   DESCRIPTION
      ""
   ::= {er1645v2Lan3MCVlan 705312768}

er1645v2Lan3MCVlanIpV6DhcpClientUserClassOptEntry OBJECT-TYPE
   SYNTAX      Er1645v2Lan3MCVlanIpV6DhcpClientUserClassOptEntry
   MAX-ACCESS  not-accessible
   STATUS      current
   DESCRIPTION
      ""
   INDEX      { er1645v2Lan3MCVlanTableIx,
                er1645v2Lan3MCVlanIpV6DhcpClientUserClassOptTableIx }
   ::= {er1645v2Lan3MCVlanIpV6DhcpClientUserClassOpt 1}

Er1645v2Lan3MCVlanIpV6DhcpClientUserClassOptEntry ::=
   SEQUENCE
      {
      er1645v2Lan3MCVlanIpV6DhcpClientUserClassOptActions
         VariableLengthTableActions,
      er1645v2Lan3MCVlanIpV6DhcpClientUserClassOptTableIx
         TableIndex,
      er1645v2Lan3MCVlanIpV6DhcpClientUserClassOptValueAscii
         DisplayString,
      er1645v2Lan3MCVlanIpV6DhcpClientUserClassOptValueDecimal
         Integer32,
      er1645v2Lan3MCVlanIpV6DhcpClientUserClassOptValueHexData
         OCTET STRING
      }

er1645v2Lan3MCVlanIpV6DhcpClientUserClassOptActions OBJECT-TYPE
   SYNTAX      VariableLengthTableActions
   MAX-ACCESS  read-write
   STATUS      current
   DESCRIPTION
      "By way of this field, some manipulations
       on this table may be performed."
   ::= {er1645v2Lan3MCVlanIpV6DhcpClientUserClassOptEntry 2}

er1645v2Lan3MCVlanIpV6DhcpClientUserClassOptTableIx OBJECT-TYPE
   SYNTAX      TableIndex
   MAX-ACCESS  not-accessible
   STATUS      current
   DESCRIPTION
      ""
   ::= {er1645v2Lan3MCVlanIpV6DhcpClientUserClassOptEntry 11}

er1645v2Lan3MCVlanIpV6DhcpClientUserClassOptValueAscii OBJECT-TYPE
   SYNTAX      DisplayString
   MAX-ACCESS  read-write
   STATUS      current
   DESCRIPTION
      "Path: ethernet3.editConf.vlan.ipV6.dhcp.client.userClassOpt.value.ascii"
   ::= {er1645v2Lan3MCVlanIpV6DhcpClientUserClassOptEntry 16842752}

er1645v2Lan3MCVlanIpV6DhcpClientUserClassOptValueDecimal OBJECT-TYPE
   SYNTAX      Integer32
   MAX-ACCESS  read-write
   STATUS      current
   DESCRIPTION
      "Path: ethernet3.editConf.vlan.ipV6.dhcp.client.userClassOpt.value.decimal"
   ::= {er1645v2Lan3MCVlanIpV6DhcpClientUserClassOptEntry 16908288}

er1645v2Lan3MCVlanIpV6DhcpClientUserClassOptValueHexData OBJECT-TYPE
   SYNTAX      OCTET STRING
   MAX-ACCESS  read-write
   STATUS      current
   DESCRIPTION
      "Path: ethernet3.editConf.vlan.ipV6.dhcp.client.userClassOpt.value.hexData"
   ::= {er1645v2Lan3MCVlanIpV6DhcpClientUserClassOptEntry 16973824}

er1645v2Lan3MCVlanIpV6DhcpClientVendorCl OBJECT-TYPE
   SYNTAX      SEQUENCE OF Er1645v2Lan3MCVlanIpV6DhcpClientVendorClEntry
   MAX-ACCESS  not-accessible
   STATUS      current
   DESCRIPTION
      ""
   ::= {er1645v2Lan3MCVlan 705313792}

er1645v2Lan3MCVlanIpV6DhcpClientVendorClEntry OBJECT-TYPE
   SYNTAX      Er1645v2Lan3MCVlanIpV6DhcpClientVendorClEntry
   MAX-ACCESS  not-accessible
   STATUS      current
   DESCRIPTION
      ""
   INDEX      { er1645v2Lan3MCVlanTableIx,
                er1645v2Lan3MCVlanIpV6DhcpClientVendorClTableIx }
   ::= {er1645v2Lan3MCVlanIpV6DhcpClientVendorCl 1}

Er1645v2Lan3MCVlanIpV6DhcpClientVendorClEntry ::=
   SEQUENCE
      {
      er1645v2Lan3MCVlanIpV6DhcpClientVendorClActions
         VariableLengthTableActions,
      er1645v2Lan3MCVlanIpV6DhcpClientVendorClTableIx
         TableIndex,
      er1645v2Lan3MCVlanIpV6DhcpClientVendorClValueAscii
         DisplayString,
      er1645v2Lan3MCVlanIpV6DhcpClientVendorClValueDecimal
         Integer32,
      er1645v2Lan3MCVlanIpV6DhcpClientVendorClValueHexData
         OCTET STRING
      }

er1645v2Lan3MCVlanIpV6DhcpClientVendorClActions OBJECT-TYPE
   SYNTAX      VariableLengthTableActions
   MAX-ACCESS  read-write
   STATUS      current
   DESCRIPTION
      "By way of this field, some manipulations
       on this table may be performed."
   ::= {er1645v2Lan3MCVlanIpV6DhcpClientVendorClEntry 2}

er1645v2Lan3MCVlanIpV6DhcpClientVendorClTableIx OBJECT-TYPE
   SYNTAX      TableIndex
   MAX-ACCESS  not-accessible
   STATUS      current
   DESCRIPTION
      ""
   ::= {er1645v2Lan3MCVlanIpV6DhcpClientVendorClEntry 11}

er1645v2Lan3MCVlanIpV6DhcpClientVendorClValueAscii OBJECT-TYPE
   SYNTAX      DisplayString
   MAX-ACCESS  read-write
   STATUS      current
   DESCRIPTION
      "Path: ethernet3.editConf.vlan.ipV6.dhcp.client.vendorClassOpt.value.ascii"
   ::= {er1645v2Lan3MCVlanIpV6DhcpClientVendorClEntry 16842752}

er1645v2Lan3MCVlanIpV6DhcpClientVendorClValueDecimal OBJECT-TYPE
   SYNTAX      Integer32
   MAX-ACCESS  read-write
   STATUS      current
   DESCRIPTION
      "Path: ethernet3.editConf.vlan.ipV6.dhcp.client.vendorClassOpt.value.decimal"
   ::= {er1645v2Lan3MCVlanIpV6DhcpClientVendorClEntry 16908288}

er1645v2Lan3MCVlanIpV6DhcpClientVendorClValueHexData OBJECT-TYPE
   SYNTAX      OCTET STRING
   MAX-ACCESS  read-write
   STATUS      current
   DESCRIPTION
      "Path: ethernet3.editConf.vlan.ipV6.dhcp.client.vendorClassOpt.value.hexData"
   ::= {er1645v2Lan3MCVlanIpV6DhcpClientVendorClEntry 16973824}

er1645v2Lan3MCVlanIpV6DhcpRelayDestinations OBJECT-TYPE
   SYNTAX      SEQUENCE OF Er1645v2Lan3MCVlanIpV6DhcpRelayDestinationsEntry
   MAX-ACCESS  not-accessible
   STATUS      current
   DESCRIPTION
      ""
   ::= {er1645v2Lan3MCVlan 705323072}

er1645v2Lan3MCVlanIpV6DhcpRelayDestinationsEntry OBJECT-TYPE
   SYNTAX      Er1645v2Lan3MCVlanIpV6DhcpRelayDestinationsEntry
   MAX-ACCESS  not-accessible
   STATUS      current
   DESCRIPTION
      ""
   INDEX      { er1645v2Lan3MCVlanTableIx,
                er1645v2Lan3MCVlanIpV6DhcpRelayDestinationsTableIx }
   ::= {er1645v2Lan3MCVlanIpV6DhcpRelayDestinations 1}

Er1645v2Lan3MCVlanIpV6DhcpRelayDestinationsEntry ::=
   SEQUENCE
      {
      er1645v2Lan3MCVlanIpV6DhcpRelayDestinationsActions
         VariableLengthTableActions,
      er1645v2Lan3MCVlanIpV6DhcpRelayDestinationsTableIx
         TableIndex,
      er1645v2Lan3MCVlanIpV6DhcpRelayDestinationsAddress
         Ipv6Address,
      er1645v2Lan3MCVlanIpV6DhcpRelayDestinationsInterface
         DisplayString
      }

er1645v2Lan3MCVlanIpV6DhcpRelayDestinationsActions OBJECT-TYPE
   SYNTAX      VariableLengthTableActions
   MAX-ACCESS  read-write
   STATUS      current
   DESCRIPTION
      "By way of this field, some manipulations
       on this table may be performed."
   ::= {er1645v2Lan3MCVlanIpV6DhcpRelayDestinationsEntry 2}

er1645v2Lan3MCVlanIpV6DhcpRelayDestinationsTableIx OBJECT-TYPE
   SYNTAX      TableIndex
   MAX-ACCESS  not-accessible
   STATUS      current
   DESCRIPTION
      ""
   ::= {er1645v2Lan3MCVlanIpV6DhcpRelayDestinationsEntry 11}

er1645v2Lan3MCVlanIpV6DhcpRelayDestinationsAddress OBJECT-TYPE
   SYNTAX      Ipv6Address
   MAX-ACCESS  read-write
   STATUS      current
   DESCRIPTION
      "Path: ethernet3.editConf.vlan.ipV6.dhcp.relay.destinations.address

       ipv6 address"
   ::= {er1645v2Lan3MCVlanIpV6DhcpRelayDestinationsEntry 16777216}

er1645v2Lan3MCVlanIpV6DhcpRelayDestinationsInterface OBJECT-TYPE
   SYNTAX      DisplayString
   MAX-ACCESS  read-write
   STATUS      current
   DESCRIPTION
      "Path: ethernet3.editConf.vlan.ipV6.dhcp.relay.destinations.interface"
   ::= {er1645v2Lan3MCVlanIpV6DhcpRelayDestinationsEntry 33554432}

er1645v2Lan3MCVlanBridgingVlTVlans OBJECT-TYPE
   SYNTAX      SEQUENCE OF Er1645v2Lan3MCVlanBridgingVlTVlansEntry
   MAX-ACCESS  not-accessible
   STATUS      current
   DESCRIPTION
      ""
   ::= {er1645v2Lan3MCVlan 459079680}

er1645v2Lan3MCVlanBridgingVlTVlansEntry OBJECT-TYPE
   SYNTAX      Er1645v2Lan3MCVlanBridgingVlTVlansEntry
   MAX-ACCESS  not-accessible
   STATUS      current
   DESCRIPTION
      ""
   INDEX      { er1645v2Lan3MCVlanTableIx,
                er1645v2Lan3MCVlanBridgingVlTVlansTableIx }
   ::= {er1645v2Lan3MCVlanBridgingVlTVlans 1}

Er1645v2Lan3MCVlanBridgingVlTVlansEntry ::=
   SEQUENCE
      {
      er1645v2Lan3MCVlanBridgingVlTVlansActions
         VariableLengthTableActions,
      er1645v2Lan3MCVlanBridgingVlTVlansTableIx
         TableIndex,
      er1645v2Lan3MCVlanBridgingVlTVlansVid
         Integer32,
      er1645v2Lan3MCVlanBridgingVlTVlansEndVid
         Integer32,
      er1645v2Lan3MCVlanBridgingVlTVlansAction
         INTEGER,
      er1645v2Lan3MCVlanBridgingVlTVlansTagInfoTpid
         INTEGER,
      er1645v2Lan3MCVlanBridgingVlTVlansTagInfoVid
         Integer32
      }

er1645v2Lan3MCVlanBridgingVlTVlansActions OBJECT-TYPE
   SYNTAX      VariableLengthTableActions
   MAX-ACCESS  read-write
   STATUS      current
   DESCRIPTION
      "By way of this field, some manipulations
       on this table may be performed."
   ::= {er1645v2Lan3MCVlanBridgingVlTVlansEntry 2}

er1645v2Lan3MCVlanBridgingVlTVlansTableIx OBJECT-TYPE
   SYNTAX      TableIndex
   MAX-ACCESS  not-accessible
   STATUS      current
   DESCRIPTION
      ""
   ::= {er1645v2Lan3MCVlanBridgingVlTVlansEntry 11}

er1645v2Lan3MCVlanBridgingVlTVlansVid OBJECT-TYPE
   SYNTAX      Integer32
   MAX-ACCESS  read-write
   STATUS      current
   DESCRIPTION
      "Path: ethernet3.editConf.vlan.bridging.vlanTagging.vlans.vid"
   ::= {er1645v2Lan3MCVlanBridgingVlTVlansEntry 536870912}

er1645v2Lan3MCVlanBridgingVlTVlansEndVid OBJECT-TYPE
   SYNTAX      Integer32
   MAX-ACCESS  read-write
   STATUS      current
   DESCRIPTION
      "Path: ethernet3.editConf.vlan.bridging.vlanTagging.vlans.endVid"
   ::= {er1645v2Lan3MCVlanBridgingVlTVlansEntry 2147483648}

er1645v2Lan3MCVlanBridgingVlTVlansAction OBJECT-TYPE
   SYNTAX      INTEGER
               {
               discard (0),
               accept (1),
               tag (2)
               }
   MAX-ACCESS  read-write
   STATUS      current
   DESCRIPTION
      "Path: ethernet3.editConf.vlan.bridging.vlanTagging.vlans.action

       Possibilities:
               discard   (0)
               accept   (1)
               tag   (2)"
   ::= {er1645v2Lan3MCVlanBridgingVlTVlansEntry 1073741824}

er1645v2Lan3MCVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.vlans.tagInfo.tpid

       Possibilities:
               dot1Q   (33024)
               dot1ad   (34984)
               0x9100   (37120)
               0x9200   (37376)
               0x9300   (37632)"
   ::= {er1645v2Lan3MCVlanBridgingVlTVlansEntry 1677721600}

er1645v2Lan3MCVlanBridgingVlTVlansTagInfoVid OBJECT-TYPE
   SYNTAX      Integer32
   MAX-ACCESS  read-write
   STATUS      current
   DESCRIPTION
      "Path: ethernet3.editConf.vlan.bridging.vlanTagging.vlans.tagInfo.vid"
   ::= {er1645v2Lan3MCVlanBridgingVlTVlansEntry 1744830464}

er1645v2Lan3MCVlanVlanVidExtensionTable OBJECT-TYPE
   SYNTAX      SEQUENCE OF Er1645v2Lan3MCVlanVlanVidExtensionTableEntry
   MAX-ACCESS  not-accessible
   STATUS      current
   DESCRIPTION
      ""
   ::= {er1645v2Lan3MCVlan 235340544}

er1645v2Lan3MCVlanVlanVidExtensionTableEntry OBJECT-TYPE
   SYNTAX      Er1645v2Lan3MCVlanVlanVidExtensionTableEntry
   MAX-ACCESS  not-accessible
   STATUS      current
   DESCRIPTION
      ""
   INDEX      { er1645v2Lan3MCVlanTableIx,
                er1645v2Lan3MCVlanVlanVidExtensionTableTableIx }
   ::= {er1645v2Lan3MCVlanVlanVidExtensionTable 1}

Er1645v2Lan3MCVlanVlanVidExtensionTableEntry ::=
   SEQUENCE
      {
      er1645v2Lan3MCVlanVlanVidExtensionTableActions
         VariableLengthTableActions,
      er1645v2Lan3MCVlanVlanVidExtensionTableTableIx
         TableIndex,
      er1645v2Lan3MCVlanVlanVidExtensionTableTpid
         INTEGER,
      er1645v2Lan3MCVlanVlanVidExtensionTableVid
         Integer32,
      er1645v2Lan3MCVlanVlanVidExtensionTableEndVid
         Integer32
      }

er1645v2Lan3MCVlanVlanVidExtensionTableActions OBJECT-TYPE
   SYNTAX      VariableLengthTableActions
   MAX-ACCESS  read-write
   STATUS      current
   DESCRIPTION
      "By way of this field, some manipulations
       on this table may be performed."
   ::= {er1645v2Lan3MCVlanVlanVidExtensionTableEntry 2}

er1645v2Lan3MCVlanVlanVidExtensionTableTableIx OBJECT-TYPE
   SYNTAX      TableIndex
   MAX-ACCESS  not-accessible
   STATUS      current
   DESCRIPTION
      ""
   ::= {er1645v2Lan3MCVlanVlanVidExtensionTableEntry 11}

er1645v2Lan3MCVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.vidExtension.table.tpid

       Possibilities:
               dot1Q   (33024)
               dot1ad   (34984)
               0x9100   (37120)
               0x9200   (37376)
               0x9300   (37632)"
   ::= {er1645v2Lan3MCVlanVlanVidExtensionTableEntry 16777216}

er1645v2Lan3MCVlanVlanVidExtensionTableVid OBJECT-TYPE
   SYNTAX      Integer32
   MAX-ACCESS  read-write
   STATUS      current
   DESCRIPTION
      "Path: ethernet3.editConf.vlan.vlan.vidExtension.table.vid"
   ::= {er1645v2Lan3MCVlanVlanVidExtensionTableEntry 33554432}

er1645v2Lan3MCVlanVlanVidExtensionTableEndVid OBJECT-TYPE
   SYNTAX      Integer32
   MAX-ACCESS  read-write
   STATUS      current
   DESCRIPTION
      "Path: ethernet3.editConf.vlan.vlan.vidExtension.table.endVid"
   ::= {er1645v2Lan3MCVlanVlanVidExtensionTableEntry 50331648}

er1645v2Lan3MCVlanVlanCSMap OBJECT-TYPE
   SYNTAX      SEQUENCE OF Er1645v2Lan3MCVlanVlanCSMapEntry
   MAX-ACCESS  not-accessible
   STATUS      current
   DESCRIPTION
      ""
   ::= {er1645v2Lan3MCVlan 235405312}

er1645v2Lan3MCVlanVlanCSMapEntry OBJECT-TYPE
   SYNTAX      Er1645v2Lan3MCVlanVlanCSMapEntry
   MAX-ACCESS  not-accessible
   STATUS      current
   DESCRIPTION
      ""
   INDEX      { er1645v2Lan3MCVlanTableIx,
                er1645v2Lan3MCVlanVlanCSMapTableIx }
   ::= {er1645v2Lan3MCVlanVlanCSMap 1}

Er1645v2Lan3MCVlanVlanCSMapEntry ::=
   SEQUENCE
      {
      er1645v2Lan3MCVlanVlanCSMapActions
         VariableLengthTableActions,
      er1645v2Lan3MCVlanVlanCSMapTableIx
         TableIndex,
      er1645v2Lan3MCVlanVlanCSMapCos
         INTEGER,
      er1645v2Lan3MCVlanVlanCSMapDei
         INTEGER,
      er1645v2Lan3MCVlanVlanCSMapTos
         INTEGER,
      er1645v2Lan3MCVlanVlanCSMapQueue
         INTEGER,
      er1645v2Lan3MCVlanVlanCSMapDropLevel
         INTEGER,
      er1645v2Lan3MCVlanVlanCSMapDeFlag
         INTEGER
      }

er1645v2Lan3MCVlanVlanCSMapActions OBJECT-TYPE
   SYNTAX      VariableLengthTableActions
   MAX-ACCESS  read-write
   STATUS      current
   DESCRIPTION
      "By way of this field, some manipulations
       on this table may be performed."
   ::= {er1645v2Lan3MCVlanVlanCSMapEntry 2}

er1645v2Lan3MCVlanVlanCSMapTableIx OBJECT-TYPE
   SYNTAX      TableIndex
   MAX-ACCESS  not-accessible
   STATUS      current
   DESCRIPTION
      ""
   ::= {er1645v2Lan3MCVlanVlanCSMapEntry 11}

er1645v2Lan3MCVlanVlanCSMapCos OBJECT-TYPE
   SYNTAX      INTEGER
               {
               any (8)
               }
   MAX-ACCESS  read-write
   STATUS      current
   DESCRIPTION
      "Path: ethernet3.editConf.vlan.vlan.cosMap.cos

       Possibilities:
               any   (8)"
   ::= {er1645v2Lan3MCVlanVlanCSMapEntry 16777216}

er1645v2Lan3MCVlanVlanCSMapDei OBJECT-TYPE
   SYNTAX      INTEGER
               {
               clear (0),
               set (1),
               any (2)
               }
   MAX-ACCESS  read-write
   STATUS      current
   DESCRIPTION
      "Path: ethernet3.editConf.vlan.vlan.cosMap.dei

       Possibilities:
               clear   (0)
               set   (1)
               any   (2)"
   ::= {er1645v2Lan3MCVlanVlanCSMapEntry 33554432}

er1645v2Lan3MCVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan3MCVlanVlanCSMapEntry 50331648}

er1645v2Lan3MCVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2Lan3MCVlanVlanCSMapEntry 67108864}

er1645v2Lan3MCVlanVlanCSMapDropLevel OBJECT-TYPE
   SYNTAX      INTEGER
               {
               unchanged (-1),
               dropOnQueue (0)
               }
   MAX-ACCESS  read-write
   STATUS      current
   DESCRIPTION
      "Path: ethernet3.editConf.vlan.vlan.cosMap.dropLevel

       Possibilities:
               unchanged   (-1)
               dropOnQueue   (0)"
   ::= {er1645v2Lan3MCVlanVlanCSMapEntry 83886080}

er1645v2Lan3MCVlanVlanCSMapDeFlag OBJECT-TYPE
   SYNTAX      INTEGER
               {
               unchanged (255),
               clear (0),
               set (1)
               }
   MAX-ACCESS  read-write
   STATUS      current
   DESCRIPTION
      "Path: ethernet3.editConf.vlan.vlan.cosMap.deFlag

       Possibilities:
               unchanged   (255)
               clear   (0)
               set   (1)"
   ::= {er1645v2Lan3MCVlanVlanCSMapEntry 117440512}

er1645v2Lan3MCVlanVlanTCMap OBJECT-TYPE
   SYNTAX      SEQUENCE OF Er1645v2Lan3MCVlanVlanTCMapEntry
   MAX-ACCESS  not-accessible
   STATUS      current
   DESCRIPTION
      ""
   ::= {er1645v2Lan3MCVlan 241369088}

er1645v2Lan3MCVlanVlanTCMapEntry OBJECT-TYPE
   SYNTAX      Er1645v2Lan3MCVlanVlanTCMapEntry
   MAX-ACCESS  not-accessible
   STATUS      current
   DESCRIPTION
      ""
   INDEX      { er1645v2Lan3MCVlanTableIx,
                er1645v2Lan3MCVlanVlanTCMapTableIx }
   ::= {er1645v2Lan3MCVlanVlanTCMap 1}

Er1645v2Lan3MCVlanVlanTCMapEntry ::=
   SEQUENCE
      {
      er1645v2Lan3MCVlanVlanTCMapActions
         VariableLengthTableActions,
      er1645v2Lan3MCVlanVlanTCMapTableIx
         TableIndex,
      er1645v2Lan3MCVlanVlanTCMapStartTos
         INTEGER,
      er1645v2Lan3MCVlanVlanTCMapEndTos
         INTEGER,
      er1645v2Lan3MCVlanVlanTCMapCos
         INTEGER
      }

er1645v2Lan3MCVlanVlanTCMapActions OBJECT-TYPE
   SYNTAX      VariableLengthTableActions
   MAX-ACCESS  read-write
   STATUS      current
   DESCRIPTION
      "By way of this field, some manipulations
       on this table may be performed."
   ::= {er1645v2Lan3MCVlanVlanTCMapEntry 2}

er1645v2Lan3MCVlanVlanTCMapTableIx OBJECT-TYPE
   SYNTAX      TableIndex
   MAX-ACCESS  not-accessible
   STATUS      current
   DESCRIPTION
      ""
   ::= {er1645v2Lan3MCVlanVlanTCMapEntry 11}

er1645v2Lan3MCVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan3MCVlanVlanTCMapEntry 16777216}

er1645v2Lan3MCVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan3MCVlanVlanTCMapEntry 33554432}

er1645v2Lan3MCVlanVlanTCMapCos OBJECT-TYPE
   SYNTAX      INTEGER
               {
               queueCosMap (8)
               }
   MAX-ACCESS  read-write
   STATUS      current
   DESCRIPTION
      "Path: ethernet3.editConf.vlan.vlan.tosCosMap.cos

       Possibilities:
               queueCosMap   (8)"
   ::= {er1645v2Lan3MCVlanVlanTCMapEntry 50331648}

er1645v2Lan3MCVlanVlanArpStaticArp OBJECT-TYPE
   SYNTAX      SEQUENCE OF Er1645v2Lan3MCVlanVlanArpStaticArpEntry
   MAX-ACCESS  not-accessible
   STATUS      current
   DESCRIPTION
      ""
   ::= {er1645v2Lan3MCVlan 235275008}

er1645v2Lan3MCVlanVlanArpStaticArpEntry OBJECT-TYPE
   SYNTAX      Er1645v2Lan3MCVlanVlanArpStaticArpEntry
   MAX-ACCESS  not-accessible
   STATUS      current
   DESCRIPTION
      ""
   INDEX      { er1645v2Lan3MCVlanTableIx,
                er1645v2Lan3MCVlanVlanArpStaticArpTableIx }
   ::= {er1645v2Lan3MCVlanVlanArpStaticArp 1}

Er1645v2Lan3MCVlanVlanArpStaticArpEntry ::=
   SEQUENCE
      {
      er1645v2Lan3MCVlanVlanArpStaticArpActions
         VariableLengthTableActions,
      er1645v2Lan3MCVlanVlanArpStaticArpTableIx
         TableIndex,
      er1645v2Lan3MCVlanVlanArpStaticArpMacAddress
         OCTET STRING,
      er1645v2Lan3MCVlanVlanArpStaticArpIpAddress
         IpAddress
      }

er1645v2Lan3MCVlanVlanArpStaticArpActions OBJECT-TYPE
   SYNTAX      VariableLengthTableActions
   MAX-ACCESS  read-write
   STATUS      current
   DESCRIPTION
      "By way of this field, some manipulations
       on this table may be performed."
   ::= {er1645v2Lan3MCVlanVlanArpStaticArpEntry 2}

er1645v2Lan3MCVlanVlanArpStaticArpTableIx OBJECT-TYPE
   SYNTAX      TableIndex
   MAX-ACCESS  not-accessible
   STATUS      current
   DESCRIPTION
      ""
   ::= {er1645v2Lan3MCVlanVlanArpStaticArpEntry 11}

er1645v2Lan3MCVlanVlanArpStaticArpMacAddress OBJECT-TYPE
   SYNTAX      OCTET STRING
   MAX-ACCESS  read-write
   STATUS      current
   DESCRIPTION
      "Path: ethernet3.editConf.vlan.vlan.arp.staticArp.macAddress

       MAC address."
   ::= {er1645v2Lan3MCVlanVlanArpStaticArpEntry 16777216}

er1645v2Lan3MCVlanVlanArpStaticArpIpAddress OBJECT-TYPE
   SYNTAX      IpAddress
   MAX-ACCESS  read-write
   STATUS      current
   DESCRIPTION
      "Path: ethernet3.editConf.vlan.vlan.arp.staticArp.ipAddress"
   ::= {er1645v2Lan3MCVlanVlanArpStaticArpEntry 33554432}


er1645v2Lan3MCPppOE OBJECT IDENTIFIER ::= {er1645v2Lan3MC 35}

er1645v2Lan3MCPppOESSCTable OBJECT-TYPE
   SYNTAX      SEQUENCE OF Er1645v2Lan3MCPppOEEntry
   MAX-ACCESS  not-accessible
   STATUS      current
   DESCRIPTION
      ""
   ::= {er1645v2Lan3MCPppOE 1}

er1645v2Lan3MCPppOEEntry OBJECT-TYPE
   SYNTAX      Er1645v2Lan3MCPppOEEntry
   MAX-ACCESS  not-accessible
   STATUS      current
   DESCRIPTION
      ""
   INDEX      { er1645v2Lan3MCPppOETableIx }
   ::= {er1645v2Lan3MCPppOESSCTable 1}

Er1645v2Lan3MCPppOEEntry ::=
   SEQUENCE
      {
      er1645v2Lan3MCPppOEActions
         VariableLengthTableActions,
      er1645v2Lan3MCPppOETableIx
         TableIndex,
      er1645v2Lan3MCPppOEName
         DisplayString,
      er1645v2Lan3MCPppOERemark
         DisplayString,
      er1645v2Lan3MCPppOEAdminStatus
         INTEGER,
      er1645v2Lan3MCPppOEMode
         INTEGER,
      er1645v2Lan3MCPppOEIpVrfRouter
         DisplayString,
      er1645v2Lan3MCPppOEIpAdr
         IpAddress,
      er1645v2Lan3MCPppOEIpNetm
         IpAddress,
      er1645v2Lan3MCPppOEIpSNetName
         INTEGER,
      er1645v2Lan3MCPppOEIpSNetCust
         DisplayString,
      er1645v2Lan3MCPppOEIpRem
         IpAddress,
      er1645v2Lan3MCPppOEIpUnnumbered
         DisplayString,
      er1645v2Lan3MCPppOEIpGwPref
         Integer32,
      er1645v2Lan3MCPppOEIpRsn
         INTEGER,
      er1645v2Lan3MCPppOEIpMtu
         Integer32,
      er1645v2Lan3MCPppOEIpMssAdjust
         INTEGER,
      er1645v2Lan3MCPppOEIpRipMetric
         Integer32,
      er1645v2Lan3MCPppOEIpRipMetricOut
         Integer32,
      er1645v2Lan3MCPppOEIpRipMode
         INTEGER,
      er1645v2Lan3MCPppOEIpRipTxVer
         INTEGER,
      er1645v2Lan3MCPppOEIpRipRxVer
         INTEGER,
      er1645v2Lan3MCPppOEIpRipSplitH
         INTEGER,
      er1645v2Lan3MCPppOEIpRipAuth
         INTEGER,
      er1645v2Lan3MCPppOEIpRipFilter
         DisplayString,
      er1645v2Lan3MCPppOEIpRipFilterIn
         DisplayString,
      er1645v2Lan3MCPppOEIpRipClearNextHop
         INTEGER,
      er1645v2Lan3MCPppOEIpAccPol
         DisplayString,
      er1645v2Lan3MCPppOEIpAB
         DisplayString,
      er1645v2Lan3MCPppOEIpMA
         INTEGER,
      er1645v2Lan3MCPppOEIpMF
         Integer32,
      er1645v2Lan3MCPppOEIpDB
         INTEGER,
      er1645v2Lan3MCPppOEIpIR
         INTEGER,
      er1645v2Lan3MCPppOEIpIgmp
         INTEGER,
      er1645v2Lan3MCPppOEIpNN
         DisplayString,
      er1645v2Lan3MCPppOEIpPimMode
         INTEGER,
      er1645v2Lan3MCPppOEIpPimDrPriority
         Counter32,
      er1645v2Lan3MCPppOEIpPimHelloTime
         TimeTicks,
      er1645v2Lan3MCPppOEIpPimPropagationDelay
         TimeTicks,
      er1645v2Lan3MCPppOEIpPimOverrideInterval
         TimeTicks,
      er1645v2Lan3MCPppOEIpPimBsrBorder
         INTEGER,
      er1645v2Lan3MCPppOEIpPimTtlThreshold
         Integer32,
      er1645v2Lan3MCPppOEIpIMNetworkUnreachable
         INTEGER,
      er1645v2Lan3MCPppOEIpIMHostUnreachable
         INTEGER,
      er1645v2Lan3MCPppOEIpIMProtocolUnreachable
         INTEGER,
      er1645v2Lan3MCPppOEIpIMPortUnreachable
         INTEGER,
      er1645v2Lan3MCPppOEIpIMMtuExceeded
         INTEGER,
      er1645v2Lan3MCPppOEIpIMAdminProhibited
         INTEGER,
      er1645v2Lan3MCPppOEIpIMTtlExceeded
         INTEGER,
      er1645v2Lan3MCPppOEIpIMRedirect
         INTEGER,
      er1645v2Lan3MCPppOEIpV6VrfRouter
         DisplayString,
      er1645v2Lan3MCPppOEIpV6AddrAutoConfigNrDupAddrDetects
         Integer32,
      er1645v2Lan3MCPppOEIpV6AddrAutoConfigAcceptRa
         INTEGER,
      er1645v2Lan3MCPppOEIpV6AddrAutoConfigAcceptRaRdnss
         INTEGER,
      er1645v2Lan3MCPppOEIpV6AddrAutoConfigAcceptRaDnssl
         INTEGER,
      er1645v2Lan3MCPppOEIpV6DefaultRoute
         INTEGER,
      er1645v2Lan3MCPppOEIpV6RaSend
         INTEGER,
      er1645v2Lan3MCPppOEIpV6RaMinInterval
         TimeTicks,
      er1645v2Lan3MCPppOEIpV6RaMaxInterval
         TimeTicks,
      er1645v2Lan3MCPppOEIpV6RaManagedFlag
         INTEGER,
      er1645v2Lan3MCPppOEIpV6RaOtherConfFlag
         INTEGER,
      er1645v2Lan3MCPppOEIpV6RaLinkMtu
         Integer32,
      er1645v2Lan3MCPppOEIpV6RaReachableTime
         TimeTicks,
      er1645v2Lan3MCPppOEIpV6RaRetransmitTime
         TimeTicks,
      er1645v2Lan3MCPppOEIpV6RaHopLimit
         Integer32,
      er1645v2Lan3MCPppOEIpV6RaDefaultLifeTime
         TimeTicks,
      er1645v2Lan3MCPppOEIpV6RaDnsOptionsRdnssLifeTime
         TimeTicks,
      er1645v2Lan3MCPppOEIpV6RaDnsOptionsRdnssImportServers
         INTEGER,
      er1645v2Lan3MCPppOEIpV6RaDnsOptionsDnsslLifeTime
         TimeTicks,
      er1645v2Lan3MCPppOEIpV6RaDnsOptionsDnsslImportDomains
         INTEGER,
      er1645v2Lan3MCPppOEIpV6RsSend
         INTEGER,
      er1645v2Lan3MCPppOEIpV6RsMaxRandomDelay
         TimeTicks,
      er1645v2Lan3MCPppOEIpV6RsInterval
         TimeTicks,
      er1645v2Lan3MCPppOEIpV6RsMaxSolicitations
         Integer32,
      er1645v2Lan3MCPppOEIpV6TrafficPolicyInbound
         DisplayString,
      er1645v2Lan3MCPppOEIpV6TrafficPolicyOutbound
         DisplayString,
      er1645v2Lan3MCPppOEIpV6FirewallZone
         DisplayString,
      er1645v2Lan3MCPppOEIpV6DhcpClientAddrAC
         INTEGER,
      er1645v2Lan3MCPppOEIpV6DhcpClientPrDelMode
         INTEGER,
      er1645v2Lan3MCPppOEIpV6DhcpClientPrDelPool
         DisplayString,
      er1645v2Lan3MCPppOEIpV6DhcpClientPrDelPdExclOpt
         INTEGER,
      er1645v2Lan3MCPppOEIpV6DhcpClientDnsServerPref
         Integer32,
      er1645v2Lan3MCPppOEIpV6DhcpClientRapidCommit
         INTEGER,
      er1645v2Lan3MCPppOEIpV6DhcpClientTimersSolTimeOut
         TimeTicks,
      er1645v2Lan3MCPppOEIpV6DhcpClientTimersSolMaxRt
         TimeTicks,
      er1645v2Lan3MCPppOEIpV6DhcpClientTimersInfoRefresh
         TimeTicks,
      er1645v2Lan3MCPppOEIpV6DhcpServerMode
         INTEGER,
      er1645v2Lan3MCPppOEIpV6DhcpServerPreference
         Integer32,
      er1645v2Lan3MCPppOEIpV6DhcpServerPool
         DisplayString,
      er1645v2Lan3MCPppOEIpV6DhcpServerRapidCommit
         INTEGER,
      er1645v2Lan3MCPppOEIpV6DhcpServerTimersInfoRefresh
         TimeTicks,
      er1645v2Lan3MCPppOEIpV6DhcpRelayMode
         INTEGER,
      er1645v2Lan3MCPppOEIpV6SendRedirect
         INTEGER,
      er1645v2Lan3MCPppOEIpV6LinkMtu
         Integer32,
      er1645v2Lan3MCPppOEIpV6InterfaceId
         OCTET STRING,
      er1645v2Lan3MCPppOEIpV6MF
         Integer32,
      er1645v2Lan3MCPppOEIpV6IcmpMessagesNoRoute
         INTEGER,
      er1645v2Lan3MCPppOEIpV6IcmpMessagesBeyondScope
         INTEGER,
      er1645v2Lan3MCPppOEIpV6IcmpMessagesAddressUnreachable
         INTEGER,
      er1645v2Lan3MCPppOEIpV6IcmpMessagesPortUnreachable
         INTEGER,
      er1645v2Lan3MCPppOEIpV6IcmpMessagesPacketTooBig
         INTEGER,
      er1645v2Lan3MCPppOEIpV6IcmpMessagesHopLimitExceeded
         INTEGER,
      er1645v2Lan3MCPppOEIpV6IcmpMessagesFragTimeExceeded
         INTEGER,
      er1645v2Lan3MCPppOEIpV6IcmpMessagesHeaderFieldErr
         INTEGER,
      er1645v2Lan3MCPppOEIpV6IcmpMessagesOptionUnrecognized
         INTEGER,
      er1645v2Lan3MCPppOEIpV6IcmpMessagesRedirect
         INTEGER,
      er1645v2Lan3MCPppOEPppLnkMOperation
         INTEGER,
      er1645v2Lan3MCPppOEPppLnkMInterval
         TimeTicks,
      er1645v2Lan3MCPppOEPppLnkMRepTimeOut
         TimeTicks,
      er1645v2Lan3MCPppOEPppLnkMFailsPrmt
         Integer32,
      er1645v2Lan3MCPppOEPppAuthentication
         INTEGER,
      er1645v2Lan3MCPppOEPppAuthenPeriod
         TimeTicks,
      er1645v2Lan3MCPppOEPppSessionName
         DisplayString,
      er1645v2Lan3MCPppOEPppSessionSecret
         DisplayString,
      er1645v2Lan3MCPppOEPppEncModeSessionSecret
         INTEGER,
      er1645v2Lan3MCPppOEPppEncSessionSecret
         DisplayString,
      er1645v2Lan3MCPppOEPppServiceName
         DisplayString
      }

er1645v2Lan3MCPppOEActions OBJECT-TYPE
   SYNTAX      VariableLengthTableActions
   MAX-ACCESS  read-write
   STATUS      current
   DESCRIPTION
      "By way of this field, some manipulations
       on this table may be performed."
   ::= {er1645v2Lan3MCPppOEEntry 2}

er1645v2Lan3MCPppOETableIx OBJECT-TYPE
   SYNTAX      TableIndex
   MAX-ACCESS  not-accessible
   STATUS      current
   DESCRIPTION
      ""
   ::= {er1645v2Lan3MCPppOEEntry 11}

er1645v2Lan3MCPppOEName OBJECT-TYPE
   SYNTAX      DisplayString
   MAX-ACCESS  read-write
   STATUS      current
   DESCRIPTION
      "Path: ethernet3.editConf.pppoEClient.name"
   ::= {er1645v2Lan3MCPppOEEntry 16777216}

er1645v2Lan3MCPppOERemark OBJECT-TYPE
   SYNTAX      DisplayString
   MAX-ACCESS  read-write
   STATUS      current
   DESCRIPTION
      "Path: ethernet3.editConf.pppoEClient.remark"
   ::= {er1645v2Lan3MCPppOEEntry 1157627904}

er1645v2Lan3MCPppOEAdminStatus OBJECT-TYPE
   SYNTAX      INTEGER
               {
               up (1),
               down (2)
               }
   MAX-ACCESS  read-write
   STATUS      current
   DESCRIPTION
      "Path: ethernet3.editConf.pppoEClient.adminStatus

       Possibilities:
               up   (1)
               down   (2)"
   ::= {er1645v2Lan3MCPppOEEntry 33554432}

er1645v2Lan3MCPppOEMode OBJECT-TYPE
   SYNTAX      INTEGER
               {
               routing (1),
               multilink (8),
               ipV6 (16),
               ipV6ipV4 (17)
               }
   MAX-ACCESS  read-write
   STATUS      current
   DESCRIPTION
      "Path: ethernet3.editConf.pppoEClient.mode

       Possibilities:
               routing   (1)
               multilink   (8)
               ipV6   (16)
               ipV6/ipV4   (17)"
   ::= {er1645v2Lan3MCPppOEEntry 67108864}

er1645v2Lan3MCPppOEIpVrfRouter OBJECT-TYPE
   SYNTAX      DisplayString
   MAX-ACCESS  read-write
   STATUS      current
   DESCRIPTION
      "Path: ethernet3.editConf.pppoEClient.ip.vrfRouter"
   ::= {er1645v2Lan3MCPppOEEntry 53215232}

er1645v2Lan3MCPppOEIpAdr OBJECT-TYPE
   SYNTAX      IpAddress
   MAX-ACCESS  read-write
   STATUS      current
   DESCRIPTION
      "Path: ethernet3.editConf.pppoEClient.ip.address"
   ::= {er1645v2Lan3MCPppOEEntry 58261504}

er1645v2Lan3MCPppOEIpNetm OBJECT-TYPE
   SYNTAX      IpAddress
   MAX-ACCESS  read-write
   STATUS      current
   DESCRIPTION
      "Path: ethernet3.editConf.pppoEClient.ip.netMask"
   ::= {er1645v2Lan3MCPppOEEntry 58392576}

er1645v2Lan3MCPppOEIpSNetName OBJECT-TYPE
   SYNTAX      INTEGER
               {
               slOPTg (0),
               corp (2),
               dmz (3),
               internet (1)
               }
   MAX-ACCESS  read-write
   STATUS      current
   DESCRIPTION
      "Path: ethernet3.editConf.pppoEClient.ip.sNet.name

       Possibilities:
               <OPT>   (0)
               corp   (2)
               dmz   (3)
               internet   (1)"
   ::= {er1645v2Lan3MCPppOEEntry 53674240}

er1645v2Lan3MCPppOEIpSNetCust OBJECT-TYPE
   SYNTAX      DisplayString
   MAX-ACCESS  read-write
   STATUS      current
   DESCRIPTION
      "Path: ethernet3.editConf.pppoEClient.ip.sNet.custom"
   ::= {er1645v2Lan3MCPppOEEntry 53674496}

er1645v2Lan3MCPppOEIpRem OBJECT-TYPE
   SYNTAX      IpAddress
   MAX-ACCESS  read-write
   STATUS      current
   DESCRIPTION
      "Path: ethernet3.editConf.pppoEClient.ip.remote"
   ::= {er1645v2Lan3MCPppOEEntry 58458112}

er1645v2Lan3MCPppOEIpUnnumbered OBJECT-TYPE
   SYNTAX      DisplayString
   MAX-ACCESS  read-write
   STATUS      current
   DESCRIPTION
      "Path: ethernet3.editConf.pppoEClient.ip.unnumbered"
   ::= {er1645v2Lan3MCPppOEEntry 52625408}

er1645v2Lan3MCPppOEIpGwPref OBJECT-TYPE
   SYNTAX      Integer32
   MAX-ACCESS  read-write
   STATUS      current
   DESCRIPTION
      "Path: ethernet3.editConf.pppoEClient.ip.gatewayPreference"
   ::= {er1645v2Lan3MCPppOEEntry 52690944}

er1645v2Lan3MCPppOEIpRsn OBJECT-TYPE
   SYNTAX      INTEGER
               {
               disabled (0),
               enabled (1)
               }
   MAX-ACCESS  read-write
   STATUS      current
   DESCRIPTION
      "Path: ethernet3.editConf.pppoEClient.ip.requestSubnet

       Possibilities:
               disabled   (0)
               enabled   (1)"
   ::= {er1645v2Lan3MCPppOEEntry 56688640}

er1645v2Lan3MCPppOEIpMtu OBJECT-TYPE
   SYNTAX      Integer32
   MAX-ACCESS  read-write
   STATUS      current
   DESCRIPTION
      "Path: ethernet3.editConf.pppoEClient.ip.mtu"
   ::= {er1645v2Lan3MCPppOEEntry 52953088}

er1645v2Lan3MCPppOEIpMssAdjust OBJECT-TYPE
   SYNTAX      INTEGER
               {
               disabled (0),
               auto (65536)
               }
   MAX-ACCESS  read-write
   STATUS      current
   DESCRIPTION
      "Path: ethernet3.editConf.pppoEClient.ip.mssAdjust

       Possibilities:
               disabled   (0)
               auto   (65536)"
   ::= {er1645v2Lan3MCPppOEEntry 53280768}

er1645v2Lan3MCPppOEIpRipMetric OBJECT-TYPE
   SYNTAX      Integer32
   MAX-ACCESS  read-write
   STATUS      current
   DESCRIPTION
      "Path: ethernet3.editConf.pppoEClient.ip.rip.metric"
   ::= {er1645v2Lan3MCPppOEEntry 51712768}

er1645v2Lan3MCPppOEIpRipMetricOut OBJECT-TYPE
   SYNTAX      Integer32
   MAX-ACCESS  read-write
   STATUS      current
   DESCRIPTION
      "Path: ethernet3.editConf.pppoEClient.ip.rip.metricOut"
   ::= {er1645v2Lan3MCPppOEEntry 51713024}

er1645v2Lan3MCPppOEIpRipMode OBJECT-TYPE
   SYNTAX      INTEGER
               {
               disabled (0),
               passive (1),
               active (2)
               }
   MAX-ACCESS  read-write
   STATUS      current
   DESCRIPTION
      "Path: ethernet3.editConf.pppoEClient.ip.rip.mode

       Possibilities:
               disabled   (0)
               passive   (1)
               active   (2)"
   ::= {er1645v2Lan3MCPppOEEntry 51713280}

er1645v2Lan3MCPppOEIpRipTxVer OBJECT-TYPE
   SYNTAX      INTEGER
               {
               rip1 (0),
               rip2 (1),
               rip1mcompatible (2)
               }
   MAX-ACCESS  read-write
   STATUS      current
   DESCRIPTION
      "Path: ethernet3.editConf.pppoEClient.ip.rip.txVersion

       Possibilities:
               rip1   (0)
               rip2   (1)
               rip1-compatible   (2)"
   ::= {er1645v2Lan3MCPppOEEntry 51716864}

er1645v2Lan3MCPppOEIpRipRxVer OBJECT-TYPE
   SYNTAX      INTEGER
               {
               rip1only (0),
               rip2only (1),
               rip12 (2)
               }
   MAX-ACCESS  read-write
   STATUS      current
   DESCRIPTION
      "Path: ethernet3.editConf.pppoEClient.ip.rip.rxVersion

       Possibilities:
               rip1only   (0)
               rip2only   (1)
               rip1&2   (2)"
   ::= {er1645v2Lan3MCPppOEEntry 51717120}

er1645v2Lan3MCPppOEIpRipSplitH OBJECT-TYPE
   SYNTAX      INTEGER
               {
               disabled (0),
               enabled (1),
               poisonedReverse (2)
               }
   MAX-ACCESS  read-write
   STATUS      current
   DESCRIPTION
      "Path: ethernet3.editConf.pppoEClient.ip.rip.splitHorizon

       Possibilities:
               disabled   (0)
               enabled   (1)
               poisonedReverse   (2)"
   ::= {er1645v2Lan3MCPppOEEntry 51713792}

er1645v2Lan3MCPppOEIpRipAuth OBJECT-TYPE
   SYNTAX      INTEGER
               {
               disabled (0),
               texts (1),
               md5 (2)
               }
   MAX-ACCESS  read-write
   STATUS      current
   DESCRIPTION
      "Path: ethernet3.editConf.pppoEClient.ip.rip.authentication

       Possibilities:
               disabled   (0)
               text    (1)
               md5   (2)"
   ::= {er1645v2Lan3MCPppOEEntry 51712512}

er1645v2Lan3MCPppOEIpRipFilter OBJECT-TYPE
   SYNTAX      DisplayString
   MAX-ACCESS  read-write
   STATUS      current
   DESCRIPTION
      "Path: ethernet3.editConf.pppoEClient.ip.rip.filter"
   ::= {er1645v2Lan3MCPppOEEntry 51716096}

er1645v2Lan3MCPppOEIpRipFilterIn OBJECT-TYPE
   SYNTAX      DisplayString
   MAX-ACCESS  read-write
   STATUS      current
   DESCRIPTION
      "Path: ethernet3.editConf.pppoEClient.ip.rip.filterIn"
   ::= {er1645v2Lan3MCPppOEEntry 51716352}

er1645v2Lan3MCPppOEIpRipClearNextHop OBJECT-TYPE
   SYNTAX      INTEGER
               {
               disabled (0),
               enabled (1)
               }
   MAX-ACCESS  read-write
   STATUS      current
   DESCRIPTION
      "Path: ethernet3.editConf.pppoEClient.ip.rip.clearNextHop

       Possibilities:
               disabled   (0)
               enabled   (1)"
   ::= {er1645v2Lan3MCPppOEEntry 51708416}

er1645v2Lan3MCPppOEIpAccPol OBJECT-TYPE
   SYNTAX      DisplayString
   MAX-ACCESS  read-write
   STATUS      current
   DESCRIPTION
      "Path: ethernet3.editConf.pppoEClient.ip.accessPolicy"
   ::= {er1645v2Lan3MCPppOEEntry 53084160}

er1645v2Lan3MCPppOEIpAB OBJECT-TYPE
   SYNTAX      DisplayString
   MAX-ACCESS  read-write
   STATUS      current
   DESCRIPTION
      "Path: ethernet3.editConf.pppoEClient.ip.trafficPolicy"
   ::= {er1645v2Lan3MCPppOEEntry 51249152}

er1645v2Lan3MCPppOEIpMA OBJECT-TYPE
   SYNTAX      INTEGER
               {
               disabled (0),
               enabled (1)
               }
   MAX-ACCESS  read-write
   STATUS      current
   DESCRIPTION
      "Path: ethernet3.editConf.pppoEClient.ip.mgmtAccess

       Possibilities:
               disabled   (0)
               enabled   (1)"
   ::= {er1645v2Lan3MCPppOEEntry 51380224}

er1645v2Lan3MCPppOEIpMF OBJECT-TYPE
   SYNTAX      Integer32
   MAX-ACCESS  read-write
   STATUS      current
   DESCRIPTION
      "Path: ethernet3.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan3MCPppOEEntry 51445760}

er1645v2Lan3MCPppOEIpDB OBJECT-TYPE
   SYNTAX      INTEGER
               {
               disabled (0),
               enabled (1)
               }
   MAX-ACCESS  read-write
   STATUS      current
   DESCRIPTION
      "Path: ethernet3.editConf.pppoEClient.ip.directedBroadcasts

       Possibilities:
               disabled   (0)
               enabled   (1)"
   ::= {er1645v2Lan3MCPppOEEntry 51773440}

er1645v2Lan3MCPppOEIpIR OBJECT-TYPE
   SYNTAX      INTEGER
               {
               disabled (0),
               enabled (1)
               }
   MAX-ACCESS  read-write
   STATUS      current
   DESCRIPTION
      "Path: ethernet3.editConf.pppoEClient.ip.icmpRedirects

       Possibilities:
               disabled   (0)
               enabled   (1)"
   ::= {er1645v2Lan3MCPppOEEntry 52035584}

er1645v2Lan3MCPppOEIpIgmp OBJECT-TYPE
   SYNTAX      INTEGER
               {
               disabled (0),
               proxy (1),
               router (2),
               v3Router (5)
               }
   MAX-ACCESS  read-write
   STATUS      current
   DESCRIPTION
      "Path: ethernet3.editConf.pppoEClient.ip.igmp

       Possibilities:
               disabled   (0)
               proxy   (1)
               router   (2)
               v3Router   (5)"
   ::= {er1645v2Lan3MCPppOEEntry 52428800}

er1645v2Lan3MCPppOEIpNN OBJECT-TYPE
   SYNTAX      DisplayString
   MAX-ACCESS  read-write
   STATUS      current
   DESCRIPTION
      "Path: ethernet3.editConf.pppoEClient.ip.nat"
   ::= {er1645v2Lan3MCPppOEEntry 52101120}

er1645v2Lan3MCPppOEIpPimMode OBJECT-TYPE
   SYNTAX      INTEGER
               {
               disabled (0),
               sparse (1),
               passive (2)
               }
   MAX-ACCESS  read-write
   STATUS      current
   DESCRIPTION
      "Path: ethernet3.editConf.pppoEClient.ip.pim.mode

       Possibilities:
               disabled   (0)
               sparse   (1)
               passive   (2)"
   ::= {er1645v2Lan3MCPppOEEntry 53346560}

er1645v2Lan3MCPppOEIpPimDrPriority OBJECT-TYPE
   SYNTAX      Counter32
   MAX-ACCESS  read-write
   STATUS      current
   DESCRIPTION
      "Path: ethernet3.editConf.pppoEClient.ip.pim.drPriority

       32 bit unsigned wrappable counter."
   ::= {er1645v2Lan3MCPppOEEntry 53346816}

er1645v2Lan3MCPppOEIpPimHelloTime OBJECT-TYPE
   SYNTAX      TimeTicks
   MAX-ACCESS  read-write
   STATUS      current
   DESCRIPTION
      "Path: ethernet3.editConf.pppoEClient.ip.pim.helloTime

       Time in centi-second."
   ::= {er1645v2Lan3MCPppOEEntry 53347072}

er1645v2Lan3MCPppOEIpPimPropagationDelay OBJECT-TYPE
   SYNTAX      TimeTicks
   MAX-ACCESS  read-write
   STATUS      current
   DESCRIPTION
      "Path: ethernet3.editConf.pppoEClient.ip.pim.propagationDelay

       Time in centi-second."
   ::= {er1645v2Lan3MCPppOEEntry 53347328}

er1645v2Lan3MCPppOEIpPimOverrideInterval OBJECT-TYPE
   SYNTAX      TimeTicks
   MAX-ACCESS  read-write
   STATUS      current
   DESCRIPTION
      "Path: ethernet3.editConf.pppoEClient.ip.pim.overrideInterval

       Time in centi-second."
   ::= {er1645v2Lan3MCPppOEEntry 53347584}

er1645v2Lan3MCPppOEIpPimBsrBorder OBJECT-TYPE
   SYNTAX      INTEGER
               {
               disabled (0),
               enabled (1)
               }
   MAX-ACCESS  read-write
   STATUS      current
   DESCRIPTION
      "Path: ethernet3.editConf.pppoEClient.ip.pim.bsrBorder

       Possibilities:
               disabled   (0)
               enabled   (1)"
   ::= {er1645v2Lan3MCPppOEEntry 53347840}

er1645v2Lan3MCPppOEIpPimTtlThreshold OBJECT-TYPE
   SYNTAX      Integer32
   MAX-ACCESS  read-write
   STATUS      current
   DESCRIPTION
      "Path: ethernet3.editConf.pppoEClient.ip.pim.ttlThreshold"
   ::= {er1645v2Lan3MCPppOEEntry 53348096}

er1645v2Lan3MCPppOEIpIMNetworkUnreachable OBJECT-TYPE
   SYNTAX      INTEGER
               {
               disabled (0),
               enabled (1)
               }
   MAX-ACCESS  read-write
   STATUS      current
   DESCRIPTION
      "Path: ethernet3.editConf.pppoEClient.ip.icmpMessages.networkUnreachable

       Possibilities:
               disabled   (0)
               enabled   (1)"
   ::= {er1645v2Lan3MCPppOEEntry 53412096}

er1645v2Lan3MCPppOEIpIMHostUnreachable OBJECT-TYPE
   SYNTAX      INTEGER
               {
               disabled (0),
               enabled (1)
               }
   MAX-ACCESS  read-write
   STATUS      current
   DESCRIPTION
      "Path: ethernet3.editConf.pppoEClient.ip.icmpMessages.hostUnreachable

       Possibilities:
               disabled   (0)
               enabled   (1)"
   ::= {er1645v2Lan3MCPppOEEntry 53412352}

er1645v2Lan3MCPppOEIpIMProtocolUnreachable OBJECT-TYPE
   SYNTAX      INTEGER
               {
               disabled (0),
               enabled (1)
               }
   MAX-ACCESS  read-write
   STATUS      current
   DESCRIPTION
      "Path: ethernet3.editConf.pppoEClient.ip.icmpMessages.protocolUnreachable

       Possibilities:
               disabled   (0)
               enabled   (1)"
   ::= {er1645v2Lan3MCPppOEEntry 53412608}

er1645v2Lan3MCPppOEIpIMPortUnreachable OBJECT-TYPE
   SYNTAX      INTEGER
               {
               disabled (0),
               enabled (1)
               }
   MAX-ACCESS  read-write
   STATUS      current
   DESCRIPTION
      "Path: ethernet3.editConf.pppoEClient.ip.icmpMessages.portUnreachable

       Possibilities:
               disabled   (0)
               enabled   (1)"
   ::= {er1645v2Lan3MCPppOEEntry 53412864}

er1645v2Lan3MCPppOEIpIMMtuExceeded OBJECT-TYPE
   SYNTAX      INTEGER
               {
               disabled (0),
               enabled (1)
               }
   MAX-ACCESS  read-write
   STATUS      current
   DESCRIPTION
      "Path: ethernet3.editConf.pppoEClient.ip.icmpMessages.mtuExceeded

       Possibilities:
               disabled   (0)
               enabled   (1)"
   ::= {er1645v2Lan3MCPppOEEntry 53413120}

er1645v2Lan3MCPppOEIpIMAdminProhibited OBJECT-TYPE
   SYNTAX      INTEGER
               {
               disabled (0),
               enabled (1)
               }
   MAX-ACCESS  read-write
   STATUS      current
   DESCRIPTION
      "Path: ethernet3.editConf.pppoEClient.ip.icmpMessages.adminProhibited

       Possibilities:
               disabled   (0)
               enabled   (1)"
   ::= {er1645v2Lan3MCPppOEEntry 53413376}

er1645v2Lan3MCPppOEIpIMTtlExceeded OBJECT-TYPE
   SYNTAX      INTEGER
               {
               disabled (0),
               enabled (1)
               }
   MAX-ACCESS  read-write
   STATUS      current
   DESCRIPTION
      "Path: ethernet3.editConf.pppoEClient.ip.icmpMessages.ttlExceeded

       Possibilities:
               disabled   (0)
               enabled   (1)"
   ::= {er1645v2Lan3MCPppOEEntry 53413632}

er1645v2Lan3MCPppOEIpIMRedirect OBJECT-TYPE
   SYNTAX      INTEGER
               {
               disabled (0),
               enabled (1)
               }
   MAX-ACCESS  read-write
   STATUS      current
   DESCRIPTION
      "Path: ethernet3.editConf.pppoEClient.ip.icmpMessages.redirect

       Possibilities:
               disabled   (0)
               enabled   (1)"
   ::= {er1645v2Lan3MCPppOEEntry 53413888}

er1645v2Lan3MCPppOEIpV6VrfRouter OBJECT-TYPE
   SYNTAX      DisplayString
   MAX-ACCESS  read-write
   STATUS      current
   DESCRIPTION
      "Path: ethernet3.editConf.pppoEClient.ipV6.vrfRouter"
   ::= {er1645v2Lan3MCPppOEEntry 704708608}

er1645v2Lan3MCPppOEIpV6AddrAutoConfigNrDupAddrDetects OBJECT-TYPE
   SYNTAX      Integer32
   MAX-ACCESS  read-write
   STATUS      current
   DESCRIPTION
      "Path: ethernet3.editConf.pppoEClient.ipV6.addrAutoConfig.nrDupAddrDetects"
   ::= {er1645v2Lan3MCPppOEEntry 704905472}

er1645v2Lan3MCPppOEIpV6AddrAutoConfigAcceptRa OBJECT-TYPE
   SYNTAX      INTEGER
               {
               disabled (0),
               enabled (1)
               }
   MAX-ACCESS  read-write
   STATUS      current
   DESCRIPTION
      "Path: ethernet3.editConf.pppoEClient.ipV6.addrAutoConfig.acceptRa

       Possibilities:
               disabled   (0)
               enabled   (1)"
   ::= {er1645v2Lan3MCPppOEEntry 704905728}

er1645v2Lan3MCPppOEIpV6AddrAutoConfigAcceptRaRdnss OBJECT-TYPE
   SYNTAX      INTEGER
               {
               disabled (0),
               enabled (1)
               }
   MAX-ACCESS  read-write
   STATUS      current
   DESCRIPTION
      "Path: ethernet3.editConf.pppoEClient.ipV6.addrAutoConfig.acceptRaRdnss

       Possibilities:
               disabled   (0)
               enabled   (1)"
   ::= {er1645v2Lan3MCPppOEEntry 704905984}

er1645v2Lan3MCPppOEIpV6AddrAutoConfigAcceptRaDnssl OBJECT-TYPE
   SYNTAX      INTEGER
               {
               disabled (0),
               enabled (1)
               }
   MAX-ACCESS  read-write
   STATUS      current
   DESCRIPTION
      "Path: ethernet3.editConf.pppoEClient.ipV6.addrAutoConfig.acceptRaDnssl

       Possibilities:
               disabled   (0)
               enabled   (1)"
   ::= {er1645v2Lan3MCPppOEEntry 704906240}

er1645v2Lan3MCPppOEIpV6DefaultRoute OBJECT-TYPE
   SYNTAX      INTEGER
               {
               disabled (0),
               enabled (1)
               }
   MAX-ACCESS  read-write
   STATUS      current
   DESCRIPTION
      "Path: ethernet3.editConf.pppoEClient.ipV6.defaultRoute

       Possibilities:
               disabled   (0)
               enabled   (1)"
   ::= {er1645v2Lan3MCPppOEEntry 704970752}

er1645v2Lan3MCPppOEIpV6RaSend OBJECT-TYPE
   SYNTAX      INTEGER
               {
               disabled (0),
               enabled (1)
               }
   MAX-ACCESS  read-write
   STATUS      current
   DESCRIPTION
      "Path: ethernet3.editConf.pppoEClient.ipV6.ra.send

       Possibilities:
               disabled   (0)
               enabled   (1)"
   ::= {er1645v2Lan3MCPppOEEntry 705036544}

er1645v2Lan3MCPppOEIpV6RaMinInterval OBJECT-TYPE
   SYNTAX      TimeTicks
   MAX-ACCESS  read-write
   STATUS      current
   DESCRIPTION
      "Path: ethernet3.editConf.pppoEClient.ipV6.ra.minInterval

       Time in centi-second."
   ::= {er1645v2Lan3MCPppOEEntry 705036800}

er1645v2Lan3MCPppOEIpV6RaMaxInterval OBJECT-TYPE
   SYNTAX      TimeTicks
   MAX-ACCESS  read-write
   STATUS      current
   DESCRIPTION
      "Path: ethernet3.editConf.pppoEClient.ipV6.ra.maxInterval

       Time in centi-second."
   ::= {er1645v2Lan3MCPppOEEntry 705037056}

er1645v2Lan3MCPppOEIpV6RaManagedFlag OBJECT-TYPE
   SYNTAX      INTEGER
               {
               disabled (0),
               enabled (1)
               }
   MAX-ACCESS  read-write
   STATUS      current
   DESCRIPTION
      "Path: ethernet3.editConf.pppoEClient.ipV6.ra.managedFlag

       Possibilities:
               disabled   (0)
               enabled   (1)"
   ::= {er1645v2Lan3MCPppOEEntry 705037312}

er1645v2Lan3MCPppOEIpV6RaOtherConfFlag OBJECT-TYPE
   SYNTAX      INTEGER
               {
               disabled (0),
               enabled (1)
               }
   MAX-ACCESS  read-write
   STATUS      current
   DESCRIPTION
      "Path: ethernet3.editConf.pppoEClient.ipV6.ra.otherConfFlag

       Possibilities:
               disabled   (0)
               enabled   (1)"
   ::= {er1645v2Lan3MCPppOEEntry 705037568}

er1645v2Lan3MCPppOEIpV6RaLinkMtu OBJECT-TYPE
   SYNTAX      Integer32
   MAX-ACCESS  read-write
   STATUS      current
   DESCRIPTION
      "Path: ethernet3.editConf.pppoEClient.ipV6.ra.linkMtu"
   ::= {er1645v2Lan3MCPppOEEntry 705037824}

er1645v2Lan3MCPppOEIpV6RaReachableTime OBJECT-TYPE
   SYNTAX      TimeTicks
   MAX-ACCESS  read-write
   STATUS      current
   DESCRIPTION
      "Path: ethernet3.editConf.pppoEClient.ipV6.ra.reachableTime

       Time in centi-second."
   ::= {er1645v2Lan3MCPppOEEntry 705038080}

er1645v2Lan3MCPppOEIpV6RaRetransmitTime OBJECT-TYPE
   SYNTAX      TimeTicks
   MAX-ACCESS  read-write
   STATUS      current
   DESCRIPTION
      "Path: ethernet3.editConf.pppoEClient.ipV6.ra.retransmitTime

       Time in centi-second."
   ::= {er1645v2Lan3MCPppOEEntry 705038336}

er1645v2Lan3MCPppOEIpV6RaHopLimit OBJECT-TYPE
   SYNTAX      Integer32
   MAX-ACCESS  read-write
   STATUS      current
   DESCRIPTION
      "Path: ethernet3.editConf.pppoEClient.ipV6.ra.hopLimit"
   ::= {er1645v2Lan3MCPppOEEntry 705038592}

er1645v2Lan3MCPppOEIpV6RaDefaultLifeTime OBJECT-TYPE
   SYNTAX      TimeTicks
   MAX-ACCESS  read-write
   STATUS      current
   DESCRIPTION
      "Path: ethernet3.editConf.pppoEClient.ipV6.ra.defaultLifeTime

       Time in centi-second."
   ::= {er1645v2Lan3MCPppOEEntry 705038848}

er1645v2Lan3MCPppOEIpV6RaDnsOptionsRdnssLifeTime OBJECT-TYPE
   SYNTAX      TimeTicks
   MAX-ACCESS  read-write
   STATUS      current
   DESCRIPTION
      "Path: ethernet3.editConf.pppoEClient.ipV6.ra.dnsOptions.rdnss.lifeTime

       Time in centi-second."
   ::= {er1645v2Lan3MCPppOEEntry 705039140}

er1645v2Lan3MCPppOEIpV6RaDnsOptionsRdnssImportServers OBJECT-TYPE
   SYNTAX      INTEGER
               {
               disabled (0),
               enabled (1)
               }
   MAX-ACCESS  read-write
   STATUS      current
   DESCRIPTION
      "Path: ethernet3.editConf.pppoEClient.ipV6.ra.dnsOptions.rdnss.importServers

       Possibilities:
               disabled   (0)
               enabled   (1)"
   ::= {er1645v2Lan3MCPppOEEntry 705039148}

er1645v2Lan3MCPppOEIpV6RaDnsOptionsDnsslLifeTime OBJECT-TYPE
   SYNTAX      TimeTicks
   MAX-ACCESS  read-write
   STATUS      current
   DESCRIPTION
      "Path: ethernet3.editConf.pppoEClient.ipV6.ra.dnsOptions.dnssl.lifeTime

       Time in centi-second."
   ::= {er1645v2Lan3MCPppOEEntry 705039172}

er1645v2Lan3MCPppOEIpV6RaDnsOptionsDnsslImportDomains OBJECT-TYPE
   SYNTAX      INTEGER
               {
               disabled (0),
               enabled (1)
               }
   MAX-ACCESS  read-write
   STATUS      current
   DESCRIPTION
      "Path: ethernet3.editConf.pppoEClient.ipV6.ra.dnsOptions.dnssl.importDomains

       Possibilities:
               disabled   (0)
               enabled   (1)"
   ::= {er1645v2Lan3MCPppOEEntry 705039180}

er1645v2Lan3MCPppOEIpV6RsSend OBJECT-TYPE
   SYNTAX      INTEGER
               {
               disabled (0),
               enabled (1)
               }
   MAX-ACCESS  read-write
   STATUS      current
   DESCRIPTION
      "Path: ethernet3.editConf.pppoEClient.ipV6.rs.send

       Possibilities:
               disabled   (0)
               enabled   (1)"
   ::= {er1645v2Lan3MCPppOEEntry 705954048}

er1645v2Lan3MCPppOEIpV6RsMaxRandomDelay OBJECT-TYPE
   SYNTAX      TimeTicks
   MAX-ACCESS  read-write
   STATUS      current
   DESCRIPTION
      "Path: ethernet3.editConf.pppoEClient.ipV6.rs.maxRandomDelay

       Time in centi-second."
   ::= {er1645v2Lan3MCPppOEEntry 705954304}

er1645v2Lan3MCPppOEIpV6RsInterval OBJECT-TYPE
   SYNTAX      TimeTicks
   MAX-ACCESS  read-write
   STATUS      current
   DESCRIPTION
      "Path: ethernet3.editConf.pppoEClient.ipV6.rs.interval

       Time in centi-second."
   ::= {er1645v2Lan3MCPppOEEntry 705954560}

er1645v2Lan3MCPppOEIpV6RsMaxSolicitations OBJECT-TYPE
   SYNTAX      Integer32
   MAX-ACCESS  read-write
   STATUS      current
   DESCRIPTION
      "Path: ethernet3.editConf.pppoEClient.ipV6.rs.maxSolicitations"
   ::= {er1645v2Lan3MCPppOEEntry 705954816}

er1645v2Lan3MCPppOEIpV6TrafficPolicyInbound OBJECT-TYPE
   SYNTAX      DisplayString
   MAX-ACCESS  read-write
   STATUS      current
   DESCRIPTION
      "Path: ethernet3.editConf.pppoEClient.ipV6.trafficPolicy.inbound"
   ::= {er1645v2Lan3MCPppOEEntry 705364224}

er1645v2Lan3MCPppOEIpV6TrafficPolicyOutbound OBJECT-TYPE
   SYNTAX      DisplayString
   MAX-ACCESS  read-write
   STATUS      current
   DESCRIPTION
      "Path: ethernet3.editConf.pppoEClient.ipV6.trafficPolicy.outbound"
   ::= {er1645v2Lan3MCPppOEEntry 705364480}

er1645v2Lan3MCPppOEIpV6FirewallZone OBJECT-TYPE
   SYNTAX      DisplayString
   MAX-ACCESS  read-write
   STATUS      current
   DESCRIPTION
      "Path: ethernet3.editConf.pppoEClient.ipV6.firewall.zone"
   ::= {er1645v2Lan3MCPppOEEntry 705429760}

er1645v2Lan3MCPppOEIpV6DhcpClientAddrAC OBJECT-TYPE
   SYNTAX      INTEGER
               {
               disabled (0),
               enabled (1)
               }
   MAX-ACCESS  read-write
   STATUS      current
   DESCRIPTION
      "Path: ethernet3.editConf.pppoEClient.ipV6.dhcp.client.addrAutoConfig

       Possibilities:
               disabled   (0)
               enabled   (1)"
   ::= {er1645v2Lan3MCPppOEEntry 705307648}

er1645v2Lan3MCPppOEIpV6DhcpClientPrDelMode OBJECT-TYPE
   SYNTAX      INTEGER
               {
               disabled (0),
               enabled (1)
               }
   MAX-ACCESS  read-write
   STATUS      current
   DESCRIPTION
      "Path: ethernet3.editConf.pppoEClient.ipV6.dhcp.client.pd.mode

       Possibilities:
               disabled   (0)
               enabled   (1)"
   ::= {er1645v2Lan3MCPppOEEntry 705308676}

er1645v2Lan3MCPppOEIpV6DhcpClientPrDelPool OBJECT-TYPE
   SYNTAX      DisplayString
   MAX-ACCESS  read-write
   STATUS      current
   DESCRIPTION
      "Path: ethernet3.editConf.pppoEClient.ipV6.dhcp.client.pd.pool"
   ::= {er1645v2Lan3MCPppOEEntry 705308680}

er1645v2Lan3MCPppOEIpV6DhcpClientPrDelPdExclOpt OBJECT-TYPE
   SYNTAX      INTEGER
               {
               disabled (0),
               enabled (1)
               }
   MAX-ACCESS  read-write
   STATUS      current
   DESCRIPTION
      "Path: ethernet3.editConf.pppoEClient.ipV6.dhcp.client.pd.pdExclOpt

       Possibilities:
               disabled   (0)
               enabled   (1)"
   ::= {er1645v2Lan3MCPppOEEntry 705308684}

er1645v2Lan3MCPppOEIpV6DhcpClientDnsServerPref OBJECT-TYPE
   SYNTAX      Integer32
   MAX-ACCESS  read-write
   STATUS      current
   DESCRIPTION
      "Path: ethernet3.editConf.pppoEClient.ipV6.dhcp.client.dns.serverPref"
   ::= {er1645v2Lan3MCPppOEEntry 705310724}

er1645v2Lan3MCPppOEIpV6DhcpClientRapidCommit OBJECT-TYPE
   SYNTAX      INTEGER
               {
               disabled (0),
               enabled (1)
               }
   MAX-ACCESS  read-write
   STATUS      current
   DESCRIPTION
      "Path: ethernet3.editConf.pppoEClient.ipV6.dhcp.client.rapidCommit

       Possibilities:
               disabled   (0)
               enabled   (1)"
   ::= {er1645v2Lan3MCPppOEEntry 705309696}

er1645v2Lan3MCPppOEIpV6DhcpClientTimersSolTimeOut OBJECT-TYPE
   SYNTAX      TimeTicks
   MAX-ACCESS  read-write
   STATUS      current
   DESCRIPTION
      "Path: ethernet3.editConf.pppoEClient.ipV6.dhcp.client.timers.solTimeOut

       Time in centi-second."
   ::= {er1645v2Lan3MCPppOEEntry 705311748}

er1645v2Lan3MCPppOEIpV6DhcpClientTimersSolMaxRt OBJECT-TYPE
   SYNTAX      TimeTicks
   MAX-ACCESS  read-write
   STATUS      current
   DESCRIPTION
      "Path: ethernet3.editConf.pppoEClient.ipV6.dhcp.client.timers.solMaxRt

       Time in centi-second."
   ::= {er1645v2Lan3MCPppOEEntry 705311752}

er1645v2Lan3MCPppOEIpV6DhcpClientTimersInfoRefresh OBJECT-TYPE
   SYNTAX      TimeTicks
   MAX-ACCESS  read-write
   STATUS      current
   DESCRIPTION
      "Path: ethernet3.editConf.pppoEClient.ipV6.dhcp.client.timers.infoRefresh

       Time in centi-second."
   ::= {er1645v2Lan3MCPppOEEntry 705311756}

er1645v2Lan3MCPppOEIpV6DhcpServerMode OBJECT-TYPE
   SYNTAX      INTEGER
               {
               disabled (0),
               enabled (1)
               }
   MAX-ACCESS  read-write
   STATUS      current
   DESCRIPTION
      "Path: ethernet3.editConf.pppoEClient.ipV6.dhcp.server.mode

       Possibilities:
               disabled   (0)
               enabled   (1)"
   ::= {er1645v2Lan3MCPppOEEntry 705315840}

er1645v2Lan3MCPppOEIpV6DhcpServerPreference OBJECT-TYPE
   SYNTAX      Integer32
   MAX-ACCESS  read-write
   STATUS      current
   DESCRIPTION
      "Path: ethernet3.editConf.pppoEClient.ipV6.dhcp.server.preference"
   ::= {er1645v2Lan3MCPppOEEntry 705316864}

er1645v2Lan3MCPppOEIpV6DhcpServerPool OBJECT-TYPE
   SYNTAX      DisplayString
   MAX-ACCESS  read-write
   STATUS      current
   DESCRIPTION
      "Path: ethernet3.editConf.pppoEClient.ipV6.dhcp.server.pool"
   ::= {er1645v2Lan3MCPppOEEntry 705317888}

er1645v2Lan3MCPppOEIpV6DhcpServerRapidCommit OBJECT-TYPE
   SYNTAX      INTEGER
               {
               disabled (0),
               enabled (1)
               }
   MAX-ACCESS  read-write
   STATUS      current
   DESCRIPTION
      "Path: ethernet3.editConf.pppoEClient.ipV6.dhcp.server.rapidCommit

       Possibilities:
               disabled   (0)
               enabled   (1)"
   ::= {er1645v2Lan3MCPppOEEntry 705318912}

er1645v2Lan3MCPppOEIpV6DhcpServerTimersInfoRefresh OBJECT-TYPE
   SYNTAX      TimeTicks
   MAX-ACCESS  read-write
   STATUS      current
   DESCRIPTION
      "Path: ethernet3.editConf.pppoEClient.ipV6.dhcp.server.timers.infoRefresh

       Time in centi-second."
   ::= {er1645v2Lan3MCPppOEEntry 705319940}

er1645v2Lan3MCPppOEIpV6DhcpRelayMode OBJECT-TYPE
   SYNTAX      INTEGER
               {
               disabled (0),
               enabled (1)
               }
   MAX-ACCESS  read-write
   STATUS      current
   DESCRIPTION
      "Path: ethernet3.editConf.pppoEClient.ipV6.dhcp.relay.mode

       Possibilities:
               disabled   (0)
               enabled   (1)"
   ::= {er1645v2Lan3MCPppOEEntry 705323040}

er1645v2Lan3MCPppOEIpV6SendRedirect OBJECT-TYPE
   SYNTAX      INTEGER
               {
               disabled (0),
               enabled (1)
               }
   MAX-ACCESS  read-write
   STATUS      current
   DESCRIPTION
      "Path: ethernet3.editConf.pppoEClient.ipV6.sendRedirect

       Possibilities:
               disabled   (0)
               enabled   (1)"
   ::= {er1645v2Lan3MCPppOEEntry 705101824}

er1645v2Lan3MCPppOEIpV6LinkMtu OBJECT-TYPE
   SYNTAX      Integer32
   MAX-ACCESS  read-write
   STATUS      current
   DESCRIPTION
      "Path: ethernet3.editConf.pppoEClient.ipV6.linkMtu"
   ::= {er1645v2Lan3MCPppOEEntry 705167360}

er1645v2Lan3MCPppOEIpV6InterfaceId OBJECT-TYPE
   SYNTAX      OCTET STRING
   MAX-ACCESS  read-write
   STATUS      current
   DESCRIPTION
      "Path: ethernet3.editConf.pppoEClient.ipV6.interfaceId"
   ::= {er1645v2Lan3MCPppOEEntry 705232896}

er1645v2Lan3MCPppOEIpV6MF OBJECT-TYPE
   SYNTAX      Integer32
   MAX-ACCESS  read-write
   STATUS      current
   DESCRIPTION
      "Path: ethernet3.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan3MCPppOEEntry 705757184}

er1645v2Lan3MCPppOEIpV6IcmpMessagesNoRoute OBJECT-TYPE
   SYNTAX      INTEGER
               {
               disabled (0),
               enabled (1)
               }
   MAX-ACCESS  read-write
   STATUS      current
   DESCRIPTION
      "Path: ethernet3.editConf.pppoEClient.ipV6.icmpMessages.noRoute

       Possibilities:
               disabled   (0)
               enabled   (1)"
   ::= {er1645v2Lan3MCPppOEEntry 705822976}

er1645v2Lan3MCPppOEIpV6IcmpMessagesBeyondScope OBJECT-TYPE
   SYNTAX      INTEGER
               {
               disabled (0),
               enabled (1)
               }
   MAX-ACCESS  read-write
   STATUS      current
   DESCRIPTION
      "Path: ethernet3.editConf.pppoEClient.ipV6.icmpMessages.beyondScope

       Possibilities:
               disabled   (0)
               enabled   (1)"
   ::= {er1645v2Lan3MCPppOEEntry 705823488}

er1645v2Lan3MCPppOEIpV6IcmpMessagesAddressUnreachable OBJECT-TYPE
   SYNTAX      INTEGER
               {
               disabled (0),
               enabled (1)
               }
   MAX-ACCESS  read-write
   STATUS      current
   DESCRIPTION
      "Path: ethernet3.editConf.pppoEClient.ipV6.icmpMessages.addressUnreachable

       Possibilities:
               disabled   (0)
               enabled   (1)"
   ::= {er1645v2Lan3MCPppOEEntry 705823744}

er1645v2Lan3MCPppOEIpV6IcmpMessagesPortUnreachable OBJECT-TYPE
   SYNTAX      INTEGER
               {
               disabled (0),
               enabled (1)
               }
   MAX-ACCESS  read-write
   STATUS      current
   DESCRIPTION
      "Path: ethernet3.editConf.pppoEClient.ipV6.icmpMessages.portUnreachable

       Possibilities:
               disabled   (0)
               enabled   (1)"
   ::= {er1645v2Lan3MCPppOEEntry 705824000}

er1645v2Lan3MCPppOEIpV6IcmpMessagesPacketTooBig OBJECT-TYPE
   SYNTAX      INTEGER
               {
               disabled (0),
               enabled (1)
               }
   MAX-ACCESS  read-write
   STATUS      current
   DESCRIPTION
      "Path: ethernet3.editConf.pppoEClient.ipV6.icmpMessages.packetTooBig

       Possibilities:
               disabled   (0)
               enabled   (1)"
   ::= {er1645v2Lan3MCPppOEEntry 705825280}

er1645v2Lan3MCPppOEIpV6IcmpMessagesHopLimitExceeded OBJECT-TYPE
   SYNTAX      INTEGER
               {
               disabled (0),
               enabled (1)
               }
   MAX-ACCESS  read-write
   STATUS      current
   DESCRIPTION
      "Path: ethernet3.editConf.pppoEClient.ipV6.icmpMessages.hopLimitExceeded

       Possibilities:
               disabled   (0)
               enabled   (1)"
   ::= {er1645v2Lan3MCPppOEEntry 705827840}

er1645v2Lan3MCPppOEIpV6IcmpMessagesFragTimeExceeded OBJECT-TYPE
   SYNTAX      INTEGER
               {
               disabled (0),
               enabled (1)
               }
   MAX-ACCESS  read-write
   STATUS      current
   DESCRIPTION
      "Path: ethernet3.editConf.pppoEClient.ipV6.icmpMessages.fragTimeExceeded

       Possibilities:
               disabled   (0)
               enabled   (1)"
   ::= {er1645v2Lan3MCPppOEEntry 705828096}

er1645v2Lan3MCPppOEIpV6IcmpMessagesHeaderFieldErr OBJECT-TYPE
   SYNTAX      INTEGER
               {
               disabled (0),
               enabled (1)
               }
   MAX-ACCESS  read-write
   STATUS      current
   DESCRIPTION
      "Path: ethernet3.editConf.pppoEClient.ipV6.icmpMessages.headerFieldErr

       Possibilities:
               disabled   (0)
               enabled   (1)"
   ::= {er1645v2Lan3MCPppOEEntry 705830400}

er1645v2Lan3MCPppOEIpV6IcmpMessagesOptionUnrecognized OBJECT-TYPE
   SYNTAX      INTEGER
               {
               disabled (0),
               enabled (1)
               }
   MAX-ACCESS  read-write
   STATUS      current
   DESCRIPTION
      "Path: ethernet3.editConf.pppoEClient.ipV6.icmpMessages.optionUnrecognized

       Possibilities:
               disabled   (0)
               enabled   (1)"
   ::= {er1645v2Lan3MCPppOEEntry 705830912}

er1645v2Lan3MCPppOEIpV6IcmpMessagesRedirect OBJECT-TYPE
   SYNTAX      INTEGER
               {
               disabled (0),
               enabled (1)
               }
   MAX-ACCESS  read-write
   STATUS      current
   DESCRIPTION
      "Path: ethernet3.editConf.pppoEClient.ipV6.icmpMessages.redirect

       Possibilities:
               disabled   (0)
               enabled   (1)"
   ::= {er1645v2Lan3MCPppOEEntry 705832960}

er1645v2Lan3MCPppOEPppLnkMOperation OBJECT-TYPE
   SYNTAX      INTEGER
               {
               disabled (0),
               enabled (1)
               }
   MAX-ACCESS  read-write
   STATUS      current
   DESCRIPTION
      "Path: ethernet3.editConf.pppoEClient.ppp.linkMonitoring.operation

       Possibilities:
               disabled   (0)
               enabled   (1)"
   ::= {er1645v2Lan3MCPppOEEntry 251724032}

er1645v2Lan3MCPppOEPppLnkMInterval OBJECT-TYPE
   SYNTAX      TimeTicks
   MAX-ACCESS  read-write
   STATUS      current
   DESCRIPTION
      "Path: ethernet3.editConf.pppoEClient.ppp.linkMonitoring.interval

       Time in centi-second."
   ::= {er1645v2Lan3MCPppOEEntry 251724288}

er1645v2Lan3MCPppOEPppLnkMRepTimeOut OBJECT-TYPE
   SYNTAX      TimeTicks
   MAX-ACCESS  read-write
   STATUS      current
   DESCRIPTION
      "Path: ethernet3.editConf.pppoEClient.ppp.linkMonitoring.replyTimeOut

       Time in centi-second."
   ::= {er1645v2Lan3MCPppOEEntry 251724544}

er1645v2Lan3MCPppOEPppLnkMFailsPrmt OBJECT-TYPE
   SYNTAX      Integer32
   MAX-ACCESS  read-write
   STATUS      current
   DESCRIPTION
      "Path: ethernet3.editConf.pppoEClient.ppp.linkMonitoring.failsPermitted"
   ::= {er1645v2Lan3MCPppOEEntry 251724800}

er1645v2Lan3MCPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.pppoEClient.ppp.authentication

       Possibilities:
               disabled   (0)
               chap   (1)
               pap   (2)
               chapOrPap   (3)
               msChap   (4)
               msChapV2   (5)"
   ::= {er1645v2Lan3MCPppOEEntry 251789312}

er1645v2Lan3MCPppOEPppAuthenPeriod OBJECT-TYPE
   SYNTAX      TimeTicks
   MAX-ACCESS  read-write
   STATUS      current
   DESCRIPTION
      "Path: ethernet3.editConf.pppoEClient.ppp.authenPeriod

       Time in centi-second."
   ::= {er1645v2Lan3MCPppOEEntry 251854848}

er1645v2Lan3MCPppOEPppSessionName OBJECT-TYPE
   SYNTAX      DisplayString
   MAX-ACCESS  read-write
   STATUS      current
   DESCRIPTION
      "Path: ethernet3.editConf.pppoEClient.ppp.sessionName"
   ::= {er1645v2Lan3MCPppOEEntry 251985920}

er1645v2Lan3MCPppOEPppSessionSecret OBJECT-TYPE
   SYNTAX      DisplayString
   MAX-ACCESS  read-write
   STATUS      current
   DESCRIPTION
      "Path: ethernet3.editConf.pppoEClient.ppp.sessionSecret"
   ::= {er1645v2Lan3MCPppOEEntry 252051456}

er1645v2Lan3MCPppOEPppEncModeSessionSecret OBJECT-TYPE
   SYNTAX      INTEGER
               {
               none (1),
               encrypt (2),
               encType1 (3),
               invalid (128)
               }
   MAX-ACCESS  read-write
   STATUS      current
   DESCRIPTION
      "Path: ethernet3.editConf.pppoEClient.ppp.encModeSessionSecret

       Possibilities:
               none   (1)
               encrypt   (2)
               encType1   (3)
               invalid   (128)"
   ::= {er1645v2Lan3MCPppOEEntry 252182528}

er1645v2Lan3MCPppOEPppEncSessionSecret OBJECT-TYPE
   SYNTAX      DisplayString
   MAX-ACCESS  read-write
   STATUS      current
   DESCRIPTION
      "Path: ethernet3.editConf.pppoEClient.ppp.encSessionSecret"
   ::= {er1645v2Lan3MCPppOEEntry 252248064}

er1645v2Lan3MCPppOEPppServiceName OBJECT-TYPE
   SYNTAX      DisplayString
   MAX-ACCESS  read-write
   STATUS      current
   DESCRIPTION
      "Path: ethernet3.editConf.pppoEClient.ppp.serviceName"
   ::= {er1645v2Lan3MCPppOEEntry 252116992}

er1645v2Lan3MCPppOEIpH OBJECT-TYPE
   SYNTAX      SEQUENCE OF Er1645v2Lan3MCPppOEIpHEntry
   MAX-ACCESS  not-accessible
   STATUS      current
   DESCRIPTION
      ""
   ::= {er1645v2Lan3MCPppOE 51314688}

er1645v2Lan3MCPppOEIpHEntry OBJECT-TYPE
   SYNTAX      Er1645v2Lan3MCPppOEIpHEntry
   MAX-ACCESS  not-accessible
   STATUS      current
   DESCRIPTION
      ""
   INDEX      { er1645v2Lan3MCPppOETableIx,
                er1645v2Lan3MCPppOEIpHTableIx }
   ::= {er1645v2Lan3MCPppOEIpH 1}

Er1645v2Lan3MCPppOEIpHEntry ::=
   SEQUENCE
      {
      er1645v2Lan3MCPppOEIpHActions
         VariableLengthTableActions,
      er1645v2Lan3MCPppOEIpHTableIx
         TableIndex,
      er1645v2Lan3MCPppOEIpHAddress
         IpAddress,
      er1645v2Lan3MCPppOEIpHDhcpRelayOptionSubscriberId
         DisplayString
      }

er1645v2Lan3MCPppOEIpHActions OBJECT-TYPE
   SYNTAX      VariableLengthTableActions
   MAX-ACCESS  read-write
   STATUS      current
   DESCRIPTION
      "By way of this field, some manipulations
       on this table may be performed."
   ::= {er1645v2Lan3MCPppOEIpHEntry 2}

er1645v2Lan3MCPppOEIpHTableIx OBJECT-TYPE
   SYNTAX      TableIndex
   MAX-ACCESS  not-accessible
   STATUS      current
   DESCRIPTION
      ""
   ::= {er1645v2Lan3MCPppOEIpHEntry 11}

er1645v2Lan3MCPppOEIpHAddress OBJECT-TYPE
   SYNTAX      IpAddress
   MAX-ACCESS  read-write
   STATUS      current
   DESCRIPTION
      "Path: ethernet3.editConf.pppoEClient.ip.helpers.address"
   ::= {er1645v2Lan3MCPppOEIpHEntry 16777216}

er1645v2Lan3MCPppOEIpHDhcpRelayOptionSubscriberId OBJECT-TYPE
   SYNTAX      DisplayString
   MAX-ACCESS  read-write
   STATUS      current
   DESCRIPTION
      "Path: ethernet3.editConf.pppoEClient.ip.helpers.dhcpRelayOption.subscriberId"
   ::= {er1645v2Lan3MCPppOEIpHEntry 33947648}

er1645v2Lan3MCPppOEIpV6Addresses OBJECT-TYPE
   SYNTAX      SEQUENCE OF Er1645v2Lan3MCPppOEIpV6AddressesEntry
   MAX-ACCESS  not-accessible
   STATUS      current
   DESCRIPTION
      ""
   ::= {er1645v2Lan3MCPppOE 704839680}

er1645v2Lan3MCPppOEIpV6AddressesEntry OBJECT-TYPE
   SYNTAX      Er1645v2Lan3MCPppOEIpV6AddressesEntry
   MAX-ACCESS  not-accessible
   STATUS      current
   DESCRIPTION
      ""
   INDEX      { er1645v2Lan3MCPppOETableIx,
                er1645v2Lan3MCPppOEIpV6AddressesTableIx }
   ::= {er1645v2Lan3MCPppOEIpV6Addresses 1}

Er1645v2Lan3MCPppOEIpV6AddressesEntry ::=
   SEQUENCE
      {
      er1645v2Lan3MCPppOEIpV6AddressesActions
         VariableLengthTableActions,
      er1645v2Lan3MCPppOEIpV6AddressesTableIx
         TableIndex,
      er1645v2Lan3MCPppOEIpV6AddressesType
         INTEGER,
      er1645v2Lan3MCPppOEIpV6AddressesAddress
         Ipv6Address,
      er1645v2Lan3MCPppOEIpV6AddressesPrefixLength
         Integer32,
      er1645v2Lan3MCPppOEIpV6AddressesGeneralPrefix
         DisplayString,
      er1645v2Lan3MCPppOEIpV6AddressesRaSend
         INTEGER,
      er1645v2Lan3MCPppOEIpV6AddressesRaOnLinkFlag
         INTEGER,
      er1645v2Lan3MCPppOEIpV6AddressesRaAutoFlag
         INTEGER,
      er1645v2Lan3MCPppOEIpV6AddressesRaValidLifeTime
         TimeTicks,
      er1645v2Lan3MCPppOEIpV6AddressesRaValidLTMode
         INTEGER,
      er1645v2Lan3MCPppOEIpV6AddressesRaPrefLifeTime
         TimeTicks,
      er1645v2Lan3MCPppOEIpV6AddressesRaPrefLTMode
         INTEGER
      }

er1645v2Lan3MCPppOEIpV6AddressesActions OBJECT-TYPE
   SYNTAX      VariableLengthTableActions
   MAX-ACCESS  read-write
   STATUS      current
   DESCRIPTION
      "By way of this field, some manipulations
       on this table may be performed."
   ::= {er1645v2Lan3MCPppOEIpV6AddressesEntry 2}

er1645v2Lan3MCPppOEIpV6AddressesTableIx OBJECT-TYPE
   SYNTAX      TableIndex
   MAX-ACCESS  not-accessible
   STATUS      current
   DESCRIPTION
      ""
   ::= {er1645v2Lan3MCPppOEIpV6AddressesEntry 11}

er1645v2Lan3MCPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.pppoEClient.ipV6.addresses.type

       Possibilities:
               unicast   (0)
               eui64   (1)
               anycast   (2)
               linkLocal   (3)
               generalPrefix   (4)"
   ::= {er1645v2Lan3MCPppOEIpV6AddressesEntry 50331648}

er1645v2Lan3MCPppOEIpV6AddressesAddress OBJECT-TYPE
   SYNTAX      Ipv6Address
   MAX-ACCESS  read-write
   STATUS      current
   DESCRIPTION
      "Path: ethernet3.editConf.pppoEClient.ipV6.addresses.address

       ipv6 address"
   ::= {er1645v2Lan3MCPppOEIpV6AddressesEntry 16777216}

er1645v2Lan3MCPppOEIpV6AddressesPrefixLength OBJECT-TYPE
   SYNTAX      Integer32
   MAX-ACCESS  read-write
   STATUS      current
   DESCRIPTION
      "Path: ethernet3.editConf.pppoEClient.ipV6.addresses.prefixLength"
   ::= {er1645v2Lan3MCPppOEIpV6AddressesEntry 33554432}

er1645v2Lan3MCPppOEIpV6AddressesGeneralPrefix OBJECT-TYPE
   SYNTAX      DisplayString
   MAX-ACCESS  read-write
   STATUS      current
   DESCRIPTION
      "Path: ethernet3.editConf.pppoEClient.ipV6.addresses.generalPrefix"
   ::= {er1645v2Lan3MCPppOEIpV6AddressesEntry 83886080}

er1645v2Lan3MCPppOEIpV6AddressesRaSend OBJECT-TYPE
   SYNTAX      INTEGER
               {
               disabled (0),
               enabled (1)
               }
   MAX-ACCESS  read-write
   STATUS      current
   DESCRIPTION
      "Path: ethernet3.editConf.pppoEClient.ipV6.addresses.ra.send

       Possibilities:
               disabled   (0)
               enabled   (1)"
   ::= {er1645v2Lan3MCPppOEIpV6AddressesEntry 67174400}

er1645v2Lan3MCPppOEIpV6AddressesRaOnLinkFlag OBJECT-TYPE
   SYNTAX      INTEGER
               {
               disabled (0),
               enabled (1)
               }
   MAX-ACCESS  read-write
   STATUS      current
   DESCRIPTION
      "Path: ethernet3.editConf.pppoEClient.ipV6.addresses.ra.onLinkFlag

       Possibilities:
               disabled   (0)
               enabled   (1)"
   ::= {er1645v2Lan3MCPppOEIpV6AddressesEntry 67371008}

er1645v2Lan3MCPppOEIpV6AddressesRaAutoFlag OBJECT-TYPE
   SYNTAX      INTEGER
               {
               disabled (0),
               enabled (1)
               }
   MAX-ACCESS  read-write
   STATUS      current
   DESCRIPTION
      "Path: ethernet3.editConf.pppoEClient.ipV6.addresses.ra.autonomousFlag

       Possibilities:
               disabled   (0)
               enabled   (1)"
   ::= {er1645v2Lan3MCPppOEIpV6AddressesEntry 67567616}

er1645v2Lan3MCPppOEIpV6AddressesRaValidLifeTime OBJECT-TYPE
   SYNTAX      TimeTicks
   MAX-ACCESS  read-write
   STATUS      current
   DESCRIPTION
      "Path: ethernet3.editConf.pppoEClient.ipV6.addresses.ra.validLifeTime

       Time in centi-second."
   ::= {er1645v2Lan3MCPppOEIpV6AddressesEntry 67239936}

er1645v2Lan3MCPppOEIpV6AddressesRaValidLTMode OBJECT-TYPE
   SYNTAX      INTEGER
               {
               fixed (0),
               infinite (2)
               }
   MAX-ACCESS  read-write
   STATUS      current
   DESCRIPTION
      "Path: ethernet3.editConf.pppoEClient.ipV6.addresses.ra.validLifeTimeMode

       Possibilities:
               fixed   (0)
               infinite   (2)"
   ::= {er1645v2Lan3MCPppOEIpV6AddressesEntry 67305472}

er1645v2Lan3MCPppOEIpV6AddressesRaPrefLifeTime OBJECT-TYPE
   SYNTAX      TimeTicks
   MAX-ACCESS  read-write
   STATUS      current
   DESCRIPTION
      "Path: ethernet3.editConf.pppoEClient.ipV6.addresses.ra.prefLifeTime

       Time in centi-second."
   ::= {er1645v2Lan3MCPppOEIpV6AddressesEntry 67436544}

er1645v2Lan3MCPppOEIpV6AddressesRaPrefLTMode OBJECT-TYPE
   SYNTAX      INTEGER
               {
               fixed (0),
               infinite (2)
               }
   MAX-ACCESS  read-write
   STATUS      current
   DESCRIPTION
      "Path: ethernet3.editConf.pppoEClient.ipV6.addresses.ra.prefLifeTimeMode

       Possibilities:
               fixed   (0)
               infinite   (2)"
   ::= {er1645v2Lan3MCPppOEIpV6AddressesEntry 67502080}

er1645v2Lan3MCPppOEIpV6RaDnsOptionsRdnssServers OBJECT-TYPE
   SYNTAX      SEQUENCE OF Er1645v2Lan3MCPppOEIpV6RaDnsOptionsRdnssServersEntry
   MAX-ACCESS  not-accessible
   STATUS      current
   DESCRIPTION
      ""
   ::= {er1645v2Lan3MCPppOE 705039144}

er1645v2Lan3MCPppOEIpV6RaDnsOptionsRdnssServersEntry OBJECT-TYPE
   SYNTAX      Er1645v2Lan3MCPppOEIpV6RaDnsOptionsRdnssServersEntry
   MAX-ACCESS  not-accessible
   STATUS      current
   DESCRIPTION
      ""
   INDEX      { er1645v2Lan3MCPppOETableIx,
                er1645v2Lan3MCPppOEIpV6RaDnsOptionsRdnssServersTableIx }
   ::= {er1645v2Lan3MCPppOEIpV6RaDnsOptionsRdnssServers 1}

Er1645v2Lan3MCPppOEIpV6RaDnsOptionsRdnssServersEntry ::=
   SEQUENCE
      {
      er1645v2Lan3MCPppOEIpV6RaDnsOptionsRdnssServersActions
         VariableLengthTableActions,
      er1645v2Lan3MCPppOEIpV6RaDnsOptionsRdnssServersTableIx
         TableIndex,
      er1645v2Lan3MCPppOEIpV6RaDnsOptionsRdnssServersAddress
         Ipv6Address
      }

er1645v2Lan3MCPppOEIpV6RaDnsOptionsRdnssServersActions OBJECT-TYPE
   SYNTAX      VariableLengthTableActions
   MAX-ACCESS  read-write
   STATUS      current
   DESCRIPTION
      "By way of this field, some manipulations
       on this table may be performed."
   ::= {er1645v2Lan3MCPppOEIpV6RaDnsOptionsRdnssServersEntry 2}

er1645v2Lan3MCPppOEIpV6RaDnsOptionsRdnssServersTableIx OBJECT-TYPE
   SYNTAX      TableIndex
   MAX-ACCESS  not-accessible
   STATUS      current
   DESCRIPTION
      ""
   ::= {er1645v2Lan3MCPppOEIpV6RaDnsOptionsRdnssServersEntry 11}

er1645v2Lan3MCPppOEIpV6RaDnsOptionsRdnssServersAddress OBJECT-TYPE
   SYNTAX      Ipv6Address
   MAX-ACCESS  read-write
   STATUS      current
   DESCRIPTION
      "Path: ethernet3.editConf.pppoEClient.ipV6.ra.dnsOptions.rdnss.servers.address

       ipv6 address"
   ::= {er1645v2Lan3MCPppOEIpV6RaDnsOptionsRdnssServersEntry 16777216}

er1645v2Lan3MCPppOEIpV6RaDnsOptionsDnsslDomains OBJECT-TYPE
   SYNTAX      SEQUENCE OF Er1645v2Lan3MCPppOEIpV6RaDnsOptionsDnsslDomainsEntry
   MAX-ACCESS  not-accessible
   STATUS      current
   DESCRIPTION
      ""
   ::= {er1645v2Lan3MCPppOE 705039176}

er1645v2Lan3MCPppOEIpV6RaDnsOptionsDnsslDomainsEntry OBJECT-TYPE
   SYNTAX      Er1645v2Lan3MCPppOEIpV6RaDnsOptionsDnsslDomainsEntry
   MAX-ACCESS  not-accessible
   STATUS      current
   DESCRIPTION
      ""
   INDEX      { er1645v2Lan3MCPppOETableIx,
                er1645v2Lan3MCPppOEIpV6RaDnsOptionsDnsslDomainsTableIx }
   ::= {er1645v2Lan3MCPppOEIpV6RaDnsOptionsDnsslDomains 1}

Er1645v2Lan3MCPppOEIpV6RaDnsOptionsDnsslDomainsEntry ::=
   SEQUENCE
      {
      er1645v2Lan3MCPppOEIpV6RaDnsOptionsDnsslDomainsActions
         VariableLengthTableActions,
      er1645v2Lan3MCPppOEIpV6RaDnsOptionsDnsslDomainsTableIx
         TableIndex,
      er1645v2Lan3MCPppOEIpV6RaDnsOptionsDnsslDomainsName
         DisplayString
      }

er1645v2Lan3MCPppOEIpV6RaDnsOptionsDnsslDomainsActions OBJECT-TYPE
   SYNTAX      VariableLengthTableActions
   MAX-ACCESS  read-write
   STATUS      current
   DESCRIPTION
      "By way of this field, some manipulations
       on this table may be performed."
   ::= {er1645v2Lan3MCPppOEIpV6RaDnsOptionsDnsslDomainsEntry 2}

er1645v2Lan3MCPppOEIpV6RaDnsOptionsDnsslDomainsTableIx OBJECT-TYPE
   SYNTAX      TableIndex
   MAX-ACCESS  not-accessible
   STATUS      current
   DESCRIPTION
      ""
   ::= {er1645v2Lan3MCPppOEIpV6RaDnsOptionsDnsslDomainsEntry 11}

er1645v2Lan3MCPppOEIpV6RaDnsOptionsDnsslDomainsName OBJECT-TYPE
   SYNTAX      DisplayString
   MAX-ACCESS  read-write
   STATUS      current
   DESCRIPTION
      "Path: ethernet3.editConf.pppoEClient.ipV6.ra.dnsOptions.dnssl.domains.name"
   ::= {er1645v2Lan3MCPppOEIpV6RaDnsOptionsDnsslDomainsEntry 16777216}

er1645v2Lan3MCPppOEIpV6DhcpClientUserClassOpt OBJECT-TYPE
   SYNTAX      SEQUENCE OF Er1645v2Lan3MCPppOEIpV6DhcpClientUserClassOptEntry
   MAX-ACCESS  not-accessible
   STATUS      current
   DESCRIPTION
      ""
   ::= {er1645v2Lan3MCPppOE 705312768}

er1645v2Lan3MCPppOEIpV6DhcpClientUserClassOptEntry OBJECT-TYPE
   SYNTAX      Er1645v2Lan3MCPppOEIpV6DhcpClientUserClassOptEntry
   MAX-ACCESS  not-accessible
   STATUS      current
   DESCRIPTION
      ""
   INDEX      { er1645v2Lan3MCPppOETableIx,
                er1645v2Lan3MCPppOEIpV6DhcpClientUserClassOptTableIx }
   ::= {er1645v2Lan3MCPppOEIpV6DhcpClientUserClassOpt 1}

Er1645v2Lan3MCPppOEIpV6DhcpClientUserClassOptEntry ::=
   SEQUENCE
      {
      er1645v2Lan3MCPppOEIpV6DhcpClientUserClassOptActions
         VariableLengthTableActions,
      er1645v2Lan3MCPppOEIpV6DhcpClientUserClassOptTableIx
         TableIndex,
      er1645v2Lan3MCPppOEIpV6DhcpClientUserClassOptValueAscii
         DisplayString,
      er1645v2Lan3MCPppOEIpV6DhcpClientUserClassOptValueDecimal
         Integer32,
      er1645v2Lan3MCPppOEIpV6DhcpClientUserClassOptValueHexData
         OCTET STRING
      }

er1645v2Lan3MCPppOEIpV6DhcpClientUserClassOptActions OBJECT-TYPE
   SYNTAX      VariableLengthTableActions
   MAX-ACCESS  read-write
   STATUS      current
   DESCRIPTION
      "By way of this field, some manipulations
       on this table may be performed."
   ::= {er1645v2Lan3MCPppOEIpV6DhcpClientUserClassOptEntry 2}

er1645v2Lan3MCPppOEIpV6DhcpClientUserClassOptTableIx OBJECT-TYPE
   SYNTAX      TableIndex
   MAX-ACCESS  not-accessible
   STATUS      current
   DESCRIPTION
      ""
   ::= {er1645v2Lan3MCPppOEIpV6DhcpClientUserClassOptEntry 11}

er1645v2Lan3MCPppOEIpV6DhcpClientUserClassOptValueAscii OBJECT-TYPE
   SYNTAX      DisplayString
   MAX-ACCESS  read-write
   STATUS      current
   DESCRIPTION
      "Path: ethernet3.editConf.pppoEClient.ipV6.dhcp.client.userClassOpt.value.ascii"
   ::= {er1645v2Lan3MCPppOEIpV6DhcpClientUserClassOptEntry 16842752}

er1645v2Lan3MCPppOEIpV6DhcpClientUserClassOptValueDecimal OBJECT-TYPE
   SYNTAX      Integer32
   MAX-ACCESS  read-write
   STATUS      current
   DESCRIPTION
      "Path: ethernet3.editConf.pppoEClient.ipV6.dhcp.client.userClassOpt.value.decimal"
   ::= {er1645v2Lan3MCPppOEIpV6DhcpClientUserClassOptEntry 16908288}

er1645v2Lan3MCPppOEIpV6DhcpClientUserClassOptValueHexData OBJECT-TYPE
   SYNTAX      OCTET STRING
   MAX-ACCESS  read-write
   STATUS      current
   DESCRIPTION
      "Path: ethernet3.editConf.pppoEClient.ipV6.dhcp.client.userClassOpt.value.hexData"
   ::= {er1645v2Lan3MCPppOEIpV6DhcpClientUserClassOptEntry 16973824}

er1645v2Lan3MCPppOEIpV6DhcpClientVendorCl OBJECT-TYPE
   SYNTAX      SEQUENCE OF Er1645v2Lan3MCPppOEIpV6DhcpClientVendorClEntry
   MAX-ACCESS  not-accessible
   STATUS      current
   DESCRIPTION
      ""
   ::= {er1645v2Lan3MCPppOE 705313792}

er1645v2Lan3MCPppOEIpV6DhcpClientVendorClEntry OBJECT-TYPE
   SYNTAX      Er1645v2Lan3MCPppOEIpV6DhcpClientVendorClEntry
   MAX-ACCESS  not-accessible
   STATUS      current
   DESCRIPTION
      ""
   INDEX      { er1645v2Lan3MCPppOETableIx,
                er1645v2Lan3MCPppOEIpV6DhcpClientVendorClTableIx }
   ::= {er1645v2Lan3MCPppOEIpV6DhcpClientVendorCl 1}

Er1645v2Lan3MCPppOEIpV6DhcpClientVendorClEntry ::=
   SEQUENCE
      {
      er1645v2Lan3MCPppOEIpV6DhcpClientVendorClActions
         VariableLengthTableActions,
      er1645v2Lan3MCPppOEIpV6DhcpClientVendorClTableIx
         TableIndex,
      er1645v2Lan3MCPppOEIpV6DhcpClientVendorClValueAscii
         DisplayString,
      er1645v2Lan3MCPppOEIpV6DhcpClientVendorClValueDecimal
         Integer32,
      er1645v2Lan3MCPppOEIpV6DhcpClientVendorClValueHexData
         OCTET STRING
      }

er1645v2Lan3MCPppOEIpV6DhcpClientVendorClActions OBJECT-TYPE
   SYNTAX      VariableLengthTableActions
   MAX-ACCESS  read-write
   STATUS      current
   DESCRIPTION
      "By way of this field, some manipulations
       on this table may be performed."
   ::= {er1645v2Lan3MCPppOEIpV6DhcpClientVendorClEntry 2}

er1645v2Lan3MCPppOEIpV6DhcpClientVendorClTableIx OBJECT-TYPE
   SYNTAX      TableIndex
   MAX-ACCESS  not-accessible
   STATUS      current
   DESCRIPTION
      ""
   ::= {er1645v2Lan3MCPppOEIpV6DhcpClientVendorClEntry 11}

er1645v2Lan3MCPppOEIpV6DhcpClientVendorClValueAscii OBJECT-TYPE
   SYNTAX      DisplayString
   MAX-ACCESS  read-write
   STATUS      current
   DESCRIPTION
      "Path: ethernet3.editConf.pppoEClient.ipV6.dhcp.client.vendorClassOpt.value.ascii"
   ::= {er1645v2Lan3MCPppOEIpV6DhcpClientVendorClEntry 16842752}

er1645v2Lan3MCPppOEIpV6DhcpClientVendorClValueDecimal OBJECT-TYPE
   SYNTAX      Integer32
   MAX-ACCESS  read-write
   STATUS      current
   DESCRIPTION
      "Path: ethernet3.editConf.pppoEClient.ipV6.dhcp.client.vendorClassOpt.value.decimal"
   ::= {er1645v2Lan3MCPppOEIpV6DhcpClientVendorClEntry 16908288}

er1645v2Lan3MCPppOEIpV6DhcpClientVendorClValueHexData OBJECT-TYPE
   SYNTAX      OCTET STRING
   MAX-ACCESS  read-write
   STATUS      current
   DESCRIPTION
      "Path: ethernet3.editConf.pppoEClient.ipV6.dhcp.client.vendorClassOpt.value.hexData"
   ::= {er1645v2Lan3MCPppOEIpV6DhcpClientVendorClEntry 16973824}

er1645v2Lan3MCPppOEIpV6DhcpRelayDestinations OBJECT-TYPE
   SYNTAX      SEQUENCE OF Er1645v2Lan3MCPppOEIpV6DhcpRelayDestinationsEntry
   MAX-ACCESS  not-accessible
   STATUS      current
   DESCRIPTION
      ""
   ::= {er1645v2Lan3MCPppOE 705323072}

er1645v2Lan3MCPppOEIpV6DhcpRelayDestinationsEntry OBJECT-TYPE
   SYNTAX      Er1645v2Lan3MCPppOEIpV6DhcpRelayDestinationsEntry
   MAX-ACCESS  not-accessible
   STATUS      current
   DESCRIPTION
      ""
   INDEX      { er1645v2Lan3MCPppOETableIx,
                er1645v2Lan3MCPppOEIpV6DhcpRelayDestinationsTableIx }
   ::= {er1645v2Lan3MCPppOEIpV6DhcpRelayDestinations 1}

Er1645v2Lan3MCPppOEIpV6DhcpRelayDestinationsEntry ::=
   SEQUENCE
      {
      er1645v2Lan3MCPppOEIpV6DhcpRelayDestinationsActions
         VariableLengthTableActions,
      er1645v2Lan3MCPppOEIpV6DhcpRelayDestinationsTableIx
         TableIndex,
      er1645v2Lan3MCPppOEIpV6DhcpRelayDestinationsAddress
         Ipv6Address,
      er1645v2Lan3MCPppOEIpV6DhcpRelayDestinationsInterface
         DisplayString
      }

er1645v2Lan3MCPppOEIpV6DhcpRelayDestinationsActions OBJECT-TYPE
   SYNTAX      VariableLengthTableActions
   MAX-ACCESS  read-write
   STATUS      current
   DESCRIPTION
      "By way of this field, some manipulations
       on this table may be performed."
   ::= {er1645v2Lan3MCPppOEIpV6DhcpRelayDestinationsEntry 2}

er1645v2Lan3MCPppOEIpV6DhcpRelayDestinationsTableIx OBJECT-TYPE
   SYNTAX      TableIndex
   MAX-ACCESS  not-accessible
   STATUS      current
   DESCRIPTION
      ""
   ::= {er1645v2Lan3MCPppOEIpV6DhcpRelayDestinationsEntry 11}

er1645v2Lan3MCPppOEIpV6DhcpRelayDestinationsAddress OBJECT-TYPE
   SYNTAX      Ipv6Address
   MAX-ACCESS  read-write
   STATUS      current
   DESCRIPTION
      "Path: ethernet3.editConf.pppoEClient.ipV6.dhcp.relay.destinations.address

       ipv6 address"
   ::= {er1645v2Lan3MCPppOEIpV6DhcpRelayDestinationsEntry 16777216}

er1645v2Lan3MCPppOEIpV6DhcpRelayDestinationsInterface OBJECT-TYPE
   SYNTAX      DisplayString
   MAX-ACCESS  read-write
   STATUS      current
   DESCRIPTION
      "Path: ethernet3.editConf.pppoEClient.ipV6.dhcp.relay.destinations.interface"
   ::= {er1645v2Lan3MCPppOEIpV6DhcpRelayDestinationsEntry 33554432}


er1645v2Lan3MCPppoEServer OBJECT-TYPE
   SYNTAX      DisplayString
   MAX-ACCESS  read-write
   STATUS      current
   DESCRIPTION
      "Path: ethernet3.editConf.pppoEServer
       Info: ppp server name on interface"
   ::= {er1645v2Lan3MC 37}


er1645v2Lan3MCMediaType OBJECT-TYPE
   SYNTAX      INTEGER
               {
               utp (1),
               sfp (2),
               auto (3)
               }
   MAX-ACCESS  read-write
   STATUS      current
   DESCRIPTION
      "Path: ethernet3.editConf.mediaType

       Possibilities:
               utp   (1)
               sfp   (2)
               auto   (3)"
   ::= {er1645v2Lan3MC 38}


er1645v2Lan3MCInboundHwPriority OBJECT IDENTIFIER ::= {er1645v2Lan3MC 231}

er1645v2Lan3MCInboundHwPrioritySSC OBJECT IDENTIFIER ::= {er1645v2Lan3MCInboundHwPriority 1}

er1645v2Lan3MCInboundHwPriorityEntry OBJECT IDENTIFIER ::= {er1645v2Lan3MCInboundHwPrioritySSC 1}

er1645v2Lan3MCInboundHwPriorityNone OBJECT-TYPE
   SYNTAX      OCTET STRING
   MAX-ACCESS  read-write
   STATUS      current
   DESCRIPTION
      "Path: ethernet3.editConf.inboundHwPriority.none"
   ::= {er1645v2Lan3MCInboundHwPriorityEntry 16777216}

er1645v2Lan3MCInboundHwPriorityMapCosToQueueP0 OBJECT-TYPE
   SYNTAX      INTEGER
               {
               queue1 (1),
               queue2 (2)
               }
   MAX-ACCESS  read-write
   STATUS      current
   DESCRIPTION
      "Path: ethernet3.editConf.inboundHwPriority.mapCosToQueue.p0

       Possibilities:
               queue1   (1)
               queue2   (2)"
   ::= {er1645v2Lan3MCInboundHwPriorityEntry 33619968}

er1645v2Lan3MCInboundHwPriorityMapCosToQueueP1 OBJECT-TYPE
   SYNTAX      INTEGER
               {
               queue1 (1),
               queue2 (2)
               }
   MAX-ACCESS  read-write
   STATUS      current
   DESCRIPTION
      "Path: ethernet3.editConf.inboundHwPriority.mapCosToQueue.p1

       Possibilities:
               queue1   (1)
               queue2   (2)"
   ::= {er1645v2Lan3MCInboundHwPriorityEntry 33685504}

er1645v2Lan3MCInboundHwPriorityMapCosToQueueP2 OBJECT-TYPE
   SYNTAX      INTEGER
               {
               queue1 (1),
               queue2 (2)
               }
   MAX-ACCESS  read-write
   STATUS      current
   DESCRIPTION
      "Path: ethernet3.editConf.inboundHwPriority.mapCosToQueue.p2

       Possibilities:
               queue1   (1)
               queue2   (2)"
   ::= {er1645v2Lan3MCInboundHwPriorityEntry 33751040}

er1645v2Lan3MCInboundHwPriorityMapCosToQueueP3 OBJECT-TYPE
   SYNTAX      INTEGER
               {
               queue1 (1),
               queue2 (2)
               }
   MAX-ACCESS  read-write
   STATUS      current
   DESCRIPTION
      "Path: ethernet3.editConf.inboundHwPriority.mapCosToQueue.p3

       Possibilities:
               queue1   (1)
               queue2   (2)"
   ::= {er1645v2Lan3MCInboundHwPriorityEntry 33816576}

er1645v2Lan3MCInboundHwPriorityMapCosToQueueP4 OBJECT-TYPE
   SYNTAX      INTEGER
               {
               queue1 (1),
               queue2 (2)
               }
   MAX-ACCESS  read-write
   STATUS      current
   DESCRIPTION
      "Path: ethernet3.editConf.inboundHwPriority.mapCosToQueue.p4

       Possibilities:
               queue1   (1)
               queue2   (2)"
   ::= {er1645v2Lan3MCInboundHwPriorityEntry 33882112}

er1645v2Lan3MCInboundHwPriorityMapCosToQueueP5 OBJECT-TYPE
   SYNTAX      INTEGER
               {
               queue1 (1),
               queue2 (2)
               }
   MAX-ACCESS  read-write
   STATUS      current
   DESCRIPTION
      "Path: ethernet3.editConf.inboundHwPriority.mapCosToQueue.p5

       Possibilities:
               queue1   (1)
               queue2   (2)"
   ::= {er1645v2Lan3MCInboundHwPriorityEntry 33947648}

er1645v2Lan3MCInboundHwPriorityMapCosToQueueP6 OBJECT-TYPE
   SYNTAX      INTEGER
               {
               queue1 (1),
               queue2 (2)
               }
   MAX-ACCESS  read-write
   STATUS      current
   DESCRIPTION
      "Path: ethernet3.editConf.inboundHwPriority.mapCosToQueue.p6

       Possibilities:
               queue1   (1)
               queue2   (2)"
   ::= {er1645v2Lan3MCInboundHwPriorityEntry 34013184}

er1645v2Lan3MCInboundHwPriorityMapCosToQueueP7 OBJECT-TYPE
   SYNTAX      INTEGER
               {
               queue1 (1),
               queue2 (2)
               }
   MAX-ACCESS  read-write
   STATUS      current
   DESCRIPTION
      "Path: ethernet3.editConf.inboundHwPriority.mapCosToQueue.p7

       Possibilities:
               queue1   (1)
               queue2   (2)"
   ::= {er1645v2Lan3MCInboundHwPriorityEntry 34078720}

er1645v2Lan3MCInboundHwPriorityMapDscpToQueue OBJECT-TYPE
   SYNTAX      SEQUENCE OF Er1645v2Lan3MCInboundHwPriorityMapDscpToQueueEntry
   MAX-ACCESS  not-accessible
   STATUS      current
   DESCRIPTION
      ""
   ::= {er1645v2Lan3MCInboundHwPriority 50331648}

er1645v2Lan3MCInboundHwPriorityMapDscpToQueueEntry OBJECT-TYPE
   SYNTAX      Er1645v2Lan3MCInboundHwPriorityMapDscpToQueueEntry
   MAX-ACCESS  not-accessible
   STATUS      current
   DESCRIPTION
      ""
   INDEX      { er1645v2Lan3MCInboundHwPriorityMapDscpToQueueTableIx }
   ::= {er1645v2Lan3MCInboundHwPriorityMapDscpToQueue 1}

Er1645v2Lan3MCInboundHwPriorityMapDscpToQueueEntry ::=
   SEQUENCE
      {
      er1645v2Lan3MCInboundHwPriorityMapDscpToQueueActions
         VariableLengthTableActions,
      er1645v2Lan3MCInboundHwPriorityMapDscpToQueueTableIx
         TableIndex,
      er1645v2Lan3MCInboundHwPriorityMapDscpToQueueStartDscp
         INTEGER,
      er1645v2Lan3MCInboundHwPriorityMapDscpToQueueEndDscp
         INTEGER,
      er1645v2Lan3MCInboundHwPriorityMapDscpToQueueQueue
         INTEGER
      }

er1645v2Lan3MCInboundHwPriorityMapDscpToQueueActions OBJECT-TYPE
   SYNTAX      VariableLengthTableActions
   MAX-ACCESS  read-write
   STATUS      current
   DESCRIPTION
      "By way of this field, some manipulations
       on this table may be performed."
   ::= {er1645v2Lan3MCInboundHwPriorityMapDscpToQueueEntry 2}

er1645v2Lan3MCInboundHwPriorityMapDscpToQueueTableIx OBJECT-TYPE
   SYNTAX      TableIndex
   MAX-ACCESS  not-accessible
   STATUS      current
   DESCRIPTION
      ""
   ::= {er1645v2Lan3MCInboundHwPriorityMapDscpToQueueEntry 11}

er1645v2Lan3MCInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan3MCInboundHwPriorityMapDscpToQueueEntry 16777216}

er1645v2Lan3MCInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan3MCInboundHwPriorityMapDscpToQueueEntry 33554432}

er1645v2Lan3MCInboundHwPriorityMapDscpToQueueQueue OBJECT-TYPE
   SYNTAX      INTEGER
               {
               queue1 (1),
               queue2 (2)
               }
   MAX-ACCESS  read-write
   STATUS      current
   DESCRIPTION
      "Path: ethernet3.editConf.inboundHwPriority.mapDscpToQueue.queue

       Possibilities:
               queue1   (1)
               queue2   (2)"
   ::= {er1645v2Lan3MCInboundHwPriorityMapDscpToQueueEntry 50331648}


er1645v2Lan3MCName OBJECT-TYPE
   SYNTAX      DisplayString
   MAX-ACCESS  read-write
   STATUS      current
   DESCRIPTION
      "Path: ethernet3.editConf.name
       Info: config interface name"
   ::= {er1645v2Lan3MC 2}


er1645v2Lan3MCInterfaceSide OBJECT-TYPE
   SYNTAX      INTEGER
               {
               user (1),
               network (2)
               }
   MAX-ACCESS  read-write
   STATUS      current
   DESCRIPTION
      "Path: ethernet3.editConf.interfaceSide

       Possibilities:
               user   (1)
               network   (2)"
   ::= {er1645v2Lan3MC 232}



sr1645v2Lan3MC OBJECT IDENTIFIER ::= {r1645v2Lan3MC 14}


sr1645v2Lan3MCDescr OBJECT-TYPE
   SYNTAX      DisplayString
   MAX-ACCESS  read-only
   STATUS      current
   DESCRIPTION
      "Path: ethernet3.status.ifDescr
       Info: ifDescr"
   ::= {sr1645v2Lan3MC 101}


sr1645v2Lan3MCType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet3.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2Lan3MC 102}


sr1645v2Lan3MCMtu OBJECT-TYPE
   SYNTAX      Integer32
   MAX-ACCESS  read-only
   STATUS      current
   DESCRIPTION
      "Path: ethernet3.status.ifMtu
       Info: ifMtu"
   ::= {sr1645v2Lan3MC 103}


sr1645v2Lan3MCOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ifOperStatus
       Info: ifOperStatus

       Possibilities:
               up   (1)
               down   (2)
               testing   (3)
               unknown   (4)
               dormant   (5)
               notPresent   (6)
               lowerLayerDown   (7)"
   ::= {sr1645v2Lan3MC 107}


sr1645v2Lan3MCLastChange OBJECT-TYPE
   SYNTAX      TimeTicks
   MAX-ACCESS  read-only
   STATUS      current
   DESCRIPTION
      "Path: ethernet3.status.ifLastChange
       Info: ifLastChange

       Time in centi-second."
   ::= {sr1645v2Lan3MC 108}


sr1645v2Lan3MCLastChangeD OBJECT-TYPE
   SYNTAX      DisplayString
   MAX-ACCESS  read-only
   STATUS      current
   DESCRIPTION
      "Path: ethernet3.status.ifLastChangeDate
       Info: ifLastChangeDate"
   ::= {sr1645v2Lan3MC 183}


sr1645v2Lan3MCSpeed OBJECT-TYPE
   SYNTAX      Gauge32
   MAX-ACCESS  read-only
   STATUS      current
   DESCRIPTION
      "Path: ethernet3.status.ifSpeed
       Info: ifSpeed

       32 bit unsigned gauge value."
   ::= {sr1645v2Lan3MC 104}


sr1645v2Lan3MCSnmpIndex OBJECT-TYPE
   SYNTAX      Integer32
   MAX-ACCESS  read-only
   STATUS      current
   DESCRIPTION
      "Path: ethernet3.status.snmpIndex
       Info: SNMP index assigned to this object"
   ::= {sr1645v2Lan3MC 269}


sr1645v2Lan3MCIp OBJECT IDENTIFIER ::= {sr1645v2Lan3MC 16}

sr1645v2Lan3MCIpSSC OBJECT IDENTIFIER ::= {sr1645v2Lan3MCIp 1}

sr1645v2Lan3MCIpEntry OBJECT IDENTIFIER ::= {sr1645v2Lan3MCIpSSC 1}

sr1645v2Lan3MCIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ip.status

       Possibilities:
               up   (1)
               down   (2)
               testing   (3)
               unknown   (4)
               dormant   (5)
               notPresent   (6)
               lowerLayerDown   (7)"
   ::= {sr1645v2Lan3MCIpEntry 1795162112}

sr1645v2Lan3MCIpAddress OBJECT-TYPE
   SYNTAX      IpAddress
   MAX-ACCESS  read-only
   STATUS      current
   DESCRIPTION
      "Path: ethernet3.status.ip.address"
   ::= {sr1645v2Lan3MCIpEntry 2030043136}

sr1645v2Lan3MCIpNetMask OBJECT-TYPE
   SYNTAX      IpAddress
   MAX-ACCESS  read-only
   STATUS      current
   DESCRIPTION
      "Path: ethernet3.status.ip.netMask"
   ::= {sr1645v2Lan3MCIpEntry 2063597568}

sr1645v2Lan3MCIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.ip.dhcp.status

       Possibilities:
               none   (0)
               selecting   (1)
               requesting   (2)
               rebinding   (3)
               bound   (4)
               renewing   (5)
               rebooting   (6)
               initreboot   (7)"
   ::= {sr1645v2Lan3MCIpEntry 402718720}

sr1645v2Lan3MCIpDhcpLeaseTime OBJECT-TYPE
   SYNTAX      TimeTicks
   MAX-ACCESS  read-only
   STATUS      current
   DESCRIPTION
      "Path: ethernet3.status.ip.dhcp.leaseTime

       Time in centi-second."
   ::= {sr1645v2Lan3MCIpEntry 402784256}

sr1645v2Lan3MCIpSecondaryIp OBJECT-TYPE
   SYNTAX      SEQUENCE OF Sr1645v2Lan3MCIpSecondaryIpEntry
   MAX-ACCESS  not-accessible
   STATUS      current
   DESCRIPTION
      ""
   ::= {sr1645v2Lan3MCIp 385875968}

sr1645v2Lan3MCIpSecondaryIpEntry OBJECT-TYPE
   SYNTAX      Sr1645v2Lan3MCIpSecondaryIpEntry
   MAX-ACCESS  not-accessible
   STATUS      current
   DESCRIPTION
      ""
   INDEX      { sr1645v2Lan3MCIpSecondaryIpTableIx }
   ::= {sr1645v2Lan3MCIpSecondaryIp 1}

Sr1645v2Lan3MCIpSecondaryIpEntry ::=
   SEQUENCE
      {
      sr1645v2Lan3MCIpSecondaryIpTableIx
         TableIndex,
      sr1645v2Lan3MCIpSecondaryIpAddress
         IpAddress,
      sr1645v2Lan3MCIpSecondaryIpNetMask
         IpAddress
      }

sr1645v2Lan3MCIpSecondaryIpTableIx OBJECT-TYPE
   SYNTAX      TableIndex
   MAX-ACCESS  not-accessible
   STATUS      current
   DESCRIPTION
      ""
   ::= {sr1645v2Lan3MCIpSecondaryIpEntry 11}

sr1645v2Lan3MCIpSecondaryIpAddress OBJECT-TYPE
   SYNTAX      IpAddress
   MAX-ACCESS  read-only
   STATUS      current
   DESCRIPTION
      "Path: ethernet3.status.ip.secondaryIp.address"
   ::= {sr1645v2Lan3MCIpSecondaryIpEntry 2030043136}

sr1645v2Lan3MCIpSecondaryIpNetMask OBJECT-TYPE
   SYNTAX      IpAddress
   MAX-ACCESS  read-only
   STATUS      current
   DESCRIPTION
      "Path: ethernet3.status.ip.secondaryIp.netMask"
   ::= {sr1645v2Lan3MCIpSecondaryIpEntry 2063597568}


sr1645v2Lan3MCArpCache OBJECT IDENTIFIER ::= {sr1645v2Lan3MC 11}

sr1645v2Lan3MCArpCacheSSCTable OBJECT-TYPE
   SYNTAX      SEQUENCE OF Sr1645v2Lan3MCArpCacheEntry
   MAX-ACCESS  not-accessible
   STATUS      current
   DESCRIPTION
      "arp cache of ethernet interface"
   ::= {sr1645v2Lan3MCArpCache 1}

sr1645v2Lan3MCArpCacheEntry OBJECT-TYPE
   SYNTAX      Sr1645v2Lan3MCArpCacheEntry
   MAX-ACCESS  not-accessible
   STATUS      current
   DESCRIPTION
      ""
   INDEX      { sr1645v2Lan3MCArpCacheTableIx }
   ::= {sr1645v2Lan3MCArpCacheSSCTable 1}

Sr1645v2Lan3MCArpCacheEntry ::=
   SEQUENCE
      {
      sr1645v2Lan3MCArpCacheTableIx
         TableIndex,
      sr1645v2Lan3MCArpCacheMacAddress
         OCTET STRING,
      sr1645v2Lan3MCArpCacheIpAddress
         IpAddress,
      sr1645v2Lan3MCArpCacheType
         INTEGER,
      sr1645v2Lan3MCArpCacheTimeOut
         TimeTicks
      }

sr1645v2Lan3MCArpCacheTableIx OBJECT-TYPE
   SYNTAX      TableIndex
   MAX-ACCESS  not-accessible
   STATUS      current
   DESCRIPTION
      ""
   ::= {sr1645v2Lan3MCArpCacheEntry 11}

sr1645v2Lan3MCArpCacheMacAddress OBJECT-TYPE
   SYNTAX      OCTET STRING
   MAX-ACCESS  read-only
   STATUS      current
   DESCRIPTION
      "Path: ethernet3.status.arpCache.macAddress

       MAC address."
   ::= {sr1645v2Lan3MCArpCacheEntry 16777216}

sr1645v2Lan3MCArpCacheIpAddress OBJECT-TYPE
   SYNTAX      IpAddress
   MAX-ACCESS  read-only
   STATUS      current
   DESCRIPTION
      "Path: ethernet3.status.arpCache.ipAddress"
   ::= {sr1645v2Lan3MCArpCacheEntry 33554432}

sr1645v2Lan3MCArpCacheType OBJECT-TYPE
   SYNTAX      INTEGER
               {
               static (0),
               dynamic (1)
               }
   MAX-ACCESS  read-only
   STATUS      current
   DESCRIPTION
      "Path: ethernet3.status.arpCache.type

       Possibilities:
               static   (0)
               dynamic   (1)"
   ::= {sr1645v2Lan3MCArpCacheEntry 50331648}

sr1645v2Lan3MCArpCacheTimeOut OBJECT-TYPE
   SYNTAX      TimeTicks
   MAX-ACCESS  read-only
   STATUS      current
   DESCRIPTION
      "Path: ethernet3.status.arpCache.timeOut

       Time in centi-second."
   ::= {sr1645v2Lan3MCArpCacheEntry 67108864}


sr1645v2Lan3MCBrS OBJECT IDENTIFIER ::= {sr1645v2Lan3MC 28}

sr1645v2Lan3MCBrSSSC OBJECT IDENTIFIER ::= {sr1645v2Lan3MCBrS 1}

sr1645v2Lan3MCBrSEntry OBJECT IDENTIFIER ::= {sr1645v2Lan3MCBrSSSC 1}

sr1645v2Lan3MCBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.bridging.status

       Possibilities:
               disabled   (0)
               discarding   (1)
               learning   (2)
               forwarding   (3)
               backupBlockedIntfDown   (256)
               backupBlockedIntfUp   (259)
               shutdown   (255)"
   ::= {sr1645v2Lan3MCBrSEntry 16777216}

sr1645v2Lan3MCBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.bridging.spanningTree.portRole

       Possibilities:
               none   (0)
               root   (1)
               designated   (2)
               alternate   (3)
               backup   (4)
               disabled   (5)
               master   (6)"
   ::= {sr1645v2Lan3MCBrSEntry 33619968}

sr1645v2Lan3MCBrSStPortId OBJECT-TYPE
   SYNTAX      Integer32
   MAX-ACCESS  read-only
   STATUS      current
   DESCRIPTION
      "Path: ethernet3.status.bridging.spanningTree.portId"
   ::= {sr1645v2Lan3MCBrSEntry 33685504}

sr1645v2Lan3MCBrSStPpCostExtPathCost OBJECT-TYPE
   SYNTAX      Integer32
   MAX-ACCESS  read-only
   STATUS      current
   DESCRIPTION
      "Path: ethernet3.status.bridging.spanningTree.portPathCosts.extPathCost"
   ::= {sr1645v2Lan3MCBrSEntry 33751296}

sr1645v2Lan3MCBrSStPpCostIntPathCost OBJECT-TYPE
   SYNTAX      Integer32
   MAX-ACCESS  read-only
   STATUS      current
   DESCRIPTION
      "Path: ethernet3.status.bridging.spanningTree.portPathCosts.intPathCost"
   ::= {sr1645v2Lan3MCBrSEntry 33751552}

sr1645v2Lan3MCBrSStExtRpCost OBJECT-TYPE
   SYNTAX      Integer32
   MAX-ACCESS  read-only
   STATUS      current
   DESCRIPTION
      "Path: ethernet3.status.bridging.spanningTree.extRootPathCost"
   ::= {sr1645v2Lan3MCBrSEntry 33816576}

sr1645v2Lan3MCBrSStIntRpCost OBJECT-TYPE
   SYNTAX      Integer32
   MAX-ACCESS  read-only
   STATUS      current
   DESCRIPTION
      "Path: ethernet3.status.bridging.spanningTree.intRootPathCost"
   ::= {sr1645v2Lan3MCBrSEntry 33882112}

sr1645v2Lan3MCBrSStDesBrIdPriority OBJECT-TYPE
   SYNTAX      Integer32
   MAX-ACCESS  read-only
   STATUS      current
   DESCRIPTION
      "Path: ethernet3.status.bridging.spanningTree.designatedBridgeId.priority"
   ::= {sr1645v2Lan3MCBrSEntry 33947904}

sr1645v2Lan3MCBrSStDesBrIdMacAddress OBJECT-TYPE
   SYNTAX      OCTET STRING
   MAX-ACCESS  read-only
   STATUS      current
   DESCRIPTION
      "Path: ethernet3.status.bridging.spanningTree.designatedBridgeId.macAddress

       MAC address."
   ::= {sr1645v2Lan3MCBrSEntry 33948160}

sr1645v2Lan3MCBrSStDesPrtId OBJECT-TYPE
   SYNTAX      Integer32
   MAX-ACCESS  read-only
   STATUS      current
   DESCRIPTION
      "Path: ethernet3.status.bridging.spanningTree.designatedPortId"
   ::= {sr1645v2Lan3MCBrSEntry 34013184}

sr1645v2Lan3MCBrSStDesInt OBJECT-TYPE
   SYNTAX      INTEGER
               {
               no (0),
               yes (1)
               }
   MAX-ACCESS  read-only
   STATUS      current
   DESCRIPTION
      "Path: ethernet3.status.bridging.spanningTree.designatedOrInternal

       Possibilities:
               no   (0)
               yes   (1)"
   ::= {sr1645v2Lan3MCBrSEntry 34078720}

sr1645v2Lan3MCBrSStEdgeDetection OBJECT-TYPE
   SYNTAX      INTEGER
               {
               none (0),
               edge (1),
               notEdge (2)
               }
   MAX-ACCESS  read-only
   STATUS      current
   DESCRIPTION
      "Path: ethernet3.status.bridging.spanningTree.edgeDetection

       Possibilities:
               none   (0)
               edge   (1)
               notEdge   (2)"
   ::= {sr1645v2Lan3MCBrSEntry 34144256}


sr1645v2Lan3MCMacAddress OBJECT-TYPE
   SYNTAX      OCTET STRING
   MAX-ACCESS  read-only
   STATUS      current
   DESCRIPTION
      "Path: ethernet3.status.macAddress
       Info: ifPhysAddress

       MAC address."
   ::= {sr1645v2Lan3MC 105}


sr1645v2Lan3MCIpAdEntBcastAddr OBJECT-TYPE
   SYNTAX      Integer32
   MAX-ACCESS  read-only
   STATUS      current
   DESCRIPTION
      "Path: ethernet3.status.ipAdEntBcastAddr
       Info: ipAdEntBcastAddr"
   ::= {sr1645v2Lan3MC 124}


sr1645v2Lan3MCIpAdEntReasmMaxSize OBJECT-TYPE
   SYNTAX      Integer32
   MAX-ACCESS  read-only
   STATUS      current
   DESCRIPTION
      "Path: ethernet3.status.ipAdEntReasmMaxSize
       Info: ipAdEntReasmMaxSize"
   ::= {sr1645v2Lan3MC 125}


sr1645v2Lan3MCAdapter OBJECT IDENTIFIER ::= {sr1645v2Lan3MC 145}

sr1645v2Lan3MCAdapterSSC OBJECT IDENTIFIER ::= {sr1645v2Lan3MCAdapter 1}

sr1645v2Lan3MCAdapterEntry OBJECT IDENTIFIER ::= {sr1645v2Lan3MCAdapterSSC 1}

sr1645v2Lan3MCAdapterSpeed OBJECT-TYPE
   SYNTAX      INTEGER
               {
               s10 (0),
               s100 (1),
               s1000 (2),
               s200 (3)
               }
   MAX-ACCESS  read-only
   STATUS      current
   DESCRIPTION
      "Path: ethernet3.status.adapter.speed

       Possibilities:
               10   (0)
               100   (1)
               1000   (2)
               200   (3)"
   ::= {sr1645v2Lan3MCAdapterEntry 16777216}

sr1645v2Lan3MCAdapterDuplex OBJECT-TYPE
   SYNTAX      INTEGER
               {
               halfDuplex (0),
               fullDuplex (1)
               }
   MAX-ACCESS  read-only
   STATUS      current
   DESCRIPTION
      "Path: ethernet3.status.adapter.duplex

       Possibilities:
               halfDuplex   (0)
               fullDuplex   (1)"
   ::= {sr1645v2Lan3MCAdapterEntry 33554432}


sr1645v2Lan3MCOam OBJECT IDENTIFIER ::= {sr1645v2Lan3MC 901}

sr1645v2Lan3MCOamSSC OBJECT IDENTIFIER ::= {sr1645v2Lan3MCOam 1}

sr1645v2Lan3MCOamEntry OBJECT IDENTIFIER ::= {sr1645v2Lan3MCOamSSC 1}

sr1645v2Lan3MCOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet3.status.oam.discovery

       Possibilities:
               fault   (0)
               sendLocal   (1)
               passiveWait   (2)
               sendLocalRemote   (3)
               sendLocalRemoteOk   (4)
               sendAny   (5)"
   ::= {sr1645v2Lan3MCOamEntry 16777216}

sr1645v2Lan3MCOamLoopback OBJECT-TYPE
   SYNTAX      INTEGER
               {
               idle (0),
               waiting (1),
               localRunning (2),
               remoteRunning (3)
               }
   MAX-ACCESS  read-only
   STATUS      current
   DESCRIPTION
      "Path: ethernet3.status.oam.loopback

       Possibilities:
               idle   (0)
               waiting   (1)
               localRunning   (2)
               remoteRunning   (3)"
   ::= {sr1645v2Lan3MCOamEntry 33554432}

sr1645v2Lan3MCOamLocalInfoVersion OBJECT-TYPE
   SYNTAX      Integer32
   MAX-ACCESS  read-only
   STATUS      current
   DESCRIPTION
      "Path: ethernet3.status.oam.localInfo.version"
   ::= {sr1645v2Lan3MCOamEntry 50397184}

sr1645v2Lan3MCOamLocalInfoRevision OBJECT-TYPE
   SYNTAX      Integer32
   MAX-ACCESS  read-only
   STATUS      current
   DESCRIPTION
      "Path: ethernet3.status.oam.localInfo.revision"
   ::= {sr1645v2Lan3MCOamEntry 50462720}

sr1645v2Lan3MCOamLocalInfoStateMuxAction OBJECT-TYPE
   SYNTAX      INTEGER
               {
               forwarding (0),
               discarding (1)
               }
   MAX-ACCESS  read-only
   STATUS      current
   DESCRIPTION
      "Path: ethernet3.status.oam.localInfo.state.muxAction

       Possibilities:
               forwarding   (0)
               discarding   (1)"
   ::= {sr1645v2Lan3MCOamEntry 50528512}

sr1645v2Lan3MCOamLocalInfoStateParserAction OBJECT-TYPE
   SYNTAX      INTEGER
               {
               forwarding (0),
               loopback (1),
               discarding (2),
               reserved (3)
               }
   MAX-ACCESS  read-only
   STATUS      current
   DESCRIPTION
      "Path: ethernet3.status.oam.localInfo.state.parserAction

       Possibilities:
               forwarding   (0)
               loopback   (1)
               discarding   (2)
               reserved   (3)"
   ::= {sr1645v2Lan3MCOamEntry 50528768}

sr1645v2Lan3MCOamLocalInfoOui OBJECT-TYPE
   SYNTAX      OCTET STRING
   MAX-ACCESS  read-only
   STATUS      current
   DESCRIPTION
      "Path: ethernet3.status.oam.localInfo.oui"
   ::= {sr1645v2Lan3MCOamEntry 50593792}

sr1645v2Lan3MCOamLocalInfoVendorInfo OBJECT-TYPE
   SYNTAX      OCTET STRING
   MAX-ACCESS  read-only
   STATUS      current
   DESCRIPTION
      "Path: ethernet3.status.oam.localInfo.vendorInfo"
   ::= {sr1645v2Lan3MCOamEntry 50659328}

sr1645v2Lan3MCOamLocalInfoVarRetrieval OBJECT-TYPE
   SYNTAX      INTEGER
               {
               notSupported (0),
               supported (1)
               }
   MAX-ACCESS  read-only
   STATUS      current
   DESCRIPTION
      "Path: ethernet3.status.oam.localInfo.varRetrieval

       Possibilities:
               notSupported   (0)
               supported   (1)"
   ::= {sr1645v2Lan3MCOamEntry 50724864}

sr1645v2Lan3MCOamLocalInfoLinkEvents OBJECT-TYPE
   SYNTAX      INTEGER
               {
               ignored (0),
               interpreted (1)
               }
   MAX-ACCESS  read-only
   STATUS      current
   DESCRIPTION
      "Path: ethernet3.status.oam.localInfo.linkEvents

       Possibilities:
               ignored   (0)
               interpreted   (1)"
   ::= {sr1645v2Lan3MCOamEntry 50790400}

sr1645v2Lan3MCOamLocalInfoLoopback OBJECT-TYPE
   SYNTAX      INTEGER
               {
               notSupported (0),
               supported (1)
               }
   MAX-ACCESS  read-only
   STATUS      current
   DESCRIPTION
      "Path: ethernet3.status.oam.localInfo.loopback

       Possibilities:
               notSupported   (0)
               supported   (1)"
   ::= {sr1645v2Lan3MCOamEntry 50855936}

sr1645v2Lan3MCOamLocalInfoUnidirectional OBJECT-TYPE
   SYNTAX      INTEGER
               {
               notSupported (0),
               supported (1)
               }
   MAX-ACCESS  read-only
   STATUS      current
   DESCRIPTION
      "Path: ethernet3.status.oam.localInfo.unidirectional

       Possibilities:
               notSupported   (0)
               supported   (1)"
   ::= {sr1645v2Lan3MCOamEntry 50921472}

sr1645v2Lan3MCOamLocalInfoMode OBJECT-TYPE
   SYNTAX      INTEGER
               {
               passive (0),
               active (1)
               }
   MAX-ACCESS  read-only
   STATUS      current
   DESCRIPTION
      "Path: ethernet3.status.oam.localInfo.mode

       Possibilities:
               passive   (0)
               active   (1)"
   ::= {sr1645v2Lan3MCOamEntry 50987008}

sr1645v2Lan3MCOamLocalInfoMaxPduSize OBJECT-TYPE
   SYNTAX      Integer32
   MAX-ACCESS  read-only
   STATUS      current
   DESCRIPTION
      "Path: ethernet3.status.oam.localInfo.maxPduSize"
   ::= {sr1645v2Lan3MCOamEntry 51052544}

sr1645v2Lan3MCOamRemoteInfoVersion OBJECT-TYPE
   SYNTAX      Integer32
   MAX-ACCESS  read-only
   STATUS      current
   DESCRIPTION
      "Path: ethernet3.status.oam.remoteInfo.version"
   ::= {sr1645v2Lan3MCOamEntry 67174400}

sr1645v2Lan3MCOamRemoteInfoRevision OBJECT-TYPE
   SYNTAX      Integer32
   MAX-ACCESS  read-only
   STATUS      current
   DESCRIPTION
      "Path: ethernet3.status.oam.remoteInfo.revision"
   ::= {sr1645v2Lan3MCOamEntry 67239936}

sr1645v2Lan3MCOamRemoteInfoStateMuxAction OBJECT-TYPE
   SYNTAX      INTEGER
               {
               forwarding (0),
               discarding (1)
               }
   MAX-ACCESS  read-only
   STATUS      current
   DESCRIPTION
      "Path: ethernet3.status.oam.remoteInfo.state.muxAction

       Possibilities:
               forwarding   (0)
               discarding   (1)"
   ::= {sr1645v2Lan3MCOamEntry 67305728}

sr1645v2Lan3MCOamRemoteInfoStateParserAction OBJECT-TYPE
   SYNTAX      INTEGER
               {
               forwarding (0),
               loopback (1),
               discarding (2),
               reserved (3)
               }
   MAX-ACCESS  read-only
   STATUS      current
   DESCRIPTION
      "Path: ethernet3.status.oam.remoteInfo.state.parserAction

       Possibilities:
               forwarding   (0)
               loopback   (1)
               discarding   (2)
               reserved   (3)"
   ::= {sr1645v2Lan3MCOamEntry 67305984}

sr1645v2Lan3MCOamRemoteInfoOui OBJECT-TYPE
   SYNTAX      OCTET STRING
   MAX-ACCESS  read-only
   STATUS      current
   DESCRIPTION
      "Path: ethernet3.status.oam.remoteInfo.oui"
   ::= {sr1645v2Lan3MCOamEntry 67371008}

sr1645v2Lan3MCOamRemoteInfoVendorInfo OBJECT-TYPE
   SYNTAX      OCTET STRING
   MAX-ACCESS  read-only
   STATUS      current
   DESCRIPTION
      "Path: ethernet3.status.oam.remoteInfo.vendorInfo"
   ::= {sr1645v2Lan3MCOamEntry 67436544}

sr1645v2Lan3MCOamRemoteInfoVarRetrieval OBJECT-TYPE
   SYNTAX      INTEGER
               {
               notSupported (0),
               supported (1)
               }
   MAX-ACCESS  read-only
   STATUS      current
   DESCRIPTION
      "Path: ethernet3.status.oam.remoteInfo.varRetrieval

       Possibilities:
               notSupported   (0)
               supported   (1)"
   ::= {sr1645v2Lan3MCOamEntry 67502080}

sr1645v2Lan3MCOamRemoteInfoLinkEvents OBJECT-TYPE
   SYNTAX      INTEGER
               {
               ignored (0),
               interpreted (1)
               }
   MAX-ACCESS  read-only
   STATUS      current
   DESCRIPTION
      "Path: ethernet3.status.oam.remoteInfo.linkEvents

       Possibilities:
               ignored   (0)
               interpreted   (1)"
   ::= {sr1645v2Lan3MCOamEntry 67567616}

sr1645v2Lan3MCOamRemoteInfoLoopback OBJECT-TYPE
   SYNTAX      INTEGER
               {
               notSupported (0),
               supported (1)
               }
   MAX-ACCESS  read-only
   STATUS      current
   DESCRIPTION
      "Path: ethernet3.status.oam.remoteInfo.loopback

       Possibilities:
               notSupported   (0)
               supported   (1)"
   ::= {sr1645v2Lan3MCOamEntry 67633152}

sr1645v2Lan3MCOamRemoteInfoUnidirectional OBJECT-TYPE
   SYNTAX      INTEGER
               {
               notSupported (0),
               supported (1)
               }
   MAX-ACCESS  read-only
   STATUS      current
   DESCRIPTION
      "Path: ethernet3.status.oam.remoteInfo.unidirectional

       Possibilities:
               notSupported   (0)
               supported   (1)"
   ::= {sr1645v2Lan3MCOamEntry 67698688}

sr1645v2Lan3MCOamRemoteInfoMode OBJECT-TYPE
   SYNTAX      INTEGER
               {
               passive (0),
               active (1)
               }
   MAX-ACCESS  read-only
   STATUS      current
   DESCRIPTION
      "Path: ethernet3.status.oam.remoteInfo.mode

       Possibilities:
               passive   (0)
               active   (1)"
   ::= {sr1645v2Lan3MCOamEntry 67764224}

sr1645v2Lan3MCOamRemoteInfoMaxPduSize OBJECT-TYPE
   SYNTAX      Integer32
   MAX-ACCESS  read-only
   STATUS      current
   DESCRIPTION
      "Path: ethernet3.status.oam.remoteInfo.maxPduSize"
   ::= {sr1645v2Lan3MCOamEntry 67829760}

sr1645v2Lan3MCOamEventsErroredSymbolWindow OBJECT-TYPE
   SYNTAX      Integer32
   UNITS       "symbols"
   MAX-ACCESS  read-only
   STATUS      current
   DESCRIPTION
      "Path: ethernet3.status.oam.events.erroredSymbol.window

       unit name = symbols"
   ::= {sr1645v2Lan3MCOamEntry 83951872}

sr1645v2Lan3MCOamEventsErroredSymbolThreshold OBJECT-TYPE
   SYNTAX      OCTET STRING
   UNITS       "symbols"
   MAX-ACCESS  read-only
   STATUS      current
   DESCRIPTION
      "Path: ethernet3.status.oam.events.erroredSymbol.threshold

       unit name = symbols"
   ::= {sr1645v2Lan3MCOamEntry 83952128}

sr1645v2Lan3MCOamEventsErroredFramePeriodWindow OBJECT-TYPE
   SYNTAX      INTEGER
               {
               default (0)
               }
   UNITS       "frames"
   MAX-ACCESS  read-only
   STATUS      current
   DESCRIPTION
      "Path: ethernet3.status.oam.events.erroredFramePeriod.window

       unit name = frames

       Possibilities:
               default   (0)"
   ::= {sr1645v2Lan3MCOamEntry 84017408}

sr1645v2Lan3MCOamEventsErroredFramePeriodThreshold OBJECT-TYPE
   SYNTAX      Integer32
   UNITS       "frames"
   MAX-ACCESS  read-only
   STATUS      current
   DESCRIPTION
      "Path: ethernet3.status.oam.events.erroredFramePeriod.threshold

       unit name = frames"
   ::= {sr1645v2Lan3MCOamEntry 84017664}

sr1645v2Lan3MCOamEventsErroredFrameWindow OBJECT-TYPE
   SYNTAX      Integer32
   UNITS       "100msec"
   MAX-ACCESS  read-only
   STATUS      current
   DESCRIPTION
      "Path: ethernet3.status.oam.events.erroredFrame.window

       unit name = 100msec"
   ::= {sr1645v2Lan3MCOamEntry 84082944}

sr1645v2Lan3MCOamEventsErroredFrameThreshold OBJECT-TYPE
   SYNTAX      Integer32
   UNITS       "frames"
   MAX-ACCESS  read-only
   STATUS      current
   DESCRIPTION
      "Path: ethernet3.status.oam.events.erroredFrame.threshold

       unit name = frames"
   ::= {sr1645v2Lan3MCOamEntry 84083200}

sr1645v2Lan3MCOamEventsErroredFrameSecondsWindow OBJECT-TYPE
   SYNTAX      Integer32
   UNITS       "100msec"
   MAX-ACCESS  read-only
   STATUS      current
   DESCRIPTION
      "Path: ethernet3.status.oam.events.erroredFrameSeconds.window

       unit name = 100msec"
   ::= {sr1645v2Lan3MCOamEntry 84148480}

sr1645v2Lan3MCOamEventsErroredFrameSecondsThreshold OBJECT-TYPE
   SYNTAX      Integer32
   UNITS       "frames"
   MAX-ACCESS  read-only
   STATUS      current
   DESCRIPTION
      "Path: ethernet3.status.oam.events.erroredFrameSeconds.threshold

       unit name = frames"
   ::= {sr1645v2Lan3MCOamEntry 84148736}


sr1645v2Lan3MCOamEventLog OBJECT IDENTIFIER ::= {sr1645v2Lan3MC 911}

sr1645v2Lan3MCOamEventLogSSCTable OBJECT-TYPE
   SYNTAX      SEQUENCE OF Sr1645v2Lan3MCOamEventLogEntry
   MAX-ACCESS  not-accessible
   STATUS      current
   DESCRIPTION
      "OAM event log"
   ::= {sr1645v2Lan3MCOamEventLog 1}

sr1645v2Lan3MCOamEventLogEntry OBJECT-TYPE
   SYNTAX      Sr1645v2Lan3MCOamEventLogEntry
   MAX-ACCESS  not-accessible
   STATUS      current
   DESCRIPTION
      ""
   INDEX      { sr1645v2Lan3MCOamEventLogTableIx }
   ::= {sr1645v2Lan3MCOamEventLogSSCTable 1}

Sr1645v2Lan3MCOamEventLogEntry ::=
   SEQUENCE
      {
      sr1645v2Lan3MCOamEventLogTableIx
         TableIndex,
      sr1645v2Lan3MCOamEventLogSysUpTime
         TimeTicks,
      sr1645v2Lan3MCOamEventLogLocation
         INTEGER,
      sr1645v2Lan3MCOamEventLogType
         INTEGER,
      sr1645v2Lan3MCOamEventLogOui
         OCTET STRING,
      sr1645v2Lan3MCOamEventLogWindow
         Counter64,
      sr1645v2Lan3MCOamEventLogThreshold
         Counter64,
      sr1645v2Lan3MCOamEventLogTotal
         Counter32,
      sr1645v2Lan3MCOamEventLogValue
         Counter64,
      sr1645v2Lan3MCOamEventLogRunningTotal
         Counter64
      }

sr1645v2Lan3MCOamEventLogTableIx OBJECT-TYPE
   SYNTAX      TableIndex
   MAX-ACCESS  not-accessible
   STATUS      current
   DESCRIPTION
      ""
   ::= {sr1645v2Lan3MCOamEventLogEntry 11}

sr1645v2Lan3MCOamEventLogSysUpTime OBJECT-TYPE
   SYNTAX      TimeTicks
   MAX-ACCESS  read-only
   STATUS      current
   DESCRIPTION
      "Path: ethernet3.status.oamEventLog.sysUpTime

       Time in centi-second."
   ::= {sr1645v2Lan3MCOamEventLogEntry 16777216}

sr1645v2Lan3MCOamEventLogLocation OBJECT-TYPE
   SYNTAX      INTEGER
               {
               local (1),
               remote (2)
               }
   MAX-ACCESS  read-only
   STATUS      current
   DESCRIPTION
      "Path: ethernet3.status.oamEventLog.location

       Possibilities:
               local   (1)
               remote   (2)"
   ::= {sr1645v2Lan3MCOamEventLogEntry 33554432}

sr1645v2Lan3MCOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet3.status.oamEventLog.type

       Possibilities:
               erroredSymbols   (1)
               erroredFramePeriod   (2)
               erroredFrame   (3)
               erroredFrameSeconds   (4)
               linkFault   (256)
               dyingGasp   (257)
               criticalLink   (258)"
   ::= {sr1645v2Lan3MCOamEventLogEntry 50331648}

sr1645v2Lan3MCOamEventLogOui OBJECT-TYPE
   SYNTAX      OCTET STRING
   MAX-ACCESS  read-only
   STATUS      current
   DESCRIPTION
      "Path: ethernet3.status.oamEventLog.oui"
   ::= {sr1645v2Lan3MCOamEventLogEntry 67108864}

sr1645v2Lan3MCOamEventLogWindow OBJECT-TYPE
   SYNTAX      Counter64
   MAX-ACCESS  read-only
   STATUS      current
   DESCRIPTION
      "Path: ethernet3.status.oamEventLog.window

       64 bit unsigned wrappable counter."
   ::= {sr1645v2Lan3MCOamEventLogEntry 83886080}

sr1645v2Lan3MCOamEventLogThreshold OBJECT-TYPE
   SYNTAX      Counter64
   MAX-ACCESS  read-only
   STATUS      current
   DESCRIPTION
      "Path: ethernet3.status.oamEventLog.threshold

       64 bit unsigned wrappable counter."
   ::= {sr1645v2Lan3MCOamEventLogEntry 100663296}

sr1645v2Lan3MCOamEventLogTotal OBJECT-TYPE
   SYNTAX      Counter32
   MAX-ACCESS  read-only
   STATUS      current
   DESCRIPTION
      "Path: ethernet3.status.oamEventLog.total

       32 bit unsigned wrappable counter."
   ::= {sr1645v2Lan3MCOamEventLogEntry 117440512}

sr1645v2Lan3MCOamEventLogValue OBJECT-TYPE
   SYNTAX      Counter64
   MAX-ACCESS  read-only
   STATUS      current
   DESCRIPTION
      "Path: ethernet3.status.oamEventLog.value

       64 bit unsigned wrappable counter."
   ::= {sr1645v2Lan3MCOamEventLogEntry 134217728}

sr1645v2Lan3MCOamEventLogRunningTotal OBJECT-TYPE
   SYNTAX      Counter64
   MAX-ACCESS  read-only
   STATUS      current
   DESCRIPTION
      "Path: ethernet3.status.oamEventLog.runningTotal

       64 bit unsigned wrappable counter."
   ::= {sr1645v2Lan3MCOamEventLogEntry 150994944}


sr1645v2Lan3MCLst OBJECT IDENTIFIER ::= {sr1645v2Lan3MC 18}

sr1645v2Lan3MCLstSSC OBJECT IDENTIFIER ::= {sr1645v2Lan3MCLst 1}

sr1645v2Lan3MCLstEntry OBJECT IDENTIFIER ::= {sr1645v2Lan3MCLstSSC 1}

sr1645v2Lan3MCLstTrackedInterface OBJECT-TYPE
   SYNTAX      DisplayString
   MAX-ACCESS  read-only
   STATUS      current
   DESCRIPTION
      "Path: ethernet3.status.linkStateTracking.trackedInterface"
   ::= {sr1645v2Lan3MCLstEntry 16777216}

sr1645v2Lan3MCLstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet3.status.linkStateTracking.ifOperStatus

       Possibilities:
               up   (1)
               down   (2)
               testing   (3)
               unknown   (4)
               dormant   (5)
               notPresent   (6)
               lowerLayerDown   (7)
                  (255)"
   ::= {sr1645v2Lan3MCLstEntry 50331648}


sr1645v2Lan3MCVlan OBJECT IDENTIFIER ::= {sr1645v2Lan3MC 34}

sr1645v2Lan3MCVlanSSCTable OBJECT-TYPE
   SYNTAX      SEQUENCE OF Sr1645v2Lan3MCVlanEntry
   MAX-ACCESS  not-accessible
   STATUS      current
   DESCRIPTION
      ""
   ::= {sr1645v2Lan3MCVlan 1}

sr1645v2Lan3MCVlanEntry OBJECT-TYPE
   SYNTAX      Sr1645v2Lan3MCVlanEntry
   MAX-ACCESS  not-accessible
   STATUS      current
   DESCRIPTION
      ""
   INDEX      { sr1645v2Lan3MCVlanTableIx }
   ::= {sr1645v2Lan3MCVlanSSCTable 1}

Sr1645v2Lan3MCVlanEntry ::=
   SEQUENCE
      {
      sr1645v2Lan3MCVlanTableIx
         TableIndex,
      sr1645v2Lan3MCVlanName
         DisplayString,
      sr1645v2Lan3MCVlanMode
         INTEGER,
      sr1645v2Lan3MCVlanIfOperStatus
         INTEGER,
      sr1645v2Lan3MCVlanIfLastChange
         TimeTicks,
      sr1645v2Lan3MCVlanIfLastChangeDate
         DisplayString,
      sr1645v2Lan3MCVlanIpAddress
         IpAddress,
      sr1645v2Lan3MCVlanIpNetMask
         IpAddress,
      sr1645v2Lan3MCVlanIpRemote
         IpAddress,
      sr1645v2Lan3MCVlanIpDhcpStatus
         INTEGER,
      sr1645v2Lan3MCVlanIpDhcpLeaseTime
         TimeTicks,
      sr1645v2Lan3MCVlanIpV6State
         INTEGER,
      sr1645v2Lan3MCVlanIpV6InterfaceId
         OCTET STRING,
      sr1645v2Lan3MCVlanIpV6LinkMtu
         Integer32,
      sr1645v2Lan3MCVlanIpV6HopLimit
         Integer32,
      sr1645v2Lan3MCVlanIpV6DhcpIaid
         Counter32,
      sr1645v2Lan3MCVlanIpV6RaRcvOption
         Integer32,
      sr1645v2Lan3MCVlanBridgingStatus
         INTEGER,
      sr1645v2Lan3MCVlanBridgingSpanningTreePortRole
         INTEGER,
      sr1645v2Lan3MCVlanBridgingSpanningTreePortId
         Integer32,
      sr1645v2Lan3MCVlanBridgingSpanningTreePpCostExtPathCost
         Integer32,
      sr1645v2Lan3MCVlanBridgingSpanningTreePpCostIntPathCost
         Integer32,
      sr1645v2Lan3MCVlanBridgingSpanningTreeExtRpCost
         Integer32,
      sr1645v2Lan3MCVlanBridgingSpanningTreeIntRpCost
         Integer32,
      sr1645v2Lan3MCVlanBridgingSpanningTreeDesBrIdPriority
         Integer32,
      sr1645v2Lan3MCVlanBridgingSpanningTreeDesBrIdMacAddress
         OCTET STRING,
      sr1645v2Lan3MCVlanBridgingSpanningTreeDesPrtId
         Integer32,
      sr1645v2Lan3MCVlanBridgingSpanningTreeDesInt
         INTEGER,
      sr1645v2Lan3MCVlanBridgingSpanningTreeEdgeDetection
         INTEGER,
      sr1645v2Lan3MCVlanVlanVid
         Integer32,
      sr1645v2Lan3MCVlanPppOEthDiscState
         INTEGER,
      sr1645v2Lan3MCVlanPppOEthPeerMac
         OCTET STRING,
      sr1645v2Lan3MCVlanPppOEthServiceName
         DisplayString,
      sr1645v2Lan3MCVlanPppLcpState
         INTEGER,
      sr1645v2Lan3MCVlanPppIpcpState
         INTEGER,
      sr1645v2Lan3MCVlanPppIp6cpState
         INTEGER,
      sr1645v2Lan3MCVlanPppMyAutSt
         INTEGER,
      sr1645v2Lan3MCVlanPppHisAutSt
         INTEGER,
      sr1645v2Lan3MCVlanPppMru
         Integer32
      }

sr1645v2Lan3MCVlanTableIx OBJECT-TYPE
   SYNTAX      TableIndex
   MAX-ACCESS  not-accessible
   STATUS      current
   DESCRIPTION
      ""
   ::= {sr1645v2Lan3MCVlanEntry 11}

sr1645v2Lan3MCVlanName OBJECT-TYPE
   SYNTAX      DisplayString
   MAX-ACCESS  read-only
   STATUS      current
   DESCRIPTION
      "Path: ethernet3.status.vlan.name"
   ::= {sr1645v2Lan3MCVlanEntry 16777216}

sr1645v2Lan3MCVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan3MCVlanEntry 335544320}

sr1645v2Lan3MCVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.vlan.ifOperStatus

       Possibilities:
               up   (1)
               down   (2)
               testing   (3)
               unknown   (4)
               dormant   (5)
               notPresent   (6)
               lowerLayerDown   (7)"
   ::= {sr1645v2Lan3MCVlanEntry 1795162112}

sr1645v2Lan3MCVlanIfLastChange OBJECT-TYPE
   SYNTAX      TimeTicks
   MAX-ACCESS  read-only
   STATUS      current
   DESCRIPTION
      "Path: ethernet3.status.vlan.ifLastChange

       Time in centi-second."
   ::= {sr1645v2Lan3MCVlanEntry 1811939328}

sr1645v2Lan3MCVlanIfLastChangeDate OBJECT-TYPE
   SYNTAX      DisplayString
   MAX-ACCESS  read-only
   STATUS      current
   DESCRIPTION
      "Path: ethernet3.status.vlan.ifLastChangeDate"
   ::= {sr1645v2Lan3MCVlanEntry 3070230528}

sr1645v2Lan3MCVlanIpAddress OBJECT-TYPE
   SYNTAX      IpAddress
   MAX-ACCESS  read-only
   STATUS      current
   DESCRIPTION
      "Path: ethernet3.status.vlan.ip.address"
   ::= {sr1645v2Lan3MCVlanEntry 51380224}

sr1645v2Lan3MCVlanIpNetMask OBJECT-TYPE
   SYNTAX      IpAddress
   MAX-ACCESS  read-only
   STATUS      current
   DESCRIPTION
      "Path: ethernet3.status.vlan.ip.netMask"
   ::= {sr1645v2Lan3MCVlanEntry 51445760}

sr1645v2Lan3MCVlanIpRemote OBJECT-TYPE
   SYNTAX      IpAddress
   MAX-ACCESS  read-only
   STATUS      current
   DESCRIPTION
      "Path: ethernet3.status.vlan.ip.remote"
   ::= {sr1645v2Lan3MCVlanEntry 51511296}

sr1645v2Lan3MCVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.vlan.ip.dhcp.status

       Possibilities:
               none   (0)
               selecting   (1)
               requesting   (2)
               rebinding   (3)
               bound   (4)
               renewing   (5)
               rebooting   (6)
               initreboot   (7)"
   ::= {sr1645v2Lan3MCVlanEntry 51904768}

sr1645v2Lan3MCVlanIpDhcpLeaseTime OBJECT-TYPE
   SYNTAX      TimeTicks
   MAX-ACCESS  read-only
   STATUS      current
   DESCRIPTION
      "Path: ethernet3.status.vlan.ip.dhcp.leaseTime

       Time in centi-second."
   ::= {sr1645v2Lan3MCVlanEntry 51905024}

sr1645v2Lan3MCVlanIpV6State OBJECT-TYPE
   SYNTAX      INTEGER
               {
               disabled (0),
               enabled (1)
               }
   MAX-ACCESS  read-only
   STATUS      current
   DESCRIPTION
      "Path: ethernet3.status.vlan.ipV6.state

       Possibilities:
               disabled   (0)
               enabled   (1)"
   ::= {sr1645v2Lan3MCVlanEntry 100728832}

sr1645v2Lan3MCVlanIpV6InterfaceId OBJECT-TYPE
   SYNTAX      OCTET STRING
   MAX-ACCESS  read-only
   STATUS      current
   DESCRIPTION
      "Path: ethernet3.status.vlan.ipV6.interfaceId"
   ::= {sr1645v2Lan3MCVlanEntry 100794368}

sr1645v2Lan3MCVlanIpV6LinkMtu OBJECT-TYPE
   SYNTAX      Integer32
   MAX-ACCESS  read-only
   STATUS      current
   DESCRIPTION
      "Path: ethernet3.status.vlan.ipV6.linkMtu"
   ::= {sr1645v2Lan3MCVlanEntry 100925440}

sr1645v2Lan3MCVlanIpV6HopLimit OBJECT-TYPE
   SYNTAX      Integer32
   MAX-ACCESS  read-only
   STATUS      current
   DESCRIPTION
      "Path: ethernet3.status.vlan.ipV6.hopLimit"
   ::= {sr1645v2Lan3MCVlanEntry 100990976}

sr1645v2Lan3MCVlanIpV6DhcpIaid OBJECT-TYPE
   SYNTAX      Counter32
   MAX-ACCESS  read-only
   STATUS      current
   DESCRIPTION
      "Path: ethernet3.status.vlan.ipV6.dhcp.iaid

       32 bit unsigned wrappable counter."
   ::= {sr1645v2Lan3MCVlanEntry 101056768}

sr1645v2Lan3MCVlanIpV6RaRcvOption OBJECT-TYPE
   SYNTAX      Integer32
   MAX-ACCESS  read-only
   STATUS      current
   DESCRIPTION
      "Path: ethernet3.status.vlan.ipV6.raRcvOption

       Bit meanings:
               bit 0 = linkMtu,
               bit 1 = srcLinkLayer,
               bit 2 = prefixInfo,
               bit 3 = rdnss,
               bit 4 = dnssl"
   ::= {sr1645v2Lan3MCVlanEntry 101122048}

sr1645v2Lan3MCVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.vlan.bridging.status

       Possibilities:
               disabled   (0)
               discarding   (1)
               learning   (2)
               forwarding   (3)
               backupBlockedIntfDown   (256)
               backupBlockedIntfUp   (259)
               shutdown   (255)"
   ::= {sr1645v2Lan3MCVlanEntry 453050368}

sr1645v2Lan3MCVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.vlan.bridging.spanningTree.portRole

       Possibilities:
               none   (0)
               root   (1)
               designated   (2)
               alternate   (3)
               backup   (4)
               disabled   (5)
               master   (6)"
   ::= {sr1645v2Lan3MCVlanEntry 453116160}

sr1645v2Lan3MCVlanBridgingSpanningTreePortId OBJECT-TYPE
   SYNTAX      Integer32
   MAX-ACCESS  read-only
   STATUS      current
   DESCRIPTION
      "Path: ethernet3.status.vlan.bridging.spanningTree.portId"
   ::= {sr1645v2Lan3MCVlanEntry 453116416}

sr1645v2Lan3MCVlanBridgingSpanningTreePpCostExtPathCost OBJECT-TYPE
   SYNTAX      Integer32
   MAX-ACCESS  read-only
   STATUS      current
   DESCRIPTION
      "Path: ethernet3.status.vlan.bridging.spanningTree.portPathCosts.extPathCost"
   ::= {sr1645v2Lan3MCVlanEntry 453116673}

sr1645v2Lan3MCVlanBridgingSpanningTreePpCostIntPathCost OBJECT-TYPE
   SYNTAX      Integer32
   MAX-ACCESS  read-only
   STATUS      current
   DESCRIPTION
      "Path: ethernet3.status.vlan.bridging.spanningTree.portPathCosts.intPathCost"
   ::= {sr1645v2Lan3MCVlanEntry 453116674}

sr1645v2Lan3MCVlanBridgingSpanningTreeExtRpCost OBJECT-TYPE
   SYNTAX      Integer32
   MAX-ACCESS  read-only
   STATUS      current
   DESCRIPTION
      "Path: ethernet3.status.vlan.bridging.spanningTree.extRootPathCost"
   ::= {sr1645v2Lan3MCVlanEntry 453116928}

sr1645v2Lan3MCVlanBridgingSpanningTreeIntRpCost OBJECT-TYPE
   SYNTAX      Integer32
   MAX-ACCESS  read-only
   STATUS      current
   DESCRIPTION
      "Path: ethernet3.status.vlan.bridging.spanningTree.intRootPathCost"
   ::= {sr1645v2Lan3MCVlanEntry 453117184}

sr1645v2Lan3MCVlanBridgingSpanningTreeDesBrIdPriority OBJECT-TYPE
   SYNTAX      Integer32
   MAX-ACCESS  read-only
   STATUS      current
   DESCRIPTION
      "Path: ethernet3.status.vlan.bridging.spanningTree.designatedBridgeId.priority"
   ::= {sr1645v2Lan3MCVlanEntry 453117441}

sr1645v2Lan3MCVlanBridgingSpanningTreeDesBrIdMacAddress OBJECT-TYPE
   SYNTAX      OCTET STRING
   MAX-ACCESS  read-only
   STATUS      current
   DESCRIPTION
      "Path: ethernet3.status.vlan.bridging.spanningTree.designatedBridgeId.macAddress

       MAC address."
   ::= {sr1645v2Lan3MCVlanEntry 453117442}

sr1645v2Lan3MCVlanBridgingSpanningTreeDesPrtId OBJECT-TYPE
   SYNTAX      Integer32
   MAX-ACCESS  read-only
   STATUS      current
   DESCRIPTION
      "Path: ethernet3.status.vlan.bridging.spanningTree.designatedPortId"
   ::= {sr1645v2Lan3MCVlanEntry 453117696}

sr1645v2Lan3MCVlanBridgingSpanningTreeDesInt OBJECT-TYPE
   SYNTAX      INTEGER
               {
               no (0),
               yes (1)
               }
   MAX-ACCESS  read-only
   STATUS      current
   DESCRIPTION
      "Path: ethernet3.status.vlan.bridging.spanningTree.designatedOrInternal

       Possibilities:
               no   (0)
               yes   (1)"
   ::= {sr1645v2Lan3MCVlanEntry 453117952}

sr1645v2Lan3MCVlanBridgingSpanningTreeEdgeDetection OBJECT-TYPE
   SYNTAX      INTEGER
               {
               none (0),
               edge (1),
               notEdge (2)
               }
   MAX-ACCESS  read-only
   STATUS      current
   DESCRIPTION
      "Path: ethernet3.status.vlan.bridging.spanningTree.edgeDetection

       Possibilities:
               none   (0)
               edge   (1)
               notEdge   (2)"
   ::= {sr1645v2Lan3MCVlanEntry 453118208}

sr1645v2Lan3MCVlanVlanVid OBJECT-TYPE
   SYNTAX      Integer32
   MAX-ACCESS  read-only
   STATUS      current
   DESCRIPTION
      "Path: ethernet3.status.vlan.vlan.vid"
   ::= {sr1645v2Lan3MCVlanEntry 234946560}

sr1645v2Lan3MCVlanPppOEthDiscState OBJECT-TYPE
   SYNTAX      INTEGER
               {
               idle (0),
               waitForPADO (1),
               waitForPADS (2),
               established (3)
               }
   MAX-ACCESS  read-only
   STATUS      current
   DESCRIPTION
      "Path: ethernet3.status.vlan.pppOverEth.discState

       Possibilities:
               idle   (0)
               waitForPADO   (1)
               waitForPADS   (2)
               established   (3)"
   ::= {sr1645v2Lan3MCVlanEntry 67174400}

sr1645v2Lan3MCVlanPppOEthPeerMac OBJECT-TYPE
   SYNTAX      OCTET STRING
   MAX-ACCESS  read-only
   STATUS      current
   DESCRIPTION
      "Path: ethernet3.status.vlan.pppOverEth.remoteMacAddress

       MAC address."
   ::= {sr1645v2Lan3MCVlanEntry 67239936}

sr1645v2Lan3MCVlanPppOEthServiceName OBJECT-TYPE
   SYNTAX      DisplayString
   MAX-ACCESS  read-only
   STATUS      current
   DESCRIPTION
      "Path: ethernet3.status.vlan.pppOverEth.serviceName"
   ::= {sr1645v2Lan3MCVlanEntry 67305472}

sr1645v2Lan3MCVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCVlanEntry 83951616}

sr1645v2Lan3MCVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCVlanEntry 84017152}

sr1645v2Lan3MCVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCVlanEntry 84869120}

sr1645v2Lan3MCVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan3MCVlanEntry 84541440}

sr1645v2Lan3MCVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan3MCVlanEntry 84606976}

sr1645v2Lan3MCVlanPppMru OBJECT-TYPE
   SYNTAX      Integer32
   MAX-ACCESS  read-only
   STATUS      current
   DESCRIPTION
      "Path: ethernet3.status.vlan.ppp.mru"
   ::= {sr1645v2Lan3MCVlanEntry 84934656}

sr1645v2Lan3MCVlanIpSecondaryIp OBJECT-TYPE
   SYNTAX      SEQUENCE OF Sr1645v2Lan3MCVlanIpSecondaryIpEntry
   MAX-ACCESS  not-accessible
   STATUS      current
   DESCRIPTION
      ""
   ::= {sr1645v2Lan3MCVlan 51838976}

sr1645v2Lan3MCVlanIpSecondaryIpEntry OBJECT-TYPE
   SYNTAX      Sr1645v2Lan3MCVlanIpSecondaryIpEntry
   MAX-ACCESS  not-accessible
   STATUS      current
   DESCRIPTION
      ""
   INDEX      { sr1645v2Lan3MCVlanTableIx,
                sr1645v2Lan3MCVlanIpSecondaryIpTableIx }
   ::= {sr1645v2Lan3MCVlanIpSecondaryIp 1}

Sr1645v2Lan3MCVlanIpSecondaryIpEntry ::=
   SEQUENCE
      {
      sr1645v2Lan3MCVlanIpSecondaryIpTableIx
         TableIndex,
      sr1645v2Lan3MCVlanIpSecondaryIpAddress
         IpAddress,
      sr1645v2Lan3MCVlanIpSecondaryIpNetMask
         IpAddress
      }

sr1645v2Lan3MCVlanIpSecondaryIpTableIx OBJECT-TYPE
   SYNTAX      TableIndex
   MAX-ACCESS  not-accessible
   STATUS      current
   DESCRIPTION
      ""
   ::= {sr1645v2Lan3MCVlanIpSecondaryIpEntry 11}

sr1645v2Lan3MCVlanIpSecondaryIpAddress OBJECT-TYPE
   SYNTAX      IpAddress
   MAX-ACCESS  read-only
   STATUS      current
   DESCRIPTION
      "Path: ethernet3.status.vlan.ip.secondaryIp.address"
   ::= {sr1645v2Lan3MCVlanIpSecondaryIpEntry 2030043136}

sr1645v2Lan3MCVlanIpSecondaryIpNetMask OBJECT-TYPE
   SYNTAX      IpAddress
   MAX-ACCESS  read-only
   STATUS      current
   DESCRIPTION
      "Path: ethernet3.status.vlan.ip.secondaryIp.netMask"
   ::= {sr1645v2Lan3MCVlanIpSecondaryIpEntry 2063597568}

sr1645v2Lan3MCVlanIpV6Addresses OBJECT-TYPE
   SYNTAX      SEQUENCE OF Sr1645v2Lan3MCVlanIpV6AddressesEntry
   MAX-ACCESS  not-accessible
   STATUS      current
   DESCRIPTION
      ""
   ::= {sr1645v2Lan3MCVlan 100859904}

sr1645v2Lan3MCVlanIpV6AddressesEntry OBJECT-TYPE
   SYNTAX      Sr1645v2Lan3MCVlanIpV6AddressesEntry
   MAX-ACCESS  not-accessible
   STATUS      current
   DESCRIPTION
      ""
   INDEX      { sr1645v2Lan3MCVlanTableIx,
                sr1645v2Lan3MCVlanIpV6AddressesTableIx }
   ::= {sr1645v2Lan3MCVlanIpV6Addresses 1}

Sr1645v2Lan3MCVlanIpV6AddressesEntry ::=
   SEQUENCE
      {
      sr1645v2Lan3MCVlanIpV6AddressesTableIx
         TableIndex,
      sr1645v2Lan3MCVlanIpV6AddressesAddress
         Ipv6Address,
      sr1645v2Lan3MCVlanIpV6AddressesPrefixLength
         Integer32,
      sr1645v2Lan3MCVlanIpV6AddressesStatus
         INTEGER,
      sr1645v2Lan3MCVlanIpV6AddressesOrigin
         INTEGER,
      sr1645v2Lan3MCVlanIpV6AddressesFlagsInterfaceId
         INTEGER,
      sr1645v2Lan3MCVlanIpV6AddressesFlagsAnycast
         INTEGER,
      sr1645v2Lan3MCVlanIpV6AddressesTimersValidLifeTime
         TimeTicks,
      sr1645v2Lan3MCVlanIpV6AddressesTimersPrefLifeTime
         TimeTicks
      }

sr1645v2Lan3MCVlanIpV6AddressesTableIx OBJECT-TYPE
   SYNTAX      TableIndex
   MAX-ACCESS  not-accessible
   STATUS      current
   DESCRIPTION
      ""
   ::= {sr1645v2Lan3MCVlanIpV6AddressesEntry 11}

sr1645v2Lan3MCVlanIpV6AddressesAddress OBJECT-TYPE
   SYNTAX      Ipv6Address
   MAX-ACCESS  read-only
   STATUS      current
   DESCRIPTION
      "Path: ethernet3.status.vlan.ipV6.addresses.address

       ipv6 address"
   ::= {sr1645v2Lan3MCVlanIpV6AddressesEntry 16777216}

sr1645v2Lan3MCVlanIpV6AddressesPrefixLength OBJECT-TYPE
   SYNTAX      Integer32
   MAX-ACCESS  read-only
   STATUS      current
   DESCRIPTION
      "Path: ethernet3.status.vlan.ipV6.addresses.prefixLength"
   ::= {sr1645v2Lan3MCVlanIpV6AddressesEntry 33554432}

sr1645v2Lan3MCVlanIpV6AddressesStatus OBJECT-TYPE
   SYNTAX      INTEGER
               {
               invalid (0),
               tentative (1),
               deprecated (2),
               preferred (3)
               }
   MAX-ACCESS  read-only
   STATUS      current
   DESCRIPTION
      "Path: ethernet3.status.vlan.ipV6.addresses.status

       Possibilities:
               invalid   (0)
               tentative   (1)
               deprecated   (2)
               preferred   (3)"
   ::= {sr1645v2Lan3MCVlanIpV6AddressesEntry 50331648}

sr1645v2Lan3MCVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.vlan.ipV6.addresses.origin

       Possibilities:
               unknown   (0)
               manual   (1)
               generalPrefix   (2)
               statelessAuto   (3)
               statefullAuto   (4)"
   ::= {sr1645v2Lan3MCVlanIpV6AddressesEntry 67108864}

sr1645v2Lan3MCVlanIpV6AddressesFlagsInterfaceId OBJECT-TYPE
   SYNTAX      INTEGER
               {
               no (0),
               yes (1)
               }
   MAX-ACCESS  read-only
   STATUS      current
   DESCRIPTION
      "Path: ethernet3.status.vlan.ipV6.addresses.flags.interfaceId

       Possibilities:
               no   (0)
               yes   (1)"
   ::= {sr1645v2Lan3MCVlanIpV6AddressesEntry 83951616}

sr1645v2Lan3MCVlanIpV6AddressesFlagsAnycast OBJECT-TYPE
   SYNTAX      INTEGER
               {
               no (0),
               yes (1)
               }
   MAX-ACCESS  read-only
   STATUS      current
   DESCRIPTION
      "Path: ethernet3.status.vlan.ipV6.addresses.flags.anycast

       Possibilities:
               no   (0)
               yes   (1)"
   ::= {sr1645v2Lan3MCVlanIpV6AddressesEntry 84017152}

sr1645v2Lan3MCVlanIpV6AddressesTimersValidLifeTime OBJECT-TYPE
   SYNTAX      TimeTicks
   MAX-ACCESS  read-only
   STATUS      current
   DESCRIPTION
      "Path: ethernet3.status.vlan.ipV6.addresses.timers.validLifeTime

       Time in centi-second."
   ::= {sr1645v2Lan3MCVlanIpV6AddressesEntry 100794368}

sr1645v2Lan3MCVlanIpV6AddressesTimersPrefLifeTime OBJECT-TYPE
   SYNTAX      TimeTicks
   MAX-ACCESS  read-only
   STATUS      current
   DESCRIPTION
      "Path: ethernet3.status.vlan.ipV6.addresses.timers.prefLifeTime

       Time in centi-second."
   ::= {sr1645v2Lan3MCVlanIpV6AddressesEntry 100728832}

sr1645v2Lan3MCVlanVlanArpCache OBJECT-TYPE
   SYNTAX      SEQUENCE OF Sr1645v2Lan3MCVlanVlanArpCacheEntry
   MAX-ACCESS  not-accessible
   STATUS      current
   DESCRIPTION
      ""
   ::= {sr1645v2Lan3MCVlan 235601920}

sr1645v2Lan3MCVlanVlanArpCacheEntry OBJECT-TYPE
   SYNTAX      Sr1645v2Lan3MCVlanVlanArpCacheEntry
   MAX-ACCESS  not-accessible
   STATUS      current
   DESCRIPTION
      ""
   INDEX      { sr1645v2Lan3MCVlanTableIx,
                sr1645v2Lan3MCVlanVlanArpCacheTableIx }
   ::= {sr1645v2Lan3MCVlanVlanArpCache 1}

Sr1645v2Lan3MCVlanVlanArpCacheEntry ::=
   SEQUENCE
      {
      sr1645v2Lan3MCVlanVlanArpCacheTableIx
         TableIndex,
      sr1645v2Lan3MCVlanVlanArpCacheMacAddress
         OCTET STRING,
      sr1645v2Lan3MCVlanVlanArpCacheIpAddress
         IpAddress,
      sr1645v2Lan3MCVlanVlanArpCacheType
         INTEGER,
      sr1645v2Lan3MCVlanVlanArpCacheTimeOut
         TimeTicks
      }

sr1645v2Lan3MCVlanVlanArpCacheTableIx OBJECT-TYPE
   SYNTAX      TableIndex
   MAX-ACCESS  not-accessible
   STATUS      current
   DESCRIPTION
      ""
   ::= {sr1645v2Lan3MCVlanVlanArpCacheEntry 11}

sr1645v2Lan3MCVlanVlanArpCacheMacAddress OBJECT-TYPE
   SYNTAX      OCTET STRING
   MAX-ACCESS  read-only
   STATUS      current
   DESCRIPTION
      "Path: ethernet3.status.vlan.vlan.arpCache.macAddress

       MAC address."
   ::= {sr1645v2Lan3MCVlanVlanArpCacheEntry 16777216}

sr1645v2Lan3MCVlanVlanArpCacheIpAddress OBJECT-TYPE
   SYNTAX      IpAddress
   MAX-ACCESS  read-only
   STATUS      current
   DESCRIPTION
      "Path: ethernet3.status.vlan.vlan.arpCache.ipAddress"
   ::= {sr1645v2Lan3MCVlanVlanArpCacheEntry 33554432}

sr1645v2Lan3MCVlanVlanArpCacheType OBJECT-TYPE
   SYNTAX      INTEGER
               {
               static (0),
               dynamic (1)
               }
   MAX-ACCESS  read-only
   STATUS      current
   DESCRIPTION
      "Path: ethernet3.status.vlan.vlan.arpCache.type

       Possibilities:
               static   (0)
               dynamic   (1)"
   ::= {sr1645v2Lan3MCVlanVlanArpCacheEntry 50331648}

sr1645v2Lan3MCVlanVlanArpCacheTimeOut OBJECT-TYPE
   SYNTAX      TimeTicks
   MAX-ACCESS  read-only
   STATUS      current
   DESCRIPTION
      "Path: ethernet3.status.vlan.vlan.arpCache.timeOut

       Time in centi-second."
   ::= {sr1645v2Lan3MCVlanVlanArpCacheEntry 67108864}


sr1645v2Lan3MCPppOE OBJECT IDENTIFIER ::= {sr1645v2Lan3MC 36}

sr1645v2Lan3MCPppOESSCTable OBJECT-TYPE
   SYNTAX      SEQUENCE OF Sr1645v2Lan3MCPppOEEntry
   MAX-ACCESS  not-accessible
   STATUS      current
   DESCRIPTION
      ""
   ::= {sr1645v2Lan3MCPppOE 1}

sr1645v2Lan3MCPppOEEntry OBJECT-TYPE
   SYNTAX      Sr1645v2Lan3MCPppOEEntry
   MAX-ACCESS  not-accessible
   STATUS      current
   DESCRIPTION
      ""
   INDEX      { sr1645v2Lan3MCPppOETableIx }
   ::= {sr1645v2Lan3MCPppOESSCTable 1}

Sr1645v2Lan3MCPppOEEntry ::=
   SEQUENCE
      {
      sr1645v2Lan3MCPppOETableIx
         TableIndex,
      sr1645v2Lan3MCPppOEName
         DisplayString,
      sr1645v2Lan3MCPppOEMode
         INTEGER,
      sr1645v2Lan3MCPppOEIfOperStatus
         INTEGER,
      sr1645v2Lan3MCPppOEIfLastChange
         TimeTicks,
      sr1645v2Lan3MCPppOEIfLastChangeDate
         DisplayString,
      sr1645v2Lan3MCPppOEIpAddress
         IpAddress,
      sr1645v2Lan3MCPppOEIpNetMask
         IpAddress,
      sr1645v2Lan3MCPppOEIpRemote
         IpAddress,
      sr1645v2Lan3MCPppOEPppOEthDiscState
         INTEGER,
      sr1645v2Lan3MCPppOEPppOEthPeerMac
         OCTET STRING,
      sr1645v2Lan3MCPppOEPppOEthServiceName
         DisplayString,
      sr1645v2Lan3MCPppOEPppLcpState
         INTEGER,
      sr1645v2Lan3MCPppOEPppIpcpState
         INTEGER,
      sr1645v2Lan3MCPppOEPppIp6cpState
         INTEGER,
      sr1645v2Lan3MCPppOEPppMyAutSt
         INTEGER,
      sr1645v2Lan3MCPppOEPppHisAutSt
         INTEGER,
      sr1645v2Lan3MCPppOEPppMru
         Integer32,
      sr1645v2Lan3MCPppOEIpV6State
         INTEGER,
      sr1645v2Lan3MCPppOEIpV6InterfaceId
         OCTET STRING,
      sr1645v2Lan3MCPppOEIpV6LinkMtu
         Integer32,
      sr1645v2Lan3MCPppOEIpV6HopLimit
         Integer32,
      sr1645v2Lan3MCPppOEIpV6DhcpIaid
         Counter32,
      sr1645v2Lan3MCPppOEIpV6RaRcvOption
         Integer32
      }

sr1645v2Lan3MCPppOETableIx OBJECT-TYPE
   SYNTAX      TableIndex
   MAX-ACCESS  not-accessible
   STATUS      current
   DESCRIPTION
      ""
   ::= {sr1645v2Lan3MCPppOEEntry 11}

sr1645v2Lan3MCPppOEName OBJECT-TYPE
   SYNTAX      DisplayString
   MAX-ACCESS  read-only
   STATUS      current
   DESCRIPTION
      "Path: ethernet3.status.pppoEClient.name"
   ::= {sr1645v2Lan3MCPppOEEntry 16777216}

sr1645v2Lan3MCPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan3MCPppOEEntry 335544320}

sr1645v2Lan3MCPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.pppoEClient.ifOperStatus

       Possibilities:
               up   (1)
               down   (2)
               testing   (3)
               unknown   (4)
               dormant   (5)
               notPresent   (6)
               lowerLayerDown   (7)"
   ::= {sr1645v2Lan3MCPppOEEntry 1795162112}

sr1645v2Lan3MCPppOEIfLastChange OBJECT-TYPE
   SYNTAX      TimeTicks
   MAX-ACCESS  read-only
   STATUS      current
   DESCRIPTION
      "Path: ethernet3.status.pppoEClient.ifLastChange

       Time in centi-second."
   ::= {sr1645v2Lan3MCPppOEEntry 1811939328}

sr1645v2Lan3MCPppOEIfLastChangeDate OBJECT-TYPE
   SYNTAX      DisplayString
   MAX-ACCESS  read-only
   STATUS      current
   DESCRIPTION
      "Path: ethernet3.status.pppoEClient.ifLastChangeDate"
   ::= {sr1645v2Lan3MCPppOEEntry 3070230528}

sr1645v2Lan3MCPppOEIpAddress OBJECT-TYPE
   SYNTAX      IpAddress
   MAX-ACCESS  read-only
   STATUS      current
   DESCRIPTION
      "Path: ethernet3.status.pppoEClient.ip.address"
   ::= {sr1645v2Lan3MCPppOEEntry 51380224}

sr1645v2Lan3MCPppOEIpNetMask OBJECT-TYPE
   SYNTAX      IpAddress
   MAX-ACCESS  read-only
   STATUS      current
   DESCRIPTION
      "Path: ethernet3.status.pppoEClient.ip.netMask"
   ::= {sr1645v2Lan3MCPppOEEntry 51445760}

sr1645v2Lan3MCPppOEIpRemote OBJECT-TYPE
   SYNTAX      IpAddress
   MAX-ACCESS  read-only
   STATUS      current
   DESCRIPTION
      "Path: ethernet3.status.pppoEClient.ip.remote"
   ::= {sr1645v2Lan3MCPppOEEntry 51511296}

sr1645v2Lan3MCPppOEPppOEthDiscState OBJECT-TYPE
   SYNTAX      INTEGER
               {
               idle (0),
               waitForPADO (1),
               waitForPADS (2),
               established (3)
               }
   MAX-ACCESS  read-only
   STATUS      current
   DESCRIPTION
      "Path: ethernet3.status.pppoEClient.pppOverEth.discState

       Possibilities:
               idle   (0)
               waitForPADO   (1)
               waitForPADS   (2)
               established   (3)"
   ::= {sr1645v2Lan3MCPppOEEntry 67174400}

sr1645v2Lan3MCPppOEPppOEthPeerMac OBJECT-TYPE
   SYNTAX      OCTET STRING
   MAX-ACCESS  read-only
   STATUS      current
   DESCRIPTION
      "Path: ethernet3.status.pppoEClient.pppOverEth.remoteMacAddress

       MAC address."
   ::= {sr1645v2Lan3MCPppOEEntry 67239936}

sr1645v2Lan3MCPppOEPppOEthServiceName OBJECT-TYPE
   SYNTAX      DisplayString
   MAX-ACCESS  read-only
   STATUS      current
   DESCRIPTION
      "Path: ethernet3.status.pppoEClient.pppOverEth.serviceName"
   ::= {sr1645v2Lan3MCPppOEEntry 67305472}

sr1645v2Lan3MCPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCPppOEEntry 83951616}

sr1645v2Lan3MCPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCPppOEEntry 84017152}

sr1645v2Lan3MCPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan3MCPppOEEntry 84869120}

sr1645v2Lan3MCPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan3MCPppOEEntry 84541440}

sr1645v2Lan3MCPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan3MCPppOEEntry 84606976}

sr1645v2Lan3MCPppOEPppMru OBJECT-TYPE
   SYNTAX      Integer32
   MAX-ACCESS  read-only
   STATUS      current
   DESCRIPTION
      "Path: ethernet3.status.pppoEClient.ppp.mru"
   ::= {sr1645v2Lan3MCPppOEEntry 84934656}

sr1645v2Lan3MCPppOEIpV6State OBJECT-TYPE
   SYNTAX      INTEGER
               {
               disabled (0),
               enabled (1)
               }
   MAX-ACCESS  read-only
   STATUS      current
   DESCRIPTION
      "Path: ethernet3.status.pppoEClient.ipV6.state

       Possibilities:
               disabled   (0)
               enabled   (1)"
   ::= {sr1645v2Lan3MCPppOEEntry 100728832}

sr1645v2Lan3MCPppOEIpV6InterfaceId OBJECT-TYPE
   SYNTAX      OCTET STRING
   MAX-ACCESS  read-only
   STATUS      current
   DESCRIPTION
      "Path: ethernet3.status.pppoEClient.ipV6.interfaceId"
   ::= {sr1645v2Lan3MCPppOEEntry 100794368}

sr1645v2Lan3MCPppOEIpV6LinkMtu OBJECT-TYPE
   SYNTAX      Integer32
   MAX-ACCESS  read-only
   STATUS      current
   DESCRIPTION
      "Path: ethernet3.status.pppoEClient.ipV6.linkMtu"
   ::= {sr1645v2Lan3MCPppOEEntry 100925440}

sr1645v2Lan3MCPppOEIpV6HopLimit OBJECT-TYPE
   SYNTAX      Integer32
   MAX-ACCESS  read-only
   STATUS      current
   DESCRIPTION
      "Path: ethernet3.status.pppoEClient.ipV6.hopLimit"
   ::= {sr1645v2Lan3MCPppOEEntry 100990976}

sr1645v2Lan3MCPppOEIpV6DhcpIaid OBJECT-TYPE
   SYNTAX      Counter32
   MAX-ACCESS  read-only
   STATUS      current
   DESCRIPTION
      "Path: ethernet3.status.pppoEClient.ipV6.dhcp.iaid

       32 bit unsigned wrappable counter."
   ::= {sr1645v2Lan3MCPppOEEntry 101056768}

sr1645v2Lan3MCPppOEIpV6RaRcvOption OBJECT-TYPE
   SYNTAX      Integer32
   MAX-ACCESS  read-only
   STATUS      current
   DESCRIPTION
      "Path: ethernet3.status.pppoEClient.ipV6.raRcvOption

       Bit meanings:
               bit 0 = linkMtu,
               bit 1 = srcLinkLayer,
               bit 2 = prefixInfo,
               bit 3 = rdnss,
               bit 4 = dnssl"
   ::= {sr1645v2Lan3MCPppOEEntry 101122048}

sr1645v2Lan3MCPppOEIpV6Addresses OBJECT-TYPE
   SYNTAX      SEQUENCE OF Sr1645v2Lan3MCPppOEIpV6AddressesEntry
   MAX-ACCESS  not-accessible
   STATUS      current
   DESCRIPTION
      ""
   ::= {sr1645v2Lan3MCPppOE 100859904}

sr1645v2Lan3MCPppOEIpV6AddressesEntry OBJECT-TYPE
   SYNTAX      Sr1645v2Lan3MCPppOEIpV6AddressesEntry
   MAX-ACCESS  not-accessible
   STATUS      current
   DESCRIPTION
      ""
   INDEX      { sr1645v2Lan3MCPppOETableIx,
                sr1645v2Lan3MCPppOEIpV6AddressesTableIx }
   ::= {sr1645v2Lan3MCPppOEIpV6Addresses 1}

Sr1645v2Lan3MCPppOEIpV6AddressesEntry ::=
   SEQUENCE
      {
      sr1645v2Lan3MCPppOEIpV6AddressesTableIx
         TableIndex,
      sr1645v2Lan3MCPppOEIpV6AddressesAddress
         Ipv6Address,
      sr1645v2Lan3MCPppOEIpV6AddressesPrefixLength
         Integer32,
      sr1645v2Lan3MCPppOEIpV6AddressesStatus
         INTEGER,
      sr1645v2Lan3MCPppOEIpV6AddressesOrigin
         INTEGER,
      sr1645v2Lan3MCPppOEIpV6AddressesFlagsInterfaceId
         INTEGER,
      sr1645v2Lan3MCPppOEIpV6AddressesFlagsAnycast
         INTEGER,
      sr1645v2Lan3MCPppOEIpV6AddressesTimersValidLifeTime
         TimeTicks,
      sr1645v2Lan3MCPppOEIpV6AddressesTimersPrefLifeTime
         TimeTicks
      }

sr1645v2Lan3MCPppOEIpV6AddressesTableIx OBJECT-TYPE
   SYNTAX      TableIndex
   MAX-ACCESS  not-accessible
   STATUS      current
   DESCRIPTION
      ""
   ::= {sr1645v2Lan3MCPppOEIpV6AddressesEntry 11}

sr1645v2Lan3MCPppOEIpV6AddressesAddress OBJECT-TYPE
   SYNTAX      Ipv6Address
   MAX-ACCESS  read-only
   STATUS      current
   DESCRIPTION
      "Path: ethernet3.status.pppoEClient.ipV6.addresses.address

       ipv6 address"
   ::= {sr1645v2Lan3MCPppOEIpV6AddressesEntry 16777216}

sr1645v2Lan3MCPppOEIpV6AddressesPrefixLength OBJECT-TYPE
   SYNTAX      Integer32
   MAX-ACCESS  read-only
   STATUS      current
   DESCRIPTION
      "Path: ethernet3.status.pppoEClient.ipV6.addresses.prefixLength"
   ::= {sr1645v2Lan3MCPppOEIpV6AddressesEntry 33554432}

sr1645v2Lan3MCPppOEIpV6AddressesStatus OBJECT-TYPE
   SYNTAX      INTEGER
               {
               invalid (0),
               tentative (1),
               deprecated (2),
               preferred (3)
               }
   MAX-ACCESS  read-only
   STATUS      current
   DESCRIPTION
      "Path: ethernet3.status.pppoEClient.ipV6.addresses.status

       Possibilities:
               invalid   (0)
               tentative   (1)
               deprecated   (2)
               preferred   (3)"
   ::= {sr1645v2Lan3MCPppOEIpV6AddressesEntry 50331648}

sr1645v2Lan3MCPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.pppoEClient.ipV6.addresses.origin

       Possibilities:
               unknown   (0)
               manual   (1)
               generalPrefix   (2)
               statelessAuto   (3)
               statefullAuto   (4)"
   ::= {sr1645v2Lan3MCPppOEIpV6AddressesEntry 67108864}

sr1645v2Lan3MCPppOEIpV6AddressesFlagsInterfaceId OBJECT-TYPE
   SYNTAX      INTEGER
               {
               no (0),
               yes (1)
               }
   MAX-ACCESS  read-only
   STATUS      current
   DESCRIPTION
      "Path: ethernet3.status.pppoEClient.ipV6.addresses.flags.interfaceId

       Possibilities:
               no   (0)
               yes   (1)"
   ::= {sr1645v2Lan3MCPppOEIpV6AddressesEntry 83951616}

sr1645v2Lan3MCPppOEIpV6AddressesFlagsAnycast OBJECT-TYPE
   SYNTAX      INTEGER
               {
               no (0),
               yes (1)
               }
   MAX-ACCESS  read-only
   STATUS      current
   DESCRIPTION
      "Path: ethernet3.status.pppoEClient.ipV6.addresses.flags.anycast

       Possibilities:
               no   (0)
               yes   (1)"
   ::= {sr1645v2Lan3MCPppOEIpV6AddressesEntry 84017152}

sr1645v2Lan3MCPppOEIpV6AddressesTimersValidLifeTime OBJECT-TYPE
   SYNTAX      TimeTicks
   MAX-ACCESS  read-only
   STATUS      current
   DESCRIPTION
      "Path: ethernet3.status.pppoEClient.ipV6.addresses.timers.validLifeTime

       Time in centi-second."
   ::= {sr1645v2Lan3MCPppOEIpV6AddressesEntry 100794368}

sr1645v2Lan3MCPppOEIpV6AddressesTimersPrefLifeTime OBJECT-TYPE
   SYNTAX      TimeTicks
   MAX-ACCESS  read-only
   STATUS      current
   DESCRIPTION
      "Path: ethernet3.status.pppoEClient.ipV6.addresses.timers.prefLifeTime

       Time in centi-second."
   ::= {sr1645v2Lan3MCPppOEIpV6AddressesEntry 100728832}


sr1645v2Lan3MCDot1x OBJECT IDENTIFIER ::= {sr1645v2Lan3MC 190}

sr1645v2Lan3MCDot1xSSCTable OBJECT-TYPE
   SYNTAX      SEQUENCE OF Sr1645v2Lan3MCDot1xEntry
   MAX-ACCESS  not-accessible
   STATUS      current
   DESCRIPTION
      "Ethernet Switch VLAN Table"
   ::= {sr1645v2Lan3MCDot1x 1}

sr1645v2Lan3MCDot1xEntry OBJECT-TYPE
   SYNTAX      Sr1645v2Lan3MCDot1xEntry
   MAX-ACCESS  not-accessible
   STATUS      current
   DESCRIPTION
      ""
   INDEX      { sr1645v2Lan3MCDot1xTableIx }
   ::= {sr1645v2Lan3MCDot1xSSCTable 1}

Sr1645v2Lan3MCDot1xEntry ::=
   SEQUENCE
      {
      sr1645v2Lan3MCDot1xTableIx
         TableIndex,
      sr1645v2Lan3MCDot1xRemote
         OCTET STRING,
      sr1645v2Lan3MCDot1xAuthorized
         INTEGER,
      sr1645v2Lan3MCDot1xAuthenticator
         INTEGER,
      sr1645v2Lan3MCDot1xBackEnd
         INTEGER,
      sr1645v2Lan3MCDot1xRetries
         Integer32,
      sr1645v2Lan3MCDot1xReAuthTime
         TimeTicks,
      sr1645v2Lan3MCDot1xHoldTime
         TimeTicks
      }

sr1645v2Lan3MCDot1xTableIx OBJECT-TYPE
   SYNTAX      TableIndex
   MAX-ACCESS  not-accessible
   STATUS      current
   DESCRIPTION
      ""
   ::= {sr1645v2Lan3MCDot1xEntry 11}

sr1645v2Lan3MCDot1xRemote OBJECT-TYPE
   SYNTAX      OCTET STRING
   MAX-ACCESS  read-only
   STATUS      current
   DESCRIPTION
      "Path: ethernet3.status.dot1x.remote

       MAC address."
   ::= {sr1645v2Lan3MCDot1xEntry 16777216}

sr1645v2Lan3MCDot1xAuthorized OBJECT-TYPE
   SYNTAX      INTEGER
               {
               no (0),
               yes (1)
               }
   MAX-ACCESS  read-only
   STATUS      current
   DESCRIPTION
      "Path: ethernet3.status.dot1x.authorized

       Possibilities:
               no   (0)
               yes   (1)"
   ::= {sr1645v2Lan3MCDot1xEntry 33554432}

sr1645v2Lan3MCDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet3.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2Lan3MCDot1xEntry 50331648}

sr1645v2Lan3MCDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet3.status.dot1x.backEnd

       Possibilities:
               preInit   (0)
               initialize   (1)
               idle   (2)
               request   (3)
               response   (4)
               success   (5)
               failure   (6)
               radiusTimeout   (7)
               timeout   (8)"
   ::= {sr1645v2Lan3MCDot1xEntry 67108864}

sr1645v2Lan3MCDot1xRetries OBJECT-TYPE
   SYNTAX      Integer32
   MAX-ACCESS  read-only
   STATUS      current
   DESCRIPTION
      "Path: ethernet3.status.dot1x.retries"
   ::= {sr1645v2Lan3MCDot1xEntry 83886080}

sr1645v2Lan3MCDot1xReAuthTime OBJECT-TYPE
   SYNTAX      TimeTicks
   MAX-ACCESS  read-only
   STATUS      current
   DESCRIPTION
      "Path: ethernet3.status.dot1x.reAuthTime

       Time in centi-second."
   ::= {sr1645v2Lan3MCDot1xEntry 100663296}

sr1645v2Lan3MCDot1xHoldTime OBJECT-TYPE
   SYNTAX      TimeTicks
   MAX-ACCESS  read-only
   STATUS      current
   DESCRIPTION
      "Path: ethernet3.status.dot1x.holdTime

       Time in centi-second."
   ::= {sr1645v2Lan3MCDot1xEntry 117440512}


sr1645v2Lan3MCIpV6 OBJECT IDENTIFIER ::= {sr1645v2Lan3MC 17}

sr1645v2Lan3MCIpV6SSC OBJECT IDENTIFIER ::= {sr1645v2Lan3MCIpV6 1}

sr1645v2Lan3MCIpV6Entry OBJECT IDENTIFIER ::= {sr1645v2Lan3MCIpV6SSC 1}

sr1645v2Lan3MCIpV6State OBJECT-TYPE
   SYNTAX      INTEGER
               {
               disabled (0),
               enabled (1)
               }
   MAX-ACCESS  read-only
   STATUS      current
   DESCRIPTION
      "Path: ethernet3.status.ipV6.state

       Possibilities:
               disabled   (0)
               enabled   (1)"
   ::= {sr1645v2Lan3MCIpV6Entry 16777216}

sr1645v2Lan3MCIpV6InterfaceId OBJECT-TYPE
   SYNTAX      OCTET STRING
   MAX-ACCESS  read-only
   STATUS      current
   DESCRIPTION
      "Path: ethernet3.status.ipV6.interfaceId"
   ::= {sr1645v2Lan3MCIpV6Entry 33554432}

sr1645v2Lan3MCIpV6LinkMtu OBJECT-TYPE
   SYNTAX      Integer32
   MAX-ACCESS  read-only
   STATUS      current
   DESCRIPTION
      "Path: ethernet3.status.ipV6.linkMtu"
   ::= {sr1645v2Lan3MCIpV6Entry 67108864}

sr1645v2Lan3MCIpV6HopLimit OBJECT-TYPE
   SYNTAX      Integer32
   MAX-ACCESS  read-only
   STATUS      current
   DESCRIPTION
      "Path: ethernet3.status.ipV6.hopLimit"
   ::= {sr1645v2Lan3MCIpV6Entry 83886080}

sr1645v2Lan3MCIpV6DhcpIaid OBJECT-TYPE
   SYNTAX      Counter32
   MAX-ACCESS  read-only
   STATUS      current
   DESCRIPTION
      "Path: ethernet3.status.ipV6.dhcp.iaid

       32 bit unsigned wrappable counter."
   ::= {sr1645v2Lan3MCIpV6Entry 100728832}

sr1645v2Lan3MCIpV6RaRcvOption OBJECT-TYPE
   SYNTAX      Integer32
   MAX-ACCESS  read-only
   STATUS      current
   DESCRIPTION
      "Path: ethernet3.status.ipV6.raRcvOption

       Bit meanings:
               bit 0 = linkMtu,
               bit 1 = srcLinkLayer,
               bit 2 = prefixInfo,
               bit 3 = rdnss,
               bit 4 = dnssl"
   ::= {sr1645v2Lan3MCIpV6Entry 117440512}

sr1645v2Lan3MCIpV6Addresses OBJECT-TYPE
   SYNTAX      SEQUENCE OF Sr1645v2Lan3MCIpV6AddressesEntry
   MAX-ACCESS  not-accessible
   STATUS      current
   DESCRIPTION
      ""
   ::= {sr1645v2Lan3MCIpV6 50331648}

sr1645v2Lan3MCIpV6AddressesEntry OBJECT-TYPE
   SYNTAX      Sr1645v2Lan3MCIpV6AddressesEntry
   MAX-ACCESS  not-accessible
   STATUS      current
   DESCRIPTION
      ""
   INDEX      { sr1645v2Lan3MCIpV6AddressesTableIx }
   ::= {sr1645v2Lan3MCIpV6Addresses 1}

Sr1645v2Lan3MCIpV6AddressesEntry ::=
   SEQUENCE
      {
      sr1645v2Lan3MCIpV6AddressesTableIx
         TableIndex,
      sr1645v2Lan3MCIpV6AddressesAddress
         Ipv6Address,
      sr1645v2Lan3MCIpV6AddressesPrefixLength
         Integer32,
      sr1645v2Lan3MCIpV6AddressesStatus
         INTEGER,
      sr1645v2Lan3MCIpV6AddressesOrigin
         INTEGER,
      sr1645v2Lan3MCIpV6AddressesFlagsInterfaceId
         INTEGER,
      sr1645v2Lan3MCIpV6AddressesFlagsAnycast
         INTEGER,
      sr1645v2Lan3MCIpV6AddressesTimersValidLifeTime
         TimeTicks,
      sr1645v2Lan3MCIpV6AddressesTimersPrefLifeTime
         TimeTicks
      }

sr1645v2Lan3MCIpV6AddressesTableIx OBJECT-TYPE
   SYNTAX      TableIndex
   MAX-ACCESS  not-accessible
   STATUS      current
   DESCRIPTION
      ""
   ::= {sr1645v2Lan3MCIpV6AddressesEntry 11}

sr1645v2Lan3MCIpV6AddressesAddress OBJECT-TYPE
   SYNTAX      Ipv6Address
   MAX-ACCESS  read-only
   STATUS      current
   DESCRIPTION
      "Path: ethernet3.status.ipV6.addresses.address

       ipv6 address"
   ::= {sr1645v2Lan3MCIpV6AddressesEntry 16777216}

sr1645v2Lan3MCIpV6AddressesPrefixLength OBJECT-TYPE
   SYNTAX      Integer32
   MAX-ACCESS  read-only
   STATUS      current
   DESCRIPTION
      "Path: ethernet3.status.ipV6.addresses.prefixLength"
   ::= {sr1645v2Lan3MCIpV6AddressesEntry 33554432}

sr1645v2Lan3MCIpV6AddressesStatus OBJECT-TYPE
   SYNTAX      INTEGER
               {
               invalid (0),
               tentative (1),
               deprecated (2),
               preferred (3)
               }
   MAX-ACCESS  read-only
   STATUS      current
   DESCRIPTION
      "Path: ethernet3.status.ipV6.addresses.status

       Possibilities:
               invalid   (0)
               tentative   (1)
               deprecated   (2)
               preferred   (3)"
   ::= {sr1645v2Lan3MCIpV6AddressesEntry 50331648}

sr1645v2Lan3MCIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.ipV6.addresses.origin

       Possibilities:
               unknown   (0)
               manual   (1)
               generalPrefix   (2)
               statelessAuto   (3)
               statefullAuto   (4)"
   ::= {sr1645v2Lan3MCIpV6AddressesEntry 67108864}

sr1645v2Lan3MCIpV6AddressesFlagsInterfaceId OBJECT-TYPE
   SYNTAX      INTEGER
               {
               no (0),
               yes (1)
               }
   MAX-ACCESS  read-only
   STATUS      current
   DESCRIPTION
      "Path: ethernet3.status.ipV6.addresses.flags.interfaceId

       Possibilities:
               no   (0)
               yes   (1)"
   ::= {sr1645v2Lan3MCIpV6AddressesEntry 83951616}

sr1645v2Lan3MCIpV6AddressesFlagsAnycast OBJECT-TYPE
   SYNTAX      INTEGER
               {
               no (0),
               yes (1)
               }
   MAX-ACCESS  read-only
   STATUS      current
   DESCRIPTION
      "Path: ethernet3.status.ipV6.addresses.flags.anycast

       Possibilities:
               no   (0)
               yes   (1)"
   ::= {sr1645v2Lan3MCIpV6AddressesEntry 84017152}

sr1645v2Lan3MCIpV6AddressesTimersValidLifeTime OBJECT-TYPE
   SYNTAX      TimeTicks
   MAX-ACCESS  read-only
   STATUS      current
   DESCRIPTION
      "Path: ethernet3.status.ipV6.addresses.timers.validLifeTime

       Time in centi-second."
   ::= {sr1645v2Lan3MCIpV6AddressesEntry 100794368}

sr1645v2Lan3MCIpV6AddressesTimersPrefLifeTime OBJECT-TYPE
   SYNTAX      TimeTicks
   MAX-ACCESS  read-only
   STATUS      current
   DESCRIPTION
      "Path: ethernet3.status.ipV6.addresses.timers.prefLifeTime

       Time in centi-second."
   ::= {sr1645v2Lan3MCIpV6AddressesEntry 100728832}


sr1645v2Lan3MCMediaType OBJECT-TYPE
   SYNTAX      INTEGER
               {
               utp (1),
               sfp (2),
               down (255)
               }
   MAX-ACCESS  read-only
   STATUS      current
   DESCRIPTION
      "Path: ethernet3.status.mediaType

       Possibilities:
               utp   (1)
               sfp   (2)
               down   (255)"
   ::= {sr1645v2Lan3MC 500}



pr1645v2Lan3MC OBJECT IDENTIFIER ::= {r1645v2Lan3MC 12}


pr1645v2Lan3MCInOctets OBJECT-TYPE
   SYNTAX      Counter64
   MAX-ACCESS  read-only
   STATUS      current
   DESCRIPTION
      "Path: ethernet3.performance.ifInOctets
       Info: ifInOctets

       64 bit unsigned wrappable counter."
   ::= {pr1645v2Lan3MC 109}


pr1645v2Lan3MCInUcast OBJECT-TYPE
   SYNTAX      Counter64
   MAX-ACCESS  read-only
   STATUS      current
   DESCRIPTION
      "Path: ethernet3.performance.ifInUcastPkts
       Info: ifInUcastPkts

       64 bit unsigned wrappable counter."
   ::= {pr1645v2Lan3MC 110}


pr1645v2Lan3MCInNUcastPkts OBJECT-TYPE
   SYNTAX      Counter64
   MAX-ACCESS  read-only
   STATUS      current
   DESCRIPTION
      "Path: ethernet3.performance.ifInNUcastPkts
       Info: ifInNUcastPkts

       64 bit unsigned wrappable counter."
   ::= {pr1645v2Lan3MC 111}


pr1645v2Lan3MCInBcastPkts OBJECT-TYPE
   SYNTAX      Counter64
   MAX-ACCESS  read-only
   STATUS      current
   DESCRIPTION
      "Path: ethernet3.performance.ifInBcastPkts
       Info: ifInBcastPkts

       64 bit unsigned wrappable counter."
   ::= {pr1645v2Lan3MC 211}


pr1645v2Lan3MCInMcastPkts OBJECT-TYPE
   SYNTAX      Counter64
   MAX-ACCESS  read-only
   STATUS      current
   DESCRIPTION
      "Path: ethernet3.performance.ifInMcastPkts
       Info: ifInNUcastPkts

       64 bit unsigned wrappable counter."
   ::= {pr1645v2Lan3MC 221}


pr1645v2Lan3MCInDiscards OBJECT-TYPE
   SYNTAX      Counter64
   MAX-ACCESS  read-only
   STATUS      current
   DESCRIPTION
      "Path: ethernet3.performance.ifInDiscards
       Info: ifInDiscards

       64 bit unsigned wrappable counter."
   ::= {pr1645v2Lan3MC 112}


pr1645v2Lan3MCInErrors OBJECT-TYPE
   SYNTAX      Counter64
   MAX-ACCESS  read-only
   STATUS      current
   DESCRIPTION
      "Path: ethernet3.performance.ifInErrors
       Info: ifInErrors

       64 bit unsigned wrappable counter."
   ::= {pr1645v2Lan3MC 113}


pr1645v2Lan3MCInUnknownProtos OBJECT-TYPE
   SYNTAX      Counter64
   MAX-ACCESS  read-only
   STATUS      current
   DESCRIPTION
      "Path: ethernet3.performance.ifInUnknownProtos
       Info: ifInUnknownprotos

       64 bit unsigned wrappable counter."
   ::= {pr1645v2Lan3MC 114}


pr1645v2Lan3MCInQLen OBJECT-TYPE
   SYNTAX      Gauge32
   MAX-ACCESS  read-only
   STATUS      current
   DESCRIPTION
      "Path: ethernet3.performance.ifInQLen
       Info: ifInQLen

       32 bit unsigned gauge value."
   ::= {pr1645v2Lan3MC 128}


pr1645v2Lan3MCInDropEx OBJECT-TYPE
   SYNTAX      Counter64
   MAX-ACCESS  read-only
   STATUS      current
   DESCRIPTION
      "Path: ethernet3.performance.ifInDropLevelExceeded
       Info: ifInDiscards

       64 bit unsigned wrappable counter."
   ::= {pr1645v2Lan3MC 130}


pr1645v2Lan3MCInDropNoMac OBJECT-TYPE
   SYNTAX      Counter64
   MAX-ACCESS  read-only
   STATUS      current
   DESCRIPTION
      "Path: ethernet3.performance.ifInDiscardsNoMacFit
       Info: ifInDiscards

       64 bit unsigned wrappable counter."
   ::= {pr1645v2Lan3MC 133}


pr1645v2Lan3MCInDropNUCast OBJECT-TYPE
   SYNTAX      Counter64
   MAX-ACCESS  read-only
   STATUS      current
   DESCRIPTION
      "Path: ethernet3.performance.ifInDiscardsNUCast
       Info: ifInDiscards

       64 bit unsigned wrappable counter."
   ::= {pr1645v2Lan3MC 136}


pr1645v2Lan3MCInDropFilter OBJECT-TYPE
   SYNTAX      Counter64
   MAX-ACCESS  read-only
   STATUS      current
   DESCRIPTION
      "Path: ethernet3.performance.ifInDiscardsFilter
       Info: ifInDiscards

       64 bit unsigned wrappable counter."
   ::= {pr1645v2Lan3MC 137}


pr1645v2Lan3MCInQueues OBJECT IDENTIFIER ::= {pr1645v2Lan3MC 131}

pr1645v2Lan3MCInQueuesSSCTable OBJECT-TYPE
   SYNTAX      SEQUENCE OF Pr1645v2Lan3MCInQueuesEntry
   MAX-ACCESS  not-accessible
   STATUS      current
   DESCRIPTION
      "Queue Lengths"
   ::= {pr1645v2Lan3MCInQueues 1}

pr1645v2Lan3MCInQueuesEntry OBJECT-TYPE
   SYNTAX      Pr1645v2Lan3MCInQueuesEntry
   MAX-ACCESS  not-accessible
   STATUS      current
   DESCRIPTION
      ""
   INDEX      { pr1645v2Lan3MCInQueuesTableIx }
   ::= {pr1645v2Lan3MCInQueuesSSCTable 1}

Pr1645v2Lan3MCInQueuesEntry ::=
   SEQUENCE
      {
      pr1645v2Lan3MCInQueuesTableIx
         TableIndex,
      pr1645v2Lan3MCInQueuesName
         INTEGER,
      pr1645v2Lan3MCInQueuesLength
         Integer32,
      pr1645v2Lan3MCInQueuesOctetLength
         Integer32,
      pr1645v2Lan3MCInQueuesRedLength
         Integer32,
      pr1645v2Lan3MCInQueuesPacketsTotal
         Counter64,
      pr1645v2Lan3MCInQueuesPacketsDirectTx
         Counter64,
      pr1645v2Lan3MCInQueuesPacketsQueued
         Counter64,
      pr1645v2Lan3MCInQueuesPacketsDropped
         Counter64,
      pr1645v2Lan3MCInQueuesPacketsRedDropped
         Counter64,
      pr1645v2Lan3MCInQueuesPacketsCirTx
         Counter64,
      pr1645v2Lan3MCInQueuesPacketsEirTx
         Counter64,
      pr1645v2Lan3MCInQueuesPacketsViolateTx
         Counter64,
      pr1645v2Lan3MCInQueuesOctetsTotal
         Counter64,
      pr1645v2Lan3MCInQueuesOctetsDirectTx
         Counter64,
      pr1645v2Lan3MCInQueuesOctetsQueued
         Counter64,
      pr1645v2Lan3MCInQueuesOctetsDropped
         Counter64,
      pr1645v2Lan3MCInQueuesOctetsRedDropped
         Counter64,
      pr1645v2Lan3MCInQueuesOctetsCirTx
         Counter64,
      pr1645v2Lan3MCInQueuesOctetsEirTx
         Counter64,
      pr1645v2Lan3MCInQueuesOctetsViolateTx
         Counter64,
      pr1645v2Lan3MCInQueuesOctetsBandwidth15sec
         Integer32,
      pr1645v2Lan3MCInQueuesOctetsBandwidth30sec
         Integer32,
      pr1645v2Lan3MCInQueuesOctetsBandwidth1min
         Integer32,
      pr1645v2Lan3MCInQueuesOctetsBandwidth2min
         Integer32,
      pr1645v2Lan3MCInQueuesOctetsBandwidth5min
         Integer32
      }

pr1645v2Lan3MCInQueuesTableIx OBJECT-TYPE
   SYNTAX      TableIndex
   MAX-ACCESS  not-accessible
   STATUS      current
   DESCRIPTION
      ""
   ::= {pr1645v2Lan3MCInQueuesEntry 11}

pr1645v2Lan3MCInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3MCInQueuesEntry 16777216}

pr1645v2Lan3MCInQueuesLength OBJECT-TYPE
   SYNTAX      Integer32
   MAX-ACCESS  read-only
   STATUS      current
   DESCRIPTION
      "Path: ethernet3.performance.ifInPriorityQueues.length"
   ::= {pr1645v2Lan3MCInQueuesEntry 33554432}

pr1645v2Lan3MCInQueuesOctetLength OBJECT-TYPE
   SYNTAX      Integer32
   MAX-ACCESS  read-only
   STATUS      current
   DESCRIPTION
      "Path: ethernet3.performance.ifInPriorityQueues.octetLength"
   ::= {pr1645v2Lan3MCInQueuesEntry 150994944}

pr1645v2Lan3MCInQueuesRedLength OBJECT-TYPE
   SYNTAX      Integer32
   MAX-ACCESS  read-only
   STATUS      current
   DESCRIPTION
      "Path: ethernet3.performance.ifInPriorityQueues.redLength"
   ::= {pr1645v2Lan3MCInQueuesEntry 134217728}

pr1645v2Lan3MCInQueuesPacketsTotal OBJECT-TYPE
   SYNTAX      Counter64
   MAX-ACCESS  read-only
   STATUS      current
   DESCRIPTION
      "Path: ethernet3.performance.ifInPriorityQueues.packets.total

       64 bit unsigned wrappable counter."
   ::= {pr1645v2Lan3MCInQueuesEntry 50790400}

pr1645v2Lan3MCInQueuesPacketsDirectTx OBJECT-TYPE
   SYNTAX      Counter64
   MAX-ACCESS  read-only
   STATUS      current
   DESCRIPTION
      "Path: ethernet3.performance.ifInPriorityQueues.packets.directTx

       64 bit unsigned wrappable counter."
   ::= {pr1645v2Lan3MCInQueuesEntry 50397184}

pr1645v2Lan3MCInQueuesPacketsQueued OBJECT-TYPE
   SYNTAX      Counter64
   MAX-ACCESS  read-only
   STATUS      current
   DESCRIPTION
      "Path: ethernet3.performance.ifInPriorityQueues.packets.queued

       64 bit unsigned wrappable counter."
   ::= {pr1645v2Lan3MCInQueuesEntry 50462720}

pr1645v2Lan3MCInQueuesPacketsDropped OBJECT-TYPE
   SYNTAX      Counter64
   MAX-ACCESS  read-only
   STATUS      current
   DESCRIPTION
      "Path: ethernet3.performance.ifInPriorityQueues.packets.dropped

       64 bit unsigned wrappable counter."
   ::= {pr1645v2Lan3MCInQueuesEntry 50528256}

pr1645v2Lan3MCInQueuesPacketsRedDropped OBJECT-TYPE
   SYNTAX      Counter64
   MAX-ACCESS  read-only
   STATUS      current
   DESCRIPTION
      "Path: ethernet3.performance.ifInPriorityQueues.packets.redDropped

       64 bit unsigned wrappable counter."
   ::= {pr1645v2Lan3MCInQueuesEntry 50724864}

pr1645v2Lan3MCInQueuesPacketsCirTx OBJECT-TYPE
   SYNTAX      Counter64
   MAX-ACCESS  read-only
   STATUS      current
   DESCRIPTION
      "Path: ethernet3.performance.ifInPriorityQueues.packets.cirTx

       64 bit unsigned wrappable counter."
   ::= {pr1645v2Lan3MCInQueuesEntry 50593792}

pr1645v2Lan3MCInQueuesPacketsEirTx OBJECT-TYPE
   SYNTAX      Counter64
   MAX-ACCESS  read-only
   STATUS      current
   DESCRIPTION
      "Path: ethernet3.performance.ifInPriorityQueues.packets.eirTx

       64 bit unsigned wrappable counter."
   ::= {pr1645v2Lan3MCInQueuesEntry 50659328}

pr1645v2Lan3MCInQueuesPacketsViolateTx OBJECT-TYPE
   SYNTAX      Counter64
   MAX-ACCESS  read-only
   STATUS      current
   DESCRIPTION
      "Path: ethernet3.performance.ifInPriorityQueues.packets.violateTx

       64 bit unsigned wrappable counter."
   ::= {pr1645v2Lan3MCInQueuesEntry 50855936}

pr1645v2Lan3MCInQueuesOctetsTotal OBJECT-TYPE
   SYNTAX      Counter64
   MAX-ACCESS  read-only
   STATUS      current
   DESCRIPTION
      "Path: ethernet3.performance.ifInPriorityQueues.octets.total

       64 bit unsigned wrappable counter."
   ::= {pr1645v2Lan3MCInQueuesEntry 67567616}

pr1645v2Lan3MCInQueuesOctetsDirectTx OBJECT-TYPE
   SYNTAX      Counter64
   MAX-ACCESS  read-only
   STATUS      current
   DESCRIPTION
      "Path: ethernet3.performance.ifInPriorityQueues.octets.directTx

       64 bit unsigned wrappable counter."
   ::= {pr1645v2Lan3MCInQueuesEntry 67174400}

pr1645v2Lan3MCInQueuesOctetsQueued OBJECT-TYPE
   SYNTAX      Counter64
   MAX-ACCESS  read-only
   STATUS      current
   DESCRIPTION
      "Path: ethernet3.performance.ifInPriorityQueues.octets.queued

       64 bit unsigned wrappable counter."
   ::= {pr1645v2Lan3MCInQueuesEntry 67239936}

pr1645v2Lan3MCInQueuesOctetsDropped OBJECT-TYPE
   SYNTAX      Counter64
   MAX-ACCESS  read-only
   STATUS      current
   DESCRIPTION
      "Path: ethernet3.performance.ifInPriorityQueues.octets.dropped

       64 bit unsigned wrappable counter."
   ::= {pr1645v2Lan3MCInQueuesEntry 67305472}

pr1645v2Lan3MCInQueuesOctetsRedDropped OBJECT-TYPE
   SYNTAX      Counter64
   MAX-ACCESS  read-only
   STATUS      current
   DESCRIPTION
      "Path: ethernet3.performance.ifInPriorityQueues.octets.redDropped

       64 bit unsigned wrappable counter."
   ::= {pr1645v2Lan3MCInQueuesEntry 67502080}

pr1645v2Lan3MCInQueuesOctetsCirTx OBJECT-TYPE
   SYNTAX      Counter64
   MAX-ACCESS  read-only
   STATUS      current
   DESCRIPTION
      "Path: ethernet3.performance.ifInPriorityQueues.octets.cirTx

       64 bit unsigned wrappable counter."
   ::= {pr1645v2Lan3MCInQueuesEntry 67371008}

pr1645v2Lan3MCInQueuesOctetsEirTx OBJECT-TYPE
   SYNTAX      Counter64
   MAX-ACCESS  read-only
   STATUS      current
   DESCRIPTION
      "Path: ethernet3.performance.ifInPriorityQueues.octets.eirTx

       64 bit unsigned wrappable counter."
   ::= {pr1645v2Lan3MCInQueuesEntry 67436544}

pr1645v2Lan3MCInQueuesOctetsViolateTx OBJECT-TYPE
   SYNTAX      Counter64
   MAX-ACCESS  read-only
   STATUS      current
   DESCRIPTION
      "Path: ethernet3.performance.ifInPriorityQueues.octets.violateTx

       64 bit unsigned wrappable counter."
   ::= {pr1645v2Lan3MCInQueuesEntry 67633152}

pr1645v2Lan3MCInQueuesOctetsBandwidth15sec OBJECT-TYPE
   SYNTAX      Integer32
   MAX-ACCESS  read-only
   STATUS      current
   DESCRIPTION
      "Path: ethernet3.performance.ifInPriorityQueues.octets.bandwidth.15sec

       unit name = bps
       formula = 8 * ; 8 /"
   ::= {pr1645v2Lan3MCInQueuesEntry 70386944}

pr1645v2Lan3MCInQueuesOctetsBandwidth30sec OBJECT-TYPE
   SYNTAX      Integer32
   MAX-ACCESS  read-only
   STATUS      current
   DESCRIPTION
      "Path: ethernet3.performance.ifInPriorityQueues.octets.bandwidth.30sec

       unit name = bps
       formula = 8 * ; 8 /"
   ::= {pr1645v2Lan3MCInQueuesEntry 70388224}

pr1645v2Lan3MCInQueuesOctetsBandwidth1min OBJECT-TYPE
   SYNTAX      Integer32
   MAX-ACCESS  read-only
   STATUS      current
   DESCRIPTION
      "Path: ethernet3.performance.ifInPriorityQueues.octets.bandwidth.1min

       unit name = bps
       formula = 8 * ; 8 /"
   ::= {pr1645v2Lan3MCInQueuesEntry 70390784}

pr1645v2Lan3MCInQueuesOctetsBandwidth2min OBJECT-TYPE
   SYNTAX      Integer32
   MAX-ACCESS  read-only
   STATUS      current
   DESCRIPTION
      "Path: ethernet3.performance.ifInPriorityQueues.octets.bandwidth.2min

       unit name = bps
       formula = 8 * ; 8 /"
   ::= {pr1645v2Lan3MCInQueuesEntry 70395904}

pr1645v2Lan3MCInQueuesOctetsBandwidth5min OBJECT-TYPE
   SYNTAX      Integer32
   MAX-ACCESS  read-only
   STATUS      current
   DESCRIPTION
      "Path: ethernet3.performance.ifInPriorityQueues.octets.bandwidth.5min

       unit name = bps
       formula = 8 * ; 8 /"
   ::= {pr1645v2Lan3MCInQueuesEntry 70411264}

pr1645v2Lan3MCInQueuesH2Performance OBJECT-TYPE
   SYNTAX      SEQUENCE OF Pr1645v2Lan3MCInQueuesH2PerformanceEntry
   MAX-ACCESS  not-accessible
   STATUS      current
   DESCRIPTION
      ""
   ::= {pr1645v2Lan3MCInQueues 83886080}

pr1645v2Lan3MCInQueuesH2PerformanceEntry OBJECT-TYPE
   SYNTAX      Pr1645v2Lan3MCInQueuesH2PerformanceEntry
   MAX-ACCESS  not-accessible
   STATUS      current
   DESCRIPTION
      ""
   INDEX      { pr1645v2Lan3MCInQueuesTableIx,
                pr1645v2Lan3MCInQueuesH2PerformanceTableIx }
   ::= {pr1645v2Lan3MCInQueuesH2Performance 1}

Pr1645v2Lan3MCInQueuesH2PerformanceEntry ::=
   SEQUENCE
      {
      pr1645v2Lan3MCInQueuesH2PerformanceTableIx
         TableIndex,
      pr1645v2Lan3MCInQueuesH2PerformanceSysUpTime
         TimeTicks,
      pr1645v2Lan3MCInQueuesH2PerformanceTotPkts
         Counter64,
      pr1645v2Lan3MCInQueuesH2PerformanceDirTxPkts
         Counter64,
      pr1645v2Lan3MCInQueuesH2PerformanceQdPkts
         Counter64,
      pr1645v2Lan3MCInQueuesH2PerformanceDropPkts
         Counter64,
      pr1645v2Lan3MCInQueuesH2PerformanceRDropPkts
         Counter64,
      pr1645v2Lan3MCInQueuesH2PerformanceCirTxPkts
         Counter64,
      pr1645v2Lan3MCInQueuesH2PerformanceEirTxPkts
         Counter64,
      pr1645v2Lan3MCInQueuesH2PerformanceViolTxPkts
         Counter64,
      pr1645v2Lan3MCInQueuesH2PerformanceTotOcts
         Counter64,
      pr1645v2Lan3MCInQueuesH2PerformanceDirTxOcts
         Counter64,
      pr1645v2Lan3MCInQueuesH2PerformanceQdOcts
         Counter64,
      pr1645v2Lan3MCInQueuesH2PerformanceDropOcts
         Counter64,
      pr1645v2Lan3MCInQueuesH2PerformanceRDropOcts
         Counter64,
      pr1645v2Lan3MCInQueuesH2PerformanceCirTxOcts
         Counter64,
      pr1645v2Lan3MCInQueuesH2PerformanceEirTxOcts
         Counter64,
      pr1645v2Lan3MCInQueuesH2PerformanceViolTxOcts
         Counter64,
      pr1645v2Lan3MCInQueuesH2PerformanceBandwidth
         Integer32
      }

pr1645v2Lan3MCInQueuesH2PerformanceTableIx OBJECT-TYPE
   SYNTAX      TableIndex
   MAX-ACCESS  not-accessible
   STATUS      current
   DESCRIPTION
      ""
   ::= {pr1645v2Lan3MCInQueuesH2PerformanceEntry 11}

pr1645v2Lan3MCInQueuesH2PerformanceSysUpTime OBJECT-TYPE
   SYNTAX      TimeTicks
   MAX-ACCESS  read-only
   STATUS      current
   DESCRIPTION
      "Path: ethernet3.performance.ifInPriorityQueues.h2Performance.sysUpTime

       Time in centi-second."
   ::= {pr1645v2Lan3MCInQueuesH2PerformanceEntry 16777216}

pr1645v2Lan3MCInQueuesH2PerformanceTotPkts OBJECT-TYPE
   SYNTAX      Counter64
   MAX-ACCESS  read-only
   STATUS      current
   DESCRIPTION
      "Path: ethernet3.performance.ifInPriorityQueues.h2Performance.totalPkts

       64 bit unsigned wrappable counter."
   ::= {pr1645v2Lan3MCInQueuesH2PerformanceEntry 234881024}

pr1645v2Lan3MCInQueuesH2PerformanceDirTxPkts OBJECT-TYPE
   SYNTAX      Counter64
   MAX-ACCESS  read-only
   STATUS      current
   DESCRIPTION
      "Path: ethernet3.performance.ifInPriorityQueues.h2Performance.directTxPkts

       64 bit unsigned wrappable counter."
   ::= {pr1645v2Lan3MCInQueuesH2PerformanceEntry 33554432}

pr1645v2Lan3MCInQueuesH2PerformanceQdPkts OBJECT-TYPE
   SYNTAX      Counter64
   MAX-ACCESS  read-only
   STATUS      current
   DESCRIPTION
      "Path: ethernet3.performance.ifInPriorityQueues.h2Performance.queuedPkts

       64 bit unsigned wrappable counter."
   ::= {pr1645v2Lan3MCInQueuesH2PerformanceEntry 50331648}

pr1645v2Lan3MCInQueuesH2PerformanceDropPkts OBJECT-TYPE
   SYNTAX      Counter64
   MAX-ACCESS  read-only
   STATUS      current
   DESCRIPTION
      "Path: ethernet3.performance.ifInPriorityQueues.h2Performance.droppedPkts

       64 bit unsigned wrappable counter."
   ::= {pr1645v2Lan3MCInQueuesH2PerformanceEntry 67108864}

pr1645v2Lan3MCInQueuesH2PerformanceRDropPkts OBJECT-TYPE
   SYNTAX      Counter64
   MAX-ACCESS  read-only
   STATUS      current
   DESCRIPTION
      "Path: ethernet3.performance.ifInPriorityQueues.h2Performance.redDroppedPkts

       64 bit unsigned wrappable counter."
   ::= {pr1645v2Lan3MCInQueuesH2PerformanceEntry 201326592}

pr1645v2Lan3MCInQueuesH2PerformanceCirTxPkts OBJECT-TYPE
   SYNTAX      Counter64
   MAX-ACCESS  read-only
   STATUS      current
   DESCRIPTION
      "Path: ethernet3.performance.ifInPriorityQueues.h2Performance.cirTxPkts

       64 bit unsigned wrappable counter."
   ::= {pr1645v2Lan3MCInQueuesH2PerformanceEntry 83886080}

pr1645v2Lan3MCInQueuesH2PerformanceEirTxPkts OBJECT-TYPE
   SYNTAX      Counter64
   MAX-ACCESS  read-only
   STATUS      current
   DESCRIPTION
      "Path: ethernet3.performance.ifInPriorityQueues.h2Performance.eirTxPkts

       64 bit unsigned wrappable counter."
   ::= {pr1645v2Lan3MCInQueuesH2PerformanceEntry 100663296}

pr1645v2Lan3MCInQueuesH2PerformanceViolTxPkts OBJECT-TYPE
   SYNTAX      Counter64
   MAX-ACCESS  read-only
   STATUS      current
   DESCRIPTION
      "Path: ethernet3.performance.ifInPriorityQueues.h2Performance.violateTxPkts

       64 bit unsigned wrappable counter."
   ::= {pr1645v2Lan3MCInQueuesH2PerformanceEntry 301989888}

pr1645v2Lan3MCInQueuesH2PerformanceTotOcts OBJECT-TYPE
   SYNTAX      Counter64
   MAX-ACCESS  read-only
   STATUS      current
   DESCRIPTION
      "Path: ethernet3.performance.ifInPriorityQueues.h2Performance.totalOctets

       64 bit unsigned wrappable counter."
   ::= {pr1645v2Lan3MCInQueuesH2PerformanceEntry 251658240}

pr1645v2Lan3MCInQueuesH2PerformanceDirTxOcts OBJECT-TYPE
   SYNTAX      Counter64
   MAX-ACCESS  read-only
   STATUS      current
   DESCRIPTION
      "Path: ethernet3.performance.ifInPriorityQueues.h2Performance.directTxOctets

       64 bit unsigned wrappable counter."
   ::= {pr1645v2Lan3MCInQueuesH2PerformanceEntry 117440512}

pr1645v2Lan3MCInQueuesH2PerformanceQdOcts OBJECT-TYPE
   SYNTAX      Counter64
   MAX-ACCESS  read-only
   STATUS      current
   DESCRIPTION
      "Path: ethernet3.performance.ifInPriorityQueues.h2Performance.queuedOctets

       64 bit unsigned wrappable counter."
   ::= {pr1645v2Lan3MCInQueuesH2PerformanceEntry 134217728}

pr1645v2Lan3MCInQueuesH2PerformanceDropOcts OBJECT-TYPE
   SYNTAX      Counter64
   MAX-ACCESS  read-only
   STATUS      current
   DESCRIPTION
      "Path: ethernet3.performance.ifInPriorityQueues.h2Performance.droppedOctets

       64 bit unsigned wrappable counter."
   ::= {pr1645v2Lan3MCInQueuesH2PerformanceEntry 150994944}

pr1645v2Lan3MCInQueuesH2PerformanceRDropOcts OBJECT-TYPE
   SYNTAX      Counter64
   MAX-ACCESS  read-only
   STATUS      current
   DESCRIPTION
      "Path: ethernet3.performance.ifInPriorityQueues.h2Performance.redDroppedOctets

       64 bit unsigned wrappable counter."
   ::= {pr1645v2Lan3MCInQueuesH2PerformanceEntry 218103808}

pr1645v2Lan3MCInQueuesH2PerformanceCirTxOcts OBJECT-TYPE
   SYNTAX      Counter64
   MAX-ACCESS  read-only
   STATUS      current
   DESCRIPTION
      "Path: ethernet3.performance.ifInPriorityQueues.h2Performance.cirTxOctets

       64 bit unsigned wrappable counter."
   ::= {pr1645v2Lan3MCInQueuesH2PerformanceEntry 167772160}

pr1645v2Lan3MCInQueuesH2PerformanceEirTxOcts OBJECT-TYPE
   SYNTAX      Counter64
   MAX-ACCESS  read-only
   STATUS      current
   DESCRIPTION
      "Path: ethernet3.performance.ifInPriorityQueues.h2Performance.eirTxOctets

       64 bit unsigned wrappable counter."
   ::= {pr1645v2Lan3MCInQueuesH2PerformanceEntry 184549376}

pr1645v2Lan3MCInQueuesH2PerformanceViolTxOcts OBJECT-TYPE
   SYNTAX      Counter64
   MAX-ACCESS  read-only
   STATUS      current
   DESCRIPTION
      "Path: ethernet3.performance.ifInPriorityQueues.h2Performance.violateTxOctets

       64 bit unsigned wrappable counter."
   ::= {pr1645v2Lan3MCInQueuesH2PerformanceEntry 318767104}

pr1645v2Lan3MCInQueuesH2PerformanceBandwidth OBJECT-TYPE
   SYNTAX      Integer32
   MAX-ACCESS  read-only
   STATUS      current
   DESCRIPTION
      "Path: ethernet3.performance.ifInPriorityQueues.h2Performance.bandwidth

       unit name = bps
       formula = 8 * ; 8 /"
   ::= {pr1645v2Lan3MCInQueuesH2PerformanceEntry 268435456}

pr1645v2Lan3MCInQueuesH24Performance OBJECT-TYPE
   SYNTAX      SEQUENCE OF Pr1645v2Lan3MCInQueuesH24PerformanceEntry
   MAX-ACCESS  not-accessible
   STATUS      current
   DESCRIPTION
      ""
   ::= {pr1645v2Lan3MCInQueues 100663296}

pr1645v2Lan3MCInQueuesH24PerformanceEntry OBJECT-TYPE
   SYNTAX      Pr1645v2Lan3MCInQueuesH24PerformanceEntry
   MAX-ACCESS  not-accessible
   STATUS      current
   DESCRIPTION
      ""
   INDEX      { pr1645v2Lan3MCInQueuesTableIx,
                pr1645v2Lan3MCInQueuesH24PerformanceTableIx }
   ::= {pr1645v2Lan3MCInQueuesH24Performance 1}

Pr1645v2Lan3MCInQueuesH24PerformanceEntry ::=
   SEQUENCE
      {
      pr1645v2Lan3MCInQueuesH24PerformanceTableIx
         TableIndex,
      pr1645v2Lan3MCInQueuesH24PerformanceSysUpTime
         TimeTicks,
      pr1645v2Lan3MCInQueuesH24PerformanceTotPkts
         Counter64,
      pr1645v2Lan3MCInQueuesH24PerformanceDirTxPkts
         Counter64,
      pr1645v2Lan3MCInQueuesH24PerformanceQdPkts
         Counter64,
      pr1645v2Lan3MCInQueuesH24PerformanceDropPkts
         Counter64,
      pr1645v2Lan3MCInQueuesH24PerformanceRDropPkts
         Counter64,
      pr1645v2Lan3MCInQueuesH24PerformanceCirTxPkts
         Counter64,
      pr1645v2Lan3MCInQueuesH24PerformanceEirTxPkts
         Counter64,
      pr1645v2Lan3MCInQueuesH24PerformanceViolTxPkts
         Counter64,
      pr1645v2Lan3MCInQueuesH24PerformanceTotOcts
         Counter64,
      pr1645v2Lan3MCInQueuesH24PerformanceDirTxOcts
         Counter64,
      pr1645v2Lan3MCInQueuesH24PerformanceQdOcts
         Counter64,
      pr1645v2Lan3MCInQueuesH24PerformanceDropOcts
         Counter64,
      pr1645v2Lan3MCInQueuesH24PerformanceRDropOcts
         Counter64,
      pr1645v2Lan3MCInQueuesH24PerformanceCirTxOcts
         Counter64,
      pr1645v2Lan3MCInQueuesH24PerformanceEirTxOcts
         Counter64,
      pr1645v2Lan3MCInQueuesH24PerformanceViolTxOcts
         Counter64,
      pr1645v2Lan3MCInQueuesH24PerformanceBandwidth
         Integer32
      }

pr1645v2Lan3MCInQueuesH24PerformanceTableIx OBJECT-TYPE
   SYNTAX      TableIndex
   MAX-ACCESS  not-accessible
   STATUS      current
   DESCRIPTION
      ""
   ::= {pr1645v2Lan3MCInQueuesH24PerformanceEntry 11}

pr1645v2Lan3MCInQueuesH24PerformanceSysUpTime OBJECT-TYPE
   SYNTAX      TimeTicks
   MAX-ACCESS  read-only
   STATUS      current
   DESCRIPTION
      "Path: ethernet3.performance.ifInPriorityQueues.h24Performance.sysUpTime

       Time in centi-second."
   ::= {pr1645v2Lan3MCInQueuesH24PerformanceEntry 16777216}

pr1645v2Lan3MCInQueuesH24PerformanceTotPkts OBJECT-TYPE
   SYNTAX      Counter64
   MAX-ACCESS  read-only
   STATUS      current
   DESCRIPTION
      "Path: ethernet3.performance.ifInPriorityQueues.h24Performance.totalPkts

       64 bit unsigned wrappable counter."
   ::= {pr1645v2Lan3MCInQueuesH24PerformanceEntry 234881024}

pr1645v2Lan3MCInQueuesH24PerformanceDirTxPkts OBJECT-TYPE
   SYNTAX      Counter64
   MAX-ACCESS  read-only
   STATUS      current
   DESCRIPTION
      "Path: ethernet3.performance.ifInPriorityQueues.h24Performance.directTxPkts

       64 bit unsigned wrappable counter."
   ::= {pr1645v2Lan3MCInQueuesH24PerformanceEntry 33554432}

pr1645v2Lan3MCInQueuesH24PerformanceQdPkts OBJECT-TYPE
   SYNTAX      Counter64
   MAX-ACCESS  read-only
   STATUS      current
   DESCRIPTION
      "Path: ethernet3.performance.ifInPriorityQueues.h24Performance.queuedPkts

       64 bit unsigned wrappable counter."
   ::= {pr1645v2Lan3MCInQueuesH24PerformanceEntry 50331648}

pr1645v2Lan3MCInQueuesH24PerformanceDropPkts OBJECT-TYPE
   SYNTAX      Counter64
   MAX-ACCESS  read-only
   STATUS      current
   DESCRIPTION
      "Path: ethernet3.performance.ifInPriorityQueues.h24Performance.droppedPkts

       64 bit unsigned wrappable counter."
   ::= {pr1645v2Lan3MCInQueuesH24PerformanceEntry 67108864}

pr1645v2Lan3MCInQueuesH24PerformanceRDropPkts OBJECT-TYPE
   SYNTAX      Counter64
   MAX-ACCESS  read-only
   STATUS      current
   DESCRIPTION
      "Path: ethernet3.performance.ifInPriorityQueues.h24Performance.redDroppedPkts

       64 bit unsigned wrappable counter."
   ::= {pr1645v2Lan3MCInQueuesH24PerformanceEntry 201326592}

pr1645v2Lan3MCInQueuesH24PerformanceCirTxPkts OBJECT-TYPE
   SYNTAX      Counter64
   MAX-ACCESS  read-only
   STATUS      current
   DESCRIPTION
      "Path: ethernet3.performance.ifInPriorityQueues.h24Performance.cirTxPkts

       64 bit unsigned wrappable counter."
   ::= {pr1645v2Lan3MCInQueuesH24PerformanceEntry 83886080}

pr1645v2Lan3MCInQueuesH24PerformanceEirTxPkts OBJECT-TYPE
   SYNTAX      Counter64
   MAX-ACCESS  read-only
   STATUS      current
   DESCRIPTION
      "Path: ethernet3.performance.ifInPriorityQueues.h24Performance.eirTxPkts

       64 bit unsigned wrappable counter."
   ::= {pr1645v2Lan3MCInQueuesH24PerformanceEntry 100663296}

pr1645v2Lan3MCInQueuesH24PerformanceViolTxPkts OBJECT-TYPE
   SYNTAX      Counter64
   MAX-ACCESS  read-only
   STATUS      current
   DESCRIPTION
      "Path: ethernet3.performance.ifInPriorityQueues.h24Performance.violateTxPkts

       64 bit unsigned wrappable counter."
   ::= {pr1645v2Lan3MCInQueuesH24PerformanceEntry 301989888}

pr1645v2Lan3MCInQueuesH24PerformanceTotOcts OBJECT-TYPE
   SYNTAX      Counter64
   MAX-ACCESS  read-only
   STATUS      current
   DESCRIPTION
      "Path: ethernet3.performance.ifInPriorityQueues.h24Performance.totalOctets

       64 bit unsigned wrappable counter."
   ::= {pr1645v2Lan3MCInQueuesH24PerformanceEntry 251658240}

pr1645v2Lan3MCInQueuesH24PerformanceDirTxOcts OBJECT-TYPE
   SYNTAX      Counter64
   MAX-ACCESS  read-only
   STATUS      current
   DESCRIPTION
      "Path: ethernet3.performance.ifInPriorityQueues.h24Performance.directTxOctets

       64 bit unsigned wrappable counter."
   ::= {pr1645v2Lan3MCInQueuesH24PerformanceEntry 117440512}

pr1645v2Lan3MCInQueuesH24PerformanceQdOcts OBJECT-TYPE
   SYNTAX      Counter64
   MAX-ACCESS  read-only
   STATUS      current
   DESCRIPTION
      "Path: ethernet3.performance.ifInPriorityQueues.h24Performance.queuedOctets

       64 bit unsigned wrappable counter."
   ::= {pr1645v2Lan3MCInQueuesH24PerformanceEntry 134217728}

pr1645v2Lan3MCInQueuesH24PerformanceDropOcts OBJECT-TYPE
   SYNTAX      Counter64
   MAX-ACCESS  read-only
   STATUS      current
   DESCRIPTION
      "Path: ethernet3.performance.ifInPriorityQueues.h24Performance.droppedOctets

       64 bit unsigned wrappable counter."
   ::= {pr1645v2Lan3MCInQueuesH24PerformanceEntry 150994944}

pr1645v2Lan3MCInQueuesH24PerformanceRDropOcts OBJECT-TYPE
   SYNTAX      Counter64
   MAX-ACCESS  read-only
   STATUS      current
   DESCRIPTION
      "Path: ethernet3.performance.ifInPriorityQueues.h24Performance.redDroppedOctets

       64 bit unsigned wrappable counter."
   ::= {pr1645v2Lan3MCInQueuesH24PerformanceEntry 218103808}

pr1645v2Lan3MCInQueuesH24PerformanceCirTxOcts OBJECT-TYPE
   SYNTAX      Counter64
   MAX-ACCESS  read-only
   STATUS      current
   DESCRIPTION
      "Path: ethernet3.performance.ifInPriorityQueues.h24Performance.cirTxOctets

       64 bit unsigned wrappable counter."
   ::= {pr1645v2Lan3MCInQueuesH24PerformanceEntry 167772160}

pr1645v2Lan3MCInQueuesH24PerformanceEirTxOcts OBJECT-TYPE
   SYNTAX      Counter64
   MAX-ACCESS  read-only
   STATUS      current
   DESCRIPTION
      "Path: ethernet3.performance.ifInPriorityQueues.h24Performance.eirTxOctets

       64 bit unsigned wrappable counter."
   ::= {pr1645v2Lan3MCInQueuesH24PerformanceEntry 184549376}

pr1645v2Lan3MCInQueuesH24PerformanceViolTxOcts OBJECT-TYPE
   SYNTAX      Counter64
   MAX-ACCESS  read-only
   STATUS      current
   DESCRIPTION
      "Path: ethernet3.performance.ifInPriorityQueues.h24Performance.violateTxOctets

       64 bit unsigned wrappable counter."
   ::= {pr1645v2Lan3MCInQueuesH24PerformanceEntry 318767104}

pr1645v2Lan3MCInQueuesH24PerformanceBandwidth OBJECT-TYPE
   SYNTAX      Integer32
   MAX-ACCESS  read-only
   STATUS      current
   DESCRIPTION
      "Path: ethernet3.performance.ifInPriorityQueues.h24Performance.bandwidth

       unit name = bps
       formula = 8 * ; 8 /"
   ::= {pr1645v2Lan3MCInQueuesH24PerformanceEntry 268435456}

pr1645v2Lan3MCInQueuesD7Performance OBJECT-TYPE
   SYNTAX      SEQUENCE OF Pr1645v2Lan3MCInQueuesD7PerformanceEntry
   MAX-ACCESS  not-accessible
   STATUS      current
   DESCRIPTION
      ""
   ::= {pr1645v2Lan3MCInQueues 117440512}

pr1645v2Lan3MCInQueuesD7PerformanceEntry OBJECT-TYPE
   SYNTAX      Pr1645v2Lan3MCInQueuesD7PerformanceEntry
   MAX-ACCESS  not-accessible
   STATUS      current
   DESCRIPTION
      ""
   INDEX      { pr1645v2Lan3MCInQueuesTableIx,
                pr1645v2Lan3MCInQueuesD7PerformanceTableIx }
   ::= {pr1645v2Lan3MCInQueuesD7Performance 1}

Pr1645v2Lan3MCInQueuesD7PerformanceEntry ::=
   SEQUENCE
      {
      pr1645v2Lan3MCInQueuesD7PerformanceTableIx
         TableIndex,
      pr1645v2Lan3MCInQueuesD7PerformanceSysUpTime
         TimeTicks,
      pr1645v2Lan3MCInQueuesD7PerformanceTotPkts
         Counter64,
      pr1645v2Lan3MCInQueuesD7PerformanceDirTxPkts
         Counter64,
      pr1645v2Lan3MCInQueuesD7PerformanceQdPkts
         Counter64,
      pr1645v2Lan3MCInQueuesD7PerformanceDropPkts
         Counter64,
      pr1645v2Lan3MCInQueuesD7PerformanceRDropPkts
         Counter64,
      pr1645v2Lan3MCInQueuesD7PerformanceCirTxPkts
         Counter64,
      pr1645v2Lan3MCInQueuesD7PerformanceEirTxPkts
         Counter64,
      pr1645v2Lan3MCInQueuesD7PerformanceViolTxPkts
         Counter64,
      pr1645v2Lan3MCInQueuesD7PerformanceTotOcts
         Counter64,
      pr1645v2Lan3MCInQueuesD7PerformanceDirTxOcts
         Counter64,
      pr1645v2Lan3MCInQueuesD7PerformanceQdOcts
         Counter64,
      pr1645v2Lan3MCInQueuesD7PerformanceDropOcts
         Counter64,
      pr1645v2Lan3MCInQueuesD7PerformanceRDropOcts
         Counter64,
      pr1645v2Lan3MCInQueuesD7PerformanceCirTxOcts
         Counter64,
      pr1645v2Lan3MCInQueuesD7PerformanceEirTxOcts
         Counter64,
      pr1645v2Lan3MCInQueuesD7PerformanceViolTxOcts
         Counter64,
      pr1645v2Lan3MCInQueuesD7PerformanceBandwidth
         Integer32
      }

pr1645v2Lan3MCInQueuesD7PerformanceTableIx OBJECT-TYPE
   SYNTAX      TableIndex
   MAX-ACCESS  not-accessible
   STATUS      current
   DESCRIPTION
      ""
   ::= {pr1645v2Lan3MCInQueuesD7PerformanceEntry 11}

pr1645v2Lan3MCInQueuesD7PerformanceSysUpTime OBJECT-TYPE
   SYNTAX      TimeTicks
   MAX-ACCESS  read-only
   STATUS      current
   DESCRIPTION
      "Path: ethernet3.performance.ifInPriorityQueues.d7Performance.sysUpTime

       Time in centi-second."
   ::= {pr1645v2Lan3MCInQueuesD7PerformanceEntry 16777216}

pr1645v2Lan3MCInQueuesD7PerformanceTotPkts OBJECT-TYPE
   SYNTAX      Counter64
   MAX-ACCESS  read-only
   STATUS      current
   DESCRIPTION
      "Path: ethernet3.performance.ifInPriorityQueues.d7Performance.totalPkts

       64 bit unsigned wrappable counter."
   ::= {pr1645v2Lan3MCInQueuesD7PerformanceEntry 234881024}

pr1645v2Lan3MCInQueuesD7PerformanceDirTxPkts OBJECT-TYPE
   SYNTAX      Counter64
   MAX-ACCESS  read-only
   STATUS      current
   DESCRIPTION
      "Path: ethernet3.performance.ifInPriorityQueues.d7Performance.directTxPkts

       64 bit unsigned wrappable counter."
   ::= {pr1645v2Lan3MCInQueuesD7PerformanceEntry 33554432}

pr1645v2Lan3MCInQueuesD7PerformanceQdPkts OBJECT-TYPE
   SYNTAX      Counter64
   MAX-ACCESS  read-only
   STATUS      current
   DESCRIPTION
      "Path: ethernet3.performance.ifInPriorityQueues.d7Performance.queuedPkts

       64 bit unsigned wrappable counter."
   ::= {pr1645v2Lan3MCInQueuesD7PerformanceEntry 50331648}

pr1645v2Lan3MCInQueuesD7PerformanceDropPkts OBJECT-TYPE
   SYNTAX      Counter64
   MAX-ACCESS  read-only
   STATUS      current
   DESCRIPTION
      "Path: ethernet3.performance.ifInPriorityQueues.d7Performance.droppedPkts

       64 bit unsigned wrappable counter."
   ::= {pr1645v2Lan3MCInQueuesD7PerformanceEntry 67108864}

pr1645v2Lan3MCInQueuesD7PerformanceRDropPkts OBJECT-TYPE
   SYNTAX      Counter64
   MAX-ACCESS  read-only
   STATUS      current
   DESCRIPTION
      "Path: ethernet3.performance.ifInPriorityQueues.d7Performance.redDroppedPkts

       64 bit unsigned wrappable counter."
   ::= {pr1645v2Lan3MCInQueuesD7PerformanceEntry 201326592}

pr1645v2Lan3MCInQueuesD7PerformanceCirTxPkts OBJECT-TYPE
   SYNTAX      Counter64
   MAX-ACCESS  read-only
   STATUS      current
   DESCRIPTION
      "Path: ethernet3.performance.ifInPriorityQueues.d7Performance.cirTxPkts

       64 bit unsigned wrappable counter."
   ::= {pr1645v2Lan3MCInQueuesD7PerformanceEntry 83886080}

pr1645v2Lan3MCInQueuesD7PerformanceEirTxPkts OBJECT-TYPE
   SYNTAX      Counter64
   MAX-ACCESS  read-only
   STATUS      current
   DESCRIPTION
      "Path: ethernet3.performance.ifInPriorityQueues.d7Performance.eirTxPkts

       64 bit unsigned wrappable counter."
   ::= {pr1645v2Lan3MCInQueuesD7PerformanceEntry 100663296}

pr1645v2Lan3MCInQueuesD7PerformanceViolTxPkts OBJECT-TYPE
   SYNTAX      Counter64
   MAX-ACCESS  read-only
   STATUS      current
   DESCRIPTION
      "Path: ethernet3.performance.ifInPriorityQueues.d7Performance.violateTxPkts

       64 bit unsigned wrappable counter."
   ::= {pr1645v2Lan3MCInQueuesD7PerformanceEntry 301989888}

pr1645v2Lan3MCInQueuesD7PerformanceTotOcts OBJECT-TYPE
   SYNTAX      Counter64
   MAX-ACCESS  read-only
   STATUS      current
   DESCRIPTION
      "Path: ethernet3.performance.ifInPriorityQueues.d7Performance.totalOctets

       64 bit unsigned wrappable counter."
   ::= {pr1645v2Lan3MCInQueuesD7PerformanceEntry 251658240}

pr1645v2Lan3MCInQueuesD7PerformanceDirTxOcts OBJECT-TYPE
   SYNTAX      Counter64
   MAX-ACCESS  read-only
   STATUS      current
   DESCRIPTION
      "Path: ethernet3.performance.ifInPriorityQueues.d7Performance.directTxOctets

       64 bit unsigned wrappable counter."
   ::= {pr1645v2Lan3MCInQueuesD7PerformanceEntry 117440512}

pr1645v2Lan3MCInQueuesD7PerformanceQdOcts OBJECT-TYPE
   SYNTAX      Counter64
   MAX-ACCESS  read-only
   STATUS      current
   DESCRIPTION
      "Path: ethernet3.performance.ifInPriorityQueues.d7Performance.queuedOctets

       64 bit unsigned wrappable counter."
   ::= {pr1645v2Lan3MCInQueuesD7PerformanceEntry 134217728}

pr1645v2Lan3MCInQueuesD7PerformanceDropOcts OBJECT-TYPE
   SYNTAX      Counter64
   MAX-ACCESS  read-only
   STATUS      current
   DESCRIPTION
      "Path: ethernet3.performance.ifInPriorityQueues.d7Performance.droppedOctets

       64 bit unsigned wrappable counter."
   ::= {pr1645v2Lan3MCInQueuesD7PerformanceEntry 150994944}

pr1645v2Lan3MCInQueuesD7PerformanceRDropOcts OBJECT-TYPE
   SYNTAX      Counter64
   MAX-ACCESS  read-only
   STATUS      current
   DESCRIPTION
      "Path: ethernet3.performance.ifInPriorityQueues.d7Performance.redDroppedOctets

       64 bit unsigned wrappable counter."
   ::= {pr1645v2Lan3MCInQueuesD7PerformanceEntry 218103808}

pr1645v2Lan3MCInQueuesD7PerformanceCirTxOcts OBJECT-TYPE
   SYNTAX      Counter64
   MAX-ACCESS  read-only
   STATUS      current
   DESCRIPTION
      "Path: ethernet3.performance.ifInPriorityQueues.d7Performance.cirTxOctets

       64 bit unsigned wrappable counter."
   ::= {pr1645v2Lan3MCInQueuesD7PerformanceEntry 167772160}

pr1645v2Lan3MCInQueuesD7PerformanceEirTxOcts OBJECT-TYPE
   SYNTAX      Counter64
   MAX-ACCESS  read-only
   STATUS      current
   DESCRIPTION
      "Path: ethernet3.performance.ifInPriorityQueues.d7Performance.eirTxOctets

       64 bit unsigned wrappable counter."
   ::= {pr1645v2Lan3MCInQueuesD7PerformanceEntry 184549376}

pr1645v2Lan3MCInQueuesD7PerformanceViolTxOcts OBJECT-TYPE
   SYNTAX      Counter64
   MAX-ACCESS  read-only
   STATUS      current
   DESCRIPTION
      "Path: ethernet3.performance.ifInPriorityQueues.d7Performance.violateTxOctets

       64 bit unsigned wrappable counter."
   ::= {pr1645v2Lan3MCInQueuesD7PerformanceEntry 318767104}

pr1645v2Lan3MCInQueuesD7PerformanceBandwidth OBJECT-TYPE
   SYNTAX      Integer32
   MAX-ACCESS  read-only
   STATUS      current
   DESCRIPTION
      "Path: ethernet3.performance.ifInPriorityQueues.d7Performance.bandwidth

       unit name = bps
       formula = 8 * ; 8 /"
   ::= {pr1645v2Lan3MCInQueuesD7PerformanceEntry 268435456}


pr1645v2Lan3MCInBandwidth OBJECT IDENTIFIER ::= {pr1645v2Lan3MC 181}

pr1645v2Lan3MCInBandwidthSSC OBJECT IDENTIFIER ::= {pr1645v2Lan3MCInBandwidth 1}

pr1645v2Lan3MCInBandwidthEntry OBJECT IDENTIFIER ::= {pr1645v2Lan3MCInBandwidthSSC 1}

pr1645v2Lan3MCInBandwidth15sec OBJECT-TYPE
   SYNTAX      Integer32
   MAX-ACCESS  read-only
   STATUS      current
   DESCRIPTION
      "Path: ethernet3.performance.ifInBandwidth.15sec

       unit name = bps
       formula = 8 * ; 8 /"
   ::= {pr1645v2Lan3MCInBandwidthEntry 83886080}

pr1645v2Lan3MCInBandwidth30sec OBJECT-TYPE
   SYNTAX      Integer32
   MAX-ACCESS  read-only
   STATUS      current
   DESCRIPTION
      "Path: ethernet3.performance.ifInBandwidth.30sec

       unit name = bps
       formula = 8 * ; 8 /"
   ::= {pr1645v2Lan3MCInBandwidthEntry 167772160}

pr1645v2Lan3MCInBandwidth1min OBJECT-TYPE
   SYNTAX      Integer32
   MAX-ACCESS  read-only
   STATUS      current
   DESCRIPTION
      "Path: ethernet3.performance.ifInBandwidth.1min

       unit name = bps
       formula = 8 * ; 8 /"
   ::= {pr1645v2Lan3MCInBandwidthEntry 335544320}

pr1645v2Lan3MCInBandwidth2min OBJECT-TYPE
   SYNTAX      Integer32
   MAX-ACCESS  read-only
   STATUS      current
   DESCRIPTION
      "Path: ethernet3.performance.ifInBandwidth.2min

       unit name = bps
       formula = 8 * ; 8 /"
   ::= {pr1645v2Lan3MCInBandwidthEntry 671088640}

pr1645v2Lan3MCInBandwidth5min OBJECT-TYPE
   SYNTAX      Integer32
   MAX-ACCESS  read-only
   STATUS      current
   DESCRIPTION
      "Path: ethernet3.performance.ifInBandwidth.5min

       unit name = bps
       formula = 8 * ; 8 /"
   ::= {pr1645v2Lan3MCInBandwidthEntry 1677721600}


pr1645v2Lan3MCOutOctets OBJECT-TYPE
   SYNTAX      Counter64
   MAX-ACCESS  read-only
   STATUS      current
   DESCRIPTION
      "Path: ethernet3.performance.ifOutOctets
       Info: ifOutOctets

       64 bit unsigned wrappable counter."
   ::= {pr1645v2Lan3MC 115}


pr1645v2Lan3MCOutUcastPkts OBJECT-TYPE
   SYNTAX      Counter64
   MAX-ACCESS  read-only
   STATUS      current
   DESCRIPTION
      "Path: ethernet3.performance.ifOutUcastPkts
       Info: ifOutUcastPkts

       64 bit unsigned wrappable counter."
   ::= {pr1645v2Lan3MC 116}


pr1645v2Lan3MCOutNUcastPkts OBJECT-TYPE
   SYNTAX      Counter64
   MAX-ACCESS  read-only
   STATUS      current
   DESCRIPTION
      "Path: ethernet3.performance.ifOutNUcastPkts
       Info: ifOutNUcastPkts

       64 bit unsigned wrappable counter."
   ::= {pr1645v2Lan3MC 117}


pr1645v2Lan3MCOutBcastPkts OBJECT-TYPE
   SYNTAX      Counter64
   MAX-ACCESS  read-only
   STATUS      current
   DESCRIPTION
      "Path: ethernet3.performance.ifOutBcastPkts
       Info: ifOutBcastPkts

       64 bit unsigned wrappable counter."
   ::= {pr1645v2Lan3MC 217}


pr1645v2Lan3MCOutMcastPkts OBJECT-TYPE
   SYNTAX      Counter64
   MAX-ACCESS  read-only
   STATUS      current
   DESCRIPTION
      "Path: ethernet3.performance.ifOutMcastPkts
       Info: ifOutMcastPkts

       64 bit unsigned wrappable counter."
   ::= {pr1645v2Lan3MC 227}


pr1645v2Lan3MCOutDiscards OBJECT-TYPE
   SYNTAX      Counter64
   MAX-ACCESS  read-only
   STATUS      current
   DESCRIPTION
      "Path: ethernet3.performance.ifOutDiscards
       Info: ifOutDiscards

       64 bit unsigned wrappable counter."
   ::= {pr1645v2Lan3MC 118}


pr1645v2Lan3MCOutErrors OBJECT-TYPE
   SYNTAX      Counter64
   MAX-ACCESS  read-only
   STATUS      current
   DESCRIPTION
      "Path: ethernet3.performance.ifOutErrors
       Info: ifOutErrors

       64 bit unsigned wrappable counter."
   ::= {pr1645v2Lan3MC 119}


pr1645v2Lan3MCOutQLen OBJECT-TYPE
   SYNTAX      Gauge32
   MAX-ACCESS  read-only
   STATUS      current
   DESCRIPTION
      "Path: ethernet3.performance.ifOutQLen
       Info: ifOutQLen

       32 bit unsigned gauge value."
   ::= {pr1645v2Lan3MC 120}


pr1645v2Lan3MCOutDropEx OBJECT-TYPE
   SYNTAX      Counter64
   MAX-ACCESS  read-only
   STATUS      current
   DESCRIPTION
      "Path: ethernet3.performance.ifOutDropLevelExceeded
       Info: ifOutDiscards

       64 bit unsigned wrappable counter."
   ::= {pr1645v2Lan3MC 127}


pr1645v2Lan3MCOutDropNoArp OBJECT-TYPE
   SYNTAX      Counter64
   MAX-ACCESS  read-only
   STATUS      current
   DESCRIPTION
      "Path: ethernet3.performance.ifOutDiscardsNoArp
       Info: ifOutDiscards

       64 bit unsigned wrappable counter."
   ::= {pr1645v2Lan3MC 134}


pr1645v2Lan3MCOutDropFilter OBJECT-TYPE
   SYNTAX      Counter64
   MAX-ACCESS  read-only
   STATUS      current
   DESCRIPTION
      "Path: ethernet3.performance.ifOutDiscardsFilter
       Info: ifOutDiscards

       64 bit unsigned wrappable counter."
   ::= {pr1645v2Lan3MC 138}


pr1645v2Lan3MCOutQueues OBJECT IDENTIFIER ::= {pr1645v2Lan3MC 129}

pr1645v2Lan3MCOutQueuesSSCTable OBJECT-TYPE
   SYNTAX      SEQUENCE OF Pr1645v2Lan3MCOutQueuesEntry
   MAX-ACCESS  not-accessible
   STATUS      current
   DESCRIPTION
      "Queue Lengths"
   ::= {pr1645v2Lan3MCOutQueues 1}

pr1645v2Lan3MCOutQueuesEntry OBJECT-TYPE
   SYNTAX      Pr1645v2Lan3MCOutQueuesEntry
   MAX-ACCESS  not-accessible
   STATUS      current
   DESCRIPTION
      ""
   INDEX      { pr1645v2Lan3MCOutQueuesTableIx }
   ::= {pr1645v2Lan3MCOutQueuesSSCTable 1}

Pr1645v2Lan3MCOutQueuesEntry ::=
   SEQUENCE
      {
      pr1645v2Lan3MCOutQueuesTableIx
         TableIndex,
      pr1645v2Lan3MCOutQueuesName
         INTEGER,
      pr1645v2Lan3MCOutQueuesLength
         Integer32,
      pr1645v2Lan3MCOutQueuesOctetLength
         Integer32,
      pr1645v2Lan3MCOutQueuesRedLength
         Integer32,
      pr1645v2Lan3MCOutQueuesPacketsTotal
         Counter64,
      pr1645v2Lan3MCOutQueuesPacketsDirectTx
         Counter64,
      pr1645v2Lan3MCOutQueuesPacketsQueued
         Counter64,
      pr1645v2Lan3MCOutQueuesPacketsDropped
         Counter64,
      pr1645v2Lan3MCOutQueuesPacketsRedDropped
         Counter64,
      pr1645v2Lan3MCOutQueuesPacketsCirTx
         Counter64,
      pr1645v2Lan3MCOutQueuesPacketsEirTx
         Counter64,
      pr1645v2Lan3MCOutQueuesPacketsViolateTx
         Counter64,
      pr1645v2Lan3MCOutQueuesOctetsTotal
         Counter64,
      pr1645v2Lan3MCOutQueuesOctetsDirectTx
         Counter64,
      pr1645v2Lan3MCOutQueuesOctetsQueued
         Counter64,
      pr1645v2Lan3MCOutQueuesOctetsDropped
         Counter64,
      pr1645v2Lan3MCOutQueuesOctetsRedDropped
         Counter64,
      pr1645v2Lan3MCOutQueuesOctetsCirTx
         Counter64,
      pr1645v2Lan3MCOutQueuesOctetsEirTx
         Counter64,
      pr1645v2Lan3MCOutQueuesOctetsViolateTx
         Counter64,
      pr1645v2Lan3MCOutQueuesOctetsBandwidth15sec
         Integer32,
      pr1645v2Lan3MCOutQueuesOctetsBandwidth30sec
         Integer32,
      pr1645v2Lan3MCOutQueuesOctetsBandwidth1min
         Integer32,
      pr1645v2Lan3MCOutQueuesOctetsBandwidth2min
         Integer32,
      pr1645v2Lan3MCOutQueuesOctetsBandwidth5min
         Integer32
      }

pr1645v2Lan3MCOutQueuesTableIx OBJECT-TYPE
   SYNTAX      TableIndex
   MAX-ACCESS  not-accessible
   STATUS      current
   DESCRIPTION
      ""
   ::= {pr1645v2Lan3MCOutQueuesEntry 11}

pr1645v2Lan3MCOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3MCOutQueuesEntry 16777216}

pr1645v2Lan3MCOutQueuesLength OBJECT-TYPE
   SYNTAX      Integer32
   MAX-ACCESS  read-only
   STATUS      current
   DESCRIPTION
      "Path: ethernet3.performance.ifOutPriorityQueues.length"
   ::= {pr1645v2Lan3MCOutQueuesEntry 33554432}

pr1645v2Lan3MCOutQueuesOctetLength OBJECT-TYPE
   SYNTAX      Integer32
   MAX-ACCESS  read-only
   STATUS      current
   DESCRIPTION
      "Path: ethernet3.performance.ifOutPriorityQueues.octetLength"
   ::= {pr1645v2Lan3MCOutQueuesEntry 150994944}

pr1645v2Lan3MCOutQueuesRedLength OBJECT-TYPE
   SYNTAX      Integer32
   MAX-ACCESS  read-only
   STATUS      current
   DESCRIPTION
      "Path: ethernet3.performance.ifOutPriorityQueues.redLength"
   ::= {pr1645v2Lan3MCOutQueuesEntry 134217728}

pr1645v2Lan3MCOutQueuesPacketsTotal OBJECT-TYPE
   SYNTAX      Counter64
   MAX-ACCESS  read-only
   STATUS      current
   DESCRIPTION
      "Path: ethernet3.performance.ifOutPriorityQueues.packets.total

       64 bit unsigned wrappable counter."
   ::= {pr1645v2Lan3MCOutQueuesEntry 50790400}

pr1645v2Lan3MCOutQueuesPacketsDirectTx OBJECT-TYPE
   SYNTAX      Counter64
   MAX-ACCESS  read-only
   STATUS      current
   DESCRIPTION
      "Path: ethernet3.performance.ifOutPriorityQueues.packets.directTx

       64 bit unsigned wrappable counter."
   ::= {pr1645v2Lan3MCOutQueuesEntry 50397184}

pr1645v2Lan3MCOutQueuesPacketsQueued OBJECT-TYPE
   SYNTAX      Counter64
   MAX-ACCESS  read-only
   STATUS      current
   DESCRIPTION
      "Path: ethernet3.performance.ifOutPriorityQueues.packets.queued

       64 bit unsigned wrappable counter."
   ::= {pr1645v2Lan3MCOutQueuesEntry 50462720}

pr1645v2Lan3MCOutQueuesPacketsDropped OBJECT-TYPE
   SYNTAX      Counter64
   MAX-ACCESS  read-only
   STATUS      current
   DESCRIPTION
      "Path: ethernet3.performance.ifOutPriorityQueues.packets.dropped

       64 bit unsigned wrappable counter."
   ::= {pr1645v2Lan3MCOutQueuesEntry 50528256}

pr1645v2Lan3MCOutQueuesPacketsRedDropped OBJECT-TYPE
   SYNTAX      Counter64
   MAX-ACCESS  read-only
   STATUS      current
   DESCRIPTION
      "Path: ethernet3.performance.ifOutPriorityQueues.packets.redDropped

       64 bit unsigned wrappable counter."
   ::= {pr1645v2Lan3MCOutQueuesEntry 50724864}

pr1645v2Lan3MCOutQueuesPacketsCirTx OBJECT-TYPE
   SYNTAX      Counter64
   MAX-ACCESS  read-only
   STATUS      current
   DESCRIPTION
      "Path: ethernet3.performance.ifOutPriorityQueues.packets.cirTx

       64 bit unsigned wrappable counter."
   ::= {pr1645v2Lan3MCOutQueuesEntry 50593792}

pr1645v2Lan3MCOutQueuesPacketsEirTx OBJECT-TYPE
   SYNTAX      Counter64
   MAX-ACCESS  read-only
   STATUS      current
   DESCRIPTION
      "Path: ethernet3.performance.ifOutPriorityQueues.packets.eirTx

       64 bit unsigned wrappable counter."
   ::= {pr1645v2Lan3MCOutQueuesEntry 50659328}

pr1645v2Lan3MCOutQueuesPacketsViolateTx OBJECT-TYPE
   SYNTAX      Counter64
   MAX-ACCESS  read-only
   STATUS      current
   DESCRIPTION
      "Path: ethernet3.performance.ifOutPriorityQueues.packets.violateTx

       64 bit unsigned wrappable counter."
   ::= {pr1645v2Lan3MCOutQueuesEntry 50855936}

pr1645v2Lan3MCOutQueuesOctetsTotal OBJECT-TYPE
   SYNTAX      Counter64
   MAX-ACCESS  read-only
   STATUS      current
   DESCRIPTION
      "Path: ethernet3.performance.ifOutPriorityQueues.octets.total

       64 bit unsigned wrappable counter."
   ::= {pr1645v2Lan3MCOutQueuesEntry 67567616}

pr1645v2Lan3MCOutQueuesOctetsDirectTx OBJECT-TYPE
   SYNTAX      Counter64
   MAX-ACCESS  read-only
   STATUS      current
   DESCRIPTION
      "Path: ethernet3.performance.ifOutPriorityQueues.octets.directTx

       64 bit unsigned wrappable counter."
   ::= {pr1645v2Lan3MCOutQueuesEntry 67174400}

pr1645v2Lan3MCOutQueuesOctetsQueued OBJECT-TYPE
   SYNTAX      Counter64
   MAX-ACCESS  read-only
   STATUS      current
   DESCRIPTION
      "Path: ethernet3.performance.ifOutPriorityQueues.octets.queued

       64 bit unsigned wrappable counter."
   ::= {pr1645v2Lan3MCOutQueuesEntry 67239936}

pr1645v2Lan3MCOutQueuesOctetsDropped OBJECT-TYPE
   SYNTAX      Counter64
   MAX-ACCESS  read-only
   STATUS      current
   DESCRIPTION
      "Path: ethernet3.performance.ifOutPriorityQueues.octets.dropped

       64 bit unsigned wrappable counter."
   ::= {pr1645v2Lan3MCOutQueuesEntry 67305472}

pr1645v2Lan3MCOutQueuesOctetsRedDropped OBJECT-TYPE
   SYNTAX      Counter64
   MAX-ACCESS  read-only
   STATUS      current
   DESCRIPTION
      "Path: ethernet3.performance.ifOutPriorityQueues.octets.redDropped

       64 bit unsigned wrappable counter."
   ::= {pr1645v2Lan3MCOutQueuesEntry 67502080}

pr1645v2Lan3MCOutQueuesOctetsCirTx OBJECT-TYPE
   SYNTAX      Counter64
   MAX-ACCESS  read-only
   STATUS      current
   DESCRIPTION
      "Path: ethernet3.performance.ifOutPriorityQueues.octets.cirTx

       64 bit unsigned wrappable counter."
   ::= {pr1645v2Lan3MCOutQueuesEntry 67371008}

pr1645v2Lan3MCOutQueuesOctetsEirTx OBJECT-TYPE
   SYNTAX      Counter64
   MAX-ACCESS  read-only
   STATUS      current
   DESCRIPTION
      "Path: ethernet3.performance.ifOutPriorityQueues.octets.eirTx

       64 bit unsigned wrappable counter."
   ::= {pr1645v2Lan3MCOutQueuesEntry 67436544}

pr1645v2Lan3MCOutQueuesOctetsViolateTx OBJECT-TYPE
   SYNTAX      Counter64
   MAX-ACCESS  read-only
   STATUS      current
   DESCRIPTION
      "Path: ethernet3.performance.ifOutPriorityQueues.octets.violateTx

       64 bit unsigned wrappable counter."
   ::= {pr1645v2Lan3MCOutQueuesEntry 67633152}

pr1645v2Lan3MCOutQueuesOctetsBandwidth15sec OBJECT-TYPE
   SYNTAX      Integer32
   MAX-ACCESS  read-only
   STATUS      current
   DESCRIPTION
      "Path: ethernet3.performance.ifOutPriorityQueues.octets.bandwidth.15sec

       unit name = bps
       formula = 8 * ; 8 /"
   ::= {pr1645v2Lan3MCOutQueuesEntry 70386944}

pr1645v2Lan3MCOutQueuesOctetsBandwidth30sec OBJECT-TYPE
   SYNTAX      Integer32
   MAX-ACCESS  read-only
   STATUS      current
   DESCRIPTION
      "Path: ethernet3.performance.ifOutPriorityQueues.octets.bandwidth.30sec

       unit name = bps
       formula = 8 * ; 8 /"
   ::= {pr1645v2Lan3MCOutQueuesEntry 70388224}

pr1645v2Lan3MCOutQueuesOctetsBandwidth1min OBJECT-TYPE
   SYNTAX      Integer32
   MAX-ACCESS  read-only
   STATUS      current
   DESCRIPTION
      "Path: ethernet3.performance.ifOutPriorityQueues.octets.bandwidth.1min

       unit name = bps
       formula = 8 * ; 8 /"
   ::= {pr1645v2Lan3MCOutQueuesEntry 70390784}

pr1645v2Lan3MCOutQueuesOctetsBandwidth2min OBJECT-TYPE
   SYNTAX      Integer32
   MAX-ACCESS  read-only
   STATUS      current
   DESCRIPTION
      "Path: ethernet3.performance.ifOutPriorityQueues.octets.bandwidth.2min

       unit name = bps
       formula = 8 * ; 8 /"
   ::= {pr1645v2Lan3MCOutQueuesEntry 70395904}

pr1645v2Lan3MCOutQueuesOctetsBandwidth5min OBJECT-TYPE
   SYNTAX      Integer32
   MAX-ACCESS  read-only
   STATUS      current
   DESCRIPTION
      "Path: ethernet3.performance.ifOutPriorityQueues.octets.bandwidth.5min

       unit name = bps
       formula = 8 * ; 8 /"
   ::= {pr1645v2Lan3MCOutQueuesEntry 70411264}

pr1645v2Lan3MCOutQueuesH2Performance OBJECT-TYPE
   SYNTAX      SEQUENCE OF Pr1645v2Lan3MCOutQueuesH2PerformanceEntry
   MAX-ACCESS  not-accessible
   STATUS      current
   DESCRIPTION
      ""
   ::= {pr1645v2Lan3MCOutQueues 83886080}

pr1645v2Lan3MCOutQueuesH2PerformanceEntry OBJECT-TYPE
   SYNTAX      Pr1645v2Lan3MCOutQueuesH2PerformanceEntry
   MAX-ACCESS  not-accessible
   STATUS      current
   DESCRIPTION
      ""
   INDEX      { pr1645v2Lan3MCOutQueuesTableIx,
                pr1645v2Lan3MCOutQueuesH2PerformanceTableIx }
   ::= {pr1645v2Lan3MCOutQueuesH2Performance 1}

Pr1645v2Lan3MCOutQueuesH2PerformanceEntry ::=
   SEQUENCE
      {
      pr1645v2Lan3MCOutQueuesH2PerformanceTableIx
         TableIndex,
      pr1645v2Lan3MCOutQueuesH2PerformanceSysUpTime
         TimeTicks,
      pr1645v2Lan3MCOutQueuesH2PerformanceTotPkts
         Counter64,
      pr1645v2Lan3MCOutQueuesH2PerformanceDirTxPkts
         Counter64,
      pr1645v2Lan3MCOutQueuesH2PerformanceQdPkts
         Counter64,
      pr1645v2Lan3MCOutQueuesH2PerformanceDropPkts
         Counter64,
      pr1645v2Lan3MCOutQueuesH2PerformanceRDropPkts
         Counter64,
      pr1645v2Lan3MCOutQueuesH2PerformanceCirTxPkts
         Counter64,
      pr1645v2Lan3MCOutQueuesH2PerformanceEirTxPkts
         Counter64,
      pr1645v2Lan3MCOutQueuesH2PerformanceViolTxPkts
         Counter64,
      pr1645v2Lan3MCOutQueuesH2PerformanceTotOcts
         Counter64,
      pr1645v2Lan3MCOutQueuesH2PerformanceDirTxOcts
         Counter64,
      pr1645v2Lan3MCOutQueuesH2PerformanceQdOcts
         Counter64,
      pr1645v2Lan3MCOutQueuesH2PerformanceDropOcts
         Counter64,
      pr1645v2Lan3MCOutQueuesH2PerformanceRDropOcts
         Counter64,
      pr1645v2Lan3MCOutQueuesH2PerformanceCirTxOcts
         Counter64,
      pr1645v2Lan3MCOutQueuesH2PerformanceEirTxOcts
         Counter64,
      pr1645v2Lan3MCOutQueuesH2PerformanceViolTxOcts
         Counter64,
      pr1645v2Lan3MCOutQueuesH2PerformanceBandwidth
         Integer32
      }

pr1645v2Lan3MCOutQueuesH2PerformanceTableIx OBJECT-TYPE
   SYNTAX      TableIndex
   MAX-ACCESS  not-accessible
   STATUS      current
   DESCRIPTION
      ""
   ::= {pr1645v2Lan3MCOutQueuesH2PerformanceEntry 11}

pr1645v2Lan3MCOutQueuesH2PerformanceSysUpTime OBJECT-TYPE
   SYNTAX      TimeTicks
   MAX-ACCESS  read-only
   STATUS      current
   DESCRIPTION
      "Path: ethernet3.performance.ifOutPriorityQueues.h2Performance.sysUpTime

       Time in centi-second."
   ::= {pr1645v2Lan3MCOutQueuesH2PerformanceEntry 16777216}

pr1645v2Lan3MCOutQueuesH2PerformanceTotPkts OBJECT-TYPE
   SYNTAX      Counter64
   MAX-ACCESS  read-only
   STATUS      current
   DESCRIPTION
      "Path: ethernet3.performance.ifOutPriorityQueues.h2Performance.totalPkts

       64 bit unsigned wrappable counter."
   ::= {pr1645v2Lan3MCOutQueuesH2PerformanceEntry 234881024}

pr1645v2Lan3MCOutQueuesH2PerformanceDirTxPkts OBJECT-TYPE
   SYNTAX      Counter64
   MAX-ACCESS  read-only
   STATUS      current
   DESCRIPTION
      "Path: ethernet3.performance.ifOutPriorityQueues.h2Performance.directTxPkts

       64 bit unsigned wrappable counter."
   ::= {pr1645v2Lan3MCOutQueuesH2PerformanceEntry 33554432}

pr1645v2Lan3MCOutQueuesH2PerformanceQdPkts OBJECT-TYPE
   SYNTAX      Counter64
   MAX-ACCESS  read-only
   STATUS      current
   DESCRIPTION
      "Path: ethernet3.performance.ifOutPriorityQueues.h2Performance.queuedPkts

       64 bit unsigned wrappable counter."
   ::= {pr1645v2Lan3MCOutQueuesH2PerformanceEntry 50331648}

pr1645v2Lan3MCOutQueuesH2PerformanceDropPkts OBJECT-TYPE
   SYNTAX      Counter64
   MAX-ACCESS  read-only
   STATUS      current
   DESCRIPTION
      "Path: ethernet3.performance.ifOutPriorityQueues.h2Performance.droppedPkts

       64 bit unsigned wrappable counter."
   ::= {pr1645v2Lan3MCOutQueuesH2PerformanceEntry 67108864}

pr1645v2Lan3MCOutQueuesH2PerformanceRDropPkts OBJECT-TYPE
   SYNTAX      Counter64
   MAX-ACCESS  read-only
   STATUS      current
   DESCRIPTION
      "Path: ethernet3.performance.ifOutPriorityQueues.h2Performance.redDroppedPkts

       64 bit unsigned wrappable counter."
   ::= {pr1645v2Lan3MCOutQueuesH2PerformanceEntry 201326592}

pr1645v2Lan3MCOutQueuesH2PerformanceCirTxPkts OBJECT-TYPE
   SYNTAX      Counter64
   MAX-ACCESS  read-only
   STATUS      current
   DESCRIPTION
      "Path: ethernet3.performance.ifOutPriorityQueues.h2Performance.cirTxPkts

       64 bit unsigned wrappable counter."
   ::= {pr1645v2Lan3MCOutQueuesH2PerformanceEntry 83886080}

pr1645v2Lan3MCOutQueuesH2PerformanceEirTxPkts OBJECT-TYPE
   SYNTAX      Counter64
   MAX-ACCESS  read-only
   STATUS      current
   DESCRIPTION
      "Path: ethernet3.performance.ifOutPriorityQueues.h2Performance.eirTxPkts

       64 bit unsigned wrappable counter."
   ::= {pr1645v2Lan3MCOutQueuesH2PerformanceEntry 100663296}

pr1645v2Lan3MCOutQueuesH2PerformanceViolTxPkts OBJECT-TYPE
   SYNTAX      Counter64
   MAX-ACCESS  read-only
   STATUS      current
   DESCRIPTION
      "Path: ethernet3.performance.ifOutPriorityQueues.h2Performance.violateTxPkts

       64 bit unsigned wrappable counter."
   ::= {pr1645v2Lan3MCOutQueuesH2PerformanceEntry 301989888}

pr1645v2Lan3MCOutQueuesH2PerformanceTotOcts OBJECT-TYPE
   SYNTAX      Counter64
   MAX-ACCESS  read-only
   STATUS      current
   DESCRIPTION
      "Path: ethernet3.performance.ifOutPriorityQueues.h2Performance.totalOctets

       64 bit unsigned wrappable counter."
   ::= {pr1645v2Lan3MCOutQueuesH2PerformanceEntry 251658240}

pr1645v2Lan3MCOutQueuesH2PerformanceDirTxOcts OBJECT-TYPE
   SYNTAX      Counter64
   MAX-ACCESS  read-only
   STATUS      current
   DESCRIPTION
      "Path: ethernet3.performance.ifOutPriorityQueues.h2Performance.directTxOctets

       64 bit unsigned wrappable counter."
   ::= {pr1645v2Lan3MCOutQueuesH2PerformanceEntry 117440512}

pr1645v2Lan3MCOutQueuesH2PerformanceQdOcts OBJECT-TYPE
   SYNTAX      Counter64
   MAX-ACCESS  read-only
   STATUS      current
   DESCRIPTION
      "Path: ethernet3.performance.ifOutPriorityQueues.h2Performance.queuedOctets

       64 bit unsigned wrappable counter."
   ::= {pr1645v2Lan3MCOutQueuesH2PerformanceEntry 134217728}

pr1645v2Lan3MCOutQueuesH2PerformanceDropOcts OBJECT-TYPE
   SYNTAX      Counter64
   MAX-ACCESS  read-only
   STATUS      current
   DESCRIPTION
      "Path: ethernet3.performance.ifOutPriorityQueues.h2Performance.droppedOctets

       64 bit unsigned wrappable counter."
   ::= {pr1645v2Lan3MCOutQueuesH2PerformanceEntry 150994944}

pr1645v2Lan3MCOutQueuesH2PerformanceRDropOcts OBJECT-TYPE
   SYNTAX      Counter64
   MAX-ACCESS  read-only
   STATUS      current
   DESCRIPTION
      "Path: ethernet3.performance.ifOutPriorityQueues.h2Performance.redDroppedOctets

       64 bit unsigned wrappable counter."
   ::= {pr1645v2Lan3MCOutQueuesH2PerformanceEntry 218103808}

pr1645v2Lan3MCOutQueuesH2PerformanceCirTxOcts OBJECT-TYPE
   SYNTAX      Counter64
   MAX-ACCESS  read-only
   STATUS      current
   DESCRIPTION
      "Path: ethernet3.performance.ifOutPriorityQueues.h2Performance.cirTxOctets

       64 bit unsigned wrappable counter."
   ::= {pr1645v2Lan3MCOutQueuesH2PerformanceEntry 167772160}

pr1645v2Lan3MCOutQueuesH2PerformanceEirTxOcts OBJECT-TYPE
   SYNTAX      Counter64
   MAX-ACCESS  read-only
   STATUS      current
   DESCRIPTION
      "Path: ethernet3.performance.ifOutPriorityQueues.h2Performance.eirTxOctets

       64 bit unsigned wrappable counter."
   ::= {pr1645v2Lan3MCOutQueuesH2PerformanceEntry 184549376}

pr1645v2Lan3MCOutQueuesH2PerformanceViolTxOcts OBJECT-TYPE
   SYNTAX      Counter64
   MAX-ACCESS  read-only
   STATUS      current
   DESCRIPTION
      "Path: ethernet3.performance.ifOutPriorityQueues.h2Performance.violateTxOctets

       64 bit unsigned wrappable counter."
   ::= {pr1645v2Lan3MCOutQueuesH2PerformanceEntry 318767104}

pr1645v2Lan3MCOutQueuesH2PerformanceBandwidth OBJECT-TYPE
   SYNTAX      Integer32
   MAX-ACCESS  read-only
   STATUS      current
   DESCRIPTION
      "Path: ethernet3.performance.ifOutPriorityQueues.h2Performance.bandwidth

       unit name = bps
       formula = 8 * ; 8 /"
   ::= {pr1645v2Lan3MCOutQueuesH2PerformanceEntry 268435456}

pr1645v2Lan3MCOutQueuesH24Performance OBJECT-TYPE
   SYNTAX      SEQUENCE OF Pr1645v2Lan3MCOutQueuesH24PerformanceEntry
   MAX-ACCESS  not-accessible
   STATUS      current
   DESCRIPTION
      ""
   ::= {pr1645v2Lan3MCOutQueues 100663296}

pr1645v2Lan3MCOutQueuesH24PerformanceEntry OBJECT-TYPE
   SYNTAX      Pr1645v2Lan3MCOutQueuesH24PerformanceEntry
   MAX-ACCESS  not-accessible
   STATUS      current
   DESCRIPTION
      ""
   INDEX      { pr1645v2Lan3MCOutQueuesTableIx,
                pr1645v2Lan3MCOutQueuesH24PerformanceTableIx }
   ::= {pr1645v2Lan3MCOutQueuesH24Performance 1}

Pr1645v2Lan3MCOutQueuesH24PerformanceEntry ::=
   SEQUENCE
      {
      pr1645v2Lan3MCOutQueuesH24PerformanceTableIx
         TableIndex,
      pr1645v2Lan3MCOutQueuesH24PerformanceSysUpTime
         TimeTicks,
      pr1645v2Lan3MCOutQueuesH24PerformanceTotPkts
         Counter64,
      pr1645v2Lan3MCOutQueuesH24PerformanceDirTxPkts
         Counter64,
      pr1645v2Lan3MCOutQueuesH24PerformanceQdPkts
         Counter64,
      pr1645v2Lan3MCOutQueuesH24PerformanceDropPkts
         Counter64,
      pr1645v2Lan3MCOutQueuesH24PerformanceRDropPkts
         Counter64,
      pr1645v2Lan3MCOutQueuesH24PerformanceCirTxPkts
         Counter64,
      pr1645v2Lan3MCOutQueuesH24PerformanceEirTxPkts
         Counter64,
      pr1645v2Lan3MCOutQueuesH24PerformanceViolTxPkts
         Counter64,
      pr1645v2Lan3MCOutQueuesH24PerformanceTotOcts
         Counter64,
      pr1645v2Lan3MCOutQueuesH24PerformanceDirTxOcts
         Counter64,
      pr1645v2Lan3MCOutQueuesH24PerformanceQdOcts
         Counter64,
      pr1645v2Lan3MCOutQueuesH24PerformanceDropOcts
         Counter64,
      pr1645v2Lan3MCOutQueuesH24PerformanceRDropOcts
         Counter64,
      pr1645v2Lan3MCOutQueuesH24PerformanceCirTxOcts
         Counter64,
      pr1645v2Lan3MCOutQueuesH24PerformanceEirTxOcts
         Counter64,
      pr1645v2Lan3MCOutQueuesH24PerformanceViolTxOcts
         Counter64,
      pr1645v2Lan3MCOutQueuesH24PerformanceBandwidth
         Integer32
      }

pr1645v2Lan3MCOutQueuesH24PerformanceTableIx OBJECT-TYPE
   SYNTAX      TableIndex
   MAX-ACCESS  not-accessible
   STATUS      current
   DESCRIPTION
      ""
   ::= {pr1645v2Lan3MCOutQueuesH24PerformanceEntry 11}

pr1645v2Lan3MCOutQueuesH24PerformanceSysUpTime OBJECT-TYPE
   SYNTAX      TimeTicks
   MAX-ACCESS  read-only
   STATUS      current
   DESCRIPTION
      "Path: ethernet3.performance.ifOutPriorityQueues.h24Performance.sysUpTime

       Time in centi-second."
   ::= {pr1645v2Lan3MCOutQueuesH24PerformanceEntry 16777216}

pr1645v2Lan3MCOutQueuesH24PerformanceTotPkts OBJECT-TYPE
   SYNTAX      Counter64
   MAX-ACCESS  read-only
   STATUS      current
   DESCRIPTION
      "Path: ethernet3.performance.ifOutPriorityQueues.h24Performance.totalPkts

       64 bit unsigned wrappable counter."
   ::= {pr1645v2Lan3MCOutQueuesH24PerformanceEntry 234881024}

pr1645v2Lan3MCOutQueuesH24PerformanceDirTxPkts OBJECT-TYPE
   SYNTAX      Counter64
   MAX-ACCESS  read-only
   STATUS      current
   DESCRIPTION
      "Path: ethernet3.performance.ifOutPriorityQueues.h24Performance.directTxPkts

       64 bit unsigned wrappable counter."
   ::= {pr1645v2Lan3MCOutQueuesH24PerformanceEntry 33554432}

pr1645v2Lan3MCOutQueuesH24PerformanceQdPkts OBJECT-TYPE
   SYNTAX      Counter64
   MAX-ACCESS  read-only
   STATUS      current
   DESCRIPTION
      "Path: ethernet3.performance.ifOutPriorityQueues.h24Performance.queuedPkts

       64 bit unsigned wrappable counter."
   ::= {pr1645v2Lan3MCOutQueuesH24PerformanceEntry 50331648}

pr1645v2Lan3MCOutQueuesH24PerformanceDropPkts OBJECT-TYPE
   SYNTAX      Counter64
   MAX-ACCESS  read-only
   STATUS      current
   DESCRIPTION
      "Path: ethernet3.performance.ifOutPriorityQueues.h24Performance.droppedPkts

       64 bit unsigned wrappable counter."
   ::= {pr1645v2Lan3MCOutQueuesH24PerformanceEntry 67108864}

pr1645v2Lan3MCOutQueuesH24PerformanceRDropPkts OBJECT-TYPE
   SYNTAX      Counter64
   MAX-ACCESS  read-only
   STATUS      current
   DESCRIPTION
      "Path: ethernet3.performance.ifOutPriorityQueues.h24Performance.redDroppedPkts

       64 bit unsigned wrappable counter."
   ::= {pr1645v2Lan3MCOutQueuesH24PerformanceEntry 201326592}

pr1645v2Lan3MCOutQueuesH24PerformanceCirTxPkts OBJECT-TYPE
   SYNTAX      Counter64
   MAX-ACCESS  read-only
   STATUS      current
   DESCRIPTION
      "Path: ethernet3.performance.ifOutPriorityQueues.h24Performance.cirTxPkts

       64 bit unsigned wrappable counter."
   ::= {pr1645v2Lan3MCOutQueuesH24PerformanceEntry 83886080}

pr1645v2Lan3MCOutQueuesH24PerformanceEirTxPkts OBJECT-TYPE
   SYNTAX      Counter64
   MAX-ACCESS  read-only
   STATUS      current
   DESCRIPTION
      "Path: ethernet3.performance.ifOutPriorityQueues.h24Performance.eirTxPkts

       64 bit unsigned wrappable counter."
   ::= {pr1645v2Lan3MCOutQueuesH24PerformanceEntry 100663296}

pr1645v2Lan3MCOutQueuesH24PerformanceViolTxPkts OBJECT-TYPE
   SYNTAX      Counter64
   MAX-ACCESS  read-only
   STATUS      current
   DESCRIPTION
      "Path: ethernet3.performance.ifOutPriorityQueues.h24Performance.violateTxPkts

       64 bit unsigned wrappable counter."
   ::= {pr1645v2Lan3MCOutQueuesH24PerformanceEntry 301989888}

pr1645v2Lan3MCOutQueuesH24PerformanceTotOcts OBJECT-TYPE
   SYNTAX      Counter64
   MAX-ACCESS  read-only
   STATUS      current
   DESCRIPTION
      "Path: ethernet3.performance.ifOutPriorityQueues.h24Performance.totalOctets

       64 bit unsigned wrappable counter."
   ::= {pr1645v2Lan3MCOutQueuesH24PerformanceEntry 251658240}

pr1645v2Lan3MCOutQueuesH24PerformanceDirTxOcts OBJECT-TYPE
   SYNTAX      Counter64
   MAX-ACCESS  read-only
   STATUS      current
   DESCRIPTION
      "Path: ethernet3.performance.ifOutPriorityQueues.h24Performance.directTxOctets

       64 bit unsigned wrappable counter."
   ::= {pr1645v2Lan3MCOutQueuesH24PerformanceEntry 117440512}

pr1645v2Lan3MCOutQueuesH24PerformanceQdOcts OBJECT-TYPE
   SYNTAX      Counter64
   MAX-ACCESS  read-only
   STATUS      current
   DESCRIPTION
      "Path: ethernet3.performance.ifOutPriorityQueues.h24Performance.queuedOctets

       64 bit unsigned wrappable counter."
   ::= {pr1645v2Lan3MCOutQueuesH24PerformanceEntry 134217728}

pr1645v2Lan3MCOutQueuesH24PerformanceDropOcts OBJECT-TYPE
   SYNTAX      Counter64
   MAX-ACCESS  read-only
   STATUS      current
   DESCRIPTION
      "Path: ethernet3.performance.ifOutPriorityQueues.h24Performance.droppedOctets

       64 bit unsigned wrappable counter."
   ::= {pr1645v2Lan3MCOutQueuesH24PerformanceEntry 150994944}

pr1645v2Lan3MCOutQueuesH24PerformanceRDropOcts OBJECT-TYPE
   SYNTAX      Counter64
   MAX-ACCESS  read-only
   STATUS      current
   DESCRIPTION
      "Path: ethernet3.performance.ifOutPriorityQueues.h24Performance.redDroppedOctets

       64 bit unsigned wrappable counter."
   ::= {pr1645v2Lan3MCOutQueuesH24PerformanceEntry 218103808}

pr1645v2Lan3MCOutQueuesH24PerformanceCirTxOcts OBJECT-TYPE
   SYNTAX      Counter64
   MAX-ACCESS  read-only
   STATUS      current
   DESCRIPTION
      "Path: ethernet3.performance.ifOutPriorityQueues.h24Performance.cirTxOctets

       64 bit unsigned wrappable counter."
   ::= {pr1645v2Lan3MCOutQueuesH24PerformanceEntry 167772160}

pr1645v2Lan3MCOutQueuesH24PerformanceEirTxOcts OBJECT-TYPE
   SYNTAX      Counter64
   MAX-ACCESS  read-only
   STATUS      current
   DESCRIPTION
      "Path: ethernet3.performance.ifOutPriorityQueues.h24Performance.eirTxOctets

       64 bit unsigned wrappable counter."
   ::= {pr1645v2Lan3MCOutQueuesH24PerformanceEntry 184549376}

pr1645v2Lan3MCOutQueuesH24PerformanceViolTxOcts OBJECT-TYPE
   SYNTAX      Counter64
   MAX-ACCESS  read-only
   STATUS      current
   DESCRIPTION
      "Path: ethernet3.performance.ifOutPriorityQueues.h24Performance.violateTxOctets

       64 bit unsigned wrappable counter."
   ::= {pr1645v2Lan3MCOutQueuesH24PerformanceEntry 318767104}

pr1645v2Lan3MCOutQueuesH24PerformanceBandwidth OBJECT-TYPE
   SYNTAX      Integer32
   MAX-ACCESS  read-only
   STATUS      current
   DESCRIPTION
      "Path: ethernet3.performance.ifOutPriorityQueues.h24Performance.bandwidth

       unit name = bps
       formula = 8 * ; 8 /"
   ::= {pr1645v2Lan3MCOutQueuesH24PerformanceEntry 268435456}

pr1645v2Lan3MCOutQueuesD7Performance OBJECT-TYPE
   SYNTAX      SEQUENCE OF Pr1645v2Lan3MCOutQueuesD7PerformanceEntry
   MAX-ACCESS  not-accessible
   STATUS      current
   DESCRIPTION
      ""
   ::= {pr1645v2Lan3MCOutQueues 117440512}

pr1645v2Lan3MCOutQueuesD7PerformanceEntry OBJECT-TYPE
   SYNTAX      Pr1645v2Lan3MCOutQueuesD7PerformanceEntry
   MAX-ACCESS  not-accessible
   STATUS      current
   DESCRIPTION
      ""
   INDEX      { pr1645v2Lan3MCOutQueuesTableIx,
                pr1645v2Lan3MCOutQueuesD7PerformanceTableIx }
   ::= {pr1645v2Lan3MCOutQueuesD7Performance 1}

Pr1645v2Lan3MCOutQueuesD7PerformanceEntry ::=
   SEQUENCE
      {
      pr1645v2Lan3MCOutQueuesD7PerformanceTableIx
         TableIndex,
      pr1645v2Lan3MCOutQueuesD7PerformanceSysUpTime
         TimeTicks,
      pr1645v2Lan3MCOutQueuesD7PerformanceTotPkts
         Counter64,
      pr1645v2Lan3MCOutQueuesD7PerformanceDirTxPkts
         Counter64,
      pr1645v2Lan3MCOutQueuesD7PerformanceQdPkts
         Counter64,
      pr1645v2Lan3MCOutQueuesD7PerformanceDropPkts
         Counter64,
      pr1645v2Lan3MCOutQueuesD7PerformanceRDropPkts
         Counter64,
      pr1645v2Lan3MCOutQueuesD7PerformanceCirTxPkts
         Counter64,
      pr1645v2Lan3MCOutQueuesD7PerformanceEirTxPkts
         Counter64,
      pr1645v2Lan3MCOutQueuesD7PerformanceViolTxPkts
         Counter64,
      pr1645v2Lan3MCOutQueuesD7PerformanceTotOcts
         Counter64,
      pr1645v2Lan3MCOutQueuesD7PerformanceDirTxOcts
         Counter64,
      pr1645v2Lan3MCOutQueuesD7PerformanceQdOcts
         Counter64,
      pr1645v2Lan3MCOutQueuesD7PerformanceDropOcts
         Counter64,
      pr1645v2Lan3MCOutQueuesD7PerformanceRDropOcts
         Counter64,
      pr1645v2Lan3MCOutQueuesD7PerformanceCirTxOcts
         Counter64,
      pr1645v2Lan3MCOutQueuesD7PerformanceEirTxOcts
         Counter64,
      pr1645v2Lan3MCOutQueuesD7PerformanceViolTxOcts
         Counter64,
      pr1645v2Lan3MCOutQueuesD7PerformanceBandwidth
         Integer32
      }

pr1645v2Lan3MCOutQueuesD7PerformanceTableIx OBJECT-TYPE
   SYNTAX      TableIndex
   MAX-ACCESS  not-accessible
   STATUS      current
   DESCRIPTION
      ""
   ::= {pr1645v2Lan3MCOutQueuesD7PerformanceEntry 11}

pr1645v2Lan3MCOutQueuesD7PerformanceSysUpTime OBJECT-TYPE
   SYNTAX      TimeTicks
   MAX-ACCESS  read-only
   STATUS      current
   DESCRIPTION
      "Path: ethernet3.performance.ifOutPriorityQueues.d7Performance.sysUpTime

       Time in centi-second."
   ::= {pr1645v2Lan3MCOutQueuesD7PerformanceEntry 16777216}

pr1645v2Lan3MCOutQueuesD7PerformanceTotPkts OBJECT-TYPE
   SYNTAX      Counter64
   MAX-ACCESS  read-only
   STATUS      current
   DESCRIPTION
      "Path: ethernet3.performance.ifOutPriorityQueues.d7Performance.totalPkts

       64 bit unsigned wrappable counter."
   ::= {pr1645v2Lan3MCOutQueuesD7PerformanceEntry 234881024}

pr1645v2Lan3MCOutQueuesD7PerformanceDirTxPkts OBJECT-TYPE
   SYNTAX      Counter64
   MAX-ACCESS  read-only
   STATUS      current
   DESCRIPTION
      "Path: ethernet3.performance.ifOutPriorityQueues.d7Performance.directTxPkts

       64 bit unsigned wrappable counter."
   ::= {pr1645v2Lan3MCOutQueuesD7PerformanceEntry 33554432}

pr1645v2Lan3MCOutQueuesD7PerformanceQdPkts OBJECT-TYPE
   SYNTAX      Counter64
   MAX-ACCESS  read-only
   STATUS      current
   DESCRIPTION
      "Path: ethernet3.performance.ifOutPriorityQueues.d7Performance.queuedPkts

       64 bit unsigned wrappable counter."
   ::= {pr1645v2Lan3MCOutQueuesD7PerformanceEntry 50331648}

pr1645v2Lan3MCOutQueuesD7PerformanceDropPkts OBJECT-TYPE
   SYNTAX      Counter64
   MAX-ACCESS  read-only
   STATUS      current
   DESCRIPTION
      "Path: ethernet3.performance.ifOutPriorityQueues.d7Performance.droppedPkts

       64 bit unsigned wrappable counter."
   ::= {pr1645v2Lan3MCOutQueuesD7PerformanceEntry 67108864}

pr1645v2Lan3MCOutQueuesD7PerformanceRDropPkts OBJECT-TYPE
   SYNTAX      Counter64
   MAX-ACCESS  read-only
   STATUS      current
   DESCRIPTION
      "Path: ethernet3.performance.ifOutPriorityQueues.d7Performance.redDroppedPkts

       64 bit unsigned wrappable counter."
   ::= {pr1645v2Lan3MCOutQueuesD7PerformanceEntry 201326592}

pr1645v2Lan3MCOutQueuesD7PerformanceCirTxPkts OBJECT-TYPE
   SYNTAX      Counter64
   MAX-ACCESS  read-only
   STATUS      current
   DESCRIPTION
      "Path: ethernet3.performance.ifOutPriorityQueues.d7Performance.cirTxPkts

       64 bit unsigned wrappable counter."
   ::= {pr1645v2Lan3MCOutQueuesD7PerformanceEntry 83886080}

pr1645v2Lan3MCOutQueuesD7PerformanceEirTxPkts OBJECT-TYPE
   SYNTAX      Counter64
   MAX-ACCESS  read-only
   STATUS      current
   DESCRIPTION
      "Path: ethernet3.performance.ifOutPriorityQueues.d7Performance.eirTxPkts

       64 bit unsigned wrappable counter."
   ::= {pr1645v2Lan3MCOutQueuesD7PerformanceEntry 100663296}

pr1645v2Lan3MCOutQueuesD7PerformanceViolTxPkts OBJECT-TYPE
   SYNTAX      Counter64
   MAX-ACCESS  read-only
   STATUS      current
   DESCRIPTION
      "Path: ethernet3.performance.ifOutPriorityQueues.d7Performance.violateTxPkts

       64 bit unsigned wrappable counter."
   ::= {pr1645v2Lan3MCOutQueuesD7PerformanceEntry 301989888}

pr1645v2Lan3MCOutQueuesD7PerformanceTotOcts OBJECT-TYPE
   SYNTAX      Counter64
   MAX-ACCESS  read-only
   STATUS      current
   DESCRIPTION
      "Path: ethernet3.performance.ifOutPriorityQueues.d7Performance.totalOctets

       64 bit unsigned wrappable counter."
   ::= {pr1645v2Lan3MCOutQueuesD7PerformanceEntry 251658240}

pr1645v2Lan3MCOutQueuesD7PerformanceDirTxOcts OBJECT-TYPE
   SYNTAX      Counter64
   MAX-ACCESS  read-only
   STATUS      current
   DESCRIPTION
      "Path: ethernet3.performance.ifOutPriorityQueues.d7Performance.directTxOctets

       64 bit unsigned wrappable counter."
   ::= {pr1645v2Lan3MCOutQueuesD7PerformanceEntry 117440512}

pr1645v2Lan3MCOutQueuesD7PerformanceQdOcts OBJECT-TYPE
   SYNTAX      Counter64
   MAX-ACCESS  read-only
   STATUS      current
   DESCRIPTION
      "Path: ethernet3.performance.ifOutPriorityQueues.d7Performance.queuedOctets

       64 bit unsigned wrappable counter."
   ::= {pr1645v2Lan3MCOutQueuesD7PerformanceEntry 134217728}

pr1645v2Lan3MCOutQueuesD7PerformanceDropOcts OBJECT-TYPE
   SYNTAX      Counter64
   MAX-ACCESS  read-only
   STATUS      current
   DESCRIPTION
      "Path: ethernet3.performance.ifOutPriorityQueues.d7Performance.droppedOctets

       64 bit unsigned wrappable counter."
   ::= {pr1645v2Lan3MCOutQueuesD7PerformanceEntry 150994944}

pr1645v2Lan3MCOutQueuesD7PerformanceRDropOcts OBJECT-TYPE
   SYNTAX      Counter64
   MAX-ACCESS  read-only
   STATUS      current
   DESCRIPTION
      "Path: ethernet3.performance.ifOutPriorityQueues.d7Performance.redDroppedOctets

       64 bit unsigned wrappable counter."
   ::= {pr1645v2Lan3MCOutQueuesD7PerformanceEntry 218103808}

pr1645v2Lan3MCOutQueuesD7PerformanceCirTxOcts OBJECT-TYPE
   SYNTAX      Counter64
   MAX-ACCESS  read-only
   STATUS      current
   DESCRIPTION
      "Path: ethernet3.performance.ifOutPriorityQueues.d7Performance.cirTxOctets

       64 bit unsigned wrappable counter."
   ::= {pr1645v2Lan3MCOutQueuesD7PerformanceEntry 167772160}

pr1645v2Lan3MCOutQueuesD7PerformanceEirTxOcts OBJECT-TYPE
   SYNTAX      Counter64
   MAX-ACCESS  read-only
   STATUS      current
   DESCRIPTION
      "Path: ethernet3.performance.ifOutPriorityQueues.d7Performance.eirTxOctets

       64 bit unsigned wrappable counter."
   ::= {pr1645v2Lan3MCOutQueuesD7PerformanceEntry 184549376}

pr1645v2Lan3MCOutQueuesD7PerformanceViolTxOcts OBJECT-TYPE
   SYNTAX      Counter64
   MAX-ACCESS  read-only
   STATUS      current
   DESCRIPTION
      "Path: ethernet3.performance.ifOutPriorityQueues.d7Performance.violateTxOctets

       64 bit unsigned wrappable counter."
   ::= {pr1645v2Lan3MCOutQueuesD7PerformanceEntry 318767104}

pr1645v2Lan3MCOutQueuesD7PerformanceBandwidth OBJECT-TYPE
   SYNTAX      Integer32
   MAX-ACCESS  read-only
   STATUS      current
   DESCRIPTION
      "Path: ethernet3.performance.ifOutPriorityQueues.d7Performance.bandwidth

       unit name = bps
       formula = 8 * ; 8 /"
   ::= {pr1645v2Lan3MCOutQueuesD7PerformanceEntry 268435456}


pr1645v2Lan3MCOutBandwidth OBJECT IDENTIFIER ::= {pr1645v2Lan3MC 182}

pr1645v2Lan3MCOutBandwidthSSC OBJECT IDENTIFIER ::= {pr1645v2Lan3MCOutBandwidth 1}

pr1645v2Lan3MCOutBandwidthEntry OBJECT IDENTIFIER ::= {pr1645v2Lan3MCOutBandwidthSSC 1}

pr1645v2Lan3MCOutBandwidth15sec OBJECT-TYPE
   SYNTAX      Integer32
   MAX-ACCESS  read-only
   STATUS      current
   DESCRIPTION
      "Path: ethernet3.performance.ifOutBandwidth.15sec

       unit name = bps
       formula = 8 * ; 8 /"
   ::= {pr1645v2Lan3MCOutBandwidthEntry 83886080}

pr1645v2Lan3MCOutBandwidth30sec OBJECT-TYPE
   SYNTAX      Integer32
   MAX-ACCESS  read-only
   STATUS      current
   DESCRIPTION
      "Path: ethernet3.performance.ifOutBandwidth.30sec

       unit name = bps
       formula = 8 * ; 8 /"
   ::= {pr1645v2Lan3MCOutBandwidthEntry 167772160}

pr1645v2Lan3MCOutBandwidth1min OBJECT-TYPE
   SYNTAX      Integer32
   MAX-ACCESS  read-only
   STATUS      current
   DESCRIPTION
      "Path: ethernet3.performance.ifOutBandwidth.1min

       unit name = bps
       formula = 8 * ; 8 /"
   ::= {pr1645v2Lan3MCOutBandwidthEntry 335544320}

pr1645v2Lan3MCOutBandwidth2min OBJECT-TYPE
   SYNTAX      Integer32
   MAX-ACCESS  read-only
   STATUS      current
   DESCRIPTION
      "Path: ethernet3.performance.ifOutBandwidth.2min

       unit name = bps
       formula = 8 * ; 8 /"
   ::= {pr1645v2Lan3MCOutBandwidthEntry 671088640}

pr1645v2Lan3MCOutBandwidth5min OBJECT-TYPE
   SYNTAX      Integer32
   MAX-ACCESS  read-only
   STATUS      current
   DESCRIPTION
      "Path: ethernet3.performance.ifOutBandwidth.5min

       unit name = bps
       formula = 8 * ; 8 /"
   ::= {pr1645v2Lan3MCOutBandwidthEntry 1677721600}


pr1645v2Lan3MCInP OBJECT IDENTIFIER ::= {pr1645v2Lan3MC 307}

pr1645v2Lan3MCInPSSCTable OBJECT-TYPE
   SYNTAX      SEQUENCE OF Pr1645v2Lan3MCInPEntry
   MAX-ACCESS  not-accessible
   STATUS      current
   DESCRIPTION
      "h2IfInPerformance"
   ::= {pr1645v2Lan3MCInP 1}

pr1645v2Lan3MCInPEntry OBJECT-TYPE
   SYNTAX      Pr1645v2Lan3MCInPEntry
   MAX-ACCESS  not-accessible
   STATUS      current
   DESCRIPTION
      ""
   INDEX      { pr1645v2Lan3MCInPTableIx }
   ::= {pr1645v2Lan3MCInPSSCTable 1}

Pr1645v2Lan3MCInPEntry ::=
   SEQUENCE
      {
      pr1645v2Lan3MCInPTableIx
         TableIndex,
      pr1645v2Lan3MCInPSysUpTime
         TimeTicks,
      pr1645v2Lan3MCInPIfUpTime
         TimeTicks,
      pr1645v2Lan3MCInPIfStatChanges
         Counter32,
      pr1645v2Lan3MCInPIfInOctets
         Counter64,
      pr1645v2Lan3MCInPIfInUCPkts
         Counter64,
      pr1645v2Lan3MCInPIfInNUCPkts
         Counter64,
      pr1645v2Lan3MCInPIfInBCPkts
         Counter64,
      pr1645v2Lan3MCInPIfInMCPkts
         Counter64,
      pr1645v2Lan3MCInPIfInDiscards
         Counter64,
      pr1645v2Lan3MCInPIfInErrors
         Counter64,
      pr1645v2Lan3MCInPIfInUnkwn
         Counter64,
      pr1645v2Lan3MCInPInDropEx
         Counter64,
      pr1645v2Lan3MCInPInDropNoMac
         Counter64,
      pr1645v2Lan3MCInPInDropNUCast
         Counter64,
      pr1645v2Lan3MCInPInDropFilter
         Counter64,
      pr1645v2Lan3MCInPIfInBandwidth
         Integer32,
      pr1645v2Lan3MCInPIfOutOctets
         Counter64,
      pr1645v2Lan3MCInPIfOutUCPkts
         Counter64,
      pr1645v2Lan3MCInPIfOutNUCPkts
         Counter64,
      pr1645v2Lan3MCInPIfOutBCPkts
         Counter64,
      pr1645v2Lan3MCInPIfOutMCPkts
         Counter64,
      pr1645v2Lan3MCInPIfOutDiscards
         Counter64,
      pr1645v2Lan3MCInPIfOutErrors
         Counter64,
      pr1645v2Lan3MCInPOutDropEx
         Counter64,
      pr1645v2Lan3MCInPOutDropNoArp
         Counter64,
      pr1645v2Lan3MCInPOutDropFilter
         Counter64,
      pr1645v2Lan3MCInPIfOutBandwidth
         Integer32,
      pr1645v2Lan3MCInPIfErrSec
         Counter32
      }

pr1645v2Lan3MCInPTableIx OBJECT-TYPE
   SYNTAX      TableIndex
   MAX-ACCESS  not-accessible
   STATUS      current
   DESCRIPTION
      ""
   ::= {pr1645v2Lan3MCInPEntry 11}

pr1645v2Lan3MCInPSysUpTime OBJECT-TYPE
   SYNTAX      TimeTicks
   MAX-ACCESS  read-only
   STATUS      current
   DESCRIPTION
      "Path: ethernet3.performance.h2Performance.sysUpTime

       Time in centi-second."
   ::= {pr1645v2Lan3MCInPEntry 16777216}

pr1645v2Lan3MCInPIfUpTime OBJECT-TYPE
   SYNTAX      TimeTicks
   MAX-ACCESS  read-only
   STATUS      current
   DESCRIPTION
      "Path: ethernet3.performance.h2Performance.ifUpTime

       Time in centi-second."
   ::= {pr1645v2Lan3MCInPEntry 33554432}

pr1645v2Lan3MCInPIfStatChanges OBJECT-TYPE
   SYNTAX      Counter32
   MAX-ACCESS  read-only
   STATUS      current
   DESCRIPTION
      "Path: ethernet3.performance.h2Performance.ifStatusChanges

       32 bit unsigned wrappable counter."
   ::= {pr1645v2Lan3MCInPEntry 50331648}

pr1645v2Lan3MCInPIfInOctets OBJECT-TYPE
   SYNTAX      Counter64
   MAX-ACCESS  read-only
   STATUS      current
   DESCRIPTION
      "Path: ethernet3.performance.h2Performance.ifInOctets

       64 bit unsigned wrappable counter."
   ::= {pr1645v2Lan3MCInPEntry 67108864}

pr1645v2Lan3MCInPIfInUCPkts OBJECT-TYPE
   SYNTAX      Counter64
   MAX-ACCESS  read-only
   STATUS      current
   DESCRIPTION
      "Path: ethernet3.performance.h2Performance.ifInUcastPkts

       64 bit unsigned wrappable counter."
   ::= {pr1645v2Lan3MCInPEntry 83886080}

pr1645v2Lan3MCInPIfInNUCPkts OBJECT-TYPE
   SYNTAX      Counter64
   MAX-ACCESS  read-only
   STATUS      current
   DESCRIPTION
      "Path: ethernet3.performance.h2Performance.ifInNUcastPkts

       64 bit unsigned wrappable counter."
   ::= {pr1645v2Lan3MCInPEntry 100663296}

pr1645v2Lan3MCInPIfInBCPkts OBJECT-TYPE
   SYNTAX      Counter64
   MAX-ACCESS  read-only
   STATUS      current
   DESCRIPTION
      "Path: ethernet3.performance.h2Performance.ifInBcastPkts

       64 bit unsigned wrappable counter."
   ::= {pr1645v2Lan3MCInPEntry 419430400}

pr1645v2Lan3MCInPIfInMCPkts OBJECT-TYPE
   SYNTAX      Counter64
   MAX-ACCESS  read-only
   STATUS      current
   DESCRIPTION
      "Path: ethernet3.performance.h2Performance.ifInMcastPkts

       64 bit unsigned wrappable counter."
   ::= {pr1645v2Lan3MCInPEntry 436207616}

pr1645v2Lan3MCInPIfInDiscards OBJECT-TYPE
   SYNTAX      Counter64
   MAX-ACCESS  read-only
   STATUS      current
   DESCRIPTION
      "Path: ethernet3.performance.h2Performance.ifInDiscards

       64 bit unsigned wrappable counter."
   ::= {pr1645v2Lan3MCInPEntry 117440512}

pr1645v2Lan3MCInPIfInErrors OBJECT-TYPE
   SYNTAX      Counter64
   MAX-ACCESS  read-only
   STATUS      current
   DESCRIPTION
      "Path: ethernet3.performance.h2Performance.ifInErrors

       64 bit unsigned wrappable counter."
   ::= {pr1645v2Lan3MCInPEntry 134217728}

pr1645v2Lan3MCInPIfInUnkwn OBJECT-TYPE
   SYNTAX      Counter64
   MAX-ACCESS  read-only
   STATUS      current
   DESCRIPTION
      "Path: ethernet3.performance.h2Performance.ifInUnknownProtos

       64 bit unsigned wrappable counter."
   ::= {pr1645v2Lan3MCInPEntry 150994944}

pr1645v2Lan3MCInPInDropEx OBJECT-TYPE
   SYNTAX      Counter64
   MAX-ACCESS  read-only
   STATUS      current
   DESCRIPTION
      "Path: ethernet3.performance.h2Performance.ifInDropLevelExceeded

       64 bit unsigned wrappable counter."
   ::= {pr1645v2Lan3MCInPEntry 335544320}

pr1645v2Lan3MCInPInDropNoMac OBJECT-TYPE
   SYNTAX      Counter64
   MAX-ACCESS  read-only
   STATUS      current
   DESCRIPTION
      "Path: ethernet3.performance.h2Performance.fInDiscardsNoMacFit

       64 bit unsigned wrappable counter."
   ::= {pr1645v2Lan3MCInPEntry 301989888}

pr1645v2Lan3MCInPInDropNUCast OBJECT-TYPE
   SYNTAX      Counter64
   MAX-ACCESS  read-only
   STATUS      current
   DESCRIPTION
      "Path: ethernet3.performance.h2Performance.fInDiscardsNUCast

       64 bit unsigned wrappable counter."
   ::= {pr1645v2Lan3MCInPEntry 318767104}

pr1645v2Lan3MCInPInDropFilter OBJECT-TYPE
   SYNTAX      Counter64
   MAX-ACCESS  read-only
   STATUS      current
   DESCRIPTION
      "Path: ethernet3.performance.h2Performance.fInDiscardsFilter

       64 bit unsigned wrappable counter."
   ::= {pr1645v2Lan3MCInPEntry 385875968}

pr1645v2Lan3MCInPIfInBandwidth OBJECT-TYPE
   SYNTAX      Integer32
   MAX-ACCESS  read-only
   STATUS      current
   DESCRIPTION
      "Path: ethernet3.performance.h2Performance.ifInBandwidth

       unit name = bps
       formula = 8 * ; 8 /"
   ::= {pr1645v2Lan3MCInPEntry 268435456}

pr1645v2Lan3MCInPIfOutOctets OBJECT-TYPE
   SYNTAX      Counter64
   MAX-ACCESS  read-only
   STATUS      current
   DESCRIPTION
      "Path: ethernet3.performance.h2Performance.ifOutOctets

       64 bit unsigned wrappable counter."
   ::= {pr1645v2Lan3MCInPEntry 167772160}

pr1645v2Lan3MCInPIfOutUCPkts OBJECT-TYPE
   SYNTAX      Counter64
   MAX-ACCESS  read-only
   STATUS      current
   DESCRIPTION
      "Path: ethernet3.performance.h2Performance.ifOutUcastPkts

       64 bit unsigned wrappable counter."
   ::= {pr1645v2Lan3MCInPEntry 184549376}

pr1645v2Lan3MCInPIfOutNUCPkts OBJECT-TYPE
   SYNTAX      Counter64
   MAX-ACCESS  read-only
   STATUS      current
   DESCRIPTION
      "Path: ethernet3.performance.h2Performance.ifOutNUcastPkts

       64 bit unsigned wrappable counter."
   ::= {pr1645v2Lan3MCInPEntry 201326592}

pr1645v2Lan3MCInPIfOutBCPkts OBJECT-TYPE
   SYNTAX      Counter64
   MAX-ACCESS  read-only
   STATUS      current
   DESCRIPTION
      "Path: ethernet3.performance.h2Performance.ifOutBcastPkts

       64 bit unsigned wrappable counter."
   ::= {pr1645v2Lan3MCInPEntry 452984832}

pr1645v2Lan3MCInPIfOutMCPkts OBJECT-TYPE
   SYNTAX      Counter64
   MAX-ACCESS  read-only
   STATUS      current
   DESCRIPTION
      "Path: ethernet3.performance.h2Performance.ifOutMcastPkts

       64 bit unsigned wrappable counter."
   ::= {pr1645v2Lan3MCInPEntry 469762048}

pr1645v2Lan3MCInPIfOutDiscards OBJECT-TYPE
   SYNTAX      Counter64
   MAX-ACCESS  read-only
   STATUS      current
   DESCRIPTION
      "Path: ethernet3.performance.h2Performance.ifOutDiscards

       64 bit unsigned wrappable counter."
   ::= {pr1645v2Lan3MCInPEntry 218103808}

pr1645v2Lan3MCInPIfOutErrors OBJECT-TYPE
   SYNTAX      Counter64
   MAX-ACCESS  read-only
   STATUS      current
   DESCRIPTION
      "Path: ethernet3.performance.h2Performance.ifOutErrors

       64 bit unsigned wrappable counter."
   ::= {pr1645v2Lan3MCInPEntry 234881024}

pr1645v2Lan3MCInPOutDropEx OBJECT-TYPE
   SYNTAX      Counter64
   MAX-ACCESS  read-only
   STATUS      current
   DESCRIPTION
      "Path: ethernet3.performance.h2Performance.ifOutDropLevelExceeded

       64 bit unsigned wrappable counter."
   ::= {pr1645v2Lan3MCInPEntry 352321536}

pr1645v2Lan3MCInPOutDropNoArp OBJECT-TYPE
   SYNTAX      Counter64
   MAX-ACCESS  read-only
   STATUS      current
   DESCRIPTION
      "Path: ethernet3.performance.h2Performance.ifOutDiscardsNoArp

       64 bit unsigned wrappable counter."
   ::= {pr1645v2Lan3MCInPEntry 369098752}

pr1645v2Lan3MCInPOutDropFilter OBJECT-TYPE
   SYNTAX      Counter64
   MAX-ACCESS  read-only
   STATUS      current
   DESCRIPTION
      "Path: ethernet3.performance.h2Performance.ifOutDiscardsFilter

       64 bit unsigned wrappable counter."
   ::= {pr1645v2Lan3MCInPEntry 402653184}

pr1645v2Lan3MCInPIfOutBandwidth OBJECT-TYPE
   SYNTAX      Integer32
   MAX-ACCESS  read-only
   STATUS      current
   DESCRIPTION
      "Path: ethernet3.performance.h2Performance.ifOutBandwidth

       unit name = bps
       formula = 8 * ; 8 /"
   ::= {pr1645v2Lan3MCInPEntry 285212672}

pr1645v2Lan3MCInPIfErrSec OBJECT-TYPE
   SYNTAX      Counter32
   MAX-ACCESS  read-only
   STATUS      current
   DESCRIPTION
      "Path: ethernet3.performance.h2Performance.ifErrSec

       32 bit unsigned wrappable counter."
   ::= {pr1645v2Lan3MCInPEntry 251658240}


pr1645v2Lan3MCH24InP OBJECT IDENTIFIER ::= {pr1645v2Lan3MC 308}

pr1645v2Lan3MCH24InPSSCTable OBJECT-TYPE
   SYNTAX      SEQUENCE OF Pr1645v2Lan3MCH24InPEntry
   MAX-ACCESS  not-accessible
   STATUS      current
   DESCRIPTION
      "h24IfInPerformance"
   ::= {pr1645v2Lan3MCH24InP 1}

pr1645v2Lan3MCH24InPEntry OBJECT-TYPE
   SYNTAX      Pr1645v2Lan3MCH24InPEntry
   MAX-ACCESS  not-accessible
   STATUS      current
   DESCRIPTION
      ""
   INDEX      { pr1645v2Lan3MCH24InPTableIx }
   ::= {pr1645v2Lan3MCH24InPSSCTable 1}

Pr1645v2Lan3MCH24InPEntry ::=
   SEQUENCE
      {
      pr1645v2Lan3MCH24InPTableIx
         TableIndex,
      pr1645v2Lan3MCH24InPSysUpTime
         TimeTicks,
      pr1645v2Lan3MCH24InPIfUpTime
         TimeTicks,
      pr1645v2Lan3MCH24InPIfStatChanges
         Counter32,
      pr1645v2Lan3MCH24InPIfInOctets
         Counter64,
      pr1645v2Lan3MCH24InPIfInUCPkts
         Counter64,
      pr1645v2Lan3MCH24InPIfInNUCPkts
         Counter64,
      pr1645v2Lan3MCH24InPIfInBCPkts
         Counter64,
      pr1645v2Lan3MCH24InPIfInMCPkts
         Counter64,
      pr1645v2Lan3MCH24InPIfInDiscards
         Counter64,
      pr1645v2Lan3MCH24InPIfInErrors
         Counter64,
      pr1645v2Lan3MCH24InPIfInUnkwn
         Counter64,
      pr1645v2Lan3MCH24InPInDropEx
         Counter64,
      pr1645v2Lan3MCH24InPInDropNoMac
         Counter64,
      pr1645v2Lan3MCH24InPInDropNUCast
         Counter64,
      pr1645v2Lan3MCH24InPInDropFilter
         Counter64,
      pr1645v2Lan3MCH24InPIfInBandwidth
         Integer32,
      pr1645v2Lan3MCH24InPIfOutOctets
         Counter64,
      pr1645v2Lan3MCH24InPIfOutUCPkts
         Counter64,
      pr1645v2Lan3MCH24InPIfOutNUCPkts
         Counter64,
      pr1645v2Lan3MCH24InPIfOutBCPkts
         Counter64,
      pr1645v2Lan3MCH24InPIfOutMCPkts
         Counter64,
      pr1645v2Lan3MCH24InPIfOutDiscards
         Counter64,
      pr1645v2Lan3MCH24InPIfOutErrors
         Counter64,
      pr1645v2Lan3MCH24InPOutDropEx
         Counter64,
      pr1645v2Lan3MCH24InPOutDropNoArp
         Counter64,
      pr1645v2Lan3MCH24InPOutDropFilter
         Counter64,
      pr1645v2Lan3MCH24InPIfOutBandwidth
         Integer32,
      pr1645v2Lan3MCH24InPIfErrSec
         Counter32
      }

pr1645v2Lan3MCH24InPTableIx OBJECT-TYPE
   SYNTAX      TableIndex
   MAX-ACCESS  not-accessible
   STATUS      current
   DESCRIPTION
      ""
   ::= {pr1645v2Lan3MCH24InPEntry 11}

pr1645v2Lan3MCH24InPSysUpTime OBJECT-TYPE
   SYNTAX      TimeTicks
   MAX-ACCESS  read-only
   STATUS      current
   DESCRIPTION
      "Path: ethernet3.performance.h24Performance.sysUpTime

       Time in centi-second."
   ::= {pr1645v2Lan3MCH24InPEntry 16777216}

pr1645v2Lan3MCH24InPIfUpTime OBJECT-TYPE
   SYNTAX      TimeTicks
   MAX-ACCESS  read-only
   STATUS      current
   DESCRIPTION
      "Path: ethernet3.performance.h24Performance.ifUpTime

       Time in centi-second."
   ::= {pr1645v2Lan3MCH24InPEntry 33554432}

pr1645v2Lan3MCH24InPIfStatChanges OBJECT-TYPE
   SYNTAX      Counter32
   MAX-ACCESS  read-only
   STATUS      current
   DESCRIPTION
      "Path: ethernet3.performance.h24Performance.ifStatusChanges

       32 bit unsigned wrappable counter."
   ::= {pr1645v2Lan3MCH24InPEntry 50331648}

pr1645v2Lan3MCH24InPIfInOctets OBJECT-TYPE
   SYNTAX      Counter64
   MAX-ACCESS  read-only
   STATUS      current
   DESCRIPTION
      "Path: ethernet3.performance.h24Performance.ifInOctets

       64 bit unsigned wrappable counter."
   ::= {pr1645v2Lan3MCH24InPEntry 67108864}

pr1645v2Lan3MCH24InPIfInUCPkts OBJECT-TYPE
   SYNTAX      Counter64
   MAX-ACCESS  read-only
   STATUS      current
   DESCRIPTION
      "Path: ethernet3.performance.h24Performance.ifInUcastPkts

       64 bit unsigned wrappable counter."
   ::= {pr1645v2Lan3MCH24InPEntry 83886080}

pr1645v2Lan3MCH24InPIfInNUCPkts OBJECT-TYPE
   SYNTAX      Counter64
   MAX-ACCESS  read-only
   STATUS      current
   DESCRIPTION
      "Path: ethernet3.performance.h24Performance.ifInNUcastPkts

       64 bit unsigned wrappable counter."
   ::= {pr1645v2Lan3MCH24InPEntry 100663296}

pr1645v2Lan3MCH24InPIfInBCPkts OBJECT-TYPE
   SYNTAX      Counter64
   MAX-ACCESS  read-only
   STATUS      current
   DESCRIPTION
      "Path: ethernet3.performance.h24Performance.ifInBcastPkts

       64 bit unsigned wrappable counter."
   ::= {pr1645v2Lan3MCH24InPEntry 419430400}

pr1645v2Lan3MCH24InPIfInMCPkts OBJECT-TYPE
   SYNTAX      Counter64
   MAX-ACCESS  read-only
   STATUS      current
   DESCRIPTION
      "Path: ethernet3.performance.h24Performance.ifInMcastPkts

       64 bit unsigned wrappable counter."
   ::= {pr1645v2Lan3MCH24InPEntry 436207616}

pr1645v2Lan3MCH24InPIfInDiscards OBJECT-TYPE
   SYNTAX      Counter64
   MAX-ACCESS  read-only
   STATUS      current
   DESCRIPTION
      "Path: ethernet3.performance.h24Performance.ifInDiscards

       64 bit unsigned wrappable counter."
   ::= {pr1645v2Lan3MCH24InPEntry 117440512}

pr1645v2Lan3MCH24InPIfInErrors OBJECT-TYPE
   SYNTAX      Counter64
   MAX-ACCESS  read-only
   STATUS      current
   DESCRIPTION
      "Path: ethernet3.performance.h24Performance.ifInErrors

       64 bit unsigned wrappable counter."
   ::= {pr1645v2Lan3MCH24InPEntry 134217728}

pr1645v2Lan3MCH24InPIfInUnkwn OBJECT-TYPE
   SYNTAX      Counter64
   MAX-ACCESS  read-only
   STATUS      current
   DESCRIPTION
      "Path: ethernet3.performance.h24Performance.ifInUnknownProtos

       64 bit unsigned wrappable counter."
   ::= {pr1645v2Lan3MCH24InPEntry 150994944}

pr1645v2Lan3MCH24InPInDropEx OBJECT-TYPE
   SYNTAX      Counter64
   MAX-ACCESS  read-only
   STATUS      current
   DESCRIPTION
      "Path: ethernet3.performance.h24Performance.ifInDropLevelExceeded

       64 bit unsigned wrappable counter."
   ::= {pr1645v2Lan3MCH24InPEntry 335544320}

pr1645v2Lan3MCH24InPInDropNoMac OBJECT-TYPE
   SYNTAX      Counter64
   MAX-ACCESS  read-only
   STATUS      current
   DESCRIPTION
      "Path: ethernet3.performance.h24Performance.fInDiscardsNoMacFit

       64 bit unsigned wrappable counter."
   ::= {pr1645v2Lan3MCH24InPEntry 301989888}

pr1645v2Lan3MCH24InPInDropNUCast OBJECT-TYPE
   SYNTAX      Counter64
   MAX-ACCESS  read-only
   STATUS      current
   DESCRIPTION
      "Path: ethernet3.performance.h24Performance.fInDiscardsNUCast

       64 bit unsigned wrappable counter."
   ::= {pr1645v2Lan3MCH24InPEntry 318767104}

pr1645v2Lan3MCH24InPInDropFilter OBJECT-TYPE
   SYNTAX      Counter64
   MAX-ACCESS  read-only
   STATUS      current
   DESCRIPTION
      "Path: ethernet3.performance.h24Performance.fInDiscardsFilter

       64 bit unsigned wrappable counter."
   ::= {pr1645v2Lan3MCH24InPEntry 385875968}

pr1645v2Lan3MCH24InPIfInBandwidth OBJECT-TYPE
   SYNTAX      Integer32
   MAX-ACCESS  read-only
   STATUS      current
   DESCRIPTION
      "Path: ethernet3.performance.h24Performance.ifInBandwidth

       unit name = bps
       formula = 8 * ; 8 /"
   ::= {pr1645v2Lan3MCH24InPEntry 268435456}

pr1645v2Lan3MCH24InPIfOutOctets OBJECT-TYPE
   SYNTAX      Counter64
   MAX-ACCESS  read-only
   STATUS      current
   DESCRIPTION
      "Path: ethernet3.performance.h24Performance.ifOutOctets

       64 bit unsigned wrappable counter."
   ::= {pr1645v2Lan3MCH24InPEntry 167772160}

pr1645v2Lan3MCH24InPIfOutUCPkts OBJECT-TYPE
   SYNTAX      Counter64
   MAX-ACCESS  read-only
   STATUS      current
   DESCRIPTION
      "Path: ethernet3.performance.h24Performance.ifOutUcastPkts

       64 bit unsigned wrappable counter."
   ::= {pr1645v2Lan3MCH24InPEntry 184549376}

pr1645v2Lan3MCH24InPIfOutNUCPkts OBJECT-TYPE
   SYNTAX      Counter64
   MAX-ACCESS  read-only
   STATUS      current
   DESCRIPTION
      "Path: ethernet3.performance.h24Performance.ifOutNUcastPkts

       64 bit unsigned wrappable counter."
   ::= {pr1645v2Lan3MCH24InPEntry 201326592}

pr1645v2Lan3MCH24InPIfOutBCPkts OBJECT-TYPE
   SYNTAX      Counter64
   MAX-ACCESS  read-only
   STATUS      current
   DESCRIPTION
      "Path: ethernet3.performance.h24Performance.ifOutBcastPkts

       64 bit unsigned wrappable counter."
   ::= {pr1645v2Lan3MCH24InPEntry 452984832}

pr1645v2Lan3MCH24InPIfOutMCPkts OBJECT-TYPE
   SYNTAX      Counter64
   MAX-ACCESS  read-only
   STATUS      current
   DESCRIPTION
      "Path: ethernet3.performance.h24Performance.ifOutMcastPkts

       64 bit unsigned wrappable counter."
   ::= {pr1645v2Lan3MCH24InPEntry 469762048}

pr1645v2Lan3MCH24InPIfOutDiscards OBJECT-TYPE
   SYNTAX      Counter64
   MAX-ACCESS  read-only
   STATUS      current
   DESCRIPTION
      "Path: ethernet3.performance.h24Performance.ifOutDiscards

       64 bit unsigned wrappable counter."
   ::= {pr1645v2Lan3MCH24InPEntry 218103808}

pr1645v2Lan3MCH24InPIfOutErrors OBJECT-TYPE
   SYNTAX      Counter64
   MAX-ACCESS  read-only
   STATUS      current
   DESCRIPTION
      "Path: ethernet3.performance.h24Performance.ifOutErrors

       64 bit unsigned wrappable counter."
   ::= {pr1645v2Lan3MCH24InPEntry 234881024}

pr1645v2Lan3MCH24InPOutDropEx OBJECT-TYPE
   SYNTAX      Counter64
   MAX-ACCESS  read-only
   STATUS      current
   DESCRIPTION
      "Path: ethernet3.performance.h24Performance.ifOutDropLevelExceeded

       64 bit unsigned wrappable counter."
   ::= {pr1645v2Lan3MCH24InPEntry 352321536}

pr1645v2Lan3MCH24InPOutDropNoArp OBJECT-TYPE
   SYNTAX      Counter64
   MAX-ACCESS  read-only
   STATUS      current
   DESCRIPTION
      "Path: ethernet3.performance.h24Performance.ifOutDiscardsNoArp

       64 bit unsigned wrappable counter."
   ::= {pr1645v2Lan3MCH24InPEntry 369098752}

pr1645v2Lan3MCH24InPOutDropFilter OBJECT-TYPE
   SYNTAX      Counter64
   MAX-ACCESS  read-only
   STATUS      current
   DESCRIPTION
      "Path: ethernet3.performance.h24Performance.ifOutDiscardsFilter

       64 bit unsigned wrappable counter."
   ::= {pr1645v2Lan3MCH24InPEntry 402653184}

pr1645v2Lan3MCH24InPIfOutBandwidth OBJECT-TYPE
   SYNTAX      Integer32
   MAX-ACCESS  read-only
   STATUS      current
   DESCRIPTION
      "Path: ethernet3.performance.h24Performance.ifOutBandwidth

       unit name = bps
       formula = 8 * ; 8 /"
   ::= {pr1645v2Lan3MCH24InPEntry 285212672}

pr1645v2Lan3MCH24InPIfErrSec OBJECT-TYPE
   SYNTAX      Counter32
   MAX-ACCESS  read-only
   STATUS      current
   DESCRIPTION
      "Path: ethernet3.performance.h24Performance.ifErrSec

       32 bit unsigned wrappable counter."
   ::= {pr1645v2Lan3MCH24InPEntry 251658240}


pr1645v2Lan3MCD7InP OBJECT IDENTIFIER ::= {pr1645v2Lan3MC 309}

pr1645v2Lan3MCD7InPSSCTable OBJECT-TYPE
   SYNTAX      SEQUENCE OF Pr1645v2Lan3MCD7InPEntry
   MAX-ACCESS  not-accessible
   STATUS      current
   DESCRIPTION
      "d7IfInPerformance"
   ::= {pr1645v2Lan3MCD7InP 1}

pr1645v2Lan3MCD7InPEntry OBJECT-TYPE
   SYNTAX      Pr1645v2Lan3MCD7InPEntry
   MAX-ACCESS  not-accessible
   STATUS      current
   DESCRIPTION
      ""
   INDEX      { pr1645v2Lan3MCD7InPTableIx }
   ::= {pr1645v2Lan3MCD7InPSSCTable 1}

Pr1645v2Lan3MCD7InPEntry ::=
   SEQUENCE
      {
      pr1645v2Lan3MCD7InPTableIx
         TableIndex,
      pr1645v2Lan3MCD7InPSysUpTime
         TimeTicks,
      pr1645v2Lan3MCD7InPIfUpTime
         TimeTicks,
      pr1645v2Lan3MCD7InPIfStatChanges
         Counter32,
      pr1645v2Lan3MCD7InPIfInOctets
         Counter64,
      pr1645v2Lan3MCD7InPIfInUCPkts
         Counter64,
      pr1645v2Lan3MCD7InPIfInNUCPkts
         Counter64,
      pr1645v2Lan3MCD7InPIfInBCPkts
         Counter64,
      pr1645v2Lan3MCD7InPIfInMCPkts
         Counter64,
      pr1645v2Lan3MCD7InPIfInDiscards
         Counter64,
      pr1645v2Lan3MCD7InPIfInErrors
         Counter64,
      pr1645v2Lan3MCD7InPIfInUnkwn
         Counter64,
      pr1645v2Lan3MCD7InPInDropEx
         Counter64,
      pr1645v2Lan3MCD7InPInDropNoMac
         Counter64,
      pr1645v2Lan3MCD7InPInDropNUCast
         Counter64,
      pr1645v2Lan3MCD7InPInDropFilter
         Counter64,
      pr1645v2Lan3MCD7InPIfInBandwidth
         Integer32,
      pr1645v2Lan3MCD7InPIfOutOctets
         Counter64,
      pr1645v2Lan3MCD7InPIfOutUCPkts
         Counter64,
      pr1645v2Lan3MCD7InPIfOutNUCPkts
         Counter64,
      pr1645v2Lan3MCD7InPIfOutBCPkts
         Counter64,
      pr1645v2Lan3MCD7InPIfOutMCPkts
         Counter64,
      pr1645v2Lan3MCD7InPIfOutDiscards
         Counter64,
      pr1645v2Lan3MCD7InPIfOutErrors
         Counter64,
      pr1645v2Lan3MCD7InPOutDropEx
         Counter64,
      pr1645v2Lan3MCD7InPOutDropNoArp
         Counter64,
      pr1645v2Lan3MCD7InPOutDropFilter
         Counter64,
      pr1645v2Lan3MCD7InPIfOutBandwidth
         Integer32,
      pr1645v2Lan3MCD7InPIfErrSec
         Counter32
      }

pr1645v2Lan3MCD7InPTableIx OBJECT-TYPE
   SYNTAX      TableIndex
   MAX-ACCESS  not-accessible
   STATUS      current
   DESCRIPTION
      ""
   ::= {pr1645v2Lan3MCD7InPEntry 11}

pr1645v2Lan3MCD7InPSysUpTime OBJECT-TYPE
   SYNTAX      TimeTicks
   MAX-ACCESS  read-only
   STATUS      current
   DESCRIPTION
      "Path: ethernet3.performance.d7Performance.sysUpTime

       Time in centi-second."
   ::= {pr1645v2Lan3MCD7InPEntry 16777216}

pr1645v2Lan3MCD7InPIfUpTime OBJECT-TYPE
   SYNTAX      TimeTicks
   MAX-ACCESS  read-only
   STATUS      current
   DESCRIPTION
      "Path: ethernet3.performance.d7Performance.ifUpTime

       Time in centi-second."
   ::= {pr1645v2Lan3MCD7InPEntry 33554432}

pr1645v2Lan3MCD7InPIfStatChanges OBJECT-TYPE
   SYNTAX      Counter32
   MAX-ACCESS  read-only
   STATUS      current
   DESCRIPTION
      "Path: ethernet3.performance.d7Performance.ifStatusChanges

       32 bit unsigned wrappable counter."
   ::= {pr1645v2Lan3MCD7InPEntry 50331648}

pr1645v2Lan3MCD7InPIfInOctets OBJECT-TYPE
   SYNTAX      Counter64
   MAX-ACCESS  read-only
   STATUS      current
   DESCRIPTION
      "Path: ethernet3.performance.d7Performance.ifInOctets

       64 bit unsigned wrappable counter."
   ::= {pr1645v2Lan3MCD7InPEntry 67108864}

pr1645v2Lan3MCD7InPIfInUCPkts OBJECT-TYPE
   SYNTAX      Counter64
   MAX-ACCESS  read-only
   STATUS      current
   DESCRIPTION
      "Path: ethernet3.performance.d7Performance.ifInUcastPkts

       64 bit unsigned wrappable counter."
   ::= {pr1645v2Lan3MCD7InPEntry 83886080}

pr1645v2Lan3MCD7InPIfInNUCPkts OBJECT-TYPE
   SYNTAX      Counter64
   MAX-ACCESS  read-only
   STATUS      current
   DESCRIPTION
      "Path: ethernet3.performance.d7Performance.ifInNUcastPkts

       64 bit unsigned wrappable counter."
   ::= {pr1645v2Lan3MCD7InPEntry 100663296}

pr1645v2Lan3MCD7InPIfInBCPkts OBJECT-TYPE
   SYNTAX      Counter64
   MAX-ACCESS  read-only
   STATUS      current
   DESCRIPTION
      "Path: ethernet3.performance.d7Performance.ifInBcastPkts

       64 bit unsigned wrappable counter."
   ::= {pr1645v2Lan3MCD7InPEntry 419430400}

pr1645v2Lan3MCD7InPIfInMCPkts OBJECT-TYPE
   SYNTAX      Counter64
   MAX-ACCESS  read-only
   STATUS      current
   DESCRIPTION
      "Path: ethernet3.performance.d7Performance.ifInMcastPkts

       64 bit unsigned wrappable counter."
   ::= {pr1645v2Lan3MCD7InPEntry 436207616}

pr1645v2Lan3MCD7InPIfInDiscards OBJECT-TYPE
   SYNTAX      Counter64
   MAX-ACCESS  read-only
   STATUS      current
   DESCRIPTION
      "Path: ethernet3.performance.d7Performance.ifInDiscards

       64 bit unsigned wrappable counter."
   ::= {pr1645v2Lan3MCD7InPEntry 117440512}

pr1645v2Lan3MCD7InPIfInErrors OBJECT-TYPE
   SYNTAX      Counter64
   MAX-ACCESS  read-only
   STATUS      current
   DESCRIPTION
      "Path: ethernet3.performance.d7Performance.ifInErrors

       64 bit unsigned wrappable counter."
   ::= {pr1645v2Lan3MCD7InPEntry 134217728}

pr1645v2Lan3MCD7InPIfInUnkwn OBJECT-TYPE
   SYNTAX      Counter64
   MAX-ACCESS  read-only
   STATUS      current
   DESCRIPTION
      "Path: ethernet3.performance.d7Performance.ifInUnknownProtos

       64 bit unsigned wrappable counter."
   ::= {pr1645v2Lan3MCD7InPEntry 150994944}

pr1645v2Lan3MCD7InPInDropEx OBJECT-TYPE
   SYNTAX      Counter64
   MAX-ACCESS  read-only
   STATUS      current
   DESCRIPTION
      "Path: ethernet3.performance.d7Performance.ifInDropLevelExceeded

       64 bit unsigned wrappable counter."
   ::= {pr1645v2Lan3MCD7InPEntry 335544320}

pr1645v2Lan3MCD7InPInDropNoMac OBJECT-TYPE
   SYNTAX      Counter64
   MAX-ACCESS  read-only
   STATUS      current
   DESCRIPTION
      "Path: ethernet3.performance.d7Performance.fInDiscardsNoMacFit

       64 bit unsigned wrappable counter."
   ::= {pr1645v2Lan3MCD7InPEntry 301989888}

pr1645v2Lan3MCD7InPInDropNUCast OBJECT-TYPE
   SYNTAX      Counter64
   MAX-ACCESS  read-only
   STATUS      current
   DESCRIPTION
      "Path: ethernet3.performance.d7Performance.fInDiscardsNUCast

       64 bit unsigned wrappable counter."
   ::= {pr1645v2Lan3MCD7InPEntry 318767104}

pr1645v2Lan3MCD7InPInDropFilter OBJECT-TYPE
   SYNTAX      Counter64
   MAX-ACCESS  read-only
   STATUS      current
   DESCRIPTION
      "Path: ethernet3.performance.d7Performance.fInDiscardsFilter

       64 bit unsigned wrappable counter."
   ::= {pr1645v2Lan3MCD7InPEntry 385875968}

pr1645v2Lan3MCD7InPIfInBandwidth OBJECT-TYPE
   SYNTAX      Integer32
   MAX-ACCESS  read-only
   STATUS      current
   DESCRIPTION
      "Path: ethernet3.performance.d7Performance.ifInBandwidth

       unit name = bps
       formula = 8 * ; 8 /"
   ::= {pr1645v2Lan3MCD7InPEntry 268435456}

pr1645v2Lan3MCD7InPIfOutOctets OBJECT-TYPE
   SYNTAX      Counter64
   MAX-ACCESS  read-only
   STATUS      current
   DESCRIPTION
      "Path: ethernet3.performance.d7Performance.ifOutOctets

       64 bit unsigned wrappable counter."
   ::= {pr1645v2Lan3MCD7InPEntry 167772160}

pr1645v2Lan3MCD7InPIfOutUCPkts OBJECT-TYPE
   SYNTAX      Counter64
   MAX-ACCESS  read-only
   STATUS      current
   DESCRIPTION
      "Path: ethernet3.performance.d7Performance.ifOutUcastPkts

       64 bit unsigned wrappable counter."
   ::= {pr1645v2Lan3MCD7InPEntry 184549376}

pr1645v2Lan3MCD7InPIfOutNUCPkts OBJECT-TYPE
   SYNTAX      Counter64
   MAX-ACCESS  read-only
   STATUS      current
   DESCRIPTION
      "Path: ethernet3.performance.d7Performance.ifOutNUcastPkts

       64 bit unsigned wrappable counter."
   ::= {pr1645v2Lan3MCD7InPEntry 201326592}

pr1645v2Lan3MCD7InPIfOutBCPkts OBJECT-TYPE
   SYNTAX      Counter64
   MAX-ACCESS  read-only
   STATUS      current
   DESCRIPTION
      "Path: ethernet3.performance.d7Performance.ifOutBcastPkts

       64 bit unsigned wrappable counter."
   ::= {pr1645v2Lan3MCD7InPEntry 452984832}

pr1645v2Lan3MCD7InPIfOutMCPkts OBJECT-TYPE
   SYNTAX      Counter64
   MAX-ACCESS  read-only
   STATUS      current
   DESCRIPTION
      "Path: ethernet3.performance.d7Performance.ifOutMcastPkts

       64 bit unsigned wrappable counter."
   ::= {pr1645v2Lan3MCD7InPEntry 469762048}

pr1645v2Lan3MCD7InPIfOutDiscards OBJECT-TYPE
   SYNTAX      Counter64
   MAX-ACCESS  read-only
   STATUS      current
   DESCRIPTION
      "Path: ethernet3.performance.d7Performance.ifOutDiscards

       64 bit unsigned wrappable counter."
   ::= {pr1645v2Lan3MCD7InPEntry 218103808}

pr1645v2Lan3MCD7InPIfOutErrors OBJECT-TYPE
   SYNTAX      Counter64
   MAX-ACCESS  read-only
   STATUS      current
   DESCRIPTION
      "Path: ethernet3.performance.d7Performance.ifOutErrors

       64 bit unsigned wrappable counter."
   ::= {pr1645v2Lan3MCD7InPEntry 234881024}

pr1645v2Lan3MCD7InPOutDropEx OBJECT-TYPE
   SYNTAX      Counter64
   MAX-ACCESS  read-only
   STATUS      current
   DESCRIPTION
      "Path: ethernet3.performance.d7Performance.ifOutDropLevelExceeded

       64 bit unsigned wrappable counter."
   ::= {pr1645v2Lan3MCD7InPEntry 352321536}

pr1645v2Lan3MCD7InPOutDropNoArp OBJECT-TYPE
   SYNTAX      Counter64
   MAX-ACCESS  read-only
   STATUS      current
   DESCRIPTION
      "Path: ethernet3.performance.d7Performance.ifOutDiscardsNoArp

       64 bit unsigned wrappable counter."
   ::= {pr1645v2Lan3MCD7InPEntry 369098752}

pr1645v2Lan3MCD7InPOutDropFilter OBJECT-TYPE
   SYNTAX      Counter64
   MAX-ACCESS  read-only
   STATUS      current
   DESCRIPTION
      "Path: ethernet3.performance.d7Performance.ifOutDiscardsFilter

       64 bit unsigned wrappable counter."
   ::= {pr1645v2Lan3MCD7InPEntry 402653184}

pr1645v2Lan3MCD7InPIfOutBandwidth OBJECT-TYPE
   SYNTAX      Integer32
   MAX-ACCESS  read-only
   STATUS      current
   DESCRIPTION
      "Path: ethernet3.performance.d7Performance.ifOutBandwidth

       unit name = bps
       formula = 8 * ; 8 /"
   ::= {pr1645v2Lan3MCD7InPEntry 285212672}

pr1645v2Lan3MCD7InPIfErrSec OBJECT-TYPE
   SYNTAX      Counter32
   MAX-ACCESS  read-only
   STATUS      current
   DESCRIPTION
      "Path: ethernet3.performance.d7Performance.ifErrSec

       32 bit unsigned wrappable counter."
   ::= {pr1645v2Lan3MCD7InPEntry 251658240}


pr1645v2Lan3MCOam OBJECT IDENTIFIER ::= {pr1645v2Lan3MC 910}

pr1645v2Lan3MCOamSSC OBJECT IDENTIFIER ::= {pr1645v2Lan3MCOam 1}

pr1645v2Lan3MCOamEntry OBJECT IDENTIFIER ::= {pr1645v2Lan3MCOamSSC 1}

pr1645v2Lan3MCOamInformationTx OBJECT-TYPE
   SYNTAX      Counter32
   MAX-ACCESS  read-only
   STATUS      current
   DESCRIPTION
      "Path: ethernet3.performance.oam.informationTx

       32 bit unsigned wrappable counter."
   ::= {pr1645v2Lan3MCOamEntry 16777216}

pr1645v2Lan3MCOamInformationRx OBJECT-TYPE
   SYNTAX      Counter32
   MAX-ACCESS  read-only
   STATUS      current
   DESCRIPTION
      "Path: ethernet3.performance.oam.informationRx

       32 bit unsigned wrappable counter."
   ::= {pr1645v2Lan3MCOamEntry 33554432}

pr1645v2Lan3MCOamUniqueEventNotifTx OBJECT-TYPE
   SYNTAX      Counter32
   MAX-ACCESS  read-only
   STATUS      current
   DESCRIPTION
      "Path: ethernet3.performance.oam.uniqueEventNotifTx

       32 bit unsigned wrappable counter."
   ::= {pr1645v2Lan3MCOamEntry 50331648}

pr1645v2Lan3MCOamUniqueEventNotifRx OBJECT-TYPE
   SYNTAX      Counter32
   MAX-ACCESS  read-only
   STATUS      current
   DESCRIPTION
      "Path: ethernet3.performance.oam.uniqueEventNotifRx

       32 bit unsigned wrappable counter."
   ::= {pr1645v2Lan3MCOamEntry 67108864}

pr1645v2Lan3MCOamLoopbackCtrlTx OBJECT-TYPE
   SYNTAX      Counter32
   MAX-ACCESS  read-only
   STATUS      current
   DESCRIPTION
      "Path: ethernet3.performance.oam.loopbackCtrlTx

       32 bit unsigned wrappable counter."
   ::= {pr1645v2Lan3MCOamEntry 117440512}

pr1645v2Lan3MCOamLoopbackCtrlRx OBJECT-TYPE
   SYNTAX      Counter32
   MAX-ACCESS  read-only
   STATUS      current
   DESCRIPTION
      "Path: ethernet3.performance.oam.loopbackCtrlRx

       32 bit unsigned wrappable counter."
   ::= {pr1645v2Lan3MCOamEntry 134217728}

pr1645v2Lan3MCOamVarReqTx OBJECT-TYPE
   SYNTAX      Counter32
   MAX-ACCESS  read-only
   STATUS      current
   DESCRIPTION
      "Path: ethernet3.performance.oam.varReqTx

       32 bit unsigned wrappable counter."
   ::= {pr1645v2Lan3MCOamEntry 150994944}

pr1645v2Lan3MCOamVarReqRx OBJECT-TYPE
   SYNTAX      Counter32
   MAX-ACCESS  read-only
   STATUS      current
   DESCRIPTION
      "Path: ethernet3.performance.oam.varReqRx

       32 bit unsigned wrappable counter."
   ::= {pr1645v2Lan3MCOamEntry 167772160}

pr1645v2Lan3MCOamVarRespTx OBJECT-TYPE
   SYNTAX      Counter32
   MAX-ACCESS  read-only
   STATUS      current
   DESCRIPTION
      "Path: ethernet3.performance.oam.varRespTx

       32 bit unsigned wrappable counter."
   ::= {pr1645v2Lan3MCOamEntry 184549376}

pr1645v2Lan3MCOamVarRespRx OBJECT-TYPE
   SYNTAX      Counter32
   MAX-ACCESS  read-only
   STATUS      current
   DESCRIPTION
      "Path: ethernet3.performance.oam.varRespRx

       32 bit unsigned wrappable counter."
   ::= {pr1645v2Lan3MCOamEntry 201326592}

pr1645v2Lan3MCOamOrgSpecificTx OBJECT-TYPE
   SYNTAX      Counter32
   MAX-ACCESS  read-only
   STATUS      current
   DESCRIPTION
      "Path: ethernet3.performance.oam.orgSpecificTx

       32 bit unsigned wrappable counter."
   ::= {pr1645v2Lan3MCOamEntry 218103808}

pr1645v2Lan3MCOamOrgSpecificRx OBJECT-TYPE
   SYNTAX      Counter32
   MAX-ACCESS  read-only
   STATUS      current
   DESCRIPTION
      "Path: ethernet3.performance.oam.orgSpecificRx

       32 bit unsigned wrappable counter."
   ::= {pr1645v2Lan3MCOamEntry 234881024}

pr1645v2Lan3MCOamUnsupportedCodesTx OBJECT-TYPE
   SYNTAX      Counter32
   MAX-ACCESS  read-only
   STATUS      current
   DESCRIPTION
      "Path: ethernet3.performance.oam.unsupportedCodesTx

       32 bit unsigned wrappable counter."
   ::= {pr1645v2Lan3MCOamEntry 251658240}

pr1645v2Lan3MCOamUnsupportedCodesRx OBJECT-TYPE
   SYNTAX      Counter32
   MAX-ACCESS  read-only
   STATUS      current
   DESCRIPTION
      "Path: ethernet3.performance.oam.unsupportedCodesRx

       32 bit unsigned wrappable counter."
   ::= {pr1645v2Lan3MCOamEntry 268435456}

pr1645v2Lan3MCOamPduDiscardRx OBJECT-TYPE
   SYNTAX      Counter32
   MAX-ACCESS  read-only
   STATUS      current
   DESCRIPTION
      "Path: ethernet3.performance.oam.pduDiscardRx

       32 bit unsigned wrappable counter."
   ::= {pr1645v2Lan3MCOamEntry 1694498816}

pr1645v2Lan3MCOamDataDiscardTx OBJECT-TYPE
   SYNTAX      Counter32
   MAX-ACCESS  read-only
   STATUS      current
   DESCRIPTION
      "Path: ethernet3.performance.oam.dataDiscardTx

       32 bit unsigned wrappable counter."
   ::= {pr1645v2Lan3MCOamEntry 1711276032}

pr1645v2Lan3MCOamDataDiscardRx OBJECT-TYPE
   SYNTAX      Counter32
   MAX-ACCESS  read-only
   STATUS      current
   DESCRIPTION
      "Path: ethernet3.performance.oam.dataDiscardRx

       32 bit unsigned wrappable counter."
   ::= {pr1645v2Lan3MCOamEntry 1728053248}


pr1645v2Lan3MCVlan OBJECT IDENTIFIER ::= {pr1645v2Lan3MC 310}

pr1645v2Lan3MCVlanSSCTable OBJECT-TYPE
   SYNTAX      SEQUENCE OF Pr1645v2Lan3MCVlanEntry
   MAX-ACCESS  not-accessible
   STATUS      current
   DESCRIPTION
      ""
   ::= {pr1645v2Lan3MCVlan 1}

pr1645v2Lan3MCVlanEntry OBJECT-TYPE
   SYNTAX      Pr1645v2Lan3MCVlanEntry
   MAX-ACCESS  not-accessible
   STATUS      current
   DESCRIPTION
      ""
   INDEX      { pr1645v2Lan3MCVlanTableIx }
   ::= {pr1645v2Lan3MCVlanSSCTable 1}

Pr1645v2Lan3MCVlanEntry ::=
   SEQUENCE
      {
      pr1645v2Lan3MCVlanTableIx
         TableIndex,
      pr1645v2Lan3MCVlanName
         DisplayString,
      pr1645v2Lan3MCVlanMCInOctets
         Counter64,
      pr1645v2Lan3MCVlanMCInUcast
         Counter64,
      pr1645v2Lan3MCVlanMCInNUcastPkts
         Counter64,
      pr1645v2Lan3MCVlanMCInBcastPkts
         Counter64,
      pr1645v2Lan3MCVlanMCInMcastPkts
         Counter64,
      pr1645v2Lan3MCVlanMCInDiscards
         Counter64,
      pr1645v2Lan3MCVlanMCInErrors
         Counter64,
      pr1645v2Lan3MCVlanMCInUnknownProtos
         Counter64,
      pr1645v2Lan3MCVlanMCInDropEx
         Counter64,
      pr1645v2Lan3MCVlanMCInDropNoMac
         Counter64,
      pr1645v2Lan3MCVlanMCInDropNUCast
         Counter64,
      pr1645v2Lan3MCVlanMCInDropFilter
         Counter64,
      pr1645v2Lan3MCVlanMCInBandwidth15sec
         Integer32,
      pr1645v2Lan3MCVlanMCInBandwidth30sec
         Integer32,
      pr1645v2Lan3MCVlanMCInBandwidth1min
         Integer32,
      pr1645v2Lan3MCVlanMCInBandwidth2min
         Integer32,
      pr1645v2Lan3MCVlanMCInBandwidth5min
         Integer32,
      pr1645v2Lan3MCVlanMCOutOctets
         Counter64,
      pr1645v2Lan3MCVlanMCOutUcastPkts
         Counter64,
      pr1645v2Lan3MCVlanMCOutNUcastPkts
         Counter64,
      pr1645v2Lan3MCVlanMCOutBcastPkts
         Counter64,
      pr1645v2Lan3MCVlanMCOutMcastPkts
         Counter64,
      pr1645v2Lan3MCVlanMCOutDiscards
         Counter64,
      pr1645v2Lan3MCVlanMCOutErrors
         Counter64,
      pr1645v2Lan3MCVlanMCOutQLen
         Counter32,
      pr1645v2Lan3MCVlanMCOutDropEx
         Counter64,
      pr1645v2Lan3MCVlanMCOutDropNoArp
         Counter64,
      pr1645v2Lan3MCVlanMCOutDropFilter
         Counter64,
      pr1645v2Lan3MCVlanMCOutBandwidth15sec
         Integer32,
      pr1645v2Lan3MCVlanMCOutBandwidth30sec
         Integer32,
      pr1645v2Lan3MCVlanMCOutBandwidth1min
         Integer32,
      pr1645v2Lan3MCVlanMCOutBandwidth2min
         Integer32,
      pr1645v2Lan3MCVlanMCOutBandwidth5min
         Integer32,
      pr1645v2Lan3MCVlanVlanVid
         Integer32,
      pr1645v2Lan3MCVlanPppLinkMonitoringRequestsSent
         Gauge32,
      pr1645v2Lan3MCVlanPppLinkMonitoringRepliesRcvd
         Gauge32,
      pr1645v2Lan3MCVlanPppLinkMonitoringRequestsRcvd
         Gauge32,
      pr1645v2Lan3MCVlanPppLinkMonitoringRepliesSent
         Gauge32
      }

pr1645v2Lan3MCVlanTableIx OBJECT-TYPE
   SYNTAX      TableIndex
   MAX-ACCESS  not-accessible
   STATUS      current
   DESCRIPTION
      ""
   ::= {pr1645v2Lan3MCVlanEntry 11}

pr1645v2Lan3MCVlanName OBJECT-TYPE
   SYNTAX      DisplayString
   MAX-ACCESS  read-only
   STATUS      current
   DESCRIPTION
      "Path: ethernet3.performance.vlan.name"
   ::= {pr1645v2Lan3MCVlanEntry 16777216}

pr1645v2Lan3MCVlanMCInOctets OBJECT-TYPE
   SYNTAX      Counter64
   MAX-ACCESS  read-only
   STATUS      current
   DESCRIPTION
      "Path: ethernet3.performance.vlan.mibCounters.ifInOctets

       64 bit unsigned wrappable counter."
   ::= {pr1645v2Lan3MCVlanEntry 40697856}

pr1645v2Lan3MCVlanMCInUcast OBJECT-TYPE
   SYNTAX      Counter64
   MAX-ACCESS  read-only
   STATUS      current
   DESCRIPTION
      "Path: ethernet3.performance.vlan.mibCounters.ifInUcastPkts

       64 bit unsigned wrappable counter."
   ::= {pr1645v2Lan3MCVlanEntry 40763392}

pr1645v2Lan3MCVlanMCInNUcastPkts OBJECT-TYPE
   SYNTAX      Counter64
   MAX-ACCESS  read-only
   STATUS      current
   DESCRIPTION
      "Path: ethernet3.performance.vlan.mibCounters.ifInNUcastPkts

       64 bit unsigned wrappable counter."
   ::= {pr1645v2Lan3MCVlanEntry 40828928}

pr1645v2Lan3MCVlanMCInBcastPkts OBJECT-TYPE
   SYNTAX      Counter64
   MAX-ACCESS  read-only
   STATUS      current
   DESCRIPTION
      "Path: ethernet3.performance.vlan.mibCounters.ifInBcastPkts

       64 bit unsigned wrappable counter."
   ::= {pr1645v2Lan3MCVlanEntry 47382528}

pr1645v2Lan3MCVlanMCInMcastPkts OBJECT-TYPE
   SYNTAX      Counter64
   MAX-ACCESS  read-only
   STATUS      current
   DESCRIPTION
      "Path: ethernet3.performance.vlan.mibCounters.ifInMcastPkts

       64 bit unsigned wrappable counter."
   ::= {pr1645v2Lan3MCVlanEntry 48037888}

pr1645v2Lan3MCVlanMCInDiscards OBJECT-TYPE
   SYNTAX      Counter64
   MAX-ACCESS  read-only
   STATUS      current
   DESCRIPTION
      "Path: ethernet3.performance.vlan.mibCounters.ifInDiscards

       64 bit unsigned wrappable counter."
   ::= {pr1645v2Lan3MCVlanEntry 40894464}

pr1645v2Lan3MCVlanMCInErrors OBJECT-TYPE
   SYNTAX      Counter64
   MAX-ACCESS  read-only
   STATUS      current
   DESCRIPTION
      "Path: ethernet3.performance.vlan.mibCounters.ifInErrors

       64 bit unsigned wrappable counter."
   ::= {pr1645v2Lan3MCVlanEntry 40960000}

pr1645v2Lan3MCVlanMCInUnknownProtos OBJECT-TYPE
   SYNTAX      Counter64
   MAX-ACCESS  read-only
   STATUS      current
   DESCRIPTION
      "Path: ethernet3.performance.vlan.mibCounters.ifInUnknownProtos

       64 bit unsigned wrappable counter."
   ::= {pr1645v2Lan3MCVlanEntry 41025536}

pr1645v2Lan3MCVlanMCInDropEx OBJECT-TYPE
   SYNTAX      Counter64
   MAX-ACCESS  read-only
   STATUS      current
   DESCRIPTION
      "Path: ethernet3.performance.vlan.mibCounters.ifInDropLevelExceeded

       64 bit unsigned wrappable counter."
   ::= {pr1645v2Lan3MCVlanEntry 42074112}

pr1645v2Lan3MCVlanMCInDropNoMac OBJECT-TYPE
   SYNTAX      Counter64
   MAX-ACCESS  read-only
   STATUS      current
   DESCRIPTION
      "Path: ethernet3.performance.vlan.mibCounters.ifInDiscardsNoMacFit

       64 bit unsigned wrappable counter."
   ::= {pr1645v2Lan3MCVlanEntry 42270720}

pr1645v2Lan3MCVlanMCInDropNUCast OBJECT-TYPE
   SYNTAX      Counter64
   MAX-ACCESS  read-only
   STATUS      current
   DESCRIPTION
      "Path: ethernet3.performance.vlan.mibCounters.ifInDiscardsNUCast

       64 bit unsigned wrappable counter."
   ::= {pr1645v2Lan3MCVlanEntry 42467328}

pr1645v2Lan3MCVlanMCInDropFilter OBJECT-TYPE
   SYNTAX      Counter64
   MAX-ACCESS  read-only
   STATUS      current
   DESCRIPTION
      "Path: ethernet3.performance.vlan.mibCounters.ifInDiscardsFilter

       64 bit unsigned wrappable counter."
   ::= {pr1645v2Lan3MCVlanEntry 42532864}

pr1645v2Lan3MCVlanMCInBandwidth15sec OBJECT-TYPE
   SYNTAX      Integer32
   MAX-ACCESS  read-only
   STATUS      current
   DESCRIPTION
      "Path: ethernet3.performance.vlan.mibCounters.ifInBandwidth.15sec

       unit name = bps
       formula = 8 * ; 8 /"
   ::= {pr1645v2Lan3MCVlanEntry 45417728}

pr1645v2Lan3MCVlanMCInBandwidth30sec OBJECT-TYPE
   SYNTAX      Integer32
   MAX-ACCESS  read-only
   STATUS      current
   DESCRIPTION
      "Path: ethernet3.performance.vlan.mibCounters.ifInBandwidth.30sec

       unit name = bps
       formula = 8 * ; 8 /"
   ::= {pr1645v2Lan3MCVlanEntry 45419008}

pr1645v2Lan3MCVlanMCInBandwidth1min OBJECT-TYPE
   SYNTAX      Integer32
   MAX-ACCESS  read-only
   STATUS      current
   DESCRIPTION
      "Path: ethernet3.performance.vlan.mibCounters.ifInBandwidth.1min

       unit name = bps
       formula = 8 * ; 8 /"
   ::= {pr1645v2Lan3MCVlanEntry 45421568}

pr1645v2Lan3MCVlanMCInBandwidth2min OBJECT-TYPE
   SYNTAX      Integer32
   MAX-ACCESS  read-only
   STATUS      current
   DESCRIPTION
      "Path: ethernet3.performance.vlan.mibCounters.ifInBandwidth.2min

       unit name = bps
       formula = 8 * ; 8 /"
   ::= {pr1645v2Lan3MCVlanEntry 45426688}

pr1645v2Lan3MCVlanMCInBandwidth5min OBJECT-TYPE
   SYNTAX      Integer32
   MAX-ACCESS  read-only
   STATUS      current
   DESCRIPTION
      "Path: ethernet3.performance.vlan.mibCounters.ifInBandwidth.5min

       unit name = bps
       formula = 8 * ; 8 /"
   ::= {pr1645v2Lan3MCVlanEntry 45442048}

pr1645v2Lan3MCVlanMCOutOctets OBJECT-TYPE
   SYNTAX      Counter64
   MAX-ACCESS  read-only
   STATUS      current
   DESCRIPTION
      "Path: ethernet3.performance.vlan.mibCounters.ifOutOctets

       64 bit unsigned wrappable counter."
   ::= {pr1645v2Lan3MCVlanEntry 41091072}

pr1645v2Lan3MCVlanMCOutUcastPkts OBJECT-TYPE
   SYNTAX      Counter64
   MAX-ACCESS  read-only
   STATUS      current
   DESCRIPTION
      "Path: ethernet3.performance.vlan.mibCounters.ifOutUcastPkts

       64 bit unsigned wrappable counter."
   ::= {pr1645v2Lan3MCVlanEntry 41156608}

pr1645v2Lan3MCVlanMCOutNUcastPkts OBJECT-TYPE
   SYNTAX      Counter64
   MAX-ACCESS  read-only
   STATUS      current
   DESCRIPTION
      "Path: ethernet3.performance.vlan.mibCounters.ifOutNUcastPkts

       64 bit unsigned wrappable counter."
   ::= {pr1645v2Lan3MCVlanEntry 41222144}

pr1645v2Lan3MCVlanMCOutBcastPkts OBJECT-TYPE
   SYNTAX      Counter64
   MAX-ACCESS  read-only
   STATUS      current
   DESCRIPTION
      "Path: ethernet3.performance.vlan.mibCounters.ifOutBcastPkts

       64 bit unsigned wrappable counter."
   ::= {pr1645v2Lan3MCVlanEntry 47775744}

pr1645v2Lan3MCVlanMCOutMcastPkts OBJECT-TYPE
   SYNTAX      Counter64
   MAX-ACCESS  read-only
   STATUS      current
   DESCRIPTION
      "Path: ethernet3.performance.vlan.mibCounters.ifOutMcastPkts

       64 bit unsigned wrappable counter."
   ::= {pr1645v2Lan3MCVlanEntry 48431104}

pr1645v2Lan3MCVlanMCOutDiscards OBJECT-TYPE
   SYNTAX      Counter64
   MAX-ACCESS  read-only
   STATUS      current
   DESCRIPTION
      "Path: ethernet3.performance.vlan.mibCounters.ifOutDiscards

       64 bit unsigned wrappable counter."
   ::= {pr1645v2Lan3MCVlanEntry 41287680}

pr1645v2Lan3MCVlanMCOutErrors OBJECT-TYPE
   SYNTAX      Counter64
   MAX-ACCESS  read-only
   STATUS      current
   DESCRIPTION
      "Path: ethernet3.performance.vlan.mibCounters.ifOutErrors

       64 bit unsigned wrappable counter."
   ::= {pr1645v2Lan3MCVlanEntry 41353216}

pr1645v2Lan3MCVlanMCOutQLen OBJECT-TYPE
   SYNTAX      Counter32
   MAX-ACCESS  read-only
   STATUS      current
   DESCRIPTION
      "Path: ethernet3.performance.vlan.mibCounters.ifOutQLen

       32 bit unsigned wrappable counter."
   ::= {pr1645v2Lan3MCVlanEntry 41418752}

pr1645v2Lan3MCVlanMCOutDropEx OBJECT-TYPE
   SYNTAX      Counter64
   MAX-ACCESS  read-only
   STATUS      current
   DESCRIPTION
      "Path: ethernet3.performance.vlan.mibCounters.ifOutDropLevelExceeded

       64 bit unsigned wrappable counter."
   ::= {pr1645v2Lan3MCVlanEntry 41484288}

pr1645v2Lan3MCVlanMCOutDropNoArp OBJECT-TYPE
   SYNTAX      Counter64
   MAX-ACCESS  read-only
   STATUS      current
   DESCRIPTION
      "Path: ethernet3.performance.vlan.mibCounters.ifOutDiscardsNoArp

       64 bit unsigned wrappable counter."
   ::= {pr1645v2Lan3MCVlanEntry 42336256}

pr1645v2Lan3MCVlanMCOutDropFilter OBJECT-TYPE
   SYNTAX      Counter64
   MAX-ACCESS  read-only
   STATUS      current
   DESCRIPTION
      "Path: ethernet3.performance.vlan.mibCounters.ifOutDiscardsFilter

       64 bit unsigned wrappable counter."
   ::= {pr1645v2Lan3MCVlanEntry 42598400}

pr1645v2Lan3MCVlanMCOutBandwidth15sec OBJECT-TYPE
   SYNTAX      Integer32
   MAX-ACCESS  read-only
   STATUS      current
   DESCRIPTION
      "Path: ethernet3.performance.vlan.mibCounters.ifOutBandwidth.15sec

       unit name = bps
       formula = 8 * ; 8 /"
   ::= {pr1645v2Lan3MCVlanEntry 45483264}

pr1645v2Lan3MCVlanMCOutBandwidth30sec OBJECT-TYPE
   SYNTAX      Integer32
   MAX-ACCESS  read-only
   STATUS      current
   DESCRIPTION
      "Path: ethernet3.performance.vlan.mibCounters.ifOutBandwidth.30sec

       unit name = bps
       formula = 8 * ; 8 /"
   ::= {pr1645v2Lan3MCVlanEntry 45484544}

pr1645v2Lan3MCVlanMCOutBandwidth1min OBJECT-TYPE
   SYNTAX      Integer32
   MAX-ACCESS  read-only
   STATUS      current
   DESCRIPTION
      "Path: ethernet3.performance.vlan.mibCounters.ifOutBandwidth.1min

       unit name = bps
       formula = 8 * ; 8 /"
   ::= {pr1645v2Lan3MCVlanEntry 45487104}

pr1645v2Lan3MCVlanMCOutBandwidth2min OBJECT-TYPE
   SYNTAX      Integer32
   MAX-ACCESS  read-only
   STATUS      current
   DESCRIPTION
      "Path: ethernet3.performance.vlan.mibCounters.ifOutBandwidth.2min

       unit name = bps
       formula = 8 * ; 8 /"
   ::= {pr1645v2Lan3MCVlanEntry 45492224}

pr1645v2Lan3MCVlanMCOutBandwidth5min OBJECT-TYPE
   SYNTAX      Integer32
   MAX-ACCESS  read-only
   STATUS      current
   DESCRIPTION
      "Path: ethernet3.performance.vlan.mibCounters.ifOutBandwidth.5min

       unit name = bps
       formula = 8 * ; 8 /"
   ::= {pr1645v2Lan3MCVlanEntry 45507584}

pr1645v2Lan3MCVlanVlanVid OBJECT-TYPE
   SYNTAX      Integer32
   MAX-ACCESS  read-only
   STATUS      current
   DESCRIPTION
      "Path: ethernet3.performance.vlan.vlan.vid"
   ::= {pr1645v2Lan3MCVlanEntry 234946560}

pr1645v2Lan3MCVlanPppLinkMonitoringRequestsSent OBJECT-TYPE
   SYNTAX      Gauge32
   MAX-ACCESS  read-only
   STATUS      current
   DESCRIPTION
      "Path: ethernet3.performance.vlan.ppp.linkMonitoring.requestsSent

       32 bit unsigned gauge value."
   ::= {pr1645v2Lan3MCVlanEntry 50397440}

pr1645v2Lan3MCVlanPppLinkMonitoringRepliesRcvd OBJECT-TYPE
   SYNTAX      Gauge32
   MAX-ACCESS  read-only
   STATUS      current
   DESCRIPTION
      "Path: ethernet3.performance.vlan.ppp.linkMonitoring.repliesRcvd

       32 bit unsigned gauge value."
   ::= {pr1645v2Lan3MCVlanEntry 50397696}

pr1645v2Lan3MCVlanPppLinkMonitoringRequestsRcvd OBJECT-TYPE
   SYNTAX      Gauge32
   MAX-ACCESS  read-only
   STATUS      current
   DESCRIPTION
      "Path: ethernet3.performance.vlan.ppp.linkMonitoring.requestsRcvd

       32 bit unsigned gauge value."
   ::= {pr1645v2Lan3MCVlanEntry 50397952}

pr1645v2Lan3MCVlanPppLinkMonitoringRepliesSent OBJECT-TYPE
   SYNTAX      Gauge32
   MAX-ACCESS  read-only
   STATUS      current
   DESCRIPTION
      "Path: ethernet3.performance.vlan.ppp.linkMonitoring.repliesSent

       32 bit unsigned gauge value."
   ::= {pr1645v2Lan3MCVlanEntry 50398208}

pr1645v2Lan3MCVlanMCH2P OBJECT-TYPE
   SYNTAX      SEQUENCE OF Pr1645v2Lan3MCVlanMCH2PEntry
   MAX-ACCESS  not-accessible
   STATUS      current
   DESCRIPTION
      ""
   ::= {pr1645v2Lan3MCVlan 41549824}

pr1645v2Lan3MCVlanMCH2PEntry OBJECT-TYPE
   SYNTAX      Pr1645v2Lan3MCVlanMCH2PEntry
   MAX-ACCESS  not-accessible
   STATUS      current
   DESCRIPTION
      ""
   INDEX      { pr1645v2Lan3MCVlanTableIx,
                pr1645v2Lan3MCVlanMCH2PTableIx }
   ::= {pr1645v2Lan3MCVlanMCH2P 1}

Pr1645v2Lan3MCVlanMCH2PEntry ::=
   SEQUENCE
      {
      pr1645v2Lan3MCVlanMCH2PTableIx
         TableIndex,
      pr1645v2Lan3MCVlanMCH2PSysUpTime
         TimeTicks,
      pr1645v2Lan3MCVlanMCH2PIfUpTime
         TimeTicks,
      pr1645v2Lan3MCVlanMCH2PIfStatChanges
         Counter32,
      pr1645v2Lan3MCVlanMCH2PIfInOctets
         Counter64,
      pr1645v2Lan3MCVlanMCH2PIfInUCPkts
         Counter64,
      pr1645v2Lan3MCVlanMCH2PIfInNUCPkts
         Counter64,
      pr1645v2Lan3MCVlanMCH2PIfInBCPkts
         Counter64,
      pr1645v2Lan3MCVlanMCH2PIfInMCPkts
         Counter64,
      pr1645v2Lan3MCVlanMCH2PIfInDiscards
         Counter64,
      pr1645v2Lan3MCVlanMCH2PIfInErrors
         Counter64,
      pr1645v2Lan3MCVlanMCH2PIfInUnkwn
         Counter64,
      pr1645v2Lan3MCVlanMCH2PInDropEx
         Counter64,
      pr1645v2Lan3MCVlanMCH2PInDropNoMac
         Counter64,
      pr1645v2Lan3MCVlanMCH2PInDropNUCast
         Counter64,
      pr1645v2Lan3MCVlanMCH2PInDropFilter
         Counter64,
      pr1645v2Lan3MCVlanMCH2PIfInBandwidth
         Integer32,
      pr1645v2Lan3MCVlanMCH2PIfOutOctets
         Counter64,
      pr1645v2Lan3MCVlanMCH2PIfOutUCPkts
         Counter64,
      pr1645v2Lan3MCVlanMCH2PIfOutNUCPkts
         Counter64,
      pr1645v2Lan3MCVlanMCH2PIfOutBCPkts
         Counter64,
      pr1645v2Lan3MCVlanMCH2PIfOutMCPkts
         Counter64,
      pr1645v2Lan3MCVlanMCH2PIfOutDiscards
         Counter64,
      pr1645v2Lan3MCVlanMCH2PIfOutErrors
         Counter64,
      pr1645v2Lan3MCVlanMCH2POutDropEx
         Counter64,
      pr1645v2Lan3MCVlanMCH2POutDropNoArp
         Counter64,
      pr1645v2Lan3MCVlanMCH2POutDropFilter
         Counter64,
      pr1645v2Lan3MCVlanMCH2PIfOutBandwidth
         Integer32,
      pr1645v2Lan3MCVlanMCH2PIfErrSec
         Counter32
      }

pr1645v2Lan3MCVlanMCH2PTableIx OBJECT-TYPE
   SYNTAX      TableIndex
   MAX-ACCESS  not-accessible
   STATUS      current
   DESCRIPTION
      ""
   ::= {pr1645v2Lan3MCVlanMCH2PEntry 11}

pr1645v2Lan3MCVlanMCH2PSysUpTime OBJECT-TYPE
   SYNTAX      TimeTicks
   MAX-ACCESS  read-only
   STATUS      current
   DESCRIPTION
      "Path: ethernet3.performance.vlan.mibCounters.h2Performance.sysUpTime

       Time in centi-second."
   ::= {pr1645v2Lan3MCVlanMCH2PEntry 16777216}

pr1645v2Lan3MCVlanMCH2PIfUpTime OBJECT-TYPE
   SYNTAX      TimeTicks
   MAX-ACCESS  read-only
   STATUS      current
   DESCRIPTION
      "Path: ethernet3.performance.vlan.mibCounters.h2Performance.ifUpTime

       Time in centi-second."
   ::= {pr1645v2Lan3MCVlanMCH2PEntry 33554432}

pr1645v2Lan3MCVlanMCH2PIfStatChanges OBJECT-TYPE
   SYNTAX      Counter32
   MAX-ACCESS  read-only
   STATUS      current
   DESCRIPTION
      "Path: ethernet3.performance.vlan.mibCounters.h2Performance.ifStatusChanges

       32 bit unsigned wrappable counter."
   ::= {pr1645v2Lan3MCVlanMCH2PEntry 50331648}

pr1645v2Lan3MCVlanMCH2PIfInOctets OBJECT-TYPE
   SYNTAX      Counter64
   MAX-ACCESS  read-only
   STATUS      current
   DESCRIPTION
      "Path: ethernet3.performance.vlan.mibCounters.h2Performance.ifInOctets

       64 bit unsigned wrappable counter."
   ::= {pr1645v2Lan3MCVlanMCH2PEntry 67108864}

pr1645v2Lan3MCVlanMCH2PIfInUCPkts OBJECT-TYPE
   SYNTAX      Counter64
   MAX-ACCESS  read-only
   STATUS      current
   DESCRIPTION
      "Path: ethernet3.performance.vlan.mibCounters.h2Performance.ifInUcastPkts

       64 bit unsigned wrappable counter."
   ::= {pr1645v2Lan3MCVlanMCH2PEntry 83886080}

pr1645v2Lan3MCVlanMCH2PIfInNUCPkts OBJECT-TYPE
   SYNTAX      Counter64
   MAX-ACCESS  read-only
   STATUS      current
   DESCRIPTION
      "Path: ethernet3.performance.vlan.mibCounters.h2Performance.ifInNUcastPkts

       64 bit unsigned wrappable counter."
   ::= {pr1645v2Lan3MCVlanMCH2PEntry 100663296}

pr1645v2Lan3MCVlanMCH2PIfInBCPkts OBJECT-TYPE
   SYNTAX      Counter64
   MAX-ACCESS  read-only
   STATUS      current
   DESCRIPTION
      "Path: ethernet3.performance.vlan.mibCounters.h2Performance.ifInBcastPkts

       64 bit unsigned wrappable counter."
   ::= {pr1645v2Lan3MCVlanMCH2PEntry 419430400}

pr1645v2Lan3MCVlanMCH2PIfInMCPkts OBJECT-TYPE
   SYNTAX      Counter64
   MAX-ACCESS  read-only
   STATUS      current
   DESCRIPTION
      "Path: ethernet3.performance.vlan.mibCounters.h2Performance.ifInMcastPkts

       64 bit unsigned wrappable counter."
   ::= {pr1645v2Lan3MCVlanMCH2PEntry 436207616}

pr1645v2Lan3MCVlanMCH2PIfInDiscards OBJECT-TYPE
   SYNTAX      Counter64
   MAX-ACCESS  read-only
   STATUS      current
   DESCRIPTION
      "Path: ethernet3.performance.vlan.mibCounters.h2Performance.ifInDiscards

       64 bit unsigned wrappable counter."
   ::= {pr1645v2Lan3MCVlanMCH2PEntry 117440512}

pr1645v2Lan3MCVlanMCH2PIfInErrors OBJECT-TYPE
   SYNTAX      Counter64
   MAX-ACCESS  read-only
   STATUS      current
   DESCRIPTION
      "Path: ethernet3.performance.vlan.mibCounters.h2Performance.ifInErrors

       64 bit unsigned wrappable counter."
   ::= {pr1645v2Lan3MCVlanMCH2PEntry 134217728}

pr1645v2Lan3MCVlanMCH2PIfInUnkwn OBJECT-TYPE
   SYNTAX      Counter64
   MAX-ACCESS  read-only
   STATUS      current
   DESCRIPTION
      "Path: ethernet3.performance.vlan.mibCounters.h2Performance.ifInUnknownProtos

       64 bit unsigned wrappable counter."
   ::= {pr1645v2Lan3MCVlanMCH2PEntry 150994944}

pr1645v2Lan3MCVlanMCH2PInDropEx OBJECT-TYPE
   SYNTAX      Counter64
   MAX-ACCESS  read-only
   STATUS      current
   DESCRIPTION
      "Path: ethernet3.performance.vlan.mibCounters.h2Performance.ifInDropLevelExceeded

       64 bit unsigned wrappable counter."
   ::= {pr1645v2Lan3MCVlanMCH2PEntry 335544320}

pr1645v2Lan3MCVlanMCH2PInDropNoMac OBJECT-TYPE
   SYNTAX      Counter64
   MAX-ACCESS  read-only
   STATUS      current
   DESCRIPTION
      "Path: ethernet3.performance.vlan.mibCounters.h2Performance.fInDiscardsNoMacFit

       64 bit unsigned wrappable counter."
   ::= {pr1645v2Lan3MCVlanMCH2PEntry 301989888}

pr1645v2Lan3MCVlanMCH2PInDropNUCast OBJECT-TYPE
   SYNTAX      Counter64
   MAX-ACCESS  read-only
   STATUS      current
   DESCRIPTION
      "Path: ethernet3.performance.vlan.mibCounters.h2Performance.fInDiscardsNUCast

       64 bit unsigned wrappable counter."
   ::= {pr1645v2Lan3MCVlanMCH2PEntry 318767104}

pr1645v2Lan3MCVlanMCH2PInDropFilter OBJECT-TYPE
   SYNTAX      Counter64
   MAX-ACCESS  read-only
   STATUS      current
   DESCRIPTION
      "Path: ethernet3.performance.vlan.mibCounters.h2Performance.fInDiscardsFilter

       64 bit unsigned wrappable counter."
   ::= {pr1645v2Lan3MCVlanMCH2PEntry 385875968}

pr1645v2Lan3MCVlanMCH2PIfInBandwidth OBJECT-TYPE
   SYNTAX      Integer32
   MAX-ACCESS  read-only
   STATUS      current
   DESCRIPTION
      "Path: ethernet3.performance.vlan.mibCounters.h2Performance.ifInBandwidth

       unit name = bps
       formula = 8 * ; 8 /"
   ::= {pr1645v2Lan3MCVlanMCH2PEntry 268435456}

pr1645v2Lan3MCVlanMCH2PIfOutOctets OBJECT-TYPE
   SYNTAX      Counter64
   MAX-ACCESS  read-only
   STATUS      current
   DESCRIPTION
      "Path: ethernet3.performance.vlan.mibCounters.h2Performance.ifOutOctets

       64 bit unsigned wrappable counter."
   ::= {pr1645v2Lan3MCVlanMCH2PEntry 167772160}

pr1645v2Lan3MCVlanMCH2PIfOutUCPkts OBJECT-TYPE
   SYNTAX      Counter64
   MAX-ACCESS  read-only
   STATUS      current
   DESCRIPTION
      "Path: ethernet3.performance.vlan.mibCounters.h2Performance.ifOutUcastPkts

       64 bit unsigned wrappable counter."
   ::= {pr1645v2Lan3MCVlanMCH2PEntry 184549376}

pr1645v2Lan3MCVlanMCH2PIfOutNUCPkts OBJECT-TYPE
   SYNTAX      Counter64
   MAX-ACCESS  read-only
   STATUS      current
   DESCRIPTION
      "Path: ethernet3.performance.vlan.mibCounters.h2Performance.ifOutNUcastPkts

       64 bit unsigned wrappable counter."
   ::= {pr1645v2Lan3MCVlanMCH2PEntry 201326592}

pr1645v2Lan3MCVlanMCH2PIfOutBCPkts OBJECT-TYPE
   SYNTAX      Counter64
   MAX-ACCESS  read-only
   STATUS      current
   DESCRIPTION
      "Path: ethernet3.performance.vlan.mibCounters.h2Performance.ifOutBcastPkts

       64 bit unsigned wrappable counter."
   ::= {pr1645v2Lan3MCVlanMCH2PEntry 452984832}

pr1645v2Lan3MCVlanMCH2PIfOutMCPkts OBJECT-TYPE
   SYNTAX      Counter64
   MAX-ACCESS  read-only
   STATUS      current
   DESCRIPTION
      "Path: ethernet3.performance.vlan.mibCounters.h2Performance.ifOutMcastPkts

       64 bit unsigned wrappable counter."
   ::= {pr1645v2Lan3MCVlanMCH2PEntry 469762048}

pr1645v2Lan3MCVlanMCH2PIfOutDiscards OBJECT-TYPE
   SYNTAX      Counter64
   MAX-ACCESS  read-only
   STATUS      current
   DESCRIPTION
      "Path: ethernet3.performance.vlan.mibCounters.h2Performance.ifOutDiscards

       64 bit unsigned wrappable counter."
   ::= {pr1645v2Lan3MCVlanMCH2PEntry 218103808}

pr1645v2Lan3MCVlanMCH2PIfOutErrors OBJECT-TYPE
   SYNTAX      Counter64
   MAX-ACCESS  read-only
   STATUS      current
   DESCRIPTION
      "Path: ethernet3.performance.vlan.mibCounters.h2Performance.ifOutErrors

       64 bit unsigned wrappable counter."
   ::= {pr1645v2Lan3MCVlanMCH2PEntry 234881024}

pr1645v2Lan3MCVlanMCH2POutDropEx OBJECT-TYPE
   SYNTAX      Counter64
   MAX-ACCESS  read-only
   STATUS      current
   DESCRIPTION
      "Path: ethernet3.performance.vlan.mibCounters.h2Performance.ifOutDropLevelExceeded

       64 bit unsigned wrappable counter."
   ::= {pr1645v2Lan3MCVlanMCH2PEntry 352321536}

pr1645v2Lan3MCVlanMCH2POutDropNoArp OBJECT-TYPE
   SYNTAX      Counter64
   MAX-ACCESS  read-only
   STATUS      current
   DESCRIPTION
      "Path: ethernet3.performance.vlan.mibCounters.h2Performance.ifOutDiscardsNoArp

       64 bit unsigned wrappable counter."
   ::= {pr1645v2Lan3MCVlanMCH2PEntry 369098752}

pr1645v2Lan3MCVlanMCH2POutDropFilter OBJECT-TYPE
   SYNTAX      Counter64
   MAX-ACCESS  read-only
   STATUS      current
   DESCRIPTION
      "Path: ethernet3.performance.vlan.mibCounters.h2Performance.ifOutDiscardsFilter

       64 bit unsigned wrappable counter."
   ::= {pr1645v2Lan3MCVlanMCH2PEntry 402653184}

pr1645v2Lan3MCVlanMCH2PIfOutBandwidth OBJECT-TYPE
   SYNTAX      Integer32
   MAX-ACCESS  read-only
   STATUS      current
   DESCRIPTION
      "Path: ethernet3.performance.vlan.mibCounters.h2Performance.ifOutBandwidth

       unit name = bps
       formula = 8 * ; 8 /"
   ::= {pr1645v2Lan3MCVlanMCH2PEntry 285212672}

pr1645v2Lan3MCVlanMCH2PIfErrSec OBJECT-TYPE
   SYNTAX      Counter32
   MAX-ACCESS  read-only
   STATUS      current
   DESCRIPTION
      "Path: ethernet3.performance.vlan.mibCounters.h2Performance.ifErrSec

       32 bit unsigned wrappable counter."
   ::= {pr1645v2Lan3MCVlanMCH2PEntry 251658240}

pr1645v2Lan3MCVlanMCH24P OBJECT-TYPE
   SYNTAX      SEQUENCE OF Pr1645v2Lan3MCVlanMCH24PEntry
   MAX-ACCESS  not-accessible
   STATUS      current
   DESCRIPTION
      ""
   ::= {pr1645v2Lan3MCVlan 41615360}

pr1645v2Lan3MCVlanMCH24PEntry OBJECT-TYPE
   SYNTAX      Pr1645v2Lan3MCVlanMCH24PEntry
   MAX-ACCESS  not-accessible
   STATUS      current
   DESCRIPTION
      ""
   INDEX      { pr1645v2Lan3MCVlanTableIx,
                pr1645v2Lan3MCVlanMCH24PTableIx }
   ::= {pr1645v2Lan3MCVlanMCH24P 1}

Pr1645v2Lan3MCVlanMCH24PEntry ::=
   SEQUENCE
      {
      pr1645v2Lan3MCVlanMCH24PTableIx
         TableIndex,
      pr1645v2Lan3MCVlanMCH24PSysUpTime
         TimeTicks,
      pr1645v2Lan3MCVlanMCH24PIfUpTime
         TimeTicks,
      pr1645v2Lan3MCVlanMCH24PIfStatChanges
         Counter32,
      pr1645v2Lan3MCVlanMCH24PIfInOctets
         Counter64,
      pr1645v2Lan3MCVlanMCH24PIfInUCPkts
         Counter64,
      pr1645v2Lan3MCVlanMCH24PIfInNUCPkts
         Counter64,
      pr1645v2Lan3MCVlanMCH24PIfInBCPkts
         Counter64,
      pr1645v2Lan3MCVlanMCH24PIfInMCPkts
         Counter64,
      pr1645v2Lan3MCVlanMCH24PIfInDiscards
         Counter64,
      pr1645v2Lan3MCVlanMCH24PIfInErrors
         Counter64,
      pr1645v2Lan3MCVlanMCH24PIfInUnkwn
         Counter64,
      pr1645v2Lan3MCVlanMCH24PInDropEx
         Counter64,
      pr1645v2Lan3MCVlanMCH24PInDropNoMac
         Counter64,
      pr1645v2Lan3MCVlanMCH24PInDropNUCast
         Counter64,
      pr1645v2Lan3MCVlanMCH24PInDropFilter
         Counter64,
      pr1645v2Lan3MCVlanMCH24PIfInBandwidth
         Integer32,
      pr1645v2Lan3MCVlanMCH24PIfOutOctets
         Counter64,
      pr1645v2Lan3MCVlanMCH24PIfOutUCPkts
         Counter64,
      pr1645v2Lan3MCVlanMCH24PIfOutNUCPkts
         Counter64,
      pr1645v2Lan3MCVlanMCH24PIfOutBCPkts
         Counter64,
      pr1645v2Lan3MCVlanMCH24PIfOutMCPkts
         Counter64,
      pr1645v2Lan3MCVlanMCH24PIfOutDiscards
         Counter64,
      pr1645v2Lan3MCVlanMCH24PIfOutErrors
         Counter64,
      pr1645v2Lan3MCVlanMCH24POutDropEx
         Counter64,
      pr1645v2Lan3MCVlanMCH24POutDropNoArp
         Counter64,
      pr1645v2Lan3MCVlanMCH24POutDropFilter
         Counter64,
      pr1645v2Lan3MCVlanMCH24PIfOutBandwidth
         Integer32,
      pr1645v2Lan3MCVlanMCH24PIfErrSec
         Counter32
      }

pr1645v2Lan3MCVlanMCH24PTableIx OBJECT-TYPE
   SYNTAX      TableIndex
   MAX-ACCESS  not-accessible
   STATUS      current
   DESCRIPTION
      ""
   ::= {pr1645v2Lan3MCVlanMCH24PEntry 11}

pr1645v2Lan3MCVlanMCH24PSysUpTime OBJECT-TYPE
   SYNTAX      TimeTicks
   MAX-ACCESS  read-only
   STATUS      current
   DESCRIPTION
      "Path: ethernet3.performance.vlan.mibCounters.h24Performance.sysUpTime

       Time in centi-second."
   ::= {pr1645v2Lan3MCVlanMCH24PEntry 16777216}

pr1645v2Lan3MCVlanMCH24PIfUpTime OBJECT-TYPE
   SYNTAX      TimeTicks
   MAX-ACCESS  read-only
   STATUS      current
   DESCRIPTION
      "Path: ethernet3.performance.vlan.mibCounters.h24Performance.ifUpTime

       Time in centi-second."
   ::= {pr1645v2Lan3MCVlanMCH24PEntry 33554432}

pr1645v2Lan3MCVlanMCH24PIfStatChanges OBJECT-TYPE
   SYNTAX      Counter32
   MAX-ACCESS  read-only
   STATUS      current
   DESCRIPTION
      "Path: ethernet3.performance.vlan.mibCounters.h24Performance.ifStatusChanges

       32 bit unsigned wrappable counter."
   ::= {pr1645v2Lan3MCVlanMCH24PEntry 50331648}

pr1645v2Lan3MCVlanMCH24PIfInOctets OBJECT-TYPE
   SYNTAX      Counter64
   MAX-ACCESS  read-only
   STATUS      current
   DESCRIPTION
      "Path: ethernet3.performance.vlan.mibCounters.h24Performance.ifInOctets

       64 bit unsigned wrappable counter."
   ::= {pr1645v2Lan3MCVlanMCH24PEntry 67108864}

pr1645v2Lan3MCVlanMCH24PIfInUCPkts OBJECT-TYPE
   SYNTAX      Counter64
   MAX-ACCESS  read-only
   STATUS      current
   DESCRIPTION
      "Path: ethernet3.performance.vlan.mibCounters.h24Performance.ifInUcastPkts

       64 bit unsigned wrappable counter."
   ::= {pr1645v2Lan3MCVlanMCH24PEntry 83886080}

pr1645v2Lan3MCVlanMCH24PIfInNUCPkts OBJECT-TYPE
   SYNTAX      Counter64
   MAX-ACCESS  read-only
   STATUS      current
   DESCRIPTION
      "Path: ethernet3.performance.vlan.mibCounters.h24Performance.ifInNUcastPkts

       64 bit unsigned wrappable counter."
   ::= {pr1645v2Lan3MCVlanMCH24PEntry 100663296}

pr1645v2Lan3MCVlanMCH24PIfInBCPkts OBJECT-TYPE
   SYNTAX      Counter64
   MAX-ACCESS  read-only
   STATUS      current
   DESCRIPTION
      "Path: ethernet3.performance.vlan.mibCounters.h24Performance.ifInBcastPkts

       64 bit unsigned wrappable counter."
   ::= {pr1645v2Lan3MCVlanMCH24PEntry 419430400}

pr1645v2Lan3MCVlanMCH24PIfInMCPkts OBJECT-TYPE
   SYNTAX      Counter64
   MAX-ACCESS  read-only
   STATUS      current
   DESCRIPTION
      "Path: ethernet3.performance.vlan.mibCounters.h24Performance.ifInMcastPkts

       64 bit unsigned wrappable counter."
   ::= {pr1645v2Lan3MCVlanMCH24PEntry 436207616}

pr1645v2Lan3MCVlanMCH24PIfInDiscards OBJECT-TYPE
   SYNTAX      Counter64
   MAX-ACCESS  read-only
   STATUS      current
   DESCRIPTION
      "Path: ethernet3.performance.vlan.mibCounters.h24Performance.ifInDiscards

       64 bit unsigned wrappable counter."
   ::= {pr1645v2Lan3MCVlanMCH24PEntry 117440512}

pr1645v2Lan3MCVlanMCH24PIfInErrors OBJECT-TYPE
   SYNTAX      Counter64
   MAX-ACCESS  read-only
   STATUS      current
   DESCRIPTION
      "Path: ethernet3.performance.vlan.mibCounters.h24Performance.ifInErrors

       64 bit unsigned wrappable counter."
   ::= {pr1645v2Lan3MCVlanMCH24PEntry 134217728}

pr1645v2Lan3MCVlanMCH24PIfInUnkwn OBJECT-TYPE
   SYNTAX      Counter64
   MAX-ACCESS  read-only
   STATUS      current
   DESCRIPTION
      "Path: ethernet3.performance.vlan.mibCounters.h24Performance.ifInUnknownProtos

       64 bit unsigned wrappable counter."
   ::= {pr1645v2Lan3MCVlanMCH24PEntry 150994944}

pr1645v2Lan3MCVlanMCH24PInDropEx OBJECT-TYPE
   SYNTAX      Counter64
   MAX-ACCESS  read-only
   STATUS      current
   DESCRIPTION
      "Path: ethernet3.performance.vlan.mibCounters.h24Performance.ifInDropLevelExceeded

       64 bit unsigned wrappable counter."
   ::= {pr1645v2Lan3MCVlanMCH24PEntry 335544320}

pr1645v2Lan3MCVlanMCH24PInDropNoMac OBJECT-TYPE
   SYNTAX      Counter64
   MAX-ACCESS  read-only
   STATUS      current
   DESCRIPTION
      "Path: ethernet3.performance.vlan.mibCounters.h24Performance.fInDiscardsNoMacFit

       64 bit unsigned wrappable counter."
   ::= {pr1645v2Lan3MCVlanMCH24PEntry 301989888}

pr1645v2Lan3MCVlanMCH24PInDropNUCast OBJECT-TYPE
   SYNTAX      Counter64
   MAX-ACCESS  read-only
   STATUS      current
   DESCRIPTION
      "Path: ethernet3.performance.vlan.mibCounters.h24Performance.fInDiscardsNUCast

       64 bit unsigned wrappable counter."
   ::= {pr1645v2Lan3MCVlanMCH24PEntry 318767104}

pr1645v2Lan3MCVlanMCH24PInDropFilter OBJECT-TYPE
   SYNTAX      Counter64
   MAX-ACCESS  read-only
   STATUS      current
   DESCRIPTION
      "Path: ethernet3.performance.vlan.mibCounters.h24Performance.fInDiscardsFilter

       64 bit unsigned wrappable counter."
   ::= {pr1645v2Lan3MCVlanMCH24PEntry 385875968}

pr1645v2Lan3MCVlanMCH24PIfInBandwidth OBJECT-TYPE
   SYNTAX      Integer32
   MAX-ACCESS  read-only
   STATUS      current
   DESCRIPTION
      "Path: ethernet3.performance.vlan.mibCounters.h24Performance.ifInBandwidth

       unit name = bps
       formula = 8 * ; 8 /"
   ::= {pr1645v2Lan3MCVlanMCH24PEntry 268435456}

pr1645v2Lan3MCVlanMCH24PIfOutOctets OBJECT-TYPE
   SYNTAX      Counter64
   MAX-ACCESS  read-only
   STATUS      current
   DESCRIPTION
      "Path: ethernet3.performance.vlan.mibCounters.h24Performance.ifOutOctets

       64 bit unsigned wrappable counter."
   ::= {pr1645v2Lan3MCVlanMCH24PEntry 167772160}

pr1645v2Lan3MCVlanMCH24PIfOutUCPkts OBJECT-TYPE
   SYNTAX      Counter64
   MAX-ACCESS  read-only
   STATUS      current
   DESCRIPTION
      "Path: ethernet3.performance.vlan.mibCounters.h24Performance.ifOutUcastPkts

       64 bit unsigned wrappable counter."
   ::= {pr1645v2Lan3MCVlanMCH24PEntry 184549376}

pr1645v2Lan3MCVlanMCH24PIfOutNUCPkts OBJECT-TYPE
   SYNTAX      Counter64
   MAX-ACCESS  read-only
   STATUS      current
   DESCRIPTION
      "Path: ethernet3.performance.vlan.mibCounters.h24Performance.ifOutNUcastPkts

       64 bit unsigned wrappable counter."
   ::= {pr1645v2Lan3MCVlanMCH24PEntry 201326592}

pr1645v2Lan3MCVlanMCH24PIfOutBCPkts OBJECT-TYPE
   SYNTAX      Counter64
   MAX-ACCESS  read-only
   STATUS      current
   DESCRIPTION
      "Path: ethernet3.performance.vlan.mibCounters.h24Performance.ifOutBcastPkts

       64 bit unsigned wrappable counter."
   ::= {pr1645v2Lan3MCVlanMCH24PEntry 452984832}

pr1645v2Lan3MCVlanMCH24PIfOutMCPkts OBJECT-TYPE
   SYNTAX      Counter64
   MAX-ACCESS  read-only
   STATUS      current
   DESCRIPTION
      "Path: ethernet3.performance.vlan.mibCounters.h24Performance.ifOutMcastPkts

       64 bit unsigned wrappable counter."
   ::= {pr1645v2Lan3MCVlanMCH24PEntry 469762048}

pr1645v2Lan3MCVlanMCH24PIfOutDiscards OBJECT-TYPE
   SYNTAX      Counter64
   MAX-ACCESS  read-only
   STATUS      current
   DESCRIPTION
      "Path: ethernet3.performance.vlan.mibCounters.h24Performance.ifOutDiscards

       64 bit unsigned wrappable counter."
   ::= {pr1645v2Lan3MCVlanMCH24PEntry 218103808}

pr1645v2Lan3MCVlanMCH24PIfOutErrors OBJECT-TYPE
   SYNTAX      Counter64
   MAX-ACCESS  read-only
   STATUS      current
   DESCRIPTION
      "Path: ethernet3.performance.vlan.mibCounters.h24Performance.ifOutErrors

       64 bit unsigned wrappable counter."
   ::= {pr1645v2Lan3MCVlanMCH24PEntry 234881024}

pr1645v2Lan3MCVlanMCH24POutDropEx OBJECT-TYPE
   SYNTAX      Counter64
   MAX-ACCESS  read-only
   STATUS      current
   DESCRIPTION
      "Path: ethernet3.performance.vlan.mibCounters.h24Performance.ifOutDropLevelExceeded

       64 bit unsigned wrappable counter."
   ::= {pr1645v2Lan3MCVlanMCH24PEntry 352321536}

pr1645v2Lan3MCVlanMCH24POutDropNoArp OBJECT-TYPE
   SYNTAX      Counter64
   MAX-ACCESS  read-only
   STATUS      current
   DESCRIPTION
      "Path: ethernet3.performance.vlan.mibCounters.h24Performance.ifOutDiscardsNoArp

       64 bit unsigned wrappable counter."
   ::= {pr1645v2Lan3MCVlanMCH24PEntry 369098752}

pr1645v2Lan3MCVlanMCH24POutDropFilter OBJECT-TYPE
   SYNTAX      Counter64
   MAX-ACCESS  read-only
   STATUS      current
   DESCRIPTION
      "Path: ethernet3.performance.vlan.mibCounters.h24Performance.ifOutDiscardsFilter

       64 bit unsigned wrappable counter."
   ::= {pr1645v2Lan3MCVlanMCH24PEntry 402653184}

pr1645v2Lan3MCVlanMCH24PIfOutBandwidth OBJECT-TYPE
   SYNTAX      Integer32
   MAX-ACCESS  read-only
   STATUS      current
   DESCRIPTION
      "Path: ethernet3.performance.vlan.mibCounters.h24Performance.ifOutBandwidth

       unit name = bps
       formula = 8 * ; 8 /"
   ::= {pr1645v2Lan3MCVlanMCH24PEntry 285212672}

pr1645v2Lan3MCVlanMCH24PIfErrSec OBJECT-TYPE
   SYNTAX      Counter32
   MAX-ACCESS  read-only
   STATUS      current
   DESCRIPTION
      "Path: ethernet3.performance.vlan.mibCounters.h24Performance.ifErrSec

       32 bit unsigned wrappable counter."
   ::= {pr1645v2Lan3MCVlanMCH24PEntry 251658240}

pr1645v2Lan3MCVlanMCD7P OBJECT-TYPE
   SYNTAX      SEQUENCE OF Pr1645v2Lan3MCVlanMCD7PEntry
   MAX-ACCESS  not-accessible
   STATUS      current
   DESCRIPTION
      ""
   ::= {pr1645v2Lan3MCVlan 41680896}

pr1645v2Lan3MCVlanMCD7PEntry OBJECT-TYPE
   SYNTAX      Pr1645v2Lan3MCVlanMCD7PEntry
   MAX-ACCESS  not-accessible
   STATUS      current
   DESCRIPTION
      ""
   INDEX      { pr1645v2Lan3MCVlanTableIx,
                pr1645v2Lan3MCVlanMCD7PTableIx }
   ::= {pr1645v2Lan3MCVlanMCD7P 1}

Pr1645v2Lan3MCVlanMCD7PEntry ::=
   SEQUENCE
      {
      pr1645v2Lan3MCVlanMCD7PTableIx
         TableIndex,
      pr1645v2Lan3MCVlanMCD7PSysUpTime
         TimeTicks,
      pr1645v2Lan3MCVlanMCD7PIfUpTime
         TimeTicks,
      pr1645v2Lan3MCVlanMCD7PIfStatChanges
         Counter32,
      pr1645v2Lan3MCVlanMCD7PIfInOctets
         Counter64,
      pr1645v2Lan3MCVlanMCD7PIfInUCPkts
         Counter64,
      pr1645v2Lan3MCVlanMCD7PIfInNUCPkts
         Counter64,
      pr1645v2Lan3MCVlanMCD7PIfInBCPkts
         Counter64,
      pr1645v2Lan3MCVlanMCD7PIfInMCPkts
         Counter64,
      pr1645v2Lan3MCVlanMCD7PIfInDiscards
         Counter64,
      pr1645v2Lan3MCVlanMCD7PIfInErrors
         Counter64,
      pr1645v2Lan3MCVlanMCD7PIfInUnkwn
         Counter64,
      pr1645v2Lan3MCVlanMCD7PInDropEx
         Counter64,
      pr1645v2Lan3MCVlanMCD7PInDropNoMac
         Counter64,
      pr1645v2Lan3MCVlanMCD7PInDropNUCast
         Counter64,
      pr1645v2Lan3MCVlanMCD7PInDropFilter
         Counter64,
      pr1645v2Lan3MCVlanMCD7PIfInBandwidth
         Integer32,
      pr1645v2Lan3MCVlanMCD7PIfOutOctets
         Counter64,
      pr1645v2Lan3MCVlanMCD7PIfOutUCPkts
         Counter64,
      pr1645v2Lan3MCVlanMCD7PIfOutNUCPkts
         Counter64,
      pr1645v2Lan3MCVlanMCD7PIfOutBCPkts
         Counter64,
      pr1645v2Lan3MCVlanMCD7PIfOutMCPkts
         Counter64,
      pr1645v2Lan3MCVlanMCD7PIfOutDiscards
         Counter64,
      pr1645v2Lan3MCVlanMCD7PIfOutErrors
         Counter64,
      pr1645v2Lan3MCVlanMCD7POutDropEx
         Counter64,
      pr1645v2Lan3MCVlanMCD7POutDropNoArp
         Counter64,
      pr1645v2Lan3MCVlanMCD7POutDropFilter
         Counter64,
      pr1645v2Lan3MCVlanMCD7PIfOutBandwidth
         Integer32,
      pr1645v2Lan3MCVlanMCD7PIfErrSec
         Counter32
      }

pr1645v2Lan3MCVlanMCD7PTableIx OBJECT-TYPE
   SYNTAX      TableIndex
   MAX-ACCESS  not-accessible
   STATUS      current
   DESCRIPTION
      ""
   ::= {pr1645v2Lan3MCVlanMCD7PEntry 11}

pr1645v2Lan3MCVlanMCD7PSysUpTime OBJECT-TYPE
   SYNTAX      TimeTicks
   MAX-ACCESS  read-only
   STATUS      current
   DESCRIPTION
      "Path: ethernet3.performance.vlan.mibCounters.d7Performance.sysUpTime

       Time in centi-second."
   ::= {pr1645v2Lan3MCVlanMCD7PEntry 16777216}

pr1645v2Lan3MCVlanMCD7PIfUpTime OBJECT-TYPE
   SYNTAX      TimeTicks
   MAX-ACCESS  read-only
   STATUS      current
   DESCRIPTION
      "Path: ethernet3.performance.vlan.mibCounters.d7Performance.ifUpTime

       Time in centi-second."
   ::= {pr1645v2Lan3MCVlanMCD7PEntry 33554432}

pr1645v2Lan3MCVlanMCD7PIfStatChanges OBJECT-TYPE
   SYNTAX      Counter32
   MAX-ACCESS  read-only
   STATUS      current
   DESCRIPTION
      "Path: ethernet3.performance.vlan.mibCounters.d7Performance.ifStatusChanges

       32 bit unsigned wrappable counter."
   ::= {pr1645v2Lan3MCVlanMCD7PEntry 50331648}

pr1645v2Lan3MCVlanMCD7PIfInOctets OBJECT-TYPE
   SYNTAX      Counter64
   MAX-ACCESS  read-only
   STATUS      current
   DESCRIPTION
      "Path: ethernet3.performance.vlan.mibCounters.d7Performance.ifInOctets

       64 bit unsigned wrappable counter."
   ::= {pr1645v2Lan3MCVlanMCD7PEntry 67108864}

pr1645v2Lan3MCVlanMCD7PIfInUCPkts OBJECT-TYPE
   SYNTAX      Counter64
   MAX-ACCESS  read-only
   STATUS      current
   DESCRIPTION
      "Path: ethernet3.performance.vlan.mibCounters.d7Performance.ifInUcastPkts

       64 bit unsigned wrappable counter."
   ::= {pr1645v2Lan3MCVlanMCD7PEntry 83886080}

pr1645v2Lan3MCVlanMCD7PIfInNUCPkts OBJECT-TYPE
   SYNTAX      Counter64
   MAX-ACCESS  read-only
   STATUS      current
   DESCRIPTION
      "Path: ethernet3.performance.vlan.mibCounters.d7Performance.ifInNUcastPkts

       64 bit unsigned wrappable counter."
   ::= {pr1645v2Lan3MCVlanMCD7PEntry 100663296}

pr1645v2Lan3MCVlanMCD7PIfInBCPkts OBJECT-TYPE
   SYNTAX      Counter64
   MAX-ACCESS  read-only
   STATUS      current
   DESCRIPTION
      "Path: ethernet3.performance.vlan.mibCounters.d7Performance.ifInBcastPkts

       64 bit unsigned wrappable counter."
   ::= {pr1645v2Lan3MCVlanMCD7PEntry 419430400}

pr1645v2Lan3MCVlanMCD7PIfInMCPkts OBJECT-TYPE
   SYNTAX      Counter64
   MAX-ACCESS  read-only
   STATUS      current
   DESCRIPTION
      "Path: ethernet3.performance.vlan.mibCounters.d7Performance.ifInMcastPkts

       64 bit unsigned wrappable counter."
   ::= {pr1645v2Lan3MCVlanMCD7PEntry 436207616}

pr1645v2Lan3MCVlanMCD7PIfInDiscards OBJECT-TYPE
   SYNTAX      Counter64
   MAX-ACCESS  read-only
   STATUS      current
   DESCRIPTION
      "Path: ethernet3.performance.vlan.mibCounters.d7Performance.ifInDiscards

       64 bit unsigned wrappable counter."
   ::= {pr1645v2Lan3MCVlanMCD7PEntry 117440512}

pr1645v2Lan3MCVlanMCD7PIfInErrors OBJECT-TYPE
   SYNTAX      Counter64
   MAX-ACCESS  read-only
   STATUS      current
   DESCRIPTION
      "Path: ethernet3.performance.vlan.mibCounters.d7Performance.ifInErrors

       64 bit unsigned wrappable counter."
   ::= {pr1645v2Lan3MCVlanMCD7PEntry 134217728}

pr1645v2Lan3MCVlanMCD7PIfInUnkwn OBJECT-TYPE
   SYNTAX      Counter64
   MAX-ACCESS  read-only
   STATUS      current
   DESCRIPTION
      "Path: ethernet3.performance.vlan.mibCounters.d7Performance.ifInUnknownProtos

       64 bit unsigned wrappable counter."
   ::= {pr1645v2Lan3MCVlanMCD7PEntry 150994944}

pr1645v2Lan3MCVlanMCD7PInDropEx OBJECT-TYPE
   SYNTAX      Counter64
   MAX-ACCESS  read-only
   STATUS      current
   DESCRIPTION
      "Path: ethernet3.performance.vlan.mibCounters.d7Performance.ifInDropLevelExceeded

       64 bit unsigned wrappable counter."
   ::= {pr1645v2Lan3MCVlanMCD7PEntry 335544320}

pr1645v2Lan3MCVlanMCD7PInDropNoMac OBJECT-TYPE
   SYNTAX      Counter64
   MAX-ACCESS  read-only
   STATUS      current
   DESCRIPTION
      "Path: ethernet3.performance.vlan.mibCounters.d7Performance.fInDiscardsNoMacFit

       64 bit unsigned wrappable counter."
   ::= {pr1645v2Lan3MCVlanMCD7PEntry 301989888}

pr1645v2Lan3MCVlanMCD7PInDropNUCast OBJECT-TYPE
   SYNTAX      Counter64
   MAX-ACCESS  read-only
   STATUS      current
   DESCRIPTION
      "Path: ethernet3.performance.vlan.mibCounters.d7Performance.fInDiscardsNUCast

       64 bit unsigned wrappable counter."
   ::= {pr1645v2Lan3MCVlanMCD7PEntry 318767104}

pr1645v2Lan3MCVlanMCD7PInDropFilter OBJECT-TYPE
   SYNTAX      Counter64
   MAX-ACCESS  read-only
   STATUS      current
   DESCRIPTION
      "Path: ethernet3.performance.vlan.mibCounters.d7Performance.fInDiscardsFilter

       64 bit unsigned wrappable counter."
   ::= {pr1645v2Lan3MCVlanMCD7PEntry 385875968}

pr1645v2Lan3MCVlanMCD7PIfInBandwidth OBJECT-TYPE
   SYNTAX      Integer32
   MAX-ACCESS  read-only
   STATUS      current
   DESCRIPTION
      "Path: ethernet3.performance.vlan.mibCounters.d7Performance.ifInBandwidth

       unit name = bps
       formula = 8 * ; 8 /"
   ::= {pr1645v2Lan3MCVlanMCD7PEntry 268435456}

pr1645v2Lan3MCVlanMCD7PIfOutOctets OBJECT-TYPE
   SYNTAX      Counter64
   MAX-ACCESS  read-only
   STATUS      current
   DESCRIPTION
      "Path: ethernet3.performance.vlan.mibCounters.d7Performance.ifOutOctets

       64 bit unsigned wrappable counter."
   ::= {pr1645v2Lan3MCVlanMCD7PEntry 167772160}

pr1645v2Lan3MCVlanMCD7PIfOutUCPkts OBJECT-TYPE
   SYNTAX      Counter64
   MAX-ACCESS  read-only
   STATUS      current
   DESCRIPTION
      "Path: ethernet3.performance.vlan.mibCounters.d7Performance.ifOutUcastPkts

       64 bit unsigned wrappable counter."
   ::= {pr1645v2Lan3MCVlanMCD7PEntry 184549376}

pr1645v2Lan3MCVlanMCD7PIfOutNUCPkts OBJECT-TYPE
   SYNTAX      Counter64
   MAX-ACCESS  read-only
   STATUS      current
   DESCRIPTION
      "Path: ethernet3.performance.vlan.mibCounters.d7Performance.ifOutNUcastPkts

       64 bit unsigned wrappable counter."
   ::= {pr1645v2Lan3MCVlanMCD7PEntry 201326592}

pr1645v2Lan3MCVlanMCD7PIfOutBCPkts OBJECT-TYPE
   SYNTAX      Counter64
   MAX-ACCESS  read-only
   STATUS      current
   DESCRIPTION
      "Path: ethernet3.performance.vlan.mibCounters.d7Performance.ifOutBcastPkts

       64 bit unsigned wrappable counter."
   ::= {pr1645v2Lan3MCVlanMCD7PEntry 452984832}

pr1645v2Lan3MCVlanMCD7PIfOutMCPkts OBJECT-TYPE
   SYNTAX      Counter64
   MAX-ACCESS  read-only
   STATUS      current
   DESCRIPTION
      "Path: ethernet3.performance.vlan.mibCounters.d7Performance.ifOutMcastPkts

       64 bit unsigned wrappable counter."
   ::= {pr1645v2Lan3MCVlanMCD7PEntry 469762048}

pr1645v2Lan3MCVlanMCD7PIfOutDiscards OBJECT-TYPE
   SYNTAX      Counter64
   MAX-ACCESS  read-only
   STATUS      current
   DESCRIPTION
      "Path: ethernet3.performance.vlan.mibCounters.d7Performance.ifOutDiscards

       64 bit unsigned wrappable counter."
   ::= {pr1645v2Lan3MCVlanMCD7PEntry 218103808}

pr1645v2Lan3MCVlanMCD7PIfOutErrors OBJECT-TYPE
   SYNTAX      Counter64
   MAX-ACCESS  read-only
   STATUS      current
   DESCRIPTION
      "Path: ethernet3.performance.vlan.mibCounters.d7Performance.ifOutErrors

       64 bit unsigned wrappable counter."
   ::= {pr1645v2Lan3MCVlanMCD7PEntry 234881024}

pr1645v2Lan3MCVlanMCD7POutDropEx OBJECT-TYPE
   SYNTAX      Counter64
   MAX-ACCESS  read-only
   STATUS      current
   DESCRIPTION
      "Path: ethernet3.performance.vlan.mibCounters.d7Performance.ifOutDropLevelExceeded

       64 bit unsigned wrappable counter."
   ::= {pr1645v2Lan3MCVlanMCD7PEntry 352321536}

pr1645v2Lan3MCVlanMCD7POutDropNoArp OBJECT-TYPE
   SYNTAX      Counter64
   MAX-ACCESS  read-only
   STATUS      current
   DESCRIPTION
      "Path: ethernet3.performance.vlan.mibCounters.d7Performance.ifOutDiscardsNoArp

       64 bit unsigned wrappable counter."
   ::= {pr1645v2Lan3MCVlanMCD7PEntry 369098752}

pr1645v2Lan3MCVlanMCD7POutDropFilter OBJECT-TYPE
   SYNTAX      Counter64
   MAX-ACCESS  read-only
   STATUS      current
   DESCRIPTION
      "Path: ethernet3.performance.vlan.mibCounters.d7Performance.ifOutDiscardsFilter

       64 bit unsigned wrappable counter."
   ::= {pr1645v2Lan3MCVlanMCD7PEntry 402653184}

pr1645v2Lan3MCVlanMCD7PIfOutBandwidth OBJECT-TYPE
   SYNTAX      Integer32
   MAX-ACCESS  read-only
   STATUS      current
   DESCRIPTION
      "Path: ethernet3.performance.vlan.mibCounters.d7Performance.ifOutBandwidth

       unit name = bps
       formula = 8 * ; 8 /"
   ::= {pr1645v2Lan3MCVlanMCD7PEntry 285212672}

pr1645v2Lan3MCVlanMCD7PIfErrSec OBJECT-TYPE
   SYNTAX      Counter32
   MAX-ACCESS  read-only
   STATUS      current
   DESCRIPTION
      "Path: ethernet3.performance.vlan.mibCounters.d7Performance.ifErrSec

       32 bit unsigned wrappable counter."
   ::= {pr1645v2Lan3MCVlanMCD7PEntry 251658240}

pr1645v2Lan3MCVlanInPQs OBJECT-TYPE
   SYNTAX      SEQUENCE OF Pr1645v2Lan3MCVlanInPQsEntry
   MAX-ACCESS  not-accessible
   STATUS      current
   DESCRIPTION
      ""
   ::= {pr1645v2Lan3MCVlan 100663296}

pr1645v2Lan3MCVlanInPQsEntry OBJECT-TYPE
   SYNTAX      Pr1645v2Lan3MCVlanInPQsEntry
   MAX-ACCESS  not-accessible
   STATUS      current
   DESCRIPTION
      ""
   INDEX      { pr1645v2Lan3MCVlanTableIx,
                pr1645v2Lan3MCVlanInPQsTableIx }
   ::= {pr1645v2Lan3MCVlanInPQs 1}

Pr1645v2Lan3MCVlanInPQsEntry ::=
   SEQUENCE
      {
      pr1645v2Lan3MCVlanInPQsTableIx
         TableIndex,
      pr1645v2Lan3MCVlanInPQsName
         INTEGER,
      pr1645v2Lan3MCVlanInPQsLength
         Integer32,
      pr1645v2Lan3MCVlanInPQsOctetLength
         Integer32,
      pr1645v2Lan3MCVlanInPQsRedLength
         Integer32,
      pr1645v2Lan3MCVlanInPQsPacketsTotal
         Counter64,
      pr1645v2Lan3MCVlanInPQsPacketsDirectTx
         Counter64,
      pr1645v2Lan3MCVlanInPQsPacketsQueued
         Counter64,
      pr1645v2Lan3MCVlanInPQsPacketsDropped
         Counter64,
      pr1645v2Lan3MCVlanInPQsPacketsRedDropped
         Counter64,
      pr1645v2Lan3MCVlanInPQsPacketsCirTx
         Counter64,
      pr1645v2Lan3MCVlanInPQsPacketsEirTx
         Counter64,
      pr1645v2Lan3MCVlanInPQsPacketsViolateTx
         Counter64,
      pr1645v2Lan3MCVlanInPQsOctetsTotal
         Counter64,
      pr1645v2Lan3MCVlanInPQsOctetsDirectTx
         Counter64,
      pr1645v2Lan3MCVlanInPQsOctetsQueued
         Counter64,
      pr1645v2Lan3MCVlanInPQsOctetsDropped
         Counter64,
      pr1645v2Lan3MCVlanInPQsOctetsRedDropped
         Counter64,
      pr1645v2Lan3MCVlanInPQsOctetsCirTx
         Counter64,
      pr1645v2Lan3MCVlanInPQsOctetsEirTx
         Counter64,
      pr1645v2Lan3MCVlanInPQsOctetsViolateTx
         Counter64,
      pr1645v2Lan3MCVlanInPQsOctetsBandwidth15sec
         Integer32,
      pr1645v2Lan3MCVlanInPQsOctetsBandwidth30sec
         Integer32,
      pr1645v2Lan3MCVlanInPQsOctetsBandwidth1min
         Integer32,
      pr1645v2Lan3MCVlanInPQsOctetsBandwidth2min
         Integer32,
      pr1645v2Lan3MCVlanInPQsOctetsBandwidth5min
         Integer32
      }

pr1645v2Lan3MCVlanInPQsTableIx OBJECT-TYPE
   SYNTAX      TableIndex
   MAX-ACCESS  not-accessible
   STATUS      current
   DESCRIPTION
      ""
   ::= {pr1645v2Lan3MCVlanInPQsEntry 11}

pr1645v2Lan3MCVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3MCVlanInPQsEntry 16777216}

pr1645v2Lan3MCVlanInPQsLength OBJECT-TYPE
   SYNTAX      Integer32
   MAX-ACCESS  read-only
   STATUS      current
   DESCRIPTION
      "Path: ethernet3.performance.vlan.inPriorityQueues.length"
   ::= {pr1645v2Lan3MCVlanInPQsEntry 33554432}

pr1645v2Lan3MCVlanInPQsOctetLength OBJECT-TYPE
   SYNTAX      Integer32
   MAX-ACCESS  read-only
   STATUS      current
   DESCRIPTION
      "Path: ethernet3.performance.vlan.inPriorityQueues.octetLength"
   ::= {pr1645v2Lan3MCVlanInPQsEntry 150994944}

pr1645v2Lan3MCVlanInPQsRedLength OBJECT-TYPE
   SYNTAX      Integer32
   MAX-ACCESS  read-only
   STATUS      current
   DESCRIPTION
      "Path: ethernet3.performance.vlan.inPriorityQueues.redLength"
   ::= {pr1645v2Lan3MCVlanInPQsEntry 134217728}

pr1645v2Lan3MCVlanInPQsPacketsTotal OBJECT-TYPE
   SYNTAX      Counter64
   MAX-ACCESS  read-only
   STATUS      current
   DESCRIPTION
      "Path: ethernet3.performance.vlan.inPriorityQueues.packets.total

       64 bit unsigned wrappable counter."
   ::= {pr1645v2Lan3MCVlanInPQsEntry 50790400}

pr1645v2Lan3MCVlanInPQsPacketsDirectTx OBJECT-TYPE
   SYNTAX      Counter64
   MAX-ACCESS  read-only
   STATUS      current
   DESCRIPTION
      "Path: ethernet3.performance.vlan.inPriorityQueues.packets.directTx

       64 bit unsigned wrappable counter."
   ::= {pr1645v2Lan3MCVlanInPQsEntry 50397184}

pr1645v2Lan3MCVlanInPQsPacketsQueued OBJECT-TYPE
   SYNTAX      Counter64
   MAX-ACCESS  read-only
   STATUS      current
   DESCRIPTION
      "Path: ethernet3.performance.vlan.inPriorityQueues.packets.queued

       64 bit unsigned wrappable counter."
   ::= {pr1645v2Lan3MCVlanInPQsEntry 50462720}

pr1645v2Lan3MCVlanInPQsPacketsDropped OBJECT-TYPE
   SYNTAX      Counter64
   MAX-ACCESS  read-only
   STATUS      current
   DESCRIPTION
      "Path: ethernet3.performance.vlan.inPriorityQueues.packets.dropped

       64 bit unsigned wrappable counter."
   ::= {pr1645v2Lan3MCVlanInPQsEntry 50528256}

pr1645v2Lan3MCVlanInPQsPacketsRedDropped OBJECT-TYPE
   SYNTAX      Counter64
   MAX-ACCESS  read-only
   STATUS      current
   DESCRIPTION
      "Path: ethernet3.performance.vlan.inPriorityQueues.packets.redDropped

       64 bit unsigned wrappable counter."
   ::= {pr1645v2Lan3MCVlanInPQsEntry 50724864}

pr1645v2Lan3MCVlanInPQsPacketsCirTx OBJECT-TYPE
   SYNTAX      Counter64
   MAX-ACCESS  read-only
   STATUS      current
   DESCRIPTION
      "Path: ethernet3.performance.vlan.inPriorityQueues.packets.cirTx

       64 bit unsigned wrappable counter."
   ::= {pr1645v2Lan3MCVlanInPQsEntry 50593792}

pr1645v2Lan3MCVlanInPQsPacketsEirTx OBJECT-TYPE
   SYNTAX      Counter64
   MAX-ACCESS  read-only
   STATUS      current
   DESCRIPTION
      "Path: ethernet3.performance.vlan.inPriorityQueues.packets.eirTx

       64 bit unsigned wrappable counter."
   ::= {pr1645v2Lan3MCVlanInPQsEntry 50659328}

pr1645v2Lan3MCVlanInPQsPacketsViolateTx OBJECT-TYPE
   SYNTAX      Counter64
   MAX-ACCESS  read-only
   STATUS      current
   DESCRIPTION
      "Path: ethernet3.performance.vlan.inPriorityQueues.packets.violateTx

       64 bit unsigned wrappable counter."
   ::= {pr1645v2Lan3MCVlanInPQsEntry 50855936}

pr1645v2Lan3MCVlanInPQsOctetsTotal OBJECT-TYPE
   SYNTAX      Counter64
   MAX-ACCESS  read-only
   STATUS      current
   DESCRIPTION
      "Path: ethernet3.performance.vlan.inPriorityQueues.octets.total

       64 bit unsigned wrappable counter."
   ::= {pr1645v2Lan3MCVlanInPQsEntry 67567616}

pr1645v2Lan3MCVlanInPQsOctetsDirectTx OBJECT-TYPE
   SYNTAX      Counter64
   MAX-ACCESS  read-only
   STATUS      current
   DESCRIPTION
      "Path: ethernet3.performance.vlan.inPriorityQueues.octets.directTx

       64 bit unsigned wrappable counter."
   ::= {pr1645v2Lan3MCVlanInPQsEntry 67174400}

pr1645v2Lan3MCVlanInPQsOctetsQueued OBJECT-TYPE
   SYNTAX      Counter64
   MAX-ACCESS  read-only
   STATUS      current
   DESCRIPTION
      "Path: ethernet3.performance.vlan.inPriorityQueues.octets.queued

       64 bit unsigned wrappable counter."
   ::= {pr1645v2Lan3MCVlanInPQsEntry 67239936}

pr1645v2Lan3MCVlanInPQsOctetsDropped OBJECT-TYPE
   SYNTAX      Counter64
   MAX-ACCESS  read-only
   STATUS      current
   DESCRIPTION
      "Path: ethernet3.performance.vlan.inPriorityQueues.octets.dropped

       64 bit unsigned wrappable counter."
   ::= {pr1645v2Lan3MCVlanInPQsEntry 67305472}

pr1645v2Lan3MCVlanInPQsOctetsRedDropped OBJECT-TYPE
   SYNTAX      Counter64
   MAX-ACCESS  read-only
   STATUS      current
   DESCRIPTION
      "Path: ethernet3.performance.vlan.inPriorityQueues.octets.redDropped

       64 bit unsigned wrappable counter."
   ::= {pr1645v2Lan3MCVlanInPQsEntry 67502080}

pr1645v2Lan3MCVlanInPQsOctetsCirTx OBJECT-TYPE
   SYNTAX      Counter64
   MAX-ACCESS  read-only
   STATUS      current
   DESCRIPTION
      "Path: ethernet3.performance.vlan.inPriorityQueues.octets.cirTx

       64 bit unsigned wrappable counter."
   ::= {pr1645v2Lan3MCVlanInPQsEntry 67371008}

pr1645v2Lan3MCVlanInPQsOctetsEirTx OBJECT-TYPE
   SYNTAX      Counter64
   MAX-ACCESS  read-only
   STATUS      current
   DESCRIPTION
      "Path: ethernet3.performance.vlan.inPriorityQueues.octets.eirTx

       64 bit unsigned wrappable counter."
   ::= {pr1645v2Lan3MCVlanInPQsEntry 67436544}

pr1645v2Lan3MCVlanInPQsOctetsViolateTx OBJECT-TYPE
   SYNTAX      Counter64
   MAX-ACCESS  read-only
   STATUS      current
   DESCRIPTION
      "Path: ethernet3.performance.vlan.inPriorityQueues.octets.violateTx

       64 bit unsigned wrappable counter."
   ::= {pr1645v2Lan3MCVlanInPQsEntry 67633152}

pr1645v2Lan3MCVlanInPQsOctetsBandwidth15sec OBJECT-TYPE
   SYNTAX      Integer32
   MAX-ACCESS  read-only
   STATUS      current
   DESCRIPTION
      "Path: ethernet3.performance.vlan.inPriorityQueues.octets.bandwidth.15sec

       unit name = bps
       formula = 8 * ; 8 /"
   ::= {pr1645v2Lan3MCVlanInPQsEntry 70386944}

pr1645v2Lan3MCVlanInPQsOctetsBandwidth30sec OBJECT-TYPE
   SYNTAX      Integer32
   MAX-ACCESS  read-only
   STATUS      current
   DESCRIPTION
      "Path: ethernet3.performance.vlan.inPriorityQueues.octets.bandwidth.30sec

       unit name = bps
       formula = 8 * ; 8 /"
   ::= {pr1645v2Lan3MCVlanInPQsEntry 70388224}

pr1645v2Lan3MCVlanInPQsOctetsBandwidth1min OBJECT-TYPE
   SYNTAX      Integer32
   MAX-ACCESS  read-only
   STATUS      current
   DESCRIPTION
      "Path: ethernet3.performance.vlan.inPriorityQueues.octets.bandwidth.1min

       unit name = bps
       formula = 8 * ; 8 /"
   ::= {pr1645v2Lan3MCVlanInPQsEntry 70390784}

pr1645v2Lan3MCVlanInPQsOctetsBandwidth2min OBJECT-TYPE
   SYNTAX      Integer32
   MAX-ACCESS  read-only
   STATUS      current
   DESCRIPTION
      "Path: ethernet3.performance.vlan.inPriorityQueues.octets.bandwidth.2min

       unit name = bps
       formula = 8 * ; 8 /"
   ::= {pr1645v2Lan3MCVlanInPQsEntry 70395904}

pr1645v2Lan3MCVlanInPQsOctetsBandwidth5min OBJECT-TYPE
   SYNTAX      Integer32
   MAX-ACCESS  read-only
   STATUS      current
   DESCRIPTION
      "Path: ethernet3.performance.vlan.inPriorityQueues.octets.bandwidth.5min

       unit name = bps
       formula = 8 * ; 8 /"
   ::= {pr1645v2Lan3MCVlanInPQsEntry 70411264}

pr1645v2Lan3MCVlanInPQsH2Performance OBJECT-TYPE
   SYNTAX      SEQUENCE OF Pr1645v2Lan3MCVlanInPQsH2PerformanceEntry
   MAX-ACCESS  not-accessible
   STATUS      current
   DESCRIPTION
      ""
   ::= {pr1645v2Lan3MCVlan 100990976}

pr1645v2Lan3MCVlanInPQsH2PerformanceEntry OBJECT-TYPE
   SYNTAX      Pr1645v2Lan3MCVlanInPQsH2PerformanceEntry
   MAX-ACCESS  not-accessible
   STATUS      current
   DESCRIPTION
      ""
   INDEX      { pr1645v2Lan3MCVlanTableIx,
                pr1645v2Lan3MCVlanInPQsTableIx,
                pr1645v2Lan3MCVlanInPQsH2PerformanceTableIx }
   ::= {pr1645v2Lan3MCVlanInPQsH2Performance 1}

Pr1645v2Lan3MCVlanInPQsH2PerformanceEntry ::=
   SEQUENCE
      {
      pr1645v2Lan3MCVlanInPQsH2PerformanceTableIx
         TableIndex,
      pr1645v2Lan3MCVlanInPQsH2PerformanceSysUpTime
         TimeTicks,
      pr1645v2Lan3MCVlanInPQsH2PerformanceTotPkts
         Counter64,
      pr1645v2Lan3MCVlanInPQsH2PerformanceDirTxPkts
         Counter64,
      pr1645v2Lan3MCVlanInPQsH2PerformanceQdPkts
         Counter64,
      pr1645v2Lan3MCVlanInPQsH2PerformanceDropPkts
         Counter64,
      pr1645v2Lan3MCVlanInPQsH2PerformanceRDropPkts
         Counter64,
      pr1645v2Lan3MCVlanInPQsH2PerformanceCirTxPkts
         Counter64,
      pr1645v2Lan3MCVlanInPQsH2PerformanceEirTxPkts
         Counter64,
      pr1645v2Lan3MCVlanInPQsH2PerformanceViolTxPkts
         Counter64,
      pr1645v2Lan3MCVlanInPQsH2PerformanceTotOcts
         Counter64,
      pr1645v2Lan3MCVlanInPQsH2PerformanceDirTxOcts
         Counter64,
      pr1645v2Lan3MCVlanInPQsH2PerformanceQdOcts
         Counter64,
      pr1645v2Lan3MCVlanInPQsH2PerformanceDropOcts
         Counter64,
      pr1645v2Lan3MCVlanInPQsH2PerformanceRDropOcts
         Counter64,
      pr1645v2Lan3MCVlanInPQsH2PerformanceCirTxOcts
         Counter64,
      pr1645v2Lan3MCVlanInPQsH2PerformanceEirTxOcts
         Counter64,
      pr1645v2Lan3MCVlanInPQsH2PerformanceViolTxOcts
         Counter64,
      pr1645v2Lan3MCVlanInPQsH2PerformanceBandwidth
         Integer32
      }

pr1645v2Lan3MCVlanInPQsH2PerformanceTableIx OBJECT-TYPE
   SYNTAX      TableIndex
   MAX-ACCESS  not-accessible
   STATUS      current
   DESCRIPTION
      ""
   ::= {pr1645v2Lan3MCVlanInPQsH2PerformanceEntry 11}

pr1645v2Lan3MCVlanInPQsH2PerformanceSysUpTime OBJECT-TYPE
   SYNTAX      TimeTicks
   MAX-ACCESS  read-only
   STATUS      current
   DESCRIPTION
      "Path: ethernet3.performance.vlan.inPriorityQueues.h2Performance.sysUpTime

       Time in centi-second."
   ::= {pr1645v2Lan3MCVlanInPQsH2PerformanceEntry 16777216}

pr1645v2Lan3MCVlanInPQsH2PerformanceTotPkts OBJECT-TYPE
   SYNTAX      Counter64
   MAX-ACCESS  read-only
   STATUS      current
   DESCRIPTION
      "Path: ethernet3.performance.vlan.inPriorityQueues.h2Performance.totalPkts

       64 bit unsigned wrappable counter."
   ::= {pr1645v2Lan3MCVlanInPQsH2PerformanceEntry 234881024}

pr1645v2Lan3MCVlanInPQsH2PerformanceDirTxPkts OBJECT-TYPE
   SYNTAX      Counter64
   MAX-ACCESS  read-only
   STATUS      current
   DESCRIPTION
      "Path: ethernet3.performance.vlan.inPriorityQueues.h2Performance.directTxPkts

       64 bit unsigned wrappable counter."
   ::= {pr1645v2Lan3MCVlanInPQsH2PerformanceEntry 33554432}

pr1645v2Lan3MCVlanInPQsH2PerformanceQdPkts OBJECT-TYPE
   SYNTAX      Counter64
   MAX-ACCESS  read-only
   STATUS      current
   DESCRIPTION
      "Path: ethernet3.performance.vlan.inPriorityQueues.h2Performance.queuedPkts

       64 bit unsigned wrappable counter."
   ::= {pr1645v2Lan3MCVlanInPQsH2PerformanceEntry 50331648}

pr1645v2Lan3MCVlanInPQsH2PerformanceDropPkts OBJECT-TYPE
   SYNTAX      Counter64
   MAX-ACCESS  read-only
   STATUS      current
   DESCRIPTION
      "Path: ethernet3.performance.vlan.inPriorityQueues.h2Performance.droppedPkts

       64 bit unsigned wrappable counter."
   ::= {pr1645v2Lan3MCVlanInPQsH2PerformanceEntry 67108864}

pr1645v2Lan3MCVlanInPQsH2PerformanceRDropPkts OBJECT-TYPE
   SYNTAX      Counter64
   MAX-ACCESS  read-only
   STATUS      current
   DESCRIPTION
      "Path: ethernet3.performance.vlan.inPriorityQueues.h2Performance.redDroppedPkts

       64 bit unsigned wrappable counter."
   ::= {pr1645v2Lan3MCVlanInPQsH2PerformanceEntry 201326592}

pr1645v2Lan3MCVlanInPQsH2PerformanceCirTxPkts OBJECT-TYPE
   SYNTAX      Counter64
   MAX-ACCESS  read-only
   STATUS      current
   DESCRIPTION
      "Path: ethernet3.performance.vlan.inPriorityQueues.h2Performance.cirTxPkts

       64 bit unsigned wrappable counter."
   ::= {pr1645v2Lan3MCVlanInPQsH2PerformanceEntry 83886080}

pr1645v2Lan3MCVlanInPQsH2PerformanceEirTxPkts OBJECT-TYPE
   SYNTAX      Counter64
   MAX-ACCESS  read-only
   STATUS      current
   DESCRIPTION
      "Path: ethernet3.performance.vlan.inPriorityQueues.h2Performance.eirTxPkts

       64 bit unsigned wrappable counter."
   ::= {pr1645v2Lan3MCVlanInPQsH2PerformanceEntry 100663296}

pr1645v2Lan3MCVlanInPQsH2PerformanceViolTxPkts OBJECT-TYPE
   SYNTAX      Counter64
   MAX-ACCESS  read-only
   STATUS      current
   DESCRIPTION
      "Path: ethernet3.performance.vlan.inPriorityQueues.h2Performance.violateTxPkts

       64 bit unsigned wrappable counter."
   ::= {pr1645v2Lan3MCVlanInPQsH2PerformanceEntry 301989888}

pr1645v2Lan3MCVlanInPQsH2PerformanceTotOcts OBJECT-TYPE
   SYNTAX      Counter64
   MAX-ACCESS  read-only
   STATUS      current
   DESCRIPTION
      "Path: ethernet3.performance.vlan.inPriorityQueues.h2Performance.totalOctets

       64 bit unsigned wrappable counter."
   ::= {pr1645v2Lan3MCVlanInPQsH2PerformanceEntry 251658240}

pr1645v2Lan3MCVlanInPQsH2PerformanceDirTxOcts OBJECT-TYPE
   SYNTAX      Counter64
   MAX-ACCESS  read-only
   STATUS      current
   DESCRIPTION
      "Path: ethernet3.performance.vlan.inPriorityQueues.h2Performance.directTxOctets

       64 bit unsigned wrappable counter."
   ::= {pr1645v2Lan3MCVlanInPQsH2PerformanceEntry 117440512}

pr1645v2Lan3MCVlanInPQsH2PerformanceQdOcts OBJECT-TYPE
   SYNTAX      Counter64
   MAX-ACCESS  read-only
   STATUS      current
   DESCRIPTION
      "Path: ethernet3.performance.vlan.inPriorityQueues.h2Performance.queuedOctets

       64 bit unsigned wrappable counter."
   ::= {pr1645v2Lan3MCVlanInPQsH2PerformanceEntry 134217728}

pr1645v2Lan3MCVlanInPQsH2PerformanceDropOcts OBJECT-TYPE
   SYNTAX      Counter64
   MAX-ACCESS  read-only
   STATUS      current
   DESCRIPTION
      "Path: ethernet3.performance.vlan.inPriorityQueues.h2Performance.droppedOctets

       64 bit unsigned wrappable counter."
   ::= {pr1645v2Lan3MCVlanInPQsH2PerformanceEntry 150994944}

pr1645v2Lan3MCVlanInPQsH2PerformanceRDropOcts OBJECT-TYPE
   SYNTAX      Counter64
   MAX-ACCESS  read-only
   STATUS      current
   DESCRIPTION
      "Path: ethernet3.performance.vlan.inPriorityQueues.h2Performance.redDroppedOctets

       64 bit unsigned wrappable counter."
   ::= {pr1645v2Lan3MCVlanInPQsH2PerformanceEntry 218103808}

pr1645v2Lan3MCVlanInPQsH2PerformanceCirTxOcts OBJECT-TYPE
   SYNTAX      Counter64
   MAX-ACCESS  read-only
   STATUS      current
   DESCRIPTION
      "Path: ethernet3.performance.vlan.inPriorityQueues.h2Performance.cirTxOctets

       64 bit unsigned wrappable counter."
   ::= {pr1645v2Lan3MCVlanInPQsH2PerformanceEntry 167772160}

pr1645v2Lan3MCVlanInPQsH2PerformanceEirTxOcts OBJECT-TYPE
   SYNTAX      Counter64
   MAX-ACCESS  read-only
   STATUS      current
   DESCRIPTION
      "Path: ethernet3.performance.vlan.inPriorityQueues.h2Performance.eirTxOctets

       64 bit unsigned wrappable counter."
   ::= {pr1645v2Lan3MCVlanInPQsH2PerformanceEntry 184549376}

pr1645v2Lan3MCVlanInPQsH2PerformanceViolTxOcts OBJECT-TYPE
   SYNTAX      Counter64
   MAX-ACCESS  read-only
   STATUS      current
   DESCRIPTION
      "Path: ethernet3.performance.vlan.inPriorityQueues.h2Performance.violateTxOctets

       64 bit unsigned wrappable counter."
   ::= {pr1645v2Lan3MCVlanInPQsH2PerformanceEntry 318767104}

pr1645v2Lan3MCVlanInPQsH2PerformanceBandwidth OBJECT-TYPE
   SYNTAX      Integer32
   MAX-ACCESS  read-only
   STATUS      current
   DESCRIPTION
      "Path: ethernet3.performance.vlan.inPriorityQueues.h2Performance.bandwidth

       unit name = bps
       formula = 8 * ; 8 /"
   ::= {pr1645v2Lan3MCVlanInPQsH2PerformanceEntry 268435456}

pr1645v2Lan3MCVlanInPQsH24Performance OBJECT-TYPE
   SYNTAX      SEQUENCE OF Pr1645v2Lan3MCVlanInPQsH24PerformanceEntry
   MAX-ACCESS  not-accessible
   STATUS      current
   DESCRIPTION
      ""
   ::= {pr1645v2Lan3MCVlan 101056512}

pr1645v2Lan3MCVlanInPQsH24PerformanceEntry OBJECT-TYPE
   SYNTAX      Pr1645v2Lan3MCVlanInPQsH24PerformanceEntry
   MAX-ACCESS  not-accessible
   STATUS      current
   DESCRIPTION
      ""
   INDEX      { pr1645v2Lan3MCVlanTableIx,
                pr1645v2Lan3MCVlanInPQsTableIx,
                pr1645v2Lan3MCVlanInPQsH24PerformanceTableIx }
   ::= {pr1645v2Lan3MCVlanInPQsH24Performance 1}

Pr1645v2Lan3MCVlanInPQsH24PerformanceEntry ::=
   SEQUENCE
      {
      pr1645v2Lan3MCVlanInPQsH24PerformanceTableIx
         TableIndex,
      pr1645v2Lan3MCVlanInPQsH24PerformanceSysUpTime
         TimeTicks,
      pr1645v2Lan3MCVlanInPQsH24PerformanceTotPkts
         Counter64,
      pr1645v2Lan3MCVlanInPQsH24PerformanceDirTxPkts
         Counter64,
      pr1645v2Lan3MCVlanInPQsH24PerformanceQdPkts
         Counter64,
      pr1645v2Lan3MCVlanInPQsH24PerformanceDropPkts
         Counter64,
      pr1645v2Lan3MCVlanInPQsH24PerformanceRDropPkts
         Counter64,
      pr1645v2Lan3MCVlanInPQsH24PerformanceCirTxPkts
         Counter64,
      pr1645v2Lan3MCVlanInPQsH24PerformanceEirTxPkts
         Counter64,
      pr1645v2Lan3MCVlanInPQsH24PerformanceViolTxPkts
         Counter64,
      pr1645v2Lan3MCVlanInPQsH24PerformanceTotOcts
         Counter64,
      pr1645v2Lan3MCVlanInPQsH24PerformanceDirTxOcts
         Counter64,
      pr1645v2Lan3MCVlanInPQsH24PerformanceQdOcts
         Counter64,
      pr1645v2Lan3MCVlanInPQsH24PerformanceDropOcts
         Counter64,
      pr1645v2Lan3MCVlanInPQsH24PerformanceRDropOcts
         Counter64,
      pr1645v2Lan3MCVlanInPQsH24PerformanceCirTxOcts
         Counter64,
      pr1645v2Lan3MCVlanInPQsH24PerformanceEirTxOcts
         Counter64,
      pr1645v2Lan3MCVlanInPQsH24PerformanceViolTxOcts
         Counter64,
      pr1645v2Lan3MCVlanInPQsH24PerformanceBandwidth
         Integer32
      }

pr1645v2Lan3MCVlanInPQsH24PerformanceTableIx OBJECT-TYPE
   SYNTAX      TableIndex
   MAX-ACCESS  not-accessible
   STATUS      current
   DESCRIPTION
      ""
   ::= {pr1645v2Lan3MCVlanInPQsH24PerformanceEntry 11}

pr1645v2Lan3MCVlanInPQsH24PerformanceSysUpTime OBJECT-TYPE
   SYNTAX      TimeTicks
   MAX-ACCESS  read-only
   STATUS      current
   DESCRIPTION
      "Path: ethernet3.performance.vlan.inPriorityQueues.h24Performance.sysUpTime

       Time in centi-second."
   ::= {pr1645v2Lan3MCVlanInPQsH24PerformanceEntry 16777216}

pr1645v2Lan3MCVlanInPQsH24PerformanceTotPkts OBJECT-TYPE
   SYNTAX      Counter64
   MAX-ACCESS  read-only
   STATUS      current
   DESCRIPTION
      "Path: ethernet3.performance.vlan.inPriorityQueues.h24Performance.totalPkts

       64 bit unsigned wrappable counter."
   ::= {pr1645v2Lan3MCVlanInPQsH24PerformanceEntry 234881024}

pr1645v2Lan3MCVlanInPQsH24PerformanceDirTxPkts OBJECT-TYPE
   SYNTAX      Counter64
   MAX-ACCESS  read-only
   STATUS      current
   DESCRIPTION
      "Path: ethernet3.performance.vlan.inPriorityQueues.h24Performance.directTxPkts

       64 bit unsigned wrappable counter."
   ::= {pr1645v2Lan3MCVlanInPQsH24PerformanceEntry 33554432}

pr1645v2Lan3MCVlanInPQsH24PerformanceQdPkts OBJECT-TYPE
   SYNTAX      Counter64
   MAX-ACCESS  read-only
   STATUS      current
   DESCRIPTION
      "Path: ethernet3.performance.vlan.inPriorityQueues.h24Performance.queuedPkts

       64 bit unsigned wrappable counter."
   ::= {pr1645v2Lan3MCVlanInPQsH24PerformanceEntry 50331648}

pr1645v2Lan3MCVlanInPQsH24PerformanceDropPkts OBJECT-TYPE
   SYNTAX      Counter64
   MAX-ACCESS  read-only
   STATUS      current
   DESCRIPTION
      "Path: ethernet3.performance.vlan.inPriorityQueues.h24Performance.droppedPkts

       64 bit unsigned wrappable counter."
   ::= {pr1645v2Lan3MCVlanInPQsH24PerformanceEntry 67108864}

pr1645v2Lan3MCVlanInPQsH24PerformanceRDropPkts OBJECT-TYPE
   SYNTAX      Counter64
   MAX-ACCESS  read-only
   STATUS      current
   DESCRIPTION
      "Path: ethernet3.performance.vlan.inPriorityQueues.h24Performance.redDroppedPkts

       64 bit unsigned wrappable counter."
   ::= {pr1645v2Lan3MCVlanInPQsH24PerformanceEntry 201326592}

pr1645v2Lan3MCVlanInPQsH24PerformanceCirTxPkts OBJECT-TYPE
   SYNTAX      Counter64
   MAX-ACCESS  read-only
   STATUS      current
   DESCRIPTION
      "Path: ethernet3.performance.vlan.inPriorityQueues.h24Performance.cirTxPkts

       64 bit unsigned wrappable counter."
   ::= {pr1645v2Lan3MCVlanInPQsH24PerformanceEntry 83886080}

pr1645v2Lan3MCVlanInPQsH24PerformanceEirTxPkts OBJECT-TYPE
   SYNTAX      Counter64
   MAX-ACCESS  read-only
   STATUS      current
   DESCRIPTION
      "Path: ethernet3.performance.vlan.inPriorityQueues.h24Performance.eirTxPkts

       64 bit unsigned wrappable counter."
   ::= {pr1645v2Lan3MCVlanInPQsH24PerformanceEntry 100663296}

pr1645v2Lan3MCVlanInPQsH24PerformanceViolTxPkts OBJECT-TYPE
   SYNTAX      Counter64
   MAX-ACCESS  read-only
   STATUS      current
   DESCRIPTION
      "Path: ethernet3.performance.vlan.inPriorityQueues.h24Performance.violateTxPkts

       64 bit unsigned wrappable counter."
   ::= {pr1645v2Lan3MCVlanInPQsH24PerformanceEntry 301989888}

pr1645v2Lan3MCVlanInPQsH24PerformanceTotOcts OBJECT-TYPE
   SYNTAX      Counter64
   MAX-ACCESS  read-only
   STATUS      current
   DESCRIPTION
      "Path: ethernet3.performance.vlan.inPriorityQueues.h24Performance.totalOctets

       64 bit unsigned wrappable counter."
   ::= {pr1645v2Lan3MCVlanInPQsH24PerformanceEntry 251658240}

pr1645v2Lan3MCVlanInPQsH24PerformanceDirTxOcts OBJECT-TYPE
   SYNTAX      Counter64
   MAX-ACCESS  read-only
   STATUS      current
   DESCRIPTION
      "Path: ethernet3.performance.vlan.inPriorityQueues.h24Performance.directTxOctets

       64 bit unsigned wrappable counter."
   ::= {pr1645v2Lan3MCVlanInPQsH24PerformanceEntry 117440512}

pr1645v2Lan3MCVlanInPQsH24PerformanceQdOcts OBJECT-TYPE
   SYNTAX      Counter64
   MAX-ACCESS  read-only
   STATUS      current
   DESCRIPTION
      "Path: ethernet3.performance.vlan.inPriorityQueues.h24Performance.queuedOctets

       64 bit unsigned wrappable counter."
   ::= {pr1645v2Lan3MCVlanInPQsH24PerformanceEntry 134217728}

pr1645v2Lan3MCVlanInPQsH24PerformanceDropOcts OBJECT-TYPE
   SYNTAX      Counter64
   MAX-ACCESS  read-only
   STATUS      current
   DESCRIPTION
      "Path: ethernet3.performance.vlan.inPriorityQueues.h24Performance.droppedOctets

       64 bit unsigned wrappable counter."
   ::= {pr1645v2Lan3MCVlanInPQsH24PerformanceEntry 150994944}

pr1645v2Lan3MCVlanInPQsH24PerformanceRDropOcts OBJECT-TYPE
   SYNTAX      Counter64
   MAX-ACCESS  read-only
   STATUS      current
   DESCRIPTION
      "Path: ethernet3.performance.vlan.inPriorityQueues.h24Performance.redDroppedOctets

       64 bit unsigned wrappable counter."
   ::= {pr1645v2Lan3MCVlanInPQsH24PerformanceEntry 218103808}

pr1645v2Lan3MCVlanInPQsH24PerformanceCirTxOcts OBJECT-TYPE
   SYNTAX      Counter64
   MAX-ACCESS  read-only
   STATUS      current
   DESCRIPTION
      "Path: ethernet3.performance.vlan.inPriorityQueues.h24Performance.cirTxOctets

       64 bit unsigned wrappable counter."
   ::= {pr1645v2Lan3MCVlanInPQsH24PerformanceEntry 167772160}

pr1645v2Lan3MCVlanInPQsH24PerformanceEirTxOcts OBJECT-TYPE
   SYNTAX      Counter64
   MAX-ACCESS  read-only
   STATUS      current
   DESCRIPTION
      "Path: ethernet3.performance.vlan.inPriorityQueues.h24Performance.eirTxOctets

       64 bit unsigned wrappable counter."
   ::= {pr1645v2Lan3MCVlanInPQsH24PerformanceEntry 184549376}

pr1645v2Lan3MCVlanInPQsH24PerformanceViolTxOcts OBJECT-TYPE
   SYNTAX      Counter64
   MAX-ACCESS  read-only
   STATUS      current
   DESCRIPTION
      "Path: ethernet3.performance.vlan.inPriorityQueues.h24Performance.violateTxOctets

       64 bit unsigned wrappable counter."
   ::= {pr1645v2Lan3MCVlanInPQsH24PerformanceEntry 318767104}

pr1645v2Lan3MCVlanInPQsH24PerformanceBandwidth OBJECT-TYPE
   SYNTAX      Integer32
   MAX-ACCESS  read-only
   STATUS      current
   DESCRIPTION
      "Path: ethernet3.performance.vlan.inPriorityQueues.h24Performance.bandwidth

       unit name = bps
       formula = 8 * ; 8 /"
   ::= {pr1645v2Lan3MCVlanInPQsH24PerformanceEntry 268435456}

pr1645v2Lan3MCVlanInPQsD7Performance OBJECT-TYPE
   SYNTAX      SEQUENCE OF Pr1645v2Lan3MCVlanInPQsD7PerformanceEntry
   MAX-ACCESS  not-accessible
   STATUS      current
   DESCRIPTION
      ""
   ::= {pr1645v2Lan3MCVlan 101122048}

pr1645v2Lan3MCVlanInPQsD7PerformanceEntry OBJECT-TYPE
   SYNTAX      Pr1645v2Lan3MCVlanInPQsD7PerformanceEntry
   MAX-ACCESS  not-accessible
   STATUS      current
   DESCRIPTION
      ""
   INDEX      { pr1645v2Lan3MCVlanTableIx,
                pr1645v2Lan3MCVlanInPQsTableIx,
                pr1645v2Lan3MCVlanInPQsD7PerformanceTableIx }
   ::= {pr1645v2Lan3MCVlanInPQsD7Performance 1}

Pr1645v2Lan3MCVlanInPQsD7PerformanceEntry ::=
   SEQUENCE
      {
      pr1645v2Lan3MCVlanInPQsD7PerformanceTableIx
         TableIndex,
      pr1645v2Lan3MCVlanInPQsD7PerformanceSysUpTime
         TimeTicks,
      pr1645v2Lan3MCVlanInPQsD7PerformanceTotPkts
         Counter64,
      pr1645v2Lan3MCVlanInPQsD7PerformanceDirTxPkts
         Counter64,
      pr1645v2Lan3MCVlanInPQsD7PerformanceQdPkts
         Counter64,
      pr1645v2Lan3MCVlanInPQsD7PerformanceDropPkts
         Counter64,
      pr1645v2Lan3MCVlanInPQsD7PerformanceRDropPkts
         Counter64,
      pr1645v2Lan3MCVlanInPQsD7PerformanceCirTxPkts
         Counter64,
      pr1645v2Lan3MCVlanInPQsD7PerformanceEirTxPkts
         Counter64,
      pr1645v2Lan3MCVlanInPQsD7PerformanceViolTxPkts
         Counter64,
      pr1645v2Lan3MCVlanInPQsD7PerformanceTotOcts
         Counter64,
      pr1645v2Lan3MCVlanInPQsD7PerformanceDirTxOcts
         Counter64,
      pr1645v2Lan3MCVlanInPQsD7PerformanceQdOcts
         Counter64,
      pr1645v2Lan3MCVlanInPQsD7PerformanceDropOcts
         Counter64,
      pr1645v2Lan3MCVlanInPQsD7PerformanceRDropOcts
         Counter64,
      pr1645v2Lan3MCVlanInPQsD7PerformanceCirTxOcts
         Counter64,
      pr1645v2Lan3MCVlanInPQsD7PerformanceEirTxOcts
         Counter64,
      pr1645v2Lan3MCVlanInPQsD7PerformanceViolTxOcts
         Counter64,
      pr1645v2Lan3MCVlanInPQsD7PerformanceBandwidth
         Integer32
      }

pr1645v2Lan3MCVlanInPQsD7PerformanceTableIx OBJECT-TYPE
   SYNTAX      TableIndex
   MAX-ACCESS  not-accessible
   STATUS      current
   DESCRIPTION
      ""
   ::= {pr1645v2Lan3MCVlanInPQsD7PerformanceEntry 11}

pr1645v2Lan3MCVlanInPQsD7PerformanceSysUpTime OBJECT-TYPE
   SYNTAX      TimeTicks
   MAX-ACCESS  read-only
   STATUS      current
   DESCRIPTION
      "Path: ethernet3.performance.vlan.inPriorityQueues.d7Performance.sysUpTime

       Time in centi-second."
   ::= {pr1645v2Lan3MCVlanInPQsD7PerformanceEntry 16777216}

pr1645v2Lan3MCVlanInPQsD7PerformanceTotPkts OBJECT-TYPE
   SYNTAX      Counter64
   MAX-ACCESS  read-only
   STATUS      current
   DESCRIPTION
      "Path: ethernet3.performance.vlan.inPriorityQueues.d7Performance.totalPkts

       64 bit unsigned wrappable counter."
   ::= {pr1645v2Lan3MCVlanInPQsD7PerformanceEntry 234881024}

pr1645v2Lan3MCVlanInPQsD7PerformanceDirTxPkts OBJECT-TYPE
   SYNTAX      Counter64
   MAX-ACCESS  read-only
   STATUS      current
   DESCRIPTION
      "Path: ethernet3.performance.vlan.inPriorityQueues.d7Performance.directTxPkts

       64 bit unsigned wrappable counter."
   ::= {pr1645v2Lan3MCVlanInPQsD7PerformanceEntry 33554432}

pr1645v2Lan3MCVlanInPQsD7PerformanceQdPkts OBJECT-TYPE
   SYNTAX      Counter64
   MAX-ACCESS  read-only
   STATUS      current
   DESCRIPTION
      "Path: ethernet3.performance.vlan.inPriorityQueues.d7Performance.queuedPkts

       64 bit unsigned wrappable counter."
   ::= {pr1645v2Lan3MCVlanInPQsD7PerformanceEntry 50331648}

pr1645v2Lan3MCVlanInPQsD7PerformanceDropPkts OBJECT-TYPE
   SYNTAX      Counter64
   MAX-ACCESS  read-only
   STATUS      current
   DESCRIPTION
      "Path: ethernet3.performance.vlan.inPriorityQueues.d7Performance.droppedPkts

       64 bit unsigned wrappable counter."
   ::= {pr1645v2Lan3MCVlanInPQsD7PerformanceEntry 67108864}

pr1645v2Lan3MCVlanInPQsD7PerformanceRDropPkts OBJECT-TYPE
   SYNTAX      Counter64
   MAX-ACCESS  read-only
   STATUS      current
   DESCRIPTION
      "Path: ethernet3.performance.vlan.inPriorityQueues.d7Performance.redDroppedPkts

       64 bit unsigned wrappable counter."
   ::= {pr1645v2Lan3MCVlanInPQsD7PerformanceEntry 201326592}

pr1645v2Lan3MCVlanInPQsD7PerformanceCirTxPkts OBJECT-TYPE
   SYNTAX      Counter64
   MAX-ACCESS  read-only
   STATUS      current
   DESCRIPTION
      "Path: ethernet3.performance.vlan.inPriorityQueues.d7Performance.cirTxPkts

       64 bit unsigned wrappable counter."
   ::= {pr1645v2Lan3MCVlanInPQsD7PerformanceEntry 83886080}

pr1645v2Lan3MCVlanInPQsD7PerformanceEirTxPkts OBJECT-TYPE
   SYNTAX      Counter64
   MAX-ACCESS  read-only
   STATUS      current
   DESCRIPTION
      "Path: ethernet3.performance.vlan.inPriorityQueues.d7Performance.eirTxPkts

       64 bit unsigned wrappable counter."
   ::= {pr1645v2Lan3MCVlanInPQsD7PerformanceEntry 100663296}

pr1645v2Lan3MCVlanInPQsD7PerformanceViolTxPkts OBJECT-TYPE
   SYNTAX      Counter64
   MAX-ACCESS  read-only
   STATUS      current
   DESCRIPTION
      "Path: ethernet3.performance.vlan.inPriorityQueues.d7Performance.violateTxPkts

       64 bit unsigned wrappable counter."
   ::= {pr1645v2Lan3MCVlanInPQsD7PerformanceEntry 301989888}

pr1645v2Lan3MCVlanInPQsD7PerformanceTotOcts OBJECT-TYPE
   SYNTAX      Counter64
   MAX-ACCESS  read-only
   STATUS      current
   DESCRIPTION
      "Path: ethernet3.performance.vlan.inPriorityQueues.d7Performance.totalOctets

       64 bit unsigned wrappable counter."
   ::= {pr1645v2Lan3MCVlanInPQsD7PerformanceEntry 251658240}

pr1645v2Lan3MCVlanInPQsD7PerformanceDirTxOcts OBJECT-TYPE
   SYNTAX      Counter64
   MAX-ACCESS  read-only
   STATUS      current
   DESCRIPTION
      "Path: ethernet3.performance.vlan.inPriorityQueues.d7Performance.directTxOctets

       64 bit unsigned wrappable counter."
   ::= {pr1645v2Lan3MCVlanInPQsD7PerformanceEntry 117440512}

pr1645v2Lan3MCVlanInPQsD7PerformanceQdOcts OBJECT-TYPE
   SYNTAX      Counter64
   MAX-ACCESS  read-only
   STATUS      current
   DESCRIPTION
      "Path: ethernet3.performance.vlan.inPriorityQueues.d7Performance.queuedOctets

       64 bit unsigned wrappable counter."
   ::= {pr1645v2Lan3MCVlanInPQsD7PerformanceEntry 134217728}

pr1645v2Lan3MCVlanInPQsD7PerformanceDropOcts OBJECT-TYPE
   SYNTAX      Counter64
   MAX-ACCESS  read-only
   STATUS      current
   DESCRIPTION
      "Path: ethernet3.performance.vlan.inPriorityQueues.d7Performance.droppedOctets

       64 bit unsigned wrappable counter."
   ::= {pr1645v2Lan3MCVlanInPQsD7PerformanceEntry 150994944}

pr1645v2Lan3MCVlanInPQsD7PerformanceRDropOcts OBJECT-TYPE
   SYNTAX      Counter64
   MAX-ACCESS  read-only
   STATUS      current
   DESCRIPTION
      "Path: ethernet3.performance.vlan.inPriorityQueues.d7Performance.redDroppedOctets

       64 bit unsigned wrappable counter."
   ::= {pr1645v2Lan3MCVlanInPQsD7PerformanceEntry 218103808}

pr1645v2Lan3MCVlanInPQsD7PerformanceCirTxOcts OBJECT-TYPE
   SYNTAX      Counter64
   MAX-ACCESS  read-only
   STATUS      current
   DESCRIPTION
      "Path: ethernet3.performance.vlan.inPriorityQueues.d7Performance.cirTxOctets

       64 bit unsigned wrappable counter."
   ::= {pr1645v2Lan3MCVlanInPQsD7PerformanceEntry 167772160}

pr1645v2Lan3MCVlanInPQsD7PerformanceEirTxOcts OBJECT-TYPE
   SYNTAX      Counter64
   MAX-ACCESS  read-only
   STATUS      current
   DESCRIPTION
      "Path: ethernet3.performance.vlan.inPriorityQueues.d7Performance.eirTxOctets

       64 bit unsigned wrappable counter."
   ::= {pr1645v2Lan3MCVlanInPQsD7PerformanceEntry 184549376}

pr1645v2Lan3MCVlanInPQsD7PerformanceViolTxOcts OBJECT-TYPE
   SYNTAX      Counter64
   MAX-ACCESS  read-only
   STATUS      current
   DESCRIPTION
      "Path: ethernet3.performance.vlan.inPriorityQueues.d7Performance.violateTxOctets

       64 bit unsigned wrappable counter."
   ::= {pr1645v2Lan3MCVlanInPQsD7PerformanceEntry 318767104}

pr1645v2Lan3MCVlanInPQsD7PerformanceBandwidth OBJECT-TYPE
   SYNTAX      Integer32
   MAX-ACCESS  read-only
   STATUS      current
   DESCRIPTION
      "Path: ethernet3.performance.vlan.inPriorityQueues.d7Performance.bandwidth

       unit name = bps
       formula = 8 * ; 8 /"
   ::= {pr1645v2Lan3MCVlanInPQsD7PerformanceEntry 268435456}

pr1645v2Lan3MCVlanOutPQs OBJECT-TYPE
   SYNTAX      SEQUENCE OF Pr1645v2Lan3MCVlanOutPQsEntry
   MAX-ACCESS  not-accessible
   STATUS      current
   DESCRIPTION
      ""
   ::= {pr1645v2Lan3MCVlan 83886080}

pr1645v2Lan3MCVlanOutPQsEntry OBJECT-TYPE
   SYNTAX      Pr1645v2Lan3MCVlanOutPQsEntry
   MAX-ACCESS  not-accessible
   STATUS      current
   DESCRIPTION
      ""
   INDEX      { pr1645v2Lan3MCVlanTableIx,
                pr1645v2Lan3MCVlanOutPQsTableIx }
   ::= {pr1645v2Lan3MCVlanOutPQs 1}

Pr1645v2Lan3MCVlanOutPQsEntry ::=
   SEQUENCE
      {
      pr1645v2Lan3MCVlanOutPQsTableIx
         TableIndex,
      pr1645v2Lan3MCVlanOutPQsName
         INTEGER,
      pr1645v2Lan3MCVlanOutPQsLength
         Integer32,
      pr1645v2Lan3MCVlanOutPQsOctetLength
         Integer32,
      pr1645v2Lan3MCVlanOutPQsRedLength
         Integer32,
      pr1645v2Lan3MCVlanOutPQsPacketsTotal
         Counter64,
      pr1645v2Lan3MCVlanOutPQsPacketsDirectTx
         Counter64,
      pr1645v2Lan3MCVlanOutPQsPacketsQueued
         Counter64,
      pr1645v2Lan3MCVlanOutPQsPacketsDropped
         Counter64,
      pr1645v2Lan3MCVlanOutPQsPacketsRedDropped
         Counter64,
      pr1645v2Lan3MCVlanOutPQsPacketsCirTx
         Counter64,
      pr1645v2Lan3MCVlanOutPQsPacketsEirTx
         Counter64,
      pr1645v2Lan3MCVlanOutPQsPacketsViolateTx
         Counter64,
      pr1645v2Lan3MCVlanOutPQsOctetsTotal
         Counter64,
      pr1645v2Lan3MCVlanOutPQsOctetsDirectTx
         Counter64,
      pr1645v2Lan3MCVlanOutPQsOctetsQueued
         Counter64,
      pr1645v2Lan3MCVlanOutPQsOctetsDropped
         Counter64,
      pr1645v2Lan3MCVlanOutPQsOctetsRedDropped
         Counter64,
      pr1645v2Lan3MCVlanOutPQsOctetsCirTx
         Counter64,
      pr1645v2Lan3MCVlanOutPQsOctetsEirTx
         Counter64,
      pr1645v2Lan3MCVlanOutPQsOctetsViolateTx
         Counter64,
      pr1645v2Lan3MCVlanOutPQsOctetsBandwidth15sec
         Integer32,
      pr1645v2Lan3MCVlanOutPQsOctetsBandwidth30sec
         Integer32,
      pr1645v2Lan3MCVlanOutPQsOctetsBandwidth1min
         Integer32,
      pr1645v2Lan3MCVlanOutPQsOctetsBandwidth2min
         Integer32,
      pr1645v2Lan3MCVlanOutPQsOctetsBandwidth5min
         Integer32
      }

pr1645v2Lan3MCVlanOutPQsTableIx OBJECT-TYPE
   SYNTAX      TableIndex
   MAX-ACCESS  not-accessible
   STATUS      current
   DESCRIPTION
      ""
   ::= {pr1645v2Lan3MCVlanOutPQsEntry 11}

pr1645v2Lan3MCVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3MCVlanOutPQsEntry 16777216}

pr1645v2Lan3MCVlanOutPQsLength OBJECT-TYPE
   SYNTAX      Integer32
   MAX-ACCESS  read-only
   STATUS      current
   DESCRIPTION
      "Path: ethernet3.performance.vlan.outPriorityQueues.length"
   ::= {pr1645v2Lan3MCVlanOutPQsEntry 33554432}

pr1645v2Lan3MCVlanOutPQsOctetLength OBJECT-TYPE
   SYNTAX      Integer32
   MAX-ACCESS  read-only
   STATUS      current
   DESCRIPTION
      "Path: ethernet3.performance.vlan.outPriorityQueues.octetLength"
   ::= {pr1645v2Lan3MCVlanOutPQsEntry 150994944}

pr1645v2Lan3MCVlanOutPQsRedLength OBJECT-TYPE
   SYNTAX      Integer32
   MAX-ACCESS  read-only
   STATUS      current
   DESCRIPTION
      "Path: ethernet3.performance.vlan.outPriorityQueues.redLength"
   ::= {pr1645v2Lan3MCVlanOutPQsEntry 134217728}

pr1645v2Lan3MCVlanOutPQsPacketsTotal OBJECT-TYPE
   SYNTAX      Counter64
   MAX-ACCESS  read-only
   STATUS      current
   DESCRIPTION
      "Path: ethernet3.performance.vlan.outPriorityQueues.packets.total

       64 bit unsigned wrappable counter."
   ::= {pr1645v2Lan3MCVlanOutPQsEntry 50790400}

pr1645v2Lan3MCVlanOutPQsPacketsDirectTx OBJECT-TYPE
   SYNTAX      Counter64
   MAX-ACCESS  read-only
   STATUS      current
   DESCRIPTION
      "Path: ethernet3.performance.vlan.outPriorityQueues.packets.directTx

       64 bit unsigned wrappable counter."
   ::= {pr1645v2Lan3MCVlanOutPQsEntry 50397184}

pr1645v2Lan3MCVlanOutPQsPacketsQueued OBJECT-TYPE
   SYNTAX      Counter64
   MAX-ACCESS  read-only
   STATUS      current
   DESCRIPTION
      "Path: ethernet3.performance.vlan.outPriorityQueues.packets.queued

       64 bit unsigned wrappable counter."
   ::= {pr1645v2Lan3MCVlanOutPQsEntry 50462720}

pr1645v2Lan3MCVlanOutPQsPacketsDropped OBJECT-TYPE
   SYNTAX      Counter64
   MAX-ACCESS  read-only
   STATUS      current
   DESCRIPTION
      "Path: ethernet3.performance.vlan.outPriorityQueues.packets.dropped

       64 bit unsigned wrappable counter."
   ::= {pr1645v2Lan3MCVlanOutPQsEntry 50528256}

pr1645v2Lan3MCVlanOutPQsPacketsRedDropped OBJECT-TYPE
   SYNTAX      Counter64
   MAX-ACCESS  read-only
   STATUS      current
   DESCRIPTION
      "Path: ethernet3.performance.vlan.outPriorityQueues.packets.redDropped

       64 bit unsigned wrappable counter."
   ::= {pr1645v2Lan3MCVlanOutPQsEntry 50724864}

pr1645v2Lan3MCVlanOutPQsPacketsCirTx OBJECT-TYPE
   SYNTAX      Counter64
   MAX-ACCESS  read-only
   STATUS      current
   DESCRIPTION
      "Path: ethernet3.performance.vlan.outPriorityQueues.packets.cirTx

       64 bit unsigned wrappable counter."
   ::= {pr1645v2Lan3MCVlanOutPQsEntry 50593792}

pr1645v2Lan3MCVlanOutPQsPacketsEirTx OBJECT-TYPE
   SYNTAX      Counter64
   MAX-ACCESS  read-only
   STATUS      current
   DESCRIPTION
      "Path: ethernet3.performance.vlan.outPriorityQueues.packets.eirTx

       64 bit unsigned wrappable counter."
   ::= {pr1645v2Lan3MCVlanOutPQsEntry 50659328}

pr1645v2Lan3MCVlanOutPQsPacketsViolateTx OBJECT-TYPE
   SYNTAX      Counter64
   MAX-ACCESS  read-only
   STATUS      current
   DESCRIPTION
      "Path: ethernet3.performance.vlan.outPriorityQueues.packets.violateTx

       64 bit unsigned wrappable counter."
   ::= {pr1645v2Lan3MCVlanOutPQsEntry 50855936}

pr1645v2Lan3MCVlanOutPQsOctetsTotal OBJECT-TYPE
   SYNTAX      Counter64
   MAX-ACCESS  read-only
   STATUS      current
   DESCRIPTION
      "Path: ethernet3.performance.vlan.outPriorityQueues.octets.total

       64 bit unsigned wrappable counter."
   ::= {pr1645v2Lan3MCVlanOutPQsEntry 67567616}

pr1645v2Lan3MCVlanOutPQsOctetsDirectTx OBJECT-TYPE
   SYNTAX      Counter64
   MAX-ACCESS  read-only
   STATUS      current
   DESCRIPTION
      "Path: ethernet3.performance.vlan.outPriorityQueues.octets.directTx

       64 bit unsigned wrappable counter."
   ::= {pr1645v2Lan3MCVlanOutPQsEntry 67174400}

pr1645v2Lan3MCVlanOutPQsOctetsQueued OBJECT-TYPE
   SYNTAX      Counter64
   MAX-ACCESS  read-only
   STATUS      current
   DESCRIPTION
      "Path: ethernet3.performance.vlan.outPriorityQueues.octets.queued

       64 bit unsigned wrappable counter."
   ::= {pr1645v2Lan3MCVlanOutPQsEntry 67239936}

pr1645v2Lan3MCVlanOutPQsOctetsDropped OBJECT-TYPE
   SYNTAX      Counter64
   MAX-ACCESS  read-only
   STATUS      current
   DESCRIPTION
      "Path: ethernet3.performance.vlan.outPriorityQueues.octets.dropped

       64 bit unsigned wrappable counter."
   ::= {pr1645v2Lan3MCVlanOutPQsEntry 67305472}

pr1645v2Lan3MCVlanOutPQsOctetsRedDropped OBJECT-TYPE
   SYNTAX      Counter64
   MAX-ACCESS  read-only
   STATUS      current
   DESCRIPTION
      "Path: ethernet3.performance.vlan.outPriorityQueues.octets.redDropped

       64 bit unsigned wrappable counter."
   ::= {pr1645v2Lan3MCVlanOutPQsEntry 67502080}

pr1645v2Lan3MCVlanOutPQsOctetsCirTx OBJECT-TYPE
   SYNTAX      Counter64
   MAX-ACCESS  read-only
   STATUS      current
   DESCRIPTION
      "Path: ethernet3.performance.vlan.outPriorityQueues.octets.cirTx

       64 bit unsigned wrappable counter."
   ::= {pr1645v2Lan3MCVlanOutPQsEntry 67371008}

pr1645v2Lan3MCVlanOutPQsOctetsEirTx OBJECT-TYPE
   SYNTAX      Counter64
   MAX-ACCESS  read-only
   STATUS      current
   DESCRIPTION
      "Path: ethernet3.performance.vlan.outPriorityQueues.octets.eirTx

       64 bit unsigned wrappable counter."
   ::= {pr1645v2Lan3MCVlanOutPQsEntry 67436544}

pr1645v2Lan3MCVlanOutPQsOctetsViolateTx OBJECT-TYPE
   SYNTAX      Counter64
   MAX-ACCESS  read-only
   STATUS      current
   DESCRIPTION
      "Path: ethernet3.performance.vlan.outPriorityQueues.octets.violateTx

       64 bit unsigned wrappable counter."
   ::= {pr1645v2Lan3MCVlanOutPQsEntry 67633152}

pr1645v2Lan3MCVlanOutPQsOctetsBandwidth15sec OBJECT-TYPE
   SYNTAX      Integer32
   MAX-ACCESS  read-only
   STATUS      current
   DESCRIPTION
      "Path: ethernet3.performance.vlan.outPriorityQueues.octets.bandwidth.15sec

       unit name = bps
       formula = 8 * ; 8 /"
   ::= {pr1645v2Lan3MCVlanOutPQsEntry 70386944}

pr1645v2Lan3MCVlanOutPQsOctetsBandwidth30sec OBJECT-TYPE
   SYNTAX      Integer32
   MAX-ACCESS  read-only
   STATUS      current
   DESCRIPTION
      "Path: ethernet3.performance.vlan.outPriorityQueues.octets.bandwidth.30sec

       unit name = bps
       formula = 8 * ; 8 /"
   ::= {pr1645v2Lan3MCVlanOutPQsEntry 70388224}

pr1645v2Lan3MCVlanOutPQsOctetsBandwidth1min OBJECT-TYPE
   SYNTAX      Integer32
   MAX-ACCESS  read-only
   STATUS      current
   DESCRIPTION
      "Path: ethernet3.performance.vlan.outPriorityQueues.octets.bandwidth.1min

       unit name = bps
       formula = 8 * ; 8 /"
   ::= {pr1645v2Lan3MCVlanOutPQsEntry 70390784}

pr1645v2Lan3MCVlanOutPQsOctetsBandwidth2min OBJECT-TYPE
   SYNTAX      Integer32
   MAX-ACCESS  read-only
   STATUS      current
   DESCRIPTION
      "Path: ethernet3.performance.vlan.outPriorityQueues.octets.bandwidth.2min

       unit name = bps
       formula = 8 * ; 8 /"
   ::= {pr1645v2Lan3MCVlanOutPQsEntry 70395904}

pr1645v2Lan3MCVlanOutPQsOctetsBandwidth5min OBJECT-TYPE
   SYNTAX      Integer32
   MAX-ACCESS  read-only
   STATUS      current
   DESCRIPTION
      "Path: ethernet3.performance.vlan.outPriorityQueues.octets.bandwidth.5min

       unit name = bps
       formula = 8 * ; 8 /"
   ::= {pr1645v2Lan3MCVlanOutPQsEntry 70411264}

pr1645v2Lan3MCVlanOutPQsH2Performance OBJECT-TYPE
   SYNTAX      SEQUENCE OF Pr1645v2Lan3MCVlanOutPQsH2PerformanceEntry
   MAX-ACCESS  not-accessible
   STATUS      current
   DESCRIPTION
      ""
   ::= {pr1645v2Lan3MCVlan 84213760}

pr1645v2Lan3MCVlanOutPQsH2PerformanceEntry OBJECT-TYPE
   SYNTAX      Pr1645v2Lan3MCVlanOutPQsH2PerformanceEntry
   MAX-ACCESS  not-accessible
   STATUS      current
   DESCRIPTION
      ""
   INDEX      { pr1645v2Lan3MCVlanTableIx,
                pr1645v2Lan3MCVlanOutPQsTableIx,
                pr1645v2Lan3MCVlanOutPQsH2PerformanceTableIx }
   ::= {pr1645v2Lan3MCVlanOutPQsH2Performance 1}

Pr1645v2Lan3MCVlanOutPQsH2PerformanceEntry ::=
   SEQUENCE
      {
      pr1645v2Lan3MCVlanOutPQsH2PerformanceTableIx
         TableIndex,
      pr1645v2Lan3MCVlanOutPQsH2PerformanceSysUpTime
         TimeTicks,
      pr1645v2Lan3MCVlanOutPQsH2PerformanceTotPkts
         Counter64,
      pr1645v2Lan3MCVlanOutPQsH2PerformanceDirTxPkts
         Counter64,
      pr1645v2Lan3MCVlanOutPQsH2PerformanceQdPkts
         Counter64,
      pr1645v2Lan3MCVlanOutPQsH2PerformanceDropPkts
         Counter64,
      pr1645v2Lan3MCVlanOutPQsH2PerformanceRDropPkts
         Counter64,
      pr1645v2Lan3MCVlanOutPQsH2PerformanceCirTxPkts
         Counter64,
      pr1645v2Lan3MCVlanOutPQsH2PerformanceEirTxPkts
         Counter64,
      pr1645v2Lan3MCVlanOutPQsH2PerformanceViolTxPkts
         Counter64,
      pr1645v2Lan3MCVlanOutPQsH2PerformanceTotOcts
         Counter64,
      pr1645v2Lan3MCVlanOutPQsH2PerformanceDirTxOcts
         Counter64,
      pr1645v2Lan3MCVlanOutPQsH2PerformanceQdOcts
         Counter64,
      pr1645v2Lan3MCVlanOutPQsH2PerformanceDropOcts
         Counter64,
      pr1645v2Lan3MCVlanOutPQsH2PerformanceRDropOcts
         Counter64,
      pr1645v2Lan3MCVlanOutPQsH2PerformanceCirTxOcts
         Counter64,
      pr1645v2Lan3MCVlanOutPQsH2PerformanceEirTxOcts
         Counter64,
      pr1645v2Lan3MCVlanOutPQsH2PerformanceViolTxOcts
         Counter64,
      pr1645v2Lan3MCVlanOutPQsH2PerformanceBandwidth
         Integer32
      }

pr1645v2Lan3MCVlanOutPQsH2PerformanceTableIx OBJECT-TYPE
   SYNTAX      TableIndex
   MAX-ACCESS  not-accessible
   STATUS      current
   DESCRIPTION
      ""
   ::= {pr1645v2Lan3MCVlanOutPQsH2PerformanceEntry 11}

pr1645v2Lan3MCVlanOutPQsH2PerformanceSysUpTime OBJECT-TYPE
   SYNTAX      TimeTicks
   MAX-ACCESS  read-only
   STATUS      current
   DESCRIPTION
      "Path: ethernet3.performance.vlan.outPriorityQueues.h2Performance.sysUpTime

       Time in centi-second."
   ::= {pr1645v2Lan3MCVlanOutPQsH2PerformanceEntry 16777216}

pr1645v2Lan3MCVlanOutPQsH2PerformanceTotPkts OBJECT-TYPE
   SYNTAX      Counter64
   MAX-ACCESS  read-only
   STATUS      current
   DESCRIPTION
      "Path: ethernet3.performance.vlan.outPriorityQueues.h2Performance.totalPkts

       64 bit unsigned wrappable counter."
   ::= {pr1645v2Lan3MCVlanOutPQsH2PerformanceEntry 234881024}

pr1645v2Lan3MCVlanOutPQsH2PerformanceDirTxPkts OBJECT-TYPE
   SYNTAX      Counter64
   MAX-ACCESS  read-only
   STATUS      current
   DESCRIPTION
      "Path: ethernet3.performance.vlan.outPriorityQueues.h2Performance.directTxPkts

       64 bit unsigned wrappable counter."
   ::= {pr1645v2Lan3MCVlanOutPQsH2PerformanceEntry 33554432}

pr1645v2Lan3MCVlanOutPQsH2PerformanceQdPkts OBJECT-TYPE
   SYNTAX      Counter64
   MAX-ACCESS  read-only
   STATUS      current
   DESCRIPTION
      "Path: ethernet3.performance.vlan.outPriorityQueues.h2Performance.queuedPkts

       64 bit unsigned wrappable counter."
   ::= {pr1645v2Lan3MCVlanOutPQsH2PerformanceEntry 50331648}

pr1645v2Lan3MCVlanOutPQsH2PerformanceDropPkts OBJECT-TYPE
   SYNTAX      Counter64
   MAX-ACCESS  read-only
   STATUS      current
   DESCRIPTION
      "Path: ethernet3.performance.vlan.outPriorityQueues.h2Performance.droppedPkts

       64 bit unsigned wrappable counter."
   ::= {pr1645v2Lan3MCVlanOutPQsH2PerformanceEntry 67108864}

pr1645v2Lan3MCVlanOutPQsH2PerformanceRDropPkts OBJECT-TYPE
   SYNTAX      Counter64
   MAX-ACCESS  read-only
   STATUS      current
   DESCRIPTION
      "Path: ethernet3.performance.vlan.outPriorityQueues.h2Performance.redDroppedPkts

       64 bit unsigned wrappable counter."
   ::= {pr1645v2Lan3MCVlanOutPQsH2PerformanceEntry 201326592}

pr1645v2Lan3MCVlanOutPQsH2PerformanceCirTxPkts OBJECT-TYPE
   SYNTAX      Counter64
   MAX-ACCESS  read-only
   STATUS      current
   DESCRIPTION
      "Path: ethernet3.performance.vlan.outPriorityQueues.h2Performance.cirTxPkts

       64 bit unsigned wrappable counter."
   ::= {pr1645v2Lan3MCVlanOutPQsH2PerformanceEntry 83886080}

pr1645v2Lan3MCVlanOutPQsH2PerformanceEirTxPkts OBJECT-TYPE
   SYNTAX      Counter64
   MAX-ACCESS  read-only
   STATUS      current
   DESCRIPTION
      "Path: ethernet3.performance.vlan.outPriorityQueues.h2Performance.eirTxPkts

       64 bit unsigned wrappable counter."
   ::= {pr1645v2Lan3MCVlanOutPQsH2PerformanceEntry 100663296}

pr1645v2Lan3MCVlanOutPQsH2PerformanceViolTxPkts OBJECT-TYPE
   SYNTAX      Counter64
   MAX-ACCESS  read-only
   STATUS      current
   DESCRIPTION
      "Path: ethernet3.performance.vlan.outPriorityQueues.h2Performance.violateTxPkts

       64 bit unsigned wrappable counter."
   ::= {pr1645v2Lan3MCVlanOutPQsH2PerformanceEntry 301989888}

pr1645v2Lan3MCVlanOutPQsH2PerformanceTotOcts OBJECT-TYPE
   SYNTAX      Counter64
   MAX-ACCESS  read-only
   STATUS      current
   DESCRIPTION
      "Path: ethernet3.performance.vlan.outPriorityQueues.h2Performance.totalOctets

       64 bit unsigned wrappable counter."
   ::= {pr1645v2Lan3MCVlanOutPQsH2PerformanceEntry 251658240}

pr1645v2Lan3MCVlanOutPQsH2PerformanceDirTxOcts OBJECT-TYPE
   SYNTAX      Counter64
   MAX-ACCESS  read-only
   STATUS      current
   DESCRIPTION
      "Path: ethernet3.performance.vlan.outPriorityQueues.h2Performance.directTxOctets

       64 bit unsigned wrappable counter."
   ::= {pr1645v2Lan3MCVlanOutPQsH2PerformanceEntry 117440512}

pr1645v2Lan3MCVlanOutPQsH2PerformanceQdOcts OBJECT-TYPE
   SYNTAX      Counter64
   MAX-ACCESS  read-only
   STATUS      current
   DESCRIPTION
      "Path: ethernet3.performance.vlan.outPriorityQueues.h2Performance.queuedOctets

       64 bit unsigned wrappable counter."
   ::= {pr1645v2Lan3MCVlanOutPQsH2PerformanceEntry 134217728}

pr1645v2Lan3MCVlanOutPQsH2PerformanceDropOcts OBJECT-TYPE
   SYNTAX      Counter64
   MAX-ACCESS  read-only
   STATUS      current
   DESCRIPTION
      "Path: ethernet3.performance.vlan.outPriorityQueues.h2Performance.droppedOctets

       64 bit unsigned wrappable counter."
   ::= {pr1645v2Lan3MCVlanOutPQsH2PerformanceEntry 150994944}

pr1645v2Lan3MCVlanOutPQsH2PerformanceRDropOcts OBJECT-TYPE
   SYNTAX      Counter64
   MAX-ACCESS  read-only
   STATUS      current
   DESCRIPTION
      "Path: ethernet3.performance.vlan.outPriorityQueues.h2Performance.redDroppedOctets

       64 bit unsigned wrappable counter."
   ::= {pr1645v2Lan3MCVlanOutPQsH2PerformanceEntry 218103808}

pr1645v2Lan3MCVlanOutPQsH2PerformanceCirTxOcts OBJECT-TYPE
   SYNTAX      Counter64
   MAX-ACCESS  read-only
   STATUS      current
   DESCRIPTION
      "Path: ethernet3.performance.vlan.outPriorityQueues.h2Performance.cirTxOctets

       64 bit unsigned wrappable counter."
   ::= {pr1645v2Lan3MCVlanOutPQsH2PerformanceEntry 167772160}

pr1645v2Lan3MCVlanOutPQsH2PerformanceEirTxOcts OBJECT-TYPE
   SYNTAX      Counter64
   MAX-ACCESS  read-only
   STATUS      current
   DESCRIPTION
      "Path: ethernet3.performance.vlan.outPriorityQueues.h2Performance.eirTxOctets

       64 bit unsigned wrappable counter."
   ::= {pr1645v2Lan3MCVlanOutPQsH2PerformanceEntry 184549376}

pr1645v2Lan3MCVlanOutPQsH2PerformanceViolTxOcts OBJECT-TYPE
   SYNTAX      Counter64
   MAX-ACCESS  read-only
   STATUS      current
   DESCRIPTION
      "Path: ethernet3.performance.vlan.outPriorityQueues.h2Performance.violateTxOctets

       64 bit unsigned wrappable counter."
   ::= {pr1645v2Lan3MCVlanOutPQsH2PerformanceEntry 318767104}

pr1645v2Lan3MCVlanOutPQsH2PerformanceBandwidth OBJECT-TYPE
   SYNTAX      Integer32
   MAX-ACCESS  read-only
   STATUS      current
   DESCRIPTION
      "Path: ethernet3.performance.vlan.outPriorityQueues.h2Performance.bandwidth

       unit name = bps
       formula = 8 * ; 8 /"
   ::= {pr1645v2Lan3MCVlanOutPQsH2PerformanceEntry 268435456}

pr1645v2Lan3MCVlanOutPQsH24Performance OBJECT-TYPE
   SYNTAX      SEQUENCE OF Pr1645v2Lan3MCVlanOutPQsH24PerformanceEntry
   MAX-ACCESS  not-accessible
   STATUS      current
   DESCRIPTION
      ""
   ::= {pr1645v2Lan3MCVlan 84279296}

pr1645v2Lan3MCVlanOutPQsH24PerformanceEntry OBJECT-TYPE
   SYNTAX      Pr1645v2Lan3MCVlanOutPQsH24PerformanceEntry
   MAX-ACCESS  not-accessible
   STATUS      current
   DESCRIPTION
      ""
   INDEX      { pr1645v2Lan3MCVlanTableIx,
                pr1645v2Lan3MCVlanOutPQsTableIx,
                pr1645v2Lan3MCVlanOutPQsH24PerformanceTableIx }
   ::= {pr1645v2Lan3MCVlanOutPQsH24Performance 1}

Pr1645v2Lan3MCVlanOutPQsH24PerformanceEntry ::=
   SEQUENCE
      {
      pr1645v2Lan3MCVlanOutPQsH24PerformanceTableIx
         TableIndex,
      pr1645v2Lan3MCVlanOutPQsH24PerformanceSysUpTime
         TimeTicks,
      pr1645v2Lan3MCVlanOutPQsH24PerformanceTotPkts
         Counter64,
      pr1645v2Lan3MCVlanOutPQsH24PerformanceDirTxPkts
         Counter64,
      pr1645v2Lan3MCVlanOutPQsH24PerformanceQdPkts
         Counter64,
      pr1645v2Lan3MCVlanOutPQsH24PerformanceDropPkts
         Counter64,
      pr1645v2Lan3MCVlanOutPQsH24PerformanceRDropPkts
         Counter64,
      pr1645v2Lan3MCVlanOutPQsH24PerformanceCirTxPkts
         Counter64,
      pr1645v2Lan3MCVlanOutPQsH24PerformanceEirTxPkts
         Counter64,
      pr1645v2Lan3MCVlanOutPQsH24PerformanceViolTxPkts
         Counter64,
      pr1645v2Lan3MCVlanOutPQsH24PerformanceTotOcts
         Counter64,
      pr1645v2Lan3MCVlanOutPQsH24PerformanceDirTxOcts
         Counter64,
      pr1645v2Lan3MCVlanOutPQsH24PerformanceQdOcts
         Counter64,
      pr1645v2Lan3MCVlanOutPQsH24PerformanceDropOcts
         Counter64,
      pr1645v2Lan3MCVlanOutPQsH24PerformanceRDropOcts
         Counter64,
      pr1645v2Lan3MCVlanOutPQsH24PerformanceCirTxOcts
         Counter64,
      pr1645v2Lan3MCVlanOutPQsH24PerformanceEirTxOcts
         Counter64,
      pr1645v2Lan3MCVlanOutPQsH24PerformanceViolTxOcts
         Counter64,
      pr1645v2Lan3MCVlanOutPQsH24PerformanceBandwidth
         Integer32
      }

pr1645v2Lan3MCVlanOutPQsH24PerformanceTableIx OBJECT-TYPE
   SYNTAX      TableIndex
   MAX-ACCESS  not-accessible
   STATUS      current
   DESCRIPTION
      ""
   ::= {pr1645v2Lan3MCVlanOutPQsH24PerformanceEntry 11}

pr1645v2Lan3MCVlanOutPQsH24PerformanceSysUpTime OBJECT-TYPE
   SYNTAX      TimeTicks
   MAX-ACCESS  read-only
   STATUS      current
   DESCRIPTION
      "Path: ethernet3.performance.vlan.outPriorityQueues.h24Performance.sysUpTime

       Time in centi-second."
   ::= {pr1645v2Lan3MCVlanOutPQsH24PerformanceEntry 16777216}

pr1645v2Lan3MCVlanOutPQsH24PerformanceTotPkts OBJECT-TYPE
   SYNTAX      Counter64
   MAX-ACCESS  read-only
   STATUS      current
   DESCRIPTION
      "Path: ethernet3.performance.vlan.outPriorityQueues.h24Performance.totalPkts

       64 bit unsigned wrappable counter."
   ::= {pr1645v2Lan3MCVlanOutPQsH24PerformanceEntry 234881024}

pr1645v2Lan3MCVlanOutPQsH24PerformanceDirTxPkts OBJECT-TYPE
   SYNTAX      Counter64
   MAX-ACCESS  read-only
   STATUS      current
   DESCRIPTION
      "Path: ethernet3.performance.vlan.outPriorityQueues.h24Performance.directTxPkts

       64 bit unsigned wrappable counter."
   ::= {pr1645v2Lan3MCVlanOutPQsH24PerformanceEntry 33554432}

pr1645v2Lan3MCVlanOutPQsH24PerformanceQdPkts OBJECT-TYPE
   SYNTAX      Counter64
   MAX-ACCESS  read-only
   STATUS      current
   DESCRIPTION
      "Path: ethernet3.performance.vlan.outPriorityQueues.h24Performance.queuedPkts

       64 bit unsigned wrappable counter."
   ::= {pr1645v2Lan3MCVlanOutPQsH24PerformanceEntry 50331648}

pr1645v2Lan3MCVlanOutPQsH24PerformanceDropPkts OBJECT-TYPE
   SYNTAX      Counter64
   MAX-ACCESS  read-only
   STATUS      current
   DESCRIPTION
      "Path: ethernet3.performance.vlan.outPriorityQueues.h24Performance.droppedPkts

       64 bit unsigned wrappable counter."
   ::= {pr1645v2Lan3MCVlanOutPQsH24PerformanceEntry 67108864}

pr1645v2Lan3MCVlanOutPQsH24PerformanceRDropPkts OBJECT-TYPE
   SYNTAX      Counter64
   MAX-ACCESS  read-only
   STATUS      current
   DESCRIPTION
      "Path: ethernet3.performance.vlan.outPriorityQueues.h24Performance.redDroppedPkts

       64 bit unsigned wrappable counter."
   ::= {pr1645v2Lan3MCVlanOutPQsH24PerformanceEntry 201326592}

pr1645v2Lan3MCVlanOutPQsH24PerformanceCirTxPkts OBJECT-TYPE
   SYNTAX      Counter64
   MAX-ACCESS  read-only
   STATUS      current
   DESCRIPTION
      "Path: ethernet3.performance.vlan.outPriorityQueues.h24Performance.cirTxPkts

       64 bit unsigned wrappable counter."
   ::= {pr1645v2Lan3MCVlanOutPQsH24PerformanceEntry 83886080}

pr1645v2Lan3MCVlanOutPQsH24PerformanceEirTxPkts OBJECT-TYPE
   SYNTAX      Counter64
   MAX-ACCESS  read-only
   STATUS      current
   DESCRIPTION
      "Path: ethernet3.performance.vlan.outPriorityQueues.h24Performance.eirTxPkts

       64 bit unsigned wrappable counter."
   ::= {pr1645v2Lan3MCVlanOutPQsH24PerformanceEntry 100663296}

pr1645v2Lan3MCVlanOutPQsH24PerformanceViolTxPkts OBJECT-TYPE
   SYNTAX      Counter64
   MAX-ACCESS  read-only
   STATUS      current
   DESCRIPTION
      "Path: ethernet3.performance.vlan.outPriorityQueues.h24Performance.violateTxPkts

       64 bit unsigned wrappable counter."
   ::= {pr1645v2Lan3MCVlanOutPQsH24PerformanceEntry 301989888}

pr1645v2Lan3MCVlanOutPQsH24PerformanceTotOcts OBJECT-TYPE
   SYNTAX      Counter64
   MAX-ACCESS  read-only
   STATUS      current
   DESCRIPTION
      "Path: ethernet3.performance.vlan.outPriorityQueues.h24Performance.totalOctets

       64 bit unsigned wrappable counter."
   ::= {pr1645v2Lan3MCVlanOutPQsH24PerformanceEntry 251658240}

pr1645v2Lan3MCVlanOutPQsH24PerformanceDirTxOcts OBJECT-TYPE
   SYNTAX      Counter64
   MAX-ACCESS  read-only
   STATUS      current
   DESCRIPTION
      "Path: ethernet3.performance.vlan.outPriorityQueues.h24Performance.directTxOctets

       64 bit unsigned wrappable counter."
   ::= {pr1645v2Lan3MCVlanOutPQsH24PerformanceEntry 117440512}

pr1645v2Lan3MCVlanOutPQsH24PerformanceQdOcts OBJECT-TYPE
   SYNTAX      Counter64
   MAX-ACCESS  read-only
   STATUS      current
   DESCRIPTION
      "Path: ethernet3.performance.vlan.outPriorityQueues.h24Performance.queuedOctets

       64 bit unsigned wrappable counter."
   ::= {pr1645v2Lan3MCVlanOutPQsH24PerformanceEntry 134217728}

pr1645v2Lan3MCVlanOutPQsH24PerformanceDropOcts OBJECT-TYPE
   SYNTAX      Counter64
   MAX-ACCESS  read-only
   STATUS      current
   DESCRIPTION
      "Path: ethernet3.performance.vlan.outPriorityQueues.h24Performance.droppedOctets

       64 bit unsigned wrappable counter."
   ::= {pr1645v2Lan3MCVlanOutPQsH24PerformanceEntry 150994944}

pr1645v2Lan3MCVlanOutPQsH24PerformanceRDropOcts OBJECT-TYPE
   SYNTAX      Counter64
   MAX-ACCESS  read-only
   STATUS      current
   DESCRIPTION
      "Path: ethernet3.performance.vlan.outPriorityQueues.h24Performance.redDroppedOctets

       64 bit unsigned wrappable counter."
   ::= {pr1645v2Lan3MCVlanOutPQsH24PerformanceEntry 218103808}

pr1645v2Lan3MCVlanOutPQsH24PerformanceCirTxOcts OBJECT-TYPE
   SYNTAX      Counter64
   MAX-ACCESS  read-only
   STATUS      current
   DESCRIPTION
      "Path: ethernet3.performance.vlan.outPriorityQueues.h24Performance.cirTxOctets

       64 bit unsigned wrappable counter."
   ::= {pr1645v2Lan3MCVlanOutPQsH24PerformanceEntry 167772160}

pr1645v2Lan3MCVlanOutPQsH24PerformanceEirTxOcts OBJECT-TYPE
   SYNTAX      Counter64
   MAX-ACCESS  read-only
   STATUS      current
   DESCRIPTION
      "Path: ethernet3.performance.vlan.outPriorityQueues.h24Performance.eirTxOctets

       64 bit unsigned wrappable counter."
   ::= {pr1645v2Lan3MCVlanOutPQsH24PerformanceEntry 184549376}

pr1645v2Lan3MCVlanOutPQsH24PerformanceViolTxOcts OBJECT-TYPE
   SYNTAX      Counter64
   MAX-ACCESS  read-only
   STATUS      current
   DESCRIPTION
      "Path: ethernet3.performance.vlan.outPriorityQueues.h24Performance.violateTxOctets

       64 bit unsigned wrappable counter."
   ::= {pr1645v2Lan3MCVlanOutPQsH24PerformanceEntry 318767104}

pr1645v2Lan3MCVlanOutPQsH24PerformanceBandwidth OBJECT-TYPE
   SYNTAX      Integer32
   MAX-ACCESS  read-only
   STATUS      current
   DESCRIPTION
      "Path: ethernet3.performance.vlan.outPriorityQueues.h24Performance.bandwidth

       unit name = bps
       formula = 8 * ; 8 /"
   ::= {pr1645v2Lan3MCVlanOutPQsH24PerformanceEntry 268435456}

pr1645v2Lan3MCVlanOutPQsD7Performance OBJECT-TYPE
   SYNTAX      SEQUENCE OF Pr1645v2Lan3MCVlanOutPQsD7PerformanceEntry
   MAX-ACCESS  not-accessible
   STATUS      current
   DESCRIPTION
      ""
   ::= {pr1645v2Lan3MCVlan 84344832}

pr1645v2Lan3MCVlanOutPQsD7PerformanceEntry OBJECT-TYPE
   SYNTAX      Pr1645v2Lan3MCVlanOutPQsD7PerformanceEntry
   MAX-ACCESS  not-accessible
   STATUS      current
   DESCRIPTION
      ""
   INDEX      { pr1645v2Lan3MCVlanTableIx,
                pr1645v2Lan3MCVlanOutPQsTableIx,
                pr1645v2Lan3MCVlanOutPQsD7PerformanceTableIx }
   ::= {pr1645v2Lan3MCVlanOutPQsD7Performance 1}

Pr1645v2Lan3MCVlanOutPQsD7PerformanceEntry ::=
   SEQUENCE
      {
      pr1645v2Lan3MCVlanOutPQsD7PerformanceTableIx
         TableIndex,
      pr1645v2Lan3MCVlanOutPQsD7PerformanceSysUpTime
         TimeTicks,
      pr1645v2Lan3MCVlanOutPQsD7PerformanceTotPkts
         Counter64,
      pr1645v2Lan3MCVlanOutPQsD7PerformanceDirTxPkts
         Counter64,
      pr1645v2Lan3MCVlanOutPQsD7PerformanceQdPkts
         Counter64,
      pr1645v2Lan3MCVlanOutPQsD7PerformanceDropPkts
         Counter64,
      pr1645v2Lan3MCVlanOutPQsD7PerformanceRDropPkts
         Counter64,
      pr1645v2Lan3MCVlanOutPQsD7PerformanceCirTxPkts
         Counter64,
      pr1645v2Lan3MCVlanOutPQsD7PerformanceEirTxPkts
         Counter64,
      pr1645v2Lan3MCVlanOutPQsD7PerformanceViolTxPkts
         Counter64,
      pr1645v2Lan3MCVlanOutPQsD7PerformanceTotOcts
         Counter64,
      pr1645v2Lan3MCVlanOutPQsD7PerformanceDirTxOcts
         Counter64,
      pr1645v2Lan3MCVlanOutPQsD7PerformanceQdOcts
         Counter64,
      pr1645v2Lan3MCVlanOutPQsD7PerformanceDropOcts
         Counter64,
      pr1645v2Lan3MCVlanOutPQsD7PerformanceRDropOcts
         Counter64,
      pr1645v2Lan3MCVlanOutPQsD7PerformanceCirTxOcts
         Counter64,
      pr1645v2Lan3MCVlanOutPQsD7PerformanceEirTxOcts
         Counter64,
      pr1645v2Lan3MCVlanOutPQsD7PerformanceViolTxOcts
         Counter64,
      pr1645v2Lan3MCVlanOutPQsD7PerformanceBandwidth
         Integer32
      }

pr1645v2Lan3MCVlanOutPQsD7PerformanceTableIx OBJECT-TYPE
   SYNTAX      TableIndex
   MAX-ACCESS  not-accessible
   STATUS      current
   DESCRIPTION
      ""
   ::= {pr1645v2Lan3MCVlanOutPQsD7PerformanceEntry 11}

pr1645v2Lan3MCVlanOutPQsD7PerformanceSysUpTime OBJECT-TYPE
   SYNTAX      TimeTicks
   MAX-ACCESS  read-only
   STATUS      current
   DESCRIPTION
      "Path: ethernet3.performance.vlan.outPriorityQueues.d7Performance.sysUpTime

       Time in centi-second."
   ::= {pr1645v2Lan3MCVlanOutPQsD7PerformanceEntry 16777216}

pr1645v2Lan3MCVlanOutPQsD7PerformanceTotPkts OBJECT-TYPE
   SYNTAX      Counter64
   MAX-ACCESS  read-only
   STATUS      current
   DESCRIPTION
      "Path: ethernet3.performance.vlan.outPriorityQueues.d7Performance.totalPkts

       64 bit unsigned wrappable counter."
   ::= {pr1645v2Lan3MCVlanOutPQsD7PerformanceEntry 234881024}

pr1645v2Lan3MCVlanOutPQsD7PerformanceDirTxPkts OBJECT-TYPE
   SYNTAX      Counter64
   MAX-ACCESS  read-only
   STATUS      current
   DESCRIPTION
      "Path: ethernet3.performance.vlan.outPriorityQueues.d7Performance.directTxPkts

       64 bit unsigned wrappable counter."
   ::= {pr1645v2Lan3MCVlanOutPQsD7PerformanceEntry 33554432}

pr1645v2Lan3MCVlanOutPQsD7PerformanceQdPkts OBJECT-TYPE
   SYNTAX      Counter64
   MAX-ACCESS  read-only
   STATUS      current
   DESCRIPTION
      "Path: ethernet3.performance.vlan.outPriorityQueues.d7Performance.queuedPkts

       64 bit unsigned wrappable counter."
   ::= {pr1645v2Lan3MCVlanOutPQsD7PerformanceEntry 50331648}

pr1645v2Lan3MCVlanOutPQsD7PerformanceDropPkts OBJECT-TYPE
   SYNTAX      Counter64
   MAX-ACCESS  read-only
   STATUS      current
   DESCRIPTION
      "Path: ethernet3.performance.vlan.outPriorityQueues.d7Performance.droppedPkts

       64 bit unsigned wrappable counter."
   ::= {pr1645v2Lan3MCVlanOutPQsD7PerformanceEntry 67108864}

pr1645v2Lan3MCVlanOutPQsD7PerformanceRDropPkts OBJECT-TYPE
   SYNTAX      Counter64
   MAX-ACCESS  read-only
   STATUS      current
   DESCRIPTION
      "Path: ethernet3.performance.vlan.outPriorityQueues.d7Performance.redDroppedPkts

       64 bit unsigned wrappable counter."
   ::= {pr1645v2Lan3MCVlanOutPQsD7PerformanceEntry 201326592}

pr1645v2Lan3MCVlanOutPQsD7PerformanceCirTxPkts OBJECT-TYPE
   SYNTAX      Counter64
   MAX-ACCESS  read-only
   STATUS      current
   DESCRIPTION
      "Path: ethernet3.performance.vlan.outPriorityQueues.d7Performance.cirTxPkts

       64 bit unsigned wrappable counter."
   ::= {pr1645v2Lan3MCVlanOutPQsD7PerformanceEntry 83886080}

pr1645v2Lan3MCVlanOutPQsD7PerformanceEirTxPkts OBJECT-TYPE
   SYNTAX      Counter64
   MAX-ACCESS  read-only
   STATUS      current
   DESCRIPTION
      "Path: ethernet3.performance.vlan.outPriorityQueues.d7Performance.eirTxPkts

       64 bit unsigned wrappable counter."
   ::= {pr1645v2Lan3MCVlanOutPQsD7PerformanceEntry 100663296}

pr1645v2Lan3MCVlanOutPQsD7PerformanceViolTxPkts OBJECT-TYPE
   SYNTAX      Counter64
   MAX-ACCESS  read-only
   STATUS      current
   DESCRIPTION
      "Path: ethernet3.performance.vlan.outPriorityQueues.d7Performance.violateTxPkts

       64 bit unsigned wrappable counter."
   ::= {pr1645v2Lan3MCVlanOutPQsD7PerformanceEntry 301989888}

pr1645v2Lan3MCVlanOutPQsD7PerformanceTotOcts OBJECT-TYPE
   SYNTAX      Counter64
   MAX-ACCESS  read-only
   STATUS      current
   DESCRIPTION
      "Path: ethernet3.performance.vlan.outPriorityQueues.d7Performance.totalOctets

       64 bit unsigned wrappable counter."
   ::= {pr1645v2Lan3MCVlanOutPQsD7PerformanceEntry 251658240}

pr1645v2Lan3MCVlanOutPQsD7PerformanceDirTxOcts OBJECT-TYPE
   SYNTAX      Counter64
   MAX-ACCESS  read-only
   STATUS      current
   DESCRIPTION
      "Path: ethernet3.performance.vlan.outPriorityQueues.d7Performance.directTxOctets

       64 bit unsigned wrappable counter."
   ::= {pr1645v2Lan3MCVlanOutPQsD7PerformanceEntry 117440512}

pr1645v2Lan3MCVlanOutPQsD7PerformanceQdOcts OBJECT-TYPE
   SYNTAX      Counter64
   MAX-ACCESS  read-only
   STATUS      current
   DESCRIPTION
      "Path: ethernet3.performance.vlan.outPriorityQueues.d7Performance.queuedOctets

       64 bit unsigned wrappable counter."
   ::= {pr1645v2Lan3MCVlanOutPQsD7PerformanceEntry 134217728}

pr1645v2Lan3MCVlanOutPQsD7PerformanceDropOcts OBJECT-TYPE
   SYNTAX      Counter64
   MAX-ACCESS  read-only
   STATUS      current
   DESCRIPTION
      "Path: ethernet3.performance.vlan.outPriorityQueues.d7Performance.droppedOctets

       64 bit unsigned wrappable counter."
   ::= {pr1645v2Lan3MCVlanOutPQsD7PerformanceEntry 150994944}

pr1645v2Lan3MCVlanOutPQsD7PerformanceRDropOcts OBJECT-TYPE
   SYNTAX      Counter64
   MAX-ACCESS  read-only
   STATUS      current
   DESCRIPTION
      "Path: ethernet3.performance.vlan.outPriorityQueues.d7Performance.redDroppedOctets

       64 bit unsigned wrappable counter."
   ::= {pr1645v2Lan3MCVlanOutPQsD7PerformanceEntry 218103808}

pr1645v2Lan3MCVlanOutPQsD7PerformanceCirTxOcts OBJECT-TYPE
   SYNTAX      Counter64
   MAX-ACCESS  read-only
   STATUS      current
   DESCRIPTION
      "Path: ethernet3.performance.vlan.outPriorityQueues.d7Performance.cirTxOctets

       64 bit unsigned wrappable counter."
   ::= {pr1645v2Lan3MCVlanOutPQsD7PerformanceEntry 167772160}

pr1645v2Lan3MCVlanOutPQsD7PerformanceEirTxOcts OBJECT-TYPE
   SYNTAX      Counter64
   MAX-ACCESS  read-only
   STATUS      current
   DESCRIPTION
      "Path: ethernet3.performance.vlan.outPriorityQueues.d7Performance.eirTxOctets

       64 bit unsigned wrappable counter."
   ::= {pr1645v2Lan3MCVlanOutPQsD7PerformanceEntry 184549376}

pr1645v2Lan3MCVlanOutPQsD7PerformanceViolTxOcts OBJECT-TYPE
   SYNTAX      Counter64
   MAX-ACCESS  read-only
   STATUS      current
   DESCRIPTION
      "Path: ethernet3.performance.vlan.outPriorityQueues.d7Performance.violateTxOctets

       64 bit unsigned wrappable counter."
   ::= {pr1645v2Lan3MCVlanOutPQsD7PerformanceEntry 318767104}

pr1645v2Lan3MCVlanOutPQsD7PerformanceBandwidth OBJECT-TYPE
   SYNTAX      Integer32
   MAX-ACCESS  read-only
   STATUS      current
   DESCRIPTION
      "Path: ethernet3.performance.vlan.outPriorityQueues.d7Performance.bandwidth

       unit name = bps
       formula = 8 * ; 8 /"
   ::= {pr1645v2Lan3MCVlanOutPQsD7PerformanceEntry 268435456}


pr1645v2Lan3MCPPPoE OBJECT IDENTIFIER ::= {pr1645v2Lan3MC 53}

pr1645v2Lan3MCPPPoESSCTable OBJECT-TYPE
   SYNTAX      SEQUENCE OF Pr1645v2Lan3MCPPPoEEntry
   MAX-ACCESS  not-accessible
   STATUS      current
   DESCRIPTION
      ""
   ::= {pr1645v2Lan3MCPPPoE 1}

pr1645v2Lan3MCPPPoEEntry OBJECT-TYPE
   SYNTAX      Pr1645v2Lan3MCPPPoEEntry
   MAX-ACCESS  not-accessible
   STATUS      current
   DESCRIPTION
      ""
   INDEX      { pr1645v2Lan3MCPPPoETableIx }
   ::= {pr1645v2Lan3MCPPPoESSCTable 1}

Pr1645v2Lan3MCPPPoEEntry ::=
   SEQUENCE
      {
      pr1645v2Lan3MCPPPoETableIx
         TableIndex,
      pr1645v2Lan3MCPPPoEName
         DisplayString,
      pr1645v2Lan3MCPPPoEMCInOctets
         Counter64,
      pr1645v2Lan3MCPPPoEMCInUcast
         Counter64,
      pr1645v2Lan3MCPPPoEMCInNUcastPkts
         Counter64,
      pr1645v2Lan3MCPPPoEMCInBcastPkts
         Counter64,
      pr1645v2Lan3MCPPPoEMCInMcastPkts
         Counter64,
      pr1645v2Lan3MCPPPoEMCInDiscards
         Counter64,
      pr1645v2Lan3MCPPPoEMCInErrors
         Counter64,
      pr1645v2Lan3MCPPPoEMCInUnknownProtos
         Counter64,
      pr1645v2Lan3MCPPPoEMCInDropEx
         Counter64,
      pr1645v2Lan3MCPPPoEMCInDropNoMac
         Counter64,
      pr1645v2Lan3MCPPPoEMCInDropNUCast
         Counter64,
      pr1645v2Lan3MCPPPoEMCInDropFilter
         Counter64,
      pr1645v2Lan3MCPPPoEMCInBandwidth15sec
         Integer32,
      pr1645v2Lan3MCPPPoEMCInBandwidth30sec
         Integer32,
      pr1645v2Lan3MCPPPoEMCInBandwidth1min
         Integer32,
      pr1645v2Lan3MCPPPoEMCInBandwidth2min
         Integer32,
      pr1645v2Lan3MCPPPoEMCInBandwidth5min
         Integer32,
      pr1645v2Lan3MCPPPoEMCOutOctets
         Counter64,
      pr1645v2Lan3MCPPPoEMCOutUcastPkts
         Counter64,
      pr1645v2Lan3MCPPPoEMCOutNUcastPkts
         Counter64,
      pr1645v2Lan3MCPPPoEMCOutBcastPkts
         Counter64,
      pr1645v2Lan3MCPPPoEMCOutMcastPkts
         Counter64,
      pr1645v2Lan3MCPPPoEMCOutDiscards
         Counter64,
      pr1645v2Lan3MCPPPoEMCOutErrors
         Counter64,
      pr1645v2Lan3MCPPPoEMCOutQLen
         Counter32,
      pr1645v2Lan3MCPPPoEMCOutDropEx
         Counter64,
      pr1645v2Lan3MCPPPoEMCOutDropNoArp
         Counter64,
      pr1645v2Lan3MCPPPoEMCOutDropFilter
         Counter64,
      pr1645v2Lan3MCPPPoEMCOutBandwidth15sec
         Integer32,
      pr1645v2Lan3MCPPPoEMCOutBandwidth30sec
         Integer32,
      pr1645v2Lan3MCPPPoEMCOutBandwidth1min
         Integer32,
      pr1645v2Lan3MCPPPoEMCOutBandwidth2min
         Integer32,
      pr1645v2Lan3MCPPPoEMCOutBandwidth5min
         Integer32,
      pr1645v2Lan3MCPPPoEPppLinkMonitoringRequestsSent
         Gauge32,
      pr1645v2Lan3MCPPPoEPppLinkMonitoringRepliesRcvd
         Gauge32,
      pr1645v2Lan3MCPPPoEPppLinkMonitoringRequestsRcvd
         Gauge32,
      pr1645v2Lan3MCPPPoEPppLinkMonitoringRepliesSent
         Gauge32
      }

pr1645v2Lan3MCPPPoETableIx OBJECT-TYPE
   SYNTAX      TableIndex
   MAX-ACCESS  not-accessible
   STATUS      current
   DESCRIPTION
      ""
   ::= {pr1645v2Lan3MCPPPoEEntry 11}

pr1645v2Lan3MCPPPoEName OBJECT-TYPE
   SYNTAX      DisplayString
   MAX-ACCESS  read-only
   STATUS      current
   DESCRIPTION
      "Path: ethernet3.performance.pppoEClient.name"
   ::= {pr1645v2Lan3MCPPPoEEntry 16777216}

pr1645v2Lan3MCPPPoEMCInOctets OBJECT-TYPE
   SYNTAX      Counter64
   MAX-ACCESS  read-only
   STATUS      current
   DESCRIPTION
      "Path: ethernet3.performance.pppoEClient.mibCounters.ifInOctets

       64 bit unsigned wrappable counter."
   ::= {pr1645v2Lan3MCPPPoEEntry 40697856}

pr1645v2Lan3MCPPPoEMCInUcast OBJECT-TYPE
   SYNTAX      Counter64
   MAX-ACCESS  read-only
   STATUS      current
   DESCRIPTION
      "Path: ethernet3.performance.pppoEClient.mibCounters.ifInUcastPkts

       64 bit unsigned wrappable counter."
   ::= {pr1645v2Lan3MCPPPoEEntry 40763392}

pr1645v2Lan3MCPPPoEMCInNUcastPkts OBJECT-TYPE
   SYNTAX      Counter64
   MAX-ACCESS  read-only
   STATUS      current
   DESCRIPTION
      "Path: ethernet3.performance.pppoEClient.mibCounters.ifInNUcastPkts

       64 bit unsigned wrappable counter."
   ::= {pr1645v2Lan3MCPPPoEEntry 40828928}

pr1645v2Lan3MCPPPoEMCInBcastPkts OBJECT-TYPE
   SYNTAX      Counter64
   MAX-ACCESS  read-only
   STATUS      current
   DESCRIPTION
      "Path: ethernet3.performance.pppoEClient.mibCounters.ifInBcastPkts

       64 bit unsigned wrappable counter."
   ::= {pr1645v2Lan3MCPPPoEEntry 47382528}

pr1645v2Lan3MCPPPoEMCInMcastPkts OBJECT-TYPE
   SYNTAX      Counter64
   MAX-ACCESS  read-only
   STATUS      current
   DESCRIPTION
      "Path: ethernet3.performance.pppoEClient.mibCounters.ifInMcastPkts

       64 bit unsigned wrappable counter."
   ::= {pr1645v2Lan3MCPPPoEEntry 48037888}

pr1645v2Lan3MCPPPoEMCInDiscards OBJECT-TYPE
   SYNTAX      Counter64
   MAX-ACCESS  read-only
   STATUS      current
   DESCRIPTION
      "Path: ethernet3.performance.pppoEClient.mibCounters.ifInDiscards

       64 bit unsigned wrappable counter."
   ::= {pr1645v2Lan3MCPPPoEEntry 40894464}

pr1645v2Lan3MCPPPoEMCInErrors OBJECT-TYPE
   SYNTAX      Counter64
   MAX-ACCESS  read-only
   STATUS      current
   DESCRIPTION
      "Path: ethernet3.performance.pppoEClient.mibCounters.ifInErrors

       64 bit unsigned wrappable counter."
   ::= {pr1645v2Lan3MCPPPoEEntry 40960000}

pr1645v2Lan3MCPPPoEMCInUnknownProtos OBJECT-TYPE
   SYNTAX      Counter64
   MAX-ACCESS  read-only
   STATUS      current
   DESCRIPTION
      "Path: ethernet3.performance.pppoEClient.mibCounters.ifInUnknownProtos

       64 bit unsigned wrappable counter."
   ::= {pr1645v2Lan3MCPPPoEEntry 41025536}

pr1645v2Lan3MCPPPoEMCInDropEx OBJECT-TYPE
   SYNTAX      Counter64
   MAX-ACCESS  read-only
   STATUS      current
   DESCRIPTION
      "Path: ethernet3.performance.pppoEClient.mibCounters.ifInDropLevelExceeded

       64 bit unsigned wrappable counter."
   ::= {pr1645v2Lan3MCPPPoEEntry 42074112}

pr1645v2Lan3MCPPPoEMCInDropNoMac OBJECT-TYPE
   SYNTAX      Counter64
   MAX-ACCESS  read-only
   STATUS      current
   DESCRIPTION
      "Path: ethernet3.performance.pppoEClient.mibCounters.ifInDiscardsNoMacFit

       64 bit unsigned wrappable counter."
   ::= {pr1645v2Lan3MCPPPoEEntry 42270720}

pr1645v2Lan3MCPPPoEMCInDropNUCast OBJECT-TYPE
   SYNTAX      Counter64
   MAX-ACCESS  read-only
   STATUS      current
   DESCRIPTION
      "Path: ethernet3.performance.pppoEClient.mibCounters.ifInDiscardsNUCast

       64 bit unsigned wrappable counter."
   ::= {pr1645v2Lan3MCPPPoEEntry 42467328}

pr1645v2Lan3MCPPPoEMCInDropFilter OBJECT-TYPE
   SYNTAX      Counter64
   MAX-ACCESS  read-only
   STATUS      current
   DESCRIPTION
      "Path: ethernet3.performance.pppoEClient.mibCounters.ifInDiscardsFilter

       64 bit unsigned wrappable counter."
   ::= {pr1645v2Lan3MCPPPoEEntry 42532864}

pr1645v2Lan3MCPPPoEMCInBandwidth15sec OBJECT-TYPE
   SYNTAX      Integer32
   MAX-ACCESS  read-only
   STATUS      current
   DESCRIPTION
      "Path: ethernet3.performance.pppoEClient.mibCounters.ifInBandwidth.15sec

       unit name = bps
       formula = 8 * ; 8 /"
   ::= {pr1645v2Lan3MCPPPoEEntry 45417728}

pr1645v2Lan3MCPPPoEMCInBandwidth30sec OBJECT-TYPE
   SYNTAX      Integer32
   MAX-ACCESS  read-only
   STATUS      current
   DESCRIPTION
      "Path: ethernet3.performance.pppoEClient.mibCounters.ifInBandwidth.30sec

       unit name = bps
       formula = 8 * ; 8 /"
   ::= {pr1645v2Lan3MCPPPoEEntry 45419008}

pr1645v2Lan3MCPPPoEMCInBandwidth1min OBJECT-TYPE
   SYNTAX      Integer32
   MAX-ACCESS  read-only
   STATUS      current
   DESCRIPTION
      "Path: ethernet3.performance.pppoEClient.mibCounters.ifInBandwidth.1min

       unit name = bps
       formula = 8 * ; 8 /"
   ::= {pr1645v2Lan3MCPPPoEEntry 45421568}

pr1645v2Lan3MCPPPoEMCInBandwidth2min OBJECT-TYPE
   SYNTAX      Integer32
   MAX-ACCESS  read-only
   STATUS      current
   DESCRIPTION
      "Path: ethernet3.performance.pppoEClient.mibCounters.ifInBandwidth.2min

       unit name = bps
       formula = 8 * ; 8 /"
   ::= {pr1645v2Lan3MCPPPoEEntry 45426688}

pr1645v2Lan3MCPPPoEMCInBandwidth5min OBJECT-TYPE
   SYNTAX      Integer32
   MAX-ACCESS  read-only
   STATUS      current
   DESCRIPTION
      "Path: ethernet3.performance.pppoEClient.mibCounters.ifInBandwidth.5min

       unit name = bps
       formula = 8 * ; 8 /"
   ::= {pr1645v2Lan3MCPPPoEEntry 45442048}

pr1645v2Lan3MCPPPoEMCOutOctets OBJECT-TYPE
   SYNTAX      Counter64
   MAX-ACCESS  read-only
   STATUS      current
   DESCRIPTION
      "Path: ethernet3.performance.pppoEClient.mibCounters.ifOutOctets

       64 bit unsigned wrappable counter."
   ::= {pr1645v2Lan3MCPPPoEEntry 41091072}

pr1645v2Lan3MCPPPoEMCOutUcastPkts OBJECT-TYPE
   SYNTAX      Counter64
   MAX-ACCESS  read-only
   STATUS      current
   DESCRIPTION
      "Path: ethernet3.performance.pppoEClient.mibCounters.ifOutUcastPkts

       64 bit unsigned wrappable counter."
   ::= {pr1645v2Lan3MCPPPoEEntry 41156608}

pr1645v2Lan3MCPPPoEMCOutNUcastPkts OBJECT-TYPE
   SYNTAX      Counter64
   MAX-ACCESS  read-only
   STATUS      current
   DESCRIPTION
      "Path: ethernet3.performance.pppoEClient.mibCounters.ifOutNUcastPkts

       64 bit unsigned wrappable counter."
   ::= {pr1645v2Lan3MCPPPoEEntry 41222144}

pr1645v2Lan3MCPPPoEMCOutBcastPkts OBJECT-TYPE
   SYNTAX      Counter64
   MAX-ACCESS  read-only
   STATUS      current
   DESCRIPTION
      "Path: ethernet3.performance.pppoEClient.mibCounters.ifOutBcastPkts

       64 bit unsigned wrappable counter."
   ::= {pr1645v2Lan3MCPPPoEEntry 47775744}

pr1645v2Lan3MCPPPoEMCOutMcastPkts OBJECT-TYPE
   SYNTAX      Counter64
   MAX-ACCESS  read-only
   STATUS      current
   DESCRIPTION
      "Path: ethernet3.performance.pppoEClient.mibCounters.ifOutMcastPkts

       64 bit unsigned wrappable counter."
   ::= {pr1645v2Lan3MCPPPoEEntry 48431104}

pr1645v2Lan3MCPPPoEMCOutDiscards OBJECT-TYPE
   SYNTAX      Counter64
   MAX-ACCESS  read-only
   STATUS      current
   DESCRIPTION
      "Path: ethernet3.performance.pppoEClient.mibCounters.ifOutDiscards

       64 bit unsigned wrappable counter."
   ::= {pr1645v2Lan3MCPPPoEEntry 41287680}

pr1645v2Lan3MCPPPoEMCOutErrors OBJECT-TYPE
   SYNTAX      Counter64
   MAX-ACCESS  read-only
   STATUS      current
   DESCRIPTION
      "Path: ethernet3.performance.pppoEClient.mibCounters.ifOutErrors

       64 bit unsigned wrappable counter."
   ::= {pr1645v2Lan3MCPPPoEEntry 41353216}

pr1645v2Lan3MCPPPoEMCOutQLen OBJECT-TYPE
   SYNTAX      Counter32
   MAX-ACCESS  read-only
   STATUS      current
   DESCRIPTION
      "Path: ethernet3.performance.pppoEClient.mibCounters.ifOutQLen

       32 bit unsigned wrappable counter."
   ::= {pr1645v2Lan3MCPPPoEEntry 41418752}

pr1645v2Lan3MCPPPoEMCOutDropEx OBJECT-TYPE
   SYNTAX      Counter64
   MAX-ACCESS  read-only
   STATUS      current
   DESCRIPTION
      "Path: ethernet3.performance.pppoEClient.mibCounters.ifOutDropLevelExceeded

       64 bit unsigned wrappable counter."
   ::= {pr1645v2Lan3MCPPPoEEntry 41484288}

pr1645v2Lan3MCPPPoEMCOutDropNoArp OBJECT-TYPE
   SYNTAX      Counter64
   MAX-ACCESS  read-only
   STATUS      current
   DESCRIPTION
      "Path: ethernet3.performance.pppoEClient.mibCounters.ifOutDiscardsNoArp

       64 bit unsigned wrappable counter."
   ::= {pr1645v2Lan3MCPPPoEEntry 42336256}

pr1645v2Lan3MCPPPoEMCOutDropFilter OBJECT-TYPE
   SYNTAX      Counter64
   MAX-ACCESS  read-only
   STATUS      current
   DESCRIPTION
      "Path: ethernet3.performance.pppoEClient.mibCounters.ifOutDiscardsFilter

       64 bit unsigned wrappable counter."
   ::= {pr1645v2Lan3MCPPPoEEntry 42598400}

pr1645v2Lan3MCPPPoEMCOutBandwidth15sec OBJECT-TYPE
   SYNTAX      Integer32
   MAX-ACCESS  read-only
   STATUS      current
   DESCRIPTION
      "Path: ethernet3.performance.pppoEClient.mibCounters.ifOutBandwidth.15sec

       unit name = bps
       formula = 8 * ; 8 /"
   ::= {pr1645v2Lan3MCPPPoEEntry 45483264}

pr1645v2Lan3MCPPPoEMCOutBandwidth30sec OBJECT-TYPE
   SYNTAX      Integer32
   MAX-ACCESS  read-only
   STATUS      current
   DESCRIPTION
      "Path: ethernet3.performance.pppoEClient.mibCounters.ifOutBandwidth.30sec

       unit name = bps
       formula = 8 * ; 8 /"
   ::= {pr1645v2Lan3MCPPPoEEntry 45484544}

pr1645v2Lan3MCPPPoEMCOutBandwidth1min OBJECT-TYPE
   SYNTAX      Integer32
   MAX-ACCESS  read-only
   STATUS      current
   DESCRIPTION
      "Path: ethernet3.performance.pppoEClient.mibCounters.ifOutBandwidth.1min

       unit name = bps
       formula = 8 * ; 8 /"
   ::= {pr1645v2Lan3MCPPPoEEntry 45487104}

pr1645v2Lan3MCPPPoEMCOutBandwidth2min OBJECT-TYPE
   SYNTAX      Integer32
   MAX-ACCESS  read-only
   STATUS      current
   DESCRIPTION
      "Path: ethernet3.performance.pppoEClient.mibCounters.ifOutBandwidth.2min

       unit name = bps
       formula = 8 * ; 8 /"
   ::= {pr1645v2Lan3MCPPPoEEntry 45492224}

pr1645v2Lan3MCPPPoEMCOutBandwidth5min OBJECT-TYPE
   SYNTAX      Integer32
   MAX-ACCESS  read-only
   STATUS      current
   DESCRIPTION
      "Path: ethernet3.performance.pppoEClient.mibCounters.ifOutBandwidth.5min

       unit name = bps
       formula = 8 * ; 8 /"
   ::= {pr1645v2Lan3MCPPPoEEntry 45507584}

pr1645v2Lan3MCPPPoEPppLinkMonitoringRequestsSent OBJECT-TYPE
   SYNTAX      Gauge32
   MAX-ACCESS  read-only
   STATUS      current
   DESCRIPTION
      "Path: ethernet3.performance.pppoEClient.ppp.linkMonitoring.requestsSent

       32 bit unsigned gauge value."
   ::= {pr1645v2Lan3MCPPPoEEntry 50397440}

pr1645v2Lan3MCPPPoEPppLinkMonitoringRepliesRcvd OBJECT-TYPE
   SYNTAX      Gauge32
   MAX-ACCESS  read-only
   STATUS      current
   DESCRIPTION
      "Path: ethernet3.performance.pppoEClient.ppp.linkMonitoring.repliesRcvd

       32 bit unsigned gauge value."
   ::= {pr1645v2Lan3MCPPPoEEntry 50397696}

pr1645v2Lan3MCPPPoEPppLinkMonitoringRequestsRcvd OBJECT-TYPE
   SYNTAX      Gauge32
   MAX-ACCESS  read-only
   STATUS      current
   DESCRIPTION
      "Path: ethernet3.performance.pppoEClient.ppp.linkMonitoring.requestsRcvd

       32 bit unsigned gauge value."
   ::= {pr1645v2Lan3MCPPPoEEntry 50397952}

pr1645v2Lan3MCPPPoEPppLinkMonitoringRepliesSent OBJECT-TYPE
   SYNTAX      Gauge32
   MAX-ACCESS  read-only
   STATUS      current
   DESCRIPTION
      "Path: ethernet3.performance.pppoEClient.ppp.linkMonitoring.repliesSent

       32 bit unsigned gauge value."
   ::= {pr1645v2Lan3MCPPPoEEntry 50398208}

pr1645v2Lan3MCPPPoEMCH2P OBJECT-TYPE
   SYNTAX      SEQUENCE OF Pr1645v2Lan3MCPPPoEMCH2PEntry
   MAX-ACCESS  not-accessible
   STATUS      current
   DESCRIPTION
      ""
   ::= {pr1645v2Lan3MCPPPoE 41549824}

pr1645v2Lan3MCPPPoEMCH2PEntry OBJECT-TYPE
   SYNTAX      Pr1645v2Lan3MCPPPoEMCH2PEntry
   MAX-ACCESS  not-accessible
   STATUS      current
   DESCRIPTION
      ""
   INDEX      { pr1645v2Lan3MCPPPoETableIx,
                pr1645v2Lan3MCPPPoEMCH2PTableIx }
   ::= {pr1645v2Lan3MCPPPoEMCH2P 1}

Pr1645v2Lan3MCPPPoEMCH2PEntry ::=
   SEQUENCE
      {
      pr1645v2Lan3MCPPPoEMCH2PTableIx
         TableIndex,
      pr1645v2Lan3MCPPPoEMCH2PSysUpTime
         TimeTicks,
      pr1645v2Lan3MCPPPoEMCH2PIfUpTime
         TimeTicks,
      pr1645v2Lan3MCPPPoEMCH2PIfStatChanges
         Counter32,
      pr1645v2Lan3MCPPPoEMCH2PIfInOctets
         Counter64,
      pr1645v2Lan3MCPPPoEMCH2PIfInUCPkts
         Counter64,
      pr1645v2Lan3MCPPPoEMCH2PIfInNUCPkts
         Counter64,
      pr1645v2Lan3MCPPPoEMCH2PIfInBCPkts
         Counter64,
      pr1645v2Lan3MCPPPoEMCH2PIfInMCPkts
         Counter64,
      pr1645v2Lan3MCPPPoEMCH2PIfInDiscards
         Counter64,
      pr1645v2Lan3MCPPPoEMCH2PIfInErrors
         Counter64,
      pr1645v2Lan3MCPPPoEMCH2PIfInUnkwn
         Counter64,
      pr1645v2Lan3MCPPPoEMCH2PInDropEx
         Counter64,
      pr1645v2Lan3MCPPPoEMCH2PInDropNoMac
         Counter64,
      pr1645v2Lan3MCPPPoEMCH2PInDropNUCast
         Counter64,
      pr1645v2Lan3MCPPPoEMCH2PInDropFilter
         Counter64,
      pr1645v2Lan3MCPPPoEMCH2PIfInBandwidth
         Integer32,
      pr1645v2Lan3MCPPPoEMCH2PIfOutOctets
         Counter64,
      pr1645v2Lan3MCPPPoEMCH2PIfOutUCPkts
         Counter64,
      pr1645v2Lan3MCPPPoEMCH2PIfOutNUCPkts
         Counter64,
      pr1645v2Lan3MCPPPoEMCH2PIfOutBCPkts
         Counter64,
      pr1645v2Lan3MCPPPoEMCH2PIfOutMCPkts
         Counter64,
      pr1645v2Lan3MCPPPoEMCH2PIfOutDiscards
         Counter64,
      pr1645v2Lan3MCPPPoEMCH2PIfOutErrors
         Counter64,
      pr1645v2Lan3MCPPPoEMCH2POutDropEx
         Counter64,
      pr1645v2Lan3MCPPPoEMCH2POutDropNoArp
         Counter64,
      pr1645v2Lan3MCPPPoEMCH2POutDropFilter
         Counter64,
      pr1645v2Lan3MCPPPoEMCH2PIfOutBandwidth
         Integer32,
      pr1645v2Lan3MCPPPoEMCH2PIfErrSec
         Counter32
      }

pr1645v2Lan3MCPPPoEMCH2PTableIx OBJECT-TYPE
   SYNTAX      TableIndex
   MAX-ACCESS  not-accessible
   STATUS      current
   DESCRIPTION
      ""
   ::= {pr1645v2Lan3MCPPPoEMCH2PEntry 11}

pr1645v2Lan3MCPPPoEMCH2PSysUpTime OBJECT-TYPE
   SYNTAX      TimeTicks
   MAX-ACCESS  read-only
   STATUS      current
   DESCRIPTION
      "Path: ethernet3.performance.pppoEClient.mibCounters.h2Performance.sysUpTime

       Time in centi-second."
   ::= {pr1645v2Lan3MCPPPoEMCH2PEntry 16777216}

pr1645v2Lan3MCPPPoEMCH2PIfUpTime OBJECT-TYPE
   SYNTAX      TimeTicks
   MAX-ACCESS  read-only
   STATUS      current
   DESCRIPTION
      "Path: ethernet3.performance.pppoEClient.mibCounters.h2Performance.ifUpTime

       Time in centi-second."
   ::= {pr1645v2Lan3MCPPPoEMCH2PEntry 33554432}

pr1645v2Lan3MCPPPoEMCH2PIfStatChanges OBJECT-TYPE
   SYNTAX      Counter32
   MAX-ACCESS  read-only
   STATUS      current
   DESCRIPTION
      "Path: ethernet3.performance.pppoEClient.mibCounters.h2Performance.ifStatusChanges

       32 bit unsigned wrappable counter."
   ::= {pr1645v2Lan3MCPPPoEMCH2PEntry 50331648}

pr1645v2Lan3MCPPPoEMCH2PIfInOctets OBJECT-TYPE
   SYNTAX      Counter64
   MAX-ACCESS  read-only
   STATUS      current
   DESCRIPTION
      "Path: ethernet3.performance.pppoEClient.mibCounters.h2Performance.ifInOctets

       64 bit unsigned wrappable counter."
   ::= {pr1645v2Lan3MCPPPoEMCH2PEntry 67108864}

pr1645v2Lan3MCPPPoEMCH2PIfInUCPkts OBJECT-TYPE
   SYNTAX      Counter64
   MAX-ACCESS  read-only
   STATUS      current
   DESCRIPTION
      "Path: ethernet3.performance.pppoEClient.mibCounters.h2Performance.ifInUcastPkts

       64 bit unsigned wrappable counter."
   ::= {pr1645v2Lan3MCPPPoEMCH2PEntry 83886080}

pr1645v2Lan3MCPPPoEMCH2PIfInNUCPkts OBJECT-TYPE
   SYNTAX      Counter64
   MAX-ACCESS  read-only
   STATUS      current
   DESCRIPTION
      "Path: ethernet3.performance.pppoEClient.mibCounters.h2Performance.ifInNUcastPkts

       64 bit unsigned wrappable counter."
   ::= {pr1645v2Lan3MCPPPoEMCH2PEntry 100663296}

pr1645v2Lan3MCPPPoEMCH2PIfInBCPkts OBJECT-TYPE
   SYNTAX      Counter64
   MAX-ACCESS  read-only
   STATUS      current
   DESCRIPTION
      "Path: ethernet3.performance.pppoEClient.mibCounters.h2Performance.ifInBcastPkts

       64 bit unsigned wrappable counter."
   ::= {pr1645v2Lan3MCPPPoEMCH2PEntry 419430400}

pr1645v2Lan3MCPPPoEMCH2PIfInMCPkts OBJECT-TYPE
   SYNTAX      Counter64
   MAX-ACCESS  read-only
   STATUS      current
   DESCRIPTION
      "Path: ethernet3.performance.pppoEClient.mibCounters.h2Performance.ifInMcastPkts

       64 bit unsigned wrappable counter."
   ::= {pr1645v2Lan3MCPPPoEMCH2PEntry 436207616}

pr1645v2Lan3MCPPPoEMCH2PIfInDiscards OBJECT-TYPE
   SYNTAX      Counter64
   MAX-ACCESS  read-only
   STATUS      current
   DESCRIPTION
      "Path: ethernet3.performance.pppoEClient.mibCounters.h2Performance.ifInDiscards

       64 bit unsigned wrappable counter."
   ::= {pr1645v2Lan3MCPPPoEMCH2PEntry 117440512}

pr1645v2Lan3MCPPPoEMCH2PIfInErrors OBJECT-TYPE
   SYNTAX      Counter64
   MAX-ACCESS  read-only
   STATUS      current
   DESCRIPTION
      "Path: ethernet3.performance.pppoEClient.mibCounters.h2Performance.ifInErrors

       64 bit unsigned wrappable counter."
   ::= {pr1645v2Lan3MCPPPoEMCH2PEntry 134217728}

pr1645v2Lan3MCPPPoEMCH2PIfInUnkwn OBJECT-TYPE
   SYNTAX      Counter64
   MAX-ACCESS  read-only
   STATUS      current
   DESCRIPTION
      "Path: ethernet3.performance.pppoEClient.mibCounters.h2Performance.ifInUnknownProtos

       64 bit unsigned wrappable counter."
   ::= {pr1645v2Lan3MCPPPoEMCH2PEntry 150994944}

pr1645v2Lan3MCPPPoEMCH2PInDropEx OBJECT-TYPE
   SYNTAX      Counter64
   MAX-ACCESS  read-only
   STATUS      current
   DESCRIPTION
      "Path: ethernet3.performance.pppoEClient.mibCounters.h2Performance.ifInDropLevelExceeded

       64 bit unsigned wrappable counter."
   ::= {pr1645v2Lan3MCPPPoEMCH2PEntry 335544320}

pr1645v2Lan3MCPPPoEMCH2PInDropNoMac OBJECT-TYPE
   SYNTAX      Counter64
   MAX-ACCESS  read-only
   STATUS      current
   DESCRIPTION
      "Path: ethernet3.performance.pppoEClient.mibCounters.h2Performance.fInDiscardsNoMacFit

       64 bit unsigned wrappable counter."
   ::= {pr1645v2Lan3MCPPPoEMCH2PEntry 301989888}

pr1645v2Lan3MCPPPoEMCH2PInDropNUCast OBJECT-TYPE
   SYNTAX      Counter64
   MAX-ACCESS  read-only
   STATUS      current
   DESCRIPTION
      "Path: ethernet3.performance.pppoEClient.mibCounters.h2Performance.fInDiscardsNUCast

       64 bit unsigned wrappable counter."
   ::= {pr1645v2Lan3MCPPPoEMCH2PEntry 318767104}

pr1645v2Lan3MCPPPoEMCH2PInDropFilter OBJECT-TYPE
   SYNTAX      Counter64
   MAX-ACCESS  read-only
   STATUS      current
   DESCRIPTION
      "Path: ethernet3.performance.pppoEClient.mibCounters.h2Performance.fInDiscardsFilter

       64 bit unsigned wrappable counter."
   ::= {pr1645v2Lan3MCPPPoEMCH2PEntry 385875968}

pr1645v2Lan3MCPPPoEMCH2PIfInBandwidth OBJECT-TYPE
   SYNTAX      Integer32
   MAX-ACCESS  read-only
   STATUS      current
   DESCRIPTION
      "Path: ethernet3.performance.pppoEClient.mibCounters.h2Performance.ifInBandwidth

       unit name = bps
       formula = 8 * ; 8 /"
   ::= {pr1645v2Lan3MCPPPoEMCH2PEntry 268435456}

pr1645v2Lan3MCPPPoEMCH2PIfOutOctets OBJECT-TYPE
   SYNTAX      Counter64
   MAX-ACCESS  read-only
   STATUS      current
   DESCRIPTION
      "Path: ethernet3.performance.pppoEClient.mibCounters.h2Performance.ifOutOctets

       64 bit unsigned wrappable counter."
   ::= {pr1645v2Lan3MCPPPoEMCH2PEntry 167772160}

pr1645v2Lan3MCPPPoEMCH2PIfOutUCPkts OBJECT-TYPE
   SYNTAX      Counter64
   MAX-ACCESS  read-only
   STATUS      current
   DESCRIPTION
      "Path: ethernet3.performance.pppoEClient.mibCounters.h2Performance.ifOutUcastPkts

       64 bit unsigned wrappable counter."
   ::= {pr1645v2Lan3MCPPPoEMCH2PEntry 184549376}

pr1645v2Lan3MCPPPoEMCH2PIfOutNUCPkts OBJECT-TYPE
   SYNTAX      Counter64
   MAX-ACCESS  read-only
   STATUS      current
   DESCRIPTION
      "Path: ethernet3.performance.pppoEClient.mibCounters.h2Performance.ifOutNUcastPkts

       64 bit unsigned wrappable counter."
   ::= {pr1645v2Lan3MCPPPoEMCH2PEntry 201326592}

pr1645v2Lan3MCPPPoEMCH2PIfOutBCPkts OBJECT-TYPE
   SYNTAX      Counter64
   MAX-ACCESS  read-only
   STATUS      current
   DESCRIPTION
      "Path: ethernet3.performance.pppoEClient.mibCounters.h2Performance.ifOutBcastPkts

       64 bit unsigned wrappable counter."
   ::= {pr1645v2Lan3MCPPPoEMCH2PEntry 452984832}

pr1645v2Lan3MCPPPoEMCH2PIfOutMCPkts OBJECT-TYPE
   SYNTAX      Counter64
   MAX-ACCESS  read-only
   STATUS      current
   DESCRIPTION
      "Path: ethernet3.performance.pppoEClient.mibCounters.h2Performance.ifOutMcastPkts

       64 bit unsigned wrappable counter."
   ::= {pr1645v2Lan3MCPPPoEMCH2PEntry 469762048}

pr1645v2Lan3MCPPPoEMCH2PIfOutDiscards OBJECT-TYPE
   SYNTAX      Counter64
   MAX-ACCESS  read-only
   STATUS      current
   DESCRIPTION
      "Path: ethernet3.performance.pppoEClient.mibCounters.h2Performance.ifOutDiscards

       64 bit unsigned wrappable counter."
   ::= {pr1645v2Lan3MCPPPoEMCH2PEntry 218103808}

pr1645v2Lan3MCPPPoEMCH2PIfOutErrors OBJECT-TYPE
   SYNTAX      Counter64
   MAX-ACCESS  read-only
   STATUS      current
   DESCRIPTION
      "Path: ethernet3.performance.pppoEClient.mibCounters.h2Performance.ifOutErrors

       64 bit unsigned wrappable counter."
   ::= {pr1645v2Lan3MCPPPoEMCH2PEntry 234881024}

pr1645v2Lan3MCPPPoEMCH2POutDropEx OBJECT-TYPE
   SYNTAX      Counter64
   MAX-ACCESS  read-only
   STATUS      current
   DESCRIPTION
      "Path: ethernet3.performance.pppoEClient.mibCounters.h2Performance.ifOutDropLevelExceeded

       64 bit unsigned wrappable counter."
   ::= {pr1645v2Lan3MCPPPoEMCH2PEntry 352321536}

pr1645v2Lan3MCPPPoEMCH2POutDropNoArp OBJECT-TYPE
   SYNTAX      Counter64
   MAX-ACCESS  read-only
   STATUS      current
   DESCRIPTION
      "Path: ethernet3.performance.pppoEClient.mibCounters.h2Performance.ifOutDiscardsNoArp

       64 bit unsigned wrappable counter."
   ::= {pr1645v2Lan3MCPPPoEMCH2PEntry 369098752}

pr1645v2Lan3MCPPPoEMCH2POutDropFilter OBJECT-TYPE
   SYNTAX      Counter64
   MAX-ACCESS  read-only
   STATUS      current
   DESCRIPTION
      "Path: ethernet3.performance.pppoEClient.mibCounters.h2Performance.ifOutDiscardsFilter

       64 bit unsigned wrappable counter."
   ::= {pr1645v2Lan3MCPPPoEMCH2PEntry 402653184}

pr1645v2Lan3MCPPPoEMCH2PIfOutBandwidth OBJECT-TYPE
   SYNTAX      Integer32
   MAX-ACCESS  read-only
   STATUS      current
   DESCRIPTION
      "Path: ethernet3.performance.pppoEClient.mibCounters.h2Performance.ifOutBandwidth

       unit name = bps
       formula = 8 * ; 8 /"
   ::= {pr1645v2Lan3MCPPPoEMCH2PEntry 285212672}

pr1645v2Lan3MCPPPoEMCH2PIfErrSec OBJECT-TYPE
   SYNTAX      Counter32
   MAX-ACCESS  read-only
   STATUS      current
   DESCRIPTION
      "Path: ethernet3.performance.pppoEClient.mibCounters.h2Performance.ifErrSec

       32 bit unsigned wrappable counter."
   ::= {pr1645v2Lan3MCPPPoEMCH2PEntry 251658240}

pr1645v2Lan3MCPPPoEMCH24P OBJECT-TYPE
   SYNTAX      SEQUENCE OF Pr1645v2Lan3MCPPPoEMCH24PEntry
   MAX-ACCESS  not-accessible
   STATUS      current
   DESCRIPTION
      ""
   ::= {pr1645v2Lan3MCPPPoE 41615360}

pr1645v2Lan3MCPPPoEMCH24PEntry OBJECT-TYPE
   SYNTAX      Pr1645v2Lan3MCPPPoEMCH24PEntry
   MAX-ACCESS  not-accessible
   STATUS      current
   DESCRIPTION
      ""
   INDEX      { pr1645v2Lan3MCPPPoETableIx,
                pr1645v2Lan3MCPPPoEMCH24PTableIx }
   ::= {pr1645v2Lan3MCPPPoEMCH24P 1}

Pr1645v2Lan3MCPPPoEMCH24PEntry ::=
   SEQUENCE
      {
      pr1645v2Lan3MCPPPoEMCH24PTableIx
         TableIndex,
      pr1645v2Lan3MCPPPoEMCH24PSysUpTime
         TimeTicks,
      pr1645v2Lan3MCPPPoEMCH24PIfUpTime
         TimeTicks,
      pr1645v2Lan3MCPPPoEMCH24PIfStatChanges
         Counter32,
      pr1645v2Lan3MCPPPoEMCH24PIfInOctets
         Counter64,
      pr1645v2Lan3MCPPPoEMCH24PIfInUCPkts
         Counter64,
      pr1645v2Lan3MCPPPoEMCH24PIfInNUCPkts
         Counter64,
      pr1645v2Lan3MCPPPoEMCH24PIfInBCPkts
         Counter64,
      pr1645v2Lan3MCPPPoEMCH24PIfInMCPkts
         Counter64,
      pr1645v2Lan3MCPPPoEMCH24PIfInDiscards
         Counter64,
      pr1645v2Lan3MCPPPoEMCH24PIfInErrors
         Counter64,
      pr1645v2Lan3MCPPPoEMCH24PIfInUnkwn
         Counter64,
      pr1645v2Lan3MCPPPoEMCH24PInDropEx
         Counter64,
      pr1645v2Lan3MCPPPoEMCH24PInDropNoMac
         Counter64,
      pr1645v2Lan3MCPPPoEMCH24PInDropNUCast
         Counter64,
      pr1645v2Lan3MCPPPoEMCH24PInDropFilter
         Counter64,
      pr1645v2Lan3MCPPPoEMCH24PIfInBandwidth
         Integer32,
      pr1645v2Lan3MCPPPoEMCH24PIfOutOctets
         Counter64,
      pr1645v2Lan3MCPPPoEMCH24PIfOutUCPkts
         Counter64,
      pr1645v2Lan3MCPPPoEMCH24PIfOutNUCPkts
         Counter64,
      pr1645v2Lan3MCPPPoEMCH24PIfOutBCPkts
         Counter64,
      pr1645v2Lan3MCPPPoEMCH24PIfOutMCPkts
         Counter64,
      pr1645v2Lan3MCPPPoEMCH24PIfOutDiscards
         Counter64,
      pr1645v2Lan3MCPPPoEMCH24PIfOutErrors
         Counter64,
      pr1645v2Lan3MCPPPoEMCH24POutDropEx
         Counter64,
      pr1645v2Lan3MCPPPoEMCH24POutDropNoArp
         Counter64,
      pr1645v2Lan3MCPPPoEMCH24POutDropFilter
         Counter64,
      pr1645v2Lan3MCPPPoEMCH24PIfOutBandwidth
         Integer32,
      pr1645v2Lan3MCPPPoEMCH24PIfErrSec
         Counter32
      }

pr1645v2Lan3MCPPPoEMCH24PTableIx OBJECT-TYPE
   SYNTAX      TableIndex
   MAX-ACCESS  not-accessible
   STATUS      current
   DESCRIPTION
      ""
   ::= {pr1645v2Lan3MCPPPoEMCH24PEntry 11}

pr1645v2Lan3MCPPPoEMCH24PSysUpTime OBJECT-TYPE
   SYNTAX      TimeTicks
   MAX-ACCESS  read-only
   STATUS      current
   DESCRIPTION
      "Path: ethernet3.performance.pppoEClient.mibCounters.h24Performance.sysUpTime

       Time in centi-second."
   ::= {pr1645v2Lan3MCPPPoEMCH24PEntry 16777216}

pr1645v2Lan3MCPPPoEMCH24PIfUpTime OBJECT-TYPE
   SYNTAX      TimeTicks
   MAX-ACCESS  read-only
   STATUS      current
   DESCRIPTION
      "Path: ethernet3.performance.pppoEClient.mibCounters.h24Performance.ifUpTime

       Time in centi-second."
   ::= {pr1645v2Lan3MCPPPoEMCH24PEntry 33554432}

pr1645v2Lan3MCPPPoEMCH24PIfStatChanges OBJECT-TYPE
   SYNTAX      Counter32
   MAX-ACCESS  read-only
   STATUS      current
   DESCRIPTION
      "Path: ethernet3.performance.pppoEClient.mibCounters.h24Performance.ifStatusChanges

       32 bit unsigned wrappable counter."
   ::= {pr1645v2Lan3MCPPPoEMCH24PEntry 50331648}

pr1645v2Lan3MCPPPoEMCH24PIfInOctets OBJECT-TYPE
   SYNTAX      Counter64
   MAX-ACCESS  read-only
   STATUS      current
   DESCRIPTION
      "Path: ethernet3.performance.pppoEClient.mibCounters.h24Performance.ifInOctets

       64 bit unsigned wrappable counter."
   ::= {pr1645v2Lan3MCPPPoEMCH24PEntry 67108864}

pr1645v2Lan3MCPPPoEMCH24PIfInUCPkts OBJECT-TYPE
   SYNTAX      Counter64
   MAX-ACCESS  read-only
   STATUS      current
   DESCRIPTION
      "Path: ethernet3.performance.pppoEClient.mibCounters.h24Performance.ifInUcastPkts

       64 bit unsigned wrappable counter."
   ::= {pr1645v2Lan3MCPPPoEMCH24PEntry 83886080}

pr1645v2Lan3MCPPPoEMCH24PIfInNUCPkts OBJECT-TYPE
   SYNTAX      Counter64
   MAX-ACCESS  read-only
   STATUS      current
   DESCRIPTION
      "Path: ethernet3.performance.pppoEClient.mibCounters.h24Performance.ifInNUcastPkts

       64 bit unsigned wrappable counter."
   ::= {pr1645v2Lan3MCPPPoEMCH24PEntry 100663296}

pr1645v2Lan3MCPPPoEMCH24PIfInBCPkts OBJECT-TYPE
   SYNTAX      Counter64
   MAX-ACCESS  read-only
   STATUS      current
   DESCRIPTION
      "Path: ethernet3.performance.pppoEClient.mibCounters.h24Performance.ifInBcastPkts

       64 bit unsigned wrappable counter."
   ::= {pr1645v2Lan3MCPPPoEMCH24PEntry 419430400}

pr1645v2Lan3MCPPPoEMCH24PIfInMCPkts OBJECT-TYPE
   SYNTAX      Counter64
   MAX-ACCESS  read-only
   STATUS      current
   DESCRIPTION
      "Path: ethernet3.performance.pppoEClient.mibCounters.h24Performance.ifInMcastPkts

       64 bit unsigned wrappable counter."
   ::= {pr1645v2Lan3MCPPPoEMCH24PEntry 436207616}

pr1645v2Lan3MCPPPoEMCH24PIfInDiscards OBJECT-TYPE
   SYNTAX      Counter64
   MAX-ACCESS  read-only
   STATUS      current
   DESCRIPTION
      "Path: ethernet3.performance.pppoEClient.mibCounters.h24Performance.ifInDiscards

       64 bit unsigned wrappable counter."
   ::= {pr1645v2Lan3MCPPPoEMCH24PEntry 117440512}

pr1645v2Lan3MCPPPoEMCH24PIfInErrors OBJECT-TYPE
   SYNTAX      Counter64
   MAX-ACCESS  read-only
   STATUS      current
   DESCRIPTION
      "Path: ethernet3.performance.pppoEClient.mibCounters.h24Performance.ifInErrors

       64 bit unsigned wrappable counter."
   ::= {pr1645v2Lan3MCPPPoEMCH24PEntry 134217728}

pr1645v2Lan3MCPPPoEMCH24PIfInUnkwn OBJECT-TYPE
   SYNTAX      Counter64
   MAX-ACCESS  read-only
   STATUS      current
   DESCRIPTION
      "Path: ethernet3.performance.pppoEClient.mibCounters.h24Performance.ifInUnknownProtos

       64 bit unsigned wrappable counter."
   ::= {pr1645v2Lan3MCPPPoEMCH24PEntry 150994944}

pr1645v2Lan3MCPPPoEMCH24PInDropEx OBJECT-TYPE
   SYNTAX      Counter64
   MAX-ACCESS  read-only
   STATUS      current
   DESCRIPTION
      "Path: ethernet3.performance.pppoEClient.mibCounters.h24Performance.ifInDropLevelExceeded

       64 bit unsigned wrappable counter."
   ::= {pr1645v2Lan3MCPPPoEMCH24PEntry 335544320}

pr1645v2Lan3MCPPPoEMCH24PInDropNoMac OBJECT-TYPE
   SYNTAX      Counter64
   MAX-ACCESS  read-only
   STATUS      current
   DESCRIPTION
      "Path: ethernet3.performance.pppoEClient.mibCounters.h24Performance.fInDiscardsNoMacFit

       64 bit unsigned wrappable counter."
   ::= {pr1645v2Lan3MCPPPoEMCH24PEntry 301989888}

pr1645v2Lan3MCPPPoEMCH24PInDropNUCast OBJECT-TYPE
   SYNTAX      Counter64
   MAX-ACCESS  read-only
   STATUS      current
   DESCRIPTION
      "Path: ethernet3.performance.pppoEClient.mibCounters.h24Performance.fInDiscardsNUCast

       64 bit unsigned wrappable counter."
   ::= {pr1645v2Lan3MCPPPoEMCH24PEntry 318767104}

pr1645v2Lan3MCPPPoEMCH24PInDropFilter OBJECT-TYPE
   SYNTAX      Counter64
   MAX-ACCESS  read-only
   STATUS      current
   DESCRIPTION
      "Path: ethernet3.performance.pppoEClient.mibCounters.h24Performance.fInDiscardsFilter

       64 bit unsigned wrappable counter."
   ::= {pr1645v2Lan3MCPPPoEMCH24PEntry 385875968}

pr1645v2Lan3MCPPPoEMCH24PIfInBandwidth OBJECT-TYPE
   SYNTAX      Integer32
   MAX-ACCESS  read-only
   STATUS      current
   DESCRIPTION
      "Path: ethernet3.performance.pppoEClient.mibCounters.h24Performance.ifInBandwidth

       unit name = bps
       formula = 8 * ; 8 /"
   ::= {pr1645v2Lan3MCPPPoEMCH24PEntry 268435456}

pr1645v2Lan3MCPPPoEMCH24PIfOutOctets OBJECT-TYPE
   SYNTAX      Counter64
   MAX-ACCESS  read-only
   STATUS      current
   DESCRIPTION
      "Path: ethernet3.performance.pppoEClient.mibCounters.h24Performance.ifOutOctets

       64 bit unsigned wrappable counter."
   ::= {pr1645v2Lan3MCPPPoEMCH24PEntry 167772160}

pr1645v2Lan3MCPPPoEMCH24PIfOutUCPkts OBJECT-TYPE
   SYNTAX      Counter64
   MAX-ACCESS  read-only
   STATUS      current
   DESCRIPTION
      "Path: ethernet3.performance.pppoEClient.mibCounters.h24Performance.ifOutUcastPkts

       64 bit unsigned wrappable counter."
   ::= {pr1645v2Lan3MCPPPoEMCH24PEntry 184549376}

pr1645v2Lan3MCPPPoEMCH24PIfOutNUCPkts OBJECT-TYPE
   SYNTAX      Counter64
   MAX-ACCESS  read-only
   STATUS      current
   DESCRIPTION
      "Path: ethernet3.performance.pppoEClient.mibCounters.h24Performance.ifOutNUcastPkts

       64 bit unsigned wrappable counter."
   ::= {pr1645v2Lan3MCPPPoEMCH24PEntry 201326592}

pr1645v2Lan3MCPPPoEMCH24PIfOutBCPkts OBJECT-TYPE
   SYNTAX      Counter64
   MAX-ACCESS  read-only
   STATUS      current
   DESCRIPTION
      "Path: ethernet3.performance.pppoEClient.mibCounters.h24Performance.ifOutBcastPkts

       64 bit unsigned wrappable counter."
   ::= {pr1645v2Lan3MCPPPoEMCH24PEntry 452984832}

pr1645v2Lan3MCPPPoEMCH24PIfOutMCPkts OBJECT-TYPE
   SYNTAX      Counter64
   MAX-ACCESS  read-only
   STATUS      current
   DESCRIPTION
      "Path: ethernet3.performance.pppoEClient.mibCounters.h24Performance.ifOutMcastPkts

       64 bit unsigned wrappable counter."
   ::= {pr1645v2Lan3MCPPPoEMCH24PEntry 469762048}

pr1645v2Lan3MCPPPoEMCH24PIfOutDiscards OBJECT-TYPE
   SYNTAX      Counter64
   MAX-ACCESS  read-only
   STATUS      current
   DESCRIPTION
      "Path: ethernet3.performance.pppoEClient.mibCounters.h24Performance.ifOutDiscards

       64 bit unsigned wrappable counter."
   ::= {pr1645v2Lan3MCPPPoEMCH24PEntry 218103808}

pr1645v2Lan3MCPPPoEMCH24PIfOutErrors OBJECT-TYPE
   SYNTAX      Counter64
   MAX-ACCESS  read-only
   STATUS      current
   DESCRIPTION
      "Path: ethernet3.performance.pppoEClient.mibCounters.h24Performance.ifOutErrors

       64 bit unsigned wrappable counter."
   ::= {pr1645v2Lan3MCPPPoEMCH24PEntry 234881024}

pr1645v2Lan3MCPPPoEMCH24POutDropEx OBJECT-TYPE
   SYNTAX      Counter64
   MAX-ACCESS  read-only
   STATUS      current
   DESCRIPTION
      "Path: ethernet3.performance.pppoEClient.mibCounters.h24Performance.ifOutDropLevelExceeded

       64 bit unsigned wrappable counter."
   ::= {pr1645v2Lan3MCPPPoEMCH24PEntry 352321536}

pr1645v2Lan3MCPPPoEMCH24POutDropNoArp OBJECT-TYPE
   SYNTAX      Counter64
   MAX-ACCESS  read-only
   STATUS      current
   DESCRIPTION
      "Path: ethernet3.performance.pppoEClient.mibCounters.h24Performance.ifOutDiscardsNoArp

       64 bit unsigned wrappable counter."
   ::= {pr1645v2Lan3MCPPPoEMCH24PEntry 369098752}

pr1645v2Lan3MCPPPoEMCH24POutDropFilter OBJECT-TYPE
   SYNTAX      Counter64
   MAX-ACCESS  read-only
   STATUS      current
   DESCRIPTION
      "Path: ethernet3.performance.pppoEClient.mibCounters.h24Performance.ifOutDiscardsFilter

       64 bit unsigned wrappable counter."
   ::= {pr1645v2Lan3MCPPPoEMCH24PEntry 402653184}

pr1645v2Lan3MCPPPoEMCH24PIfOutBandwidth OBJECT-TYPE
   SYNTAX      Integer32
   MAX-ACCESS  read-only
   STATUS      current
   DESCRIPTION
      "Path: ethernet3.performance.pppoEClient.mibCounters.h24Performance.ifOutBandwidth

       unit name = bps
       formula = 8 * ; 8 /"
   ::= {pr1645v2Lan3MCPPPoEMCH24PEntry 285212672}

pr1645v2Lan3MCPPPoEMCH24PIfErrSec OBJECT-TYPE
   SYNTAX      Counter32
   MAX-ACCESS  read-only
   STATUS      current
   DESCRIPTION
      "Path: ethernet3.performance.pppoEClient.mibCounters.h24Performance.ifErrSec

       32 bit unsigned wrappable counter."
   ::= {pr1645v2Lan3MCPPPoEMCH24PEntry 251658240}

pr1645v2Lan3MCPPPoEMCD7P OBJECT-TYPE
   SYNTAX      SEQUENCE OF Pr1645v2Lan3MCPPPoEMCD7PEntry
   MAX-ACCESS  not-accessible
   STATUS      current
   DESCRIPTION
      ""
   ::= {pr1645v2Lan3MCPPPoE 41680896}

pr1645v2Lan3MCPPPoEMCD7PEntry OBJECT-TYPE
   SYNTAX      Pr1645v2Lan3MCPPPoEMCD7PEntry
   MAX-ACCESS  not-accessible
   STATUS      current
   DESCRIPTION
      ""
   INDEX      { pr1645v2Lan3MCPPPoETableIx,
                pr1645v2Lan3MCPPPoEMCD7PTableIx }
   ::= {pr1645v2Lan3MCPPPoEMCD7P 1}

Pr1645v2Lan3MCPPPoEMCD7PEntry ::=
   SEQUENCE
      {
      pr1645v2Lan3MCPPPoEMCD7PTableIx
         TableIndex,
      pr1645v2Lan3MCPPPoEMCD7PSysUpTime
         TimeTicks,
      pr1645v2Lan3MCPPPoEMCD7PIfUpTime
         TimeTicks,
      pr1645v2Lan3MCPPPoEMCD7PIfStatChanges
         Counter32,
      pr1645v2Lan3MCPPPoEMCD7PIfInOctets
         Counter64,
      pr1645v2Lan3MCPPPoEMCD7PIfInUCPkts
         Counter64,
      pr1645v2Lan3MCPPPoEMCD7PIfInNUCPkts
         Counter64,
      pr1645v2Lan3MCPPPoEMCD7PIfInBCPkts
         Counter64,
      pr1645v2Lan3MCPPPoEMCD7PIfInMCPkts
         Counter64,
      pr1645v2Lan3MCPPPoEMCD7PIfInDiscards
         Counter64,
      pr1645v2Lan3MCPPPoEMCD7PIfInErrors
         Counter64,
      pr1645v2Lan3MCPPPoEMCD7PIfInUnkwn
         Counter64,
      pr1645v2Lan3MCPPPoEMCD7PInDropEx
         Counter64,
      pr1645v2Lan3MCPPPoEMCD7PInDropNoMac
         Counter64,
      pr1645v2Lan3MCPPPoEMCD7PInDropNUCast
         Counter64,
      pr1645v2Lan3MCPPPoEMCD7PInDropFilter
         Counter64,
      pr1645v2Lan3MCPPPoEMCD7PIfInBandwidth
         Integer32,
      pr1645v2Lan3MCPPPoEMCD7PIfOutOctets
         Counter64,
      pr1645v2Lan3MCPPPoEMCD7PIfOutUCPkts
         Counter64,
      pr1645v2Lan3MCPPPoEMCD7PIfOutNUCPkts
         Counter64,
      pr1645v2Lan3MCPPPoEMCD7PIfOutBCPkts
         Counter64,
      pr1645v2Lan3MCPPPoEMCD7PIfOutMCPkts
         Counter64,
      pr1645v2Lan3MCPPPoEMCD7PIfOutDiscards
         Counter64,
      pr1645v2Lan3MCPPPoEMCD7PIfOutErrors
         Counter64,
      pr1645v2Lan3MCPPPoEMCD7POutDropEx
         Counter64,
      pr1645v2Lan3MCPPPoEMCD7POutDropNoArp
         Counter64,
      pr1645v2Lan3MCPPPoEMCD7POutDropFilter
         Counter64,
      pr1645v2Lan3MCPPPoEMCD7PIfOutBandwidth
         Integer32,
      pr1645v2Lan3MCPPPoEMCD7PIfErrSec
         Counter32
      }

pr1645v2Lan3MCPPPoEMCD7PTableIx OBJECT-TYPE
   SYNTAX      TableIndex
   MAX-ACCESS  not-accessible
   STATUS      current
   DESCRIPTION
      ""
   ::= {pr1645v2Lan3MCPPPoEMCD7PEntry 11}

pr1645v2Lan3MCPPPoEMCD7PSysUpTime OBJECT-TYPE
   SYNTAX      TimeTicks
   MAX-ACCESS  read-only
   STATUS      current
   DESCRIPTION
      "Path: ethernet3.performance.pppoEClient.mibCounters.d7Performance.sysUpTime

       Time in centi-second."
   ::= {pr1645v2Lan3MCPPPoEMCD7PEntry 16777216}

pr1645v2Lan3MCPPPoEMCD7PIfUpTime OBJECT-TYPE
   SYNTAX      TimeTicks
   MAX-ACCESS  read-only
   STATUS      current
   DESCRIPTION
      "Path: ethernet3.performance.pppoEClient.mibCounters.d7Performance.ifUpTime

       Time in centi-second."
   ::= {pr1645v2Lan3MCPPPoEMCD7PEntry 33554432}

pr1645v2Lan3MCPPPoEMCD7PIfStatChanges OBJECT-TYPE
   SYNTAX      Counter32
   MAX-ACCESS  read-only
   STATUS      current
   DESCRIPTION
      "Path: ethernet3.performance.pppoEClient.mibCounters.d7Performance.ifStatusChanges

       32 bit unsigned wrappable counter."
   ::= {pr1645v2Lan3MCPPPoEMCD7PEntry 50331648}

pr1645v2Lan3MCPPPoEMCD7PIfInOctets OBJECT-TYPE
   SYNTAX      Counter64
   MAX-ACCESS  read-only
   STATUS      current
   DESCRIPTION
      "Path: ethernet3.performance.pppoEClient.mibCounters.d7Performance.ifInOctets

       64 bit unsigned wrappable counter."
   ::= {pr1645v2Lan3MCPPPoEMCD7PEntry 67108864}

pr1645v2Lan3MCPPPoEMCD7PIfInUCPkts OBJECT-TYPE
   SYNTAX      Counter64
   MAX-ACCESS  read-only
   STATUS      current
   DESCRIPTION
      "Path: ethernet3.performance.pppoEClient.mibCounters.d7Performance.ifInUcastPkts

       64 bit unsigned wrappable counter."
   ::= {pr1645v2Lan3MCPPPoEMCD7PEntry 83886080}

pr1645v2Lan3MCPPPoEMCD7PIfInNUCPkts OBJECT-TYPE
   SYNTAX      Counter64
   MAX-ACCESS  read-only
   STATUS      current
   DESCRIPTION
      "Path: ethernet3.performance.pppoEClient.mibCounters.d7Performance.ifInNUcastPkts

       64 bit unsigned wrappable counter."
   ::= {pr1645v2Lan3MCPPPoEMCD7PEntry 100663296}

pr1645v2Lan3MCPPPoEMCD7PIfInBCPkts OBJECT-TYPE
   SYNTAX      Counter64
   MAX-ACCESS  read-only
   STATUS      current
   DESCRIPTION
      "Path: ethernet3.performance.pppoEClient.mibCounters.d7Performance.ifInBcastPkts

       64 bit unsigned wrappable counter."
   ::= {pr1645v2Lan3MCPPPoEMCD7PEntry 419430400}

pr1645v2Lan3MCPPPoEMCD7PIfInMCPkts OBJECT-TYPE
   SYNTAX      Counter64
   MAX-ACCESS  read-only
   STATUS      current
   DESCRIPTION
      "Path: ethernet3.performance.pppoEClient.mibCounters.d7Performance.ifInMcastPkts

       64 bit unsigned wrappable counter."
   ::= {pr1645v2Lan3MCPPPoEMCD7PEntry 436207616}

pr1645v2Lan3MCPPPoEMCD7PIfInDiscards OBJECT-TYPE
   SYNTAX      Counter64
   MAX-ACCESS  read-only
   STATUS      current
   DESCRIPTION
      "Path: ethernet3.performance.pppoEClient.mibCounters.d7Performance.ifInDiscards

       64 bit unsigned wrappable counter."
   ::= {pr1645v2Lan3MCPPPoEMCD7PEntry 117440512}

pr1645v2Lan3MCPPPoEMCD7PIfInErrors OBJECT-TYPE
   SYNTAX      Counter64
   MAX-ACCESS  read-only
   STATUS      current
   DESCRIPTION
      "Path: ethernet3.performance.pppoEClient.mibCounters.d7Performance.ifInErrors

       64 bit unsigned wrappable counter."
   ::= {pr1645v2Lan3MCPPPoEMCD7PEntry 134217728}

pr1645v2Lan3MCPPPoEMCD7PIfInUnkwn OBJECT-TYPE
   SYNTAX      Counter64
   MAX-ACCESS  read-only
   STATUS      current
   DESCRIPTION
      "Path: ethernet3.performance.pppoEClient.mibCounters.d7Performance.ifInUnknownProtos

       64 bit unsigned wrappable counter."
   ::= {pr1645v2Lan3MCPPPoEMCD7PEntry 150994944}

pr1645v2Lan3MCPPPoEMCD7PInDropEx OBJECT-TYPE
   SYNTAX      Counter64
   MAX-ACCESS  read-only
   STATUS      current
   DESCRIPTION
      "Path: ethernet3.performance.pppoEClient.mibCounters.d7Performance.ifInDropLevelExceeded

       64 bit unsigned wrappable counter."
   ::= {pr1645v2Lan3MCPPPoEMCD7PEntry 335544320}

pr1645v2Lan3MCPPPoEMCD7PInDropNoMac OBJECT-TYPE
   SYNTAX      Counter64
   MAX-ACCESS  read-only
   STATUS      current
   DESCRIPTION
      "Path: ethernet3.performance.pppoEClient.mibCounters.d7Performance.fInDiscardsNoMacFit

       64 bit unsigned wrappable counter."
   ::= {pr1645v2Lan3MCPPPoEMCD7PEntry 301989888}

pr1645v2Lan3MCPPPoEMCD7PInDropNUCast OBJECT-TYPE
   SYNTAX      Counter64
   MAX-ACCESS  read-only
   STATUS      current
   DESCRIPTION
      "Path: ethernet3.performance.pppoEClient.mibCounters.d7Performance.fInDiscardsNUCast

       64 bit unsigned wrappable counter."
   ::= {pr1645v2Lan3MCPPPoEMCD7PEntry 318767104}

pr1645v2Lan3MCPPPoEMCD7PInDropFilter OBJECT-TYPE
   SYNTAX      Counter64
   MAX-ACCESS  read-only
   STATUS      current
   DESCRIPTION
      "Path: ethernet3.performance.pppoEClient.mibCounters.d7Performance.fInDiscardsFilter

       64 bit unsigned wrappable counter."
   ::= {pr1645v2Lan3MCPPPoEMCD7PEntry 385875968}

pr1645v2Lan3MCPPPoEMCD7PIfInBandwidth OBJECT-TYPE
   SYNTAX      Integer32
   MAX-ACCESS  read-only
   STATUS      current
   DESCRIPTION
      "Path: ethernet3.performance.pppoEClient.mibCounters.d7Performance.ifInBandwidth

       unit name = bps
       formula = 8 * ; 8 /"
   ::= {pr1645v2Lan3MCPPPoEMCD7PEntry 268435456}

pr1645v2Lan3MCPPPoEMCD7PIfOutOctets OBJECT-TYPE
   SYNTAX      Counter64
   MAX-ACCESS  read-only
   STATUS      current
   DESCRIPTION
      "Path: ethernet3.performance.pppoEClient.mibCounters.d7Performance.ifOutOctets

       64 bit unsigned wrappable counter."
   ::= {pr1645v2Lan3MCPPPoEMCD7PEntry 167772160}

pr1645v2Lan3MCPPPoEMCD7PIfOutUCPkts OBJECT-TYPE
   SYNTAX      Counter64
   MAX-ACCESS  read-only
   STATUS      current
   DESCRIPTION
      "Path: ethernet3.performance.pppoEClient.mibCounters.d7Performance.ifOutUcastPkts

       64 bit unsigned wrappable counter."
   ::= {pr1645v2Lan3MCPPPoEMCD7PEntry 184549376}

pr1645v2Lan3MCPPPoEMCD7PIfOutNUCPkts OBJECT-TYPE
   SYNTAX      Counter64
   MAX-ACCESS  read-only
   STATUS      current
   DESCRIPTION
      "Path: ethernet3.performance.pppoEClient.mibCounters.d7Performance.ifOutNUcastPkts

       64 bit unsigned wrappable counter."
   ::= {pr1645v2Lan3MCPPPoEMCD7PEntry 201326592}

pr1645v2Lan3MCPPPoEMCD7PIfOutBCPkts OBJECT-TYPE
   SYNTAX      Counter64
   MAX-ACCESS  read-only
   STATUS      current
   DESCRIPTION
      "Path: ethernet3.performance.pppoEClient.mibCounters.d7Performance.ifOutBcastPkts

       64 bit unsigned wrappable counter."
   ::= {pr1645v2Lan3MCPPPoEMCD7PEntry 452984832}

pr1645v2Lan3MCPPPoEMCD7PIfOutMCPkts OBJECT-TYPE
   SYNTAX      Counter64
   MAX-ACCESS  read-only
   STATUS      current
   DESCRIPTION
      "Path: ethernet3.performance.pppoEClient.mibCounters.d7Performance.ifOutMcastPkts

       64 bit unsigned wrappable counter."
   ::= {pr1645v2Lan3MCPPPoEMCD7PEntry 469762048}

pr1645v2Lan3MCPPPoEMCD7PIfOutDiscards OBJECT-TYPE
   SYNTAX      Counter64
   MAX-ACCESS  read-only
   STATUS      current
   DESCRIPTION
      "Path: ethernet3.performance.pppoEClient.mibCounters.d7Performance.ifOutDiscards

       64 bit unsigned wrappable counter."
   ::= {pr1645v2Lan3MCPPPoEMCD7PEntry 218103808}

pr1645v2Lan3MCPPPoEMCD7PIfOutErrors OBJECT-TYPE
   SYNTAX      Counter64
   MAX-ACCESS  read-only
   STATUS      current
   DESCRIPTION
      "Path: ethernet3.performance.pppoEClient.mibCounters.d7Performance.ifOutErrors

       64 bit unsigned wrappable counter."
   ::= {pr1645v2Lan3MCPPPoEMCD7PEntry 234881024}

pr1645v2Lan3MCPPPoEMCD7POutDropEx OBJECT-TYPE
   SYNTAX      Counter64
   MAX-ACCESS  read-only
   STATUS      current
   DESCRIPTION
      "Path: ethernet3.performance.pppoEClient.mibCounters.d7Performance.ifOutDropLevelExceeded

       64 bit unsigned wrappable counter."
   ::= {pr1645v2Lan3MCPPPoEMCD7PEntry 352321536}

pr1645v2Lan3MCPPPoEMCD7POutDropNoArp OBJECT-TYPE
   SYNTAX      Counter64
   MAX-ACCESS  read-only
   STATUS      current
   DESCRIPTION
      "Path: ethernet3.performance.pppoEClient.mibCounters.d7Performance.ifOutDiscardsNoArp

       64 bit unsigned wrappable counter."
   ::= {pr1645v2Lan3MCPPPoEMCD7PEntry 369098752}

pr1645v2Lan3MCPPPoEMCD7POutDropFilter OBJECT-TYPE
   SYNTAX      Counter64
   MAX-ACCESS  read-only
   STATUS      current
   DESCRIPTION
      "Path: ethernet3.performance.pppoEClient.mibCounters.d7Performance.ifOutDiscardsFilter

       64 bit unsigned wrappable counter."
   ::= {pr1645v2Lan3MCPPPoEMCD7PEntry 402653184}

pr1645v2Lan3MCPPPoEMCD7PIfOutBandwidth OBJECT-TYPE
   SYNTAX      Integer32
   MAX-ACCESS  read-only
   STATUS      current
   DESCRIPTION
      "Path: ethernet3.performance.pppoEClient.mibCounters.d7Performance.ifOutBandwidth

       unit name = bps
       formula = 8 * ; 8 /"
   ::= {pr1645v2Lan3MCPPPoEMCD7PEntry 285212672}

pr1645v2Lan3MCPPPoEMCD7PIfErrSec OBJECT-TYPE
   SYNTAX      Counter32
   MAX-ACCESS  read-only
   STATUS      current
   DESCRIPTION
      "Path: ethernet3.performance.pppoEClient.mibCounters.d7Performance.ifErrSec

       32 bit unsigned wrappable counter."
   ::= {pr1645v2Lan3MCPPPoEMCD7PEntry 251658240}


pr1645v2Lan3MCIfInHwPriorityQueues OBJECT IDENTIFIER ::= {pr1645v2Lan3MC 132}

pr1645v2Lan3MCIfInHwPriorityQueuesSSCTable OBJECT-TYPE
   SYNTAX      SEQUENCE OF Pr1645v2Lan3MCIfInHwPriorityQueuesEntry
   MAX-ACCESS  not-accessible
   STATUS      current
   DESCRIPTION
      "hwPriorityQueues"
   ::= {pr1645v2Lan3MCIfInHwPriorityQueues 1}

pr1645v2Lan3MCIfInHwPriorityQueuesEntry OBJECT-TYPE
   SYNTAX      Pr1645v2Lan3MCIfInHwPriorityQueuesEntry
   MAX-ACCESS  not-accessible
   STATUS      current
   DESCRIPTION
      ""
   INDEX      { pr1645v2Lan3MCIfInHwPriorityQueuesTableIx }
   ::= {pr1645v2Lan3MCIfInHwPriorityQueuesSSCTable 1}

Pr1645v2Lan3MCIfInHwPriorityQueuesEntry ::=
   SEQUENCE
      {
      pr1645v2Lan3MCIfInHwPriorityQueuesTableIx
         TableIndex,
      pr1645v2Lan3MCIfInHwPriorityQueuesName
         INTEGER,
      pr1645v2Lan3MCIfInHwPriorityQueuesLength
         Integer32,
      pr1645v2Lan3MCIfInHwPriorityQueuesPacketsTotal
         Counter64,
      pr1645v2Lan3MCIfInHwPriorityQueuesOctetsTotal
         Counter64,
      pr1645v2Lan3MCIfInHwPriorityQueuesOctetsBandwidth15sec
         Integer32,
      pr1645v2Lan3MCIfInHwPriorityQueuesOctetsBandwidth30sec
         Integer32,
      pr1645v2Lan3MCIfInHwPriorityQueuesOctetsBandwidth1min
         Integer32,
      pr1645v2Lan3MCIfInHwPriorityQueuesOctetsBandwidth2min
         Integer32,
      pr1645v2Lan3MCIfInHwPriorityQueuesOctetsBandwidth5min
         Integer32
      }

pr1645v2Lan3MCIfInHwPriorityQueuesTableIx OBJECT-TYPE
   SYNTAX      TableIndex
   MAX-ACCESS  not-accessible
   STATUS      current
   DESCRIPTION
      ""
   ::= {pr1645v2Lan3MCIfInHwPriorityQueuesEntry 11}

pr1645v2Lan3MCIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan3MCIfInHwPriorityQueuesEntry 16777216}

pr1645v2Lan3MCIfInHwPriorityQueuesLength OBJECT-TYPE
   SYNTAX      Integer32
   MAX-ACCESS  read-only
   STATUS      current
   DESCRIPTION
      "Path: ethernet3.performance.ifInHwPriorityQueues.length"
   ::= {pr1645v2Lan3MCIfInHwPriorityQueuesEntry 33554432}

pr1645v2Lan3MCIfInHwPriorityQueuesPacketsTotal OBJECT-TYPE
   SYNTAX      Counter64
   MAX-ACCESS  read-only
   STATUS      current
   DESCRIPTION
      "Path: ethernet3.performance.ifInHwPriorityQueues.packets.total

       64 bit unsigned wrappable counter."
   ::= {pr1645v2Lan3MCIfInHwPriorityQueuesEntry 50790400}

pr1645v2Lan3MCIfInHwPriorityQueuesOctetsTotal OBJECT-TYPE
   SYNTAX      Counter64
   MAX-ACCESS  read-only
   STATUS      current
   DESCRIPTION
      "Path: ethernet3.performance.ifInHwPriorityQueues.octets.total

       64 bit unsigned wrappable counter."
   ::= {pr1645v2Lan3MCIfInHwPriorityQueuesEntry 67567616}

pr1645v2Lan3MCIfInHwPriorityQueuesOctetsBandwidth15sec OBJECT-TYPE
   SYNTAX      Integer32
   MAX-ACCESS  read-only
   STATUS      current
   DESCRIPTION
      "Path: ethernet3.performance.ifInHwPriorityQueues.octets.bandwidth.15sec

       unit name = bps
       formula = 8 * ; 8 /"
   ::= {pr1645v2Lan3MCIfInHwPriorityQueuesEntry 70386944}

pr1645v2Lan3MCIfInHwPriorityQueuesOctetsBandwidth30sec OBJECT-TYPE
   SYNTAX      Integer32
   MAX-ACCESS  read-only
   STATUS      current
   DESCRIPTION
      "Path: ethernet3.performance.ifInHwPriorityQueues.octets.bandwidth.30sec

       unit name = bps
       formula = 8 * ; 8 /"
   ::= {pr1645v2Lan3MCIfInHwPriorityQueuesEntry 70388224}

pr1645v2Lan3MCIfInHwPriorityQueuesOctetsBandwidth1min OBJECT-TYPE
   SYNTAX      Integer32
   MAX-ACCESS  read-only
   STATUS      current
   DESCRIPTION
      "Path: ethernet3.performance.ifInHwPriorityQueues.octets.bandwidth.1min

       unit name = bps
       formula = 8 * ; 8 /"
   ::= {pr1645v2Lan3MCIfInHwPriorityQueuesEntry 70390784}

pr1645v2Lan3MCIfInHwPriorityQueuesOctetsBandwidth2min OBJECT-TYPE
   SYNTAX      Integer32
   MAX-ACCESS  read-only
   STATUS      current
   DESCRIPTION
      "Path: ethernet3.performance.ifInHwPriorityQueues.octets.bandwidth.2min

       unit name = bps
       formula = 8 * ; 8 /"
   ::= {pr1645v2Lan3MCIfInHwPriorityQueuesEntry 70395904}

pr1645v2Lan3MCIfInHwPriorityQueuesOctetsBandwidth5min OBJECT-TYPE
   SYNTAX      Integer32
   MAX-ACCESS  read-only
   STATUS      current
   DESCRIPTION
      "Path: ethernet3.performance.ifInHwPriorityQueues.octets.bandwidth.5min

       unit name = bps
       formula = 8 * ; 8 /"
   ::= {pr1645v2Lan3MCIfInHwPriorityQueuesEntry 70411264}

pr1645v2Lan3MCIfInHwPriorityQueuesH2Performance OBJECT-TYPE
   SYNTAX      SEQUENCE OF Pr1645v2Lan3MCIfInHwPriorityQueuesH2PerformanceEntry
   MAX-ACCESS  not-accessible
   STATUS      current
   DESCRIPTION
      ""
   ::= {pr1645v2Lan3MCIfInHwPriorityQueues 83886080}

pr1645v2Lan3MCIfInHwPriorityQueuesH2PerformanceEntry OBJECT-TYPE
   SYNTAX      Pr1645v2Lan3MCIfInHwPriorityQueuesH2PerformanceEntry
   MAX-ACCESS  not-accessible
   STATUS      current
   DESCRIPTION
      ""
   INDEX      { pr1645v2Lan3MCIfInHwPriorityQueuesTableIx,
                pr1645v2Lan3MCIfInHwPriorityQueuesH2PerformanceTableIx }
   ::= {pr1645v2Lan3MCIfInHwPriorityQueuesH2Performance 1}

Pr1645v2Lan3MCIfInHwPriorityQueuesH2PerformanceEntry ::=
   SEQUENCE
      {
      pr1645v2Lan3MCIfInHwPriorityQueuesH2PerformanceTableIx
         TableIndex,
      pr1645v2Lan3MCIfInHwPriorityQueuesH2PerformanceSysUpTime
         TimeTicks,
      pr1645v2Lan3MCIfInHwPriorityQueuesH2PerformanceTotPkts
         Counter64,
      pr1645v2Lan3MCIfInHwPriorityQueuesH2PerformanceTotOcts
         Counter64,
      pr1645v2Lan3MCIfInHwPriorityQueuesH2PerformanceBandwidth
         Integer32
      }

pr1645v2Lan3MCIfInHwPriorityQueuesH2PerformanceTableIx OBJECT-TYPE
   SYNTAX      TableIndex
   MAX-ACCESS  not-accessible
   STATUS      current
   DESCRIPTION
      ""
   ::= {pr1645v2Lan3MCIfInHwPriorityQueuesH2PerformanceEntry 11}

pr1645v2Lan3MCIfInHwPriorityQueuesH2PerformanceSysUpTime OBJECT-TYPE
   SYNTAX      TimeTicks
   MAX-ACCESS  read-only
   STATUS      current
   DESCRIPTION
      "Path: ethernet3.performance.ifInHwPriorityQueues.h2Performance.sysUpTime

       Time in centi-second."
   ::= {pr1645v2Lan3MCIfInHwPriorityQueuesH2PerformanceEntry 16777216}

pr1645v2Lan3MCIfInHwPriorityQueuesH2PerformanceTotPkts OBJECT-TYPE
   SYNTAX      Counter64
   MAX-ACCESS  read-only
   STATUS      current
   DESCRIPTION
      "Path: ethernet3.performance.ifInHwPriorityQueues.h2Performance.totalPkts

       64 bit unsigned wrappable counter."
   ::= {pr1645v2Lan3MCIfInHwPriorityQueuesH2PerformanceEntry 234881024}

pr1645v2Lan3MCIfInHwPriorityQueuesH2PerformanceTotOcts OBJECT-TYPE
   SYNTAX      Counter64
   MAX-ACCESS  read-only
   STATUS      current
   DESCRIPTION
      "Path: ethernet3.performance.ifInHwPriorityQueues.h2Performance.totalOctets

       64 bit unsigned wrappable counter."
   ::= {pr1645v2Lan3MCIfInHwPriorityQueuesH2PerformanceEntry 251658240}

pr1645v2Lan3MCIfInHwPriorityQueuesH2PerformanceBandwidth OBJECT-TYPE
   SYNTAX      Integer32
   MAX-ACCESS  read-only
   STATUS      current
   DESCRIPTION
      "Path: ethernet3.performance.ifInHwPriorityQueues.h2Performance.bandwidth

       unit name = bps
       formula = 8 * ; 8 /"
   ::= {pr1645v2Lan3MCIfInHwPriorityQueuesH2PerformanceEntry 268435456}

pr1645v2Lan3MCIfInHwPriorityQueuesH24Performance OBJECT-TYPE
   SYNTAX      SEQUENCE OF Pr1645v2Lan3MCIfInHwPriorityQueuesH24PerformanceEntry
   MAX-ACCESS  not-accessible
   STATUS      current
   DESCRIPTION
      ""
   ::= {pr1645v2Lan3MCIfInHwPriorityQueues 100663296}

pr1645v2Lan3MCIfInHwPriorityQueuesH24PerformanceEntry OBJECT-TYPE
   SYNTAX      Pr1645v2Lan3MCIfInHwPriorityQueuesH24PerformanceEntry
   MAX-ACCESS  not-accessible
   STATUS      current
   DESCRIPTION
      ""
   INDEX      { pr1645v2Lan3MCIfInHwPriorityQueuesTableIx,
                pr1645v2Lan3MCIfInHwPriorityQueuesH24PerformanceTableIx }
   ::= {pr1645v2Lan3MCIfInHwPriorityQueuesH24Performance 1}

Pr1645v2Lan3MCIfInHwPriorityQueuesH24PerformanceEntry ::=
   SEQUENCE
      {
      pr1645v2Lan3MCIfInHwPriorityQueuesH24PerformanceTableIx
         TableIndex,
      pr1645v2Lan3MCIfInHwPriorityQueuesH24PerformanceSysUpTime
         TimeTicks,
      pr1645v2Lan3MCIfInHwPriorityQueuesH24PerformanceTotPkts
         Counter64,
      pr1645v2Lan3MCIfInHwPriorityQueuesH24PerformanceTotOcts
         Counter64,
      pr1645v2Lan3MCIfInHwPriorityQueuesH24PerformanceBandwidth
         Integer32
      }

pr1645v2Lan3MCIfInHwPriorityQueuesH24PerformanceTableIx OBJECT-TYPE
   SYNTAX      TableIndex
   MAX-ACCESS  not-accessible
   STATUS      current
   DESCRIPTION
      ""
   ::= {pr1645v2Lan3MCIfInHwPriorityQueuesH24PerformanceEntry 11}

pr1645v2Lan3MCIfInHwPriorityQueuesH24PerformanceSysUpTime OBJECT-TYPE
   SYNTAX      TimeTicks
   MAX-ACCESS  read-only
   STATUS      current
   DESCRIPTION
      "Path: ethernet3.performance.ifInHwPriorityQueues.h24Performance.sysUpTime

       Time in centi-second."
   ::= {pr1645v2Lan3MCIfInHwPriorityQueuesH24PerformanceEntry 16777216}

pr1645v2Lan3MCIfInHwPriorityQueuesH24PerformanceTotPkts OBJECT-TYPE
   SYNTAX      Counter64
   MAX-ACCESS  read-only
   STATUS      current
   DESCRIPTION
      "Path: ethernet3.performance.ifInHwPriorityQueues.h24Performance.totalPkts

       64 bit unsigned wrappable counter."
   ::= {pr1645v2Lan3MCIfInHwPriorityQueuesH24PerformanceEntry 234881024}

pr1645v2Lan3MCIfInHwPriorityQueuesH24PerformanceTotOcts OBJECT-TYPE
   SYNTAX      Counter64
   MAX-ACCESS  read-only
   STATUS      current
   DESCRIPTION
      "Path: ethernet3.performance.ifInHwPriorityQueues.h24Performance.totalOctets

       64 bit unsigned wrappable counter."
   ::= {pr1645v2Lan3MCIfInHwPriorityQueuesH24PerformanceEntry 251658240}

pr1645v2Lan3MCIfInHwPriorityQueuesH24PerformanceBandwidth OBJECT-TYPE
   SYNTAX      Integer32
   MAX-ACCESS  read-only
   STATUS      current
   DESCRIPTION
      "Path: ethernet3.performance.ifInHwPriorityQueues.h24Performance.bandwidth

       unit name = bps
       formula = 8 * ; 8 /"
   ::= {pr1645v2Lan3MCIfInHwPriorityQueuesH24PerformanceEntry 268435456}

pr1645v2Lan3MCIfInHwPriorityQueuesD7Performance OBJECT-TYPE
   SYNTAX      SEQUENCE OF Pr1645v2Lan3MCIfInHwPriorityQueuesD7PerformanceEntry
   MAX-ACCESS  not-accessible
   STATUS      current
   DESCRIPTION
      ""
   ::= {pr1645v2Lan3MCIfInHwPriorityQueues 117440512}

pr1645v2Lan3MCIfInHwPriorityQueuesD7PerformanceEntry OBJECT-TYPE
   SYNTAX      Pr1645v2Lan3MCIfInHwPriorityQueuesD7PerformanceEntry
   MAX-ACCESS  not-accessible
   STATUS      current
   DESCRIPTION
      ""
   INDEX      { pr1645v2Lan3MCIfInHwPriorityQueuesTableIx,
                pr1645v2Lan3MCIfInHwPriorityQueuesD7PerformanceTableIx }
   ::= {pr1645v2Lan3MCIfInHwPriorityQueuesD7Performance 1}

Pr1645v2Lan3MCIfInHwPriorityQueuesD7PerformanceEntry ::=
   SEQUENCE
      {
      pr1645v2Lan3MCIfInHwPriorityQueuesD7PerformanceTableIx
         TableIndex,
      pr1645v2Lan3MCIfInHwPriorityQueuesD7PerformanceSysUpTime
         TimeTicks,
      pr1645v2Lan3MCIfInHwPriorityQueuesD7PerformanceTotPkts
         Counter64,
      pr1645v2Lan3MCIfInHwPriorityQueuesD7PerformanceTotOcts
         Counter64,
      pr1645v2Lan3MCIfInHwPriorityQueuesD7PerformanceBandwidth
         Integer32
      }

pr1645v2Lan3MCIfInHwPriorityQueuesD7PerformanceTableIx OBJECT-TYPE
   SYNTAX      TableIndex
   MAX-ACCESS  not-accessible
   STATUS      current
   DESCRIPTION
      ""
   ::= {pr1645v2Lan3MCIfInHwPriorityQueuesD7PerformanceEntry 11}

pr1645v2Lan3MCIfInHwPriorityQueuesD7PerformanceSysUpTime OBJECT-TYPE
   SYNTAX      TimeTicks
   MAX-ACCESS  read-only
   STATUS      current
   DESCRIPTION
      "Path: ethernet3.performance.ifInHwPriorityQueues.d7Performance.sysUpTime

       Time in centi-second."
   ::= {pr1645v2Lan3MCIfInHwPriorityQueuesD7PerformanceEntry 16777216}

pr1645v2Lan3MCIfInHwPriorityQueuesD7PerformanceTotPkts OBJECT-TYPE
   SYNTAX      Counter64
   MAX-ACCESS  read-only
   STATUS      current
   DESCRIPTION
      "Path: ethernet3.performance.ifInHwPriorityQueues.d7Performance.totalPkts

       64 bit unsigned wrappable counter."
   ::= {pr1645v2Lan3MCIfInHwPriorityQueuesD7PerformanceEntry 234881024}

pr1645v2Lan3MCIfInHwPriorityQueuesD7PerformanceTotOcts OBJECT-TYPE
   SYNTAX      Counter64
   MAX-ACCESS  read-only
   STATUS      current
   DESCRIPTION
      "Path: ethernet3.performance.ifInHwPriorityQueues.d7Performance.totalOctets

       64 bit unsigned wrappable counter."
   ::= {pr1645v2Lan3MCIfInHwPriorityQueuesD7PerformanceEntry 251658240}

pr1645v2Lan3MCIfInHwPriorityQueuesD7PerformanceBandwidth OBJECT-TYPE
   SYNTAX      Integer32
   MAX-ACCESS  read-only
   STATUS      current
   DESCRIPTION
      "Path: ethernet3.performance.ifInHwPriorityQueues.d7Performance.bandwidth

       unit name = bps
       formula = 8 * ; 8 /"
   ::= {pr1645v2Lan3MCIfInHwPriorityQueuesD7PerformanceEntry 268435456}



ar1645v2Lan3MC OBJECT IDENTIFIER ::= {r1645v2Lan3MC 16}


ar1645v2Lan3MCClearCounters OBJECT-TYPE
   SYNTAX      Integer32
   MAX-ACCESS  read-write
   STATUS      current
   DESCRIPTION
      "Path: ethernet3.actions.clearCounters
       Info: reset counters"
   ::= {ar1645v2Lan3MC 263}


ar1645v2Lan3MCPowerToggle OBJECT-TYPE
   SYNTAX      Integer32
   MAX-ACCESS  read-write
   STATUS      current
   DESCRIPTION
      "Path: ethernet3.actions.powerToggle
       Info: action in the debug group"
   ::= {ar1645v2Lan3MC 68}


ar1645v2Lan3MCRestartIntf OBJECT-TYPE
   SYNTAX      Integer32
   MAX-ACCESS  read-write
   STATUS      current
   DESCRIPTION
      "Path: ethernet3.actions.restartIntf
       Info: action in the debug group"
   ::= {ar1645v2Lan3MC 67}


ar1645v2Lan3MCClearOamEventLog OBJECT-TYPE
   SYNTAX      Integer32
   MAX-ACCESS  read-write
   STATUS      current
   DESCRIPTION
      "Path: ethernet3.actions.clearOamEventLog
       Info: clear the OAM event log"
   ::= {ar1645v2Lan3MC 916}


ar1645v2Lan3MCLoopback OBJECT-TYPE
   SYNTAX      Integer32
   MAX-ACCESS  read-write
   STATUS      current
   DESCRIPTION
      "Path: ethernet3.actions.loopback
       Info: ethernet loopback"
   ::= {ar1645v2Lan3MC 914}


ar1645v2Lan3MCLoop OBJECT IDENTIFIER ::= {ar1645v2Lan3MC 915}

ar1645v2Lan3MCLoopSSC OBJECT IDENTIFIER ::= {ar1645v2Lan3MCLoop 1}

ar1645v2Lan3MCLoopEntry OBJECT IDENTIFIER ::= {ar1645v2Lan3MCLoopSSC 1}

ar1645v2Lan3MCLoopAction OBJECT-TYPE
   SYNTAX      INTEGER
               {
               start (1),
               stop (2)
               }
   MAX-ACCESS  read-write
   STATUS      current
   DESCRIPTION
      "Path: ethernet3.actions.loop.action

       Possibilities:
               start   (1)
               stop   (2)"
   ::= {ar1645v2Lan3MCLoopEntry 16777216}

ar1645v2Lan3MCLoopTime OBJECT-TYPE
   SYNTAX      TimeTicks
   MAX-ACCESS  read-write
   STATUS      current
   DESCRIPTION
      "Path: ethernet3.actions.loop.time

       Time in centi-second."
   ::= {ar1645v2Lan3MCLoopEntry 50331648}

ar1645v2Lan3MCLoopIntfName OBJECT-TYPE
   SYNTAX      DisplayString
   MAX-ACCESS  read-write
   STATUS      current
   DESCRIPTION
      "Path: ethernet3.actions.loop.intfName"
   ::= {ar1645v2Lan3MCLoopEntry 67108864}


ar1645v2Lan3MCOamRemLoopback OBJECT-TYPE
   SYNTAX      Integer32
   MAX-ACCESS  read-write
   STATUS      current
   DESCRIPTION
      "Path: ethernet3.actions.oamRemLoopback
       Info: OAM Remote Loopback"
   ::= {ar1645v2Lan3MC 912}


ar1645v2Lan3MCType OBJECT-TYPE
   SYNTAX      INTEGER
               {
               start (0),
               stop (1)
               }
   MAX-ACCESS  read-write
   STATUS      current
   DESCRIPTION
      "Path: ethernet3.actions.type
       Info: OAM Remote Loopback type

       Possibilities:
               start   (0)
               stop   (1)"
   ::= {ar1645v2Lan3MC 913}


ar1645v2Lan3MCSendWOL OBJECT-TYPE
   SYNTAX      Integer32
   MAX-ACCESS  read-write
   STATUS      current
   DESCRIPTION
      "Path: ethernet3.actions.sendWOL
       Info: send a WakeOnLan message on this interface"
   ::= {ar1645v2Lan3MC 333}


ar1645v2Lan3MCWolInfo OBJECT IDENTIFIER ::= {ar1645v2Lan3MC 332}

ar1645v2Lan3MCWolInfoSSC OBJECT IDENTIFIER ::= {ar1645v2Lan3MCWolInfo 1}

ar1645v2Lan3MCWolInfoEntry OBJECT IDENTIFIER ::= {ar1645v2Lan3MCWolInfoSSC 1}

ar1645v2Lan3MCWolInfoTargetMAC OBJECT-TYPE
   SYNTAX      OCTET STRING
   MAX-ACCESS  read-write
   STATUS      current
   DESCRIPTION
      "Path: ethernet3.actions.wolInfo.targetMAC

       MAC address."
   ::= {ar1645v2Lan3MCWolInfoEntry 16777216}

ar1645v2Lan3MCWolInfoPassword OBJECT-TYPE
   SYNTAX      OCTET STRING
   MAX-ACCESS  read-write
   STATUS      current
   DESCRIPTION
      "Path: ethernet3.actions.wolInfo.password"
   ::= {ar1645v2Lan3MCWolInfoEntry 33554432}


ar1645v2Lan3MCClearArpCache OBJECT-TYPE
   SYNTAX      Integer32
   MAX-ACCESS  read-write
   STATUS      current
   DESCRIPTION
      "Path: ethernet3.actions.clearArpCache
       Info: clear all dynamic enties in ARP cache table"
   ::= {ar1645v2Lan3MC 25}


ar1645v2Lan3MCClearDebugCounters OBJECT-TYPE
   SYNTAX      Integer32
   MAX-ACCESS  read-write
   STATUS      current
   DESCRIPTION
      "Path: ethernet3.actions.clearDebugCounters
       Info: action in the debug group"
   ::= {ar1645v2Lan3MC 76}


ar1645v2Lan3MCEnableRds OBJECT-TYPE
   SYNTAX      Integer32
   MAX-ACCESS  read-write
   STATUS      current
   DESCRIPTION
      "Path: ethernet3.actions.enableRds
       Info: action in the debug group"
   ::= {ar1645v2Lan3MC 367}


ar1645v2Lan3MCDisableRds OBJECT-TYPE
   SYNTAX      Integer32
   MAX-ACCESS  read-write
   STATUS      current
   DESCRIPTION
      "Path: ethernet3.actions.disableRds
       Info: action in the debug group"
   ::= {ar1645v2Lan3MC 366}


ar1645v2Lan3MCEnableTds OBJECT-TYPE
   SYNTAX      Integer32
   MAX-ACCESS  read-write
   STATUS      current
   DESCRIPTION
      "Path: ethernet3.actions.enableTds
       Info: action in the debug group"
   ::= {ar1645v2Lan3MC 365}


ar1645v2Lan3MCDisableTds OBJECT-TYPE
   SYNTAX      Integer32
   MAX-ACCESS  read-write
   STATUS      current
   DESCRIPTION
      "Path: ethernet3.actions.disableTds
       Info: action in the debug group"
   ::= {ar1645v2Lan3MC 364}


ar1645v2Lan3MCClearTsecStats OBJECT-TYPE
   SYNTAX      Integer32
   MAX-ACCESS  read-write
   STATUS      current
   DESCRIPTION
      "Path: ethernet3.actions.clearTsecStats
       Info: action in the debug group"
   ::= {ar1645v2Lan3MC 363}


ar1645v2Lan3MCStopTsecStats OBJECT-TYPE
   SYNTAX      Integer32
   MAX-ACCESS  read-write
   STATUS      current
   DESCRIPTION
      "Path: ethernet3.actions.stopTsecStats
       Info: action in the debug group"
   ::= {ar1645v2Lan3MC 362}


ar1645v2Lan3MCStartTsecStats OBJECT-TYPE
   SYNTAX      Integer32
   MAX-ACCESS  read-write
   STATUS      current
   DESCRIPTION
      "Path: ethernet3.actions.startTsecStats
       Info: action in the debug group"
   ::= {ar1645v2Lan3MC 361}


ar1645v2Lan3MCPhyAction OBJECT-TYPE
   SYNTAX      Integer32
   MAX-ACCESS  read-write
   STATUS      current
   DESCRIPTION
      "Path: ethernet3.actions.phyAction
       Info: action in the debug group"
   ::= {ar1645v2Lan3MC 90}



fr1645v2Lan3MC OBJECT IDENTIFIER ::= {r1645v2Lan3MC 13}


fr1645v2Lan3MCAlarm OBJECT IDENTIFIER ::= {fr1645v2Lan3MC 207}

fr1645v2Lan3MCAlarmSSC OBJECT IDENTIFIER ::= {fr1645v2Lan3MCAlarm 1}

fr1645v2Lan3MCAlarmEntry OBJECT IDENTIFIER ::= {fr1645v2Lan3MCAlarmSSC 1}

fr1645v2Lan3MCAlarmDiscriminator OBJECT-TYPE
   SYNTAX      Integer32
   MAX-ACCESS  read-only
   STATUS      current
   DESCRIPTION
      "Path: ethernet3.alarms.alarmInfo.discriminator"
   ::= {fr1645v2Lan3MCAlarmEntry 16777216}

fr1645v2Lan3MCAlarmCurrent OBJECT-TYPE
   SYNTAX      Integer32
   MAX-ACCESS  read-only
   STATUS      current
   DESCRIPTION
      "Path: ethernet3.alarms.alarmInfo.currentAlarms

       Bit meanings:
               bit 0 = linkDown,
               bit 9 = pppoEDown"
   ::= {fr1645v2Lan3MCAlarmEntry 33554432}

fr1645v2Lan3MCAlarmPrevious OBJECT-TYPE
   SYNTAX      Integer32
   MAX-ACCESS  read-only
   STATUS      current
   DESCRIPTION
      "Path: ethernet3.alarms.alarmInfo.previousAlarms

       Bit meanings:
               bit 0 = linkDown,
               bit 9 = pppoEDown"
   ::= {fr1645v2Lan3MCAlarmEntry 50331648}

fr1645v2Lan3MCAlarmMask OBJECT-TYPE
   SYNTAX      Integer32
   MAX-ACCESS  read-only
   STATUS      current
   DESCRIPTION
      "Path: ethernet3.alarms.alarmInfo.alarmMask

       Bit meanings:
               bit 0 = linkDown,
               bit 9 = pppoEDown"
   ::= {fr1645v2Lan3MCAlarmEntry 67108864}

fr1645v2Lan3MCAlarmLevLinkDown OBJECT-TYPE
   SYNTAX      Integer32
   MAX-ACCESS  read-only
   STATUS      current
   DESCRIPTION
      "Path: ethernet3.alarms.alarmInfo.alarmLevel.linkDown"
   ::= {fr1645v2Lan3MCAlarmEntry 83951616}

fr1645v2Lan3MCAlarmLevPppoEDown OBJECT-TYPE
   SYNTAX      Integer32
   MAX-ACCESS  read-only
   STATUS      current
   DESCRIPTION
      "Path: ethernet3.alarms.alarmInfo.alarmLevel.pppoEDown"
   ::= {fr1645v2Lan3MCAlarmEntry 84541440}


fr1645v2Lan3MCAlarmE2 OBJECT IDENTIFIER ::= {fr1645v2Lan3MCAlarm 2}

fr1645v2Lan3MCAlarmE2Entry OBJECT IDENTIFIER ::= {fr1645v2Lan3MCAlarmE2 1}

fr1645v2Lan3MCAlarmE2LinkDown OBJECT IDENTIFIER ::= {fr1645v2Lan3MCAlarmE2Entry 10}

fr1645v2Lan3MCAlarmE2LinkDownPfx OBJECT IDENTIFIER ::= {fr1645v2Lan3MCAlarmE2LinkDown 0}

fr1645v2Lan3MCAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lan3GigaMC'
                (root='router1645') has changed from the ON to the OFF state."
   ::= {fr1645v2Lan3MCAlarmE2LinkDownPfx 1}

fr1645v2Lan3MCAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lan3GigaMC'
                (root='router1645') has changed from the OFF to the ON state."
   ::= {fr1645v2Lan3MCAlarmE2LinkDownPfx 2}

fr1645v2Lan3MCAlarmE2PppoEDown OBJECT IDENTIFIER ::= {fr1645v2Lan3MCAlarmE2Entry 19}

fr1645v2Lan3MCAlarmE2PppoEDownPfx OBJECT IDENTIFIER ::= {fr1645v2Lan3MCAlarmE2PppoEDown 0}

fr1645v2Lan3MCAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lan3GigaMC'
                (root='router1645') has changed from the ON to the OFF state."
   ::= {fr1645v2Lan3MCAlarmE2PppoEDownPfx 1}

fr1645v2Lan3MCAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lan3GigaMC'
                (root='router1645') has changed from the OFF to the ON state."
   ::= {fr1645v2Lan3MCAlarmE2PppoEDownPfx 2}



END
