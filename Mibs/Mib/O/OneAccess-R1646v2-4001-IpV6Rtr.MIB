OneAccess-R1646v2-4001-IpV6Rtr DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2IpV6Rtr OBJECT IDENTIFIER ::= {r1646Rootv2 4001}

r1646v2IpV6RtrMOProp OBJECT IDENTIFIER ::= {r1646v2IpV6Rtr 1}

r1646v2IpV6RtrMOPropEntry OBJECT IDENTIFIER ::= {r1646v2IpV6RtrMOProp 1}

r1646v2IpV6RtrMOPropPath OBJECT-TYPE
   SYNTAX      ContainmentPath
   MAX-ACCESS  read-only
   STATUS      current
   DESCRIPTION
      "Textual description of the containment tree from the instance of
       the root object down to the instance of the current object."
   ::= {r1646v2IpV6RtrMOPropEntry 3}

r1646v2IpV6RtrMOPropRev OBJECT-TYPE
   SYNTAX      ObjectRevision
   MAX-ACCESS  read-only
   STATUS      current
   DESCRIPTION
      "This value corresponds with the revision of the MANAGED OBJECT."
   ::= {r1646v2IpV6RtrMOPropEntry 4}



er1646v2IpV6Rtr OBJECT IDENTIFIER ::= {r1646v2IpV6Rtr 11}


er1646v2IpV6RtrRoutingTable OBJECT IDENTIFIER ::= {er1646v2IpV6Rtr 2}

er1646v2IpV6RtrRoutingTableSSCTable OBJECT-TYPE
   SYNTAX      SEQUENCE OF Er1646v2IpV6RtrRoutingTableEntry
   MAX-ACCESS  not-accessible
   STATUS      current
   DESCRIPTION
      "ipV6 static route configuration"
   ::= {er1646v2IpV6RtrRoutingTable 1}

er1646v2IpV6RtrRoutingTableEntry OBJECT-TYPE
   SYNTAX      Er1646v2IpV6RtrRoutingTableEntry
   MAX-ACCESS  not-accessible
   STATUS      current
   DESCRIPTION
      ""
   INDEX      { er1646v2IpV6RtrRoutingTableTableIx }
   ::= {er1646v2IpV6RtrRoutingTableSSCTable 1}

Er1646v2IpV6RtrRoutingTableEntry ::=
   SEQUENCE
      {
      er1646v2IpV6RtrRoutingTableActions
         VariableLengthTableActions,
      er1646v2IpV6RtrRoutingTableTableIx
         TableIndex,
      er1646v2IpV6RtrRoutingTableAddress
         Ipv6Address,
      er1646v2IpV6RtrRoutingTablePrefixLength
         Integer32,
      er1646v2IpV6RtrRoutingTableNextHop
         Ipv6Address,
      er1646v2IpV6RtrRoutingTableInterface
         DisplayString,
      er1646v2IpV6RtrRoutingTablePreference
         Integer32,
      er1646v2IpV6RtrRoutingTableMetric
         Integer32,
      er1646v2IpV6RtrRoutingTableRemark
         DisplayString
      }

er1646v2IpV6RtrRoutingTableActions OBJECT-TYPE
   SYNTAX      VariableLengthTableActions
   MAX-ACCESS  read-write
   STATUS      current
   DESCRIPTION
      "By way of this field, some manipulations
       on this table may be performed."
   ::= {er1646v2IpV6RtrRoutingTableEntry 2}

er1646v2IpV6RtrRoutingTableTableIx OBJECT-TYPE
   SYNTAX      TableIndex
   MAX-ACCESS  not-accessible
   STATUS      current
   DESCRIPTION
      ""
   ::= {er1646v2IpV6RtrRoutingTableEntry 11}

er1646v2IpV6RtrRoutingTableAddress OBJECT-TYPE
   SYNTAX      Ipv6Address
   MAX-ACCESS  read-write
   STATUS      current
   DESCRIPTION
      "Path: v6Router.editConf.routingTable.address

       ipv6 address"
   ::= {er1646v2IpV6RtrRoutingTableEntry 16777216}

er1646v2IpV6RtrRoutingTablePrefixLength OBJECT-TYPE
   SYNTAX      Integer32
   MAX-ACCESS  read-write
   STATUS      current
   DESCRIPTION
      "Path: v6Router.editConf.routingTable.prefixLength"
   ::= {er1646v2IpV6RtrRoutingTableEntry 33554432}

er1646v2IpV6RtrRoutingTableNextHop OBJECT-TYPE
   SYNTAX      Ipv6Address
   MAX-ACCESS  read-write
   STATUS      current
   DESCRIPTION
      "Path: v6Router.editConf.routingTable.nextHop

       ipv6 address"
   ::= {er1646v2IpV6RtrRoutingTableEntry 50331648}

er1646v2IpV6RtrRoutingTableInterface OBJECT-TYPE
   SYNTAX      DisplayString
   MAX-ACCESS  read-write
   STATUS      current
   DESCRIPTION
      "Path: v6Router.editConf.routingTable.interface"
   ::= {er1646v2IpV6RtrRoutingTableEntry 67108864}

er1646v2IpV6RtrRoutingTablePreference OBJECT-TYPE
   SYNTAX      Integer32
   MAX-ACCESS  read-write
   STATUS      current
   DESCRIPTION
      "Path: v6Router.editConf.routingTable.preference"
   ::= {er1646v2IpV6RtrRoutingTableEntry 83886080}

er1646v2IpV6RtrRoutingTableMetric OBJECT-TYPE
   SYNTAX      Integer32
   MAX-ACCESS  read-write
   STATUS      current
   DESCRIPTION
      "Path: v6Router.editConf.routingTable.metric"
   ::= {er1646v2IpV6RtrRoutingTableEntry 100663296}

er1646v2IpV6RtrRoutingTableRemark OBJECT-TYPE
   SYNTAX      DisplayString
   MAX-ACCESS  read-write
   STATUS      current
   DESCRIPTION
      "Path: v6Router.editConf.routingTable.remark"
   ::= {er1646v2IpV6RtrRoutingTableEntry 1157627904}


er1646v2IpV6RtrType0Routing OBJECT-TYPE
   SYNTAX      INTEGER
               {
               disabled (0),
               enabled (1)
               }
   MAX-ACCESS  read-write
   STATUS      current
   DESCRIPTION
      "Path: v6Router.editConf.type0Routing
       Info: enable support for type0 routing header

       Possibilities:
               disabled   (0)
               enabled   (1)"
   ::= {er1646v2IpV6Rtr 3}


er1646v2IpV6RtrMaxPendingFrags OBJECT-TYPE
   SYNTAX      Integer32
   MAX-ACCESS  read-write
   STATUS      current
   DESCRIPTION
      "Path: v6Router.editConf.maxPendingFrags
       Info: limit the number of pending fragments"
   ::= {er1646v2IpV6Rtr 4}


er1646v2IpV6RtrGeneralPrefixes OBJECT IDENTIFIER ::= {er1646v2IpV6Rtr 5}

er1646v2IpV6RtrGeneralPrefixesSSCTable OBJECT-TYPE
   SYNTAX      SEQUENCE OF Er1646v2IpV6RtrGeneralPrefixesEntry
   MAX-ACCESS  not-accessible
   STATUS      current
   DESCRIPTION
      "ipV6 prefix pool config"
   ::= {er1646v2IpV6RtrGeneralPrefixes 1}

er1646v2IpV6RtrGeneralPrefixesEntry OBJECT-TYPE
   SYNTAX      Er1646v2IpV6RtrGeneralPrefixesEntry
   MAX-ACCESS  not-accessible
   STATUS      current
   DESCRIPTION
      ""
   INDEX      { er1646v2IpV6RtrGeneralPrefixesTableIx }
   ::= {er1646v2IpV6RtrGeneralPrefixesSSCTable 1}

Er1646v2IpV6RtrGeneralPrefixesEntry ::=
   SEQUENCE
      {
      er1646v2IpV6RtrGeneralPrefixesActions
         VariableLengthTableActions,
      er1646v2IpV6RtrGeneralPrefixesTableIx
         TableIndex,
      er1646v2IpV6RtrGeneralPrefixesName
         DisplayString,
      er1646v2IpV6RtrGeneralPrefixesType
         INTEGER,
      er1646v2IpV6RtrGeneralPrefixesPrefix
         Ipv6Address,
      er1646v2IpV6RtrGeneralPrefixesPrefixLength
         Integer32,
      er1646v2IpV6RtrGeneralPrefixesAuto6to4Auto6to4Intf
         DisplayString,
      er1646v2IpV6RtrGeneralPrefixesAuto6to4IpV4Address
         IpAddress,
      er1646v2IpV6RtrGeneralPrefixesAuto6to4Subnet
         OCTET STRING
      }

er1646v2IpV6RtrGeneralPrefixesActions OBJECT-TYPE
   SYNTAX      VariableLengthTableActions
   MAX-ACCESS  read-write
   STATUS      current
   DESCRIPTION
      "By way of this field, some manipulations
       on this table may be performed."
   ::= {er1646v2IpV6RtrGeneralPrefixesEntry 2}

er1646v2IpV6RtrGeneralPrefixesTableIx OBJECT-TYPE
   SYNTAX      TableIndex
   MAX-ACCESS  not-accessible
   STATUS      current
   DESCRIPTION
      ""
   ::= {er1646v2IpV6RtrGeneralPrefixesEntry 11}

er1646v2IpV6RtrGeneralPrefixesName OBJECT-TYPE
   SYNTAX      DisplayString
   MAX-ACCESS  read-write
   STATUS      current
   DESCRIPTION
      "Path: v6Router.editConf.generalPrefixes.name"
   ::= {er1646v2IpV6RtrGeneralPrefixesEntry 16777216}

er1646v2IpV6RtrGeneralPrefixesType OBJECT-TYPE
   SYNTAX      INTEGER
               {
               static (0),
               auto6to4 (2)
               }
   MAX-ACCESS  read-write
   STATUS      current
   DESCRIPTION
      "Path: v6Router.editConf.generalPrefixes.type

       Possibilities:
               static   (0)
               auto6to4   (2)"
   ::= {er1646v2IpV6RtrGeneralPrefixesEntry 67108864}

er1646v2IpV6RtrGeneralPrefixesPrefix OBJECT-TYPE
   SYNTAX      Ipv6Address
   MAX-ACCESS  read-write
   STATUS      current
   DESCRIPTION
      "Path: v6Router.editConf.generalPrefixes.prefix

       ipv6 address"
   ::= {er1646v2IpV6RtrGeneralPrefixesEntry 33554432}

er1646v2IpV6RtrGeneralPrefixesPrefixLength OBJECT-TYPE
   SYNTAX      Integer32
   MAX-ACCESS  read-write
   STATUS      current
   DESCRIPTION
      "Path: v6Router.editConf.generalPrefixes.prefixLength"
   ::= {er1646v2IpV6RtrGeneralPrefixesEntry 50331648}

er1646v2IpV6RtrGeneralPrefixesAuto6to4Auto6to4Intf OBJECT-TYPE
   SYNTAX      DisplayString
   MAX-ACCESS  read-write
   STATUS      current
   DESCRIPTION
      "Path: v6Router.editConf.generalPrefixes.auto6to4.auto6to4Intf"
   ::= {er1646v2IpV6RtrGeneralPrefixesEntry 84082688}

er1646v2IpV6RtrGeneralPrefixesAuto6to4IpV4Address OBJECT-TYPE
   SYNTAX      IpAddress
   MAX-ACCESS  read-write
   STATUS      current
   DESCRIPTION
      "Path: v6Router.editConf.generalPrefixes.auto6to4.ipV4Address"
   ::= {er1646v2IpV6RtrGeneralPrefixesEntry 83951616}

er1646v2IpV6RtrGeneralPrefixesAuto6to4Subnet OBJECT-TYPE
   SYNTAX      OCTET STRING
   MAX-ACCESS  read-write
   STATUS      current
   DESCRIPTION
      "Path: v6Router.editConf.generalPrefixes.auto6to4.subnet"
   ::= {er1646v2IpV6RtrGeneralPrefixesEntry 84017152}


er1646v2IpV6RtrDns OBJECT IDENTIFIER ::= {er1646v2IpV6Rtr 6}

er1646v2IpV6RtrDnsSSC OBJECT IDENTIFIER ::= {er1646v2IpV6RtrDns 1}

er1646v2IpV6RtrDnsEntry OBJECT IDENTIFIER ::= {er1646v2IpV6RtrDnsSSC 1}

er1646v2IpV6RtrDnsDomainName OBJECT-TYPE
   SYNTAX      DisplayString
   MAX-ACCESS  read-write
   STATUS      current
   DESCRIPTION
      "Path: v6Router.editConf.dns.domainName"
   ::= {er1646v2IpV6RtrDnsEntry 33554432}

er1646v2IpV6RtrDnsIpV4Router OBJECT-TYPE
   SYNTAX      DisplayString
   MAX-ACCESS  read-write
   STATUS      current
   DESCRIPTION
      "Path: v6Router.editConf.dns.ipV4Router"
   ::= {er1646v2IpV6RtrDnsEntry 67108864}

er1646v2IpV6RtrDnsProxy OBJECT-TYPE
   SYNTAX      INTEGER
               {
               disabled (0),
               enabled (1)
               }
   MAX-ACCESS  read-write
   STATUS      current
   DESCRIPTION
      "Path: v6Router.editConf.dns.proxy

       Possibilities:
               disabled   (0)
               enabled   (1)"
   ::= {er1646v2IpV6RtrDnsEntry 83886080}

er1646v2IpV6RtrDnsCacheSize OBJECT-TYPE
   SYNTAX      Integer32
   MAX-ACCESS  read-write
   STATUS      current
   DESCRIPTION
      "Path: v6Router.editConf.dns.cacheSize"
   ::= {er1646v2IpV6RtrDnsEntry 100663296}

er1646v2IpV6RtrDnsServers OBJECT-TYPE
   SYNTAX      SEQUENCE OF Er1646v2IpV6RtrDnsServersEntry
   MAX-ACCESS  not-accessible
   STATUS      current
   DESCRIPTION
      ""
   ::= {er1646v2IpV6RtrDns 16777216}

er1646v2IpV6RtrDnsServersEntry OBJECT-TYPE
   SYNTAX      Er1646v2IpV6RtrDnsServersEntry
   MAX-ACCESS  not-accessible
   STATUS      current
   DESCRIPTION
      ""
   INDEX      { er1646v2IpV6RtrDnsServersTableIx }
   ::= {er1646v2IpV6RtrDnsServers 1}

Er1646v2IpV6RtrDnsServersEntry ::=
   SEQUENCE
      {
      er1646v2IpV6RtrDnsServersActions
         VariableLengthTableActions,
      er1646v2IpV6RtrDnsServersTableIx
         TableIndex,
      er1646v2IpV6RtrDnsServersAddress
         Ipv6Address,
      er1646v2IpV6RtrDnsServersPreference
         Integer32
      }

er1646v2IpV6RtrDnsServersActions OBJECT-TYPE
   SYNTAX      VariableLengthTableActions
   MAX-ACCESS  read-write
   STATUS      current
   DESCRIPTION
      "By way of this field, some manipulations
       on this table may be performed."
   ::= {er1646v2IpV6RtrDnsServersEntry 2}

er1646v2IpV6RtrDnsServersTableIx OBJECT-TYPE
   SYNTAX      TableIndex
   MAX-ACCESS  not-accessible
   STATUS      current
   DESCRIPTION
      ""
   ::= {er1646v2IpV6RtrDnsServersEntry 11}

er1646v2IpV6RtrDnsServersAddress OBJECT-TYPE
   SYNTAX      Ipv6Address
   MAX-ACCESS  read-write
   STATUS      current
   DESCRIPTION
      "Path: v6Router.editConf.dns.servers.address

       ipv6 address"
   ::= {er1646v2IpV6RtrDnsServersEntry 16777216}

er1646v2IpV6RtrDnsServersPreference OBJECT-TYPE
   SYNTAX      Integer32
   MAX-ACCESS  read-write
   STATUS      current
   DESCRIPTION
      "Path: v6Router.editConf.dns.servers.preference"
   ::= {er1646v2IpV6RtrDnsServersEntry 33554432}

er1646v2IpV6RtrDnsHosts OBJECT-TYPE
   SYNTAX      SEQUENCE OF Er1646v2IpV6RtrDnsHostsEntry
   MAX-ACCESS  not-accessible
   STATUS      current
   DESCRIPTION
      ""
   ::= {er1646v2IpV6RtrDns 50331648}

er1646v2IpV6RtrDnsHostsEntry OBJECT-TYPE
   SYNTAX      Er1646v2IpV6RtrDnsHostsEntry
   MAX-ACCESS  not-accessible
   STATUS      current
   DESCRIPTION
      ""
   INDEX      { er1646v2IpV6RtrDnsHostsTableIx }
   ::= {er1646v2IpV6RtrDnsHosts 1}

Er1646v2IpV6RtrDnsHostsEntry ::=
   SEQUENCE
      {
      er1646v2IpV6RtrDnsHostsActions
         VariableLengthTableActions,
      er1646v2IpV6RtrDnsHostsTableIx
         TableIndex,
      er1646v2IpV6RtrDnsHostsName
         DisplayString,
      er1646v2IpV6RtrDnsHostsAddress
         Ipv6Address
      }

er1646v2IpV6RtrDnsHostsActions OBJECT-TYPE
   SYNTAX      VariableLengthTableActions
   MAX-ACCESS  read-write
   STATUS      current
   DESCRIPTION
      "By way of this field, some manipulations
       on this table may be performed."
   ::= {er1646v2IpV6RtrDnsHostsEntry 2}

er1646v2IpV6RtrDnsHostsTableIx OBJECT-TYPE
   SYNTAX      TableIndex
   MAX-ACCESS  not-accessible
   STATUS      current
   DESCRIPTION
      ""
   ::= {er1646v2IpV6RtrDnsHostsEntry 11}

er1646v2IpV6RtrDnsHostsName OBJECT-TYPE
   SYNTAX      DisplayString
   MAX-ACCESS  read-write
   STATUS      current
   DESCRIPTION
      "Path: v6Router.editConf.dns.hosts.name"
   ::= {er1646v2IpV6RtrDnsHostsEntry 16777216}

er1646v2IpV6RtrDnsHostsAddress OBJECT-TYPE
   SYNTAX      Ipv6Address
   MAX-ACCESS  read-write
   STATUS      current
   DESCRIPTION
      "Path: v6Router.editConf.dns.hosts.address

       ipv6 address"
   ::= {er1646v2IpV6RtrDnsHostsEntry 33554432}


er1646v2IpV6RtrQMon OBJECT IDENTIFIER ::= {er1646v2IpV6Rtr 7}

er1646v2IpV6RtrQMonSSC OBJECT IDENTIFIER ::= {er1646v2IpV6RtrQMon 1}

er1646v2IpV6RtrQMonEntry OBJECT IDENTIFIER ::= {er1646v2IpV6RtrQMonSSC 1}

er1646v2IpV6RtrQMonMonitor OBJECT-TYPE
   SYNTAX      INTEGER
               {
               disabled (0),
               enabled (1)
               }
   MAX-ACCESS  read-write
   STATUS      current
   DESCRIPTION
      "Path: v6Router.editConf.qualityMonitor.monitor

       Possibilities:
               disabled   (0)
               enabled   (1)"
   ::= {er1646v2IpV6RtrQMonEntry 33554432}

er1646v2IpV6RtrQMonType OBJECT-TYPE
   SYNTAX      INTEGER
               {
               sequential (0),
               concurrent (1)
               }
   MAX-ACCESS  read-write
   STATUS      current
   DESCRIPTION
      "Path: v6Router.editConf.qualityMonitor.type

       Possibilities:
               sequential   (0)
               concurrent   (1)"
   ::= {er1646v2IpV6RtrQMonEntry 16777216}

er1646v2IpV6RtrQMonStartDelay OBJECT-TYPE
   SYNTAX      TimeTicks
   MAX-ACCESS  read-write
   STATUS      current
   DESCRIPTION
      "Path: v6Router.editConf.qualityMonitor.startDelay

       Time in centi-second."
   ::= {er1646v2IpV6RtrQMonEntry 83886080}

er1646v2IpV6RtrQMonDestinations OBJECT-TYPE
   SYNTAX      SEQUENCE OF Er1646v2IpV6RtrQMonDestinationsEntry
   MAX-ACCESS  not-accessible
   STATUS      current
   DESCRIPTION
      ""
   ::= {er1646v2IpV6RtrQMon 50331648}

er1646v2IpV6RtrQMonDestinationsEntry OBJECT-TYPE
   SYNTAX      Er1646v2IpV6RtrQMonDestinationsEntry
   MAX-ACCESS  not-accessible
   STATUS      current
   DESCRIPTION
      ""
   INDEX      { er1646v2IpV6RtrQMonDestinationsTableIx }
   ::= {er1646v2IpV6RtrQMonDestinations 1}

Er1646v2IpV6RtrQMonDestinationsEntry ::=
   SEQUENCE
      {
      er1646v2IpV6RtrQMonDestinationsActions
         VariableLengthTableActions,
      er1646v2IpV6RtrQMonDestinationsTableIx
         TableIndex,
      er1646v2IpV6RtrQMonDestinationsName
         DisplayString,
      er1646v2IpV6RtrQMonDestinationsAdminStatus
         INTEGER,
      er1646v2IpV6RtrQMonDestinationsIpAddress
         Ipv6Address,
      er1646v2IpV6RtrQMonDestinationsHostName
         DisplayString,
      er1646v2IpV6RtrQMonDestinationsSource
         Ipv6Address,
      er1646v2IpV6RtrQMonDestinationsTrafficClass
         Integer32,
      er1646v2IpV6RtrQMonDestinationsPriority
         INTEGER,
      er1646v2IpV6RtrQMonDestinationsProtocolIcmpV6
         OCTET STRING,
      er1646v2IpV6RtrQMonDestinationsProtocolUdpEcho
         OCTET STRING,
      er1646v2IpV6RtrQMonDestinationsProtocolUdpServerPort
         Integer32,
      er1646v2IpV6RtrQMonDestinationsProtocolTwampLightPort
         Integer32,
      er1646v2IpV6RtrQMonDestinationsTxInterface
         DisplayString,
      er1646v2IpV6RtrQMonDestinationsTxGateway
         Ipv6Address,
      er1646v2IpV6RtrQMonDestinationsInterval
         Integer32,
      er1646v2IpV6RtrQMonDestinationsTimeOut
         Integer32,
      er1646v2IpV6RtrQMonDestinationsLength
         Integer32,
      er1646v2IpV6RtrQMonDestinationsIdleSamples
         Integer32,
      er1646v2IpV6RtrQMonDestinationsLossAlarmSamples
         Integer32,
      er1646v2IpV6RtrQMonDestinationsLossAlarmAlarmOn
         Integer32,
      er1646v2IpV6RtrQMonDestinationsLossAlarmAlarmOff
         Integer32,
      er1646v2IpV6RtrQMonDestinationsLossAlarmAlarmUpOn
         Integer32,
      er1646v2IpV6RtrQMonDestinationsLossAlarmAlarmUpOff
         Integer32,
      er1646v2IpV6RtrQMonDestinationsLossAlarmAlarmDownOn
         Integer32,
      er1646v2IpV6RtrQMonDestinationsLossAlarmAlarmDownOff
         Integer32,
      er1646v2IpV6RtrQMonDestinationsDelayAlarmSamples
         Integer32,
      er1646v2IpV6RtrQMonDestinationsDelayAlarmDelayAvrgOn
         Integer32,
      er1646v2IpV6RtrQMonDestinationsDelayAlarmDelayAvrgOff
         Integer32,
      er1646v2IpV6RtrQMonDestinationsDelayAlarmDelayMaxOn
         Integer32,
      er1646v2IpV6RtrQMonDestinationsDelayAlarmDelayMaxOff
         Integer32,
      er1646v2IpV6RtrQMonDestinationsDelayAlarmDelayMinMaxOn
         Integer32,
      er1646v2IpV6RtrQMonDestinationsDelayAlarmDelayMinMaxOff
         Integer32,
      er1646v2IpV6RtrQMonDestinationsDelayAlarmDsType
         INTEGER,
      er1646v2IpV6RtrQMonDestinationsDelayAlarmDsBinsN
         INTEGER,
      er1646v2IpV6RtrQMonDestinationsDelayAlarmDsBinsNMn
         Integer32,
      er1646v2IpV6RtrQMonDestinationsDelayAlarmDsBinsNMx
         Integer32,
      er1646v2IpV6RtrQMonDestinationsDelayAlarmDsBinsTB1
         Integer32,
      er1646v2IpV6RtrQMonDestinationsDelayAlarmDsBinsTB2
         Integer32,
      er1646v2IpV6RtrQMonDestinationsDelayAlarmDsBinsTB3
         Integer32,
      er1646v2IpV6RtrQMonDestinationsDelayAlarmDsBinsTB4
         Integer32,
      er1646v2IpV6RtrQMonDestinationsDelayAlarmDsBinsTB5
         Integer32,
      er1646v2IpV6RtrQMonDestinationsDelayAlarmDsBinsTB6
         Integer32,
      er1646v2IpV6RtrQMonDestinationsDelayAlarmDsBinsTB7
         Integer32,
      er1646v2IpV6RtrQMonDestinationsDelayAlarmDsBinsTB8
         Integer32,
      er1646v2IpV6RtrQMonDestinationsDelayAlarmDsBinsTMx
         Integer32,
      er1646v2IpV6RtrQMonDestinationsDelayAlarmJitterAvrgOn
         Integer32,
      er1646v2IpV6RtrQMonDestinationsDelayAlarmJitterAvrgOff
         Integer32,
      er1646v2IpV6RtrQMonDestinationsDelayAlarmJitterMaxOn
         Integer32,
      er1646v2IpV6RtrQMonDestinationsDelayAlarmJitterMaxOff
         Integer32,
      er1646v2IpV6RtrQMonDestinationsDelayAlarmJsN
         INTEGER,
      er1646v2IpV6RtrQMonDestinationsDelayAlarmJsNMn
         Integer32,
      er1646v2IpV6RtrQMonDestinationsDelayAlarmJsNMx
         Integer32,
      er1646v2IpV6RtrQMonDestinationsDelayAlarmJsTB1
         Integer32,
      er1646v2IpV6RtrQMonDestinationsDelayAlarmJsTB2
         Integer32,
      er1646v2IpV6RtrQMonDestinationsDelayAlarmJsTB3
         Integer32,
      er1646v2IpV6RtrQMonDestinationsDelayAlarmJsTB4
         Integer32,
      er1646v2IpV6RtrQMonDestinationsDelayAlarmJsTB5
         Integer32,
      er1646v2IpV6RtrQMonDestinationsDelayAlarmJsTB6
         Integer32,
      er1646v2IpV6RtrQMonDestinationsDelayAlarmJsTB7
         Integer32,
      er1646v2IpV6RtrQMonDestinationsDelayAlarmJsTB8
         Integer32,
      er1646v2IpV6RtrQMonDestinationsDelayAlarmJsTMx
         Integer32,
      er1646v2IpV6RtrQMonDestinationsDelayAlarmJitterUpAvrgOn
         Integer32,
      er1646v2IpV6RtrQMonDestinationsDelayAlarmJitterUpAvrgOff
         Integer32,
      er1646v2IpV6RtrQMonDestinationsDelayAlarmJitterUpMaxOn
         Integer32,
      er1646v2IpV6RtrQMonDestinationsDelayAlarmJitterUpMaxOff
         Integer32,
      er1646v2IpV6RtrQMonDestinationsDelayAlarmJupsN
         INTEGER,
      er1646v2IpV6RtrQMonDestinationsDelayAlarmJupsNMn
         Integer32,
      er1646v2IpV6RtrQMonDestinationsDelayAlarmJupsNMx
         Integer32,
      er1646v2IpV6RtrQMonDestinationsDelayAlarmJupsTB1
         Integer32,
      er1646v2IpV6RtrQMonDestinationsDelayAlarmJupsTB2
         Integer32,
      er1646v2IpV6RtrQMonDestinationsDelayAlarmJupsTB3
         Integer32,
      er1646v2IpV6RtrQMonDestinationsDelayAlarmJupsTB4
         Integer32,
      er1646v2IpV6RtrQMonDestinationsDelayAlarmJupsTB5
         Integer32,
      er1646v2IpV6RtrQMonDestinationsDelayAlarmJupsTB6
         Integer32,
      er1646v2IpV6RtrQMonDestinationsDelayAlarmJupsTB7
         Integer32,
      er1646v2IpV6RtrQMonDestinationsDelayAlarmJupsTB8
         Integer32,
      er1646v2IpV6RtrQMonDestinationsDelayAlarmJupsTMx
         Integer32,
      er1646v2IpV6RtrQMonDestinationsDelayAlarmJitterDownAvrgOn
         Integer32,
      er1646v2IpV6RtrQMonDestinationsDelayAlarmJitterDownAvrgOff
         Integer32,
      er1646v2IpV6RtrQMonDestinationsDelayAlarmJitterDownMaxOn
         Integer32,
      er1646v2IpV6RtrQMonDestinationsDelayAlarmJitterDownMaxOff
         Integer32,
      er1646v2IpV6RtrQMonDestinationsDelayAlarmJdownsN
         INTEGER,
      er1646v2IpV6RtrQMonDestinationsDelayAlarmJdownsNMn
         Integer32,
      er1646v2IpV6RtrQMonDestinationsDelayAlarmJdownsNMx
         Integer32,
      er1646v2IpV6RtrQMonDestinationsDelayAlarmJdownsTB1
         Integer32,
      er1646v2IpV6RtrQMonDestinationsDelayAlarmJdownsTB2
         Integer32,
      er1646v2IpV6RtrQMonDestinationsDelayAlarmJdownsTB3
         Integer32,
      er1646v2IpV6RtrQMonDestinationsDelayAlarmJdownsTB4
         Integer32,
      er1646v2IpV6RtrQMonDestinationsDelayAlarmJdownsTB5
         Integer32,
      er1646v2IpV6RtrQMonDestinationsDelayAlarmJdownsTB6
         Integer32,
      er1646v2IpV6RtrQMonDestinationsDelayAlarmJdownsTB7
         Integer32,
      er1646v2IpV6RtrQMonDestinationsDelayAlarmJdownsTB8
         Integer32,
      er1646v2IpV6RtrQMonDestinationsDelayAlarmJdownsTMx
         Integer32,
      er1646v2IpV6RtrQMonDestinationsDelayAlarmDelayUpAvrgOn
         Integer32,
      er1646v2IpV6RtrQMonDestinationsDelayAlarmDelayUpAvrgOff
         Integer32,
      er1646v2IpV6RtrQMonDestinationsDelayAlarmDelayUpMaxOn
         Integer32,
      er1646v2IpV6RtrQMonDestinationsDelayAlarmDelayUpMaxOff
         Integer32,
      er1646v2IpV6RtrQMonDestinationsDelayAlarmDupsType
         INTEGER,
      er1646v2IpV6RtrQMonDestinationsDelayAlarmDupsBinsN
         INTEGER,
      er1646v2IpV6RtrQMonDestinationsDelayAlarmDupsBinsNMn
         Integer32,
      er1646v2IpV6RtrQMonDestinationsDelayAlarmDupsBinsNMx
         Integer32,
      er1646v2IpV6RtrQMonDestinationsDelayAlarmDupsBinsTB1
         Integer32,
      er1646v2IpV6RtrQMonDestinationsDelayAlarmDupsBinsTB2
         Integer32,
      er1646v2IpV6RtrQMonDestinationsDelayAlarmDupsBinsTB3
         Integer32,
      er1646v2IpV6RtrQMonDestinationsDelayAlarmDupsBinsTB4
         Integer32,
      er1646v2IpV6RtrQMonDestinationsDelayAlarmDupsBinsTB5
         Integer32,
      er1646v2IpV6RtrQMonDestinationsDelayAlarmDupsBinsTB6
         Integer32,
      er1646v2IpV6RtrQMonDestinationsDelayAlarmDupsBinsTB7
         Integer32,
      er1646v2IpV6RtrQMonDestinationsDelayAlarmDupsBinsTB8
         Integer32,
      er1646v2IpV6RtrQMonDestinationsDelayAlarmDupsBinsTMx
         Integer32,
      er1646v2IpV6RtrQMonDestinationsDelayAlarmDelayDownAvrgOn
         Integer32,
      er1646v2IpV6RtrQMonDestinationsDelayAlarmDelayDownAvrgOff
         Integer32,
      er1646v2IpV6RtrQMonDestinationsDelayAlarmDelayDownMaxOn
         Integer32,
      er1646v2IpV6RtrQMonDestinationsDelayAlarmDelayDownMaxOff
         Integer32,
      er1646v2IpV6RtrQMonDestinationsDelayAlarmDdownsType
         INTEGER,
      er1646v2IpV6RtrQMonDestinationsDelayAlarmDdownsBinsN
         INTEGER,
      er1646v2IpV6RtrQMonDestinationsDelayAlarmDdownsBinsNMn
         Integer32,
      er1646v2IpV6RtrQMonDestinationsDelayAlarmDdownsBinsNMx
         Integer32,
      er1646v2IpV6RtrQMonDestinationsDelayAlarmDdownsBinsTB1
         Integer32,
      er1646v2IpV6RtrQMonDestinationsDelayAlarmDdownsBinsTB2
         Integer32,
      er1646v2IpV6RtrQMonDestinationsDelayAlarmDdownsBinsTB3
         Integer32,
      er1646v2IpV6RtrQMonDestinationsDelayAlarmDdownsBinsTB4
         Integer32,
      er1646v2IpV6RtrQMonDestinationsDelayAlarmDdownsBinsTB5
         Integer32,
      er1646v2IpV6RtrQMonDestinationsDelayAlarmDdownsBinsTB6
         Integer32,
      er1646v2IpV6RtrQMonDestinationsDelayAlarmDdownsBinsTB7
         Integer32,
      er1646v2IpV6RtrQMonDestinationsDelayAlarmDdownsBinsTB8
         Integer32,
      er1646v2IpV6RtrQMonDestinationsDelayAlarmDdownsBinsTMx
         Integer32,
      er1646v2IpV6RtrQMonDestinationsAlarmMask
         Integer32,
      er1646v2IpV6RtrQMonDestinationsLogging
         INTEGER,
      er1646v2IpV6RtrQMonDestinationsLoggingDepth
         INTEGER
      }

er1646v2IpV6RtrQMonDestinationsActions OBJECT-TYPE
   SYNTAX      VariableLengthTableActions
   MAX-ACCESS  read-write
   STATUS      current
   DESCRIPTION
      "By way of this field, some manipulations
       on this table may be performed."
   ::= {er1646v2IpV6RtrQMonDestinationsEntry 2}

er1646v2IpV6RtrQMonDestinationsTableIx OBJECT-TYPE
   SYNTAX      TableIndex
   MAX-ACCESS  not-accessible
   STATUS      current
   DESCRIPTION
      ""
   ::= {er1646v2IpV6RtrQMonDestinationsEntry 11}

er1646v2IpV6RtrQMonDestinationsName OBJECT-TYPE
   SYNTAX      DisplayString
   MAX-ACCESS  read-write
   STATUS      current
   DESCRIPTION
      "Path: v6Router.editConf.qualityMonitor.destinations.name"
   ::= {er1646v2IpV6RtrQMonDestinationsEntry 234881024}

er1646v2IpV6RtrQMonDestinationsAdminStatus OBJECT-TYPE
   SYNTAX      INTEGER
               {
               enabled (1),
               onDemand (2),
               disabled (3)
               }
   MAX-ACCESS  read-write
   STATUS      current
   DESCRIPTION
      "Path: v6Router.editConf.qualityMonitor.destinations.adminStatus

       Possibilities:
               enabled   (1)
               onDemand   (2)
               disabled   (3)"
   ::= {er1646v2IpV6RtrQMonDestinationsEntry 369098752}

er1646v2IpV6RtrQMonDestinationsIpAddress OBJECT-TYPE
   SYNTAX      Ipv6Address
   MAX-ACCESS  read-write
   STATUS      current
   DESCRIPTION
      "Path: v6Router.editConf.qualityMonitor.destinations.ipAddress

       ipv6 address"
   ::= {er1646v2IpV6RtrQMonDestinationsEntry 16777216}

er1646v2IpV6RtrQMonDestinationsHostName OBJECT-TYPE
   SYNTAX      DisplayString
   MAX-ACCESS  read-write
   STATUS      current
   DESCRIPTION
      "Path: v6Router.editConf.qualityMonitor.destinations.hostName"
   ::= {er1646v2IpV6RtrQMonDestinationsEntry 33554432}

er1646v2IpV6RtrQMonDestinationsSource OBJECT-TYPE
   SYNTAX      Ipv6Address
   MAX-ACCESS  read-write
   STATUS      current
   DESCRIPTION
      "Path: v6Router.editConf.qualityMonitor.destinations.source

       ipv6 address"
   ::= {er1646v2IpV6RtrQMonDestinationsEntry 184549376}

er1646v2IpV6RtrQMonDestinationsTrafficClass OBJECT-TYPE
   SYNTAX      Integer32
   MAX-ACCESS  read-write
   STATUS      current
   DESCRIPTION
      "Path: v6Router.editConf.qualityMonitor.destinations.trafficClass"
   ::= {er1646v2IpV6RtrQMonDestinationsEntry 167772160}

er1646v2IpV6RtrQMonDestinationsPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: v6Router.editConf.qualityMonitor.destinations.priority

       Possibilities:
               queue1   (0)
               queue2   (1)
               queue3   (2)
               queue4   (3)
               queue5   (4)
               lowDelayQueue   (5)
               lowDelay2Queue   (6)
               systemQueue   (7)"
   ::= {er1646v2IpV6RtrQMonDestinationsEntry 218103808}

er1646v2IpV6RtrQMonDestinationsProtocolIcmpV6 OBJECT-TYPE
   SYNTAX      OCTET STRING
   MAX-ACCESS  read-write
   STATUS      current
   DESCRIPTION
      "Path: v6Router.editConf.qualityMonitor.destinations.protocol.icmpV6"
   ::= {er1646v2IpV6RtrQMonDestinationsEntry 50397184}

er1646v2IpV6RtrQMonDestinationsProtocolUdpEcho OBJECT-TYPE
   SYNTAX      OCTET STRING
   MAX-ACCESS  read-write
   STATUS      current
   DESCRIPTION
      "Path: v6Router.editConf.qualityMonitor.destinations.protocol.udpEcho"
   ::= {er1646v2IpV6RtrQMonDestinationsEntry 50462720}

er1646v2IpV6RtrQMonDestinationsProtocolUdpServerPort OBJECT-TYPE
   SYNTAX      Integer32
   MAX-ACCESS  read-write
   STATUS      current
   DESCRIPTION
      "Path: v6Router.editConf.qualityMonitor.destinations.protocol.udpServerPort"
   ::= {er1646v2IpV6RtrQMonDestinationsEntry 50528256}

er1646v2IpV6RtrQMonDestinationsProtocolTwampLightPort OBJECT-TYPE
   SYNTAX      Integer32
   MAX-ACCESS  read-write
   STATUS      current
   DESCRIPTION
      "Path: v6Router.editConf.qualityMonitor.destinations.protocol.twampLightPort"
   ::= {er1646v2IpV6RtrQMonDestinationsEntry 50593792}

er1646v2IpV6RtrQMonDestinationsTxInterface OBJECT-TYPE
   SYNTAX      DisplayString
   MAX-ACCESS  read-write
   STATUS      current
   DESCRIPTION
      "Path: v6Router.editConf.qualityMonitor.destinations.txInterface"
   ::= {er1646v2IpV6RtrQMonDestinationsEntry 402653184}

er1646v2IpV6RtrQMonDestinationsTxGateway OBJECT-TYPE
   SYNTAX      Ipv6Address
   MAX-ACCESS  read-write
   STATUS      current
   DESCRIPTION
      "Path: v6Router.editConf.qualityMonitor.destinations.txGateway

       ipv6 address"
   ::= {er1646v2IpV6RtrQMonDestinationsEntry 419430400}

er1646v2IpV6RtrQMonDestinationsInterval OBJECT-TYPE
   SYNTAX      Integer32
   UNITS       "100msec"
   MAX-ACCESS  read-write
   STATUS      current
   DESCRIPTION
      "Path: v6Router.editConf.qualityMonitor.destinations.interval

       unit name = 100msec"
   ::= {er1646v2IpV6RtrQMonDestinationsEntry 67108864}

er1646v2IpV6RtrQMonDestinationsTimeOut OBJECT-TYPE
   SYNTAX      Integer32
   UNITS       "100msec"
   MAX-ACCESS  read-write
   STATUS      current
   DESCRIPTION
      "Path: v6Router.editConf.qualityMonitor.destinations.timeOut

       unit name = 100msec"
   ::= {er1646v2IpV6RtrQMonDestinationsEntry 150994944}

er1646v2IpV6RtrQMonDestinationsLength OBJECT-TYPE
   SYNTAX      Integer32
   MAX-ACCESS  read-write
   STATUS      current
   DESCRIPTION
      "Path: v6Router.editConf.qualityMonitor.destinations.length"
   ::= {er1646v2IpV6RtrQMonDestinationsEntry 83886080}

er1646v2IpV6RtrQMonDestinationsIdleSamples OBJECT-TYPE
   SYNTAX      Integer32
   MAX-ACCESS  read-write
   STATUS      current
   DESCRIPTION
      "Path: v6Router.editConf.qualityMonitor.destinations.idleSamples"
   ::= {er1646v2IpV6RtrQMonDestinationsEntry 268435456}

er1646v2IpV6RtrQMonDestinationsLossAlarmSamples OBJECT-TYPE
   SYNTAX      Integer32
   MAX-ACCESS  read-write
   STATUS      current
   DESCRIPTION
      "Path: v6Router.editConf.qualityMonitor.destinations.lossAlarm.samples"
   ::= {er1646v2IpV6RtrQMonDestinationsEntry 100728832}

er1646v2IpV6RtrQMonDestinationsLossAlarmAlarmOn OBJECT-TYPE
   SYNTAX      Integer32
   MAX-ACCESS  read-write
   STATUS      current
   DESCRIPTION
      "Path: v6Router.editConf.qualityMonitor.destinations.lossAlarm.alarmOn"
   ::= {er1646v2IpV6RtrQMonDestinationsEntry 100794368}

er1646v2IpV6RtrQMonDestinationsLossAlarmAlarmOff OBJECT-TYPE
   SYNTAX      Integer32
   MAX-ACCESS  read-write
   STATUS      current
   DESCRIPTION
      "Path: v6Router.editConf.qualityMonitor.destinations.lossAlarm.alarmOff"
   ::= {er1646v2IpV6RtrQMonDestinationsEntry 100859904}

er1646v2IpV6RtrQMonDestinationsLossAlarmAlarmUpOn OBJECT-TYPE
   SYNTAX      Integer32
   MAX-ACCESS  read-write
   STATUS      current
   DESCRIPTION
      "Path: v6Router.editConf.qualityMonitor.destinations.lossAlarm.alarmUpOn"
   ::= {er1646v2IpV6RtrQMonDestinationsEntry 100925440}

er1646v2IpV6RtrQMonDestinationsLossAlarmAlarmUpOff OBJECT-TYPE
   SYNTAX      Integer32
   MAX-ACCESS  read-write
   STATUS      current
   DESCRIPTION
      "Path: v6Router.editConf.qualityMonitor.destinations.lossAlarm.alarmUpOff"
   ::= {er1646v2IpV6RtrQMonDestinationsEntry 100990976}

er1646v2IpV6RtrQMonDestinationsLossAlarmAlarmDownOn OBJECT-TYPE
   SYNTAX      Integer32
   MAX-ACCESS  read-write
   STATUS      current
   DESCRIPTION
      "Path: v6Router.editConf.qualityMonitor.destinations.lossAlarm.alarmDownOn"
   ::= {er1646v2IpV6RtrQMonDestinationsEntry 101056512}

er1646v2IpV6RtrQMonDestinationsLossAlarmAlarmDownOff OBJECT-TYPE
   SYNTAX      Integer32
   MAX-ACCESS  read-write
   STATUS      current
   DESCRIPTION
      "Path: v6Router.editConf.qualityMonitor.destinations.lossAlarm.alarmDownOff"
   ::= {er1646v2IpV6RtrQMonDestinationsEntry 101122048}

er1646v2IpV6RtrQMonDestinationsDelayAlarmSamples OBJECT-TYPE
   SYNTAX      Integer32
   MAX-ACCESS  read-write
   STATUS      current
   DESCRIPTION
      "Path: v6Router.editConf.qualityMonitor.destinations.delayAlarm.samples"
   ::= {er1646v2IpV6RtrQMonDestinationsEntry 117506048}

er1646v2IpV6RtrQMonDestinationsDelayAlarmDelayAvrgOn OBJECT-TYPE
   SYNTAX      Integer32
   UNITS       "msec"
   MAX-ACCESS  read-write
   STATUS      current
   DESCRIPTION
      "Path: v6Router.editConf.qualityMonitor.destinations.delayAlarm.delayAvrgOn

       unit name = msec"
   ::= {er1646v2IpV6RtrQMonDestinationsEntry 117571584}

er1646v2IpV6RtrQMonDestinationsDelayAlarmDelayAvrgOff OBJECT-TYPE
   SYNTAX      Integer32
   UNITS       "msec"
   MAX-ACCESS  read-write
   STATUS      current
   DESCRIPTION
      "Path: v6Router.editConf.qualityMonitor.destinations.delayAlarm.delayAvrgOff

       unit name = msec"
   ::= {er1646v2IpV6RtrQMonDestinationsEntry 117637120}

er1646v2IpV6RtrQMonDestinationsDelayAlarmDelayMaxOn OBJECT-TYPE
   SYNTAX      Integer32
   UNITS       "msec"
   MAX-ACCESS  read-write
   STATUS      current
   DESCRIPTION
      "Path: v6Router.editConf.qualityMonitor.destinations.delayAlarm.delayMaxOn

       unit name = msec"
   ::= {er1646v2IpV6RtrQMonDestinationsEntry 117702656}

er1646v2IpV6RtrQMonDestinationsDelayAlarmDelayMaxOff OBJECT-TYPE
   SYNTAX      Integer32
   UNITS       "msec"
   MAX-ACCESS  read-write
   STATUS      current
   DESCRIPTION
      "Path: v6Router.editConf.qualityMonitor.destinations.delayAlarm.delayMaxOff

       unit name = msec"
   ::= {er1646v2IpV6RtrQMonDestinationsEntry 117768192}

er1646v2IpV6RtrQMonDestinationsDelayAlarmDelayMinMaxOn OBJECT-TYPE
   SYNTAX      Integer32
   UNITS       "msec"
   MAX-ACCESS  read-write
   STATUS      current
   DESCRIPTION
      "Path: v6Router.editConf.qualityMonitor.destinations.delayAlarm.delayMinMaxOn

       unit name = msec"
   ::= {er1646v2IpV6RtrQMonDestinationsEntry 118095872}

er1646v2IpV6RtrQMonDestinationsDelayAlarmDelayMinMaxOff OBJECT-TYPE
   SYNTAX      Integer32
   UNITS       "msec"
   MAX-ACCESS  read-write
   STATUS      current
   DESCRIPTION
      "Path: v6Router.editConf.qualityMonitor.destinations.delayAlarm.delayMinMaxOff

       unit name = msec"
   ::= {er1646v2IpV6RtrQMonDestinationsEntry 118161408}

er1646v2IpV6RtrQMonDestinationsDelayAlarmDsType OBJECT-TYPE
   SYNTAX      INTEGER
               {
               fd (1),
               fdr (2)
               }
   MAX-ACCESS  read-write
   STATUS      current
   DESCRIPTION
      "Path: v6Router.editConf.qualityMonitor.destinations.delayAlarm.delayStat.type

       Possibilities:
               fd   (1)
               fdr   (2)"
   ::= {er1646v2IpV6RtrQMonDestinationsEntry 119283712}

er1646v2IpV6RtrQMonDestinationsDelayAlarmDsBinsN OBJECT-TYPE
   SYNTAX      INTEGER
               {
               none (0)
               }
   MAX-ACCESS  read-write
   STATUS      current
   DESCRIPTION
      "Path: v6Router.editConf.qualityMonitor.destinations.delayAlarm.delayStat.bins.none

       Possibilities:
               none   (0)"
   ::= {er1646v2IpV6RtrQMonDestinationsEntry 119292928}

er1646v2IpV6RtrQMonDestinationsDelayAlarmDsBinsNMn OBJECT-TYPE
   SYNTAX      Integer32
   UNITS       "msec"
   MAX-ACCESS  read-write
   STATUS      current
   DESCRIPTION
      "Path: v6Router.editConf.qualityMonitor.destinations.delayAlarm.delayStat.bins.range.min

       unit name = msec"
   ::= {er1646v2IpV6RtrQMonDestinationsEntry 119294080}

er1646v2IpV6RtrQMonDestinationsDelayAlarmDsBinsNMx OBJECT-TYPE
   SYNTAX      Integer32
   UNITS       "msec"
   MAX-ACCESS  read-write
   STATUS      current
   DESCRIPTION
      "Path: v6Router.editConf.qualityMonitor.destinations.delayAlarm.delayStat.bins.range.max

       unit name = msec"
   ::= {er1646v2IpV6RtrQMonDestinationsEntry 119294208}

er1646v2IpV6RtrQMonDestinationsDelayAlarmDsBinsTB1 OBJECT-TYPE
   SYNTAX      Integer32
   UNITS       "msec"
   MAX-ACCESS  read-write
   STATUS      current
   DESCRIPTION
      "Path: v6Router.editConf.qualityMonitor.destinations.delayAlarm.delayStat.bins.table.bin1

       unit name = msec"
   ::= {er1646v2IpV6RtrQMonDestinationsEntry 119295040}

er1646v2IpV6RtrQMonDestinationsDelayAlarmDsBinsTB2 OBJECT-TYPE
   SYNTAX      Integer32
   UNITS       "msec"
   MAX-ACCESS  read-write
   STATUS      current
   DESCRIPTION
      "Path: v6Router.editConf.qualityMonitor.destinations.delayAlarm.delayStat.bins.table.bin2

       unit name = msec"
   ::= {er1646v2IpV6RtrQMonDestinationsEntry 119295104}

er1646v2IpV6RtrQMonDestinationsDelayAlarmDsBinsTB3 OBJECT-TYPE
   SYNTAX      Integer32
   UNITS       "msec"
   MAX-ACCESS  read-write
   STATUS      current
   DESCRIPTION
      "Path: v6Router.editConf.qualityMonitor.destinations.delayAlarm.delayStat.bins.table.bin3

       unit name = msec"
   ::= {er1646v2IpV6RtrQMonDestinationsEntry 119295168}

er1646v2IpV6RtrQMonDestinationsDelayAlarmDsBinsTB4 OBJECT-TYPE
   SYNTAX      Integer32
   UNITS       "msec"
   MAX-ACCESS  read-write
   STATUS      current
   DESCRIPTION
      "Path: v6Router.editConf.qualityMonitor.destinations.delayAlarm.delayStat.bins.table.bin4

       unit name = msec"
   ::= {er1646v2IpV6RtrQMonDestinationsEntry 119295232}

er1646v2IpV6RtrQMonDestinationsDelayAlarmDsBinsTB5 OBJECT-TYPE
   SYNTAX      Integer32
   UNITS       "msec"
   MAX-ACCESS  read-write
   STATUS      current
   DESCRIPTION
      "Path: v6Router.editConf.qualityMonitor.destinations.delayAlarm.delayStat.bins.table.bin5

       unit name = msec"
   ::= {er1646v2IpV6RtrQMonDestinationsEntry 119295296}

er1646v2IpV6RtrQMonDestinationsDelayAlarmDsBinsTB6 OBJECT-TYPE
   SYNTAX      Integer32
   UNITS       "msec"
   MAX-ACCESS  read-write
   STATUS      current
   DESCRIPTION
      "Path: v6Router.editConf.qualityMonitor.destinations.delayAlarm.delayStat.bins.table.bin6

       unit name = msec"
   ::= {er1646v2IpV6RtrQMonDestinationsEntry 119295360}

er1646v2IpV6RtrQMonDestinationsDelayAlarmDsBinsTB7 OBJECT-TYPE
   SYNTAX      Integer32
   UNITS       "msec"
   MAX-ACCESS  read-write
   STATUS      current
   DESCRIPTION
      "Path: v6Router.editConf.qualityMonitor.destinations.delayAlarm.delayStat.bins.table.bin7

       unit name = msec"
   ::= {er1646v2IpV6RtrQMonDestinationsEntry 119295424}

er1646v2IpV6RtrQMonDestinationsDelayAlarmDsBinsTB8 OBJECT-TYPE
   SYNTAX      Integer32
   UNITS       "msec"
   MAX-ACCESS  read-write
   STATUS      current
   DESCRIPTION
      "Path: v6Router.editConf.qualityMonitor.destinations.delayAlarm.delayStat.bins.table.bin8

       unit name = msec"
   ::= {er1646v2IpV6RtrQMonDestinationsEntry 119295488}

er1646v2IpV6RtrQMonDestinationsDelayAlarmDsBinsTMx OBJECT-TYPE
   SYNTAX      Integer32
   UNITS       "msec"
   MAX-ACCESS  read-write
   STATUS      current
   DESCRIPTION
      "Path: v6Router.editConf.qualityMonitor.destinations.delayAlarm.delayStat.bins.table.max

       unit name = msec"
   ::= {er1646v2IpV6RtrQMonDestinationsEntry 119295552}

er1646v2IpV6RtrQMonDestinationsDelayAlarmJitterAvrgOn OBJECT-TYPE
   SYNTAX      Integer32
   UNITS       "msec"
   MAX-ACCESS  read-write
   STATUS      current
   DESCRIPTION
      "Path: v6Router.editConf.qualityMonitor.destinations.delayAlarm.jitterAvrgOn

       unit name = msec"
   ::= {er1646v2IpV6RtrQMonDestinationsEntry 117833728}

er1646v2IpV6RtrQMonDestinationsDelayAlarmJitterAvrgOff OBJECT-TYPE
   SYNTAX      Integer32
   UNITS       "msec"
   MAX-ACCESS  read-write
   STATUS      current
   DESCRIPTION
      "Path: v6Router.editConf.qualityMonitor.destinations.delayAlarm.jitterAvrgOff

       unit name = msec"
   ::= {er1646v2IpV6RtrQMonDestinationsEntry 117899264}

er1646v2IpV6RtrQMonDestinationsDelayAlarmJitterMaxOn OBJECT-TYPE
   SYNTAX      Integer32
   UNITS       "msec"
   MAX-ACCESS  read-write
   STATUS      current
   DESCRIPTION
      "Path: v6Router.editConf.qualityMonitor.destinations.delayAlarm.jitterMaxOn

       unit name = msec"
   ::= {er1646v2IpV6RtrQMonDestinationsEntry 117964800}

er1646v2IpV6RtrQMonDestinationsDelayAlarmJitterMaxOff OBJECT-TYPE
   SYNTAX      Integer32
   UNITS       "msec"
   MAX-ACCESS  read-write
   STATUS      current
   DESCRIPTION
      "Path: v6Router.editConf.qualityMonitor.destinations.delayAlarm.jitterMaxOff

       unit name = msec"
   ::= {er1646v2IpV6RtrQMonDestinationsEntry 118030336}

er1646v2IpV6RtrQMonDestinationsDelayAlarmJsN OBJECT-TYPE
   SYNTAX      INTEGER
               {
               none (0)
               }
   MAX-ACCESS  read-write
   STATUS      current
   DESCRIPTION
      "Path: v6Router.editConf.qualityMonitor.destinations.delayAlarm.jitterStat.none

       Possibilities:
               none   (0)"
   ::= {er1646v2IpV6RtrQMonDestinationsEntry 119676928}

er1646v2IpV6RtrQMonDestinationsDelayAlarmJsNMn OBJECT-TYPE
   SYNTAX      Integer32
   UNITS       "msec"
   MAX-ACCESS  read-write
   STATUS      current
   DESCRIPTION
      "Path: v6Router.editConf.qualityMonitor.destinations.delayAlarm.jitterStat.range.min

       unit name = msec"
   ::= {er1646v2IpV6RtrQMonDestinationsEntry 119686144}

er1646v2IpV6RtrQMonDestinationsDelayAlarmJsNMx OBJECT-TYPE
   SYNTAX      Integer32
   UNITS       "msec"
   MAX-ACCESS  read-write
   STATUS      current
   DESCRIPTION
      "Path: v6Router.editConf.qualityMonitor.destinations.delayAlarm.jitterStat.range.max

       unit name = msec"
   ::= {er1646v2IpV6RtrQMonDestinationsEntry 119687168}

er1646v2IpV6RtrQMonDestinationsDelayAlarmJsTB1 OBJECT-TYPE
   SYNTAX      Integer32
   UNITS       "msec"
   MAX-ACCESS  read-write
   STATUS      current
   DESCRIPTION
      "Path: v6Router.editConf.qualityMonitor.destinations.delayAlarm.jitterStat.table.bin1

       unit name = msec"
   ::= {er1646v2IpV6RtrQMonDestinationsEntry 119693824}

er1646v2IpV6RtrQMonDestinationsDelayAlarmJsTB2 OBJECT-TYPE
   SYNTAX      Integer32
   UNITS       "msec"
   MAX-ACCESS  read-write
   STATUS      current
   DESCRIPTION
      "Path: v6Router.editConf.qualityMonitor.destinations.delayAlarm.jitterStat.table.bin2

       unit name = msec"
   ::= {er1646v2IpV6RtrQMonDestinationsEntry 119694336}

er1646v2IpV6RtrQMonDestinationsDelayAlarmJsTB3 OBJECT-TYPE
   SYNTAX      Integer32
   UNITS       "msec"
   MAX-ACCESS  read-write
   STATUS      current
   DESCRIPTION
      "Path: v6Router.editConf.qualityMonitor.destinations.delayAlarm.jitterStat.table.bin3

       unit name = msec"
   ::= {er1646v2IpV6RtrQMonDestinationsEntry 119694848}

er1646v2IpV6RtrQMonDestinationsDelayAlarmJsTB4 OBJECT-TYPE
   SYNTAX      Integer32
   UNITS       "msec"
   MAX-ACCESS  read-write
   STATUS      current
   DESCRIPTION
      "Path: v6Router.editConf.qualityMonitor.destinations.delayAlarm.jitterStat.table.bin4

       unit name = msec"
   ::= {er1646v2IpV6RtrQMonDestinationsEntry 119695360}

er1646v2IpV6RtrQMonDestinationsDelayAlarmJsTB5 OBJECT-TYPE
   SYNTAX      Integer32
   UNITS       "msec"
   MAX-ACCESS  read-write
   STATUS      current
   DESCRIPTION
      "Path: v6Router.editConf.qualityMonitor.destinations.delayAlarm.jitterStat.table.bin5

       unit name = msec"
   ::= {er1646v2IpV6RtrQMonDestinationsEntry 119695872}

er1646v2IpV6RtrQMonDestinationsDelayAlarmJsTB6 OBJECT-TYPE
   SYNTAX      Integer32
   UNITS       "msec"
   MAX-ACCESS  read-write
   STATUS      current
   DESCRIPTION
      "Path: v6Router.editConf.qualityMonitor.destinations.delayAlarm.jitterStat.table.bin6

       unit name = msec"
   ::= {er1646v2IpV6RtrQMonDestinationsEntry 119696384}

er1646v2IpV6RtrQMonDestinationsDelayAlarmJsTB7 OBJECT-TYPE
   SYNTAX      Integer32
   UNITS       "msec"
   MAX-ACCESS  read-write
   STATUS      current
   DESCRIPTION
      "Path: v6Router.editConf.qualityMonitor.destinations.delayAlarm.jitterStat.table.bin7

       unit name = msec"
   ::= {er1646v2IpV6RtrQMonDestinationsEntry 119696896}

er1646v2IpV6RtrQMonDestinationsDelayAlarmJsTB8 OBJECT-TYPE
   SYNTAX      Integer32
   UNITS       "msec"
   MAX-ACCESS  read-write
   STATUS      current
   DESCRIPTION
      "Path: v6Router.editConf.qualityMonitor.destinations.delayAlarm.jitterStat.table.bin8

       unit name = msec"
   ::= {er1646v2IpV6RtrQMonDestinationsEntry 119697408}

er1646v2IpV6RtrQMonDestinationsDelayAlarmJsTMx OBJECT-TYPE
   SYNTAX      Integer32
   UNITS       "msec"
   MAX-ACCESS  read-write
   STATUS      current
   DESCRIPTION
      "Path: v6Router.editConf.qualityMonitor.destinations.delayAlarm.jitterStat.table.max

       unit name = msec"
   ::= {er1646v2IpV6RtrQMonDestinationsEntry 119697920}

er1646v2IpV6RtrQMonDestinationsDelayAlarmJitterUpAvrgOn OBJECT-TYPE
   SYNTAX      Integer32
   UNITS       "msec"
   MAX-ACCESS  read-write
   STATUS      current
   DESCRIPTION
      "Path: v6Router.editConf.qualityMonitor.destinations.delayAlarm.jitterUpAvrgOn

       unit name = msec"
   ::= {er1646v2IpV6RtrQMonDestinationsEntry 118226944}

er1646v2IpV6RtrQMonDestinationsDelayAlarmJitterUpAvrgOff OBJECT-TYPE
   SYNTAX      Integer32
   UNITS       "msec"
   MAX-ACCESS  read-write
   STATUS      current
   DESCRIPTION
      "Path: v6Router.editConf.qualityMonitor.destinations.delayAlarm.jitterUpAvrgOff

       unit name = msec"
   ::= {er1646v2IpV6RtrQMonDestinationsEntry 118292480}

er1646v2IpV6RtrQMonDestinationsDelayAlarmJitterUpMaxOn OBJECT-TYPE
   SYNTAX      Integer32
   UNITS       "msec"
   MAX-ACCESS  read-write
   STATUS      current
   DESCRIPTION
      "Path: v6Router.editConf.qualityMonitor.destinations.delayAlarm.jitterUpMaxOn

       unit name = msec"
   ::= {er1646v2IpV6RtrQMonDestinationsEntry 118358016}

er1646v2IpV6RtrQMonDestinationsDelayAlarmJitterUpMaxOff OBJECT-TYPE
   SYNTAX      Integer32
   UNITS       "msec"
   MAX-ACCESS  read-write
   STATUS      current
   DESCRIPTION
      "Path: v6Router.editConf.qualityMonitor.destinations.delayAlarm.jitterUpMaxOff

       unit name = msec"
   ::= {er1646v2IpV6RtrQMonDestinationsEntry 118423552}

er1646v2IpV6RtrQMonDestinationsDelayAlarmJupsN OBJECT-TYPE
   SYNTAX      INTEGER
               {
               none (0)
               }
   MAX-ACCESS  read-write
   STATUS      current
   DESCRIPTION
      "Path: v6Router.editConf.qualityMonitor.destinations.delayAlarm.jitterUpStat.none

       Possibilities:
               none   (0)"
   ::= {er1646v2IpV6RtrQMonDestinationsEntry 119808000}

er1646v2IpV6RtrQMonDestinationsDelayAlarmJupsNMn OBJECT-TYPE
   SYNTAX      Integer32
   UNITS       "msec"
   MAX-ACCESS  read-write
   STATUS      current
   DESCRIPTION
      "Path: v6Router.editConf.qualityMonitor.destinations.delayAlarm.jitterUpStat.range.min

       unit name = msec"
   ::= {er1646v2IpV6RtrQMonDestinationsEntry 119817216}

er1646v2IpV6RtrQMonDestinationsDelayAlarmJupsNMx OBJECT-TYPE
   SYNTAX      Integer32
   UNITS       "msec"
   MAX-ACCESS  read-write
   STATUS      current
   DESCRIPTION
      "Path: v6Router.editConf.qualityMonitor.destinations.delayAlarm.jitterUpStat.range.max

       unit name = msec"
   ::= {er1646v2IpV6RtrQMonDestinationsEntry 119818240}

er1646v2IpV6RtrQMonDestinationsDelayAlarmJupsTB1 OBJECT-TYPE
   SYNTAX      Integer32
   UNITS       "msec"
   MAX-ACCESS  read-write
   STATUS      current
   DESCRIPTION
      "Path: v6Router.editConf.qualityMonitor.destinations.delayAlarm.jitterUpStat.table.bin1

       unit name = msec"
   ::= {er1646v2IpV6RtrQMonDestinationsEntry 119824896}

er1646v2IpV6RtrQMonDestinationsDelayAlarmJupsTB2 OBJECT-TYPE
   SYNTAX      Integer32
   UNITS       "msec"
   MAX-ACCESS  read-write
   STATUS      current
   DESCRIPTION
      "Path: v6Router.editConf.qualityMonitor.destinations.delayAlarm.jitterUpStat.table.bin2

       unit name = msec"
   ::= {er1646v2IpV6RtrQMonDestinationsEntry 119825408}

er1646v2IpV6RtrQMonDestinationsDelayAlarmJupsTB3 OBJECT-TYPE
   SYNTAX      Integer32
   UNITS       "msec"
   MAX-ACCESS  read-write
   STATUS      current
   DESCRIPTION
      "Path: v6Router.editConf.qualityMonitor.destinations.delayAlarm.jitterUpStat.table.bin3

       unit name = msec"
   ::= {er1646v2IpV6RtrQMonDestinationsEntry 119825920}

er1646v2IpV6RtrQMonDestinationsDelayAlarmJupsTB4 OBJECT-TYPE
   SYNTAX      Integer32
   UNITS       "msec"
   MAX-ACCESS  read-write
   STATUS      current
   DESCRIPTION
      "Path: v6Router.editConf.qualityMonitor.destinations.delayAlarm.jitterUpStat.table.bin4

       unit name = msec"
   ::= {er1646v2IpV6RtrQMonDestinationsEntry 119826432}

er1646v2IpV6RtrQMonDestinationsDelayAlarmJupsTB5 OBJECT-TYPE
   SYNTAX      Integer32
   UNITS       "msec"
   MAX-ACCESS  read-write
   STATUS      current
   DESCRIPTION
      "Path: v6Router.editConf.qualityMonitor.destinations.delayAlarm.jitterUpStat.table.bin5

       unit name = msec"
   ::= {er1646v2IpV6RtrQMonDestinationsEntry 119826944}

er1646v2IpV6RtrQMonDestinationsDelayAlarmJupsTB6 OBJECT-TYPE
   SYNTAX      Integer32
   UNITS       "msec"
   MAX-ACCESS  read-write
   STATUS      current
   DESCRIPTION
      "Path: v6Router.editConf.qualityMonitor.destinations.delayAlarm.jitterUpStat.table.bin6

       unit name = msec"
   ::= {er1646v2IpV6RtrQMonDestinationsEntry 119827456}

er1646v2IpV6RtrQMonDestinationsDelayAlarmJupsTB7 OBJECT-TYPE
   SYNTAX      Integer32
   UNITS       "msec"
   MAX-ACCESS  read-write
   STATUS      current
   DESCRIPTION
      "Path: v6Router.editConf.qualityMonitor.destinations.delayAlarm.jitterUpStat.table.bin7

       unit name = msec"
   ::= {er1646v2IpV6RtrQMonDestinationsEntry 119827968}

er1646v2IpV6RtrQMonDestinationsDelayAlarmJupsTB8 OBJECT-TYPE
   SYNTAX      Integer32
   UNITS       "msec"
   MAX-ACCESS  read-write
   STATUS      current
   DESCRIPTION
      "Path: v6Router.editConf.qualityMonitor.destinations.delayAlarm.jitterUpStat.table.bin8

       unit name = msec"
   ::= {er1646v2IpV6RtrQMonDestinationsEntry 119828480}

er1646v2IpV6RtrQMonDestinationsDelayAlarmJupsTMx OBJECT-TYPE
   SYNTAX      Integer32
   UNITS       "msec"
   MAX-ACCESS  read-write
   STATUS      current
   DESCRIPTION
      "Path: v6Router.editConf.qualityMonitor.destinations.delayAlarm.jitterUpStat.table.max

       unit name = msec"
   ::= {er1646v2IpV6RtrQMonDestinationsEntry 119828992}

er1646v2IpV6RtrQMonDestinationsDelayAlarmJitterDownAvrgOn OBJECT-TYPE
   SYNTAX      Integer32
   UNITS       "msec"
   MAX-ACCESS  read-write
   STATUS      current
   DESCRIPTION
      "Path: v6Router.editConf.qualityMonitor.destinations.delayAlarm.jitterDownAvrgOn

       unit name = msec"
   ::= {er1646v2IpV6RtrQMonDestinationsEntry 118489088}

er1646v2IpV6RtrQMonDestinationsDelayAlarmJitterDownAvrgOff OBJECT-TYPE
   SYNTAX      Integer32
   UNITS       "msec"
   MAX-ACCESS  read-write
   STATUS      current
   DESCRIPTION
      "Path: v6Router.editConf.qualityMonitor.destinations.delayAlarm.jitterDownAvrgOff

       unit name = msec"
   ::= {er1646v2IpV6RtrQMonDestinationsEntry 118554624}

er1646v2IpV6RtrQMonDestinationsDelayAlarmJitterDownMaxOn OBJECT-TYPE
   SYNTAX      Integer32
   UNITS       "msec"
   MAX-ACCESS  read-write
   STATUS      current
   DESCRIPTION
      "Path: v6Router.editConf.qualityMonitor.destinations.delayAlarm.jitterDownMaxOn

       unit name = msec"
   ::= {er1646v2IpV6RtrQMonDestinationsEntry 118620160}

er1646v2IpV6RtrQMonDestinationsDelayAlarmJitterDownMaxOff OBJECT-TYPE
   SYNTAX      Integer32
   UNITS       "msec"
   MAX-ACCESS  read-write
   STATUS      current
   DESCRIPTION
      "Path: v6Router.editConf.qualityMonitor.destinations.delayAlarm.jitterDownMaxOff

       unit name = msec"
   ::= {er1646v2IpV6RtrQMonDestinationsEntry 118685696}

er1646v2IpV6RtrQMonDestinationsDelayAlarmJdownsN OBJECT-TYPE
   SYNTAX      INTEGER
               {
               none (0)
               }
   MAX-ACCESS  read-write
   STATUS      current
   DESCRIPTION
      "Path: v6Router.editConf.qualityMonitor.destinations.delayAlarm.jitterDownStat.none

       Possibilities:
               none   (0)"
   ::= {er1646v2IpV6RtrQMonDestinationsEntry 119939072}

er1646v2IpV6RtrQMonDestinationsDelayAlarmJdownsNMn OBJECT-TYPE
   SYNTAX      Integer32
   UNITS       "msec"
   MAX-ACCESS  read-write
   STATUS      current
   DESCRIPTION
      "Path: v6Router.editConf.qualityMonitor.destinations.delayAlarm.jitterDownStat.range.min

       unit name = msec"
   ::= {er1646v2IpV6RtrQMonDestinationsEntry 119948288}

er1646v2IpV6RtrQMonDestinationsDelayAlarmJdownsNMx OBJECT-TYPE
   SYNTAX      Integer32
   UNITS       "msec"
   MAX-ACCESS  read-write
   STATUS      current
   DESCRIPTION
      "Path: v6Router.editConf.qualityMonitor.destinations.delayAlarm.jitterDownStat.range.max

       unit name = msec"
   ::= {er1646v2IpV6RtrQMonDestinationsEntry 119949312}

er1646v2IpV6RtrQMonDestinationsDelayAlarmJdownsTB1 OBJECT-TYPE
   SYNTAX      Integer32
   UNITS       "msec"
   MAX-ACCESS  read-write
   STATUS      current
   DESCRIPTION
      "Path: v6Router.editConf.qualityMonitor.destinations.delayAlarm.jitterDownStat.table.bin1

       unit name = msec"
   ::= {er1646v2IpV6RtrQMonDestinationsEntry 119955968}

er1646v2IpV6RtrQMonDestinationsDelayAlarmJdownsTB2 OBJECT-TYPE
   SYNTAX      Integer32
   UNITS       "msec"
   MAX-ACCESS  read-write
   STATUS      current
   DESCRIPTION
      "Path: v6Router.editConf.qualityMonitor.destinations.delayAlarm.jitterDownStat.table.bin2

       unit name = msec"
   ::= {er1646v2IpV6RtrQMonDestinationsEntry 119956480}

er1646v2IpV6RtrQMonDestinationsDelayAlarmJdownsTB3 OBJECT-TYPE
   SYNTAX      Integer32
   UNITS       "msec"
   MAX-ACCESS  read-write
   STATUS      current
   DESCRIPTION
      "Path: v6Router.editConf.qualityMonitor.destinations.delayAlarm.jitterDownStat.table.bin3

       unit name = msec"
   ::= {er1646v2IpV6RtrQMonDestinationsEntry 119956992}

er1646v2IpV6RtrQMonDestinationsDelayAlarmJdownsTB4 OBJECT-TYPE
   SYNTAX      Integer32
   UNITS       "msec"
   MAX-ACCESS  read-write
   STATUS      current
   DESCRIPTION
      "Path: v6Router.editConf.qualityMonitor.destinations.delayAlarm.jitterDownStat.table.bin4

       unit name = msec"
   ::= {er1646v2IpV6RtrQMonDestinationsEntry 119957504}

er1646v2IpV6RtrQMonDestinationsDelayAlarmJdownsTB5 OBJECT-TYPE
   SYNTAX      Integer32
   UNITS       "msec"
   MAX-ACCESS  read-write
   STATUS      current
   DESCRIPTION
      "Path: v6Router.editConf.qualityMonitor.destinations.delayAlarm.jitterDownStat.table.bin5

       unit name = msec"
   ::= {er1646v2IpV6RtrQMonDestinationsEntry 119958016}

er1646v2IpV6RtrQMonDestinationsDelayAlarmJdownsTB6 OBJECT-TYPE
   SYNTAX      Integer32
   UNITS       "msec"
   MAX-ACCESS  read-write
   STATUS      current
   DESCRIPTION
      "Path: v6Router.editConf.qualityMonitor.destinations.delayAlarm.jitterDownStat.table.bin6

       unit name = msec"
   ::= {er1646v2IpV6RtrQMonDestinationsEntry 119958528}

er1646v2IpV6RtrQMonDestinationsDelayAlarmJdownsTB7 OBJECT-TYPE
   SYNTAX      Integer32
   UNITS       "msec"
   MAX-ACCESS  read-write
   STATUS      current
   DESCRIPTION
      "Path: v6Router.editConf.qualityMonitor.destinations.delayAlarm.jitterDownStat.table.bin7

       unit name = msec"
   ::= {er1646v2IpV6RtrQMonDestinationsEntry 119959040}

er1646v2IpV6RtrQMonDestinationsDelayAlarmJdownsTB8 OBJECT-TYPE
   SYNTAX      Integer32
   UNITS       "msec"
   MAX-ACCESS  read-write
   STATUS      current
   DESCRIPTION
      "Path: v6Router.editConf.qualityMonitor.destinations.delayAlarm.jitterDownStat.table.bin8

       unit name = msec"
   ::= {er1646v2IpV6RtrQMonDestinationsEntry 119959552}

er1646v2IpV6RtrQMonDestinationsDelayAlarmJdownsTMx OBJECT-TYPE
   SYNTAX      Integer32
   UNITS       "msec"
   MAX-ACCESS  read-write
   STATUS      current
   DESCRIPTION
      "Path: v6Router.editConf.qualityMonitor.destinations.delayAlarm.jitterDownStat.table.max

       unit name = msec"
   ::= {er1646v2IpV6RtrQMonDestinationsEntry 119960064}

er1646v2IpV6RtrQMonDestinationsDelayAlarmDelayUpAvrgOn OBJECT-TYPE
   SYNTAX      Integer32
   UNITS       "msec"
   MAX-ACCESS  read-write
   STATUS      current
   DESCRIPTION
      "Path: v6Router.editConf.qualityMonitor.destinations.delayAlarm.delayUpAvrgOn

       unit name = msec"
   ::= {er1646v2IpV6RtrQMonDestinationsEntry 118751232}

er1646v2IpV6RtrQMonDestinationsDelayAlarmDelayUpAvrgOff OBJECT-TYPE
   SYNTAX      Integer32
   UNITS       "msec"
   MAX-ACCESS  read-write
   STATUS      current
   DESCRIPTION
      "Path: v6Router.editConf.qualityMonitor.destinations.delayAlarm.delayUpAvrgOff

       unit name = msec"
   ::= {er1646v2IpV6RtrQMonDestinationsEntry 118816768}

er1646v2IpV6RtrQMonDestinationsDelayAlarmDelayUpMaxOn OBJECT-TYPE
   SYNTAX      Integer32
   UNITS       "msec"
   MAX-ACCESS  read-write
   STATUS      current
   DESCRIPTION
      "Path: v6Router.editConf.qualityMonitor.destinations.delayAlarm.delayUpMaxOn

       unit name = msec"
   ::= {er1646v2IpV6RtrQMonDestinationsEntry 118882304}

er1646v2IpV6RtrQMonDestinationsDelayAlarmDelayUpMaxOff OBJECT-TYPE
   SYNTAX      Integer32
   UNITS       "msec"
   MAX-ACCESS  read-write
   STATUS      current
   DESCRIPTION
      "Path: v6Router.editConf.qualityMonitor.destinations.delayAlarm.delayUpMaxOff

       unit name = msec"
   ::= {er1646v2IpV6RtrQMonDestinationsEntry 118947840}

er1646v2IpV6RtrQMonDestinationsDelayAlarmDupsType OBJECT-TYPE
   SYNTAX      INTEGER
               {
               fd (1),
               fdr (2)
               }
   MAX-ACCESS  read-write
   STATUS      current
   DESCRIPTION
      "Path: v6Router.editConf.qualityMonitor.destinations.delayAlarm.delayUpStat.type

       Possibilities:
               fd   (1)
               fdr   (2)"
   ::= {er1646v2IpV6RtrQMonDestinationsEntry 119414784}

er1646v2IpV6RtrQMonDestinationsDelayAlarmDupsBinsN OBJECT-TYPE
   SYNTAX      INTEGER
               {
               none (0)
               }
   MAX-ACCESS  read-write
   STATUS      current
   DESCRIPTION
      "Path: v6Router.editConf.qualityMonitor.destinations.delayAlarm.delayUpStat.bins.none

       Possibilities:
               none   (0)"
   ::= {er1646v2IpV6RtrQMonDestinationsEntry 119424000}

er1646v2IpV6RtrQMonDestinationsDelayAlarmDupsBinsNMn OBJECT-TYPE
   SYNTAX      Integer32
   UNITS       "msec"
   MAX-ACCESS  read-write
   STATUS      current
   DESCRIPTION
      "Path: v6Router.editConf.qualityMonitor.destinations.delayAlarm.delayUpStat.bins.range.min

       unit name = msec"
   ::= {er1646v2IpV6RtrQMonDestinationsEntry 119425152}

er1646v2IpV6RtrQMonDestinationsDelayAlarmDupsBinsNMx OBJECT-TYPE
   SYNTAX      Integer32
   UNITS       "msec"
   MAX-ACCESS  read-write
   STATUS      current
   DESCRIPTION
      "Path: v6Router.editConf.qualityMonitor.destinations.delayAlarm.delayUpStat.bins.range.max

       unit name = msec"
   ::= {er1646v2IpV6RtrQMonDestinationsEntry 119425280}

er1646v2IpV6RtrQMonDestinationsDelayAlarmDupsBinsTB1 OBJECT-TYPE
   SYNTAX      Integer32
   UNITS       "msec"
   MAX-ACCESS  read-write
   STATUS      current
   DESCRIPTION
      "Path: v6Router.editConf.qualityMonitor.destinations.delayAlarm.delayUpStat.bins.table.bin1

       unit name = msec"
   ::= {er1646v2IpV6RtrQMonDestinationsEntry 119426112}

er1646v2IpV6RtrQMonDestinationsDelayAlarmDupsBinsTB2 OBJECT-TYPE
   SYNTAX      Integer32
   UNITS       "msec"
   MAX-ACCESS  read-write
   STATUS      current
   DESCRIPTION
      "Path: v6Router.editConf.qualityMonitor.destinations.delayAlarm.delayUpStat.bins.table.bin2

       unit name = msec"
   ::= {er1646v2IpV6RtrQMonDestinationsEntry 119426176}

er1646v2IpV6RtrQMonDestinationsDelayAlarmDupsBinsTB3 OBJECT-TYPE
   SYNTAX      Integer32
   UNITS       "msec"
   MAX-ACCESS  read-write
   STATUS      current
   DESCRIPTION
      "Path: v6Router.editConf.qualityMonitor.destinations.delayAlarm.delayUpStat.bins.table.bin3

       unit name = msec"
   ::= {er1646v2IpV6RtrQMonDestinationsEntry 119426240}

er1646v2IpV6RtrQMonDestinationsDelayAlarmDupsBinsTB4 OBJECT-TYPE
   SYNTAX      Integer32
   UNITS       "msec"
   MAX-ACCESS  read-write
   STATUS      current
   DESCRIPTION
      "Path: v6Router.editConf.qualityMonitor.destinations.delayAlarm.delayUpStat.bins.table.bin4

       unit name = msec"
   ::= {er1646v2IpV6RtrQMonDestinationsEntry 119426304}

er1646v2IpV6RtrQMonDestinationsDelayAlarmDupsBinsTB5 OBJECT-TYPE
   SYNTAX      Integer32
   UNITS       "msec"
   MAX-ACCESS  read-write
   STATUS      current
   DESCRIPTION
      "Path: v6Router.editConf.qualityMonitor.destinations.delayAlarm.delayUpStat.bins.table.bin5

       unit name = msec"
   ::= {er1646v2IpV6RtrQMonDestinationsEntry 119426368}

er1646v2IpV6RtrQMonDestinationsDelayAlarmDupsBinsTB6 OBJECT-TYPE
   SYNTAX      Integer32
   UNITS       "msec"
   MAX-ACCESS  read-write
   STATUS      current
   DESCRIPTION
      "Path: v6Router.editConf.qualityMonitor.destinations.delayAlarm.delayUpStat.bins.table.bin6

       unit name = msec"
   ::= {er1646v2IpV6RtrQMonDestinationsEntry 119426432}

er1646v2IpV6RtrQMonDestinationsDelayAlarmDupsBinsTB7 OBJECT-TYPE
   SYNTAX      Integer32
   UNITS       "msec"
   MAX-ACCESS  read-write
   STATUS      current
   DESCRIPTION
      "Path: v6Router.editConf.qualityMonitor.destinations.delayAlarm.delayUpStat.bins.table.bin7

       unit name = msec"
   ::= {er1646v2IpV6RtrQMonDestinationsEntry 119426496}

er1646v2IpV6RtrQMonDestinationsDelayAlarmDupsBinsTB8 OBJECT-TYPE
   SYNTAX      Integer32
   UNITS       "msec"
   MAX-ACCESS  read-write
   STATUS      current
   DESCRIPTION
      "Path: v6Router.editConf.qualityMonitor.destinations.delayAlarm.delayUpStat.bins.table.bin8

       unit name = msec"
   ::= {er1646v2IpV6RtrQMonDestinationsEntry 119426560}

er1646v2IpV6RtrQMonDestinationsDelayAlarmDupsBinsTMx OBJECT-TYPE
   SYNTAX      Integer32
   UNITS       "msec"
   MAX-ACCESS  read-write
   STATUS      current
   DESCRIPTION
      "Path: v6Router.editConf.qualityMonitor.destinations.delayAlarm.delayUpStat.bins.table.max

       unit name = msec"
   ::= {er1646v2IpV6RtrQMonDestinationsEntry 119426624}

er1646v2IpV6RtrQMonDestinationsDelayAlarmDelayDownAvrgOn OBJECT-TYPE
   SYNTAX      Integer32
   UNITS       "msec"
   MAX-ACCESS  read-write
   STATUS      current
   DESCRIPTION
      "Path: v6Router.editConf.qualityMonitor.destinations.delayAlarm.delayDownAvrgOn

       unit name = msec"
   ::= {er1646v2IpV6RtrQMonDestinationsEntry 119013376}

er1646v2IpV6RtrQMonDestinationsDelayAlarmDelayDownAvrgOff OBJECT-TYPE
   SYNTAX      Integer32
   UNITS       "msec"
   MAX-ACCESS  read-write
   STATUS      current
   DESCRIPTION
      "Path: v6Router.editConf.qualityMonitor.destinations.delayAlarm.delayDownAvrgOff

       unit name = msec"
   ::= {er1646v2IpV6RtrQMonDestinationsEntry 119078912}

er1646v2IpV6RtrQMonDestinationsDelayAlarmDelayDownMaxOn OBJECT-TYPE
   SYNTAX      Integer32
   UNITS       "msec"
   MAX-ACCESS  read-write
   STATUS      current
   DESCRIPTION
      "Path: v6Router.editConf.qualityMonitor.destinations.delayAlarm.delayDownMaxOn

       unit name = msec"
   ::= {er1646v2IpV6RtrQMonDestinationsEntry 119144448}

er1646v2IpV6RtrQMonDestinationsDelayAlarmDelayDownMaxOff OBJECT-TYPE
   SYNTAX      Integer32
   UNITS       "msec"
   MAX-ACCESS  read-write
   STATUS      current
   DESCRIPTION
      "Path: v6Router.editConf.qualityMonitor.destinations.delayAlarm.delayDownMaxOff

       unit name = msec"
   ::= {er1646v2IpV6RtrQMonDestinationsEntry 119209984}

er1646v2IpV6RtrQMonDestinationsDelayAlarmDdownsType OBJECT-TYPE
   SYNTAX      INTEGER
               {
               fd (1),
               fdr (2)
               }
   MAX-ACCESS  read-write
   STATUS      current
   DESCRIPTION
      "Path: v6Router.editConf.qualityMonitor.destinations.delayAlarm.delayDownStat.type

       Possibilities:
               fd   (1)
               fdr   (2)"
   ::= {er1646v2IpV6RtrQMonDestinationsEntry 119545856}

er1646v2IpV6RtrQMonDestinationsDelayAlarmDdownsBinsN OBJECT-TYPE
   SYNTAX      INTEGER
               {
               none (0)
               }
   MAX-ACCESS  read-write
   STATUS      current
   DESCRIPTION
      "Path: v6Router.editConf.qualityMonitor.destinations.delayAlarm.delayDownStat.bins.none

       Possibilities:
               none   (0)"
   ::= {er1646v2IpV6RtrQMonDestinationsEntry 119555072}

er1646v2IpV6RtrQMonDestinationsDelayAlarmDdownsBinsNMn OBJECT-TYPE
   SYNTAX      Integer32
   UNITS       "msec"
   MAX-ACCESS  read-write
   STATUS      current
   DESCRIPTION
      "Path: v6Router.editConf.qualityMonitor.destinations.delayAlarm.delayDownStat.bins.range.min

       unit name = msec"
   ::= {er1646v2IpV6RtrQMonDestinationsEntry 119556224}

er1646v2IpV6RtrQMonDestinationsDelayAlarmDdownsBinsNMx OBJECT-TYPE
   SYNTAX      Integer32
   UNITS       "msec"
   MAX-ACCESS  read-write
   STATUS      current
   DESCRIPTION
      "Path: v6Router.editConf.qualityMonitor.destinations.delayAlarm.delayDownStat.bins.range.max

       unit name = msec"
   ::= {er1646v2IpV6RtrQMonDestinationsEntry 119556352}

er1646v2IpV6RtrQMonDestinationsDelayAlarmDdownsBinsTB1 OBJECT-TYPE
   SYNTAX      Integer32
   UNITS       "msec"
   MAX-ACCESS  read-write
   STATUS      current
   DESCRIPTION
      "Path: v6Router.editConf.qualityMonitor.destinations.delayAlarm.delayDownStat.bins.table.bin1

       unit name = msec"
   ::= {er1646v2IpV6RtrQMonDestinationsEntry 119557184}

er1646v2IpV6RtrQMonDestinationsDelayAlarmDdownsBinsTB2 OBJECT-TYPE
   SYNTAX      Integer32
   UNITS       "msec"
   MAX-ACCESS  read-write
   STATUS      current
   DESCRIPTION
      "Path: v6Router.editConf.qualityMonitor.destinations.delayAlarm.delayDownStat.bins.table.bin2

       unit name = msec"
   ::= {er1646v2IpV6RtrQMonDestinationsEntry 119557248}

er1646v2IpV6RtrQMonDestinationsDelayAlarmDdownsBinsTB3 OBJECT-TYPE
   SYNTAX      Integer32
   UNITS       "msec"
   MAX-ACCESS  read-write
   STATUS      current
   DESCRIPTION
      "Path: v6Router.editConf.qualityMonitor.destinations.delayAlarm.delayDownStat.bins.table.bin3

       unit name = msec"
   ::= {er1646v2IpV6RtrQMonDestinationsEntry 119557312}

er1646v2IpV6RtrQMonDestinationsDelayAlarmDdownsBinsTB4 OBJECT-TYPE
   SYNTAX      Integer32
   UNITS       "msec"
   MAX-ACCESS  read-write
   STATUS      current
   DESCRIPTION
      "Path: v6Router.editConf.qualityMonitor.destinations.delayAlarm.delayDownStat.bins.table.bin4

       unit name = msec"
   ::= {er1646v2IpV6RtrQMonDestinationsEntry 119557376}

er1646v2IpV6RtrQMonDestinationsDelayAlarmDdownsBinsTB5 OBJECT-TYPE
   SYNTAX      Integer32
   UNITS       "msec"
   MAX-ACCESS  read-write
   STATUS      current
   DESCRIPTION
      "Path: v6Router.editConf.qualityMonitor.destinations.delayAlarm.delayDownStat.bins.table.bin5

       unit name = msec"
   ::= {er1646v2IpV6RtrQMonDestinationsEntry 119557440}

er1646v2IpV6RtrQMonDestinationsDelayAlarmDdownsBinsTB6 OBJECT-TYPE
   SYNTAX      Integer32
   UNITS       "msec"
   MAX-ACCESS  read-write
   STATUS      current
   DESCRIPTION
      "Path: v6Router.editConf.qualityMonitor.destinations.delayAlarm.delayDownStat.bins.table.bin6

       unit name = msec"
   ::= {er1646v2IpV6RtrQMonDestinationsEntry 119557504}

er1646v2IpV6RtrQMonDestinationsDelayAlarmDdownsBinsTB7 OBJECT-TYPE
   SYNTAX      Integer32
   UNITS       "msec"
   MAX-ACCESS  read-write
   STATUS      current
   DESCRIPTION
      "Path: v6Router.editConf.qualityMonitor.destinations.delayAlarm.delayDownStat.bins.table.bin7

       unit name = msec"
   ::= {er1646v2IpV6RtrQMonDestinationsEntry 119557568}

er1646v2IpV6RtrQMonDestinationsDelayAlarmDdownsBinsTB8 OBJECT-TYPE
   SYNTAX      Integer32
   UNITS       "msec"
   MAX-ACCESS  read-write
   STATUS      current
   DESCRIPTION
      "Path: v6Router.editConf.qualityMonitor.destinations.delayAlarm.delayDownStat.bins.table.bin8

       unit name = msec"
   ::= {er1646v2IpV6RtrQMonDestinationsEntry 119557632}

er1646v2IpV6RtrQMonDestinationsDelayAlarmDdownsBinsTMx OBJECT-TYPE
   SYNTAX      Integer32
   UNITS       "msec"
   MAX-ACCESS  read-write
   STATUS      current
   DESCRIPTION
      "Path: v6Router.editConf.qualityMonitor.destinations.delayAlarm.delayDownStat.bins.table.max

       unit name = msec"
   ::= {er1646v2IpV6RtrQMonDestinationsEntry 119557696}

er1646v2IpV6RtrQMonDestinationsAlarmMask OBJECT-TYPE
   SYNTAX      Integer32
   MAX-ACCESS  read-write
   STATUS      current
   DESCRIPTION
      "Path: v6Router.editConf.qualityMonitor.destinations.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2IpV6RtrQMonDestinationsEntry 251658240}

er1646v2IpV6RtrQMonDestinationsLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: v6Router.editConf.qualityMonitor.destinations.logging

       Possibilities:
               disabled   (0)
               3min   (3)
               5min   (5)
               10min   (10)
               15min   (15)
               30min   (30)
               60min   (60)"
   ::= {er1646v2IpV6RtrQMonDestinationsEntry 201326592}

er1646v2IpV6RtrQMonDestinationsLoggingDepth OBJECT-TYPE
   SYNTAX      INTEGER
               {
               s4 (4),
               s8 (8),
               s16 (16),
               s32 (32),
               s128 (128),
               s512 (512),
               s1024 (1024)
               }
   MAX-ACCESS  read-write
   STATUS      current
   DESCRIPTION
      "Path: v6Router.editConf.qualityMonitor.destinations.loggingDepth

       Possibilities:
               4   (4)
               8   (8)
               16   (16)
               32   (32)
               128   (128)
               512   (512)
               1024   (1024)"
   ::= {er1646v2IpV6RtrQMonDestinationsEntry 503316480}

er1646v2IpV6RtrQMonUdpServerPort OBJECT-TYPE
   SYNTAX      SEQUENCE OF Er1646v2IpV6RtrQMonUdpServerPortEntry
   MAX-ACCESS  not-accessible
   STATUS      current
   DESCRIPTION
      ""
   ::= {er1646v2IpV6RtrQMon 67108864}

er1646v2IpV6RtrQMonUdpServerPortEntry OBJECT-TYPE
   SYNTAX      Er1646v2IpV6RtrQMonUdpServerPortEntry
   MAX-ACCESS  not-accessible
   STATUS      current
   DESCRIPTION
      ""
   INDEX      { er1646v2IpV6RtrQMonUdpServerPortTableIx }
   ::= {er1646v2IpV6RtrQMonUdpServerPort 1}

Er1646v2IpV6RtrQMonUdpServerPortEntry ::=
   SEQUENCE
      {
      er1646v2IpV6RtrQMonUdpServerPortActions
         VariableLengthTableActions,
      er1646v2IpV6RtrQMonUdpServerPortTableIx
         TableIndex,
      er1646v2IpV6RtrQMonUdpServerPortDestinationPort
         Integer32,
      er1646v2IpV6RtrQMonUdpServerPortService
         INTEGER,
      er1646v2IpV6RtrQMonUdpServerPortPriority
         INTEGER,
      er1646v2IpV6RtrQMonUdpServerPortTrafficClass
         INTEGER
      }

er1646v2IpV6RtrQMonUdpServerPortActions OBJECT-TYPE
   SYNTAX      VariableLengthTableActions
   MAX-ACCESS  read-write
   STATUS      current
   DESCRIPTION
      "By way of this field, some manipulations
       on this table may be performed."
   ::= {er1646v2IpV6RtrQMonUdpServerPortEntry 2}

er1646v2IpV6RtrQMonUdpServerPortTableIx OBJECT-TYPE
   SYNTAX      TableIndex
   MAX-ACCESS  not-accessible
   STATUS      current
   DESCRIPTION
      ""
   ::= {er1646v2IpV6RtrQMonUdpServerPortEntry 11}

er1646v2IpV6RtrQMonUdpServerPortDestinationPort OBJECT-TYPE
   SYNTAX      Integer32
   MAX-ACCESS  read-write
   STATUS      current
   DESCRIPTION
      "Path: v6Router.editConf.qualityMonitor.udpServerPort.destinationPort"
   ::= {er1646v2IpV6RtrQMonUdpServerPortEntry 16777216}

er1646v2IpV6RtrQMonUdpServerPortService OBJECT-TYPE
   SYNTAX      INTEGER
               {
               proprietary (1),
               twampLight (2)
               }
   MAX-ACCESS  read-write
   STATUS      current
   DESCRIPTION
      "Path: v6Router.editConf.qualityMonitor.udpServerPort.service

       Possibilities:
               proprietary   (1)
               twampLight   (2)"
   ::= {er1646v2IpV6RtrQMonUdpServerPortEntry 234881024}

er1646v2IpV6RtrQMonUdpServerPortPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: v6Router.editConf.qualityMonitor.udpServerPort.priority

       Possibilities:
               queue1   (0)
               queue2   (1)
               queue3   (2)
               queue4   (3)
               queue5   (4)
               lowDelayQueue   (5)
               lowDelay2Queue   (6)
               systemQueue   (7)"
   ::= {er1646v2IpV6RtrQMonUdpServerPortEntry 218103808}

er1646v2IpV6RtrQMonUdpServerPortTrafficClass OBJECT-TYPE
   SYNTAX      INTEGER
               {
               keepTos (-1),
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: v6Router.editConf.qualityMonitor.udpServerPort.trafficClass

       Possibilities:
               keepTos   (-1)
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2IpV6RtrQMonUdpServerPortEntry 167772160}


er1646v2IpV6RtrAlarmMask OBJECT-TYPE
   SYNTAX      Integer32
   MAX-ACCESS  read-write
   STATUS      current
   DESCRIPTION
      "Path: v6Router.editConf.alarmMask
       Info: routAlarmMask

       Bit meanings:
               bit 0 = pingActive,
               bit 1 = qMonLoss,
               bit 2 = qMonDelay,
               bit 3 = qMonJitter"
   ::= {er1646v2IpV6Rtr 135}


er1646v2IpV6RtrAlarmLev OBJECT IDENTIFIER ::= {er1646v2IpV6Rtr 170}

er1646v2IpV6RtrAlarmLevSSC OBJECT IDENTIFIER ::= {er1646v2IpV6RtrAlarmLev 1}

er1646v2IpV6RtrAlarmLevEntry OBJECT IDENTIFIER ::= {er1646v2IpV6RtrAlarmLevSSC 1}

er1646v2IpV6RtrAlarmLevPingActive OBJECT-TYPE
   SYNTAX      Integer32
   MAX-ACCESS  read-write
   STATUS      current
   DESCRIPTION
      "Path: v6Router.editConf.alarmLevel.pingActive"
   ::= {er1646v2IpV6RtrAlarmLevEntry 16777216}

er1646v2IpV6RtrAlarmLevQMonLoss OBJECT-TYPE
   SYNTAX      Integer32
   MAX-ACCESS  read-write
   STATUS      current
   DESCRIPTION
      "Path: v6Router.editConf.alarmLevel.qMonLoss"
   ::= {er1646v2IpV6RtrAlarmLevEntry 33554432}

er1646v2IpV6RtrAlarmLevQMonDelay OBJECT-TYPE
   SYNTAX      Integer32
   MAX-ACCESS  read-write
   STATUS      current
   DESCRIPTION
      "Path: v6Router.editConf.alarmLevel.qMonDelay"
   ::= {er1646v2IpV6RtrAlarmLevEntry 50331648}

er1646v2IpV6RtrAlarmLevQMonJitter OBJECT-TYPE
   SYNTAX      Integer32
   MAX-ACCESS  read-write
   STATUS      current
   DESCRIPTION
      "Path: v6Router.editConf.alarmLevel.qMonJitter"
   ::= {er1646v2IpV6RtrAlarmLevEntry 67108864}



sr1646v2IpV6Rtr OBJECT IDENTIFIER ::= {r1646v2IpV6Rtr 14}


sr1646v2IpV6RtrInterfaces OBJECT IDENTIFIER ::= {sr1646v2IpV6Rtr 20}

sr1646v2IpV6RtrInterfacesSSCTable OBJECT-TYPE
   SYNTAX      SEQUENCE OF Sr1646v2IpV6RtrInterfacesEntry
   MAX-ACCESS  not-accessible
   STATUS      current
   DESCRIPTION
      "ipV6 routing interfaces"
   ::= {sr1646v2IpV6RtrInterfaces 1}

sr1646v2IpV6RtrInterfacesEntry OBJECT-TYPE
   SYNTAX      Sr1646v2IpV6RtrInterfacesEntry
   MAX-ACCESS  not-accessible
   STATUS      current
   DESCRIPTION
      ""
   INDEX      { sr1646v2IpV6RtrInterfacesTableIx }
   ::= {sr1646v2IpV6RtrInterfacesSSCTable 1}

Sr1646v2IpV6RtrInterfacesEntry ::=
   SEQUENCE
      {
      sr1646v2IpV6RtrInterfacesTableIx
         TableIndex,
      sr1646v2IpV6RtrInterfacesName
         DisplayString,
      sr1646v2IpV6RtrInterfacesState
         INTEGER,
      sr1646v2IpV6RtrInterfacesInterfaceId
         OCTET STRING,
      sr1646v2IpV6RtrInterfacesLinkMtu
         Integer32,
      sr1646v2IpV6RtrInterfacesHopLimit
         Integer32,
      sr1646v2IpV6RtrInterfacesTimersBaseReachableTime
         TimeTicks,
      sr1646v2IpV6RtrInterfacesTimersReachableTime
         TimeTicks,
      sr1646v2IpV6RtrInterfacesTimersRetransmitTime
         TimeTicks,
      sr1646v2IpV6RtrInterfacesDhcpIaid
         Counter32
      }

sr1646v2IpV6RtrInterfacesTableIx OBJECT-TYPE
   SYNTAX      TableIndex
   MAX-ACCESS  not-accessible
   STATUS      current
   DESCRIPTION
      ""
   ::= {sr1646v2IpV6RtrInterfacesEntry 11}

sr1646v2IpV6RtrInterfacesName OBJECT-TYPE
   SYNTAX      DisplayString
   MAX-ACCESS  read-only
   STATUS      current
   DESCRIPTION
      "Path: v6Router.status.interfaces.name"
   ::= {sr1646v2IpV6RtrInterfacesEntry 16777216}

sr1646v2IpV6RtrInterfacesState OBJECT-TYPE
   SYNTAX      INTEGER
               {
               disabled (0),
               enabled (1)
               }
   MAX-ACCESS  read-only
   STATUS      current
   DESCRIPTION
      "Path: v6Router.status.interfaces.state

       Possibilities:
               disabled   (0)
               enabled   (1)"
   ::= {sr1646v2IpV6RtrInterfacesEntry 33554432}

sr1646v2IpV6RtrInterfacesInterfaceId OBJECT-TYPE
   SYNTAX      OCTET STRING
   MAX-ACCESS  read-only
   STATUS      current
   DESCRIPTION
      "Path: v6Router.status.interfaces.interfaceId"
   ::= {sr1646v2IpV6RtrInterfacesEntry 50331648}

sr1646v2IpV6RtrInterfacesLinkMtu OBJECT-TYPE
   SYNTAX      Integer32
   MAX-ACCESS  read-only
   STATUS      current
   DESCRIPTION
      "Path: v6Router.status.interfaces.linkMtu"
   ::= {sr1646v2IpV6RtrInterfacesEntry 83886080}

sr1646v2IpV6RtrInterfacesHopLimit OBJECT-TYPE
   SYNTAX      Integer32
   MAX-ACCESS  read-only
   STATUS      current
   DESCRIPTION
      "Path: v6Router.status.interfaces.hopLimit"
   ::= {sr1646v2IpV6RtrInterfacesEntry 100663296}

sr1646v2IpV6RtrInterfacesTimersBaseReachableTime OBJECT-TYPE
   SYNTAX      TimeTicks
   MAX-ACCESS  read-only
   STATUS      current
   DESCRIPTION
      "Path: v6Router.status.interfaces.timers.baseReachableTime

       Time in centi-second."
   ::= {sr1646v2IpV6RtrInterfacesEntry 117506048}

sr1646v2IpV6RtrInterfacesTimersReachableTime OBJECT-TYPE
   SYNTAX      TimeTicks
   MAX-ACCESS  read-only
   STATUS      current
   DESCRIPTION
      "Path: v6Router.status.interfaces.timers.reachableTime

       Time in centi-second."
   ::= {sr1646v2IpV6RtrInterfacesEntry 117571584}

sr1646v2IpV6RtrInterfacesTimersRetransmitTime OBJECT-TYPE
   SYNTAX      TimeTicks
   MAX-ACCESS  read-only
   STATUS      current
   DESCRIPTION
      "Path: v6Router.status.interfaces.timers.retransmitTime

       Time in centi-second."
   ::= {sr1646v2IpV6RtrInterfacesEntry 117637120}

sr1646v2IpV6RtrInterfacesDhcpIaid OBJECT-TYPE
   SYNTAX      Counter32
   MAX-ACCESS  read-only
   STATUS      current
   DESCRIPTION
      "Path: v6Router.status.interfaces.dhcp.iaid

       32 bit unsigned wrappable counter."
   ::= {sr1646v2IpV6RtrInterfacesEntry 134283264}

sr1646v2IpV6RtrInterfacesAddresses OBJECT-TYPE
   SYNTAX      SEQUENCE OF Sr1646v2IpV6RtrInterfacesAddressesEntry
   MAX-ACCESS  not-accessible
   STATUS      current
   DESCRIPTION
      ""
   ::= {sr1646v2IpV6RtrInterfaces 67108864}

sr1646v2IpV6RtrInterfacesAddressesEntry OBJECT-TYPE
   SYNTAX      Sr1646v2IpV6RtrInterfacesAddressesEntry
   MAX-ACCESS  not-accessible
   STATUS      current
   DESCRIPTION
      ""
   INDEX      { sr1646v2IpV6RtrInterfacesTableIx,
                sr1646v2IpV6RtrInterfacesAddressesTableIx }
   ::= {sr1646v2IpV6RtrInterfacesAddresses 1}

Sr1646v2IpV6RtrInterfacesAddressesEntry ::=
   SEQUENCE
      {
      sr1646v2IpV6RtrInterfacesAddressesTableIx
         TableIndex,
      sr1646v2IpV6RtrInterfacesAddressesAddress
         Ipv6Address,
      sr1646v2IpV6RtrInterfacesAddressesPrefixLength
         Integer32,
      sr1646v2IpV6RtrInterfacesAddressesStatus
         INTEGER,
      sr1646v2IpV6RtrInterfacesAddressesOrigin
         INTEGER,
      sr1646v2IpV6RtrInterfacesAddressesFlagsInterfaceId
         INTEGER,
      sr1646v2IpV6RtrInterfacesAddressesFlagsAnycast
         INTEGER,
      sr1646v2IpV6RtrInterfacesAddressesTimersValidLifeTime
         TimeTicks,
      sr1646v2IpV6RtrInterfacesAddressesTimersPrefLifeTime
         TimeTicks
      }

sr1646v2IpV6RtrInterfacesAddressesTableIx OBJECT-TYPE
   SYNTAX      TableIndex
   MAX-ACCESS  not-accessible
   STATUS      current
   DESCRIPTION
      ""
   ::= {sr1646v2IpV6RtrInterfacesAddressesEntry 11}

sr1646v2IpV6RtrInterfacesAddressesAddress OBJECT-TYPE
   SYNTAX      Ipv6Address
   MAX-ACCESS  read-only
   STATUS      current
   DESCRIPTION
      "Path: v6Router.status.interfaces.addresses.address

       ipv6 address"
   ::= {sr1646v2IpV6RtrInterfacesAddressesEntry 16777216}

sr1646v2IpV6RtrInterfacesAddressesPrefixLength OBJECT-TYPE
   SYNTAX      Integer32
   MAX-ACCESS  read-only
   STATUS      current
   DESCRIPTION
      "Path: v6Router.status.interfaces.addresses.prefixLength"
   ::= {sr1646v2IpV6RtrInterfacesAddressesEntry 33554432}

sr1646v2IpV6RtrInterfacesAddressesStatus OBJECT-TYPE
   SYNTAX      INTEGER
               {
               invalid (0),
               tentative (1),
               deprecated (2),
               preferred (3)
               }
   MAX-ACCESS  read-only
   STATUS      current
   DESCRIPTION
      "Path: v6Router.status.interfaces.addresses.status

       Possibilities:
               invalid   (0)
               tentative   (1)
               deprecated   (2)
               preferred   (3)"
   ::= {sr1646v2IpV6RtrInterfacesAddressesEntry 50331648}

sr1646v2IpV6RtrInterfacesAddressesOrigin OBJECT-TYPE
   SYNTAX      INTEGER
               {
               unknown (0),
               manual (1),
               generalPrefix (2),
               statelessAuto (3),
               statefullAuto (4)
               }
   MAX-ACCESS  read-only
   STATUS      current
   DESCRIPTION
      "Path: v6Router.status.interfaces.addresses.origin

       Possibilities:
               unknown   (0)
               manual   (1)
               generalPrefix   (2)
               statelessAuto   (3)
               statefullAuto   (4)"
   ::= {sr1646v2IpV6RtrInterfacesAddressesEntry 67108864}

sr1646v2IpV6RtrInterfacesAddressesFlagsInterfaceId OBJECT-TYPE
   SYNTAX      INTEGER
               {
               no (0),
               yes (1)
               }
   MAX-ACCESS  read-only
   STATUS      current
   DESCRIPTION
      "Path: v6Router.status.interfaces.addresses.flags.interfaceId

       Possibilities:
               no   (0)
               yes   (1)"
   ::= {sr1646v2IpV6RtrInterfacesAddressesEntry 83951616}

sr1646v2IpV6RtrInterfacesAddressesFlagsAnycast OBJECT-TYPE
   SYNTAX      INTEGER
               {
               no (0),
               yes (1)
               }
   MAX-ACCESS  read-only
   STATUS      current
   DESCRIPTION
      "Path: v6Router.status.interfaces.addresses.flags.anycast

       Possibilities:
               no   (0)
               yes   (1)"
   ::= {sr1646v2IpV6RtrInterfacesAddressesEntry 84017152}

sr1646v2IpV6RtrInterfacesAddressesTimersValidLifeTime OBJECT-TYPE
   SYNTAX      TimeTicks
   MAX-ACCESS  read-only
   STATUS      current
   DESCRIPTION
      "Path: v6Router.status.interfaces.addresses.timers.validLifeTime

       Time in centi-second."
   ::= {sr1646v2IpV6RtrInterfacesAddressesEntry 100794368}

sr1646v2IpV6RtrInterfacesAddressesTimersPrefLifeTime OBJECT-TYPE
   SYNTAX      TimeTicks
   MAX-ACCESS  read-only
   STATUS      current
   DESCRIPTION
      "Path: v6Router.status.interfaces.addresses.timers.prefLifeTime

       Time in centi-second."
   ::= {sr1646v2IpV6RtrInterfacesAddressesEntry 100728832}


sr1646v2IpV6RtrRoutingTable OBJECT IDENTIFIER ::= {sr1646v2IpV6Rtr 21}

sr1646v2IpV6RtrRoutingTableSSCTable OBJECT-TYPE
   SYNTAX      SEQUENCE OF Sr1646v2IpV6RtrRoutingTableEntry
   MAX-ACCESS  not-accessible
   STATUS      current
   DESCRIPTION
      "ipV6 routing table"
   ::= {sr1646v2IpV6RtrRoutingTable 1}

sr1646v2IpV6RtrRoutingTableEntry OBJECT-TYPE
   SYNTAX      Sr1646v2IpV6RtrRoutingTableEntry
   MAX-ACCESS  not-accessible
   STATUS      current
   DESCRIPTION
      ""
   INDEX      { sr1646v2IpV6RtrRoutingTableTableIx }
   ::= {sr1646v2IpV6RtrRoutingTableSSCTable 1}

Sr1646v2IpV6RtrRoutingTableEntry ::=
   SEQUENCE
      {
      sr1646v2IpV6RtrRoutingTableTableIx
         TableIndex,
      sr1646v2IpV6RtrRoutingTableAddress
         Ipv6Address,
      sr1646v2IpV6RtrRoutingTablePrefixLength
         Integer32,
      sr1646v2IpV6RtrRoutingTableNextHop
         Ipv6Address,
      sr1646v2IpV6RtrRoutingTableInterface
         DisplayString,
      sr1646v2IpV6RtrRoutingTableStatus
         INTEGER,
      sr1646v2IpV6RtrRoutingTableType
         INTEGER,
      sr1646v2IpV6RtrRoutingTablePreference
         Integer32,
      sr1646v2IpV6RtrRoutingTableMetric
         Integer32,
      sr1646v2IpV6RtrRoutingTableTimeOut
         TimeTicks
      }

sr1646v2IpV6RtrRoutingTableTableIx OBJECT-TYPE
   SYNTAX      TableIndex
   MAX-ACCESS  not-accessible
   STATUS      current
   DESCRIPTION
      ""
   ::= {sr1646v2IpV6RtrRoutingTableEntry 11}

sr1646v2IpV6RtrRoutingTableAddress OBJECT-TYPE
   SYNTAX      Ipv6Address
   MAX-ACCESS  read-only
   STATUS      current
   DESCRIPTION
      "Path: v6Router.status.routingTable.address

       ipv6 address"
   ::= {sr1646v2IpV6RtrRoutingTableEntry 16777216}

sr1646v2IpV6RtrRoutingTablePrefixLength OBJECT-TYPE
   SYNTAX      Integer32
   MAX-ACCESS  read-only
   STATUS      current
   DESCRIPTION
      "Path: v6Router.status.routingTable.prefixLength"
   ::= {sr1646v2IpV6RtrRoutingTableEntry 33554432}

sr1646v2IpV6RtrRoutingTableNextHop OBJECT-TYPE
   SYNTAX      Ipv6Address
   MAX-ACCESS  read-only
   STATUS      current
   DESCRIPTION
      "Path: v6Router.status.routingTable.nextHop

       ipv6 address"
   ::= {sr1646v2IpV6RtrRoutingTableEntry 50331648}

sr1646v2IpV6RtrRoutingTableInterface OBJECT-TYPE
   SYNTAX      DisplayString
   MAX-ACCESS  read-only
   STATUS      current
   DESCRIPTION
      "Path: v6Router.status.routingTable.interface"
   ::= {sr1646v2IpV6RtrRoutingTableEntry 67108864}

sr1646v2IpV6RtrRoutingTableStatus OBJECT-TYPE
   SYNTAX      INTEGER
               {
               down (0),
               up (1),
               discard (3)
               }
   MAX-ACCESS  read-only
   STATUS      current
   DESCRIPTION
      "Path: v6Router.status.routingTable.status

       Possibilities:
               down   (0)
               up   (1)
               discard   (3)"
   ::= {sr1646v2IpV6RtrRoutingTableEntry 83886080}

sr1646v2IpV6RtrRoutingTableType OBJECT-TYPE
   SYNTAX      INTEGER
               {
               fixed (0),
               linkLocal (1),
               host (2),
               anycast (3),
               solicited (4),
               dhcp (5),
               redirect (8),
               advertised (9),
               static (10),
               network (11),
               natpt (12)
               }
   MAX-ACCESS  read-only
   STATUS      current
   DESCRIPTION
      "Path: v6Router.status.routingTable.type

       Possibilities:
               fixed   (0)
               linkLocal   (1)
               host   (2)
               anycast   (3)
               solicited   (4)
               dhcp   (5)
               redirect   (8)
               advertised   (9)
               static   (10)
               network   (11)
               natpt   (12)"
   ::= {sr1646v2IpV6RtrRoutingTableEntry 100663296}

sr1646v2IpV6RtrRoutingTablePreference OBJECT-TYPE
   SYNTAX      Integer32
   MAX-ACCESS  read-only
   STATUS      current
   DESCRIPTION
      "Path: v6Router.status.routingTable.preference"
   ::= {sr1646v2IpV6RtrRoutingTableEntry 117440512}

sr1646v2IpV6RtrRoutingTableMetric OBJECT-TYPE
   SYNTAX      Integer32
   MAX-ACCESS  read-only
   STATUS      current
   DESCRIPTION
      "Path: v6Router.status.routingTable.metric"
   ::= {sr1646v2IpV6RtrRoutingTableEntry 134217728}

sr1646v2IpV6RtrRoutingTableTimeOut OBJECT-TYPE
   SYNTAX      TimeTicks
   MAX-ACCESS  read-only
   STATUS      current
   DESCRIPTION
      "Path: v6Router.status.routingTable.timeOut

       Time in centi-second."
   ::= {sr1646v2IpV6RtrRoutingTableEntry 150994944}


sr1646v2IpV6RtrFragments OBJECT IDENTIFIER ::= {sr1646v2IpV6Rtr 22}

sr1646v2IpV6RtrFragmentsSSC OBJECT IDENTIFIER ::= {sr1646v2IpV6RtrFragments 1}

sr1646v2IpV6RtrFragmentsEntry OBJECT IDENTIFIER ::= {sr1646v2IpV6RtrFragmentsSSC 1}

sr1646v2IpV6RtrFragmentsPktsPending OBJECT-TYPE
   SYNTAX      Counter64
   MAX-ACCESS  read-only
   STATUS      current
   DESCRIPTION
      "Path: v6Router.status.fragments.pktsPending

       64 bit unsigned wrappable counter."
   ::= {sr1646v2IpV6RtrFragmentsEntry 16777216}

sr1646v2IpV6RtrFragmentsFragsPending OBJECT-TYPE
   SYNTAX      Counter64
   MAX-ACCESS  read-only
   STATUS      current
   DESCRIPTION
      "Path: v6Router.status.fragments.fragsPending

       64 bit unsigned wrappable counter."
   ::= {sr1646v2IpV6RtrFragmentsEntry 33554432}


sr1646v2IpV6RtrGeneralPrefixes OBJECT IDENTIFIER ::= {sr1646v2IpV6Rtr 23}

sr1646v2IpV6RtrGeneralPrefixesSSCTable OBJECT-TYPE
   SYNTAX      SEQUENCE OF Sr1646v2IpV6RtrGeneralPrefixesEntry
   MAX-ACCESS  not-accessible
   STATUS      current
   DESCRIPTION
      "ipV6 prefix pool status"
   ::= {sr1646v2IpV6RtrGeneralPrefixes 1}

sr1646v2IpV6RtrGeneralPrefixesEntry OBJECT-TYPE
   SYNTAX      Sr1646v2IpV6RtrGeneralPrefixesEntry
   MAX-ACCESS  not-accessible
   STATUS      current
   DESCRIPTION
      ""
   INDEX      { sr1646v2IpV6RtrGeneralPrefixesTableIx }
   ::= {sr1646v2IpV6RtrGeneralPrefixesSSCTable 1}

Sr1646v2IpV6RtrGeneralPrefixesEntry ::=
   SEQUENCE
      {
      sr1646v2IpV6RtrGeneralPrefixesTableIx
         TableIndex,
      sr1646v2IpV6RtrGeneralPrefixesName
         DisplayString,
      sr1646v2IpV6RtrGeneralPrefixesType
         INTEGER,
      sr1646v2IpV6RtrGeneralPrefixesPrefix
         Ipv6Address,
      sr1646v2IpV6RtrGeneralPrefixesPrefixLength
         Integer32,
      sr1646v2IpV6RtrGeneralPrefixesValidLifeTime
         TimeTicks,
      sr1646v2IpV6RtrGeneralPrefixesPrefLifeTime
         TimeTicks,
      sr1646v2IpV6RtrGeneralPrefixesAvailable
         Counter64,
      sr1646v2IpV6RtrGeneralPrefixesOccupied
         Counter32,
      sr1646v2IpV6RtrGeneralPrefixesAuto6to4Auto6to4Intf
         DisplayString,
      sr1646v2IpV6RtrGeneralPrefixesAuto6to4IpV4Address
         IpAddress,
      sr1646v2IpV6RtrGeneralPrefixesAuto6to4Subnet
         OCTET STRING
      }

sr1646v2IpV6RtrGeneralPrefixesTableIx OBJECT-TYPE
   SYNTAX      TableIndex
   MAX-ACCESS  not-accessible
   STATUS      current
   DESCRIPTION
      ""
   ::= {sr1646v2IpV6RtrGeneralPrefixesEntry 11}

sr1646v2IpV6RtrGeneralPrefixesName OBJECT-TYPE
   SYNTAX      DisplayString
   MAX-ACCESS  read-only
   STATUS      current
   DESCRIPTION
      "Path: v6Router.status.generalPrefixes.name"
   ::= {sr1646v2IpV6RtrGeneralPrefixesEntry 16777216}

sr1646v2IpV6RtrGeneralPrefixesType OBJECT-TYPE
   SYNTAX      INTEGER
               {
               static (0),
               dhcp (1),
               auto6to4 (2)
               }
   MAX-ACCESS  read-only
   STATUS      current
   DESCRIPTION
      "Path: v6Router.status.generalPrefixes.type

       Possibilities:
               static   (0)
               dhcp   (1)
               auto6to4   (2)"
   ::= {sr1646v2IpV6RtrGeneralPrefixesEntry 33554432}

sr1646v2IpV6RtrGeneralPrefixesPrefix OBJECT-TYPE
   SYNTAX      Ipv6Address
   MAX-ACCESS  read-only
   STATUS      current
   DESCRIPTION
      "Path: v6Router.status.generalPrefixes.prefix

       ipv6 address"
   ::= {sr1646v2IpV6RtrGeneralPrefixesEntry 50331648}

sr1646v2IpV6RtrGeneralPrefixesPrefixLength OBJECT-TYPE
   SYNTAX      Integer32
   MAX-ACCESS  read-only
   STATUS      current
   DESCRIPTION
      "Path: v6Router.status.generalPrefixes.prefixLength"
   ::= {sr1646v2IpV6RtrGeneralPrefixesEntry 67108864}

sr1646v2IpV6RtrGeneralPrefixesValidLifeTime OBJECT-TYPE
   SYNTAX      TimeTicks
   MAX-ACCESS  read-only
   STATUS      current
   DESCRIPTION
      "Path: v6Router.status.generalPrefixes.validLifeTime

       Time in centi-second."
   ::= {sr1646v2IpV6RtrGeneralPrefixesEntry 83886080}

sr1646v2IpV6RtrGeneralPrefixesPrefLifeTime OBJECT-TYPE
   SYNTAX      TimeTicks
   MAX-ACCESS  read-only
   STATUS      current
   DESCRIPTION
      "Path: v6Router.status.generalPrefixes.prefLifeTime

       Time in centi-second."
   ::= {sr1646v2IpV6RtrGeneralPrefixesEntry 100663296}

sr1646v2IpV6RtrGeneralPrefixesAvailable OBJECT-TYPE
   SYNTAX      Counter64
   MAX-ACCESS  read-only
   STATUS      current
   DESCRIPTION
      "Path: v6Router.status.generalPrefixes.available

       64 bit unsigned wrappable counter."
   ::= {sr1646v2IpV6RtrGeneralPrefixesEntry 117440512}

sr1646v2IpV6RtrGeneralPrefixesOccupied OBJECT-TYPE
   SYNTAX      Counter32
   MAX-ACCESS  read-only
   STATUS      current
   DESCRIPTION
      "Path: v6Router.status.generalPrefixes.occupied

       32 bit unsigned wrappable counter."
   ::= {sr1646v2IpV6RtrGeneralPrefixesEntry 134217728}

sr1646v2IpV6RtrGeneralPrefixesAuto6to4Auto6to4Intf OBJECT-TYPE
   SYNTAX      DisplayString
   MAX-ACCESS  read-only
   STATUS      current
   DESCRIPTION
      "Path: v6Router.status.generalPrefixes.auto6to4.auto6to4Intf"
   ::= {sr1646v2IpV6RtrGeneralPrefixesEntry 151191552}

sr1646v2IpV6RtrGeneralPrefixesAuto6to4IpV4Address OBJECT-TYPE
   SYNTAX      IpAddress
   MAX-ACCESS  read-only
   STATUS      current
   DESCRIPTION
      "Path: v6Router.status.generalPrefixes.auto6to4.ipV4Address"
   ::= {sr1646v2IpV6RtrGeneralPrefixesEntry 151060480}

sr1646v2IpV6RtrGeneralPrefixesAuto6to4Subnet OBJECT-TYPE
   SYNTAX      OCTET STRING
   MAX-ACCESS  read-only
   STATUS      current
   DESCRIPTION
      "Path: v6Router.status.generalPrefixes.auto6to4.subnet"
   ::= {sr1646v2IpV6RtrGeneralPrefixesEntry 151126016}


sr1646v2IpV6RtrPrefixBindings OBJECT IDENTIFIER ::= {sr1646v2IpV6Rtr 24}

sr1646v2IpV6RtrPrefixBindingsSSCTable OBJECT-TYPE
   SYNTAX      SEQUENCE OF Sr1646v2IpV6RtrPrefixBindingsEntry
   MAX-ACCESS  not-accessible
   STATUS      current
   DESCRIPTION
      "ipV6 prefix pool binding overview"
   ::= {sr1646v2IpV6RtrPrefixBindings 1}

sr1646v2IpV6RtrPrefixBindingsEntry OBJECT-TYPE
   SYNTAX      Sr1646v2IpV6RtrPrefixBindingsEntry
   MAX-ACCESS  not-accessible
   STATUS      current
   DESCRIPTION
      ""
   INDEX      { sr1646v2IpV6RtrPrefixBindingsTableIx }
   ::= {sr1646v2IpV6RtrPrefixBindingsSSCTable 1}

Sr1646v2IpV6RtrPrefixBindingsEntry ::=
   SEQUENCE
      {
      sr1646v2IpV6RtrPrefixBindingsTableIx
         TableIndex,
      sr1646v2IpV6RtrPrefixBindingsPool
         DisplayString,
      sr1646v2IpV6RtrPrefixBindingsInterface
         DisplayString,
      sr1646v2IpV6RtrPrefixBindingsPrefix
         Ipv6Address,
      sr1646v2IpV6RtrPrefixBindingsPrefixLength
         Integer32
      }

sr1646v2IpV6RtrPrefixBindingsTableIx OBJECT-TYPE
   SYNTAX      TableIndex
   MAX-ACCESS  not-accessible
   STATUS      current
   DESCRIPTION
      ""
   ::= {sr1646v2IpV6RtrPrefixBindingsEntry 11}

sr1646v2IpV6RtrPrefixBindingsPool OBJECT-TYPE
   SYNTAX      DisplayString
   MAX-ACCESS  read-only
   STATUS      current
   DESCRIPTION
      "Path: v6Router.status.prefixBindings.pool"
   ::= {sr1646v2IpV6RtrPrefixBindingsEntry 16777216}

sr1646v2IpV6RtrPrefixBindingsInterface OBJECT-TYPE
   SYNTAX      DisplayString
   MAX-ACCESS  read-only
   STATUS      current
   DESCRIPTION
      "Path: v6Router.status.prefixBindings.interface"
   ::= {sr1646v2IpV6RtrPrefixBindingsEntry 33554432}

sr1646v2IpV6RtrPrefixBindingsPrefix OBJECT-TYPE
   SYNTAX      Ipv6Address
   MAX-ACCESS  read-only
   STATUS      current
   DESCRIPTION
      "Path: v6Router.status.prefixBindings.prefix

       ipv6 address"
   ::= {sr1646v2IpV6RtrPrefixBindingsEntry 50331648}

sr1646v2IpV6RtrPrefixBindingsPrefixLength OBJECT-TYPE
   SYNTAX      Integer32
   MAX-ACCESS  read-only
   STATUS      current
   DESCRIPTION
      "Path: v6Router.status.prefixBindings.prefixLength"
   ::= {sr1646v2IpV6RtrPrefixBindingsEntry 67108864}


sr1646v2IpV6RtrMessages OBJECT IDENTIFIER ::= {sr1646v2IpV6Rtr 25}

sr1646v2IpV6RtrMessagesSSCTable OBJECT-TYPE
   SYNTAX      SEQUENCE OF Sr1646v2IpV6RtrMessagesEntry
   MAX-ACCESS  not-accessible
   STATUS      current
   DESCRIPTION
      "log or tracing messages"
   ::= {sr1646v2IpV6RtrMessages 1}

sr1646v2IpV6RtrMessagesEntry OBJECT-TYPE
   SYNTAX      Sr1646v2IpV6RtrMessagesEntry
   MAX-ACCESS  not-accessible
   STATUS      current
   DESCRIPTION
      ""
   INDEX      { sr1646v2IpV6RtrMessagesTableIx }
   ::= {sr1646v2IpV6RtrMessagesSSCTable 1}

Sr1646v2IpV6RtrMessagesEntry ::=
   SEQUENCE
      {
      sr1646v2IpV6RtrMessagesTableIx
         TableIndex,
      sr1646v2IpV6RtrMessagesMessage
         DisplayString
      }

sr1646v2IpV6RtrMessagesTableIx OBJECT-TYPE
   SYNTAX      TableIndex
   MAX-ACCESS  not-accessible
   STATUS      current
   DESCRIPTION
      ""
   ::= {sr1646v2IpV6RtrMessagesEntry 11}

sr1646v2IpV6RtrMessagesMessage OBJECT-TYPE
   SYNTAX      DisplayString
   MAX-ACCESS  read-only
   STATUS      current
   DESCRIPTION
      "Path: v6Router.status.messages.message"
   ::= {sr1646v2IpV6RtrMessagesEntry 16777216}


sr1646v2IpV6RtrDnsCache OBJECT IDENTIFIER ::= {sr1646v2IpV6Rtr 26}

sr1646v2IpV6RtrDnsCacheSSCTable OBJECT-TYPE
   SYNTAX      SEQUENCE OF Sr1646v2IpV6RtrDnsCacheEntry
   MAX-ACCESS  not-accessible
   STATUS      current
   DESCRIPTION
      "DNS cache table"
   ::= {sr1646v2IpV6RtrDnsCache 1}

sr1646v2IpV6RtrDnsCacheEntry OBJECT-TYPE
   SYNTAX      Sr1646v2IpV6RtrDnsCacheEntry
   MAX-ACCESS  not-accessible
   STATUS      current
   DESCRIPTION
      ""
   INDEX      { sr1646v2IpV6RtrDnsCacheTableIx }
   ::= {sr1646v2IpV6RtrDnsCacheSSCTable 1}

Sr1646v2IpV6RtrDnsCacheEntry ::=
   SEQUENCE
      {
      sr1646v2IpV6RtrDnsCacheTableIx
         TableIndex,
      sr1646v2IpV6RtrDnsCacheIpAddress
         IpAddress,
      sr1646v2IpV6RtrDnsCacheIpV6Address
         Ipv6Address,
      sr1646v2IpV6RtrDnsCacheHostname
         DisplayString,
      sr1646v2IpV6RtrDnsCacheTtl
         TimeTicks,
      sr1646v2IpV6RtrDnsCacheInfiniteTimeOut
         INTEGER,
      sr1646v2IpV6RtrDnsCacheMatches
         Counter32
      }

sr1646v2IpV6RtrDnsCacheTableIx OBJECT-TYPE
   SYNTAX      TableIndex
   MAX-ACCESS  not-accessible
   STATUS      current
   DESCRIPTION
      ""
   ::= {sr1646v2IpV6RtrDnsCacheEntry 11}

sr1646v2IpV6RtrDnsCacheIpAddress OBJECT-TYPE
   SYNTAX      IpAddress
   MAX-ACCESS  read-only
   STATUS      current
   DESCRIPTION
      "Path: v6Router.status.dnsCache.ipAddress"
   ::= {sr1646v2IpV6RtrDnsCacheEntry 16777216}

sr1646v2IpV6RtrDnsCacheIpV6Address OBJECT-TYPE
   SYNTAX      Ipv6Address
   MAX-ACCESS  read-only
   STATUS      current
   DESCRIPTION
      "Path: v6Router.status.dnsCache.ipV6Address

       ipv6 address"
   ::= {sr1646v2IpV6RtrDnsCacheEntry 83886080}

sr1646v2IpV6RtrDnsCacheHostname OBJECT-TYPE
   SYNTAX      DisplayString
   MAX-ACCESS  read-only
   STATUS      current
   DESCRIPTION
      "Path: v6Router.status.dnsCache.hostname"
   ::= {sr1646v2IpV6RtrDnsCacheEntry 33554432}

sr1646v2IpV6RtrDnsCacheTtl OBJECT-TYPE
   SYNTAX      TimeTicks
   MAX-ACCESS  read-only
   STATUS      current
   DESCRIPTION
      "Path: v6Router.status.dnsCache.ttl

       Time in centi-second."
   ::= {sr1646v2IpV6RtrDnsCacheEntry 50331648}

sr1646v2IpV6RtrDnsCacheInfiniteTimeOut OBJECT-TYPE
   SYNTAX      INTEGER
               {
               disabled (0),
               enabled (1),
               static (2)
               }
   MAX-ACCESS  read-only
   STATUS      current
   DESCRIPTION
      "Path: v6Router.status.dnsCache.infiniteTimeOut

       Possibilities:
               disabled   (0)
               enabled   (1)
               static   (2)"
   ::= {sr1646v2IpV6RtrDnsCacheEntry 67108864}

sr1646v2IpV6RtrDnsCacheMatches OBJECT-TYPE
   SYNTAX      Counter32
   MAX-ACCESS  read-only
   STATUS      current
   DESCRIPTION
      "Path: v6Router.status.dnsCache.matches

       32 bit unsigned wrappable counter."
   ::= {sr1646v2IpV6RtrDnsCacheEntry 100663296}


sr1646v2IpV6RtrDnsServers OBJECT IDENTIFIER ::= {sr1646v2IpV6Rtr 27}

sr1646v2IpV6RtrDnsServersSSCTable OBJECT-TYPE
   SYNTAX      SEQUENCE OF Sr1646v2IpV6RtrDnsServersEntry
   MAX-ACCESS  not-accessible
   STATUS      current
   DESCRIPTION
      "DNS server list"
   ::= {sr1646v2IpV6RtrDnsServers 1}

sr1646v2IpV6RtrDnsServersEntry OBJECT-TYPE
   SYNTAX      Sr1646v2IpV6RtrDnsServersEntry
   MAX-ACCESS  not-accessible
   STATUS      current
   DESCRIPTION
      ""
   INDEX      { sr1646v2IpV6RtrDnsServersTableIx }
   ::= {sr1646v2IpV6RtrDnsServersSSCTable 1}

Sr1646v2IpV6RtrDnsServersEntry ::=
   SEQUENCE
      {
      sr1646v2IpV6RtrDnsServersTableIx
         TableIndex,
      sr1646v2IpV6RtrDnsServersIpAddress
         Ipv6Address,
      sr1646v2IpV6RtrDnsServersType
         INTEGER,
      sr1646v2IpV6RtrDnsServersRcvdInterface
         DisplayString,
      sr1646v2IpV6RtrDnsServersPreference
         Integer32,
      sr1646v2IpV6RtrDnsServersStatus
         INTEGER,
      sr1646v2IpV6RtrDnsServersLifeTimer
         TimeTicks
      }

sr1646v2IpV6RtrDnsServersTableIx OBJECT-TYPE
   SYNTAX      TableIndex
   MAX-ACCESS  not-accessible
   STATUS      current
   DESCRIPTION
      ""
   ::= {sr1646v2IpV6RtrDnsServersEntry 11}

sr1646v2IpV6RtrDnsServersIpAddress OBJECT-TYPE
   SYNTAX      Ipv6Address
   MAX-ACCESS  read-only
   STATUS      current
   DESCRIPTION
      "Path: v6Router.status.dnsServers.ipAddress

       ipv6 address"
   ::= {sr1646v2IpV6RtrDnsServersEntry 16777216}

sr1646v2IpV6RtrDnsServersType OBJECT-TYPE
   SYNTAX      INTEGER
               {
               static (0),
               dhcp (1),
               ra (3)
               }
   MAX-ACCESS  read-only
   STATUS      current
   DESCRIPTION
      "Path: v6Router.status.dnsServers.type

       Possibilities:
               static   (0)
               dhcp   (1)
               ra   (3)"
   ::= {sr1646v2IpV6RtrDnsServersEntry 33554432}

sr1646v2IpV6RtrDnsServersRcvdInterface OBJECT-TYPE
   SYNTAX      DisplayString
   MAX-ACCESS  read-only
   STATUS      current
   DESCRIPTION
      "Path: v6Router.status.dnsServers.rcvdInterface"
   ::= {sr1646v2IpV6RtrDnsServersEntry 50331648}

sr1646v2IpV6RtrDnsServersPreference OBJECT-TYPE
   SYNTAX      Integer32
   MAX-ACCESS  read-only
   STATUS      current
   DESCRIPTION
      "Path: v6Router.status.dnsServers.preference"
   ::= {sr1646v2IpV6RtrDnsServersEntry 67108864}

sr1646v2IpV6RtrDnsServersStatus OBJECT-TYPE
   SYNTAX      INTEGER
               {
               unreachable (0),
               reachable (1),
               primary (2),
               secondary (3)
               }
   MAX-ACCESS  read-only
   STATUS      current
   DESCRIPTION
      "Path: v6Router.status.dnsServers.status

       Possibilities:
               unreachable   (0)
               reachable   (1)
               primary   (2)
               secondary   (3)"
   ::= {sr1646v2IpV6RtrDnsServersEntry 83886080}

sr1646v2IpV6RtrDnsServersLifeTimer OBJECT-TYPE
   SYNTAX      TimeTicks
   MAX-ACCESS  read-only
   STATUS      current
   DESCRIPTION
      "Path: v6Router.status.dnsServers.lifeTimer

       Time in centi-second."
   ::= {sr1646v2IpV6RtrDnsServersEntry 100663296}


sr1646v2IpV6RtrDnsDomains OBJECT IDENTIFIER ::= {sr1646v2IpV6Rtr 28}

sr1646v2IpV6RtrDnsDomainsSSCTable OBJECT-TYPE
   SYNTAX      SEQUENCE OF Sr1646v2IpV6RtrDnsDomainsEntry
   MAX-ACCESS  not-accessible
   STATUS      current
   DESCRIPTION
      "DNS domain list"
   ::= {sr1646v2IpV6RtrDnsDomains 1}

sr1646v2IpV6RtrDnsDomainsEntry OBJECT-TYPE
   SYNTAX      Sr1646v2IpV6RtrDnsDomainsEntry
   MAX-ACCESS  not-accessible
   STATUS      current
   DESCRIPTION
      ""
   INDEX      { sr1646v2IpV6RtrDnsDomainsTableIx }
   ::= {sr1646v2IpV6RtrDnsDomainsSSCTable 1}

Sr1646v2IpV6RtrDnsDomainsEntry ::=
   SEQUENCE
      {
      sr1646v2IpV6RtrDnsDomainsTableIx
         TableIndex,
      sr1646v2IpV6RtrDnsDomainsName
         DisplayString,
      sr1646v2IpV6RtrDnsDomainsType
         INTEGER,
      sr1646v2IpV6RtrDnsDomainsRcvdInterface
         DisplayString,
      sr1646v2IpV6RtrDnsDomainsLifeTimer
         TimeTicks
      }

sr1646v2IpV6RtrDnsDomainsTableIx OBJECT-TYPE
   SYNTAX      TableIndex
   MAX-ACCESS  not-accessible
   STATUS      current
   DESCRIPTION
      ""
   ::= {sr1646v2IpV6RtrDnsDomainsEntry 11}

sr1646v2IpV6RtrDnsDomainsName OBJECT-TYPE
   SYNTAX      DisplayString
   MAX-ACCESS  read-only
   STATUS      current
   DESCRIPTION
      "Path: v6Router.status.dnsDomains.name"
   ::= {sr1646v2IpV6RtrDnsDomainsEntry 16777216}

sr1646v2IpV6RtrDnsDomainsType OBJECT-TYPE
   SYNTAX      INTEGER
               {
               static (0),
               dhcp (1),
               ra (3)
               }
   MAX-ACCESS  read-only
   STATUS      current
   DESCRIPTION
      "Path: v6Router.status.dnsDomains.type

       Possibilities:
               static   (0)
               dhcp   (1)
               ra   (3)"
   ::= {sr1646v2IpV6RtrDnsDomainsEntry 33554432}

sr1646v2IpV6RtrDnsDomainsRcvdInterface OBJECT-TYPE
   SYNTAX      DisplayString
   MAX-ACCESS  read-only
   STATUS      current
   DESCRIPTION
      "Path: v6Router.status.dnsDomains.rcvdInterface"
   ::= {sr1646v2IpV6RtrDnsDomainsEntry 50331648}

sr1646v2IpV6RtrDnsDomainsLifeTimer OBJECT-TYPE
   SYNTAX      TimeTicks
   MAX-ACCESS  read-only
   STATUS      current
   DESCRIPTION
      "Path: v6Router.status.dnsDomains.lifeTimer

       Time in centi-second."
   ::= {sr1646v2IpV6RtrDnsDomainsEntry 67108864}



pr1646v2IpV6Rtr OBJECT IDENTIFIER ::= {r1646v2IpV6Rtr 12}


pr1646v2IpV6RtrInterfaces OBJECT IDENTIFIER ::= {pr1646v2IpV6Rtr 40}

pr1646v2IpV6RtrInterfacesSSCTable OBJECT-TYPE
   SYNTAX      SEQUENCE OF Pr1646v2IpV6RtrInterfacesEntry
   MAX-ACCESS  not-accessible
   STATUS      current
   DESCRIPTION
      "ipV6 routing interface performance"
   ::= {pr1646v2IpV6RtrInterfaces 1}

pr1646v2IpV6RtrInterfacesEntry OBJECT-TYPE
   SYNTAX      Pr1646v2IpV6RtrInterfacesEntry
   MAX-ACCESS  not-accessible
   STATUS      current
   DESCRIPTION
      ""
   INDEX      { pr1646v2IpV6RtrInterfacesTableIx }
   ::= {pr1646v2IpV6RtrInterfacesSSCTable 1}

Pr1646v2IpV6RtrInterfacesEntry ::=
   SEQUENCE
      {
      pr1646v2IpV6RtrInterfacesTableIx
         TableIndex,
      pr1646v2IpV6RtrInterfacesName
         DisplayString,
      pr1646v2IpV6RtrInterfacesInterfaceId
         OCTET STRING,
      pr1646v2IpV6RtrInterfacesSentRa
         Counter32,
      pr1646v2IpV6RtrInterfacesSentRs
         Counter32,
      pr1646v2IpV6RtrInterfacesSentNa
         Counter32,
      pr1646v2IpV6RtrInterfacesSentNs
         Counter32,
      pr1646v2IpV6RtrInterfacesSentRedirs
         Counter32,
      pr1646v2IpV6RtrInterfacesRcvdRa
         Counter32,
      pr1646v2IpV6RtrInterfacesRcvdRs
         Counter32,
      pr1646v2IpV6RtrInterfacesRcvdNa
         Counter32,
      pr1646v2IpV6RtrInterfacesRcvdNs
         Counter32,
      pr1646v2IpV6RtrInterfacesRcvdRedirs
         Counter32
      }

pr1646v2IpV6RtrInterfacesTableIx OBJECT-TYPE
   SYNTAX      TableIndex
   MAX-ACCESS  not-accessible
   STATUS      current
   DESCRIPTION
      ""
   ::= {pr1646v2IpV6RtrInterfacesEntry 11}

pr1646v2IpV6RtrInterfacesName OBJECT-TYPE
   SYNTAX      DisplayString
   MAX-ACCESS  read-only
   STATUS      current
   DESCRIPTION
      "Path: v6Router.performance.interfaces.name"
   ::= {pr1646v2IpV6RtrInterfacesEntry 16777216}

pr1646v2IpV6RtrInterfacesInterfaceId OBJECT-TYPE
   SYNTAX      OCTET STRING
   MAX-ACCESS  read-only
   STATUS      current
   DESCRIPTION
      "Path: v6Router.performance.interfaces.interfaceId"
   ::= {pr1646v2IpV6RtrInterfacesEntry 33554432}

pr1646v2IpV6RtrInterfacesSentRa OBJECT-TYPE
   SYNTAX      Counter32
   MAX-ACCESS  read-only
   STATUS      current
   DESCRIPTION
      "Path: v6Router.performance.interfaces.sent.ra

       32 bit unsigned wrappable counter."
   ::= {pr1646v2IpV6RtrInterfacesEntry 50397184}

pr1646v2IpV6RtrInterfacesSentRs OBJECT-TYPE
   SYNTAX      Counter32
   MAX-ACCESS  read-only
   STATUS      current
   DESCRIPTION
      "Path: v6Router.performance.interfaces.sent.rs

       32 bit unsigned wrappable counter."
   ::= {pr1646v2IpV6RtrInterfacesEntry 50462720}

pr1646v2IpV6RtrInterfacesSentNa OBJECT-TYPE
   SYNTAX      Counter32
   MAX-ACCESS  read-only
   STATUS      current
   DESCRIPTION
      "Path: v6Router.performance.interfaces.sent.na

       32 bit unsigned wrappable counter."
   ::= {pr1646v2IpV6RtrInterfacesEntry 50528256}

pr1646v2IpV6RtrInterfacesSentNs OBJECT-TYPE
   SYNTAX      Counter32
   MAX-ACCESS  read-only
   STATUS      current
   DESCRIPTION
      "Path: v6Router.performance.interfaces.sent.ns

       32 bit unsigned wrappable counter."
   ::= {pr1646v2IpV6RtrInterfacesEntry 50593792}

pr1646v2IpV6RtrInterfacesSentRedirs OBJECT-TYPE
   SYNTAX      Counter32
   MAX-ACCESS  read-only
   STATUS      current
   DESCRIPTION
      "Path: v6Router.performance.interfaces.sent.redirs

       32 bit unsigned wrappable counter."
   ::= {pr1646v2IpV6RtrInterfacesEntry 50659328}

pr1646v2IpV6RtrInterfacesRcvdRa OBJECT-TYPE
   SYNTAX      Counter32
   MAX-ACCESS  read-only
   STATUS      current
   DESCRIPTION
      "Path: v6Router.performance.interfaces.rcvd.ra

       32 bit unsigned wrappable counter."
   ::= {pr1646v2IpV6RtrInterfacesEntry 67174400}

pr1646v2IpV6RtrInterfacesRcvdRs OBJECT-TYPE
   SYNTAX      Counter32
   MAX-ACCESS  read-only
   STATUS      current
   DESCRIPTION
      "Path: v6Router.performance.interfaces.rcvd.rs

       32 bit unsigned wrappable counter."
   ::= {pr1646v2IpV6RtrInterfacesEntry 67239936}

pr1646v2IpV6RtrInterfacesRcvdNa OBJECT-TYPE
   SYNTAX      Counter32
   MAX-ACCESS  read-only
   STATUS      current
   DESCRIPTION
      "Path: v6Router.performance.interfaces.rcvd.na

       32 bit unsigned wrappable counter."
   ::= {pr1646v2IpV6RtrInterfacesEntry 67305472}

pr1646v2IpV6RtrInterfacesRcvdNs OBJECT-TYPE
   SYNTAX      Counter32
   MAX-ACCESS  read-only
   STATUS      current
   DESCRIPTION
      "Path: v6Router.performance.interfaces.rcvd.ns

       32 bit unsigned wrappable counter."
   ::= {pr1646v2IpV6RtrInterfacesEntry 67371008}

pr1646v2IpV6RtrInterfacesRcvdRedirs OBJECT-TYPE
   SYNTAX      Counter32
   MAX-ACCESS  read-only
   STATUS      current
   DESCRIPTION
      "Path: v6Router.performance.interfaces.rcvd.redirs

       32 bit unsigned wrappable counter."
   ::= {pr1646v2IpV6RtrInterfacesEntry 67436544}


pr1646v2IpV6RtrRoutingTable OBJECT IDENTIFIER ::= {pr1646v2IpV6Rtr 41}

pr1646v2IpV6RtrRoutingTableSSCTable OBJECT-TYPE
   SYNTAX      SEQUENCE OF Pr1646v2IpV6RtrRoutingTableEntry
   MAX-ACCESS  not-accessible
   STATUS      current
   DESCRIPTION
      "ipV6 routing table performance"
   ::= {pr1646v2IpV6RtrRoutingTable 1}

pr1646v2IpV6RtrRoutingTableEntry OBJECT-TYPE
   SYNTAX      Pr1646v2IpV6RtrRoutingTableEntry
   MAX-ACCESS  not-accessible
   STATUS      current
   DESCRIPTION
      ""
   INDEX      { pr1646v2IpV6RtrRoutingTableTableIx }
   ::= {pr1646v2IpV6RtrRoutingTableSSCTable 1}

Pr1646v2IpV6RtrRoutingTableEntry ::=
   SEQUENCE
      {
      pr1646v2IpV6RtrRoutingTableTableIx
         TableIndex,
      pr1646v2IpV6RtrRoutingTableAddress
         Ipv6Address,
      pr1646v2IpV6RtrRoutingTablePrefixLength
         Integer32,
      pr1646v2IpV6RtrRoutingTableNextHop
         Ipv6Address,
      pr1646v2IpV6RtrRoutingTableInterface
         DisplayString,
      pr1646v2IpV6RtrRoutingTableType
         INTEGER,
      pr1646v2IpV6RtrRoutingTableUses
         Counter32,
      pr1646v2IpV6RtrRoutingTableOctets
         Counter32
      }

pr1646v2IpV6RtrRoutingTableTableIx OBJECT-TYPE
   SYNTAX      TableIndex
   MAX-ACCESS  not-accessible
   STATUS      current
   DESCRIPTION
      ""
   ::= {pr1646v2IpV6RtrRoutingTableEntry 11}

pr1646v2IpV6RtrRoutingTableAddress OBJECT-TYPE
   SYNTAX      Ipv6Address
   MAX-ACCESS  read-only
   STATUS      current
   DESCRIPTION
      "Path: v6Router.performance.routingTable.address

       ipv6 address"
   ::= {pr1646v2IpV6RtrRoutingTableEntry 16777216}

pr1646v2IpV6RtrRoutingTablePrefixLength OBJECT-TYPE
   SYNTAX      Integer32
   MAX-ACCESS  read-only
   STATUS      current
   DESCRIPTION
      "Path: v6Router.performance.routingTable.prefixLength"
   ::= {pr1646v2IpV6RtrRoutingTableEntry 33554432}

pr1646v2IpV6RtrRoutingTableNextHop OBJECT-TYPE
   SYNTAX      Ipv6Address
   MAX-ACCESS  read-only
   STATUS      current
   DESCRIPTION
      "Path: v6Router.performance.routingTable.nextHop

       ipv6 address"
   ::= {pr1646v2IpV6RtrRoutingTableEntry 50331648}

pr1646v2IpV6RtrRoutingTableInterface OBJECT-TYPE
   SYNTAX      DisplayString
   MAX-ACCESS  read-only
   STATUS      current
   DESCRIPTION
      "Path: v6Router.performance.routingTable.interface"
   ::= {pr1646v2IpV6RtrRoutingTableEntry 67108864}

pr1646v2IpV6RtrRoutingTableType OBJECT-TYPE
   SYNTAX      INTEGER
               {
               fixed (0),
               linkLocal (1),
               host (2),
               anycast (3),
               solicited (4),
               dhcp (5),
               redirect (8),
               advertised (9),
               static (10),
               network (11),
               natpt (12)
               }
   MAX-ACCESS  read-only
   STATUS      current
   DESCRIPTION
      "Path: v6Router.performance.routingTable.type

       Possibilities:
               fixed   (0)
               linkLocal   (1)
               host   (2)
               anycast   (3)
               solicited   (4)
               dhcp   (5)
               redirect   (8)
               advertised   (9)
               static   (10)
               network   (11)
               natpt   (12)"
   ::= {pr1646v2IpV6RtrRoutingTableEntry 83886080}

pr1646v2IpV6RtrRoutingTableUses OBJECT-TYPE
   SYNTAX      Counter32
   MAX-ACCESS  read-only
   STATUS      current
   DESCRIPTION
      "Path: v6Router.performance.routingTable.uses

       32 bit unsigned wrappable counter."
   ::= {pr1646v2IpV6RtrRoutingTableEntry 100663296}

pr1646v2IpV6RtrRoutingTableOctets OBJECT-TYPE
   SYNTAX      Counter32
   MAX-ACCESS  read-only
   STATUS      current
   DESCRIPTION
      "Path: v6Router.performance.routingTable.octets

       32 bit unsigned wrappable counter."
   ::= {pr1646v2IpV6RtrRoutingTableEntry 117440512}


pr1646v2IpV6RtrRouter OBJECT IDENTIFIER ::= {pr1646v2IpV6Rtr 42}

pr1646v2IpV6RtrRouterSSC OBJECT IDENTIFIER ::= {pr1646v2IpV6RtrRouter 1}

pr1646v2IpV6RtrRouterEntry OBJECT IDENTIFIER ::= {pr1646v2IpV6RtrRouterSSC 1}

pr1646v2IpV6RtrRouterInPkts OBJECT-TYPE
   SYNTAX      Counter64
   MAX-ACCESS  read-only
   STATUS      current
   DESCRIPTION
      "Path: v6Router.performance.router.inPkts

       64 bit unsigned wrappable counter."
   ::= {pr1646v2IpV6RtrRouterEntry 16777216}

pr1646v2IpV6RtrRouterFwdPkts OBJECT-TYPE
   SYNTAX      Counter64
   MAX-ACCESS  read-only
   STATUS      current
   DESCRIPTION
      "Path: v6Router.performance.router.fwdPkts

       64 bit unsigned wrappable counter."
   ::= {pr1646v2IpV6RtrRouterEntry 33554432}

pr1646v2IpV6RtrRouterRouteCacheHits OBJECT-TYPE
   SYNTAX      Counter64
   MAX-ACCESS  read-only
   STATUS      current
   DESCRIPTION
      "Path: v6Router.performance.router.routeCacheHits

       64 bit unsigned wrappable counter."
   ::= {pr1646v2IpV6RtrRouterEntry 50331648}

pr1646v2IpV6RtrRouterRouteCacheMisses OBJECT-TYPE
   SYNTAX      Counter64
   MAX-ACCESS  read-only
   STATUS      current
   DESCRIPTION
      "Path: v6Router.performance.router.routeCacheMisses

       64 bit unsigned wrappable counter."
   ::= {pr1646v2IpV6RtrRouterEntry 67108864}


pr1646v2IpV6RtrErrors OBJECT IDENTIFIER ::= {pr1646v2IpV6Rtr 43}

pr1646v2IpV6RtrErrorsSSC OBJECT IDENTIFIER ::= {pr1646v2IpV6RtrErrors 1}

pr1646v2IpV6RtrErrorsEntry OBJECT IDENTIFIER ::= {pr1646v2IpV6RtrErrorsSSC 1}

pr1646v2IpV6RtrErrorsPktLength OBJECT-TYPE
   SYNTAX      Counter64
   MAX-ACCESS  read-only
   STATUS      current
   DESCRIPTION
      "Path: v6Router.performance.errors.pktLength

       64 bit unsigned wrappable counter."
   ::= {pr1646v2IpV6RtrErrorsEntry 16777216}

pr1646v2IpV6RtrErrorsHdrLength OBJECT-TYPE
   SYNTAX      Counter64
   MAX-ACCESS  read-only
   STATUS      current
   DESCRIPTION
      "Path: v6Router.performance.errors.hdrLength

       64 bit unsigned wrappable counter."
   ::= {pr1646v2IpV6RtrErrorsEntry 33554432}

pr1646v2IpV6RtrErrorsBadVersion OBJECT-TYPE
   SYNTAX      Counter64
   MAX-ACCESS  read-only
   STATUS      current
   DESCRIPTION
      "Path: v6Router.performance.errors.badVersion

       64 bit unsigned wrappable counter."
   ::= {pr1646v2IpV6RtrErrorsEntry 50331648}

pr1646v2IpV6RtrErrorsBadOption OBJECT-TYPE
   SYNTAX      Counter64
   MAX-ACCESS  read-only
   STATUS      current
   DESCRIPTION
      "Path: v6Router.performance.errors.badOption

       64 bit unsigned wrappable counter."
   ::= {pr1646v2IpV6RtrErrorsEntry 67108864}

pr1646v2IpV6RtrErrorsChecksum OBJECT-TYPE
   SYNTAX      Counter64
   MAX-ACCESS  read-only
   STATUS      current
   DESCRIPTION
      "Path: v6Router.performance.errors.checksum

       64 bit unsigned wrappable counter."
   ::= {pr1646v2IpV6RtrErrorsEntry 83886080}

pr1646v2IpV6RtrErrorsBadScope OBJECT-TYPE
   SYNTAX      Counter64
   MAX-ACCESS  read-only
   STATUS      current
   DESCRIPTION
      "Path: v6Router.performance.errors.badScope

       64 bit unsigned wrappable counter."
   ::= {pr1646v2IpV6RtrErrorsEntry 100663296}

pr1646v2IpV6RtrErrorsNotJoined OBJECT-TYPE
   SYNTAX      Counter64
   MAX-ACCESS  read-only
   STATUS      current
   DESCRIPTION
      "Path: v6Router.performance.errors.notJoined

       64 bit unsigned wrappable counter."
   ::= {pr1646v2IpV6RtrErrorsEntry 117440512}

pr1646v2IpV6RtrErrorsMulticastSrc OBJECT-TYPE
   SYNTAX      Counter64
   MAX-ACCESS  read-only
   STATUS      current
   DESCRIPTION
      "Path: v6Router.performance.errors.multicastSrc

       64 bit unsigned wrappable counter."
   ::= {pr1646v2IpV6RtrErrorsEntry 134217728}

pr1646v2IpV6RtrErrorsCantForward OBJECT-TYPE
   SYNTAX      Counter64
   MAX-ACCESS  read-only
   STATUS      current
   DESCRIPTION
      "Path: v6Router.performance.errors.cantForward

       64 bit unsigned wrappable counter."
   ::= {pr1646v2IpV6RtrErrorsEntry 150994944}

pr1646v2IpV6RtrErrorsTooBig OBJECT-TYPE
   SYNTAX      Counter64
   MAX-ACCESS  read-only
   STATUS      current
   DESCRIPTION
      "Path: v6Router.performance.errors.tooBig

       64 bit unsigned wrappable counter."
   ::= {pr1646v2IpV6RtrErrorsEntry 167772160}


pr1646v2IpV6RtrFragments OBJECT IDENTIFIER ::= {pr1646v2IpV6Rtr 44}

pr1646v2IpV6RtrFragmentsSSC OBJECT IDENTIFIER ::= {pr1646v2IpV6RtrFragments 1}

pr1646v2IpV6RtrFragmentsEntry OBJECT IDENTIFIER ::= {pr1646v2IpV6RtrFragmentsSSC 1}

pr1646v2IpV6RtrFragmentsPktsFragmented OBJECT-TYPE
   SYNTAX      Counter64
   MAX-ACCESS  read-only
   STATUS      current
   DESCRIPTION
      "Path: v6Router.performance.fragments.pktsFragmented

       64 bit unsigned wrappable counter."
   ::= {pr1646v2IpV6RtrFragmentsEntry 16777216}

pr1646v2IpV6RtrFragmentsFragsSent OBJECT-TYPE
   SYNTAX      Counter64
   MAX-ACCESS  read-only
   STATUS      current
   DESCRIPTION
      "Path: v6Router.performance.fragments.fragsSent

       64 bit unsigned wrappable counter."
   ::= {pr1646v2IpV6RtrFragmentsEntry 33554432}

pr1646v2IpV6RtrFragmentsFragFailed OBJECT-TYPE
   SYNTAX      Counter64
   MAX-ACCESS  read-only
   STATUS      current
   DESCRIPTION
      "Path: v6Router.performance.fragments.fragFailed

       64 bit unsigned wrappable counter."
   ::= {pr1646v2IpV6RtrFragmentsEntry 50331648}

pr1646v2IpV6RtrFragmentsFragsRcvd OBJECT-TYPE
   SYNTAX      Counter64
   MAX-ACCESS  read-only
   STATUS      current
   DESCRIPTION
      "Path: v6Router.performance.fragments.fragsRcvd

       64 bit unsigned wrappable counter."
   ::= {pr1646v2IpV6RtrFragmentsEntry 67108864}

pr1646v2IpV6RtrFragmentsPktsReassembled OBJECT-TYPE
   SYNTAX      Counter64
   MAX-ACCESS  read-only
   STATUS      current
   DESCRIPTION
      "Path: v6Router.performance.fragments.pktsReassembled

       64 bit unsigned wrappable counter."
   ::= {pr1646v2IpV6RtrFragmentsEntry 83886080}

pr1646v2IpV6RtrFragmentsFragsDropped OBJECT-TYPE
   SYNTAX      Counter64
   MAX-ACCESS  read-only
   STATUS      current
   DESCRIPTION
      "Path: v6Router.performance.fragments.fragsDropped

       64 bit unsigned wrappable counter."
   ::= {pr1646v2IpV6RtrFragmentsEntry 100663296}

pr1646v2IpV6RtrFragmentsFragsTimedOut OBJECT-TYPE
   SYNTAX      Counter64
   MAX-ACCESS  read-only
   STATUS      current
   DESCRIPTION
      "Path: v6Router.performance.fragments.fragsTimedOut

       64 bit unsigned wrappable counter."
   ::= {pr1646v2IpV6RtrFragmentsEntry 117440512}

pr1646v2IpV6RtrFragmentsFragsOverflow OBJECT-TYPE
   SYNTAX      Counter64
   MAX-ACCESS  read-only
   STATUS      current
   DESCRIPTION
      "Path: v6Router.performance.fragments.fragsOverflow

       64 bit unsigned wrappable counter."
   ::= {pr1646v2IpV6RtrFragmentsEntry 134217728}


pr1646v2IpV6RtrDns OBJECT IDENTIFIER ::= {pr1646v2IpV6Rtr 45}

pr1646v2IpV6RtrDnsSSC OBJECT IDENTIFIER ::= {pr1646v2IpV6RtrDns 1}

pr1646v2IpV6RtrDnsEntry OBJECT IDENTIFIER ::= {pr1646v2IpV6RtrDnsSSC 1}

pr1646v2IpV6RtrDnsRequests OBJECT-TYPE
   SYNTAX      Counter32
   MAX-ACCESS  read-only
   STATUS      current
   DESCRIPTION
      "Path: v6Router.performance.dns.requests

       32 bit unsigned wrappable counter."
   ::= {pr1646v2IpV6RtrDnsEntry 16777216}

pr1646v2IpV6RtrDnsInternalRequests OBJECT-TYPE
   SYNTAX      Counter32
   MAX-ACCESS  read-only
   STATUS      current
   DESCRIPTION
      "Path: v6Router.performance.dns.internalRequests

       32 bit unsigned wrappable counter."
   ::= {pr1646v2IpV6RtrDnsEntry 33554432}

pr1646v2IpV6RtrDnsExternalRequests OBJECT-TYPE
   SYNTAX      Counter32
   MAX-ACCESS  read-only
   STATUS      current
   DESCRIPTION
      "Path: v6Router.performance.dns.externalRequests

       32 bit unsigned wrappable counter."
   ::= {pr1646v2IpV6RtrDnsEntry 50331648}

pr1646v2IpV6RtrDnsForwardedRequests OBJECT-TYPE
   SYNTAX      Counter32
   MAX-ACCESS  read-only
   STATUS      current
   DESCRIPTION
      "Path: v6Router.performance.dns.forwardedRequests

       32 bit unsigned wrappable counter."
   ::= {pr1646v2IpV6RtrDnsEntry 67108864}

pr1646v2IpV6RtrDnsFailedRequests OBJECT-TYPE
   SYNTAX      Counter32
   MAX-ACCESS  read-only
   STATUS      current
   DESCRIPTION
      "Path: v6Router.performance.dns.failedRequests

       32 bit unsigned wrappable counter."
   ::= {pr1646v2IpV6RtrDnsEntry 83886080}

pr1646v2IpV6RtrDnsFreeCache OBJECT-TYPE
   SYNTAX      Gauge32
   MAX-ACCESS  read-only
   STATUS      current
   DESCRIPTION
      "Path: v6Router.performance.dns.freeCache

       32 bit unsigned gauge value."
   ::= {pr1646v2IpV6RtrDnsEntry 117440512}


pr1646v2IpV6RtrH2Perf OBJECT IDENTIFIER ::= {pr1646v2IpV6Rtr 50}

pr1646v2IpV6RtrH2PerfSSCTable OBJECT-TYPE
   SYNTAX      SEQUENCE OF Pr1646v2IpV6RtrH2PerfEntry
   MAX-ACCESS  not-accessible
   STATUS      current
   DESCRIPTION
      "2 hour dns stats"
   ::= {pr1646v2IpV6RtrH2Perf 1}

pr1646v2IpV6RtrH2PerfEntry OBJECT-TYPE
   SYNTAX      Pr1646v2IpV6RtrH2PerfEntry
   MAX-ACCESS  not-accessible
   STATUS      current
   DESCRIPTION
      ""
   INDEX      { pr1646v2IpV6RtrH2PerfTableIx }
   ::= {pr1646v2IpV6RtrH2PerfSSCTable 1}

Pr1646v2IpV6RtrH2PerfEntry ::=
   SEQUENCE
      {
      pr1646v2IpV6RtrH2PerfTableIx
         TableIndex,
      pr1646v2IpV6RtrH2PerfSysUpTime
         TimeTicks,
      pr1646v2IpV6RtrH2PerfRequests
         Counter32,
      pr1646v2IpV6RtrH2PerfInternalRequests
         Counter32,
      pr1646v2IpV6RtrH2PerfExternalRequests
         Counter32,
      pr1646v2IpV6RtrH2PerfForwardedRequests
         Counter32,
      pr1646v2IpV6RtrH2PerfFailedRequests
         Counter32,
      pr1646v2IpV6RtrH2PerfFreeCacheMin
         Gauge32,
      pr1646v2IpV6RtrH2PerfFreeCacheAvrg
         Gauge32,
      pr1646v2IpV6RtrH2PerfFreeCacheMax
         Gauge32
      }

pr1646v2IpV6RtrH2PerfTableIx OBJECT-TYPE
   SYNTAX      TableIndex
   MAX-ACCESS  not-accessible
   STATUS      current
   DESCRIPTION
      ""
   ::= {pr1646v2IpV6RtrH2PerfEntry 11}

pr1646v2IpV6RtrH2PerfSysUpTime OBJECT-TYPE
   SYNTAX      TimeTicks
   MAX-ACCESS  read-only
   STATUS      current
   DESCRIPTION
      "Path: v6Router.performance.h2Dns.sysUpTime

       Time in centi-second."
   ::= {pr1646v2IpV6RtrH2PerfEntry 16777216}

pr1646v2IpV6RtrH2PerfRequests OBJECT-TYPE
   SYNTAX      Counter32
   MAX-ACCESS  read-only
   STATUS      current
   DESCRIPTION
      "Path: v6Router.performance.h2Dns.requests

       32 bit unsigned wrappable counter."
   ::= {pr1646v2IpV6RtrH2PerfEntry 33554432}

pr1646v2IpV6RtrH2PerfInternalRequests OBJECT-TYPE
   SYNTAX      Counter32
   MAX-ACCESS  read-only
   STATUS      current
   DESCRIPTION
      "Path: v6Router.performance.h2Dns.internalRequests

       32 bit unsigned wrappable counter."
   ::= {pr1646v2IpV6RtrH2PerfEntry 50331648}

pr1646v2IpV6RtrH2PerfExternalRequests OBJECT-TYPE
   SYNTAX      Counter32
   MAX-ACCESS  read-only
   STATUS      current
   DESCRIPTION
      "Path: v6Router.performance.h2Dns.externalRequests

       32 bit unsigned wrappable counter."
   ::= {pr1646v2IpV6RtrH2PerfEntry 67108864}

pr1646v2IpV6RtrH2PerfForwardedRequests OBJECT-TYPE
   SYNTAX      Counter32
   MAX-ACCESS  read-only
   STATUS      current
   DESCRIPTION
      "Path: v6Router.performance.h2Dns.forwardedRequests

       32 bit unsigned wrappable counter."
   ::= {pr1646v2IpV6RtrH2PerfEntry 83886080}

pr1646v2IpV6RtrH2PerfFailedRequests OBJECT-TYPE
   SYNTAX      Counter32
   MAX-ACCESS  read-only
   STATUS      current
   DESCRIPTION
      "Path: v6Router.performance.h2Dns.failedRequests

       32 bit unsigned wrappable counter."
   ::= {pr1646v2IpV6RtrH2PerfEntry 100663296}

pr1646v2IpV6RtrH2PerfFreeCacheMin OBJECT-TYPE
   SYNTAX      Gauge32
   MAX-ACCESS  read-only
   STATUS      current
   DESCRIPTION
      "Path: v6Router.performance.h2Dns.freeCacheMin

       32 bit unsigned gauge value."
   ::= {pr1646v2IpV6RtrH2PerfEntry 117440512}

pr1646v2IpV6RtrH2PerfFreeCacheAvrg OBJECT-TYPE
   SYNTAX      Gauge32
   MAX-ACCESS  read-only
   STATUS      current
   DESCRIPTION
      "Path: v6Router.performance.h2Dns.freeCacheAvrg

       32 bit unsigned gauge value."
   ::= {pr1646v2IpV6RtrH2PerfEntry 134217728}

pr1646v2IpV6RtrH2PerfFreeCacheMax OBJECT-TYPE
   SYNTAX      Gauge32
   MAX-ACCESS  read-only
   STATUS      current
   DESCRIPTION
      "Path: v6Router.performance.h2Dns.freeCacheMax

       32 bit unsigned gauge value."
   ::= {pr1646v2IpV6RtrH2PerfEntry 150994944}


pr1646v2IpV6RtrH24Perf OBJECT IDENTIFIER ::= {pr1646v2IpV6Rtr 51}

pr1646v2IpV6RtrH24PerfSSCTable OBJECT-TYPE
   SYNTAX      SEQUENCE OF Pr1646v2IpV6RtrH24PerfEntry
   MAX-ACCESS  not-accessible
   STATUS      current
   DESCRIPTION
      "24 hour dns stats"
   ::= {pr1646v2IpV6RtrH24Perf 1}

pr1646v2IpV6RtrH24PerfEntry OBJECT-TYPE
   SYNTAX      Pr1646v2IpV6RtrH24PerfEntry
   MAX-ACCESS  not-accessible
   STATUS      current
   DESCRIPTION
      ""
   INDEX      { pr1646v2IpV6RtrH24PerfTableIx }
   ::= {pr1646v2IpV6RtrH24PerfSSCTable 1}

Pr1646v2IpV6RtrH24PerfEntry ::=
   SEQUENCE
      {
      pr1646v2IpV6RtrH24PerfTableIx
         TableIndex,
      pr1646v2IpV6RtrH24PerfSysUpTime
         TimeTicks,
      pr1646v2IpV6RtrH24PerfRequests
         Counter32,
      pr1646v2IpV6RtrH24PerfInternalRequests
         Counter32,
      pr1646v2IpV6RtrH24PerfExternalRequests
         Counter32,
      pr1646v2IpV6RtrH24PerfForwardedRequests
         Counter32,
      pr1646v2IpV6RtrH24PerfFailedRequests
         Counter32,
      pr1646v2IpV6RtrH24PerfFreeCacheMin
         Gauge32,
      pr1646v2IpV6RtrH24PerfFreeCacheAvrg
         Gauge32,
      pr1646v2IpV6RtrH24PerfFreeCacheMax
         Gauge32
      }

pr1646v2IpV6RtrH24PerfTableIx OBJECT-TYPE
   SYNTAX      TableIndex
   MAX-ACCESS  not-accessible
   STATUS      current
   DESCRIPTION
      ""
   ::= {pr1646v2IpV6RtrH24PerfEntry 11}

pr1646v2IpV6RtrH24PerfSysUpTime OBJECT-TYPE
   SYNTAX      TimeTicks
   MAX-ACCESS  read-only
   STATUS      current
   DESCRIPTION
      "Path: v6Router.performance.h24Dns.sysUpTime

       Time in centi-second."
   ::= {pr1646v2IpV6RtrH24PerfEntry 16777216}

pr1646v2IpV6RtrH24PerfRequests OBJECT-TYPE
   SYNTAX      Counter32
   MAX-ACCESS  read-only
   STATUS      current
   DESCRIPTION
      "Path: v6Router.performance.h24Dns.requests

       32 bit unsigned wrappable counter."
   ::= {pr1646v2IpV6RtrH24PerfEntry 33554432}

pr1646v2IpV6RtrH24PerfInternalRequests OBJECT-TYPE
   SYNTAX      Counter32
   MAX-ACCESS  read-only
   STATUS      current
   DESCRIPTION
      "Path: v6Router.performance.h24Dns.internalRequests

       32 bit unsigned wrappable counter."
   ::= {pr1646v2IpV6RtrH24PerfEntry 50331648}

pr1646v2IpV6RtrH24PerfExternalRequests OBJECT-TYPE
   SYNTAX      Counter32
   MAX-ACCESS  read-only
   STATUS      current
   DESCRIPTION
      "Path: v6Router.performance.h24Dns.externalRequests

       32 bit unsigned wrappable counter."
   ::= {pr1646v2IpV6RtrH24PerfEntry 67108864}

pr1646v2IpV6RtrH24PerfForwardedRequests OBJECT-TYPE
   SYNTAX      Counter32
   MAX-ACCESS  read-only
   STATUS      current
   DESCRIPTION
      "Path: v6Router.performance.h24Dns.forwardedRequests

       32 bit unsigned wrappable counter."
   ::= {pr1646v2IpV6RtrH24PerfEntry 83886080}

pr1646v2IpV6RtrH24PerfFailedRequests OBJECT-TYPE
   SYNTAX      Counter32
   MAX-ACCESS  read-only
   STATUS      current
   DESCRIPTION
      "Path: v6Router.performance.h24Dns.failedRequests

       32 bit unsigned wrappable counter."
   ::= {pr1646v2IpV6RtrH24PerfEntry 100663296}

pr1646v2IpV6RtrH24PerfFreeCacheMin OBJECT-TYPE
   SYNTAX      Gauge32
   MAX-ACCESS  read-only
   STATUS      current
   DESCRIPTION
      "Path: v6Router.performance.h24Dns.freeCacheMin

       32 bit unsigned gauge value."
   ::= {pr1646v2IpV6RtrH24PerfEntry 117440512}

pr1646v2IpV6RtrH24PerfFreeCacheAvrg OBJECT-TYPE
   SYNTAX      Gauge32
   MAX-ACCESS  read-only
   STATUS      current
   DESCRIPTION
      "Path: v6Router.performance.h24Dns.freeCacheAvrg

       32 bit unsigned gauge value."
   ::= {pr1646v2IpV6RtrH24PerfEntry 134217728}

pr1646v2IpV6RtrH24PerfFreeCacheMax OBJECT-TYPE
   SYNTAX      Gauge32
   MAX-ACCESS  read-only
   STATUS      current
   DESCRIPTION
      "Path: v6Router.performance.h24Dns.freeCacheMax

       32 bit unsigned gauge value."
   ::= {pr1646v2IpV6RtrH24PerfEntry 150994944}


pr1646v2IpV6RtrD7Perf OBJECT IDENTIFIER ::= {pr1646v2IpV6Rtr 52}

pr1646v2IpV6RtrD7PerfSSCTable OBJECT-TYPE
   SYNTAX      SEQUENCE OF Pr1646v2IpV6RtrD7PerfEntry
   MAX-ACCESS  not-accessible
   STATUS      current
   DESCRIPTION
      "7 days dns stats"
   ::= {pr1646v2IpV6RtrD7Perf 1}

pr1646v2IpV6RtrD7PerfEntry OBJECT-TYPE
   SYNTAX      Pr1646v2IpV6RtrD7PerfEntry
   MAX-ACCESS  not-accessible
   STATUS      current
   DESCRIPTION
      ""
   INDEX      { pr1646v2IpV6RtrD7PerfTableIx }
   ::= {pr1646v2IpV6RtrD7PerfSSCTable 1}

Pr1646v2IpV6RtrD7PerfEntry ::=
   SEQUENCE
      {
      pr1646v2IpV6RtrD7PerfTableIx
         TableIndex,
      pr1646v2IpV6RtrD7PerfSysUpTime
         TimeTicks,
      pr1646v2IpV6RtrD7PerfRequests
         Counter32,
      pr1646v2IpV6RtrD7PerfInternalRequests
         Counter32,
      pr1646v2IpV6RtrD7PerfExternalRequests
         Counter32,
      pr1646v2IpV6RtrD7PerfForwardedRequests
         Counter32,
      pr1646v2IpV6RtrD7PerfFailedRequests
         Counter32,
      pr1646v2IpV6RtrD7PerfFreeCacheMin
         Gauge32,
      pr1646v2IpV6RtrD7PerfFreeCacheAvrg
         Gauge32,
      pr1646v2IpV6RtrD7PerfFreeCacheMax
         Gauge32
      }

pr1646v2IpV6RtrD7PerfTableIx OBJECT-TYPE
   SYNTAX      TableIndex
   MAX-ACCESS  not-accessible
   STATUS      current
   DESCRIPTION
      ""
   ::= {pr1646v2IpV6RtrD7PerfEntry 11}

pr1646v2IpV6RtrD7PerfSysUpTime OBJECT-TYPE
   SYNTAX      TimeTicks
   MAX-ACCESS  read-only
   STATUS      current
   DESCRIPTION
      "Path: v6Router.performance.d7Dns.sysUpTime

       Time in centi-second."
   ::= {pr1646v2IpV6RtrD7PerfEntry 16777216}

pr1646v2IpV6RtrD7PerfRequests OBJECT-TYPE
   SYNTAX      Counter32
   MAX-ACCESS  read-only
   STATUS      current
   DESCRIPTION
      "Path: v6Router.performance.d7Dns.requests

       32 bit unsigned wrappable counter."
   ::= {pr1646v2IpV6RtrD7PerfEntry 33554432}

pr1646v2IpV6RtrD7PerfInternalRequests OBJECT-TYPE
   SYNTAX      Counter32
   MAX-ACCESS  read-only
   STATUS      current
   DESCRIPTION
      "Path: v6Router.performance.d7Dns.internalRequests

       32 bit unsigned wrappable counter."
   ::= {pr1646v2IpV6RtrD7PerfEntry 50331648}

pr1646v2IpV6RtrD7PerfExternalRequests OBJECT-TYPE
   SYNTAX      Counter32
   MAX-ACCESS  read-only
   STATUS      current
   DESCRIPTION
      "Path: v6Router.performance.d7Dns.externalRequests

       32 bit unsigned wrappable counter."
   ::= {pr1646v2IpV6RtrD7PerfEntry 67108864}

pr1646v2IpV6RtrD7PerfForwardedRequests OBJECT-TYPE
   SYNTAX      Counter32
   MAX-ACCESS  read-only
   STATUS      current
   DESCRIPTION
      "Path: v6Router.performance.d7Dns.forwardedRequests

       32 bit unsigned wrappable counter."
   ::= {pr1646v2IpV6RtrD7PerfEntry 83886080}

pr1646v2IpV6RtrD7PerfFailedRequests OBJECT-TYPE
   SYNTAX      Counter32
   MAX-ACCESS  read-only
   STATUS      current
   DESCRIPTION
      "Path: v6Router.performance.d7Dns.failedRequests

       32 bit unsigned wrappable counter."
   ::= {pr1646v2IpV6RtrD7PerfEntry 100663296}

pr1646v2IpV6RtrD7PerfFreeCacheMin OBJECT-TYPE
   SYNTAX      Gauge32
   MAX-ACCESS  read-only
   STATUS      current
   DESCRIPTION
      "Path: v6Router.performance.d7Dns.freeCacheMin

       32 bit unsigned gauge value."
   ::= {pr1646v2IpV6RtrD7PerfEntry 117440512}

pr1646v2IpV6RtrD7PerfFreeCacheAvrg OBJECT-TYPE
   SYNTAX      Gauge32
   MAX-ACCESS  read-only
   STATUS      current
   DESCRIPTION
      "Path: v6Router.performance.d7Dns.freeCacheAvrg

       32 bit unsigned gauge value."
   ::= {pr1646v2IpV6RtrD7PerfEntry 134217728}

pr1646v2IpV6RtrD7PerfFreeCacheMax OBJECT-TYPE
   SYNTAX      Gauge32
   MAX-ACCESS  read-only
   STATUS      current
   DESCRIPTION
      "Path: v6Router.performance.d7Dns.freeCacheMax

       32 bit unsigned gauge value."
   ::= {pr1646v2IpV6RtrD7PerfEntry 150994944}


pr1646v2IpV6RtrQMon OBJECT IDENTIFIER ::= {pr1646v2IpV6Rtr 53}

pr1646v2IpV6RtrQMonSSCTable OBJECT-TYPE
   SYNTAX      SEQUENCE OF Pr1646v2IpV6RtrQMonEntry
   MAX-ACCESS  not-accessible
   STATUS      current
   DESCRIPTION
      "quality monitor"
   ::= {pr1646v2IpV6RtrQMon 1}

pr1646v2IpV6RtrQMonEntry OBJECT-TYPE
   SYNTAX      Pr1646v2IpV6RtrQMonEntry
   MAX-ACCESS  not-accessible
   STATUS      current
   DESCRIPTION
      ""
   INDEX      { pr1646v2IpV6RtrQMonTableIx }
   ::= {pr1646v2IpV6RtrQMonSSCTable 1}

Pr1646v2IpV6RtrQMonEntry ::=
   SEQUENCE
      {
      pr1646v2IpV6RtrQMonTableIx
         TableIndex,
      pr1646v2IpV6RtrQMonName
         DisplayString,
      pr1646v2IpV6RtrQMonStatus
         INTEGER,
      pr1646v2IpV6RtrQMonIpAddress
         Ipv6Address,
      pr1646v2IpV6RtrQMonHostName
         DisplayString,
      pr1646v2IpV6RtrQMonSourceIp
         Ipv6Address,
      pr1646v2IpV6RtrQMonSourceId
         Counter32,
      pr1646v2IpV6RtrQMonNbrTxPckt
         Counter32,
      pr1646v2IpV6RtrQMonNbrRxPckt
         Counter32,
      pr1646v2IpV6RtrQMonError
         Counter32,
      pr1646v2IpV6RtrQMonDelay
         Integer32,
      pr1646v2IpV6RtrQMonJitter
         Integer32,
      pr1646v2IpV6RtrQMonLoss
         Counter32,
      pr1646v2IpV6RtrQMonLossDelay
         Counter32,
      pr1646v2IpV6RtrQMonDelayMin
         Integer32,
      pr1646v2IpV6RtrQMonDelayAvrg
         Integer32,
      pr1646v2IpV6RtrQMonDelayMax
         Integer32,
      pr1646v2IpV6RtrQMonDelayBinsType
         INTEGER,
      pr1646v2IpV6RtrQMonDelayBinsMinMin
         Counter32,
      pr1646v2IpV6RtrQMonDelayBinsMin
         Integer32,
      pr1646v2IpV6RtrQMonDelayBinsMinBin1
         Counter32,
      pr1646v2IpV6RtrQMonDelayBinsBin2
         Counter32,
      pr1646v2IpV6RtrQMonDelayBinsBin3
         Counter32,
      pr1646v2IpV6RtrQMonDelayBinsBin4
         Counter32,
      pr1646v2IpV6RtrQMonDelayBinsBin5
         Counter32,
      pr1646v2IpV6RtrQMonDelayBinsBin6
         Counter32,
      pr1646v2IpV6RtrQMonDelayBinsBin7
         Counter32,
      pr1646v2IpV6RtrQMonDelayBinsMaxBin8
         Counter32,
      pr1646v2IpV6RtrQMonDelayBinsMax
         Integer32,
      pr1646v2IpV6RtrQMonDelayBinsPlusMax
         Counter32,
      pr1646v2IpV6RtrQMonJitterNegMax
         Integer32,
      pr1646v2IpV6RtrQMonJitterAvrg
         Integer32,
      pr1646v2IpV6RtrQMonJitterPosMax
         Integer32,
      pr1646v2IpV6RtrQMonJitterBinsType
         INTEGER,
      pr1646v2IpV6RtrQMonJitterBinsMinMin
         Counter32,
      pr1646v2IpV6RtrQMonJitterBinsMin
         Integer32,
      pr1646v2IpV6RtrQMonJitterBinsMinBin1
         Counter32,
      pr1646v2IpV6RtrQMonJitterBinsBin2
         Counter32,
      pr1646v2IpV6RtrQMonJitterBinsBin3
         Counter32,
      pr1646v2IpV6RtrQMonJitterBinsBin4
         Counter32,
      pr1646v2IpV6RtrQMonJitterBinsBin5
         Counter32,
      pr1646v2IpV6RtrQMonJitterBinsBin6
         Counter32,
      pr1646v2IpV6RtrQMonJitterBinsBin7
         Counter32,
      pr1646v2IpV6RtrQMonJitterBinsMaxBin8
         Counter32,
      pr1646v2IpV6RtrQMonJitterBinsMax
         Integer32,
      pr1646v2IpV6RtrQMonJitterBinsPlusMax
         Counter32,
      pr1646v2IpV6RtrQMonUpDownStatus
         INTEGER,
      pr1646v2IpV6RtrQMonUpDownLossUp
         Counter32,
      pr1646v2IpV6RtrQMonUpDownLossDelayUp
         Counter32,
      pr1646v2IpV6RtrQMonUpDownDelayUpMin
         Integer32,
      pr1646v2IpV6RtrQMonUpDownDelayUpAvrg
         Integer32,
      pr1646v2IpV6RtrQMonUpDownDelayUpMax
         Integer32,
      pr1646v2IpV6RtrQMonUpDownDelayUpBinsType
         INTEGER,
      pr1646v2IpV6RtrQMonUpDownDelayUpBinsMinMin
         Counter32,
      pr1646v2IpV6RtrQMonUpDownDelayUpBinsMin
         Integer32,
      pr1646v2IpV6RtrQMonUpDownDelayUpBinsMinBin1
         Counter32,
      pr1646v2IpV6RtrQMonUpDownDelayUpBinsBin2
         Counter32,
      pr1646v2IpV6RtrQMonUpDownDelayUpBinsBin3
         Counter32,
      pr1646v2IpV6RtrQMonUpDownDelayUpBinsBin4
         Counter32,
      pr1646v2IpV6RtrQMonUpDownDelayUpBinsBin5
         Counter32,
      pr1646v2IpV6RtrQMonUpDownDelayUpBinsBin6
         Counter32,
      pr1646v2IpV6RtrQMonUpDownDelayUpBinsBin7
         Counter32,
      pr1646v2IpV6RtrQMonUpDownDelayUpBinsMaxBin8
         Counter32,
      pr1646v2IpV6RtrQMonUpDownDelayUpBinsMax
         Integer32,
      pr1646v2IpV6RtrQMonUpDownDelayUpBinsPlusMax
         Counter32,
      pr1646v2IpV6RtrQMonUpDownJitterUp
         Integer32,
      pr1646v2IpV6RtrQMonUpDownJitterUpNegMax
         Integer32,
      pr1646v2IpV6RtrQMonUpDownJitterUpAvrg
         Integer32,
      pr1646v2IpV6RtrQMonUpDownJitterUpPosMax
         Integer32,
      pr1646v2IpV6RtrQMonUpDownJitterUpBinsType
         INTEGER,
      pr1646v2IpV6RtrQMonUpDownJitterUpBinsMinMin
         Counter32,
      pr1646v2IpV6RtrQMonUpDownJitterUpBinsMin
         Integer32,
      pr1646v2IpV6RtrQMonUpDownJitterUpBinsMinBin1
         Counter32,
      pr1646v2IpV6RtrQMonUpDownJitterUpBinsBin2
         Counter32,
      pr1646v2IpV6RtrQMonUpDownJitterUpBinsBin3
         Counter32,
      pr1646v2IpV6RtrQMonUpDownJitterUpBinsBin4
         Counter32,
      pr1646v2IpV6RtrQMonUpDownJitterUpBinsBin5
         Counter32,
      pr1646v2IpV6RtrQMonUpDownJitterUpBinsBin6
         Counter32,
      pr1646v2IpV6RtrQMonUpDownJitterUpBinsBin7
         Counter32,
      pr1646v2IpV6RtrQMonUpDownJitterUpBinsMaxBin8
         Counter32,
      pr1646v2IpV6RtrQMonUpDownJitterUpBinsMax
         Integer32,
      pr1646v2IpV6RtrQMonUpDownJitterUpBinsPlusMax
         Counter32,
      pr1646v2IpV6RtrQMonUpDownLossDown
         Counter32,
      pr1646v2IpV6RtrQMonUpDownLossDelayDown
         Counter32,
      pr1646v2IpV6RtrQMonUpDownDelayDownMin
         Integer32,
      pr1646v2IpV6RtrQMonUpDownDelayDownAvrg
         Integer32,
      pr1646v2IpV6RtrQMonUpDownDelayDownMax
         Integer32,
      pr1646v2IpV6RtrQMonUpDownDelayDownBinsType
         INTEGER,
      pr1646v2IpV6RtrQMonUpDownDelayDownBinsMinMin
         Counter32,
      pr1646v2IpV6RtrQMonUpDownDelayDownBinsMin
         Integer32,
      pr1646v2IpV6RtrQMonUpDownDelayDownBinsMinBin1
         Counter32,
      pr1646v2IpV6RtrQMonUpDownDelayDownBinsBin2
         Counter32,
      pr1646v2IpV6RtrQMonUpDownDelayDownBinsBin3
         Counter32,
      pr1646v2IpV6RtrQMonUpDownDelayDownBinsBin4
         Counter32,
      pr1646v2IpV6RtrQMonUpDownDelayDownBinsBin5
         Counter32,
      pr1646v2IpV6RtrQMonUpDownDelayDownBinsBin6
         Counter32,
      pr1646v2IpV6RtrQMonUpDownDelayDownBinsBin7
         Counter32,
      pr1646v2IpV6RtrQMonUpDownDelayDownBinsMaxBin8
         Counter32,
      pr1646v2IpV6RtrQMonUpDownDelayDownBinsMax
         Integer32,
      pr1646v2IpV6RtrQMonUpDownDelayDownBinsPlusMax
         Counter32,
      pr1646v2IpV6RtrQMonUpDownJitterDown
         Integer32,
      pr1646v2IpV6RtrQMonUpDownJitterDownNegMax
         Integer32,
      pr1646v2IpV6RtrQMonUpDownJitterDownAvrg
         Integer32,
      pr1646v2IpV6RtrQMonUpDownJitterDownPosMax
         Integer32,
      pr1646v2IpV6RtrQMonUpDownJitterDownBinsType
         INTEGER,
      pr1646v2IpV6RtrQMonUpDownJitterDownBinsMinMin
         Counter32,
      pr1646v2IpV6RtrQMonUpDownJitterDownBinsMin
         Integer32,
      pr1646v2IpV6RtrQMonUpDownJitterDownBinsMinBin1
         Counter32,
      pr1646v2IpV6RtrQMonUpDownJitterDownBinsBin2
         Counter32,
      pr1646v2IpV6RtrQMonUpDownJitterDownBinsBin3
         Counter32,
      pr1646v2IpV6RtrQMonUpDownJitterDownBinsBin4
         Counter32,
      pr1646v2IpV6RtrQMonUpDownJitterDownBinsBin5
         Counter32,
      pr1646v2IpV6RtrQMonUpDownJitterDownBinsBin6
         Counter32,
      pr1646v2IpV6RtrQMonUpDownJitterDownBinsBin7
         Counter32,
      pr1646v2IpV6RtrQMonUpDownJitterDownBinsMaxBin8
         Counter32,
      pr1646v2IpV6RtrQMonUpDownJitterDownBinsMax
         Integer32,
      pr1646v2IpV6RtrQMonUpDownJitterDownBinsPlusMax
         Counter32,
      pr1646v2IpV6RtrQMonLastLogSysUpTime
         TimeTicks,
      pr1646v2IpV6RtrQMonLastLogNbrTxPckt
         Counter32,
      pr1646v2IpV6RtrQMonLastLogNbrRxPckt
         Counter32,
      pr1646v2IpV6RtrQMonLastLogError
         Counter32,
      pr1646v2IpV6RtrQMonLastLogLoss
         Counter32,
      pr1646v2IpV6RtrQMonLastLogLossDelay
         Counter32,
      pr1646v2IpV6RtrQMonLastLogDelayMin
         Integer32,
      pr1646v2IpV6RtrQMonLastLogDelayAvrg
         Integer32,
      pr1646v2IpV6RtrQMonLastLogDelayMax
         Integer32,
      pr1646v2IpV6RtrQMonLastLogJitterNegMax
         Integer32,
      pr1646v2IpV6RtrQMonLastLogJitterAvrg
         Integer32,
      pr1646v2IpV6RtrQMonLastLogJitterPosMax
         Integer32,
      pr1646v2IpV6RtrQMonLastLogUpDownStatus
         INTEGER,
      pr1646v2IpV6RtrQMonLastLogUpDownLossUp
         Counter32,
      pr1646v2IpV6RtrQMonLastLogUpDownLossDelayUp
         Counter32,
      pr1646v2IpV6RtrQMonLastLogUpDownDelayUpMin
         Integer32,
      pr1646v2IpV6RtrQMonLastLogUpDownDelayUpAvrg
         Integer32,
      pr1646v2IpV6RtrQMonLastLogUpDownDelayUpMax
         Integer32,
      pr1646v2IpV6RtrQMonLastLogUpDownJitterUpNegMax
         Integer32,
      pr1646v2IpV6RtrQMonLastLogUpDownJitterUpAvrg
         Integer32,
      pr1646v2IpV6RtrQMonLastLogUpDownJitterUpPosMax
         Integer32,
      pr1646v2IpV6RtrQMonLastLogUpDownLossDown
         Counter32,
      pr1646v2IpV6RtrQMonLastLogUpDownLossDelayDown
         Counter32,
      pr1646v2IpV6RtrQMonLastLogUpDownDelayDownMin
         Integer32,
      pr1646v2IpV6RtrQMonLastLogUpDownDelayDownAvrg
         Integer32,
      pr1646v2IpV6RtrQMonLastLogUpDownDelayDownMax
         Integer32,
      pr1646v2IpV6RtrQMonLastLogUpDownJitterDownNegMax
         Integer32,
      pr1646v2IpV6RtrQMonLastLogUpDownJitterDownAvrg
         Integer32,
      pr1646v2IpV6RtrQMonLastLogUpDownJitterDownPosMax
         Integer32,
      pr1646v2IpV6RtrQMonLastLogDate
         DisplayString,
      pr1646v2IpV6RtrQMonAlarm
         Integer32,
      pr1646v2IpV6RtrQMonLastError
         DisplayString
      }

pr1646v2IpV6RtrQMonTableIx OBJECT-TYPE
   SYNTAX      TableIndex
   MAX-ACCESS  not-accessible
   STATUS      current
   DESCRIPTION
      ""
   ::= {pr1646v2IpV6RtrQMonEntry 11}

pr1646v2IpV6RtrQMonName OBJECT-TYPE
   SYNTAX      DisplayString
   MAX-ACCESS  read-only
   STATUS      current
   DESCRIPTION
      "Path: v6Router.performance.qualityMonitor.name"
   ::= {pr1646v2IpV6RtrQMonEntry 301989888}

pr1646v2IpV6RtrQMonStatus OBJECT-TYPE
   SYNTAX      INTEGER
               {
               run (1),
               runOnDemand (3),
               halted (2),
               cleared (6),
               disabled (8),
               runIdle (9)
               }
   MAX-ACCESS  read-only
   STATUS      current
   DESCRIPTION
      "Path: v6Router.performance.qualityMonitor.status

       Possibilities:
               run   (1)
               runOnDemand   (3)
               halted   (2)
               cleared   (6)
               disabled   (8)
               runIdle   (9)"
   ::= {pr1646v2IpV6RtrQMonEntry 369098752}

pr1646v2IpV6RtrQMonIpAddress OBJECT-TYPE
   SYNTAX      Ipv6Address
   MAX-ACCESS  read-only
   STATUS      current
   DESCRIPTION
      "Path: v6Router.performance.qualityMonitor.ipAddress

       ipv6 address"
   ::= {pr1646v2IpV6RtrQMonEntry 16777216}

pr1646v2IpV6RtrQMonHostName OBJECT-TYPE
   SYNTAX      DisplayString
   MAX-ACCESS  read-only
   STATUS      current
   DESCRIPTION
      "Path: v6Router.performance.qualityMonitor.hostName"
   ::= {pr1646v2IpV6RtrQMonEntry 33554432}

pr1646v2IpV6RtrQMonSourceIp OBJECT-TYPE
   SYNTAX      Ipv6Address
   MAX-ACCESS  read-only
   STATUS      current
   DESCRIPTION
      "Path: v6Router.performance.qualityMonitor.sourceIp

       ipv6 address"
   ::= {pr1646v2IpV6RtrQMonEntry 83886080}

pr1646v2IpV6RtrQMonSourceId OBJECT-TYPE
   SYNTAX      Counter32
   MAX-ACCESS  read-only
   STATUS      current
   DESCRIPTION
      "Path: v6Router.performance.qualityMonitor.sourceId

       32 bit unsigned wrappable counter."
   ::= {pr1646v2IpV6RtrQMonEntry 352321536}

pr1646v2IpV6RtrQMonNbrTxPckt OBJECT-TYPE
   SYNTAX      Counter32
   MAX-ACCESS  read-only
   STATUS      current
   DESCRIPTION
      "Path: v6Router.performance.qualityMonitor.nbrOfTxPackets

       32 bit unsigned wrappable counter."
   ::= {pr1646v2IpV6RtrQMonEntry 50331648}

pr1646v2IpV6RtrQMonNbrRxPckt OBJECT-TYPE
   SYNTAX      Counter32
   MAX-ACCESS  read-only
   STATUS      current
   DESCRIPTION
      "Path: v6Router.performance.qualityMonitor.nbrOfRxPackets

       32 bit unsigned wrappable counter."
   ::= {pr1646v2IpV6RtrQMonEntry 67108864}

pr1646v2IpV6RtrQMonError OBJECT-TYPE
   SYNTAX      Counter32
   MAX-ACCESS  read-only
   STATUS      current
   DESCRIPTION
      "Path: v6Router.performance.qualityMonitor.error

       32 bit unsigned wrappable counter."
   ::= {pr1646v2IpV6RtrQMonEntry 285212672}

pr1646v2IpV6RtrQMonDelay OBJECT-TYPE
   SYNTAX      Integer32
   MAX-ACCESS  read-only
   STATUS      current
   DESCRIPTION
      "Path: v6Router.performance.qualityMonitor.delay

       unit name = sec
       formula = 1000 / ; 1000 *"
   ::= {pr1646v2IpV6RtrQMonEntry 201326592}

pr1646v2IpV6RtrQMonJitter OBJECT-TYPE
   SYNTAX      Integer32
   MAX-ACCESS  read-only
   STATUS      current
   DESCRIPTION
      "Path: v6Router.performance.qualityMonitor.jitter

       unit name = sec
       formula = 1000 / ; 1000 *"
   ::= {pr1646v2IpV6RtrQMonEntry 218103808}

pr1646v2IpV6RtrQMonLoss OBJECT-TYPE
   SYNTAX      Counter32
   MAX-ACCESS  read-only
   STATUS      current
   DESCRIPTION
      "Path: v6Router.performance.qualityMonitor.loss

       32 bit unsigned wrappable counter."
   ::= {pr1646v2IpV6RtrQMonEntry 100663296}

pr1646v2IpV6RtrQMonLossDelay OBJECT-TYPE
   SYNTAX      Counter32
   MAX-ACCESS  read-only
   STATUS      current
   DESCRIPTION
      "Path: v6Router.performance.qualityMonitor.lossDelay

       32 bit unsigned wrappable counter."
   ::= {pr1646v2IpV6RtrQMonEntry 268435456}

pr1646v2IpV6RtrQMonDelayMin OBJECT-TYPE
   SYNTAX      Integer32
   MAX-ACCESS  read-only
   STATUS      current
   DESCRIPTION
      "Path: v6Router.performance.qualityMonitor.delayMin

       unit name = sec
       formula = 1000 / ; 1000 *"
   ::= {pr1646v2IpV6RtrQMonEntry 184549376}

pr1646v2IpV6RtrQMonDelayAvrg OBJECT-TYPE
   SYNTAX      Integer32
   MAX-ACCESS  read-only
   STATUS      current
   DESCRIPTION
      "Path: v6Router.performance.qualityMonitor.delayAvrg

       unit name = sec
       formula = 1000 / ; 1000 *"
   ::= {pr1646v2IpV6RtrQMonEntry 117440512}

pr1646v2IpV6RtrQMonDelayMax OBJECT-TYPE
   SYNTAX      Integer32
   MAX-ACCESS  read-only
   STATUS      current
   DESCRIPTION
      "Path: v6Router.performance.qualityMonitor.delayMax

       unit name = sec
       formula = 1000 / ; 1000 *"
   ::= {pr1646v2IpV6RtrQMonEntry 134217728}

pr1646v2IpV6RtrQMonDelayBinsType OBJECT-TYPE
   SYNTAX      INTEGER
               {
               fd (1),
               fdr (2),
               notInUse (3),
               ifdv (4)
               }
   MAX-ACCESS  read-only
   STATUS      current
   DESCRIPTION
      "Path: v6Router.performance.qualityMonitor.delayBins.type

       Possibilities:
               fd   (1)
               fdr   (2)
               notInUse   (3)
               ifdv   (4)"
   ::= {pr1646v2IpV6RtrQMonEntry 420937728}

pr1646v2IpV6RtrQMonDelayBinsMinMin OBJECT-TYPE
   SYNTAX      Counter32
   MAX-ACCESS  read-only
   STATUS      current
   DESCRIPTION
      "Path: v6Router.performance.qualityMonitor.delayBins.minMin

       32 bit unsigned wrappable counter."
   ::= {pr1646v2IpV6RtrQMonEntry 419495936}

pr1646v2IpV6RtrQMonDelayBinsMin OBJECT-TYPE
   SYNTAX      Integer32
   MAX-ACCESS  read-only
   STATUS      current
   DESCRIPTION
      "Path: v6Router.performance.qualityMonitor.delayBins.min

       unit name = sec
       formula = 1000 / ; 1000 *"
   ::= {pr1646v2IpV6RtrQMonEntry 420806656}

pr1646v2IpV6RtrQMonDelayBinsMinBin1 OBJECT-TYPE
   SYNTAX      Counter32
   MAX-ACCESS  read-only
   STATUS      current
   DESCRIPTION
      "Path: v6Router.performance.qualityMonitor.delayBins.minBin1

       32 bit unsigned wrappable counter."
   ::= {pr1646v2IpV6RtrQMonEntry 419561472}

pr1646v2IpV6RtrQMonDelayBinsBin2 OBJECT-TYPE
   SYNTAX      Counter32
   MAX-ACCESS  read-only
   STATUS      current
   DESCRIPTION
      "Path: v6Router.performance.qualityMonitor.delayBins.bin2

       32 bit unsigned wrappable counter."
   ::= {pr1646v2IpV6RtrQMonEntry 419627008}

pr1646v2IpV6RtrQMonDelayBinsBin3 OBJECT-TYPE
   SYNTAX      Counter32
   MAX-ACCESS  read-only
   STATUS      current
   DESCRIPTION
      "Path: v6Router.performance.qualityMonitor.delayBins.bin3

       32 bit unsigned wrappable counter."
   ::= {pr1646v2IpV6RtrQMonEntry 419692544}

pr1646v2IpV6RtrQMonDelayBinsBin4 OBJECT-TYPE
   SYNTAX      Counter32
   MAX-ACCESS  read-only
   STATUS      current
   DESCRIPTION
      "Path: v6Router.performance.qualityMonitor.delayBins.bin4

       32 bit unsigned wrappable counter."
   ::= {pr1646v2IpV6RtrQMonEntry 419758080}

pr1646v2IpV6RtrQMonDelayBinsBin5 OBJECT-TYPE
   SYNTAX      Counter32
   MAX-ACCESS  read-only
   STATUS      current
   DESCRIPTION
      "Path: v6Router.performance.qualityMonitor.delayBins.bin5

       32 bit unsigned wrappable counter."
   ::= {pr1646v2IpV6RtrQMonEntry 419823616}

pr1646v2IpV6RtrQMonDelayBinsBin6 OBJECT-TYPE
   SYNTAX      Counter32
   MAX-ACCESS  read-only
   STATUS      current
   DESCRIPTION
      "Path: v6Router.performance.qualityMonitor.delayBins.bin6

       32 bit unsigned wrappable counter."
   ::= {pr1646v2IpV6RtrQMonEntry 419889152}

pr1646v2IpV6RtrQMonDelayBinsBin7 OBJECT-TYPE
   SYNTAX      Counter32
   MAX-ACCESS  read-only
   STATUS      current
   DESCRIPTION
      "Path: v6Router.performance.qualityMonitor.delayBins.bin7

       32 bit unsigned wrappable counter."
   ::= {pr1646v2IpV6RtrQMonEntry 419954688}

pr1646v2IpV6RtrQMonDelayBinsMaxBin8 OBJECT-TYPE
   SYNTAX      Counter32
   MAX-ACCESS  read-only
   STATUS      current
   DESCRIPTION
      "Path: v6Router.performance.qualityMonitor.delayBins.maxBin8

       32 bit unsigned wrappable counter."
   ::= {pr1646v2IpV6RtrQMonEntry 420020224}

pr1646v2IpV6RtrQMonDelayBinsMax OBJECT-TYPE
   SYNTAX      Integer32
   MAX-ACCESS  read-only
   STATUS      current
   DESCRIPTION
      "Path: v6Router.performance.qualityMonitor.delayBins.max

       unit name = sec
       formula = 1000 / ; 1000 *"
   ::= {pr1646v2IpV6RtrQMonEntry 420872192}

pr1646v2IpV6RtrQMonDelayBinsPlusMax OBJECT-TYPE
   SYNTAX      Counter32
   MAX-ACCESS  read-only
   STATUS      current
   DESCRIPTION
      "Path: v6Router.performance.qualityMonitor.delayBins.plusMax

       32 bit unsigned wrappable counter."
   ::= {pr1646v2IpV6RtrQMonEntry 420085760}

pr1646v2IpV6RtrQMonJitterNegMax OBJECT-TYPE
   SYNTAX      Integer32
   MAX-ACCESS  read-only
   STATUS      current
   DESCRIPTION
      "Path: v6Router.performance.qualityMonitor.jitterNegMax

       unit name = sec
       formula = 1000 / ; 1000 *"
   ::= {pr1646v2IpV6RtrQMonEntry 234881024}

pr1646v2IpV6RtrQMonJitterAvrg OBJECT-TYPE
   SYNTAX      Integer32
   MAX-ACCESS  read-only
   STATUS      current
   DESCRIPTION
      "Path: v6Router.performance.qualityMonitor.jitterAvrg

       unit name = sec
       formula = 1000 / ; 1000 *"
   ::= {pr1646v2IpV6RtrQMonEntry 150994944}

pr1646v2IpV6RtrQMonJitterPosMax OBJECT-TYPE
   SYNTAX      Integer32
   MAX-ACCESS  read-only
   STATUS      current
   DESCRIPTION
      "Path: v6Router.performance.qualityMonitor.jitterPosMax

       unit name = sec
       formula = 1000 / ; 1000 *"
   ::= {pr1646v2IpV6RtrQMonEntry 167772160}

pr1646v2IpV6RtrQMonJitterBinsType OBJECT-TYPE
   SYNTAX      INTEGER
               {
               fd (1),
               fdr (2),
               notInUse (3),
               ifdv (4)
               }
   MAX-ACCESS  read-only
   STATUS      current
   DESCRIPTION
      "Path: v6Router.performance.qualityMonitor.jitterBins.type

       Possibilities:
               fd   (1)
               fdr   (2)
               notInUse   (3)
               ifdv   (4)"
   ::= {pr1646v2IpV6RtrQMonEntry 437714944}

pr1646v2IpV6RtrQMonJitterBinsMinMin OBJECT-TYPE
   SYNTAX      Counter32
   MAX-ACCESS  read-only
   STATUS      current
   DESCRIPTION
      "Path: v6Router.performance.qualityMonitor.jitterBins.minMin

       32 bit unsigned wrappable counter."
   ::= {pr1646v2IpV6RtrQMonEntry 436273152}

pr1646v2IpV6RtrQMonJitterBinsMin OBJECT-TYPE
   SYNTAX      Integer32
   MAX-ACCESS  read-only
   STATUS      current
   DESCRIPTION
      "Path: v6Router.performance.qualityMonitor.jitterBins.min

       unit name = sec
       formula = 1000 / ; 1000 *"
   ::= {pr1646v2IpV6RtrQMonEntry 437583872}

pr1646v2IpV6RtrQMonJitterBinsMinBin1 OBJECT-TYPE
   SYNTAX      Counter32
   MAX-ACCESS  read-only
   STATUS      current
   DESCRIPTION
      "Path: v6Router.performance.qualityMonitor.jitterBins.minBin1

       32 bit unsigned wrappable counter."
   ::= {pr1646v2IpV6RtrQMonEntry 436338688}

pr1646v2IpV6RtrQMonJitterBinsBin2 OBJECT-TYPE
   SYNTAX      Counter32
   MAX-ACCESS  read-only
   STATUS      current
   DESCRIPTION
      "Path: v6Router.performance.qualityMonitor.jitterBins.bin2

       32 bit unsigned wrappable counter."
   ::= {pr1646v2IpV6RtrQMonEntry 436404224}

pr1646v2IpV6RtrQMonJitterBinsBin3 OBJECT-TYPE
   SYNTAX      Counter32
   MAX-ACCESS  read-only
   STATUS      current
   DESCRIPTION
      "Path: v6Router.performance.qualityMonitor.jitterBins.bin3

       32 bit unsigned wrappable counter."
   ::= {pr1646v2IpV6RtrQMonEntry 436469760}

pr1646v2IpV6RtrQMonJitterBinsBin4 OBJECT-TYPE
   SYNTAX      Counter32
   MAX-ACCESS  read-only
   STATUS      current
   DESCRIPTION
      "Path: v6Router.performance.qualityMonitor.jitterBins.bin4

       32 bit unsigned wrappable counter."
   ::= {pr1646v2IpV6RtrQMonEntry 436535296}

pr1646v2IpV6RtrQMonJitterBinsBin5 OBJECT-TYPE
   SYNTAX      Counter32
   MAX-ACCESS  read-only
   STATUS      current
   DESCRIPTION
      "Path: v6Router.performance.qualityMonitor.jitterBins.bin5

       32 bit unsigned wrappable counter."
   ::= {pr1646v2IpV6RtrQMonEntry 436600832}

pr1646v2IpV6RtrQMonJitterBinsBin6 OBJECT-TYPE
   SYNTAX      Counter32
   MAX-ACCESS  read-only
   STATUS      current
   DESCRIPTION
      "Path: v6Router.performance.qualityMonitor.jitterBins.bin6

       32 bit unsigned wrappable counter."
   ::= {pr1646v2IpV6RtrQMonEntry 436666368}

pr1646v2IpV6RtrQMonJitterBinsBin7 OBJECT-TYPE
   SYNTAX      Counter32
   MAX-ACCESS  read-only
   STATUS      current
   DESCRIPTION
      "Path: v6Router.performance.qualityMonitor.jitterBins.bin7

       32 bit unsigned wrappable counter."
   ::= {pr1646v2IpV6RtrQMonEntry 436731904}

pr1646v2IpV6RtrQMonJitterBinsMaxBin8 OBJECT-TYPE
   SYNTAX      Counter32
   MAX-ACCESS  read-only
   STATUS      current
   DESCRIPTION
      "Path: v6Router.performance.qualityMonitor.jitterBins.maxBin8

       32 bit unsigned wrappable counter."
   ::= {pr1646v2IpV6RtrQMonEntry 436797440}

pr1646v2IpV6RtrQMonJitterBinsMax OBJECT-TYPE
   SYNTAX      Integer32
   MAX-ACCESS  read-only
   STATUS      current
   DESCRIPTION
      "Path: v6Router.performance.qualityMonitor.jitterBins.max

       unit name = sec
       formula = 1000 / ; 1000 *"
   ::= {pr1646v2IpV6RtrQMonEntry 437649408}

pr1646v2IpV6RtrQMonJitterBinsPlusMax OBJECT-TYPE
   SYNTAX      Counter32
   MAX-ACCESS  read-only
   STATUS      current
   DESCRIPTION
      "Path: v6Router.performance.qualityMonitor.jitterBins.plusMax

       32 bit unsigned wrappable counter."
   ::= {pr1646v2IpV6RtrQMonEntry 436862976}

pr1646v2IpV6RtrQMonUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: v6Router.performance.qualityMonitor.upDown.status

       Possibilities:
               notInUse   (3)
               onlyJitter   (1)
               jitterAndLoss   (2)
               all   (4)
               onlyLoss   (8)"
   ::= {pr1646v2IpV6RtrQMonEntry 504627200}

pr1646v2IpV6RtrQMonUpDownLossUp OBJECT-TYPE
   SYNTAX      Counter32
   MAX-ACCESS  read-only
   STATUS      current
   DESCRIPTION
      "Path: v6Router.performance.qualityMonitor.upDown.lossUp

       32 bit unsigned wrappable counter."
   ::= {pr1646v2IpV6RtrQMonEntry 503971840}

pr1646v2IpV6RtrQMonUpDownLossDelayUp OBJECT-TYPE
   SYNTAX      Counter32
   MAX-ACCESS  read-only
   STATUS      current
   DESCRIPTION
      "Path: v6Router.performance.qualityMonitor.upDown.lossDelayUp

       32 bit unsigned wrappable counter."
   ::= {pr1646v2IpV6RtrQMonEntry 504037376}

pr1646v2IpV6RtrQMonUpDownDelayUpMin OBJECT-TYPE
   SYNTAX      Integer32
   MAX-ACCESS  read-only
   STATUS      current
   DESCRIPTION
      "Path: v6Router.performance.qualityMonitor.upDown.delayUpMin

       unit name = sec
       formula = 1000 / ; 1000 *"
   ::= {pr1646v2IpV6RtrQMonEntry 505282560}

pr1646v2IpV6RtrQMonUpDownDelayUpAvrg OBJECT-TYPE
   SYNTAX      Integer32
   MAX-ACCESS  read-only
   STATUS      current
   DESCRIPTION
      "Path: v6Router.performance.qualityMonitor.upDown.delayUpAvrg

       unit name = sec
       formula = 1000 / ; 1000 *"
   ::= {pr1646v2IpV6RtrQMonEntry 505348096}

pr1646v2IpV6RtrQMonUpDownDelayUpMax OBJECT-TYPE
   SYNTAX      Integer32
   MAX-ACCESS  read-only
   STATUS      current
   DESCRIPTION
      "Path: v6Router.performance.qualityMonitor.upDown.delayUpMax

       unit name = sec
       formula = 1000 / ; 1000 *"
   ::= {pr1646v2IpV6RtrQMonEntry 505413632}

pr1646v2IpV6RtrQMonUpDownDelayUpBinsType OBJECT-TYPE
   SYNTAX      INTEGER
               {
               fd (1),
               fdr (2),
               notInUse (3),
               ifdv (4)
               }
   MAX-ACCESS  read-only
   STATUS      current
   DESCRIPTION
      "Path: v6Router.performance.qualityMonitor.upDown.delayUpBins.type

       Possibilities:
               fd   (1)
               fdr   (2)
               notInUse   (3)
               ifdv   (4)"
   ::= {pr1646v2IpV6RtrQMonEntry 505943808}

pr1646v2IpV6RtrQMonUpDownDelayUpBinsMinMin OBJECT-TYPE
   SYNTAX      Counter32
   MAX-ACCESS  read-only
   STATUS      current
   DESCRIPTION
      "Path: v6Router.performance.qualityMonitor.upDown.delayUpBins.minMin

       32 bit unsigned wrappable counter."
   ::= {pr1646v2IpV6RtrQMonEntry 505938176}

pr1646v2IpV6RtrQMonUpDownDelayUpBinsMin OBJECT-TYPE
   SYNTAX      Integer32
   MAX-ACCESS  read-only
   STATUS      current
   DESCRIPTION
      "Path: v6Router.performance.qualityMonitor.upDown.delayUpBins.min

       unit name = sec
       formula = 1000 / ; 1000 *"
   ::= {pr1646v2IpV6RtrQMonEntry 505943296}

pr1646v2IpV6RtrQMonUpDownDelayUpBinsMinBin1 OBJECT-TYPE
   SYNTAX      Counter32
   MAX-ACCESS  read-only
   STATUS      current
   DESCRIPTION
      "Path: v6Router.performance.qualityMonitor.upDown.delayUpBins.minBin1

       32 bit unsigned wrappable counter."
   ::= {pr1646v2IpV6RtrQMonEntry 505938432}

pr1646v2IpV6RtrQMonUpDownDelayUpBinsBin2 OBJECT-TYPE
   SYNTAX      Counter32
   MAX-ACCESS  read-only
   STATUS      current
   DESCRIPTION
      "Path: v6Router.performance.qualityMonitor.upDown.delayUpBins.bin2

       32 bit unsigned wrappable counter."
   ::= {pr1646v2IpV6RtrQMonEntry 505938688}

pr1646v2IpV6RtrQMonUpDownDelayUpBinsBin3 OBJECT-TYPE
   SYNTAX      Counter32
   MAX-ACCESS  read-only
   STATUS      current
   DESCRIPTION
      "Path: v6Router.performance.qualityMonitor.upDown.delayUpBins.bin3

       32 bit unsigned wrappable counter."
   ::= {pr1646v2IpV6RtrQMonEntry 505938944}

pr1646v2IpV6RtrQMonUpDownDelayUpBinsBin4 OBJECT-TYPE
   SYNTAX      Counter32
   MAX-ACCESS  read-only
   STATUS      current
   DESCRIPTION
      "Path: v6Router.performance.qualityMonitor.upDown.delayUpBins.bin4

       32 bit unsigned wrappable counter."
   ::= {pr1646v2IpV6RtrQMonEntry 505939200}

pr1646v2IpV6RtrQMonUpDownDelayUpBinsBin5 OBJECT-TYPE
   SYNTAX      Counter32
   MAX-ACCESS  read-only
   STATUS      current
   DESCRIPTION
      "Path: v6Router.performance.qualityMonitor.upDown.delayUpBins.bin5

       32 bit unsigned wrappable counter."
   ::= {pr1646v2IpV6RtrQMonEntry 505939456}

pr1646v2IpV6RtrQMonUpDownDelayUpBinsBin6 OBJECT-TYPE
   SYNTAX      Counter32
   MAX-ACCESS  read-only
   STATUS      current
   DESCRIPTION
      "Path: v6Router.performance.qualityMonitor.upDown.delayUpBins.bin6

       32 bit unsigned wrappable counter."
   ::= {pr1646v2IpV6RtrQMonEntry 505939712}

pr1646v2IpV6RtrQMonUpDownDelayUpBinsBin7 OBJECT-TYPE
   SYNTAX      Counter32
   MAX-ACCESS  read-only
   STATUS      current
   DESCRIPTION
      "Path: v6Router.performance.qualityMonitor.upDown.delayUpBins.bin7

       32 bit unsigned wrappable counter."
   ::= {pr1646v2IpV6RtrQMonEntry 505939968}

pr1646v2IpV6RtrQMonUpDownDelayUpBinsMaxBin8 OBJECT-TYPE
   SYNTAX      Counter32
   MAX-ACCESS  read-only
   STATUS      current
   DESCRIPTION
      "Path: v6Router.performance.qualityMonitor.upDown.delayUpBins.maxBin8

       32 bit unsigned wrappable counter."
   ::= {pr1646v2IpV6RtrQMonEntry 505940224}

pr1646v2IpV6RtrQMonUpDownDelayUpBinsMax OBJECT-TYPE
   SYNTAX      Integer32
   MAX-ACCESS  read-only
   STATUS      current
   DESCRIPTION
      "Path: v6Router.performance.qualityMonitor.upDown.delayUpBins.max

       unit name = sec
       formula = 1000 / ; 1000 *"
   ::= {pr1646v2IpV6RtrQMonEntry 505943552}

pr1646v2IpV6RtrQMonUpDownDelayUpBinsPlusMax OBJECT-TYPE
   SYNTAX      Counter32
   MAX-ACCESS  read-only
   STATUS      current
   DESCRIPTION
      "Path: v6Router.performance.qualityMonitor.upDown.delayUpBins.plusMax

       32 bit unsigned wrappable counter."
   ::= {pr1646v2IpV6RtrQMonEntry 505940480}

pr1646v2IpV6RtrQMonUpDownJitterUp OBJECT-TYPE
   SYNTAX      Integer32
   MAX-ACCESS  read-only
   STATUS      current
   DESCRIPTION
      "Path: v6Router.performance.qualityMonitor.upDown.jitterUp

       unit name = sec
       formula = 1000 / ; 1000 *"
   ::= {pr1646v2IpV6RtrQMonEntry 503775232}

pr1646v2IpV6RtrQMonUpDownJitterUpNegMax OBJECT-TYPE
   SYNTAX      Integer32
   MAX-ACCESS  read-only
   STATUS      current
   DESCRIPTION
      "Path: v6Router.performance.qualityMonitor.upDown.jitterUpNegMax

       unit name = sec
       formula = 1000 / ; 1000 *"
   ::= {pr1646v2IpV6RtrQMonEntry 503382016}

pr1646v2IpV6RtrQMonUpDownJitterUpAvrg OBJECT-TYPE
   SYNTAX      Integer32
   MAX-ACCESS  read-only
   STATUS      current
   DESCRIPTION
      "Path: v6Router.performance.qualityMonitor.upDown.jitterUpAvrg

       unit name = sec
       formula = 1000 / ; 1000 *"
   ::= {pr1646v2IpV6RtrQMonEntry 503447552}

pr1646v2IpV6RtrQMonUpDownJitterUpPosMax OBJECT-TYPE
   SYNTAX      Integer32
   MAX-ACCESS  read-only
   STATUS      current
   DESCRIPTION
      "Path: v6Router.performance.qualityMonitor.upDown.jitterUpPosMax

       unit name = sec
       formula = 1000 / ; 1000 *"
   ::= {pr1646v2IpV6RtrQMonEntry 503513088}

pr1646v2IpV6RtrQMonUpDownJitterUpBinsType OBJECT-TYPE
   SYNTAX      INTEGER
               {
               fd (1),
               fdr (2),
               notInUse (3),
               ifdv (4)
               }
   MAX-ACCESS  read-only
   STATUS      current
   DESCRIPTION
      "Path: v6Router.performance.qualityMonitor.upDown.jitterUpBins.type

       Possibilities:
               fd   (1)
               fdr   (2)
               notInUse   (3)
               ifdv   (4)"
   ::= {pr1646v2IpV6RtrQMonEntry 506074880}

pr1646v2IpV6RtrQMonUpDownJitterUpBinsMinMin OBJECT-TYPE
   SYNTAX      Counter32
   MAX-ACCESS  read-only
   STATUS      current
   DESCRIPTION
      "Path: v6Router.performance.qualityMonitor.upDown.jitterUpBins.minMin

       32 bit unsigned wrappable counter."
   ::= {pr1646v2IpV6RtrQMonEntry 506069248}

pr1646v2IpV6RtrQMonUpDownJitterUpBinsMin OBJECT-TYPE
   SYNTAX      Integer32
   MAX-ACCESS  read-only
   STATUS      current
   DESCRIPTION
      "Path: v6Router.performance.qualityMonitor.upDown.jitterUpBins.min

       unit name = sec
       formula = 1000 / ; 1000 *"
   ::= {pr1646v2IpV6RtrQMonEntry 506074368}

pr1646v2IpV6RtrQMonUpDownJitterUpBinsMinBin1 OBJECT-TYPE
   SYNTAX      Counter32
   MAX-ACCESS  read-only
   STATUS      current
   DESCRIPTION
      "Path: v6Router.performance.qualityMonitor.upDown.jitterUpBins.minBin1

       32 bit unsigned wrappable counter."
   ::= {pr1646v2IpV6RtrQMonEntry 506069504}

pr1646v2IpV6RtrQMonUpDownJitterUpBinsBin2 OBJECT-TYPE
   SYNTAX      Counter32
   MAX-ACCESS  read-only
   STATUS      current
   DESCRIPTION
      "Path: v6Router.performance.qualityMonitor.upDown.jitterUpBins.bin2

       32 bit unsigned wrappable counter."
   ::= {pr1646v2IpV6RtrQMonEntry 506069760}

pr1646v2IpV6RtrQMonUpDownJitterUpBinsBin3 OBJECT-TYPE
   SYNTAX      Counter32
   MAX-ACCESS  read-only
   STATUS      current
   DESCRIPTION
      "Path: v6Router.performance.qualityMonitor.upDown.jitterUpBins.bin3

       32 bit unsigned wrappable counter."
   ::= {pr1646v2IpV6RtrQMonEntry 506070016}

pr1646v2IpV6RtrQMonUpDownJitterUpBinsBin4 OBJECT-TYPE
   SYNTAX      Counter32
   MAX-ACCESS  read-only
   STATUS      current
   DESCRIPTION
      "Path: v6Router.performance.qualityMonitor.upDown.jitterUpBins.bin4

       32 bit unsigned wrappable counter."
   ::= {pr1646v2IpV6RtrQMonEntry 506070272}

pr1646v2IpV6RtrQMonUpDownJitterUpBinsBin5 OBJECT-TYPE
   SYNTAX      Counter32
   MAX-ACCESS  read-only
   STATUS      current
   DESCRIPTION
      "Path: v6Router.performance.qualityMonitor.upDown.jitterUpBins.bin5

       32 bit unsigned wrappable counter."
   ::= {pr1646v2IpV6RtrQMonEntry 506070528}

pr1646v2IpV6RtrQMonUpDownJitterUpBinsBin6 OBJECT-TYPE
   SYNTAX      Counter32
   MAX-ACCESS  read-only
   STATUS      current
   DESCRIPTION
      "Path: v6Router.performance.qualityMonitor.upDown.jitterUpBins.bin6

       32 bit unsigned wrappable counter."
   ::= {pr1646v2IpV6RtrQMonEntry 506070784}

pr1646v2IpV6RtrQMonUpDownJitterUpBinsBin7 OBJECT-TYPE
   SYNTAX      Counter32
   MAX-ACCESS  read-only
   STATUS      current
   DESCRIPTION
      "Path: v6Router.performance.qualityMonitor.upDown.jitterUpBins.bin7

       32 bit unsigned wrappable counter."
   ::= {pr1646v2IpV6RtrQMonEntry 506071040}

pr1646v2IpV6RtrQMonUpDownJitterUpBinsMaxBin8 OBJECT-TYPE
   SYNTAX      Counter32
   MAX-ACCESS  read-only
   STATUS      current
   DESCRIPTION
      "Path: v6Router.performance.qualityMonitor.upDown.jitterUpBins.maxBin8

       32 bit unsigned wrappable counter."
   ::= {pr1646v2IpV6RtrQMonEntry 506071296}

pr1646v2IpV6RtrQMonUpDownJitterUpBinsMax OBJECT-TYPE
   SYNTAX      Integer32
   MAX-ACCESS  read-only
   STATUS      current
   DESCRIPTION
      "Path: v6Router.performance.qualityMonitor.upDown.jitterUpBins.max

       unit name = sec
       formula = 1000 / ; 1000 *"
   ::= {pr1646v2IpV6RtrQMonEntry 506074624}

pr1646v2IpV6RtrQMonUpDownJitterUpBinsPlusMax OBJECT-TYPE
   SYNTAX      Counter32
   MAX-ACCESS  read-only
   STATUS      current
   DESCRIPTION
      "Path: v6Router.performance.qualityMonitor.upDown.jitterUpBins.plusMax

       32 bit unsigned wrappable counter."
   ::= {pr1646v2IpV6RtrQMonEntry 506071552}

pr1646v2IpV6RtrQMonUpDownLossDown OBJECT-TYPE
   SYNTAX      Counter32
   MAX-ACCESS  read-only
   STATUS      current
   DESCRIPTION
      "Path: v6Router.performance.qualityMonitor.upDown.lossDown

       32 bit unsigned wrappable counter."
   ::= {pr1646v2IpV6RtrQMonEntry 504102912}

pr1646v2IpV6RtrQMonUpDownLossDelayDown OBJECT-TYPE
   SYNTAX      Counter32
   MAX-ACCESS  read-only
   STATUS      current
   DESCRIPTION
      "Path: v6Router.performance.qualityMonitor.upDown.lossDelayDown

       32 bit unsigned wrappable counter."
   ::= {pr1646v2IpV6RtrQMonEntry 504168448}

pr1646v2IpV6RtrQMonUpDownDelayDownMin OBJECT-TYPE
   SYNTAX      Integer32
   MAX-ACCESS  read-only
   STATUS      current
   DESCRIPTION
      "Path: v6Router.performance.qualityMonitor.upDown.delayDownMin

       unit name = sec
       formula = 1000 / ; 1000 *"
   ::= {pr1646v2IpV6RtrQMonEntry 505610240}

pr1646v2IpV6RtrQMonUpDownDelayDownAvrg OBJECT-TYPE
   SYNTAX      Integer32
   MAX-ACCESS  read-only
   STATUS      current
   DESCRIPTION
      "Path: v6Router.performance.qualityMonitor.upDown.delayDownAvrg

       unit name = sec
       formula = 1000 / ; 1000 *"
   ::= {pr1646v2IpV6RtrQMonEntry 505675776}

pr1646v2IpV6RtrQMonUpDownDelayDownMax OBJECT-TYPE
   SYNTAX      Integer32
   MAX-ACCESS  read-only
   STATUS      current
   DESCRIPTION
      "Path: v6Router.performance.qualityMonitor.upDown.delayDownMax

       unit name = sec
       formula = 1000 / ; 1000 *"
   ::= {pr1646v2IpV6RtrQMonEntry 505741312}

pr1646v2IpV6RtrQMonUpDownDelayDownBinsType OBJECT-TYPE
   SYNTAX      INTEGER
               {
               fd (1),
               fdr (2),
               notInUse (3),
               ifdv (4)
               }
   MAX-ACCESS  read-only
   STATUS      current
   DESCRIPTION
      "Path: v6Router.performance.qualityMonitor.upDown.delayDownBins.type

       Possibilities:
               fd   (1)
               fdr   (2)
               notInUse   (3)
               ifdv   (4)"
   ::= {pr1646v2IpV6RtrQMonEntry 506009344}

pr1646v2IpV6RtrQMonUpDownDelayDownBinsMinMin OBJECT-TYPE
   SYNTAX      Counter32
   MAX-ACCESS  read-only
   STATUS      current
   DESCRIPTION
      "Path: v6Router.performance.qualityMonitor.upDown.delayDownBins.minMin

       32 bit unsigned wrappable counter."
   ::= {pr1646v2IpV6RtrQMonEntry 506003712}

pr1646v2IpV6RtrQMonUpDownDelayDownBinsMin OBJECT-TYPE
   SYNTAX      Integer32
   MAX-ACCESS  read-only
   STATUS      current
   DESCRIPTION
      "Path: v6Router.performance.qualityMonitor.upDown.delayDownBins.min

       unit name = sec
       formula = 1000 / ; 1000 *"
   ::= {pr1646v2IpV6RtrQMonEntry 506008832}

pr1646v2IpV6RtrQMonUpDownDelayDownBinsMinBin1 OBJECT-TYPE
   SYNTAX      Counter32
   MAX-ACCESS  read-only
   STATUS      current
   DESCRIPTION
      "Path: v6Router.performance.qualityMonitor.upDown.delayDownBins.minBin1

       32 bit unsigned wrappable counter."
   ::= {pr1646v2IpV6RtrQMonEntry 506003968}

pr1646v2IpV6RtrQMonUpDownDelayDownBinsBin2 OBJECT-TYPE
   SYNTAX      Counter32
   MAX-ACCESS  read-only
   STATUS      current
   DESCRIPTION
      "Path: v6Router.performance.qualityMonitor.upDown.delayDownBins.bin2

       32 bit unsigned wrappable counter."
   ::= {pr1646v2IpV6RtrQMonEntry 506004224}

pr1646v2IpV6RtrQMonUpDownDelayDownBinsBin3 OBJECT-TYPE
   SYNTAX      Counter32
   MAX-ACCESS  read-only
   STATUS      current
   DESCRIPTION
      "Path: v6Router.performance.qualityMonitor.upDown.delayDownBins.bin3

       32 bit unsigned wrappable counter."
   ::= {pr1646v2IpV6RtrQMonEntry 506004480}

pr1646v2IpV6RtrQMonUpDownDelayDownBinsBin4 OBJECT-TYPE
   SYNTAX      Counter32
   MAX-ACCESS  read-only
   STATUS      current
   DESCRIPTION
      "Path: v6Router.performance.qualityMonitor.upDown.delayDownBins.bin4

       32 bit unsigned wrappable counter."
   ::= {pr1646v2IpV6RtrQMonEntry 506004736}

pr1646v2IpV6RtrQMonUpDownDelayDownBinsBin5 OBJECT-TYPE
   SYNTAX      Counter32
   MAX-ACCESS  read-only
   STATUS      current
   DESCRIPTION
      "Path: v6Router.performance.qualityMonitor.upDown.delayDownBins.bin5

       32 bit unsigned wrappable counter."
   ::= {pr1646v2IpV6RtrQMonEntry 506004992}

pr1646v2IpV6RtrQMonUpDownDelayDownBinsBin6 OBJECT-TYPE
   SYNTAX      Counter32
   MAX-ACCESS  read-only
   STATUS      current
   DESCRIPTION
      "Path: v6Router.performance.qualityMonitor.upDown.delayDownBins.bin6

       32 bit unsigned wrappable counter."
   ::= {pr1646v2IpV6RtrQMonEntry 506005248}

pr1646v2IpV6RtrQMonUpDownDelayDownBinsBin7 OBJECT-TYPE
   SYNTAX      Counter32
   MAX-ACCESS  read-only
   STATUS      current
   DESCRIPTION
      "Path: v6Router.performance.qualityMonitor.upDown.delayDownBins.bin7

       32 bit unsigned wrappable counter."
   ::= {pr1646v2IpV6RtrQMonEntry 506005504}

pr1646v2IpV6RtrQMonUpDownDelayDownBinsMaxBin8 OBJECT-TYPE
   SYNTAX      Counter32
   MAX-ACCESS  read-only
   STATUS      current
   DESCRIPTION
      "Path: v6Router.performance.qualityMonitor.upDown.delayDownBins.maxBin8

       32 bit unsigned wrappable counter."
   ::= {pr1646v2IpV6RtrQMonEntry 506005760}

pr1646v2IpV6RtrQMonUpDownDelayDownBinsMax OBJECT-TYPE
   SYNTAX      Integer32
   MAX-ACCESS  read-only
   STATUS      current
   DESCRIPTION
      "Path: v6Router.performance.qualityMonitor.upDown.delayDownBins.max

       unit name = sec
       formula = 1000 / ; 1000 *"
   ::= {pr1646v2IpV6RtrQMonEntry 506009088}

pr1646v2IpV6RtrQMonUpDownDelayDownBinsPlusMax OBJECT-TYPE
   SYNTAX      Counter32
   MAX-ACCESS  read-only
   STATUS      current
   DESCRIPTION
      "Path: v6Router.performance.qualityMonitor.upDown.delayDownBins.plusMax

       32 bit unsigned wrappable counter."
   ::= {pr1646v2IpV6RtrQMonEntry 506006016}

pr1646v2IpV6RtrQMonUpDownJitterDown OBJECT-TYPE
   SYNTAX      Integer32
   MAX-ACCESS  read-only
   STATUS      current
   DESCRIPTION
      "Path: v6Router.performance.qualityMonitor.upDown.jitterDown

       unit name = sec
       formula = 1000 / ; 1000 *"
   ::= {pr1646v2IpV6RtrQMonEntry 503840768}

pr1646v2IpV6RtrQMonUpDownJitterDownNegMax OBJECT-TYPE
   SYNTAX      Integer32
   MAX-ACCESS  read-only
   STATUS      current
   DESCRIPTION
      "Path: v6Router.performance.qualityMonitor.upDown.jitterDownNegMax

       unit name = sec
       formula = 1000 / ; 1000 *"
   ::= {pr1646v2IpV6RtrQMonEntry 503578624}

pr1646v2IpV6RtrQMonUpDownJitterDownAvrg OBJECT-TYPE
   SYNTAX      Integer32
   MAX-ACCESS  read-only
   STATUS      current
   DESCRIPTION
      "Path: v6Router.performance.qualityMonitor.upDown.jitterDownAvrg

       unit name = sec
       formula = 1000 / ; 1000 *"
   ::= {pr1646v2IpV6RtrQMonEntry 503644160}

pr1646v2IpV6RtrQMonUpDownJitterDownPosMax OBJECT-TYPE
   SYNTAX      Integer32
   MAX-ACCESS  read-only
   STATUS      current
   DESCRIPTION
      "Path: v6Router.performance.qualityMonitor.upDown.jitterDownPosMax

       unit name = sec
       formula = 1000 / ; 1000 *"
   ::= {pr1646v2IpV6RtrQMonEntry 503709696}

pr1646v2IpV6RtrQMonUpDownJitterDownBinsType OBJECT-TYPE
   SYNTAX      INTEGER
               {
               fd (1),
               fdr (2),
               notInUse (3),
               ifdv (4)
               }
   MAX-ACCESS  read-only
   STATUS      current
   DESCRIPTION
      "Path: v6Router.performance.qualityMonitor.upDown.jitterDownBins.type

       Possibilities:
               fd   (1)
               fdr   (2)
               notInUse   (3)
               ifdv   (4)"
   ::= {pr1646v2IpV6RtrQMonEntry 506205952}

pr1646v2IpV6RtrQMonUpDownJitterDownBinsMinMin OBJECT-TYPE
   SYNTAX      Counter32
   MAX-ACCESS  read-only
   STATUS      current
   DESCRIPTION
      "Path: v6Router.performance.qualityMonitor.upDown.jitterDownBins.minMin

       32 bit unsigned wrappable counter."
   ::= {pr1646v2IpV6RtrQMonEntry 506200320}

pr1646v2IpV6RtrQMonUpDownJitterDownBinsMin OBJECT-TYPE
   SYNTAX      Integer32
   MAX-ACCESS  read-only
   STATUS      current
   DESCRIPTION
      "Path: v6Router.performance.qualityMonitor.upDown.jitterDownBins.min

       unit name = sec
       formula = 1000 / ; 1000 *"
   ::= {pr1646v2IpV6RtrQMonEntry 506205440}

pr1646v2IpV6RtrQMonUpDownJitterDownBinsMinBin1 OBJECT-TYPE
   SYNTAX      Counter32
   MAX-ACCESS  read-only
   STATUS      current
   DESCRIPTION
      "Path: v6Router.performance.qualityMonitor.upDown.jitterDownBins.minBin1

       32 bit unsigned wrappable counter."
   ::= {pr1646v2IpV6RtrQMonEntry 506200576}

pr1646v2IpV6RtrQMonUpDownJitterDownBinsBin2 OBJECT-TYPE
   SYNTAX      Counter32
   MAX-ACCESS  read-only
   STATUS      current
   DESCRIPTION
      "Path: v6Router.performance.qualityMonitor.upDown.jitterDownBins.bin2

       32 bit unsigned wrappable counter."
   ::= {pr1646v2IpV6RtrQMonEntry 506200832}

pr1646v2IpV6RtrQMonUpDownJitterDownBinsBin3 OBJECT-TYPE
   SYNTAX      Counter32
   MAX-ACCESS  read-only
   STATUS      current
   DESCRIPTION
      "Path: v6Router.performance.qualityMonitor.upDown.jitterDownBins.bin3

       32 bit unsigned wrappable counter."
   ::= {pr1646v2IpV6RtrQMonEntry 506201088}

pr1646v2IpV6RtrQMonUpDownJitterDownBinsBin4 OBJECT-TYPE
   SYNTAX      Counter32
   MAX-ACCESS  read-only
   STATUS      current
   DESCRIPTION
      "Path: v6Router.performance.qualityMonitor.upDown.jitterDownBins.bin4

       32 bit unsigned wrappable counter."
   ::= {pr1646v2IpV6RtrQMonEntry 506201344}

pr1646v2IpV6RtrQMonUpDownJitterDownBinsBin5 OBJECT-TYPE
   SYNTAX      Counter32
   MAX-ACCESS  read-only
   STATUS      current
   DESCRIPTION
      "Path: v6Router.performance.qualityMonitor.upDown.jitterDownBins.bin5

       32 bit unsigned wrappable counter."
   ::= {pr1646v2IpV6RtrQMonEntry 506201600}

pr1646v2IpV6RtrQMonUpDownJitterDownBinsBin6 OBJECT-TYPE
   SYNTAX      Counter32
   MAX-ACCESS  read-only
   STATUS      current
   DESCRIPTION
      "Path: v6Router.performance.qualityMonitor.upDown.jitterDownBins.bin6

       32 bit unsigned wrappable counter."
   ::= {pr1646v2IpV6RtrQMonEntry 506201856}

pr1646v2IpV6RtrQMonUpDownJitterDownBinsBin7 OBJECT-TYPE
   SYNTAX      Counter32
   MAX-ACCESS  read-only
   STATUS      current
   DESCRIPTION
      "Path: v6Router.performance.qualityMonitor.upDown.jitterDownBins.bin7

       32 bit unsigned wrappable counter."
   ::= {pr1646v2IpV6RtrQMonEntry 506202112}

pr1646v2IpV6RtrQMonUpDownJitterDownBinsMaxBin8 OBJECT-TYPE
   SYNTAX      Counter32
   MAX-ACCESS  read-only
   STATUS      current
   DESCRIPTION
      "Path: v6Router.performance.qualityMonitor.upDown.jitterDownBins.maxBin8

       32 bit unsigned wrappable counter."
   ::= {pr1646v2IpV6RtrQMonEntry 506202368}

pr1646v2IpV6RtrQMonUpDownJitterDownBinsMax OBJECT-TYPE
   SYNTAX      Integer32
   MAX-ACCESS  read-only
   STATUS      current
   DESCRIPTION
      "Path: v6Router.performance.qualityMonitor.upDown.jitterDownBins.max

       unit name = sec
       formula = 1000 / ; 1000 *"
   ::= {pr1646v2IpV6RtrQMonEntry 506205696}

pr1646v2IpV6RtrQMonUpDownJitterDownBinsPlusMax OBJECT-TYPE
   SYNTAX      Counter32
   MAX-ACCESS  read-only
   STATUS      current
   DESCRIPTION
      "Path: v6Router.performance.qualityMonitor.upDown.jitterDownBins.plusMax

       32 bit unsigned wrappable counter."
   ::= {pr1646v2IpV6RtrQMonEntry 506202624}

pr1646v2IpV6RtrQMonLastLogSysUpTime OBJECT-TYPE
   SYNTAX      TimeTicks
   MAX-ACCESS  read-only
   STATUS      current
   DESCRIPTION
      "Path: v6Router.performance.qualityMonitor.lastLog.sysUpTime

       Time in centi-second."
   ::= {pr1646v2IpV6RtrQMonEntry 671154176}

pr1646v2IpV6RtrQMonLastLogNbrTxPckt OBJECT-TYPE
   SYNTAX      Counter32
   MAX-ACCESS  read-only
   STATUS      current
   DESCRIPTION
      "Path: v6Router.performance.qualityMonitor.lastLog.nbrOfTxPackets

       32 bit unsigned wrappable counter."
   ::= {pr1646v2IpV6RtrQMonEntry 671285248}

pr1646v2IpV6RtrQMonLastLogNbrRxPckt OBJECT-TYPE
   SYNTAX      Counter32
   MAX-ACCESS  read-only
   STATUS      current
   DESCRIPTION
      "Path: v6Router.performance.qualityMonitor.lastLog.nbrOfRxPackets

       32 bit unsigned wrappable counter."
   ::= {pr1646v2IpV6RtrQMonEntry 671350784}

pr1646v2IpV6RtrQMonLastLogError OBJECT-TYPE
   SYNTAX      Counter32
   MAX-ACCESS  read-only
   STATUS      current
   DESCRIPTION
      "Path: v6Router.performance.qualityMonitor.lastLog.error

       32 bit unsigned wrappable counter."
   ::= {pr1646v2IpV6RtrQMonEntry 672202752}

pr1646v2IpV6RtrQMonLastLogLoss OBJECT-TYPE
   SYNTAX      Counter32
   MAX-ACCESS  read-only
   STATUS      current
   DESCRIPTION
      "Path: v6Router.performance.qualityMonitor.lastLog.loss

       32 bit unsigned wrappable counter."
   ::= {pr1646v2IpV6RtrQMonEntry 671481856}

pr1646v2IpV6RtrQMonLastLogLossDelay OBJECT-TYPE
   SYNTAX      Counter32
   MAX-ACCESS  read-only
   STATUS      current
   DESCRIPTION
      "Path: v6Router.performance.qualityMonitor.lastLog.lossDelay

       32 bit unsigned wrappable counter."
   ::= {pr1646v2IpV6RtrQMonEntry 672137216}

pr1646v2IpV6RtrQMonLastLogDelayMin OBJECT-TYPE
   SYNTAX      Integer32
   MAX-ACCESS  read-only
   STATUS      current
   DESCRIPTION
      "Path: v6Router.performance.qualityMonitor.lastLog.delayMin

       unit name = sec
       formula = 1000 / ; 1000 *"
   ::= {pr1646v2IpV6RtrQMonEntry 671809536}

pr1646v2IpV6RtrQMonLastLogDelayAvrg OBJECT-TYPE
   SYNTAX      Integer32
   MAX-ACCESS  read-only
   STATUS      current
   DESCRIPTION
      "Path: v6Router.performance.qualityMonitor.lastLog.delayAvrg

       unit name = sec
       formula = 1000 / ; 1000 *"
   ::= {pr1646v2IpV6RtrQMonEntry 671547392}

pr1646v2IpV6RtrQMonLastLogDelayMax OBJECT-TYPE
   SYNTAX      Integer32
   MAX-ACCESS  read-only
   STATUS      current
   DESCRIPTION
      "Path: v6Router.performance.qualityMonitor.lastLog.delayMax

       unit name = sec
       formula = 1000 / ; 1000 *"
   ::= {pr1646v2IpV6RtrQMonEntry 671612928}

pr1646v2IpV6RtrQMonLastLogJitterNegMax OBJECT-TYPE
   SYNTAX      Integer32
   MAX-ACCESS  read-only
   STATUS      current
   DESCRIPTION
      "Path: v6Router.performance.qualityMonitor.lastLog.jitterNegMax

       unit name = sec
       formula = 1000 / ; 1000 *"
   ::= {pr1646v2IpV6RtrQMonEntry 672006144}

pr1646v2IpV6RtrQMonLastLogJitterAvrg OBJECT-TYPE
   SYNTAX      Integer32
   MAX-ACCESS  read-only
   STATUS      current
   DESCRIPTION
      "Path: v6Router.performance.qualityMonitor.lastLog.jitterAvrg

       unit name = sec
       formula = 1000 / ; 1000 *"
   ::= {pr1646v2IpV6RtrQMonEntry 671678464}

pr1646v2IpV6RtrQMonLastLogJitterPosMax OBJECT-TYPE
   SYNTAX      Integer32
   MAX-ACCESS  read-only
   STATUS      current
   DESCRIPTION
      "Path: v6Router.performance.qualityMonitor.lastLog.jitterPosMax

       unit name = sec
       formula = 1000 / ; 1000 *"
   ::= {pr1646v2IpV6RtrQMonEntry 671744000}

pr1646v2IpV6RtrQMonLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: v6Router.performance.qualityMonitor.lastLog.upDown.status

       Possibilities:
               notInUse   (3)
               onlyJitter   (1)
               jitterAndLoss   (2)
               all   (4)
               onlyLoss   (8)"
   ::= {pr1646v2IpV6RtrQMonEntry 673059840}

pr1646v2IpV6RtrQMonLastLogUpDownLossUp OBJECT-TYPE
   SYNTAX      Counter32
   MAX-ACCESS  read-only
   STATUS      current
   DESCRIPTION
      "Path: v6Router.performance.qualityMonitor.lastLog.upDown.lossUp

       32 bit unsigned wrappable counter."
   ::= {pr1646v2IpV6RtrQMonEntry 673057280}

pr1646v2IpV6RtrQMonLastLogUpDownLossDelayUp OBJECT-TYPE
   SYNTAX      Counter32
   MAX-ACCESS  read-only
   STATUS      current
   DESCRIPTION
      "Path: v6Router.performance.qualityMonitor.lastLog.upDown.lossDelayUp

       32 bit unsigned wrappable counter."
   ::= {pr1646v2IpV6RtrQMonEntry 673057536}

pr1646v2IpV6RtrQMonLastLogUpDownDelayUpMin OBJECT-TYPE
   SYNTAX      Integer32
   MAX-ACCESS  read-only
   STATUS      current
   DESCRIPTION
      "Path: v6Router.performance.qualityMonitor.lastLog.upDown.delayUpMin

       unit name = sec
       formula = 1000 / ; 1000 *"
   ::= {pr1646v2IpV6RtrQMonEntry 673062400}

pr1646v2IpV6RtrQMonLastLogUpDownDelayUpAvrg OBJECT-TYPE
   SYNTAX      Integer32
   MAX-ACCESS  read-only
   STATUS      current
   DESCRIPTION
      "Path: v6Router.performance.qualityMonitor.lastLog.upDown.delayUpAvrg

       unit name = sec
       formula = 1000 / ; 1000 *"
   ::= {pr1646v2IpV6RtrQMonEntry 673062656}

pr1646v2IpV6RtrQMonLastLogUpDownDelayUpMax OBJECT-TYPE
   SYNTAX      Integer32
   MAX-ACCESS  read-only
   STATUS      current
   DESCRIPTION
      "Path: v6Router.performance.qualityMonitor.lastLog.upDown.delayUpMax

       unit name = sec
       formula = 1000 / ; 1000 *"
   ::= {pr1646v2IpV6RtrQMonEntry 673062912}

pr1646v2IpV6RtrQMonLastLogUpDownJitterUpNegMax OBJECT-TYPE
   SYNTAX      Integer32
   MAX-ACCESS  read-only
   STATUS      current
   DESCRIPTION
      "Path: v6Router.performance.qualityMonitor.lastLog.upDown.jitterUpNegMax

       unit name = sec
       formula = 1000 / ; 1000 *"
   ::= {pr1646v2IpV6RtrQMonEntry 673054976}

pr1646v2IpV6RtrQMonLastLogUpDownJitterUpAvrg OBJECT-TYPE
   SYNTAX      Integer32
   MAX-ACCESS  read-only
   STATUS      current
   DESCRIPTION
      "Path: v6Router.performance.qualityMonitor.lastLog.upDown.jitterUpAvrg

       unit name = sec
       formula = 1000 / ; 1000 *"
   ::= {pr1646v2IpV6RtrQMonEntry 673055232}

pr1646v2IpV6RtrQMonLastLogUpDownJitterUpPosMax OBJECT-TYPE
   SYNTAX      Integer32
   MAX-ACCESS  read-only
   STATUS      current
   DESCRIPTION
      "Path: v6Router.performance.qualityMonitor.lastLog.upDown.jitterUpPosMax

       unit name = sec
       formula = 1000 / ; 1000 *"
   ::= {pr1646v2IpV6RtrQMonEntry 673055488}

pr1646v2IpV6RtrQMonLastLogUpDownLossDown OBJECT-TYPE
   SYNTAX      Counter32
   MAX-ACCESS  read-only
   STATUS      current
   DESCRIPTION
      "Path: v6Router.performance.qualityMonitor.lastLog.upDown.lossDown

       32 bit unsigned wrappable counter."
   ::= {pr1646v2IpV6RtrQMonEntry 673057792}

pr1646v2IpV6RtrQMonLastLogUpDownLossDelayDown OBJECT-TYPE
   SYNTAX      Counter32
   MAX-ACCESS  read-only
   STATUS      current
   DESCRIPTION
      "Path: v6Router.performance.qualityMonitor.lastLog.upDown.lossDelayDown

       32 bit unsigned wrappable counter."
   ::= {pr1646v2IpV6RtrQMonEntry 673058048}

pr1646v2IpV6RtrQMonLastLogUpDownDelayDownMin OBJECT-TYPE
   SYNTAX      Integer32
   MAX-ACCESS  read-only
   STATUS      current
   DESCRIPTION
      "Path: v6Router.performance.qualityMonitor.lastLog.upDown.delayDownMin

       unit name = sec
       formula = 1000 / ; 1000 *"
   ::= {pr1646v2IpV6RtrQMonEntry 673063680}

pr1646v2IpV6RtrQMonLastLogUpDownDelayDownAvrg OBJECT-TYPE
   SYNTAX      Integer32
   MAX-ACCESS  read-only
   STATUS      current
   DESCRIPTION
      "Path: v6Router.performance.qualityMonitor.lastLog.upDown.delayDownAvrg

       unit name = sec
       formula = 1000 / ; 1000 *"
   ::= {pr1646v2IpV6RtrQMonEntry 673063936}

pr1646v2IpV6RtrQMonLastLogUpDownDelayDownMax OBJECT-TYPE
   SYNTAX      Integer32
   MAX-ACCESS  read-only
   STATUS      current
   DESCRIPTION
      "Path: v6Router.performance.qualityMonitor.lastLog.upDown.delayDownMax

       unit name = sec
       formula = 1000 / ; 1000 *"
   ::= {pr1646v2IpV6RtrQMonEntry 673064192}

pr1646v2IpV6RtrQMonLastLogUpDownJitterDownNegMax OBJECT-TYPE
   SYNTAX      Integer32
   MAX-ACCESS  read-only
   STATUS      current
   DESCRIPTION
      "Path: v6Router.performance.qualityMonitor.lastLog.upDown.jitterDownNegMax

       unit name = sec
       formula = 1000 / ; 1000 *"
   ::= {pr1646v2IpV6RtrQMonEntry 673055744}

pr1646v2IpV6RtrQMonLastLogUpDownJitterDownAvrg OBJECT-TYPE
   SYNTAX      Integer32
   MAX-ACCESS  read-only
   STATUS      current
   DESCRIPTION
      "Path: v6Router.performance.qualityMonitor.lastLog.upDown.jitterDownAvrg

       unit name = sec
       formula = 1000 / ; 1000 *"
   ::= {pr1646v2IpV6RtrQMonEntry 673056000}

pr1646v2IpV6RtrQMonLastLogUpDownJitterDownPosMax OBJECT-TYPE
   SYNTAX      Integer32
   MAX-ACCESS  read-only
   STATUS      current
   DESCRIPTION
      "Path: v6Router.performance.qualityMonitor.lastLog.upDown.jitterDownPosMax

       unit name = sec
       formula = 1000 / ; 1000 *"
   ::= {pr1646v2IpV6RtrQMonEntry 673056256}

pr1646v2IpV6RtrQMonLastLogDate OBJECT-TYPE
   SYNTAX      DisplayString
   MAX-ACCESS  read-only
   STATUS      current
   DESCRIPTION
      "Path: v6Router.performance.qualityMonitor.lastLog.date"
   ::= {pr1646v2IpV6RtrQMonEntry 673120256}

pr1646v2IpV6RtrQMonAlarm OBJECT-TYPE
   SYNTAX      Integer32
   MAX-ACCESS  read-only
   STATUS      current
   DESCRIPTION
      "Path: v6Router.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1646v2IpV6RtrQMonEntry 251658240}

pr1646v2IpV6RtrQMonLastError OBJECT-TYPE
   SYNTAX      DisplayString
   MAX-ACCESS  read-only
   STATUS      current
   DESCRIPTION
      "Path: v6Router.performance.qualityMonitor.lastError"
   ::= {pr1646v2IpV6RtrQMonEntry 318767104}

pr1646v2IpV6RtrQMonLogging OBJECT-TYPE
   SYNTAX      SEQUENCE OF Pr1646v2IpV6RtrQMonLoggingEntry
   MAX-ACCESS  not-accessible
   STATUS      current
   DESCRIPTION
      ""
   ::= {pr1646v2IpV6RtrQMon 335544320}

pr1646v2IpV6RtrQMonLoggingEntry OBJECT-TYPE
   SYNTAX      Pr1646v2IpV6RtrQMonLoggingEntry
   MAX-ACCESS  not-accessible
   STATUS      current
   DESCRIPTION
      ""
   INDEX      { pr1646v2IpV6RtrQMonTableIx,
                pr1646v2IpV6RtrQMonLoggingTableIx }
   ::= {pr1646v2IpV6RtrQMonLogging 1}

Pr1646v2IpV6RtrQMonLoggingEntry ::=
   SEQUENCE
      {
      pr1646v2IpV6RtrQMonLoggingTableIx
         TableIndex,
      pr1646v2IpV6RtrQMonLoggingSysUpTime
         TimeTicks,
      pr1646v2IpV6RtrQMonLoggingNbrTxPckt
         Counter32,
      pr1646v2IpV6RtrQMonLoggingNbrRxPckt
         Counter32,
      pr1646v2IpV6RtrQMonLoggingError
         Counter32,
      pr1646v2IpV6RtrQMonLoggingLoss
         Counter32,
      pr1646v2IpV6RtrQMonLoggingLossDelay
         Counter32,
      pr1646v2IpV6RtrQMonLoggingDelayMin
         Integer32,
      pr1646v2IpV6RtrQMonLoggingDelayAvrg
         Integer32,
      pr1646v2IpV6RtrQMonLoggingDelayMax
         Integer32,
      pr1646v2IpV6RtrQMonLoggingJitterNegMax
         Integer32,
      pr1646v2IpV6RtrQMonLoggingJitterAvrg
         Integer32,
      pr1646v2IpV6RtrQMonLoggingJitterPosMax
         Integer32,
      pr1646v2IpV6RtrQMonLoggingUpDownStatus
         INTEGER,
      pr1646v2IpV6RtrQMonLoggingUpDownLossUp
         Counter32,
      pr1646v2IpV6RtrQMonLoggingUpDownLossDelayUp
         Counter32,
      pr1646v2IpV6RtrQMonLoggingUpDownDelayUpMin
         Integer32,
      pr1646v2IpV6RtrQMonLoggingUpDownDelayUpAvrg
         Integer32,
      pr1646v2IpV6RtrQMonLoggingUpDownDelayUpMax
         Integer32,
      pr1646v2IpV6RtrQMonLoggingUpDownJitterUpNegMax
         Integer32,
      pr1646v2IpV6RtrQMonLoggingUpDownJitterUpAvrg
         Integer32,
      pr1646v2IpV6RtrQMonLoggingUpDownJitterUpPosMax
         Integer32,
      pr1646v2IpV6RtrQMonLoggingUpDownLossDown
         Counter32,
      pr1646v2IpV6RtrQMonLoggingUpDownLossDelayDown
         Counter32,
      pr1646v2IpV6RtrQMonLoggingUpDownDelayDownMin
         Integer32,
      pr1646v2IpV6RtrQMonLoggingUpDownDelayDownAvrg
         Integer32,
      pr1646v2IpV6RtrQMonLoggingUpDownDelayDownMax
         Integer32,
      pr1646v2IpV6RtrQMonLoggingUpDownJitterDownNegMax
         Integer32,
      pr1646v2IpV6RtrQMonLoggingUpDownJitterDownAvrg
         Integer32,
      pr1646v2IpV6RtrQMonLoggingUpDownJitterDownPosMax
         Integer32,
      pr1646v2IpV6RtrQMonLoggingDate
         DisplayString
      }

pr1646v2IpV6RtrQMonLoggingTableIx OBJECT-TYPE
   SYNTAX      TableIndex
   MAX-ACCESS  not-accessible
   STATUS      current
   DESCRIPTION
      ""
   ::= {pr1646v2IpV6RtrQMonLoggingEntry 11}

pr1646v2IpV6RtrQMonLoggingSysUpTime OBJECT-TYPE
   SYNTAX      TimeTicks
   MAX-ACCESS  read-only
   STATUS      current
   DESCRIPTION
      "Path: v6Router.performance.qualityMonitor.logging.sysUpTime

       Time in centi-second."
   ::= {pr1646v2IpV6RtrQMonLoggingEntry 16777216}

pr1646v2IpV6RtrQMonLoggingNbrTxPckt OBJECT-TYPE
   SYNTAX      Counter32
   MAX-ACCESS  read-only
   STATUS      current
   DESCRIPTION
      "Path: v6Router.performance.qualityMonitor.logging.nbrOfTxPackets

       32 bit unsigned wrappable counter."
   ::= {pr1646v2IpV6RtrQMonLoggingEntry 50331648}

pr1646v2IpV6RtrQMonLoggingNbrRxPckt OBJECT-TYPE
   SYNTAX      Counter32
   MAX-ACCESS  read-only
   STATUS      current
   DESCRIPTION
      "Path: v6Router.performance.qualityMonitor.logging.nbrOfRxPackets

       32 bit unsigned wrappable counter."
   ::= {pr1646v2IpV6RtrQMonLoggingEntry 67108864}

pr1646v2IpV6RtrQMonLoggingError OBJECT-TYPE
   SYNTAX      Counter32
   MAX-ACCESS  read-only
   STATUS      current
   DESCRIPTION
      "Path: v6Router.performance.qualityMonitor.logging.error

       32 bit unsigned wrappable counter."
   ::= {pr1646v2IpV6RtrQMonLoggingEntry 285212672}

pr1646v2IpV6RtrQMonLoggingLoss OBJECT-TYPE
   SYNTAX      Counter32
   MAX-ACCESS  read-only
   STATUS      current
   DESCRIPTION
      "Path: v6Router.performance.qualityMonitor.logging.loss

       32 bit unsigned wrappable counter."
   ::= {pr1646v2IpV6RtrQMonLoggingEntry 100663296}

pr1646v2IpV6RtrQMonLoggingLossDelay OBJECT-TYPE
   SYNTAX      Counter32
   MAX-ACCESS  read-only
   STATUS      current
   DESCRIPTION
      "Path: v6Router.performance.qualityMonitor.logging.lossDelay

       32 bit unsigned wrappable counter."
   ::= {pr1646v2IpV6RtrQMonLoggingEntry 268435456}

pr1646v2IpV6RtrQMonLoggingDelayMin OBJECT-TYPE
   SYNTAX      Integer32
   MAX-ACCESS  read-only
   STATUS      current
   DESCRIPTION
      "Path: v6Router.performance.qualityMonitor.logging.delayMin

       unit name = sec
       formula = 1000 / ; 1000 *"
   ::= {pr1646v2IpV6RtrQMonLoggingEntry 184549376}

pr1646v2IpV6RtrQMonLoggingDelayAvrg OBJECT-TYPE
   SYNTAX      Integer32
   MAX-ACCESS  read-only
   STATUS      current
   DESCRIPTION
      "Path: v6Router.performance.qualityMonitor.logging.delayAvrg

       unit name = sec
       formula = 1000 / ; 1000 *"
   ::= {pr1646v2IpV6RtrQMonLoggingEntry 117440512}

pr1646v2IpV6RtrQMonLoggingDelayMax OBJECT-TYPE
   SYNTAX      Integer32
   MAX-ACCESS  read-only
   STATUS      current
   DESCRIPTION
      "Path: v6Router.performance.qualityMonitor.logging.delayMax

       unit name = sec
       formula = 1000 / ; 1000 *"
   ::= {pr1646v2IpV6RtrQMonLoggingEntry 134217728}

pr1646v2IpV6RtrQMonLoggingJitterNegMax OBJECT-TYPE
   SYNTAX      Integer32
   MAX-ACCESS  read-only
   STATUS      current
   DESCRIPTION
      "Path: v6Router.performance.qualityMonitor.logging.jitterNegMax

       unit name = sec
       formula = 1000 / ; 1000 *"
   ::= {pr1646v2IpV6RtrQMonLoggingEntry 234881024}

pr1646v2IpV6RtrQMonLoggingJitterAvrg OBJECT-TYPE
   SYNTAX      Integer32
   MAX-ACCESS  read-only
   STATUS      current
   DESCRIPTION
      "Path: v6Router.performance.qualityMonitor.logging.jitterAvrg

       unit name = sec
       formula = 1000 / ; 1000 *"
   ::= {pr1646v2IpV6RtrQMonLoggingEntry 150994944}

pr1646v2IpV6RtrQMonLoggingJitterPosMax OBJECT-TYPE
   SYNTAX      Integer32
   MAX-ACCESS  read-only
   STATUS      current
   DESCRIPTION
      "Path: v6Router.performance.qualityMonitor.logging.jitterPosMax

       unit name = sec
       formula = 1000 / ; 1000 *"
   ::= {pr1646v2IpV6RtrQMonLoggingEntry 167772160}

pr1646v2IpV6RtrQMonLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: v6Router.performance.qualityMonitor.logging.upDown.status

       Possibilities:
               notInUse   (3)
               onlyJitter   (1)
               jitterAndLoss   (2)
               all   (4)
               onlyLoss   (8)"
   ::= {pr1646v2IpV6RtrQMonLoggingEntry 504627200}

pr1646v2IpV6RtrQMonLoggingUpDownLossUp OBJECT-TYPE
   SYNTAX      Counter32
   MAX-ACCESS  read-only
   STATUS      current
   DESCRIPTION
      "Path: v6Router.performance.qualityMonitor.logging.upDown.lossUp

       32 bit unsigned wrappable counter."
   ::= {pr1646v2IpV6RtrQMonLoggingEntry 503971840}

pr1646v2IpV6RtrQMonLoggingUpDownLossDelayUp OBJECT-TYPE
   SYNTAX      Counter32
   MAX-ACCESS  read-only
   STATUS      current
   DESCRIPTION
      "Path: v6Router.performance.qualityMonitor.logging.upDown.lossDelayUp

       32 bit unsigned wrappable counter."
   ::= {pr1646v2IpV6RtrQMonLoggingEntry 504037376}

pr1646v2IpV6RtrQMonLoggingUpDownDelayUpMin OBJECT-TYPE
   SYNTAX      Integer32
   MAX-ACCESS  read-only
   STATUS      current
   DESCRIPTION
      "Path: v6Router.performance.qualityMonitor.logging.upDown.delayUpMin

       unit name = sec
       formula = 1000 / ; 1000 *"
   ::= {pr1646v2IpV6RtrQMonLoggingEntry 505282560}

pr1646v2IpV6RtrQMonLoggingUpDownDelayUpAvrg OBJECT-TYPE
   SYNTAX      Integer32
   MAX-ACCESS  read-only
   STATUS      current
   DESCRIPTION
      "Path: v6Router.performance.qualityMonitor.logging.upDown.delayUpAvrg

       unit name = sec
       formula = 1000 / ; 1000 *"
   ::= {pr1646v2IpV6RtrQMonLoggingEntry 505348096}

pr1646v2IpV6RtrQMonLoggingUpDownDelayUpMax OBJECT-TYPE
   SYNTAX      Integer32
   MAX-ACCESS  read-only
   STATUS      current
   DESCRIPTION
      "Path: v6Router.performance.qualityMonitor.logging.upDown.delayUpMax

       unit name = sec
       formula = 1000 / ; 1000 *"
   ::= {pr1646v2IpV6RtrQMonLoggingEntry 505413632}

pr1646v2IpV6RtrQMonLoggingUpDownJitterUpNegMax OBJECT-TYPE
   SYNTAX      Integer32
   MAX-ACCESS  read-only
   STATUS      current
   DESCRIPTION
      "Path: v6Router.performance.qualityMonitor.logging.upDown.jitterUpNegMax

       unit name = sec
       formula = 1000 / ; 1000 *"
   ::= {pr1646v2IpV6RtrQMonLoggingEntry 503382016}

pr1646v2IpV6RtrQMonLoggingUpDownJitterUpAvrg OBJECT-TYPE
   SYNTAX      Integer32
   MAX-ACCESS  read-only
   STATUS      current
   DESCRIPTION
      "Path: v6Router.performance.qualityMonitor.logging.upDown.jitterUpAvrg

       unit name = sec
       formula = 1000 / ; 1000 *"
   ::= {pr1646v2IpV6RtrQMonLoggingEntry 503447552}

pr1646v2IpV6RtrQMonLoggingUpDownJitterUpPosMax OBJECT-TYPE
   SYNTAX      Integer32
   MAX-ACCESS  read-only
   STATUS      current
   DESCRIPTION
      "Path: v6Router.performance.qualityMonitor.logging.upDown.jitterUpPosMax

       unit name = sec
       formula = 1000 / ; 1000 *"
   ::= {pr1646v2IpV6RtrQMonLoggingEntry 503513088}

pr1646v2IpV6RtrQMonLoggingUpDownLossDown OBJECT-TYPE
   SYNTAX      Counter32
   MAX-ACCESS  read-only
   STATUS      current
   DESCRIPTION
      "Path: v6Router.performance.qualityMonitor.logging.upDown.lossDown

       32 bit unsigned wrappable counter."
   ::= {pr1646v2IpV6RtrQMonLoggingEntry 504102912}

pr1646v2IpV6RtrQMonLoggingUpDownLossDelayDown OBJECT-TYPE
   SYNTAX      Counter32
   MAX-ACCESS  read-only
   STATUS      current
   DESCRIPTION
      "Path: v6Router.performance.qualityMonitor.logging.upDown.lossDelayDown

       32 bit unsigned wrappable counter."
   ::= {pr1646v2IpV6RtrQMonLoggingEntry 504168448}

pr1646v2IpV6RtrQMonLoggingUpDownDelayDownMin OBJECT-TYPE
   SYNTAX      Integer32
   MAX-ACCESS  read-only
   STATUS      current
   DESCRIPTION
      "Path: v6Router.performance.qualityMonitor.logging.upDown.delayDownMin

       unit name = sec
       formula = 1000 / ; 1000 *"
   ::= {pr1646v2IpV6RtrQMonLoggingEntry 505610240}

pr1646v2IpV6RtrQMonLoggingUpDownDelayDownAvrg OBJECT-TYPE
   SYNTAX      Integer32
   MAX-ACCESS  read-only
   STATUS      current
   DESCRIPTION
      "Path: v6Router.performance.qualityMonitor.logging.upDown.delayDownAvrg

       unit name = sec
       formula = 1000 / ; 1000 *"
   ::= {pr1646v2IpV6RtrQMonLoggingEntry 505675776}

pr1646v2IpV6RtrQMonLoggingUpDownDelayDownMax OBJECT-TYPE
   SYNTAX      Integer32
   MAX-ACCESS  read-only
   STATUS      current
   DESCRIPTION
      "Path: v6Router.performance.qualityMonitor.logging.upDown.delayDownMax

       unit name = sec
       formula = 1000 / ; 1000 *"
   ::= {pr1646v2IpV6RtrQMonLoggingEntry 505741312}

pr1646v2IpV6RtrQMonLoggingUpDownJitterDownNegMax OBJECT-TYPE
   SYNTAX      Integer32
   MAX-ACCESS  read-only
   STATUS      current
   DESCRIPTION
      "Path: v6Router.performance.qualityMonitor.logging.upDown.jitterDownNegMax

       unit name = sec
       formula = 1000 / ; 1000 *"
   ::= {pr1646v2IpV6RtrQMonLoggingEntry 503578624}

pr1646v2IpV6RtrQMonLoggingUpDownJitterDownAvrg OBJECT-TYPE
   SYNTAX      Integer32
   MAX-ACCESS  read-only
   STATUS      current
   DESCRIPTION
      "Path: v6Router.performance.qualityMonitor.logging.upDown.jitterDownAvrg

       unit name = sec
       formula = 1000 / ; 1000 *"
   ::= {pr1646v2IpV6RtrQMonLoggingEntry 503644160}

pr1646v2IpV6RtrQMonLoggingUpDownJitterDownPosMax OBJECT-TYPE
   SYNTAX      Integer32
   MAX-ACCESS  read-only
   STATUS      current
   DESCRIPTION
      "Path: v6Router.performance.qualityMonitor.logging.upDown.jitterDownPosMax

       unit name = sec
       formula = 1000 / ; 1000 *"
   ::= {pr1646v2IpV6RtrQMonLoggingEntry 503709696}

pr1646v2IpV6RtrQMonLoggingDate OBJECT-TYPE
   SYNTAX      DisplayString
   MAX-ACCESS  read-only
   STATUS      current
   DESCRIPTION
      "Path: v6Router.performance.qualityMonitor.logging.date"
   ::= {pr1646v2IpV6RtrQMonLoggingEntry 520093696}

pr1646v2IpV6RtrQMonLoggingBin OBJECT-TYPE
   SYNTAX      SEQUENCE OF Pr1646v2IpV6RtrQMonLoggingBinEntry
   MAX-ACCESS  not-accessible
   STATUS      current
   DESCRIPTION
      ""
   ::= {pr1646v2IpV6RtrQMon 337641472}

pr1646v2IpV6RtrQMonLoggingBinEntry OBJECT-TYPE
   SYNTAX      Pr1646v2IpV6RtrQMonLoggingBinEntry
   MAX-ACCESS  not-accessible
   STATUS      current
   DESCRIPTION
      ""
   INDEX      { pr1646v2IpV6RtrQMonTableIx,
                pr1646v2IpV6RtrQMonLoggingTableIx,
                pr1646v2IpV6RtrQMonLoggingBinTableIx }
   ::= {pr1646v2IpV6RtrQMonLoggingBin 1}

Pr1646v2IpV6RtrQMonLoggingBinEntry ::=
   SEQUENCE
      {
      pr1646v2IpV6RtrQMonLoggingBinTableIx
         TableIndex,
      pr1646v2IpV6RtrQMonLoggingBinName
         INTEGER,
      pr1646v2IpV6RtrQMonLoggingBinType
         INTEGER,
      pr1646v2IpV6RtrQMonLoggingBinMinMin
         Counter32,
      pr1646v2IpV6RtrQMonLoggingBinMin
         Integer32,
      pr1646v2IpV6RtrQMonLoggingBinMinBin1
         Counter32,
      pr1646v2IpV6RtrQMonLoggingBinBin2
         Counter32,
      pr1646v2IpV6RtrQMonLoggingBinBin3
         Counter32,
      pr1646v2IpV6RtrQMonLoggingBinBin4
         Counter32,
      pr1646v2IpV6RtrQMonLoggingBinBin5
         Counter32,
      pr1646v2IpV6RtrQMonLoggingBinBin6
         Counter32,
      pr1646v2IpV6RtrQMonLoggingBinBin7
         Counter32,
      pr1646v2IpV6RtrQMonLoggingBinMaxBin8
         Counter32,
      pr1646v2IpV6RtrQMonLoggingBinMax
         Integer32,
      pr1646v2IpV6RtrQMonLoggingBinPlusMax
         Counter32
      }

pr1646v2IpV6RtrQMonLoggingBinTableIx OBJECT-TYPE
   SYNTAX      TableIndex
   MAX-ACCESS  not-accessible
   STATUS      current
   DESCRIPTION
      ""
   ::= {pr1646v2IpV6RtrQMonLoggingBinEntry 11}

pr1646v2IpV6RtrQMonLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: v6Router.performance.qualityMonitor.logging.bin.name

       Possibilities:
               delay   (1)
               delayUp   (2)
               delayDown   (3)
               jitter   (4)
               jitterUp   (5)
               jitterDown   (6)"
   ::= {pr1646v2IpV6RtrQMonLoggingBinEntry 503316480}

pr1646v2IpV6RtrQMonLoggingBinType OBJECT-TYPE
   SYNTAX      INTEGER
               {
               fd (1),
               fdr (2),
               notInUse (3),
               ifdv (4)
               }
   MAX-ACCESS  read-only
   STATUS      current
   DESCRIPTION
      "Path: v6Router.performance.qualityMonitor.logging.bin.type

       Possibilities:
               fd   (1)
               fdr   (2)
               notInUse   (3)
               ifdv   (4)"
   ::= {pr1646v2IpV6RtrQMonLoggingBinEntry 520093696}

pr1646v2IpV6RtrQMonLoggingBinMinMin OBJECT-TYPE
   SYNTAX      Counter32
   MAX-ACCESS  read-only
   STATUS      current
   DESCRIPTION
      "Path: v6Router.performance.qualityMonitor.logging.bin.minMin

       32 bit unsigned wrappable counter."
   ::= {pr1646v2IpV6RtrQMonLoggingBinEntry 16777216}

pr1646v2IpV6RtrQMonLoggingBinMin OBJECT-TYPE
   SYNTAX      Integer32
   MAX-ACCESS  read-only
   STATUS      current
   DESCRIPTION
      "Path: v6Router.performance.qualityMonitor.logging.bin.min

       unit name = sec
       formula = 1000 / ; 1000 *"
   ::= {pr1646v2IpV6RtrQMonLoggingBinEntry 352321536}

pr1646v2IpV6RtrQMonLoggingBinMinBin1 OBJECT-TYPE
   SYNTAX      Counter32
   MAX-ACCESS  read-only
   STATUS      current
   DESCRIPTION
      "Path: v6Router.performance.qualityMonitor.logging.bin.minBin1

       32 bit unsigned wrappable counter."
   ::= {pr1646v2IpV6RtrQMonLoggingBinEntry 33554432}

pr1646v2IpV6RtrQMonLoggingBinBin2 OBJECT-TYPE
   SYNTAX      Counter32
   MAX-ACCESS  read-only
   STATUS      current
   DESCRIPTION
      "Path: v6Router.performance.qualityMonitor.logging.bin.bin2

       32 bit unsigned wrappable counter."
   ::= {pr1646v2IpV6RtrQMonLoggingBinEntry 50331648}

pr1646v2IpV6RtrQMonLoggingBinBin3 OBJECT-TYPE
   SYNTAX      Counter32
   MAX-ACCESS  read-only
   STATUS      current
   DESCRIPTION
      "Path: v6Router.performance.qualityMonitor.logging.bin.bin3

       32 bit unsigned wrappable counter."
   ::= {pr1646v2IpV6RtrQMonLoggingBinEntry 67108864}

pr1646v2IpV6RtrQMonLoggingBinBin4 OBJECT-TYPE
   SYNTAX      Counter32
   MAX-ACCESS  read-only
   STATUS      current
   DESCRIPTION
      "Path: v6Router.performance.qualityMonitor.logging.bin.bin4

       32 bit unsigned wrappable counter."
   ::= {pr1646v2IpV6RtrQMonLoggingBinEntry 83886080}

pr1646v2IpV6RtrQMonLoggingBinBin5 OBJECT-TYPE
   SYNTAX      Counter32
   MAX-ACCESS  read-only
   STATUS      current
   DESCRIPTION
      "Path: v6Router.performance.qualityMonitor.logging.bin.bin5

       32 bit unsigned wrappable counter."
   ::= {pr1646v2IpV6RtrQMonLoggingBinEntry 100663296}

pr1646v2IpV6RtrQMonLoggingBinBin6 OBJECT-TYPE
   SYNTAX      Counter32
   MAX-ACCESS  read-only
   STATUS      current
   DESCRIPTION
      "Path: v6Router.performance.qualityMonitor.logging.bin.bin6

       32 bit unsigned wrappable counter."
   ::= {pr1646v2IpV6RtrQMonLoggingBinEntry 117440512}

pr1646v2IpV6RtrQMonLoggingBinBin7 OBJECT-TYPE
   SYNTAX      Counter32
   MAX-ACCESS  read-only
   STATUS      current
   DESCRIPTION
      "Path: v6Router.performance.qualityMonitor.logging.bin.bin7

       32 bit unsigned wrappable counter."
   ::= {pr1646v2IpV6RtrQMonLoggingBinEntry 134217728}

pr1646v2IpV6RtrQMonLoggingBinMaxBin8 OBJECT-TYPE
   SYNTAX      Counter32
   MAX-ACCESS  read-only
   STATUS      current
   DESCRIPTION
      "Path: v6Router.performance.qualityMonitor.logging.bin.maxBin8

       32 bit unsigned wrappable counter."
   ::= {pr1646v2IpV6RtrQMonLoggingBinEntry 150994944}

pr1646v2IpV6RtrQMonLoggingBinMax OBJECT-TYPE
   SYNTAX      Integer32
   MAX-ACCESS  read-only
   STATUS      current
   DESCRIPTION
      "Path: v6Router.performance.qualityMonitor.logging.bin.max

       unit name = sec
       formula = 1000 / ; 1000 *"
   ::= {pr1646v2IpV6RtrQMonLoggingBinEntry 369098752}

pr1646v2IpV6RtrQMonLoggingBinPlusMax OBJECT-TYPE
   SYNTAX      Counter32
   MAX-ACCESS  read-only
   STATUS      current
   DESCRIPTION
      "Path: v6Router.performance.qualityMonitor.logging.bin.plusMax

       32 bit unsigned wrappable counter."
   ::= {pr1646v2IpV6RtrQMonLoggingBinEntry 167772160}

pr1646v2IpV6RtrQMonLastLogBin OBJECT-TYPE
   SYNTAX      SEQUENCE OF Pr1646v2IpV6RtrQMonLastLogBinEntry
   MAX-ACCESS  not-accessible
   STATUS      current
   DESCRIPTION
      ""
   ::= {pr1646v2IpV6RtrQMon 673185792}

pr1646v2IpV6RtrQMonLastLogBinEntry OBJECT-TYPE
   SYNTAX      Pr1646v2IpV6RtrQMonLastLogBinEntry
   MAX-ACCESS  not-accessible
   STATUS      current
   DESCRIPTION
      ""
   INDEX      { pr1646v2IpV6RtrQMonTableIx,
                pr1646v2IpV6RtrQMonLastLogBinTableIx }
   ::= {pr1646v2IpV6RtrQMonLastLogBin 1}

Pr1646v2IpV6RtrQMonLastLogBinEntry ::=
   SEQUENCE
      {
      pr1646v2IpV6RtrQMonLastLogBinTableIx
         TableIndex,
      pr1646v2IpV6RtrQMonLastLogBinName
         INTEGER,
      pr1646v2IpV6RtrQMonLastLogBinType
         INTEGER,
      pr1646v2IpV6RtrQMonLastLogBinMinMin
         Counter32,
      pr1646v2IpV6RtrQMonLastLogBinMin
         Integer32,
      pr1646v2IpV6RtrQMonLastLogBinMinBin1
         Counter32,
      pr1646v2IpV6RtrQMonLastLogBinBin2
         Counter32,
      pr1646v2IpV6RtrQMonLastLogBinBin3
         Counter32,
      pr1646v2IpV6RtrQMonLastLogBinBin4
         Counter32,
      pr1646v2IpV6RtrQMonLastLogBinBin5
         Counter32,
      pr1646v2IpV6RtrQMonLastLogBinBin6
         Counter32,
      pr1646v2IpV6RtrQMonLastLogBinBin7
         Counter32,
      pr1646v2IpV6RtrQMonLastLogBinMaxBin8
         Counter32,
      pr1646v2IpV6RtrQMonLastLogBinMax
         Integer32,
      pr1646v2IpV6RtrQMonLastLogBinPlusMax
         Counter32
      }

pr1646v2IpV6RtrQMonLastLogBinTableIx OBJECT-TYPE
   SYNTAX      TableIndex
   MAX-ACCESS  not-accessible
   STATUS      current
   DESCRIPTION
      ""
   ::= {pr1646v2IpV6RtrQMonLastLogBinEntry 11}

pr1646v2IpV6RtrQMonLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: v6Router.performance.qualityMonitor.lastLog.bin.name

       Possibilities:
               delay   (1)
               delayUp   (2)
               delayDown   (3)
               jitter   (4)
               jitterUp   (5)
               jitterDown   (6)"
   ::= {pr1646v2IpV6RtrQMonLastLogBinEntry 503316480}

pr1646v2IpV6RtrQMonLastLogBinType OBJECT-TYPE
   SYNTAX      INTEGER
               {
               fd (1),
               fdr (2),
               notInUse (3),
               ifdv (4)
               }
   MAX-ACCESS  read-only
   STATUS      current
   DESCRIPTION
      "Path: v6Router.performance.qualityMonitor.lastLog.bin.type

       Possibilities:
               fd   (1)
               fdr   (2)
               notInUse   (3)
               ifdv   (4)"
   ::= {pr1646v2IpV6RtrQMonLastLogBinEntry 520093696}

pr1646v2IpV6RtrQMonLastLogBinMinMin OBJECT-TYPE
   SYNTAX      Counter32
   MAX-ACCESS  read-only
   STATUS      current
   DESCRIPTION
      "Path: v6Router.performance.qualityMonitor.lastLog.bin.minMin

       32 bit unsigned wrappable counter."
   ::= {pr1646v2IpV6RtrQMonLastLogBinEntry 16777216}

pr1646v2IpV6RtrQMonLastLogBinMin OBJECT-TYPE
   SYNTAX      Integer32
   MAX-ACCESS  read-only
   STATUS      current
   DESCRIPTION
      "Path: v6Router.performance.qualityMonitor.lastLog.bin.min

       unit name = sec
       formula = 1000 / ; 1000 *"
   ::= {pr1646v2IpV6RtrQMonLastLogBinEntry 352321536}

pr1646v2IpV6RtrQMonLastLogBinMinBin1 OBJECT-TYPE
   SYNTAX      Counter32
   MAX-ACCESS  read-only
   STATUS      current
   DESCRIPTION
      "Path: v6Router.performance.qualityMonitor.lastLog.bin.minBin1

       32 bit unsigned wrappable counter."
   ::= {pr1646v2IpV6RtrQMonLastLogBinEntry 33554432}

pr1646v2IpV6RtrQMonLastLogBinBin2 OBJECT-TYPE
   SYNTAX      Counter32
   MAX-ACCESS  read-only
   STATUS      current
   DESCRIPTION
      "Path: v6Router.performance.qualityMonitor.lastLog.bin.bin2

       32 bit unsigned wrappable counter."
   ::= {pr1646v2IpV6RtrQMonLastLogBinEntry 50331648}

pr1646v2IpV6RtrQMonLastLogBinBin3 OBJECT-TYPE
   SYNTAX      Counter32
   MAX-ACCESS  read-only
   STATUS      current
   DESCRIPTION
      "Path: v6Router.performance.qualityMonitor.lastLog.bin.bin3

       32 bit unsigned wrappable counter."
   ::= {pr1646v2IpV6RtrQMonLastLogBinEntry 67108864}

pr1646v2IpV6RtrQMonLastLogBinBin4 OBJECT-TYPE
   SYNTAX      Counter32
   MAX-ACCESS  read-only
   STATUS      current
   DESCRIPTION
      "Path: v6Router.performance.qualityMonitor.lastLog.bin.bin4

       32 bit unsigned wrappable counter."
   ::= {pr1646v2IpV6RtrQMonLastLogBinEntry 83886080}

pr1646v2IpV6RtrQMonLastLogBinBin5 OBJECT-TYPE
   SYNTAX      Counter32
   MAX-ACCESS  read-only
   STATUS      current
   DESCRIPTION
      "Path: v6Router.performance.qualityMonitor.lastLog.bin.bin5

       32 bit unsigned wrappable counter."
   ::= {pr1646v2IpV6RtrQMonLastLogBinEntry 100663296}

pr1646v2IpV6RtrQMonLastLogBinBin6 OBJECT-TYPE
   SYNTAX      Counter32
   MAX-ACCESS  read-only
   STATUS      current
   DESCRIPTION
      "Path: v6Router.performance.qualityMonitor.lastLog.bin.bin6

       32 bit unsigned wrappable counter."
   ::= {pr1646v2IpV6RtrQMonLastLogBinEntry 117440512}

pr1646v2IpV6RtrQMonLastLogBinBin7 OBJECT-TYPE
   SYNTAX      Counter32
   MAX-ACCESS  read-only
   STATUS      current
   DESCRIPTION
      "Path: v6Router.performance.qualityMonitor.lastLog.bin.bin7

       32 bit unsigned wrappable counter."
   ::= {pr1646v2IpV6RtrQMonLastLogBinEntry 134217728}

pr1646v2IpV6RtrQMonLastLogBinMaxBin8 OBJECT-TYPE
   SYNTAX      Counter32
   MAX-ACCESS  read-only
   STATUS      current
   DESCRIPTION
      "Path: v6Router.performance.qualityMonitor.lastLog.bin.maxBin8

       32 bit unsigned wrappable counter."
   ::= {pr1646v2IpV6RtrQMonLastLogBinEntry 150994944}

pr1646v2IpV6RtrQMonLastLogBinMax OBJECT-TYPE
   SYNTAX      Integer32
   MAX-ACCESS  read-only
   STATUS      current
   DESCRIPTION
      "Path: v6Router.performance.qualityMonitor.lastLog.bin.max

       unit name = sec
       formula = 1000 / ; 1000 *"
   ::= {pr1646v2IpV6RtrQMonLastLogBinEntry 369098752}

pr1646v2IpV6RtrQMonLastLogBinPlusMax OBJECT-TYPE
   SYNTAX      Counter32
   MAX-ACCESS  read-only
   STATUS      current
   DESCRIPTION
      "Path: v6Router.performance.qualityMonitor.lastLog.bin.plusMax

       32 bit unsigned wrappable counter."
   ::= {pr1646v2IpV6RtrQMonLastLogBinEntry 167772160}


pr1646v2IpV6RtrUdpServer OBJECT IDENTIFIER ::= {pr1646v2IpV6Rtr 55}

pr1646v2IpV6RtrUdpServerSSCTable OBJECT-TYPE
   SYNTAX      SEQUENCE OF Pr1646v2IpV6RtrUdpServerEntry
   MAX-ACCESS  not-accessible
   STATUS      current
   DESCRIPTION
      "udpServer"
   ::= {pr1646v2IpV6RtrUdpServer 1}

pr1646v2IpV6RtrUdpServerEntry OBJECT-TYPE
   SYNTAX      Pr1646v2IpV6RtrUdpServerEntry
   MAX-ACCESS  not-accessible
   STATUS      current
   DESCRIPTION
      ""
   INDEX      { pr1646v2IpV6RtrUdpServerTableIx }
   ::= {pr1646v2IpV6RtrUdpServerSSCTable 1}

Pr1646v2IpV6RtrUdpServerEntry ::=
   SEQUENCE
      {
      pr1646v2IpV6RtrUdpServerTableIx
         TableIndex,
      pr1646v2IpV6RtrUdpServerDestinationPort
         Integer32,
      pr1646v2IpV6RtrUdpServerActiveSessions
         Gauge32,
      pr1646v2IpV6RtrUdpServerNbrPckt
         Counter64
      }

pr1646v2IpV6RtrUdpServerTableIx OBJECT-TYPE
   SYNTAX      TableIndex
   MAX-ACCESS  not-accessible
   STATUS      current
   DESCRIPTION
      ""
   ::= {pr1646v2IpV6RtrUdpServerEntry 11}

pr1646v2IpV6RtrUdpServerDestinationPort OBJECT-TYPE
   SYNTAX      Integer32
   MAX-ACCESS  read-only
   STATUS      current
   DESCRIPTION
      "Path: v6Router.performance.udpServer.destinationPort"
   ::= {pr1646v2IpV6RtrUdpServerEntry 16777216}

pr1646v2IpV6RtrUdpServerActiveSessions OBJECT-TYPE
   SYNTAX      Gauge32
   MAX-ACCESS  read-only
   STATUS      current
   DESCRIPTION
      "Path: v6Router.performance.udpServer.activeSessions

       32 bit unsigned gauge value."
   ::= {pr1646v2IpV6RtrUdpServerEntry 33554432}

pr1646v2IpV6RtrUdpServerNbrPckt OBJECT-TYPE
   SYNTAX      Counter64
   MAX-ACCESS  read-only
   STATUS      current
   DESCRIPTION
      "Path: v6Router.performance.udpServer.nbrOfPackets

       64 bit unsigned wrappable counter."
   ::= {pr1646v2IpV6RtrUdpServerEntry 50331648}

pr1646v2IpV6RtrUdpServerSessions OBJECT-TYPE
   SYNTAX      SEQUENCE OF Pr1646v2IpV6RtrUdpServerSessionsEntry
   MAX-ACCESS  not-accessible
   STATUS      current
   DESCRIPTION
      ""
   ::= {pr1646v2IpV6RtrUdpServer 67108864}

pr1646v2IpV6RtrUdpServerSessionsEntry OBJECT-TYPE
   SYNTAX      Pr1646v2IpV6RtrUdpServerSessionsEntry
   MAX-ACCESS  not-accessible
   STATUS      current
   DESCRIPTION
      ""
   INDEX      { pr1646v2IpV6RtrUdpServerTableIx,
                pr1646v2IpV6RtrUdpServerSessionsTableIx }
   ::= {pr1646v2IpV6RtrUdpServerSessions 1}

Pr1646v2IpV6RtrUdpServerSessionsEntry ::=
   SEQUENCE
      {
      pr1646v2IpV6RtrUdpServerSessionsTableIx
         TableIndex,
      pr1646v2IpV6RtrUdpServerSessionsSourceIpV6Address
         Ipv6Address,
      pr1646v2IpV6RtrUdpServerSessionsSourcePort
         Integer32,
      pr1646v2IpV6RtrUdpServerSessionsNbrPckt
         Counter64,
      pr1646v2IpV6RtrUdpServerSessionsFirstActivityTime
         TimeTicks,
      pr1646v2IpV6RtrUdpServerSessionsLastActivityTime
         TimeTicks
      }

pr1646v2IpV6RtrUdpServerSessionsTableIx OBJECT-TYPE
   SYNTAX      TableIndex
   MAX-ACCESS  not-accessible
   STATUS      current
   DESCRIPTION
      ""
   ::= {pr1646v2IpV6RtrUdpServerSessionsEntry 11}

pr1646v2IpV6RtrUdpServerSessionsSourceIpV6Address OBJECT-TYPE
   SYNTAX      Ipv6Address
   MAX-ACCESS  read-only
   STATUS      current
   DESCRIPTION
      "Path: v6Router.performance.udpServer.sessions.sourceIpV6Address

       ipv6 address"
   ::= {pr1646v2IpV6RtrUdpServerSessionsEntry 16777216}

pr1646v2IpV6RtrUdpServerSessionsSourcePort OBJECT-TYPE
   SYNTAX      Integer32
   MAX-ACCESS  read-only
   STATUS      current
   DESCRIPTION
      "Path: v6Router.performance.udpServer.sessions.sourcePort"
   ::= {pr1646v2IpV6RtrUdpServerSessionsEntry 33554432}

pr1646v2IpV6RtrUdpServerSessionsNbrPckt OBJECT-TYPE
   SYNTAX      Counter64
   MAX-ACCESS  read-only
   STATUS      current
   DESCRIPTION
      "Path: v6Router.performance.udpServer.sessions.nbrOfPackets

       64 bit unsigned wrappable counter."
   ::= {pr1646v2IpV6RtrUdpServerSessionsEntry 50331648}

pr1646v2IpV6RtrUdpServerSessionsFirstActivityTime OBJECT-TYPE
   SYNTAX      TimeTicks
   MAX-ACCESS  read-only
   STATUS      current
   DESCRIPTION
      "Path: v6Router.performance.udpServer.sessions.firstActivityTime

       Time in centi-second."
   ::= {pr1646v2IpV6RtrUdpServerSessionsEntry 67108864}

pr1646v2IpV6RtrUdpServerSessionsLastActivityTime OBJECT-TYPE
   SYNTAX      TimeTicks
   MAX-ACCESS  read-only
   STATUS      current
   DESCRIPTION
      "Path: v6Router.performance.udpServer.sessions.lastActivityTime

       Time in centi-second."
   ::= {pr1646v2IpV6RtrUdpServerSessionsEntry 83886080}


pr1646v2IpV6RtrPingResults OBJECT IDENTIFIER ::= {pr1646v2IpV6Rtr 54}

pr1646v2IpV6RtrPingResultsSSC OBJECT IDENTIFIER ::= {pr1646v2IpV6RtrPingResults 1}

pr1646v2IpV6RtrPingResultsEntry OBJECT IDENTIFIER ::= {pr1646v2IpV6RtrPingResultsSSC 1}

pr1646v2IpV6RtrPingResultsIpAddr OBJECT-TYPE
   SYNTAX      Ipv6Address
   MAX-ACCESS  read-only
   STATUS      current
   DESCRIPTION
      "Path: v6Router.performance.pingResults.ipV6Address

       ipv6 address"
   ::= {pr1646v2IpV6RtrPingResultsEntry 16777216}

pr1646v2IpV6RtrPingResultsNbrTxPckt OBJECT-TYPE
   SYNTAX      Counter32
   MAX-ACCESS  read-only
   STATUS      current
   DESCRIPTION
      "Path: v6Router.performance.pingResults.nbrOfTxPackets

       32 bit unsigned wrappable counter."
   ::= {pr1646v2IpV6RtrPingResultsEntry 33554432}

pr1646v2IpV6RtrPingResultsNbrRxPckt OBJECT-TYPE
   SYNTAX      Counter32
   MAX-ACCESS  read-only
   STATUS      current
   DESCRIPTION
      "Path: v6Router.performance.pingResults.nbrOfRxPackets

       32 bit unsigned wrappable counter."
   ::= {pr1646v2IpV6RtrPingResultsEntry 50331648}

pr1646v2IpV6RtrPingResultsRepTimMin OBJECT-TYPE
   SYNTAX      TimeTicks
   MAX-ACCESS  read-only
   STATUS      current
   DESCRIPTION
      "Path: v6Router.performance.pingResults.replyTimeMin

       Time in centi-second."
   ::= {pr1646v2IpV6RtrPingResultsEntry 67108864}

pr1646v2IpV6RtrPingResultsRepTimMax OBJECT-TYPE
   SYNTAX      TimeTicks
   MAX-ACCESS  read-only
   STATUS      current
   DESCRIPTION
      "Path: v6Router.performance.pingResults.replyTimeMax

       Time in centi-second."
   ::= {pr1646v2IpV6RtrPingResultsEntry 83886080}

pr1646v2IpV6RtrPingResultsRepTimAvrg OBJECT-TYPE
   SYNTAX      TimeTicks
   MAX-ACCESS  read-only
   STATUS      current
   DESCRIPTION
      "Path: v6Router.performance.pingResults.replyTimeAvrg

       Time in centi-second."
   ::= {pr1646v2IpV6RtrPingResultsEntry 100663296}

pr1646v2IpV6RtrPingResultsLastError OBJECT-TYPE
   SYNTAX      DisplayString
   MAX-ACCESS  read-only
   STATUS      current
   DESCRIPTION
      "Path: v6Router.performance.pingResults.lastError"
   ::= {pr1646v2IpV6RtrPingResultsEntry 117440512}



fr1646v2IpV6Rtr OBJECT IDENTIFIER ::= {r1646v2IpV6Rtr 13}


fr1646v2IpV6RtrAlarm OBJECT IDENTIFIER ::= {fr1646v2IpV6Rtr 202}

fr1646v2IpV6RtrAlarmSSC OBJECT IDENTIFIER ::= {fr1646v2IpV6RtrAlarm 1}

fr1646v2IpV6RtrAlarmEntry OBJECT IDENTIFIER ::= {fr1646v2IpV6RtrAlarmSSC 1}

fr1646v2IpV6RtrAlarmDiscriminator OBJECT-TYPE
   SYNTAX      Integer32
   MAX-ACCESS  read-only
   STATUS      current
   DESCRIPTION
      "Path: v6Router.alarms.alarmInfo.discriminator"
   ::= {fr1646v2IpV6RtrAlarmEntry 16777216}

fr1646v2IpV6RtrAlarmCurrent OBJECT-TYPE
   SYNTAX      Integer32
   MAX-ACCESS  read-only
   STATUS      current
   DESCRIPTION
      "Path: v6Router.alarms.alarmInfo.currentAlarms

       Bit meanings:
               bit 0 = pingActive,
               bit 1 = qMonLoss,
               bit 2 = qMonDelay,
               bit 3 = qMonJitter"
   ::= {fr1646v2IpV6RtrAlarmEntry 33554432}

fr1646v2IpV6RtrAlarmPrevious OBJECT-TYPE
   SYNTAX      Integer32
   MAX-ACCESS  read-only
   STATUS      current
   DESCRIPTION
      "Path: v6Router.alarms.alarmInfo.previousAlarms

       Bit meanings:
               bit 0 = pingActive,
               bit 1 = qMonLoss,
               bit 2 = qMonDelay,
               bit 3 = qMonJitter"
   ::= {fr1646v2IpV6RtrAlarmEntry 50331648}

fr1646v2IpV6RtrAlarmMask OBJECT-TYPE
   SYNTAX      Integer32
   MAX-ACCESS  read-only
   STATUS      current
   DESCRIPTION
      "Path: v6Router.alarms.alarmInfo.alarmMask

       Bit meanings:
               bit 0 = pingActive,
               bit 1 = qMonLoss,
               bit 2 = qMonDelay,
               bit 3 = qMonJitter"
   ::= {fr1646v2IpV6RtrAlarmEntry 67108864}

fr1646v2IpV6RtrAlarmLevPingActive OBJECT-TYPE
   SYNTAX      Integer32
   MAX-ACCESS  read-only
   STATUS      current
   DESCRIPTION
      "Path: v6Router.alarms.alarmInfo.alarmLevel.pingActive"
   ::= {fr1646v2IpV6RtrAlarmEntry 83951616}

fr1646v2IpV6RtrAlarmLevQMonLoss OBJECT-TYPE
   SYNTAX      Integer32
   MAX-ACCESS  read-only
   STATUS      current
   DESCRIPTION
      "Path: v6Router.alarms.alarmInfo.alarmLevel.qMonLoss"
   ::= {fr1646v2IpV6RtrAlarmEntry 84017152}

fr1646v2IpV6RtrAlarmLevQMonDelay OBJECT-TYPE
   SYNTAX      Integer32
   MAX-ACCESS  read-only
   STATUS      current
   DESCRIPTION
      "Path: v6Router.alarms.alarmInfo.alarmLevel.qMonDelay"
   ::= {fr1646v2IpV6RtrAlarmEntry 84082688}

fr1646v2IpV6RtrAlarmLevQMonJitter OBJECT-TYPE
   SYNTAX      Integer32
   MAX-ACCESS  read-only
   STATUS      current
   DESCRIPTION
      "Path: v6Router.alarms.alarmInfo.alarmLevel.qMonJitter"
   ::= {fr1646v2IpV6RtrAlarmEntry 84148224}


fr1646v2IpV6RtrAlarmE2 OBJECT IDENTIFIER ::= {fr1646v2IpV6RtrAlarm 2}

fr1646v2IpV6RtrAlarmE2Entry OBJECT IDENTIFIER ::= {fr1646v2IpV6RtrAlarmE2 1}

fr1646v2IpV6RtrAlarmE2PingActive OBJECT IDENTIFIER ::= {fr1646v2IpV6RtrAlarmE2Entry 10}

fr1646v2IpV6RtrAlarmE2PingActivePfx OBJECT IDENTIFIER ::= {fr1646v2IpV6RtrAlarmE2PingActive 0}

fr1646v2IpV6RtrAlarmE2PingActiveOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'ipV6Router'
                (root='router1646') has changed from the ON to the OFF state."
   ::= {fr1646v2IpV6RtrAlarmE2PingActivePfx 1}

fr1646v2IpV6RtrAlarmE2PingActiveOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'ipV6Router'
                (root='router1646') has changed from the OFF to the ON state."
   ::= {fr1646v2IpV6RtrAlarmE2PingActivePfx 2}

fr1646v2IpV6RtrAlarmE2QMonLoss OBJECT IDENTIFIER ::= {fr1646v2IpV6RtrAlarmE2Entry 11}

fr1646v2IpV6RtrAlarmE2QMonLossPfx OBJECT IDENTIFIER ::= {fr1646v2IpV6RtrAlarmE2QMonLoss 0}

fr1646v2IpV6RtrAlarmE2QMonLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'ipV6Router'
                (root='router1646') has changed from the ON to the OFF state."
   ::= {fr1646v2IpV6RtrAlarmE2QMonLossPfx 1}

fr1646v2IpV6RtrAlarmE2QMonLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'ipV6Router'
                (root='router1646') has changed from the OFF to the ON state."
   ::= {fr1646v2IpV6RtrAlarmE2QMonLossPfx 2}

fr1646v2IpV6RtrAlarmE2QMonDelay OBJECT IDENTIFIER ::= {fr1646v2IpV6RtrAlarmE2Entry 12}

fr1646v2IpV6RtrAlarmE2QMonDelayPfx OBJECT IDENTIFIER ::= {fr1646v2IpV6RtrAlarmE2QMonDelay 0}

fr1646v2IpV6RtrAlarmE2QMonDelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'ipV6Router'
                (root='router1646') has changed from the ON to the OFF state."
   ::= {fr1646v2IpV6RtrAlarmE2QMonDelayPfx 1}

fr1646v2IpV6RtrAlarmE2QMonDelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'ipV6Router'
                (root='router1646') has changed from the OFF to the ON state."
   ::= {fr1646v2IpV6RtrAlarmE2QMonDelayPfx 2}

fr1646v2IpV6RtrAlarmE2QMonJitter OBJECT IDENTIFIER ::= {fr1646v2IpV6RtrAlarmE2Entry 13}

fr1646v2IpV6RtrAlarmE2QMonJitterPfx OBJECT IDENTIFIER ::= {fr1646v2IpV6RtrAlarmE2QMonJitter 0}

fr1646v2IpV6RtrAlarmE2QMonJitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'ipV6Router'
                (root='router1646') has changed from the ON to the OFF state."
   ::= {fr1646v2IpV6RtrAlarmE2QMonJitterPfx 1}

fr1646v2IpV6RtrAlarmE2QMonJitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'ipV6Router'
                (root='router1646') has changed from the OFF to the ON state."
   ::= {fr1646v2IpV6RtrAlarmE2QMonJitterPfx 2}



ar1646v2IpV6Rtr OBJECT IDENTIFIER ::= {r1646v2IpV6Rtr 16}


ar1646v2IpV6RtrQmOnDemand OBJECT-TYPE
   SYNTAX      Integer32
   MAX-ACCESS  read-write
   STATUS      current
   DESCRIPTION
      "Path: v6Router.actions.qmOnDemand
       Info: start sending pings"
   ::= {ar1646v2IpV6Rtr 8043}


ar1646v2IpV6RtrAction OBJECT IDENTIFIER ::= {ar1646v2IpV6Rtr 8044}

ar1646v2IpV6RtrActionSSC OBJECT IDENTIFIER ::= {ar1646v2IpV6RtrAction 1}

ar1646v2IpV6RtrActionEntry OBJECT IDENTIFIER ::= {ar1646v2IpV6RtrActionSSC 1}

ar1646v2IpV6RtrActionAction OBJECT-TYPE
   SYNTAX      INTEGER
               {
               restart (1),
               restartLossWindow (2),
               stop (3),
               stopAndClear (4)
               }
   MAX-ACCESS  read-write
   STATUS      current
   DESCRIPTION
      "Path: v6Router.actions.action.action

       Possibilities:
               restart   (1)
               restartLossWindow   (2)
               stop   (3)
               stopAndClear   (4)"
   ::= {ar1646v2IpV6RtrActionEntry 16777216}

ar1646v2IpV6RtrActionName OBJECT-TYPE
   SYNTAX      DisplayString
   MAX-ACCESS  read-write
   STATUS      current
   DESCRIPTION
      "Path: v6Router.actions.action.name"
   ::= {ar1646v2IpV6RtrActionEntry 33554432}


ar1646v2IpV6RtrStopPing OBJECT-TYPE
   SYNTAX      Integer32
   MAX-ACCESS  read-write
   STATUS      current
   DESCRIPTION
      "Path: v6Router.actions.stopPing
       Info: stop sending pings"
   ::= {ar1646v2IpV6Rtr 115}


ar1646v2IpV6RtrStartPing OBJECT-TYPE
   SYNTAX      Integer32
   MAX-ACCESS  read-write
   STATUS      current
   DESCRIPTION
      "Path: v6Router.actions.startPing
       Info: start sending pings"
   ::= {ar1646v2IpV6Rtr 113}


ar1646v2IpV6RtrPingData OBJECT IDENTIFIER ::= {ar1646v2IpV6Rtr 114}

ar1646v2IpV6RtrPingDataSSC OBJECT IDENTIFIER ::= {ar1646v2IpV6RtrPingData 1}

ar1646v2IpV6RtrPingDataEntry OBJECT IDENTIFIER ::= {ar1646v2IpV6RtrPingDataSSC 1}

ar1646v2IpV6RtrPingDataIpV6Address OBJECT-TYPE
   SYNTAX      Ipv6Address
   MAX-ACCESS  read-write
   STATUS      current
   DESCRIPTION
      "Path: v6Router.actions.pingData.ipV6Address

       ipv6 address"
   ::= {ar1646v2IpV6RtrPingDataEntry 16777216}

ar1646v2IpV6RtrPingDataHostName OBJECT-TYPE
   SYNTAX      DisplayString
   MAX-ACCESS  read-write
   STATUS      current
   DESCRIPTION
      "Path: v6Router.actions.pingData.hostName"
   ::= {ar1646v2IpV6RtrPingDataEntry 100663296}

ar1646v2IpV6RtrPingDataSourceIpV6 OBJECT-TYPE
   SYNTAX      Ipv6Address
   MAX-ACCESS  read-write
   STATUS      current
   DESCRIPTION
      "Path: v6Router.actions.pingData.sourceIpV6

       ipv6 address"
   ::= {ar1646v2IpV6RtrPingDataEntry 117440512}

ar1646v2IpV6RtrPingDataTrafficClass OBJECT-TYPE
   SYNTAX      Integer32
   MAX-ACCESS  read-write
   STATUS      current
   DESCRIPTION
      "Path: v6Router.actions.pingData.trafficClass"
   ::= {ar1646v2IpV6RtrPingDataEntry 134217728}

ar1646v2IpV6RtrPingDataFragment OBJECT-TYPE
   SYNTAX      INTEGER
               {
               yes (1),
               no (2)
               }
   MAX-ACCESS  read-write
   STATUS      current
   DESCRIPTION
      "Path: v6Router.actions.pingData.fragment

       Possibilities:
               yes   (1)
               no   (2)"
   ::= {ar1646v2IpV6RtrPingDataEntry 150994944}

ar1646v2IpV6RtrPingDataTtl OBJECT-TYPE
   SYNTAX      Integer32
   MAX-ACCESS  read-write
   STATUS      current
   DESCRIPTION
      "Path: v6Router.actions.pingData.ttl"
   ::= {ar1646v2IpV6RtrPingDataEntry 167772160}

ar1646v2IpV6RtrPingDataIterations OBJECT-TYPE
   SYNTAX      INTEGER
               {
               unlimited (0)
               }
   MAX-ACCESS  read-write
   STATUS      current
   DESCRIPTION
      "Path: v6Router.actions.pingData.iterations

       Possibilities:
               unlimited   (0)"
   ::= {ar1646v2IpV6RtrPingDataEntry 33554432}

ar1646v2IpV6RtrPingDataInterval OBJECT-TYPE
   SYNTAX      Integer32
   MAX-ACCESS  read-write
   STATUS      current
   DESCRIPTION
      "Path: v6Router.actions.pingData.interval"
   ::= {ar1646v2IpV6RtrPingDataEntry 50331648}

ar1646v2IpV6RtrPingDataDataLength OBJECT-TYPE
   SYNTAX      Integer32
   MAX-ACCESS  read-write
   STATUS      current
   DESCRIPTION
      "Path: v6Router.actions.pingData.dataLength"
   ::= {ar1646v2IpV6RtrPingDataEntry 67108864}

ar1646v2IpV6RtrPingDataTimeOut OBJECT-TYPE
   SYNTAX      TimeTicks
   MAX-ACCESS  read-write
   STATUS      current
   DESCRIPTION
      "Path: v6Router.actions.pingData.timeOut

       Time in centi-second."
   ::= {ar1646v2IpV6RtrPingDataEntry 83886080}


ar1646v2IpV6RtrClearCounters OBJECT-TYPE
   SYNTAX      Integer32
   MAX-ACCESS  read-write
   STATUS      current
   DESCRIPTION
      "Path: v6Router.actions.clearCounters
       Info: reset counters"
   ::= {ar1646v2IpV6Rtr 263}


ar1646v2IpV6RtrRequestDnsByAddress OBJECT-TYPE
   SYNTAX      Integer32
   MAX-ACCESS  read-write
   STATUS      current
   DESCRIPTION
      "Path: v6Router.actions.requestDnsByAddress
       Info: do a DNS request"
   ::= {ar1646v2IpV6Rtr 103}


ar1646v2IpV6RtrHostAddress OBJECT-TYPE
   SYNTAX      Ipv6Address
   MAX-ACCESS  read-write
   STATUS      current
   DESCRIPTION
      "Path: v6Router.actions.hostAddress
       Info: address of the host

       ipv6 address"
   ::= {ar1646v2IpV6Rtr 104}


ar1646v2IpV6RtrRequestDnsByName OBJECT-TYPE
   SYNTAX      Integer32
   MAX-ACCESS  read-write
   STATUS      current
   DESCRIPTION
      "Path: v6Router.actions.requestDnsByName
       Info: do a DNS request"
   ::= {ar1646v2IpV6Rtr 101}


ar1646v2IpV6RtrHostName OBJECT-TYPE
   SYNTAX      DisplayString
   MAX-ACCESS  read-write
   STATUS      current
   DESCRIPTION
      "Path: v6Router.actions.hostName
       Info: name of the host"
   ::= {ar1646v2IpV6Rtr 102}


ar1646v2IpV6RtrClearDnsCache OBJECT-TYPE
   SYNTAX      Integer32
   MAX-ACCESS  read-write
   STATUS      current
   DESCRIPTION
      "Path: v6Router.actions.clearDnsCache
       Info: clear the DNS cache table"
   ::= {ar1646v2IpV6Rtr 155}



END
