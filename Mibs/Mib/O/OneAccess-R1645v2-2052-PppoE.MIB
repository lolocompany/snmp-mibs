OneAccess-R1645v2-2052-PppoE DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PppoE OBJECT IDENTIFIER ::= {r1645Rootv2 2052}

r1645v2PppoEMOProp OBJECT IDENTIFIER ::= {r1645v2PppoE 1}

r1645v2PppoEMOPropEntry OBJECT IDENTIFIER ::= {r1645v2PppoEMOProp 1}

r1645v2PppoEMOPropPath OBJECT-TYPE
   SYNTAX      ContainmentPath
   MAX-ACCESS  read-only
   STATUS      current
   DESCRIPTION
      "Textual description of the containment tree from the instance of
       the root object down to the instance of the current object."
   ::= {r1645v2PppoEMOPropEntry 3}

r1645v2PppoEMOPropRev OBJECT-TYPE
   SYNTAX      ObjectRevision
   MAX-ACCESS  read-only
   STATUS      current
   DESCRIPTION
      "This value corresponds with the revision of the MANAGED OBJECT."
   ::= {r1645v2PppoEMOPropEntry 4}



er1645v2PppoE OBJECT IDENTIFIER ::= {r1645v2PppoE 11}


er1645v2PppoEMode OBJECT IDENTIFIER ::= {er1645v2PppoE 2}

er1645v2PppoEModeSSC OBJECT IDENTIFIER ::= {er1645v2PppoEMode 1}

er1645v2PppoEModeEntry OBJECT IDENTIFIER ::= {er1645v2PppoEModeSSC 1}

er1645v2PppoEModeRouting OBJECT-TYPE
   SYNTAX      DisplayString
   MAX-ACCESS  read-write
   STATUS      current
   DESCRIPTION
      "Path: server.editConf.mode.routing"
   ::= {er1645v2PppoEModeEntry 33554432}

er1645v2PppoEModeMultiLink OBJECT-TYPE
   SYNTAX      DisplayString
   MAX-ACCESS  read-write
   STATUS      current
   DESCRIPTION
      "Path: server.editConf.mode.multiLink"
   ::= {er1645v2PppoEModeEntry 100663296}

er1645v2PppoEModeIpV6 OBJECT-TYPE
   SYNTAX      DisplayString
   MAX-ACCESS  read-write
   STATUS      current
   DESCRIPTION
      "Path: server.editConf.mode.ipV6"
   ::= {er1645v2PppoEModeEntry 150994944}

er1645v2PppoEModeIpV6ipV4 OBJECT-TYPE
   SYNTAX      DisplayString
   MAX-ACCESS  read-write
   STATUS      current
   DESCRIPTION
      "Path: server.editConf.mode.ipV6/ipV4"
   ::= {er1645v2PppoEModeEntry 167772160}


er1645v2PppoEIpV6 OBJECT IDENTIFIER ::= {er1645v2PppoE 10}

er1645v2PppoEIpV6SSC OBJECT IDENTIFIER ::= {er1645v2PppoEIpV6 1}

er1645v2PppoEIpV6Entry OBJECT IDENTIFIER ::= {er1645v2PppoEIpV6SSC 1}

er1645v2PppoEIpV6VrfRouter OBJECT-TYPE
   SYNTAX      DisplayString
   MAX-ACCESS  read-write
   STATUS      current
   DESCRIPTION
      "Path: server.editConf.ipV6.vrfRouter"
   ::= {er1645v2PppoEIpV6Entry 16777216}

er1645v2PppoEIpV6AddrAutoConfigNrDupAddrDetects OBJECT-TYPE
   SYNTAX      Integer32
   MAX-ACCESS  read-write
   STATUS      current
   DESCRIPTION
      "Path: server.editConf.ipV6.addrAutoConfig.nrDupAddrDetects"
   ::= {er1645v2PppoEIpV6Entry 67174400}

er1645v2PppoEIpV6AddrAutoConfigAcceptRa OBJECT-TYPE
   SYNTAX      INTEGER
               {
               disabled (0),
               enabled (1)
               }
   MAX-ACCESS  read-write
   STATUS      current
   DESCRIPTION
      "Path: server.editConf.ipV6.addrAutoConfig.acceptRa

       Possibilities:
               disabled   (0)
               enabled   (1)"
   ::= {er1645v2PppoEIpV6Entry 67239936}

er1645v2PppoEIpV6AddrAutoConfigAcceptRaRdnss OBJECT-TYPE
   SYNTAX      INTEGER
               {
               disabled (0),
               enabled (1)
               }
   MAX-ACCESS  read-write
   STATUS      current
   DESCRIPTION
      "Path: server.editConf.ipV6.addrAutoConfig.acceptRaRdnss

       Possibilities:
               disabled   (0)
               enabled   (1)"
   ::= {er1645v2PppoEIpV6Entry 67305472}

er1645v2PppoEIpV6AddrAutoConfigAcceptRaDnssl OBJECT-TYPE
   SYNTAX      INTEGER
               {
               disabled (0),
               enabled (1)
               }
   MAX-ACCESS  read-write
   STATUS      current
   DESCRIPTION
      "Path: server.editConf.ipV6.addrAutoConfig.acceptRaDnssl

       Possibilities:
               disabled   (0)
               enabled   (1)"
   ::= {er1645v2PppoEIpV6Entry 67371008}

er1645v2PppoEIpV6DefaultRoute OBJECT-TYPE
   SYNTAX      INTEGER
               {
               disabled (0),
               enabled (1)
               }
   MAX-ACCESS  read-write
   STATUS      current
   DESCRIPTION
      "Path: server.editConf.ipV6.defaultRoute

       Possibilities:
               disabled   (0)
               enabled   (1)"
   ::= {er1645v2PppoEIpV6Entry 83886080}

er1645v2PppoEIpV6RaSend OBJECT-TYPE
   SYNTAX      INTEGER
               {
               disabled (0),
               enabled (1)
               }
   MAX-ACCESS  read-write
   STATUS      current
   DESCRIPTION
      "Path: server.editConf.ipV6.ra.send

       Possibilities:
               disabled   (0)
               enabled   (1)"
   ::= {er1645v2PppoEIpV6Entry 100728832}

er1645v2PppoEIpV6RaMinInterval OBJECT-TYPE
   SYNTAX      TimeTicks
   MAX-ACCESS  read-write
   STATUS      current
   DESCRIPTION
      "Path: server.editConf.ipV6.ra.minInterval

       Time in centi-second."
   ::= {er1645v2PppoEIpV6Entry 100794368}

er1645v2PppoEIpV6RaMaxInterval OBJECT-TYPE
   SYNTAX      TimeTicks
   MAX-ACCESS  read-write
   STATUS      current
   DESCRIPTION
      "Path: server.editConf.ipV6.ra.maxInterval

       Time in centi-second."
   ::= {er1645v2PppoEIpV6Entry 100859904}

er1645v2PppoEIpV6RaManagedFlag OBJECT-TYPE
   SYNTAX      INTEGER
               {
               disabled (0),
               enabled (1)
               }
   MAX-ACCESS  read-write
   STATUS      current
   DESCRIPTION
      "Path: server.editConf.ipV6.ra.managedFlag

       Possibilities:
               disabled   (0)
               enabled   (1)"
   ::= {er1645v2PppoEIpV6Entry 100925440}

er1645v2PppoEIpV6RaOtherConfFlag OBJECT-TYPE
   SYNTAX      INTEGER
               {
               disabled (0),
               enabled (1)
               }
   MAX-ACCESS  read-write
   STATUS      current
   DESCRIPTION
      "Path: server.editConf.ipV6.ra.otherConfFlag

       Possibilities:
               disabled   (0)
               enabled   (1)"
   ::= {er1645v2PppoEIpV6Entry 100990976}

er1645v2PppoEIpV6RaLinkMtu OBJECT-TYPE
   SYNTAX      Integer32
   MAX-ACCESS  read-write
   STATUS      current
   DESCRIPTION
      "Path: server.editConf.ipV6.ra.linkMtu"
   ::= {er1645v2PppoEIpV6Entry 101056512}

er1645v2PppoEIpV6RaReachableTime OBJECT-TYPE
   SYNTAX      TimeTicks
   MAX-ACCESS  read-write
   STATUS      current
   DESCRIPTION
      "Path: server.editConf.ipV6.ra.reachableTime

       Time in centi-second."
   ::= {er1645v2PppoEIpV6Entry 101122048}

er1645v2PppoEIpV6RaRetransmitTime OBJECT-TYPE
   SYNTAX      TimeTicks
   MAX-ACCESS  read-write
   STATUS      current
   DESCRIPTION
      "Path: server.editConf.ipV6.ra.retransmitTime

       Time in centi-second."
   ::= {er1645v2PppoEIpV6Entry 101187584}

er1645v2PppoEIpV6RaHopLimit OBJECT-TYPE
   SYNTAX      Integer32
   MAX-ACCESS  read-write
   STATUS      current
   DESCRIPTION
      "Path: server.editConf.ipV6.ra.hopLimit"
   ::= {er1645v2PppoEIpV6Entry 101253120}

er1645v2PppoEIpV6RaDefaultLifeTime OBJECT-TYPE
   SYNTAX      TimeTicks
   MAX-ACCESS  read-write
   STATUS      current
   DESCRIPTION
      "Path: server.editConf.ipV6.ra.defaultLifeTime

       Time in centi-second."
   ::= {er1645v2PppoEIpV6Entry 101318656}

er1645v2PppoEIpV6RaDnsOptionsRdnssLifeTime OBJECT-TYPE
   SYNTAX      TimeTicks
   MAX-ACCESS  read-write
   STATUS      current
   DESCRIPTION
      "Path: server.editConf.ipV6.ra.dnsOptions.rdnss.lifeTime

       Time in centi-second."
   ::= {er1645v2PppoEIpV6Entry 101393408}

er1645v2PppoEIpV6RaDnsOptionsRdnssImportServers OBJECT-TYPE
   SYNTAX      INTEGER
               {
               disabled (0),
               enabled (1)
               }
   MAX-ACCESS  read-write
   STATUS      current
   DESCRIPTION
      "Path: server.editConf.ipV6.ra.dnsOptions.rdnss.importServers

       Possibilities:
               disabled   (0)
               enabled   (1)"
   ::= {er1645v2PppoEIpV6Entry 101395456}

er1645v2PppoEIpV6RaDnsOptionsDnsslLifeTime OBJECT-TYPE
   SYNTAX      TimeTicks
   MAX-ACCESS  read-write
   STATUS      current
   DESCRIPTION
      "Path: server.editConf.ipV6.ra.dnsOptions.dnssl.lifeTime

       Time in centi-second."
   ::= {er1645v2PppoEIpV6Entry 101401600}

er1645v2PppoEIpV6RaDnsOptionsDnsslImportDomains OBJECT-TYPE
   SYNTAX      INTEGER
               {
               disabled (0),
               enabled (1)
               }
   MAX-ACCESS  read-write
   STATUS      current
   DESCRIPTION
      "Path: server.editConf.ipV6.ra.dnsOptions.dnssl.importDomains

       Possibilities:
               disabled   (0)
               enabled   (1)"
   ::= {er1645v2PppoEIpV6Entry 101403648}

er1645v2PppoEIpV6RsSend OBJECT-TYPE
   SYNTAX      INTEGER
               {
               disabled (0),
               enabled (1)
               }
   MAX-ACCESS  read-write
   STATUS      current
   DESCRIPTION
      "Path: server.editConf.ipV6.rs.send

       Possibilities:
               disabled   (0)
               enabled   (1)"
   ::= {er1645v2PppoEIpV6Entry 335609856}

er1645v2PppoEIpV6RsMaxRandomDelay OBJECT-TYPE
   SYNTAX      TimeTicks
   MAX-ACCESS  read-write
   STATUS      current
   DESCRIPTION
      "Path: server.editConf.ipV6.rs.maxRandomDelay

       Time in centi-second."
   ::= {er1645v2PppoEIpV6Entry 335675392}

er1645v2PppoEIpV6RsInterval OBJECT-TYPE
   SYNTAX      TimeTicks
   MAX-ACCESS  read-write
   STATUS      current
   DESCRIPTION
      "Path: server.editConf.ipV6.rs.interval

       Time in centi-second."
   ::= {er1645v2PppoEIpV6Entry 335740928}

er1645v2PppoEIpV6RsMaxSolicitations OBJECT-TYPE
   SYNTAX      Integer32
   MAX-ACCESS  read-write
   STATUS      current
   DESCRIPTION
      "Path: server.editConf.ipV6.rs.maxSolicitations"
   ::= {er1645v2PppoEIpV6Entry 335806464}

er1645v2PppoEIpV6TrafficPolicyInbound OBJECT-TYPE
   SYNTAX      DisplayString
   MAX-ACCESS  read-write
   STATUS      current
   DESCRIPTION
      "Path: server.editConf.ipV6.trafficPolicy.inbound"
   ::= {er1645v2PppoEIpV6Entry 184614912}

er1645v2PppoEIpV6TrafficPolicyOutbound OBJECT-TYPE
   SYNTAX      DisplayString
   MAX-ACCESS  read-write
   STATUS      current
   DESCRIPTION
      "Path: server.editConf.ipV6.trafficPolicy.outbound"
   ::= {er1645v2PppoEIpV6Entry 184680448}

er1645v2PppoEIpV6FirewallZone OBJECT-TYPE
   SYNTAX      DisplayString
   MAX-ACCESS  read-write
   STATUS      current
   DESCRIPTION
      "Path: server.editConf.ipV6.firewall.zone"
   ::= {er1645v2PppoEIpV6Entry 201392128}

er1645v2PppoEIpV6DhcpClientAddrAC OBJECT-TYPE
   SYNTAX      INTEGER
               {
               disabled (0),
               enabled (1)
               }
   MAX-ACCESS  read-write
   STATUS      current
   DESCRIPTION
      "Path: server.editConf.ipV6.dhcp.client.addrAutoConfig

       Possibilities:
               disabled   (0)
               enabled   (1)"
   ::= {er1645v2PppoEIpV6Entry 170131456}

er1645v2PppoEIpV6DhcpClientPrDelMode OBJECT-TYPE
   SYNTAX      INTEGER
               {
               disabled (0),
               enabled (1)
               }
   MAX-ACCESS  read-write
   STATUS      current
   DESCRIPTION
      "Path: server.editConf.ipV6.dhcp.client.pd.mode

       Possibilities:
               disabled   (0)
               enabled   (1)"
   ::= {er1645v2PppoEIpV6Entry 170394624}

er1645v2PppoEIpV6DhcpClientPrDelPool OBJECT-TYPE
   SYNTAX      DisplayString
   MAX-ACCESS  read-write
   STATUS      current
   DESCRIPTION
      "Path: server.editConf.ipV6.dhcp.client.pd.pool"
   ::= {er1645v2PppoEIpV6Entry 170395648}

er1645v2PppoEIpV6DhcpClientPrDelPdExclOpt OBJECT-TYPE
   SYNTAX      INTEGER
               {
               disabled (0),
               enabled (1)
               }
   MAX-ACCESS  read-write
   STATUS      current
   DESCRIPTION
      "Path: server.editConf.ipV6.dhcp.client.pd.pdExclOpt

       Possibilities:
               disabled   (0)
               enabled   (1)"
   ::= {er1645v2PppoEIpV6Entry 170396672}

er1645v2PppoEIpV6DhcpClientDnsServerPref OBJECT-TYPE
   SYNTAX      Integer32
   MAX-ACCESS  read-write
   STATUS      current
   DESCRIPTION
      "Path: server.editConf.ipV6.dhcp.client.dns.serverPref"
   ::= {er1645v2PppoEIpV6Entry 170918912}

er1645v2PppoEIpV6DhcpClientRapidCommit OBJECT-TYPE
   SYNTAX      INTEGER
               {
               disabled (0),
               enabled (1)
               }
   MAX-ACCESS  read-write
   STATUS      current
   DESCRIPTION
      "Path: server.editConf.ipV6.dhcp.client.rapidCommit

       Possibilities:
               disabled   (0)
               enabled   (1)"
   ::= {er1645v2PppoEIpV6Entry 170655744}

er1645v2PppoEIpV6DhcpClientTimersSolTimeOut OBJECT-TYPE
   SYNTAX      TimeTicks
   MAX-ACCESS  read-write
   STATUS      current
   DESCRIPTION
      "Path: server.editConf.ipV6.dhcp.client.timers.solTimeOut

       Time in centi-second."
   ::= {er1645v2PppoEIpV6Entry 171181056}

er1645v2PppoEIpV6DhcpClientTimersSolMaxRt OBJECT-TYPE
   SYNTAX      TimeTicks
   MAX-ACCESS  read-write
   STATUS      current
   DESCRIPTION
      "Path: server.editConf.ipV6.dhcp.client.timers.solMaxRt

       Time in centi-second."
   ::= {er1645v2PppoEIpV6Entry 171182080}

er1645v2PppoEIpV6DhcpClientTimersInfoRefresh OBJECT-TYPE
   SYNTAX      TimeTicks
   MAX-ACCESS  read-write
   STATUS      current
   DESCRIPTION
      "Path: server.editConf.ipV6.dhcp.client.timers.infoRefresh

       Time in centi-second."
   ::= {er1645v2PppoEIpV6Entry 171183104}

er1645v2PppoEIpV6DhcpServerMode OBJECT-TYPE
   SYNTAX      INTEGER
               {
               disabled (0),
               enabled (1)
               }
   MAX-ACCESS  read-write
   STATUS      current
   DESCRIPTION
      "Path: server.editConf.ipV6.dhcp.server.mode

       Possibilities:
               disabled   (0)
               enabled   (1)"
   ::= {er1645v2PppoEIpV6Entry 172228608}

er1645v2PppoEIpV6DhcpServerPreference OBJECT-TYPE
   SYNTAX      Integer32
   MAX-ACCESS  read-write
   STATUS      current
   DESCRIPTION
      "Path: server.editConf.ipV6.dhcp.server.preference"
   ::= {er1645v2PppoEIpV6Entry 172490752}

er1645v2PppoEIpV6DhcpServerPool OBJECT-TYPE
   SYNTAX      DisplayString
   MAX-ACCESS  read-write
   STATUS      current
   DESCRIPTION
      "Path: server.editConf.ipV6.dhcp.server.pool"
   ::= {er1645v2PppoEIpV6Entry 172752896}

er1645v2PppoEIpV6DhcpServerRapidCommit OBJECT-TYPE
   SYNTAX      INTEGER
               {
               disabled (0),
               enabled (1)
               }
   MAX-ACCESS  read-write
   STATUS      current
   DESCRIPTION
      "Path: server.editConf.ipV6.dhcp.server.rapidCommit

       Possibilities:
               disabled   (0)
               enabled   (1)"
   ::= {er1645v2PppoEIpV6Entry 173015040}

er1645v2PppoEIpV6DhcpServerTimersInfoRefresh OBJECT-TYPE
   SYNTAX      TimeTicks
   MAX-ACCESS  read-write
   STATUS      current
   DESCRIPTION
      "Path: server.editConf.ipV6.dhcp.server.timers.infoRefresh

       Time in centi-second."
   ::= {er1645v2PppoEIpV6Entry 173278208}

er1645v2PppoEIpV6DhcpRelayMode OBJECT-TYPE
   SYNTAX      INTEGER
               {
               disabled (0),
               enabled (1)
               }
   MAX-ACCESS  read-write
   STATUS      current
   DESCRIPTION
      "Path: server.editConf.ipV6.dhcp.relay.mode

       Possibilities:
               disabled   (0)
               enabled   (1)"
   ::= {er1645v2PppoEIpV6Entry 174071808}

er1645v2PppoEIpV6SendRedirect OBJECT-TYPE
   SYNTAX      INTEGER
               {
               disabled (0),
               enabled (1)
               }
   MAX-ACCESS  read-write
   STATUS      current
   DESCRIPTION
      "Path: server.editConf.ipV6.sendRedirect

       Possibilities:
               disabled   (0)
               enabled   (1)"
   ::= {er1645v2PppoEIpV6Entry 117440512}

er1645v2PppoEIpV6LinkMtu OBJECT-TYPE
   SYNTAX      Integer32
   MAX-ACCESS  read-write
   STATUS      current
   DESCRIPTION
      "Path: server.editConf.ipV6.linkMtu"
   ::= {er1645v2PppoEIpV6Entry 134217728}

er1645v2PppoEIpV6InterfaceId OBJECT-TYPE
   SYNTAX      OCTET STRING
   MAX-ACCESS  read-write
   STATUS      current
   DESCRIPTION
      "Path: server.editConf.ipV6.interfaceId"
   ::= {er1645v2PppoEIpV6Entry 150994944}

er1645v2PppoEIpV6IcmpMessagesNoRoute OBJECT-TYPE
   SYNTAX      INTEGER
               {
               disabled (0),
               enabled (1)
               }
   MAX-ACCESS  read-write
   STATUS      current
   DESCRIPTION
      "Path: server.editConf.ipV6.icmpMessages.noRoute

       Possibilities:
               disabled   (0)
               enabled   (1)"
   ::= {er1645v2PppoEIpV6Entry 302055424}

er1645v2PppoEIpV6IcmpMessagesBeyondScope OBJECT-TYPE
   SYNTAX      INTEGER
               {
               disabled (0),
               enabled (1)
               }
   MAX-ACCESS  read-write
   STATUS      current
   DESCRIPTION
      "Path: server.editConf.ipV6.icmpMessages.beyondScope

       Possibilities:
               disabled   (0)
               enabled   (1)"
   ::= {er1645v2PppoEIpV6Entry 302186496}

er1645v2PppoEIpV6IcmpMessagesAddressUnreachable OBJECT-TYPE
   SYNTAX      INTEGER
               {
               disabled (0),
               enabled (1)
               }
   MAX-ACCESS  read-write
   STATUS      current
   DESCRIPTION
      "Path: server.editConf.ipV6.icmpMessages.addressUnreachable

       Possibilities:
               disabled   (0)
               enabled   (1)"
   ::= {er1645v2PppoEIpV6Entry 302252032}

er1645v2PppoEIpV6IcmpMessagesPortUnreachable OBJECT-TYPE
   SYNTAX      INTEGER
               {
               disabled (0),
               enabled (1)
               }
   MAX-ACCESS  read-write
   STATUS      current
   DESCRIPTION
      "Path: server.editConf.ipV6.icmpMessages.portUnreachable

       Possibilities:
               disabled   (0)
               enabled   (1)"
   ::= {er1645v2PppoEIpV6Entry 302317568}

er1645v2PppoEIpV6IcmpMessagesPacketTooBig OBJECT-TYPE
   SYNTAX      INTEGER
               {
               disabled (0),
               enabled (1)
               }
   MAX-ACCESS  read-write
   STATUS      current
   DESCRIPTION
      "Path: server.editConf.ipV6.icmpMessages.packetTooBig

       Possibilities:
               disabled   (0)
               enabled   (1)"
   ::= {er1645v2PppoEIpV6Entry 302645248}

er1645v2PppoEIpV6IcmpMessagesHopLimitExceeded OBJECT-TYPE
   SYNTAX      INTEGER
               {
               disabled (0),
               enabled (1)
               }
   MAX-ACCESS  read-write
   STATUS      current
   DESCRIPTION
      "Path: server.editConf.ipV6.icmpMessages.hopLimitExceeded

       Possibilities:
               disabled   (0)
               enabled   (1)"
   ::= {er1645v2PppoEIpV6Entry 303300608}

er1645v2PppoEIpV6IcmpMessagesFragTimeExceeded OBJECT-TYPE
   SYNTAX      INTEGER
               {
               disabled (0),
               enabled (1)
               }
   MAX-ACCESS  read-write
   STATUS      current
   DESCRIPTION
      "Path: server.editConf.ipV6.icmpMessages.fragTimeExceeded

       Possibilities:
               disabled   (0)
               enabled   (1)"
   ::= {er1645v2PppoEIpV6Entry 303366144}

er1645v2PppoEIpV6IcmpMessagesHeaderFieldErr OBJECT-TYPE
   SYNTAX      INTEGER
               {
               disabled (0),
               enabled (1)
               }
   MAX-ACCESS  read-write
   STATUS      current
   DESCRIPTION
      "Path: server.editConf.ipV6.icmpMessages.headerFieldErr

       Possibilities:
               disabled   (0)
               enabled   (1)"
   ::= {er1645v2PppoEIpV6Entry 303955968}

er1645v2PppoEIpV6IcmpMessagesOptionUnrecognized OBJECT-TYPE
   SYNTAX      INTEGER
               {
               disabled (0),
               enabled (1)
               }
   MAX-ACCESS  read-write
   STATUS      current
   DESCRIPTION
      "Path: server.editConf.ipV6.icmpMessages.optionUnrecognized

       Possibilities:
               disabled   (0)
               enabled   (1)"
   ::= {er1645v2PppoEIpV6Entry 304087040}

er1645v2PppoEIpV6IcmpMessagesRedirect OBJECT-TYPE
   SYNTAX      INTEGER
               {
               disabled (0),
               enabled (1)
               }
   MAX-ACCESS  read-write
   STATUS      current
   DESCRIPTION
      "Path: server.editConf.ipV6.icmpMessages.redirect

       Possibilities:
               disabled   (0)
               enabled   (1)"
   ::= {er1645v2PppoEIpV6Entry 304611328}

er1645v2PppoEIpV6Addresses OBJECT-TYPE
   SYNTAX      SEQUENCE OF Er1645v2PppoEIpV6AddressesEntry
   MAX-ACCESS  not-accessible
   STATUS      current
   DESCRIPTION
      ""
   ::= {er1645v2PppoEIpV6 50331648}

er1645v2PppoEIpV6AddressesEntry OBJECT-TYPE
   SYNTAX      Er1645v2PppoEIpV6AddressesEntry
   MAX-ACCESS  not-accessible
   STATUS      current
   DESCRIPTION
      ""
   INDEX      { er1645v2PppoEIpV6AddressesTableIx }
   ::= {er1645v2PppoEIpV6Addresses 1}

Er1645v2PppoEIpV6AddressesEntry ::=
   SEQUENCE
      {
      er1645v2PppoEIpV6AddressesActions
         VariableLengthTableActions,
      er1645v2PppoEIpV6AddressesTableIx
         TableIndex,
      er1645v2PppoEIpV6AddressesAddress
         Ipv6Address,
      er1645v2PppoEIpV6AddressesPrefixLength
         Integer32,
      er1645v2PppoEIpV6AddressesGeneralPrefix
         DisplayString,
      er1645v2PppoEIpV6AddressesRaSend
         INTEGER,
      er1645v2PppoEIpV6AddressesRaOnLinkFlag
         INTEGER,
      er1645v2PppoEIpV6AddressesRaAutoFlag
         INTEGER,
      er1645v2PppoEIpV6AddressesRaValidLifeTime
         TimeTicks,
      er1645v2PppoEIpV6AddressesRaValidLTMode
         INTEGER,
      er1645v2PppoEIpV6AddressesRaPrefLifeTime
         TimeTicks,
      er1645v2PppoEIpV6AddressesRaPrefLTMode
         INTEGER
      }

er1645v2PppoEIpV6AddressesActions OBJECT-TYPE
   SYNTAX      VariableLengthTableActions
   MAX-ACCESS  read-write
   STATUS      current
   DESCRIPTION
      "By way of this field, some manipulations
       on this table may be performed."
   ::= {er1645v2PppoEIpV6AddressesEntry 2}

er1645v2PppoEIpV6AddressesTableIx OBJECT-TYPE
   SYNTAX      TableIndex
   MAX-ACCESS  not-accessible
   STATUS      current
   DESCRIPTION
      ""
   ::= {er1645v2PppoEIpV6AddressesEntry 11}

er1645v2PppoEIpV6AddressesAddress OBJECT-TYPE
   SYNTAX      Ipv6Address
   MAX-ACCESS  read-write
   STATUS      current
   DESCRIPTION
      "Path: server.editConf.ipV6.addresses.address

       ipv6 address"
   ::= {er1645v2PppoEIpV6AddressesEntry 16777216}

er1645v2PppoEIpV6AddressesPrefixLength OBJECT-TYPE
   SYNTAX      Integer32
   MAX-ACCESS  read-write
   STATUS      current
   DESCRIPTION
      "Path: server.editConf.ipV6.addresses.prefixLength"
   ::= {er1645v2PppoEIpV6AddressesEntry 33554432}

er1645v2PppoEIpV6AddressesGeneralPrefix OBJECT-TYPE
   SYNTAX      DisplayString
   MAX-ACCESS  read-write
   STATUS      current
   DESCRIPTION
      "Path: server.editConf.ipV6.addresses.generalPrefix"
   ::= {er1645v2PppoEIpV6AddressesEntry 83886080}

er1645v2PppoEIpV6AddressesRaSend OBJECT-TYPE
   SYNTAX      INTEGER
               {
               disabled (0),
               enabled (1)
               }
   MAX-ACCESS  read-write
   STATUS      current
   DESCRIPTION
      "Path: server.editConf.ipV6.addresses.ra.send

       Possibilities:
               disabled   (0)
               enabled   (1)"
   ::= {er1645v2PppoEIpV6AddressesEntry 67174400}

er1645v2PppoEIpV6AddressesRaOnLinkFlag OBJECT-TYPE
   SYNTAX      INTEGER
               {
               disabled (0),
               enabled (1)
               }
   MAX-ACCESS  read-write
   STATUS      current
   DESCRIPTION
      "Path: server.editConf.ipV6.addresses.ra.onLinkFlag

       Possibilities:
               disabled   (0)
               enabled   (1)"
   ::= {er1645v2PppoEIpV6AddressesEntry 67371008}

er1645v2PppoEIpV6AddressesRaAutoFlag OBJECT-TYPE
   SYNTAX      INTEGER
               {
               disabled (0),
               enabled (1)
               }
   MAX-ACCESS  read-write
   STATUS      current
   DESCRIPTION
      "Path: server.editConf.ipV6.addresses.ra.autonomousFlag

       Possibilities:
               disabled   (0)
               enabled   (1)"
   ::= {er1645v2PppoEIpV6AddressesEntry 67567616}

er1645v2PppoEIpV6AddressesRaValidLifeTime OBJECT-TYPE
   SYNTAX      TimeTicks
   MAX-ACCESS  read-write
   STATUS      current
   DESCRIPTION
      "Path: server.editConf.ipV6.addresses.ra.validLifeTime

       Time in centi-second."
   ::= {er1645v2PppoEIpV6AddressesEntry 67239936}

er1645v2PppoEIpV6AddressesRaValidLTMode OBJECT-TYPE
   SYNTAX      INTEGER
               {
               fixed (0),
               infinite (2)
               }
   MAX-ACCESS  read-write
   STATUS      current
   DESCRIPTION
      "Path: server.editConf.ipV6.addresses.ra.validLifeTimeMode

       Possibilities:
               fixed   (0)
               infinite   (2)"
   ::= {er1645v2PppoEIpV6AddressesEntry 67305472}

er1645v2PppoEIpV6AddressesRaPrefLifeTime OBJECT-TYPE
   SYNTAX      TimeTicks
   MAX-ACCESS  read-write
   STATUS      current
   DESCRIPTION
      "Path: server.editConf.ipV6.addresses.ra.prefLifeTime

       Time in centi-second."
   ::= {er1645v2PppoEIpV6AddressesEntry 67436544}

er1645v2PppoEIpV6AddressesRaPrefLTMode OBJECT-TYPE
   SYNTAX      INTEGER
               {
               fixed (0),
               infinite (2)
               }
   MAX-ACCESS  read-write
   STATUS      current
   DESCRIPTION
      "Path: server.editConf.ipV6.addresses.ra.prefLifeTimeMode

       Possibilities:
               fixed   (0)
               infinite   (2)"
   ::= {er1645v2PppoEIpV6AddressesEntry 67502080}

er1645v2PppoEIpV6RaDnsOptionsRdnssServers OBJECT-TYPE
   SYNTAX      SEQUENCE OF Er1645v2PppoEIpV6RaDnsOptionsRdnssServersEntry
   MAX-ACCESS  not-accessible
   STATUS      current
   DESCRIPTION
      ""
   ::= {er1645v2PppoEIpV6 101394432}

er1645v2PppoEIpV6RaDnsOptionsRdnssServersEntry OBJECT-TYPE
   SYNTAX      Er1645v2PppoEIpV6RaDnsOptionsRdnssServersEntry
   MAX-ACCESS  not-accessible
   STATUS      current
   DESCRIPTION
      ""
   INDEX      { er1645v2PppoEIpV6RaDnsOptionsRdnssServersTableIx }
   ::= {er1645v2PppoEIpV6RaDnsOptionsRdnssServers 1}

Er1645v2PppoEIpV6RaDnsOptionsRdnssServersEntry ::=
   SEQUENCE
      {
      er1645v2PppoEIpV6RaDnsOptionsRdnssServersActions
         VariableLengthTableActions,
      er1645v2PppoEIpV6RaDnsOptionsRdnssServersTableIx
         TableIndex,
      er1645v2PppoEIpV6RaDnsOptionsRdnssServersAddress
         Ipv6Address
      }

er1645v2PppoEIpV6RaDnsOptionsRdnssServersActions OBJECT-TYPE
   SYNTAX      VariableLengthTableActions
   MAX-ACCESS  read-write
   STATUS      current
   DESCRIPTION
      "By way of this field, some manipulations
       on this table may be performed."
   ::= {er1645v2PppoEIpV6RaDnsOptionsRdnssServersEntry 2}

er1645v2PppoEIpV6RaDnsOptionsRdnssServersTableIx OBJECT-TYPE
   SYNTAX      TableIndex
   MAX-ACCESS  not-accessible
   STATUS      current
   DESCRIPTION
      ""
   ::= {er1645v2PppoEIpV6RaDnsOptionsRdnssServersEntry 11}

er1645v2PppoEIpV6RaDnsOptionsRdnssServersAddress OBJECT-TYPE
   SYNTAX      Ipv6Address
   MAX-ACCESS  read-write
   STATUS      current
   DESCRIPTION
      "Path: server.editConf.ipV6.ra.dnsOptions.rdnss.servers.address

       ipv6 address"
   ::= {er1645v2PppoEIpV6RaDnsOptionsRdnssServersEntry 16777216}

er1645v2PppoEIpV6RaDnsOptionsDnsslDomains OBJECT-TYPE
   SYNTAX      SEQUENCE OF Er1645v2PppoEIpV6RaDnsOptionsDnsslDomainsEntry
   MAX-ACCESS  not-accessible
   STATUS      current
   DESCRIPTION
      ""
   ::= {er1645v2PppoEIpV6 101402624}

er1645v2PppoEIpV6RaDnsOptionsDnsslDomainsEntry OBJECT-TYPE
   SYNTAX      Er1645v2PppoEIpV6RaDnsOptionsDnsslDomainsEntry
   MAX-ACCESS  not-accessible
   STATUS      current
   DESCRIPTION
      ""
   INDEX      { er1645v2PppoEIpV6RaDnsOptionsDnsslDomainsTableIx }
   ::= {er1645v2PppoEIpV6RaDnsOptionsDnsslDomains 1}

Er1645v2PppoEIpV6RaDnsOptionsDnsslDomainsEntry ::=
   SEQUENCE
      {
      er1645v2PppoEIpV6RaDnsOptionsDnsslDomainsActions
         VariableLengthTableActions,
      er1645v2PppoEIpV6RaDnsOptionsDnsslDomainsTableIx
         TableIndex,
      er1645v2PppoEIpV6RaDnsOptionsDnsslDomainsName
         DisplayString
      }

er1645v2PppoEIpV6RaDnsOptionsDnsslDomainsActions OBJECT-TYPE
   SYNTAX      VariableLengthTableActions
   MAX-ACCESS  read-write
   STATUS      current
   DESCRIPTION
      "By way of this field, some manipulations
       on this table may be performed."
   ::= {er1645v2PppoEIpV6RaDnsOptionsDnsslDomainsEntry 2}

er1645v2PppoEIpV6RaDnsOptionsDnsslDomainsTableIx OBJECT-TYPE
   SYNTAX      TableIndex
   MAX-ACCESS  not-accessible
   STATUS      current
   DESCRIPTION
      ""
   ::= {er1645v2PppoEIpV6RaDnsOptionsDnsslDomainsEntry 11}

er1645v2PppoEIpV6RaDnsOptionsDnsslDomainsName OBJECT-TYPE
   SYNTAX      DisplayString
   MAX-ACCESS  read-write
   STATUS      current
   DESCRIPTION
      "Path: server.editConf.ipV6.ra.dnsOptions.dnssl.domains.name"
   ::= {er1645v2PppoEIpV6RaDnsOptionsDnsslDomainsEntry 16777216}

er1645v2PppoEIpV6DhcpClientUserClassOpt OBJECT-TYPE
   SYNTAX      SEQUENCE OF Er1645v2PppoEIpV6DhcpClientUserClassOptEntry
   MAX-ACCESS  not-accessible
   STATUS      current
   DESCRIPTION
      ""
   ::= {er1645v2PppoEIpV6 171442176}

er1645v2PppoEIpV6DhcpClientUserClassOptEntry OBJECT-TYPE
   SYNTAX      Er1645v2PppoEIpV6DhcpClientUserClassOptEntry
   MAX-ACCESS  not-accessible
   STATUS      current
   DESCRIPTION
      ""
   INDEX      { er1645v2PppoEIpV6DhcpClientUserClassOptTableIx }
   ::= {er1645v2PppoEIpV6DhcpClientUserClassOpt 1}

Er1645v2PppoEIpV6DhcpClientUserClassOptEntry ::=
   SEQUENCE
      {
      er1645v2PppoEIpV6DhcpClientUserClassOptActions
         VariableLengthTableActions,
      er1645v2PppoEIpV6DhcpClientUserClassOptTableIx
         TableIndex,
      er1645v2PppoEIpV6DhcpClientUserClassOptValueAscii
         DisplayString,
      er1645v2PppoEIpV6DhcpClientUserClassOptValueDecimal
         Integer32,
      er1645v2PppoEIpV6DhcpClientUserClassOptValueHexData
         OCTET STRING
      }

er1645v2PppoEIpV6DhcpClientUserClassOptActions OBJECT-TYPE
   SYNTAX      VariableLengthTableActions
   MAX-ACCESS  read-write
   STATUS      current
   DESCRIPTION
      "By way of this field, some manipulations
       on this table may be performed."
   ::= {er1645v2PppoEIpV6DhcpClientUserClassOptEntry 2}

er1645v2PppoEIpV6DhcpClientUserClassOptTableIx OBJECT-TYPE
   SYNTAX      TableIndex
   MAX-ACCESS  not-accessible
   STATUS      current
   DESCRIPTION
      ""
   ::= {er1645v2PppoEIpV6DhcpClientUserClassOptEntry 11}

er1645v2PppoEIpV6DhcpClientUserClassOptValueAscii OBJECT-TYPE
   SYNTAX      DisplayString
   MAX-ACCESS  read-write
   STATUS      current
   DESCRIPTION
      "Path: server.editConf.ipV6.dhcp.client.userClassOpt.value.ascii"
   ::= {er1645v2PppoEIpV6DhcpClientUserClassOptEntry 16842752}

er1645v2PppoEIpV6DhcpClientUserClassOptValueDecimal OBJECT-TYPE
   SYNTAX      Integer32
   MAX-ACCESS  read-write
   STATUS      current
   DESCRIPTION
      "Path: server.editConf.ipV6.dhcp.client.userClassOpt.value.decimal"
   ::= {er1645v2PppoEIpV6DhcpClientUserClassOptEntry 16908288}

er1645v2PppoEIpV6DhcpClientUserClassOptValueHexData OBJECT-TYPE
   SYNTAX      OCTET STRING
   MAX-ACCESS  read-write
   STATUS      current
   DESCRIPTION
      "Path: server.editConf.ipV6.dhcp.client.userClassOpt.value.hexData"
   ::= {er1645v2PppoEIpV6DhcpClientUserClassOptEntry 16973824}

er1645v2PppoEIpV6DhcpClientVendorCl OBJECT-TYPE
   SYNTAX      SEQUENCE OF Er1645v2PppoEIpV6DhcpClientVendorClEntry
   MAX-ACCESS  not-accessible
   STATUS      current
   DESCRIPTION
      ""
   ::= {er1645v2PppoEIpV6 171704320}

er1645v2PppoEIpV6DhcpClientVendorClEntry OBJECT-TYPE
   SYNTAX      Er1645v2PppoEIpV6DhcpClientVendorClEntry
   MAX-ACCESS  not-accessible
   STATUS      current
   DESCRIPTION
      ""
   INDEX      { er1645v2PppoEIpV6DhcpClientVendorClTableIx }
   ::= {er1645v2PppoEIpV6DhcpClientVendorCl 1}

Er1645v2PppoEIpV6DhcpClientVendorClEntry ::=
   SEQUENCE
      {
      er1645v2PppoEIpV6DhcpClientVendorClActions
         VariableLengthTableActions,
      er1645v2PppoEIpV6DhcpClientVendorClTableIx
         TableIndex,
      er1645v2PppoEIpV6DhcpClientVendorClValueAscii
         DisplayString,
      er1645v2PppoEIpV6DhcpClientVendorClValueDecimal
         Integer32,
      er1645v2PppoEIpV6DhcpClientVendorClValueHexData
         OCTET STRING
      }

er1645v2PppoEIpV6DhcpClientVendorClActions OBJECT-TYPE
   SYNTAX      VariableLengthTableActions
   MAX-ACCESS  read-write
   STATUS      current
   DESCRIPTION
      "By way of this field, some manipulations
       on this table may be performed."
   ::= {er1645v2PppoEIpV6DhcpClientVendorClEntry 2}

er1645v2PppoEIpV6DhcpClientVendorClTableIx OBJECT-TYPE
   SYNTAX      TableIndex
   MAX-ACCESS  not-accessible
   STATUS      current
   DESCRIPTION
      ""
   ::= {er1645v2PppoEIpV6DhcpClientVendorClEntry 11}

er1645v2PppoEIpV6DhcpClientVendorClValueAscii OBJECT-TYPE
   SYNTAX      DisplayString
   MAX-ACCESS  read-write
   STATUS      current
   DESCRIPTION
      "Path: server.editConf.ipV6.dhcp.client.vendorClassOpt.value.ascii"
   ::= {er1645v2PppoEIpV6DhcpClientVendorClEntry 16842752}

er1645v2PppoEIpV6DhcpClientVendorClValueDecimal OBJECT-TYPE
   SYNTAX      Integer32
   MAX-ACCESS  read-write
   STATUS      current
   DESCRIPTION
      "Path: server.editConf.ipV6.dhcp.client.vendorClassOpt.value.decimal"
   ::= {er1645v2PppoEIpV6DhcpClientVendorClEntry 16908288}

er1645v2PppoEIpV6DhcpClientVendorClValueHexData OBJECT-TYPE
   SYNTAX      OCTET STRING
   MAX-ACCESS  read-write
   STATUS      current
   DESCRIPTION
      "Path: server.editConf.ipV6.dhcp.client.vendorClassOpt.value.hexData"
   ::= {er1645v2PppoEIpV6DhcpClientVendorClEntry 16973824}

er1645v2PppoEIpV6DhcpRelayDestinations OBJECT-TYPE
   SYNTAX      SEQUENCE OF Er1645v2PppoEIpV6DhcpRelayDestinationsEntry
   MAX-ACCESS  not-accessible
   STATUS      current
   DESCRIPTION
      ""
   ::= {er1645v2PppoEIpV6 174080000}

er1645v2PppoEIpV6DhcpRelayDestinationsEntry OBJECT-TYPE
   SYNTAX      Er1645v2PppoEIpV6DhcpRelayDestinationsEntry
   MAX-ACCESS  not-accessible
   STATUS      current
   DESCRIPTION
      ""
   INDEX      { er1645v2PppoEIpV6DhcpRelayDestinationsTableIx }
   ::= {er1645v2PppoEIpV6DhcpRelayDestinations 1}

Er1645v2PppoEIpV6DhcpRelayDestinationsEntry ::=
   SEQUENCE
      {
      er1645v2PppoEIpV6DhcpRelayDestinationsActions
         VariableLengthTableActions,
      er1645v2PppoEIpV6DhcpRelayDestinationsTableIx
         TableIndex,
      er1645v2PppoEIpV6DhcpRelayDestinationsAddress
         Ipv6Address,
      er1645v2PppoEIpV6DhcpRelayDestinationsInterface
         DisplayString
      }

er1645v2PppoEIpV6DhcpRelayDestinationsActions OBJECT-TYPE
   SYNTAX      VariableLengthTableActions
   MAX-ACCESS  read-write
   STATUS      current
   DESCRIPTION
      "By way of this field, some manipulations
       on this table may be performed."
   ::= {er1645v2PppoEIpV6DhcpRelayDestinationsEntry 2}

er1645v2PppoEIpV6DhcpRelayDestinationsTableIx OBJECT-TYPE
   SYNTAX      TableIndex
   MAX-ACCESS  not-accessible
   STATUS      current
   DESCRIPTION
      ""
   ::= {er1645v2PppoEIpV6DhcpRelayDestinationsEntry 11}

er1645v2PppoEIpV6DhcpRelayDestinationsAddress OBJECT-TYPE
   SYNTAX      Ipv6Address
   MAX-ACCESS  read-write
   STATUS      current
   DESCRIPTION
      "Path: server.editConf.ipV6.dhcp.relay.destinations.address

       ipv6 address"
   ::= {er1645v2PppoEIpV6DhcpRelayDestinationsEntry 16777216}

er1645v2PppoEIpV6DhcpRelayDestinationsInterface OBJECT-TYPE
   SYNTAX      DisplayString
   MAX-ACCESS  read-write
   STATUS      current
   DESCRIPTION
      "Path: server.editConf.ipV6.dhcp.relay.destinations.interface"
   ::= {er1645v2PppoEIpV6DhcpRelayDestinationsEntry 33554432}


er1645v2PppoELinkMon OBJECT IDENTIFIER ::= {er1645v2PppoE 3}

er1645v2PppoELinkMonSSC OBJECT IDENTIFIER ::= {er1645v2PppoELinkMon 1}

er1645v2PppoELinkMonEntry OBJECT IDENTIFIER ::= {er1645v2PppoELinkMonSSC 1}

er1645v2PppoELinkMonOperation OBJECT-TYPE
   SYNTAX      INTEGER
               {
               disabled (0),
               enabled (1)
               }
   MAX-ACCESS  read-write
   STATUS      current
   DESCRIPTION
      "Path: server.editConf.linkMonitoring.operation

       Possibilities:
               disabled   (0)
               enabled   (1)"
   ::= {er1645v2PppoELinkMonEntry 16777216}

er1645v2PppoELinkMonInterval OBJECT-TYPE
   SYNTAX      TimeTicks
   MAX-ACCESS  read-write
   STATUS      current
   DESCRIPTION
      "Path: server.editConf.linkMonitoring.interval

       Time in centi-second."
   ::= {er1645v2PppoELinkMonEntry 33554432}

er1645v2PppoELinkMonRepTimeOut OBJECT-TYPE
   SYNTAX      TimeTicks
   MAX-ACCESS  read-write
   STATUS      current
   DESCRIPTION
      "Path: server.editConf.linkMonitoring.replyTimeOut

       Time in centi-second."
   ::= {er1645v2PppoELinkMonEntry 50331648}

er1645v2PppoELinkMonFailsPrmt OBJECT-TYPE
   SYNTAX      Integer32
   MAX-ACCESS  read-write
   STATUS      current
   DESCRIPTION
      "Path: server.editConf.linkMonitoring.failsPermitted"
   ::= {er1645v2PppoELinkMonEntry 67108864}


er1645v2PppoEAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: server.editConf.authentication
       Info: pppAuthentication

       Possibilities:
               disabled   (0)
               chap   (1)
               pap   (2)
               chapOrPap   (3)
               msChap   (4)
               msChapV2   (5)"
   ::= {er1645v2PppoE 4}


er1645v2PppoEAuthenPeriod OBJECT-TYPE
   SYNTAX      TimeTicks
   MAX-ACCESS  read-write
   STATUS      current
   DESCRIPTION
      "Path: server.editConf.authenPeriod
       Info: pppAuthenPeriod

       Time in centi-second."
   ::= {er1645v2PppoE 5}


er1645v2PppoESessionsPerMac OBJECT-TYPE
   SYNTAX      Integer32
   MAX-ACCESS  read-write
   STATUS      current
   DESCRIPTION
      "Path: server.editConf.sessionsPerMac
       Info: pppoe session limit configuration"
   ::= {er1645v2PppoE 7}


er1645v2PppoEMaxSessions OBJECT-TYPE
   SYNTAX      Integer32
   MAX-ACCESS  read-write
   STATUS      current
   DESCRIPTION
      "Path: server.editConf.maxSessions
       Info: pppoe session limit configuration"
   ::= {er1645v2PppoE 8}


er1645v2PppoEServiceNames OBJECT IDENTIFIER ::= {er1645v2PppoE 9}

er1645v2PppoEServiceNamesSSCTable OBJECT-TYPE
   SYNTAX      SEQUENCE OF Er1645v2PppoEServiceNamesEntry
   MAX-ACCESS  not-accessible
   STATUS      current
   DESCRIPTION
      "Service name"
   ::= {er1645v2PppoEServiceNames 1}

er1645v2PppoEServiceNamesEntry OBJECT-TYPE
   SYNTAX      Er1645v2PppoEServiceNamesEntry
   MAX-ACCESS  not-accessible
   STATUS      current
   DESCRIPTION
      ""
   INDEX      { er1645v2PppoEServiceNamesTableIx }
   ::= {er1645v2PppoEServiceNamesSSCTable 1}

Er1645v2PppoEServiceNamesEntry ::=
   SEQUENCE
      {
      er1645v2PppoEServiceNamesActions
         VariableLengthTableActions,
      er1645v2PppoEServiceNamesTableIx
         TableIndex,
      er1645v2PppoEServiceNamesServiceName
         DisplayString
      }

er1645v2PppoEServiceNamesActions OBJECT-TYPE
   SYNTAX      VariableLengthTableActions
   MAX-ACCESS  read-write
   STATUS      current
   DESCRIPTION
      "By way of this field, some manipulations
       on this table may be performed."
   ::= {er1645v2PppoEServiceNamesEntry 2}

er1645v2PppoEServiceNamesTableIx OBJECT-TYPE
   SYNTAX      TableIndex
   MAX-ACCESS  not-accessible
   STATUS      current
   DESCRIPTION
      ""
   ::= {er1645v2PppoEServiceNamesEntry 11}

er1645v2PppoEServiceNamesServiceName OBJECT-TYPE
   SYNTAX      DisplayString
   MAX-ACCESS  read-write
   STATUS      current
   DESCRIPTION
      "Path: server.editConf.serviceNames.serviceName"
   ::= {er1645v2PppoEServiceNamesEntry 16777216}



sr1645v2PppoE OBJECT IDENTIFIER ::= {r1645v2PppoE 14}


sr1645v2PppoEPPPoE OBJECT IDENTIFIER ::= {sr1645v2PppoE 40}

sr1645v2PppoEPPPoESSCTable OBJECT-TYPE
   SYNTAX      SEQUENCE OF Sr1645v2PppoEPPPoEEntry
   MAX-ACCESS  not-accessible
   STATUS      current
   DESCRIPTION
      ""
   ::= {sr1645v2PppoEPPPoE 1}

sr1645v2PppoEPPPoEEntry OBJECT-TYPE
   SYNTAX      Sr1645v2PppoEPPPoEEntry
   MAX-ACCESS  not-accessible
   STATUS      current
   DESCRIPTION
      ""
   INDEX      { sr1645v2PppoEPPPoETableIx }
   ::= {sr1645v2PppoEPPPoESSCTable 1}

Sr1645v2PppoEPPPoEEntry ::=
   SEQUENCE
      {
      sr1645v2PppoEPPPoETableIx
         TableIndex,
      sr1645v2PppoEPPPoEName
         DisplayString,
      sr1645v2PppoEPPPoEMode
         INTEGER,
      sr1645v2PppoEPPPoEIfOperStatus
         INTEGER,
      sr1645v2PppoEPPPoEIfLastChange
         TimeTicks,
      sr1645v2PppoEPPPoEIfLastChangeDate
         DisplayString,
      sr1645v2PppoEPPPoEIpAddress
         IpAddress,
      sr1645v2PppoEPPPoEIpNetMask
         IpAddress,
      sr1645v2PppoEPPPoEIpRemote
         IpAddress,
      sr1645v2PppoEPPPoEPppOEthDiscState
         INTEGER,
      sr1645v2PppoEPPPoEPppOEthPeerMac
         OCTET STRING,
      sr1645v2PppoEPPPoEPppOEthServiceName
         DisplayString,
      sr1645v2PppoEPPPoEPppLcpState
         INTEGER,
      sr1645v2PppoEPPPoEPppIpcpState
         INTEGER,
      sr1645v2PppoEPPPoEPppIp6cpState
         INTEGER,
      sr1645v2PppoEPPPoEPppMyAutSt
         INTEGER,
      sr1645v2PppoEPPPoEPppHisAutSt
         INTEGER,
      sr1645v2PppoEPPPoEPppMru
         Integer32,
      sr1645v2PppoEPPPoEIpV6State
         INTEGER,
      sr1645v2PppoEPPPoEIpV6InterfaceId
         OCTET STRING,
      sr1645v2PppoEPPPoEIpV6LinkMtu
         Integer32,
      sr1645v2PppoEPPPoEIpV6HopLimit
         Integer32,
      sr1645v2PppoEPPPoEIpV6DhcpIaid
         Counter32,
      sr1645v2PppoEPPPoEIpV6RaRcvOption
         Integer32
      }

sr1645v2PppoEPPPoETableIx OBJECT-TYPE
   SYNTAX      TableIndex
   MAX-ACCESS  not-accessible
   STATUS      current
   DESCRIPTION
      ""
   ::= {sr1645v2PppoEPPPoEEntry 11}

sr1645v2PppoEPPPoEName OBJECT-TYPE
   SYNTAX      DisplayString
   MAX-ACCESS  read-only
   STATUS      current
   DESCRIPTION
      "Path: server.status.pppSessions.name"
   ::= {sr1645v2PppoEPPPoEEntry 16777216}

sr1645v2PppoEPPPoEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: server.status.pppSessions.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2PppoEPPPoEEntry 335544320}

sr1645v2PppoEPPPoEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: server.status.pppSessions.ifOperStatus

       Possibilities:
               up   (1)
               down   (2)
               testing   (3)
               unknown   (4)
               dormant   (5)
               notPresent   (6)
               lowerLayerDown   (7)"
   ::= {sr1645v2PppoEPPPoEEntry 1795162112}

sr1645v2PppoEPPPoEIfLastChange OBJECT-TYPE
   SYNTAX      TimeTicks
   MAX-ACCESS  read-only
   STATUS      current
   DESCRIPTION
      "Path: server.status.pppSessions.ifLastChange

       Time in centi-second."
   ::= {sr1645v2PppoEPPPoEEntry 1811939328}

sr1645v2PppoEPPPoEIfLastChangeDate OBJECT-TYPE
   SYNTAX      DisplayString
   MAX-ACCESS  read-only
   STATUS      current
   DESCRIPTION
      "Path: server.status.pppSessions.ifLastChangeDate"
   ::= {sr1645v2PppoEPPPoEEntry 3070230528}

sr1645v2PppoEPPPoEIpAddress OBJECT-TYPE
   SYNTAX      IpAddress
   MAX-ACCESS  read-only
   STATUS      current
   DESCRIPTION
      "Path: server.status.pppSessions.ip.address"
   ::= {sr1645v2PppoEPPPoEEntry 51380224}

sr1645v2PppoEPPPoEIpNetMask OBJECT-TYPE
   SYNTAX      IpAddress
   MAX-ACCESS  read-only
   STATUS      current
   DESCRIPTION
      "Path: server.status.pppSessions.ip.netMask"
   ::= {sr1645v2PppoEPPPoEEntry 51445760}

sr1645v2PppoEPPPoEIpRemote OBJECT-TYPE
   SYNTAX      IpAddress
   MAX-ACCESS  read-only
   STATUS      current
   DESCRIPTION
      "Path: server.status.pppSessions.ip.remote"
   ::= {sr1645v2PppoEPPPoEEntry 51511296}

sr1645v2PppoEPPPoEPppOEthDiscState OBJECT-TYPE
   SYNTAX      INTEGER
               {
               idle (0),
               waitForPADO (1),
               waitForPADS (2),
               established (3)
               }
   MAX-ACCESS  read-only
   STATUS      current
   DESCRIPTION
      "Path: server.status.pppSessions.pppOverEth.discState

       Possibilities:
               idle   (0)
               waitForPADO   (1)
               waitForPADS   (2)
               established   (3)"
   ::= {sr1645v2PppoEPPPoEEntry 67174400}

sr1645v2PppoEPPPoEPppOEthPeerMac OBJECT-TYPE
   SYNTAX      OCTET STRING
   MAX-ACCESS  read-only
   STATUS      current
   DESCRIPTION
      "Path: server.status.pppSessions.pppOverEth.remoteMacAddress

       MAC address."
   ::= {sr1645v2PppoEPPPoEEntry 67239936}

sr1645v2PppoEPPPoEPppOEthServiceName OBJECT-TYPE
   SYNTAX      DisplayString
   MAX-ACCESS  read-only
   STATUS      current
   DESCRIPTION
      "Path: server.status.pppSessions.pppOverEth.serviceName"
   ::= {sr1645v2PppoEPPPoEEntry 67305472}

sr1645v2PppoEPPPoEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: server.status.pppSessions.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppoEPPPoEEntry 83951616}

sr1645v2PppoEPPPoEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: server.status.pppSessions.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppoEPPPoEEntry 84017152}

sr1645v2PppoEPPPoEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: server.status.pppSessions.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppoEPPPoEEntry 84869120}

sr1645v2PppoEPPPoEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: server.status.pppSessions.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2PppoEPPPoEEntry 84541440}

sr1645v2PppoEPPPoEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: server.status.pppSessions.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2PppoEPPPoEEntry 84606976}

sr1645v2PppoEPPPoEPppMru OBJECT-TYPE
   SYNTAX      Integer32
   MAX-ACCESS  read-only
   STATUS      current
   DESCRIPTION
      "Path: server.status.pppSessions.ppp.mru"
   ::= {sr1645v2PppoEPPPoEEntry 84934656}

sr1645v2PppoEPPPoEIpV6State OBJECT-TYPE
   SYNTAX      INTEGER
               {
               disabled (0),
               enabled (1)
               }
   MAX-ACCESS  read-only
   STATUS      current
   DESCRIPTION
      "Path: server.status.pppSessions.ipV6.state

       Possibilities:
               disabled   (0)
               enabled   (1)"
   ::= {sr1645v2PppoEPPPoEEntry 100728832}

sr1645v2PppoEPPPoEIpV6InterfaceId OBJECT-TYPE
   SYNTAX      OCTET STRING
   MAX-ACCESS  read-only
   STATUS      current
   DESCRIPTION
      "Path: server.status.pppSessions.ipV6.interfaceId"
   ::= {sr1645v2PppoEPPPoEEntry 100794368}

sr1645v2PppoEPPPoEIpV6LinkMtu OBJECT-TYPE
   SYNTAX      Integer32
   MAX-ACCESS  read-only
   STATUS      current
   DESCRIPTION
      "Path: server.status.pppSessions.ipV6.linkMtu"
   ::= {sr1645v2PppoEPPPoEEntry 100925440}

sr1645v2PppoEPPPoEIpV6HopLimit OBJECT-TYPE
   SYNTAX      Integer32
   MAX-ACCESS  read-only
   STATUS      current
   DESCRIPTION
      "Path: server.status.pppSessions.ipV6.hopLimit"
   ::= {sr1645v2PppoEPPPoEEntry 100990976}

sr1645v2PppoEPPPoEIpV6DhcpIaid OBJECT-TYPE
   SYNTAX      Counter32
   MAX-ACCESS  read-only
   STATUS      current
   DESCRIPTION
      "Path: server.status.pppSessions.ipV6.dhcp.iaid

       32 bit unsigned wrappable counter."
   ::= {sr1645v2PppoEPPPoEEntry 101056768}

sr1645v2PppoEPPPoEIpV6RaRcvOption OBJECT-TYPE
   SYNTAX      Integer32
   MAX-ACCESS  read-only
   STATUS      current
   DESCRIPTION
      "Path: server.status.pppSessions.ipV6.raRcvOption

       Bit meanings:
               bit 0 = linkMtu,
               bit 1 = srcLinkLayer,
               bit 2 = prefixInfo,
               bit 3 = rdnss,
               bit 4 = dnssl"
   ::= {sr1645v2PppoEPPPoEEntry 101122048}

sr1645v2PppoEPPPoEIpV6Addresses OBJECT-TYPE
   SYNTAX      SEQUENCE OF Sr1645v2PppoEPPPoEIpV6AddressesEntry
   MAX-ACCESS  not-accessible
   STATUS      current
   DESCRIPTION
      ""
   ::= {sr1645v2PppoEPPPoE 100859904}

sr1645v2PppoEPPPoEIpV6AddressesEntry OBJECT-TYPE
   SYNTAX      Sr1645v2PppoEPPPoEIpV6AddressesEntry
   MAX-ACCESS  not-accessible
   STATUS      current
   DESCRIPTION
      ""
   INDEX      { sr1645v2PppoEPPPoETableIx,
                sr1645v2PppoEPPPoEIpV6AddressesTableIx }
   ::= {sr1645v2PppoEPPPoEIpV6Addresses 1}

Sr1645v2PppoEPPPoEIpV6AddressesEntry ::=
   SEQUENCE
      {
      sr1645v2PppoEPPPoEIpV6AddressesTableIx
         TableIndex,
      sr1645v2PppoEPPPoEIpV6AddressesAddress
         Ipv6Address,
      sr1645v2PppoEPPPoEIpV6AddressesPrefixLength
         Integer32,
      sr1645v2PppoEPPPoEIpV6AddressesStatus
         INTEGER,
      sr1645v2PppoEPPPoEIpV6AddressesOrigin
         INTEGER,
      sr1645v2PppoEPPPoEIpV6AddressesFlagsInterfaceId
         INTEGER,
      sr1645v2PppoEPPPoEIpV6AddressesFlagsAnycast
         INTEGER,
      sr1645v2PppoEPPPoEIpV6AddressesTimersValidLifeTime
         TimeTicks,
      sr1645v2PppoEPPPoEIpV6AddressesTimersPrefLifeTime
         TimeTicks
      }

sr1645v2PppoEPPPoEIpV6AddressesTableIx OBJECT-TYPE
   SYNTAX      TableIndex
   MAX-ACCESS  not-accessible
   STATUS      current
   DESCRIPTION
      ""
   ::= {sr1645v2PppoEPPPoEIpV6AddressesEntry 11}

sr1645v2PppoEPPPoEIpV6AddressesAddress OBJECT-TYPE
   SYNTAX      Ipv6Address
   MAX-ACCESS  read-only
   STATUS      current
   DESCRIPTION
      "Path: server.status.pppSessions.ipV6.addresses.address

       ipv6 address"
   ::= {sr1645v2PppoEPPPoEIpV6AddressesEntry 16777216}

sr1645v2PppoEPPPoEIpV6AddressesPrefixLength OBJECT-TYPE
   SYNTAX      Integer32
   MAX-ACCESS  read-only
   STATUS      current
   DESCRIPTION
      "Path: server.status.pppSessions.ipV6.addresses.prefixLength"
   ::= {sr1645v2PppoEPPPoEIpV6AddressesEntry 33554432}

sr1645v2PppoEPPPoEIpV6AddressesStatus OBJECT-TYPE
   SYNTAX      INTEGER
               {
               invalid (0),
               tentative (1),
               deprecated (2),
               preferred (3)
               }
   MAX-ACCESS  read-only
   STATUS      current
   DESCRIPTION
      "Path: server.status.pppSessions.ipV6.addresses.status

       Possibilities:
               invalid   (0)
               tentative   (1)
               deprecated   (2)
               preferred   (3)"
   ::= {sr1645v2PppoEPPPoEIpV6AddressesEntry 50331648}

sr1645v2PppoEPPPoEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: server.status.pppSessions.ipV6.addresses.origin

       Possibilities:
               unknown   (0)
               manual   (1)
               generalPrefix   (2)
               statelessAuto   (3)
               statefullAuto   (4)"
   ::= {sr1645v2PppoEPPPoEIpV6AddressesEntry 67108864}

sr1645v2PppoEPPPoEIpV6AddressesFlagsInterfaceId OBJECT-TYPE
   SYNTAX      INTEGER
               {
               no (0),
               yes (1)
               }
   MAX-ACCESS  read-only
   STATUS      current
   DESCRIPTION
      "Path: server.status.pppSessions.ipV6.addresses.flags.interfaceId

       Possibilities:
               no   (0)
               yes   (1)"
   ::= {sr1645v2PppoEPPPoEIpV6AddressesEntry 83951616}

sr1645v2PppoEPPPoEIpV6AddressesFlagsAnycast OBJECT-TYPE
   SYNTAX      INTEGER
               {
               no (0),
               yes (1)
               }
   MAX-ACCESS  read-only
   STATUS      current
   DESCRIPTION
      "Path: server.status.pppSessions.ipV6.addresses.flags.anycast

       Possibilities:
               no   (0)
               yes   (1)"
   ::= {sr1645v2PppoEPPPoEIpV6AddressesEntry 84017152}

sr1645v2PppoEPPPoEIpV6AddressesTimersValidLifeTime OBJECT-TYPE
   SYNTAX      TimeTicks
   MAX-ACCESS  read-only
   STATUS      current
   DESCRIPTION
      "Path: server.status.pppSessions.ipV6.addresses.timers.validLifeTime

       Time in centi-second."
   ::= {sr1645v2PppoEPPPoEIpV6AddressesEntry 100794368}

sr1645v2PppoEPPPoEIpV6AddressesTimersPrefLifeTime OBJECT-TYPE
   SYNTAX      TimeTicks
   MAX-ACCESS  read-only
   STATUS      current
   DESCRIPTION
      "Path: server.status.pppSessions.ipV6.addresses.timers.prefLifeTime

       Time in centi-second."
   ::= {sr1645v2PppoEPPPoEIpV6AddressesEntry 100728832}


sr1645v2PppoELog OBJECT IDENTIFIER ::= {sr1645v2PppoE 28}

sr1645v2PppoELogSSCTable OBJECT-TYPE
   SYNTAX      SEQUENCE OF Sr1645v2PppoELogEntry
   MAX-ACCESS  not-accessible
   STATUS      current
   DESCRIPTION
      "PPPoE server log table of events"
   ::= {sr1645v2PppoELog 1}

sr1645v2PppoELogEntry OBJECT-TYPE
   SYNTAX      Sr1645v2PppoELogEntry
   MAX-ACCESS  not-accessible
   STATUS      current
   DESCRIPTION
      ""
   INDEX      { sr1645v2PppoELogTableIx }
   ::= {sr1645v2PppoELogSSCTable 1}

Sr1645v2PppoELogEntry ::=
   SEQUENCE
      {
      sr1645v2PppoELogTableIx
         TableIndex,
      sr1645v2PppoELogDate
         DisplayString,
      sr1645v2PppoELogSysUptime
         TimeTicks,
      sr1645v2PppoELogInterface
         DisplayString,
      sr1645v2PppoELogMacAddress
         OCTET STRING,
      sr1645v2PppoELogSessionId
         Gauge32,
      sr1645v2PppoELogEvent
         INTEGER
      }

sr1645v2PppoELogTableIx OBJECT-TYPE
   SYNTAX      TableIndex
   MAX-ACCESS  not-accessible
   STATUS      current
   DESCRIPTION
      ""
   ::= {sr1645v2PppoELogEntry 11}

sr1645v2PppoELogDate OBJECT-TYPE
   SYNTAX      DisplayString
   MAX-ACCESS  read-only
   STATUS      current
   DESCRIPTION
      "Path: server.status.log.date"
   ::= {sr1645v2PppoELogEntry 16777216}

sr1645v2PppoELogSysUptime OBJECT-TYPE
   SYNTAX      TimeTicks
   MAX-ACCESS  read-only
   STATUS      current
   DESCRIPTION
      "Path: server.status.log.sysUptime

       Time in centi-second."
   ::= {sr1645v2PppoELogEntry 33554432}

sr1645v2PppoELogInterface OBJECT-TYPE
   SYNTAX      DisplayString
   MAX-ACCESS  read-only
   STATUS      current
   DESCRIPTION
      "Path: server.status.log.interface"
   ::= {sr1645v2PppoELogEntry 50331648}

sr1645v2PppoELogMacAddress OBJECT-TYPE
   SYNTAX      OCTET STRING
   MAX-ACCESS  read-only
   STATUS      current
   DESCRIPTION
      "Path: server.status.log.macAddress

       MAC address."
   ::= {sr1645v2PppoELogEntry 67108864}

sr1645v2PppoELogSessionId OBJECT-TYPE
   SYNTAX      Gauge32
   MAX-ACCESS  read-only
   STATUS      current
   DESCRIPTION
      "Path: server.status.log.sessionId

       32 bit unsigned gauge value."
   ::= {sr1645v2PppoELogEntry 83886080}

sr1645v2PppoELogEvent OBJECT-TYPE
   SYNTAX      INTEGER
               {
               noseventsrecordedsyet (0),
               pADIsreceivedsbutsallssessionssinsuse (1),
               pADIsreceivedsbutsallssessionssforsthissMACsinsuse (2),
               pADIsreceivedsPADOssent (3),
               pADIsreceivedsbutsnosserviceNamestagsfound (4),
               pADRsreceivedsPADSssentscreatingssesssion (5),
               pADRsreceivedsnosmatchsfound (6),
               pADTsreceivedsremovingssession (7),
               pADTsreceivedsnosmatchsfound (8),
               unknownscodesreceived (9),
               removingssessionsunablestoscompletesdiscoverysphase (10),
               removingssessionspppssessionsabortedsorstimedsout (11),
               removingssessionsauthenticationsfailure (12),
               removingssessionscarrierslost (13),
               discardingsdataspacketsillegalssessionsIDsvalues0 (14),
               removingssessionslinksmonitoringsfailed (15),
               removingssessionsipcpsfailuresnosipsaddress (16),
               discardingsPADIPADRspacketsinvalidsserversconfig (17),
               pADIsreceivedsbutsserviceNamesnotssupported (18),
               removingssessionsPADTsreceived (19),
               removingssessionsLCPsDownsevent (20)
               }
   MAX-ACCESS  read-only
   STATUS      current
   DESCRIPTION
      "Path: server.status.log.event

       Possibilities:
               No event recorded yet   (0)
               PADI received but all sessions in use   (1)
               PADI received but all sessions for this MAC in use   (2)
               PADI received, PADO sent   (3)
               PADI received but no serviceName tag found   (4)
               PADR received, PADS sent, creating sesssion   (5)
               PADR received, no match found   (6)
               PADT received, removing session   (7)
               PADT received, no match found   (8)
               Unknown code received   (9)
               Removing session, unable to complete discovery phase   (10)
               Removing session, ppp session aborted or timed out   (11)
               Removing session, authentication failure   (12)
               Removing session, carrier lost   (13)
               Discarding data packet, illegal session ID value 0   (14)
               Removing session, link monitoring failed   (15)
               Removing session, ipcp failure, no ip address   (16)
               Discarding PADI/PADR packet, invalid server config   (17)
               PADI received but serviceName not supported   (18)
               Removing session, PADT received   (19)
               Removing session, LCP Down event   (20)"
   ::= {sr1645v2PppoELogEntry 100663296}



pr1645v2PppoE OBJECT IDENTIFIER ::= {r1645v2PppoE 12}


pr1645v2PppoEPPPoE OBJECT IDENTIFIER ::= {pr1645v2PppoE 27}

pr1645v2PppoEPPPoESSCTable OBJECT-TYPE
   SYNTAX      SEQUENCE OF Pr1645v2PppoEPPPoEEntry
   MAX-ACCESS  not-accessible
   STATUS      current
   DESCRIPTION
      ""
   ::= {pr1645v2PppoEPPPoE 1}

pr1645v2PppoEPPPoEEntry OBJECT-TYPE
   SYNTAX      Pr1645v2PppoEPPPoEEntry
   MAX-ACCESS  not-accessible
   STATUS      current
   DESCRIPTION
      ""
   INDEX      { pr1645v2PppoEPPPoETableIx }
   ::= {pr1645v2PppoEPPPoESSCTable 1}

Pr1645v2PppoEPPPoEEntry ::=
   SEQUENCE
      {
      pr1645v2PppoEPPPoETableIx
         TableIndex,
      pr1645v2PppoEPPPoEName
         DisplayString,
      pr1645v2PppoEPPPoEMCInOctets
         Counter64,
      pr1645v2PppoEPPPoEMCInUcast
         Counter64,
      pr1645v2PppoEPPPoEMCInNUcastPkts
         Counter64,
      pr1645v2PppoEPPPoEMCInBcastPkts
         Counter64,
      pr1645v2PppoEPPPoEMCInMcastPkts
         Counter64,
      pr1645v2PppoEPPPoEMCInDiscards
         Counter64,
      pr1645v2PppoEPPPoEMCInErrors
         Counter64,
      pr1645v2PppoEPPPoEMCInUnknownProtos
         Counter64,
      pr1645v2PppoEPPPoEMCInDropEx
         Counter64,
      pr1645v2PppoEPPPoEMCInDropNoMac
         Counter64,
      pr1645v2PppoEPPPoEMCInDropNUCast
         Counter64,
      pr1645v2PppoEPPPoEMCInDropFilter
         Counter64,
      pr1645v2PppoEPPPoEMCInBandwidth15sec
         Integer32,
      pr1645v2PppoEPPPoEMCInBandwidth30sec
         Integer32,
      pr1645v2PppoEPPPoEMCInBandwidth1min
         Integer32,
      pr1645v2PppoEPPPoEMCInBandwidth2min
         Integer32,
      pr1645v2PppoEPPPoEMCInBandwidth5min
         Integer32,
      pr1645v2PppoEPPPoEMCOutOctets
         Counter64,
      pr1645v2PppoEPPPoEMCOutUcastPkts
         Counter64,
      pr1645v2PppoEPPPoEMCOutNUcastPkts
         Counter64,
      pr1645v2PppoEPPPoEMCOutBcastPkts
         Counter64,
      pr1645v2PppoEPPPoEMCOutMcastPkts
         Counter64,
      pr1645v2PppoEPPPoEMCOutDiscards
         Counter64,
      pr1645v2PppoEPPPoEMCOutErrors
         Counter64,
      pr1645v2PppoEPPPoEMCOutQLen
         Counter32,
      pr1645v2PppoEPPPoEMCOutDropEx
         Counter64,
      pr1645v2PppoEPPPoEMCOutDropNoArp
         Counter64,
      pr1645v2PppoEPPPoEMCOutDropFilter
         Counter64,
      pr1645v2PppoEPPPoEMCOutBandwidth15sec
         Integer32,
      pr1645v2PppoEPPPoEMCOutBandwidth30sec
         Integer32,
      pr1645v2PppoEPPPoEMCOutBandwidth1min
         Integer32,
      pr1645v2PppoEPPPoEMCOutBandwidth2min
         Integer32,
      pr1645v2PppoEPPPoEMCOutBandwidth5min
         Integer32,
      pr1645v2PppoEPPPoELinkMonitoringRequestsSent
         Gauge32,
      pr1645v2PppoEPPPoELinkMonitoringRepliesRcvd
         Gauge32,
      pr1645v2PppoEPPPoELinkMonitoringRequestsRcvd
         Gauge32,
      pr1645v2PppoEPPPoELinkMonitoringRepliesSent
         Gauge32
      }

pr1645v2PppoEPPPoETableIx OBJECT-TYPE
   SYNTAX      TableIndex
   MAX-ACCESS  not-accessible
   STATUS      current
   DESCRIPTION
      ""
   ::= {pr1645v2PppoEPPPoEEntry 11}

pr1645v2PppoEPPPoEName OBJECT-TYPE
   SYNTAX      DisplayString
   MAX-ACCESS  read-only
   STATUS      current
   DESCRIPTION
      "Path: server.performance.pppSessions.name"
   ::= {pr1645v2PppoEPPPoEEntry 16777216}

pr1645v2PppoEPPPoEMCInOctets OBJECT-TYPE
   SYNTAX      Counter64
   MAX-ACCESS  read-only
   STATUS      current
   DESCRIPTION
      "Path: server.performance.pppSessions.mibCounters.ifInOctets

       64 bit unsigned wrappable counter."
   ::= {pr1645v2PppoEPPPoEEntry 40697856}

pr1645v2PppoEPPPoEMCInUcast OBJECT-TYPE
   SYNTAX      Counter64
   MAX-ACCESS  read-only
   STATUS      current
   DESCRIPTION
      "Path: server.performance.pppSessions.mibCounters.ifInUcastPkts

       64 bit unsigned wrappable counter."
   ::= {pr1645v2PppoEPPPoEEntry 40763392}

pr1645v2PppoEPPPoEMCInNUcastPkts OBJECT-TYPE
   SYNTAX      Counter64
   MAX-ACCESS  read-only
   STATUS      current
   DESCRIPTION
      "Path: server.performance.pppSessions.mibCounters.ifInNUcastPkts

       64 bit unsigned wrappable counter."
   ::= {pr1645v2PppoEPPPoEEntry 40828928}

pr1645v2PppoEPPPoEMCInBcastPkts OBJECT-TYPE
   SYNTAX      Counter64
   MAX-ACCESS  read-only
   STATUS      current
   DESCRIPTION
      "Path: server.performance.pppSessions.mibCounters.ifInBcastPkts

       64 bit unsigned wrappable counter."
   ::= {pr1645v2PppoEPPPoEEntry 47382528}

pr1645v2PppoEPPPoEMCInMcastPkts OBJECT-TYPE
   SYNTAX      Counter64
   MAX-ACCESS  read-only
   STATUS      current
   DESCRIPTION
      "Path: server.performance.pppSessions.mibCounters.ifInMcastPkts

       64 bit unsigned wrappable counter."
   ::= {pr1645v2PppoEPPPoEEntry 48037888}

pr1645v2PppoEPPPoEMCInDiscards OBJECT-TYPE
   SYNTAX      Counter64
   MAX-ACCESS  read-only
   STATUS      current
   DESCRIPTION
      "Path: server.performance.pppSessions.mibCounters.ifInDiscards

       64 bit unsigned wrappable counter."
   ::= {pr1645v2PppoEPPPoEEntry 40894464}

pr1645v2PppoEPPPoEMCInErrors OBJECT-TYPE
   SYNTAX      Counter64
   MAX-ACCESS  read-only
   STATUS      current
   DESCRIPTION
      "Path: server.performance.pppSessions.mibCounters.ifInErrors

       64 bit unsigned wrappable counter."
   ::= {pr1645v2PppoEPPPoEEntry 40960000}

pr1645v2PppoEPPPoEMCInUnknownProtos OBJECT-TYPE
   SYNTAX      Counter64
   MAX-ACCESS  read-only
   STATUS      current
   DESCRIPTION
      "Path: server.performance.pppSessions.mibCounters.ifInUnknownProtos

       64 bit unsigned wrappable counter."
   ::= {pr1645v2PppoEPPPoEEntry 41025536}

pr1645v2PppoEPPPoEMCInDropEx OBJECT-TYPE
   SYNTAX      Counter64
   MAX-ACCESS  read-only
   STATUS      current
   DESCRIPTION
      "Path: server.performance.pppSessions.mibCounters.ifInDropLevelExceeded

       64 bit unsigned wrappable counter."
   ::= {pr1645v2PppoEPPPoEEntry 42074112}

pr1645v2PppoEPPPoEMCInDropNoMac OBJECT-TYPE
   SYNTAX      Counter64
   MAX-ACCESS  read-only
   STATUS      current
   DESCRIPTION
      "Path: server.performance.pppSessions.mibCounters.ifInDiscardsNoMacFit

       64 bit unsigned wrappable counter."
   ::= {pr1645v2PppoEPPPoEEntry 42270720}

pr1645v2PppoEPPPoEMCInDropNUCast OBJECT-TYPE
   SYNTAX      Counter64
   MAX-ACCESS  read-only
   STATUS      current
   DESCRIPTION
      "Path: server.performance.pppSessions.mibCounters.ifInDiscardsNUCast

       64 bit unsigned wrappable counter."
   ::= {pr1645v2PppoEPPPoEEntry 42467328}

pr1645v2PppoEPPPoEMCInDropFilter OBJECT-TYPE
   SYNTAX      Counter64
   MAX-ACCESS  read-only
   STATUS      current
   DESCRIPTION
      "Path: server.performance.pppSessions.mibCounters.ifInDiscardsFilter

       64 bit unsigned wrappable counter."
   ::= {pr1645v2PppoEPPPoEEntry 42532864}

pr1645v2PppoEPPPoEMCInBandwidth15sec OBJECT-TYPE
   SYNTAX      Integer32
   MAX-ACCESS  read-only
   STATUS      current
   DESCRIPTION
      "Path: server.performance.pppSessions.mibCounters.ifInBandwidth.15sec

       unit name = bps
       formula = 8 * ; 8 /"
   ::= {pr1645v2PppoEPPPoEEntry 45417728}

pr1645v2PppoEPPPoEMCInBandwidth30sec OBJECT-TYPE
   SYNTAX      Integer32
   MAX-ACCESS  read-only
   STATUS      current
   DESCRIPTION
      "Path: server.performance.pppSessions.mibCounters.ifInBandwidth.30sec

       unit name = bps
       formula = 8 * ; 8 /"
   ::= {pr1645v2PppoEPPPoEEntry 45419008}

pr1645v2PppoEPPPoEMCInBandwidth1min OBJECT-TYPE
   SYNTAX      Integer32
   MAX-ACCESS  read-only
   STATUS      current
   DESCRIPTION
      "Path: server.performance.pppSessions.mibCounters.ifInBandwidth.1min

       unit name = bps
       formula = 8 * ; 8 /"
   ::= {pr1645v2PppoEPPPoEEntry 45421568}

pr1645v2PppoEPPPoEMCInBandwidth2min OBJECT-TYPE
   SYNTAX      Integer32
   MAX-ACCESS  read-only
   STATUS      current
   DESCRIPTION
      "Path: server.performance.pppSessions.mibCounters.ifInBandwidth.2min

       unit name = bps
       formula = 8 * ; 8 /"
   ::= {pr1645v2PppoEPPPoEEntry 45426688}

pr1645v2PppoEPPPoEMCInBandwidth5min OBJECT-TYPE
   SYNTAX      Integer32
   MAX-ACCESS  read-only
   STATUS      current
   DESCRIPTION
      "Path: server.performance.pppSessions.mibCounters.ifInBandwidth.5min

       unit name = bps
       formula = 8 * ; 8 /"
   ::= {pr1645v2PppoEPPPoEEntry 45442048}

pr1645v2PppoEPPPoEMCOutOctets OBJECT-TYPE
   SYNTAX      Counter64
   MAX-ACCESS  read-only
   STATUS      current
   DESCRIPTION
      "Path: server.performance.pppSessions.mibCounters.ifOutOctets

       64 bit unsigned wrappable counter."
   ::= {pr1645v2PppoEPPPoEEntry 41091072}

pr1645v2PppoEPPPoEMCOutUcastPkts OBJECT-TYPE
   SYNTAX      Counter64
   MAX-ACCESS  read-only
   STATUS      current
   DESCRIPTION
      "Path: server.performance.pppSessions.mibCounters.ifOutUcastPkts

       64 bit unsigned wrappable counter."
   ::= {pr1645v2PppoEPPPoEEntry 41156608}

pr1645v2PppoEPPPoEMCOutNUcastPkts OBJECT-TYPE
   SYNTAX      Counter64
   MAX-ACCESS  read-only
   STATUS      current
   DESCRIPTION
      "Path: server.performance.pppSessions.mibCounters.ifOutNUcastPkts

       64 bit unsigned wrappable counter."
   ::= {pr1645v2PppoEPPPoEEntry 41222144}

pr1645v2PppoEPPPoEMCOutBcastPkts OBJECT-TYPE
   SYNTAX      Counter64
   MAX-ACCESS  read-only
   STATUS      current
   DESCRIPTION
      "Path: server.performance.pppSessions.mibCounters.ifOutBcastPkts

       64 bit unsigned wrappable counter."
   ::= {pr1645v2PppoEPPPoEEntry 47775744}

pr1645v2PppoEPPPoEMCOutMcastPkts OBJECT-TYPE
   SYNTAX      Counter64
   MAX-ACCESS  read-only
   STATUS      current
   DESCRIPTION
      "Path: server.performance.pppSessions.mibCounters.ifOutMcastPkts

       64 bit unsigned wrappable counter."
   ::= {pr1645v2PppoEPPPoEEntry 48431104}

pr1645v2PppoEPPPoEMCOutDiscards OBJECT-TYPE
   SYNTAX      Counter64
   MAX-ACCESS  read-only
   STATUS      current
   DESCRIPTION
      "Path: server.performance.pppSessions.mibCounters.ifOutDiscards

       64 bit unsigned wrappable counter."
   ::= {pr1645v2PppoEPPPoEEntry 41287680}

pr1645v2PppoEPPPoEMCOutErrors OBJECT-TYPE
   SYNTAX      Counter64
   MAX-ACCESS  read-only
   STATUS      current
   DESCRIPTION
      "Path: server.performance.pppSessions.mibCounters.ifOutErrors

       64 bit unsigned wrappable counter."
   ::= {pr1645v2PppoEPPPoEEntry 41353216}

pr1645v2PppoEPPPoEMCOutQLen OBJECT-TYPE
   SYNTAX      Counter32
   MAX-ACCESS  read-only
   STATUS      current
   DESCRIPTION
      "Path: server.performance.pppSessions.mibCounters.ifOutQLen

       32 bit unsigned wrappable counter."
   ::= {pr1645v2PppoEPPPoEEntry 41418752}

pr1645v2PppoEPPPoEMCOutDropEx OBJECT-TYPE
   SYNTAX      Counter64
   MAX-ACCESS  read-only
   STATUS      current
   DESCRIPTION
      "Path: server.performance.pppSessions.mibCounters.ifOutDropLevelExceeded

       64 bit unsigned wrappable counter."
   ::= {pr1645v2PppoEPPPoEEntry 41484288}

pr1645v2PppoEPPPoEMCOutDropNoArp OBJECT-TYPE
   SYNTAX      Counter64
   MAX-ACCESS  read-only
   STATUS      current
   DESCRIPTION
      "Path: server.performance.pppSessions.mibCounters.ifOutDiscardsNoArp

       64 bit unsigned wrappable counter."
   ::= {pr1645v2PppoEPPPoEEntry 42336256}

pr1645v2PppoEPPPoEMCOutDropFilter OBJECT-TYPE
   SYNTAX      Counter64
   MAX-ACCESS  read-only
   STATUS      current
   DESCRIPTION
      "Path: server.performance.pppSessions.mibCounters.ifOutDiscardsFilter

       64 bit unsigned wrappable counter."
   ::= {pr1645v2PppoEPPPoEEntry 42598400}

pr1645v2PppoEPPPoEMCOutBandwidth15sec OBJECT-TYPE
   SYNTAX      Integer32
   MAX-ACCESS  read-only
   STATUS      current
   DESCRIPTION
      "Path: server.performance.pppSessions.mibCounters.ifOutBandwidth.15sec

       unit name = bps
       formula = 8 * ; 8 /"
   ::= {pr1645v2PppoEPPPoEEntry 45483264}

pr1645v2PppoEPPPoEMCOutBandwidth30sec OBJECT-TYPE
   SYNTAX      Integer32
   MAX-ACCESS  read-only
   STATUS      current
   DESCRIPTION
      "Path: server.performance.pppSessions.mibCounters.ifOutBandwidth.30sec

       unit name = bps
       formula = 8 * ; 8 /"
   ::= {pr1645v2PppoEPPPoEEntry 45484544}

pr1645v2PppoEPPPoEMCOutBandwidth1min OBJECT-TYPE
   SYNTAX      Integer32
   MAX-ACCESS  read-only
   STATUS      current
   DESCRIPTION
      "Path: server.performance.pppSessions.mibCounters.ifOutBandwidth.1min

       unit name = bps
       formula = 8 * ; 8 /"
   ::= {pr1645v2PppoEPPPoEEntry 45487104}

pr1645v2PppoEPPPoEMCOutBandwidth2min OBJECT-TYPE
   SYNTAX      Integer32
   MAX-ACCESS  read-only
   STATUS      current
   DESCRIPTION
      "Path: server.performance.pppSessions.mibCounters.ifOutBandwidth.2min

       unit name = bps
       formula = 8 * ; 8 /"
   ::= {pr1645v2PppoEPPPoEEntry 45492224}

pr1645v2PppoEPPPoEMCOutBandwidth5min OBJECT-TYPE
   SYNTAX      Integer32
   MAX-ACCESS  read-only
   STATUS      current
   DESCRIPTION
      "Path: server.performance.pppSessions.mibCounters.ifOutBandwidth.5min

       unit name = bps
       formula = 8 * ; 8 /"
   ::= {pr1645v2PppoEPPPoEEntry 45507584}

pr1645v2PppoEPPPoELinkMonitoringRequestsSent OBJECT-TYPE
   SYNTAX      Gauge32
   MAX-ACCESS  read-only
   STATUS      current
   DESCRIPTION
      "Path: server.performance.pppSessions.linkMonitoring.requestsSent

       32 bit unsigned gauge value."
   ::= {pr1645v2PppoEPPPoEEntry 50397184}

pr1645v2PppoEPPPoELinkMonitoringRepliesRcvd OBJECT-TYPE
   SYNTAX      Gauge32
   MAX-ACCESS  read-only
   STATUS      current
   DESCRIPTION
      "Path: server.performance.pppSessions.linkMonitoring.repliesRcvd

       32 bit unsigned gauge value."
   ::= {pr1645v2PppoEPPPoEEntry 50462720}

pr1645v2PppoEPPPoELinkMonitoringRequestsRcvd OBJECT-TYPE
   SYNTAX      Gauge32
   MAX-ACCESS  read-only
   STATUS      current
   DESCRIPTION
      "Path: server.performance.pppSessions.linkMonitoring.requestsRcvd

       32 bit unsigned gauge value."
   ::= {pr1645v2PppoEPPPoEEntry 50528256}

pr1645v2PppoEPPPoELinkMonitoringRepliesSent OBJECT-TYPE
   SYNTAX      Gauge32
   MAX-ACCESS  read-only
   STATUS      current
   DESCRIPTION
      "Path: server.performance.pppSessions.linkMonitoring.repliesSent

       32 bit unsigned gauge value."
   ::= {pr1645v2PppoEPPPoEEntry 50593792}

pr1645v2PppoEPPPoEMCH2P OBJECT-TYPE
   SYNTAX      SEQUENCE OF Pr1645v2PppoEPPPoEMCH2PEntry
   MAX-ACCESS  not-accessible
   STATUS      current
   DESCRIPTION
      ""
   ::= {pr1645v2PppoEPPPoE 41549824}

pr1645v2PppoEPPPoEMCH2PEntry OBJECT-TYPE
   SYNTAX      Pr1645v2PppoEPPPoEMCH2PEntry
   MAX-ACCESS  not-accessible
   STATUS      current
   DESCRIPTION
      ""
   INDEX      { pr1645v2PppoEPPPoETableIx,
                pr1645v2PppoEPPPoEMCH2PTableIx }
   ::= {pr1645v2PppoEPPPoEMCH2P 1}

Pr1645v2PppoEPPPoEMCH2PEntry ::=
   SEQUENCE
      {
      pr1645v2PppoEPPPoEMCH2PTableIx
         TableIndex,
      pr1645v2PppoEPPPoEMCH2PSysUpTime
         TimeTicks,
      pr1645v2PppoEPPPoEMCH2PIfUpTime
         TimeTicks,
      pr1645v2PppoEPPPoEMCH2PIfStatChanges
         Counter32,
      pr1645v2PppoEPPPoEMCH2PIfInOctets
         Counter64,
      pr1645v2PppoEPPPoEMCH2PIfInUCPkts
         Counter64,
      pr1645v2PppoEPPPoEMCH2PIfInNUCPkts
         Counter64,
      pr1645v2PppoEPPPoEMCH2PIfInBCPkts
         Counter64,
      pr1645v2PppoEPPPoEMCH2PIfInMCPkts
         Counter64,
      pr1645v2PppoEPPPoEMCH2PIfInDiscards
         Counter64,
      pr1645v2PppoEPPPoEMCH2PIfInErrors
         Counter64,
      pr1645v2PppoEPPPoEMCH2PIfInUnkwn
         Counter64,
      pr1645v2PppoEPPPoEMCH2PInDropEx
         Counter64,
      pr1645v2PppoEPPPoEMCH2PInDropNoMac
         Counter64,
      pr1645v2PppoEPPPoEMCH2PInDropNUCast
         Counter64,
      pr1645v2PppoEPPPoEMCH2PInDropFilter
         Counter64,
      pr1645v2PppoEPPPoEMCH2PIfInBandwidth
         Integer32,
      pr1645v2PppoEPPPoEMCH2PIfOutOctets
         Counter64,
      pr1645v2PppoEPPPoEMCH2PIfOutUCPkts
         Counter64,
      pr1645v2PppoEPPPoEMCH2PIfOutNUCPkts
         Counter64,
      pr1645v2PppoEPPPoEMCH2PIfOutBCPkts
         Counter64,
      pr1645v2PppoEPPPoEMCH2PIfOutMCPkts
         Counter64,
      pr1645v2PppoEPPPoEMCH2PIfOutDiscards
         Counter64,
      pr1645v2PppoEPPPoEMCH2PIfOutErrors
         Counter64,
      pr1645v2PppoEPPPoEMCH2POutDropEx
         Counter64,
      pr1645v2PppoEPPPoEMCH2POutDropNoArp
         Counter64,
      pr1645v2PppoEPPPoEMCH2POutDropFilter
         Counter64,
      pr1645v2PppoEPPPoEMCH2PIfOutBandwidth
         Integer32,
      pr1645v2PppoEPPPoEMCH2PIfErrSec
         Counter32
      }

pr1645v2PppoEPPPoEMCH2PTableIx OBJECT-TYPE
   SYNTAX      TableIndex
   MAX-ACCESS  not-accessible
   STATUS      current
   DESCRIPTION
      ""
   ::= {pr1645v2PppoEPPPoEMCH2PEntry 11}

pr1645v2PppoEPPPoEMCH2PSysUpTime OBJECT-TYPE
   SYNTAX      TimeTicks
   MAX-ACCESS  read-only
   STATUS      current
   DESCRIPTION
      "Path: server.performance.pppSessions.mibCounters.h2Performance.sysUpTime

       Time in centi-second."
   ::= {pr1645v2PppoEPPPoEMCH2PEntry 16777216}

pr1645v2PppoEPPPoEMCH2PIfUpTime OBJECT-TYPE
   SYNTAX      TimeTicks
   MAX-ACCESS  read-only
   STATUS      current
   DESCRIPTION
      "Path: server.performance.pppSessions.mibCounters.h2Performance.ifUpTime

       Time in centi-second."
   ::= {pr1645v2PppoEPPPoEMCH2PEntry 33554432}

pr1645v2PppoEPPPoEMCH2PIfStatChanges OBJECT-TYPE
   SYNTAX      Counter32
   MAX-ACCESS  read-only
   STATUS      current
   DESCRIPTION
      "Path: server.performance.pppSessions.mibCounters.h2Performance.ifStatusChanges

       32 bit unsigned wrappable counter."
   ::= {pr1645v2PppoEPPPoEMCH2PEntry 50331648}

pr1645v2PppoEPPPoEMCH2PIfInOctets OBJECT-TYPE
   SYNTAX      Counter64
   MAX-ACCESS  read-only
   STATUS      current
   DESCRIPTION
      "Path: server.performance.pppSessions.mibCounters.h2Performance.ifInOctets

       64 bit unsigned wrappable counter."
   ::= {pr1645v2PppoEPPPoEMCH2PEntry 67108864}

pr1645v2PppoEPPPoEMCH2PIfInUCPkts OBJECT-TYPE
   SYNTAX      Counter64
   MAX-ACCESS  read-only
   STATUS      current
   DESCRIPTION
      "Path: server.performance.pppSessions.mibCounters.h2Performance.ifInUcastPkts

       64 bit unsigned wrappable counter."
   ::= {pr1645v2PppoEPPPoEMCH2PEntry 83886080}

pr1645v2PppoEPPPoEMCH2PIfInNUCPkts OBJECT-TYPE
   SYNTAX      Counter64
   MAX-ACCESS  read-only
   STATUS      current
   DESCRIPTION
      "Path: server.performance.pppSessions.mibCounters.h2Performance.ifInNUcastPkts

       64 bit unsigned wrappable counter."
   ::= {pr1645v2PppoEPPPoEMCH2PEntry 100663296}

pr1645v2PppoEPPPoEMCH2PIfInBCPkts OBJECT-TYPE
   SYNTAX      Counter64
   MAX-ACCESS  read-only
   STATUS      current
   DESCRIPTION
      "Path: server.performance.pppSessions.mibCounters.h2Performance.ifInBcastPkts

       64 bit unsigned wrappable counter."
   ::= {pr1645v2PppoEPPPoEMCH2PEntry 419430400}

pr1645v2PppoEPPPoEMCH2PIfInMCPkts OBJECT-TYPE
   SYNTAX      Counter64
   MAX-ACCESS  read-only
   STATUS      current
   DESCRIPTION
      "Path: server.performance.pppSessions.mibCounters.h2Performance.ifInMcastPkts

       64 bit unsigned wrappable counter."
   ::= {pr1645v2PppoEPPPoEMCH2PEntry 436207616}

pr1645v2PppoEPPPoEMCH2PIfInDiscards OBJECT-TYPE
   SYNTAX      Counter64
   MAX-ACCESS  read-only
   STATUS      current
   DESCRIPTION
      "Path: server.performance.pppSessions.mibCounters.h2Performance.ifInDiscards

       64 bit unsigned wrappable counter."
   ::= {pr1645v2PppoEPPPoEMCH2PEntry 117440512}

pr1645v2PppoEPPPoEMCH2PIfInErrors OBJECT-TYPE
   SYNTAX      Counter64
   MAX-ACCESS  read-only
   STATUS      current
   DESCRIPTION
      "Path: server.performance.pppSessions.mibCounters.h2Performance.ifInErrors

       64 bit unsigned wrappable counter."
   ::= {pr1645v2PppoEPPPoEMCH2PEntry 134217728}

pr1645v2PppoEPPPoEMCH2PIfInUnkwn OBJECT-TYPE
   SYNTAX      Counter64
   MAX-ACCESS  read-only
   STATUS      current
   DESCRIPTION
      "Path: server.performance.pppSessions.mibCounters.h2Performance.ifInUnknownProtos

       64 bit unsigned wrappable counter."
   ::= {pr1645v2PppoEPPPoEMCH2PEntry 150994944}

pr1645v2PppoEPPPoEMCH2PInDropEx OBJECT-TYPE
   SYNTAX      Counter64
   MAX-ACCESS  read-only
   STATUS      current
   DESCRIPTION
      "Path: server.performance.pppSessions.mibCounters.h2Performance.ifInDropLevelExceeded

       64 bit unsigned wrappable counter."
   ::= {pr1645v2PppoEPPPoEMCH2PEntry 335544320}

pr1645v2PppoEPPPoEMCH2PInDropNoMac OBJECT-TYPE
   SYNTAX      Counter64
   MAX-ACCESS  read-only
   STATUS      current
   DESCRIPTION
      "Path: server.performance.pppSessions.mibCounters.h2Performance.fInDiscardsNoMacFit

       64 bit unsigned wrappable counter."
   ::= {pr1645v2PppoEPPPoEMCH2PEntry 301989888}

pr1645v2PppoEPPPoEMCH2PInDropNUCast OBJECT-TYPE
   SYNTAX      Counter64
   MAX-ACCESS  read-only
   STATUS      current
   DESCRIPTION
      "Path: server.performance.pppSessions.mibCounters.h2Performance.fInDiscardsNUCast

       64 bit unsigned wrappable counter."
   ::= {pr1645v2PppoEPPPoEMCH2PEntry 318767104}

pr1645v2PppoEPPPoEMCH2PInDropFilter OBJECT-TYPE
   SYNTAX      Counter64
   MAX-ACCESS  read-only
   STATUS      current
   DESCRIPTION
      "Path: server.performance.pppSessions.mibCounters.h2Performance.fInDiscardsFilter

       64 bit unsigned wrappable counter."
   ::= {pr1645v2PppoEPPPoEMCH2PEntry 385875968}

pr1645v2PppoEPPPoEMCH2PIfInBandwidth OBJECT-TYPE
   SYNTAX      Integer32
   MAX-ACCESS  read-only
   STATUS      current
   DESCRIPTION
      "Path: server.performance.pppSessions.mibCounters.h2Performance.ifInBandwidth

       unit name = bps
       formula = 8 * ; 8 /"
   ::= {pr1645v2PppoEPPPoEMCH2PEntry 268435456}

pr1645v2PppoEPPPoEMCH2PIfOutOctets OBJECT-TYPE
   SYNTAX      Counter64
   MAX-ACCESS  read-only
   STATUS      current
   DESCRIPTION
      "Path: server.performance.pppSessions.mibCounters.h2Performance.ifOutOctets

       64 bit unsigned wrappable counter."
   ::= {pr1645v2PppoEPPPoEMCH2PEntry 167772160}

pr1645v2PppoEPPPoEMCH2PIfOutUCPkts OBJECT-TYPE
   SYNTAX      Counter64
   MAX-ACCESS  read-only
   STATUS      current
   DESCRIPTION
      "Path: server.performance.pppSessions.mibCounters.h2Performance.ifOutUcastPkts

       64 bit unsigned wrappable counter."
   ::= {pr1645v2PppoEPPPoEMCH2PEntry 184549376}

pr1645v2PppoEPPPoEMCH2PIfOutNUCPkts OBJECT-TYPE
   SYNTAX      Counter64
   MAX-ACCESS  read-only
   STATUS      current
   DESCRIPTION
      "Path: server.performance.pppSessions.mibCounters.h2Performance.ifOutNUcastPkts

       64 bit unsigned wrappable counter."
   ::= {pr1645v2PppoEPPPoEMCH2PEntry 201326592}

pr1645v2PppoEPPPoEMCH2PIfOutBCPkts OBJECT-TYPE
   SYNTAX      Counter64
   MAX-ACCESS  read-only
   STATUS      current
   DESCRIPTION
      "Path: server.performance.pppSessions.mibCounters.h2Performance.ifOutBcastPkts

       64 bit unsigned wrappable counter."
   ::= {pr1645v2PppoEPPPoEMCH2PEntry 452984832}

pr1645v2PppoEPPPoEMCH2PIfOutMCPkts OBJECT-TYPE
   SYNTAX      Counter64
   MAX-ACCESS  read-only
   STATUS      current
   DESCRIPTION
      "Path: server.performance.pppSessions.mibCounters.h2Performance.ifOutMcastPkts

       64 bit unsigned wrappable counter."
   ::= {pr1645v2PppoEPPPoEMCH2PEntry 469762048}

pr1645v2PppoEPPPoEMCH2PIfOutDiscards OBJECT-TYPE
   SYNTAX      Counter64
   MAX-ACCESS  read-only
   STATUS      current
   DESCRIPTION
      "Path: server.performance.pppSessions.mibCounters.h2Performance.ifOutDiscards

       64 bit unsigned wrappable counter."
   ::= {pr1645v2PppoEPPPoEMCH2PEntry 218103808}

pr1645v2PppoEPPPoEMCH2PIfOutErrors OBJECT-TYPE
   SYNTAX      Counter64
   MAX-ACCESS  read-only
   STATUS      current
   DESCRIPTION
      "Path: server.performance.pppSessions.mibCounters.h2Performance.ifOutErrors

       64 bit unsigned wrappable counter."
   ::= {pr1645v2PppoEPPPoEMCH2PEntry 234881024}

pr1645v2PppoEPPPoEMCH2POutDropEx OBJECT-TYPE
   SYNTAX      Counter64
   MAX-ACCESS  read-only
   STATUS      current
   DESCRIPTION
      "Path: server.performance.pppSessions.mibCounters.h2Performance.ifOutDropLevelExceeded

       64 bit unsigned wrappable counter."
   ::= {pr1645v2PppoEPPPoEMCH2PEntry 352321536}

pr1645v2PppoEPPPoEMCH2POutDropNoArp OBJECT-TYPE
   SYNTAX      Counter64
   MAX-ACCESS  read-only
   STATUS      current
   DESCRIPTION
      "Path: server.performance.pppSessions.mibCounters.h2Performance.ifOutDiscardsNoArp

       64 bit unsigned wrappable counter."
   ::= {pr1645v2PppoEPPPoEMCH2PEntry 369098752}

pr1645v2PppoEPPPoEMCH2POutDropFilter OBJECT-TYPE
   SYNTAX      Counter64
   MAX-ACCESS  read-only
   STATUS      current
   DESCRIPTION
      "Path: server.performance.pppSessions.mibCounters.h2Performance.ifOutDiscardsFilter

       64 bit unsigned wrappable counter."
   ::= {pr1645v2PppoEPPPoEMCH2PEntry 402653184}

pr1645v2PppoEPPPoEMCH2PIfOutBandwidth OBJECT-TYPE
   SYNTAX      Integer32
   MAX-ACCESS  read-only
   STATUS      current
   DESCRIPTION
      "Path: server.performance.pppSessions.mibCounters.h2Performance.ifOutBandwidth

       unit name = bps
       formula = 8 * ; 8 /"
   ::= {pr1645v2PppoEPPPoEMCH2PEntry 285212672}

pr1645v2PppoEPPPoEMCH2PIfErrSec OBJECT-TYPE
   SYNTAX      Counter32
   MAX-ACCESS  read-only
   STATUS      current
   DESCRIPTION
      "Path: server.performance.pppSessions.mibCounters.h2Performance.ifErrSec

       32 bit unsigned wrappable counter."
   ::= {pr1645v2PppoEPPPoEMCH2PEntry 251658240}

pr1645v2PppoEPPPoEMCH24P OBJECT-TYPE
   SYNTAX      SEQUENCE OF Pr1645v2PppoEPPPoEMCH24PEntry
   MAX-ACCESS  not-accessible
   STATUS      current
   DESCRIPTION
      ""
   ::= {pr1645v2PppoEPPPoE 41615360}

pr1645v2PppoEPPPoEMCH24PEntry OBJECT-TYPE
   SYNTAX      Pr1645v2PppoEPPPoEMCH24PEntry
   MAX-ACCESS  not-accessible
   STATUS      current
   DESCRIPTION
      ""
   INDEX      { pr1645v2PppoEPPPoETableIx,
                pr1645v2PppoEPPPoEMCH24PTableIx }
   ::= {pr1645v2PppoEPPPoEMCH24P 1}

Pr1645v2PppoEPPPoEMCH24PEntry ::=
   SEQUENCE
      {
      pr1645v2PppoEPPPoEMCH24PTableIx
         TableIndex,
      pr1645v2PppoEPPPoEMCH24PSysUpTime
         TimeTicks,
      pr1645v2PppoEPPPoEMCH24PIfUpTime
         TimeTicks,
      pr1645v2PppoEPPPoEMCH24PIfStatChanges
         Counter32,
      pr1645v2PppoEPPPoEMCH24PIfInOctets
         Counter64,
      pr1645v2PppoEPPPoEMCH24PIfInUCPkts
         Counter64,
      pr1645v2PppoEPPPoEMCH24PIfInNUCPkts
         Counter64,
      pr1645v2PppoEPPPoEMCH24PIfInBCPkts
         Counter64,
      pr1645v2PppoEPPPoEMCH24PIfInMCPkts
         Counter64,
      pr1645v2PppoEPPPoEMCH24PIfInDiscards
         Counter64,
      pr1645v2PppoEPPPoEMCH24PIfInErrors
         Counter64,
      pr1645v2PppoEPPPoEMCH24PIfInUnkwn
         Counter64,
      pr1645v2PppoEPPPoEMCH24PInDropEx
         Counter64,
      pr1645v2PppoEPPPoEMCH24PInDropNoMac
         Counter64,
      pr1645v2PppoEPPPoEMCH24PInDropNUCast
         Counter64,
      pr1645v2PppoEPPPoEMCH24PInDropFilter
         Counter64,
      pr1645v2PppoEPPPoEMCH24PIfInBandwidth
         Integer32,
      pr1645v2PppoEPPPoEMCH24PIfOutOctets
         Counter64,
      pr1645v2PppoEPPPoEMCH24PIfOutUCPkts
         Counter64,
      pr1645v2PppoEPPPoEMCH24PIfOutNUCPkts
         Counter64,
      pr1645v2PppoEPPPoEMCH24PIfOutBCPkts
         Counter64,
      pr1645v2PppoEPPPoEMCH24PIfOutMCPkts
         Counter64,
      pr1645v2PppoEPPPoEMCH24PIfOutDiscards
         Counter64,
      pr1645v2PppoEPPPoEMCH24PIfOutErrors
         Counter64,
      pr1645v2PppoEPPPoEMCH24POutDropEx
         Counter64,
      pr1645v2PppoEPPPoEMCH24POutDropNoArp
         Counter64,
      pr1645v2PppoEPPPoEMCH24POutDropFilter
         Counter64,
      pr1645v2PppoEPPPoEMCH24PIfOutBandwidth
         Integer32,
      pr1645v2PppoEPPPoEMCH24PIfErrSec
         Counter32
      }

pr1645v2PppoEPPPoEMCH24PTableIx OBJECT-TYPE
   SYNTAX      TableIndex
   MAX-ACCESS  not-accessible
   STATUS      current
   DESCRIPTION
      ""
   ::= {pr1645v2PppoEPPPoEMCH24PEntry 11}

pr1645v2PppoEPPPoEMCH24PSysUpTime OBJECT-TYPE
   SYNTAX      TimeTicks
   MAX-ACCESS  read-only
   STATUS      current
   DESCRIPTION
      "Path: server.performance.pppSessions.mibCounters.h24Performance.sysUpTime

       Time in centi-second."
   ::= {pr1645v2PppoEPPPoEMCH24PEntry 16777216}

pr1645v2PppoEPPPoEMCH24PIfUpTime OBJECT-TYPE
   SYNTAX      TimeTicks
   MAX-ACCESS  read-only
   STATUS      current
   DESCRIPTION
      "Path: server.performance.pppSessions.mibCounters.h24Performance.ifUpTime

       Time in centi-second."
   ::= {pr1645v2PppoEPPPoEMCH24PEntry 33554432}

pr1645v2PppoEPPPoEMCH24PIfStatChanges OBJECT-TYPE
   SYNTAX      Counter32
   MAX-ACCESS  read-only
   STATUS      current
   DESCRIPTION
      "Path: server.performance.pppSessions.mibCounters.h24Performance.ifStatusChanges

       32 bit unsigned wrappable counter."
   ::= {pr1645v2PppoEPPPoEMCH24PEntry 50331648}

pr1645v2PppoEPPPoEMCH24PIfInOctets OBJECT-TYPE
   SYNTAX      Counter64
   MAX-ACCESS  read-only
   STATUS      current
   DESCRIPTION
      "Path: server.performance.pppSessions.mibCounters.h24Performance.ifInOctets

       64 bit unsigned wrappable counter."
   ::= {pr1645v2PppoEPPPoEMCH24PEntry 67108864}

pr1645v2PppoEPPPoEMCH24PIfInUCPkts OBJECT-TYPE
   SYNTAX      Counter64
   MAX-ACCESS  read-only
   STATUS      current
   DESCRIPTION
      "Path: server.performance.pppSessions.mibCounters.h24Performance.ifInUcastPkts

       64 bit unsigned wrappable counter."
   ::= {pr1645v2PppoEPPPoEMCH24PEntry 83886080}

pr1645v2PppoEPPPoEMCH24PIfInNUCPkts OBJECT-TYPE
   SYNTAX      Counter64
   MAX-ACCESS  read-only
   STATUS      current
   DESCRIPTION
      "Path: server.performance.pppSessions.mibCounters.h24Performance.ifInNUcastPkts

       64 bit unsigned wrappable counter."
   ::= {pr1645v2PppoEPPPoEMCH24PEntry 100663296}

pr1645v2PppoEPPPoEMCH24PIfInBCPkts OBJECT-TYPE
   SYNTAX      Counter64
   MAX-ACCESS  read-only
   STATUS      current
   DESCRIPTION
      "Path: server.performance.pppSessions.mibCounters.h24Performance.ifInBcastPkts

       64 bit unsigned wrappable counter."
   ::= {pr1645v2PppoEPPPoEMCH24PEntry 419430400}

pr1645v2PppoEPPPoEMCH24PIfInMCPkts OBJECT-TYPE
   SYNTAX      Counter64
   MAX-ACCESS  read-only
   STATUS      current
   DESCRIPTION
      "Path: server.performance.pppSessions.mibCounters.h24Performance.ifInMcastPkts

       64 bit unsigned wrappable counter."
   ::= {pr1645v2PppoEPPPoEMCH24PEntry 436207616}

pr1645v2PppoEPPPoEMCH24PIfInDiscards OBJECT-TYPE
   SYNTAX      Counter64
   MAX-ACCESS  read-only
   STATUS      current
   DESCRIPTION
      "Path: server.performance.pppSessions.mibCounters.h24Performance.ifInDiscards

       64 bit unsigned wrappable counter."
   ::= {pr1645v2PppoEPPPoEMCH24PEntry 117440512}

pr1645v2PppoEPPPoEMCH24PIfInErrors OBJECT-TYPE
   SYNTAX      Counter64
   MAX-ACCESS  read-only
   STATUS      current
   DESCRIPTION
      "Path: server.performance.pppSessions.mibCounters.h24Performance.ifInErrors

       64 bit unsigned wrappable counter."
   ::= {pr1645v2PppoEPPPoEMCH24PEntry 134217728}

pr1645v2PppoEPPPoEMCH24PIfInUnkwn OBJECT-TYPE
   SYNTAX      Counter64
   MAX-ACCESS  read-only
   STATUS      current
   DESCRIPTION
      "Path: server.performance.pppSessions.mibCounters.h24Performance.ifInUnknownProtos

       64 bit unsigned wrappable counter."
   ::= {pr1645v2PppoEPPPoEMCH24PEntry 150994944}

pr1645v2PppoEPPPoEMCH24PInDropEx OBJECT-TYPE
   SYNTAX      Counter64
   MAX-ACCESS  read-only
   STATUS      current
   DESCRIPTION
      "Path: server.performance.pppSessions.mibCounters.h24Performance.ifInDropLevelExceeded

       64 bit unsigned wrappable counter."
   ::= {pr1645v2PppoEPPPoEMCH24PEntry 335544320}

pr1645v2PppoEPPPoEMCH24PInDropNoMac OBJECT-TYPE
   SYNTAX      Counter64
   MAX-ACCESS  read-only
   STATUS      current
   DESCRIPTION
      "Path: server.performance.pppSessions.mibCounters.h24Performance.fInDiscardsNoMacFit

       64 bit unsigned wrappable counter."
   ::= {pr1645v2PppoEPPPoEMCH24PEntry 301989888}

pr1645v2PppoEPPPoEMCH24PInDropNUCast OBJECT-TYPE
   SYNTAX      Counter64
   MAX-ACCESS  read-only
   STATUS      current
   DESCRIPTION
      "Path: server.performance.pppSessions.mibCounters.h24Performance.fInDiscardsNUCast

       64 bit unsigned wrappable counter."
   ::= {pr1645v2PppoEPPPoEMCH24PEntry 318767104}

pr1645v2PppoEPPPoEMCH24PInDropFilter OBJECT-TYPE
   SYNTAX      Counter64
   MAX-ACCESS  read-only
   STATUS      current
   DESCRIPTION
      "Path: server.performance.pppSessions.mibCounters.h24Performance.fInDiscardsFilter

       64 bit unsigned wrappable counter."
   ::= {pr1645v2PppoEPPPoEMCH24PEntry 385875968}

pr1645v2PppoEPPPoEMCH24PIfInBandwidth OBJECT-TYPE
   SYNTAX      Integer32
   MAX-ACCESS  read-only
   STATUS      current
   DESCRIPTION
      "Path: server.performance.pppSessions.mibCounters.h24Performance.ifInBandwidth

       unit name = bps
       formula = 8 * ; 8 /"
   ::= {pr1645v2PppoEPPPoEMCH24PEntry 268435456}

pr1645v2PppoEPPPoEMCH24PIfOutOctets OBJECT-TYPE
   SYNTAX      Counter64
   MAX-ACCESS  read-only
   STATUS      current
   DESCRIPTION
      "Path: server.performance.pppSessions.mibCounters.h24Performance.ifOutOctets

       64 bit unsigned wrappable counter."
   ::= {pr1645v2PppoEPPPoEMCH24PEntry 167772160}

pr1645v2PppoEPPPoEMCH24PIfOutUCPkts OBJECT-TYPE
   SYNTAX      Counter64
   MAX-ACCESS  read-only
   STATUS      current
   DESCRIPTION
      "Path: server.performance.pppSessions.mibCounters.h24Performance.ifOutUcastPkts

       64 bit unsigned wrappable counter."
   ::= {pr1645v2PppoEPPPoEMCH24PEntry 184549376}

pr1645v2PppoEPPPoEMCH24PIfOutNUCPkts OBJECT-TYPE
   SYNTAX      Counter64
   MAX-ACCESS  read-only
   STATUS      current
   DESCRIPTION
      "Path: server.performance.pppSessions.mibCounters.h24Performance.ifOutNUcastPkts

       64 bit unsigned wrappable counter."
   ::= {pr1645v2PppoEPPPoEMCH24PEntry 201326592}

pr1645v2PppoEPPPoEMCH24PIfOutBCPkts OBJECT-TYPE
   SYNTAX      Counter64
   MAX-ACCESS  read-only
   STATUS      current
   DESCRIPTION
      "Path: server.performance.pppSessions.mibCounters.h24Performance.ifOutBcastPkts

       64 bit unsigned wrappable counter."
   ::= {pr1645v2PppoEPPPoEMCH24PEntry 452984832}

pr1645v2PppoEPPPoEMCH24PIfOutMCPkts OBJECT-TYPE
   SYNTAX      Counter64
   MAX-ACCESS  read-only
   STATUS      current
   DESCRIPTION
      "Path: server.performance.pppSessions.mibCounters.h24Performance.ifOutMcastPkts

       64 bit unsigned wrappable counter."
   ::= {pr1645v2PppoEPPPoEMCH24PEntry 469762048}

pr1645v2PppoEPPPoEMCH24PIfOutDiscards OBJECT-TYPE
   SYNTAX      Counter64
   MAX-ACCESS  read-only
   STATUS      current
   DESCRIPTION
      "Path: server.performance.pppSessions.mibCounters.h24Performance.ifOutDiscards

       64 bit unsigned wrappable counter."
   ::= {pr1645v2PppoEPPPoEMCH24PEntry 218103808}

pr1645v2PppoEPPPoEMCH24PIfOutErrors OBJECT-TYPE
   SYNTAX      Counter64
   MAX-ACCESS  read-only
   STATUS      current
   DESCRIPTION
      "Path: server.performance.pppSessions.mibCounters.h24Performance.ifOutErrors

       64 bit unsigned wrappable counter."
   ::= {pr1645v2PppoEPPPoEMCH24PEntry 234881024}

pr1645v2PppoEPPPoEMCH24POutDropEx OBJECT-TYPE
   SYNTAX      Counter64
   MAX-ACCESS  read-only
   STATUS      current
   DESCRIPTION
      "Path: server.performance.pppSessions.mibCounters.h24Performance.ifOutDropLevelExceeded

       64 bit unsigned wrappable counter."
   ::= {pr1645v2PppoEPPPoEMCH24PEntry 352321536}

pr1645v2PppoEPPPoEMCH24POutDropNoArp OBJECT-TYPE
   SYNTAX      Counter64
   MAX-ACCESS  read-only
   STATUS      current
   DESCRIPTION
      "Path: server.performance.pppSessions.mibCounters.h24Performance.ifOutDiscardsNoArp

       64 bit unsigned wrappable counter."
   ::= {pr1645v2PppoEPPPoEMCH24PEntry 369098752}

pr1645v2PppoEPPPoEMCH24POutDropFilter OBJECT-TYPE
   SYNTAX      Counter64
   MAX-ACCESS  read-only
   STATUS      current
   DESCRIPTION
      "Path: server.performance.pppSessions.mibCounters.h24Performance.ifOutDiscardsFilter

       64 bit unsigned wrappable counter."
   ::= {pr1645v2PppoEPPPoEMCH24PEntry 402653184}

pr1645v2PppoEPPPoEMCH24PIfOutBandwidth OBJECT-TYPE
   SYNTAX      Integer32
   MAX-ACCESS  read-only
   STATUS      current
   DESCRIPTION
      "Path: server.performance.pppSessions.mibCounters.h24Performance.ifOutBandwidth

       unit name = bps
       formula = 8 * ; 8 /"
   ::= {pr1645v2PppoEPPPoEMCH24PEntry 285212672}

pr1645v2PppoEPPPoEMCH24PIfErrSec OBJECT-TYPE
   SYNTAX      Counter32
   MAX-ACCESS  read-only
   STATUS      current
   DESCRIPTION
      "Path: server.performance.pppSessions.mibCounters.h24Performance.ifErrSec

       32 bit unsigned wrappable counter."
   ::= {pr1645v2PppoEPPPoEMCH24PEntry 251658240}

pr1645v2PppoEPPPoEMCD7P OBJECT-TYPE
   SYNTAX      SEQUENCE OF Pr1645v2PppoEPPPoEMCD7PEntry
   MAX-ACCESS  not-accessible
   STATUS      current
   DESCRIPTION
      ""
   ::= {pr1645v2PppoEPPPoE 41680896}

pr1645v2PppoEPPPoEMCD7PEntry OBJECT-TYPE
   SYNTAX      Pr1645v2PppoEPPPoEMCD7PEntry
   MAX-ACCESS  not-accessible
   STATUS      current
   DESCRIPTION
      ""
   INDEX      { pr1645v2PppoEPPPoETableIx,
                pr1645v2PppoEPPPoEMCD7PTableIx }
   ::= {pr1645v2PppoEPPPoEMCD7P 1}

Pr1645v2PppoEPPPoEMCD7PEntry ::=
   SEQUENCE
      {
      pr1645v2PppoEPPPoEMCD7PTableIx
         TableIndex,
      pr1645v2PppoEPPPoEMCD7PSysUpTime
         TimeTicks,
      pr1645v2PppoEPPPoEMCD7PIfUpTime
         TimeTicks,
      pr1645v2PppoEPPPoEMCD7PIfStatChanges
         Counter32,
      pr1645v2PppoEPPPoEMCD7PIfInOctets
         Counter64,
      pr1645v2PppoEPPPoEMCD7PIfInUCPkts
         Counter64,
      pr1645v2PppoEPPPoEMCD7PIfInNUCPkts
         Counter64,
      pr1645v2PppoEPPPoEMCD7PIfInBCPkts
         Counter64,
      pr1645v2PppoEPPPoEMCD7PIfInMCPkts
         Counter64,
      pr1645v2PppoEPPPoEMCD7PIfInDiscards
         Counter64,
      pr1645v2PppoEPPPoEMCD7PIfInErrors
         Counter64,
      pr1645v2PppoEPPPoEMCD7PIfInUnkwn
         Counter64,
      pr1645v2PppoEPPPoEMCD7PInDropEx
         Counter64,
      pr1645v2PppoEPPPoEMCD7PInDropNoMac
         Counter64,
      pr1645v2PppoEPPPoEMCD7PInDropNUCast
         Counter64,
      pr1645v2PppoEPPPoEMCD7PInDropFilter
         Counter64,
      pr1645v2PppoEPPPoEMCD7PIfInBandwidth
         Integer32,
      pr1645v2PppoEPPPoEMCD7PIfOutOctets
         Counter64,
      pr1645v2PppoEPPPoEMCD7PIfOutUCPkts
         Counter64,
      pr1645v2PppoEPPPoEMCD7PIfOutNUCPkts
         Counter64,
      pr1645v2PppoEPPPoEMCD7PIfOutBCPkts
         Counter64,
      pr1645v2PppoEPPPoEMCD7PIfOutMCPkts
         Counter64,
      pr1645v2PppoEPPPoEMCD7PIfOutDiscards
         Counter64,
      pr1645v2PppoEPPPoEMCD7PIfOutErrors
         Counter64,
      pr1645v2PppoEPPPoEMCD7POutDropEx
         Counter64,
      pr1645v2PppoEPPPoEMCD7POutDropNoArp
         Counter64,
      pr1645v2PppoEPPPoEMCD7POutDropFilter
         Counter64,
      pr1645v2PppoEPPPoEMCD7PIfOutBandwidth
         Integer32,
      pr1645v2PppoEPPPoEMCD7PIfErrSec
         Counter32
      }

pr1645v2PppoEPPPoEMCD7PTableIx OBJECT-TYPE
   SYNTAX      TableIndex
   MAX-ACCESS  not-accessible
   STATUS      current
   DESCRIPTION
      ""
   ::= {pr1645v2PppoEPPPoEMCD7PEntry 11}

pr1645v2PppoEPPPoEMCD7PSysUpTime OBJECT-TYPE
   SYNTAX      TimeTicks
   MAX-ACCESS  read-only
   STATUS      current
   DESCRIPTION
      "Path: server.performance.pppSessions.mibCounters.d7Performance.sysUpTime

       Time in centi-second."
   ::= {pr1645v2PppoEPPPoEMCD7PEntry 16777216}

pr1645v2PppoEPPPoEMCD7PIfUpTime OBJECT-TYPE
   SYNTAX      TimeTicks
   MAX-ACCESS  read-only
   STATUS      current
   DESCRIPTION
      "Path: server.performance.pppSessions.mibCounters.d7Performance.ifUpTime

       Time in centi-second."
   ::= {pr1645v2PppoEPPPoEMCD7PEntry 33554432}

pr1645v2PppoEPPPoEMCD7PIfStatChanges OBJECT-TYPE
   SYNTAX      Counter32
   MAX-ACCESS  read-only
   STATUS      current
   DESCRIPTION
      "Path: server.performance.pppSessions.mibCounters.d7Performance.ifStatusChanges

       32 bit unsigned wrappable counter."
   ::= {pr1645v2PppoEPPPoEMCD7PEntry 50331648}

pr1645v2PppoEPPPoEMCD7PIfInOctets OBJECT-TYPE
   SYNTAX      Counter64
   MAX-ACCESS  read-only
   STATUS      current
   DESCRIPTION
      "Path: server.performance.pppSessions.mibCounters.d7Performance.ifInOctets

       64 bit unsigned wrappable counter."
   ::= {pr1645v2PppoEPPPoEMCD7PEntry 67108864}

pr1645v2PppoEPPPoEMCD7PIfInUCPkts OBJECT-TYPE
   SYNTAX      Counter64
   MAX-ACCESS  read-only
   STATUS      current
   DESCRIPTION
      "Path: server.performance.pppSessions.mibCounters.d7Performance.ifInUcastPkts

       64 bit unsigned wrappable counter."
   ::= {pr1645v2PppoEPPPoEMCD7PEntry 83886080}

pr1645v2PppoEPPPoEMCD7PIfInNUCPkts OBJECT-TYPE
   SYNTAX      Counter64
   MAX-ACCESS  read-only
   STATUS      current
   DESCRIPTION
      "Path: server.performance.pppSessions.mibCounters.d7Performance.ifInNUcastPkts

       64 bit unsigned wrappable counter."
   ::= {pr1645v2PppoEPPPoEMCD7PEntry 100663296}

pr1645v2PppoEPPPoEMCD7PIfInBCPkts OBJECT-TYPE
   SYNTAX      Counter64
   MAX-ACCESS  read-only
   STATUS      current
   DESCRIPTION
      "Path: server.performance.pppSessions.mibCounters.d7Performance.ifInBcastPkts

       64 bit unsigned wrappable counter."
   ::= {pr1645v2PppoEPPPoEMCD7PEntry 419430400}

pr1645v2PppoEPPPoEMCD7PIfInMCPkts OBJECT-TYPE
   SYNTAX      Counter64
   MAX-ACCESS  read-only
   STATUS      current
   DESCRIPTION
      "Path: server.performance.pppSessions.mibCounters.d7Performance.ifInMcastPkts

       64 bit unsigned wrappable counter."
   ::= {pr1645v2PppoEPPPoEMCD7PEntry 436207616}

pr1645v2PppoEPPPoEMCD7PIfInDiscards OBJECT-TYPE
   SYNTAX      Counter64
   MAX-ACCESS  read-only
   STATUS      current
   DESCRIPTION
      "Path: server.performance.pppSessions.mibCounters.d7Performance.ifInDiscards

       64 bit unsigned wrappable counter."
   ::= {pr1645v2PppoEPPPoEMCD7PEntry 117440512}

pr1645v2PppoEPPPoEMCD7PIfInErrors OBJECT-TYPE
   SYNTAX      Counter64
   MAX-ACCESS  read-only
   STATUS      current
   DESCRIPTION
      "Path: server.performance.pppSessions.mibCounters.d7Performance.ifInErrors

       64 bit unsigned wrappable counter."
   ::= {pr1645v2PppoEPPPoEMCD7PEntry 134217728}

pr1645v2PppoEPPPoEMCD7PIfInUnkwn OBJECT-TYPE
   SYNTAX      Counter64
   MAX-ACCESS  read-only
   STATUS      current
   DESCRIPTION
      "Path: server.performance.pppSessions.mibCounters.d7Performance.ifInUnknownProtos

       64 bit unsigned wrappable counter."
   ::= {pr1645v2PppoEPPPoEMCD7PEntry 150994944}

pr1645v2PppoEPPPoEMCD7PInDropEx OBJECT-TYPE
   SYNTAX      Counter64
   MAX-ACCESS  read-only
   STATUS      current
   DESCRIPTION
      "Path: server.performance.pppSessions.mibCounters.d7Performance.ifInDropLevelExceeded

       64 bit unsigned wrappable counter."
   ::= {pr1645v2PppoEPPPoEMCD7PEntry 335544320}

pr1645v2PppoEPPPoEMCD7PInDropNoMac OBJECT-TYPE
   SYNTAX      Counter64
   MAX-ACCESS  read-only
   STATUS      current
   DESCRIPTION
      "Path: server.performance.pppSessions.mibCounters.d7Performance.fInDiscardsNoMacFit

       64 bit unsigned wrappable counter."
   ::= {pr1645v2PppoEPPPoEMCD7PEntry 301989888}

pr1645v2PppoEPPPoEMCD7PInDropNUCast OBJECT-TYPE
   SYNTAX      Counter64
   MAX-ACCESS  read-only
   STATUS      current
   DESCRIPTION
      "Path: server.performance.pppSessions.mibCounters.d7Performance.fInDiscardsNUCast

       64 bit unsigned wrappable counter."
   ::= {pr1645v2PppoEPPPoEMCD7PEntry 318767104}

pr1645v2PppoEPPPoEMCD7PInDropFilter OBJECT-TYPE
   SYNTAX      Counter64
   MAX-ACCESS  read-only
   STATUS      current
   DESCRIPTION
      "Path: server.performance.pppSessions.mibCounters.d7Performance.fInDiscardsFilter

       64 bit unsigned wrappable counter."
   ::= {pr1645v2PppoEPPPoEMCD7PEntry 385875968}

pr1645v2PppoEPPPoEMCD7PIfInBandwidth OBJECT-TYPE
   SYNTAX      Integer32
   MAX-ACCESS  read-only
   STATUS      current
   DESCRIPTION
      "Path: server.performance.pppSessions.mibCounters.d7Performance.ifInBandwidth

       unit name = bps
       formula = 8 * ; 8 /"
   ::= {pr1645v2PppoEPPPoEMCD7PEntry 268435456}

pr1645v2PppoEPPPoEMCD7PIfOutOctets OBJECT-TYPE
   SYNTAX      Counter64
   MAX-ACCESS  read-only
   STATUS      current
   DESCRIPTION
      "Path: server.performance.pppSessions.mibCounters.d7Performance.ifOutOctets

       64 bit unsigned wrappable counter."
   ::= {pr1645v2PppoEPPPoEMCD7PEntry 167772160}

pr1645v2PppoEPPPoEMCD7PIfOutUCPkts OBJECT-TYPE
   SYNTAX      Counter64
   MAX-ACCESS  read-only
   STATUS      current
   DESCRIPTION
      "Path: server.performance.pppSessions.mibCounters.d7Performance.ifOutUcastPkts

       64 bit unsigned wrappable counter."
   ::= {pr1645v2PppoEPPPoEMCD7PEntry 184549376}

pr1645v2PppoEPPPoEMCD7PIfOutNUCPkts OBJECT-TYPE
   SYNTAX      Counter64
   MAX-ACCESS  read-only
   STATUS      current
   DESCRIPTION
      "Path: server.performance.pppSessions.mibCounters.d7Performance.ifOutNUcastPkts

       64 bit unsigned wrappable counter."
   ::= {pr1645v2PppoEPPPoEMCD7PEntry 201326592}

pr1645v2PppoEPPPoEMCD7PIfOutBCPkts OBJECT-TYPE
   SYNTAX      Counter64
   MAX-ACCESS  read-only
   STATUS      current
   DESCRIPTION
      "Path: server.performance.pppSessions.mibCounters.d7Performance.ifOutBcastPkts

       64 bit unsigned wrappable counter."
   ::= {pr1645v2PppoEPPPoEMCD7PEntry 452984832}

pr1645v2PppoEPPPoEMCD7PIfOutMCPkts OBJECT-TYPE
   SYNTAX      Counter64
   MAX-ACCESS  read-only
   STATUS      current
   DESCRIPTION
      "Path: server.performance.pppSessions.mibCounters.d7Performance.ifOutMcastPkts

       64 bit unsigned wrappable counter."
   ::= {pr1645v2PppoEPPPoEMCD7PEntry 469762048}

pr1645v2PppoEPPPoEMCD7PIfOutDiscards OBJECT-TYPE
   SYNTAX      Counter64
   MAX-ACCESS  read-only
   STATUS      current
   DESCRIPTION
      "Path: server.performance.pppSessions.mibCounters.d7Performance.ifOutDiscards

       64 bit unsigned wrappable counter."
   ::= {pr1645v2PppoEPPPoEMCD7PEntry 218103808}

pr1645v2PppoEPPPoEMCD7PIfOutErrors OBJECT-TYPE
   SYNTAX      Counter64
   MAX-ACCESS  read-only
   STATUS      current
   DESCRIPTION
      "Path: server.performance.pppSessions.mibCounters.d7Performance.ifOutErrors

       64 bit unsigned wrappable counter."
   ::= {pr1645v2PppoEPPPoEMCD7PEntry 234881024}

pr1645v2PppoEPPPoEMCD7POutDropEx OBJECT-TYPE
   SYNTAX      Counter64
   MAX-ACCESS  read-only
   STATUS      current
   DESCRIPTION
      "Path: server.performance.pppSessions.mibCounters.d7Performance.ifOutDropLevelExceeded

       64 bit unsigned wrappable counter."
   ::= {pr1645v2PppoEPPPoEMCD7PEntry 352321536}

pr1645v2PppoEPPPoEMCD7POutDropNoArp OBJECT-TYPE
   SYNTAX      Counter64
   MAX-ACCESS  read-only
   STATUS      current
   DESCRIPTION
      "Path: server.performance.pppSessions.mibCounters.d7Performance.ifOutDiscardsNoArp

       64 bit unsigned wrappable counter."
   ::= {pr1645v2PppoEPPPoEMCD7PEntry 369098752}

pr1645v2PppoEPPPoEMCD7POutDropFilter OBJECT-TYPE
   SYNTAX      Counter64
   MAX-ACCESS  read-only
   STATUS      current
   DESCRIPTION
      "Path: server.performance.pppSessions.mibCounters.d7Performance.ifOutDiscardsFilter

       64 bit unsigned wrappable counter."
   ::= {pr1645v2PppoEPPPoEMCD7PEntry 402653184}

pr1645v2PppoEPPPoEMCD7PIfOutBandwidth OBJECT-TYPE
   SYNTAX      Integer32
   MAX-ACCESS  read-only
   STATUS      current
   DESCRIPTION
      "Path: server.performance.pppSessions.mibCounters.d7Performance.ifOutBandwidth

       unit name = bps
       formula = 8 * ; 8 /"
   ::= {pr1645v2PppoEPPPoEMCD7PEntry 285212672}

pr1645v2PppoEPPPoEMCD7PIfErrSec OBJECT-TYPE
   SYNTAX      Counter32
   MAX-ACCESS  read-only
   STATUS      current
   DESCRIPTION
      "Path: server.performance.pppSessions.mibCounters.d7Performance.ifErrSec

       32 bit unsigned wrappable counter."
   ::= {pr1645v2PppoEPPPoEMCD7PEntry 251658240}


pr1645v2PppoETotalSessionsSetup OBJECT-TYPE
   SYNTAX      Gauge32
   MAX-ACCESS  read-only
   STATUS      current
   DESCRIPTION
      "Path: server.performance.totalSessionsSetup
       Info: mode

       32 bit unsigned gauge value."
   ::= {pr1645v2PppoE 20}


pr1645v2PppoEActiveSessions OBJECT-TYPE
   SYNTAX      Gauge32
   MAX-ACCESS  read-only
   STATUS      current
   DESCRIPTION
      "Path: server.performance.activeSessions
       Info: mode

       32 bit unsigned gauge value."
   ::= {pr1645v2PppoE 21}


pr1645v2PppoEErrors OBJECT IDENTIFIER ::= {pr1645v2PppoE 22}

pr1645v2PppoEErrorsSSC OBJECT IDENTIFIER ::= {pr1645v2PppoEErrors 1}

pr1645v2PppoEErrorsEntry OBJECT IDENTIFIER ::= {pr1645v2PppoEErrorsSSC 1}

pr1645v2PppoEErrorsMse OBJECT-TYPE
   SYNTAX      Gauge32
   MAX-ACCESS  read-only
   STATUS      current
   DESCRIPTION
      "Path: server.performance.errors.maxSessionsExceeded

       32 bit unsigned gauge value."
   ::= {pr1645v2PppoEErrorsEntry 16777216}

pr1645v2PppoEErrorsSme OBJECT-TYPE
   SYNTAX      Gauge32
   MAX-ACCESS  read-only
   STATUS      current
   DESCRIPTION
      "Path: server.performance.errors.sessionsPerMacExceeded

       32 bit unsigned gauge value."
   ::= {pr1645v2PppoEErrorsEntry 33554432}

pr1645v2PppoEErrorsDf OBJECT-TYPE
   SYNTAX      Gauge32
   MAX-ACCESS  read-only
   STATUS      current
   DESCRIPTION
      "Path: server.performance.errors.discoveryFailed

       32 bit unsigned gauge value."
   ::= {pr1645v2PppoEErrorsEntry 50331648}

pr1645v2PppoEErrorsPsf OBJECT-TYPE
   SYNTAX      Gauge32
   MAX-ACCESS  read-only
   STATUS      current
   DESCRIPTION
      "Path: server.performance.errors.pppSetupFailed

       32 bit unsigned gauge value."
   ::= {pr1645v2PppoEErrorsEntry 67108864}

pr1645v2PppoEErrorsUc OBJECT-TYPE
   SYNTAX      Gauge32
   MAX-ACCESS  read-only
   STATUS      current
   DESCRIPTION
      "Path: server.performance.errors.unknownCode

       32 bit unsigned gauge value."
   ::= {pr1645v2PppoEErrorsEntry 83886080}



ar1645v2PppoE OBJECT IDENTIFIER ::= {r1645v2PppoE 16}


ar1645v2PppoEClearCounters OBJECT-TYPE
   SYNTAX      Integer32
   MAX-ACCESS  read-write
   STATUS      current
   DESCRIPTION
      "Path: server.actions.clearCounters
       Info: reset counters"
   ::= {ar1645v2PppoE 263}


ar1645v2PppoEClearLog OBJECT-TYPE
   SYNTAX      Integer32
   MAX-ACCESS  read-write
   STATUS      current
   DESCRIPTION
      "Path: server.actions.clearLog
       Info: clear PPPoE server log table of events"
   ::= {ar1645v2PppoE 29}



END
