OneAccess-R1646v2-4776-VxlBGIMVp DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2VxlBGIMVp OBJECT IDENTIFIER ::= {r1646Rootv2 4776}

r1646v2VxlBGIMVpMOProp OBJECT-TYPE
   SYNTAX      SEQUENCE OF R1646v2VxlBGIMVpMOPropEntry
   MAX-ACCESS  not-accessible
   STATUS      current
   DESCRIPTION
      ""
   ::= {r1646v2VxlBGIMVp 1}

r1646v2VxlBGIMVpMOPropEntry OBJECT-TYPE
   SYNTAX      R1646v2VxlBGIMVpMOPropEntry
   MAX-ACCESS  not-accessible
   STATUS      current
   DESCRIPTION
      ""
   INDEX      { r1646v2VxlBGIMVpMOPropGlobalIx }
   ::= {r1646v2VxlBGIMVpMOProp 1}

R1646v2VxlBGIMVpMOPropEntry ::=
   SEQUENCE
      {
      r1646v2VxlBGIMVpMOPropPath
         ContainmentPath,
      r1646v2VxlBGIMVpMOPropRev
         ObjectRevision,
      r1646v2VxlBGIMVpMOPropGlobalIx
         GlobalIndex
      }

r1646v2VxlBGIMVpMOPropPath OBJECT-TYPE
   SYNTAX      ContainmentPath
   MAX-ACCESS  read-only
   STATUS      current
   DESCRIPTION
      "Textual description of the containment tree from the instance of
       the root object down to the instance of the current object."
   ::= {r1646v2VxlBGIMVpMOPropEntry 3}

r1646v2VxlBGIMVpMOPropRev OBJECT-TYPE
   SYNTAX      ObjectRevision
   MAX-ACCESS  read-only
   STATUS      current
   DESCRIPTION
      "This value corresponds with the revision of the MANAGED OBJECT."
   ::= {r1646v2VxlBGIMVpMOPropEntry 4}

r1646v2VxlBGIMVpMOPropGlobalIx OBJECT-TYPE
   SYNTAX      GlobalIndex
   MAX-ACCESS  read-only
   STATUS      current
   DESCRIPTION
      "The value of the tlsCntTreeGlobalIndex of the MANAGED OBJECT."
   ::= {r1646v2VxlBGIMVpMOPropEntry 10}



er1646v2VxlBGIMVp OBJECT IDENTIFIER ::= {r1646v2VxlBGIMVp 11}


er1646v2VxlBGIMVpBridgeCache OBJECT IDENTIFIER ::= {er1646v2VxlBGIMVp 10}

er1646v2VxlBGIMVpBridgeCacheTable OBJECT-TYPE
   SYNTAX      SEQUENCE OF Er1646v2VxlBGIMVpBridgeCacheEntry
   MAX-ACCESS  not-accessible
   STATUS      current
   DESCRIPTION
      "used for bridgeCache"
   ::= {er1646v2VxlBGIMVpBridgeCache 1}

er1646v2VxlBGIMVpBridgeCacheEntry OBJECT-TYPE
   SYNTAX      Er1646v2VxlBGIMVpBridgeCacheEntry
   MAX-ACCESS  not-accessible
   STATUS      current
   DESCRIPTION
      ""
   INDEX      { er1646v2VxlBGIMVpBridgeCacheGlobalIx }
   ::= {er1646v2VxlBGIMVpBridgeCacheTable 1}

Er1646v2VxlBGIMVpBridgeCacheEntry ::=
   SEQUENCE
      {
      er1646v2VxlBGIMVpBridgeCacheGlobalIx
         GlobalIndex,
      er1646v2VxlBGIMVpBridgeCacheValue
         INTEGER
      }

er1646v2VxlBGIMVpBridgeCacheGlobalIx OBJECT-TYPE
   SYNTAX      GlobalIndex
   MAX-ACCESS  not-accessible
   STATUS      current
   DESCRIPTION
      "The value of the tlsCntTreeGlobalIndex of the MANAGED OBJECT."
   ::= {er1646v2VxlBGIMVpBridgeCacheEntry 10}

er1646v2VxlBGIMVpBridgeCacheValue OBJECT-TYPE
   SYNTAX      INTEGER
               {
               disabled (0),
               learning (1),
               switching (2)
               }
   MAX-ACCESS  read-write
   STATUS      current
   DESCRIPTION
      "Path: vxLanBridgeGroup.editConf.bridgeCache

       Possibilities:
               disabled   (0)
               learning   (1)
               switching   (2)"
   ::= {er1646v2VxlBGIMVpBridgeCacheEntry 2147483648}


er1646v2VxlBGIMVpMaxCacheSize OBJECT IDENTIFIER ::= {er1646v2VxlBGIMVp 38}

er1646v2VxlBGIMVpMaxCacheSizeTable OBJECT-TYPE
   SYNTAX      SEQUENCE OF Er1646v2VxlBGIMVpMaxCacheSizeEntry
   MAX-ACCESS  not-accessible
   STATUS      current
   DESCRIPTION
      "used for size of bridgeCache"
   ::= {er1646v2VxlBGIMVpMaxCacheSize 1}

er1646v2VxlBGIMVpMaxCacheSizeEntry OBJECT-TYPE
   SYNTAX      Er1646v2VxlBGIMVpMaxCacheSizeEntry
   MAX-ACCESS  not-accessible
   STATUS      current
   DESCRIPTION
      ""
   INDEX      { er1646v2VxlBGIMVpMaxCacheSizeGlobalIx }
   ::= {er1646v2VxlBGIMVpMaxCacheSizeTable 1}

Er1646v2VxlBGIMVpMaxCacheSizeEntry ::=
   SEQUENCE
      {
      er1646v2VxlBGIMVpMaxCacheSizeGlobalIx
         GlobalIndex,
      er1646v2VxlBGIMVpMaxCacheSizeValue
         INTEGER
      }

er1646v2VxlBGIMVpMaxCacheSizeGlobalIx OBJECT-TYPE
   SYNTAX      GlobalIndex
   MAX-ACCESS  not-accessible
   STATUS      current
   DESCRIPTION
      "The value of the tlsCntTreeGlobalIndex of the MANAGED OBJECT."
   ::= {er1646v2VxlBGIMVpMaxCacheSizeEntry 10}

er1646v2VxlBGIMVpMaxCacheSizeValue OBJECT-TYPE
   SYNTAX      INTEGER
               {
               unlimited (0)
               }
   MAX-ACCESS  read-write
   STATUS      current
   DESCRIPTION
      "Path: vxLanBridgeGroup.editConf.maxCacheSize

       Possibilities:
               unlimited   (0)"
   ::= {er1646v2VxlBGIMVpMaxCacheSizeEntry 2147483648}


er1646v2VxlBGIMVpStaticBridgeCache OBJECT IDENTIFIER ::= {er1646v2VxlBGIMVp 36}

er1646v2VxlBGIMVpStaticBridgeCacheSSCTable OBJECT-TYPE
   SYNTAX      SEQUENCE OF Er1646v2VxlBGIMVpStaticBridgeCacheEntry
   MAX-ACCESS  not-accessible
   STATUS      current
   DESCRIPTION
      "bridge cache"
   ::= {er1646v2VxlBGIMVpStaticBridgeCache 1}

er1646v2VxlBGIMVpStaticBridgeCacheEntry OBJECT-TYPE
   SYNTAX      Er1646v2VxlBGIMVpStaticBridgeCacheEntry
   MAX-ACCESS  not-accessible
   STATUS      current
   DESCRIPTION
      ""
   INDEX      { er1646v2VxlBGIMVpStaticBridgeCacheGlobalIx,
                er1646v2VxlBGIMVpStaticBridgeCacheTableIx }
   ::= {er1646v2VxlBGIMVpStaticBridgeCacheSSCTable 1}

Er1646v2VxlBGIMVpStaticBridgeCacheEntry ::=
   SEQUENCE
      {
      er1646v2VxlBGIMVpStaticBridgeCacheActions
         VariableLengthTableActions,
      er1646v2VxlBGIMVpStaticBridgeCacheGlobalIx
         GlobalIndex,
      er1646v2VxlBGIMVpStaticBridgeCacheTableIx
         TableIndex,
      er1646v2VxlBGIMVpStaticBridgeCacheIf
         DisplayString,
      er1646v2VxlBGIMVpStaticBridgeCacheMacAddress
         OCTET STRING,
      er1646v2VxlBGIMVpStaticBridgeCacheVlanId
         Integer32
      }

er1646v2VxlBGIMVpStaticBridgeCacheActions OBJECT-TYPE
   SYNTAX      VariableLengthTableActions
   MAX-ACCESS  read-write
   STATUS      current
   DESCRIPTION
      "By way of this field, some manipulations
       on this table may be performed."
   ::= {er1646v2VxlBGIMVpStaticBridgeCacheEntry 2}

er1646v2VxlBGIMVpStaticBridgeCacheGlobalIx OBJECT-TYPE
   SYNTAX      GlobalIndex
   MAX-ACCESS  not-accessible
   STATUS      current
   DESCRIPTION
      "The value of the tlsCntTreeGlobalIndex of the MANAGED OBJECT."
   ::= {er1646v2VxlBGIMVpStaticBridgeCacheEntry 10}

er1646v2VxlBGIMVpStaticBridgeCacheTableIx OBJECT-TYPE
   SYNTAX      TableIndex
   MAX-ACCESS  not-accessible
   STATUS      current
   DESCRIPTION
      ""
   ::= {er1646v2VxlBGIMVpStaticBridgeCacheEntry 11}

er1646v2VxlBGIMVpStaticBridgeCacheIf OBJECT-TYPE
   SYNTAX      DisplayString
   MAX-ACCESS  read-write
   STATUS      current
   DESCRIPTION
      "Path: vxLanBridgeGroup.editConf.staticBridgeCache.interface"
   ::= {er1646v2VxlBGIMVpStaticBridgeCacheEntry 16777216}

er1646v2VxlBGIMVpStaticBridgeCacheMacAddress OBJECT-TYPE
   SYNTAX      OCTET STRING
   MAX-ACCESS  read-write
   STATUS      current
   DESCRIPTION
      "Path: vxLanBridgeGroup.editConf.staticBridgeCache.macAddress

       MAC address."
   ::= {er1646v2VxlBGIMVpStaticBridgeCacheEntry 33554432}

er1646v2VxlBGIMVpStaticBridgeCacheVlanId OBJECT-TYPE
   SYNTAX      Integer32
   MAX-ACCESS  read-write
   STATUS      current
   DESCRIPTION
      "Path: vxLanBridgeGroup.editConf.staticBridgeCache.vlanId"
   ::= {er1646v2VxlBGIMVpStaticBridgeCacheEntry 50331648}


er1646v2VxlBGIMVpForwardMulticast OBJECT IDENTIFIER ::= {er1646v2VxlBGIMVp 35}

er1646v2VxlBGIMVpForwardMulticastTable OBJECT-TYPE
   SYNTAX      SEQUENCE OF Er1646v2VxlBGIMVpForwardMulticastEntry
   MAX-ACCESS  not-accessible
   STATUS      current
   DESCRIPTION
      "used for size of bridgeCache"
   ::= {er1646v2VxlBGIMVpForwardMulticast 1}

er1646v2VxlBGIMVpForwardMulticastEntry OBJECT-TYPE
   SYNTAX      Er1646v2VxlBGIMVpForwardMulticastEntry
   MAX-ACCESS  not-accessible
   STATUS      current
   DESCRIPTION
      ""
   INDEX      { er1646v2VxlBGIMVpForwardMulticastGlobalIx }
   ::= {er1646v2VxlBGIMVpForwardMulticastTable 1}

Er1646v2VxlBGIMVpForwardMulticastEntry ::=
   SEQUENCE
      {
      er1646v2VxlBGIMVpForwardMulticastGlobalIx
         GlobalIndex,
      er1646v2VxlBGIMVpForwardMulticastValue
         INTEGER
      }

er1646v2VxlBGIMVpForwardMulticastGlobalIx OBJECT-TYPE
   SYNTAX      GlobalIndex
   MAX-ACCESS  not-accessible
   STATUS      current
   DESCRIPTION
      "The value of the tlsCntTreeGlobalIndex of the MANAGED OBJECT."
   ::= {er1646v2VxlBGIMVpForwardMulticastEntry 10}

er1646v2VxlBGIMVpForwardMulticastValue OBJECT-TYPE
   SYNTAX      INTEGER
               {
               noSpanningTree (0),
               all (1),
               noLinkConstrainedProtos (2),
               dot1ad (3)
               }
   MAX-ACCESS  read-write
   STATUS      current
   DESCRIPTION
      "Path: vxLanBridgeGroup.editConf.forwardMulticast

       Possibilities:
               noSpanningTree   (0)
               all   (1)
               noLinkConstrainedProtos   (2)
               dot1ad   (3)"
   ::= {er1646v2VxlBGIMVpForwardMulticastEntry 2147483648}


er1646v2VxlBGIMVpVlanLearningMode OBJECT IDENTIFIER ::= {er1646v2VxlBGIMVp 17}

er1646v2VxlBGIMVpVlanLearningModeTable OBJECT-TYPE
   SYNTAX      SEQUENCE OF Er1646v2VxlBGIMVpVlanLearningModeEntry
   MAX-ACCESS  not-accessible
   STATUS      current
   DESCRIPTION
      ""
   ::= {er1646v2VxlBGIMVpVlanLearningMode 1}

er1646v2VxlBGIMVpVlanLearningModeEntry OBJECT-TYPE
   SYNTAX      Er1646v2VxlBGIMVpVlanLearningModeEntry
   MAX-ACCESS  not-accessible
   STATUS      current
   DESCRIPTION
      ""
   INDEX      { er1646v2VxlBGIMVpVlanLearningModeGlobalIx }
   ::= {er1646v2VxlBGIMVpVlanLearningModeTable 1}

Er1646v2VxlBGIMVpVlanLearningModeEntry ::=
   SEQUENCE
      {
      er1646v2VxlBGIMVpVlanLearningModeGlobalIx
         GlobalIndex,
      er1646v2VxlBGIMVpVlanLearningModeValue
         INTEGER
      }

er1646v2VxlBGIMVpVlanLearningModeGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanLearningModeEntry 10}

er1646v2VxlBGIMVpVlanLearningModeValue OBJECT-TYPE
   SYNTAX      INTEGER
               {
               shared (0),
               independent (1),
               grouped (2)
               }
   MAX-ACCESS  read-write
   STATUS      current
   DESCRIPTION
      "Path: vxLanBridgeGroup.editConf.vlanLearningMode

       Possibilities:
               shared   (0)
               independent   (1)
               grouped   (2)"
   ::= {er1646v2VxlBGIMVpVlanLearningModeEntry 2147483648}


er1646v2VxlBGIMVpVlanSwitching OBJECT IDENTIFIER ::= {er1646v2VxlBGIMVp 15}

er1646v2VxlBGIMVpVlanSwitchingSSCTable OBJECT-TYPE
   SYNTAX      SEQUENCE OF Er1646v2VxlBGIMVpVlanSwitchingEntry
   MAX-ACCESS  not-accessible
   STATUS      current
   DESCRIPTION
      "used for bridgeCache"
   ::= {er1646v2VxlBGIMVpVlanSwitching 1}

er1646v2VxlBGIMVpVlanSwitchingEntry OBJECT-TYPE
   SYNTAX      Er1646v2VxlBGIMVpVlanSwitchingEntry
   MAX-ACCESS  not-accessible
   STATUS      current
   DESCRIPTION
      ""
   INDEX      { er1646v2VxlBGIMVpVlanSwitchingGlobalIx,
                er1646v2VxlBGIMVpVlanSwitchingTableIx }
   ::= {er1646v2VxlBGIMVpVlanSwitchingSSCTable 1}

Er1646v2VxlBGIMVpVlanSwitchingEntry ::=
   SEQUENCE
      {
      er1646v2VxlBGIMVpVlanSwitchingActions
         VariableLengthTableActions,
      er1646v2VxlBGIMVpVlanSwitchingGlobalIx
         GlobalIndex,
      er1646v2VxlBGIMVpVlanSwitchingTableIx
         TableIndex,
      er1646v2VxlBGIMVpVlanSwitchingSi
         DisplayString,
      er1646v2VxlBGIMVpVlanSwitchingSv
         INTEGER,
      er1646v2VxlBGIMVpVlanSwitchingSp
         INTEGER,
      er1646v2VxlBGIMVpVlanSwitchingSmP0
         Integer32,
      er1646v2VxlBGIMVpVlanSwitchingSmP1
         Integer32,
      er1646v2VxlBGIMVpVlanSwitchingSmP2
         Integer32,
      er1646v2VxlBGIMVpVlanSwitchingSmP3
         Integer32,
      er1646v2VxlBGIMVpVlanSwitchingSmP4
         Integer32,
      er1646v2VxlBGIMVpVlanSwitchingSmP5
         Integer32,
      er1646v2VxlBGIMVpVlanSwitchingSmP6
         Integer32,
      er1646v2VxlBGIMVpVlanSwitchingSmP7
         Integer32,
      er1646v2VxlBGIMVpVlanSwitchingDi
         DisplayString,
      er1646v2VxlBGIMVpVlanSwitchingDv
         INTEGER,
      er1646v2VxlBGIMVpVlanSwitchingDp
         INTEGER,
      er1646v2VxlBGIMVpVlanSwitchingDmP0
         Integer32,
      er1646v2VxlBGIMVpVlanSwitchingDmP1
         Integer32,
      er1646v2VxlBGIMVpVlanSwitchingDmP2
         Integer32,
      er1646v2VxlBGIMVpVlanSwitchingDmP3
         Integer32,
      er1646v2VxlBGIMVpVlanSwitchingDmP4
         Integer32,
      er1646v2VxlBGIMVpVlanSwitchingDmP5
         Integer32,
      er1646v2VxlBGIMVpVlanSwitchingDmP6
         Integer32,
      er1646v2VxlBGIMVpVlanSwitchingDmP7
         Integer32,
      er1646v2VxlBGIMVpVlanSwitchingTunnel
         INTEGER,
      er1646v2VxlBGIMVpVlanSwitchingBidir
         INTEGER
      }

er1646v2VxlBGIMVpVlanSwitchingActions OBJECT-TYPE
   SYNTAX      VariableLengthTableActions
   MAX-ACCESS  read-write
   STATUS      current
   DESCRIPTION
      "By way of this field, some manipulations
       on this table may be performed."
   ::= {er1646v2VxlBGIMVpVlanSwitchingEntry 2}

er1646v2VxlBGIMVpVlanSwitchingGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanSwitchingEntry 10}

er1646v2VxlBGIMVpVlanSwitchingTableIx OBJECT-TYPE
   SYNTAX      TableIndex
   MAX-ACCESS  not-accessible
   STATUS      current
   DESCRIPTION
      ""
   ::= {er1646v2VxlBGIMVpVlanSwitchingEntry 11}

er1646v2VxlBGIMVpVlanSwitchingSi OBJECT-TYPE
   SYNTAX      DisplayString
   MAX-ACCESS  read-write
   STATUS      current
   DESCRIPTION
      "Path: vxLanBridgeGroup.editConf.vlanSwitching.sourceIntf"
   ::= {er1646v2VxlBGIMVpVlanSwitchingEntry 16777216}

er1646v2VxlBGIMVpVlanSwitchingSv OBJECT-TYPE
   SYNTAX      INTEGER
               {
               any (-1)
               }
   MAX-ACCESS  read-write
   STATUS      current
   DESCRIPTION
      "Path: vxLanBridgeGroup.editConf.vlanSwitching.sourceVlan

       Possibilities:
               any   (-1)"
   ::= {er1646v2VxlBGIMVpVlanSwitchingEntry 33554432}

er1646v2VxlBGIMVpVlanSwitchingSp OBJECT-TYPE
   SYNTAX      INTEGER
               {
               any (-1)
               }
   MAX-ACCESS  read-write
   STATUS      current
   DESCRIPTION
      "Path: vxLanBridgeGroup.editConf.vlanSwitching.sourcePFilter

       Possibilities:
               any   (-1)"
   ::= {er1646v2VxlBGIMVpVlanSwitchingEntry 134217728}

er1646v2VxlBGIMVpVlanSwitchingSmP0 OBJECT-TYPE
   SYNTAX      Integer32
   MAX-ACCESS  read-write
   STATUS      current
   DESCRIPTION
      "Path: vxLanBridgeGroup.editConf.vlanSwitching.sourcePMap.p0"
   ::= {er1646v2VxlBGIMVpVlanSwitchingEntry 50397184}

er1646v2VxlBGIMVpVlanSwitchingSmP1 OBJECT-TYPE
   SYNTAX      Integer32
   MAX-ACCESS  read-write
   STATUS      current
   DESCRIPTION
      "Path: vxLanBridgeGroup.editConf.vlanSwitching.sourcePMap.p1"
   ::= {er1646v2VxlBGIMVpVlanSwitchingEntry 50462720}

er1646v2VxlBGIMVpVlanSwitchingSmP2 OBJECT-TYPE
   SYNTAX      Integer32
   MAX-ACCESS  read-write
   STATUS      current
   DESCRIPTION
      "Path: vxLanBridgeGroup.editConf.vlanSwitching.sourcePMap.p2"
   ::= {er1646v2VxlBGIMVpVlanSwitchingEntry 50528256}

er1646v2VxlBGIMVpVlanSwitchingSmP3 OBJECT-TYPE
   SYNTAX      Integer32
   MAX-ACCESS  read-write
   STATUS      current
   DESCRIPTION
      "Path: vxLanBridgeGroup.editConf.vlanSwitching.sourcePMap.p3"
   ::= {er1646v2VxlBGIMVpVlanSwitchingEntry 50593792}

er1646v2VxlBGIMVpVlanSwitchingSmP4 OBJECT-TYPE
   SYNTAX      Integer32
   MAX-ACCESS  read-write
   STATUS      current
   DESCRIPTION
      "Path: vxLanBridgeGroup.editConf.vlanSwitching.sourcePMap.p4"
   ::= {er1646v2VxlBGIMVpVlanSwitchingEntry 50659328}

er1646v2VxlBGIMVpVlanSwitchingSmP5 OBJECT-TYPE
   SYNTAX      Integer32
   MAX-ACCESS  read-write
   STATUS      current
   DESCRIPTION
      "Path: vxLanBridgeGroup.editConf.vlanSwitching.sourcePMap.p5"
   ::= {er1646v2VxlBGIMVpVlanSwitchingEntry 50724864}

er1646v2VxlBGIMVpVlanSwitchingSmP6 OBJECT-TYPE
   SYNTAX      Integer32
   MAX-ACCESS  read-write
   STATUS      current
   DESCRIPTION
      "Path: vxLanBridgeGroup.editConf.vlanSwitching.sourcePMap.p6"
   ::= {er1646v2VxlBGIMVpVlanSwitchingEntry 50790400}

er1646v2VxlBGIMVpVlanSwitchingSmP7 OBJECT-TYPE
   SYNTAX      Integer32
   MAX-ACCESS  read-write
   STATUS      current
   DESCRIPTION
      "Path: vxLanBridgeGroup.editConf.vlanSwitching.sourcePMap.p7"
   ::= {er1646v2VxlBGIMVpVlanSwitchingEntry 50855936}

er1646v2VxlBGIMVpVlanSwitchingDi OBJECT-TYPE
   SYNTAX      DisplayString
   MAX-ACCESS  read-write
   STATUS      current
   DESCRIPTION
      "Path: vxLanBridgeGroup.editConf.vlanSwitching.destinationIntf"
   ::= {er1646v2VxlBGIMVpVlanSwitchingEntry 67108864}

er1646v2VxlBGIMVpVlanSwitchingDv OBJECT-TYPE
   SYNTAX      INTEGER
               {
               unchanged (-1)
               }
   MAX-ACCESS  read-write
   STATUS      current
   DESCRIPTION
      "Path: vxLanBridgeGroup.editConf.vlanSwitching.destinationVlan

       Possibilities:
               unchanged   (-1)"
   ::= {er1646v2VxlBGIMVpVlanSwitchingEntry 83886080}

er1646v2VxlBGIMVpVlanSwitchingDp OBJECT-TYPE
   SYNTAX      INTEGER
               {
               any (-1)
               }
   MAX-ACCESS  read-write
   STATUS      current
   DESCRIPTION
      "Path: vxLanBridgeGroup.editConf.vlanSwitching.destinationPFilter

       Possibilities:
               any   (-1)"
   ::= {er1646v2VxlBGIMVpVlanSwitchingEntry 167772160}

er1646v2VxlBGIMVpVlanSwitchingDmP0 OBJECT-TYPE
   SYNTAX      Integer32
   MAX-ACCESS  read-write
   STATUS      current
   DESCRIPTION
      "Path: vxLanBridgeGroup.editConf.vlanSwitching.destinationPMap.p0"
   ::= {er1646v2VxlBGIMVpVlanSwitchingEntry 100728832}

er1646v2VxlBGIMVpVlanSwitchingDmP1 OBJECT-TYPE
   SYNTAX      Integer32
   MAX-ACCESS  read-write
   STATUS      current
   DESCRIPTION
      "Path: vxLanBridgeGroup.editConf.vlanSwitching.destinationPMap.p1"
   ::= {er1646v2VxlBGIMVpVlanSwitchingEntry 100794368}

er1646v2VxlBGIMVpVlanSwitchingDmP2 OBJECT-TYPE
   SYNTAX      Integer32
   MAX-ACCESS  read-write
   STATUS      current
   DESCRIPTION
      "Path: vxLanBridgeGroup.editConf.vlanSwitching.destinationPMap.p2"
   ::= {er1646v2VxlBGIMVpVlanSwitchingEntry 100859904}

er1646v2VxlBGIMVpVlanSwitchingDmP3 OBJECT-TYPE
   SYNTAX      Integer32
   MAX-ACCESS  read-write
   STATUS      current
   DESCRIPTION
      "Path: vxLanBridgeGroup.editConf.vlanSwitching.destinationPMap.p3"
   ::= {er1646v2VxlBGIMVpVlanSwitchingEntry 100925440}

er1646v2VxlBGIMVpVlanSwitchingDmP4 OBJECT-TYPE
   SYNTAX      Integer32
   MAX-ACCESS  read-write
   STATUS      current
   DESCRIPTION
      "Path: vxLanBridgeGroup.editConf.vlanSwitching.destinationPMap.p4"
   ::= {er1646v2VxlBGIMVpVlanSwitchingEntry 100990976}

er1646v2VxlBGIMVpVlanSwitchingDmP5 OBJECT-TYPE
   SYNTAX      Integer32
   MAX-ACCESS  read-write
   STATUS      current
   DESCRIPTION
      "Path: vxLanBridgeGroup.editConf.vlanSwitching.destinationPMap.p5"
   ::= {er1646v2VxlBGIMVpVlanSwitchingEntry 101056512}

er1646v2VxlBGIMVpVlanSwitchingDmP6 OBJECT-TYPE
   SYNTAX      Integer32
   MAX-ACCESS  read-write
   STATUS      current
   DESCRIPTION
      "Path: vxLanBridgeGroup.editConf.vlanSwitching.destinationPMap.p6"
   ::= {er1646v2VxlBGIMVpVlanSwitchingEntry 101122048}

er1646v2VxlBGIMVpVlanSwitchingDmP7 OBJECT-TYPE
   SYNTAX      Integer32
   MAX-ACCESS  read-write
   STATUS      current
   DESCRIPTION
      "Path: vxLanBridgeGroup.editConf.vlanSwitching.destinationPMap.p7"
   ::= {er1646v2VxlBGIMVpVlanSwitchingEntry 101187584}

er1646v2VxlBGIMVpVlanSwitchingTunnel OBJECT-TYPE
   SYNTAX      INTEGER
               {
               disabled (0),
               enabled (1),
               sVlan (3)
               }
   MAX-ACCESS  read-write
   STATUS      current
   DESCRIPTION
      "Path: vxLanBridgeGroup.editConf.vlanSwitching.tunnel

       Possibilities:
               disabled   (0)
               enabled   (1)
               sVlan   (3)"
   ::= {er1646v2VxlBGIMVpVlanSwitchingEntry 117440512}

er1646v2VxlBGIMVpVlanSwitchingBidir OBJECT-TYPE
   SYNTAX      INTEGER
               {
               no (0),
               yes (1)
               }
   MAX-ACCESS  read-write
   STATUS      current
   DESCRIPTION
      "Path: vxLanBridgeGroup.editConf.vlanSwitching.bidirectional

       Possibilities:
               no   (0)
               yes   (1)"
   ::= {er1646v2VxlBGIMVpVlanSwitchingEntry 150994944}


er1646v2VxlBGIMVpPktCounters OBJECT IDENTIFIER ::= {er1646v2VxlBGIMVp 31}

er1646v2VxlBGIMVpPktCountersTable OBJECT-TYPE
   SYNTAX      SEQUENCE OF Er1646v2VxlBGIMVpPktCountersEntry
   MAX-ACCESS  not-accessible
   STATUS      current
   DESCRIPTION
      ""
   ::= {er1646v2VxlBGIMVpPktCounters 1}

er1646v2VxlBGIMVpPktCountersEntry OBJECT-TYPE
   SYNTAX      Er1646v2VxlBGIMVpPktCountersEntry
   MAX-ACCESS  not-accessible
   STATUS      current
   DESCRIPTION
      ""
   INDEX      { er1646v2VxlBGIMVpPktCountersGlobalIx }
   ::= {er1646v2VxlBGIMVpPktCountersTable 1}

Er1646v2VxlBGIMVpPktCountersEntry ::=
   SEQUENCE
      {
      er1646v2VxlBGIMVpPktCountersGlobalIx
         GlobalIndex,
      er1646v2VxlBGIMVpPktCountersValue
         INTEGER
      }

er1646v2VxlBGIMVpPktCountersGlobalIx OBJECT-TYPE
   SYNTAX      GlobalIndex
   MAX-ACCESS  not-accessible
   STATUS      current
   DESCRIPTION
      "The value of the tlsCntTreeGlobalIndex of the MANAGED OBJECT."
   ::= {er1646v2VxlBGIMVpPktCountersEntry 10}

er1646v2VxlBGIMVpPktCountersValue OBJECT-TYPE
   SYNTAX      INTEGER
               {
               disabled (1),
               enabled (2)
               }
   MAX-ACCESS  read-write
   STATUS      current
   DESCRIPTION
      "Path: vxLanBridgeGroup.editConf.pktCounters

       Possibilities:
               disabled   (1)
               enabled   (2)"
   ::= {er1646v2VxlBGIMVpPktCountersEntry 2147483648}


er1646v2VxlBGIMVpBackup OBJECT IDENTIFIER ::= {er1646v2VxlBGIMVp 32}

er1646v2VxlBGIMVpBackupSSCTable OBJECT-TYPE
   SYNTAX      SEQUENCE OF Er1646v2VxlBGIMVpBackupEntry
   MAX-ACCESS  not-accessible
   STATUS      current
   DESCRIPTION
      ""
   ::= {er1646v2VxlBGIMVpBackup 1}

er1646v2VxlBGIMVpBackupEntry OBJECT-TYPE
   SYNTAX      Er1646v2VxlBGIMVpBackupEntry
   MAX-ACCESS  not-accessible
   STATUS      current
   DESCRIPTION
      ""
   INDEX      { er1646v2VxlBGIMVpBackupGlobalIx }
   ::= {er1646v2VxlBGIMVpBackupSSCTable 1}

Er1646v2VxlBGIMVpBackupEntry ::=
   SEQUENCE
      {
      er1646v2VxlBGIMVpBackupGlobalIx
         GlobalIndex,
      er1646v2VxlBGIMVpBackupDisabled
         OCTET STRING,
      er1646v2VxlBGIMVpBackupSimpleInterface1
         DisplayString,
      er1646v2VxlBGIMVpBackupSimpleInterface1MepName
         DisplayString,
      er1646v2VxlBGIMVpBackupSimpleInterface2
         DisplayString,
      er1646v2VxlBGIMVpBackupSimpleInterface2MepName
         DisplayString,
      er1646v2VxlBGIMVpBackupSimpleBackup
         DisplayString,
      er1646v2VxlBGIMVpBackupSimpleBackupMepName
         DisplayString,
      er1646v2VxlBGIMVpBackupSimpleType
         INTEGER
      }

er1646v2VxlBGIMVpBackupGlobalIx OBJECT-TYPE
   SYNTAX      GlobalIndex
   MAX-ACCESS  not-accessible
   STATUS      current
   DESCRIPTION
      "The value of the tlsCntTreeGlobalIndex of the MANAGED OBJECT."
   ::= {er1646v2VxlBGIMVpBackupEntry 10}

er1646v2VxlBGIMVpBackupDisabled OBJECT-TYPE
   SYNTAX      OCTET STRING
   MAX-ACCESS  read-write
   STATUS      current
   DESCRIPTION
      "Path: vxLanBridgeGroup.editConf.backup.disabled"
   ::= {er1646v2VxlBGIMVpBackupEntry 16777216}

er1646v2VxlBGIMVpBackupSimpleInterface1 OBJECT-TYPE
   SYNTAX      DisplayString
   MAX-ACCESS  read-write
   STATUS      current
   DESCRIPTION
      "Path: vxLanBridgeGroup.editConf.backup.simple.interface1"
   ::= {er1646v2VxlBGIMVpBackupEntry 33619968}

er1646v2VxlBGIMVpBackupSimpleInterface1MepName OBJECT-TYPE
   SYNTAX      DisplayString
   MAX-ACCESS  read-write
   STATUS      current
   DESCRIPTION
      "Path: vxLanBridgeGroup.editConf.backup.simple.interface1MepName"
   ::= {er1646v2VxlBGIMVpBackupEntry 33947648}

er1646v2VxlBGIMVpBackupSimpleInterface2 OBJECT-TYPE
   SYNTAX      DisplayString
   MAX-ACCESS  read-write
   STATUS      current
   DESCRIPTION
      "Path: vxLanBridgeGroup.editConf.backup.simple.interface2"
   ::= {er1646v2VxlBGIMVpBackupEntry 33685504}

er1646v2VxlBGIMVpBackupSimpleInterface2MepName OBJECT-TYPE
   SYNTAX      DisplayString
   MAX-ACCESS  read-write
   STATUS      current
   DESCRIPTION
      "Path: vxLanBridgeGroup.editConf.backup.simple.interface2MepName"
   ::= {er1646v2VxlBGIMVpBackupEntry 34013184}

er1646v2VxlBGIMVpBackupSimpleBackup OBJECT-TYPE
   SYNTAX      DisplayString
   MAX-ACCESS  read-write
   STATUS      current
   DESCRIPTION
      "Path: vxLanBridgeGroup.editConf.backup.simple.backup"
   ::= {er1646v2VxlBGIMVpBackupEntry 33751040}

er1646v2VxlBGIMVpBackupSimpleBackupMepName OBJECT-TYPE
   SYNTAX      DisplayString
   MAX-ACCESS  read-write
   STATUS      current
   DESCRIPTION
      "Path: vxLanBridgeGroup.editConf.backup.simple.backupMepName"
   ::= {er1646v2VxlBGIMVpBackupEntry 33816576}

er1646v2VxlBGIMVpBackupSimpleType OBJECT-TYPE
   SYNTAX      INTEGER
               {
               master (1),
               slave (2)
               }
   MAX-ACCESS  read-write
   STATUS      current
   DESCRIPTION
      "Path: vxLanBridgeGroup.editConf.backup.simple.type

       Possibilities:
               master   (1)
               slave   (2)"
   ::= {er1646v2VxlBGIMVpBackupEntry 33882112}

er1646v2VxlBGIMVpBackupSimpleCacheDistribution OBJECT-TYPE
   SYNTAX      SEQUENCE OF Er1646v2VxlBGIMVpBackupSimpleCacheDistributionEntry
   MAX-ACCESS  not-accessible
   STATUS      current
   DESCRIPTION
      ""
   ::= {er1646v2VxlBGIMVpBackup 34078720}

er1646v2VxlBGIMVpBackupSimpleCacheDistributionEntry OBJECT-TYPE
   SYNTAX      Er1646v2VxlBGIMVpBackupSimpleCacheDistributionEntry
   MAX-ACCESS  not-accessible
   STATUS      current
   DESCRIPTION
      ""
   INDEX      { er1646v2VxlBGIMVpBackupSimpleCacheDistributionGlobalIx,
                er1646v2VxlBGIMVpBackupSimpleCacheDistributionTableIx }
   ::= {er1646v2VxlBGIMVpBackupSimpleCacheDistribution 1}

Er1646v2VxlBGIMVpBackupSimpleCacheDistributionEntry ::=
   SEQUENCE
      {
      er1646v2VxlBGIMVpBackupSimpleCacheDistributionActions
         VariableLengthTableActions,
      er1646v2VxlBGIMVpBackupSimpleCacheDistributionGlobalIx
         GlobalIndex,
      er1646v2VxlBGIMVpBackupSimpleCacheDistributionTableIx
         TableIndex,
      er1646v2VxlBGIMVpBackupSimpleCacheDistributionDestinationMac
         OCTET STRING,
      er1646v2VxlBGIMVpBackupSimpleCacheDistributionType
         INTEGER
      }

er1646v2VxlBGIMVpBackupSimpleCacheDistributionActions OBJECT-TYPE
   SYNTAX      VariableLengthTableActions
   MAX-ACCESS  read-write
   STATUS      current
   DESCRIPTION
      "By way of this field, some manipulations
       on this table may be performed."
   ::= {er1646v2VxlBGIMVpBackupSimpleCacheDistributionEntry 2}

er1646v2VxlBGIMVpBackupSimpleCacheDistributionGlobalIx OBJECT-TYPE
   SYNTAX      GlobalIndex
   MAX-ACCESS  not-accessible
   STATUS      current
   DESCRIPTION
      "The value of the tlsCntTreeGlobalIndex of the MANAGED OBJECT."
   ::= {er1646v2VxlBGIMVpBackupSimpleCacheDistributionEntry 10}

er1646v2VxlBGIMVpBackupSimpleCacheDistributionTableIx OBJECT-TYPE
   SYNTAX      TableIndex
   MAX-ACCESS  not-accessible
   STATUS      current
   DESCRIPTION
      ""
   ::= {er1646v2VxlBGIMVpBackupSimpleCacheDistributionEntry 11}

er1646v2VxlBGIMVpBackupSimpleCacheDistributionDestinationMac OBJECT-TYPE
   SYNTAX      OCTET STRING
   MAX-ACCESS  read-write
   STATUS      current
   DESCRIPTION
      "Path: vxLanBridgeGroup.editConf.backup.simple.cacheDistribution.destinationMac

       MAC address."
   ::= {er1646v2VxlBGIMVpBackupSimpleCacheDistributionEntry 16777216}

er1646v2VxlBGIMVpBackupSimpleCacheDistributionType OBJECT-TYPE
   SYNTAX      INTEGER
               {
               arp (2054)
               }
   MAX-ACCESS  read-write
   STATUS      current
   DESCRIPTION
      "Path: vxLanBridgeGroup.editConf.backup.simple.cacheDistribution.type

       Possibilities:
               arp   (2054)"
   ::= {er1646v2VxlBGIMVpBackupSimpleCacheDistributionEntry 33554432}


er1646v2VxlBGIMVpAlarmMask OBJECT IDENTIFIER ::= {er1646v2VxlBGIMVp 50}

er1646v2VxlBGIMVpAlarmMaskTable OBJECT-TYPE
   SYNTAX      SEQUENCE OF Er1646v2VxlBGIMVpAlarmMaskEntry
   MAX-ACCESS  not-accessible
   STATUS      current
   DESCRIPTION
      "bridge group alarmMask"
   ::= {er1646v2VxlBGIMVpAlarmMask 1}

er1646v2VxlBGIMVpAlarmMaskEntry OBJECT-TYPE
   SYNTAX      Er1646v2VxlBGIMVpAlarmMaskEntry
   MAX-ACCESS  not-accessible
   STATUS      current
   DESCRIPTION
      ""
   INDEX      { er1646v2VxlBGIMVpAlarmMaskGlobalIx }
   ::= {er1646v2VxlBGIMVpAlarmMaskTable 1}

Er1646v2VxlBGIMVpAlarmMaskEntry ::=
   SEQUENCE
      {
      er1646v2VxlBGIMVpAlarmMaskGlobalIx
         GlobalIndex,
      er1646v2VxlBGIMVpAlarmMaskValue
         Integer32
      }

er1646v2VxlBGIMVpAlarmMaskGlobalIx OBJECT-TYPE
   SYNTAX      GlobalIndex
   MAX-ACCESS  not-accessible
   STATUS      current
   DESCRIPTION
      "The value of the tlsCntTreeGlobalIndex of the MANAGED OBJECT."
   ::= {er1646v2VxlBGIMVpAlarmMaskEntry 10}

er1646v2VxlBGIMVpAlarmMaskValue OBJECT-TYPE
   SYNTAX      Integer32
   MAX-ACCESS  read-write
   STATUS      current
   DESCRIPTION
      "Path: vxLanBridgeGroup.editConf.alarmMask

       Bit meanings:
               bit 0 = linkDown,
               bit 1 = linkShutdown"
   ::= {er1646v2VxlBGIMVpAlarmMaskEntry 2147483648}


er1646v2VxlBGIMVpAlarmLev OBJECT IDENTIFIER ::= {er1646v2VxlBGIMVp 51}

er1646v2VxlBGIMVpAlarmLevSSCTable OBJECT-TYPE
   SYNTAX      SEQUENCE OF Er1646v2VxlBGIMVpAlarmLevEntry
   MAX-ACCESS  not-accessible
   STATUS      current
   DESCRIPTION
      "bridge group alarmLevels"
   ::= {er1646v2VxlBGIMVpAlarmLev 1}

er1646v2VxlBGIMVpAlarmLevEntry OBJECT-TYPE
   SYNTAX      Er1646v2VxlBGIMVpAlarmLevEntry
   MAX-ACCESS  not-accessible
   STATUS      current
   DESCRIPTION
      ""
   INDEX      { er1646v2VxlBGIMVpAlarmLevGlobalIx }
   ::= {er1646v2VxlBGIMVpAlarmLevSSCTable 1}

Er1646v2VxlBGIMVpAlarmLevEntry ::=
   SEQUENCE
      {
      er1646v2VxlBGIMVpAlarmLevGlobalIx
         GlobalIndex,
      er1646v2VxlBGIMVpAlarmLevLinkDown
         Integer32,
      er1646v2VxlBGIMVpAlarmLevLinkShutdown
         Integer32
      }

er1646v2VxlBGIMVpAlarmLevGlobalIx OBJECT-TYPE
   SYNTAX      GlobalIndex
   MAX-ACCESS  not-accessible
   STATUS      current
   DESCRIPTION
      "The value of the tlsCntTreeGlobalIndex of the MANAGED OBJECT."
   ::= {er1646v2VxlBGIMVpAlarmLevEntry 10}

er1646v2VxlBGIMVpAlarmLevLinkDown OBJECT-TYPE
   SYNTAX      Integer32
   MAX-ACCESS  read-write
   STATUS      current
   DESCRIPTION
      "Path: vxLanBridgeGroup.editConf.alarmLevel.linkDown"
   ::= {er1646v2VxlBGIMVpAlarmLevEntry 16777216}

er1646v2VxlBGIMVpAlarmLevLinkShutdown OBJECT-TYPE
   SYNTAX      Integer32
   MAX-ACCESS  read-write
   STATUS      current
   DESCRIPTION
      "Path: vxLanBridgeGroup.editConf.alarmLevel.linkShutdown"
   ::= {er1646v2VxlBGIMVpAlarmLevEntry 33554432}


er1646v2VxlBGIMVpBridgeTimeOut OBJECT IDENTIFIER ::= {er1646v2VxlBGIMVp 21}

er1646v2VxlBGIMVpBridgeTimeOutTable OBJECT-TYPE
   SYNTAX      SEQUENCE OF Er1646v2VxlBGIMVpBridgeTimeOutEntry
   MAX-ACCESS  not-accessible
   STATUS      current
   DESCRIPTION
      "timeout of bridge cache entries"
   ::= {er1646v2VxlBGIMVpBridgeTimeOut 1}

er1646v2VxlBGIMVpBridgeTimeOutEntry OBJECT-TYPE
   SYNTAX      Er1646v2VxlBGIMVpBridgeTimeOutEntry
   MAX-ACCESS  not-accessible
   STATUS      current
   DESCRIPTION
      ""
   INDEX      { er1646v2VxlBGIMVpBridgeTimeOutGlobalIx }
   ::= {er1646v2VxlBGIMVpBridgeTimeOutTable 1}

Er1646v2VxlBGIMVpBridgeTimeOutEntry ::=
   SEQUENCE
      {
      er1646v2VxlBGIMVpBridgeTimeOutGlobalIx
         GlobalIndex,
      er1646v2VxlBGIMVpBridgeTimeOutValue
         TimeTicks
      }

er1646v2VxlBGIMVpBridgeTimeOutGlobalIx OBJECT-TYPE
   SYNTAX      GlobalIndex
   MAX-ACCESS  not-accessible
   STATUS      current
   DESCRIPTION
      "The value of the tlsCntTreeGlobalIndex of the MANAGED OBJECT."
   ::= {er1646v2VxlBGIMVpBridgeTimeOutEntry 10}

er1646v2VxlBGIMVpBridgeTimeOutValue OBJECT-TYPE
   SYNTAX      TimeTicks
   MAX-ACCESS  read-write
   STATUS      current
   DESCRIPTION
      "Path: vxLanBridgeGroup.editConf.bridgeTimeOut

       Time in centi-second."
   ::= {er1646v2VxlBGIMVpBridgeTimeOutEntry 2147483648}


er1646v2VxlBGIMVpRemark OBJECT IDENTIFIER ::= {er1646v2VxlBGIMVp 321}

er1646v2VxlBGIMVpRemarkTable OBJECT-TYPE
   SYNTAX      SEQUENCE OF Er1646v2VxlBGIMVpRemarkEntry
   MAX-ACCESS  not-accessible
   STATUS      current
   DESCRIPTION
      "intfRemark"
   ::= {er1646v2VxlBGIMVpRemark 1}

er1646v2VxlBGIMVpRemarkEntry OBJECT-TYPE
   SYNTAX      Er1646v2VxlBGIMVpRemarkEntry
   MAX-ACCESS  not-accessible
   STATUS      current
   DESCRIPTION
      ""
   INDEX      { er1646v2VxlBGIMVpRemarkGlobalIx }
   ::= {er1646v2VxlBGIMVpRemarkTable 1}

Er1646v2VxlBGIMVpRemarkEntry ::=
   SEQUENCE
      {
      er1646v2VxlBGIMVpRemarkGlobalIx
         GlobalIndex,
      er1646v2VxlBGIMVpRemarkValue
         DisplayString
      }

er1646v2VxlBGIMVpRemarkGlobalIx OBJECT-TYPE
   SYNTAX      GlobalIndex
   MAX-ACCESS  not-accessible
   STATUS      current
   DESCRIPTION
      "The value of the tlsCntTreeGlobalIndex of the MANAGED OBJECT."
   ::= {er1646v2VxlBGIMVpRemarkEntry 10}

er1646v2VxlBGIMVpRemarkValue OBJECT-TYPE
   SYNTAX      DisplayString
   MAX-ACCESS  read-write
   STATUS      current
   DESCRIPTION
      "Path: vxLanBridgeGroup.editConf.remark"
   ::= {er1646v2VxlBGIMVpRemarkEntry 2147483648}


er1646v2VxlBGIMVpMode OBJECT IDENTIFIER ::= {er1646v2VxlBGIMVp 4}

er1646v2VxlBGIMVpModeTable OBJECT-TYPE
   SYNTAX      SEQUENCE OF Er1646v2VxlBGIMVpModeEntry
   MAX-ACCESS  not-accessible
   STATUS      current
   DESCRIPTION
      "routing and/or ipV6 selection"
   ::= {er1646v2VxlBGIMVpMode 1}

er1646v2VxlBGIMVpModeEntry OBJECT-TYPE
   SYNTAX      Er1646v2VxlBGIMVpModeEntry
   MAX-ACCESS  not-accessible
   STATUS      current
   DESCRIPTION
      ""
   INDEX      { er1646v2VxlBGIMVpModeGlobalIx }
   ::= {er1646v2VxlBGIMVpModeTable 1}

Er1646v2VxlBGIMVpModeEntry ::=
   SEQUENCE
      {
      er1646v2VxlBGIMVpModeGlobalIx
         GlobalIndex,
      er1646v2VxlBGIMVpModeValue
         INTEGER
      }

er1646v2VxlBGIMVpModeGlobalIx OBJECT-TYPE
   SYNTAX      GlobalIndex
   MAX-ACCESS  not-accessible
   STATUS      current
   DESCRIPTION
      "The value of the tlsCntTreeGlobalIndex of the MANAGED OBJECT."
   ::= {er1646v2VxlBGIMVpModeEntry 10}

er1646v2VxlBGIMVpModeValue OBJECT-TYPE
   SYNTAX      INTEGER
               {
               routing (1),
               ipV6 (3),
               ipV6ipV4 (4),
               disabled (100)
               }
   MAX-ACCESS  read-write
   STATUS      current
   DESCRIPTION
      "Path: vxLanBridgeGroup.editConf.mode

       Possibilities:
               routing   (1)
               ipV6   (3)
               ipV6/ipV4   (4)
               disabled   (100)"
   ::= {er1646v2VxlBGIMVpModeEntry 2147483648}


er1646v2VxlBGIMVpIpV6 OBJECT IDENTIFIER ::= {er1646v2VxlBGIMVp 16}

er1646v2VxlBGIMVpIpV6SSCTable OBJECT-TYPE
   SYNTAX      SEQUENCE OF Er1646v2VxlBGIMVpIpV6Entry
   MAX-ACCESS  not-accessible
   STATUS      current
   DESCRIPTION
      "IPv6 interface config parameters"
   ::= {er1646v2VxlBGIMVpIpV6 1}

er1646v2VxlBGIMVpIpV6Entry OBJECT-TYPE
   SYNTAX      Er1646v2VxlBGIMVpIpV6Entry
   MAX-ACCESS  not-accessible
   STATUS      current
   DESCRIPTION
      ""
   INDEX      { er1646v2VxlBGIMVpIpV6GlobalIx }
   ::= {er1646v2VxlBGIMVpIpV6SSCTable 1}

Er1646v2VxlBGIMVpIpV6Entry ::=
   SEQUENCE
      {
      er1646v2VxlBGIMVpIpV6GlobalIx
         GlobalIndex,
      er1646v2VxlBGIMVpIpV6VrfRouter
         DisplayString,
      er1646v2VxlBGIMVpIpV6AddrAutoConfigNrDupAddrDetects
         Integer32,
      er1646v2VxlBGIMVpIpV6AddrAutoConfigAcceptRa
         INTEGER,
      er1646v2VxlBGIMVpIpV6AddrAutoConfigAcceptRaRdnss
         INTEGER,
      er1646v2VxlBGIMVpIpV6AddrAutoConfigAcceptRaDnssl
         INTEGER,
      er1646v2VxlBGIMVpIpV6DefaultRoute
         INTEGER,
      er1646v2VxlBGIMVpIpV6RaSend
         INTEGER,
      er1646v2VxlBGIMVpIpV6RaMinInterval
         TimeTicks,
      er1646v2VxlBGIMVpIpV6RaMaxInterval
         TimeTicks,
      er1646v2VxlBGIMVpIpV6RaManagedFlag
         INTEGER,
      er1646v2VxlBGIMVpIpV6RaOtherConfFlag
         INTEGER,
      er1646v2VxlBGIMVpIpV6RaLinkMtu
         Integer32,
      er1646v2VxlBGIMVpIpV6RaReachableTime
         TimeTicks,
      er1646v2VxlBGIMVpIpV6RaRetransmitTime
         TimeTicks,
      er1646v2VxlBGIMVpIpV6RaHopLimit
         Integer32,
      er1646v2VxlBGIMVpIpV6RaDefaultLifeTime
         TimeTicks,
      er1646v2VxlBGIMVpIpV6RaDnsOptionsRdnssLifeTime
         TimeTicks,
      er1646v2VxlBGIMVpIpV6RaDnsOptionsRdnssImportServers
         INTEGER,
      er1646v2VxlBGIMVpIpV6RaDnsOptionsDnsslLifeTime
         TimeTicks,
      er1646v2VxlBGIMVpIpV6RaDnsOptionsDnsslImportDomains
         INTEGER,
      er1646v2VxlBGIMVpIpV6RsSend
         INTEGER,
      er1646v2VxlBGIMVpIpV6RsMaxRandomDelay
         TimeTicks,
      er1646v2VxlBGIMVpIpV6RsInterval
         TimeTicks,
      er1646v2VxlBGIMVpIpV6RsMaxSolicitations
         Integer32,
      er1646v2VxlBGIMVpIpV6TrafficPolicyInbound
         DisplayString,
      er1646v2VxlBGIMVpIpV6TrafficPolicyOutbound
         DisplayString,
      er1646v2VxlBGIMVpIpV6FirewallZone
         DisplayString,
      er1646v2VxlBGIMVpIpV6DhcpClientAddrAC
         INTEGER,
      er1646v2VxlBGIMVpIpV6DhcpClientPrDelMode
         INTEGER,
      er1646v2VxlBGIMVpIpV6DhcpClientPrDelPool
         DisplayString,
      er1646v2VxlBGIMVpIpV6DhcpClientPrDelPdExclOpt
         INTEGER,
      er1646v2VxlBGIMVpIpV6DhcpClientDnsServerPref
         Integer32,
      er1646v2VxlBGIMVpIpV6DhcpClientRapidCommit
         INTEGER,
      er1646v2VxlBGIMVpIpV6DhcpClientTimersSolTimeOut
         TimeTicks,
      er1646v2VxlBGIMVpIpV6DhcpClientTimersSolMaxRt
         TimeTicks,
      er1646v2VxlBGIMVpIpV6DhcpClientTimersInfoRefresh
         TimeTicks,
      er1646v2VxlBGIMVpIpV6DhcpServerMode
         INTEGER,
      er1646v2VxlBGIMVpIpV6DhcpServerPreference
         Integer32,
      er1646v2VxlBGIMVpIpV6DhcpServerPool
         DisplayString,
      er1646v2VxlBGIMVpIpV6DhcpServerRapidCommit
         INTEGER,
      er1646v2VxlBGIMVpIpV6DhcpServerTimersInfoRefresh
         TimeTicks,
      er1646v2VxlBGIMVpIpV6DhcpRelayMode
         INTEGER,
      er1646v2VxlBGIMVpIpV6SendRedirect
         INTEGER,
      er1646v2VxlBGIMVpIpV6LinkMtu
         Integer32,
      er1646v2VxlBGIMVpIpV6InterfaceId
         OCTET STRING,
      er1646v2VxlBGIMVpIpV6MF
         Integer32,
      er1646v2VxlBGIMVpIpV6IcmpMessagesNoRoute
         INTEGER,
      er1646v2VxlBGIMVpIpV6IcmpMessagesBeyondScope
         INTEGER,
      er1646v2VxlBGIMVpIpV6IcmpMessagesAddressUnreachable
         INTEGER,
      er1646v2VxlBGIMVpIpV6IcmpMessagesPortUnreachable
         INTEGER,
      er1646v2VxlBGIMVpIpV6IcmpMessagesPacketTooBig
         INTEGER,
      er1646v2VxlBGIMVpIpV6IcmpMessagesHopLimitExceeded
         INTEGER,
      er1646v2VxlBGIMVpIpV6IcmpMessagesFragTimeExceeded
         INTEGER,
      er1646v2VxlBGIMVpIpV6IcmpMessagesHeaderFieldErr
         INTEGER,
      er1646v2VxlBGIMVpIpV6IcmpMessagesOptionUnrecognized
         INTEGER,
      er1646v2VxlBGIMVpIpV6IcmpMessagesRedirect
         INTEGER
      }

er1646v2VxlBGIMVpIpV6GlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6Entry 10}

er1646v2VxlBGIMVpIpV6VrfRouter OBJECT-TYPE
   SYNTAX      DisplayString
   MAX-ACCESS  read-write
   STATUS      current
   DESCRIPTION
      "Path: vxLanBridgeGroup.editConf.ipV6.vrfRouter"
   ::= {er1646v2VxlBGIMVpIpV6Entry 16777216}

er1646v2VxlBGIMVpIpV6AddrAutoConfigNrDupAddrDetects OBJECT-TYPE
   SYNTAX      Integer32
   MAX-ACCESS  read-write
   STATUS      current
   DESCRIPTION
      "Path: vxLanBridgeGroup.editConf.ipV6.addrAutoConfig.nrDupAddrDetects"
   ::= {er1646v2VxlBGIMVpIpV6Entry 67174400}

er1646v2VxlBGIMVpIpV6AddrAutoConfigAcceptRa OBJECT-TYPE
   SYNTAX      INTEGER
               {
               disabled (0),
               enabled (1)
               }
   MAX-ACCESS  read-write
   STATUS      current
   DESCRIPTION
      "Path: vxLanBridgeGroup.editConf.ipV6.addrAutoConfig.acceptRa

       Possibilities:
               disabled   (0)
               enabled   (1)"
   ::= {er1646v2VxlBGIMVpIpV6Entry 67239936}

er1646v2VxlBGIMVpIpV6AddrAutoConfigAcceptRaRdnss OBJECT-TYPE
   SYNTAX      INTEGER
               {
               disabled (0),
               enabled (1)
               }
   MAX-ACCESS  read-write
   STATUS      current
   DESCRIPTION
      "Path: vxLanBridgeGroup.editConf.ipV6.addrAutoConfig.acceptRaRdnss

       Possibilities:
               disabled   (0)
               enabled   (1)"
   ::= {er1646v2VxlBGIMVpIpV6Entry 67305472}

er1646v2VxlBGIMVpIpV6AddrAutoConfigAcceptRaDnssl OBJECT-TYPE
   SYNTAX      INTEGER
               {
               disabled (0),
               enabled (1)
               }
   MAX-ACCESS  read-write
   STATUS      current
   DESCRIPTION
      "Path: vxLanBridgeGroup.editConf.ipV6.addrAutoConfig.acceptRaDnssl

       Possibilities:
               disabled   (0)
               enabled   (1)"
   ::= {er1646v2VxlBGIMVpIpV6Entry 67371008}

er1646v2VxlBGIMVpIpV6DefaultRoute OBJECT-TYPE
   SYNTAX      INTEGER
               {
               disabled (0),
               enabled (1)
               }
   MAX-ACCESS  read-write
   STATUS      current
   DESCRIPTION
      "Path: vxLanBridgeGroup.editConf.ipV6.defaultRoute

       Possibilities:
               disabled   (0)
               enabled   (1)"
   ::= {er1646v2VxlBGIMVpIpV6Entry 83886080}

er1646v2VxlBGIMVpIpV6RaSend OBJECT-TYPE
   SYNTAX      INTEGER
               {
               disabled (0),
               enabled (1)
               }
   MAX-ACCESS  read-write
   STATUS      current
   DESCRIPTION
      "Path: vxLanBridgeGroup.editConf.ipV6.ra.send

       Possibilities:
               disabled   (0)
               enabled   (1)"
   ::= {er1646v2VxlBGIMVpIpV6Entry 100728832}

er1646v2VxlBGIMVpIpV6RaMinInterval OBJECT-TYPE
   SYNTAX      TimeTicks
   MAX-ACCESS  read-write
   STATUS      current
   DESCRIPTION
      "Path: vxLanBridgeGroup.editConf.ipV6.ra.minInterval

       Time in centi-second."
   ::= {er1646v2VxlBGIMVpIpV6Entry 100794368}

er1646v2VxlBGIMVpIpV6RaMaxInterval OBJECT-TYPE
   SYNTAX      TimeTicks
   MAX-ACCESS  read-write
   STATUS      current
   DESCRIPTION
      "Path: vxLanBridgeGroup.editConf.ipV6.ra.maxInterval

       Time in centi-second."
   ::= {er1646v2VxlBGIMVpIpV6Entry 100859904}

er1646v2VxlBGIMVpIpV6RaManagedFlag OBJECT-TYPE
   SYNTAX      INTEGER
               {
               disabled (0),
               enabled (1)
               }
   MAX-ACCESS  read-write
   STATUS      current
   DESCRIPTION
      "Path: vxLanBridgeGroup.editConf.ipV6.ra.managedFlag

       Possibilities:
               disabled   (0)
               enabled   (1)"
   ::= {er1646v2VxlBGIMVpIpV6Entry 100925440}

er1646v2VxlBGIMVpIpV6RaOtherConfFlag OBJECT-TYPE
   SYNTAX      INTEGER
               {
               disabled (0),
               enabled (1)
               }
   MAX-ACCESS  read-write
   STATUS      current
   DESCRIPTION
      "Path: vxLanBridgeGroup.editConf.ipV6.ra.otherConfFlag

       Possibilities:
               disabled   (0)
               enabled   (1)"
   ::= {er1646v2VxlBGIMVpIpV6Entry 100990976}

er1646v2VxlBGIMVpIpV6RaLinkMtu OBJECT-TYPE
   SYNTAX      Integer32
   MAX-ACCESS  read-write
   STATUS      current
   DESCRIPTION
      "Path: vxLanBridgeGroup.editConf.ipV6.ra.linkMtu"
   ::= {er1646v2VxlBGIMVpIpV6Entry 101056512}

er1646v2VxlBGIMVpIpV6RaReachableTime OBJECT-TYPE
   SYNTAX      TimeTicks
   MAX-ACCESS  read-write
   STATUS      current
   DESCRIPTION
      "Path: vxLanBridgeGroup.editConf.ipV6.ra.reachableTime

       Time in centi-second."
   ::= {er1646v2VxlBGIMVpIpV6Entry 101122048}

er1646v2VxlBGIMVpIpV6RaRetransmitTime OBJECT-TYPE
   SYNTAX      TimeTicks
   MAX-ACCESS  read-write
   STATUS      current
   DESCRIPTION
      "Path: vxLanBridgeGroup.editConf.ipV6.ra.retransmitTime

       Time in centi-second."
   ::= {er1646v2VxlBGIMVpIpV6Entry 101187584}

er1646v2VxlBGIMVpIpV6RaHopLimit OBJECT-TYPE
   SYNTAX      Integer32
   MAX-ACCESS  read-write
   STATUS      current
   DESCRIPTION
      "Path: vxLanBridgeGroup.editConf.ipV6.ra.hopLimit"
   ::= {er1646v2VxlBGIMVpIpV6Entry 101253120}

er1646v2VxlBGIMVpIpV6RaDefaultLifeTime OBJECT-TYPE
   SYNTAX      TimeTicks
   MAX-ACCESS  read-write
   STATUS      current
   DESCRIPTION
      "Path: vxLanBridgeGroup.editConf.ipV6.ra.defaultLifeTime

       Time in centi-second."
   ::= {er1646v2VxlBGIMVpIpV6Entry 101318656}

er1646v2VxlBGIMVpIpV6RaDnsOptionsRdnssLifeTime OBJECT-TYPE
   SYNTAX      TimeTicks
   MAX-ACCESS  read-write
   STATUS      current
   DESCRIPTION
      "Path: vxLanBridgeGroup.editConf.ipV6.ra.dnsOptions.rdnss.lifeTime

       Time in centi-second."
   ::= {er1646v2VxlBGIMVpIpV6Entry 101393408}

er1646v2VxlBGIMVpIpV6RaDnsOptionsRdnssImportServers OBJECT-TYPE
   SYNTAX      INTEGER
               {
               disabled (0),
               enabled (1)
               }
   MAX-ACCESS  read-write
   STATUS      current
   DESCRIPTION
      "Path: vxLanBridgeGroup.editConf.ipV6.ra.dnsOptions.rdnss.importServers

       Possibilities:
               disabled   (0)
               enabled   (1)"
   ::= {er1646v2VxlBGIMVpIpV6Entry 101395456}

er1646v2VxlBGIMVpIpV6RaDnsOptionsDnsslLifeTime OBJECT-TYPE
   SYNTAX      TimeTicks
   MAX-ACCESS  read-write
   STATUS      current
   DESCRIPTION
      "Path: vxLanBridgeGroup.editConf.ipV6.ra.dnsOptions.dnssl.lifeTime

       Time in centi-second."
   ::= {er1646v2VxlBGIMVpIpV6Entry 101401600}

er1646v2VxlBGIMVpIpV6RaDnsOptionsDnsslImportDomains OBJECT-TYPE
   SYNTAX      INTEGER
               {
               disabled (0),
               enabled (1)
               }
   MAX-ACCESS  read-write
   STATUS      current
   DESCRIPTION
      "Path: vxLanBridgeGroup.editConf.ipV6.ra.dnsOptions.dnssl.importDomains

       Possibilities:
               disabled   (0)
               enabled   (1)"
   ::= {er1646v2VxlBGIMVpIpV6Entry 101403648}

er1646v2VxlBGIMVpIpV6RsSend OBJECT-TYPE
   SYNTAX      INTEGER
               {
               disabled (0),
               enabled (1)
               }
   MAX-ACCESS  read-write
   STATUS      current
   DESCRIPTION
      "Path: vxLanBridgeGroup.editConf.ipV6.rs.send

       Possibilities:
               disabled   (0)
               enabled   (1)"
   ::= {er1646v2VxlBGIMVpIpV6Entry 335609856}

er1646v2VxlBGIMVpIpV6RsMaxRandomDelay OBJECT-TYPE
   SYNTAX      TimeTicks
   MAX-ACCESS  read-write
   STATUS      current
   DESCRIPTION
      "Path: vxLanBridgeGroup.editConf.ipV6.rs.maxRandomDelay

       Time in centi-second."
   ::= {er1646v2VxlBGIMVpIpV6Entry 335675392}

er1646v2VxlBGIMVpIpV6RsInterval OBJECT-TYPE
   SYNTAX      TimeTicks
   MAX-ACCESS  read-write
   STATUS      current
   DESCRIPTION
      "Path: vxLanBridgeGroup.editConf.ipV6.rs.interval

       Time in centi-second."
   ::= {er1646v2VxlBGIMVpIpV6Entry 335740928}

er1646v2VxlBGIMVpIpV6RsMaxSolicitations OBJECT-TYPE
   SYNTAX      Integer32
   MAX-ACCESS  read-write
   STATUS      current
   DESCRIPTION
      "Path: vxLanBridgeGroup.editConf.ipV6.rs.maxSolicitations"
   ::= {er1646v2VxlBGIMVpIpV6Entry 335806464}

er1646v2VxlBGIMVpIpV6TrafficPolicyInbound OBJECT-TYPE
   SYNTAX      DisplayString
   MAX-ACCESS  read-write
   STATUS      current
   DESCRIPTION
      "Path: vxLanBridgeGroup.editConf.ipV6.trafficPolicy.inbound"
   ::= {er1646v2VxlBGIMVpIpV6Entry 184614912}

er1646v2VxlBGIMVpIpV6TrafficPolicyOutbound OBJECT-TYPE
   SYNTAX      DisplayString
   MAX-ACCESS  read-write
   STATUS      current
   DESCRIPTION
      "Path: vxLanBridgeGroup.editConf.ipV6.trafficPolicy.outbound"
   ::= {er1646v2VxlBGIMVpIpV6Entry 184680448}

er1646v2VxlBGIMVpIpV6FirewallZone OBJECT-TYPE
   SYNTAX      DisplayString
   MAX-ACCESS  read-write
   STATUS      current
   DESCRIPTION
      "Path: vxLanBridgeGroup.editConf.ipV6.firewall.zone"
   ::= {er1646v2VxlBGIMVpIpV6Entry 201392128}

er1646v2VxlBGIMVpIpV6DhcpClientAddrAC OBJECT-TYPE
   SYNTAX      INTEGER
               {
               disabled (0),
               enabled (1)
               }
   MAX-ACCESS  read-write
   STATUS      current
   DESCRIPTION
      "Path: vxLanBridgeGroup.editConf.ipV6.dhcp.client.addrAutoConfig

       Possibilities:
               disabled   (0)
               enabled   (1)"
   ::= {er1646v2VxlBGIMVpIpV6Entry 170131456}

er1646v2VxlBGIMVpIpV6DhcpClientPrDelMode OBJECT-TYPE
   SYNTAX      INTEGER
               {
               disabled (0),
               enabled (1)
               }
   MAX-ACCESS  read-write
   STATUS      current
   DESCRIPTION
      "Path: vxLanBridgeGroup.editConf.ipV6.dhcp.client.pd.mode

       Possibilities:
               disabled   (0)
               enabled   (1)"
   ::= {er1646v2VxlBGIMVpIpV6Entry 170394624}

er1646v2VxlBGIMVpIpV6DhcpClientPrDelPool OBJECT-TYPE
   SYNTAX      DisplayString
   MAX-ACCESS  read-write
   STATUS      current
   DESCRIPTION
      "Path: vxLanBridgeGroup.editConf.ipV6.dhcp.client.pd.pool"
   ::= {er1646v2VxlBGIMVpIpV6Entry 170395648}

er1646v2VxlBGIMVpIpV6DhcpClientPrDelPdExclOpt OBJECT-TYPE
   SYNTAX      INTEGER
               {
               disabled (0),
               enabled (1)
               }
   MAX-ACCESS  read-write
   STATUS      current
   DESCRIPTION
      "Path: vxLanBridgeGroup.editConf.ipV6.dhcp.client.pd.pdExclOpt

       Possibilities:
               disabled   (0)
               enabled   (1)"
   ::= {er1646v2VxlBGIMVpIpV6Entry 170396672}

er1646v2VxlBGIMVpIpV6DhcpClientDnsServerPref OBJECT-TYPE
   SYNTAX      Integer32
   MAX-ACCESS  read-write
   STATUS      current
   DESCRIPTION
      "Path: vxLanBridgeGroup.editConf.ipV6.dhcp.client.dns.serverPref"
   ::= {er1646v2VxlBGIMVpIpV6Entry 170918912}

er1646v2VxlBGIMVpIpV6DhcpClientRapidCommit OBJECT-TYPE
   SYNTAX      INTEGER
               {
               disabled (0),
               enabled (1)
               }
   MAX-ACCESS  read-write
   STATUS      current
   DESCRIPTION
      "Path: vxLanBridgeGroup.editConf.ipV6.dhcp.client.rapidCommit

       Possibilities:
               disabled   (0)
               enabled   (1)"
   ::= {er1646v2VxlBGIMVpIpV6Entry 170655744}

er1646v2VxlBGIMVpIpV6DhcpClientTimersSolTimeOut OBJECT-TYPE
   SYNTAX      TimeTicks
   MAX-ACCESS  read-write
   STATUS      current
   DESCRIPTION
      "Path: vxLanBridgeGroup.editConf.ipV6.dhcp.client.timers.solTimeOut

       Time in centi-second."
   ::= {er1646v2VxlBGIMVpIpV6Entry 171181056}

er1646v2VxlBGIMVpIpV6DhcpClientTimersSolMaxRt OBJECT-TYPE
   SYNTAX      TimeTicks
   MAX-ACCESS  read-write
   STATUS      current
   DESCRIPTION
      "Path: vxLanBridgeGroup.editConf.ipV6.dhcp.client.timers.solMaxRt

       Time in centi-second."
   ::= {er1646v2VxlBGIMVpIpV6Entry 171182080}

er1646v2VxlBGIMVpIpV6DhcpClientTimersInfoRefresh OBJECT-TYPE
   SYNTAX      TimeTicks
   MAX-ACCESS  read-write
   STATUS      current
   DESCRIPTION
      "Path: vxLanBridgeGroup.editConf.ipV6.dhcp.client.timers.infoRefresh

       Time in centi-second."
   ::= {er1646v2VxlBGIMVpIpV6Entry 171183104}

er1646v2VxlBGIMVpIpV6DhcpServerMode OBJECT-TYPE
   SYNTAX      INTEGER
               {
               disabled (0),
               enabled (1)
               }
   MAX-ACCESS  read-write
   STATUS      current
   DESCRIPTION
      "Path: vxLanBridgeGroup.editConf.ipV6.dhcp.server.mode

       Possibilities:
               disabled   (0)
               enabled   (1)"
   ::= {er1646v2VxlBGIMVpIpV6Entry 172228608}

er1646v2VxlBGIMVpIpV6DhcpServerPreference OBJECT-TYPE
   SYNTAX      Integer32
   MAX-ACCESS  read-write
   STATUS      current
   DESCRIPTION
      "Path: vxLanBridgeGroup.editConf.ipV6.dhcp.server.preference"
   ::= {er1646v2VxlBGIMVpIpV6Entry 172490752}

er1646v2VxlBGIMVpIpV6DhcpServerPool OBJECT-TYPE
   SYNTAX      DisplayString
   MAX-ACCESS  read-write
   STATUS      current
   DESCRIPTION
      "Path: vxLanBridgeGroup.editConf.ipV6.dhcp.server.pool"
   ::= {er1646v2VxlBGIMVpIpV6Entry 172752896}

er1646v2VxlBGIMVpIpV6DhcpServerRapidCommit OBJECT-TYPE
   SYNTAX      INTEGER
               {
               disabled (0),
               enabled (1)
               }
   MAX-ACCESS  read-write
   STATUS      current
   DESCRIPTION
      "Path: vxLanBridgeGroup.editConf.ipV6.dhcp.server.rapidCommit

       Possibilities:
               disabled   (0)
               enabled   (1)"
   ::= {er1646v2VxlBGIMVpIpV6Entry 173015040}

er1646v2VxlBGIMVpIpV6DhcpServerTimersInfoRefresh OBJECT-TYPE
   SYNTAX      TimeTicks
   MAX-ACCESS  read-write
   STATUS      current
   DESCRIPTION
      "Path: vxLanBridgeGroup.editConf.ipV6.dhcp.server.timers.infoRefresh

       Time in centi-second."
   ::= {er1646v2VxlBGIMVpIpV6Entry 173278208}

er1646v2VxlBGIMVpIpV6DhcpRelayMode OBJECT-TYPE
   SYNTAX      INTEGER
               {
               disabled (0),
               enabled (1)
               }
   MAX-ACCESS  read-write
   STATUS      current
   DESCRIPTION
      "Path: vxLanBridgeGroup.editConf.ipV6.dhcp.relay.mode

       Possibilities:
               disabled   (0)
               enabled   (1)"
   ::= {er1646v2VxlBGIMVpIpV6Entry 174071808}

er1646v2VxlBGIMVpIpV6SendRedirect OBJECT-TYPE
   SYNTAX      INTEGER
               {
               disabled (0),
               enabled (1)
               }
   MAX-ACCESS  read-write
   STATUS      current
   DESCRIPTION
      "Path: vxLanBridgeGroup.editConf.ipV6.sendRedirect

       Possibilities:
               disabled   (0)
               enabled   (1)"
   ::= {er1646v2VxlBGIMVpIpV6Entry 117440512}

er1646v2VxlBGIMVpIpV6LinkMtu OBJECT-TYPE
   SYNTAX      Integer32
   MAX-ACCESS  read-write
   STATUS      current
   DESCRIPTION
      "Path: vxLanBridgeGroup.editConf.ipV6.linkMtu"
   ::= {er1646v2VxlBGIMVpIpV6Entry 134217728}

er1646v2VxlBGIMVpIpV6InterfaceId OBJECT-TYPE
   SYNTAX      OCTET STRING
   MAX-ACCESS  read-write
   STATUS      current
   DESCRIPTION
      "Path: vxLanBridgeGroup.editConf.ipV6.interfaceId"
   ::= {er1646v2VxlBGIMVpIpV6Entry 150994944}

er1646v2VxlBGIMVpIpV6MF OBJECT-TYPE
   SYNTAX      Integer32
   MAX-ACCESS  read-write
   STATUS      current
   DESCRIPTION
      "Path: vxLanBridgeGroup.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VxlBGIMVpIpV6Entry 285212672}

er1646v2VxlBGIMVpIpV6IcmpMessagesNoRoute OBJECT-TYPE
   SYNTAX      INTEGER
               {
               disabled (0),
               enabled (1)
               }
   MAX-ACCESS  read-write
   STATUS      current
   DESCRIPTION
      "Path: vxLanBridgeGroup.editConf.ipV6.icmpMessages.noRoute

       Possibilities:
               disabled   (0)
               enabled   (1)"
   ::= {er1646v2VxlBGIMVpIpV6Entry 302055424}

er1646v2VxlBGIMVpIpV6IcmpMessagesBeyondScope OBJECT-TYPE
   SYNTAX      INTEGER
               {
               disabled (0),
               enabled (1)
               }
   MAX-ACCESS  read-write
   STATUS      current
   DESCRIPTION
      "Path: vxLanBridgeGroup.editConf.ipV6.icmpMessages.beyondScope

       Possibilities:
               disabled   (0)
               enabled   (1)"
   ::= {er1646v2VxlBGIMVpIpV6Entry 302186496}

er1646v2VxlBGIMVpIpV6IcmpMessagesAddressUnreachable OBJECT-TYPE
   SYNTAX      INTEGER
               {
               disabled (0),
               enabled (1)
               }
   MAX-ACCESS  read-write
   STATUS      current
   DESCRIPTION
      "Path: vxLanBridgeGroup.editConf.ipV6.icmpMessages.addressUnreachable

       Possibilities:
               disabled   (0)
               enabled   (1)"
   ::= {er1646v2VxlBGIMVpIpV6Entry 302252032}

er1646v2VxlBGIMVpIpV6IcmpMessagesPortUnreachable OBJECT-TYPE
   SYNTAX      INTEGER
               {
               disabled (0),
               enabled (1)
               }
   MAX-ACCESS  read-write
   STATUS      current
   DESCRIPTION
      "Path: vxLanBridgeGroup.editConf.ipV6.icmpMessages.portUnreachable

       Possibilities:
               disabled   (0)
               enabled   (1)"
   ::= {er1646v2VxlBGIMVpIpV6Entry 302317568}

er1646v2VxlBGIMVpIpV6IcmpMessagesPacketTooBig OBJECT-TYPE
   SYNTAX      INTEGER
               {
               disabled (0),
               enabled (1)
               }
   MAX-ACCESS  read-write
   STATUS      current
   DESCRIPTION
      "Path: vxLanBridgeGroup.editConf.ipV6.icmpMessages.packetTooBig

       Possibilities:
               disabled   (0)
               enabled   (1)"
   ::= {er1646v2VxlBGIMVpIpV6Entry 302645248}

er1646v2VxlBGIMVpIpV6IcmpMessagesHopLimitExceeded OBJECT-TYPE
   SYNTAX      INTEGER
               {
               disabled (0),
               enabled (1)
               }
   MAX-ACCESS  read-write
   STATUS      current
   DESCRIPTION
      "Path: vxLanBridgeGroup.editConf.ipV6.icmpMessages.hopLimitExceeded

       Possibilities:
               disabled   (0)
               enabled   (1)"
   ::= {er1646v2VxlBGIMVpIpV6Entry 303300608}

er1646v2VxlBGIMVpIpV6IcmpMessagesFragTimeExceeded OBJECT-TYPE
   SYNTAX      INTEGER
               {
               disabled (0),
               enabled (1)
               }
   MAX-ACCESS  read-write
   STATUS      current
   DESCRIPTION
      "Path: vxLanBridgeGroup.editConf.ipV6.icmpMessages.fragTimeExceeded

       Possibilities:
               disabled   (0)
               enabled   (1)"
   ::= {er1646v2VxlBGIMVpIpV6Entry 303366144}

er1646v2VxlBGIMVpIpV6IcmpMessagesHeaderFieldErr OBJECT-TYPE
   SYNTAX      INTEGER
               {
               disabled (0),
               enabled (1)
               }
   MAX-ACCESS  read-write
   STATUS      current
   DESCRIPTION
      "Path: vxLanBridgeGroup.editConf.ipV6.icmpMessages.headerFieldErr

       Possibilities:
               disabled   (0)
               enabled   (1)"
   ::= {er1646v2VxlBGIMVpIpV6Entry 303955968}

er1646v2VxlBGIMVpIpV6IcmpMessagesOptionUnrecognized OBJECT-TYPE
   SYNTAX      INTEGER
               {
               disabled (0),
               enabled (1)
               }
   MAX-ACCESS  read-write
   STATUS      current
   DESCRIPTION
      "Path: vxLanBridgeGroup.editConf.ipV6.icmpMessages.optionUnrecognized

       Possibilities:
               disabled   (0)
               enabled   (1)"
   ::= {er1646v2VxlBGIMVpIpV6Entry 304087040}

er1646v2VxlBGIMVpIpV6IcmpMessagesRedirect OBJECT-TYPE
   SYNTAX      INTEGER
               {
               disabled (0),
               enabled (1)
               }
   MAX-ACCESS  read-write
   STATUS      current
   DESCRIPTION
      "Path: vxLanBridgeGroup.editConf.ipV6.icmpMessages.redirect

       Possibilities:
               disabled   (0)
               enabled   (1)"
   ::= {er1646v2VxlBGIMVpIpV6Entry 304611328}

er1646v2VxlBGIMVpIpV6Addresses OBJECT-TYPE
   SYNTAX      SEQUENCE OF Er1646v2VxlBGIMVpIpV6AddressesEntry
   MAX-ACCESS  not-accessible
   STATUS      current
   DESCRIPTION
      ""
   ::= {er1646v2VxlBGIMVpIpV6 50331648}

er1646v2VxlBGIMVpIpV6AddressesEntry OBJECT-TYPE
   SYNTAX      Er1646v2VxlBGIMVpIpV6AddressesEntry
   MAX-ACCESS  not-accessible
   STATUS      current
   DESCRIPTION
      ""
   INDEX      { er1646v2VxlBGIMVpIpV6AddressesGlobalIx,
                er1646v2VxlBGIMVpIpV6AddressesTableIx }
   ::= {er1646v2VxlBGIMVpIpV6Addresses 1}

Er1646v2VxlBGIMVpIpV6AddressesEntry ::=
   SEQUENCE
      {
      er1646v2VxlBGIMVpIpV6AddressesActions
         VariableLengthTableActions,
      er1646v2VxlBGIMVpIpV6AddressesGlobalIx
         GlobalIndex,
      er1646v2VxlBGIMVpIpV6AddressesTableIx
         TableIndex,
      er1646v2VxlBGIMVpIpV6AddressesType
         INTEGER,
      er1646v2VxlBGIMVpIpV6AddressesAddress
         Ipv6Address,
      er1646v2VxlBGIMVpIpV6AddressesPrefixLength
         Integer32,
      er1646v2VxlBGIMVpIpV6AddressesGeneralPrefix
         DisplayString,
      er1646v2VxlBGIMVpIpV6AddressesRaSend
         INTEGER,
      er1646v2VxlBGIMVpIpV6AddressesRaOnLinkFlag
         INTEGER,
      er1646v2VxlBGIMVpIpV6AddressesRaAutoFlag
         INTEGER,
      er1646v2VxlBGIMVpIpV6AddressesRaValidLifeTime
         TimeTicks,
      er1646v2VxlBGIMVpIpV6AddressesRaValidLTMode
         INTEGER,
      er1646v2VxlBGIMVpIpV6AddressesRaPrefLifeTime
         TimeTicks,
      er1646v2VxlBGIMVpIpV6AddressesRaPrefLTMode
         INTEGER
      }

er1646v2VxlBGIMVpIpV6AddressesActions OBJECT-TYPE
   SYNTAX      VariableLengthTableActions
   MAX-ACCESS  read-write
   STATUS      current
   DESCRIPTION
      "By way of this field, some manipulations
       on this table may be performed."
   ::= {er1646v2VxlBGIMVpIpV6AddressesEntry 2}

er1646v2VxlBGIMVpIpV6AddressesGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6AddressesEntry 10}

er1646v2VxlBGIMVpIpV6AddressesTableIx OBJECT-TYPE
   SYNTAX      TableIndex
   MAX-ACCESS  not-accessible
   STATUS      current
   DESCRIPTION
      ""
   ::= {er1646v2VxlBGIMVpIpV6AddressesEntry 11}

er1646v2VxlBGIMVpIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vxLanBridgeGroup.editConf.ipV6.addresses.type

       Possibilities:
               unicast   (0)
               eui64   (1)
               anycast   (2)
               linkLocal   (3)
               generalPrefix   (4)"
   ::= {er1646v2VxlBGIMVpIpV6AddressesEntry 50331648}

er1646v2VxlBGIMVpIpV6AddressesAddress OBJECT-TYPE
   SYNTAX      Ipv6Address
   MAX-ACCESS  read-write
   STATUS      current
   DESCRIPTION
      "Path: vxLanBridgeGroup.editConf.ipV6.addresses.address

       ipv6 address"
   ::= {er1646v2VxlBGIMVpIpV6AddressesEntry 16777216}

er1646v2VxlBGIMVpIpV6AddressesPrefixLength OBJECT-TYPE
   SYNTAX      Integer32
   MAX-ACCESS  read-write
   STATUS      current
   DESCRIPTION
      "Path: vxLanBridgeGroup.editConf.ipV6.addresses.prefixLength"
   ::= {er1646v2VxlBGIMVpIpV6AddressesEntry 33554432}

er1646v2VxlBGIMVpIpV6AddressesGeneralPrefix OBJECT-TYPE
   SYNTAX      DisplayString
   MAX-ACCESS  read-write
   STATUS      current
   DESCRIPTION
      "Path: vxLanBridgeGroup.editConf.ipV6.addresses.generalPrefix"
   ::= {er1646v2VxlBGIMVpIpV6AddressesEntry 83886080}

er1646v2VxlBGIMVpIpV6AddressesRaSend OBJECT-TYPE
   SYNTAX      INTEGER
               {
               disabled (0),
               enabled (1)
               }
   MAX-ACCESS  read-write
   STATUS      current
   DESCRIPTION
      "Path: vxLanBridgeGroup.editConf.ipV6.addresses.ra.send

       Possibilities:
               disabled   (0)
               enabled   (1)"
   ::= {er1646v2VxlBGIMVpIpV6AddressesEntry 67174400}

er1646v2VxlBGIMVpIpV6AddressesRaOnLinkFlag OBJECT-TYPE
   SYNTAX      INTEGER
               {
               disabled (0),
               enabled (1)
               }
   MAX-ACCESS  read-write
   STATUS      current
   DESCRIPTION
      "Path: vxLanBridgeGroup.editConf.ipV6.addresses.ra.onLinkFlag

       Possibilities:
               disabled   (0)
               enabled   (1)"
   ::= {er1646v2VxlBGIMVpIpV6AddressesEntry 67371008}

er1646v2VxlBGIMVpIpV6AddressesRaAutoFlag OBJECT-TYPE
   SYNTAX      INTEGER
               {
               disabled (0),
               enabled (1)
               }
   MAX-ACCESS  read-write
   STATUS      current
   DESCRIPTION
      "Path: vxLanBridgeGroup.editConf.ipV6.addresses.ra.autonomousFlag

       Possibilities:
               disabled   (0)
               enabled   (1)"
   ::= {er1646v2VxlBGIMVpIpV6AddressesEntry 67567616}

er1646v2VxlBGIMVpIpV6AddressesRaValidLifeTime OBJECT-TYPE
   SYNTAX      TimeTicks
   MAX-ACCESS  read-write
   STATUS      current
   DESCRIPTION
      "Path: vxLanBridgeGroup.editConf.ipV6.addresses.ra.validLifeTime

       Time in centi-second."
   ::= {er1646v2VxlBGIMVpIpV6AddressesEntry 67239936}

er1646v2VxlBGIMVpIpV6AddressesRaValidLTMode OBJECT-TYPE
   SYNTAX      INTEGER
               {
               fixed (0),
               infinite (2)
               }
   MAX-ACCESS  read-write
   STATUS      current
   DESCRIPTION
      "Path: vxLanBridgeGroup.editConf.ipV6.addresses.ra.validLifeTimeMode

       Possibilities:
               fixed   (0)
               infinite   (2)"
   ::= {er1646v2VxlBGIMVpIpV6AddressesEntry 67305472}

er1646v2VxlBGIMVpIpV6AddressesRaPrefLifeTime OBJECT-TYPE
   SYNTAX      TimeTicks
   MAX-ACCESS  read-write
   STATUS      current
   DESCRIPTION
      "Path: vxLanBridgeGroup.editConf.ipV6.addresses.ra.prefLifeTime

       Time in centi-second."
   ::= {er1646v2VxlBGIMVpIpV6AddressesEntry 67436544}

er1646v2VxlBGIMVpIpV6AddressesRaPrefLTMode OBJECT-TYPE
   SYNTAX      INTEGER
               {
               fixed (0),
               infinite (2)
               }
   MAX-ACCESS  read-write
   STATUS      current
   DESCRIPTION
      "Path: vxLanBridgeGroup.editConf.ipV6.addresses.ra.prefLifeTimeMode

       Possibilities:
               fixed   (0)
               infinite   (2)"
   ::= {er1646v2VxlBGIMVpIpV6AddressesEntry 67502080}

er1646v2VxlBGIMVpIpV6RaDnsOptionsRdnssServers OBJECT-TYPE
   SYNTAX      SEQUENCE OF Er1646v2VxlBGIMVpIpV6RaDnsOptionsRdnssServersEntry
   MAX-ACCESS  not-accessible
   STATUS      current
   DESCRIPTION
      ""
   ::= {er1646v2VxlBGIMVpIpV6 101394432}

er1646v2VxlBGIMVpIpV6RaDnsOptionsRdnssServersEntry OBJECT-TYPE
   SYNTAX      Er1646v2VxlBGIMVpIpV6RaDnsOptionsRdnssServersEntry
   MAX-ACCESS  not-accessible
   STATUS      current
   DESCRIPTION
      ""
   INDEX      { er1646v2VxlBGIMVpIpV6RaDnsOptionsRdnssServersGlobalIx,
                er1646v2VxlBGIMVpIpV6RaDnsOptionsRdnssServersTableIx }
   ::= {er1646v2VxlBGIMVpIpV6RaDnsOptionsRdnssServers 1}

Er1646v2VxlBGIMVpIpV6RaDnsOptionsRdnssServersEntry ::=
   SEQUENCE
      {
      er1646v2VxlBGIMVpIpV6RaDnsOptionsRdnssServersActions
         VariableLengthTableActions,
      er1646v2VxlBGIMVpIpV6RaDnsOptionsRdnssServersGlobalIx
         GlobalIndex,
      er1646v2VxlBGIMVpIpV6RaDnsOptionsRdnssServersTableIx
         TableIndex,
      er1646v2VxlBGIMVpIpV6RaDnsOptionsRdnssServersAddress
         Ipv6Address
      }

er1646v2VxlBGIMVpIpV6RaDnsOptionsRdnssServersActions OBJECT-TYPE
   SYNTAX      VariableLengthTableActions
   MAX-ACCESS  read-write
   STATUS      current
   DESCRIPTION
      "By way of this field, some manipulations
       on this table may be performed."
   ::= {er1646v2VxlBGIMVpIpV6RaDnsOptionsRdnssServersEntry 2}

er1646v2VxlBGIMVpIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6RaDnsOptionsRdnssServersEntry 10}

er1646v2VxlBGIMVpIpV6RaDnsOptionsRdnssServersTableIx OBJECT-TYPE
   SYNTAX      TableIndex
   MAX-ACCESS  not-accessible
   STATUS      current
   DESCRIPTION
      ""
   ::= {er1646v2VxlBGIMVpIpV6RaDnsOptionsRdnssServersEntry 11}

er1646v2VxlBGIMVpIpV6RaDnsOptionsRdnssServersAddress OBJECT-TYPE
   SYNTAX      Ipv6Address
   MAX-ACCESS  read-write
   STATUS      current
   DESCRIPTION
      "Path: vxLanBridgeGroup.editConf.ipV6.ra.dnsOptions.rdnss.servers.address

       ipv6 address"
   ::= {er1646v2VxlBGIMVpIpV6RaDnsOptionsRdnssServersEntry 16777216}

er1646v2VxlBGIMVpIpV6RaDnsOptionsDnsslDomains OBJECT-TYPE
   SYNTAX      SEQUENCE OF Er1646v2VxlBGIMVpIpV6RaDnsOptionsDnsslDomainsEntry
   MAX-ACCESS  not-accessible
   STATUS      current
   DESCRIPTION
      ""
   ::= {er1646v2VxlBGIMVpIpV6 101402624}

er1646v2VxlBGIMVpIpV6RaDnsOptionsDnsslDomainsEntry OBJECT-TYPE
   SYNTAX      Er1646v2VxlBGIMVpIpV6RaDnsOptionsDnsslDomainsEntry
   MAX-ACCESS  not-accessible
   STATUS      current
   DESCRIPTION
      ""
   INDEX      { er1646v2VxlBGIMVpIpV6RaDnsOptionsDnsslDomainsGlobalIx,
                er1646v2VxlBGIMVpIpV6RaDnsOptionsDnsslDomainsTableIx }
   ::= {er1646v2VxlBGIMVpIpV6RaDnsOptionsDnsslDomains 1}

Er1646v2VxlBGIMVpIpV6RaDnsOptionsDnsslDomainsEntry ::=
   SEQUENCE
      {
      er1646v2VxlBGIMVpIpV6RaDnsOptionsDnsslDomainsActions
         VariableLengthTableActions,
      er1646v2VxlBGIMVpIpV6RaDnsOptionsDnsslDomainsGlobalIx
         GlobalIndex,
      er1646v2VxlBGIMVpIpV6RaDnsOptionsDnsslDomainsTableIx
         TableIndex,
      er1646v2VxlBGIMVpIpV6RaDnsOptionsDnsslDomainsName
         DisplayString
      }

er1646v2VxlBGIMVpIpV6RaDnsOptionsDnsslDomainsActions OBJECT-TYPE
   SYNTAX      VariableLengthTableActions
   MAX-ACCESS  read-write
   STATUS      current
   DESCRIPTION
      "By way of this field, some manipulations
       on this table may be performed."
   ::= {er1646v2VxlBGIMVpIpV6RaDnsOptionsDnsslDomainsEntry 2}

er1646v2VxlBGIMVpIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6RaDnsOptionsDnsslDomainsEntry 10}

er1646v2VxlBGIMVpIpV6RaDnsOptionsDnsslDomainsTableIx OBJECT-TYPE
   SYNTAX      TableIndex
   MAX-ACCESS  not-accessible
   STATUS      current
   DESCRIPTION
      ""
   ::= {er1646v2VxlBGIMVpIpV6RaDnsOptionsDnsslDomainsEntry 11}

er1646v2VxlBGIMVpIpV6RaDnsOptionsDnsslDomainsName OBJECT-TYPE
   SYNTAX      DisplayString
   MAX-ACCESS  read-write
   STATUS      current
   DESCRIPTION
      "Path: vxLanBridgeGroup.editConf.ipV6.ra.dnsOptions.dnssl.domains.name"
   ::= {er1646v2VxlBGIMVpIpV6RaDnsOptionsDnsslDomainsEntry 16777216}

er1646v2VxlBGIMVpIpV6DhcpClientUserClassOpt OBJECT-TYPE
   SYNTAX      SEQUENCE OF Er1646v2VxlBGIMVpIpV6DhcpClientUserClassOptEntry
   MAX-ACCESS  not-accessible
   STATUS      current
   DESCRIPTION
      ""
   ::= {er1646v2VxlBGIMVpIpV6 171442176}

er1646v2VxlBGIMVpIpV6DhcpClientUserClassOptEntry OBJECT-TYPE
   SYNTAX      Er1646v2VxlBGIMVpIpV6DhcpClientUserClassOptEntry
   MAX-ACCESS  not-accessible
   STATUS      current
   DESCRIPTION
      ""
   INDEX      { er1646v2VxlBGIMVpIpV6DhcpClientUserClassOptGlobalIx,
                er1646v2VxlBGIMVpIpV6DhcpClientUserClassOptTableIx }
   ::= {er1646v2VxlBGIMVpIpV6DhcpClientUserClassOpt 1}

Er1646v2VxlBGIMVpIpV6DhcpClientUserClassOptEntry ::=
   SEQUENCE
      {
      er1646v2VxlBGIMVpIpV6DhcpClientUserClassOptActions
         VariableLengthTableActions,
      er1646v2VxlBGIMVpIpV6DhcpClientUserClassOptGlobalIx
         GlobalIndex,
      er1646v2VxlBGIMVpIpV6DhcpClientUserClassOptTableIx
         TableIndex,
      er1646v2VxlBGIMVpIpV6DhcpClientUserClassOptValueAscii
         DisplayString,
      er1646v2VxlBGIMVpIpV6DhcpClientUserClassOptValueDecimal
         Integer32,
      er1646v2VxlBGIMVpIpV6DhcpClientUserClassOptValueHexData
         OCTET STRING
      }

er1646v2VxlBGIMVpIpV6DhcpClientUserClassOptActions OBJECT-TYPE
   SYNTAX      VariableLengthTableActions
   MAX-ACCESS  read-write
   STATUS      current
   DESCRIPTION
      "By way of this field, some manipulations
       on this table may be performed."
   ::= {er1646v2VxlBGIMVpIpV6DhcpClientUserClassOptEntry 2}

er1646v2VxlBGIMVpIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6DhcpClientUserClassOptEntry 10}

er1646v2VxlBGIMVpIpV6DhcpClientUserClassOptTableIx OBJECT-TYPE
   SYNTAX      TableIndex
   MAX-ACCESS  not-accessible
   STATUS      current
   DESCRIPTION
      ""
   ::= {er1646v2VxlBGIMVpIpV6DhcpClientUserClassOptEntry 11}

er1646v2VxlBGIMVpIpV6DhcpClientUserClassOptValueAscii OBJECT-TYPE
   SYNTAX      DisplayString
   MAX-ACCESS  read-write
   STATUS      current
   DESCRIPTION
      "Path: vxLanBridgeGroup.editConf.ipV6.dhcp.client.userClassOpt.value.ascii"
   ::= {er1646v2VxlBGIMVpIpV6DhcpClientUserClassOptEntry 16842752}

er1646v2VxlBGIMVpIpV6DhcpClientUserClassOptValueDecimal OBJECT-TYPE
   SYNTAX      Integer32
   MAX-ACCESS  read-write
   STATUS      current
   DESCRIPTION
      "Path: vxLanBridgeGroup.editConf.ipV6.dhcp.client.userClassOpt.value.decimal"
   ::= {er1646v2VxlBGIMVpIpV6DhcpClientUserClassOptEntry 16908288}

er1646v2VxlBGIMVpIpV6DhcpClientUserClassOptValueHexData OBJECT-TYPE
   SYNTAX      OCTET STRING
   MAX-ACCESS  read-write
   STATUS      current
   DESCRIPTION
      "Path: vxLanBridgeGroup.editConf.ipV6.dhcp.client.userClassOpt.value.hexData"
   ::= {er1646v2VxlBGIMVpIpV6DhcpClientUserClassOptEntry 16973824}

er1646v2VxlBGIMVpIpV6DhcpClientVendorCl OBJECT-TYPE
   SYNTAX      SEQUENCE OF Er1646v2VxlBGIMVpIpV6DhcpClientVendorClEntry
   MAX-ACCESS  not-accessible
   STATUS      current
   DESCRIPTION
      ""
   ::= {er1646v2VxlBGIMVpIpV6 171704320}

er1646v2VxlBGIMVpIpV6DhcpClientVendorClEntry OBJECT-TYPE
   SYNTAX      Er1646v2VxlBGIMVpIpV6DhcpClientVendorClEntry
   MAX-ACCESS  not-accessible
   STATUS      current
   DESCRIPTION
      ""
   INDEX      { er1646v2VxlBGIMVpIpV6DhcpClientVendorClGlobalIx,
                er1646v2VxlBGIMVpIpV6DhcpClientVendorClTableIx }
   ::= {er1646v2VxlBGIMVpIpV6DhcpClientVendorCl 1}

Er1646v2VxlBGIMVpIpV6DhcpClientVendorClEntry ::=
   SEQUENCE
      {
      er1646v2VxlBGIMVpIpV6DhcpClientVendorClActions
         VariableLengthTableActions,
      er1646v2VxlBGIMVpIpV6DhcpClientVendorClGlobalIx
         GlobalIndex,
      er1646v2VxlBGIMVpIpV6DhcpClientVendorClTableIx
         TableIndex,
      er1646v2VxlBGIMVpIpV6DhcpClientVendorClValueAscii
         DisplayString,
      er1646v2VxlBGIMVpIpV6DhcpClientVendorClValueDecimal
         Integer32,
      er1646v2VxlBGIMVpIpV6DhcpClientVendorClValueHexData
         OCTET STRING
      }

er1646v2VxlBGIMVpIpV6DhcpClientVendorClActions OBJECT-TYPE
   SYNTAX      VariableLengthTableActions
   MAX-ACCESS  read-write
   STATUS      current
   DESCRIPTION
      "By way of this field, some manipulations
       on this table may be performed."
   ::= {er1646v2VxlBGIMVpIpV6DhcpClientVendorClEntry 2}

er1646v2VxlBGIMVpIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6DhcpClientVendorClEntry 10}

er1646v2VxlBGIMVpIpV6DhcpClientVendorClTableIx OBJECT-TYPE
   SYNTAX      TableIndex
   MAX-ACCESS  not-accessible
   STATUS      current
   DESCRIPTION
      ""
   ::= {er1646v2VxlBGIMVpIpV6DhcpClientVendorClEntry 11}

er1646v2VxlBGIMVpIpV6DhcpClientVendorClValueAscii OBJECT-TYPE
   SYNTAX      DisplayString
   MAX-ACCESS  read-write
   STATUS      current
   DESCRIPTION
      "Path: vxLanBridgeGroup.editConf.ipV6.dhcp.client.vendorClassOpt.value.ascii"
   ::= {er1646v2VxlBGIMVpIpV6DhcpClientVendorClEntry 16842752}

er1646v2VxlBGIMVpIpV6DhcpClientVendorClValueDecimal OBJECT-TYPE
   SYNTAX      Integer32
   MAX-ACCESS  read-write
   STATUS      current
   DESCRIPTION
      "Path: vxLanBridgeGroup.editConf.ipV6.dhcp.client.vendorClassOpt.value.decimal"
   ::= {er1646v2VxlBGIMVpIpV6DhcpClientVendorClEntry 16908288}

er1646v2VxlBGIMVpIpV6DhcpClientVendorClValueHexData OBJECT-TYPE
   SYNTAX      OCTET STRING
   MAX-ACCESS  read-write
   STATUS      current
   DESCRIPTION
      "Path: vxLanBridgeGroup.editConf.ipV6.dhcp.client.vendorClassOpt.value.hexData"
   ::= {er1646v2VxlBGIMVpIpV6DhcpClientVendorClEntry 16973824}

er1646v2VxlBGIMVpIpV6DhcpRelayDestinations OBJECT-TYPE
   SYNTAX      SEQUENCE OF Er1646v2VxlBGIMVpIpV6DhcpRelayDestinationsEntry
   MAX-ACCESS  not-accessible
   STATUS      current
   DESCRIPTION
      ""
   ::= {er1646v2VxlBGIMVpIpV6 174080000}

er1646v2VxlBGIMVpIpV6DhcpRelayDestinationsEntry OBJECT-TYPE
   SYNTAX      Er1646v2VxlBGIMVpIpV6DhcpRelayDestinationsEntry
   MAX-ACCESS  not-accessible
   STATUS      current
   DESCRIPTION
      ""
   INDEX      { er1646v2VxlBGIMVpIpV6DhcpRelayDestinationsGlobalIx,
                er1646v2VxlBGIMVpIpV6DhcpRelayDestinationsTableIx }
   ::= {er1646v2VxlBGIMVpIpV6DhcpRelayDestinations 1}

Er1646v2VxlBGIMVpIpV6DhcpRelayDestinationsEntry ::=
   SEQUENCE
      {
      er1646v2VxlBGIMVpIpV6DhcpRelayDestinationsActions
         VariableLengthTableActions,
      er1646v2VxlBGIMVpIpV6DhcpRelayDestinationsGlobalIx
         GlobalIndex,
      er1646v2VxlBGIMVpIpV6DhcpRelayDestinationsTableIx
         TableIndex,
      er1646v2VxlBGIMVpIpV6DhcpRelayDestinationsAddress
         Ipv6Address,
      er1646v2VxlBGIMVpIpV6DhcpRelayDestinationsInterface
         DisplayString
      }

er1646v2VxlBGIMVpIpV6DhcpRelayDestinationsActions OBJECT-TYPE
   SYNTAX      VariableLengthTableActions
   MAX-ACCESS  read-write
   STATUS      current
   DESCRIPTION
      "By way of this field, some manipulations
       on this table may be performed."
   ::= {er1646v2VxlBGIMVpIpV6DhcpRelayDestinationsEntry 2}

er1646v2VxlBGIMVpIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VxlBGIMVpIpV6DhcpRelayDestinationsEntry 10}

er1646v2VxlBGIMVpIpV6DhcpRelayDestinationsTableIx OBJECT-TYPE
   SYNTAX      TableIndex
   MAX-ACCESS  not-accessible
   STATUS      current
   DESCRIPTION
      ""
   ::= {er1646v2VxlBGIMVpIpV6DhcpRelayDestinationsEntry 11}

er1646v2VxlBGIMVpIpV6DhcpRelayDestinationsAddress OBJECT-TYPE
   SYNTAX      Ipv6Address
   MAX-ACCESS  read-write
   STATUS      current
   DESCRIPTION
      "Path: vxLanBridgeGroup.editConf.ipV6.dhcp.relay.destinations.address

       ipv6 address"
   ::= {er1646v2VxlBGIMVpIpV6DhcpRelayDestinationsEntry 16777216}

er1646v2VxlBGIMVpIpV6DhcpRelayDestinationsInterface OBJECT-TYPE
   SYNTAX      DisplayString
   MAX-ACCESS  read-write
   STATUS      current
   DESCRIPTION
      "Path: vxLanBridgeGroup.editConf.ipV6.dhcp.relay.destinations.interface"
   ::= {er1646v2VxlBGIMVpIpV6DhcpRelayDestinationsEntry 33554432}


er1646v2VxlBGIMVpArp OBJECT IDENTIFIER ::= {er1646v2VxlBGIMVp 19}

er1646v2VxlBGIMVpArpSSCTable OBJECT-TYPE
   SYNTAX      SEQUENCE OF Er1646v2VxlBGIMVpArpEntry
   MAX-ACCESS  not-accessible
   STATUS      current
   DESCRIPTION
      "ethernet related config parameters"
   ::= {er1646v2VxlBGIMVpArp 1}

er1646v2VxlBGIMVpArpEntry OBJECT-TYPE
   SYNTAX      Er1646v2VxlBGIMVpArpEntry
   MAX-ACCESS  not-accessible
   STATUS      current
   DESCRIPTION
      ""
   INDEX      { er1646v2VxlBGIMVpArpGlobalIx }
   ::= {er1646v2VxlBGIMVpArpSSCTable 1}

Er1646v2VxlBGIMVpArpEntry ::=
   SEQUENCE
      {
      er1646v2VxlBGIMVpArpGlobalIx
         GlobalIndex,
      er1646v2VxlBGIMVpArpTimeOut
         TimeTicks,
      er1646v2VxlBGIMVpArpProxyArp
         INTEGER
      }

er1646v2VxlBGIMVpArpGlobalIx OBJECT-TYPE
   SYNTAX      GlobalIndex
   MAX-ACCESS  not-accessible
   STATUS      current
   DESCRIPTION
      "The value of the tlsCntTreeGlobalIndex of the MANAGED OBJECT."
   ::= {er1646v2VxlBGIMVpArpEntry 10}

er1646v2VxlBGIMVpArpTimeOut OBJECT-TYPE
   SYNTAX      TimeTicks
   MAX-ACCESS  read-write
   STATUS      current
   DESCRIPTION
      "Path: vxLanBridgeGroup.editConf.arp.timeOut

       Time in centi-second."
   ::= {er1646v2VxlBGIMVpArpEntry 201326592}

er1646v2VxlBGIMVpArpProxyArp OBJECT-TYPE
   SYNTAX      INTEGER
               {
               disabled (0),
               enabled (1)
               }
   MAX-ACCESS  read-write
   STATUS      current
   DESCRIPTION
      "Path: vxLanBridgeGroup.editConf.arp.proxyArp

       Possibilities:
               disabled   (0)
               enabled   (1)"
   ::= {er1646v2VxlBGIMVpArpEntry 838860800}

er1646v2VxlBGIMVpArpStaticArp OBJECT-TYPE
   SYNTAX      SEQUENCE OF Er1646v2VxlBGIMVpArpStaticArpEntry
   MAX-ACCESS  not-accessible
   STATUS      current
   DESCRIPTION
      ""
   ::= {er1646v2VxlBGIMVpArp 50331648}

er1646v2VxlBGIMVpArpStaticArpEntry OBJECT-TYPE
   SYNTAX      Er1646v2VxlBGIMVpArpStaticArpEntry
   MAX-ACCESS  not-accessible
   STATUS      current
   DESCRIPTION
      ""
   INDEX      { er1646v2VxlBGIMVpArpStaticArpGlobalIx,
                er1646v2VxlBGIMVpArpStaticArpTableIx }
   ::= {er1646v2VxlBGIMVpArpStaticArp 1}

Er1646v2VxlBGIMVpArpStaticArpEntry ::=
   SEQUENCE
      {
      er1646v2VxlBGIMVpArpStaticArpActions
         VariableLengthTableActions,
      er1646v2VxlBGIMVpArpStaticArpGlobalIx
         GlobalIndex,
      er1646v2VxlBGIMVpArpStaticArpTableIx
         TableIndex,
      er1646v2VxlBGIMVpArpStaticArpMacAddress
         OCTET STRING,
      er1646v2VxlBGIMVpArpStaticArpIpAddress
         IpAddress
      }

er1646v2VxlBGIMVpArpStaticArpActions OBJECT-TYPE
   SYNTAX      VariableLengthTableActions
   MAX-ACCESS  read-write
   STATUS      current
   DESCRIPTION
      "By way of this field, some manipulations
       on this table may be performed."
   ::= {er1646v2VxlBGIMVpArpStaticArpEntry 2}

er1646v2VxlBGIMVpArpStaticArpGlobalIx OBJECT-TYPE
   SYNTAX      GlobalIndex
   MAX-ACCESS  not-accessible
   STATUS      current
   DESCRIPTION
      "The value of the tlsCntTreeGlobalIndex of the MANAGED OBJECT."
   ::= {er1646v2VxlBGIMVpArpStaticArpEntry 10}

er1646v2VxlBGIMVpArpStaticArpTableIx OBJECT-TYPE
   SYNTAX      TableIndex
   MAX-ACCESS  not-accessible
   STATUS      current
   DESCRIPTION
      ""
   ::= {er1646v2VxlBGIMVpArpStaticArpEntry 11}

er1646v2VxlBGIMVpArpStaticArpMacAddress OBJECT-TYPE
   SYNTAX      OCTET STRING
   MAX-ACCESS  read-write
   STATUS      current
   DESCRIPTION
      "Path: vxLanBridgeGroup.editConf.arp.staticArp.macAddress

       MAC address."
   ::= {er1646v2VxlBGIMVpArpStaticArpEntry 16777216}

er1646v2VxlBGIMVpArpStaticArpIpAddress OBJECT-TYPE
   SYNTAX      IpAddress
   MAX-ACCESS  read-write
   STATUS      current
   DESCRIPTION
      "Path: vxLanBridgeGroup.editConf.arp.staticArp.ipAddress"
   ::= {er1646v2VxlBGIMVpArpStaticArpEntry 33554432}


er1646v2VxlBGIMVpSpanningTree OBJECT IDENTIFIER ::= {er1646v2VxlBGIMVp 5}

er1646v2VxlBGIMVpSpanningTreeSSCTable OBJECT-TYPE
   SYNTAX      SEQUENCE OF Er1646v2VxlBGIMVpSpanningTreeEntry
   MAX-ACCESS  not-accessible
   STATUS      current
   DESCRIPTION
      "Enable spanning tree algorithm"
   ::= {er1646v2VxlBGIMVpSpanningTree 1}

er1646v2VxlBGIMVpSpanningTreeEntry OBJECT-TYPE
   SYNTAX      Er1646v2VxlBGIMVpSpanningTreeEntry
   MAX-ACCESS  not-accessible
   STATUS      current
   DESCRIPTION
      ""
   INDEX      { er1646v2VxlBGIMVpSpanningTreeGlobalIx }
   ::= {er1646v2VxlBGIMVpSpanningTreeSSCTable 1}

Er1646v2VxlBGIMVpSpanningTreeEntry ::=
   SEQUENCE
      {
      er1646v2VxlBGIMVpSpanningTreeGlobalIx
         GlobalIndex,
      er1646v2VxlBGIMVpSpanningTreeSpTProt
         INTEGER,
      er1646v2VxlBGIMVpSpanningTreeBrPrio
         Integer32,
      er1646v2VxlBGIMVpSpanningTreeBrMAge
         TimeTicks,
      er1646v2VxlBGIMVpSpanningTreeBrHTim
         TimeTicks,
      er1646v2VxlBGIMVpSpanningTreeBrFDel
         TimeTicks,
      er1646v2VxlBGIMVpSpanningTreeTxHoldCnt
         Integer32,
      er1646v2VxlBGIMVpSpanningTreeMstConfigIdName
         DisplayString,
      er1646v2VxlBGIMVpSpanningTreeMstConfigIdRevisionLevel
         Integer32,
      er1646v2VxlBGIMVpSpanningTreeMaxHops
         Integer32
      }

er1646v2VxlBGIMVpSpanningTreeGlobalIx OBJECT-TYPE
   SYNTAX      GlobalIndex
   MAX-ACCESS  not-accessible
   STATUS      current
   DESCRIPTION
      "The value of the tlsCntTreeGlobalIndex of the MANAGED OBJECT."
   ::= {er1646v2VxlBGIMVpSpanningTreeEntry 10}

er1646v2VxlBGIMVpSpanningTreeSpTProt OBJECT-TYPE
   SYNTAX      INTEGER
               {
               none (0),
               p802d1DsmsSTPsCompatibility (2),
               p802d1D (1),
               p802d1Q (3)
               }
   MAX-ACCESS  read-write
   STATUS      current
   DESCRIPTION
      "Path: vxLanBridgeGroup.editConf.spanningTree.protocol

       Possibilities:
               none   (0)
               p802.1D - STP Compatibility   (2)
               p802.1D   (1)
               p802.1Q   (3)"
   ::= {er1646v2VxlBGIMVpSpanningTreeEntry 16777216}

er1646v2VxlBGIMVpSpanningTreeBrPrio OBJECT-TYPE
   SYNTAX      Integer32
   MAX-ACCESS  read-write
   STATUS      current
   DESCRIPTION
      "Path: vxLanBridgeGroup.editConf.spanningTree.bridgePriority"
   ::= {er1646v2VxlBGIMVpSpanningTreeEntry 33554432}

er1646v2VxlBGIMVpSpanningTreeBrMAge OBJECT-TYPE
   SYNTAX      TimeTicks
   MAX-ACCESS  read-write
   STATUS      current
   DESCRIPTION
      "Path: vxLanBridgeGroup.editConf.spanningTree.bridgeMaxAge

       Time in centi-second."
   ::= {er1646v2VxlBGIMVpSpanningTreeEntry 50331648}

er1646v2VxlBGIMVpSpanningTreeBrHTim OBJECT-TYPE
   SYNTAX      TimeTicks
   MAX-ACCESS  read-write
   STATUS      current
   DESCRIPTION
      "Path: vxLanBridgeGroup.editConf.spanningTree.bridgeHelloTime

       Time in centi-second."
   ::= {er1646v2VxlBGIMVpSpanningTreeEntry 67108864}

er1646v2VxlBGIMVpSpanningTreeBrFDel OBJECT-TYPE
   SYNTAX      TimeTicks
   MAX-ACCESS  read-write
   STATUS      current
   DESCRIPTION
      "Path: vxLanBridgeGroup.editConf.spanningTree.bridgeForwardDelay

       Time in centi-second."
   ::= {er1646v2VxlBGIMVpSpanningTreeEntry 83886080}

er1646v2VxlBGIMVpSpanningTreeTxHoldCnt OBJECT-TYPE
   SYNTAX      Integer32
   MAX-ACCESS  read-write
   STATUS      current
   DESCRIPTION
      "Path: vxLanBridgeGroup.editConf.spanningTree.transmitHoldCount"
   ::= {er1646v2VxlBGIMVpSpanningTreeEntry 100663296}

er1646v2VxlBGIMVpSpanningTreeMstConfigIdName OBJECT-TYPE
   SYNTAX      DisplayString
   MAX-ACCESS  read-write
   STATUS      current
   DESCRIPTION
      "Path: vxLanBridgeGroup.editConf.spanningTree.mstConfigId.name"
   ::= {er1646v2VxlBGIMVpSpanningTreeEntry 117506048}

er1646v2VxlBGIMVpSpanningTreeMstConfigIdRevisionLevel OBJECT-TYPE
   SYNTAX      Integer32
   MAX-ACCESS  read-write
   STATUS      current
   DESCRIPTION
      "Path: vxLanBridgeGroup.editConf.spanningTree.mstConfigId.revisionLevel"
   ::= {er1646v2VxlBGIMVpSpanningTreeEntry 117571584}

er1646v2VxlBGIMVpSpanningTreeMaxHops OBJECT-TYPE
   SYNTAX      Integer32
   MAX-ACCESS  read-write
   STATUS      current
   DESCRIPTION
      "Path: vxLanBridgeGroup.editConf.spanningTree.maxHops"
   ::= {er1646v2VxlBGIMVpSpanningTreeEntry 134217728}


er1646v2VxlBGIMVpLocalAccess OBJECT IDENTIFIER ::= {er1646v2VxlBGIMVp 28}

er1646v2VxlBGIMVpLocalAccessTable OBJECT-TYPE
   SYNTAX      SEQUENCE OF Er1646v2VxlBGIMVpLocalAccessEntry
   MAX-ACCESS  not-accessible
   STATUS      current
   DESCRIPTION
      "restricts access to protocolstack via bridgegroup"
   ::= {er1646v2VxlBGIMVpLocalAccess 1}

er1646v2VxlBGIMVpLocalAccessEntry OBJECT-TYPE
   SYNTAX      Er1646v2VxlBGIMVpLocalAccessEntry
   MAX-ACCESS  not-accessible
   STATUS      current
   DESCRIPTION
      ""
   INDEX      { er1646v2VxlBGIMVpLocalAccessGlobalIx }
   ::= {er1646v2VxlBGIMVpLocalAccessTable 1}

Er1646v2VxlBGIMVpLocalAccessEntry ::=
   SEQUENCE
      {
      er1646v2VxlBGIMVpLocalAccessGlobalIx
         GlobalIndex,
      er1646v2VxlBGIMVpLocalAccessValue
         INTEGER
      }

er1646v2VxlBGIMVpLocalAccessGlobalIx OBJECT-TYPE
   SYNTAX      GlobalIndex
   MAX-ACCESS  not-accessible
   STATUS      current
   DESCRIPTION
      "The value of the tlsCntTreeGlobalIndex of the MANAGED OBJECT."
   ::= {er1646v2VxlBGIMVpLocalAccessEntry 10}

er1646v2VxlBGIMVpLocalAccessValue OBJECT-TYPE
   SYNTAX      INTEGER
               {
               permitted (0),
               restricted (1)
               }
   MAX-ACCESS  read-write
   STATUS      current
   DESCRIPTION
      "Path: vxLanBridgeGroup.editConf.localAccess

       Possibilities:
               permitted   (0)
               restricted   (1)"
   ::= {er1646v2VxlBGIMVpLocalAccessEntry 2147483648}


er1646v2VxlBGIMVpAccessControl OBJECT IDENTIFIER ::= {er1646v2VxlBGIMVp 29}

er1646v2VxlBGIMVpAccessControlSSCTable OBJECT-TYPE
   SYNTAX      SEQUENCE OF Er1646v2VxlBGIMVpAccessControlEntry
   MAX-ACCESS  not-accessible
   STATUS      current
   DESCRIPTION
      "access control on bridgegroups"
   ::= {er1646v2VxlBGIMVpAccessControl 1}

er1646v2VxlBGIMVpAccessControlEntry OBJECT-TYPE
   SYNTAX      Er1646v2VxlBGIMVpAccessControlEntry
   MAX-ACCESS  not-accessible
   STATUS      current
   DESCRIPTION
      ""
   INDEX      { er1646v2VxlBGIMVpAccessControlGlobalIx }
   ::= {er1646v2VxlBGIMVpAccessControlSSCTable 1}

Er1646v2VxlBGIMVpAccessControlEntry ::=
   SEQUENCE
      {
      er1646v2VxlBGIMVpAccessControlGlobalIx
         GlobalIndex,
      er1646v2VxlBGIMVpAccessControlInAccessList
         DisplayString,
      er1646v2VxlBGIMVpAccessControlLimBC
         INTEGER
      }

er1646v2VxlBGIMVpAccessControlGlobalIx OBJECT-TYPE
   SYNTAX      GlobalIndex
   MAX-ACCESS  not-accessible
   STATUS      current
   DESCRIPTION
      "The value of the tlsCntTreeGlobalIndex of the MANAGED OBJECT."
   ::= {er1646v2VxlBGIMVpAccessControlEntry 10}

er1646v2VxlBGIMVpAccessControlInAccessList OBJECT-TYPE
   SYNTAX      DisplayString
   MAX-ACCESS  read-write
   STATUS      current
   DESCRIPTION
      "Path: vxLanBridgeGroup.editConf.accessControl.inAccessList"
   ::= {er1646v2VxlBGIMVpAccessControlEntry 83886080}

er1646v2VxlBGIMVpAccessControlLimBC OBJECT-TYPE
   SYNTAX      INTEGER
               {
               disabled (0),
               enabled (1)
               }
   MAX-ACCESS  read-write
   STATUS      current
   DESCRIPTION
      "Path: vxLanBridgeGroup.editConf.accessControl.limitBroadcasts

       Possibilities:
               disabled   (0)
               enabled   (1)"
   ::= {er1646v2VxlBGIMVpAccessControlEntry 134217728}


er1646v2VxlBGIMVpIp OBJECT IDENTIFIER ::= {er1646v2VxlBGIMVp 18}

er1646v2VxlBGIMVpIpSSCTable OBJECT-TYPE
   SYNTAX      SEQUENCE OF Er1646v2VxlBGIMVpIpEntry
   MAX-ACCESS  not-accessible
   STATUS      current
   DESCRIPTION
      "ip interface config parameters"
   ::= {er1646v2VxlBGIMVpIp 1}

er1646v2VxlBGIMVpIpEntry OBJECT-TYPE
   SYNTAX      Er1646v2VxlBGIMVpIpEntry
   MAX-ACCESS  not-accessible
   STATUS      current
   DESCRIPTION
      ""
   INDEX      { er1646v2VxlBGIMVpIpGlobalIx }
   ::= {er1646v2VxlBGIMVpIpSSCTable 1}

Er1646v2VxlBGIMVpIpEntry ::=
   SEQUENCE
      {
      er1646v2VxlBGIMVpIpGlobalIx
         GlobalIndex,
      er1646v2VxlBGIMVpIpVrfRouter
         DisplayString,
      er1646v2VxlBGIMVpIpAdr
         IpAddress,
      er1646v2VxlBGIMVpIpNetm
         IpAddress,
      er1646v2VxlBGIMVpIpSNetName
         INTEGER,
      er1646v2VxlBGIMVpIpSNetCust
         DisplayString,
      er1646v2VxlBGIMVpIpDhcpC
         INTEGER,
      er1646v2VxlBGIMVpIpDhcpGatewayPreference
         Integer32,
      er1646v2VxlBGIMVpIpDhcpRoutePreference
         Integer32,
      er1646v2VxlBGIMVpIpDhcpDnsPreference
         Integer32,
      er1646v2VxlBGIMVpIpMtu
         Integer32,
      er1646v2VxlBGIMVpIpMssAdjust
         INTEGER,
      er1646v2VxlBGIMVpIpRipMetric
         Integer32,
      er1646v2VxlBGIMVpIpRipMetricOut
         Integer32,
      er1646v2VxlBGIMVpIpRipMode
         INTEGER,
      er1646v2VxlBGIMVpIpRipTxVer
         INTEGER,
      er1646v2VxlBGIMVpIpRipRxVer
         INTEGER,
      er1646v2VxlBGIMVpIpRipSplitH
         INTEGER,
      er1646v2VxlBGIMVpIpRipAuth
         INTEGER,
      er1646v2VxlBGIMVpIpRipFilter
         DisplayString,
      er1646v2VxlBGIMVpIpRipFilterIn
         DisplayString,
      er1646v2VxlBGIMVpIpRipClearNextHop
         INTEGER,
      er1646v2VxlBGIMVpIpAccPol
         DisplayString,
      er1646v2VxlBGIMVpIpAB
         DisplayString,
      er1646v2VxlBGIMVpIpMA
         INTEGER,
      er1646v2VxlBGIMVpIpMF
         Integer32,
      er1646v2VxlBGIMVpIpDB
         INTEGER,
      er1646v2VxlBGIMVpIpIR
         INTEGER,
      er1646v2VxlBGIMVpIpIgmp
         INTEGER,
      er1646v2VxlBGIMVpIpNN
         DisplayString,
      er1646v2VxlBGIMVpIpVrrp
         INTEGER,
      er1646v2VxlBGIMVpIpPimMode
         INTEGER,
      er1646v2VxlBGIMVpIpPimDrPriority
         Counter32,
      er1646v2VxlBGIMVpIpPimHelloTime
         TimeTicks,
      er1646v2VxlBGIMVpIpPimPropagationDelay
         TimeTicks,
      er1646v2VxlBGIMVpIpPimOverrideInterval
         TimeTicks,
      er1646v2VxlBGIMVpIpPimBsrBorder
         INTEGER,
      er1646v2VxlBGIMVpIpPimTtlThreshold
         Integer32,
      er1646v2VxlBGIMVpIpIMNetworkUnreachable
         INTEGER,
      er1646v2VxlBGIMVpIpIMHostUnreachable
         INTEGER,
      er1646v2VxlBGIMVpIpIMProtocolUnreachable
         INTEGER,
      er1646v2VxlBGIMVpIpIMPortUnreachable
         INTEGER,
      er1646v2VxlBGIMVpIpIMMtuExceeded
         INTEGER,
      er1646v2VxlBGIMVpIpIMAdminProhibited
         INTEGER,
      er1646v2VxlBGIMVpIpIMTtlExceeded
         INTEGER,
      er1646v2VxlBGIMVpIpIMRedirect
         INTEGER
      }

er1646v2VxlBGIMVpIpGlobalIx OBJECT-TYPE
   SYNTAX      GlobalIndex
   MAX-ACCESS  not-accessible
   STATUS      current
   DESCRIPTION
      "The value of the tlsCntTreeGlobalIndex of the MANAGED OBJECT."
   ::= {er1646v2VxlBGIMVpIpEntry 10}

er1646v2VxlBGIMVpIpVrfRouter OBJECT-TYPE
   SYNTAX      DisplayString
   MAX-ACCESS  read-write
   STATUS      current
   DESCRIPTION
      "Path: vxLanBridgeGroup.editConf.ip.vrfRouter"
   ::= {er1646v2VxlBGIMVpIpEntry 738197504}

er1646v2VxlBGIMVpIpAdr OBJECT-TYPE
   SYNTAX      IpAddress
   MAX-ACCESS  read-write
   STATUS      current
   DESCRIPTION
      "Path: vxLanBridgeGroup.editConf.ip.address"
   ::= {er1646v2VxlBGIMVpIpEntry 2030043136}

er1646v2VxlBGIMVpIpNetm OBJECT-TYPE
   SYNTAX      IpAddress
   MAX-ACCESS  read-write
   STATUS      current
   DESCRIPTION
      "Path: vxLanBridgeGroup.editConf.ip.netMask"
   ::= {er1646v2VxlBGIMVpIpEntry 2063597568}

er1646v2VxlBGIMVpIpSNetName OBJECT-TYPE
   SYNTAX      INTEGER
               {
               slOPTg (0),
               corp (2),
               dmz (3),
               internet (1)
               }
   MAX-ACCESS  read-write
   STATUS      current
   DESCRIPTION
      "Path: vxLanBridgeGroup.editConf.ip.sNet.name

       Possibilities:
               <OPT>   (0)
               corp   (2)
               dmz   (3)
               internet   (1)"
   ::= {er1646v2VxlBGIMVpIpEntry 855703552}

er1646v2VxlBGIMVpIpSNetCust OBJECT-TYPE
   SYNTAX      DisplayString
   MAX-ACCESS  read-write
   STATUS      current
   DESCRIPTION
      "Path: vxLanBridgeGroup.editConf.ip.sNet.custom"
   ::= {er1646v2VxlBGIMVpIpEntry 855769088}

er1646v2VxlBGIMVpIpDhcpC OBJECT-TYPE
   SYNTAX      INTEGER
               {
               disabled (0),
               enabled (1)
               }
   MAX-ACCESS  read-write
   STATUS      current
   DESCRIPTION
      "Path: vxLanBridgeGroup.editConf.ip.dhcpClient

       Possibilities:
               disabled   (0)
               enabled   (1)"
   ::= {er1646v2VxlBGIMVpIpEntry 838860800}

er1646v2VxlBGIMVpIpDhcpGatewayPreference OBJECT-TYPE
   SYNTAX      Integer32
   MAX-ACCESS  read-write
   STATUS      current
   DESCRIPTION
      "Path: vxLanBridgeGroup.editConf.ip.dhcp.gatewayPreference"
   ::= {er1646v2VxlBGIMVpIpEntry 872480768}

er1646v2VxlBGIMVpIpDhcpRoutePreference OBJECT-TYPE
   SYNTAX      Integer32
   MAX-ACCESS  read-write
   STATUS      current
   DESCRIPTION
      "Path: vxLanBridgeGroup.editConf.ip.dhcp.routePreference"
   ::= {er1646v2VxlBGIMVpIpEntry 872546304}

er1646v2VxlBGIMVpIpDhcpDnsPreference OBJECT-TYPE
   SYNTAX      Integer32
   MAX-ACCESS  read-write
   STATUS      current
   DESCRIPTION
      "Path: vxLanBridgeGroup.editConf.ip.dhcp.dnsPreference"
   ::= {er1646v2VxlBGIMVpIpEntry 872611840}

er1646v2VxlBGIMVpIpMtu OBJECT-TYPE
   SYNTAX      Integer32
   MAX-ACCESS  read-write
   STATUS      current
   DESCRIPTION
      "Path: vxLanBridgeGroup.editConf.ip.mtu"
   ::= {er1646v2VxlBGIMVpIpEntry 671088640}

er1646v2VxlBGIMVpIpMssAdjust OBJECT-TYPE
   SYNTAX      INTEGER
               {
               disabled (0),
               auto (65536)
               }
   MAX-ACCESS  read-write
   STATUS      current
   DESCRIPTION
      "Path: vxLanBridgeGroup.editConf.ip.mssAdjust

       Possibilities:
               disabled   (0)
               auto   (65536)"
   ::= {er1646v2VxlBGIMVpIpEntry 754974720}

er1646v2VxlBGIMVpIpRipMetric OBJECT-TYPE
   SYNTAX      Integer32
   MAX-ACCESS  read-write
   STATUS      current
   DESCRIPTION
      "Path: vxLanBridgeGroup.editConf.ip.rip.metric"
   ::= {er1646v2VxlBGIMVpIpEntry 353566720}

er1646v2VxlBGIMVpIpRipMetricOut OBJECT-TYPE
   SYNTAX      Integer32
   MAX-ACCESS  read-write
   STATUS      current
   DESCRIPTION
      "Path: vxLanBridgeGroup.editConf.ip.rip.metricOut"
   ::= {er1646v2VxlBGIMVpIpEntry 353632256}

er1646v2VxlBGIMVpIpRipMode OBJECT-TYPE
   SYNTAX      INTEGER
               {
               disabled (0),
               passive (1),
               active (2)
               }
   MAX-ACCESS  read-write
   STATUS      current
   DESCRIPTION
      "Path: vxLanBridgeGroup.editConf.ip.rip.mode

       Possibilities:
               disabled   (0)
               passive   (1)
               active   (2)"
   ::= {er1646v2VxlBGIMVpIpEntry 353697792}

er1646v2VxlBGIMVpIpRipTxVer OBJECT-TYPE
   SYNTAX      INTEGER
               {
               rip1 (0),
               rip2 (1),
               rip1mcompatible (2)
               }
   MAX-ACCESS  read-write
   STATUS      current
   DESCRIPTION
      "Path: vxLanBridgeGroup.editConf.ip.rip.txVersion

       Possibilities:
               rip1   (0)
               rip2   (1)
               rip1-compatible   (2)"
   ::= {er1646v2VxlBGIMVpIpEntry 354615296}

er1646v2VxlBGIMVpIpRipRxVer OBJECT-TYPE
   SYNTAX      INTEGER
               {
               rip1only (0),
               rip2only (1),
               rip12 (2)
               }
   MAX-ACCESS  read-write
   STATUS      current
   DESCRIPTION
      "Path: vxLanBridgeGroup.editConf.ip.rip.rxVersion

       Possibilities:
               rip1only   (0)
               rip2only   (1)
               rip1&2   (2)"
   ::= {er1646v2VxlBGIMVpIpEntry 354680832}

er1646v2VxlBGIMVpIpRipSplitH OBJECT-TYPE
   SYNTAX      INTEGER
               {
               disabled (0),
               enabled (1),
               poisonedReverse (2)
               }
   MAX-ACCESS  read-write
   STATUS      current
   DESCRIPTION
      "Path: vxLanBridgeGroup.editConf.ip.rip.splitHorizon

       Possibilities:
               disabled   (0)
               enabled   (1)
               poisonedReverse   (2)"
   ::= {er1646v2VxlBGIMVpIpEntry 353828864}

er1646v2VxlBGIMVpIpRipAuth OBJECT-TYPE
   SYNTAX      INTEGER
               {
               disabled (0),
               texts (1),
               md5 (2)
               }
   MAX-ACCESS  read-write
   STATUS      current
   DESCRIPTION
      "Path: vxLanBridgeGroup.editConf.ip.rip.authentication

       Possibilities:
               disabled   (0)
               text    (1)
               md5   (2)"
   ::= {er1646v2VxlBGIMVpIpEntry 353501184}

er1646v2VxlBGIMVpIpRipFilter OBJECT-TYPE
   SYNTAX      DisplayString
   MAX-ACCESS  read-write
   STATUS      current
   DESCRIPTION
      "Path: vxLanBridgeGroup.editConf.ip.rip.filter"
   ::= {er1646v2VxlBGIMVpIpEntry 354418688}

er1646v2VxlBGIMVpIpRipFilterIn OBJECT-TYPE
   SYNTAX      DisplayString
   MAX-ACCESS  read-write
   STATUS      current
   DESCRIPTION
      "Path: vxLanBridgeGroup.editConf.ip.rip.filterIn"
   ::= {er1646v2VxlBGIMVpIpEntry 354484224}

er1646v2VxlBGIMVpIpRipClearNextHop OBJECT-TYPE
   SYNTAX      INTEGER
               {
               disabled (0),
               enabled (1)
               }
   MAX-ACCESS  read-write
   STATUS      current
   DESCRIPTION
      "Path: vxLanBridgeGroup.editConf.ip.rip.clearNextHop

       Possibilities:
               disabled   (0)
               enabled   (1)"
   ::= {er1646v2VxlBGIMVpIpEntry 352452608}

er1646v2VxlBGIMVpIpAccPol OBJECT-TYPE
   SYNTAX      DisplayString
   MAX-ACCESS  read-write
   STATUS      current
   DESCRIPTION
      "Path: vxLanBridgeGroup.editConf.ip.accessPolicy"
   ::= {er1646v2VxlBGIMVpIpEntry 704643072}

er1646v2VxlBGIMVpIpAB OBJECT-TYPE
   SYNTAX      DisplayString
   MAX-ACCESS  read-write
   STATUS      current
   DESCRIPTION
      "Path: vxLanBridgeGroup.editConf.ip.trafficPolicy"
   ::= {er1646v2VxlBGIMVpIpEntry 234881024}

er1646v2VxlBGIMVpIpMA OBJECT-TYPE
   SYNTAX      INTEGER
               {
               disabled (0),
               enabled (1)
               }
   MAX-ACCESS  read-write
   STATUS      current
   DESCRIPTION
      "Path: vxLanBridgeGroup.editConf.ip.mgmtAccess

       Possibilities:
               disabled   (0)
               enabled   (1)"
   ::= {er1646v2VxlBGIMVpIpEntry 268435456}

er1646v2VxlBGIMVpIpMF OBJECT-TYPE
   SYNTAX      Integer32
   MAX-ACCESS  read-write
   STATUS      current
   DESCRIPTION
      "Path: vxLanBridgeGroup.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VxlBGIMVpIpEntry 285212672}

er1646v2VxlBGIMVpIpDB OBJECT-TYPE
   SYNTAX      INTEGER
               {
               disabled (0),
               enabled (1)
               }
   MAX-ACCESS  read-write
   STATUS      current
   DESCRIPTION
      "Path: vxLanBridgeGroup.editConf.ip.directedBroadcasts

       Possibilities:
               disabled   (0)
               enabled   (1)"
   ::= {er1646v2VxlBGIMVpIpEntry 369098752}

er1646v2VxlBGIMVpIpIR OBJECT-TYPE
   SYNTAX      INTEGER
               {
               disabled (0),
               enabled (1)
               }
   MAX-ACCESS  read-write
   STATUS      current
   DESCRIPTION
      "Path: vxLanBridgeGroup.editConf.ip.icmpRedirects

       Possibilities:
               disabled   (0)
               enabled   (1)"
   ::= {er1646v2VxlBGIMVpIpEntry 436207616}

er1646v2VxlBGIMVpIpIgmp OBJECT-TYPE
   SYNTAX      INTEGER
               {
               disabled (0),
               proxy (1),
               router (2),
               v3Router (5)
               }
   MAX-ACCESS  read-write
   STATUS      current
   DESCRIPTION
      "Path: vxLanBridgeGroup.editConf.ip.igmp

       Possibilities:
               disabled   (0)
               proxy   (1)
               router   (2)
               v3Router   (5)"
   ::= {er1646v2VxlBGIMVpIpEntry 536870912}

er1646v2VxlBGIMVpIpNN OBJECT-TYPE
   SYNTAX      DisplayString
   MAX-ACCESS  read-write
   STATUS      current
   DESCRIPTION
      "Path: vxLanBridgeGroup.editConf.ip.nat"
   ::= {er1646v2VxlBGIMVpIpEntry 452984832}

er1646v2VxlBGIMVpIpVrrp OBJECT-TYPE
   SYNTAX      INTEGER
               {
               disabled (0),
               enabled (1)
               }
   MAX-ACCESS  read-write
   STATUS      current
   DESCRIPTION
      "Path: vxLanBridgeGroup.editConf.ip.vrrp

       Possibilities:
               disabled   (0)
               enabled   (1)"
   ::= {er1646v2VxlBGIMVpIpEntry 721420288}

er1646v2VxlBGIMVpIpPimMode OBJECT-TYPE
   SYNTAX      INTEGER
               {
               disabled (0),
               sparse (1),
               passive (2)
               }
   MAX-ACCESS  read-write
   STATUS      current
   DESCRIPTION
      "Path: vxLanBridgeGroup.editConf.ip.pim.mode

       Possibilities:
               disabled   (0)
               sparse   (1)
               passive   (2)"
   ::= {er1646v2VxlBGIMVpIpEntry 771817472}

er1646v2VxlBGIMVpIpPimDrPriority OBJECT-TYPE
   SYNTAX      Counter32
   MAX-ACCESS  read-write
   STATUS      current
   DESCRIPTION
      "Path: vxLanBridgeGroup.editConf.ip.pim.drPriority

       32 bit unsigned wrappable counter."
   ::= {er1646v2VxlBGIMVpIpEntry 771883008}

er1646v2VxlBGIMVpIpPimHelloTime OBJECT-TYPE
   SYNTAX      TimeTicks
   MAX-ACCESS  read-write
   STATUS      current
   DESCRIPTION
      "Path: vxLanBridgeGroup.editConf.ip.pim.helloTime

       Time in centi-second."
   ::= {er1646v2VxlBGIMVpIpEntry 771948544}

er1646v2VxlBGIMVpIpPimPropagationDelay OBJECT-TYPE
   SYNTAX      TimeTicks
   MAX-ACCESS  read-write
   STATUS      current
   DESCRIPTION
      "Path: vxLanBridgeGroup.editConf.ip.pim.propagationDelay

       Time in centi-second."
   ::= {er1646v2VxlBGIMVpIpEntry 772014080}

er1646v2VxlBGIMVpIpPimOverrideInterval OBJECT-TYPE
   SYNTAX      TimeTicks
   MAX-ACCESS  read-write
   STATUS      current
   DESCRIPTION
      "Path: vxLanBridgeGroup.editConf.ip.pim.overrideInterval

       Time in centi-second."
   ::= {er1646v2VxlBGIMVpIpEntry 772079616}

er1646v2VxlBGIMVpIpPimBsrBorder OBJECT-TYPE
   SYNTAX      INTEGER
               {
               disabled (0),
               enabled (1)
               }
   MAX-ACCESS  read-write
   STATUS      current
   DESCRIPTION
      "Path: vxLanBridgeGroup.editConf.ip.pim.bsrBorder

       Possibilities:
               disabled   (0)
               enabled   (1)"
   ::= {er1646v2VxlBGIMVpIpEntry 772145152}

er1646v2VxlBGIMVpIpPimTtlThreshold OBJECT-TYPE
   SYNTAX      Integer32
   MAX-ACCESS  read-write
   STATUS      current
   DESCRIPTION
      "Path: vxLanBridgeGroup.editConf.ip.pim.ttlThreshold"
   ::= {er1646v2VxlBGIMVpIpEntry 772210688}

er1646v2VxlBGIMVpIpIMNetworkUnreachable OBJECT-TYPE
   SYNTAX      INTEGER
               {
               disabled (0),
               enabled (1)
               }
   MAX-ACCESS  read-write
   STATUS      current
   DESCRIPTION
      "Path: vxLanBridgeGroup.editConf.ip.icmpMessages.networkUnreachable

       Possibilities:
               disabled   (0)
               enabled   (1)"
   ::= {er1646v2VxlBGIMVpIpEntry 788594688}

er1646v2VxlBGIMVpIpIMHostUnreachable OBJECT-TYPE
   SYNTAX      INTEGER
               {
               disabled (0),
               enabled (1)
               }
   MAX-ACCESS  read-write
   STATUS      current
   DESCRIPTION
      "Path: vxLanBridgeGroup.editConf.ip.icmpMessages.hostUnreachable

       Possibilities:
               disabled   (0)
               enabled   (1)"
   ::= {er1646v2VxlBGIMVpIpEntry 788660224}

er1646v2VxlBGIMVpIpIMProtocolUnreachable OBJECT-TYPE
   SYNTAX      INTEGER
               {
               disabled (0),
               enabled (1)
               }
   MAX-ACCESS  read-write
   STATUS      current
   DESCRIPTION
      "Path: vxLanBridgeGroup.editConf.ip.icmpMessages.protocolUnreachable

       Possibilities:
               disabled   (0)
               enabled   (1)"
   ::= {er1646v2VxlBGIMVpIpEntry 788725760}

er1646v2VxlBGIMVpIpIMPortUnreachable OBJECT-TYPE
   SYNTAX      INTEGER
               {
               disabled (0),
               enabled (1)
               }
   MAX-ACCESS  read-write
   STATUS      current
   DESCRIPTION
      "Path: vxLanBridgeGroup.editConf.ip.icmpMessages.portUnreachable

       Possibilities:
               disabled   (0)
               enabled   (1)"
   ::= {er1646v2VxlBGIMVpIpEntry 788791296}

er1646v2VxlBGIMVpIpIMMtuExceeded OBJECT-TYPE
   SYNTAX      INTEGER
               {
               disabled (0),
               enabled (1)
               }
   MAX-ACCESS  read-write
   STATUS      current
   DESCRIPTION
      "Path: vxLanBridgeGroup.editConf.ip.icmpMessages.mtuExceeded

       Possibilities:
               disabled   (0)
               enabled   (1)"
   ::= {er1646v2VxlBGIMVpIpEntry 788856832}

er1646v2VxlBGIMVpIpIMAdminProhibited OBJECT-TYPE
   SYNTAX      INTEGER
               {
               disabled (0),
               enabled (1)
               }
   MAX-ACCESS  read-write
   STATUS      current
   DESCRIPTION
      "Path: vxLanBridgeGroup.editConf.ip.icmpMessages.adminProhibited

       Possibilities:
               disabled   (0)
               enabled   (1)"
   ::= {er1646v2VxlBGIMVpIpEntry 788922368}

er1646v2VxlBGIMVpIpIMTtlExceeded OBJECT-TYPE
   SYNTAX      INTEGER
               {
               disabled (0),
               enabled (1)
               }
   MAX-ACCESS  read-write
   STATUS      current
   DESCRIPTION
      "Path: vxLanBridgeGroup.editConf.ip.icmpMessages.ttlExceeded

       Possibilities:
               disabled   (0)
               enabled   (1)"
   ::= {er1646v2VxlBGIMVpIpEntry 788987904}

er1646v2VxlBGIMVpIpIMRedirect OBJECT-TYPE
   SYNTAX      INTEGER
               {
               disabled (0),
               enabled (1)
               }
   MAX-ACCESS  read-write
   STATUS      current
   DESCRIPTION
      "Path: vxLanBridgeGroup.editConf.ip.icmpMessages.redirect

       Possibilities:
               disabled   (0)
               enabled   (1)"
   ::= {er1646v2VxlBGIMVpIpEntry 789053440}

er1646v2VxlBGIMVpIpSaddr OBJECT-TYPE
   SYNTAX      SEQUENCE OF Er1646v2VxlBGIMVpIpSaddrEntry
   MAX-ACCESS  not-accessible
   STATUS      current
   DESCRIPTION
      ""
   ::= {er1646v2VxlBGIMVpIp 385875968}

er1646v2VxlBGIMVpIpSaddrEntry OBJECT-TYPE
   SYNTAX      Er1646v2VxlBGIMVpIpSaddrEntry
   MAX-ACCESS  not-accessible
   STATUS      current
   DESCRIPTION
      ""
   INDEX      { er1646v2VxlBGIMVpIpSaddrGlobalIx,
                er1646v2VxlBGIMVpIpSaddrTableIx }
   ::= {er1646v2VxlBGIMVpIpSaddr 1}

Er1646v2VxlBGIMVpIpSaddrEntry ::=
   SEQUENCE
      {
      er1646v2VxlBGIMVpIpSaddrActions
         VariableLengthTableActions,
      er1646v2VxlBGIMVpIpSaddrGlobalIx
         GlobalIndex,
      er1646v2VxlBGIMVpIpSaddrTableIx
         TableIndex,
      er1646v2VxlBGIMVpIpSaddrAddress
         IpAddress,
      er1646v2VxlBGIMVpIpSaddrNetMask
         IpAddress
      }

er1646v2VxlBGIMVpIpSaddrActions OBJECT-TYPE
   SYNTAX      VariableLengthTableActions
   MAX-ACCESS  read-write
   STATUS      current
   DESCRIPTION
      "By way of this field, some manipulations
       on this table may be performed."
   ::= {er1646v2VxlBGIMVpIpSaddrEntry 2}

er1646v2VxlBGIMVpIpSaddrGlobalIx OBJECT-TYPE
   SYNTAX      GlobalIndex
   MAX-ACCESS  not-accessible
   STATUS      current
   DESCRIPTION
      "The value of the tlsCntTreeGlobalIndex of the MANAGED OBJECT."
   ::= {er1646v2VxlBGIMVpIpSaddrEntry 10}

er1646v2VxlBGIMVpIpSaddrTableIx OBJECT-TYPE
   SYNTAX      TableIndex
   MAX-ACCESS  not-accessible
   STATUS      current
   DESCRIPTION
      ""
   ::= {er1646v2VxlBGIMVpIpSaddrEntry 11}

er1646v2VxlBGIMVpIpSaddrAddress OBJECT-TYPE
   SYNTAX      IpAddress
   MAX-ACCESS  read-write
   STATUS      current
   DESCRIPTION
      "Path: vxLanBridgeGroup.editConf.ip.secondaryIp.address"
   ::= {er1646v2VxlBGIMVpIpSaddrEntry 2030043136}

er1646v2VxlBGIMVpIpSaddrNetMask OBJECT-TYPE
   SYNTAX      IpAddress
   MAX-ACCESS  read-write
   STATUS      current
   DESCRIPTION
      "Path: vxLanBridgeGroup.editConf.ip.secondaryIp.netMask"
   ::= {er1646v2VxlBGIMVpIpSaddrEntry 2063597568}

er1646v2VxlBGIMVpIpH OBJECT-TYPE
   SYNTAX      SEQUENCE OF Er1646v2VxlBGIMVpIpHEntry
   MAX-ACCESS  not-accessible
   STATUS      current
   DESCRIPTION
      ""
   ::= {er1646v2VxlBGIMVpIp 251658240}

er1646v2VxlBGIMVpIpHEntry OBJECT-TYPE
   SYNTAX      Er1646v2VxlBGIMVpIpHEntry
   MAX-ACCESS  not-accessible
   STATUS      current
   DESCRIPTION
      ""
   INDEX      { er1646v2VxlBGIMVpIpHGlobalIx,
                er1646v2VxlBGIMVpIpHTableIx }
   ::= {er1646v2VxlBGIMVpIpH 1}

Er1646v2VxlBGIMVpIpHEntry ::=
   SEQUENCE
      {
      er1646v2VxlBGIMVpIpHActions
         VariableLengthTableActions,
      er1646v2VxlBGIMVpIpHGlobalIx
         GlobalIndex,
      er1646v2VxlBGIMVpIpHTableIx
         TableIndex,
      er1646v2VxlBGIMVpIpHAddress
         IpAddress,
      er1646v2VxlBGIMVpIpHDhcpRelayOptionSubscriberId
         DisplayString
      }

er1646v2VxlBGIMVpIpHActions OBJECT-TYPE
   SYNTAX      VariableLengthTableActions
   MAX-ACCESS  read-write
   STATUS      current
   DESCRIPTION
      "By way of this field, some manipulations
       on this table may be performed."
   ::= {er1646v2VxlBGIMVpIpHEntry 2}

er1646v2VxlBGIMVpIpHGlobalIx OBJECT-TYPE
   SYNTAX      GlobalIndex
   MAX-ACCESS  not-accessible
   STATUS      current
   DESCRIPTION
      "The value of the tlsCntTreeGlobalIndex of the MANAGED OBJECT."
   ::= {er1646v2VxlBGIMVpIpHEntry 10}

er1646v2VxlBGIMVpIpHTableIx OBJECT-TYPE
   SYNTAX      TableIndex
   MAX-ACCESS  not-accessible
   STATUS      current
   DESCRIPTION
      ""
   ::= {er1646v2VxlBGIMVpIpHEntry 11}

er1646v2VxlBGIMVpIpHAddress OBJECT-TYPE
   SYNTAX      IpAddress
   MAX-ACCESS  read-write
   STATUS      current
   DESCRIPTION
      "Path: vxLanBridgeGroup.editConf.ip.helpers.address"
   ::= {er1646v2VxlBGIMVpIpHEntry 16777216}

er1646v2VxlBGIMVpIpHDhcpRelayOptionSubscriberId OBJECT-TYPE
   SYNTAX      DisplayString
   MAX-ACCESS  read-write
   STATUS      current
   DESCRIPTION
      "Path: vxLanBridgeGroup.editConf.ip.helpers.dhcpRelayOption.subscriberId"
   ::= {er1646v2VxlBGIMVpIpHEntry 33947648}


er1646v2VxlBGIMVpVlan OBJECT IDENTIFIER ::= {er1646v2VxlBGIMVp 33}

er1646v2VxlBGIMVpVlanSSCTable OBJECT-TYPE
   SYNTAX      SEQUENCE OF Er1646v2VxlBGIMVpVlanEntry
   MAX-ACCESS  not-accessible
   STATUS      current
   DESCRIPTION
      ""
   ::= {er1646v2VxlBGIMVpVlan 1}

er1646v2VxlBGIMVpVlanEntry OBJECT-TYPE
   SYNTAX      Er1646v2VxlBGIMVpVlanEntry
   MAX-ACCESS  not-accessible
   STATUS      current
   DESCRIPTION
      ""
   INDEX      { er1646v2VxlBGIMVpVlanGlobalIx,
                er1646v2VxlBGIMVpVlanTableIx }
   ::= {er1646v2VxlBGIMVpVlanSSCTable 1}

Er1646v2VxlBGIMVpVlanEntry ::=
   SEQUENCE
      {
      er1646v2VxlBGIMVpVlanActions
         VariableLengthTableActions,
      er1646v2VxlBGIMVpVlanGlobalIx
         GlobalIndex,
      er1646v2VxlBGIMVpVlanTableIx
         TableIndex,
      er1646v2VxlBGIMVpVlanName
         DisplayString,
      er1646v2VxlBGIMVpVlanRemark
         DisplayString,
      er1646v2VxlBGIMVpVlanAdminStatus
         INTEGER,
      er1646v2VxlBGIMVpVlanMode
         INTEGER,
      er1646v2VxlBGIMVpVlanIpVrfRouter
         DisplayString,
      er1646v2VxlBGIMVpVlanIpAdr
         IpAddress,
      er1646v2VxlBGIMVpVlanIpNetm
         IpAddress,
      er1646v2VxlBGIMVpVlanIpSNetName
         INTEGER,
      er1646v2VxlBGIMVpVlanIpSNetCust
         DisplayString,
      er1646v2VxlBGIMVpVlanIpDhcpC
         INTEGER,
      er1646v2VxlBGIMVpVlanIpDhcpGatewayPreference
         Integer32,
      er1646v2VxlBGIMVpVlanIpDhcpRoutePreference
         Integer32,
      er1646v2VxlBGIMVpVlanIpDhcpDnsPreference
         Integer32,
      er1646v2VxlBGIMVpVlanIpMtu
         Integer32,
      er1646v2VxlBGIMVpVlanIpMssAdjust
         INTEGER,
      er1646v2VxlBGIMVpVlanIpRipMetric
         Integer32,
      er1646v2VxlBGIMVpVlanIpRipMetricOut
         Integer32,
      er1646v2VxlBGIMVpVlanIpRipMode
         INTEGER,
      er1646v2VxlBGIMVpVlanIpRipTxVer
         INTEGER,
      er1646v2VxlBGIMVpVlanIpRipRxVer
         INTEGER,
      er1646v2VxlBGIMVpVlanIpRipSplitH
         INTEGER,
      er1646v2VxlBGIMVpVlanIpRipAuth
         INTEGER,
      er1646v2VxlBGIMVpVlanIpRipFilter
         DisplayString,
      er1646v2VxlBGIMVpVlanIpRipFilterIn
         DisplayString,
      er1646v2VxlBGIMVpVlanIpRipClearNextHop
         INTEGER,
      er1646v2VxlBGIMVpVlanIpAccPol
         DisplayString,
      er1646v2VxlBGIMVpVlanIpAB
         DisplayString,
      er1646v2VxlBGIMVpVlanIpMA
         INTEGER,
      er1646v2VxlBGIMVpVlanIpMF
         Integer32,
      er1646v2VxlBGIMVpVlanIpDB
         INTEGER,
      er1646v2VxlBGIMVpVlanIpIR
         INTEGER,
      er1646v2VxlBGIMVpVlanIpIgmp
         INTEGER,
      er1646v2VxlBGIMVpVlanIpNN
         DisplayString,
      er1646v2VxlBGIMVpVlanIpVrrp
         INTEGER,
      er1646v2VxlBGIMVpVlanIpPimMode
         INTEGER,
      er1646v2VxlBGIMVpVlanIpPimDrPriority
         Counter32,
      er1646v2VxlBGIMVpVlanIpPimHelloTime
         TimeTicks,
      er1646v2VxlBGIMVpVlanIpPimPropagationDelay
         TimeTicks,
      er1646v2VxlBGIMVpVlanIpPimOverrideInterval
         TimeTicks,
      er1646v2VxlBGIMVpVlanIpPimBsrBorder
         INTEGER,
      er1646v2VxlBGIMVpVlanIpPimTtlThreshold
         Integer32,
      er1646v2VxlBGIMVpVlanIpIMNetworkUnreachable
         INTEGER,
      er1646v2VxlBGIMVpVlanIpIMHostUnreachable
         INTEGER,
      er1646v2VxlBGIMVpVlanIpIMProtocolUnreachable
         INTEGER,
      er1646v2VxlBGIMVpVlanIpIMPortUnreachable
         INTEGER,
      er1646v2VxlBGIMVpVlanIpIMMtuExceeded
         INTEGER,
      er1646v2VxlBGIMVpVlanIpIMAdminProhibited
         INTEGER,
      er1646v2VxlBGIMVpVlanIpIMTtlExceeded
         INTEGER,
      er1646v2VxlBGIMVpVlanIpIMRedirect
         INTEGER,
      er1646v2VxlBGIMVpVlanIpV6VrfRouter
         DisplayString,
      er1646v2VxlBGIMVpVlanIpV6AddrAutoConfigNrDupAddrDetects
         Integer32,
      er1646v2VxlBGIMVpVlanIpV6AddrAutoConfigAcceptRa
         INTEGER,
      er1646v2VxlBGIMVpVlanIpV6AddrAutoConfigAcceptRaRdnss
         INTEGER,
      er1646v2VxlBGIMVpVlanIpV6AddrAutoConfigAcceptRaDnssl
         INTEGER,
      er1646v2VxlBGIMVpVlanIpV6DefaultRoute
         INTEGER,
      er1646v2VxlBGIMVpVlanIpV6RaSend
         INTEGER,
      er1646v2VxlBGIMVpVlanIpV6RaMinInterval
         TimeTicks,
      er1646v2VxlBGIMVpVlanIpV6RaMaxInterval
         TimeTicks,
      er1646v2VxlBGIMVpVlanIpV6RaManagedFlag
         INTEGER,
      er1646v2VxlBGIMVpVlanIpV6RaOtherConfFlag
         INTEGER,
      er1646v2VxlBGIMVpVlanIpV6RaLinkMtu
         Integer32,
      er1646v2VxlBGIMVpVlanIpV6RaReachableTime
         TimeTicks,
      er1646v2VxlBGIMVpVlanIpV6RaRetransmitTime
         TimeTicks,
      er1646v2VxlBGIMVpVlanIpV6RaHopLimit
         Integer32,
      er1646v2VxlBGIMVpVlanIpV6RaDefaultLifeTime
         TimeTicks,
      er1646v2VxlBGIMVpVlanIpV6RaDnsOptionsRdnssLifeTime
         TimeTicks,
      er1646v2VxlBGIMVpVlanIpV6RaDnsOptionsRdnssImportServers
         INTEGER,
      er1646v2VxlBGIMVpVlanIpV6RaDnsOptionsDnsslLifeTime
         TimeTicks,
      er1646v2VxlBGIMVpVlanIpV6RaDnsOptionsDnsslImportDomains
         INTEGER,
      er1646v2VxlBGIMVpVlanIpV6RsSend
         INTEGER,
      er1646v2VxlBGIMVpVlanIpV6RsMaxRandomDelay
         TimeTicks,
      er1646v2VxlBGIMVpVlanIpV6RsInterval
         TimeTicks,
      er1646v2VxlBGIMVpVlanIpV6RsMaxSolicitations
         Integer32,
      er1646v2VxlBGIMVpVlanIpV6TrafficPolicyInbound
         DisplayString,
      er1646v2VxlBGIMVpVlanIpV6TrafficPolicyOutbound
         DisplayString,
      er1646v2VxlBGIMVpVlanIpV6FirewallZone
         DisplayString,
      er1646v2VxlBGIMVpVlanIpV6DhcpClientAddrAC
         INTEGER,
      er1646v2VxlBGIMVpVlanIpV6DhcpClientPrDelMode
         INTEGER,
      er1646v2VxlBGIMVpVlanIpV6DhcpClientPrDelPool
         DisplayString,
      er1646v2VxlBGIMVpVlanIpV6DhcpClientPrDelPdExclOpt
         INTEGER,
      er1646v2VxlBGIMVpVlanIpV6DhcpClientDnsServerPref
         Integer32,
      er1646v2VxlBGIMVpVlanIpV6DhcpClientRapidCommit
         INTEGER,
      er1646v2VxlBGIMVpVlanIpV6DhcpClientTimersSolTimeOut
         TimeTicks,
      er1646v2VxlBGIMVpVlanIpV6DhcpClientTimersSolMaxRt
         TimeTicks,
      er1646v2VxlBGIMVpVlanIpV6DhcpClientTimersInfoRefresh
         TimeTicks,
      er1646v2VxlBGIMVpVlanIpV6DhcpServerMode
         INTEGER,
      er1646v2VxlBGIMVpVlanIpV6DhcpServerPreference
         Integer32,
      er1646v2VxlBGIMVpVlanIpV6DhcpServerPool
         DisplayString,
      er1646v2VxlBGIMVpVlanIpV6DhcpServerRapidCommit
         INTEGER,
      er1646v2VxlBGIMVpVlanIpV6DhcpServerTimersInfoRefresh
         TimeTicks,
      er1646v2VxlBGIMVpVlanIpV6DhcpRelayMode
         INTEGER,
      er1646v2VxlBGIMVpVlanIpV6SendRedirect
         INTEGER,
      er1646v2VxlBGIMVpVlanIpV6LinkMtu
         Integer32,
      er1646v2VxlBGIMVpVlanIpV6InterfaceId
         OCTET STRING,
      er1646v2VxlBGIMVpVlanIpV6MF
         Integer32,
      er1646v2VxlBGIMVpVlanIpV6IcmpMessagesNoRoute
         INTEGER,
      er1646v2VxlBGIMVpVlanIpV6IcmpMessagesBeyondScope
         INTEGER,
      er1646v2VxlBGIMVpVlanIpV6IcmpMessagesAddressUnreachable
         INTEGER,
      er1646v2VxlBGIMVpVlanIpV6IcmpMessagesPortUnreachable
         INTEGER,
      er1646v2VxlBGIMVpVlanIpV6IcmpMessagesPacketTooBig
         INTEGER,
      er1646v2VxlBGIMVpVlanIpV6IcmpMessagesHopLimitExceeded
         INTEGER,
      er1646v2VxlBGIMVpVlanIpV6IcmpMessagesFragTimeExceeded
         INTEGER,
      er1646v2VxlBGIMVpVlanIpV6IcmpMessagesHeaderFieldErr
         INTEGER,
      er1646v2VxlBGIMVpVlanIpV6IcmpMessagesOptionUnrecognized
         INTEGER,
      er1646v2VxlBGIMVpVlanIpV6IcmpMessagesRedirect
         INTEGER,
      er1646v2VxlBGIMVpVlanVlanVid
         INTEGER,
      er1646v2VxlBGIMVpVlanVlanTpid
         INTEGER,
      er1646v2VxlBGIMVpVlanVlanTxCos
         INTEGER,
      er1646v2VxlBGIMVpVlanVlanChTos
         INTEGER,
      er1646v2VxlBGIMVpVlanVlanCTMapP0
         INTEGER,
      er1646v2VxlBGIMVpVlanVlanCTMapP1
         INTEGER,
      er1646v2VxlBGIMVpVlanVlanCTMapP2
         INTEGER,
      er1646v2VxlBGIMVpVlanVlanCTMapP3
         INTEGER,
      er1646v2VxlBGIMVpVlanVlanCTMapP4
         INTEGER,
      er1646v2VxlBGIMVpVlanVlanCTMapP5
         INTEGER,
      er1646v2VxlBGIMVpVlanVlanCTMapP6
         INTEGER,
      er1646v2VxlBGIMVpVlanVlanCTMapP7
         INTEGER,
      er1646v2VxlBGIMVpVlanVlanQCMapQueue1
         Integer32,
      er1646v2VxlBGIMVpVlanVlanQCMapQueue2
         Integer32,
      er1646v2VxlBGIMVpVlanVlanQCMapQueue3
         Integer32,
      er1646v2VxlBGIMVpVlanVlanQCMapQueue4
         Integer32,
      er1646v2VxlBGIMVpVlanVlanQCMapQueue5
         Integer32,
      er1646v2VxlBGIMVpVlanVlanQCMapLowDelayQueue
         Integer32,
      er1646v2VxlBGIMVpVlanVlanQCMapLowDelay2Queue
         Integer32,
      er1646v2VxlBGIMVpVlanVlanQCMapSystemQueue
         Integer32,
      er1646v2VxlBGIMVpVlanVlanArpTimeOut
         TimeTicks,
      er1646v2VxlBGIMVpVlanVlanArpProxyArp
         INTEGER
      }

er1646v2VxlBGIMVpVlanActions OBJECT-TYPE
   SYNTAX      VariableLengthTableActions
   MAX-ACCESS  read-write
   STATUS      current
   DESCRIPTION
      "By way of this field, some manipulations
       on this table may be performed."
   ::= {er1646v2VxlBGIMVpVlanEntry 2}

er1646v2VxlBGIMVpVlanGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanEntry 10}

er1646v2VxlBGIMVpVlanTableIx OBJECT-TYPE
   SYNTAX      TableIndex
   MAX-ACCESS  not-accessible
   STATUS      current
   DESCRIPTION
      ""
   ::= {er1646v2VxlBGIMVpVlanEntry 11}

er1646v2VxlBGIMVpVlanName OBJECT-TYPE
   SYNTAX      DisplayString
   MAX-ACCESS  read-write
   STATUS      current
   DESCRIPTION
      "Path: vxLanBridgeGroup.editConf.vlan.name"
   ::= {er1646v2VxlBGIMVpVlanEntry 16777216}

er1646v2VxlBGIMVpVlanRemark OBJECT-TYPE
   SYNTAX      DisplayString
   MAX-ACCESS  read-write
   STATUS      current
   DESCRIPTION
      "Path: vxLanBridgeGroup.editConf.vlan.remark"
   ::= {er1646v2VxlBGIMVpVlanEntry 1157627904}

er1646v2VxlBGIMVpVlanAdminStatus OBJECT-TYPE
   SYNTAX      INTEGER
               {
               up (1),
               down (2)
               }
   MAX-ACCESS  read-write
   STATUS      current
   DESCRIPTION
      "Path: vxLanBridgeGroup.editConf.vlan.adminStatus

       Possibilities:
               up   (1)
               down   (2)"
   ::= {er1646v2VxlBGIMVpVlanEntry 33554432}

er1646v2VxlBGIMVpVlanMode OBJECT-TYPE
   SYNTAX      INTEGER
               {
               routing (1),
               ipV6 (16),
               ipV6ipV4 (17)
               }
   MAX-ACCESS  read-write
   STATUS      current
   DESCRIPTION
      "Path: vxLanBridgeGroup.editConf.vlan.mode

       Possibilities:
               routing   (1)
               ipV6   (16)
               ipV6/ipV4   (17)"
   ::= {er1646v2VxlBGIMVpVlanEntry 67108864}

er1646v2VxlBGIMVpVlanIpVrfRouter OBJECT-TYPE
   SYNTAX      DisplayString
   MAX-ACCESS  read-write
   STATUS      current
   DESCRIPTION
      "Path: vxLanBridgeGroup.editConf.vlan.ip.vrfRouter"
   ::= {er1646v2VxlBGIMVpVlanEntry 53215232}

er1646v2VxlBGIMVpVlanIpAdr OBJECT-TYPE
   SYNTAX      IpAddress
   MAX-ACCESS  read-write
   STATUS      current
   DESCRIPTION
      "Path: vxLanBridgeGroup.editConf.vlan.ip.address"
   ::= {er1646v2VxlBGIMVpVlanEntry 58261504}

er1646v2VxlBGIMVpVlanIpNetm OBJECT-TYPE
   SYNTAX      IpAddress
   MAX-ACCESS  read-write
   STATUS      current
   DESCRIPTION
      "Path: vxLanBridgeGroup.editConf.vlan.ip.netMask"
   ::= {er1646v2VxlBGIMVpVlanEntry 58392576}

er1646v2VxlBGIMVpVlanIpSNetName OBJECT-TYPE
   SYNTAX      INTEGER
               {
               slOPTg (0),
               corp (2),
               dmz (3),
               internet (1)
               }
   MAX-ACCESS  read-write
   STATUS      current
   DESCRIPTION
      "Path: vxLanBridgeGroup.editConf.vlan.ip.sNet.name

       Possibilities:
               <OPT>   (0)
               corp   (2)
               dmz   (3)
               internet   (1)"
   ::= {er1646v2VxlBGIMVpVlanEntry 53674240}

er1646v2VxlBGIMVpVlanIpSNetCust OBJECT-TYPE
   SYNTAX      DisplayString
   MAX-ACCESS  read-write
   STATUS      current
   DESCRIPTION
      "Path: vxLanBridgeGroup.editConf.vlan.ip.sNet.custom"
   ::= {er1646v2VxlBGIMVpVlanEntry 53674496}

er1646v2VxlBGIMVpVlanIpDhcpC OBJECT-TYPE
   SYNTAX      INTEGER
               {
               disabled (0),
               enabled (1)
               }
   MAX-ACCESS  read-write
   STATUS      current
   DESCRIPTION
      "Path: vxLanBridgeGroup.editConf.vlan.ip.dhcpClient

       Possibilities:
               disabled   (0)
               enabled   (1)"
   ::= {er1646v2VxlBGIMVpVlanEntry 53608448}

er1646v2VxlBGIMVpVlanIpDhcpGatewayPreference OBJECT-TYPE
   SYNTAX      Integer32
   MAX-ACCESS  read-write
   STATUS      current
   DESCRIPTION
      "Path: vxLanBridgeGroup.editConf.vlan.ip.dhcp.gatewayPreference"
   ::= {er1646v2VxlBGIMVpVlanEntry 53739776}

er1646v2VxlBGIMVpVlanIpDhcpRoutePreference OBJECT-TYPE
   SYNTAX      Integer32
   MAX-ACCESS  read-write
   STATUS      current
   DESCRIPTION
      "Path: vxLanBridgeGroup.editConf.vlan.ip.dhcp.routePreference"
   ::= {er1646v2VxlBGIMVpVlanEntry 53740032}

er1646v2VxlBGIMVpVlanIpDhcpDnsPreference OBJECT-TYPE
   SYNTAX      Integer32
   MAX-ACCESS  read-write
   STATUS      current
   DESCRIPTION
      "Path: vxLanBridgeGroup.editConf.vlan.ip.dhcp.dnsPreference"
   ::= {er1646v2VxlBGIMVpVlanEntry 53740288}

er1646v2VxlBGIMVpVlanIpMtu OBJECT-TYPE
   SYNTAX      Integer32
   MAX-ACCESS  read-write
   STATUS      current
   DESCRIPTION
      "Path: vxLanBridgeGroup.editConf.vlan.ip.mtu"
   ::= {er1646v2VxlBGIMVpVlanEntry 52953088}

er1646v2VxlBGIMVpVlanIpMssAdjust OBJECT-TYPE
   SYNTAX      INTEGER
               {
               disabled (0),
               auto (65536)
               }
   MAX-ACCESS  read-write
   STATUS      current
   DESCRIPTION
      "Path: vxLanBridgeGroup.editConf.vlan.ip.mssAdjust

       Possibilities:
               disabled   (0)
               auto   (65536)"
   ::= {er1646v2VxlBGIMVpVlanEntry 53280768}

er1646v2VxlBGIMVpVlanIpRipMetric OBJECT-TYPE
   SYNTAX      Integer32
   MAX-ACCESS  read-write
   STATUS      current
   DESCRIPTION
      "Path: vxLanBridgeGroup.editConf.vlan.ip.rip.metric"
   ::= {er1646v2VxlBGIMVpVlanEntry 51712768}

er1646v2VxlBGIMVpVlanIpRipMetricOut OBJECT-TYPE
   SYNTAX      Integer32
   MAX-ACCESS  read-write
   STATUS      current
   DESCRIPTION
      "Path: vxLanBridgeGroup.editConf.vlan.ip.rip.metricOut"
   ::= {er1646v2VxlBGIMVpVlanEntry 51713024}

er1646v2VxlBGIMVpVlanIpRipMode OBJECT-TYPE
   SYNTAX      INTEGER
               {
               disabled (0),
               passive (1),
               active (2)
               }
   MAX-ACCESS  read-write
   STATUS      current
   DESCRIPTION
      "Path: vxLanBridgeGroup.editConf.vlan.ip.rip.mode

       Possibilities:
               disabled   (0)
               passive   (1)
               active   (2)"
   ::= {er1646v2VxlBGIMVpVlanEntry 51713280}

er1646v2VxlBGIMVpVlanIpRipTxVer OBJECT-TYPE
   SYNTAX      INTEGER
               {
               rip1 (0),
               rip2 (1),
               rip1mcompatible (2)
               }
   MAX-ACCESS  read-write
   STATUS      current
   DESCRIPTION
      "Path: vxLanBridgeGroup.editConf.vlan.ip.rip.txVersion

       Possibilities:
               rip1   (0)
               rip2   (1)
               rip1-compatible   (2)"
   ::= {er1646v2VxlBGIMVpVlanEntry 51716864}

er1646v2VxlBGIMVpVlanIpRipRxVer OBJECT-TYPE
   SYNTAX      INTEGER
               {
               rip1only (0),
               rip2only (1),
               rip12 (2)
               }
   MAX-ACCESS  read-write
   STATUS      current
   DESCRIPTION
      "Path: vxLanBridgeGroup.editConf.vlan.ip.rip.rxVersion

       Possibilities:
               rip1only   (0)
               rip2only   (1)
               rip1&2   (2)"
   ::= {er1646v2VxlBGIMVpVlanEntry 51717120}

er1646v2VxlBGIMVpVlanIpRipSplitH OBJECT-TYPE
   SYNTAX      INTEGER
               {
               disabled (0),
               enabled (1),
               poisonedReverse (2)
               }
   MAX-ACCESS  read-write
   STATUS      current
   DESCRIPTION
      "Path: vxLanBridgeGroup.editConf.vlan.ip.rip.splitHorizon

       Possibilities:
               disabled   (0)
               enabled   (1)
               poisonedReverse   (2)"
   ::= {er1646v2VxlBGIMVpVlanEntry 51713792}

er1646v2VxlBGIMVpVlanIpRipAuth OBJECT-TYPE
   SYNTAX      INTEGER
               {
               disabled (0),
               texts (1),
               md5 (2)
               }
   MAX-ACCESS  read-write
   STATUS      current
   DESCRIPTION
      "Path: vxLanBridgeGroup.editConf.vlan.ip.rip.authentication

       Possibilities:
               disabled   (0)
               text    (1)
               md5   (2)"
   ::= {er1646v2VxlBGIMVpVlanEntry 51712512}

er1646v2VxlBGIMVpVlanIpRipFilter OBJECT-TYPE
   SYNTAX      DisplayString
   MAX-ACCESS  read-write
   STATUS      current
   DESCRIPTION
      "Path: vxLanBridgeGroup.editConf.vlan.ip.rip.filter"
   ::= {er1646v2VxlBGIMVpVlanEntry 51716096}

er1646v2VxlBGIMVpVlanIpRipFilterIn OBJECT-TYPE
   SYNTAX      DisplayString
   MAX-ACCESS  read-write
   STATUS      current
   DESCRIPTION
      "Path: vxLanBridgeGroup.editConf.vlan.ip.rip.filterIn"
   ::= {er1646v2VxlBGIMVpVlanEntry 51716352}

er1646v2VxlBGIMVpVlanIpRipClearNextHop OBJECT-TYPE
   SYNTAX      INTEGER
               {
               disabled (0),
               enabled (1)
               }
   MAX-ACCESS  read-write
   STATUS      current
   DESCRIPTION
      "Path: vxLanBridgeGroup.editConf.vlan.ip.rip.clearNextHop

       Possibilities:
               disabled   (0)
               enabled   (1)"
   ::= {er1646v2VxlBGIMVpVlanEntry 51708416}

er1646v2VxlBGIMVpVlanIpAccPol OBJECT-TYPE
   SYNTAX      DisplayString
   MAX-ACCESS  read-write
   STATUS      current
   DESCRIPTION
      "Path: vxLanBridgeGroup.editConf.vlan.ip.accessPolicy"
   ::= {er1646v2VxlBGIMVpVlanEntry 53084160}

er1646v2VxlBGIMVpVlanIpAB OBJECT-TYPE
   SYNTAX      DisplayString
   MAX-ACCESS  read-write
   STATUS      current
   DESCRIPTION
      "Path: vxLanBridgeGroup.editConf.vlan.ip.trafficPolicy"
   ::= {er1646v2VxlBGIMVpVlanEntry 51249152}

er1646v2VxlBGIMVpVlanIpMA OBJECT-TYPE
   SYNTAX      INTEGER
               {
               disabled (0),
               enabled (1)
               }
   MAX-ACCESS  read-write
   STATUS      current
   DESCRIPTION
      "Path: vxLanBridgeGroup.editConf.vlan.ip.mgmtAccess

       Possibilities:
               disabled   (0)
               enabled   (1)"
   ::= {er1646v2VxlBGIMVpVlanEntry 51380224}

er1646v2VxlBGIMVpVlanIpMF OBJECT-TYPE
   SYNTAX      Integer32
   MAX-ACCESS  read-write
   STATUS      current
   DESCRIPTION
      "Path: vxLanBridgeGroup.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VxlBGIMVpVlanEntry 51445760}

er1646v2VxlBGIMVpVlanIpDB OBJECT-TYPE
   SYNTAX      INTEGER
               {
               disabled (0),
               enabled (1)
               }
   MAX-ACCESS  read-write
   STATUS      current
   DESCRIPTION
      "Path: vxLanBridgeGroup.editConf.vlan.ip.directedBroadcasts

       Possibilities:
               disabled   (0)
               enabled   (1)"
   ::= {er1646v2VxlBGIMVpVlanEntry 51773440}

er1646v2VxlBGIMVpVlanIpIR OBJECT-TYPE
   SYNTAX      INTEGER
               {
               disabled (0),
               enabled (1)
               }
   MAX-ACCESS  read-write
   STATUS      current
   DESCRIPTION
      "Path: vxLanBridgeGroup.editConf.vlan.ip.icmpRedirects

       Possibilities:
               disabled   (0)
               enabled   (1)"
   ::= {er1646v2VxlBGIMVpVlanEntry 52035584}

er1646v2VxlBGIMVpVlanIpIgmp OBJECT-TYPE
   SYNTAX      INTEGER
               {
               disabled (0),
               proxy (1),
               router (2),
               v3Router (5)
               }
   MAX-ACCESS  read-write
   STATUS      current
   DESCRIPTION
      "Path: vxLanBridgeGroup.editConf.vlan.ip.igmp

       Possibilities:
               disabled   (0)
               proxy   (1)
               router   (2)
               v3Router   (5)"
   ::= {er1646v2VxlBGIMVpVlanEntry 52428800}

er1646v2VxlBGIMVpVlanIpNN OBJECT-TYPE
   SYNTAX      DisplayString
   MAX-ACCESS  read-write
   STATUS      current
   DESCRIPTION
      "Path: vxLanBridgeGroup.editConf.vlan.ip.nat"
   ::= {er1646v2VxlBGIMVpVlanEntry 52101120}

er1646v2VxlBGIMVpVlanIpVrrp OBJECT-TYPE
   SYNTAX      INTEGER
               {
               disabled (0),
               enabled (1)
               }
   MAX-ACCESS  read-write
   STATUS      current
   DESCRIPTION
      "Path: vxLanBridgeGroup.editConf.vlan.ip.vrrp

       Possibilities:
               disabled   (0)
               enabled   (1)"
   ::= {er1646v2VxlBGIMVpVlanEntry 53149696}

er1646v2VxlBGIMVpVlanIpPimMode OBJECT-TYPE
   SYNTAX      INTEGER
               {
               disabled (0),
               sparse (1),
               passive (2)
               }
   MAX-ACCESS  read-write
   STATUS      current
   DESCRIPTION
      "Path: vxLanBridgeGroup.editConf.vlan.ip.pim.mode

       Possibilities:
               disabled   (0)
               sparse   (1)
               passive   (2)"
   ::= {er1646v2VxlBGIMVpVlanEntry 53346560}

er1646v2VxlBGIMVpVlanIpPimDrPriority OBJECT-TYPE
   SYNTAX      Counter32
   MAX-ACCESS  read-write
   STATUS      current
   DESCRIPTION
      "Path: vxLanBridgeGroup.editConf.vlan.ip.pim.drPriority

       32 bit unsigned wrappable counter."
   ::= {er1646v2VxlBGIMVpVlanEntry 53346816}

er1646v2VxlBGIMVpVlanIpPimHelloTime OBJECT-TYPE
   SYNTAX      TimeTicks
   MAX-ACCESS  read-write
   STATUS      current
   DESCRIPTION
      "Path: vxLanBridgeGroup.editConf.vlan.ip.pim.helloTime

       Time in centi-second."
   ::= {er1646v2VxlBGIMVpVlanEntry 53347072}

er1646v2VxlBGIMVpVlanIpPimPropagationDelay OBJECT-TYPE
   SYNTAX      TimeTicks
   MAX-ACCESS  read-write
   STATUS      current
   DESCRIPTION
      "Path: vxLanBridgeGroup.editConf.vlan.ip.pim.propagationDelay

       Time in centi-second."
   ::= {er1646v2VxlBGIMVpVlanEntry 53347328}

er1646v2VxlBGIMVpVlanIpPimOverrideInterval OBJECT-TYPE
   SYNTAX      TimeTicks
   MAX-ACCESS  read-write
   STATUS      current
   DESCRIPTION
      "Path: vxLanBridgeGroup.editConf.vlan.ip.pim.overrideInterval

       Time in centi-second."
   ::= {er1646v2VxlBGIMVpVlanEntry 53347584}

er1646v2VxlBGIMVpVlanIpPimBsrBorder OBJECT-TYPE
   SYNTAX      INTEGER
               {
               disabled (0),
               enabled (1)
               }
   MAX-ACCESS  read-write
   STATUS      current
   DESCRIPTION
      "Path: vxLanBridgeGroup.editConf.vlan.ip.pim.bsrBorder

       Possibilities:
               disabled   (0)
               enabled   (1)"
   ::= {er1646v2VxlBGIMVpVlanEntry 53347840}

er1646v2VxlBGIMVpVlanIpPimTtlThreshold OBJECT-TYPE
   SYNTAX      Integer32
   MAX-ACCESS  read-write
   STATUS      current
   DESCRIPTION
      "Path: vxLanBridgeGroup.editConf.vlan.ip.pim.ttlThreshold"
   ::= {er1646v2VxlBGIMVpVlanEntry 53348096}

er1646v2VxlBGIMVpVlanIpIMNetworkUnreachable OBJECT-TYPE
   SYNTAX      INTEGER
               {
               disabled (0),
               enabled (1)
               }
   MAX-ACCESS  read-write
   STATUS      current
   DESCRIPTION
      "Path: vxLanBridgeGroup.editConf.vlan.ip.icmpMessages.networkUnreachable

       Possibilities:
               disabled   (0)
               enabled   (1)"
   ::= {er1646v2VxlBGIMVpVlanEntry 53412096}

er1646v2VxlBGIMVpVlanIpIMHostUnreachable OBJECT-TYPE
   SYNTAX      INTEGER
               {
               disabled (0),
               enabled (1)
               }
   MAX-ACCESS  read-write
   STATUS      current
   DESCRIPTION
      "Path: vxLanBridgeGroup.editConf.vlan.ip.icmpMessages.hostUnreachable

       Possibilities:
               disabled   (0)
               enabled   (1)"
   ::= {er1646v2VxlBGIMVpVlanEntry 53412352}

er1646v2VxlBGIMVpVlanIpIMProtocolUnreachable OBJECT-TYPE
   SYNTAX      INTEGER
               {
               disabled (0),
               enabled (1)
               }
   MAX-ACCESS  read-write
   STATUS      current
   DESCRIPTION
      "Path: vxLanBridgeGroup.editConf.vlan.ip.icmpMessages.protocolUnreachable

       Possibilities:
               disabled   (0)
               enabled   (1)"
   ::= {er1646v2VxlBGIMVpVlanEntry 53412608}

er1646v2VxlBGIMVpVlanIpIMPortUnreachable OBJECT-TYPE
   SYNTAX      INTEGER
               {
               disabled (0),
               enabled (1)
               }
   MAX-ACCESS  read-write
   STATUS      current
   DESCRIPTION
      "Path: vxLanBridgeGroup.editConf.vlan.ip.icmpMessages.portUnreachable

       Possibilities:
               disabled   (0)
               enabled   (1)"
   ::= {er1646v2VxlBGIMVpVlanEntry 53412864}

er1646v2VxlBGIMVpVlanIpIMMtuExceeded OBJECT-TYPE
   SYNTAX      INTEGER
               {
               disabled (0),
               enabled (1)
               }
   MAX-ACCESS  read-write
   STATUS      current
   DESCRIPTION
      "Path: vxLanBridgeGroup.editConf.vlan.ip.icmpMessages.mtuExceeded

       Possibilities:
               disabled   (0)
               enabled   (1)"
   ::= {er1646v2VxlBGIMVpVlanEntry 53413120}

er1646v2VxlBGIMVpVlanIpIMAdminProhibited OBJECT-TYPE
   SYNTAX      INTEGER
               {
               disabled (0),
               enabled (1)
               }
   MAX-ACCESS  read-write
   STATUS      current
   DESCRIPTION
      "Path: vxLanBridgeGroup.editConf.vlan.ip.icmpMessages.adminProhibited

       Possibilities:
               disabled   (0)
               enabled   (1)"
   ::= {er1646v2VxlBGIMVpVlanEntry 53413376}

er1646v2VxlBGIMVpVlanIpIMTtlExceeded OBJECT-TYPE
   SYNTAX      INTEGER
               {
               disabled (0),
               enabled (1)
               }
   MAX-ACCESS  read-write
   STATUS      current
   DESCRIPTION
      "Path: vxLanBridgeGroup.editConf.vlan.ip.icmpMessages.ttlExceeded

       Possibilities:
               disabled   (0)
               enabled   (1)"
   ::= {er1646v2VxlBGIMVpVlanEntry 53413632}

er1646v2VxlBGIMVpVlanIpIMRedirect OBJECT-TYPE
   SYNTAX      INTEGER
               {
               disabled (0),
               enabled (1)
               }
   MAX-ACCESS  read-write
   STATUS      current
   DESCRIPTION
      "Path: vxLanBridgeGroup.editConf.vlan.ip.icmpMessages.redirect

       Possibilities:
               disabled   (0)
               enabled   (1)"
   ::= {er1646v2VxlBGIMVpVlanEntry 53413888}

er1646v2VxlBGIMVpVlanIpV6VrfRouter OBJECT-TYPE
   SYNTAX      DisplayString
   MAX-ACCESS  read-write
   STATUS      current
   DESCRIPTION
      "Path: vxLanBridgeGroup.editConf.vlan.ipV6.vrfRouter"
   ::= {er1646v2VxlBGIMVpVlanEntry 704708608}

er1646v2VxlBGIMVpVlanIpV6AddrAutoConfigNrDupAddrDetects OBJECT-TYPE
   SYNTAX      Integer32
   MAX-ACCESS  read-write
   STATUS      current
   DESCRIPTION
      "Path: vxLanBridgeGroup.editConf.vlan.ipV6.addrAutoConfig.nrDupAddrDetects"
   ::= {er1646v2VxlBGIMVpVlanEntry 704905472}

er1646v2VxlBGIMVpVlanIpV6AddrAutoConfigAcceptRa OBJECT-TYPE
   SYNTAX      INTEGER
               {
               disabled (0),
               enabled (1)
               }
   MAX-ACCESS  read-write
   STATUS      current
   DESCRIPTION
      "Path: vxLanBridgeGroup.editConf.vlan.ipV6.addrAutoConfig.acceptRa

       Possibilities:
               disabled   (0)
               enabled   (1)"
   ::= {er1646v2VxlBGIMVpVlanEntry 704905728}

er1646v2VxlBGIMVpVlanIpV6AddrAutoConfigAcceptRaRdnss OBJECT-TYPE
   SYNTAX      INTEGER
               {
               disabled (0),
               enabled (1)
               }
   MAX-ACCESS  read-write
   STATUS      current
   DESCRIPTION
      "Path: vxLanBridgeGroup.editConf.vlan.ipV6.addrAutoConfig.acceptRaRdnss

       Possibilities:
               disabled   (0)
               enabled   (1)"
   ::= {er1646v2VxlBGIMVpVlanEntry 704905984}

er1646v2VxlBGIMVpVlanIpV6AddrAutoConfigAcceptRaDnssl OBJECT-TYPE
   SYNTAX      INTEGER
               {
               disabled (0),
               enabled (1)
               }
   MAX-ACCESS  read-write
   STATUS      current
   DESCRIPTION
      "Path: vxLanBridgeGroup.editConf.vlan.ipV6.addrAutoConfig.acceptRaDnssl

       Possibilities:
               disabled   (0)
               enabled   (1)"
   ::= {er1646v2VxlBGIMVpVlanEntry 704906240}

er1646v2VxlBGIMVpVlanIpV6DefaultRoute OBJECT-TYPE
   SYNTAX      INTEGER
               {
               disabled (0),
               enabled (1)
               }
   MAX-ACCESS  read-write
   STATUS      current
   DESCRIPTION
      "Path: vxLanBridgeGroup.editConf.vlan.ipV6.defaultRoute

       Possibilities:
               disabled   (0)
               enabled   (1)"
   ::= {er1646v2VxlBGIMVpVlanEntry 704970752}

er1646v2VxlBGIMVpVlanIpV6RaSend OBJECT-TYPE
   SYNTAX      INTEGER
               {
               disabled (0),
               enabled (1)
               }
   MAX-ACCESS  read-write
   STATUS      current
   DESCRIPTION
      "Path: vxLanBridgeGroup.editConf.vlan.ipV6.ra.send

       Possibilities:
               disabled   (0)
               enabled   (1)"
   ::= {er1646v2VxlBGIMVpVlanEntry 705036544}

er1646v2VxlBGIMVpVlanIpV6RaMinInterval OBJECT-TYPE
   SYNTAX      TimeTicks
   MAX-ACCESS  read-write
   STATUS      current
   DESCRIPTION
      "Path: vxLanBridgeGroup.editConf.vlan.ipV6.ra.minInterval

       Time in centi-second."
   ::= {er1646v2VxlBGIMVpVlanEntry 705036800}

er1646v2VxlBGIMVpVlanIpV6RaMaxInterval OBJECT-TYPE
   SYNTAX      TimeTicks
   MAX-ACCESS  read-write
   STATUS      current
   DESCRIPTION
      "Path: vxLanBridgeGroup.editConf.vlan.ipV6.ra.maxInterval

       Time in centi-second."
   ::= {er1646v2VxlBGIMVpVlanEntry 705037056}

er1646v2VxlBGIMVpVlanIpV6RaManagedFlag OBJECT-TYPE
   SYNTAX      INTEGER
               {
               disabled (0),
               enabled (1)
               }
   MAX-ACCESS  read-write
   STATUS      current
   DESCRIPTION
      "Path: vxLanBridgeGroup.editConf.vlan.ipV6.ra.managedFlag

       Possibilities:
               disabled   (0)
               enabled   (1)"
   ::= {er1646v2VxlBGIMVpVlanEntry 705037312}

er1646v2VxlBGIMVpVlanIpV6RaOtherConfFlag OBJECT-TYPE
   SYNTAX      INTEGER
               {
               disabled (0),
               enabled (1)
               }
   MAX-ACCESS  read-write
   STATUS      current
   DESCRIPTION
      "Path: vxLanBridgeGroup.editConf.vlan.ipV6.ra.otherConfFlag

       Possibilities:
               disabled   (0)
               enabled   (1)"
   ::= {er1646v2VxlBGIMVpVlanEntry 705037568}

er1646v2VxlBGIMVpVlanIpV6RaLinkMtu OBJECT-TYPE
   SYNTAX      Integer32
   MAX-ACCESS  read-write
   STATUS      current
   DESCRIPTION
      "Path: vxLanBridgeGroup.editConf.vlan.ipV6.ra.linkMtu"
   ::= {er1646v2VxlBGIMVpVlanEntry 705037824}

er1646v2VxlBGIMVpVlanIpV6RaReachableTime OBJECT-TYPE
   SYNTAX      TimeTicks
   MAX-ACCESS  read-write
   STATUS      current
   DESCRIPTION
      "Path: vxLanBridgeGroup.editConf.vlan.ipV6.ra.reachableTime

       Time in centi-second."
   ::= {er1646v2VxlBGIMVpVlanEntry 705038080}

er1646v2VxlBGIMVpVlanIpV6RaRetransmitTime OBJECT-TYPE
   SYNTAX      TimeTicks
   MAX-ACCESS  read-write
   STATUS      current
   DESCRIPTION
      "Path: vxLanBridgeGroup.editConf.vlan.ipV6.ra.retransmitTime

       Time in centi-second."
   ::= {er1646v2VxlBGIMVpVlanEntry 705038336}

er1646v2VxlBGIMVpVlanIpV6RaHopLimit OBJECT-TYPE
   SYNTAX      Integer32
   MAX-ACCESS  read-write
   STATUS      current
   DESCRIPTION
      "Path: vxLanBridgeGroup.editConf.vlan.ipV6.ra.hopLimit"
   ::= {er1646v2VxlBGIMVpVlanEntry 705038592}

er1646v2VxlBGIMVpVlanIpV6RaDefaultLifeTime OBJECT-TYPE
   SYNTAX      TimeTicks
   MAX-ACCESS  read-write
   STATUS      current
   DESCRIPTION
      "Path: vxLanBridgeGroup.editConf.vlan.ipV6.ra.defaultLifeTime

       Time in centi-second."
   ::= {er1646v2VxlBGIMVpVlanEntry 705038848}

er1646v2VxlBGIMVpVlanIpV6RaDnsOptionsRdnssLifeTime OBJECT-TYPE
   SYNTAX      TimeTicks
   MAX-ACCESS  read-write
   STATUS      current
   DESCRIPTION
      "Path: vxLanBridgeGroup.editConf.vlan.ipV6.ra.dnsOptions.rdnss.lifeTime

       Time in centi-second."
   ::= {er1646v2VxlBGIMVpVlanEntry 705039140}

er1646v2VxlBGIMVpVlanIpV6RaDnsOptionsRdnssImportServers OBJECT-TYPE
   SYNTAX      INTEGER
               {
               disabled (0),
               enabled (1)
               }
   MAX-ACCESS  read-write
   STATUS      current
   DESCRIPTION
      "Path: vxLanBridgeGroup.editConf.vlan.ipV6.ra.dnsOptions.rdnss.importServers

       Possibilities:
               disabled   (0)
               enabled   (1)"
   ::= {er1646v2VxlBGIMVpVlanEntry 705039148}

er1646v2VxlBGIMVpVlanIpV6RaDnsOptionsDnsslLifeTime OBJECT-TYPE
   SYNTAX      TimeTicks
   MAX-ACCESS  read-write
   STATUS      current
   DESCRIPTION
      "Path: vxLanBridgeGroup.editConf.vlan.ipV6.ra.dnsOptions.dnssl.lifeTime

       Time in centi-second."
   ::= {er1646v2VxlBGIMVpVlanEntry 705039172}

er1646v2VxlBGIMVpVlanIpV6RaDnsOptionsDnsslImportDomains OBJECT-TYPE
   SYNTAX      INTEGER
               {
               disabled (0),
               enabled (1)
               }
   MAX-ACCESS  read-write
   STATUS      current
   DESCRIPTION
      "Path: vxLanBridgeGroup.editConf.vlan.ipV6.ra.dnsOptions.dnssl.importDomains

       Possibilities:
               disabled   (0)
               enabled   (1)"
   ::= {er1646v2VxlBGIMVpVlanEntry 705039180}

er1646v2VxlBGIMVpVlanIpV6RsSend OBJECT-TYPE
   SYNTAX      INTEGER
               {
               disabled (0),
               enabled (1)
               }
   MAX-ACCESS  read-write
   STATUS      current
   DESCRIPTION
      "Path: vxLanBridgeGroup.editConf.vlan.ipV6.rs.send

       Possibilities:
               disabled   (0)
               enabled   (1)"
   ::= {er1646v2VxlBGIMVpVlanEntry 705954048}

er1646v2VxlBGIMVpVlanIpV6RsMaxRandomDelay OBJECT-TYPE
   SYNTAX      TimeTicks
   MAX-ACCESS  read-write
   STATUS      current
   DESCRIPTION
      "Path: vxLanBridgeGroup.editConf.vlan.ipV6.rs.maxRandomDelay

       Time in centi-second."
   ::= {er1646v2VxlBGIMVpVlanEntry 705954304}

er1646v2VxlBGIMVpVlanIpV6RsInterval OBJECT-TYPE
   SYNTAX      TimeTicks
   MAX-ACCESS  read-write
   STATUS      current
   DESCRIPTION
      "Path: vxLanBridgeGroup.editConf.vlan.ipV6.rs.interval

       Time in centi-second."
   ::= {er1646v2VxlBGIMVpVlanEntry 705954560}

er1646v2VxlBGIMVpVlanIpV6RsMaxSolicitations OBJECT-TYPE
   SYNTAX      Integer32
   MAX-ACCESS  read-write
   STATUS      current
   DESCRIPTION
      "Path: vxLanBridgeGroup.editConf.vlan.ipV6.rs.maxSolicitations"
   ::= {er1646v2VxlBGIMVpVlanEntry 705954816}

er1646v2VxlBGIMVpVlanIpV6TrafficPolicyInbound OBJECT-TYPE
   SYNTAX      DisplayString
   MAX-ACCESS  read-write
   STATUS      current
   DESCRIPTION
      "Path: vxLanBridgeGroup.editConf.vlan.ipV6.trafficPolicy.inbound"
   ::= {er1646v2VxlBGIMVpVlanEntry 705364224}

er1646v2VxlBGIMVpVlanIpV6TrafficPolicyOutbound OBJECT-TYPE
   SYNTAX      DisplayString
   MAX-ACCESS  read-write
   STATUS      current
   DESCRIPTION
      "Path: vxLanBridgeGroup.editConf.vlan.ipV6.trafficPolicy.outbound"
   ::= {er1646v2VxlBGIMVpVlanEntry 705364480}

er1646v2VxlBGIMVpVlanIpV6FirewallZone OBJECT-TYPE
   SYNTAX      DisplayString
   MAX-ACCESS  read-write
   STATUS      current
   DESCRIPTION
      "Path: vxLanBridgeGroup.editConf.vlan.ipV6.firewall.zone"
   ::= {er1646v2VxlBGIMVpVlanEntry 705429760}

er1646v2VxlBGIMVpVlanIpV6DhcpClientAddrAC OBJECT-TYPE
   SYNTAX      INTEGER
               {
               disabled (0),
               enabled (1)
               }
   MAX-ACCESS  read-write
   STATUS      current
   DESCRIPTION
      "Path: vxLanBridgeGroup.editConf.vlan.ipV6.dhcp.client.addrAutoConfig

       Possibilities:
               disabled   (0)
               enabled   (1)"
   ::= {er1646v2VxlBGIMVpVlanEntry 705307648}

er1646v2VxlBGIMVpVlanIpV6DhcpClientPrDelMode OBJECT-TYPE
   SYNTAX      INTEGER
               {
               disabled (0),
               enabled (1)
               }
   MAX-ACCESS  read-write
   STATUS      current
   DESCRIPTION
      "Path: vxLanBridgeGroup.editConf.vlan.ipV6.dhcp.client.pd.mode

       Possibilities:
               disabled   (0)
               enabled   (1)"
   ::= {er1646v2VxlBGIMVpVlanEntry 705308676}

er1646v2VxlBGIMVpVlanIpV6DhcpClientPrDelPool OBJECT-TYPE
   SYNTAX      DisplayString
   MAX-ACCESS  read-write
   STATUS      current
   DESCRIPTION
      "Path: vxLanBridgeGroup.editConf.vlan.ipV6.dhcp.client.pd.pool"
   ::= {er1646v2VxlBGIMVpVlanEntry 705308680}

er1646v2VxlBGIMVpVlanIpV6DhcpClientPrDelPdExclOpt OBJECT-TYPE
   SYNTAX      INTEGER
               {
               disabled (0),
               enabled (1)
               }
   MAX-ACCESS  read-write
   STATUS      current
   DESCRIPTION
      "Path: vxLanBridgeGroup.editConf.vlan.ipV6.dhcp.client.pd.pdExclOpt

       Possibilities:
               disabled   (0)
               enabled   (1)"
   ::= {er1646v2VxlBGIMVpVlanEntry 705308684}

er1646v2VxlBGIMVpVlanIpV6DhcpClientDnsServerPref OBJECT-TYPE
   SYNTAX      Integer32
   MAX-ACCESS  read-write
   STATUS      current
   DESCRIPTION
      "Path: vxLanBridgeGroup.editConf.vlan.ipV6.dhcp.client.dns.serverPref"
   ::= {er1646v2VxlBGIMVpVlanEntry 705310724}

er1646v2VxlBGIMVpVlanIpV6DhcpClientRapidCommit OBJECT-TYPE
   SYNTAX      INTEGER
               {
               disabled (0),
               enabled (1)
               }
   MAX-ACCESS  read-write
   STATUS      current
   DESCRIPTION
      "Path: vxLanBridgeGroup.editConf.vlan.ipV6.dhcp.client.rapidCommit

       Possibilities:
               disabled   (0)
               enabled   (1)"
   ::= {er1646v2VxlBGIMVpVlanEntry 705309696}

er1646v2VxlBGIMVpVlanIpV6DhcpClientTimersSolTimeOut OBJECT-TYPE
   SYNTAX      TimeTicks
   MAX-ACCESS  read-write
   STATUS      current
   DESCRIPTION
      "Path: vxLanBridgeGroup.editConf.vlan.ipV6.dhcp.client.timers.solTimeOut

       Time in centi-second."
   ::= {er1646v2VxlBGIMVpVlanEntry 705311748}

er1646v2VxlBGIMVpVlanIpV6DhcpClientTimersSolMaxRt OBJECT-TYPE
   SYNTAX      TimeTicks
   MAX-ACCESS  read-write
   STATUS      current
   DESCRIPTION
      "Path: vxLanBridgeGroup.editConf.vlan.ipV6.dhcp.client.timers.solMaxRt

       Time in centi-second."
   ::= {er1646v2VxlBGIMVpVlanEntry 705311752}

er1646v2VxlBGIMVpVlanIpV6DhcpClientTimersInfoRefresh OBJECT-TYPE
   SYNTAX      TimeTicks
   MAX-ACCESS  read-write
   STATUS      current
   DESCRIPTION
      "Path: vxLanBridgeGroup.editConf.vlan.ipV6.dhcp.client.timers.infoRefresh

       Time in centi-second."
   ::= {er1646v2VxlBGIMVpVlanEntry 705311756}

er1646v2VxlBGIMVpVlanIpV6DhcpServerMode OBJECT-TYPE
   SYNTAX      INTEGER
               {
               disabled (0),
               enabled (1)
               }
   MAX-ACCESS  read-write
   STATUS      current
   DESCRIPTION
      "Path: vxLanBridgeGroup.editConf.vlan.ipV6.dhcp.server.mode

       Possibilities:
               disabled   (0)
               enabled   (1)"
   ::= {er1646v2VxlBGIMVpVlanEntry 705315840}

er1646v2VxlBGIMVpVlanIpV6DhcpServerPreference OBJECT-TYPE
   SYNTAX      Integer32
   MAX-ACCESS  read-write
   STATUS      current
   DESCRIPTION
      "Path: vxLanBridgeGroup.editConf.vlan.ipV6.dhcp.server.preference"
   ::= {er1646v2VxlBGIMVpVlanEntry 705316864}

er1646v2VxlBGIMVpVlanIpV6DhcpServerPool OBJECT-TYPE
   SYNTAX      DisplayString
   MAX-ACCESS  read-write
   STATUS      current
   DESCRIPTION
      "Path: vxLanBridgeGroup.editConf.vlan.ipV6.dhcp.server.pool"
   ::= {er1646v2VxlBGIMVpVlanEntry 705317888}

er1646v2VxlBGIMVpVlanIpV6DhcpServerRapidCommit OBJECT-TYPE
   SYNTAX      INTEGER
               {
               disabled (0),
               enabled (1)
               }
   MAX-ACCESS  read-write
   STATUS      current
   DESCRIPTION
      "Path: vxLanBridgeGroup.editConf.vlan.ipV6.dhcp.server.rapidCommit

       Possibilities:
               disabled   (0)
               enabled   (1)"
   ::= {er1646v2VxlBGIMVpVlanEntry 705318912}

er1646v2VxlBGIMVpVlanIpV6DhcpServerTimersInfoRefresh OBJECT-TYPE
   SYNTAX      TimeTicks
   MAX-ACCESS  read-write
   STATUS      current
   DESCRIPTION
      "Path: vxLanBridgeGroup.editConf.vlan.ipV6.dhcp.server.timers.infoRefresh

       Time in centi-second."
   ::= {er1646v2VxlBGIMVpVlanEntry 705319940}

er1646v2VxlBGIMVpVlanIpV6DhcpRelayMode OBJECT-TYPE
   SYNTAX      INTEGER
               {
               disabled (0),
               enabled (1)
               }
   MAX-ACCESS  read-write
   STATUS      current
   DESCRIPTION
      "Path: vxLanBridgeGroup.editConf.vlan.ipV6.dhcp.relay.mode

       Possibilities:
               disabled   (0)
               enabled   (1)"
   ::= {er1646v2VxlBGIMVpVlanEntry 705323040}

er1646v2VxlBGIMVpVlanIpV6SendRedirect OBJECT-TYPE
   SYNTAX      INTEGER
               {
               disabled (0),
               enabled (1)
               }
   MAX-ACCESS  read-write
   STATUS      current
   DESCRIPTION
      "Path: vxLanBridgeGroup.editConf.vlan.ipV6.sendRedirect

       Possibilities:
               disabled   (0)
               enabled   (1)"
   ::= {er1646v2VxlBGIMVpVlanEntry 705101824}

er1646v2VxlBGIMVpVlanIpV6LinkMtu OBJECT-TYPE
   SYNTAX      Integer32
   MAX-ACCESS  read-write
   STATUS      current
   DESCRIPTION
      "Path: vxLanBridgeGroup.editConf.vlan.ipV6.linkMtu"
   ::= {er1646v2VxlBGIMVpVlanEntry 705167360}

er1646v2VxlBGIMVpVlanIpV6InterfaceId OBJECT-TYPE
   SYNTAX      OCTET STRING
   MAX-ACCESS  read-write
   STATUS      current
   DESCRIPTION
      "Path: vxLanBridgeGroup.editConf.vlan.ipV6.interfaceId"
   ::= {er1646v2VxlBGIMVpVlanEntry 705232896}

er1646v2VxlBGIMVpVlanIpV6MF OBJECT-TYPE
   SYNTAX      Integer32
   MAX-ACCESS  read-write
   STATUS      current
   DESCRIPTION
      "Path: vxLanBridgeGroup.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VxlBGIMVpVlanEntry 705757184}

er1646v2VxlBGIMVpVlanIpV6IcmpMessagesNoRoute OBJECT-TYPE
   SYNTAX      INTEGER
               {
               disabled (0),
               enabled (1)
               }
   MAX-ACCESS  read-write
   STATUS      current
   DESCRIPTION
      "Path: vxLanBridgeGroup.editConf.vlan.ipV6.icmpMessages.noRoute

       Possibilities:
               disabled   (0)
               enabled   (1)"
   ::= {er1646v2VxlBGIMVpVlanEntry 705822976}

er1646v2VxlBGIMVpVlanIpV6IcmpMessagesBeyondScope OBJECT-TYPE
   SYNTAX      INTEGER
               {
               disabled (0),
               enabled (1)
               }
   MAX-ACCESS  read-write
   STATUS      current
   DESCRIPTION
      "Path: vxLanBridgeGroup.editConf.vlan.ipV6.icmpMessages.beyondScope

       Possibilities:
               disabled   (0)
               enabled   (1)"
   ::= {er1646v2VxlBGIMVpVlanEntry 705823488}

er1646v2VxlBGIMVpVlanIpV6IcmpMessagesAddressUnreachable OBJECT-TYPE
   SYNTAX      INTEGER
               {
               disabled (0),
               enabled (1)
               }
   MAX-ACCESS  read-write
   STATUS      current
   DESCRIPTION
      "Path: vxLanBridgeGroup.editConf.vlan.ipV6.icmpMessages.addressUnreachable

       Possibilities:
               disabled   (0)
               enabled   (1)"
   ::= {er1646v2VxlBGIMVpVlanEntry 705823744}

er1646v2VxlBGIMVpVlanIpV6IcmpMessagesPortUnreachable OBJECT-TYPE
   SYNTAX      INTEGER
               {
               disabled (0),
               enabled (1)
               }
   MAX-ACCESS  read-write
   STATUS      current
   DESCRIPTION
      "Path: vxLanBridgeGroup.editConf.vlan.ipV6.icmpMessages.portUnreachable

       Possibilities:
               disabled   (0)
               enabled   (1)"
   ::= {er1646v2VxlBGIMVpVlanEntry 705824000}

er1646v2VxlBGIMVpVlanIpV6IcmpMessagesPacketTooBig OBJECT-TYPE
   SYNTAX      INTEGER
               {
               disabled (0),
               enabled (1)
               }
   MAX-ACCESS  read-write
   STATUS      current
   DESCRIPTION
      "Path: vxLanBridgeGroup.editConf.vlan.ipV6.icmpMessages.packetTooBig

       Possibilities:
               disabled   (0)
               enabled   (1)"
   ::= {er1646v2VxlBGIMVpVlanEntry 705825280}

er1646v2VxlBGIMVpVlanIpV6IcmpMessagesHopLimitExceeded OBJECT-TYPE
   SYNTAX      INTEGER
               {
               disabled (0),
               enabled (1)
               }
   MAX-ACCESS  read-write
   STATUS      current
   DESCRIPTION
      "Path: vxLanBridgeGroup.editConf.vlan.ipV6.icmpMessages.hopLimitExceeded

       Possibilities:
               disabled   (0)
               enabled   (1)"
   ::= {er1646v2VxlBGIMVpVlanEntry 705827840}

er1646v2VxlBGIMVpVlanIpV6IcmpMessagesFragTimeExceeded OBJECT-TYPE
   SYNTAX      INTEGER
               {
               disabled (0),
               enabled (1)
               }
   MAX-ACCESS  read-write
   STATUS      current
   DESCRIPTION
      "Path: vxLanBridgeGroup.editConf.vlan.ipV6.icmpMessages.fragTimeExceeded

       Possibilities:
               disabled   (0)
               enabled   (1)"
   ::= {er1646v2VxlBGIMVpVlanEntry 705828096}

er1646v2VxlBGIMVpVlanIpV6IcmpMessagesHeaderFieldErr OBJECT-TYPE
   SYNTAX      INTEGER
               {
               disabled (0),
               enabled (1)
               }
   MAX-ACCESS  read-write
   STATUS      current
   DESCRIPTION
      "Path: vxLanBridgeGroup.editConf.vlan.ipV6.icmpMessages.headerFieldErr

       Possibilities:
               disabled   (0)
               enabled   (1)"
   ::= {er1646v2VxlBGIMVpVlanEntry 705830400}

er1646v2VxlBGIMVpVlanIpV6IcmpMessagesOptionUnrecognized OBJECT-TYPE
   SYNTAX      INTEGER
               {
               disabled (0),
               enabled (1)
               }
   MAX-ACCESS  read-write
   STATUS      current
   DESCRIPTION
      "Path: vxLanBridgeGroup.editConf.vlan.ipV6.icmpMessages.optionUnrecognized

       Possibilities:
               disabled   (0)
               enabled   (1)"
   ::= {er1646v2VxlBGIMVpVlanEntry 705830912}

er1646v2VxlBGIMVpVlanIpV6IcmpMessagesRedirect OBJECT-TYPE
   SYNTAX      INTEGER
               {
               disabled (0),
               enabled (1)
               }
   MAX-ACCESS  read-write
   STATUS      current
   DESCRIPTION
      "Path: vxLanBridgeGroup.editConf.vlan.ipV6.icmpMessages.redirect

       Possibilities:
               disabled   (0)
               enabled   (1)"
   ::= {er1646v2VxlBGIMVpVlanEntry 705832960}

er1646v2VxlBGIMVpVlanVlanVid OBJECT-TYPE
   SYNTAX      INTEGER
               {
               prioTagged (4096)
               }
   MAX-ACCESS  read-write
   STATUS      current
   DESCRIPTION
      "Path: vxLanBridgeGroup.editConf.vlan.vlan.vid

       Possibilities:
               prioTagged   (4096)"
   ::= {er1646v2VxlBGIMVpVlanEntry 234946560}

er1646v2VxlBGIMVpVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: vxLanBridgeGroup.editConf.vlan.vlan.tpid

       Possibilities:
               dot1Q   (33024)
               dot1ad   (34984)
               0x9100   (37120)
               0x9200   (37376)
               0x9300   (37632)"
   ::= {er1646v2VxlBGIMVpVlanEntry 241238016}

er1646v2VxlBGIMVpVlanVlanTxCos OBJECT-TYPE
   SYNTAX      INTEGER
               {
               tosCosMap (8),
               queueCosMap (16)
               }
   MAX-ACCESS  read-write
   STATUS      current
   DESCRIPTION
      "Path: vxLanBridgeGroup.editConf.vlan.vlan.txCos

       Possibilities:
               tosCosMap   (8)
               queueCosMap   (16)"
   ::= {er1646v2VxlBGIMVpVlanEntry 235077632}

er1646v2VxlBGIMVpVlanVlanChTos OBJECT-TYPE
   SYNTAX      INTEGER
               {
               disabled (0),
               enabled (1)
               }
   MAX-ACCESS  read-write
   STATUS      current
   DESCRIPTION
      "Path: vxLanBridgeGroup.editConf.vlan.vlan.changeTos

       Possibilities:
               disabled   (0)
               enabled   (1)"
   ::= {er1646v2VxlBGIMVpVlanEntry 235208704}

er1646v2VxlBGIMVpVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235143424}

er1646v2VxlBGIMVpVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235143680}

er1646v2VxlBGIMVpVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235143936}

er1646v2VxlBGIMVpVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235144192}

er1646v2VxlBGIMVpVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235144448}

er1646v2VxlBGIMVpVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235144704}

er1646v2VxlBGIMVpVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235144960}

er1646v2VxlBGIMVpVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vxLanBridgeGroup.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VxlBGIMVpVlanEntry 235145216}

er1646v2VxlBGIMVpVlanVlanQCMapQueue1 OBJECT-TYPE
   SYNTAX      Integer32
   MAX-ACCESS  read-write
   STATUS      current
   DESCRIPTION
      "Path: vxLanBridgeGroup.editConf.vlan.vlan.queueCosMap.queue1"
   ::= {er1646v2VxlBGIMVpVlanEntry 241434880}

er1646v2VxlBGIMVpVlanVlanQCMapQueue2 OBJECT-TYPE
   SYNTAX      Integer32
   MAX-ACCESS  read-write
   STATUS      current
   DESCRIPTION
      "Path: vxLanBridgeGroup.editConf.vlan.vlan.queueCosMap.queue2"
   ::= {er1646v2VxlBGIMVpVlanEntry 241435136}

er1646v2VxlBGIMVpVlanVlanQCMapQueue3 OBJECT-TYPE
   SYNTAX      Integer32
   MAX-ACCESS  read-write
   STATUS      current
   DESCRIPTION
      "Path: vxLanBridgeGroup.editConf.vlan.vlan.queueCosMap.queue3"
   ::= {er1646v2VxlBGIMVpVlanEntry 241435392}

er1646v2VxlBGIMVpVlanVlanQCMapQueue4 OBJECT-TYPE
   SYNTAX      Integer32
   MAX-ACCESS  read-write
   STATUS      current
   DESCRIPTION
      "Path: vxLanBridgeGroup.editConf.vlan.vlan.queueCosMap.queue4"
   ::= {er1646v2VxlBGIMVpVlanEntry 241435648}

er1646v2VxlBGIMVpVlanVlanQCMapQueue5 OBJECT-TYPE
   SYNTAX      Integer32
   MAX-ACCESS  read-write
   STATUS      current
   DESCRIPTION
      "Path: vxLanBridgeGroup.editConf.vlan.vlan.queueCosMap.queue5"
   ::= {er1646v2VxlBGIMVpVlanEntry 241435904}

er1646v2VxlBGIMVpVlanVlanQCMapLowDelayQueue OBJECT-TYPE
   SYNTAX      Integer32
   MAX-ACCESS  read-write
   STATUS      current
   DESCRIPTION
      "Path: vxLanBridgeGroup.editConf.vlan.vlan.queueCosMap.lowDelayQueue"
   ::= {er1646v2VxlBGIMVpVlanEntry 241436160}

er1646v2VxlBGIMVpVlanVlanQCMapLowDelay2Queue OBJECT-TYPE
   SYNTAX      Integer32
   MAX-ACCESS  read-write
   STATUS      current
   DESCRIPTION
      "Path: vxLanBridgeGroup.editConf.vlan.vlan.queueCosMap.lowDelay2Queue"
   ::= {er1646v2VxlBGIMVpVlanEntry 241436416}

er1646v2VxlBGIMVpVlanVlanQCMapSystemQueue OBJECT-TYPE
   SYNTAX      Integer32
   MAX-ACCESS  read-write
   STATUS      current
   DESCRIPTION
      "Path: vxLanBridgeGroup.editConf.vlan.vlan.queueCosMap.systemQueue"
   ::= {er1646v2VxlBGIMVpVlanEntry 241436672}

er1646v2VxlBGIMVpVlanVlanArpTimeOut OBJECT-TYPE
   SYNTAX      TimeTicks
   MAX-ACCESS  read-write
   STATUS      current
   DESCRIPTION
      "Path: vxLanBridgeGroup.editConf.vlan.vlan.arp.timeOut

       Time in centi-second."
   ::= {er1646v2VxlBGIMVpVlanEntry 235277312}

er1646v2VxlBGIMVpVlanVlanArpProxyArp OBJECT-TYPE
   SYNTAX      INTEGER
               {
               disabled (0),
               enabled (1)
               }
   MAX-ACCESS  read-write
   STATUS      current
   DESCRIPTION
      "Path: vxLanBridgeGroup.editConf.vlan.vlan.arp.proxyArp

       Possibilities:
               disabled   (0)
               enabled   (1)"
   ::= {er1646v2VxlBGIMVpVlanEntry 235287040}

er1646v2VxlBGIMVpVlanIpSaddr OBJECT-TYPE
   SYNTAX      SEQUENCE OF Er1646v2VxlBGIMVpVlanIpSaddrEntry
   MAX-ACCESS  not-accessible
   STATUS      current
   DESCRIPTION
      ""
   ::= {er1646v2VxlBGIMVpVlan 51838976}

er1646v2VxlBGIMVpVlanIpSaddrEntry OBJECT-TYPE
   SYNTAX      Er1646v2VxlBGIMVpVlanIpSaddrEntry
   MAX-ACCESS  not-accessible
   STATUS      current
   DESCRIPTION
      ""
   INDEX      { er1646v2VxlBGIMVpVlanIpSaddrGlobalIx,
                er1646v2VxlBGIMVpVlanTableIx,
                er1646v2VxlBGIMVpVlanIpSaddrTableIx }
   ::= {er1646v2VxlBGIMVpVlanIpSaddr 1}

Er1646v2VxlBGIMVpVlanIpSaddrEntry ::=
   SEQUENCE
      {
      er1646v2VxlBGIMVpVlanIpSaddrActions
         VariableLengthTableActions,
      er1646v2VxlBGIMVpVlanIpSaddrGlobalIx
         GlobalIndex,
      er1646v2VxlBGIMVpVlanIpSaddrTableIx
         TableIndex,
      er1646v2VxlBGIMVpVlanIpSaddrAddress
         IpAddress,
      er1646v2VxlBGIMVpVlanIpSaddrNetMask
         IpAddress
      }

er1646v2VxlBGIMVpVlanIpSaddrActions OBJECT-TYPE
   SYNTAX      VariableLengthTableActions
   MAX-ACCESS  read-write
   STATUS      current
   DESCRIPTION
      "By way of this field, some manipulations
       on this table may be performed."
   ::= {er1646v2VxlBGIMVpVlanIpSaddrEntry 2}

er1646v2VxlBGIMVpVlanIpSaddrGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpSaddrEntry 10}

er1646v2VxlBGIMVpVlanIpSaddrTableIx OBJECT-TYPE
   SYNTAX      TableIndex
   MAX-ACCESS  not-accessible
   STATUS      current
   DESCRIPTION
      ""
   ::= {er1646v2VxlBGIMVpVlanIpSaddrEntry 11}

er1646v2VxlBGIMVpVlanIpSaddrAddress OBJECT-TYPE
   SYNTAX      IpAddress
   MAX-ACCESS  read-write
   STATUS      current
   DESCRIPTION
      "Path: vxLanBridgeGroup.editConf.vlan.ip.secondaryIp.address"
   ::= {er1646v2VxlBGIMVpVlanIpSaddrEntry 2030043136}

er1646v2VxlBGIMVpVlanIpSaddrNetMask OBJECT-TYPE
   SYNTAX      IpAddress
   MAX-ACCESS  read-write
   STATUS      current
   DESCRIPTION
      "Path: vxLanBridgeGroup.editConf.vlan.ip.secondaryIp.netMask"
   ::= {er1646v2VxlBGIMVpVlanIpSaddrEntry 2063597568}

er1646v2VxlBGIMVpVlanIpH OBJECT-TYPE
   SYNTAX      SEQUENCE OF Er1646v2VxlBGIMVpVlanIpHEntry
   MAX-ACCESS  not-accessible
   STATUS      current
   DESCRIPTION
      ""
   ::= {er1646v2VxlBGIMVpVlan 51314688}

er1646v2VxlBGIMVpVlanIpHEntry OBJECT-TYPE
   SYNTAX      Er1646v2VxlBGIMVpVlanIpHEntry
   MAX-ACCESS  not-accessible
   STATUS      current
   DESCRIPTION
      ""
   INDEX      { er1646v2VxlBGIMVpVlanIpHGlobalIx,
                er1646v2VxlBGIMVpVlanTableIx,
                er1646v2VxlBGIMVpVlanIpHTableIx }
   ::= {er1646v2VxlBGIMVpVlanIpH 1}

Er1646v2VxlBGIMVpVlanIpHEntry ::=
   SEQUENCE
      {
      er1646v2VxlBGIMVpVlanIpHActions
         VariableLengthTableActions,
      er1646v2VxlBGIMVpVlanIpHGlobalIx
         GlobalIndex,
      er1646v2VxlBGIMVpVlanIpHTableIx
         TableIndex,
      er1646v2VxlBGIMVpVlanIpHAddress
         IpAddress,
      er1646v2VxlBGIMVpVlanIpHDhcpRelayOptionSubscriberId
         DisplayString
      }

er1646v2VxlBGIMVpVlanIpHActions OBJECT-TYPE
   SYNTAX      VariableLengthTableActions
   MAX-ACCESS  read-write
   STATUS      current
   DESCRIPTION
      "By way of this field, some manipulations
       on this table may be performed."
   ::= {er1646v2VxlBGIMVpVlanIpHEntry 2}

er1646v2VxlBGIMVpVlanIpHGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpHEntry 10}

er1646v2VxlBGIMVpVlanIpHTableIx OBJECT-TYPE
   SYNTAX      TableIndex
   MAX-ACCESS  not-accessible
   STATUS      current
   DESCRIPTION
      ""
   ::= {er1646v2VxlBGIMVpVlanIpHEntry 11}

er1646v2VxlBGIMVpVlanIpHAddress OBJECT-TYPE
   SYNTAX      IpAddress
   MAX-ACCESS  read-write
   STATUS      current
   DESCRIPTION
      "Path: vxLanBridgeGroup.editConf.vlan.ip.helpers.address"
   ::= {er1646v2VxlBGIMVpVlanIpHEntry 16777216}

er1646v2VxlBGIMVpVlanIpHDhcpRelayOptionSubscriberId OBJECT-TYPE
   SYNTAX      DisplayString
   MAX-ACCESS  read-write
   STATUS      current
   DESCRIPTION
      "Path: vxLanBridgeGroup.editConf.vlan.ip.helpers.dhcpRelayOption.subscriberId"
   ::= {er1646v2VxlBGIMVpVlanIpHEntry 33947648}

er1646v2VxlBGIMVpVlanIpV6Addresses OBJECT-TYPE
   SYNTAX      SEQUENCE OF Er1646v2VxlBGIMVpVlanIpV6AddressesEntry
   MAX-ACCESS  not-accessible
   STATUS      current
   DESCRIPTION
      ""
   ::= {er1646v2VxlBGIMVpVlan 704839680}

er1646v2VxlBGIMVpVlanIpV6AddressesEntry OBJECT-TYPE
   SYNTAX      Er1646v2VxlBGIMVpVlanIpV6AddressesEntry
   MAX-ACCESS  not-accessible
   STATUS      current
   DESCRIPTION
      ""
   INDEX      { er1646v2VxlBGIMVpVlanIpV6AddressesGlobalIx,
                er1646v2VxlBGIMVpVlanTableIx,
                er1646v2VxlBGIMVpVlanIpV6AddressesTableIx }
   ::= {er1646v2VxlBGIMVpVlanIpV6Addresses 1}

Er1646v2VxlBGIMVpVlanIpV6AddressesEntry ::=
   SEQUENCE
      {
      er1646v2VxlBGIMVpVlanIpV6AddressesActions
         VariableLengthTableActions,
      er1646v2VxlBGIMVpVlanIpV6AddressesGlobalIx
         GlobalIndex,
      er1646v2VxlBGIMVpVlanIpV6AddressesTableIx
         TableIndex,
      er1646v2VxlBGIMVpVlanIpV6AddressesType
         INTEGER,
      er1646v2VxlBGIMVpVlanIpV6AddressesAddress
         Ipv6Address,
      er1646v2VxlBGIMVpVlanIpV6AddressesPrefixLength
         Integer32,
      er1646v2VxlBGIMVpVlanIpV6AddressesGeneralPrefix
         DisplayString,
      er1646v2VxlBGIMVpVlanIpV6AddressesRaSend
         INTEGER,
      er1646v2VxlBGIMVpVlanIpV6AddressesRaOnLinkFlag
         INTEGER,
      er1646v2VxlBGIMVpVlanIpV6AddressesRaAutoFlag
         INTEGER,
      er1646v2VxlBGIMVpVlanIpV6AddressesRaValidLifeTime
         TimeTicks,
      er1646v2VxlBGIMVpVlanIpV6AddressesRaValidLTMode
         INTEGER,
      er1646v2VxlBGIMVpVlanIpV6AddressesRaPrefLifeTime
         TimeTicks,
      er1646v2VxlBGIMVpVlanIpV6AddressesRaPrefLTMode
         INTEGER
      }

er1646v2VxlBGIMVpVlanIpV6AddressesActions OBJECT-TYPE
   SYNTAX      VariableLengthTableActions
   MAX-ACCESS  read-write
   STATUS      current
   DESCRIPTION
      "By way of this field, some manipulations
       on this table may be performed."
   ::= {er1646v2VxlBGIMVpVlanIpV6AddressesEntry 2}

er1646v2VxlBGIMVpVlanIpV6AddressesGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6AddressesEntry 10}

er1646v2VxlBGIMVpVlanIpV6AddressesTableIx OBJECT-TYPE
   SYNTAX      TableIndex
   MAX-ACCESS  not-accessible
   STATUS      current
   DESCRIPTION
      ""
   ::= {er1646v2VxlBGIMVpVlanIpV6AddressesEntry 11}

er1646v2VxlBGIMVpVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vxLanBridgeGroup.editConf.vlan.ipV6.addresses.type

       Possibilities:
               unicast   (0)
               eui64   (1)
               anycast   (2)
               linkLocal   (3)
               generalPrefix   (4)"
   ::= {er1646v2VxlBGIMVpVlanIpV6AddressesEntry 50331648}

er1646v2VxlBGIMVpVlanIpV6AddressesAddress OBJECT-TYPE
   SYNTAX      Ipv6Address
   MAX-ACCESS  read-write
   STATUS      current
   DESCRIPTION
      "Path: vxLanBridgeGroup.editConf.vlan.ipV6.addresses.address

       ipv6 address"
   ::= {er1646v2VxlBGIMVpVlanIpV6AddressesEntry 16777216}

er1646v2VxlBGIMVpVlanIpV6AddressesPrefixLength OBJECT-TYPE
   SYNTAX      Integer32
   MAX-ACCESS  read-write
   STATUS      current
   DESCRIPTION
      "Path: vxLanBridgeGroup.editConf.vlan.ipV6.addresses.prefixLength"
   ::= {er1646v2VxlBGIMVpVlanIpV6AddressesEntry 33554432}

er1646v2VxlBGIMVpVlanIpV6AddressesGeneralPrefix OBJECT-TYPE
   SYNTAX      DisplayString
   MAX-ACCESS  read-write
   STATUS      current
   DESCRIPTION
      "Path: vxLanBridgeGroup.editConf.vlan.ipV6.addresses.generalPrefix"
   ::= {er1646v2VxlBGIMVpVlanIpV6AddressesEntry 83886080}

er1646v2VxlBGIMVpVlanIpV6AddressesRaSend OBJECT-TYPE
   SYNTAX      INTEGER
               {
               disabled (0),
               enabled (1)
               }
   MAX-ACCESS  read-write
   STATUS      current
   DESCRIPTION
      "Path: vxLanBridgeGroup.editConf.vlan.ipV6.addresses.ra.send

       Possibilities:
               disabled   (0)
               enabled   (1)"
   ::= {er1646v2VxlBGIMVpVlanIpV6AddressesEntry 67174400}

er1646v2VxlBGIMVpVlanIpV6AddressesRaOnLinkFlag OBJECT-TYPE
   SYNTAX      INTEGER
               {
               disabled (0),
               enabled (1)
               }
   MAX-ACCESS  read-write
   STATUS      current
   DESCRIPTION
      "Path: vxLanBridgeGroup.editConf.vlan.ipV6.addresses.ra.onLinkFlag

       Possibilities:
               disabled   (0)
               enabled   (1)"
   ::= {er1646v2VxlBGIMVpVlanIpV6AddressesEntry 67371008}

er1646v2VxlBGIMVpVlanIpV6AddressesRaAutoFlag OBJECT-TYPE
   SYNTAX      INTEGER
               {
               disabled (0),
               enabled (1)
               }
   MAX-ACCESS  read-write
   STATUS      current
   DESCRIPTION
      "Path: vxLanBridgeGroup.editConf.vlan.ipV6.addresses.ra.autonomousFlag

       Possibilities:
               disabled   (0)
               enabled   (1)"
   ::= {er1646v2VxlBGIMVpVlanIpV6AddressesEntry 67567616}

er1646v2VxlBGIMVpVlanIpV6AddressesRaValidLifeTime OBJECT-TYPE
   SYNTAX      TimeTicks
   MAX-ACCESS  read-write
   STATUS      current
   DESCRIPTION
      "Path: vxLanBridgeGroup.editConf.vlan.ipV6.addresses.ra.validLifeTime

       Time in centi-second."
   ::= {er1646v2VxlBGIMVpVlanIpV6AddressesEntry 67239936}

er1646v2VxlBGIMVpVlanIpV6AddressesRaValidLTMode OBJECT-TYPE
   SYNTAX      INTEGER
               {
               fixed (0),
               infinite (2)
               }
   MAX-ACCESS  read-write
   STATUS      current
   DESCRIPTION
      "Path: vxLanBridgeGroup.editConf.vlan.ipV6.addresses.ra.validLifeTimeMode

       Possibilities:
               fixed   (0)
               infinite   (2)"
   ::= {er1646v2VxlBGIMVpVlanIpV6AddressesEntry 67305472}

er1646v2VxlBGIMVpVlanIpV6AddressesRaPrefLifeTime OBJECT-TYPE
   SYNTAX      TimeTicks
   MAX-ACCESS  read-write
   STATUS      current
   DESCRIPTION
      "Path: vxLanBridgeGroup.editConf.vlan.ipV6.addresses.ra.prefLifeTime

       Time in centi-second."
   ::= {er1646v2VxlBGIMVpVlanIpV6AddressesEntry 67436544}

er1646v2VxlBGIMVpVlanIpV6AddressesRaPrefLTMode OBJECT-TYPE
   SYNTAX      INTEGER
               {
               fixed (0),
               infinite (2)
               }
   MAX-ACCESS  read-write
   STATUS      current
   DESCRIPTION
      "Path: vxLanBridgeGroup.editConf.vlan.ipV6.addresses.ra.prefLifeTimeMode

       Possibilities:
               fixed   (0)
               infinite   (2)"
   ::= {er1646v2VxlBGIMVpVlanIpV6AddressesEntry 67502080}

er1646v2VxlBGIMVpVlanIpV6RaDnsOptionsRdnssServers OBJECT-TYPE
   SYNTAX      SEQUENCE OF Er1646v2VxlBGIMVpVlanIpV6RaDnsOptionsRdnssServersEntry
   MAX-ACCESS  not-accessible
   STATUS      current
   DESCRIPTION
      ""
   ::= {er1646v2VxlBGIMVpVlan 705039144}

er1646v2VxlBGIMVpVlanIpV6RaDnsOptionsRdnssServersEntry OBJECT-TYPE
   SYNTAX      Er1646v2VxlBGIMVpVlanIpV6RaDnsOptionsRdnssServersEntry
   MAX-ACCESS  not-accessible
   STATUS      current
   DESCRIPTION
      ""
   INDEX      { er1646v2VxlBGIMVpVlanIpV6RaDnsOptionsRdnssServersGlobalIx,
                er1646v2VxlBGIMVpVlanTableIx,
                er1646v2VxlBGIMVpVlanIpV6RaDnsOptionsRdnssServersTableIx }
   ::= {er1646v2VxlBGIMVpVlanIpV6RaDnsOptionsRdnssServers 1}

Er1646v2VxlBGIMVpVlanIpV6RaDnsOptionsRdnssServersEntry ::=
   SEQUENCE
      {
      er1646v2VxlBGIMVpVlanIpV6RaDnsOptionsRdnssServersActions
         VariableLengthTableActions,
      er1646v2VxlBGIMVpVlanIpV6RaDnsOptionsRdnssServersGlobalIx
         GlobalIndex,
      er1646v2VxlBGIMVpVlanIpV6RaDnsOptionsRdnssServersTableIx
         TableIndex,
      er1646v2VxlBGIMVpVlanIpV6RaDnsOptionsRdnssServersAddress
         Ipv6Address
      }

er1646v2VxlBGIMVpVlanIpV6RaDnsOptionsRdnssServersActions OBJECT-TYPE
   SYNTAX      VariableLengthTableActions
   MAX-ACCESS  read-write
   STATUS      current
   DESCRIPTION
      "By way of this field, some manipulations
       on this table may be performed."
   ::= {er1646v2VxlBGIMVpVlanIpV6RaDnsOptionsRdnssServersEntry 2}

er1646v2VxlBGIMVpVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6RaDnsOptionsRdnssServersEntry 10}

er1646v2VxlBGIMVpVlanIpV6RaDnsOptionsRdnssServersTableIx OBJECT-TYPE
   SYNTAX      TableIndex
   MAX-ACCESS  not-accessible
   STATUS      current
   DESCRIPTION
      ""
   ::= {er1646v2VxlBGIMVpVlanIpV6RaDnsOptionsRdnssServersEntry 11}

er1646v2VxlBGIMVpVlanIpV6RaDnsOptionsRdnssServersAddress OBJECT-TYPE
   SYNTAX      Ipv6Address
   MAX-ACCESS  read-write
   STATUS      current
   DESCRIPTION
      "Path: vxLanBridgeGroup.editConf.vlan.ipV6.ra.dnsOptions.rdnss.servers.address

       ipv6 address"
   ::= {er1646v2VxlBGIMVpVlanIpV6RaDnsOptionsRdnssServersEntry 16777216}

er1646v2VxlBGIMVpVlanIpV6RaDnsOptionsDnsslDomains OBJECT-TYPE
   SYNTAX      SEQUENCE OF Er1646v2VxlBGIMVpVlanIpV6RaDnsOptionsDnsslDomainsEntry
   MAX-ACCESS  not-accessible
   STATUS      current
   DESCRIPTION
      ""
   ::= {er1646v2VxlBGIMVpVlan 705039176}

er1646v2VxlBGIMVpVlanIpV6RaDnsOptionsDnsslDomainsEntry OBJECT-TYPE
   SYNTAX      Er1646v2VxlBGIMVpVlanIpV6RaDnsOptionsDnsslDomainsEntry
   MAX-ACCESS  not-accessible
   STATUS      current
   DESCRIPTION
      ""
   INDEX      { er1646v2VxlBGIMVpVlanIpV6RaDnsOptionsDnsslDomainsGlobalIx,
                er1646v2VxlBGIMVpVlanTableIx,
                er1646v2VxlBGIMVpVlanIpV6RaDnsOptionsDnsslDomainsTableIx }
   ::= {er1646v2VxlBGIMVpVlanIpV6RaDnsOptionsDnsslDomains 1}

Er1646v2VxlBGIMVpVlanIpV6RaDnsOptionsDnsslDomainsEntry ::=
   SEQUENCE
      {
      er1646v2VxlBGIMVpVlanIpV6RaDnsOptionsDnsslDomainsActions
         VariableLengthTableActions,
      er1646v2VxlBGIMVpVlanIpV6RaDnsOptionsDnsslDomainsGlobalIx
         GlobalIndex,
      er1646v2VxlBGIMVpVlanIpV6RaDnsOptionsDnsslDomainsTableIx
         TableIndex,
      er1646v2VxlBGIMVpVlanIpV6RaDnsOptionsDnsslDomainsName
         DisplayString
      }

er1646v2VxlBGIMVpVlanIpV6RaDnsOptionsDnsslDomainsActions OBJECT-TYPE
   SYNTAX      VariableLengthTableActions
   MAX-ACCESS  read-write
   STATUS      current
   DESCRIPTION
      "By way of this field, some manipulations
       on this table may be performed."
   ::= {er1646v2VxlBGIMVpVlanIpV6RaDnsOptionsDnsslDomainsEntry 2}

er1646v2VxlBGIMVpVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6RaDnsOptionsDnsslDomainsEntry 10}

er1646v2VxlBGIMVpVlanIpV6RaDnsOptionsDnsslDomainsTableIx OBJECT-TYPE
   SYNTAX      TableIndex
   MAX-ACCESS  not-accessible
   STATUS      current
   DESCRIPTION
      ""
   ::= {er1646v2VxlBGIMVpVlanIpV6RaDnsOptionsDnsslDomainsEntry 11}

er1646v2VxlBGIMVpVlanIpV6RaDnsOptionsDnsslDomainsName OBJECT-TYPE
   SYNTAX      DisplayString
   MAX-ACCESS  read-write
   STATUS      current
   DESCRIPTION
      "Path: vxLanBridgeGroup.editConf.vlan.ipV6.ra.dnsOptions.dnssl.domains.name"
   ::= {er1646v2VxlBGIMVpVlanIpV6RaDnsOptionsDnsslDomainsEntry 16777216}

er1646v2VxlBGIMVpVlanIpV6DhcpClientUserClassOpt OBJECT-TYPE
   SYNTAX      SEQUENCE OF Er1646v2VxlBGIMVpVlanIpV6DhcpClientUserClassOptEntry
   MAX-ACCESS  not-accessible
   STATUS      current
   DESCRIPTION
      ""
   ::= {er1646v2VxlBGIMVpVlan 705312768}

er1646v2VxlBGIMVpVlanIpV6DhcpClientUserClassOptEntry OBJECT-TYPE
   SYNTAX      Er1646v2VxlBGIMVpVlanIpV6DhcpClientUserClassOptEntry
   MAX-ACCESS  not-accessible
   STATUS      current
   DESCRIPTION
      ""
   INDEX      { er1646v2VxlBGIMVpVlanIpV6DhcpClientUserClassOptGlobalIx,
                er1646v2VxlBGIMVpVlanTableIx,
                er1646v2VxlBGIMVpVlanIpV6DhcpClientUserClassOptTableIx }
   ::= {er1646v2VxlBGIMVpVlanIpV6DhcpClientUserClassOpt 1}

Er1646v2VxlBGIMVpVlanIpV6DhcpClientUserClassOptEntry ::=
   SEQUENCE
      {
      er1646v2VxlBGIMVpVlanIpV6DhcpClientUserClassOptActions
         VariableLengthTableActions,
      er1646v2VxlBGIMVpVlanIpV6DhcpClientUserClassOptGlobalIx
         GlobalIndex,
      er1646v2VxlBGIMVpVlanIpV6DhcpClientUserClassOptTableIx
         TableIndex,
      er1646v2VxlBGIMVpVlanIpV6DhcpClientUserClassOptValueAscii
         DisplayString,
      er1646v2VxlBGIMVpVlanIpV6DhcpClientUserClassOptValueDecimal
         Integer32,
      er1646v2VxlBGIMVpVlanIpV6DhcpClientUserClassOptValueHexData
         OCTET STRING
      }

er1646v2VxlBGIMVpVlanIpV6DhcpClientUserClassOptActions OBJECT-TYPE
   SYNTAX      VariableLengthTableActions
   MAX-ACCESS  read-write
   STATUS      current
   DESCRIPTION
      "By way of this field, some manipulations
       on this table may be performed."
   ::= {er1646v2VxlBGIMVpVlanIpV6DhcpClientUserClassOptEntry 2}

er1646v2VxlBGIMVpVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6DhcpClientUserClassOptEntry 10}

er1646v2VxlBGIMVpVlanIpV6DhcpClientUserClassOptTableIx OBJECT-TYPE
   SYNTAX      TableIndex
   MAX-ACCESS  not-accessible
   STATUS      current
   DESCRIPTION
      ""
   ::= {er1646v2VxlBGIMVpVlanIpV6DhcpClientUserClassOptEntry 11}

er1646v2VxlBGIMVpVlanIpV6DhcpClientUserClassOptValueAscii OBJECT-TYPE
   SYNTAX      DisplayString
   MAX-ACCESS  read-write
   STATUS      current
   DESCRIPTION
      "Path: vxLanBridgeGroup.editConf.vlan.ipV6.dhcp.client.userClassOpt.value.ascii"
   ::= {er1646v2VxlBGIMVpVlanIpV6DhcpClientUserClassOptEntry 16842752}

er1646v2VxlBGIMVpVlanIpV6DhcpClientUserClassOptValueDecimal OBJECT-TYPE
   SYNTAX      Integer32
   MAX-ACCESS  read-write
   STATUS      current
   DESCRIPTION
      "Path: vxLanBridgeGroup.editConf.vlan.ipV6.dhcp.client.userClassOpt.value.decimal"
   ::= {er1646v2VxlBGIMVpVlanIpV6DhcpClientUserClassOptEntry 16908288}

er1646v2VxlBGIMVpVlanIpV6DhcpClientUserClassOptValueHexData OBJECT-TYPE
   SYNTAX      OCTET STRING
   MAX-ACCESS  read-write
   STATUS      current
   DESCRIPTION
      "Path: vxLanBridgeGroup.editConf.vlan.ipV6.dhcp.client.userClassOpt.value.hexData"
   ::= {er1646v2VxlBGIMVpVlanIpV6DhcpClientUserClassOptEntry 16973824}

er1646v2VxlBGIMVpVlanIpV6DhcpClientVendorCl OBJECT-TYPE
   SYNTAX      SEQUENCE OF Er1646v2VxlBGIMVpVlanIpV6DhcpClientVendorClEntry
   MAX-ACCESS  not-accessible
   STATUS      current
   DESCRIPTION
      ""
   ::= {er1646v2VxlBGIMVpVlan 705313792}

er1646v2VxlBGIMVpVlanIpV6DhcpClientVendorClEntry OBJECT-TYPE
   SYNTAX      Er1646v2VxlBGIMVpVlanIpV6DhcpClientVendorClEntry
   MAX-ACCESS  not-accessible
   STATUS      current
   DESCRIPTION
      ""
   INDEX      { er1646v2VxlBGIMVpVlanIpV6DhcpClientVendorClGlobalIx,
                er1646v2VxlBGIMVpVlanTableIx,
                er1646v2VxlBGIMVpVlanIpV6DhcpClientVendorClTableIx }
   ::= {er1646v2VxlBGIMVpVlanIpV6DhcpClientVendorCl 1}

Er1646v2VxlBGIMVpVlanIpV6DhcpClientVendorClEntry ::=
   SEQUENCE
      {
      er1646v2VxlBGIMVpVlanIpV6DhcpClientVendorClActions
         VariableLengthTableActions,
      er1646v2VxlBGIMVpVlanIpV6DhcpClientVendorClGlobalIx
         GlobalIndex,
      er1646v2VxlBGIMVpVlanIpV6DhcpClientVendorClTableIx
         TableIndex,
      er1646v2VxlBGIMVpVlanIpV6DhcpClientVendorClValueAscii
         DisplayString,
      er1646v2VxlBGIMVpVlanIpV6DhcpClientVendorClValueDecimal
         Integer32,
      er1646v2VxlBGIMVpVlanIpV6DhcpClientVendorClValueHexData
         OCTET STRING
      }

er1646v2VxlBGIMVpVlanIpV6DhcpClientVendorClActions OBJECT-TYPE
   SYNTAX      VariableLengthTableActions
   MAX-ACCESS  read-write
   STATUS      current
   DESCRIPTION
      "By way of this field, some manipulations
       on this table may be performed."
   ::= {er1646v2VxlBGIMVpVlanIpV6DhcpClientVendorClEntry 2}

er1646v2VxlBGIMVpVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6DhcpClientVendorClEntry 10}

er1646v2VxlBGIMVpVlanIpV6DhcpClientVendorClTableIx OBJECT-TYPE
   SYNTAX      TableIndex
   MAX-ACCESS  not-accessible
   STATUS      current
   DESCRIPTION
      ""
   ::= {er1646v2VxlBGIMVpVlanIpV6DhcpClientVendorClEntry 11}

er1646v2VxlBGIMVpVlanIpV6DhcpClientVendorClValueAscii OBJECT-TYPE
   SYNTAX      DisplayString
   MAX-ACCESS  read-write
   STATUS      current
   DESCRIPTION
      "Path: vxLanBridgeGroup.editConf.vlan.ipV6.dhcp.client.vendorClassOpt.value.ascii"
   ::= {er1646v2VxlBGIMVpVlanIpV6DhcpClientVendorClEntry 16842752}

er1646v2VxlBGIMVpVlanIpV6DhcpClientVendorClValueDecimal OBJECT-TYPE
   SYNTAX      Integer32
   MAX-ACCESS  read-write
   STATUS      current
   DESCRIPTION
      "Path: vxLanBridgeGroup.editConf.vlan.ipV6.dhcp.client.vendorClassOpt.value.decimal"
   ::= {er1646v2VxlBGIMVpVlanIpV6DhcpClientVendorClEntry 16908288}

er1646v2VxlBGIMVpVlanIpV6DhcpClientVendorClValueHexData OBJECT-TYPE
   SYNTAX      OCTET STRING
   MAX-ACCESS  read-write
   STATUS      current
   DESCRIPTION
      "Path: vxLanBridgeGroup.editConf.vlan.ipV6.dhcp.client.vendorClassOpt.value.hexData"
   ::= {er1646v2VxlBGIMVpVlanIpV6DhcpClientVendorClEntry 16973824}

er1646v2VxlBGIMVpVlanIpV6DhcpRelayDestinations OBJECT-TYPE
   SYNTAX      SEQUENCE OF Er1646v2VxlBGIMVpVlanIpV6DhcpRelayDestinationsEntry
   MAX-ACCESS  not-accessible
   STATUS      current
   DESCRIPTION
      ""
   ::= {er1646v2VxlBGIMVpVlan 705323072}

er1646v2VxlBGIMVpVlanIpV6DhcpRelayDestinationsEntry OBJECT-TYPE
   SYNTAX      Er1646v2VxlBGIMVpVlanIpV6DhcpRelayDestinationsEntry
   MAX-ACCESS  not-accessible
   STATUS      current
   DESCRIPTION
      ""
   INDEX      { er1646v2VxlBGIMVpVlanIpV6DhcpRelayDestinationsGlobalIx,
                er1646v2VxlBGIMVpVlanTableIx,
                er1646v2VxlBGIMVpVlanIpV6DhcpRelayDestinationsTableIx }
   ::= {er1646v2VxlBGIMVpVlanIpV6DhcpRelayDestinations 1}

Er1646v2VxlBGIMVpVlanIpV6DhcpRelayDestinationsEntry ::=
   SEQUENCE
      {
      er1646v2VxlBGIMVpVlanIpV6DhcpRelayDestinationsActions
         VariableLengthTableActions,
      er1646v2VxlBGIMVpVlanIpV6DhcpRelayDestinationsGlobalIx
         GlobalIndex,
      er1646v2VxlBGIMVpVlanIpV6DhcpRelayDestinationsTableIx
         TableIndex,
      er1646v2VxlBGIMVpVlanIpV6DhcpRelayDestinationsAddress
         Ipv6Address,
      er1646v2VxlBGIMVpVlanIpV6DhcpRelayDestinationsInterface
         DisplayString
      }

er1646v2VxlBGIMVpVlanIpV6DhcpRelayDestinationsActions OBJECT-TYPE
   SYNTAX      VariableLengthTableActions
   MAX-ACCESS  read-write
   STATUS      current
   DESCRIPTION
      "By way of this field, some manipulations
       on this table may be performed."
   ::= {er1646v2VxlBGIMVpVlanIpV6DhcpRelayDestinationsEntry 2}

er1646v2VxlBGIMVpVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanIpV6DhcpRelayDestinationsEntry 10}

er1646v2VxlBGIMVpVlanIpV6DhcpRelayDestinationsTableIx OBJECT-TYPE
   SYNTAX      TableIndex
   MAX-ACCESS  not-accessible
   STATUS      current
   DESCRIPTION
      ""
   ::= {er1646v2VxlBGIMVpVlanIpV6DhcpRelayDestinationsEntry 11}

er1646v2VxlBGIMVpVlanIpV6DhcpRelayDestinationsAddress OBJECT-TYPE
   SYNTAX      Ipv6Address
   MAX-ACCESS  read-write
   STATUS      current
   DESCRIPTION
      "Path: vxLanBridgeGroup.editConf.vlan.ipV6.dhcp.relay.destinations.address

       ipv6 address"
   ::= {er1646v2VxlBGIMVpVlanIpV6DhcpRelayDestinationsEntry 16777216}

er1646v2VxlBGIMVpVlanIpV6DhcpRelayDestinationsInterface OBJECT-TYPE
   SYNTAX      DisplayString
   MAX-ACCESS  read-write
   STATUS      current
   DESCRIPTION
      "Path: vxLanBridgeGroup.editConf.vlan.ipV6.dhcp.relay.destinations.interface"
   ::= {er1646v2VxlBGIMVpVlanIpV6DhcpRelayDestinationsEntry 33554432}

er1646v2VxlBGIMVpVlanVlanTCMap OBJECT-TYPE
   SYNTAX      SEQUENCE OF Er1646v2VxlBGIMVpVlanVlanTCMapEntry
   MAX-ACCESS  not-accessible
   STATUS      current
   DESCRIPTION
      ""
   ::= {er1646v2VxlBGIMVpVlan 241369088}

er1646v2VxlBGIMVpVlanVlanTCMapEntry OBJECT-TYPE
   SYNTAX      Er1646v2VxlBGIMVpVlanVlanTCMapEntry
   MAX-ACCESS  not-accessible
   STATUS      current
   DESCRIPTION
      ""
   INDEX      { er1646v2VxlBGIMVpVlanVlanTCMapGlobalIx,
                er1646v2VxlBGIMVpVlanTableIx,
                er1646v2VxlBGIMVpVlanVlanTCMapTableIx }
   ::= {er1646v2VxlBGIMVpVlanVlanTCMap 1}

Er1646v2VxlBGIMVpVlanVlanTCMapEntry ::=
   SEQUENCE
      {
      er1646v2VxlBGIMVpVlanVlanTCMapActions
         VariableLengthTableActions,
      er1646v2VxlBGIMVpVlanVlanTCMapGlobalIx
         GlobalIndex,
      er1646v2VxlBGIMVpVlanVlanTCMapTableIx
         TableIndex,
      er1646v2VxlBGIMVpVlanVlanTCMapStartTos
         INTEGER,
      er1646v2VxlBGIMVpVlanVlanTCMapEndTos
         INTEGER,
      er1646v2VxlBGIMVpVlanVlanTCMapCos
         INTEGER
      }

er1646v2VxlBGIMVpVlanVlanTCMapActions OBJECT-TYPE
   SYNTAX      VariableLengthTableActions
   MAX-ACCESS  read-write
   STATUS      current
   DESCRIPTION
      "By way of this field, some manipulations
       on this table may be performed."
   ::= {er1646v2VxlBGIMVpVlanVlanTCMapEntry 2}

er1646v2VxlBGIMVpVlanVlanTCMapGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanVlanTCMapEntry 10}

er1646v2VxlBGIMVpVlanVlanTCMapTableIx OBJECT-TYPE
   SYNTAX      TableIndex
   MAX-ACCESS  not-accessible
   STATUS      current
   DESCRIPTION
      ""
   ::= {er1646v2VxlBGIMVpVlanVlanTCMapEntry 11}

er1646v2VxlBGIMVpVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: vxLanBridgeGroup.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2VxlBGIMVpVlanVlanTCMapEntry 16777216}

er1646v2VxlBGIMVpVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: vxLanBridgeGroup.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2VxlBGIMVpVlanVlanTCMapEntry 33554432}

er1646v2VxlBGIMVpVlanVlanTCMapCos OBJECT-TYPE
   SYNTAX      INTEGER
               {
               queueCosMap (8)
               }
   MAX-ACCESS  read-write
   STATUS      current
   DESCRIPTION
      "Path: vxLanBridgeGroup.editConf.vlan.vlan.tosCosMap.cos

       Possibilities:
               queueCosMap   (8)"
   ::= {er1646v2VxlBGIMVpVlanVlanTCMapEntry 50331648}

er1646v2VxlBGIMVpVlanVlanArpStaticArp OBJECT-TYPE
   SYNTAX      SEQUENCE OF Er1646v2VxlBGIMVpVlanVlanArpStaticArpEntry
   MAX-ACCESS  not-accessible
   STATUS      current
   DESCRIPTION
      ""
   ::= {er1646v2VxlBGIMVpVlan 235275008}

er1646v2VxlBGIMVpVlanVlanArpStaticArpEntry OBJECT-TYPE
   SYNTAX      Er1646v2VxlBGIMVpVlanVlanArpStaticArpEntry
   MAX-ACCESS  not-accessible
   STATUS      current
   DESCRIPTION
      ""
   INDEX      { er1646v2VxlBGIMVpVlanVlanArpStaticArpGlobalIx,
                er1646v2VxlBGIMVpVlanTableIx,
                er1646v2VxlBGIMVpVlanVlanArpStaticArpTableIx }
   ::= {er1646v2VxlBGIMVpVlanVlanArpStaticArp 1}

Er1646v2VxlBGIMVpVlanVlanArpStaticArpEntry ::=
   SEQUENCE
      {
      er1646v2VxlBGIMVpVlanVlanArpStaticArpActions
         VariableLengthTableActions,
      er1646v2VxlBGIMVpVlanVlanArpStaticArpGlobalIx
         GlobalIndex,
      er1646v2VxlBGIMVpVlanVlanArpStaticArpTableIx
         TableIndex,
      er1646v2VxlBGIMVpVlanVlanArpStaticArpMacAddress
         OCTET STRING,
      er1646v2VxlBGIMVpVlanVlanArpStaticArpIpAddress
         IpAddress
      }

er1646v2VxlBGIMVpVlanVlanArpStaticArpActions OBJECT-TYPE
   SYNTAX      VariableLengthTableActions
   MAX-ACCESS  read-write
   STATUS      current
   DESCRIPTION
      "By way of this field, some manipulations
       on this table may be performed."
   ::= {er1646v2VxlBGIMVpVlanVlanArpStaticArpEntry 2}

er1646v2VxlBGIMVpVlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2VxlBGIMVpVlanVlanArpStaticArpEntry 10}

er1646v2VxlBGIMVpVlanVlanArpStaticArpTableIx OBJECT-TYPE
   SYNTAX      TableIndex
   MAX-ACCESS  not-accessible
   STATUS      current
   DESCRIPTION
      ""
   ::= {er1646v2VxlBGIMVpVlanVlanArpStaticArpEntry 11}

er1646v2VxlBGIMVpVlanVlanArpStaticArpMacAddress OBJECT-TYPE
   SYNTAX      OCTET STRING
   MAX-ACCESS  read-write
   STATUS      current
   DESCRIPTION
      "Path: vxLanBridgeGroup.editConf.vlan.vlan.arp.staticArp.macAddress

       MAC address."
   ::= {er1646v2VxlBGIMVpVlanVlanArpStaticArpEntry 16777216}

er1646v2VxlBGIMVpVlanVlanArpStaticArpIpAddress OBJECT-TYPE
   SYNTAX      IpAddress
   MAX-ACCESS  read-write
   STATUS      current
   DESCRIPTION
      "Path: vxLanBridgeGroup.editConf.vlan.vlan.arp.staticArp.ipAddress"
   ::= {er1646v2VxlBGIMVpVlanVlanArpStaticArpEntry 33554432}


er1646v2VxlBGIMVpPppOE OBJECT IDENTIFIER ::= {er1646v2VxlBGIMVp 80}

er1646v2VxlBGIMVpPppOESSCTable OBJECT-TYPE
   SYNTAX      SEQUENCE OF Er1646v2VxlBGIMVpPppOEEntry
   MAX-ACCESS  not-accessible
   STATUS      current
   DESCRIPTION
      ""
   ::= {er1646v2VxlBGIMVpPppOE 1}

er1646v2VxlBGIMVpPppOEEntry OBJECT-TYPE
   SYNTAX      Er1646v2VxlBGIMVpPppOEEntry
   MAX-ACCESS  not-accessible
   STATUS      current
   DESCRIPTION
      ""
   INDEX      { er1646v2VxlBGIMVpPppOEGlobalIx,
                er1646v2VxlBGIMVpPppOETableIx }
   ::= {er1646v2VxlBGIMVpPppOESSCTable 1}

Er1646v2VxlBGIMVpPppOEEntry ::=
   SEQUENCE
      {
      er1646v2VxlBGIMVpPppOEActions
         VariableLengthTableActions,
      er1646v2VxlBGIMVpPppOEGlobalIx
         GlobalIndex,
      er1646v2VxlBGIMVpPppOETableIx
         TableIndex,
      er1646v2VxlBGIMVpPppOEName
         DisplayString,
      er1646v2VxlBGIMVpPppOERemark
         DisplayString,
      er1646v2VxlBGIMVpPppOEAdminStatus
         INTEGER,
      er1646v2VxlBGIMVpPppOEMode
         INTEGER,
      er1646v2VxlBGIMVpPppOEIpVrfRouter
         DisplayString,
      er1646v2VxlBGIMVpPppOEIpAdr
         IpAddress,
      er1646v2VxlBGIMVpPppOEIpNetm
         IpAddress,
      er1646v2VxlBGIMVpPppOEIpSNetName
         INTEGER,
      er1646v2VxlBGIMVpPppOEIpSNetCust
         DisplayString,
      er1646v2VxlBGIMVpPppOEIpRem
         IpAddress,
      er1646v2VxlBGIMVpPppOEIpUnnumbered
         DisplayString,
      er1646v2VxlBGIMVpPppOEIpGwPref
         Integer32,
      er1646v2VxlBGIMVpPppOEIpRsn
         INTEGER,
      er1646v2VxlBGIMVpPppOEIpMtu
         Integer32,
      er1646v2VxlBGIMVpPppOEIpMssAdjust
         INTEGER,
      er1646v2VxlBGIMVpPppOEIpRipMetric
         Integer32,
      er1646v2VxlBGIMVpPppOEIpRipMetricOut
         Integer32,
      er1646v2VxlBGIMVpPppOEIpRipMode
         INTEGER,
      er1646v2VxlBGIMVpPppOEIpRipTxVer
         INTEGER,
      er1646v2VxlBGIMVpPppOEIpRipRxVer
         INTEGER,
      er1646v2VxlBGIMVpPppOEIpRipSplitH
         INTEGER,
      er1646v2VxlBGIMVpPppOEIpRipAuth
         INTEGER,
      er1646v2VxlBGIMVpPppOEIpRipFilter
         DisplayString,
      er1646v2VxlBGIMVpPppOEIpRipFilterIn
         DisplayString,
      er1646v2VxlBGIMVpPppOEIpRipClearNextHop
         INTEGER,
      er1646v2VxlBGIMVpPppOEIpAccPol
         DisplayString,
      er1646v2VxlBGIMVpPppOEIpAB
         DisplayString,
      er1646v2VxlBGIMVpPppOEIpMA
         INTEGER,
      er1646v2VxlBGIMVpPppOEIpMF
         Integer32,
      er1646v2VxlBGIMVpPppOEIpDB
         INTEGER,
      er1646v2VxlBGIMVpPppOEIpIR
         INTEGER,
      er1646v2VxlBGIMVpPppOEIpIgmp
         INTEGER,
      er1646v2VxlBGIMVpPppOEIpNN
         DisplayString,
      er1646v2VxlBGIMVpPppOEIpPimMode
         INTEGER,
      er1646v2VxlBGIMVpPppOEIpPimDrPriority
         Counter32,
      er1646v2VxlBGIMVpPppOEIpPimHelloTime
         TimeTicks,
      er1646v2VxlBGIMVpPppOEIpPimPropagationDelay
         TimeTicks,
      er1646v2VxlBGIMVpPppOEIpPimOverrideInterval
         TimeTicks,
      er1646v2VxlBGIMVpPppOEIpPimBsrBorder
         INTEGER,
      er1646v2VxlBGIMVpPppOEIpPimTtlThreshold
         Integer32,
      er1646v2VxlBGIMVpPppOEIpIMNetworkUnreachable
         INTEGER,
      er1646v2VxlBGIMVpPppOEIpIMHostUnreachable
         INTEGER,
      er1646v2VxlBGIMVpPppOEIpIMProtocolUnreachable
         INTEGER,
      er1646v2VxlBGIMVpPppOEIpIMPortUnreachable
         INTEGER,
      er1646v2VxlBGIMVpPppOEIpIMMtuExceeded
         INTEGER,
      er1646v2VxlBGIMVpPppOEIpIMAdminProhibited
         INTEGER,
      er1646v2VxlBGIMVpPppOEIpIMTtlExceeded
         INTEGER,
      er1646v2VxlBGIMVpPppOEIpIMRedirect
         INTEGER,
      er1646v2VxlBGIMVpPppOEIpV6VrfRouter
         DisplayString,
      er1646v2VxlBGIMVpPppOEIpV6AddrAutoConfigNrDupAddrDetects
         Integer32,
      er1646v2VxlBGIMVpPppOEIpV6AddrAutoConfigAcceptRa
         INTEGER,
      er1646v2VxlBGIMVpPppOEIpV6AddrAutoConfigAcceptRaRdnss
         INTEGER,
      er1646v2VxlBGIMVpPppOEIpV6AddrAutoConfigAcceptRaDnssl
         INTEGER,
      er1646v2VxlBGIMVpPppOEIpV6DefaultRoute
         INTEGER,
      er1646v2VxlBGIMVpPppOEIpV6RaSend
         INTEGER,
      er1646v2VxlBGIMVpPppOEIpV6RaMinInterval
         TimeTicks,
      er1646v2VxlBGIMVpPppOEIpV6RaMaxInterval
         TimeTicks,
      er1646v2VxlBGIMVpPppOEIpV6RaManagedFlag
         INTEGER,
      er1646v2VxlBGIMVpPppOEIpV6RaOtherConfFlag
         INTEGER,
      er1646v2VxlBGIMVpPppOEIpV6RaLinkMtu
         Integer32,
      er1646v2VxlBGIMVpPppOEIpV6RaReachableTime
         TimeTicks,
      er1646v2VxlBGIMVpPppOEIpV6RaRetransmitTime
         TimeTicks,
      er1646v2VxlBGIMVpPppOEIpV6RaHopLimit
         Integer32,
      er1646v2VxlBGIMVpPppOEIpV6RaDefaultLifeTime
         TimeTicks,
      er1646v2VxlBGIMVpPppOEIpV6RaDnsOptionsRdnssLifeTime
         TimeTicks,
      er1646v2VxlBGIMVpPppOEIpV6RaDnsOptionsRdnssImportServers
         INTEGER,
      er1646v2VxlBGIMVpPppOEIpV6RaDnsOptionsDnsslLifeTime
         TimeTicks,
      er1646v2VxlBGIMVpPppOEIpV6RaDnsOptionsDnsslImportDomains
         INTEGER,
      er1646v2VxlBGIMVpPppOEIpV6RsSend
         INTEGER,
      er1646v2VxlBGIMVpPppOEIpV6RsMaxRandomDelay
         TimeTicks,
      er1646v2VxlBGIMVpPppOEIpV6RsInterval
         TimeTicks,
      er1646v2VxlBGIMVpPppOEIpV6RsMaxSolicitations
         Integer32,
      er1646v2VxlBGIMVpPppOEIpV6TrafficPolicyInbound
         DisplayString,
      er1646v2VxlBGIMVpPppOEIpV6TrafficPolicyOutbound
         DisplayString,
      er1646v2VxlBGIMVpPppOEIpV6FirewallZone
         DisplayString,
      er1646v2VxlBGIMVpPppOEIpV6DhcpClientAddrAC
         INTEGER,
      er1646v2VxlBGIMVpPppOEIpV6DhcpClientPrDelMode
         INTEGER,
      er1646v2VxlBGIMVpPppOEIpV6DhcpClientPrDelPool
         DisplayString,
      er1646v2VxlBGIMVpPppOEIpV6DhcpClientPrDelPdExclOpt
         INTEGER,
      er1646v2VxlBGIMVpPppOEIpV6DhcpClientDnsServerPref
         Integer32,
      er1646v2VxlBGIMVpPppOEIpV6DhcpClientRapidCommit
         INTEGER,
      er1646v2VxlBGIMVpPppOEIpV6DhcpClientTimersSolTimeOut
         TimeTicks,
      er1646v2VxlBGIMVpPppOEIpV6DhcpClientTimersSolMaxRt
         TimeTicks,
      er1646v2VxlBGIMVpPppOEIpV6DhcpClientTimersInfoRefresh
         TimeTicks,
      er1646v2VxlBGIMVpPppOEIpV6DhcpServerMode
         INTEGER,
      er1646v2VxlBGIMVpPppOEIpV6DhcpServerPreference
         Integer32,
      er1646v2VxlBGIMVpPppOEIpV6DhcpServerPool
         DisplayString,
      er1646v2VxlBGIMVpPppOEIpV6DhcpServerRapidCommit
         INTEGER,
      er1646v2VxlBGIMVpPppOEIpV6DhcpServerTimersInfoRefresh
         TimeTicks,
      er1646v2VxlBGIMVpPppOEIpV6DhcpRelayMode
         INTEGER,
      er1646v2VxlBGIMVpPppOEIpV6SendRedirect
         INTEGER,
      er1646v2VxlBGIMVpPppOEIpV6LinkMtu
         Integer32,
      er1646v2VxlBGIMVpPppOEIpV6InterfaceId
         OCTET STRING,
      er1646v2VxlBGIMVpPppOEIpV6MF
         Integer32,
      er1646v2VxlBGIMVpPppOEIpV6IcmpMessagesNoRoute
         INTEGER,
      er1646v2VxlBGIMVpPppOEIpV6IcmpMessagesBeyondScope
         INTEGER,
      er1646v2VxlBGIMVpPppOEIpV6IcmpMessagesAddressUnreachable
         INTEGER,
      er1646v2VxlBGIMVpPppOEIpV6IcmpMessagesPortUnreachable
         INTEGER,
      er1646v2VxlBGIMVpPppOEIpV6IcmpMessagesPacketTooBig
         INTEGER,
      er1646v2VxlBGIMVpPppOEIpV6IcmpMessagesHopLimitExceeded
         INTEGER,
      er1646v2VxlBGIMVpPppOEIpV6IcmpMessagesFragTimeExceeded
         INTEGER,
      er1646v2VxlBGIMVpPppOEIpV6IcmpMessagesHeaderFieldErr
         INTEGER,
      er1646v2VxlBGIMVpPppOEIpV6IcmpMessagesOptionUnrecognized
         INTEGER,
      er1646v2VxlBGIMVpPppOEIpV6IcmpMessagesRedirect
         INTEGER,
      er1646v2VxlBGIMVpPppOEPppLnkMOperation
         INTEGER,
      er1646v2VxlBGIMVpPppOEPppLnkMInterval
         TimeTicks,
      er1646v2VxlBGIMVpPppOEPppLnkMRepTimeOut
         TimeTicks,
      er1646v2VxlBGIMVpPppOEPppLnkMFailsPrmt
         Integer32,
      er1646v2VxlBGIMVpPppOEPppAuthentication
         INTEGER,
      er1646v2VxlBGIMVpPppOEPppAuthenPeriod
         TimeTicks,
      er1646v2VxlBGIMVpPppOEPppSessionName
         DisplayString,
      er1646v2VxlBGIMVpPppOEPppSessionSecret
         DisplayString,
      er1646v2VxlBGIMVpPppOEPppEncModeSessionSecret
         INTEGER,
      er1646v2VxlBGIMVpPppOEPppEncSessionSecret
         DisplayString,
      er1646v2VxlBGIMVpPppOEPppServiceName
         DisplayString
      }

er1646v2VxlBGIMVpPppOEActions OBJECT-TYPE
   SYNTAX      VariableLengthTableActions
   MAX-ACCESS  read-write
   STATUS      current
   DESCRIPTION
      "By way of this field, some manipulations
       on this table may be performed."
   ::= {er1646v2VxlBGIMVpPppOEEntry 2}

er1646v2VxlBGIMVpPppOEGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEEntry 10}

er1646v2VxlBGIMVpPppOETableIx OBJECT-TYPE
   SYNTAX      TableIndex
   MAX-ACCESS  not-accessible
   STATUS      current
   DESCRIPTION
      ""
   ::= {er1646v2VxlBGIMVpPppOEEntry 11}

er1646v2VxlBGIMVpPppOEName OBJECT-TYPE
   SYNTAX      DisplayString
   MAX-ACCESS  read-write
   STATUS      current
   DESCRIPTION
      "Path: vxLanBridgeGroup.editConf.pppoEClient.name"
   ::= {er1646v2VxlBGIMVpPppOEEntry 16777216}

er1646v2VxlBGIMVpPppOERemark OBJECT-TYPE
   SYNTAX      DisplayString
   MAX-ACCESS  read-write
   STATUS      current
   DESCRIPTION
      "Path: vxLanBridgeGroup.editConf.pppoEClient.remark"
   ::= {er1646v2VxlBGIMVpPppOEEntry 1157627904}

er1646v2VxlBGIMVpPppOEAdminStatus OBJECT-TYPE
   SYNTAX      INTEGER
               {
               up (1),
               down (2)
               }
   MAX-ACCESS  read-write
   STATUS      current
   DESCRIPTION
      "Path: vxLanBridgeGroup.editConf.pppoEClient.adminStatus

       Possibilities:
               up   (1)
               down   (2)"
   ::= {er1646v2VxlBGIMVpPppOEEntry 33554432}

er1646v2VxlBGIMVpPppOEMode OBJECT-TYPE
   SYNTAX      INTEGER
               {
               routing (1),
               multilink (8),
               ipV6 (16),
               ipV6ipV4 (17)
               }
   MAX-ACCESS  read-write
   STATUS      current
   DESCRIPTION
      "Path: vxLanBridgeGroup.editConf.pppoEClient.mode

       Possibilities:
               routing   (1)
               multilink   (8)
               ipV6   (16)
               ipV6/ipV4   (17)"
   ::= {er1646v2VxlBGIMVpPppOEEntry 67108864}

er1646v2VxlBGIMVpPppOEIpVrfRouter OBJECT-TYPE
   SYNTAX      DisplayString
   MAX-ACCESS  read-write
   STATUS      current
   DESCRIPTION
      "Path: vxLanBridgeGroup.editConf.pppoEClient.ip.vrfRouter"
   ::= {er1646v2VxlBGIMVpPppOEEntry 53215232}

er1646v2VxlBGIMVpPppOEIpAdr OBJECT-TYPE
   SYNTAX      IpAddress
   MAX-ACCESS  read-write
   STATUS      current
   DESCRIPTION
      "Path: vxLanBridgeGroup.editConf.pppoEClient.ip.address"
   ::= {er1646v2VxlBGIMVpPppOEEntry 58261504}

er1646v2VxlBGIMVpPppOEIpNetm OBJECT-TYPE
   SYNTAX      IpAddress
   MAX-ACCESS  read-write
   STATUS      current
   DESCRIPTION
      "Path: vxLanBridgeGroup.editConf.pppoEClient.ip.netMask"
   ::= {er1646v2VxlBGIMVpPppOEEntry 58392576}

er1646v2VxlBGIMVpPppOEIpSNetName OBJECT-TYPE
   SYNTAX      INTEGER
               {
               slOPTg (0),
               corp (2),
               dmz (3),
               internet (1)
               }
   MAX-ACCESS  read-write
   STATUS      current
   DESCRIPTION
      "Path: vxLanBridgeGroup.editConf.pppoEClient.ip.sNet.name

       Possibilities:
               <OPT>   (0)
               corp   (2)
               dmz   (3)
               internet   (1)"
   ::= {er1646v2VxlBGIMVpPppOEEntry 53674240}

er1646v2VxlBGIMVpPppOEIpSNetCust OBJECT-TYPE
   SYNTAX      DisplayString
   MAX-ACCESS  read-write
   STATUS      current
   DESCRIPTION
      "Path: vxLanBridgeGroup.editConf.pppoEClient.ip.sNet.custom"
   ::= {er1646v2VxlBGIMVpPppOEEntry 53674496}

er1646v2VxlBGIMVpPppOEIpRem OBJECT-TYPE
   SYNTAX      IpAddress
   MAX-ACCESS  read-write
   STATUS      current
   DESCRIPTION
      "Path: vxLanBridgeGroup.editConf.pppoEClient.ip.remote"
   ::= {er1646v2VxlBGIMVpPppOEEntry 58458112}

er1646v2VxlBGIMVpPppOEIpUnnumbered OBJECT-TYPE
   SYNTAX      DisplayString
   MAX-ACCESS  read-write
   STATUS      current
   DESCRIPTION
      "Path: vxLanBridgeGroup.editConf.pppoEClient.ip.unnumbered"
   ::= {er1646v2VxlBGIMVpPppOEEntry 52625408}

er1646v2VxlBGIMVpPppOEIpGwPref OBJECT-TYPE
   SYNTAX      Integer32
   MAX-ACCESS  read-write
   STATUS      current
   DESCRIPTION
      "Path: vxLanBridgeGroup.editConf.pppoEClient.ip.gatewayPreference"
   ::= {er1646v2VxlBGIMVpPppOEEntry 52690944}

er1646v2VxlBGIMVpPppOEIpRsn OBJECT-TYPE
   SYNTAX      INTEGER
               {
               disabled (0),
               enabled (1)
               }
   MAX-ACCESS  read-write
   STATUS      current
   DESCRIPTION
      "Path: vxLanBridgeGroup.editConf.pppoEClient.ip.requestSubnet

       Possibilities:
               disabled   (0)
               enabled   (1)"
   ::= {er1646v2VxlBGIMVpPppOEEntry 56688640}

er1646v2VxlBGIMVpPppOEIpMtu OBJECT-TYPE
   SYNTAX      Integer32
   MAX-ACCESS  read-write
   STATUS      current
   DESCRIPTION
      "Path: vxLanBridgeGroup.editConf.pppoEClient.ip.mtu"
   ::= {er1646v2VxlBGIMVpPppOEEntry 52953088}

er1646v2VxlBGIMVpPppOEIpMssAdjust OBJECT-TYPE
   SYNTAX      INTEGER
               {
               disabled (0),
               auto (65536)
               }
   MAX-ACCESS  read-write
   STATUS      current
   DESCRIPTION
      "Path: vxLanBridgeGroup.editConf.pppoEClient.ip.mssAdjust

       Possibilities:
               disabled   (0)
               auto   (65536)"
   ::= {er1646v2VxlBGIMVpPppOEEntry 53280768}

er1646v2VxlBGIMVpPppOEIpRipMetric OBJECT-TYPE
   SYNTAX      Integer32
   MAX-ACCESS  read-write
   STATUS      current
   DESCRIPTION
      "Path: vxLanBridgeGroup.editConf.pppoEClient.ip.rip.metric"
   ::= {er1646v2VxlBGIMVpPppOEEntry 51712768}

er1646v2VxlBGIMVpPppOEIpRipMetricOut OBJECT-TYPE
   SYNTAX      Integer32
   MAX-ACCESS  read-write
   STATUS      current
   DESCRIPTION
      "Path: vxLanBridgeGroup.editConf.pppoEClient.ip.rip.metricOut"
   ::= {er1646v2VxlBGIMVpPppOEEntry 51713024}

er1646v2VxlBGIMVpPppOEIpRipMode OBJECT-TYPE
   SYNTAX      INTEGER
               {
               disabled (0),
               passive (1),
               active (2)
               }
   MAX-ACCESS  read-write
   STATUS      current
   DESCRIPTION
      "Path: vxLanBridgeGroup.editConf.pppoEClient.ip.rip.mode

       Possibilities:
               disabled   (0)
               passive   (1)
               active   (2)"
   ::= {er1646v2VxlBGIMVpPppOEEntry 51713280}

er1646v2VxlBGIMVpPppOEIpRipTxVer OBJECT-TYPE
   SYNTAX      INTEGER
               {
               rip1 (0),
               rip2 (1),
               rip1mcompatible (2)
               }
   MAX-ACCESS  read-write
   STATUS      current
   DESCRIPTION
      "Path: vxLanBridgeGroup.editConf.pppoEClient.ip.rip.txVersion

       Possibilities:
               rip1   (0)
               rip2   (1)
               rip1-compatible   (2)"
   ::= {er1646v2VxlBGIMVpPppOEEntry 51716864}

er1646v2VxlBGIMVpPppOEIpRipRxVer OBJECT-TYPE
   SYNTAX      INTEGER
               {
               rip1only (0),
               rip2only (1),
               rip12 (2)
               }
   MAX-ACCESS  read-write
   STATUS      current
   DESCRIPTION
      "Path: vxLanBridgeGroup.editConf.pppoEClient.ip.rip.rxVersion

       Possibilities:
               rip1only   (0)
               rip2only   (1)
               rip1&2   (2)"
   ::= {er1646v2VxlBGIMVpPppOEEntry 51717120}

er1646v2VxlBGIMVpPppOEIpRipSplitH OBJECT-TYPE
   SYNTAX      INTEGER
               {
               disabled (0),
               enabled (1),
               poisonedReverse (2)
               }
   MAX-ACCESS  read-write
   STATUS      current
   DESCRIPTION
      "Path: vxLanBridgeGroup.editConf.pppoEClient.ip.rip.splitHorizon

       Possibilities:
               disabled   (0)
               enabled   (1)
               poisonedReverse   (2)"
   ::= {er1646v2VxlBGIMVpPppOEEntry 51713792}

er1646v2VxlBGIMVpPppOEIpRipAuth OBJECT-TYPE
   SYNTAX      INTEGER
               {
               disabled (0),
               texts (1),
               md5 (2)
               }
   MAX-ACCESS  read-write
   STATUS      current
   DESCRIPTION
      "Path: vxLanBridgeGroup.editConf.pppoEClient.ip.rip.authentication

       Possibilities:
               disabled   (0)
               text    (1)
               md5   (2)"
   ::= {er1646v2VxlBGIMVpPppOEEntry 51712512}

er1646v2VxlBGIMVpPppOEIpRipFilter OBJECT-TYPE
   SYNTAX      DisplayString
   MAX-ACCESS  read-write
   STATUS      current
   DESCRIPTION
      "Path: vxLanBridgeGroup.editConf.pppoEClient.ip.rip.filter"
   ::= {er1646v2VxlBGIMVpPppOEEntry 51716096}

er1646v2VxlBGIMVpPppOEIpRipFilterIn OBJECT-TYPE
   SYNTAX      DisplayString
   MAX-ACCESS  read-write
   STATUS      current
   DESCRIPTION
      "Path: vxLanBridgeGroup.editConf.pppoEClient.ip.rip.filterIn"
   ::= {er1646v2VxlBGIMVpPppOEEntry 51716352}

er1646v2VxlBGIMVpPppOEIpRipClearNextHop OBJECT-TYPE
   SYNTAX      INTEGER
               {
               disabled (0),
               enabled (1)
               }
   MAX-ACCESS  read-write
   STATUS      current
   DESCRIPTION
      "Path: vxLanBridgeGroup.editConf.pppoEClient.ip.rip.clearNextHop

       Possibilities:
               disabled   (0)
               enabled   (1)"
   ::= {er1646v2VxlBGIMVpPppOEEntry 51708416}

er1646v2VxlBGIMVpPppOEIpAccPol OBJECT-TYPE
   SYNTAX      DisplayString
   MAX-ACCESS  read-write
   STATUS      current
   DESCRIPTION
      "Path: vxLanBridgeGroup.editConf.pppoEClient.ip.accessPolicy"
   ::= {er1646v2VxlBGIMVpPppOEEntry 53084160}

er1646v2VxlBGIMVpPppOEIpAB OBJECT-TYPE
   SYNTAX      DisplayString
   MAX-ACCESS  read-write
   STATUS      current
   DESCRIPTION
      "Path: vxLanBridgeGroup.editConf.pppoEClient.ip.trafficPolicy"
   ::= {er1646v2VxlBGIMVpPppOEEntry 51249152}

er1646v2VxlBGIMVpPppOEIpMA OBJECT-TYPE
   SYNTAX      INTEGER
               {
               disabled (0),
               enabled (1)
               }
   MAX-ACCESS  read-write
   STATUS      current
   DESCRIPTION
      "Path: vxLanBridgeGroup.editConf.pppoEClient.ip.mgmtAccess

       Possibilities:
               disabled   (0)
               enabled   (1)"
   ::= {er1646v2VxlBGIMVpPppOEEntry 51380224}

er1646v2VxlBGIMVpPppOEIpMF OBJECT-TYPE
   SYNTAX      Integer32
   MAX-ACCESS  read-write
   STATUS      current
   DESCRIPTION
      "Path: vxLanBridgeGroup.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VxlBGIMVpPppOEEntry 51445760}

er1646v2VxlBGIMVpPppOEIpDB OBJECT-TYPE
   SYNTAX      INTEGER
               {
               disabled (0),
               enabled (1)
               }
   MAX-ACCESS  read-write
   STATUS      current
   DESCRIPTION
      "Path: vxLanBridgeGroup.editConf.pppoEClient.ip.directedBroadcasts

       Possibilities:
               disabled   (0)
               enabled   (1)"
   ::= {er1646v2VxlBGIMVpPppOEEntry 51773440}

er1646v2VxlBGIMVpPppOEIpIR OBJECT-TYPE
   SYNTAX      INTEGER
               {
               disabled (0),
               enabled (1)
               }
   MAX-ACCESS  read-write
   STATUS      current
   DESCRIPTION
      "Path: vxLanBridgeGroup.editConf.pppoEClient.ip.icmpRedirects

       Possibilities:
               disabled   (0)
               enabled   (1)"
   ::= {er1646v2VxlBGIMVpPppOEEntry 52035584}

er1646v2VxlBGIMVpPppOEIpIgmp OBJECT-TYPE
   SYNTAX      INTEGER
               {
               disabled (0),
               proxy (1),
               router (2),
               v3Router (5)
               }
   MAX-ACCESS  read-write
   STATUS      current
   DESCRIPTION
      "Path: vxLanBridgeGroup.editConf.pppoEClient.ip.igmp

       Possibilities:
               disabled   (0)
               proxy   (1)
               router   (2)
               v3Router   (5)"
   ::= {er1646v2VxlBGIMVpPppOEEntry 52428800}

er1646v2VxlBGIMVpPppOEIpNN OBJECT-TYPE
   SYNTAX      DisplayString
   MAX-ACCESS  read-write
   STATUS      current
   DESCRIPTION
      "Path: vxLanBridgeGroup.editConf.pppoEClient.ip.nat"
   ::= {er1646v2VxlBGIMVpPppOEEntry 52101120}

er1646v2VxlBGIMVpPppOEIpPimMode OBJECT-TYPE
   SYNTAX      INTEGER
               {
               disabled (0),
               sparse (1),
               passive (2)
               }
   MAX-ACCESS  read-write
   STATUS      current
   DESCRIPTION
      "Path: vxLanBridgeGroup.editConf.pppoEClient.ip.pim.mode

       Possibilities:
               disabled   (0)
               sparse   (1)
               passive   (2)"
   ::= {er1646v2VxlBGIMVpPppOEEntry 53346560}

er1646v2VxlBGIMVpPppOEIpPimDrPriority OBJECT-TYPE
   SYNTAX      Counter32
   MAX-ACCESS  read-write
   STATUS      current
   DESCRIPTION
      "Path: vxLanBridgeGroup.editConf.pppoEClient.ip.pim.drPriority

       32 bit unsigned wrappable counter."
   ::= {er1646v2VxlBGIMVpPppOEEntry 53346816}

er1646v2VxlBGIMVpPppOEIpPimHelloTime OBJECT-TYPE
   SYNTAX      TimeTicks
   MAX-ACCESS  read-write
   STATUS      current
   DESCRIPTION
      "Path: vxLanBridgeGroup.editConf.pppoEClient.ip.pim.helloTime

       Time in centi-second."
   ::= {er1646v2VxlBGIMVpPppOEEntry 53347072}

er1646v2VxlBGIMVpPppOEIpPimPropagationDelay OBJECT-TYPE
   SYNTAX      TimeTicks
   MAX-ACCESS  read-write
   STATUS      current
   DESCRIPTION
      "Path: vxLanBridgeGroup.editConf.pppoEClient.ip.pim.propagationDelay

       Time in centi-second."
   ::= {er1646v2VxlBGIMVpPppOEEntry 53347328}

er1646v2VxlBGIMVpPppOEIpPimOverrideInterval OBJECT-TYPE
   SYNTAX      TimeTicks
   MAX-ACCESS  read-write
   STATUS      current
   DESCRIPTION
      "Path: vxLanBridgeGroup.editConf.pppoEClient.ip.pim.overrideInterval

       Time in centi-second."
   ::= {er1646v2VxlBGIMVpPppOEEntry 53347584}

er1646v2VxlBGIMVpPppOEIpPimBsrBorder OBJECT-TYPE
   SYNTAX      INTEGER
               {
               disabled (0),
               enabled (1)
               }
   MAX-ACCESS  read-write
   STATUS      current
   DESCRIPTION
      "Path: vxLanBridgeGroup.editConf.pppoEClient.ip.pim.bsrBorder

       Possibilities:
               disabled   (0)
               enabled   (1)"
   ::= {er1646v2VxlBGIMVpPppOEEntry 53347840}

er1646v2VxlBGIMVpPppOEIpPimTtlThreshold OBJECT-TYPE
   SYNTAX      Integer32
   MAX-ACCESS  read-write
   STATUS      current
   DESCRIPTION
      "Path: vxLanBridgeGroup.editConf.pppoEClient.ip.pim.ttlThreshold"
   ::= {er1646v2VxlBGIMVpPppOEEntry 53348096}

er1646v2VxlBGIMVpPppOEIpIMNetworkUnreachable OBJECT-TYPE
   SYNTAX      INTEGER
               {
               disabled (0),
               enabled (1)
               }
   MAX-ACCESS  read-write
   STATUS      current
   DESCRIPTION
      "Path: vxLanBridgeGroup.editConf.pppoEClient.ip.icmpMessages.networkUnreachable

       Possibilities:
               disabled   (0)
               enabled   (1)"
   ::= {er1646v2VxlBGIMVpPppOEEntry 53412096}

er1646v2VxlBGIMVpPppOEIpIMHostUnreachable OBJECT-TYPE
   SYNTAX      INTEGER
               {
               disabled (0),
               enabled (1)
               }
   MAX-ACCESS  read-write
   STATUS      current
   DESCRIPTION
      "Path: vxLanBridgeGroup.editConf.pppoEClient.ip.icmpMessages.hostUnreachable

       Possibilities:
               disabled   (0)
               enabled   (1)"
   ::= {er1646v2VxlBGIMVpPppOEEntry 53412352}

er1646v2VxlBGIMVpPppOEIpIMProtocolUnreachable OBJECT-TYPE
   SYNTAX      INTEGER
               {
               disabled (0),
               enabled (1)
               }
   MAX-ACCESS  read-write
   STATUS      current
   DESCRIPTION
      "Path: vxLanBridgeGroup.editConf.pppoEClient.ip.icmpMessages.protocolUnreachable

       Possibilities:
               disabled   (0)
               enabled   (1)"
   ::= {er1646v2VxlBGIMVpPppOEEntry 53412608}

er1646v2VxlBGIMVpPppOEIpIMPortUnreachable OBJECT-TYPE
   SYNTAX      INTEGER
               {
               disabled (0),
               enabled (1)
               }
   MAX-ACCESS  read-write
   STATUS      current
   DESCRIPTION
      "Path: vxLanBridgeGroup.editConf.pppoEClient.ip.icmpMessages.portUnreachable

       Possibilities:
               disabled   (0)
               enabled   (1)"
   ::= {er1646v2VxlBGIMVpPppOEEntry 53412864}

er1646v2VxlBGIMVpPppOEIpIMMtuExceeded OBJECT-TYPE
   SYNTAX      INTEGER
               {
               disabled (0),
               enabled (1)
               }
   MAX-ACCESS  read-write
   STATUS      current
   DESCRIPTION
      "Path: vxLanBridgeGroup.editConf.pppoEClient.ip.icmpMessages.mtuExceeded

       Possibilities:
               disabled   (0)
               enabled   (1)"
   ::= {er1646v2VxlBGIMVpPppOEEntry 53413120}

er1646v2VxlBGIMVpPppOEIpIMAdminProhibited OBJECT-TYPE
   SYNTAX      INTEGER
               {
               disabled (0),
               enabled (1)
               }
   MAX-ACCESS  read-write
   STATUS      current
   DESCRIPTION
      "Path: vxLanBridgeGroup.editConf.pppoEClient.ip.icmpMessages.adminProhibited

       Possibilities:
               disabled   (0)
               enabled   (1)"
   ::= {er1646v2VxlBGIMVpPppOEEntry 53413376}

er1646v2VxlBGIMVpPppOEIpIMTtlExceeded OBJECT-TYPE
   SYNTAX      INTEGER
               {
               disabled (0),
               enabled (1)
               }
   MAX-ACCESS  read-write
   STATUS      current
   DESCRIPTION
      "Path: vxLanBridgeGroup.editConf.pppoEClient.ip.icmpMessages.ttlExceeded

       Possibilities:
               disabled   (0)
               enabled   (1)"
   ::= {er1646v2VxlBGIMVpPppOEEntry 53413632}

er1646v2VxlBGIMVpPppOEIpIMRedirect OBJECT-TYPE
   SYNTAX      INTEGER
               {
               disabled (0),
               enabled (1)
               }
   MAX-ACCESS  read-write
   STATUS      current
   DESCRIPTION
      "Path: vxLanBridgeGroup.editConf.pppoEClient.ip.icmpMessages.redirect

       Possibilities:
               disabled   (0)
               enabled   (1)"
   ::= {er1646v2VxlBGIMVpPppOEEntry 53413888}

er1646v2VxlBGIMVpPppOEIpV6VrfRouter OBJECT-TYPE
   SYNTAX      DisplayString
   MAX-ACCESS  read-write
   STATUS      current
   DESCRIPTION
      "Path: vxLanBridgeGroup.editConf.pppoEClient.ipV6.vrfRouter"
   ::= {er1646v2VxlBGIMVpPppOEEntry 704708608}

er1646v2VxlBGIMVpPppOEIpV6AddrAutoConfigNrDupAddrDetects OBJECT-TYPE
   SYNTAX      Integer32
   MAX-ACCESS  read-write
   STATUS      current
   DESCRIPTION
      "Path: vxLanBridgeGroup.editConf.pppoEClient.ipV6.addrAutoConfig.nrDupAddrDetects"
   ::= {er1646v2VxlBGIMVpPppOEEntry 704905472}

er1646v2VxlBGIMVpPppOEIpV6AddrAutoConfigAcceptRa OBJECT-TYPE
   SYNTAX      INTEGER
               {
               disabled (0),
               enabled (1)
               }
   MAX-ACCESS  read-write
   STATUS      current
   DESCRIPTION
      "Path: vxLanBridgeGroup.editConf.pppoEClient.ipV6.addrAutoConfig.acceptRa

       Possibilities:
               disabled   (0)
               enabled   (1)"
   ::= {er1646v2VxlBGIMVpPppOEEntry 704905728}

er1646v2VxlBGIMVpPppOEIpV6AddrAutoConfigAcceptRaRdnss OBJECT-TYPE
   SYNTAX      INTEGER
               {
               disabled (0),
               enabled (1)
               }
   MAX-ACCESS  read-write
   STATUS      current
   DESCRIPTION
      "Path: vxLanBridgeGroup.editConf.pppoEClient.ipV6.addrAutoConfig.acceptRaRdnss

       Possibilities:
               disabled   (0)
               enabled   (1)"
   ::= {er1646v2VxlBGIMVpPppOEEntry 704905984}

er1646v2VxlBGIMVpPppOEIpV6AddrAutoConfigAcceptRaDnssl OBJECT-TYPE
   SYNTAX      INTEGER
               {
               disabled (0),
               enabled (1)
               }
   MAX-ACCESS  read-write
   STATUS      current
   DESCRIPTION
      "Path: vxLanBridgeGroup.editConf.pppoEClient.ipV6.addrAutoConfig.acceptRaDnssl

       Possibilities:
               disabled   (0)
               enabled   (1)"
   ::= {er1646v2VxlBGIMVpPppOEEntry 704906240}

er1646v2VxlBGIMVpPppOEIpV6DefaultRoute OBJECT-TYPE
   SYNTAX      INTEGER
               {
               disabled (0),
               enabled (1)
               }
   MAX-ACCESS  read-write
   STATUS      current
   DESCRIPTION
      "Path: vxLanBridgeGroup.editConf.pppoEClient.ipV6.defaultRoute

       Possibilities:
               disabled   (0)
               enabled   (1)"
   ::= {er1646v2VxlBGIMVpPppOEEntry 704970752}

er1646v2VxlBGIMVpPppOEIpV6RaSend OBJECT-TYPE
   SYNTAX      INTEGER
               {
               disabled (0),
               enabled (1)
               }
   MAX-ACCESS  read-write
   STATUS      current
   DESCRIPTION
      "Path: vxLanBridgeGroup.editConf.pppoEClient.ipV6.ra.send

       Possibilities:
               disabled   (0)
               enabled   (1)"
   ::= {er1646v2VxlBGIMVpPppOEEntry 705036544}

er1646v2VxlBGIMVpPppOEIpV6RaMinInterval OBJECT-TYPE
   SYNTAX      TimeTicks
   MAX-ACCESS  read-write
   STATUS      current
   DESCRIPTION
      "Path: vxLanBridgeGroup.editConf.pppoEClient.ipV6.ra.minInterval

       Time in centi-second."
   ::= {er1646v2VxlBGIMVpPppOEEntry 705036800}

er1646v2VxlBGIMVpPppOEIpV6RaMaxInterval OBJECT-TYPE
   SYNTAX      TimeTicks
   MAX-ACCESS  read-write
   STATUS      current
   DESCRIPTION
      "Path: vxLanBridgeGroup.editConf.pppoEClient.ipV6.ra.maxInterval

       Time in centi-second."
   ::= {er1646v2VxlBGIMVpPppOEEntry 705037056}

er1646v2VxlBGIMVpPppOEIpV6RaManagedFlag OBJECT-TYPE
   SYNTAX      INTEGER
               {
               disabled (0),
               enabled (1)
               }
   MAX-ACCESS  read-write
   STATUS      current
   DESCRIPTION
      "Path: vxLanBridgeGroup.editConf.pppoEClient.ipV6.ra.managedFlag

       Possibilities:
               disabled   (0)
               enabled   (1)"
   ::= {er1646v2VxlBGIMVpPppOEEntry 705037312}

er1646v2VxlBGIMVpPppOEIpV6RaOtherConfFlag OBJECT-TYPE
   SYNTAX      INTEGER
               {
               disabled (0),
               enabled (1)
               }
   MAX-ACCESS  read-write
   STATUS      current
   DESCRIPTION
      "Path: vxLanBridgeGroup.editConf.pppoEClient.ipV6.ra.otherConfFlag

       Possibilities:
               disabled   (0)
               enabled   (1)"
   ::= {er1646v2VxlBGIMVpPppOEEntry 705037568}

er1646v2VxlBGIMVpPppOEIpV6RaLinkMtu OBJECT-TYPE
   SYNTAX      Integer32
   MAX-ACCESS  read-write
   STATUS      current
   DESCRIPTION
      "Path: vxLanBridgeGroup.editConf.pppoEClient.ipV6.ra.linkMtu"
   ::= {er1646v2VxlBGIMVpPppOEEntry 705037824}

er1646v2VxlBGIMVpPppOEIpV6RaReachableTime OBJECT-TYPE
   SYNTAX      TimeTicks
   MAX-ACCESS  read-write
   STATUS      current
   DESCRIPTION
      "Path: vxLanBridgeGroup.editConf.pppoEClient.ipV6.ra.reachableTime

       Time in centi-second."
   ::= {er1646v2VxlBGIMVpPppOEEntry 705038080}

er1646v2VxlBGIMVpPppOEIpV6RaRetransmitTime OBJECT-TYPE
   SYNTAX      TimeTicks
   MAX-ACCESS  read-write
   STATUS      current
   DESCRIPTION
      "Path: vxLanBridgeGroup.editConf.pppoEClient.ipV6.ra.retransmitTime

       Time in centi-second."
   ::= {er1646v2VxlBGIMVpPppOEEntry 705038336}

er1646v2VxlBGIMVpPppOEIpV6RaHopLimit OBJECT-TYPE
   SYNTAX      Integer32
   MAX-ACCESS  read-write
   STATUS      current
   DESCRIPTION
      "Path: vxLanBridgeGroup.editConf.pppoEClient.ipV6.ra.hopLimit"
   ::= {er1646v2VxlBGIMVpPppOEEntry 705038592}

er1646v2VxlBGIMVpPppOEIpV6RaDefaultLifeTime OBJECT-TYPE
   SYNTAX      TimeTicks
   MAX-ACCESS  read-write
   STATUS      current
   DESCRIPTION
      "Path: vxLanBridgeGroup.editConf.pppoEClient.ipV6.ra.defaultLifeTime

       Time in centi-second."
   ::= {er1646v2VxlBGIMVpPppOEEntry 705038848}

er1646v2VxlBGIMVpPppOEIpV6RaDnsOptionsRdnssLifeTime OBJECT-TYPE
   SYNTAX      TimeTicks
   MAX-ACCESS  read-write
   STATUS      current
   DESCRIPTION
      "Path: vxLanBridgeGroup.editConf.pppoEClient.ipV6.ra.dnsOptions.rdnss.lifeTime

       Time in centi-second."
   ::= {er1646v2VxlBGIMVpPppOEEntry 705039140}

er1646v2VxlBGIMVpPppOEIpV6RaDnsOptionsRdnssImportServers OBJECT-TYPE
   SYNTAX      INTEGER
               {
               disabled (0),
               enabled (1)
               }
   MAX-ACCESS  read-write
   STATUS      current
   DESCRIPTION
      "Path: vxLanBridgeGroup.editConf.pppoEClient.ipV6.ra.dnsOptions.rdnss.importServers

       Possibilities:
               disabled   (0)
               enabled   (1)"
   ::= {er1646v2VxlBGIMVpPppOEEntry 705039148}

er1646v2VxlBGIMVpPppOEIpV6RaDnsOptionsDnsslLifeTime OBJECT-TYPE
   SYNTAX      TimeTicks
   MAX-ACCESS  read-write
   STATUS      current
   DESCRIPTION
      "Path: vxLanBridgeGroup.editConf.pppoEClient.ipV6.ra.dnsOptions.dnssl.lifeTime

       Time in centi-second."
   ::= {er1646v2VxlBGIMVpPppOEEntry 705039172}

er1646v2VxlBGIMVpPppOEIpV6RaDnsOptionsDnsslImportDomains OBJECT-TYPE
   SYNTAX      INTEGER
               {
               disabled (0),
               enabled (1)
               }
   MAX-ACCESS  read-write
   STATUS      current
   DESCRIPTION
      "Path: vxLanBridgeGroup.editConf.pppoEClient.ipV6.ra.dnsOptions.dnssl.importDomains

       Possibilities:
               disabled   (0)
               enabled   (1)"
   ::= {er1646v2VxlBGIMVpPppOEEntry 705039180}

er1646v2VxlBGIMVpPppOEIpV6RsSend OBJECT-TYPE
   SYNTAX      INTEGER
               {
               disabled (0),
               enabled (1)
               }
   MAX-ACCESS  read-write
   STATUS      current
   DESCRIPTION
      "Path: vxLanBridgeGroup.editConf.pppoEClient.ipV6.rs.send

       Possibilities:
               disabled   (0)
               enabled   (1)"
   ::= {er1646v2VxlBGIMVpPppOEEntry 705954048}

er1646v2VxlBGIMVpPppOEIpV6RsMaxRandomDelay OBJECT-TYPE
   SYNTAX      TimeTicks
   MAX-ACCESS  read-write
   STATUS      current
   DESCRIPTION
      "Path: vxLanBridgeGroup.editConf.pppoEClient.ipV6.rs.maxRandomDelay

       Time in centi-second."
   ::= {er1646v2VxlBGIMVpPppOEEntry 705954304}

er1646v2VxlBGIMVpPppOEIpV6RsInterval OBJECT-TYPE
   SYNTAX      TimeTicks
   MAX-ACCESS  read-write
   STATUS      current
   DESCRIPTION
      "Path: vxLanBridgeGroup.editConf.pppoEClient.ipV6.rs.interval

       Time in centi-second."
   ::= {er1646v2VxlBGIMVpPppOEEntry 705954560}

er1646v2VxlBGIMVpPppOEIpV6RsMaxSolicitations OBJECT-TYPE
   SYNTAX      Integer32
   MAX-ACCESS  read-write
   STATUS      current
   DESCRIPTION
      "Path: vxLanBridgeGroup.editConf.pppoEClient.ipV6.rs.maxSolicitations"
   ::= {er1646v2VxlBGIMVpPppOEEntry 705954816}

er1646v2VxlBGIMVpPppOEIpV6TrafficPolicyInbound OBJECT-TYPE
   SYNTAX      DisplayString
   MAX-ACCESS  read-write
   STATUS      current
   DESCRIPTION
      "Path: vxLanBridgeGroup.editConf.pppoEClient.ipV6.trafficPolicy.inbound"
   ::= {er1646v2VxlBGIMVpPppOEEntry 705364224}

er1646v2VxlBGIMVpPppOEIpV6TrafficPolicyOutbound OBJECT-TYPE
   SYNTAX      DisplayString
   MAX-ACCESS  read-write
   STATUS      current
   DESCRIPTION
      "Path: vxLanBridgeGroup.editConf.pppoEClient.ipV6.trafficPolicy.outbound"
   ::= {er1646v2VxlBGIMVpPppOEEntry 705364480}

er1646v2VxlBGIMVpPppOEIpV6FirewallZone OBJECT-TYPE
   SYNTAX      DisplayString
   MAX-ACCESS  read-write
   STATUS      current
   DESCRIPTION
      "Path: vxLanBridgeGroup.editConf.pppoEClient.ipV6.firewall.zone"
   ::= {er1646v2VxlBGIMVpPppOEEntry 705429760}

er1646v2VxlBGIMVpPppOEIpV6DhcpClientAddrAC OBJECT-TYPE
   SYNTAX      INTEGER
               {
               disabled (0),
               enabled (1)
               }
   MAX-ACCESS  read-write
   STATUS      current
   DESCRIPTION
      "Path: vxLanBridgeGroup.editConf.pppoEClient.ipV6.dhcp.client.addrAutoConfig

       Possibilities:
               disabled   (0)
               enabled   (1)"
   ::= {er1646v2VxlBGIMVpPppOEEntry 705307648}

er1646v2VxlBGIMVpPppOEIpV6DhcpClientPrDelMode OBJECT-TYPE
   SYNTAX      INTEGER
               {
               disabled (0),
               enabled (1)
               }
   MAX-ACCESS  read-write
   STATUS      current
   DESCRIPTION
      "Path: vxLanBridgeGroup.editConf.pppoEClient.ipV6.dhcp.client.pd.mode

       Possibilities:
               disabled   (0)
               enabled   (1)"
   ::= {er1646v2VxlBGIMVpPppOEEntry 705308676}

er1646v2VxlBGIMVpPppOEIpV6DhcpClientPrDelPool OBJECT-TYPE
   SYNTAX      DisplayString
   MAX-ACCESS  read-write
   STATUS      current
   DESCRIPTION
      "Path: vxLanBridgeGroup.editConf.pppoEClient.ipV6.dhcp.client.pd.pool"
   ::= {er1646v2VxlBGIMVpPppOEEntry 705308680}

er1646v2VxlBGIMVpPppOEIpV6DhcpClientPrDelPdExclOpt OBJECT-TYPE
   SYNTAX      INTEGER
               {
               disabled (0),
               enabled (1)
               }
   MAX-ACCESS  read-write
   STATUS      current
   DESCRIPTION
      "Path: vxLanBridgeGroup.editConf.pppoEClient.ipV6.dhcp.client.pd.pdExclOpt

       Possibilities:
               disabled   (0)
               enabled   (1)"
   ::= {er1646v2VxlBGIMVpPppOEEntry 705308684}

er1646v2VxlBGIMVpPppOEIpV6DhcpClientDnsServerPref OBJECT-TYPE
   SYNTAX      Integer32
   MAX-ACCESS  read-write
   STATUS      current
   DESCRIPTION
      "Path: vxLanBridgeGroup.editConf.pppoEClient.ipV6.dhcp.client.dns.serverPref"
   ::= {er1646v2VxlBGIMVpPppOEEntry 705310724}

er1646v2VxlBGIMVpPppOEIpV6DhcpClientRapidCommit OBJECT-TYPE
   SYNTAX      INTEGER
               {
               disabled (0),
               enabled (1)
               }
   MAX-ACCESS  read-write
   STATUS      current
   DESCRIPTION
      "Path: vxLanBridgeGroup.editConf.pppoEClient.ipV6.dhcp.client.rapidCommit

       Possibilities:
               disabled   (0)
               enabled   (1)"
   ::= {er1646v2VxlBGIMVpPppOEEntry 705309696}

er1646v2VxlBGIMVpPppOEIpV6DhcpClientTimersSolTimeOut OBJECT-TYPE
   SYNTAX      TimeTicks
   MAX-ACCESS  read-write
   STATUS      current
   DESCRIPTION
      "Path: vxLanBridgeGroup.editConf.pppoEClient.ipV6.dhcp.client.timers.solTimeOut

       Time in centi-second."
   ::= {er1646v2VxlBGIMVpPppOEEntry 705311748}

er1646v2VxlBGIMVpPppOEIpV6DhcpClientTimersSolMaxRt OBJECT-TYPE
   SYNTAX      TimeTicks
   MAX-ACCESS  read-write
   STATUS      current
   DESCRIPTION
      "Path: vxLanBridgeGroup.editConf.pppoEClient.ipV6.dhcp.client.timers.solMaxRt

       Time in centi-second."
   ::= {er1646v2VxlBGIMVpPppOEEntry 705311752}

er1646v2VxlBGIMVpPppOEIpV6DhcpClientTimersInfoRefresh OBJECT-TYPE
   SYNTAX      TimeTicks
   MAX-ACCESS  read-write
   STATUS      current
   DESCRIPTION
      "Path: vxLanBridgeGroup.editConf.pppoEClient.ipV6.dhcp.client.timers.infoRefresh

       Time in centi-second."
   ::= {er1646v2VxlBGIMVpPppOEEntry 705311756}

er1646v2VxlBGIMVpPppOEIpV6DhcpServerMode OBJECT-TYPE
   SYNTAX      INTEGER
               {
               disabled (0),
               enabled (1)
               }
   MAX-ACCESS  read-write
   STATUS      current
   DESCRIPTION
      "Path: vxLanBridgeGroup.editConf.pppoEClient.ipV6.dhcp.server.mode

       Possibilities:
               disabled   (0)
               enabled   (1)"
   ::= {er1646v2VxlBGIMVpPppOEEntry 705315840}

er1646v2VxlBGIMVpPppOEIpV6DhcpServerPreference OBJECT-TYPE
   SYNTAX      Integer32
   MAX-ACCESS  read-write
   STATUS      current
   DESCRIPTION
      "Path: vxLanBridgeGroup.editConf.pppoEClient.ipV6.dhcp.server.preference"
   ::= {er1646v2VxlBGIMVpPppOEEntry 705316864}

er1646v2VxlBGIMVpPppOEIpV6DhcpServerPool OBJECT-TYPE
   SYNTAX      DisplayString
   MAX-ACCESS  read-write
   STATUS      current
   DESCRIPTION
      "Path: vxLanBridgeGroup.editConf.pppoEClient.ipV6.dhcp.server.pool"
   ::= {er1646v2VxlBGIMVpPppOEEntry 705317888}

er1646v2VxlBGIMVpPppOEIpV6DhcpServerRapidCommit OBJECT-TYPE
   SYNTAX      INTEGER
               {
               disabled (0),
               enabled (1)
               }
   MAX-ACCESS  read-write
   STATUS      current
   DESCRIPTION
      "Path: vxLanBridgeGroup.editConf.pppoEClient.ipV6.dhcp.server.rapidCommit

       Possibilities:
               disabled   (0)
               enabled   (1)"
   ::= {er1646v2VxlBGIMVpPppOEEntry 705318912}

er1646v2VxlBGIMVpPppOEIpV6DhcpServerTimersInfoRefresh OBJECT-TYPE
   SYNTAX      TimeTicks
   MAX-ACCESS  read-write
   STATUS      current
   DESCRIPTION
      "Path: vxLanBridgeGroup.editConf.pppoEClient.ipV6.dhcp.server.timers.infoRefresh

       Time in centi-second."
   ::= {er1646v2VxlBGIMVpPppOEEntry 705319940}

er1646v2VxlBGIMVpPppOEIpV6DhcpRelayMode OBJECT-TYPE
   SYNTAX      INTEGER
               {
               disabled (0),
               enabled (1)
               }
   MAX-ACCESS  read-write
   STATUS      current
   DESCRIPTION
      "Path: vxLanBridgeGroup.editConf.pppoEClient.ipV6.dhcp.relay.mode

       Possibilities:
               disabled   (0)
               enabled   (1)"
   ::= {er1646v2VxlBGIMVpPppOEEntry 705323040}

er1646v2VxlBGIMVpPppOEIpV6SendRedirect OBJECT-TYPE
   SYNTAX      INTEGER
               {
               disabled (0),
               enabled (1)
               }
   MAX-ACCESS  read-write
   STATUS      current
   DESCRIPTION
      "Path: vxLanBridgeGroup.editConf.pppoEClient.ipV6.sendRedirect

       Possibilities:
               disabled   (0)
               enabled   (1)"
   ::= {er1646v2VxlBGIMVpPppOEEntry 705101824}

er1646v2VxlBGIMVpPppOEIpV6LinkMtu OBJECT-TYPE
   SYNTAX      Integer32
   MAX-ACCESS  read-write
   STATUS      current
   DESCRIPTION
      "Path: vxLanBridgeGroup.editConf.pppoEClient.ipV6.linkMtu"
   ::= {er1646v2VxlBGIMVpPppOEEntry 705167360}

er1646v2VxlBGIMVpPppOEIpV6InterfaceId OBJECT-TYPE
   SYNTAX      OCTET STRING
   MAX-ACCESS  read-write
   STATUS      current
   DESCRIPTION
      "Path: vxLanBridgeGroup.editConf.pppoEClient.ipV6.interfaceId"
   ::= {er1646v2VxlBGIMVpPppOEEntry 705232896}

er1646v2VxlBGIMVpPppOEIpV6MF OBJECT-TYPE
   SYNTAX      Integer32
   MAX-ACCESS  read-write
   STATUS      current
   DESCRIPTION
      "Path: vxLanBridgeGroup.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VxlBGIMVpPppOEEntry 705757184}

er1646v2VxlBGIMVpPppOEIpV6IcmpMessagesNoRoute OBJECT-TYPE
   SYNTAX      INTEGER
               {
               disabled (0),
               enabled (1)
               }
   MAX-ACCESS  read-write
   STATUS      current
   DESCRIPTION
      "Path: vxLanBridgeGroup.editConf.pppoEClient.ipV6.icmpMessages.noRoute

       Possibilities:
               disabled   (0)
               enabled   (1)"
   ::= {er1646v2VxlBGIMVpPppOEEntry 705822976}

er1646v2VxlBGIMVpPppOEIpV6IcmpMessagesBeyondScope OBJECT-TYPE
   SYNTAX      INTEGER
               {
               disabled (0),
               enabled (1)
               }
   MAX-ACCESS  read-write
   STATUS      current
   DESCRIPTION
      "Path: vxLanBridgeGroup.editConf.pppoEClient.ipV6.icmpMessages.beyondScope

       Possibilities:
               disabled   (0)
               enabled   (1)"
   ::= {er1646v2VxlBGIMVpPppOEEntry 705823488}

er1646v2VxlBGIMVpPppOEIpV6IcmpMessagesAddressUnreachable OBJECT-TYPE
   SYNTAX      INTEGER
               {
               disabled (0),
               enabled (1)
               }
   MAX-ACCESS  read-write
   STATUS      current
   DESCRIPTION
      "Path: vxLanBridgeGroup.editConf.pppoEClient.ipV6.icmpMessages.addressUnreachable

       Possibilities:
               disabled   (0)
               enabled   (1)"
   ::= {er1646v2VxlBGIMVpPppOEEntry 705823744}

er1646v2VxlBGIMVpPppOEIpV6IcmpMessagesPortUnreachable OBJECT-TYPE
   SYNTAX      INTEGER
               {
               disabled (0),
               enabled (1)
               }
   MAX-ACCESS  read-write
   STATUS      current
   DESCRIPTION
      "Path: vxLanBridgeGroup.editConf.pppoEClient.ipV6.icmpMessages.portUnreachable

       Possibilities:
               disabled   (0)
               enabled   (1)"
   ::= {er1646v2VxlBGIMVpPppOEEntry 705824000}

er1646v2VxlBGIMVpPppOEIpV6IcmpMessagesPacketTooBig OBJECT-TYPE
   SYNTAX      INTEGER
               {
               disabled (0),
               enabled (1)
               }
   MAX-ACCESS  read-write
   STATUS      current
   DESCRIPTION
      "Path: vxLanBridgeGroup.editConf.pppoEClient.ipV6.icmpMessages.packetTooBig

       Possibilities:
               disabled   (0)
               enabled   (1)"
   ::= {er1646v2VxlBGIMVpPppOEEntry 705825280}

er1646v2VxlBGIMVpPppOEIpV6IcmpMessagesHopLimitExceeded OBJECT-TYPE
   SYNTAX      INTEGER
               {
               disabled (0),
               enabled (1)
               }
   MAX-ACCESS  read-write
   STATUS      current
   DESCRIPTION
      "Path: vxLanBridgeGroup.editConf.pppoEClient.ipV6.icmpMessages.hopLimitExceeded

       Possibilities:
               disabled   (0)
               enabled   (1)"
   ::= {er1646v2VxlBGIMVpPppOEEntry 705827840}

er1646v2VxlBGIMVpPppOEIpV6IcmpMessagesFragTimeExceeded OBJECT-TYPE
   SYNTAX      INTEGER
               {
               disabled (0),
               enabled (1)
               }
   MAX-ACCESS  read-write
   STATUS      current
   DESCRIPTION
      "Path: vxLanBridgeGroup.editConf.pppoEClient.ipV6.icmpMessages.fragTimeExceeded

       Possibilities:
               disabled   (0)
               enabled   (1)"
   ::= {er1646v2VxlBGIMVpPppOEEntry 705828096}

er1646v2VxlBGIMVpPppOEIpV6IcmpMessagesHeaderFieldErr OBJECT-TYPE
   SYNTAX      INTEGER
               {
               disabled (0),
               enabled (1)
               }
   MAX-ACCESS  read-write
   STATUS      current
   DESCRIPTION
      "Path: vxLanBridgeGroup.editConf.pppoEClient.ipV6.icmpMessages.headerFieldErr

       Possibilities:
               disabled   (0)
               enabled   (1)"
   ::= {er1646v2VxlBGIMVpPppOEEntry 705830400}

er1646v2VxlBGIMVpPppOEIpV6IcmpMessagesOptionUnrecognized OBJECT-TYPE
   SYNTAX      INTEGER
               {
               disabled (0),
               enabled (1)
               }
   MAX-ACCESS  read-write
   STATUS      current
   DESCRIPTION
      "Path: vxLanBridgeGroup.editConf.pppoEClient.ipV6.icmpMessages.optionUnrecognized

       Possibilities:
               disabled   (0)
               enabled   (1)"
   ::= {er1646v2VxlBGIMVpPppOEEntry 705830912}

er1646v2VxlBGIMVpPppOEIpV6IcmpMessagesRedirect OBJECT-TYPE
   SYNTAX      INTEGER
               {
               disabled (0),
               enabled (1)
               }
   MAX-ACCESS  read-write
   STATUS      current
   DESCRIPTION
      "Path: vxLanBridgeGroup.editConf.pppoEClient.ipV6.icmpMessages.redirect

       Possibilities:
               disabled   (0)
               enabled   (1)"
   ::= {er1646v2VxlBGIMVpPppOEEntry 705832960}

er1646v2VxlBGIMVpPppOEPppLnkMOperation OBJECT-TYPE
   SYNTAX      INTEGER
               {
               disabled (0),
               enabled (1)
               }
   MAX-ACCESS  read-write
   STATUS      current
   DESCRIPTION
      "Path: vxLanBridgeGroup.editConf.pppoEClient.ppp.linkMonitoring.operation

       Possibilities:
               disabled   (0)
               enabled   (1)"
   ::= {er1646v2VxlBGIMVpPppOEEntry 251724032}

er1646v2VxlBGIMVpPppOEPppLnkMInterval OBJECT-TYPE
   SYNTAX      TimeTicks
   MAX-ACCESS  read-write
   STATUS      current
   DESCRIPTION
      "Path: vxLanBridgeGroup.editConf.pppoEClient.ppp.linkMonitoring.interval

       Time in centi-second."
   ::= {er1646v2VxlBGIMVpPppOEEntry 251724288}

er1646v2VxlBGIMVpPppOEPppLnkMRepTimeOut OBJECT-TYPE
   SYNTAX      TimeTicks
   MAX-ACCESS  read-write
   STATUS      current
   DESCRIPTION
      "Path: vxLanBridgeGroup.editConf.pppoEClient.ppp.linkMonitoring.replyTimeOut

       Time in centi-second."
   ::= {er1646v2VxlBGIMVpPppOEEntry 251724544}

er1646v2VxlBGIMVpPppOEPppLnkMFailsPrmt OBJECT-TYPE
   SYNTAX      Integer32
   MAX-ACCESS  read-write
   STATUS      current
   DESCRIPTION
      "Path: vxLanBridgeGroup.editConf.pppoEClient.ppp.linkMonitoring.failsPermitted"
   ::= {er1646v2VxlBGIMVpPppOEEntry 251724800}

er1646v2VxlBGIMVpPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: vxLanBridgeGroup.editConf.pppoEClient.ppp.authentication

       Possibilities:
               disabled   (0)
               chap   (1)
               pap   (2)
               chapOrPap   (3)
               msChap   (4)
               msChapV2   (5)"
   ::= {er1646v2VxlBGIMVpPppOEEntry 251789312}

er1646v2VxlBGIMVpPppOEPppAuthenPeriod OBJECT-TYPE
   SYNTAX      TimeTicks
   MAX-ACCESS  read-write
   STATUS      current
   DESCRIPTION
      "Path: vxLanBridgeGroup.editConf.pppoEClient.ppp.authenPeriod

       Time in centi-second."
   ::= {er1646v2VxlBGIMVpPppOEEntry 251854848}

er1646v2VxlBGIMVpPppOEPppSessionName OBJECT-TYPE
   SYNTAX      DisplayString
   MAX-ACCESS  read-write
   STATUS      current
   DESCRIPTION
      "Path: vxLanBridgeGroup.editConf.pppoEClient.ppp.sessionName"
   ::= {er1646v2VxlBGIMVpPppOEEntry 251985920}

er1646v2VxlBGIMVpPppOEPppSessionSecret OBJECT-TYPE
   SYNTAX      DisplayString
   MAX-ACCESS  read-write
   STATUS      current
   DESCRIPTION
      "Path: vxLanBridgeGroup.editConf.pppoEClient.ppp.sessionSecret"
   ::= {er1646v2VxlBGIMVpPppOEEntry 252051456}

er1646v2VxlBGIMVpPppOEPppEncModeSessionSecret OBJECT-TYPE
   SYNTAX      INTEGER
               {
               none (1),
               encrypt (2),
               encType1 (3),
               invalid (128)
               }
   MAX-ACCESS  read-write
   STATUS      current
   DESCRIPTION
      "Path: vxLanBridgeGroup.editConf.pppoEClient.ppp.encModeSessionSecret

       Possibilities:
               none   (1)
               encrypt   (2)
               encType1   (3)
               invalid   (128)"
   ::= {er1646v2VxlBGIMVpPppOEEntry 252182528}

er1646v2VxlBGIMVpPppOEPppEncSessionSecret OBJECT-TYPE
   SYNTAX      DisplayString
   MAX-ACCESS  read-write
   STATUS      current
   DESCRIPTION
      "Path: vxLanBridgeGroup.editConf.pppoEClient.ppp.encSessionSecret"
   ::= {er1646v2VxlBGIMVpPppOEEntry 252248064}

er1646v2VxlBGIMVpPppOEPppServiceName OBJECT-TYPE
   SYNTAX      DisplayString
   MAX-ACCESS  read-write
   STATUS      current
   DESCRIPTION
      "Path: vxLanBridgeGroup.editConf.pppoEClient.ppp.serviceName"
   ::= {er1646v2VxlBGIMVpPppOEEntry 252116992}

er1646v2VxlBGIMVpPppOEIpH OBJECT-TYPE
   SYNTAX      SEQUENCE OF Er1646v2VxlBGIMVpPppOEIpHEntry
   MAX-ACCESS  not-accessible
   STATUS      current
   DESCRIPTION
      ""
   ::= {er1646v2VxlBGIMVpPppOE 51314688}

er1646v2VxlBGIMVpPppOEIpHEntry OBJECT-TYPE
   SYNTAX      Er1646v2VxlBGIMVpPppOEIpHEntry
   MAX-ACCESS  not-accessible
   STATUS      current
   DESCRIPTION
      ""
   INDEX      { er1646v2VxlBGIMVpPppOEIpHGlobalIx,
                er1646v2VxlBGIMVpPppOETableIx,
                er1646v2VxlBGIMVpPppOEIpHTableIx }
   ::= {er1646v2VxlBGIMVpPppOEIpH 1}

Er1646v2VxlBGIMVpPppOEIpHEntry ::=
   SEQUENCE
      {
      er1646v2VxlBGIMVpPppOEIpHActions
         VariableLengthTableActions,
      er1646v2VxlBGIMVpPppOEIpHGlobalIx
         GlobalIndex,
      er1646v2VxlBGIMVpPppOEIpHTableIx
         TableIndex,
      er1646v2VxlBGIMVpPppOEIpHAddress
         IpAddress,
      er1646v2VxlBGIMVpPppOEIpHDhcpRelayOptionSubscriberId
         DisplayString
      }

er1646v2VxlBGIMVpPppOEIpHActions OBJECT-TYPE
   SYNTAX      VariableLengthTableActions
   MAX-ACCESS  read-write
   STATUS      current
   DESCRIPTION
      "By way of this field, some manipulations
       on this table may be performed."
   ::= {er1646v2VxlBGIMVpPppOEIpHEntry 2}

er1646v2VxlBGIMVpPppOEIpHGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpHEntry 10}

er1646v2VxlBGIMVpPppOEIpHTableIx OBJECT-TYPE
   SYNTAX      TableIndex
   MAX-ACCESS  not-accessible
   STATUS      current
   DESCRIPTION
      ""
   ::= {er1646v2VxlBGIMVpPppOEIpHEntry 11}

er1646v2VxlBGIMVpPppOEIpHAddress OBJECT-TYPE
   SYNTAX      IpAddress
   MAX-ACCESS  read-write
   STATUS      current
   DESCRIPTION
      "Path: vxLanBridgeGroup.editConf.pppoEClient.ip.helpers.address"
   ::= {er1646v2VxlBGIMVpPppOEIpHEntry 16777216}

er1646v2VxlBGIMVpPppOEIpHDhcpRelayOptionSubscriberId OBJECT-TYPE
   SYNTAX      DisplayString
   MAX-ACCESS  read-write
   STATUS      current
   DESCRIPTION
      "Path: vxLanBridgeGroup.editConf.pppoEClient.ip.helpers.dhcpRelayOption.subscriberId"
   ::= {er1646v2VxlBGIMVpPppOEIpHEntry 33947648}

er1646v2VxlBGIMVpPppOEIpV6Addresses OBJECT-TYPE
   SYNTAX      SEQUENCE OF Er1646v2VxlBGIMVpPppOEIpV6AddressesEntry
   MAX-ACCESS  not-accessible
   STATUS      current
   DESCRIPTION
      ""
   ::= {er1646v2VxlBGIMVpPppOE 704839680}

er1646v2VxlBGIMVpPppOEIpV6AddressesEntry OBJECT-TYPE
   SYNTAX      Er1646v2VxlBGIMVpPppOEIpV6AddressesEntry
   MAX-ACCESS  not-accessible
   STATUS      current
   DESCRIPTION
      ""
   INDEX      { er1646v2VxlBGIMVpPppOEIpV6AddressesGlobalIx,
                er1646v2VxlBGIMVpPppOETableIx,
                er1646v2VxlBGIMVpPppOEIpV6AddressesTableIx }
   ::= {er1646v2VxlBGIMVpPppOEIpV6Addresses 1}

Er1646v2VxlBGIMVpPppOEIpV6AddressesEntry ::=
   SEQUENCE
      {
      er1646v2VxlBGIMVpPppOEIpV6AddressesActions
         VariableLengthTableActions,
      er1646v2VxlBGIMVpPppOEIpV6AddressesGlobalIx
         GlobalIndex,
      er1646v2VxlBGIMVpPppOEIpV6AddressesTableIx
         TableIndex,
      er1646v2VxlBGIMVpPppOEIpV6AddressesType
         INTEGER,
      er1646v2VxlBGIMVpPppOEIpV6AddressesAddress
         Ipv6Address,
      er1646v2VxlBGIMVpPppOEIpV6AddressesPrefixLength
         Integer32,
      er1646v2VxlBGIMVpPppOEIpV6AddressesGeneralPrefix
         DisplayString,
      er1646v2VxlBGIMVpPppOEIpV6AddressesRaSend
         INTEGER,
      er1646v2VxlBGIMVpPppOEIpV6AddressesRaOnLinkFlag
         INTEGER,
      er1646v2VxlBGIMVpPppOEIpV6AddressesRaAutoFlag
         INTEGER,
      er1646v2VxlBGIMVpPppOEIpV6AddressesRaValidLifeTime
         TimeTicks,
      er1646v2VxlBGIMVpPppOEIpV6AddressesRaValidLTMode
         INTEGER,
      er1646v2VxlBGIMVpPppOEIpV6AddressesRaPrefLifeTime
         TimeTicks,
      er1646v2VxlBGIMVpPppOEIpV6AddressesRaPrefLTMode
         INTEGER
      }

er1646v2VxlBGIMVpPppOEIpV6AddressesActions OBJECT-TYPE
   SYNTAX      VariableLengthTableActions
   MAX-ACCESS  read-write
   STATUS      current
   DESCRIPTION
      "By way of this field, some manipulations
       on this table may be performed."
   ::= {er1646v2VxlBGIMVpPppOEIpV6AddressesEntry 2}

er1646v2VxlBGIMVpPppOEIpV6AddressesGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6AddressesEntry 10}

er1646v2VxlBGIMVpPppOEIpV6AddressesTableIx OBJECT-TYPE
   SYNTAX      TableIndex
   MAX-ACCESS  not-accessible
   STATUS      current
   DESCRIPTION
      ""
   ::= {er1646v2VxlBGIMVpPppOEIpV6AddressesEntry 11}

er1646v2VxlBGIMVpPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: vxLanBridgeGroup.editConf.pppoEClient.ipV6.addresses.type

       Possibilities:
               unicast   (0)
               eui64   (1)
               anycast   (2)
               linkLocal   (3)
               generalPrefix   (4)"
   ::= {er1646v2VxlBGIMVpPppOEIpV6AddressesEntry 50331648}

er1646v2VxlBGIMVpPppOEIpV6AddressesAddress OBJECT-TYPE
   SYNTAX      Ipv6Address
   MAX-ACCESS  read-write
   STATUS      current
   DESCRIPTION
      "Path: vxLanBridgeGroup.editConf.pppoEClient.ipV6.addresses.address

       ipv6 address"
   ::= {er1646v2VxlBGIMVpPppOEIpV6AddressesEntry 16777216}

er1646v2VxlBGIMVpPppOEIpV6AddressesPrefixLength OBJECT-TYPE
   SYNTAX      Integer32
   MAX-ACCESS  read-write
   STATUS      current
   DESCRIPTION
      "Path: vxLanBridgeGroup.editConf.pppoEClient.ipV6.addresses.prefixLength"
   ::= {er1646v2VxlBGIMVpPppOEIpV6AddressesEntry 33554432}

er1646v2VxlBGIMVpPppOEIpV6AddressesGeneralPrefix OBJECT-TYPE
   SYNTAX      DisplayString
   MAX-ACCESS  read-write
   STATUS      current
   DESCRIPTION
      "Path: vxLanBridgeGroup.editConf.pppoEClient.ipV6.addresses.generalPrefix"
   ::= {er1646v2VxlBGIMVpPppOEIpV6AddressesEntry 83886080}

er1646v2VxlBGIMVpPppOEIpV6AddressesRaSend OBJECT-TYPE
   SYNTAX      INTEGER
               {
               disabled (0),
               enabled (1)
               }
   MAX-ACCESS  read-write
   STATUS      current
   DESCRIPTION
      "Path: vxLanBridgeGroup.editConf.pppoEClient.ipV6.addresses.ra.send

       Possibilities:
               disabled   (0)
               enabled   (1)"
   ::= {er1646v2VxlBGIMVpPppOEIpV6AddressesEntry 67174400}

er1646v2VxlBGIMVpPppOEIpV6AddressesRaOnLinkFlag OBJECT-TYPE
   SYNTAX      INTEGER
               {
               disabled (0),
               enabled (1)
               }
   MAX-ACCESS  read-write
   STATUS      current
   DESCRIPTION
      "Path: vxLanBridgeGroup.editConf.pppoEClient.ipV6.addresses.ra.onLinkFlag

       Possibilities:
               disabled   (0)
               enabled   (1)"
   ::= {er1646v2VxlBGIMVpPppOEIpV6AddressesEntry 67371008}

er1646v2VxlBGIMVpPppOEIpV6AddressesRaAutoFlag OBJECT-TYPE
   SYNTAX      INTEGER
               {
               disabled (0),
               enabled (1)
               }
   MAX-ACCESS  read-write
   STATUS      current
   DESCRIPTION
      "Path: vxLanBridgeGroup.editConf.pppoEClient.ipV6.addresses.ra.autonomousFlag

       Possibilities:
               disabled   (0)
               enabled   (1)"
   ::= {er1646v2VxlBGIMVpPppOEIpV6AddressesEntry 67567616}

er1646v2VxlBGIMVpPppOEIpV6AddressesRaValidLifeTime OBJECT-TYPE
   SYNTAX      TimeTicks
   MAX-ACCESS  read-write
   STATUS      current
   DESCRIPTION
      "Path: vxLanBridgeGroup.editConf.pppoEClient.ipV6.addresses.ra.validLifeTime

       Time in centi-second."
   ::= {er1646v2VxlBGIMVpPppOEIpV6AddressesEntry 67239936}

er1646v2VxlBGIMVpPppOEIpV6AddressesRaValidLTMode OBJECT-TYPE
   SYNTAX      INTEGER
               {
               fixed (0),
               infinite (2)
               }
   MAX-ACCESS  read-write
   STATUS      current
   DESCRIPTION
      "Path: vxLanBridgeGroup.editConf.pppoEClient.ipV6.addresses.ra.validLifeTimeMode

       Possibilities:
               fixed   (0)
               infinite   (2)"
   ::= {er1646v2VxlBGIMVpPppOEIpV6AddressesEntry 67305472}

er1646v2VxlBGIMVpPppOEIpV6AddressesRaPrefLifeTime OBJECT-TYPE
   SYNTAX      TimeTicks
   MAX-ACCESS  read-write
   STATUS      current
   DESCRIPTION
      "Path: vxLanBridgeGroup.editConf.pppoEClient.ipV6.addresses.ra.prefLifeTime

       Time in centi-second."
   ::= {er1646v2VxlBGIMVpPppOEIpV6AddressesEntry 67436544}

er1646v2VxlBGIMVpPppOEIpV6AddressesRaPrefLTMode OBJECT-TYPE
   SYNTAX      INTEGER
               {
               fixed (0),
               infinite (2)
               }
   MAX-ACCESS  read-write
   STATUS      current
   DESCRIPTION
      "Path: vxLanBridgeGroup.editConf.pppoEClient.ipV6.addresses.ra.prefLifeTimeMode

       Possibilities:
               fixed   (0)
               infinite   (2)"
   ::= {er1646v2VxlBGIMVpPppOEIpV6AddressesEntry 67502080}

er1646v2VxlBGIMVpPppOEIpV6RaDnsOptionsRdnssServers OBJECT-TYPE
   SYNTAX      SEQUENCE OF Er1646v2VxlBGIMVpPppOEIpV6RaDnsOptionsRdnssServersEntry
   MAX-ACCESS  not-accessible
   STATUS      current
   DESCRIPTION
      ""
   ::= {er1646v2VxlBGIMVpPppOE 705039144}

er1646v2VxlBGIMVpPppOEIpV6RaDnsOptionsRdnssServersEntry OBJECT-TYPE
   SYNTAX      Er1646v2VxlBGIMVpPppOEIpV6RaDnsOptionsRdnssServersEntry
   MAX-ACCESS  not-accessible
   STATUS      current
   DESCRIPTION
      ""
   INDEX      { er1646v2VxlBGIMVpPppOEIpV6RaDnsOptionsRdnssServersGlobalIx,
                er1646v2VxlBGIMVpPppOETableIx,
                er1646v2VxlBGIMVpPppOEIpV6RaDnsOptionsRdnssServersTableIx }
   ::= {er1646v2VxlBGIMVpPppOEIpV6RaDnsOptionsRdnssServers 1}

Er1646v2VxlBGIMVpPppOEIpV6RaDnsOptionsRdnssServersEntry ::=
   SEQUENCE
      {
      er1646v2VxlBGIMVpPppOEIpV6RaDnsOptionsRdnssServersActions
         VariableLengthTableActions,
      er1646v2VxlBGIMVpPppOEIpV6RaDnsOptionsRdnssServersGlobalIx
         GlobalIndex,
      er1646v2VxlBGIMVpPppOEIpV6RaDnsOptionsRdnssServersTableIx
         TableIndex,
      er1646v2VxlBGIMVpPppOEIpV6RaDnsOptionsRdnssServersAddress
         Ipv6Address
      }

er1646v2VxlBGIMVpPppOEIpV6RaDnsOptionsRdnssServersActions OBJECT-TYPE
   SYNTAX      VariableLengthTableActions
   MAX-ACCESS  read-write
   STATUS      current
   DESCRIPTION
      "By way of this field, some manipulations
       on this table may be performed."
   ::= {er1646v2VxlBGIMVpPppOEIpV6RaDnsOptionsRdnssServersEntry 2}

er1646v2VxlBGIMVpPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6RaDnsOptionsRdnssServersEntry 10}

er1646v2VxlBGIMVpPppOEIpV6RaDnsOptionsRdnssServersTableIx OBJECT-TYPE
   SYNTAX      TableIndex
   MAX-ACCESS  not-accessible
   STATUS      current
   DESCRIPTION
      ""
   ::= {er1646v2VxlBGIMVpPppOEIpV6RaDnsOptionsRdnssServersEntry 11}

er1646v2VxlBGIMVpPppOEIpV6RaDnsOptionsRdnssServersAddress OBJECT-TYPE
   SYNTAX      Ipv6Address
   MAX-ACCESS  read-write
   STATUS      current
   DESCRIPTION
      "Path: vxLanBridgeGroup.editConf.pppoEClient.ipV6.ra.dnsOptions.rdnss.servers.address

       ipv6 address"
   ::= {er1646v2VxlBGIMVpPppOEIpV6RaDnsOptionsRdnssServersEntry 16777216}

er1646v2VxlBGIMVpPppOEIpV6RaDnsOptionsDnsslDomains OBJECT-TYPE
   SYNTAX      SEQUENCE OF Er1646v2VxlBGIMVpPppOEIpV6RaDnsOptionsDnsslDomainsEntry
   MAX-ACCESS  not-accessible
   STATUS      current
   DESCRIPTION
      ""
   ::= {er1646v2VxlBGIMVpPppOE 705039176}

er1646v2VxlBGIMVpPppOEIpV6RaDnsOptionsDnsslDomainsEntry OBJECT-TYPE
   SYNTAX      Er1646v2VxlBGIMVpPppOEIpV6RaDnsOptionsDnsslDomainsEntry
   MAX-ACCESS  not-accessible
   STATUS      current
   DESCRIPTION
      ""
   INDEX      { er1646v2VxlBGIMVpPppOEIpV6RaDnsOptionsDnsslDomainsGlobalIx,
                er1646v2VxlBGIMVpPppOETableIx,
                er1646v2VxlBGIMVpPppOEIpV6RaDnsOptionsDnsslDomainsTableIx }
   ::= {er1646v2VxlBGIMVpPppOEIpV6RaDnsOptionsDnsslDomains 1}

Er1646v2VxlBGIMVpPppOEIpV6RaDnsOptionsDnsslDomainsEntry ::=
   SEQUENCE
      {
      er1646v2VxlBGIMVpPppOEIpV6RaDnsOptionsDnsslDomainsActions
         VariableLengthTableActions,
      er1646v2VxlBGIMVpPppOEIpV6RaDnsOptionsDnsslDomainsGlobalIx
         GlobalIndex,
      er1646v2VxlBGIMVpPppOEIpV6RaDnsOptionsDnsslDomainsTableIx
         TableIndex,
      er1646v2VxlBGIMVpPppOEIpV6RaDnsOptionsDnsslDomainsName
         DisplayString
      }

er1646v2VxlBGIMVpPppOEIpV6RaDnsOptionsDnsslDomainsActions OBJECT-TYPE
   SYNTAX      VariableLengthTableActions
   MAX-ACCESS  read-write
   STATUS      current
   DESCRIPTION
      "By way of this field, some manipulations
       on this table may be performed."
   ::= {er1646v2VxlBGIMVpPppOEIpV6RaDnsOptionsDnsslDomainsEntry 2}

er1646v2VxlBGIMVpPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6RaDnsOptionsDnsslDomainsEntry 10}

er1646v2VxlBGIMVpPppOEIpV6RaDnsOptionsDnsslDomainsTableIx OBJECT-TYPE
   SYNTAX      TableIndex
   MAX-ACCESS  not-accessible
   STATUS      current
   DESCRIPTION
      ""
   ::= {er1646v2VxlBGIMVpPppOEIpV6RaDnsOptionsDnsslDomainsEntry 11}

er1646v2VxlBGIMVpPppOEIpV6RaDnsOptionsDnsslDomainsName OBJECT-TYPE
   SYNTAX      DisplayString
   MAX-ACCESS  read-write
   STATUS      current
   DESCRIPTION
      "Path: vxLanBridgeGroup.editConf.pppoEClient.ipV6.ra.dnsOptions.dnssl.domains.name"
   ::= {er1646v2VxlBGIMVpPppOEIpV6RaDnsOptionsDnsslDomainsEntry 16777216}

er1646v2VxlBGIMVpPppOEIpV6DhcpClientUserClassOpt OBJECT-TYPE
   SYNTAX      SEQUENCE OF Er1646v2VxlBGIMVpPppOEIpV6DhcpClientUserClassOptEntry
   MAX-ACCESS  not-accessible
   STATUS      current
   DESCRIPTION
      ""
   ::= {er1646v2VxlBGIMVpPppOE 705312768}

er1646v2VxlBGIMVpPppOEIpV6DhcpClientUserClassOptEntry OBJECT-TYPE
   SYNTAX      Er1646v2VxlBGIMVpPppOEIpV6DhcpClientUserClassOptEntry
   MAX-ACCESS  not-accessible
   STATUS      current
   DESCRIPTION
      ""
   INDEX      { er1646v2VxlBGIMVpPppOEIpV6DhcpClientUserClassOptGlobalIx,
                er1646v2VxlBGIMVpPppOETableIx,
                er1646v2VxlBGIMVpPppOEIpV6DhcpClientUserClassOptTableIx }
   ::= {er1646v2VxlBGIMVpPppOEIpV6DhcpClientUserClassOpt 1}

Er1646v2VxlBGIMVpPppOEIpV6DhcpClientUserClassOptEntry ::=
   SEQUENCE
      {
      er1646v2VxlBGIMVpPppOEIpV6DhcpClientUserClassOptActions
         VariableLengthTableActions,
      er1646v2VxlBGIMVpPppOEIpV6DhcpClientUserClassOptGlobalIx
         GlobalIndex,
      er1646v2VxlBGIMVpPppOEIpV6DhcpClientUserClassOptTableIx
         TableIndex,
      er1646v2VxlBGIMVpPppOEIpV6DhcpClientUserClassOptValueAscii
         DisplayString,
      er1646v2VxlBGIMVpPppOEIpV6DhcpClientUserClassOptValueDecimal
         Integer32,
      er1646v2VxlBGIMVpPppOEIpV6DhcpClientUserClassOptValueHexData
         OCTET STRING
      }

er1646v2VxlBGIMVpPppOEIpV6DhcpClientUserClassOptActions OBJECT-TYPE
   SYNTAX      VariableLengthTableActions
   MAX-ACCESS  read-write
   STATUS      current
   DESCRIPTION
      "By way of this field, some manipulations
       on this table may be performed."
   ::= {er1646v2VxlBGIMVpPppOEIpV6DhcpClientUserClassOptEntry 2}

er1646v2VxlBGIMVpPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6DhcpClientUserClassOptEntry 10}

er1646v2VxlBGIMVpPppOEIpV6DhcpClientUserClassOptTableIx OBJECT-TYPE
   SYNTAX      TableIndex
   MAX-ACCESS  not-accessible
   STATUS      current
   DESCRIPTION
      ""
   ::= {er1646v2VxlBGIMVpPppOEIpV6DhcpClientUserClassOptEntry 11}

er1646v2VxlBGIMVpPppOEIpV6DhcpClientUserClassOptValueAscii OBJECT-TYPE
   SYNTAX      DisplayString
   MAX-ACCESS  read-write
   STATUS      current
   DESCRIPTION
      "Path: vxLanBridgeGroup.editConf.pppoEClient.ipV6.dhcp.client.userClassOpt.value.ascii"
   ::= {er1646v2VxlBGIMVpPppOEIpV6DhcpClientUserClassOptEntry 16842752}

er1646v2VxlBGIMVpPppOEIpV6DhcpClientUserClassOptValueDecimal OBJECT-TYPE
   SYNTAX      Integer32
   MAX-ACCESS  read-write
   STATUS      current
   DESCRIPTION
      "Path: vxLanBridgeGroup.editConf.pppoEClient.ipV6.dhcp.client.userClassOpt.value.decimal"
   ::= {er1646v2VxlBGIMVpPppOEIpV6DhcpClientUserClassOptEntry 16908288}

er1646v2VxlBGIMVpPppOEIpV6DhcpClientUserClassOptValueHexData OBJECT-TYPE
   SYNTAX      OCTET STRING
   MAX-ACCESS  read-write
   STATUS      current
   DESCRIPTION
      "Path: vxLanBridgeGroup.editConf.pppoEClient.ipV6.dhcp.client.userClassOpt.value.hexData"
   ::= {er1646v2VxlBGIMVpPppOEIpV6DhcpClientUserClassOptEntry 16973824}

er1646v2VxlBGIMVpPppOEIpV6DhcpClientVendorCl OBJECT-TYPE
   SYNTAX      SEQUENCE OF Er1646v2VxlBGIMVpPppOEIpV6DhcpClientVendorClEntry
   MAX-ACCESS  not-accessible
   STATUS      current
   DESCRIPTION
      ""
   ::= {er1646v2VxlBGIMVpPppOE 705313792}

er1646v2VxlBGIMVpPppOEIpV6DhcpClientVendorClEntry OBJECT-TYPE
   SYNTAX      Er1646v2VxlBGIMVpPppOEIpV6DhcpClientVendorClEntry
   MAX-ACCESS  not-accessible
   STATUS      current
   DESCRIPTION
      ""
   INDEX      { er1646v2VxlBGIMVpPppOEIpV6DhcpClientVendorClGlobalIx,
                er1646v2VxlBGIMVpPppOETableIx,
                er1646v2VxlBGIMVpPppOEIpV6DhcpClientVendorClTableIx }
   ::= {er1646v2VxlBGIMVpPppOEIpV6DhcpClientVendorCl 1}

Er1646v2VxlBGIMVpPppOEIpV6DhcpClientVendorClEntry ::=
   SEQUENCE
      {
      er1646v2VxlBGIMVpPppOEIpV6DhcpClientVendorClActions
         VariableLengthTableActions,
      er1646v2VxlBGIMVpPppOEIpV6DhcpClientVendorClGlobalIx
         GlobalIndex,
      er1646v2VxlBGIMVpPppOEIpV6DhcpClientVendorClTableIx
         TableIndex,
      er1646v2VxlBGIMVpPppOEIpV6DhcpClientVendorClValueAscii
         DisplayString,
      er1646v2VxlBGIMVpPppOEIpV6DhcpClientVendorClValueDecimal
         Integer32,
      er1646v2VxlBGIMVpPppOEIpV6DhcpClientVendorClValueHexData
         OCTET STRING
      }

er1646v2VxlBGIMVpPppOEIpV6DhcpClientVendorClActions OBJECT-TYPE
   SYNTAX      VariableLengthTableActions
   MAX-ACCESS  read-write
   STATUS      current
   DESCRIPTION
      "By way of this field, some manipulations
       on this table may be performed."
   ::= {er1646v2VxlBGIMVpPppOEIpV6DhcpClientVendorClEntry 2}

er1646v2VxlBGIMVpPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6DhcpClientVendorClEntry 10}

er1646v2VxlBGIMVpPppOEIpV6DhcpClientVendorClTableIx OBJECT-TYPE
   SYNTAX      TableIndex
   MAX-ACCESS  not-accessible
   STATUS      current
   DESCRIPTION
      ""
   ::= {er1646v2VxlBGIMVpPppOEIpV6DhcpClientVendorClEntry 11}

er1646v2VxlBGIMVpPppOEIpV6DhcpClientVendorClValueAscii OBJECT-TYPE
   SYNTAX      DisplayString
   MAX-ACCESS  read-write
   STATUS      current
   DESCRIPTION
      "Path: vxLanBridgeGroup.editConf.pppoEClient.ipV6.dhcp.client.vendorClassOpt.value.ascii"
   ::= {er1646v2VxlBGIMVpPppOEIpV6DhcpClientVendorClEntry 16842752}

er1646v2VxlBGIMVpPppOEIpV6DhcpClientVendorClValueDecimal OBJECT-TYPE
   SYNTAX      Integer32
   MAX-ACCESS  read-write
   STATUS      current
   DESCRIPTION
      "Path: vxLanBridgeGroup.editConf.pppoEClient.ipV6.dhcp.client.vendorClassOpt.value.decimal"
   ::= {er1646v2VxlBGIMVpPppOEIpV6DhcpClientVendorClEntry 16908288}

er1646v2VxlBGIMVpPppOEIpV6DhcpClientVendorClValueHexData OBJECT-TYPE
   SYNTAX      OCTET STRING
   MAX-ACCESS  read-write
   STATUS      current
   DESCRIPTION
      "Path: vxLanBridgeGroup.editConf.pppoEClient.ipV6.dhcp.client.vendorClassOpt.value.hexData"
   ::= {er1646v2VxlBGIMVpPppOEIpV6DhcpClientVendorClEntry 16973824}

er1646v2VxlBGIMVpPppOEIpV6DhcpRelayDestinations OBJECT-TYPE
   SYNTAX      SEQUENCE OF Er1646v2VxlBGIMVpPppOEIpV6DhcpRelayDestinationsEntry
   MAX-ACCESS  not-accessible
   STATUS      current
   DESCRIPTION
      ""
   ::= {er1646v2VxlBGIMVpPppOE 705323072}

er1646v2VxlBGIMVpPppOEIpV6DhcpRelayDestinationsEntry OBJECT-TYPE
   SYNTAX      Er1646v2VxlBGIMVpPppOEIpV6DhcpRelayDestinationsEntry
   MAX-ACCESS  not-accessible
   STATUS      current
   DESCRIPTION
      ""
   INDEX      { er1646v2VxlBGIMVpPppOEIpV6DhcpRelayDestinationsGlobalIx,
                er1646v2VxlBGIMVpPppOETableIx,
                er1646v2VxlBGIMVpPppOEIpV6DhcpRelayDestinationsTableIx }
   ::= {er1646v2VxlBGIMVpPppOEIpV6DhcpRelayDestinations 1}

Er1646v2VxlBGIMVpPppOEIpV6DhcpRelayDestinationsEntry ::=
   SEQUENCE
      {
      er1646v2VxlBGIMVpPppOEIpV6DhcpRelayDestinationsActions
         VariableLengthTableActions,
      er1646v2VxlBGIMVpPppOEIpV6DhcpRelayDestinationsGlobalIx
         GlobalIndex,
      er1646v2VxlBGIMVpPppOEIpV6DhcpRelayDestinationsTableIx
         TableIndex,
      er1646v2VxlBGIMVpPppOEIpV6DhcpRelayDestinationsAddress
         Ipv6Address,
      er1646v2VxlBGIMVpPppOEIpV6DhcpRelayDestinationsInterface
         DisplayString
      }

er1646v2VxlBGIMVpPppOEIpV6DhcpRelayDestinationsActions OBJECT-TYPE
   SYNTAX      VariableLengthTableActions
   MAX-ACCESS  read-write
   STATUS      current
   DESCRIPTION
      "By way of this field, some manipulations
       on this table may be performed."
   ::= {er1646v2VxlBGIMVpPppOEIpV6DhcpRelayDestinationsEntry 2}

er1646v2VxlBGIMVpPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VxlBGIMVpPppOEIpV6DhcpRelayDestinationsEntry 10}

er1646v2VxlBGIMVpPppOEIpV6DhcpRelayDestinationsTableIx OBJECT-TYPE
   SYNTAX      TableIndex
   MAX-ACCESS  not-accessible
   STATUS      current
   DESCRIPTION
      ""
   ::= {er1646v2VxlBGIMVpPppOEIpV6DhcpRelayDestinationsEntry 11}

er1646v2VxlBGIMVpPppOEIpV6DhcpRelayDestinationsAddress OBJECT-TYPE
   SYNTAX      Ipv6Address
   MAX-ACCESS  read-write
   STATUS      current
   DESCRIPTION
      "Path: vxLanBridgeGroup.editConf.pppoEClient.ipV6.dhcp.relay.destinations.address

       ipv6 address"
   ::= {er1646v2VxlBGIMVpPppOEIpV6DhcpRelayDestinationsEntry 16777216}

er1646v2VxlBGIMVpPppOEIpV6DhcpRelayDestinationsInterface OBJECT-TYPE
   SYNTAX      DisplayString
   MAX-ACCESS  read-write
   STATUS      current
   DESCRIPTION
      "Path: vxLanBridgeGroup.editConf.pppoEClient.ipV6.dhcp.relay.destinations.interface"
   ::= {er1646v2VxlBGIMVpPppOEIpV6DhcpRelayDestinationsEntry 33554432}


er1646v2VxlBGIMVpMacAddress OBJECT IDENTIFIER ::= {er1646v2VxlBGIMVp 27}

er1646v2VxlBGIMVpMacAddressSSCTable OBJECT-TYPE
   SYNTAX      SEQUENCE OF Er1646v2VxlBGIMVpMacAddressEntry
   MAX-ACCESS  not-accessible
   STATUS      current
   DESCRIPTION
      "Configurable MAC address of Bridge group"
   ::= {er1646v2VxlBGIMVpMacAddress 1}

er1646v2VxlBGIMVpMacAddressEntry OBJECT-TYPE
   SYNTAX      Er1646v2VxlBGIMVpMacAddressEntry
   MAX-ACCESS  not-accessible
   STATUS      current
   DESCRIPTION
      ""
   INDEX      { er1646v2VxlBGIMVpMacAddressGlobalIx }
   ::= {er1646v2VxlBGIMVpMacAddressSSCTable 1}

Er1646v2VxlBGIMVpMacAddressEntry ::=
   SEQUENCE
      {
      er1646v2VxlBGIMVpMacAddressGlobalIx
         GlobalIndex,
      er1646v2VxlBGIMVpMacAddressDeviceMac
         DisplayString,
      er1646v2VxlBGIMVpMacAddressUserMac
         OCTET STRING,
      er1646v2VxlBGIMVpMacAddressRandomMac
         Integer32
      }

er1646v2VxlBGIMVpMacAddressGlobalIx OBJECT-TYPE
   SYNTAX      GlobalIndex
   MAX-ACCESS  not-accessible
   STATUS      current
   DESCRIPTION
      "The value of the tlsCntTreeGlobalIndex of the MANAGED OBJECT."
   ::= {er1646v2VxlBGIMVpMacAddressEntry 10}

er1646v2VxlBGIMVpMacAddressDeviceMac OBJECT-TYPE
   SYNTAX      DisplayString
   MAX-ACCESS  read-write
   STATUS      current
   DESCRIPTION
      "Path: vxLanBridgeGroup.editConf.macAddress.deviceMac"
   ::= {er1646v2VxlBGIMVpMacAddressEntry 50331648}

er1646v2VxlBGIMVpMacAddressUserMac OBJECT-TYPE
   SYNTAX      OCTET STRING
   MAX-ACCESS  read-write
   STATUS      current
   DESCRIPTION
      "Path: vxLanBridgeGroup.editConf.macAddress.userMac

       MAC address."
   ::= {er1646v2VxlBGIMVpMacAddressEntry 33554432}

er1646v2VxlBGIMVpMacAddressRandomMac OBJECT-TYPE
   SYNTAX      Integer32
   MAX-ACCESS  read-write
   STATUS      current
   DESCRIPTION
      "Path: vxLanBridgeGroup.editConf.macAddress.randomMac"
   ::= {er1646v2VxlBGIMVpMacAddressEntry 67108864}


er1646v2VxlBGIMVpSnmpIndexOffset OBJECT IDENTIFIER ::= {er1646v2VxlBGIMVp 268}

er1646v2VxlBGIMVpSnmpIndexOffsetTable OBJECT-TYPE
   SYNTAX      SEQUENCE OF Er1646v2VxlBGIMVpSnmpIndexOffsetEntry
   MAX-ACCESS  not-accessible
   STATUS      current
   DESCRIPTION
      "Preferred offset in the range of SNMP indices for this SWinst, 0 means automatic"
   ::= {er1646v2VxlBGIMVpSnmpIndexOffset 1}

er1646v2VxlBGIMVpSnmpIndexOffsetEntry OBJECT-TYPE
   SYNTAX      Er1646v2VxlBGIMVpSnmpIndexOffsetEntry
   MAX-ACCESS  not-accessible
   STATUS      current
   DESCRIPTION
      ""
   INDEX      { er1646v2VxlBGIMVpSnmpIndexOffsetGlobalIx }
   ::= {er1646v2VxlBGIMVpSnmpIndexOffsetTable 1}

Er1646v2VxlBGIMVpSnmpIndexOffsetEntry ::=
   SEQUENCE
      {
      er1646v2VxlBGIMVpSnmpIndexOffsetGlobalIx
         GlobalIndex,
      er1646v2VxlBGIMVpSnmpIndexOffsetValue
         Integer32
      }

er1646v2VxlBGIMVpSnmpIndexOffsetGlobalIx OBJECT-TYPE
   SYNTAX      GlobalIndex
   MAX-ACCESS  not-accessible
   STATUS      current
   DESCRIPTION
      "The value of the tlsCntTreeGlobalIndex of the MANAGED OBJECT."
   ::= {er1646v2VxlBGIMVpSnmpIndexOffsetEntry 10}

er1646v2VxlBGIMVpSnmpIndexOffsetValue OBJECT-TYPE
   SYNTAX      Integer32
   MAX-ACCESS  read-write
   STATUS      current
   DESCRIPTION
      "Path: vxLanBridgeGroup.editConf.snmpIndexOffset"
   ::= {er1646v2VxlBGIMVpSnmpIndexOffsetEntry 2147483648}



sr1646v2VxlBGIMVp OBJECT IDENTIFIER ::= {r1646v2VxlBGIMVp 14}


sr1646v2VxlBGIMVpBridgeCacheSize OBJECT IDENTIFIER ::= {sr1646v2VxlBGIMVp 39}

sr1646v2VxlBGIMVpBridgeCacheSizeSSCTable OBJECT-TYPE
   SYNTAX      SEQUENCE OF Sr1646v2VxlBGIMVpBridgeCacheSizeEntry
   MAX-ACCESS  not-accessible
   STATUS      current
   DESCRIPTION
      "bridge cache size info"
   ::= {sr1646v2VxlBGIMVpBridgeCacheSize 1}

sr1646v2VxlBGIMVpBridgeCacheSizeEntry OBJECT-TYPE
   SYNTAX      Sr1646v2VxlBGIMVpBridgeCacheSizeEntry
   MAX-ACCESS  not-accessible
   STATUS      current
   DESCRIPTION
      ""
   INDEX      { sr1646v2VxlBGIMVpBridgeCacheSizeGlobalIx }
   ::= {sr1646v2VxlBGIMVpBridgeCacheSizeSSCTable 1}

Sr1646v2VxlBGIMVpBridgeCacheSizeEntry ::=
   SEQUENCE
      {
      sr1646v2VxlBGIMVpBridgeCacheSizeGlobalIx
         GlobalIndex,
      sr1646v2VxlBGIMVpBridgeCacheSizeSize
         Counter32,
      sr1646v2VxlBGIMVpBridgeCacheSizeMaxSize
         INTEGER
      }

sr1646v2VxlBGIMVpBridgeCacheSizeGlobalIx OBJECT-TYPE
   SYNTAX      GlobalIndex
   MAX-ACCESS  not-accessible
   STATUS      current
   DESCRIPTION
      "The value of the tlsCntTreeGlobalIndex of the MANAGED OBJECT."
   ::= {sr1646v2VxlBGIMVpBridgeCacheSizeEntry 10}

sr1646v2VxlBGIMVpBridgeCacheSizeSize OBJECT-TYPE
   SYNTAX      Counter32
   MAX-ACCESS  read-only
   STATUS      current
   DESCRIPTION
      "Path: vxLanBridgeGroup.status.bridgeCacheSize.size

       32 bit unsigned wrappable counter."
   ::= {sr1646v2VxlBGIMVpBridgeCacheSizeEntry 16777216}

sr1646v2VxlBGIMVpBridgeCacheSizeMaxSize OBJECT-TYPE
   SYNTAX      INTEGER
               {
               unlimited (0)
               }
   MAX-ACCESS  read-only
   STATUS      current
   DESCRIPTION
      "Path: vxLanBridgeGroup.status.bridgeCacheSize.maxSize

       Possibilities:
               unlimited   (0)"
   ::= {sr1646v2VxlBGIMVpBridgeCacheSizeEntry 33554432}


sr1646v2VxlBGIMVpMacAddress OBJECT IDENTIFIER ::= {sr1646v2VxlBGIMVp 105}

sr1646v2VxlBGIMVpMacAddressTable OBJECT-TYPE
   SYNTAX      SEQUENCE OF Sr1646v2VxlBGIMVpMacAddressEntry
   MAX-ACCESS  not-accessible
   STATUS      current
   DESCRIPTION
      "ifPhysAddress"
   ::= {sr1646v2VxlBGIMVpMacAddress 1}

sr1646v2VxlBGIMVpMacAddressEntry OBJECT-TYPE
   SYNTAX      Sr1646v2VxlBGIMVpMacAddressEntry
   MAX-ACCESS  not-accessible
   STATUS      current
   DESCRIPTION
      ""
   INDEX      { sr1646v2VxlBGIMVpMacAddressGlobalIx }
   ::= {sr1646v2VxlBGIMVpMacAddressTable 1}

Sr1646v2VxlBGIMVpMacAddressEntry ::=
   SEQUENCE
      {
      sr1646v2VxlBGIMVpMacAddressGlobalIx
         GlobalIndex,
      sr1646v2VxlBGIMVpMacAddressValue
         OCTET STRING
      }

sr1646v2VxlBGIMVpMacAddressGlobalIx OBJECT-TYPE
   SYNTAX      GlobalIndex
   MAX-ACCESS  not-accessible
   STATUS      current
   DESCRIPTION
      "The value of the tlsCntTreeGlobalIndex of the MANAGED OBJECT."
   ::= {sr1646v2VxlBGIMVpMacAddressEntry 10}

sr1646v2VxlBGIMVpMacAddressValue OBJECT-TYPE
   SYNTAX      OCTET STRING
   MAX-ACCESS  read-only
   STATUS      current
   DESCRIPTION
      "Path: vxLanBridgeGroup.status.macAddress

       MAC address."
   ::= {sr1646v2VxlBGIMVpMacAddressEntry 2147483648}


sr1646v2VxlBGIMVpDescr OBJECT IDENTIFIER ::= {sr1646v2VxlBGIMVp 101}

sr1646v2VxlBGIMVpDescrTable OBJECT-TYPE
   SYNTAX      SEQUENCE OF Sr1646v2VxlBGIMVpDescrEntry
   MAX-ACCESS  not-accessible
   STATUS      current
   DESCRIPTION
      "ifDescr"
   ::= {sr1646v2VxlBGIMVpDescr 1}

sr1646v2VxlBGIMVpDescrEntry OBJECT-TYPE
   SYNTAX      Sr1646v2VxlBGIMVpDescrEntry
   MAX-ACCESS  not-accessible
   STATUS      current
   DESCRIPTION
      ""
   INDEX      { sr1646v2VxlBGIMVpDescrGlobalIx }
   ::= {sr1646v2VxlBGIMVpDescrTable 1}

Sr1646v2VxlBGIMVpDescrEntry ::=
   SEQUENCE
      {
      sr1646v2VxlBGIMVpDescrGlobalIx
         GlobalIndex,
      sr1646v2VxlBGIMVpDescrValue
         DisplayString
      }

sr1646v2VxlBGIMVpDescrGlobalIx OBJECT-TYPE
   SYNTAX      GlobalIndex
   MAX-ACCESS  not-accessible
   STATUS      current
   DESCRIPTION
      "The value of the tlsCntTreeGlobalIndex of the MANAGED OBJECT."
   ::= {sr1646v2VxlBGIMVpDescrEntry 10}

sr1646v2VxlBGIMVpDescrValue OBJECT-TYPE
   SYNTAX      DisplayString
   MAX-ACCESS  read-only
   STATUS      current
   DESCRIPTION
      "Path: vxLanBridgeGroup.status.ifDescr"
   ::= {sr1646v2VxlBGIMVpDescrEntry 2147483648}


sr1646v2VxlBGIMVpType OBJECT IDENTIFIER ::= {sr1646v2VxlBGIMVp 102}

sr1646v2VxlBGIMVpTypeTable OBJECT-TYPE
   SYNTAX      SEQUENCE OF Sr1646v2VxlBGIMVpTypeEntry
   MAX-ACCESS  not-accessible
   STATUS      current
   DESCRIPTION
      "ifType"
   ::= {sr1646v2VxlBGIMVpType 1}

sr1646v2VxlBGIMVpTypeEntry OBJECT-TYPE
   SYNTAX      Sr1646v2VxlBGIMVpTypeEntry
   MAX-ACCESS  not-accessible
   STATUS      current
   DESCRIPTION
      ""
   INDEX      { sr1646v2VxlBGIMVpTypeGlobalIx }
   ::= {sr1646v2VxlBGIMVpTypeTable 1}

Sr1646v2VxlBGIMVpTypeEntry ::=
   SEQUENCE
      {
      sr1646v2VxlBGIMVpTypeGlobalIx
         GlobalIndex,
      sr1646v2VxlBGIMVpTypeValue
         INTEGER
      }

sr1646v2VxlBGIMVpTypeGlobalIx OBJECT-TYPE
   SYNTAX      GlobalIndex
   MAX-ACCESS  not-accessible
   STATUS      current
   DESCRIPTION
      "The value of the tlsCntTreeGlobalIndex of the MANAGED OBJECT."
   ::= {sr1646v2VxlBGIMVpTypeEntry 10}

sr1646v2VxlBGIMVpTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: vxLanBridgeGroup.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2VxlBGIMVpTypeEntry 2147483648}


sr1646v2VxlBGIMVpMtu OBJECT IDENTIFIER ::= {sr1646v2VxlBGIMVp 103}

sr1646v2VxlBGIMVpMtuTable OBJECT-TYPE
   SYNTAX      SEQUENCE OF Sr1646v2VxlBGIMVpMtuEntry
   MAX-ACCESS  not-accessible
   STATUS      current
   DESCRIPTION
      "ifMtu"
   ::= {sr1646v2VxlBGIMVpMtu 1}

sr1646v2VxlBGIMVpMtuEntry OBJECT-TYPE
   SYNTAX      Sr1646v2VxlBGIMVpMtuEntry
   MAX-ACCESS  not-accessible
   STATUS      current
   DESCRIPTION
      ""
   INDEX      { sr1646v2VxlBGIMVpMtuGlobalIx }
   ::= {sr1646v2VxlBGIMVpMtuTable 1}

Sr1646v2VxlBGIMVpMtuEntry ::=
   SEQUENCE
      {
      sr1646v2VxlBGIMVpMtuGlobalIx
         GlobalIndex,
      sr1646v2VxlBGIMVpMtuValue
         Integer32
      }

sr1646v2VxlBGIMVpMtuGlobalIx OBJECT-TYPE
   SYNTAX      GlobalIndex
   MAX-ACCESS  not-accessible
   STATUS      current
   DESCRIPTION
      "The value of the tlsCntTreeGlobalIndex of the MANAGED OBJECT."
   ::= {sr1646v2VxlBGIMVpMtuEntry 10}

sr1646v2VxlBGIMVpMtuValue OBJECT-TYPE
   SYNTAX      Integer32
   MAX-ACCESS  read-only
   STATUS      current
   DESCRIPTION
      "Path: vxLanBridgeGroup.status.ifMtu"
   ::= {sr1646v2VxlBGIMVpMtuEntry 2147483648}


sr1646v2VxlBGIMVpOperStatus OBJECT IDENTIFIER ::= {sr1646v2VxlBGIMVp 107}

sr1646v2VxlBGIMVpOperStatusTable OBJECT-TYPE
   SYNTAX      SEQUENCE OF Sr1646v2VxlBGIMVpOperStatusEntry
   MAX-ACCESS  not-accessible
   STATUS      current
   DESCRIPTION
      "ifOperStatus"
   ::= {sr1646v2VxlBGIMVpOperStatus 1}

sr1646v2VxlBGIMVpOperStatusEntry OBJECT-TYPE
   SYNTAX      Sr1646v2VxlBGIMVpOperStatusEntry
   MAX-ACCESS  not-accessible
   STATUS      current
   DESCRIPTION
      ""
   INDEX      { sr1646v2VxlBGIMVpOperStatusGlobalIx }
   ::= {sr1646v2VxlBGIMVpOperStatusTable 1}

Sr1646v2VxlBGIMVpOperStatusEntry ::=
   SEQUENCE
      {
      sr1646v2VxlBGIMVpOperStatusGlobalIx
         GlobalIndex,
      sr1646v2VxlBGIMVpOperStatusValue
         INTEGER
      }

sr1646v2VxlBGIMVpOperStatusGlobalIx OBJECT-TYPE
   SYNTAX      GlobalIndex
   MAX-ACCESS  not-accessible
   STATUS      current
   DESCRIPTION
      "The value of the tlsCntTreeGlobalIndex of the MANAGED OBJECT."
   ::= {sr1646v2VxlBGIMVpOperStatusEntry 10}

sr1646v2VxlBGIMVpOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vxLanBridgeGroup.status.ifOperStatus

       Possibilities:
               up   (1)
               down   (2)
               testing   (3)
               unknown   (4)
               dormant   (5)
               notPresent   (6)
               lowerLayerDown   (7)"
   ::= {sr1646v2VxlBGIMVpOperStatusEntry 2147483648}


sr1646v2VxlBGIMVpIp OBJECT IDENTIFIER ::= {sr1646v2VxlBGIMVp 11}

sr1646v2VxlBGIMVpIpSSCTable OBJECT-TYPE
   SYNTAX      SEQUENCE OF Sr1646v2VxlBGIMVpIpEntry
   MAX-ACCESS  not-accessible
   STATUS      current
   DESCRIPTION
      "Ip status parameters of a bridge gateway"
   ::= {sr1646v2VxlBGIMVpIp 1}

sr1646v2VxlBGIMVpIpEntry OBJECT-TYPE
   SYNTAX      Sr1646v2VxlBGIMVpIpEntry
   MAX-ACCESS  not-accessible
   STATUS      current
   DESCRIPTION
      ""
   INDEX      { sr1646v2VxlBGIMVpIpGlobalIx }
   ::= {sr1646v2VxlBGIMVpIpSSCTable 1}

Sr1646v2VxlBGIMVpIpEntry ::=
   SEQUENCE
      {
      sr1646v2VxlBGIMVpIpGlobalIx
         GlobalIndex,
      sr1646v2VxlBGIMVpIpAddress
         IpAddress,
      sr1646v2VxlBGIMVpIpNetMask
         IpAddress,
      sr1646v2VxlBGIMVpIpDhcpStatus
         INTEGER,
      sr1646v2VxlBGIMVpIpDhcpLeaseTime
         TimeTicks
      }

sr1646v2VxlBGIMVpIpGlobalIx OBJECT-TYPE
   SYNTAX      GlobalIndex
   MAX-ACCESS  not-accessible
   STATUS      current
   DESCRIPTION
      "The value of the tlsCntTreeGlobalIndex of the MANAGED OBJECT."
   ::= {sr1646v2VxlBGIMVpIpEntry 10}

sr1646v2VxlBGIMVpIpAddress OBJECT-TYPE
   SYNTAX      IpAddress
   MAX-ACCESS  read-only
   STATUS      current
   DESCRIPTION
      "Path: vxLanBridgeGroup.status.ip.address"
   ::= {sr1646v2VxlBGIMVpIpEntry 268435456}

sr1646v2VxlBGIMVpIpNetMask OBJECT-TYPE
   SYNTAX      IpAddress
   MAX-ACCESS  read-only
   STATUS      current
   DESCRIPTION
      "Path: vxLanBridgeGroup.status.ip.netMask"
   ::= {sr1646v2VxlBGIMVpIpEntry 285212672}

sr1646v2VxlBGIMVpIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: vxLanBridgeGroup.status.ip.dhcp.status

       Possibilities:
               none   (0)
               selecting   (1)
               requesting   (2)
               rebinding   (3)
               bound   (4)
               renewing   (5)
               rebooting   (6)
               initreboot   (7)"
   ::= {sr1646v2VxlBGIMVpIpEntry 402718720}

sr1646v2VxlBGIMVpIpDhcpLeaseTime OBJECT-TYPE
   SYNTAX      TimeTicks
   MAX-ACCESS  read-only
   STATUS      current
   DESCRIPTION
      "Path: vxLanBridgeGroup.status.ip.dhcp.leaseTime

       Time in centi-second."
   ::= {sr1646v2VxlBGIMVpIpEntry 402784256}

sr1646v2VxlBGIMVpIpSecondaryIp OBJECT-TYPE
   SYNTAX      SEQUENCE OF Sr1646v2VxlBGIMVpIpSecondaryIpEntry
   MAX-ACCESS  not-accessible
   STATUS      current
   DESCRIPTION
      ""
   ::= {sr1646v2VxlBGIMVpIp 385875968}

sr1646v2VxlBGIMVpIpSecondaryIpEntry OBJECT-TYPE
   SYNTAX      Sr1646v2VxlBGIMVpIpSecondaryIpEntry
   MAX-ACCESS  not-accessible
   STATUS      current
   DESCRIPTION
      ""
   INDEX      { sr1646v2VxlBGIMVpIpSecondaryIpGlobalIx,
                sr1646v2VxlBGIMVpIpSecondaryIpTableIx }
   ::= {sr1646v2VxlBGIMVpIpSecondaryIp 1}

Sr1646v2VxlBGIMVpIpSecondaryIpEntry ::=
   SEQUENCE
      {
      sr1646v2VxlBGIMVpIpSecondaryIpGlobalIx
         GlobalIndex,
      sr1646v2VxlBGIMVpIpSecondaryIpTableIx
         TableIndex,
      sr1646v2VxlBGIMVpIpSecondaryIpAddress
         IpAddress,
      sr1646v2VxlBGIMVpIpSecondaryIpNetMask
         IpAddress
      }

sr1646v2VxlBGIMVpIpSecondaryIpGlobalIx OBJECT-TYPE
   SYNTAX      GlobalIndex
   MAX-ACCESS  not-accessible
   STATUS      current
   DESCRIPTION
      "The value of the tlsCntTreeGlobalIndex of the MANAGED OBJECT."
   ::= {sr1646v2VxlBGIMVpIpSecondaryIpEntry 10}

sr1646v2VxlBGIMVpIpSecondaryIpTableIx OBJECT-TYPE
   SYNTAX      TableIndex
   MAX-ACCESS  not-accessible
   STATUS      current
   DESCRIPTION
      ""
   ::= {sr1646v2VxlBGIMVpIpSecondaryIpEntry 11}

sr1646v2VxlBGIMVpIpSecondaryIpAddress OBJECT-TYPE
   SYNTAX      IpAddress
   MAX-ACCESS  read-only
   STATUS      current
   DESCRIPTION
      "Path: vxLanBridgeGroup.status.ip.secondaryIp.address"
   ::= {sr1646v2VxlBGIMVpIpSecondaryIpEntry 2030043136}

sr1646v2VxlBGIMVpIpSecondaryIpNetMask OBJECT-TYPE
   SYNTAX      IpAddress
   MAX-ACCESS  read-only
   STATUS      current
   DESCRIPTION
      "Path: vxLanBridgeGroup.status.ip.secondaryIp.netMask"
   ::= {sr1646v2VxlBGIMVpIpSecondaryIpEntry 2063597568}


sr1646v2VxlBGIMVpIpV6 OBJECT IDENTIFIER ::= {sr1646v2VxlBGIMVp 22}

sr1646v2VxlBGIMVpIpV6SSCTable OBJECT-TYPE
   SYNTAX      SEQUENCE OF Sr1646v2VxlBGIMVpIpV6Entry
   MAX-ACCESS  not-accessible
   STATUS      current
   DESCRIPTION
      "IPv6 interface config parameters"
   ::= {sr1646v2VxlBGIMVpIpV6 1}

sr1646v2VxlBGIMVpIpV6Entry OBJECT-TYPE
   SYNTAX      Sr1646v2VxlBGIMVpIpV6Entry
   MAX-ACCESS  not-accessible
   STATUS      current
   DESCRIPTION
      ""
   INDEX      { sr1646v2VxlBGIMVpIpV6GlobalIx }
   ::= {sr1646v2VxlBGIMVpIpV6SSCTable 1}

Sr1646v2VxlBGIMVpIpV6Entry ::=
   SEQUENCE
      {
      sr1646v2VxlBGIMVpIpV6GlobalIx
         GlobalIndex,
      sr1646v2VxlBGIMVpIpV6State
         INTEGER,
      sr1646v2VxlBGIMVpIpV6InterfaceId
         OCTET STRING,
      sr1646v2VxlBGIMVpIpV6LinkMtu
         Integer32,
      sr1646v2VxlBGIMVpIpV6HopLimit
         Integer32,
      sr1646v2VxlBGIMVpIpV6DhcpIaid
         Counter32,
      sr1646v2VxlBGIMVpIpV6RaRcvOption
         Integer32
      }

sr1646v2VxlBGIMVpIpV6GlobalIx OBJECT-TYPE
   SYNTAX      GlobalIndex
   MAX-ACCESS  not-accessible
   STATUS      current
   DESCRIPTION
      "The value of the tlsCntTreeGlobalIndex of the MANAGED OBJECT."
   ::= {sr1646v2VxlBGIMVpIpV6Entry 10}

sr1646v2VxlBGIMVpIpV6State OBJECT-TYPE
   SYNTAX      INTEGER
               {
               disabled (0),
               enabled (1)
               }
   MAX-ACCESS  read-only
   STATUS      current
   DESCRIPTION
      "Path: vxLanBridgeGroup.status.ipV6.state

       Possibilities:
               disabled   (0)
               enabled   (1)"
   ::= {sr1646v2VxlBGIMVpIpV6Entry 16777216}

sr1646v2VxlBGIMVpIpV6InterfaceId OBJECT-TYPE
   SYNTAX      OCTET STRING
   MAX-ACCESS  read-only
   STATUS      current
   DESCRIPTION
      "Path: vxLanBridgeGroup.status.ipV6.interfaceId"
   ::= {sr1646v2VxlBGIMVpIpV6Entry 33554432}

sr1646v2VxlBGIMVpIpV6LinkMtu OBJECT-TYPE
   SYNTAX      Integer32
   MAX-ACCESS  read-only
   STATUS      current
   DESCRIPTION
      "Path: vxLanBridgeGroup.status.ipV6.linkMtu"
   ::= {sr1646v2VxlBGIMVpIpV6Entry 67108864}

sr1646v2VxlBGIMVpIpV6HopLimit OBJECT-TYPE
   SYNTAX      Integer32
   MAX-ACCESS  read-only
   STATUS      current
   DESCRIPTION
      "Path: vxLanBridgeGroup.status.ipV6.hopLimit"
   ::= {sr1646v2VxlBGIMVpIpV6Entry 83886080}

sr1646v2VxlBGIMVpIpV6DhcpIaid OBJECT-TYPE
   SYNTAX      Counter32
   MAX-ACCESS  read-only
   STATUS      current
   DESCRIPTION
      "Path: vxLanBridgeGroup.status.ipV6.dhcp.iaid

       32 bit unsigned wrappable counter."
   ::= {sr1646v2VxlBGIMVpIpV6Entry 100728832}

sr1646v2VxlBGIMVpIpV6RaRcvOption OBJECT-TYPE
   SYNTAX      Integer32
   MAX-ACCESS  read-only
   STATUS      current
   DESCRIPTION
      "Path: vxLanBridgeGroup.status.ipV6.raRcvOption

       Bit meanings:
               bit 0 = linkMtu,
               bit 1 = srcLinkLayer,
               bit 2 = prefixInfo,
               bit 3 = rdnss,
               bit 4 = dnssl"
   ::= {sr1646v2VxlBGIMVpIpV6Entry 117440512}

sr1646v2VxlBGIMVpIpV6Addresses OBJECT-TYPE
   SYNTAX      SEQUENCE OF Sr1646v2VxlBGIMVpIpV6AddressesEntry
   MAX-ACCESS  not-accessible
   STATUS      current
   DESCRIPTION
      ""
   ::= {sr1646v2VxlBGIMVpIpV6 50331648}

sr1646v2VxlBGIMVpIpV6AddressesEntry OBJECT-TYPE
   SYNTAX      Sr1646v2VxlBGIMVpIpV6AddressesEntry
   MAX-ACCESS  not-accessible
   STATUS      current
   DESCRIPTION
      ""
   INDEX      { sr1646v2VxlBGIMVpIpV6AddressesGlobalIx,
                sr1646v2VxlBGIMVpIpV6AddressesTableIx }
   ::= {sr1646v2VxlBGIMVpIpV6Addresses 1}

Sr1646v2VxlBGIMVpIpV6AddressesEntry ::=
   SEQUENCE
      {
      sr1646v2VxlBGIMVpIpV6AddressesGlobalIx
         GlobalIndex,
      sr1646v2VxlBGIMVpIpV6AddressesTableIx
         TableIndex,
      sr1646v2VxlBGIMVpIpV6AddressesAddress
         Ipv6Address,
      sr1646v2VxlBGIMVpIpV6AddressesPrefixLength
         Integer32,
      sr1646v2VxlBGIMVpIpV6AddressesStatus
         INTEGER,
      sr1646v2VxlBGIMVpIpV6AddressesOrigin
         INTEGER,
      sr1646v2VxlBGIMVpIpV6AddressesFlagsInterfaceId
         INTEGER,
      sr1646v2VxlBGIMVpIpV6AddressesFlagsAnycast
         INTEGER,
      sr1646v2VxlBGIMVpIpV6AddressesTimersValidLifeTime
         TimeTicks,
      sr1646v2VxlBGIMVpIpV6AddressesTimersPrefLifeTime
         TimeTicks
      }

sr1646v2VxlBGIMVpIpV6AddressesGlobalIx OBJECT-TYPE
   SYNTAX      GlobalIndex
   MAX-ACCESS  not-accessible
   STATUS      current
   DESCRIPTION
      "The value of the tlsCntTreeGlobalIndex of the MANAGED OBJECT."
   ::= {sr1646v2VxlBGIMVpIpV6AddressesEntry 10}

sr1646v2VxlBGIMVpIpV6AddressesTableIx OBJECT-TYPE
   SYNTAX      TableIndex
   MAX-ACCESS  not-accessible
   STATUS      current
   DESCRIPTION
      ""
   ::= {sr1646v2VxlBGIMVpIpV6AddressesEntry 11}

sr1646v2VxlBGIMVpIpV6AddressesAddress OBJECT-TYPE
   SYNTAX      Ipv6Address
   MAX-ACCESS  read-only
   STATUS      current
   DESCRIPTION
      "Path: vxLanBridgeGroup.status.ipV6.addresses.address

       ipv6 address"
   ::= {sr1646v2VxlBGIMVpIpV6AddressesEntry 16777216}

sr1646v2VxlBGIMVpIpV6AddressesPrefixLength OBJECT-TYPE
   SYNTAX      Integer32
   MAX-ACCESS  read-only
   STATUS      current
   DESCRIPTION
      "Path: vxLanBridgeGroup.status.ipV6.addresses.prefixLength"
   ::= {sr1646v2VxlBGIMVpIpV6AddressesEntry 33554432}

sr1646v2VxlBGIMVpIpV6AddressesStatus OBJECT-TYPE
   SYNTAX      INTEGER
               {
               invalid (0),
               tentative (1),
               deprecated (2),
               preferred (3)
               }
   MAX-ACCESS  read-only
   STATUS      current
   DESCRIPTION
      "Path: vxLanBridgeGroup.status.ipV6.addresses.status

       Possibilities:
               invalid   (0)
               tentative   (1)
               deprecated   (2)
               preferred   (3)"
   ::= {sr1646v2VxlBGIMVpIpV6AddressesEntry 50331648}

sr1646v2VxlBGIMVpIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vxLanBridgeGroup.status.ipV6.addresses.origin

       Possibilities:
               unknown   (0)
               manual   (1)
               generalPrefix   (2)
               statelessAuto   (3)
               statefullAuto   (4)"
   ::= {sr1646v2VxlBGIMVpIpV6AddressesEntry 67108864}

sr1646v2VxlBGIMVpIpV6AddressesFlagsInterfaceId OBJECT-TYPE
   SYNTAX      INTEGER
               {
               no (0),
               yes (1)
               }
   MAX-ACCESS  read-only
   STATUS      current
   DESCRIPTION
      "Path: vxLanBridgeGroup.status.ipV6.addresses.flags.interfaceId

       Possibilities:
               no   (0)
               yes   (1)"
   ::= {sr1646v2VxlBGIMVpIpV6AddressesEntry 83951616}

sr1646v2VxlBGIMVpIpV6AddressesFlagsAnycast OBJECT-TYPE
   SYNTAX      INTEGER
               {
               no (0),
               yes (1)
               }
   MAX-ACCESS  read-only
   STATUS      current
   DESCRIPTION
      "Path: vxLanBridgeGroup.status.ipV6.addresses.flags.anycast

       Possibilities:
               no   (0)
               yes   (1)"
   ::= {sr1646v2VxlBGIMVpIpV6AddressesEntry 84017152}

sr1646v2VxlBGIMVpIpV6AddressesTimersValidLifeTime OBJECT-TYPE
   SYNTAX      TimeTicks
   MAX-ACCESS  read-only
   STATUS      current
   DESCRIPTION
      "Path: vxLanBridgeGroup.status.ipV6.addresses.timers.validLifeTime

       Time in centi-second."
   ::= {sr1646v2VxlBGIMVpIpV6AddressesEntry 100794368}

sr1646v2VxlBGIMVpIpV6AddressesTimersPrefLifeTime OBJECT-TYPE
   SYNTAX      TimeTicks
   MAX-ACCESS  read-only
   STATUS      current
   DESCRIPTION
      "Path: vxLanBridgeGroup.status.ipV6.addresses.timers.prefLifeTime

       Time in centi-second."
   ::= {sr1646v2VxlBGIMVpIpV6AddressesEntry 100728832}


sr1646v2VxlBGIMVpStp OBJECT IDENTIFIER ::= {sr1646v2VxlBGIMVp 9}

sr1646v2VxlBGIMVpStpSSCTable OBJECT-TYPE
   SYNTAX      SEQUENCE OF Sr1646v2VxlBGIMVpStpEntry
   MAX-ACCESS  not-accessible
   STATUS      current
   DESCRIPTION
      "spanning tree info on bridge group"
   ::= {sr1646v2VxlBGIMVpStp 1}

sr1646v2VxlBGIMVpStpEntry OBJECT-TYPE
   SYNTAX      Sr1646v2VxlBGIMVpStpEntry
   MAX-ACCESS  not-accessible
   STATUS      current
   DESCRIPTION
      ""
   INDEX      { sr1646v2VxlBGIMVpStpGlobalIx }
   ::= {sr1646v2VxlBGIMVpStpSSCTable 1}

Sr1646v2VxlBGIMVpStpEntry ::=
   SEQUENCE
      {
      sr1646v2VxlBGIMVpStpGlobalIx
         GlobalIndex,
      sr1646v2VxlBGIMVpStpBridgePriority
         Integer32,
      sr1646v2VxlBGIMVpStpBridgeMacAddress
         OCTET STRING,
      sr1646v2VxlBGIMVpStpBridgeTimesMessageAge
         TimeTicks,
      sr1646v2VxlBGIMVpStpBridgeTimesMaxAge
         TimeTicks,
      sr1646v2VxlBGIMVpStpBridgeTimesForwardDelay
         TimeTicks,
      sr1646v2VxlBGIMVpStpBridgeTimesNrHops
         Integer32,
      sr1646v2VxlBGIMVpStpRootBridgeIdPriority
         Integer32,
      sr1646v2VxlBGIMVpStpRootBridgeIdMacAddress
         OCTET STRING,
      sr1646v2VxlBGIMVpStpRootPortId
         Integer32,
      sr1646v2VxlBGIMVpStpExtRootPathCost
         Integer32,
      sr1646v2VxlBGIMVpStpIntRootPathCost
         Integer32,
      sr1646v2VxlBGIMVpStpMstConfigIdFormatSelector
         Integer32,
      sr1646v2VxlBGIMVpStpMstConfigIdName
         DisplayString,
      sr1646v2VxlBGIMVpStpMstConfigIdRevisionLevel
         Integer32,
      sr1646v2VxlBGIMVpStpMstConfigIdDigest
         OCTET STRING
      }

sr1646v2VxlBGIMVpStpGlobalIx OBJECT-TYPE
   SYNTAX      GlobalIndex
   MAX-ACCESS  not-accessible
   STATUS      current
   DESCRIPTION
      "The value of the tlsCntTreeGlobalIndex of the MANAGED OBJECT."
   ::= {sr1646v2VxlBGIMVpStpEntry 10}

sr1646v2VxlBGIMVpStpBridgePriority OBJECT-TYPE
   SYNTAX      Integer32
   MAX-ACCESS  read-only
   STATUS      current
   DESCRIPTION
      "Path: vxLanBridgeGroup.status.spanningTree.bridgePriority"
   ::= {sr1646v2VxlBGIMVpStpEntry 16777216}

sr1646v2VxlBGIMVpStpBridgeMacAddress OBJECT-TYPE
   SYNTAX      OCTET STRING
   MAX-ACCESS  read-only
   STATUS      current
   DESCRIPTION
      "Path: vxLanBridgeGroup.status.spanningTree.bridgeMacAddress

       MAC address."
   ::= {sr1646v2VxlBGIMVpStpEntry 33554432}

sr1646v2VxlBGIMVpStpBridgeTimesMessageAge OBJECT-TYPE
   SYNTAX      TimeTicks
   MAX-ACCESS  read-only
   STATUS      current
   DESCRIPTION
      "Path: vxLanBridgeGroup.status.spanningTree.bridgeTimes.messageAge

       Time in centi-second."
   ::= {sr1646v2VxlBGIMVpStpEntry 50397184}

sr1646v2VxlBGIMVpStpBridgeTimesMaxAge OBJECT-TYPE
   SYNTAX      TimeTicks
   MAX-ACCESS  read-only
   STATUS      current
   DESCRIPTION
      "Path: vxLanBridgeGroup.status.spanningTree.bridgeTimes.maxAge

       Time in centi-second."
   ::= {sr1646v2VxlBGIMVpStpEntry 50462720}

sr1646v2VxlBGIMVpStpBridgeTimesForwardDelay OBJECT-TYPE
   SYNTAX      TimeTicks
   MAX-ACCESS  read-only
   STATUS      current
   DESCRIPTION
      "Path: vxLanBridgeGroup.status.spanningTree.bridgeTimes.forwardDelay

       Time in centi-second."
   ::= {sr1646v2VxlBGIMVpStpEntry 50528256}

sr1646v2VxlBGIMVpStpBridgeTimesNrHops OBJECT-TYPE
   SYNTAX      Integer32
   MAX-ACCESS  read-only
   STATUS      current
   DESCRIPTION
      "Path: vxLanBridgeGroup.status.spanningTree.bridgeTimes.nrHops"
   ::= {sr1646v2VxlBGIMVpStpEntry 50593792}

sr1646v2VxlBGIMVpStpRootBridgeIdPriority OBJECT-TYPE
   SYNTAX      Integer32
   MAX-ACCESS  read-only
   STATUS      current
   DESCRIPTION
      "Path: vxLanBridgeGroup.status.spanningTree.rootBridgeId.priority"
   ::= {sr1646v2VxlBGIMVpStpEntry 67174400}

sr1646v2VxlBGIMVpStpRootBridgeIdMacAddress OBJECT-TYPE
   SYNTAX      OCTET STRING
   MAX-ACCESS  read-only
   STATUS      current
   DESCRIPTION
      "Path: vxLanBridgeGroup.status.spanningTree.rootBridgeId.macAddress

       MAC address."
   ::= {sr1646v2VxlBGIMVpStpEntry 67239936}

sr1646v2VxlBGIMVpStpRootPortId OBJECT-TYPE
   SYNTAX      Integer32
   MAX-ACCESS  read-only
   STATUS      current
   DESCRIPTION
      "Path: vxLanBridgeGroup.status.spanningTree.rootPortId"
   ::= {sr1646v2VxlBGIMVpStpEntry 83886080}

sr1646v2VxlBGIMVpStpExtRootPathCost OBJECT-TYPE
   SYNTAX      Integer32
   MAX-ACCESS  read-only
   STATUS      current
   DESCRIPTION
      "Path: vxLanBridgeGroup.status.spanningTree.extRootPathCost"
   ::= {sr1646v2VxlBGIMVpStpEntry 100663296}

sr1646v2VxlBGIMVpStpIntRootPathCost OBJECT-TYPE
   SYNTAX      Integer32
   MAX-ACCESS  read-only
   STATUS      current
   DESCRIPTION
      "Path: vxLanBridgeGroup.status.spanningTree.intRootPathCost"
   ::= {sr1646v2VxlBGIMVpStpEntry 117440512}

sr1646v2VxlBGIMVpStpMstConfigIdFormatSelector OBJECT-TYPE
   SYNTAX      Integer32
   MAX-ACCESS  read-only
   STATUS      current
   DESCRIPTION
      "Path: vxLanBridgeGroup.status.spanningTree.mstConfigId.formatSelector"
   ::= {sr1646v2VxlBGIMVpStpEntry 134283264}

sr1646v2VxlBGIMVpStpMstConfigIdName OBJECT-TYPE
   SYNTAX      DisplayString
   MAX-ACCESS  read-only
   STATUS      current
   DESCRIPTION
      "Path: vxLanBridgeGroup.status.spanningTree.mstConfigId.name"
   ::= {sr1646v2VxlBGIMVpStpEntry 134348800}

sr1646v2VxlBGIMVpStpMstConfigIdRevisionLevel OBJECT-TYPE
   SYNTAX      Integer32
   MAX-ACCESS  read-only
   STATUS      current
   DESCRIPTION
      "Path: vxLanBridgeGroup.status.spanningTree.mstConfigId.revisionLevel"
   ::= {sr1646v2VxlBGIMVpStpEntry 134414336}

sr1646v2VxlBGIMVpStpMstConfigIdDigest OBJECT-TYPE
   SYNTAX      OCTET STRING
   MAX-ACCESS  read-only
   STATUS      current
   DESCRIPTION
      "Path: vxLanBridgeGroup.status.spanningTree.mstConfigId.digest"
   ::= {sr1646v2VxlBGIMVpStpEntry 134479872}


sr1646v2VxlBGIMVpArpCache OBJECT IDENTIFIER ::= {sr1646v2VxlBGIMVp 13}

sr1646v2VxlBGIMVpArpCacheSSCTable OBJECT-TYPE
   SYNTAX      SEQUENCE OF Sr1646v2VxlBGIMVpArpCacheEntry
   MAX-ACCESS  not-accessible
   STATUS      current
   DESCRIPTION
      "arp cache of ethernet interface"
   ::= {sr1646v2VxlBGIMVpArpCache 1}

sr1646v2VxlBGIMVpArpCacheEntry OBJECT-TYPE
   SYNTAX      Sr1646v2VxlBGIMVpArpCacheEntry
   MAX-ACCESS  not-accessible
   STATUS      current
   DESCRIPTION
      ""
   INDEX      { sr1646v2VxlBGIMVpArpCacheGlobalIx,
                sr1646v2VxlBGIMVpArpCacheTableIx }
   ::= {sr1646v2VxlBGIMVpArpCacheSSCTable 1}

Sr1646v2VxlBGIMVpArpCacheEntry ::=
   SEQUENCE
      {
      sr1646v2VxlBGIMVpArpCacheGlobalIx
         GlobalIndex,
      sr1646v2VxlBGIMVpArpCacheTableIx
         TableIndex,
      sr1646v2VxlBGIMVpArpCacheMacAddress
         OCTET STRING,
      sr1646v2VxlBGIMVpArpCacheIpAddress
         IpAddress,
      sr1646v2VxlBGIMVpArpCacheType
         INTEGER,
      sr1646v2VxlBGIMVpArpCacheTimeOut
         TimeTicks
      }

sr1646v2VxlBGIMVpArpCacheGlobalIx OBJECT-TYPE
   SYNTAX      GlobalIndex
   MAX-ACCESS  not-accessible
   STATUS      current
   DESCRIPTION
      "The value of the tlsCntTreeGlobalIndex of the MANAGED OBJECT."
   ::= {sr1646v2VxlBGIMVpArpCacheEntry 10}

sr1646v2VxlBGIMVpArpCacheTableIx OBJECT-TYPE
   SYNTAX      TableIndex
   MAX-ACCESS  not-accessible
   STATUS      current
   DESCRIPTION
      ""
   ::= {sr1646v2VxlBGIMVpArpCacheEntry 11}

sr1646v2VxlBGIMVpArpCacheMacAddress OBJECT-TYPE
   SYNTAX      OCTET STRING
   MAX-ACCESS  read-only
   STATUS      current
   DESCRIPTION
      "Path: vxLanBridgeGroup.status.arpCache.macAddress

       MAC address."
   ::= {sr1646v2VxlBGIMVpArpCacheEntry 16777216}

sr1646v2VxlBGIMVpArpCacheIpAddress OBJECT-TYPE
   SYNTAX      IpAddress
   MAX-ACCESS  read-only
   STATUS      current
   DESCRIPTION
      "Path: vxLanBridgeGroup.status.arpCache.ipAddress"
   ::= {sr1646v2VxlBGIMVpArpCacheEntry 33554432}

sr1646v2VxlBGIMVpArpCacheType OBJECT-TYPE
   SYNTAX      INTEGER
               {
               static (0),
               dynamic (1)
               }
   MAX-ACCESS  read-only
   STATUS      current
   DESCRIPTION
      "Path: vxLanBridgeGroup.status.arpCache.type

       Possibilities:
               static   (0)
               dynamic   (1)"
   ::= {sr1646v2VxlBGIMVpArpCacheEntry 50331648}

sr1646v2VxlBGIMVpArpCacheTimeOut OBJECT-TYPE
   SYNTAX      TimeTicks
   MAX-ACCESS  read-only
   STATUS      current
   DESCRIPTION
      "Path: vxLanBridgeGroup.status.arpCache.timeOut

       Time in centi-second."
   ::= {sr1646v2VxlBGIMVpArpCacheEntry 67108864}


sr1646v2VxlBGIMVpVlan OBJECT IDENTIFIER ::= {sr1646v2VxlBGIMVp 34}

sr1646v2VxlBGIMVpVlanSSCTable OBJECT-TYPE
   SYNTAX      SEQUENCE OF Sr1646v2VxlBGIMVpVlanEntry
   MAX-ACCESS  not-accessible
   STATUS      current
   DESCRIPTION
      ""
   ::= {sr1646v2VxlBGIMVpVlan 1}

sr1646v2VxlBGIMVpVlanEntry OBJECT-TYPE
   SYNTAX      Sr1646v2VxlBGIMVpVlanEntry
   MAX-ACCESS  not-accessible
   STATUS      current
   DESCRIPTION
      ""
   INDEX      { sr1646v2VxlBGIMVpVlanGlobalIx,
                sr1646v2VxlBGIMVpVlanTableIx }
   ::= {sr1646v2VxlBGIMVpVlanSSCTable 1}

Sr1646v2VxlBGIMVpVlanEntry ::=
   SEQUENCE
      {
      sr1646v2VxlBGIMVpVlanGlobalIx
         GlobalIndex,
      sr1646v2VxlBGIMVpVlanTableIx
         TableIndex,
      sr1646v2VxlBGIMVpVlanName
         DisplayString,
      sr1646v2VxlBGIMVpVlanMode
         INTEGER,
      sr1646v2VxlBGIMVpVlanIfOperStatus
         INTEGER,
      sr1646v2VxlBGIMVpVlanIfLastChange
         TimeTicks,
      sr1646v2VxlBGIMVpVlanIfLastChangeDate
         DisplayString,
      sr1646v2VxlBGIMVpVlanIpAddress
         IpAddress,
      sr1646v2VxlBGIMVpVlanIpNetMask
         IpAddress,
      sr1646v2VxlBGIMVpVlanIpDhcpStatus
         INTEGER,
      sr1646v2VxlBGIMVpVlanIpDhcpLeaseTime
         TimeTicks,
      sr1646v2VxlBGIMVpVlanIpV6State
         INTEGER,
      sr1646v2VxlBGIMVpVlanIpV6InterfaceId
         OCTET STRING,
      sr1646v2VxlBGIMVpVlanIpV6LinkMtu
         Integer32,
      sr1646v2VxlBGIMVpVlanIpV6HopLimit
         Integer32,
      sr1646v2VxlBGIMVpVlanIpV6DhcpIaid
         Counter32,
      sr1646v2VxlBGIMVpVlanIpV6RaRcvOption
         Integer32,
      sr1646v2VxlBGIMVpVlanVlanVid
         Integer32
      }

sr1646v2VxlBGIMVpVlanGlobalIx OBJECT-TYPE
   SYNTAX      GlobalIndex
   MAX-ACCESS  not-accessible
   STATUS      current
   DESCRIPTION
      "The value of the tlsCntTreeGlobalIndex of the MANAGED OBJECT."
   ::= {sr1646v2VxlBGIMVpVlanEntry 10}

sr1646v2VxlBGIMVpVlanTableIx OBJECT-TYPE
   SYNTAX      TableIndex
   MAX-ACCESS  not-accessible
   STATUS      current
   DESCRIPTION
      ""
   ::= {sr1646v2VxlBGIMVpVlanEntry 11}

sr1646v2VxlBGIMVpVlanName OBJECT-TYPE
   SYNTAX      DisplayString
   MAX-ACCESS  read-only
   STATUS      current
   DESCRIPTION
      "Path: vxLanBridgeGroup.status.vlan.name"
   ::= {sr1646v2VxlBGIMVpVlanEntry 16777216}

sr1646v2VxlBGIMVpVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: vxLanBridgeGroup.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2VxlBGIMVpVlanEntry 335544320}

sr1646v2VxlBGIMVpVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vxLanBridgeGroup.status.vlan.ifOperStatus

       Possibilities:
               up   (1)
               down   (2)
               testing   (3)
               unknown   (4)
               dormant   (5)
               notPresent   (6)
               lowerLayerDown   (7)"
   ::= {sr1646v2VxlBGIMVpVlanEntry 1795162112}

sr1646v2VxlBGIMVpVlanIfLastChange OBJECT-TYPE
   SYNTAX      TimeTicks
   MAX-ACCESS  read-only
   STATUS      current
   DESCRIPTION
      "Path: vxLanBridgeGroup.status.vlan.ifLastChange

       Time in centi-second."
   ::= {sr1646v2VxlBGIMVpVlanEntry 1811939328}

sr1646v2VxlBGIMVpVlanIfLastChangeDate OBJECT-TYPE
   SYNTAX      DisplayString
   MAX-ACCESS  read-only
   STATUS      current
   DESCRIPTION
      "Path: vxLanBridgeGroup.status.vlan.ifLastChangeDate"
   ::= {sr1646v2VxlBGIMVpVlanEntry 3070230528}

sr1646v2VxlBGIMVpVlanIpAddress OBJECT-TYPE
   SYNTAX      IpAddress
   MAX-ACCESS  read-only
   STATUS      current
   DESCRIPTION
      "Path: vxLanBridgeGroup.status.vlan.ip.address"
   ::= {sr1646v2VxlBGIMVpVlanEntry 51380224}

sr1646v2VxlBGIMVpVlanIpNetMask OBJECT-TYPE
   SYNTAX      IpAddress
   MAX-ACCESS  read-only
   STATUS      current
   DESCRIPTION
      "Path: vxLanBridgeGroup.status.vlan.ip.netMask"
   ::= {sr1646v2VxlBGIMVpVlanEntry 51445760}

sr1646v2VxlBGIMVpVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: vxLanBridgeGroup.status.vlan.ip.dhcp.status

       Possibilities:
               none   (0)
               selecting   (1)
               requesting   (2)
               rebinding   (3)
               bound   (4)
               renewing   (5)
               rebooting   (6)
               initreboot   (7)"
   ::= {sr1646v2VxlBGIMVpVlanEntry 51904768}

sr1646v2VxlBGIMVpVlanIpDhcpLeaseTime OBJECT-TYPE
   SYNTAX      TimeTicks
   MAX-ACCESS  read-only
   STATUS      current
   DESCRIPTION
      "Path: vxLanBridgeGroup.status.vlan.ip.dhcp.leaseTime

       Time in centi-second."
   ::= {sr1646v2VxlBGIMVpVlanEntry 51905024}

sr1646v2VxlBGIMVpVlanIpV6State OBJECT-TYPE
   SYNTAX      INTEGER
               {
               disabled (0),
               enabled (1)
               }
   MAX-ACCESS  read-only
   STATUS      current
   DESCRIPTION
      "Path: vxLanBridgeGroup.status.vlan.ipV6.state

       Possibilities:
               disabled   (0)
               enabled   (1)"
   ::= {sr1646v2VxlBGIMVpVlanEntry 100728832}

sr1646v2VxlBGIMVpVlanIpV6InterfaceId OBJECT-TYPE
   SYNTAX      OCTET STRING
   MAX-ACCESS  read-only
   STATUS      current
   DESCRIPTION
      "Path: vxLanBridgeGroup.status.vlan.ipV6.interfaceId"
   ::= {sr1646v2VxlBGIMVpVlanEntry 100794368}

sr1646v2VxlBGIMVpVlanIpV6LinkMtu OBJECT-TYPE
   SYNTAX      Integer32
   MAX-ACCESS  read-only
   STATUS      current
   DESCRIPTION
      "Path: vxLanBridgeGroup.status.vlan.ipV6.linkMtu"
   ::= {sr1646v2VxlBGIMVpVlanEntry 100925440}

sr1646v2VxlBGIMVpVlanIpV6HopLimit OBJECT-TYPE
   SYNTAX      Integer32
   MAX-ACCESS  read-only
   STATUS      current
   DESCRIPTION
      "Path: vxLanBridgeGroup.status.vlan.ipV6.hopLimit"
   ::= {sr1646v2VxlBGIMVpVlanEntry 100990976}

sr1646v2VxlBGIMVpVlanIpV6DhcpIaid OBJECT-TYPE
   SYNTAX      Counter32
   MAX-ACCESS  read-only
   STATUS      current
   DESCRIPTION
      "Path: vxLanBridgeGroup.status.vlan.ipV6.dhcp.iaid

       32 bit unsigned wrappable counter."
   ::= {sr1646v2VxlBGIMVpVlanEntry 101056768}

sr1646v2VxlBGIMVpVlanIpV6RaRcvOption OBJECT-TYPE
   SYNTAX      Integer32
   MAX-ACCESS  read-only
   STATUS      current
   DESCRIPTION
      "Path: vxLanBridgeGroup.status.vlan.ipV6.raRcvOption

       Bit meanings:
               bit 0 = linkMtu,
               bit 1 = srcLinkLayer,
               bit 2 = prefixInfo,
               bit 3 = rdnss,
               bit 4 = dnssl"
   ::= {sr1646v2VxlBGIMVpVlanEntry 101122048}

sr1646v2VxlBGIMVpVlanVlanVid OBJECT-TYPE
   SYNTAX      Integer32
   MAX-ACCESS  read-only
   STATUS      current
   DESCRIPTION
      "Path: vxLanBridgeGroup.status.vlan.vlan.vid"
   ::= {sr1646v2VxlBGIMVpVlanEntry 234946560}

sr1646v2VxlBGIMVpVlanIpSecondaryIp OBJECT-TYPE
   SYNTAX      SEQUENCE OF Sr1646v2VxlBGIMVpVlanIpSecondaryIpEntry
   MAX-ACCESS  not-accessible
   STATUS      current
   DESCRIPTION
      ""
   ::= {sr1646v2VxlBGIMVpVlan 51838976}

sr1646v2VxlBGIMVpVlanIpSecondaryIpEntry OBJECT-TYPE
   SYNTAX      Sr1646v2VxlBGIMVpVlanIpSecondaryIpEntry
   MAX-ACCESS  not-accessible
   STATUS      current
   DESCRIPTION
      ""
   INDEX      { sr1646v2VxlBGIMVpVlanIpSecondaryIpGlobalIx,
                sr1646v2VxlBGIMVpVlanTableIx,
                sr1646v2VxlBGIMVpVlanIpSecondaryIpTableIx }
   ::= {sr1646v2VxlBGIMVpVlanIpSecondaryIp 1}

Sr1646v2VxlBGIMVpVlanIpSecondaryIpEntry ::=
   SEQUENCE
      {
      sr1646v2VxlBGIMVpVlanIpSecondaryIpGlobalIx
         GlobalIndex,
      sr1646v2VxlBGIMVpVlanIpSecondaryIpTableIx
         TableIndex,
      sr1646v2VxlBGIMVpVlanIpSecondaryIpAddress
         IpAddress,
      sr1646v2VxlBGIMVpVlanIpSecondaryIpNetMask
         IpAddress
      }

sr1646v2VxlBGIMVpVlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2VxlBGIMVpVlanIpSecondaryIpEntry 10}

sr1646v2VxlBGIMVpVlanIpSecondaryIpTableIx OBJECT-TYPE
   SYNTAX      TableIndex
   MAX-ACCESS  not-accessible
   STATUS      current
   DESCRIPTION
      ""
   ::= {sr1646v2VxlBGIMVpVlanIpSecondaryIpEntry 11}

sr1646v2VxlBGIMVpVlanIpSecondaryIpAddress OBJECT-TYPE
   SYNTAX      IpAddress
   MAX-ACCESS  read-only
   STATUS      current
   DESCRIPTION
      "Path: vxLanBridgeGroup.status.vlan.ip.secondaryIp.address"
   ::= {sr1646v2VxlBGIMVpVlanIpSecondaryIpEntry 2030043136}

sr1646v2VxlBGIMVpVlanIpSecondaryIpNetMask OBJECT-TYPE
   SYNTAX      IpAddress
   MAX-ACCESS  read-only
   STATUS      current
   DESCRIPTION
      "Path: vxLanBridgeGroup.status.vlan.ip.secondaryIp.netMask"
   ::= {sr1646v2VxlBGIMVpVlanIpSecondaryIpEntry 2063597568}

sr1646v2VxlBGIMVpVlanIpV6Addresses OBJECT-TYPE
   SYNTAX      SEQUENCE OF Sr1646v2VxlBGIMVpVlanIpV6AddressesEntry
   MAX-ACCESS  not-accessible
   STATUS      current
   DESCRIPTION
      ""
   ::= {sr1646v2VxlBGIMVpVlan 100859904}

sr1646v2VxlBGIMVpVlanIpV6AddressesEntry OBJECT-TYPE
   SYNTAX      Sr1646v2VxlBGIMVpVlanIpV6AddressesEntry
   MAX-ACCESS  not-accessible
   STATUS      current
   DESCRIPTION
      ""
   INDEX      { sr1646v2VxlBGIMVpVlanIpV6AddressesGlobalIx,
                sr1646v2VxlBGIMVpVlanTableIx,
                sr1646v2VxlBGIMVpVlanIpV6AddressesTableIx }
   ::= {sr1646v2VxlBGIMVpVlanIpV6Addresses 1}

Sr1646v2VxlBGIMVpVlanIpV6AddressesEntry ::=
   SEQUENCE
      {
      sr1646v2VxlBGIMVpVlanIpV6AddressesGlobalIx
         GlobalIndex,
      sr1646v2VxlBGIMVpVlanIpV6AddressesTableIx
         TableIndex,
      sr1646v2VxlBGIMVpVlanIpV6AddressesAddress
         Ipv6Address,
      sr1646v2VxlBGIMVpVlanIpV6AddressesPrefixLength
         Integer32,
      sr1646v2VxlBGIMVpVlanIpV6AddressesStatus
         INTEGER,
      sr1646v2VxlBGIMVpVlanIpV6AddressesOrigin
         INTEGER,
      sr1646v2VxlBGIMVpVlanIpV6AddressesFlagsInterfaceId
         INTEGER,
      sr1646v2VxlBGIMVpVlanIpV6AddressesFlagsAnycast
         INTEGER,
      sr1646v2VxlBGIMVpVlanIpV6AddressesTimersValidLifeTime
         TimeTicks,
      sr1646v2VxlBGIMVpVlanIpV6AddressesTimersPrefLifeTime
         TimeTicks
      }

sr1646v2VxlBGIMVpVlanIpV6AddressesGlobalIx OBJECT-TYPE
   SYNTAX      GlobalIndex
   MAX-ACCESS  not-accessible
   STATUS      current
   DESCRIPTION
      "The value of the tlsCntTreeGlobalIndex of the MANAGED OBJECT."
   ::= {sr1646v2VxlBGIMVpVlanIpV6AddressesEntry 10}

sr1646v2VxlBGIMVpVlanIpV6AddressesTableIx OBJECT-TYPE
   SYNTAX      TableIndex
   MAX-ACCESS  not-accessible
   STATUS      current
   DESCRIPTION
      ""
   ::= {sr1646v2VxlBGIMVpVlanIpV6AddressesEntry 11}

sr1646v2VxlBGIMVpVlanIpV6AddressesAddress OBJECT-TYPE
   SYNTAX      Ipv6Address
   MAX-ACCESS  read-only
   STATUS      current
   DESCRIPTION
      "Path: vxLanBridgeGroup.status.vlan.ipV6.addresses.address

       ipv6 address"
   ::= {sr1646v2VxlBGIMVpVlanIpV6AddressesEntry 16777216}

sr1646v2VxlBGIMVpVlanIpV6AddressesPrefixLength OBJECT-TYPE
   SYNTAX      Integer32
   MAX-ACCESS  read-only
   STATUS      current
   DESCRIPTION
      "Path: vxLanBridgeGroup.status.vlan.ipV6.addresses.prefixLength"
   ::= {sr1646v2VxlBGIMVpVlanIpV6AddressesEntry 33554432}

sr1646v2VxlBGIMVpVlanIpV6AddressesStatus OBJECT-TYPE
   SYNTAX      INTEGER
               {
               invalid (0),
               tentative (1),
               deprecated (2),
               preferred (3)
               }
   MAX-ACCESS  read-only
   STATUS      current
   DESCRIPTION
      "Path: vxLanBridgeGroup.status.vlan.ipV6.addresses.status

       Possibilities:
               invalid   (0)
               tentative   (1)
               deprecated   (2)
               preferred   (3)"
   ::= {sr1646v2VxlBGIMVpVlanIpV6AddressesEntry 50331648}

sr1646v2VxlBGIMVpVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vxLanBridgeGroup.status.vlan.ipV6.addresses.origin

       Possibilities:
               unknown   (0)
               manual   (1)
               generalPrefix   (2)
               statelessAuto   (3)
               statefullAuto   (4)"
   ::= {sr1646v2VxlBGIMVpVlanIpV6AddressesEntry 67108864}

sr1646v2VxlBGIMVpVlanIpV6AddressesFlagsInterfaceId OBJECT-TYPE
   SYNTAX      INTEGER
               {
               no (0),
               yes (1)
               }
   MAX-ACCESS  read-only
   STATUS      current
   DESCRIPTION
      "Path: vxLanBridgeGroup.status.vlan.ipV6.addresses.flags.interfaceId

       Possibilities:
               no   (0)
               yes   (1)"
   ::= {sr1646v2VxlBGIMVpVlanIpV6AddressesEntry 83951616}

sr1646v2VxlBGIMVpVlanIpV6AddressesFlagsAnycast OBJECT-TYPE
   SYNTAX      INTEGER
               {
               no (0),
               yes (1)
               }
   MAX-ACCESS  read-only
   STATUS      current
   DESCRIPTION
      "Path: vxLanBridgeGroup.status.vlan.ipV6.addresses.flags.anycast

       Possibilities:
               no   (0)
               yes   (1)"
   ::= {sr1646v2VxlBGIMVpVlanIpV6AddressesEntry 84017152}

sr1646v2VxlBGIMVpVlanIpV6AddressesTimersValidLifeTime OBJECT-TYPE
   SYNTAX      TimeTicks
   MAX-ACCESS  read-only
   STATUS      current
   DESCRIPTION
      "Path: vxLanBridgeGroup.status.vlan.ipV6.addresses.timers.validLifeTime

       Time in centi-second."
   ::= {sr1646v2VxlBGIMVpVlanIpV6AddressesEntry 100794368}

sr1646v2VxlBGIMVpVlanIpV6AddressesTimersPrefLifeTime OBJECT-TYPE
   SYNTAX      TimeTicks
   MAX-ACCESS  read-only
   STATUS      current
   DESCRIPTION
      "Path: vxLanBridgeGroup.status.vlan.ipV6.addresses.timers.prefLifeTime

       Time in centi-second."
   ::= {sr1646v2VxlBGIMVpVlanIpV6AddressesEntry 100728832}

sr1646v2VxlBGIMVpVlanVlanArpCache OBJECT-TYPE
   SYNTAX      SEQUENCE OF Sr1646v2VxlBGIMVpVlanVlanArpCacheEntry
   MAX-ACCESS  not-accessible
   STATUS      current
   DESCRIPTION
      ""
   ::= {sr1646v2VxlBGIMVpVlan 235601920}

sr1646v2VxlBGIMVpVlanVlanArpCacheEntry OBJECT-TYPE
   SYNTAX      Sr1646v2VxlBGIMVpVlanVlanArpCacheEntry
   MAX-ACCESS  not-accessible
   STATUS      current
   DESCRIPTION
      ""
   INDEX      { sr1646v2VxlBGIMVpVlanVlanArpCacheGlobalIx,
                sr1646v2VxlBGIMVpVlanTableIx,
                sr1646v2VxlBGIMVpVlanVlanArpCacheTableIx }
   ::= {sr1646v2VxlBGIMVpVlanVlanArpCache 1}

Sr1646v2VxlBGIMVpVlanVlanArpCacheEntry ::=
   SEQUENCE
      {
      sr1646v2VxlBGIMVpVlanVlanArpCacheGlobalIx
         GlobalIndex,
      sr1646v2VxlBGIMVpVlanVlanArpCacheTableIx
         TableIndex,
      sr1646v2VxlBGIMVpVlanVlanArpCacheMacAddress
         OCTET STRING,
      sr1646v2VxlBGIMVpVlanVlanArpCacheIpAddress
         IpAddress,
      sr1646v2VxlBGIMVpVlanVlanArpCacheType
         INTEGER,
      sr1646v2VxlBGIMVpVlanVlanArpCacheTimeOut
         TimeTicks
      }

sr1646v2VxlBGIMVpVlanVlanArpCacheGlobalIx OBJECT-TYPE
   SYNTAX      GlobalIndex
   MAX-ACCESS  not-accessible
   STATUS      current
   DESCRIPTION
      "The value of the tlsCntTreeGlobalIndex of the MANAGED OBJECT."
   ::= {sr1646v2VxlBGIMVpVlanVlanArpCacheEntry 10}

sr1646v2VxlBGIMVpVlanVlanArpCacheTableIx OBJECT-TYPE
   SYNTAX      TableIndex
   MAX-ACCESS  not-accessible
   STATUS      current
   DESCRIPTION
      ""
   ::= {sr1646v2VxlBGIMVpVlanVlanArpCacheEntry 11}

sr1646v2VxlBGIMVpVlanVlanArpCacheMacAddress OBJECT-TYPE
   SYNTAX      OCTET STRING
   MAX-ACCESS  read-only
   STATUS      current
   DESCRIPTION
      "Path: vxLanBridgeGroup.status.vlan.vlan.arpCache.macAddress

       MAC address."
   ::= {sr1646v2VxlBGIMVpVlanVlanArpCacheEntry 16777216}

sr1646v2VxlBGIMVpVlanVlanArpCacheIpAddress OBJECT-TYPE
   SYNTAX      IpAddress
   MAX-ACCESS  read-only
   STATUS      current
   DESCRIPTION
      "Path: vxLanBridgeGroup.status.vlan.vlan.arpCache.ipAddress"
   ::= {sr1646v2VxlBGIMVpVlanVlanArpCacheEntry 33554432}

sr1646v2VxlBGIMVpVlanVlanArpCacheType OBJECT-TYPE
   SYNTAX      INTEGER
               {
               static (0),
               dynamic (1)
               }
   MAX-ACCESS  read-only
   STATUS      current
   DESCRIPTION
      "Path: vxLanBridgeGroup.status.vlan.vlan.arpCache.type

       Possibilities:
               static   (0)
               dynamic   (1)"
   ::= {sr1646v2VxlBGIMVpVlanVlanArpCacheEntry 50331648}

sr1646v2VxlBGIMVpVlanVlanArpCacheTimeOut OBJECT-TYPE
   SYNTAX      TimeTicks
   MAX-ACCESS  read-only
   STATUS      current
   DESCRIPTION
      "Path: vxLanBridgeGroup.status.vlan.vlan.arpCache.timeOut

       Time in centi-second."
   ::= {sr1646v2VxlBGIMVpVlanVlanArpCacheEntry 67108864}


sr1646v2VxlBGIMVpPppOE OBJECT IDENTIFIER ::= {sr1646v2VxlBGIMVp 81}

sr1646v2VxlBGIMVpPppOESSCTable OBJECT-TYPE
   SYNTAX      SEQUENCE OF Sr1646v2VxlBGIMVpPppOEEntry
   MAX-ACCESS  not-accessible
   STATUS      current
   DESCRIPTION
      ""
   ::= {sr1646v2VxlBGIMVpPppOE 1}

sr1646v2VxlBGIMVpPppOEEntry OBJECT-TYPE
   SYNTAX      Sr1646v2VxlBGIMVpPppOEEntry
   MAX-ACCESS  not-accessible
   STATUS      current
   DESCRIPTION
      ""
   INDEX      { sr1646v2VxlBGIMVpPppOEGlobalIx,
                sr1646v2VxlBGIMVpPppOETableIx }
   ::= {sr1646v2VxlBGIMVpPppOESSCTable 1}

Sr1646v2VxlBGIMVpPppOEEntry ::=
   SEQUENCE
      {
      sr1646v2VxlBGIMVpPppOEGlobalIx
         GlobalIndex,
      sr1646v2VxlBGIMVpPppOETableIx
         TableIndex,
      sr1646v2VxlBGIMVpPppOEName
         DisplayString,
      sr1646v2VxlBGIMVpPppOEMode
         INTEGER,
      sr1646v2VxlBGIMVpPppOEIfOperStatus
         INTEGER,
      sr1646v2VxlBGIMVpPppOEIfLastChange
         TimeTicks,
      sr1646v2VxlBGIMVpPppOEIfLastChangeDate
         DisplayString,
      sr1646v2VxlBGIMVpPppOEIpAddress
         IpAddress,
      sr1646v2VxlBGIMVpPppOEIpNetMask
         IpAddress,
      sr1646v2VxlBGIMVpPppOEIpRemote
         IpAddress,
      sr1646v2VxlBGIMVpPppOEPppOEthDiscState
         INTEGER,
      sr1646v2VxlBGIMVpPppOEPppOEthPeerMac
         OCTET STRING,
      sr1646v2VxlBGIMVpPppOEPppOEthServiceName
         DisplayString,
      sr1646v2VxlBGIMVpPppOEPppLcpState
         INTEGER,
      sr1646v2VxlBGIMVpPppOEPppIpcpState
         INTEGER,
      sr1646v2VxlBGIMVpPppOEPppIp6cpState
         INTEGER,
      sr1646v2VxlBGIMVpPppOEPppMyAutSt
         INTEGER,
      sr1646v2VxlBGIMVpPppOEPppHisAutSt
         INTEGER,
      sr1646v2VxlBGIMVpPppOEPppMru
         Integer32,
      sr1646v2VxlBGIMVpPppOEIpV6State
         INTEGER,
      sr1646v2VxlBGIMVpPppOEIpV6InterfaceId
         OCTET STRING,
      sr1646v2VxlBGIMVpPppOEIpV6LinkMtu
         Integer32,
      sr1646v2VxlBGIMVpPppOEIpV6HopLimit
         Integer32,
      sr1646v2VxlBGIMVpPppOEIpV6DhcpIaid
         Counter32,
      sr1646v2VxlBGIMVpPppOEIpV6RaRcvOption
         Integer32
      }

sr1646v2VxlBGIMVpPppOEGlobalIx OBJECT-TYPE
   SYNTAX      GlobalIndex
   MAX-ACCESS  not-accessible
   STATUS      current
   DESCRIPTION
      "The value of the tlsCntTreeGlobalIndex of the MANAGED OBJECT."
   ::= {sr1646v2VxlBGIMVpPppOEEntry 10}

sr1646v2VxlBGIMVpPppOETableIx OBJECT-TYPE
   SYNTAX      TableIndex
   MAX-ACCESS  not-accessible
   STATUS      current
   DESCRIPTION
      ""
   ::= {sr1646v2VxlBGIMVpPppOEEntry 11}

sr1646v2VxlBGIMVpPppOEName OBJECT-TYPE
   SYNTAX      DisplayString
   MAX-ACCESS  read-only
   STATUS      current
   DESCRIPTION
      "Path: vxLanBridgeGroup.status.pppoEClient.name"
   ::= {sr1646v2VxlBGIMVpPppOEEntry 16777216}

sr1646v2VxlBGIMVpPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: vxLanBridgeGroup.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2VxlBGIMVpPppOEEntry 335544320}

sr1646v2VxlBGIMVpPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vxLanBridgeGroup.status.pppoEClient.ifOperStatus

       Possibilities:
               up   (1)
               down   (2)
               testing   (3)
               unknown   (4)
               dormant   (5)
               notPresent   (6)
               lowerLayerDown   (7)"
   ::= {sr1646v2VxlBGIMVpPppOEEntry 1795162112}

sr1646v2VxlBGIMVpPppOEIfLastChange OBJECT-TYPE
   SYNTAX      TimeTicks
   MAX-ACCESS  read-only
   STATUS      current
   DESCRIPTION
      "Path: vxLanBridgeGroup.status.pppoEClient.ifLastChange

       Time in centi-second."
   ::= {sr1646v2VxlBGIMVpPppOEEntry 1811939328}

sr1646v2VxlBGIMVpPppOEIfLastChangeDate OBJECT-TYPE
   SYNTAX      DisplayString
   MAX-ACCESS  read-only
   STATUS      current
   DESCRIPTION
      "Path: vxLanBridgeGroup.status.pppoEClient.ifLastChangeDate"
   ::= {sr1646v2VxlBGIMVpPppOEEntry 3070230528}

sr1646v2VxlBGIMVpPppOEIpAddress OBJECT-TYPE
   SYNTAX      IpAddress
   MAX-ACCESS  read-only
   STATUS      current
   DESCRIPTION
      "Path: vxLanBridgeGroup.status.pppoEClient.ip.address"
   ::= {sr1646v2VxlBGIMVpPppOEEntry 51380224}

sr1646v2VxlBGIMVpPppOEIpNetMask OBJECT-TYPE
   SYNTAX      IpAddress
   MAX-ACCESS  read-only
   STATUS      current
   DESCRIPTION
      "Path: vxLanBridgeGroup.status.pppoEClient.ip.netMask"
   ::= {sr1646v2VxlBGIMVpPppOEEntry 51445760}

sr1646v2VxlBGIMVpPppOEIpRemote OBJECT-TYPE
   SYNTAX      IpAddress
   MAX-ACCESS  read-only
   STATUS      current
   DESCRIPTION
      "Path: vxLanBridgeGroup.status.pppoEClient.ip.remote"
   ::= {sr1646v2VxlBGIMVpPppOEEntry 51511296}

sr1646v2VxlBGIMVpPppOEPppOEthDiscState OBJECT-TYPE
   SYNTAX      INTEGER
               {
               idle (0),
               waitForPADO (1),
               waitForPADS (2),
               established (3)
               }
   MAX-ACCESS  read-only
   STATUS      current
   DESCRIPTION
      "Path: vxLanBridgeGroup.status.pppoEClient.pppOverEth.discState

       Possibilities:
               idle   (0)
               waitForPADO   (1)
               waitForPADS   (2)
               established   (3)"
   ::= {sr1646v2VxlBGIMVpPppOEEntry 67174400}

sr1646v2VxlBGIMVpPppOEPppOEthPeerMac OBJECT-TYPE
   SYNTAX      OCTET STRING
   MAX-ACCESS  read-only
   STATUS      current
   DESCRIPTION
      "Path: vxLanBridgeGroup.status.pppoEClient.pppOverEth.remoteMacAddress

       MAC address."
   ::= {sr1646v2VxlBGIMVpPppOEEntry 67239936}

sr1646v2VxlBGIMVpPppOEPppOEthServiceName OBJECT-TYPE
   SYNTAX      DisplayString
   MAX-ACCESS  read-only
   STATUS      current
   DESCRIPTION
      "Path: vxLanBridgeGroup.status.pppoEClient.pppOverEth.serviceName"
   ::= {sr1646v2VxlBGIMVpPppOEEntry 67305472}

sr1646v2VxlBGIMVpPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vxLanBridgeGroup.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VxlBGIMVpPppOEEntry 83951616}

sr1646v2VxlBGIMVpPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vxLanBridgeGroup.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VxlBGIMVpPppOEEntry 84017152}

sr1646v2VxlBGIMVpPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: vxLanBridgeGroup.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VxlBGIMVpPppOEEntry 84869120}

sr1646v2VxlBGIMVpPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: vxLanBridgeGroup.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2VxlBGIMVpPppOEEntry 84541440}

sr1646v2VxlBGIMVpPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: vxLanBridgeGroup.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2VxlBGIMVpPppOEEntry 84606976}

sr1646v2VxlBGIMVpPppOEPppMru OBJECT-TYPE
   SYNTAX      Integer32
   MAX-ACCESS  read-only
   STATUS      current
   DESCRIPTION
      "Path: vxLanBridgeGroup.status.pppoEClient.ppp.mru"
   ::= {sr1646v2VxlBGIMVpPppOEEntry 84934656}

sr1646v2VxlBGIMVpPppOEIpV6State OBJECT-TYPE
   SYNTAX      INTEGER
               {
               disabled (0),
               enabled (1)
               }
   MAX-ACCESS  read-only
   STATUS      current
   DESCRIPTION
      "Path: vxLanBridgeGroup.status.pppoEClient.ipV6.state

       Possibilities:
               disabled   (0)
               enabled   (1)"
   ::= {sr1646v2VxlBGIMVpPppOEEntry 100728832}

sr1646v2VxlBGIMVpPppOEIpV6InterfaceId OBJECT-TYPE
   SYNTAX      OCTET STRING
   MAX-ACCESS  read-only
   STATUS      current
   DESCRIPTION
      "Path: vxLanBridgeGroup.status.pppoEClient.ipV6.interfaceId"
   ::= {sr1646v2VxlBGIMVpPppOEEntry 100794368}

sr1646v2VxlBGIMVpPppOEIpV6LinkMtu OBJECT-TYPE
   SYNTAX      Integer32
   MAX-ACCESS  read-only
   STATUS      current
   DESCRIPTION
      "Path: vxLanBridgeGroup.status.pppoEClient.ipV6.linkMtu"
   ::= {sr1646v2VxlBGIMVpPppOEEntry 100925440}

sr1646v2VxlBGIMVpPppOEIpV6HopLimit OBJECT-TYPE
   SYNTAX      Integer32
   MAX-ACCESS  read-only
   STATUS      current
   DESCRIPTION
      "Path: vxLanBridgeGroup.status.pppoEClient.ipV6.hopLimit"
   ::= {sr1646v2VxlBGIMVpPppOEEntry 100990976}

sr1646v2VxlBGIMVpPppOEIpV6DhcpIaid OBJECT-TYPE
   SYNTAX      Counter32
   MAX-ACCESS  read-only
   STATUS      current
   DESCRIPTION
      "Path: vxLanBridgeGroup.status.pppoEClient.ipV6.dhcp.iaid

       32 bit unsigned wrappable counter."
   ::= {sr1646v2VxlBGIMVpPppOEEntry 101056768}

sr1646v2VxlBGIMVpPppOEIpV6RaRcvOption OBJECT-TYPE
   SYNTAX      Integer32
   MAX-ACCESS  read-only
   STATUS      current
   DESCRIPTION
      "Path: vxLanBridgeGroup.status.pppoEClient.ipV6.raRcvOption

       Bit meanings:
               bit 0 = linkMtu,
               bit 1 = srcLinkLayer,
               bit 2 = prefixInfo,
               bit 3 = rdnss,
               bit 4 = dnssl"
   ::= {sr1646v2VxlBGIMVpPppOEEntry 101122048}

sr1646v2VxlBGIMVpPppOEIpV6Addresses OBJECT-TYPE
   SYNTAX      SEQUENCE OF Sr1646v2VxlBGIMVpPppOEIpV6AddressesEntry
   MAX-ACCESS  not-accessible
   STATUS      current
   DESCRIPTION
      ""
   ::= {sr1646v2VxlBGIMVpPppOE 100859904}

sr1646v2VxlBGIMVpPppOEIpV6AddressesEntry OBJECT-TYPE
   SYNTAX      Sr1646v2VxlBGIMVpPppOEIpV6AddressesEntry
   MAX-ACCESS  not-accessible
   STATUS      current
   DESCRIPTION
      ""
   INDEX      { sr1646v2VxlBGIMVpPppOEIpV6AddressesGlobalIx,
                sr1646v2VxlBGIMVpPppOETableIx,
                sr1646v2VxlBGIMVpPppOEIpV6AddressesTableIx }
   ::= {sr1646v2VxlBGIMVpPppOEIpV6Addresses 1}

Sr1646v2VxlBGIMVpPppOEIpV6AddressesEntry ::=
   SEQUENCE
      {
      sr1646v2VxlBGIMVpPppOEIpV6AddressesGlobalIx
         GlobalIndex,
      sr1646v2VxlBGIMVpPppOEIpV6AddressesTableIx
         TableIndex,
      sr1646v2VxlBGIMVpPppOEIpV6AddressesAddress
         Ipv6Address,
      sr1646v2VxlBGIMVpPppOEIpV6AddressesPrefixLength
         Integer32,
      sr1646v2VxlBGIMVpPppOEIpV6AddressesStatus
         INTEGER,
      sr1646v2VxlBGIMVpPppOEIpV6AddressesOrigin
         INTEGER,
      sr1646v2VxlBGIMVpPppOEIpV6AddressesFlagsInterfaceId
         INTEGER,
      sr1646v2VxlBGIMVpPppOEIpV6AddressesFlagsAnycast
         INTEGER,
      sr1646v2VxlBGIMVpPppOEIpV6AddressesTimersValidLifeTime
         TimeTicks,
      sr1646v2VxlBGIMVpPppOEIpV6AddressesTimersPrefLifeTime
         TimeTicks
      }

sr1646v2VxlBGIMVpPppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2VxlBGIMVpPppOEIpV6AddressesEntry 10}

sr1646v2VxlBGIMVpPppOEIpV6AddressesTableIx OBJECT-TYPE
   SYNTAX      TableIndex
   MAX-ACCESS  not-accessible
   STATUS      current
   DESCRIPTION
      ""
   ::= {sr1646v2VxlBGIMVpPppOEIpV6AddressesEntry 11}

sr1646v2VxlBGIMVpPppOEIpV6AddressesAddress OBJECT-TYPE
   SYNTAX      Ipv6Address
   MAX-ACCESS  read-only
   STATUS      current
   DESCRIPTION
      "Path: vxLanBridgeGroup.status.pppoEClient.ipV6.addresses.address

       ipv6 address"
   ::= {sr1646v2VxlBGIMVpPppOEIpV6AddressesEntry 16777216}

sr1646v2VxlBGIMVpPppOEIpV6AddressesPrefixLength OBJECT-TYPE
   SYNTAX      Integer32
   MAX-ACCESS  read-only
   STATUS      current
   DESCRIPTION
      "Path: vxLanBridgeGroup.status.pppoEClient.ipV6.addresses.prefixLength"
   ::= {sr1646v2VxlBGIMVpPppOEIpV6AddressesEntry 33554432}

sr1646v2VxlBGIMVpPppOEIpV6AddressesStatus OBJECT-TYPE
   SYNTAX      INTEGER
               {
               invalid (0),
               tentative (1),
               deprecated (2),
               preferred (3)
               }
   MAX-ACCESS  read-only
   STATUS      current
   DESCRIPTION
      "Path: vxLanBridgeGroup.status.pppoEClient.ipV6.addresses.status

       Possibilities:
               invalid   (0)
               tentative   (1)
               deprecated   (2)
               preferred   (3)"
   ::= {sr1646v2VxlBGIMVpPppOEIpV6AddressesEntry 50331648}

sr1646v2VxlBGIMVpPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vxLanBridgeGroup.status.pppoEClient.ipV6.addresses.origin

       Possibilities:
               unknown   (0)
               manual   (1)
               generalPrefix   (2)
               statelessAuto   (3)
               statefullAuto   (4)"
   ::= {sr1646v2VxlBGIMVpPppOEIpV6AddressesEntry 67108864}

sr1646v2VxlBGIMVpPppOEIpV6AddressesFlagsInterfaceId OBJECT-TYPE
   SYNTAX      INTEGER
               {
               no (0),
               yes (1)
               }
   MAX-ACCESS  read-only
   STATUS      current
   DESCRIPTION
      "Path: vxLanBridgeGroup.status.pppoEClient.ipV6.addresses.flags.interfaceId

       Possibilities:
               no   (0)
               yes   (1)"
   ::= {sr1646v2VxlBGIMVpPppOEIpV6AddressesEntry 83951616}

sr1646v2VxlBGIMVpPppOEIpV6AddressesFlagsAnycast OBJECT-TYPE
   SYNTAX      INTEGER
               {
               no (0),
               yes (1)
               }
   MAX-ACCESS  read-only
   STATUS      current
   DESCRIPTION
      "Path: vxLanBridgeGroup.status.pppoEClient.ipV6.addresses.flags.anycast

       Possibilities:
               no   (0)
               yes   (1)"
   ::= {sr1646v2VxlBGIMVpPppOEIpV6AddressesEntry 84017152}

sr1646v2VxlBGIMVpPppOEIpV6AddressesTimersValidLifeTime OBJECT-TYPE
   SYNTAX      TimeTicks
   MAX-ACCESS  read-only
   STATUS      current
   DESCRIPTION
      "Path: vxLanBridgeGroup.status.pppoEClient.ipV6.addresses.timers.validLifeTime

       Time in centi-second."
   ::= {sr1646v2VxlBGIMVpPppOEIpV6AddressesEntry 100794368}

sr1646v2VxlBGIMVpPppOEIpV6AddressesTimersPrefLifeTime OBJECT-TYPE
   SYNTAX      TimeTicks
   MAX-ACCESS  read-only
   STATUS      current
   DESCRIPTION
      "Path: vxLanBridgeGroup.status.pppoEClient.ipV6.addresses.timers.prefLifeTime

       Time in centi-second."
   ::= {sr1646v2VxlBGIMVpPppOEIpV6AddressesEntry 100728832}


sr1646v2VxlBGIMVpBridgeCache OBJECT IDENTIFIER ::= {sr1646v2VxlBGIMVp 3}

sr1646v2VxlBGIMVpBridgeCacheSSCTable OBJECT-TYPE
   SYNTAX      SEQUENCE OF Sr1646v2VxlBGIMVpBridgeCacheEntry
   MAX-ACCESS  not-accessible
   STATUS      current
   DESCRIPTION
      "bridge cache"
   ::= {sr1646v2VxlBGIMVpBridgeCache 1}

sr1646v2VxlBGIMVpBridgeCacheEntry OBJECT-TYPE
   SYNTAX      Sr1646v2VxlBGIMVpBridgeCacheEntry
   MAX-ACCESS  not-accessible
   STATUS      current
   DESCRIPTION
      ""
   INDEX      { sr1646v2VxlBGIMVpBridgeCacheGlobalIx,
                sr1646v2VxlBGIMVpBridgeCacheTableIx }
   ::= {sr1646v2VxlBGIMVpBridgeCacheSSCTable 1}

Sr1646v2VxlBGIMVpBridgeCacheEntry ::=
   SEQUENCE
      {
      sr1646v2VxlBGIMVpBridgeCacheGlobalIx
         GlobalIndex,
      sr1646v2VxlBGIMVpBridgeCacheTableIx
         TableIndex,
      sr1646v2VxlBGIMVpBridgeCacheIf
         DisplayString,
      sr1646v2VxlBGIMVpBridgeCacheMacAddress
         OCTET STRING,
      sr1646v2VxlBGIMVpBridgeCacheVteAddress
         IpAddress,
      sr1646v2VxlBGIMVpBridgeCacheVni
         Integer32,
      sr1646v2VxlBGIMVpBridgeCacheTpid
         INTEGER,
      sr1646v2VxlBGIMVpBridgeCacheVlanId
         INTEGER,
      sr1646v2VxlBGIMVpBridgeCacheTpid2
         INTEGER,
      sr1646v2VxlBGIMVpBridgeCacheVlanId2
         INTEGER,
      sr1646v2VxlBGIMVpBridgeCacheType
         INTEGER,
      sr1646v2VxlBGIMVpBridgeCacheAge
         TimeTicks
      }

sr1646v2VxlBGIMVpBridgeCacheGlobalIx OBJECT-TYPE
   SYNTAX      GlobalIndex
   MAX-ACCESS  not-accessible
   STATUS      current
   DESCRIPTION
      "The value of the tlsCntTreeGlobalIndex of the MANAGED OBJECT."
   ::= {sr1646v2VxlBGIMVpBridgeCacheEntry 10}

sr1646v2VxlBGIMVpBridgeCacheTableIx OBJECT-TYPE
   SYNTAX      TableIndex
   MAX-ACCESS  not-accessible
   STATUS      current
   DESCRIPTION
      ""
   ::= {sr1646v2VxlBGIMVpBridgeCacheEntry 11}

sr1646v2VxlBGIMVpBridgeCacheIf OBJECT-TYPE
   SYNTAX      DisplayString
   MAX-ACCESS  read-only
   STATUS      current
   DESCRIPTION
      "Path: vxLanBridgeGroup.status.bridgeCache.interface"
   ::= {sr1646v2VxlBGIMVpBridgeCacheEntry 16777216}

sr1646v2VxlBGIMVpBridgeCacheMacAddress OBJECT-TYPE
   SYNTAX      OCTET STRING
   MAX-ACCESS  read-only
   STATUS      current
   DESCRIPTION
      "Path: vxLanBridgeGroup.status.bridgeCache.macAddress

       MAC address."
   ::= {sr1646v2VxlBGIMVpBridgeCacheEntry 33554432}

sr1646v2VxlBGIMVpBridgeCacheVteAddress OBJECT-TYPE
   SYNTAX      IpAddress
   MAX-ACCESS  read-only
   STATUS      current
   DESCRIPTION
      "Path: vxLanBridgeGroup.status.bridgeCache.vteAddress"
   ::= {sr1646v2VxlBGIMVpBridgeCacheEntry 117440512}

sr1646v2VxlBGIMVpBridgeCacheVni OBJECT-TYPE
   SYNTAX      Integer32
   MAX-ACCESS  read-only
   STATUS      current
   DESCRIPTION
      "Path: vxLanBridgeGroup.status.bridgeCache.vni"
   ::= {sr1646v2VxlBGIMVpBridgeCacheEntry 134217728}

sr1646v2VxlBGIMVpBridgeCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vxLanBridgeGroup.status.bridgeCache.tpid

       Possibilities:
               untagged   (0)
               dot1q   (33024)
               dot1ad   (34984)
               group   (65534)
               notUsed   (65535)
               dot1qOrDot1ad   (65536)"
   ::= {sr1646v2VxlBGIMVpBridgeCacheEntry 150994944}

sr1646v2VxlBGIMVpBridgeCacheVlanId OBJECT-TYPE
   SYNTAX      INTEGER
               {
               undefined (-1)
               }
   MAX-ACCESS  read-only
   STATUS      current
   DESCRIPTION
      "Path: vxLanBridgeGroup.status.bridgeCache.vlanId

       Possibilities:
               undefined   (-1)"
   ::= {sr1646v2VxlBGIMVpBridgeCacheEntry 83886080}

sr1646v2VxlBGIMVpBridgeCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vxLanBridgeGroup.status.bridgeCache.tpid2

       Possibilities:
               untagged   (0)
               dot1q   (33024)
               dot1ad   (34984)
               group   (65534)
               notUsed   (65535)
               dot1qOrDot1ad   (65536)"
   ::= {sr1646v2VxlBGIMVpBridgeCacheEntry 369098752}

sr1646v2VxlBGIMVpBridgeCacheVlanId2 OBJECT-TYPE
   SYNTAX      INTEGER
               {
               undefined (-1)
               }
   MAX-ACCESS  read-only
   STATUS      current
   DESCRIPTION
      "Path: vxLanBridgeGroup.status.bridgeCache.vlanId2

       Possibilities:
               undefined   (-1)"
   ::= {sr1646v2VxlBGIMVpBridgeCacheEntry 385875968}

sr1646v2VxlBGIMVpBridgeCacheType OBJECT-TYPE
   SYNTAX      INTEGER
               {
               static (0),
               dynamic (1),
               tester (2),
               fastFlood (3)
               }
   MAX-ACCESS  read-only
   STATUS      current
   DESCRIPTION
      "Path: vxLanBridgeGroup.status.bridgeCache.type

       Possibilities:
               static   (0)
               dynamic   (1)
               tester   (2)
               fastFlood   (3)"
   ::= {sr1646v2VxlBGIMVpBridgeCacheEntry 50331648}

sr1646v2VxlBGIMVpBridgeCacheAge OBJECT-TYPE
   SYNTAX      TimeTicks
   MAX-ACCESS  read-only
   STATUS      current
   DESCRIPTION
      "Path: vxLanBridgeGroup.status.bridgeCache.age

       Time in centi-second."
   ::= {sr1646v2VxlBGIMVpBridgeCacheEntry 67108864}


sr1646v2VxlBGIMVpBridging OBJECT IDENTIFIER ::= {sr1646v2VxlBGIMVp 12}

sr1646v2VxlBGIMVpBridgingSSCTable OBJECT-TYPE
   SYNTAX      SEQUENCE OF Sr1646v2VxlBGIMVpBridgingEntry
   MAX-ACCESS  not-accessible
   STATUS      current
   DESCRIPTION
      " bridge-port status"
   ::= {sr1646v2VxlBGIMVpBridging 1}

sr1646v2VxlBGIMVpBridgingEntry OBJECT-TYPE
   SYNTAX      Sr1646v2VxlBGIMVpBridgingEntry
   MAX-ACCESS  not-accessible
   STATUS      current
   DESCRIPTION
      ""
   INDEX      { sr1646v2VxlBGIMVpBridgingGlobalIx,
                sr1646v2VxlBGIMVpBridgingTableIx }
   ::= {sr1646v2VxlBGIMVpBridgingSSCTable 1}

Sr1646v2VxlBGIMVpBridgingEntry ::=
   SEQUENCE
      {
      sr1646v2VxlBGIMVpBridgingGlobalIx
         GlobalIndex,
      sr1646v2VxlBGIMVpBridgingTableIx
         TableIndex,
      sr1646v2VxlBGIMVpBridgingName
         DisplayString,
      sr1646v2VxlBGIMVpBridgingState
         INTEGER,
      sr1646v2VxlBGIMVpBridgingCacheSize
         Counter32,
      sr1646v2VxlBGIMVpBridgingMaxCacheSize
         INTEGER,
      sr1646v2VxlBGIMVpBridgingVlMmbAll
         DisplayString,
      sr1646v2VxlBGIMVpBridgingVlMmbNone
         DisplayString,
      sr1646v2VxlBGIMVpBridgingStPortRole
         INTEGER,
      sr1646v2VxlBGIMVpBridgingStPortId
         Integer32,
      sr1646v2VxlBGIMVpBridgingStPpCostExtPathCost
         Integer32,
      sr1646v2VxlBGIMVpBridgingStPpCostIntPathCost
         Integer32,
      sr1646v2VxlBGIMVpBridgingStExtRpCost
         Integer32,
      sr1646v2VxlBGIMVpBridgingStIntRpCost
         Integer32,
      sr1646v2VxlBGIMVpBridgingStDesBrIdPriority
         Integer32,
      sr1646v2VxlBGIMVpBridgingStDesBrIdMacAddress
         OCTET STRING,
      sr1646v2VxlBGIMVpBridgingStDesPrtId
         Integer32,
      sr1646v2VxlBGIMVpBridgingStDesInt
         INTEGER,
      sr1646v2VxlBGIMVpBridgingStEdgeDetection
         INTEGER,
      sr1646v2VxlBGIMVpBridgingVxLan
         Counter32
      }

sr1646v2VxlBGIMVpBridgingGlobalIx OBJECT-TYPE
   SYNTAX      GlobalIndex
   MAX-ACCESS  not-accessible
   STATUS      current
   DESCRIPTION
      "The value of the tlsCntTreeGlobalIndex of the MANAGED OBJECT."
   ::= {sr1646v2VxlBGIMVpBridgingEntry 10}

sr1646v2VxlBGIMVpBridgingTableIx OBJECT-TYPE
   SYNTAX      TableIndex
   MAX-ACCESS  not-accessible
   STATUS      current
   DESCRIPTION
      ""
   ::= {sr1646v2VxlBGIMVpBridgingEntry 11}

sr1646v2VxlBGIMVpBridgingName OBJECT-TYPE
   SYNTAX      DisplayString
   MAX-ACCESS  read-only
   STATUS      current
   DESCRIPTION
      "Path: vxLanBridgeGroup.status.bridging.name"
   ::= {sr1646v2VxlBGIMVpBridgingEntry 16777216}

sr1646v2VxlBGIMVpBridgingState OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: vxLanBridgeGroup.status.bridging.state

       Possibilities:
               disabled   (0)
               discarding   (1)
               learning   (2)
               forwarding   (3)
               backupBlockedIntfDown   (256)
               backupBlockedIntfUp   (259)
               shutdown   (255)"
   ::= {sr1646v2VxlBGIMVpBridgingEntry 33554432}

sr1646v2VxlBGIMVpBridgingCacheSize OBJECT-TYPE
   SYNTAX      Counter32
   MAX-ACCESS  read-only
   STATUS      current
   DESCRIPTION
      "Path: vxLanBridgeGroup.status.bridging.cacheSize

       32 bit unsigned wrappable counter."
   ::= {sr1646v2VxlBGIMVpBridgingEntry 50331648}

sr1646v2VxlBGIMVpBridgingMaxCacheSize OBJECT-TYPE
   SYNTAX      INTEGER
               {
               unlimited (0)
               }
   MAX-ACCESS  read-only
   STATUS      current
   DESCRIPTION
      "Path: vxLanBridgeGroup.status.bridging.maxCacheSize

       Possibilities:
               unlimited   (0)"
   ::= {sr1646v2VxlBGIMVpBridgingEntry 67108864}

sr1646v2VxlBGIMVpBridgingVlMmbAll OBJECT-TYPE
   SYNTAX      DisplayString
   MAX-ACCESS  read-only
   STATUS      current
   DESCRIPTION
      "Path: vxLanBridgeGroup.status.bridging.vlanMemberShip.all"
   ::= {sr1646v2VxlBGIMVpBridgingEntry 100728832}

sr1646v2VxlBGIMVpBridgingVlMmbNone OBJECT-TYPE
   SYNTAX      DisplayString
   MAX-ACCESS  read-only
   STATUS      current
   DESCRIPTION
      "Path: vxLanBridgeGroup.status.bridging.vlanMemberShip.none"
   ::= {sr1646v2VxlBGIMVpBridgingEntry 100794368}

sr1646v2VxlBGIMVpBridgingStPortRole OBJECT-TYPE
   SYNTAX      INTEGER
               {
               none (0),
               root (1),
               designated (2),
               alternate (3),
               backup (4),
               disabled (5),
               master (6)
               }
   MAX-ACCESS  read-only
   STATUS      current
   DESCRIPTION
      "Path: vxLanBridgeGroup.status.bridging.spanningTree.portRole

       Possibilities:
               none   (0)
               root   (1)
               designated   (2)
               alternate   (3)
               backup   (4)
               disabled   (5)
               master   (6)"
   ::= {sr1646v2VxlBGIMVpBridgingEntry 83951616}

sr1646v2VxlBGIMVpBridgingStPortId OBJECT-TYPE
   SYNTAX      Integer32
   MAX-ACCESS  read-only
   STATUS      current
   DESCRIPTION
      "Path: vxLanBridgeGroup.status.bridging.spanningTree.portId"
   ::= {sr1646v2VxlBGIMVpBridgingEntry 84017152}

sr1646v2VxlBGIMVpBridgingStPpCostExtPathCost OBJECT-TYPE
   SYNTAX      Integer32
   MAX-ACCESS  read-only
   STATUS      current
   DESCRIPTION
      "Path: vxLanBridgeGroup.status.bridging.spanningTree.portPathCosts.extPathCost"
   ::= {sr1646v2VxlBGIMVpBridgingEntry 84082944}

sr1646v2VxlBGIMVpBridgingStPpCostIntPathCost OBJECT-TYPE
   SYNTAX      Integer32
   MAX-ACCESS  read-only
   STATUS      current
   DESCRIPTION
      "Path: vxLanBridgeGroup.status.bridging.spanningTree.portPathCosts.intPathCost"
   ::= {sr1646v2VxlBGIMVpBridgingEntry 84083200}

sr1646v2VxlBGIMVpBridgingStExtRpCost OBJECT-TYPE
   SYNTAX      Integer32
   MAX-ACCESS  read-only
   STATUS      current
   DESCRIPTION
      "Path: vxLanBridgeGroup.status.bridging.spanningTree.extRootPathCost"
   ::= {sr1646v2VxlBGIMVpBridgingEntry 84148224}

sr1646v2VxlBGIMVpBridgingStIntRpCost OBJECT-TYPE
   SYNTAX      Integer32
   MAX-ACCESS  read-only
   STATUS      current
   DESCRIPTION
      "Path: vxLanBridgeGroup.status.bridging.spanningTree.intRootPathCost"
   ::= {sr1646v2VxlBGIMVpBridgingEntry 84213760}

sr1646v2VxlBGIMVpBridgingStDesBrIdPriority OBJECT-TYPE
   SYNTAX      Integer32
   MAX-ACCESS  read-only
   STATUS      current
   DESCRIPTION
      "Path: vxLanBridgeGroup.status.bridging.spanningTree.designatedBridgeId.priority"
   ::= {sr1646v2VxlBGIMVpBridgingEntry 84279552}

sr1646v2VxlBGIMVpBridgingStDesBrIdMacAddress OBJECT-TYPE
   SYNTAX      OCTET STRING
   MAX-ACCESS  read-only
   STATUS      current
   DESCRIPTION
      "Path: vxLanBridgeGroup.status.bridging.spanningTree.designatedBridgeId.macAddress

       MAC address."
   ::= {sr1646v2VxlBGIMVpBridgingEntry 84279808}

sr1646v2VxlBGIMVpBridgingStDesPrtId OBJECT-TYPE
   SYNTAX      Integer32
   MAX-ACCESS  read-only
   STATUS      current
   DESCRIPTION
      "Path: vxLanBridgeGroup.status.bridging.spanningTree.designatedPortId"
   ::= {sr1646v2VxlBGIMVpBridgingEntry 84344832}

sr1646v2VxlBGIMVpBridgingStDesInt OBJECT-TYPE
   SYNTAX      INTEGER
               {
               no (0),
               yes (1)
               }
   MAX-ACCESS  read-only
   STATUS      current
   DESCRIPTION
      "Path: vxLanBridgeGroup.status.bridging.spanningTree.designatedOrInternal

       Possibilities:
               no   (0)
               yes   (1)"
   ::= {sr1646v2VxlBGIMVpBridgingEntry 84410368}

sr1646v2VxlBGIMVpBridgingStEdgeDetection OBJECT-TYPE
   SYNTAX      INTEGER
               {
               none (0),
               edge (1),
               notEdge (2)
               }
   MAX-ACCESS  read-only
   STATUS      current
   DESCRIPTION
      "Path: vxLanBridgeGroup.status.bridging.spanningTree.edgeDetection

       Possibilities:
               none   (0)
               edge   (1)
               notEdge   (2)"
   ::= {sr1646v2VxlBGIMVpBridgingEntry 84475904}

sr1646v2VxlBGIMVpBridgingVxLan OBJECT-TYPE
   SYNTAX      Counter32
   MAX-ACCESS  read-only
   STATUS      current
   DESCRIPTION
      "Path: vxLanBridgeGroup.status.bridging.vxLan

       32 bit unsigned wrappable counter."
   ::= {sr1646v2VxlBGIMVpBridgingEntry 117440512}

sr1646v2VxlBGIMVpBridgingVlMmbGrouped OBJECT-TYPE
   SYNTAX      SEQUENCE OF Sr1646v2VxlBGIMVpBridgingVlMmbGroupedEntry
   MAX-ACCESS  not-accessible
   STATUS      current
   DESCRIPTION
      ""
   ::= {sr1646v2VxlBGIMVpBridging 100859904}

sr1646v2VxlBGIMVpBridgingVlMmbGroupedEntry OBJECT-TYPE
   SYNTAX      Sr1646v2VxlBGIMVpBridgingVlMmbGroupedEntry
   MAX-ACCESS  not-accessible
   STATUS      current
   DESCRIPTION
      ""
   INDEX      { sr1646v2VxlBGIMVpBridgingVlMmbGroupedGlobalIx,
                sr1646v2VxlBGIMVpBridgingTableIx,
                sr1646v2VxlBGIMVpBridgingVlMmbGroupedTableIx }
   ::= {sr1646v2VxlBGIMVpBridgingVlMmbGrouped 1}

Sr1646v2VxlBGIMVpBridgingVlMmbGroupedEntry ::=
   SEQUENCE
      {
      sr1646v2VxlBGIMVpBridgingVlMmbGroupedGlobalIx
         GlobalIndex,
      sr1646v2VxlBGIMVpBridgingVlMmbGroupedTableIx
         TableIndex,
      sr1646v2VxlBGIMVpBridgingVlMmbGroupedVlanId
         Integer32
      }

sr1646v2VxlBGIMVpBridgingVlMmbGroupedGlobalIx OBJECT-TYPE
   SYNTAX      GlobalIndex
   MAX-ACCESS  not-accessible
   STATUS      current
   DESCRIPTION
      "The value of the tlsCntTreeGlobalIndex of the MANAGED OBJECT."
   ::= {sr1646v2VxlBGIMVpBridgingVlMmbGroupedEntry 10}

sr1646v2VxlBGIMVpBridgingVlMmbGroupedTableIx OBJECT-TYPE
   SYNTAX      TableIndex
   MAX-ACCESS  not-accessible
   STATUS      current
   DESCRIPTION
      ""
   ::= {sr1646v2VxlBGIMVpBridgingVlMmbGroupedEntry 11}

sr1646v2VxlBGIMVpBridgingVlMmbGroupedVlanId OBJECT-TYPE
   SYNTAX      Integer32
   MAX-ACCESS  read-only
   STATUS      current
   DESCRIPTION
      "Path: vxLanBridgeGroup.status.bridging.vlanMemberShip.grouped.vlanId"
   ::= {sr1646v2VxlBGIMVpBridgingVlMmbGroupedEntry 16777216}


sr1646v2VxlBGIMVpSnmpIndex OBJECT IDENTIFIER ::= {sr1646v2VxlBGIMVp 269}

sr1646v2VxlBGIMVpSnmpIndexTable OBJECT-TYPE
   SYNTAX      SEQUENCE OF Sr1646v2VxlBGIMVpSnmpIndexEntry
   MAX-ACCESS  not-accessible
   STATUS      current
   DESCRIPTION
      "SNMP index assigned to this object"
   ::= {sr1646v2VxlBGIMVpSnmpIndex 1}

sr1646v2VxlBGIMVpSnmpIndexEntry OBJECT-TYPE
   SYNTAX      Sr1646v2VxlBGIMVpSnmpIndexEntry
   MAX-ACCESS  not-accessible
   STATUS      current
   DESCRIPTION
      ""
   INDEX      { sr1646v2VxlBGIMVpSnmpIndexGlobalIx }
   ::= {sr1646v2VxlBGIMVpSnmpIndexTable 1}

Sr1646v2VxlBGIMVpSnmpIndexEntry ::=
   SEQUENCE
      {
      sr1646v2VxlBGIMVpSnmpIndexGlobalIx
         GlobalIndex,
      sr1646v2VxlBGIMVpSnmpIndexValue
         Integer32
      }

sr1646v2VxlBGIMVpSnmpIndexGlobalIx OBJECT-TYPE
   SYNTAX      GlobalIndex
   MAX-ACCESS  not-accessible
   STATUS      current
   DESCRIPTION
      "The value of the tlsCntTreeGlobalIndex of the MANAGED OBJECT."
   ::= {sr1646v2VxlBGIMVpSnmpIndexEntry 10}

sr1646v2VxlBGIMVpSnmpIndexValue OBJECT-TYPE
   SYNTAX      Integer32
   MAX-ACCESS  read-only
   STATUS      current
   DESCRIPTION
      "Path: vxLanBridgeGroup.status.snmpIndex"
   ::= {sr1646v2VxlBGIMVpSnmpIndexEntry 2147483648}



pr1646v2VxlBGIMVp OBJECT IDENTIFIER ::= {r1646v2VxlBGIMVp 12}


pr1646v2VxlBGIMVpResCachePerf OBJECT IDENTIFIER ::= {pr1646v2VxlBGIMVp 45}

pr1646v2VxlBGIMVpResCachePerfSSCTable OBJECT-TYPE
   SYNTAX      SEQUENCE OF Pr1646v2VxlBGIMVpResCachePerfEntry
   MAX-ACCESS  not-accessible
   STATUS      current
   DESCRIPTION
      "cache of reserved Ethernet addresses"
   ::= {pr1646v2VxlBGIMVpResCachePerf 1}

pr1646v2VxlBGIMVpResCachePerfEntry OBJECT-TYPE
   SYNTAX      Pr1646v2VxlBGIMVpResCachePerfEntry
   MAX-ACCESS  not-accessible
   STATUS      current
   DESCRIPTION
      ""
   INDEX      { pr1646v2VxlBGIMVpResCachePerfGlobalIx,
                pr1646v2VxlBGIMVpResCachePerfTableIx }
   ::= {pr1646v2VxlBGIMVpResCachePerfSSCTable 1}

Pr1646v2VxlBGIMVpResCachePerfEntry ::=
   SEQUENCE
      {
      pr1646v2VxlBGIMVpResCachePerfGlobalIx
         GlobalIndex,
      pr1646v2VxlBGIMVpResCachePerfTableIx
         TableIndex,
      pr1646v2VxlBGIMVpResCachePerfMacAddress
         OCTET STRING,
      pr1646v2VxlBGIMVpResCachePerfRxPkts
         Counter32
      }

pr1646v2VxlBGIMVpResCachePerfGlobalIx OBJECT-TYPE
   SYNTAX      GlobalIndex
   MAX-ACCESS  not-accessible
   STATUS      current
   DESCRIPTION
      "The value of the tlsCntTreeGlobalIndex of the MANAGED OBJECT."
   ::= {pr1646v2VxlBGIMVpResCachePerfEntry 10}

pr1646v2VxlBGIMVpResCachePerfTableIx OBJECT-TYPE
   SYNTAX      TableIndex
   MAX-ACCESS  not-accessible
   STATUS      current
   DESCRIPTION
      ""
   ::= {pr1646v2VxlBGIMVpResCachePerfEntry 11}

pr1646v2VxlBGIMVpResCachePerfMacAddress OBJECT-TYPE
   SYNTAX      OCTET STRING
   MAX-ACCESS  read-only
   STATUS      current
   DESCRIPTION
      "Path: vxLanBridgeGroup.performance.reservedAddressCache.macAddress

       MAC address."
   ::= {pr1646v2VxlBGIMVpResCachePerfEntry 16777216}

pr1646v2VxlBGIMVpResCachePerfRxPkts OBJECT-TYPE
   SYNTAX      Counter32
   MAX-ACCESS  read-only
   STATUS      current
   DESCRIPTION
      "Path: vxLanBridgeGroup.performance.reservedAddressCache.rxPkts

       32 bit unsigned wrappable counter."
   ::= {pr1646v2VxlBGIMVpResCachePerfEntry 33554432}


pr1646v2VxlBGIMVpBridgeRxPkts OBJECT IDENTIFIER ::= {pr1646v2VxlBGIMVp 42}

pr1646v2VxlBGIMVpBridgeRxPktsTable OBJECT-TYPE
   SYNTAX      SEQUENCE OF Pr1646v2VxlBGIMVpBridgeRxPktsEntry
   MAX-ACCESS  not-accessible
   STATUS      current
   DESCRIPTION
      "counter (floods or discards) of bridge"
   ::= {pr1646v2VxlBGIMVpBridgeRxPkts 1}

pr1646v2VxlBGIMVpBridgeRxPktsEntry OBJECT-TYPE
   SYNTAX      Pr1646v2VxlBGIMVpBridgeRxPktsEntry
   MAX-ACCESS  not-accessible
   STATUS      current
   DESCRIPTION
      ""
   INDEX      { pr1646v2VxlBGIMVpBridgeRxPktsGlobalIx }
   ::= {pr1646v2VxlBGIMVpBridgeRxPktsTable 1}

Pr1646v2VxlBGIMVpBridgeRxPktsEntry ::=
   SEQUENCE
      {
      pr1646v2VxlBGIMVpBridgeRxPktsGlobalIx
         GlobalIndex,
      pr1646v2VxlBGIMVpBridgeRxPktsValue
         Counter32
      }

pr1646v2VxlBGIMVpBridgeRxPktsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeRxPktsEntry 10}

pr1646v2VxlBGIMVpBridgeRxPktsValue OBJECT-TYPE
   SYNTAX      Counter32
   MAX-ACCESS  read-only
   STATUS      current
   DESCRIPTION
      "Path: vxLanBridgeGroup.performance.bridgeRxPkts

       32 bit unsigned wrappable counter."
   ::= {pr1646v2VxlBGIMVpBridgeRxPktsEntry 2147483648}


pr1646v2VxlBGIMVpBridgeTxPkts OBJECT IDENTIFIER ::= {pr1646v2VxlBGIMVp 43}

pr1646v2VxlBGIMVpBridgeTxPktsTable OBJECT-TYPE
   SYNTAX      SEQUENCE OF Pr1646v2VxlBGIMVpBridgeTxPktsEntry
   MAX-ACCESS  not-accessible
   STATUS      current
   DESCRIPTION
      "counter (floods or discards) of bridge"
   ::= {pr1646v2VxlBGIMVpBridgeTxPkts 1}

pr1646v2VxlBGIMVpBridgeTxPktsEntry OBJECT-TYPE
   SYNTAX      Pr1646v2VxlBGIMVpBridgeTxPktsEntry
   MAX-ACCESS  not-accessible
   STATUS      current
   DESCRIPTION
      ""
   INDEX      { pr1646v2VxlBGIMVpBridgeTxPktsGlobalIx }
   ::= {pr1646v2VxlBGIMVpBridgeTxPktsTable 1}

Pr1646v2VxlBGIMVpBridgeTxPktsEntry ::=
   SEQUENCE
      {
      pr1646v2VxlBGIMVpBridgeTxPktsGlobalIx
         GlobalIndex,
      pr1646v2VxlBGIMVpBridgeTxPktsValue
         Counter32
      }

pr1646v2VxlBGIMVpBridgeTxPktsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeTxPktsEntry 10}

pr1646v2VxlBGIMVpBridgeTxPktsValue OBJECT-TYPE
   SYNTAX      Counter32
   MAX-ACCESS  read-only
   STATUS      current
   DESCRIPTION
      "Path: vxLanBridgeGroup.performance.bridgeTxPkts

       32 bit unsigned wrappable counter."
   ::= {pr1646v2VxlBGIMVpBridgeTxPktsEntry 2147483648}


pr1646v2VxlBGIMVpBridgeDiscards OBJECT IDENTIFIER ::= {pr1646v2VxlBGIMVp 7}

pr1646v2VxlBGIMVpBridgeDiscardsTable OBJECT-TYPE
   SYNTAX      SEQUENCE OF Pr1646v2VxlBGIMVpBridgeDiscardsEntry
   MAX-ACCESS  not-accessible
   STATUS      current
   DESCRIPTION
      "counter (floods or discards) of bridge"
   ::= {pr1646v2VxlBGIMVpBridgeDiscards 1}

pr1646v2VxlBGIMVpBridgeDiscardsEntry OBJECT-TYPE
   SYNTAX      Pr1646v2VxlBGIMVpBridgeDiscardsEntry
   MAX-ACCESS  not-accessible
   STATUS      current
   DESCRIPTION
      ""
   INDEX      { pr1646v2VxlBGIMVpBridgeDiscardsGlobalIx }
   ::= {pr1646v2VxlBGIMVpBridgeDiscardsTable 1}

Pr1646v2VxlBGIMVpBridgeDiscardsEntry ::=
   SEQUENCE
      {
      pr1646v2VxlBGIMVpBridgeDiscardsGlobalIx
         GlobalIndex,
      pr1646v2VxlBGIMVpBridgeDiscardsValue
         Counter32
      }

pr1646v2VxlBGIMVpBridgeDiscardsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeDiscardsEntry 10}

pr1646v2VxlBGIMVpBridgeDiscardsValue OBJECT-TYPE
   SYNTAX      Counter32
   MAX-ACCESS  read-only
   STATUS      current
   DESCRIPTION
      "Path: vxLanBridgeGroup.performance.bridgeDiscards

       32 bit unsigned wrappable counter."
   ::= {pr1646v2VxlBGIMVpBridgeDiscardsEntry 2147483648}


pr1646v2VxlBGIMVpBridgeFloods OBJECT IDENTIFIER ::= {pr1646v2VxlBGIMVp 8}

pr1646v2VxlBGIMVpBridgeFloodsTable OBJECT-TYPE
   SYNTAX      SEQUENCE OF Pr1646v2VxlBGIMVpBridgeFloodsEntry
   MAX-ACCESS  not-accessible
   STATUS      current
   DESCRIPTION
      "counter (floods or discards) of bridge"
   ::= {pr1646v2VxlBGIMVpBridgeFloods 1}

pr1646v2VxlBGIMVpBridgeFloodsEntry OBJECT-TYPE
   SYNTAX      Pr1646v2VxlBGIMVpBridgeFloodsEntry
   MAX-ACCESS  not-accessible
   STATUS      current
   DESCRIPTION
      ""
   INDEX      { pr1646v2VxlBGIMVpBridgeFloodsGlobalIx }
   ::= {pr1646v2VxlBGIMVpBridgeFloodsTable 1}

Pr1646v2VxlBGIMVpBridgeFloodsEntry ::=
   SEQUENCE
      {
      pr1646v2VxlBGIMVpBridgeFloodsGlobalIx
         GlobalIndex,
      pr1646v2VxlBGIMVpBridgeFloodsValue
         Counter32
      }

pr1646v2VxlBGIMVpBridgeFloodsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeFloodsEntry 10}

pr1646v2VxlBGIMVpBridgeFloodsValue OBJECT-TYPE
   SYNTAX      Counter32
   MAX-ACCESS  read-only
   STATUS      current
   DESCRIPTION
      "Path: vxLanBridgeGroup.performance.bridgeFloods

       32 bit unsigned wrappable counter."
   ::= {pr1646v2VxlBGIMVpBridgeFloodsEntry 2147483648}


pr1646v2VxlBGIMVpBridgeBroadcasts OBJECT IDENTIFIER ::= {pr1646v2VxlBGIMVp 40}

pr1646v2VxlBGIMVpBridgeBroadcastsTable OBJECT-TYPE
   SYNTAX      SEQUENCE OF Pr1646v2VxlBGIMVpBridgeBroadcastsEntry
   MAX-ACCESS  not-accessible
   STATUS      current
   DESCRIPTION
      "counter (floods or discards) of bridge"
   ::= {pr1646v2VxlBGIMVpBridgeBroadcasts 1}

pr1646v2VxlBGIMVpBridgeBroadcastsEntry OBJECT-TYPE
   SYNTAX      Pr1646v2VxlBGIMVpBridgeBroadcastsEntry
   MAX-ACCESS  not-accessible
   STATUS      current
   DESCRIPTION
      ""
   INDEX      { pr1646v2VxlBGIMVpBridgeBroadcastsGlobalIx }
   ::= {pr1646v2VxlBGIMVpBridgeBroadcastsTable 1}

Pr1646v2VxlBGIMVpBridgeBroadcastsEntry ::=
   SEQUENCE
      {
      pr1646v2VxlBGIMVpBridgeBroadcastsGlobalIx
         GlobalIndex,
      pr1646v2VxlBGIMVpBridgeBroadcastsValue
         Counter32
      }

pr1646v2VxlBGIMVpBridgeBroadcastsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeBroadcastsEntry 10}

pr1646v2VxlBGIMVpBridgeBroadcastsValue OBJECT-TYPE
   SYNTAX      Counter32
   MAX-ACCESS  read-only
   STATUS      current
   DESCRIPTION
      "Path: vxLanBridgeGroup.performance.bridgeBroadcasts

       32 bit unsigned wrappable counter."
   ::= {pr1646v2VxlBGIMVpBridgeBroadcastsEntry 2147483648}


pr1646v2VxlBGIMVpBridgeMulticasts OBJECT IDENTIFIER ::= {pr1646v2VxlBGIMVp 41}

pr1646v2VxlBGIMVpBridgeMulticastsTable OBJECT-TYPE
   SYNTAX      SEQUENCE OF Pr1646v2VxlBGIMVpBridgeMulticastsEntry
   MAX-ACCESS  not-accessible
   STATUS      current
   DESCRIPTION
      "counter (floods or discards) of bridge"
   ::= {pr1646v2VxlBGIMVpBridgeMulticasts 1}

pr1646v2VxlBGIMVpBridgeMulticastsEntry OBJECT-TYPE
   SYNTAX      Pr1646v2VxlBGIMVpBridgeMulticastsEntry
   MAX-ACCESS  not-accessible
   STATUS      current
   DESCRIPTION
      ""
   INDEX      { pr1646v2VxlBGIMVpBridgeMulticastsGlobalIx }
   ::= {pr1646v2VxlBGIMVpBridgeMulticastsTable 1}

Pr1646v2VxlBGIMVpBridgeMulticastsEntry ::=
   SEQUENCE
      {
      pr1646v2VxlBGIMVpBridgeMulticastsGlobalIx
         GlobalIndex,
      pr1646v2VxlBGIMVpBridgeMulticastsValue
         Counter32
      }

pr1646v2VxlBGIMVpBridgeMulticastsGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeMulticastsEntry 10}

pr1646v2VxlBGIMVpBridgeMulticastsValue OBJECT-TYPE
   SYNTAX      Counter32
   MAX-ACCESS  read-only
   STATUS      current
   DESCRIPTION
      "Path: vxLanBridgeGroup.performance.bridgeMulticasts

       32 bit unsigned wrappable counter."
   ::= {pr1646v2VxlBGIMVpBridgeMulticastsEntry 2147483648}


pr1646v2VxlBGIMVpVlanSwitching OBJECT IDENTIFIER ::= {pr1646v2VxlBGIMVp 30}

pr1646v2VxlBGIMVpVlanSwitchingSSCTable OBJECT-TYPE
   SYNTAX      SEQUENCE OF Pr1646v2VxlBGIMVpVlanSwitchingEntry
   MAX-ACCESS  not-accessible
   STATUS      current
   DESCRIPTION
      "ospf area summary lsa overview"
   ::= {pr1646v2VxlBGIMVpVlanSwitching 1}

pr1646v2VxlBGIMVpVlanSwitchingEntry OBJECT-TYPE
   SYNTAX      Pr1646v2VxlBGIMVpVlanSwitchingEntry
   MAX-ACCESS  not-accessible
   STATUS      current
   DESCRIPTION
      ""
   INDEX      { pr1646v2VxlBGIMVpVlanSwitchingGlobalIx,
                pr1646v2VxlBGIMVpVlanSwitchingTableIx }
   ::= {pr1646v2VxlBGIMVpVlanSwitchingSSCTable 1}

Pr1646v2VxlBGIMVpVlanSwitchingEntry ::=
   SEQUENCE
      {
      pr1646v2VxlBGIMVpVlanSwitchingGlobalIx
         GlobalIndex,
      pr1646v2VxlBGIMVpVlanSwitchingTableIx
         TableIndex,
      pr1646v2VxlBGIMVpVlanSwitchingSrcIntf
         DisplayString,
      pr1646v2VxlBGIMVpVlanSwitchingSrcVlan
         INTEGER,
      pr1646v2VxlBGIMVpVlanSwitchingSrcPFlt
         INTEGER,
      pr1646v2VxlBGIMVpVlanSwitchingDestIntf
         DisplayString,
      pr1646v2VxlBGIMVpVlanSwitchingDestVlan
         INTEGER,
      pr1646v2VxlBGIMVpVlanSwitchingTunnelMode
         INTEGER,
      pr1646v2VxlBGIMVpVlanSwitchingUses
         Counter32
      }

pr1646v2VxlBGIMVpVlanSwitchingGlobalIx OBJECT-TYPE
   SYNTAX      GlobalIndex
   MAX-ACCESS  not-accessible
   STATUS      current
   DESCRIPTION
      "The value of the tlsCntTreeGlobalIndex of the MANAGED OBJECT."
   ::= {pr1646v2VxlBGIMVpVlanSwitchingEntry 10}

pr1646v2VxlBGIMVpVlanSwitchingTableIx OBJECT-TYPE
   SYNTAX      TableIndex
   MAX-ACCESS  not-accessible
   STATUS      current
   DESCRIPTION
      ""
   ::= {pr1646v2VxlBGIMVpVlanSwitchingEntry 11}

pr1646v2VxlBGIMVpVlanSwitchingSrcIntf OBJECT-TYPE
   SYNTAX      DisplayString
   MAX-ACCESS  read-only
   STATUS      current
   DESCRIPTION
      "Path: vxLanBridgeGroup.performance.vlanSwitching.sourceIntf"
   ::= {pr1646v2VxlBGIMVpVlanSwitchingEntry 16777216}

pr1646v2VxlBGIMVpVlanSwitchingSrcVlan OBJECT-TYPE
   SYNTAX      INTEGER
               {
               any (-1)
               }
   MAX-ACCESS  read-only
   STATUS      current
   DESCRIPTION
      "Path: vxLanBridgeGroup.performance.vlanSwitching.sourceVlan

       Possibilities:
               any   (-1)"
   ::= {pr1646v2VxlBGIMVpVlanSwitchingEntry 33554432}

pr1646v2VxlBGIMVpVlanSwitchingSrcPFlt OBJECT-TYPE
   SYNTAX      INTEGER
               {
               any (-1)
               }
   MAX-ACCESS  read-only
   STATUS      current
   DESCRIPTION
      "Path: vxLanBridgeGroup.performance.vlanSwitching.sourcePFilter

       Possibilities:
               any   (-1)"
   ::= {pr1646v2VxlBGIMVpVlanSwitchingEntry 100663296}

pr1646v2VxlBGIMVpVlanSwitchingDestIntf OBJECT-TYPE
   SYNTAX      DisplayString
   MAX-ACCESS  read-only
   STATUS      current
   DESCRIPTION
      "Path: vxLanBridgeGroup.performance.vlanSwitching.destinationIntf"
   ::= {pr1646v2VxlBGIMVpVlanSwitchingEntry 50331648}

pr1646v2VxlBGIMVpVlanSwitchingDestVlan OBJECT-TYPE
   SYNTAX      INTEGER
               {
               unchanged (-1)
               }
   MAX-ACCESS  read-only
   STATUS      current
   DESCRIPTION
      "Path: vxLanBridgeGroup.performance.vlanSwitching.destinationVlan

       Possibilities:
               unchanged   (-1)"
   ::= {pr1646v2VxlBGIMVpVlanSwitchingEntry 67108864}

pr1646v2VxlBGIMVpVlanSwitchingTunnelMode OBJECT-TYPE
   SYNTAX      INTEGER
               {
               none (0),
               toTunnel (1),
               fromTunnel (2),
               toSVlanTunnel (3),
               fromSVlanTunnel (4)
               }
   MAX-ACCESS  read-only
   STATUS      current
   DESCRIPTION
      "Path: vxLanBridgeGroup.performance.vlanSwitching.tunnelMode

       Possibilities:
               none   (0)
               toTunnel   (1)
               fromTunnel   (2)
               toSVlanTunnel   (3)
               fromSVlanTunnel   (4)"
   ::= {pr1646v2VxlBGIMVpVlanSwitchingEntry 117440512}

pr1646v2VxlBGIMVpVlanSwitchingUses OBJECT-TYPE
   SYNTAX      Counter32
   MAX-ACCESS  read-only
   STATUS      current
   DESCRIPTION
      "Path: vxLanBridgeGroup.performance.vlanSwitching.uses

       32 bit unsigned wrappable counter."
   ::= {pr1646v2VxlBGIMVpVlanSwitchingEntry 83886080}


pr1646v2VxlBGIMVpMibCounters OBJECT IDENTIFIER ::= {pr1646v2VxlBGIMVp 100}

pr1646v2VxlBGIMVpMibCountersSSCTable OBJECT-TYPE
   SYNTAX      SEQUENCE OF Pr1646v2VxlBGIMVpMibCountersEntry
   MAX-ACCESS  not-accessible
   STATUS      current
   DESCRIPTION
      "mibCounter"
   ::= {pr1646v2VxlBGIMVpMibCounters 1}

pr1646v2VxlBGIMVpMibCountersEntry OBJECT-TYPE
   SYNTAX      Pr1646v2VxlBGIMVpMibCountersEntry
   MAX-ACCESS  not-accessible
   STATUS      current
   DESCRIPTION
      ""
   INDEX      { pr1646v2VxlBGIMVpMibCountersGlobalIx }
   ::= {pr1646v2VxlBGIMVpMibCountersSSCTable 1}

Pr1646v2VxlBGIMVpMibCountersEntry ::=
   SEQUENCE
      {
      pr1646v2VxlBGIMVpMibCountersGlobalIx
         GlobalIndex,
      pr1646v2VxlBGIMVpMibCountersInOctets
         Counter64,
      pr1646v2VxlBGIMVpMibCountersInUcast
         Counter64,
      pr1646v2VxlBGIMVpMibCountersInNUcastPkts
         Counter64,
      pr1646v2VxlBGIMVpMibCountersInBcastPkts
         Counter64,
      pr1646v2VxlBGIMVpMibCountersInMcastPkts
         Counter64,
      pr1646v2VxlBGIMVpMibCountersInDiscards
         Counter64,
      pr1646v2VxlBGIMVpMibCountersInErrors
         Counter64,
      pr1646v2VxlBGIMVpMibCountersInUnknownProtos
         Counter64,
      pr1646v2VxlBGIMVpMibCountersInDropEx
         Counter64,
      pr1646v2VxlBGIMVpMibCountersInDropNoMac
         Counter64,
      pr1646v2VxlBGIMVpMibCountersInDropNUCast
         Counter64,
      pr1646v2VxlBGIMVpMibCountersInDropFilter
         Counter64,
      pr1646v2VxlBGIMVpMibCountersInBandwidth15sec
         Integer32,
      pr1646v2VxlBGIMVpMibCountersInBandwidth30sec
         Integer32,
      pr1646v2VxlBGIMVpMibCountersInBandwidth1min
         Integer32,
      pr1646v2VxlBGIMVpMibCountersInBandwidth2min
         Integer32,
      pr1646v2VxlBGIMVpMibCountersInBandwidth5min
         Integer32,
      pr1646v2VxlBGIMVpMibCountersOutOctets
         Counter64,
      pr1646v2VxlBGIMVpMibCountersOutUcastPkts
         Counter64,
      pr1646v2VxlBGIMVpMibCountersOutNUcastPkts
         Counter64,
      pr1646v2VxlBGIMVpMibCountersOutBcastPkts
         Counter64,
      pr1646v2VxlBGIMVpMibCountersOutMcastPkts
         Counter64,
      pr1646v2VxlBGIMVpMibCountersOutDiscards
         Counter64,
      pr1646v2VxlBGIMVpMibCountersOutErrors
         Counter64,
      pr1646v2VxlBGIMVpMibCountersOutQLen
         Counter32,
      pr1646v2VxlBGIMVpMibCountersOutDropEx
         Counter64,
      pr1646v2VxlBGIMVpMibCountersOutDropNoArp
         Counter64,
      pr1646v2VxlBGIMVpMibCountersOutDropFilter
         Counter64,
      pr1646v2VxlBGIMVpMibCountersOutBandwidth15sec
         Integer32,
      pr1646v2VxlBGIMVpMibCountersOutBandwidth30sec
         Integer32,
      pr1646v2VxlBGIMVpMibCountersOutBandwidth1min
         Integer32,
      pr1646v2VxlBGIMVpMibCountersOutBandwidth2min
         Integer32,
      pr1646v2VxlBGIMVpMibCountersOutBandwidth5min
         Integer32
      }

pr1646v2VxlBGIMVpMibCountersGlobalIx OBJECT-TYPE
   SYNTAX      GlobalIndex
   MAX-ACCESS  not-accessible
   STATUS      current
   DESCRIPTION
      "The value of the tlsCntTreeGlobalIndex of the MANAGED OBJECT."
   ::= {pr1646v2VxlBGIMVpMibCountersEntry 10}

pr1646v2VxlBGIMVpMibCountersInOctets OBJECT-TYPE
   SYNTAX      Counter64
   MAX-ACCESS  read-only
   STATUS      current
   DESCRIPTION
      "Path: vxLanBridgeGroup.performance.mibCounters.ifInOctets

       64 bit unsigned wrappable counter."
   ::= {pr1646v2VxlBGIMVpMibCountersEntry 1828716544}

pr1646v2VxlBGIMVpMibCountersInUcast OBJECT-TYPE
   SYNTAX      Counter64
   MAX-ACCESS  read-only
   STATUS      current
   DESCRIPTION
      "Path: vxLanBridgeGroup.performance.mibCounters.ifInUcastPkts

       64 bit unsigned wrappable counter."
   ::= {pr1646v2VxlBGIMVpMibCountersEntry 1845493760}

pr1646v2VxlBGIMVpMibCountersInNUcastPkts OBJECT-TYPE
   SYNTAX      Counter64
   MAX-ACCESS  read-only
   STATUS      current
   DESCRIPTION
      "Path: vxLanBridgeGroup.performance.mibCounters.ifInNUcastPkts

       64 bit unsigned wrappable counter."
   ::= {pr1646v2VxlBGIMVpMibCountersEntry 1862270976}

pr1646v2VxlBGIMVpMibCountersInBcastPkts OBJECT-TYPE
   SYNTAX      Counter64
   MAX-ACCESS  read-only
   STATUS      current
   DESCRIPTION
      "Path: vxLanBridgeGroup.performance.mibCounters.ifInBcastPkts

       64 bit unsigned wrappable counter."
   ::= {pr1646v2VxlBGIMVpMibCountersEntry 3539992576}

pr1646v2VxlBGIMVpMibCountersInMcastPkts OBJECT-TYPE
   SYNTAX      Counter64
   MAX-ACCESS  read-only
   STATUS      current
   DESCRIPTION
      "Path: vxLanBridgeGroup.performance.mibCounters.ifInMcastPkts

       64 bit unsigned wrappable counter."
   ::= {pr1646v2VxlBGIMVpMibCountersEntry 3707764736}

pr1646v2VxlBGIMVpMibCountersInDiscards OBJECT-TYPE
   SYNTAX      Counter64
   MAX-ACCESS  read-only
   STATUS      current
   DESCRIPTION
      "Path: vxLanBridgeGroup.performance.mibCounters.ifInDiscards

       64 bit unsigned wrappable counter."
   ::= {pr1646v2VxlBGIMVpMibCountersEntry 1879048192}

pr1646v2VxlBGIMVpMibCountersInErrors OBJECT-TYPE
   SYNTAX      Counter64
   MAX-ACCESS  read-only
   STATUS      current
   DESCRIPTION
      "Path: vxLanBridgeGroup.performance.mibCounters.ifInErrors

       64 bit unsigned wrappable counter."
   ::= {pr1646v2VxlBGIMVpMibCountersEntry 1895825408}

pr1646v2VxlBGIMVpMibCountersInUnknownProtos OBJECT-TYPE
   SYNTAX      Counter64
   MAX-ACCESS  read-only
   STATUS      current
   DESCRIPTION
      "Path: vxLanBridgeGroup.performance.mibCounters.ifInUnknownProtos

       64 bit unsigned wrappable counter."
   ::= {pr1646v2VxlBGIMVpMibCountersEntry 1912602624}

pr1646v2VxlBGIMVpMibCountersInDropEx OBJECT-TYPE
   SYNTAX      Counter64
   MAX-ACCESS  read-only
   STATUS      current
   DESCRIPTION
      "Path: vxLanBridgeGroup.performance.mibCounters.ifInDropLevelExceeded

       64 bit unsigned wrappable counter."
   ::= {pr1646v2VxlBGIMVpMibCountersEntry 2181038080}

pr1646v2VxlBGIMVpMibCountersInDropNoMac OBJECT-TYPE
   SYNTAX      Counter64
   MAX-ACCESS  read-only
   STATUS      current
   DESCRIPTION
      "Path: vxLanBridgeGroup.performance.mibCounters.ifInDiscardsNoMacFit

       64 bit unsigned wrappable counter."
   ::= {pr1646v2VxlBGIMVpMibCountersEntry 2231369728}

pr1646v2VxlBGIMVpMibCountersInDropNUCast OBJECT-TYPE
   SYNTAX      Counter64
   MAX-ACCESS  read-only
   STATUS      current
   DESCRIPTION
      "Path: vxLanBridgeGroup.performance.mibCounters.ifInDiscardsNUCast

       64 bit unsigned wrappable counter."
   ::= {pr1646v2VxlBGIMVpMibCountersEntry 2281701376}

pr1646v2VxlBGIMVpMibCountersInDropFilter OBJECT-TYPE
   SYNTAX      Counter64
   MAX-ACCESS  read-only
   STATUS      current
   DESCRIPTION
      "Path: vxLanBridgeGroup.performance.mibCounters.ifInDiscardsFilter

       64 bit unsigned wrappable counter."
   ::= {pr1646v2VxlBGIMVpMibCountersEntry 2298478592}

pr1646v2VxlBGIMVpMibCountersInBandwidth15sec OBJECT-TYPE
   SYNTAX      Integer32
   MAX-ACCESS  read-only
   STATUS      current
   DESCRIPTION
      "Path: vxLanBridgeGroup.performance.mibCounters.ifInBandwidth.15sec

       unit name = bps
       formula = 8 * ; 8 /"
   ::= {pr1646v2VxlBGIMVpMibCountersEntry 3037003776}

pr1646v2VxlBGIMVpMibCountersInBandwidth30sec OBJECT-TYPE
   SYNTAX      Integer32
   MAX-ACCESS  read-only
   STATUS      current
   DESCRIPTION
      "Path: vxLanBridgeGroup.performance.mibCounters.ifInBandwidth.30sec

       unit name = bps
       formula = 8 * ; 8 /"
   ::= {pr1646v2VxlBGIMVpMibCountersEntry 3037331456}

pr1646v2VxlBGIMVpMibCountersInBandwidth1min OBJECT-TYPE
   SYNTAX      Integer32
   MAX-ACCESS  read-only
   STATUS      current
   DESCRIPTION
      "Path: vxLanBridgeGroup.performance.mibCounters.ifInBandwidth.1min

       unit name = bps
       formula = 8 * ; 8 /"
   ::= {pr1646v2VxlBGIMVpMibCountersEntry 3037986816}

pr1646v2VxlBGIMVpMibCountersInBandwidth2min OBJECT-TYPE
   SYNTAX      Integer32
   MAX-ACCESS  read-only
   STATUS      current
   DESCRIPTION
      "Path: vxLanBridgeGroup.performance.mibCounters.ifInBandwidth.2min

       unit name = bps
       formula = 8 * ; 8 /"
   ::= {pr1646v2VxlBGIMVpMibCountersEntry 3039297536}

pr1646v2VxlBGIMVpMibCountersInBandwidth5min OBJECT-TYPE
   SYNTAX      Integer32
   MAX-ACCESS  read-only
   STATUS      current
   DESCRIPTION
      "Path: vxLanBridgeGroup.performance.mibCounters.ifInBandwidth.5min

       unit name = bps
       formula = 8 * ; 8 /"
   ::= {pr1646v2VxlBGIMVpMibCountersEntry 3043229696}

pr1646v2VxlBGIMVpMibCountersOutOctets OBJECT-TYPE
   SYNTAX      Counter64
   MAX-ACCESS  read-only
   STATUS      current
   DESCRIPTION
      "Path: vxLanBridgeGroup.performance.mibCounters.ifOutOctets

       64 bit unsigned wrappable counter."
   ::= {pr1646v2VxlBGIMVpMibCountersEntry 1929379840}

pr1646v2VxlBGIMVpMibCountersOutUcastPkts OBJECT-TYPE
   SYNTAX      Counter64
   MAX-ACCESS  read-only
   STATUS      current
   DESCRIPTION
      "Path: vxLanBridgeGroup.performance.mibCounters.ifOutUcastPkts

       64 bit unsigned wrappable counter."
   ::= {pr1646v2VxlBGIMVpMibCountersEntry 1946157056}

pr1646v2VxlBGIMVpMibCountersOutNUcastPkts OBJECT-TYPE
   SYNTAX      Counter64
   MAX-ACCESS  read-only
   STATUS      current
   DESCRIPTION
      "Path: vxLanBridgeGroup.performance.mibCounters.ifOutNUcastPkts

       64 bit unsigned wrappable counter."
   ::= {pr1646v2VxlBGIMVpMibCountersEntry 1962934272}

pr1646v2VxlBGIMVpMibCountersOutBcastPkts OBJECT-TYPE
   SYNTAX      Counter64
   MAX-ACCESS  read-only
   STATUS      current
   DESCRIPTION
      "Path: vxLanBridgeGroup.performance.mibCounters.ifOutBcastPkts

       64 bit unsigned wrappable counter."
   ::= {pr1646v2VxlBGIMVpMibCountersEntry 3640655872}

pr1646v2VxlBGIMVpMibCountersOutMcastPkts OBJECT-TYPE
   SYNTAX      Counter64
   MAX-ACCESS  read-only
   STATUS      current
   DESCRIPTION
      "Path: vxLanBridgeGroup.performance.mibCounters.ifOutMcastPkts

       64 bit unsigned wrappable counter."
   ::= {pr1646v2VxlBGIMVpMibCountersEntry 3808428032}

pr1646v2VxlBGIMVpMibCountersOutDiscards OBJECT-TYPE
   SYNTAX      Counter64
   MAX-ACCESS  read-only
   STATUS      current
   DESCRIPTION
      "Path: vxLanBridgeGroup.performance.mibCounters.ifOutDiscards

       64 bit unsigned wrappable counter."
   ::= {pr1646v2VxlBGIMVpMibCountersEntry 1979711488}

pr1646v2VxlBGIMVpMibCountersOutErrors OBJECT-TYPE
   SYNTAX      Counter64
   MAX-ACCESS  read-only
   STATUS      current
   DESCRIPTION
      "Path: vxLanBridgeGroup.performance.mibCounters.ifOutErrors

       64 bit unsigned wrappable counter."
   ::= {pr1646v2VxlBGIMVpMibCountersEntry 1996488704}

pr1646v2VxlBGIMVpMibCountersOutQLen OBJECT-TYPE
   SYNTAX      Counter32
   MAX-ACCESS  read-only
   STATUS      current
   DESCRIPTION
      "Path: vxLanBridgeGroup.performance.mibCounters.ifOutQLen

       32 bit unsigned wrappable counter."
   ::= {pr1646v2VxlBGIMVpMibCountersEntry 2013265920}

pr1646v2VxlBGIMVpMibCountersOutDropEx OBJECT-TYPE
   SYNTAX      Counter64
   MAX-ACCESS  read-only
   STATUS      current
   DESCRIPTION
      "Path: vxLanBridgeGroup.performance.mibCounters.ifOutDropLevelExceeded

       64 bit unsigned wrappable counter."
   ::= {pr1646v2VxlBGIMVpMibCountersEntry 2030043136}

pr1646v2VxlBGIMVpMibCountersOutDropNoArp OBJECT-TYPE
   SYNTAX      Counter64
   MAX-ACCESS  read-only
   STATUS      current
   DESCRIPTION
      "Path: vxLanBridgeGroup.performance.mibCounters.ifOutDiscardsNoArp

       64 bit unsigned wrappable counter."
   ::= {pr1646v2VxlBGIMVpMibCountersEntry 2248146944}

pr1646v2VxlBGIMVpMibCountersOutDropFilter OBJECT-TYPE
   SYNTAX      Counter64
   MAX-ACCESS  read-only
   STATUS      current
   DESCRIPTION
      "Path: vxLanBridgeGroup.performance.mibCounters.ifOutDiscardsFilter

       64 bit unsigned wrappable counter."
   ::= {pr1646v2VxlBGIMVpMibCountersEntry 2315255808}

pr1646v2VxlBGIMVpMibCountersOutBandwidth15sec OBJECT-TYPE
   SYNTAX      Integer32
   MAX-ACCESS  read-only
   STATUS      current
   DESCRIPTION
      "Path: vxLanBridgeGroup.performance.mibCounters.ifOutBandwidth.15sec

       unit name = bps
       formula = 8 * ; 8 /"
   ::= {pr1646v2VxlBGIMVpMibCountersEntry 3053780992}

pr1646v2VxlBGIMVpMibCountersOutBandwidth30sec OBJECT-TYPE
   SYNTAX      Integer32
   MAX-ACCESS  read-only
   STATUS      current
   DESCRIPTION
      "Path: vxLanBridgeGroup.performance.mibCounters.ifOutBandwidth.30sec

       unit name = bps
       formula = 8 * ; 8 /"
   ::= {pr1646v2VxlBGIMVpMibCountersEntry 3054108672}

pr1646v2VxlBGIMVpMibCountersOutBandwidth1min OBJECT-TYPE
   SYNTAX      Integer32
   MAX-ACCESS  read-only
   STATUS      current
   DESCRIPTION
      "Path: vxLanBridgeGroup.performance.mibCounters.ifOutBandwidth.1min

       unit name = bps
       formula = 8 * ; 8 /"
   ::= {pr1646v2VxlBGIMVpMibCountersEntry 3054764032}

pr1646v2VxlBGIMVpMibCountersOutBandwidth2min OBJECT-TYPE
   SYNTAX      Integer32
   MAX-ACCESS  read-only
   STATUS      current
   DESCRIPTION
      "Path: vxLanBridgeGroup.performance.mibCounters.ifOutBandwidth.2min

       unit name = bps
       formula = 8 * ; 8 /"
   ::= {pr1646v2VxlBGIMVpMibCountersEntry 3056074752}

pr1646v2VxlBGIMVpMibCountersOutBandwidth5min OBJECT-TYPE
   SYNTAX      Integer32
   MAX-ACCESS  read-only
   STATUS      current
   DESCRIPTION
      "Path: vxLanBridgeGroup.performance.mibCounters.ifOutBandwidth.5min

       unit name = bps
       formula = 8 * ; 8 /"
   ::= {pr1646v2VxlBGIMVpMibCountersEntry 3060006912}

pr1646v2VxlBGIMVpMibCountersH2P OBJECT-TYPE
   SYNTAX      SEQUENCE OF Pr1646v2VxlBGIMVpMibCountersH2PEntry
   MAX-ACCESS  not-accessible
   STATUS      current
   DESCRIPTION
      ""
   ::= {pr1646v2VxlBGIMVpMibCounters 2046820352}

pr1646v2VxlBGIMVpMibCountersH2PEntry OBJECT-TYPE
   SYNTAX      Pr1646v2VxlBGIMVpMibCountersH2PEntry
   MAX-ACCESS  not-accessible
   STATUS      current
   DESCRIPTION
      ""
   INDEX      { pr1646v2VxlBGIMVpMibCountersH2PGlobalIx,
                pr1646v2VxlBGIMVpMibCountersH2PTableIx }
   ::= {pr1646v2VxlBGIMVpMibCountersH2P 1}

Pr1646v2VxlBGIMVpMibCountersH2PEntry ::=
   SEQUENCE
      {
      pr1646v2VxlBGIMVpMibCountersH2PGlobalIx
         GlobalIndex,
      pr1646v2VxlBGIMVpMibCountersH2PTableIx
         TableIndex,
      pr1646v2VxlBGIMVpMibCountersH2PSysUpTime
         TimeTicks,
      pr1646v2VxlBGIMVpMibCountersH2PIfUpTime
         TimeTicks,
      pr1646v2VxlBGIMVpMibCountersH2PIfStatChanges
         Counter32,
      pr1646v2VxlBGIMVpMibCountersH2PIfInOctets
         Counter64,
      pr1646v2VxlBGIMVpMibCountersH2PIfInUCPkts
         Counter64,
      pr1646v2VxlBGIMVpMibCountersH2PIfInNUCPkts
         Counter64,
      pr1646v2VxlBGIMVpMibCountersH2PIfInBCPkts
         Counter64,
      pr1646v2VxlBGIMVpMibCountersH2PIfInMCPkts
         Counter64,
      pr1646v2VxlBGIMVpMibCountersH2PIfInDiscards
         Counter64,
      pr1646v2VxlBGIMVpMibCountersH2PIfInErrors
         Counter64,
      pr1646v2VxlBGIMVpMibCountersH2PIfInUnkwn
         Counter64,
      pr1646v2VxlBGIMVpMibCountersH2PInDropEx
         Counter64,
      pr1646v2VxlBGIMVpMibCountersH2PInDropNoMac
         Counter64,
      pr1646v2VxlBGIMVpMibCountersH2PInDropNUCast
         Counter64,
      pr1646v2VxlBGIMVpMibCountersH2PInDropFilter
         Counter64,
      pr1646v2VxlBGIMVpMibCountersH2PIfInBandwidth
         Integer32,
      pr1646v2VxlBGIMVpMibCountersH2PIfOutOctets
         Counter64,
      pr1646v2VxlBGIMVpMibCountersH2PIfOutUCPkts
         Counter64,
      pr1646v2VxlBGIMVpMibCountersH2PIfOutNUCPkts
         Counter64,
      pr1646v2VxlBGIMVpMibCountersH2PIfOutBCPkts
         Counter64,
      pr1646v2VxlBGIMVpMibCountersH2PIfOutMCPkts
         Counter64,
      pr1646v2VxlBGIMVpMibCountersH2PIfOutDiscards
         Counter64,
      pr1646v2VxlBGIMVpMibCountersH2PIfOutErrors
         Counter64,
      pr1646v2VxlBGIMVpMibCountersH2POutDropEx
         Counter64,
      pr1646v2VxlBGIMVpMibCountersH2POutDropNoArp
         Counter64,
      pr1646v2VxlBGIMVpMibCountersH2POutDropFilter
         Counter64,
      pr1646v2VxlBGIMVpMibCountersH2PIfOutBandwidth
         Integer32,
      pr1646v2VxlBGIMVpMibCountersH2PIfErrSec
         Counter32
      }

pr1646v2VxlBGIMVpMibCountersH2PGlobalIx OBJECT-TYPE
   SYNTAX      GlobalIndex
   MAX-ACCESS  not-accessible
   STATUS      current
   DESCRIPTION
      "The value of the tlsCntTreeGlobalIndex of the MANAGED OBJECT."
   ::= {pr1646v2VxlBGIMVpMibCountersH2PEntry 10}

pr1646v2VxlBGIMVpMibCountersH2PTableIx OBJECT-TYPE
   SYNTAX      TableIndex
   MAX-ACCESS  not-accessible
   STATUS      current
   DESCRIPTION
      ""
   ::= {pr1646v2VxlBGIMVpMibCountersH2PEntry 11}

pr1646v2VxlBGIMVpMibCountersH2PSysUpTime OBJECT-TYPE
   SYNTAX      TimeTicks
   MAX-ACCESS  read-only
   STATUS      current
   DESCRIPTION
      "Path: vxLanBridgeGroup.performance.mibCounters.h2Performance.sysUpTime

       Time in centi-second."
   ::= {pr1646v2VxlBGIMVpMibCountersH2PEntry 16777216}

pr1646v2VxlBGIMVpMibCountersH2PIfUpTime OBJECT-TYPE
   SYNTAX      TimeTicks
   MAX-ACCESS  read-only
   STATUS      current
   DESCRIPTION
      "Path: vxLanBridgeGroup.performance.mibCounters.h2Performance.ifUpTime

       Time in centi-second."
   ::= {pr1646v2VxlBGIMVpMibCountersH2PEntry 33554432}

pr1646v2VxlBGIMVpMibCountersH2PIfStatChanges OBJECT-TYPE
   SYNTAX      Counter32
   MAX-ACCESS  read-only
   STATUS      current
   DESCRIPTION
      "Path: vxLanBridgeGroup.performance.mibCounters.h2Performance.ifStatusChanges

       32 bit unsigned wrappable counter."
   ::= {pr1646v2VxlBGIMVpMibCountersH2PEntry 50331648}

pr1646v2VxlBGIMVpMibCountersH2PIfInOctets OBJECT-TYPE
   SYNTAX      Counter64
   MAX-ACCESS  read-only
   STATUS      current
   DESCRIPTION
      "Path: vxLanBridgeGroup.performance.mibCounters.h2Performance.ifInOctets

       64 bit unsigned wrappable counter."
   ::= {pr1646v2VxlBGIMVpMibCountersH2PEntry 67108864}

pr1646v2VxlBGIMVpMibCountersH2PIfInUCPkts OBJECT-TYPE
   SYNTAX      Counter64
   MAX-ACCESS  read-only
   STATUS      current
   DESCRIPTION
      "Path: vxLanBridgeGroup.performance.mibCounters.h2Performance.ifInUcastPkts

       64 bit unsigned wrappable counter."
   ::= {pr1646v2VxlBGIMVpMibCountersH2PEntry 83886080}

pr1646v2VxlBGIMVpMibCountersH2PIfInNUCPkts OBJECT-TYPE
   SYNTAX      Counter64
   MAX-ACCESS  read-only
   STATUS      current
   DESCRIPTION
      "Path: vxLanBridgeGroup.performance.mibCounters.h2Performance.ifInNUcastPkts

       64 bit unsigned wrappable counter."
   ::= {pr1646v2VxlBGIMVpMibCountersH2PEntry 100663296}

pr1646v2VxlBGIMVpMibCountersH2PIfInBCPkts OBJECT-TYPE
   SYNTAX      Counter64
   MAX-ACCESS  read-only
   STATUS      current
   DESCRIPTION
      "Path: vxLanBridgeGroup.performance.mibCounters.h2Performance.ifInBcastPkts

       64 bit unsigned wrappable counter."
   ::= {pr1646v2VxlBGIMVpMibCountersH2PEntry 419430400}

pr1646v2VxlBGIMVpMibCountersH2PIfInMCPkts OBJECT-TYPE
   SYNTAX      Counter64
   MAX-ACCESS  read-only
   STATUS      current
   DESCRIPTION
      "Path: vxLanBridgeGroup.performance.mibCounters.h2Performance.ifInMcastPkts

       64 bit unsigned wrappable counter."
   ::= {pr1646v2VxlBGIMVpMibCountersH2PEntry 436207616}

pr1646v2VxlBGIMVpMibCountersH2PIfInDiscards OBJECT-TYPE
   SYNTAX      Counter64
   MAX-ACCESS  read-only
   STATUS      current
   DESCRIPTION
      "Path: vxLanBridgeGroup.performance.mibCounters.h2Performance.ifInDiscards

       64 bit unsigned wrappable counter."
   ::= {pr1646v2VxlBGIMVpMibCountersH2PEntry 117440512}

pr1646v2VxlBGIMVpMibCountersH2PIfInErrors OBJECT-TYPE
   SYNTAX      Counter64
   MAX-ACCESS  read-only
   STATUS      current
   DESCRIPTION
      "Path: vxLanBridgeGroup.performance.mibCounters.h2Performance.ifInErrors

       64 bit unsigned wrappable counter."
   ::= {pr1646v2VxlBGIMVpMibCountersH2PEntry 134217728}

pr1646v2VxlBGIMVpMibCountersH2PIfInUnkwn OBJECT-TYPE
   SYNTAX      Counter64
   MAX-ACCESS  read-only
   STATUS      current
   DESCRIPTION
      "Path: vxLanBridgeGroup.performance.mibCounters.h2Performance.ifInUnknownProtos

       64 bit unsigned wrappable counter."
   ::= {pr1646v2VxlBGIMVpMibCountersH2PEntry 150994944}

pr1646v2VxlBGIMVpMibCountersH2PInDropEx OBJECT-TYPE
   SYNTAX      Counter64
   MAX-ACCESS  read-only
   STATUS      current
   DESCRIPTION
      "Path: vxLanBridgeGroup.performance.mibCounters.h2Performance.ifInDropLevelExceeded

       64 bit unsigned wrappable counter."
   ::= {pr1646v2VxlBGIMVpMibCountersH2PEntry 335544320}

pr1646v2VxlBGIMVpMibCountersH2PInDropNoMac OBJECT-TYPE
   SYNTAX      Counter64
   MAX-ACCESS  read-only
   STATUS      current
   DESCRIPTION
      "Path: vxLanBridgeGroup.performance.mibCounters.h2Performance.fInDiscardsNoMacFit

       64 bit unsigned wrappable counter."
   ::= {pr1646v2VxlBGIMVpMibCountersH2PEntry 301989888}

pr1646v2VxlBGIMVpMibCountersH2PInDropNUCast OBJECT-TYPE
   SYNTAX      Counter64
   MAX-ACCESS  read-only
   STATUS      current
   DESCRIPTION
      "Path: vxLanBridgeGroup.performance.mibCounters.h2Performance.fInDiscardsNUCast

       64 bit unsigned wrappable counter."
   ::= {pr1646v2VxlBGIMVpMibCountersH2PEntry 318767104}

pr1646v2VxlBGIMVpMibCountersH2PInDropFilter OBJECT-TYPE
   SYNTAX      Counter64
   MAX-ACCESS  read-only
   STATUS      current
   DESCRIPTION
      "Path: vxLanBridgeGroup.performance.mibCounters.h2Performance.fInDiscardsFilter

       64 bit unsigned wrappable counter."
   ::= {pr1646v2VxlBGIMVpMibCountersH2PEntry 385875968}

pr1646v2VxlBGIMVpMibCountersH2PIfInBandwidth OBJECT-TYPE
   SYNTAX      Integer32
   MAX-ACCESS  read-only
   STATUS      current
   DESCRIPTION
      "Path: vxLanBridgeGroup.performance.mibCounters.h2Performance.ifInBandwidth

       unit name = bps
       formula = 8 * ; 8 /"
   ::= {pr1646v2VxlBGIMVpMibCountersH2PEntry 268435456}

pr1646v2VxlBGIMVpMibCountersH2PIfOutOctets OBJECT-TYPE
   SYNTAX      Counter64
   MAX-ACCESS  read-only
   STATUS      current
   DESCRIPTION
      "Path: vxLanBridgeGroup.performance.mibCounters.h2Performance.ifOutOctets

       64 bit unsigned wrappable counter."
   ::= {pr1646v2VxlBGIMVpMibCountersH2PEntry 167772160}

pr1646v2VxlBGIMVpMibCountersH2PIfOutUCPkts OBJECT-TYPE
   SYNTAX      Counter64
   MAX-ACCESS  read-only
   STATUS      current
   DESCRIPTION
      "Path: vxLanBridgeGroup.performance.mibCounters.h2Performance.ifOutUcastPkts

       64 bit unsigned wrappable counter."
   ::= {pr1646v2VxlBGIMVpMibCountersH2PEntry 184549376}

pr1646v2VxlBGIMVpMibCountersH2PIfOutNUCPkts OBJECT-TYPE
   SYNTAX      Counter64
   MAX-ACCESS  read-only
   STATUS      current
   DESCRIPTION
      "Path: vxLanBridgeGroup.performance.mibCounters.h2Performance.ifOutNUcastPkts

       64 bit unsigned wrappable counter."
   ::= {pr1646v2VxlBGIMVpMibCountersH2PEntry 201326592}

pr1646v2VxlBGIMVpMibCountersH2PIfOutBCPkts OBJECT-TYPE
   SYNTAX      Counter64
   MAX-ACCESS  read-only
   STATUS      current
   DESCRIPTION
      "Path: vxLanBridgeGroup.performance.mibCounters.h2Performance.ifOutBcastPkts

       64 bit unsigned wrappable counter."
   ::= {pr1646v2VxlBGIMVpMibCountersH2PEntry 452984832}

pr1646v2VxlBGIMVpMibCountersH2PIfOutMCPkts OBJECT-TYPE
   SYNTAX      Counter64
   MAX-ACCESS  read-only
   STATUS      current
   DESCRIPTION
      "Path: vxLanBridgeGroup.performance.mibCounters.h2Performance.ifOutMcastPkts

       64 bit unsigned wrappable counter."
   ::= {pr1646v2VxlBGIMVpMibCountersH2PEntry 469762048}

pr1646v2VxlBGIMVpMibCountersH2PIfOutDiscards OBJECT-TYPE
   SYNTAX      Counter64
   MAX-ACCESS  read-only
   STATUS      current
   DESCRIPTION
      "Path: vxLanBridgeGroup.performance.mibCounters.h2Performance.ifOutDiscards

       64 bit unsigned wrappable counter."
   ::= {pr1646v2VxlBGIMVpMibCountersH2PEntry 218103808}

pr1646v2VxlBGIMVpMibCountersH2PIfOutErrors OBJECT-TYPE
   SYNTAX      Counter64
   MAX-ACCESS  read-only
   STATUS      current
   DESCRIPTION
      "Path: vxLanBridgeGroup.performance.mibCounters.h2Performance.ifOutErrors

       64 bit unsigned wrappable counter."
   ::= {pr1646v2VxlBGIMVpMibCountersH2PEntry 234881024}

pr1646v2VxlBGIMVpMibCountersH2POutDropEx OBJECT-TYPE
   SYNTAX      Counter64
   MAX-ACCESS  read-only
   STATUS      current
   DESCRIPTION
      "Path: vxLanBridgeGroup.performance.mibCounters.h2Performance.ifOutDropLevelExceeded

       64 bit unsigned wrappable counter."
   ::= {pr1646v2VxlBGIMVpMibCountersH2PEntry 352321536}

pr1646v2VxlBGIMVpMibCountersH2POutDropNoArp OBJECT-TYPE
   SYNTAX      Counter64
   MAX-ACCESS  read-only
   STATUS      current
   DESCRIPTION
      "Path: vxLanBridgeGroup.performance.mibCounters.h2Performance.ifOutDiscardsNoArp

       64 bit unsigned wrappable counter."
   ::= {pr1646v2VxlBGIMVpMibCountersH2PEntry 369098752}

pr1646v2VxlBGIMVpMibCountersH2POutDropFilter OBJECT-TYPE
   SYNTAX      Counter64
   MAX-ACCESS  read-only
   STATUS      current
   DESCRIPTION
      "Path: vxLanBridgeGroup.performance.mibCounters.h2Performance.ifOutDiscardsFilter

       64 bit unsigned wrappable counter."
   ::= {pr1646v2VxlBGIMVpMibCountersH2PEntry 402653184}

pr1646v2VxlBGIMVpMibCountersH2PIfOutBandwidth OBJECT-TYPE
   SYNTAX      Integer32
   MAX-ACCESS  read-only
   STATUS      current
   DESCRIPTION
      "Path: vxLanBridgeGroup.performance.mibCounters.h2Performance.ifOutBandwidth

       unit name = bps
       formula = 8 * ; 8 /"
   ::= {pr1646v2VxlBGIMVpMibCountersH2PEntry 285212672}

pr1646v2VxlBGIMVpMibCountersH2PIfErrSec OBJECT-TYPE
   SYNTAX      Counter32
   MAX-ACCESS  read-only
   STATUS      current
   DESCRIPTION
      "Path: vxLanBridgeGroup.performance.mibCounters.h2Performance.ifErrSec

       32 bit unsigned wrappable counter."
   ::= {pr1646v2VxlBGIMVpMibCountersH2PEntry 251658240}

pr1646v2VxlBGIMVpMibCountersH24P OBJECT-TYPE
   SYNTAX      SEQUENCE OF Pr1646v2VxlBGIMVpMibCountersH24PEntry
   MAX-ACCESS  not-accessible
   STATUS      current
   DESCRIPTION
      ""
   ::= {pr1646v2VxlBGIMVpMibCounters 2063597568}

pr1646v2VxlBGIMVpMibCountersH24PEntry OBJECT-TYPE
   SYNTAX      Pr1646v2VxlBGIMVpMibCountersH24PEntry
   MAX-ACCESS  not-accessible
   STATUS      current
   DESCRIPTION
      ""
   INDEX      { pr1646v2VxlBGIMVpMibCountersH24PGlobalIx,
                pr1646v2VxlBGIMVpMibCountersH24PTableIx }
   ::= {pr1646v2VxlBGIMVpMibCountersH24P 1}

Pr1646v2VxlBGIMVpMibCountersH24PEntry ::=
   SEQUENCE
      {
      pr1646v2VxlBGIMVpMibCountersH24PGlobalIx
         GlobalIndex,
      pr1646v2VxlBGIMVpMibCountersH24PTableIx
         TableIndex,
      pr1646v2VxlBGIMVpMibCountersH24PSysUpTime
         TimeTicks,
      pr1646v2VxlBGIMVpMibCountersH24PIfUpTime
         TimeTicks,
      pr1646v2VxlBGIMVpMibCountersH24PIfStatChanges
         Counter32,
      pr1646v2VxlBGIMVpMibCountersH24PIfInOctets
         Counter64,
      pr1646v2VxlBGIMVpMibCountersH24PIfInUCPkts
         Counter64,
      pr1646v2VxlBGIMVpMibCountersH24PIfInNUCPkts
         Counter64,
      pr1646v2VxlBGIMVpMibCountersH24PIfInBCPkts
         Counter64,
      pr1646v2VxlBGIMVpMibCountersH24PIfInMCPkts
         Counter64,
      pr1646v2VxlBGIMVpMibCountersH24PIfInDiscards
         Counter64,
      pr1646v2VxlBGIMVpMibCountersH24PIfInErrors
         Counter64,
      pr1646v2VxlBGIMVpMibCountersH24PIfInUnkwn
         Counter64,
      pr1646v2VxlBGIMVpMibCountersH24PInDropEx
         Counter64,
      pr1646v2VxlBGIMVpMibCountersH24PInDropNoMac
         Counter64,
      pr1646v2VxlBGIMVpMibCountersH24PInDropNUCast
         Counter64,
      pr1646v2VxlBGIMVpMibCountersH24PInDropFilter
         Counter64,
      pr1646v2VxlBGIMVpMibCountersH24PIfInBandwidth
         Integer32,
      pr1646v2VxlBGIMVpMibCountersH24PIfOutOctets
         Counter64,
      pr1646v2VxlBGIMVpMibCountersH24PIfOutUCPkts
         Counter64,
      pr1646v2VxlBGIMVpMibCountersH24PIfOutNUCPkts
         Counter64,
      pr1646v2VxlBGIMVpMibCountersH24PIfOutBCPkts
         Counter64,
      pr1646v2VxlBGIMVpMibCountersH24PIfOutMCPkts
         Counter64,
      pr1646v2VxlBGIMVpMibCountersH24PIfOutDiscards
         Counter64,
      pr1646v2VxlBGIMVpMibCountersH24PIfOutErrors
         Counter64,
      pr1646v2VxlBGIMVpMibCountersH24POutDropEx
         Counter64,
      pr1646v2VxlBGIMVpMibCountersH24POutDropNoArp
         Counter64,
      pr1646v2VxlBGIMVpMibCountersH24POutDropFilter
         Counter64,
      pr1646v2VxlBGIMVpMibCountersH24PIfOutBandwidth
         Integer32,
      pr1646v2VxlBGIMVpMibCountersH24PIfErrSec
         Counter32
      }

pr1646v2VxlBGIMVpMibCountersH24PGlobalIx OBJECT-TYPE
   SYNTAX      GlobalIndex
   MAX-ACCESS  not-accessible
   STATUS      current
   DESCRIPTION
      "The value of the tlsCntTreeGlobalIndex of the MANAGED OBJECT."
   ::= {pr1646v2VxlBGIMVpMibCountersH24PEntry 10}

pr1646v2VxlBGIMVpMibCountersH24PTableIx OBJECT-TYPE
   SYNTAX      TableIndex
   MAX-ACCESS  not-accessible
   STATUS      current
   DESCRIPTION
      ""
   ::= {pr1646v2VxlBGIMVpMibCountersH24PEntry 11}

pr1646v2VxlBGIMVpMibCountersH24PSysUpTime OBJECT-TYPE
   SYNTAX      TimeTicks
   MAX-ACCESS  read-only
   STATUS      current
   DESCRIPTION
      "Path: vxLanBridgeGroup.performance.mibCounters.h24Performance.sysUpTime

       Time in centi-second."
   ::= {pr1646v2VxlBGIMVpMibCountersH24PEntry 16777216}

pr1646v2VxlBGIMVpMibCountersH24PIfUpTime OBJECT-TYPE
   SYNTAX      TimeTicks
   MAX-ACCESS  read-only
   STATUS      current
   DESCRIPTION
      "Path: vxLanBridgeGroup.performance.mibCounters.h24Performance.ifUpTime

       Time in centi-second."
   ::= {pr1646v2VxlBGIMVpMibCountersH24PEntry 33554432}

pr1646v2VxlBGIMVpMibCountersH24PIfStatChanges OBJECT-TYPE
   SYNTAX      Counter32
   MAX-ACCESS  read-only
   STATUS      current
   DESCRIPTION
      "Path: vxLanBridgeGroup.performance.mibCounters.h24Performance.ifStatusChanges

       32 bit unsigned wrappable counter."
   ::= {pr1646v2VxlBGIMVpMibCountersH24PEntry 50331648}

pr1646v2VxlBGIMVpMibCountersH24PIfInOctets OBJECT-TYPE
   SYNTAX      Counter64
   MAX-ACCESS  read-only
   STATUS      current
   DESCRIPTION
      "Path: vxLanBridgeGroup.performance.mibCounters.h24Performance.ifInOctets

       64 bit unsigned wrappable counter."
   ::= {pr1646v2VxlBGIMVpMibCountersH24PEntry 67108864}

pr1646v2VxlBGIMVpMibCountersH24PIfInUCPkts OBJECT-TYPE
   SYNTAX      Counter64
   MAX-ACCESS  read-only
   STATUS      current
   DESCRIPTION
      "Path: vxLanBridgeGroup.performance.mibCounters.h24Performance.ifInUcastPkts

       64 bit unsigned wrappable counter."
   ::= {pr1646v2VxlBGIMVpMibCountersH24PEntry 83886080}

pr1646v2VxlBGIMVpMibCountersH24PIfInNUCPkts OBJECT-TYPE
   SYNTAX      Counter64
   MAX-ACCESS  read-only
   STATUS      current
   DESCRIPTION
      "Path: vxLanBridgeGroup.performance.mibCounters.h24Performance.ifInNUcastPkts

       64 bit unsigned wrappable counter."
   ::= {pr1646v2VxlBGIMVpMibCountersH24PEntry 100663296}

pr1646v2VxlBGIMVpMibCountersH24PIfInBCPkts OBJECT-TYPE
   SYNTAX      Counter64
   MAX-ACCESS  read-only
   STATUS      current
   DESCRIPTION
      "Path: vxLanBridgeGroup.performance.mibCounters.h24Performance.ifInBcastPkts

       64 bit unsigned wrappable counter."
   ::= {pr1646v2VxlBGIMVpMibCountersH24PEntry 419430400}

pr1646v2VxlBGIMVpMibCountersH24PIfInMCPkts OBJECT-TYPE
   SYNTAX      Counter64
   MAX-ACCESS  read-only
   STATUS      current
   DESCRIPTION
      "Path: vxLanBridgeGroup.performance.mibCounters.h24Performance.ifInMcastPkts

       64 bit unsigned wrappable counter."
   ::= {pr1646v2VxlBGIMVpMibCountersH24PEntry 436207616}

pr1646v2VxlBGIMVpMibCountersH24PIfInDiscards OBJECT-TYPE
   SYNTAX      Counter64
   MAX-ACCESS  read-only
   STATUS      current
   DESCRIPTION
      "Path: vxLanBridgeGroup.performance.mibCounters.h24Performance.ifInDiscards

       64 bit unsigned wrappable counter."
   ::= {pr1646v2VxlBGIMVpMibCountersH24PEntry 117440512}

pr1646v2VxlBGIMVpMibCountersH24PIfInErrors OBJECT-TYPE
   SYNTAX      Counter64
   MAX-ACCESS  read-only
   STATUS      current
   DESCRIPTION
      "Path: vxLanBridgeGroup.performance.mibCounters.h24Performance.ifInErrors

       64 bit unsigned wrappable counter."
   ::= {pr1646v2VxlBGIMVpMibCountersH24PEntry 134217728}

pr1646v2VxlBGIMVpMibCountersH24PIfInUnkwn OBJECT-TYPE
   SYNTAX      Counter64
   MAX-ACCESS  read-only
   STATUS      current
   DESCRIPTION
      "Path: vxLanBridgeGroup.performance.mibCounters.h24Performance.ifInUnknownProtos

       64 bit unsigned wrappable counter."
   ::= {pr1646v2VxlBGIMVpMibCountersH24PEntry 150994944}

pr1646v2VxlBGIMVpMibCountersH24PInDropEx OBJECT-TYPE
   SYNTAX      Counter64
   MAX-ACCESS  read-only
   STATUS      current
   DESCRIPTION
      "Path: vxLanBridgeGroup.performance.mibCounters.h24Performance.ifInDropLevelExceeded

       64 bit unsigned wrappable counter."
   ::= {pr1646v2VxlBGIMVpMibCountersH24PEntry 335544320}

pr1646v2VxlBGIMVpMibCountersH24PInDropNoMac OBJECT-TYPE
   SYNTAX      Counter64
   MAX-ACCESS  read-only
   STATUS      current
   DESCRIPTION
      "Path: vxLanBridgeGroup.performance.mibCounters.h24Performance.fInDiscardsNoMacFit

       64 bit unsigned wrappable counter."
   ::= {pr1646v2VxlBGIMVpMibCountersH24PEntry 301989888}

pr1646v2VxlBGIMVpMibCountersH24PInDropNUCast OBJECT-TYPE
   SYNTAX      Counter64
   MAX-ACCESS  read-only
   STATUS      current
   DESCRIPTION
      "Path: vxLanBridgeGroup.performance.mibCounters.h24Performance.fInDiscardsNUCast

       64 bit unsigned wrappable counter."
   ::= {pr1646v2VxlBGIMVpMibCountersH24PEntry 318767104}

pr1646v2VxlBGIMVpMibCountersH24PInDropFilter OBJECT-TYPE
   SYNTAX      Counter64
   MAX-ACCESS  read-only
   STATUS      current
   DESCRIPTION
      "Path: vxLanBridgeGroup.performance.mibCounters.h24Performance.fInDiscardsFilter

       64 bit unsigned wrappable counter."
   ::= {pr1646v2VxlBGIMVpMibCountersH24PEntry 385875968}

pr1646v2VxlBGIMVpMibCountersH24PIfInBandwidth OBJECT-TYPE
   SYNTAX      Integer32
   MAX-ACCESS  read-only
   STATUS      current
   DESCRIPTION
      "Path: vxLanBridgeGroup.performance.mibCounters.h24Performance.ifInBandwidth

       unit name = bps
       formula = 8 * ; 8 /"
   ::= {pr1646v2VxlBGIMVpMibCountersH24PEntry 268435456}

pr1646v2VxlBGIMVpMibCountersH24PIfOutOctets OBJECT-TYPE
   SYNTAX      Counter64
   MAX-ACCESS  read-only
   STATUS      current
   DESCRIPTION
      "Path: vxLanBridgeGroup.performance.mibCounters.h24Performance.ifOutOctets

       64 bit unsigned wrappable counter."
   ::= {pr1646v2VxlBGIMVpMibCountersH24PEntry 167772160}

pr1646v2VxlBGIMVpMibCountersH24PIfOutUCPkts OBJECT-TYPE
   SYNTAX      Counter64
   MAX-ACCESS  read-only
   STATUS      current
   DESCRIPTION
      "Path: vxLanBridgeGroup.performance.mibCounters.h24Performance.ifOutUcastPkts

       64 bit unsigned wrappable counter."
   ::= {pr1646v2VxlBGIMVpMibCountersH24PEntry 184549376}

pr1646v2VxlBGIMVpMibCountersH24PIfOutNUCPkts OBJECT-TYPE
   SYNTAX      Counter64
   MAX-ACCESS  read-only
   STATUS      current
   DESCRIPTION
      "Path: vxLanBridgeGroup.performance.mibCounters.h24Performance.ifOutNUcastPkts

       64 bit unsigned wrappable counter."
   ::= {pr1646v2VxlBGIMVpMibCountersH24PEntry 201326592}

pr1646v2VxlBGIMVpMibCountersH24PIfOutBCPkts OBJECT-TYPE
   SYNTAX      Counter64
   MAX-ACCESS  read-only
   STATUS      current
   DESCRIPTION
      "Path: vxLanBridgeGroup.performance.mibCounters.h24Performance.ifOutBcastPkts

       64 bit unsigned wrappable counter."
   ::= {pr1646v2VxlBGIMVpMibCountersH24PEntry 452984832}

pr1646v2VxlBGIMVpMibCountersH24PIfOutMCPkts OBJECT-TYPE
   SYNTAX      Counter64
   MAX-ACCESS  read-only
   STATUS      current
   DESCRIPTION
      "Path: vxLanBridgeGroup.performance.mibCounters.h24Performance.ifOutMcastPkts

       64 bit unsigned wrappable counter."
   ::= {pr1646v2VxlBGIMVpMibCountersH24PEntry 469762048}

pr1646v2VxlBGIMVpMibCountersH24PIfOutDiscards OBJECT-TYPE
   SYNTAX      Counter64
   MAX-ACCESS  read-only
   STATUS      current
   DESCRIPTION
      "Path: vxLanBridgeGroup.performance.mibCounters.h24Performance.ifOutDiscards

       64 bit unsigned wrappable counter."
   ::= {pr1646v2VxlBGIMVpMibCountersH24PEntry 218103808}

pr1646v2VxlBGIMVpMibCountersH24PIfOutErrors OBJECT-TYPE
   SYNTAX      Counter64
   MAX-ACCESS  read-only
   STATUS      current
   DESCRIPTION
      "Path: vxLanBridgeGroup.performance.mibCounters.h24Performance.ifOutErrors

       64 bit unsigned wrappable counter."
   ::= {pr1646v2VxlBGIMVpMibCountersH24PEntry 234881024}

pr1646v2VxlBGIMVpMibCountersH24POutDropEx OBJECT-TYPE
   SYNTAX      Counter64
   MAX-ACCESS  read-only
   STATUS      current
   DESCRIPTION
      "Path: vxLanBridgeGroup.performance.mibCounters.h24Performance.ifOutDropLevelExceeded

       64 bit unsigned wrappable counter."
   ::= {pr1646v2VxlBGIMVpMibCountersH24PEntry 352321536}

pr1646v2VxlBGIMVpMibCountersH24POutDropNoArp OBJECT-TYPE
   SYNTAX      Counter64
   MAX-ACCESS  read-only
   STATUS      current
   DESCRIPTION
      "Path: vxLanBridgeGroup.performance.mibCounters.h24Performance.ifOutDiscardsNoArp

       64 bit unsigned wrappable counter."
   ::= {pr1646v2VxlBGIMVpMibCountersH24PEntry 369098752}

pr1646v2VxlBGIMVpMibCountersH24POutDropFilter OBJECT-TYPE
   SYNTAX      Counter64
   MAX-ACCESS  read-only
   STATUS      current
   DESCRIPTION
      "Path: vxLanBridgeGroup.performance.mibCounters.h24Performance.ifOutDiscardsFilter

       64 bit unsigned wrappable counter."
   ::= {pr1646v2VxlBGIMVpMibCountersH24PEntry 402653184}

pr1646v2VxlBGIMVpMibCountersH24PIfOutBandwidth OBJECT-TYPE
   SYNTAX      Integer32
   MAX-ACCESS  read-only
   STATUS      current
   DESCRIPTION
      "Path: vxLanBridgeGroup.performance.mibCounters.h24Performance.ifOutBandwidth

       unit name = bps
       formula = 8 * ; 8 /"
   ::= {pr1646v2VxlBGIMVpMibCountersH24PEntry 285212672}

pr1646v2VxlBGIMVpMibCountersH24PIfErrSec OBJECT-TYPE
   SYNTAX      Counter32
   MAX-ACCESS  read-only
   STATUS      current
   DESCRIPTION
      "Path: vxLanBridgeGroup.performance.mibCounters.h24Performance.ifErrSec

       32 bit unsigned wrappable counter."
   ::= {pr1646v2VxlBGIMVpMibCountersH24PEntry 251658240}

pr1646v2VxlBGIMVpMibCountersD7P OBJECT-TYPE
   SYNTAX      SEQUENCE OF Pr1646v2VxlBGIMVpMibCountersD7PEntry
   MAX-ACCESS  not-accessible
   STATUS      current
   DESCRIPTION
      ""
   ::= {pr1646v2VxlBGIMVpMibCounters 2080374784}

pr1646v2VxlBGIMVpMibCountersD7PEntry OBJECT-TYPE
   SYNTAX      Pr1646v2VxlBGIMVpMibCountersD7PEntry
   MAX-ACCESS  not-accessible
   STATUS      current
   DESCRIPTION
      ""
   INDEX      { pr1646v2VxlBGIMVpMibCountersD7PGlobalIx,
                pr1646v2VxlBGIMVpMibCountersD7PTableIx }
   ::= {pr1646v2VxlBGIMVpMibCountersD7P 1}

Pr1646v2VxlBGIMVpMibCountersD7PEntry ::=
   SEQUENCE
      {
      pr1646v2VxlBGIMVpMibCountersD7PGlobalIx
         GlobalIndex,
      pr1646v2VxlBGIMVpMibCountersD7PTableIx
         TableIndex,
      pr1646v2VxlBGIMVpMibCountersD7PSysUpTime
         TimeTicks,
      pr1646v2VxlBGIMVpMibCountersD7PIfUpTime
         TimeTicks,
      pr1646v2VxlBGIMVpMibCountersD7PIfStatChanges
         Counter32,
      pr1646v2VxlBGIMVpMibCountersD7PIfInOctets
         Counter64,
      pr1646v2VxlBGIMVpMibCountersD7PIfInUCPkts
         Counter64,
      pr1646v2VxlBGIMVpMibCountersD7PIfInNUCPkts
         Counter64,
      pr1646v2VxlBGIMVpMibCountersD7PIfInBCPkts
         Counter64,
      pr1646v2VxlBGIMVpMibCountersD7PIfInMCPkts
         Counter64,
      pr1646v2VxlBGIMVpMibCountersD7PIfInDiscards
         Counter64,
      pr1646v2VxlBGIMVpMibCountersD7PIfInErrors
         Counter64,
      pr1646v2VxlBGIMVpMibCountersD7PIfInUnkwn
         Counter64,
      pr1646v2VxlBGIMVpMibCountersD7PInDropEx
         Counter64,
      pr1646v2VxlBGIMVpMibCountersD7PInDropNoMac
         Counter64,
      pr1646v2VxlBGIMVpMibCountersD7PInDropNUCast
         Counter64,
      pr1646v2VxlBGIMVpMibCountersD7PInDropFilter
         Counter64,
      pr1646v2VxlBGIMVpMibCountersD7PIfInBandwidth
         Integer32,
      pr1646v2VxlBGIMVpMibCountersD7PIfOutOctets
         Counter64,
      pr1646v2VxlBGIMVpMibCountersD7PIfOutUCPkts
         Counter64,
      pr1646v2VxlBGIMVpMibCountersD7PIfOutNUCPkts
         Counter64,
      pr1646v2VxlBGIMVpMibCountersD7PIfOutBCPkts
         Counter64,
      pr1646v2VxlBGIMVpMibCountersD7PIfOutMCPkts
         Counter64,
      pr1646v2VxlBGIMVpMibCountersD7PIfOutDiscards
         Counter64,
      pr1646v2VxlBGIMVpMibCountersD7PIfOutErrors
         Counter64,
      pr1646v2VxlBGIMVpMibCountersD7POutDropEx
         Counter64,
      pr1646v2VxlBGIMVpMibCountersD7POutDropNoArp
         Counter64,
      pr1646v2VxlBGIMVpMibCountersD7POutDropFilter
         Counter64,
      pr1646v2VxlBGIMVpMibCountersD7PIfOutBandwidth
         Integer32,
      pr1646v2VxlBGIMVpMibCountersD7PIfErrSec
         Counter32
      }

pr1646v2VxlBGIMVpMibCountersD7PGlobalIx OBJECT-TYPE
   SYNTAX      GlobalIndex
   MAX-ACCESS  not-accessible
   STATUS      current
   DESCRIPTION
      "The value of the tlsCntTreeGlobalIndex of the MANAGED OBJECT."
   ::= {pr1646v2VxlBGIMVpMibCountersD7PEntry 10}

pr1646v2VxlBGIMVpMibCountersD7PTableIx OBJECT-TYPE
   SYNTAX      TableIndex
   MAX-ACCESS  not-accessible
   STATUS      current
   DESCRIPTION
      ""
   ::= {pr1646v2VxlBGIMVpMibCountersD7PEntry 11}

pr1646v2VxlBGIMVpMibCountersD7PSysUpTime OBJECT-TYPE
   SYNTAX      TimeTicks
   MAX-ACCESS  read-only
   STATUS      current
   DESCRIPTION
      "Path: vxLanBridgeGroup.performance.mibCounters.d7Performance.sysUpTime

       Time in centi-second."
   ::= {pr1646v2VxlBGIMVpMibCountersD7PEntry 16777216}

pr1646v2VxlBGIMVpMibCountersD7PIfUpTime OBJECT-TYPE
   SYNTAX      TimeTicks
   MAX-ACCESS  read-only
   STATUS      current
   DESCRIPTION
      "Path: vxLanBridgeGroup.performance.mibCounters.d7Performance.ifUpTime

       Time in centi-second."
   ::= {pr1646v2VxlBGIMVpMibCountersD7PEntry 33554432}

pr1646v2VxlBGIMVpMibCountersD7PIfStatChanges OBJECT-TYPE
   SYNTAX      Counter32
   MAX-ACCESS  read-only
   STATUS      current
   DESCRIPTION
      "Path: vxLanBridgeGroup.performance.mibCounters.d7Performance.ifStatusChanges

       32 bit unsigned wrappable counter."
   ::= {pr1646v2VxlBGIMVpMibCountersD7PEntry 50331648}

pr1646v2VxlBGIMVpMibCountersD7PIfInOctets OBJECT-TYPE
   SYNTAX      Counter64
   MAX-ACCESS  read-only
   STATUS      current
   DESCRIPTION
      "Path: vxLanBridgeGroup.performance.mibCounters.d7Performance.ifInOctets

       64 bit unsigned wrappable counter."
   ::= {pr1646v2VxlBGIMVpMibCountersD7PEntry 67108864}

pr1646v2VxlBGIMVpMibCountersD7PIfInUCPkts OBJECT-TYPE
   SYNTAX      Counter64
   MAX-ACCESS  read-only
   STATUS      current
   DESCRIPTION
      "Path: vxLanBridgeGroup.performance.mibCounters.d7Performance.ifInUcastPkts

       64 bit unsigned wrappable counter."
   ::= {pr1646v2VxlBGIMVpMibCountersD7PEntry 83886080}

pr1646v2VxlBGIMVpMibCountersD7PIfInNUCPkts OBJECT-TYPE
   SYNTAX      Counter64
   MAX-ACCESS  read-only
   STATUS      current
   DESCRIPTION
      "Path: vxLanBridgeGroup.performance.mibCounters.d7Performance.ifInNUcastPkts

       64 bit unsigned wrappable counter."
   ::= {pr1646v2VxlBGIMVpMibCountersD7PEntry 100663296}

pr1646v2VxlBGIMVpMibCountersD7PIfInBCPkts OBJECT-TYPE
   SYNTAX      Counter64
   MAX-ACCESS  read-only
   STATUS      current
   DESCRIPTION
      "Path: vxLanBridgeGroup.performance.mibCounters.d7Performance.ifInBcastPkts

       64 bit unsigned wrappable counter."
   ::= {pr1646v2VxlBGIMVpMibCountersD7PEntry 419430400}

pr1646v2VxlBGIMVpMibCountersD7PIfInMCPkts OBJECT-TYPE
   SYNTAX      Counter64
   MAX-ACCESS  read-only
   STATUS      current
   DESCRIPTION
      "Path: vxLanBridgeGroup.performance.mibCounters.d7Performance.ifInMcastPkts

       64 bit unsigned wrappable counter."
   ::= {pr1646v2VxlBGIMVpMibCountersD7PEntry 436207616}

pr1646v2VxlBGIMVpMibCountersD7PIfInDiscards OBJECT-TYPE
   SYNTAX      Counter64
   MAX-ACCESS  read-only
   STATUS      current
   DESCRIPTION
      "Path: vxLanBridgeGroup.performance.mibCounters.d7Performance.ifInDiscards

       64 bit unsigned wrappable counter."
   ::= {pr1646v2VxlBGIMVpMibCountersD7PEntry 117440512}

pr1646v2VxlBGIMVpMibCountersD7PIfInErrors OBJECT-TYPE
   SYNTAX      Counter64
   MAX-ACCESS  read-only
   STATUS      current
   DESCRIPTION
      "Path: vxLanBridgeGroup.performance.mibCounters.d7Performance.ifInErrors

       64 bit unsigned wrappable counter."
   ::= {pr1646v2VxlBGIMVpMibCountersD7PEntry 134217728}

pr1646v2VxlBGIMVpMibCountersD7PIfInUnkwn OBJECT-TYPE
   SYNTAX      Counter64
   MAX-ACCESS  read-only
   STATUS      current
   DESCRIPTION
      "Path: vxLanBridgeGroup.performance.mibCounters.d7Performance.ifInUnknownProtos

       64 bit unsigned wrappable counter."
   ::= {pr1646v2VxlBGIMVpMibCountersD7PEntry 150994944}

pr1646v2VxlBGIMVpMibCountersD7PInDropEx OBJECT-TYPE
   SYNTAX      Counter64
   MAX-ACCESS  read-only
   STATUS      current
   DESCRIPTION
      "Path: vxLanBridgeGroup.performance.mibCounters.d7Performance.ifInDropLevelExceeded

       64 bit unsigned wrappable counter."
   ::= {pr1646v2VxlBGIMVpMibCountersD7PEntry 335544320}

pr1646v2VxlBGIMVpMibCountersD7PInDropNoMac OBJECT-TYPE
   SYNTAX      Counter64
   MAX-ACCESS  read-only
   STATUS      current
   DESCRIPTION
      "Path: vxLanBridgeGroup.performance.mibCounters.d7Performance.fInDiscardsNoMacFit

       64 bit unsigned wrappable counter."
   ::= {pr1646v2VxlBGIMVpMibCountersD7PEntry 301989888}

pr1646v2VxlBGIMVpMibCountersD7PInDropNUCast OBJECT-TYPE
   SYNTAX      Counter64
   MAX-ACCESS  read-only
   STATUS      current
   DESCRIPTION
      "Path: vxLanBridgeGroup.performance.mibCounters.d7Performance.fInDiscardsNUCast

       64 bit unsigned wrappable counter."
   ::= {pr1646v2VxlBGIMVpMibCountersD7PEntry 318767104}

pr1646v2VxlBGIMVpMibCountersD7PInDropFilter OBJECT-TYPE
   SYNTAX      Counter64
   MAX-ACCESS  read-only
   STATUS      current
   DESCRIPTION
      "Path: vxLanBridgeGroup.performance.mibCounters.d7Performance.fInDiscardsFilter

       64 bit unsigned wrappable counter."
   ::= {pr1646v2VxlBGIMVpMibCountersD7PEntry 385875968}

pr1646v2VxlBGIMVpMibCountersD7PIfInBandwidth OBJECT-TYPE
   SYNTAX      Integer32
   MAX-ACCESS  read-only
   STATUS      current
   DESCRIPTION
      "Path: vxLanBridgeGroup.performance.mibCounters.d7Performance.ifInBandwidth

       unit name = bps
       formula = 8 * ; 8 /"
   ::= {pr1646v2VxlBGIMVpMibCountersD7PEntry 268435456}

pr1646v2VxlBGIMVpMibCountersD7PIfOutOctets OBJECT-TYPE
   SYNTAX      Counter64
   MAX-ACCESS  read-only
   STATUS      current
   DESCRIPTION
      "Path: vxLanBridgeGroup.performance.mibCounters.d7Performance.ifOutOctets

       64 bit unsigned wrappable counter."
   ::= {pr1646v2VxlBGIMVpMibCountersD7PEntry 167772160}

pr1646v2VxlBGIMVpMibCountersD7PIfOutUCPkts OBJECT-TYPE
   SYNTAX      Counter64
   MAX-ACCESS  read-only
   STATUS      current
   DESCRIPTION
      "Path: vxLanBridgeGroup.performance.mibCounters.d7Performance.ifOutUcastPkts

       64 bit unsigned wrappable counter."
   ::= {pr1646v2VxlBGIMVpMibCountersD7PEntry 184549376}

pr1646v2VxlBGIMVpMibCountersD7PIfOutNUCPkts OBJECT-TYPE
   SYNTAX      Counter64
   MAX-ACCESS  read-only
   STATUS      current
   DESCRIPTION
      "Path: vxLanBridgeGroup.performance.mibCounters.d7Performance.ifOutNUcastPkts

       64 bit unsigned wrappable counter."
   ::= {pr1646v2VxlBGIMVpMibCountersD7PEntry 201326592}

pr1646v2VxlBGIMVpMibCountersD7PIfOutBCPkts OBJECT-TYPE
   SYNTAX      Counter64
   MAX-ACCESS  read-only
   STATUS      current
   DESCRIPTION
      "Path: vxLanBridgeGroup.performance.mibCounters.d7Performance.ifOutBcastPkts

       64 bit unsigned wrappable counter."
   ::= {pr1646v2VxlBGIMVpMibCountersD7PEntry 452984832}

pr1646v2VxlBGIMVpMibCountersD7PIfOutMCPkts OBJECT-TYPE
   SYNTAX      Counter64
   MAX-ACCESS  read-only
   STATUS      current
   DESCRIPTION
      "Path: vxLanBridgeGroup.performance.mibCounters.d7Performance.ifOutMcastPkts

       64 bit unsigned wrappable counter."
   ::= {pr1646v2VxlBGIMVpMibCountersD7PEntry 469762048}

pr1646v2VxlBGIMVpMibCountersD7PIfOutDiscards OBJECT-TYPE
   SYNTAX      Counter64
   MAX-ACCESS  read-only
   STATUS      current
   DESCRIPTION
      "Path: vxLanBridgeGroup.performance.mibCounters.d7Performance.ifOutDiscards

       64 bit unsigned wrappable counter."
   ::= {pr1646v2VxlBGIMVpMibCountersD7PEntry 218103808}

pr1646v2VxlBGIMVpMibCountersD7PIfOutErrors OBJECT-TYPE
   SYNTAX      Counter64
   MAX-ACCESS  read-only
   STATUS      current
   DESCRIPTION
      "Path: vxLanBridgeGroup.performance.mibCounters.d7Performance.ifOutErrors

       64 bit unsigned wrappable counter."
   ::= {pr1646v2VxlBGIMVpMibCountersD7PEntry 234881024}

pr1646v2VxlBGIMVpMibCountersD7POutDropEx OBJECT-TYPE
   SYNTAX      Counter64
   MAX-ACCESS  read-only
   STATUS      current
   DESCRIPTION
      "Path: vxLanBridgeGroup.performance.mibCounters.d7Performance.ifOutDropLevelExceeded

       64 bit unsigned wrappable counter."
   ::= {pr1646v2VxlBGIMVpMibCountersD7PEntry 352321536}

pr1646v2VxlBGIMVpMibCountersD7POutDropNoArp OBJECT-TYPE
   SYNTAX      Counter64
   MAX-ACCESS  read-only
   STATUS      current
   DESCRIPTION
      "Path: vxLanBridgeGroup.performance.mibCounters.d7Performance.ifOutDiscardsNoArp

       64 bit unsigned wrappable counter."
   ::= {pr1646v2VxlBGIMVpMibCountersD7PEntry 369098752}

pr1646v2VxlBGIMVpMibCountersD7POutDropFilter OBJECT-TYPE
   SYNTAX      Counter64
   MAX-ACCESS  read-only
   STATUS      current
   DESCRIPTION
      "Path: vxLanBridgeGroup.performance.mibCounters.d7Performance.ifOutDiscardsFilter

       64 bit unsigned wrappable counter."
   ::= {pr1646v2VxlBGIMVpMibCountersD7PEntry 402653184}

pr1646v2VxlBGIMVpMibCountersD7PIfOutBandwidth OBJECT-TYPE
   SYNTAX      Integer32
   MAX-ACCESS  read-only
   STATUS      current
   DESCRIPTION
      "Path: vxLanBridgeGroup.performance.mibCounters.d7Performance.ifOutBandwidth

       unit name = bps
       formula = 8 * ; 8 /"
   ::= {pr1646v2VxlBGIMVpMibCountersD7PEntry 285212672}

pr1646v2VxlBGIMVpMibCountersD7PIfErrSec OBJECT-TYPE
   SYNTAX      Counter32
   MAX-ACCESS  read-only
   STATUS      current
   DESCRIPTION
      "Path: vxLanBridgeGroup.performance.mibCounters.d7Performance.ifErrSec

       32 bit unsigned wrappable counter."
   ::= {pr1646v2VxlBGIMVpMibCountersD7PEntry 251658240}


pr1646v2VxlBGIMVpL2ProtTunnel OBJECT IDENTIFIER ::= {pr1646v2VxlBGIMVp 46}

pr1646v2VxlBGIMVpL2ProtTunnelSSCTable OBJECT-TYPE
   SYNTAX      SEQUENCE OF Pr1646v2VxlBGIMVpL2ProtTunnelEntry
   MAX-ACCESS  not-accessible
   STATUS      current
   DESCRIPTION
      "l2 protocol tunnel performance"
   ::= {pr1646v2VxlBGIMVpL2ProtTunnel 1}

pr1646v2VxlBGIMVpL2ProtTunnelEntry OBJECT-TYPE
   SYNTAX      Pr1646v2VxlBGIMVpL2ProtTunnelEntry
   MAX-ACCESS  not-accessible
   STATUS      current
   DESCRIPTION
      ""
   INDEX      { pr1646v2VxlBGIMVpL2ProtTunnelGlobalIx,
                pr1646v2VxlBGIMVpL2ProtTunnelTableIx }
   ::= {pr1646v2VxlBGIMVpL2ProtTunnelSSCTable 1}

Pr1646v2VxlBGIMVpL2ProtTunnelEntry ::=
   SEQUENCE
      {
      pr1646v2VxlBGIMVpL2ProtTunnelGlobalIx
         GlobalIndex,
      pr1646v2VxlBGIMVpL2ProtTunnelTableIx
         TableIndex,
      pr1646v2VxlBGIMVpL2ProtTunnelName
         DisplayString,
      pr1646v2VxlBGIMVpL2ProtTunnelEncapsPktsStp
         Counter32,
      pr1646v2VxlBGIMVpL2ProtTunnelEncapsPktsLldp
         Counter32,
      pr1646v2VxlBGIMVpL2ProtTunnelEncapsPktsOam
         Counter32,
      pr1646v2VxlBGIMVpL2ProtTunnelEncapsPktsCdp
         Counter32,
      pr1646v2VxlBGIMVpL2ProtTunnelEncapsPktsVtp
         Counter32,
      pr1646v2VxlBGIMVpL2ProtTunnelEncapsPktsLacp
         Counter32,
      pr1646v2VxlBGIMVpL2ProtTunnelEncapsPktsEfmOam
         Counter32,
      pr1646v2VxlBGIMVpL2ProtTunnelEncapsPktsPvst
         Counter32,
      pr1646v2VxlBGIMVpL2ProtTunnelEncapsPktsMmrp
         Counter32,
      pr1646v2VxlBGIMVpL2ProtTunnelEncapsPktsMvrp
         Counter32,
      pr1646v2VxlBGIMVpL2ProtTunnelEncapsPktsGvrp
         Counter32,
      pr1646v2VxlBGIMVpL2ProtTunnelEncapsPktsGmrp
         Counter32,
      pr1646v2VxlBGIMVpL2ProtTunnelEncapsPktsDtp
         Counter32,
      pr1646v2VxlBGIMVpL2ProtTunnelEncapsPktsPagp
         Counter32,
      pr1646v2VxlBGIMVpL2ProtTunnelEncapsPktsUdld
         Counter32,
      pr1646v2VxlBGIMVpL2ProtTunnelDecapsPktsStp
         Counter32,
      pr1646v2VxlBGIMVpL2ProtTunnelDecapsPktsLldp
         Counter32,
      pr1646v2VxlBGIMVpL2ProtTunnelDecapsPktsOam
         Counter32,
      pr1646v2VxlBGIMVpL2ProtTunnelDecapsPktsCdp
         Counter32,
      pr1646v2VxlBGIMVpL2ProtTunnelDecapsPktsVtp
         Counter32,
      pr1646v2VxlBGIMVpL2ProtTunnelDecapsPktsLacp
         Counter32,
      pr1646v2VxlBGIMVpL2ProtTunnelDecapsPktsEfmOam
         Counter32,
      pr1646v2VxlBGIMVpL2ProtTunnelDecapsPktsPvst
         Counter32,
      pr1646v2VxlBGIMVpL2ProtTunnelDecapsPktsMmrp
         Counter32,
      pr1646v2VxlBGIMVpL2ProtTunnelDecapsPktsMvrp
         Counter32,
      pr1646v2VxlBGIMVpL2ProtTunnelDecapsPktsGvrp
         Counter32,
      pr1646v2VxlBGIMVpL2ProtTunnelDecapsPktsGmrp
         Counter32,
      pr1646v2VxlBGIMVpL2ProtTunnelDecapsPktsDtp
         Counter32,
      pr1646v2VxlBGIMVpL2ProtTunnelDecapsPktsPagp
         Counter32,
      pr1646v2VxlBGIMVpL2ProtTunnelDecapsPktsUdld
         Counter32,
      pr1646v2VxlBGIMVpL2ProtTunnelDroppedStp
         Counter32,
      pr1646v2VxlBGIMVpL2ProtTunnelDroppedLldp
         Counter32,
      pr1646v2VxlBGIMVpL2ProtTunnelDroppedOam
         Counter32,
      pr1646v2VxlBGIMVpL2ProtTunnelDroppedCdp
         Counter32,
      pr1646v2VxlBGIMVpL2ProtTunnelDroppedVtp
         Counter32,
      pr1646v2VxlBGIMVpL2ProtTunnelDroppedLacp
         Counter32,
      pr1646v2VxlBGIMVpL2ProtTunnelDroppedEfmOam
         Counter32,
      pr1646v2VxlBGIMVpL2ProtTunnelDroppedPvst
         Counter32,
      pr1646v2VxlBGIMVpL2ProtTunnelDroppedMmrp
         Counter32,
      pr1646v2VxlBGIMVpL2ProtTunnelDroppedMvrp
         Counter32,
      pr1646v2VxlBGIMVpL2ProtTunnelDroppedGvrp
         Counter32,
      pr1646v2VxlBGIMVpL2ProtTunnelDroppedGmrp
         Counter32,
      pr1646v2VxlBGIMVpL2ProtTunnelDroppedDtp
         Counter32,
      pr1646v2VxlBGIMVpL2ProtTunnelDroppedPagp
         Counter32,
      pr1646v2VxlBGIMVpL2ProtTunnelDroppedUdld
         Counter32
      }

pr1646v2VxlBGIMVpL2ProtTunnelGlobalIx OBJECT-TYPE
   SYNTAX      GlobalIndex
   MAX-ACCESS  not-accessible
   STATUS      current
   DESCRIPTION
      "The value of the tlsCntTreeGlobalIndex of the MANAGED OBJECT."
   ::= {pr1646v2VxlBGIMVpL2ProtTunnelEntry 10}

pr1646v2VxlBGIMVpL2ProtTunnelTableIx OBJECT-TYPE
   SYNTAX      TableIndex
   MAX-ACCESS  not-accessible
   STATUS      current
   DESCRIPTION
      ""
   ::= {pr1646v2VxlBGIMVpL2ProtTunnelEntry 11}

pr1646v2VxlBGIMVpL2ProtTunnelName OBJECT-TYPE
   SYNTAX      DisplayString
   MAX-ACCESS  read-only
   STATUS      current
   DESCRIPTION
      "Path: vxLanBridgeGroup.performance.l2ProtTunnel.name"
   ::= {pr1646v2VxlBGIMVpL2ProtTunnelEntry 16777216}

pr1646v2VxlBGIMVpL2ProtTunnelEncapsPktsStp OBJECT-TYPE
   SYNTAX      Counter32
   MAX-ACCESS  read-only
   STATUS      current
   DESCRIPTION
      "Path: vxLanBridgeGroup.performance.l2ProtTunnel.encapsPkts.stp

       32 bit unsigned wrappable counter."
   ::= {pr1646v2VxlBGIMVpL2ProtTunnelEntry 33619968}

pr1646v2VxlBGIMVpL2ProtTunnelEncapsPktsLldp OBJECT-TYPE
   SYNTAX      Counter32
   MAX-ACCESS  read-only
   STATUS      current
   DESCRIPTION
      "Path: vxLanBridgeGroup.performance.l2ProtTunnel.encapsPkts.lldp

       32 bit unsigned wrappable counter."
   ::= {pr1646v2VxlBGIMVpL2ProtTunnelEntry 33685504}

pr1646v2VxlBGIMVpL2ProtTunnelEncapsPktsOam OBJECT-TYPE
   SYNTAX      Counter32
   MAX-ACCESS  read-only
   STATUS      current
   DESCRIPTION
      "Path: vxLanBridgeGroup.performance.l2ProtTunnel.encapsPkts.oam

       32 bit unsigned wrappable counter."
   ::= {pr1646v2VxlBGIMVpL2ProtTunnelEntry 33751040}

pr1646v2VxlBGIMVpL2ProtTunnelEncapsPktsCdp OBJECT-TYPE
   SYNTAX      Counter32
   MAX-ACCESS  read-only
   STATUS      current
   DESCRIPTION
      "Path: vxLanBridgeGroup.performance.l2ProtTunnel.encapsPkts.cdp

       32 bit unsigned wrappable counter."
   ::= {pr1646v2VxlBGIMVpL2ProtTunnelEntry 33816576}

pr1646v2VxlBGIMVpL2ProtTunnelEncapsPktsVtp OBJECT-TYPE
   SYNTAX      Counter32
   MAX-ACCESS  read-only
   STATUS      current
   DESCRIPTION
      "Path: vxLanBridgeGroup.performance.l2ProtTunnel.encapsPkts.vtp

       32 bit unsigned wrappable counter."
   ::= {pr1646v2VxlBGIMVpL2ProtTunnelEntry 33882112}

pr1646v2VxlBGIMVpL2ProtTunnelEncapsPktsLacp OBJECT-TYPE
   SYNTAX      Counter32
   MAX-ACCESS  read-only
   STATUS      current
   DESCRIPTION
      "Path: vxLanBridgeGroup.performance.l2ProtTunnel.encapsPkts.lacp

       32 bit unsigned wrappable counter."
   ::= {pr1646v2VxlBGIMVpL2ProtTunnelEntry 33947648}

pr1646v2VxlBGIMVpL2ProtTunnelEncapsPktsEfmOam OBJECT-TYPE
   SYNTAX      Counter32
   MAX-ACCESS  read-only
   STATUS      current
   DESCRIPTION
      "Path: vxLanBridgeGroup.performance.l2ProtTunnel.encapsPkts.efmOam

       32 bit unsigned wrappable counter."
   ::= {pr1646v2VxlBGIMVpL2ProtTunnelEntry 34013184}

pr1646v2VxlBGIMVpL2ProtTunnelEncapsPktsPvst OBJECT-TYPE
   SYNTAX      Counter32
   MAX-ACCESS  read-only
   STATUS      current
   DESCRIPTION
      "Path: vxLanBridgeGroup.performance.l2ProtTunnel.encapsPkts.pvst

       32 bit unsigned wrappable counter."
   ::= {pr1646v2VxlBGIMVpL2ProtTunnelEntry 34078720}

pr1646v2VxlBGIMVpL2ProtTunnelEncapsPktsMmrp OBJECT-TYPE
   SYNTAX      Counter32
   MAX-ACCESS  read-only
   STATUS      current
   DESCRIPTION
      "Path: vxLanBridgeGroup.performance.l2ProtTunnel.encapsPkts.mmrp

       32 bit unsigned wrappable counter."
   ::= {pr1646v2VxlBGIMVpL2ProtTunnelEntry 34144256}

pr1646v2VxlBGIMVpL2ProtTunnelEncapsPktsMvrp OBJECT-TYPE
   SYNTAX      Counter32
   MAX-ACCESS  read-only
   STATUS      current
   DESCRIPTION
      "Path: vxLanBridgeGroup.performance.l2ProtTunnel.encapsPkts.mvrp

       32 bit unsigned wrappable counter."
   ::= {pr1646v2VxlBGIMVpL2ProtTunnelEntry 34209792}

pr1646v2VxlBGIMVpL2ProtTunnelEncapsPktsGvrp OBJECT-TYPE
   SYNTAX      Counter32
   MAX-ACCESS  read-only
   STATUS      current
   DESCRIPTION
      "Path: vxLanBridgeGroup.performance.l2ProtTunnel.encapsPkts.gvrp

       32 bit unsigned wrappable counter."
   ::= {pr1646v2VxlBGIMVpL2ProtTunnelEntry 34275328}

pr1646v2VxlBGIMVpL2ProtTunnelEncapsPktsGmrp OBJECT-TYPE
   SYNTAX      Counter32
   MAX-ACCESS  read-only
   STATUS      current
   DESCRIPTION
      "Path: vxLanBridgeGroup.performance.l2ProtTunnel.encapsPkts.gmrp

       32 bit unsigned wrappable counter."
   ::= {pr1646v2VxlBGIMVpL2ProtTunnelEntry 34340864}

pr1646v2VxlBGIMVpL2ProtTunnelEncapsPktsDtp OBJECT-TYPE
   SYNTAX      Counter32
   MAX-ACCESS  read-only
   STATUS      current
   DESCRIPTION
      "Path: vxLanBridgeGroup.performance.l2ProtTunnel.encapsPkts.dtp

       32 bit unsigned wrappable counter."
   ::= {pr1646v2VxlBGIMVpL2ProtTunnelEntry 34406400}

pr1646v2VxlBGIMVpL2ProtTunnelEncapsPktsPagp OBJECT-TYPE
   SYNTAX      Counter32
   MAX-ACCESS  read-only
   STATUS      current
   DESCRIPTION
      "Path: vxLanBridgeGroup.performance.l2ProtTunnel.encapsPkts.pagp

       32 bit unsigned wrappable counter."
   ::= {pr1646v2VxlBGIMVpL2ProtTunnelEntry 34471936}

pr1646v2VxlBGIMVpL2ProtTunnelEncapsPktsUdld OBJECT-TYPE
   SYNTAX      Counter32
   MAX-ACCESS  read-only
   STATUS      current
   DESCRIPTION
      "Path: vxLanBridgeGroup.performance.l2ProtTunnel.encapsPkts.udld

       32 bit unsigned wrappable counter."
   ::= {pr1646v2VxlBGIMVpL2ProtTunnelEntry 34537472}

pr1646v2VxlBGIMVpL2ProtTunnelDecapsPktsStp OBJECT-TYPE
   SYNTAX      Counter32
   MAX-ACCESS  read-only
   STATUS      current
   DESCRIPTION
      "Path: vxLanBridgeGroup.performance.l2ProtTunnel.decapsPkts.stp

       32 bit unsigned wrappable counter."
   ::= {pr1646v2VxlBGIMVpL2ProtTunnelEntry 50397184}

pr1646v2VxlBGIMVpL2ProtTunnelDecapsPktsLldp OBJECT-TYPE
   SYNTAX      Counter32
   MAX-ACCESS  read-only
   STATUS      current
   DESCRIPTION
      "Path: vxLanBridgeGroup.performance.l2ProtTunnel.decapsPkts.lldp

       32 bit unsigned wrappable counter."
   ::= {pr1646v2VxlBGIMVpL2ProtTunnelEntry 50462720}

pr1646v2VxlBGIMVpL2ProtTunnelDecapsPktsOam OBJECT-TYPE
   SYNTAX      Counter32
   MAX-ACCESS  read-only
   STATUS      current
   DESCRIPTION
      "Path: vxLanBridgeGroup.performance.l2ProtTunnel.decapsPkts.oam

       32 bit unsigned wrappable counter."
   ::= {pr1646v2VxlBGIMVpL2ProtTunnelEntry 50528256}

pr1646v2VxlBGIMVpL2ProtTunnelDecapsPktsCdp OBJECT-TYPE
   SYNTAX      Counter32
   MAX-ACCESS  read-only
   STATUS      current
   DESCRIPTION
      "Path: vxLanBridgeGroup.performance.l2ProtTunnel.decapsPkts.cdp

       32 bit unsigned wrappable counter."
   ::= {pr1646v2VxlBGIMVpL2ProtTunnelEntry 50593792}

pr1646v2VxlBGIMVpL2ProtTunnelDecapsPktsVtp OBJECT-TYPE
   SYNTAX      Counter32
   MAX-ACCESS  read-only
   STATUS      current
   DESCRIPTION
      "Path: vxLanBridgeGroup.performance.l2ProtTunnel.decapsPkts.vtp

       32 bit unsigned wrappable counter."
   ::= {pr1646v2VxlBGIMVpL2ProtTunnelEntry 50659328}

pr1646v2VxlBGIMVpL2ProtTunnelDecapsPktsLacp OBJECT-TYPE
   SYNTAX      Counter32
   MAX-ACCESS  read-only
   STATUS      current
   DESCRIPTION
      "Path: vxLanBridgeGroup.performance.l2ProtTunnel.decapsPkts.lacp

       32 bit unsigned wrappable counter."
   ::= {pr1646v2VxlBGIMVpL2ProtTunnelEntry 50724864}

pr1646v2VxlBGIMVpL2ProtTunnelDecapsPktsEfmOam OBJECT-TYPE
   SYNTAX      Counter32
   MAX-ACCESS  read-only
   STATUS      current
   DESCRIPTION
      "Path: vxLanBridgeGroup.performance.l2ProtTunnel.decapsPkts.efmOam

       32 bit unsigned wrappable counter."
   ::= {pr1646v2VxlBGIMVpL2ProtTunnelEntry 50790400}

pr1646v2VxlBGIMVpL2ProtTunnelDecapsPktsPvst OBJECT-TYPE
   SYNTAX      Counter32
   MAX-ACCESS  read-only
   STATUS      current
   DESCRIPTION
      "Path: vxLanBridgeGroup.performance.l2ProtTunnel.decapsPkts.pvst

       32 bit unsigned wrappable counter."
   ::= {pr1646v2VxlBGIMVpL2ProtTunnelEntry 50855936}

pr1646v2VxlBGIMVpL2ProtTunnelDecapsPktsMmrp OBJECT-TYPE
   SYNTAX      Counter32
   MAX-ACCESS  read-only
   STATUS      current
   DESCRIPTION
      "Path: vxLanBridgeGroup.performance.l2ProtTunnel.decapsPkts.mmrp

       32 bit unsigned wrappable counter."
   ::= {pr1646v2VxlBGIMVpL2ProtTunnelEntry 50921472}

pr1646v2VxlBGIMVpL2ProtTunnelDecapsPktsMvrp OBJECT-TYPE
   SYNTAX      Counter32
   MAX-ACCESS  read-only
   STATUS      current
   DESCRIPTION
      "Path: vxLanBridgeGroup.performance.l2ProtTunnel.decapsPkts.mvrp

       32 bit unsigned wrappable counter."
   ::= {pr1646v2VxlBGIMVpL2ProtTunnelEntry 50987008}

pr1646v2VxlBGIMVpL2ProtTunnelDecapsPktsGvrp OBJECT-TYPE
   SYNTAX      Counter32
   MAX-ACCESS  read-only
   STATUS      current
   DESCRIPTION
      "Path: vxLanBridgeGroup.performance.l2ProtTunnel.decapsPkts.gvrp

       32 bit unsigned wrappable counter."
   ::= {pr1646v2VxlBGIMVpL2ProtTunnelEntry 51052544}

pr1646v2VxlBGIMVpL2ProtTunnelDecapsPktsGmrp OBJECT-TYPE
   SYNTAX      Counter32
   MAX-ACCESS  read-only
   STATUS      current
   DESCRIPTION
      "Path: vxLanBridgeGroup.performance.l2ProtTunnel.decapsPkts.gmrp

       32 bit unsigned wrappable counter."
   ::= {pr1646v2VxlBGIMVpL2ProtTunnelEntry 51118080}

pr1646v2VxlBGIMVpL2ProtTunnelDecapsPktsDtp OBJECT-TYPE
   SYNTAX      Counter32
   MAX-ACCESS  read-only
   STATUS      current
   DESCRIPTION
      "Path: vxLanBridgeGroup.performance.l2ProtTunnel.decapsPkts.dtp

       32 bit unsigned wrappable counter."
   ::= {pr1646v2VxlBGIMVpL2ProtTunnelEntry 51183616}

pr1646v2VxlBGIMVpL2ProtTunnelDecapsPktsPagp OBJECT-TYPE
   SYNTAX      Counter32
   MAX-ACCESS  read-only
   STATUS      current
   DESCRIPTION
      "Path: vxLanBridgeGroup.performance.l2ProtTunnel.decapsPkts.pagp

       32 bit unsigned wrappable counter."
   ::= {pr1646v2VxlBGIMVpL2ProtTunnelEntry 51249152}

pr1646v2VxlBGIMVpL2ProtTunnelDecapsPktsUdld OBJECT-TYPE
   SYNTAX      Counter32
   MAX-ACCESS  read-only
   STATUS      current
   DESCRIPTION
      "Path: vxLanBridgeGroup.performance.l2ProtTunnel.decapsPkts.udld

       32 bit unsigned wrappable counter."
   ::= {pr1646v2VxlBGIMVpL2ProtTunnelEntry 51314688}

pr1646v2VxlBGIMVpL2ProtTunnelDroppedStp OBJECT-TYPE
   SYNTAX      Counter32
   MAX-ACCESS  read-only
   STATUS      current
   DESCRIPTION
      "Path: vxLanBridgeGroup.performance.l2ProtTunnel.dropped.stp

       32 bit unsigned wrappable counter."
   ::= {pr1646v2VxlBGIMVpL2ProtTunnelEntry 67174400}

pr1646v2VxlBGIMVpL2ProtTunnelDroppedLldp OBJECT-TYPE
   SYNTAX      Counter32
   MAX-ACCESS  read-only
   STATUS      current
   DESCRIPTION
      "Path: vxLanBridgeGroup.performance.l2ProtTunnel.dropped.lldp

       32 bit unsigned wrappable counter."
   ::= {pr1646v2VxlBGIMVpL2ProtTunnelEntry 67239936}

pr1646v2VxlBGIMVpL2ProtTunnelDroppedOam OBJECT-TYPE
   SYNTAX      Counter32
   MAX-ACCESS  read-only
   STATUS      current
   DESCRIPTION
      "Path: vxLanBridgeGroup.performance.l2ProtTunnel.dropped.oam

       32 bit unsigned wrappable counter."
   ::= {pr1646v2VxlBGIMVpL2ProtTunnelEntry 67305472}

pr1646v2VxlBGIMVpL2ProtTunnelDroppedCdp OBJECT-TYPE
   SYNTAX      Counter32
   MAX-ACCESS  read-only
   STATUS      current
   DESCRIPTION
      "Path: vxLanBridgeGroup.performance.l2ProtTunnel.dropped.cdp

       32 bit unsigned wrappable counter."
   ::= {pr1646v2VxlBGIMVpL2ProtTunnelEntry 67371008}

pr1646v2VxlBGIMVpL2ProtTunnelDroppedVtp OBJECT-TYPE
   SYNTAX      Counter32
   MAX-ACCESS  read-only
   STATUS      current
   DESCRIPTION
      "Path: vxLanBridgeGroup.performance.l2ProtTunnel.dropped.vtp

       32 bit unsigned wrappable counter."
   ::= {pr1646v2VxlBGIMVpL2ProtTunnelEntry 67436544}

pr1646v2VxlBGIMVpL2ProtTunnelDroppedLacp OBJECT-TYPE
   SYNTAX      Counter32
   MAX-ACCESS  read-only
   STATUS      current
   DESCRIPTION
      "Path: vxLanBridgeGroup.performance.l2ProtTunnel.dropped.lacp

       32 bit unsigned wrappable counter."
   ::= {pr1646v2VxlBGIMVpL2ProtTunnelEntry 67502080}

pr1646v2VxlBGIMVpL2ProtTunnelDroppedEfmOam OBJECT-TYPE
   SYNTAX      Counter32
   MAX-ACCESS  read-only
   STATUS      current
   DESCRIPTION
      "Path: vxLanBridgeGroup.performance.l2ProtTunnel.dropped.efmOam

       32 bit unsigned wrappable counter."
   ::= {pr1646v2VxlBGIMVpL2ProtTunnelEntry 67567616}

pr1646v2VxlBGIMVpL2ProtTunnelDroppedPvst OBJECT-TYPE
   SYNTAX      Counter32
   MAX-ACCESS  read-only
   STATUS      current
   DESCRIPTION
      "Path: vxLanBridgeGroup.performance.l2ProtTunnel.dropped.pvst

       32 bit unsigned wrappable counter."
   ::= {pr1646v2VxlBGIMVpL2ProtTunnelEntry 67633152}

pr1646v2VxlBGIMVpL2ProtTunnelDroppedMmrp OBJECT-TYPE
   SYNTAX      Counter32
   MAX-ACCESS  read-only
   STATUS      current
   DESCRIPTION
      "Path: vxLanBridgeGroup.performance.l2ProtTunnel.dropped.mmrp

       32 bit unsigned wrappable counter."
   ::= {pr1646v2VxlBGIMVpL2ProtTunnelEntry 67698688}

pr1646v2VxlBGIMVpL2ProtTunnelDroppedMvrp OBJECT-TYPE
   SYNTAX      Counter32
   MAX-ACCESS  read-only
   STATUS      current
   DESCRIPTION
      "Path: vxLanBridgeGroup.performance.l2ProtTunnel.dropped.mvrp

       32 bit unsigned wrappable counter."
   ::= {pr1646v2VxlBGIMVpL2ProtTunnelEntry 67764224}

pr1646v2VxlBGIMVpL2ProtTunnelDroppedGvrp OBJECT-TYPE
   SYNTAX      Counter32
   MAX-ACCESS  read-only
   STATUS      current
   DESCRIPTION
      "Path: vxLanBridgeGroup.performance.l2ProtTunnel.dropped.gvrp

       32 bit unsigned wrappable counter."
   ::= {pr1646v2VxlBGIMVpL2ProtTunnelEntry 67829760}

pr1646v2VxlBGIMVpL2ProtTunnelDroppedGmrp OBJECT-TYPE
   SYNTAX      Counter32
   MAX-ACCESS  read-only
   STATUS      current
   DESCRIPTION
      "Path: vxLanBridgeGroup.performance.l2ProtTunnel.dropped.gmrp

       32 bit unsigned wrappable counter."
   ::= {pr1646v2VxlBGIMVpL2ProtTunnelEntry 67895296}

pr1646v2VxlBGIMVpL2ProtTunnelDroppedDtp OBJECT-TYPE
   SYNTAX      Counter32
   MAX-ACCESS  read-only
   STATUS      current
   DESCRIPTION
      "Path: vxLanBridgeGroup.performance.l2ProtTunnel.dropped.dtp

       32 bit unsigned wrappable counter."
   ::= {pr1646v2VxlBGIMVpL2ProtTunnelEntry 67960832}

pr1646v2VxlBGIMVpL2ProtTunnelDroppedPagp OBJECT-TYPE
   SYNTAX      Counter32
   MAX-ACCESS  read-only
   STATUS      current
   DESCRIPTION
      "Path: vxLanBridgeGroup.performance.l2ProtTunnel.dropped.pagp

       32 bit unsigned wrappable counter."
   ::= {pr1646v2VxlBGIMVpL2ProtTunnelEntry 68026368}

pr1646v2VxlBGIMVpL2ProtTunnelDroppedUdld OBJECT-TYPE
   SYNTAX      Counter32
   MAX-ACCESS  read-only
   STATUS      current
   DESCRIPTION
      "Path: vxLanBridgeGroup.performance.l2ProtTunnel.dropped.udld

       32 bit unsigned wrappable counter."
   ::= {pr1646v2VxlBGIMVpL2ProtTunnelEntry 68091904}


pr1646v2VxlBGIMVpVlan OBJECT IDENTIFIER ::= {pr1646v2VxlBGIMVp 310}

pr1646v2VxlBGIMVpVlanSSCTable OBJECT-TYPE
   SYNTAX      SEQUENCE OF Pr1646v2VxlBGIMVpVlanEntry
   MAX-ACCESS  not-accessible
   STATUS      current
   DESCRIPTION
      ""
   ::= {pr1646v2VxlBGIMVpVlan 1}

pr1646v2VxlBGIMVpVlanEntry OBJECT-TYPE
   SYNTAX      Pr1646v2VxlBGIMVpVlanEntry
   MAX-ACCESS  not-accessible
   STATUS      current
   DESCRIPTION
      ""
   INDEX      { pr1646v2VxlBGIMVpVlanGlobalIx,
                pr1646v2VxlBGIMVpVlanTableIx }
   ::= {pr1646v2VxlBGIMVpVlanSSCTable 1}

Pr1646v2VxlBGIMVpVlanEntry ::=
   SEQUENCE
      {
      pr1646v2VxlBGIMVpVlanGlobalIx
         GlobalIndex,
      pr1646v2VxlBGIMVpVlanTableIx
         TableIndex,
      pr1646v2VxlBGIMVpVlanName
         DisplayString,
      pr1646v2VxlBGIMVpVlanMCInOctets
         Counter64,
      pr1646v2VxlBGIMVpVlanMCInUcast
         Counter64,
      pr1646v2VxlBGIMVpVlanMCInNUcastPkts
         Counter64,
      pr1646v2VxlBGIMVpVlanMCInBcastPkts
         Counter64,
      pr1646v2VxlBGIMVpVlanMCInMcastPkts
         Counter64,
      pr1646v2VxlBGIMVpVlanMCInDiscards
         Counter64,
      pr1646v2VxlBGIMVpVlanMCInErrors
         Counter64,
      pr1646v2VxlBGIMVpVlanMCInUnknownProtos
         Counter64,
      pr1646v2VxlBGIMVpVlanMCInDropEx
         Counter64,
      pr1646v2VxlBGIMVpVlanMCInDropNoMac
         Counter64,
      pr1646v2VxlBGIMVpVlanMCInDropNUCast
         Counter64,
      pr1646v2VxlBGIMVpVlanMCInDropFilter
         Counter64,
      pr1646v2VxlBGIMVpVlanMCInBandwidth15sec
         Integer32,
      pr1646v2VxlBGIMVpVlanMCInBandwidth30sec
         Integer32,
      pr1646v2VxlBGIMVpVlanMCInBandwidth1min
         Integer32,
      pr1646v2VxlBGIMVpVlanMCInBandwidth2min
         Integer32,
      pr1646v2VxlBGIMVpVlanMCInBandwidth5min
         Integer32,
      pr1646v2VxlBGIMVpVlanMCOutOctets
         Counter64,
      pr1646v2VxlBGIMVpVlanMCOutUcastPkts
         Counter64,
      pr1646v2VxlBGIMVpVlanMCOutNUcastPkts
         Counter64,
      pr1646v2VxlBGIMVpVlanMCOutBcastPkts
         Counter64,
      pr1646v2VxlBGIMVpVlanMCOutMcastPkts
         Counter64,
      pr1646v2VxlBGIMVpVlanMCOutDiscards
         Counter64,
      pr1646v2VxlBGIMVpVlanMCOutErrors
         Counter64,
      pr1646v2VxlBGIMVpVlanMCOutQLen
         Counter32,
      pr1646v2VxlBGIMVpVlanMCOutDropEx
         Counter64,
      pr1646v2VxlBGIMVpVlanMCOutDropNoArp
         Counter64,
      pr1646v2VxlBGIMVpVlanMCOutDropFilter
         Counter64,
      pr1646v2VxlBGIMVpVlanMCOutBandwidth15sec
         Integer32,
      pr1646v2VxlBGIMVpVlanMCOutBandwidth30sec
         Integer32,
      pr1646v2VxlBGIMVpVlanMCOutBandwidth1min
         Integer32,
      pr1646v2VxlBGIMVpVlanMCOutBandwidth2min
         Integer32,
      pr1646v2VxlBGIMVpVlanMCOutBandwidth5min
         Integer32,
      pr1646v2VxlBGIMVpVlanVlanVid
         Integer32
      }

pr1646v2VxlBGIMVpVlanGlobalIx OBJECT-TYPE
   SYNTAX      GlobalIndex
   MAX-ACCESS  not-accessible
   STATUS      current
   DESCRIPTION
      "The value of the tlsCntTreeGlobalIndex of the MANAGED OBJECT."
   ::= {pr1646v2VxlBGIMVpVlanEntry 10}

pr1646v2VxlBGIMVpVlanTableIx OBJECT-TYPE
   SYNTAX      TableIndex
   MAX-ACCESS  not-accessible
   STATUS      current
   DESCRIPTION
      ""
   ::= {pr1646v2VxlBGIMVpVlanEntry 11}

pr1646v2VxlBGIMVpVlanName OBJECT-TYPE
   SYNTAX      DisplayString
   MAX-ACCESS  read-only
   STATUS      current
   DESCRIPTION
      "Path: vxLanBridgeGroup.performance.vlan.name"
   ::= {pr1646v2VxlBGIMVpVlanEntry 16777216}

pr1646v2VxlBGIMVpVlanMCInOctets OBJECT-TYPE
   SYNTAX      Counter64
   MAX-ACCESS  read-only
   STATUS      current
   DESCRIPTION
      "Path: vxLanBridgeGroup.performance.vlan.mibCounters.ifInOctets

       64 bit unsigned wrappable counter."
   ::= {pr1646v2VxlBGIMVpVlanEntry 40697856}

pr1646v2VxlBGIMVpVlanMCInUcast OBJECT-TYPE
   SYNTAX      Counter64
   MAX-ACCESS  read-only
   STATUS      current
   DESCRIPTION
      "Path: vxLanBridgeGroup.performance.vlan.mibCounters.ifInUcastPkts

       64 bit unsigned wrappable counter."
   ::= {pr1646v2VxlBGIMVpVlanEntry 40763392}

pr1646v2VxlBGIMVpVlanMCInNUcastPkts OBJECT-TYPE
   SYNTAX      Counter64
   MAX-ACCESS  read-only
   STATUS      current
   DESCRIPTION
      "Path: vxLanBridgeGroup.performance.vlan.mibCounters.ifInNUcastPkts

       64 bit unsigned wrappable counter."
   ::= {pr1646v2VxlBGIMVpVlanEntry 40828928}

pr1646v2VxlBGIMVpVlanMCInBcastPkts OBJECT-TYPE
   SYNTAX      Counter64
   MAX-ACCESS  read-only
   STATUS      current
   DESCRIPTION
      "Path: vxLanBridgeGroup.performance.vlan.mibCounters.ifInBcastPkts

       64 bit unsigned wrappable counter."
   ::= {pr1646v2VxlBGIMVpVlanEntry 47382528}

pr1646v2VxlBGIMVpVlanMCInMcastPkts OBJECT-TYPE
   SYNTAX      Counter64
   MAX-ACCESS  read-only
   STATUS      current
   DESCRIPTION
      "Path: vxLanBridgeGroup.performance.vlan.mibCounters.ifInMcastPkts

       64 bit unsigned wrappable counter."
   ::= {pr1646v2VxlBGIMVpVlanEntry 48037888}

pr1646v2VxlBGIMVpVlanMCInDiscards OBJECT-TYPE
   SYNTAX      Counter64
   MAX-ACCESS  read-only
   STATUS      current
   DESCRIPTION
      "Path: vxLanBridgeGroup.performance.vlan.mibCounters.ifInDiscards

       64 bit unsigned wrappable counter."
   ::= {pr1646v2VxlBGIMVpVlanEntry 40894464}

pr1646v2VxlBGIMVpVlanMCInErrors OBJECT-TYPE
   SYNTAX      Counter64
   MAX-ACCESS  read-only
   STATUS      current
   DESCRIPTION
      "Path: vxLanBridgeGroup.performance.vlan.mibCounters.ifInErrors

       64 bit unsigned wrappable counter."
   ::= {pr1646v2VxlBGIMVpVlanEntry 40960000}

pr1646v2VxlBGIMVpVlanMCInUnknownProtos OBJECT-TYPE
   SYNTAX      Counter64
   MAX-ACCESS  read-only
   STATUS      current
   DESCRIPTION
      "Path: vxLanBridgeGroup.performance.vlan.mibCounters.ifInUnknownProtos

       64 bit unsigned wrappable counter."
   ::= {pr1646v2VxlBGIMVpVlanEntry 41025536}

pr1646v2VxlBGIMVpVlanMCInDropEx OBJECT-TYPE
   SYNTAX      Counter64
   MAX-ACCESS  read-only
   STATUS      current
   DESCRIPTION
      "Path: vxLanBridgeGroup.performance.vlan.mibCounters.ifInDropLevelExceeded

       64 bit unsigned wrappable counter."
   ::= {pr1646v2VxlBGIMVpVlanEntry 42074112}

pr1646v2VxlBGIMVpVlanMCInDropNoMac OBJECT-TYPE
   SYNTAX      Counter64
   MAX-ACCESS  read-only
   STATUS      current
   DESCRIPTION
      "Path: vxLanBridgeGroup.performance.vlan.mibCounters.ifInDiscardsNoMacFit

       64 bit unsigned wrappable counter."
   ::= {pr1646v2VxlBGIMVpVlanEntry 42270720}

pr1646v2VxlBGIMVpVlanMCInDropNUCast OBJECT-TYPE
   SYNTAX      Counter64
   MAX-ACCESS  read-only
   STATUS      current
   DESCRIPTION
      "Path: vxLanBridgeGroup.performance.vlan.mibCounters.ifInDiscardsNUCast

       64 bit unsigned wrappable counter."
   ::= {pr1646v2VxlBGIMVpVlanEntry 42467328}

pr1646v2VxlBGIMVpVlanMCInDropFilter OBJECT-TYPE
   SYNTAX      Counter64
   MAX-ACCESS  read-only
   STATUS      current
   DESCRIPTION
      "Path: vxLanBridgeGroup.performance.vlan.mibCounters.ifInDiscardsFilter

       64 bit unsigned wrappable counter."
   ::= {pr1646v2VxlBGIMVpVlanEntry 42532864}

pr1646v2VxlBGIMVpVlanMCInBandwidth15sec OBJECT-TYPE
   SYNTAX      Integer32
   MAX-ACCESS  read-only
   STATUS      current
   DESCRIPTION
      "Path: vxLanBridgeGroup.performance.vlan.mibCounters.ifInBandwidth.15sec

       unit name = bps
       formula = 8 * ; 8 /"
   ::= {pr1646v2VxlBGIMVpVlanEntry 45417728}

pr1646v2VxlBGIMVpVlanMCInBandwidth30sec OBJECT-TYPE
   SYNTAX      Integer32
   MAX-ACCESS  read-only
   STATUS      current
   DESCRIPTION
      "Path: vxLanBridgeGroup.performance.vlan.mibCounters.ifInBandwidth.30sec

       unit name = bps
       formula = 8 * ; 8 /"
   ::= {pr1646v2VxlBGIMVpVlanEntry 45419008}

pr1646v2VxlBGIMVpVlanMCInBandwidth1min OBJECT-TYPE
   SYNTAX      Integer32
   MAX-ACCESS  read-only
   STATUS      current
   DESCRIPTION
      "Path: vxLanBridgeGroup.performance.vlan.mibCounters.ifInBandwidth.1min

       unit name = bps
       formula = 8 * ; 8 /"
   ::= {pr1646v2VxlBGIMVpVlanEntry 45421568}

pr1646v2VxlBGIMVpVlanMCInBandwidth2min OBJECT-TYPE
   SYNTAX      Integer32
   MAX-ACCESS  read-only
   STATUS      current
   DESCRIPTION
      "Path: vxLanBridgeGroup.performance.vlan.mibCounters.ifInBandwidth.2min

       unit name = bps
       formula = 8 * ; 8 /"
   ::= {pr1646v2VxlBGIMVpVlanEntry 45426688}

pr1646v2VxlBGIMVpVlanMCInBandwidth5min OBJECT-TYPE
   SYNTAX      Integer32
   MAX-ACCESS  read-only
   STATUS      current
   DESCRIPTION
      "Path: vxLanBridgeGroup.performance.vlan.mibCounters.ifInBandwidth.5min

       unit name = bps
       formula = 8 * ; 8 /"
   ::= {pr1646v2VxlBGIMVpVlanEntry 45442048}

pr1646v2VxlBGIMVpVlanMCOutOctets OBJECT-TYPE
   SYNTAX      Counter64
   MAX-ACCESS  read-only
   STATUS      current
   DESCRIPTION
      "Path: vxLanBridgeGroup.performance.vlan.mibCounters.ifOutOctets

       64 bit unsigned wrappable counter."
   ::= {pr1646v2VxlBGIMVpVlanEntry 41091072}

pr1646v2VxlBGIMVpVlanMCOutUcastPkts OBJECT-TYPE
   SYNTAX      Counter64
   MAX-ACCESS  read-only
   STATUS      current
   DESCRIPTION
      "Path: vxLanBridgeGroup.performance.vlan.mibCounters.ifOutUcastPkts

       64 bit unsigned wrappable counter."
   ::= {pr1646v2VxlBGIMVpVlanEntry 41156608}

pr1646v2VxlBGIMVpVlanMCOutNUcastPkts OBJECT-TYPE
   SYNTAX      Counter64
   MAX-ACCESS  read-only
   STATUS      current
   DESCRIPTION
      "Path: vxLanBridgeGroup.performance.vlan.mibCounters.ifOutNUcastPkts

       64 bit unsigned wrappable counter."
   ::= {pr1646v2VxlBGIMVpVlanEntry 41222144}

pr1646v2VxlBGIMVpVlanMCOutBcastPkts OBJECT-TYPE
   SYNTAX      Counter64
   MAX-ACCESS  read-only
   STATUS      current
   DESCRIPTION
      "Path: vxLanBridgeGroup.performance.vlan.mibCounters.ifOutBcastPkts

       64 bit unsigned wrappable counter."
   ::= {pr1646v2VxlBGIMVpVlanEntry 47775744}

pr1646v2VxlBGIMVpVlanMCOutMcastPkts OBJECT-TYPE
   SYNTAX      Counter64
   MAX-ACCESS  read-only
   STATUS      current
   DESCRIPTION
      "Path: vxLanBridgeGroup.performance.vlan.mibCounters.ifOutMcastPkts

       64 bit unsigned wrappable counter."
   ::= {pr1646v2VxlBGIMVpVlanEntry 48431104}

pr1646v2VxlBGIMVpVlanMCOutDiscards OBJECT-TYPE
   SYNTAX      Counter64
   MAX-ACCESS  read-only
   STATUS      current
   DESCRIPTION
      "Path: vxLanBridgeGroup.performance.vlan.mibCounters.ifOutDiscards

       64 bit unsigned wrappable counter."
   ::= {pr1646v2VxlBGIMVpVlanEntry 41287680}

pr1646v2VxlBGIMVpVlanMCOutErrors OBJECT-TYPE
   SYNTAX      Counter64
   MAX-ACCESS  read-only
   STATUS      current
   DESCRIPTION
      "Path: vxLanBridgeGroup.performance.vlan.mibCounters.ifOutErrors

       64 bit unsigned wrappable counter."
   ::= {pr1646v2VxlBGIMVpVlanEntry 41353216}

pr1646v2VxlBGIMVpVlanMCOutQLen OBJECT-TYPE
   SYNTAX      Counter32
   MAX-ACCESS  read-only
   STATUS      current
   DESCRIPTION
      "Path: vxLanBridgeGroup.performance.vlan.mibCounters.ifOutQLen

       32 bit unsigned wrappable counter."
   ::= {pr1646v2VxlBGIMVpVlanEntry 41418752}

pr1646v2VxlBGIMVpVlanMCOutDropEx OBJECT-TYPE
   SYNTAX      Counter64
   MAX-ACCESS  read-only
   STATUS      current
   DESCRIPTION
      "Path: vxLanBridgeGroup.performance.vlan.mibCounters.ifOutDropLevelExceeded

       64 bit unsigned wrappable counter."
   ::= {pr1646v2VxlBGIMVpVlanEntry 41484288}

pr1646v2VxlBGIMVpVlanMCOutDropNoArp OBJECT-TYPE
   SYNTAX      Counter64
   MAX-ACCESS  read-only
   STATUS      current
   DESCRIPTION
      "Path: vxLanBridgeGroup.performance.vlan.mibCounters.ifOutDiscardsNoArp

       64 bit unsigned wrappable counter."
   ::= {pr1646v2VxlBGIMVpVlanEntry 42336256}

pr1646v2VxlBGIMVpVlanMCOutDropFilter OBJECT-TYPE
   SYNTAX      Counter64
   MAX-ACCESS  read-only
   STATUS      current
   DESCRIPTION
      "Path: vxLanBridgeGroup.performance.vlan.mibCounters.ifOutDiscardsFilter

       64 bit unsigned wrappable counter."
   ::= {pr1646v2VxlBGIMVpVlanEntry 42598400}

pr1646v2VxlBGIMVpVlanMCOutBandwidth15sec OBJECT-TYPE
   SYNTAX      Integer32
   MAX-ACCESS  read-only
   STATUS      current
   DESCRIPTION
      "Path: vxLanBridgeGroup.performance.vlan.mibCounters.ifOutBandwidth.15sec

       unit name = bps
       formula = 8 * ; 8 /"
   ::= {pr1646v2VxlBGIMVpVlanEntry 45483264}

pr1646v2VxlBGIMVpVlanMCOutBandwidth30sec OBJECT-TYPE
   SYNTAX      Integer32
   MAX-ACCESS  read-only
   STATUS      current
   DESCRIPTION
      "Path: vxLanBridgeGroup.performance.vlan.mibCounters.ifOutBandwidth.30sec

       unit name = bps
       formula = 8 * ; 8 /"
   ::= {pr1646v2VxlBGIMVpVlanEntry 45484544}

pr1646v2VxlBGIMVpVlanMCOutBandwidth1min OBJECT-TYPE
   SYNTAX      Integer32
   MAX-ACCESS  read-only
   STATUS      current
   DESCRIPTION
      "Path: vxLanBridgeGroup.performance.vlan.mibCounters.ifOutBandwidth.1min

       unit name = bps
       formula = 8 * ; 8 /"
   ::= {pr1646v2VxlBGIMVpVlanEntry 45487104}

pr1646v2VxlBGIMVpVlanMCOutBandwidth2min OBJECT-TYPE
   SYNTAX      Integer32
   MAX-ACCESS  read-only
   STATUS      current
   DESCRIPTION
      "Path: vxLanBridgeGroup.performance.vlan.mibCounters.ifOutBandwidth.2min

       unit name = bps
       formula = 8 * ; 8 /"
   ::= {pr1646v2VxlBGIMVpVlanEntry 45492224}

pr1646v2VxlBGIMVpVlanMCOutBandwidth5min OBJECT-TYPE
   SYNTAX      Integer32
   MAX-ACCESS  read-only
   STATUS      current
   DESCRIPTION
      "Path: vxLanBridgeGroup.performance.vlan.mibCounters.ifOutBandwidth.5min

       unit name = bps
       formula = 8 * ; 8 /"
   ::= {pr1646v2VxlBGIMVpVlanEntry 45507584}

pr1646v2VxlBGIMVpVlanVlanVid OBJECT-TYPE
   SYNTAX      Integer32
   MAX-ACCESS  read-only
   STATUS      current
   DESCRIPTION
      "Path: vxLanBridgeGroup.performance.vlan.vlan.vid"
   ::= {pr1646v2VxlBGIMVpVlanEntry 234946560}

pr1646v2VxlBGIMVpVlanMCH2P OBJECT-TYPE
   SYNTAX      SEQUENCE OF Pr1646v2VxlBGIMVpVlanMCH2PEntry
   MAX-ACCESS  not-accessible
   STATUS      current
   DESCRIPTION
      ""
   ::= {pr1646v2VxlBGIMVpVlan 41549824}

pr1646v2VxlBGIMVpVlanMCH2PEntry OBJECT-TYPE
   SYNTAX      Pr1646v2VxlBGIMVpVlanMCH2PEntry
   MAX-ACCESS  not-accessible
   STATUS      current
   DESCRIPTION
      ""
   INDEX      { pr1646v2VxlBGIMVpVlanMCH2PGlobalIx,
                pr1646v2VxlBGIMVpVlanTableIx,
                pr1646v2VxlBGIMVpVlanMCH2PTableIx }
   ::= {pr1646v2VxlBGIMVpVlanMCH2P 1}

Pr1646v2VxlBGIMVpVlanMCH2PEntry ::=
   SEQUENCE
      {
      pr1646v2VxlBGIMVpVlanMCH2PGlobalIx
         GlobalIndex,
      pr1646v2VxlBGIMVpVlanMCH2PTableIx
         TableIndex,
      pr1646v2VxlBGIMVpVlanMCH2PSysUpTime
         TimeTicks,
      pr1646v2VxlBGIMVpVlanMCH2PIfUpTime
         TimeTicks,
      pr1646v2VxlBGIMVpVlanMCH2PIfStatChanges
         Counter32,
      pr1646v2VxlBGIMVpVlanMCH2PIfInOctets
         Counter64,
      pr1646v2VxlBGIMVpVlanMCH2PIfInUCPkts
         Counter64,
      pr1646v2VxlBGIMVpVlanMCH2PIfInNUCPkts
         Counter64,
      pr1646v2VxlBGIMVpVlanMCH2PIfInBCPkts
         Counter64,
      pr1646v2VxlBGIMVpVlanMCH2PIfInMCPkts
         Counter64,
      pr1646v2VxlBGIMVpVlanMCH2PIfInDiscards
         Counter64,
      pr1646v2VxlBGIMVpVlanMCH2PIfInErrors
         Counter64,
      pr1646v2VxlBGIMVpVlanMCH2PIfInUnkwn
         Counter64,
      pr1646v2VxlBGIMVpVlanMCH2PInDropEx
         Counter64,
      pr1646v2VxlBGIMVpVlanMCH2PInDropNoMac
         Counter64,
      pr1646v2VxlBGIMVpVlanMCH2PInDropNUCast
         Counter64,
      pr1646v2VxlBGIMVpVlanMCH2PInDropFilter
         Counter64,
      pr1646v2VxlBGIMVpVlanMCH2PIfInBandwidth
         Integer32,
      pr1646v2VxlBGIMVpVlanMCH2PIfOutOctets
         Counter64,
      pr1646v2VxlBGIMVpVlanMCH2PIfOutUCPkts
         Counter64,
      pr1646v2VxlBGIMVpVlanMCH2PIfOutNUCPkts
         Counter64,
      pr1646v2VxlBGIMVpVlanMCH2PIfOutBCPkts
         Counter64,
      pr1646v2VxlBGIMVpVlanMCH2PIfOutMCPkts
         Counter64,
      pr1646v2VxlBGIMVpVlanMCH2PIfOutDiscards
         Counter64,
      pr1646v2VxlBGIMVpVlanMCH2PIfOutErrors
         Counter64,
      pr1646v2VxlBGIMVpVlanMCH2POutDropEx
         Counter64,
      pr1646v2VxlBGIMVpVlanMCH2POutDropNoArp
         Counter64,
      pr1646v2VxlBGIMVpVlanMCH2POutDropFilter
         Counter64,
      pr1646v2VxlBGIMVpVlanMCH2PIfOutBandwidth
         Integer32,
      pr1646v2VxlBGIMVpVlanMCH2PIfErrSec
         Counter32
      }

pr1646v2VxlBGIMVpVlanMCH2PGlobalIx OBJECT-TYPE
   SYNTAX      GlobalIndex
   MAX-ACCESS  not-accessible
   STATUS      current
   DESCRIPTION
      "The value of the tlsCntTreeGlobalIndex of the MANAGED OBJECT."
   ::= {pr1646v2VxlBGIMVpVlanMCH2PEntry 10}

pr1646v2VxlBGIMVpVlanMCH2PTableIx OBJECT-TYPE
   SYNTAX      TableIndex
   MAX-ACCESS  not-accessible
   STATUS      current
   DESCRIPTION
      ""
   ::= {pr1646v2VxlBGIMVpVlanMCH2PEntry 11}

pr1646v2VxlBGIMVpVlanMCH2PSysUpTime OBJECT-TYPE
   SYNTAX      TimeTicks
   MAX-ACCESS  read-only
   STATUS      current
   DESCRIPTION
      "Path: vxLanBridgeGroup.performance.vlan.mibCounters.h2Performance.sysUpTime

       Time in centi-second."
   ::= {pr1646v2VxlBGIMVpVlanMCH2PEntry 16777216}

pr1646v2VxlBGIMVpVlanMCH2PIfUpTime OBJECT-TYPE
   SYNTAX      TimeTicks
   MAX-ACCESS  read-only
   STATUS      current
   DESCRIPTION
      "Path: vxLanBridgeGroup.performance.vlan.mibCounters.h2Performance.ifUpTime

       Time in centi-second."
   ::= {pr1646v2VxlBGIMVpVlanMCH2PEntry 33554432}

pr1646v2VxlBGIMVpVlanMCH2PIfStatChanges OBJECT-TYPE
   SYNTAX      Counter32
   MAX-ACCESS  read-only
   STATUS      current
   DESCRIPTION
      "Path: vxLanBridgeGroup.performance.vlan.mibCounters.h2Performance.ifStatusChanges

       32 bit unsigned wrappable counter."
   ::= {pr1646v2VxlBGIMVpVlanMCH2PEntry 50331648}

pr1646v2VxlBGIMVpVlanMCH2PIfInOctets OBJECT-TYPE
   SYNTAX      Counter64
   MAX-ACCESS  read-only
   STATUS      current
   DESCRIPTION
      "Path: vxLanBridgeGroup.performance.vlan.mibCounters.h2Performance.ifInOctets

       64 bit unsigned wrappable counter."
   ::= {pr1646v2VxlBGIMVpVlanMCH2PEntry 67108864}

pr1646v2VxlBGIMVpVlanMCH2PIfInUCPkts OBJECT-TYPE
   SYNTAX      Counter64
   MAX-ACCESS  read-only
   STATUS      current
   DESCRIPTION
      "Path: vxLanBridgeGroup.performance.vlan.mibCounters.h2Performance.ifInUcastPkts

       64 bit unsigned wrappable counter."
   ::= {pr1646v2VxlBGIMVpVlanMCH2PEntry 83886080}

pr1646v2VxlBGIMVpVlanMCH2PIfInNUCPkts OBJECT-TYPE
   SYNTAX      Counter64
   MAX-ACCESS  read-only
   STATUS      current
   DESCRIPTION
      "Path: vxLanBridgeGroup.performance.vlan.mibCounters.h2Performance.ifInNUcastPkts

       64 bit unsigned wrappable counter."
   ::= {pr1646v2VxlBGIMVpVlanMCH2PEntry 100663296}

pr1646v2VxlBGIMVpVlanMCH2PIfInBCPkts OBJECT-TYPE
   SYNTAX      Counter64
   MAX-ACCESS  read-only
   STATUS      current
   DESCRIPTION
      "Path: vxLanBridgeGroup.performance.vlan.mibCounters.h2Performance.ifInBcastPkts

       64 bit unsigned wrappable counter."
   ::= {pr1646v2VxlBGIMVpVlanMCH2PEntry 419430400}

pr1646v2VxlBGIMVpVlanMCH2PIfInMCPkts OBJECT-TYPE
   SYNTAX      Counter64
   MAX-ACCESS  read-only
   STATUS      current
   DESCRIPTION
      "Path: vxLanBridgeGroup.performance.vlan.mibCounters.h2Performance.ifInMcastPkts

       64 bit unsigned wrappable counter."
   ::= {pr1646v2VxlBGIMVpVlanMCH2PEntry 436207616}

pr1646v2VxlBGIMVpVlanMCH2PIfInDiscards OBJECT-TYPE
   SYNTAX      Counter64
   MAX-ACCESS  read-only
   STATUS      current
   DESCRIPTION
      "Path: vxLanBridgeGroup.performance.vlan.mibCounters.h2Performance.ifInDiscards

       64 bit unsigned wrappable counter."
   ::= {pr1646v2VxlBGIMVpVlanMCH2PEntry 117440512}

pr1646v2VxlBGIMVpVlanMCH2PIfInErrors OBJECT-TYPE
   SYNTAX      Counter64
   MAX-ACCESS  read-only
   STATUS      current
   DESCRIPTION
      "Path: vxLanBridgeGroup.performance.vlan.mibCounters.h2Performance.ifInErrors

       64 bit unsigned wrappable counter."
   ::= {pr1646v2VxlBGIMVpVlanMCH2PEntry 134217728}

pr1646v2VxlBGIMVpVlanMCH2PIfInUnkwn OBJECT-TYPE
   SYNTAX      Counter64
   MAX-ACCESS  read-only
   STATUS      current
   DESCRIPTION
      "Path: vxLanBridgeGroup.performance.vlan.mibCounters.h2Performance.ifInUnknownProtos

       64 bit unsigned wrappable counter."
   ::= {pr1646v2VxlBGIMVpVlanMCH2PEntry 150994944}

pr1646v2VxlBGIMVpVlanMCH2PInDropEx OBJECT-TYPE
   SYNTAX      Counter64
   MAX-ACCESS  read-only
   STATUS      current
   DESCRIPTION
      "Path: vxLanBridgeGroup.performance.vlan.mibCounters.h2Performance.ifInDropLevelExceeded

       64 bit unsigned wrappable counter."
   ::= {pr1646v2VxlBGIMVpVlanMCH2PEntry 335544320}

pr1646v2VxlBGIMVpVlanMCH2PInDropNoMac OBJECT-TYPE
   SYNTAX      Counter64
   MAX-ACCESS  read-only
   STATUS      current
   DESCRIPTION
      "Path: vxLanBridgeGroup.performance.vlan.mibCounters.h2Performance.fInDiscardsNoMacFit

       64 bit unsigned wrappable counter."
   ::= {pr1646v2VxlBGIMVpVlanMCH2PEntry 301989888}

pr1646v2VxlBGIMVpVlanMCH2PInDropNUCast OBJECT-TYPE
   SYNTAX      Counter64
   MAX-ACCESS  read-only
   STATUS      current
   DESCRIPTION
      "Path: vxLanBridgeGroup.performance.vlan.mibCounters.h2Performance.fInDiscardsNUCast

       64 bit unsigned wrappable counter."
   ::= {pr1646v2VxlBGIMVpVlanMCH2PEntry 318767104}

pr1646v2VxlBGIMVpVlanMCH2PInDropFilter OBJECT-TYPE
   SYNTAX      Counter64
   MAX-ACCESS  read-only
   STATUS      current
   DESCRIPTION
      "Path: vxLanBridgeGroup.performance.vlan.mibCounters.h2Performance.fInDiscardsFilter

       64 bit unsigned wrappable counter."
   ::= {pr1646v2VxlBGIMVpVlanMCH2PEntry 385875968}

pr1646v2VxlBGIMVpVlanMCH2PIfInBandwidth OBJECT-TYPE
   SYNTAX      Integer32
   MAX-ACCESS  read-only
   STATUS      current
   DESCRIPTION
      "Path: vxLanBridgeGroup.performance.vlan.mibCounters.h2Performance.ifInBandwidth

       unit name = bps
       formula = 8 * ; 8 /"
   ::= {pr1646v2VxlBGIMVpVlanMCH2PEntry 268435456}

pr1646v2VxlBGIMVpVlanMCH2PIfOutOctets OBJECT-TYPE
   SYNTAX      Counter64
   MAX-ACCESS  read-only
   STATUS      current
   DESCRIPTION
      "Path: vxLanBridgeGroup.performance.vlan.mibCounters.h2Performance.ifOutOctets

       64 bit unsigned wrappable counter."
   ::= {pr1646v2VxlBGIMVpVlanMCH2PEntry 167772160}

pr1646v2VxlBGIMVpVlanMCH2PIfOutUCPkts OBJECT-TYPE
   SYNTAX      Counter64
   MAX-ACCESS  read-only
   STATUS      current
   DESCRIPTION
      "Path: vxLanBridgeGroup.performance.vlan.mibCounters.h2Performance.ifOutUcastPkts

       64 bit unsigned wrappable counter."
   ::= {pr1646v2VxlBGIMVpVlanMCH2PEntry 184549376}

pr1646v2VxlBGIMVpVlanMCH2PIfOutNUCPkts OBJECT-TYPE
   SYNTAX      Counter64
   MAX-ACCESS  read-only
   STATUS      current
   DESCRIPTION
      "Path: vxLanBridgeGroup.performance.vlan.mibCounters.h2Performance.ifOutNUcastPkts

       64 bit unsigned wrappable counter."
   ::= {pr1646v2VxlBGIMVpVlanMCH2PEntry 201326592}

pr1646v2VxlBGIMVpVlanMCH2PIfOutBCPkts OBJECT-TYPE
   SYNTAX      Counter64
   MAX-ACCESS  read-only
   STATUS      current
   DESCRIPTION
      "Path: vxLanBridgeGroup.performance.vlan.mibCounters.h2Performance.ifOutBcastPkts

       64 bit unsigned wrappable counter."
   ::= {pr1646v2VxlBGIMVpVlanMCH2PEntry 452984832}

pr1646v2VxlBGIMVpVlanMCH2PIfOutMCPkts OBJECT-TYPE
   SYNTAX      Counter64
   MAX-ACCESS  read-only
   STATUS      current
   DESCRIPTION
      "Path: vxLanBridgeGroup.performance.vlan.mibCounters.h2Performance.ifOutMcastPkts

       64 bit unsigned wrappable counter."
   ::= {pr1646v2VxlBGIMVpVlanMCH2PEntry 469762048}

pr1646v2VxlBGIMVpVlanMCH2PIfOutDiscards OBJECT-TYPE
   SYNTAX      Counter64
   MAX-ACCESS  read-only
   STATUS      current
   DESCRIPTION
      "Path: vxLanBridgeGroup.performance.vlan.mibCounters.h2Performance.ifOutDiscards

       64 bit unsigned wrappable counter."
   ::= {pr1646v2VxlBGIMVpVlanMCH2PEntry 218103808}

pr1646v2VxlBGIMVpVlanMCH2PIfOutErrors OBJECT-TYPE
   SYNTAX      Counter64
   MAX-ACCESS  read-only
   STATUS      current
   DESCRIPTION
      "Path: vxLanBridgeGroup.performance.vlan.mibCounters.h2Performance.ifOutErrors

       64 bit unsigned wrappable counter."
   ::= {pr1646v2VxlBGIMVpVlanMCH2PEntry 234881024}

pr1646v2VxlBGIMVpVlanMCH2POutDropEx OBJECT-TYPE
   SYNTAX      Counter64
   MAX-ACCESS  read-only
   STATUS      current
   DESCRIPTION
      "Path: vxLanBridgeGroup.performance.vlan.mibCounters.h2Performance.ifOutDropLevelExceeded

       64 bit unsigned wrappable counter."
   ::= {pr1646v2VxlBGIMVpVlanMCH2PEntry 352321536}

pr1646v2VxlBGIMVpVlanMCH2POutDropNoArp OBJECT-TYPE
   SYNTAX      Counter64
   MAX-ACCESS  read-only
   STATUS      current
   DESCRIPTION
      "Path: vxLanBridgeGroup.performance.vlan.mibCounters.h2Performance.ifOutDiscardsNoArp

       64 bit unsigned wrappable counter."
   ::= {pr1646v2VxlBGIMVpVlanMCH2PEntry 369098752}

pr1646v2VxlBGIMVpVlanMCH2POutDropFilter OBJECT-TYPE
   SYNTAX      Counter64
   MAX-ACCESS  read-only
   STATUS      current
   DESCRIPTION
      "Path: vxLanBridgeGroup.performance.vlan.mibCounters.h2Performance.ifOutDiscardsFilter

       64 bit unsigned wrappable counter."
   ::= {pr1646v2VxlBGIMVpVlanMCH2PEntry 402653184}

pr1646v2VxlBGIMVpVlanMCH2PIfOutBandwidth OBJECT-TYPE
   SYNTAX      Integer32
   MAX-ACCESS  read-only
   STATUS      current
   DESCRIPTION
      "Path: vxLanBridgeGroup.performance.vlan.mibCounters.h2Performance.ifOutBandwidth

       unit name = bps
       formula = 8 * ; 8 /"
   ::= {pr1646v2VxlBGIMVpVlanMCH2PEntry 285212672}

pr1646v2VxlBGIMVpVlanMCH2PIfErrSec OBJECT-TYPE
   SYNTAX      Counter32
   MAX-ACCESS  read-only
   STATUS      current
   DESCRIPTION
      "Path: vxLanBridgeGroup.performance.vlan.mibCounters.h2Performance.ifErrSec

       32 bit unsigned wrappable counter."
   ::= {pr1646v2VxlBGIMVpVlanMCH2PEntry 251658240}

pr1646v2VxlBGIMVpVlanMCH24P OBJECT-TYPE
   SYNTAX      SEQUENCE OF Pr1646v2VxlBGIMVpVlanMCH24PEntry
   MAX-ACCESS  not-accessible
   STATUS      current
   DESCRIPTION
      ""
   ::= {pr1646v2VxlBGIMVpVlan 41615360}

pr1646v2VxlBGIMVpVlanMCH24PEntry OBJECT-TYPE
   SYNTAX      Pr1646v2VxlBGIMVpVlanMCH24PEntry
   MAX-ACCESS  not-accessible
   STATUS      current
   DESCRIPTION
      ""
   INDEX      { pr1646v2VxlBGIMVpVlanMCH24PGlobalIx,
                pr1646v2VxlBGIMVpVlanTableIx,
                pr1646v2VxlBGIMVpVlanMCH24PTableIx }
   ::= {pr1646v2VxlBGIMVpVlanMCH24P 1}

Pr1646v2VxlBGIMVpVlanMCH24PEntry ::=
   SEQUENCE
      {
      pr1646v2VxlBGIMVpVlanMCH24PGlobalIx
         GlobalIndex,
      pr1646v2VxlBGIMVpVlanMCH24PTableIx
         TableIndex,
      pr1646v2VxlBGIMVpVlanMCH24PSysUpTime
         TimeTicks,
      pr1646v2VxlBGIMVpVlanMCH24PIfUpTime
         TimeTicks,
      pr1646v2VxlBGIMVpVlanMCH24PIfStatChanges
         Counter32,
      pr1646v2VxlBGIMVpVlanMCH24PIfInOctets
         Counter64,
      pr1646v2VxlBGIMVpVlanMCH24PIfInUCPkts
         Counter64,
      pr1646v2VxlBGIMVpVlanMCH24PIfInNUCPkts
         Counter64,
      pr1646v2VxlBGIMVpVlanMCH24PIfInBCPkts
         Counter64,
      pr1646v2VxlBGIMVpVlanMCH24PIfInMCPkts
         Counter64,
      pr1646v2VxlBGIMVpVlanMCH24PIfInDiscards
         Counter64,
      pr1646v2VxlBGIMVpVlanMCH24PIfInErrors
         Counter64,
      pr1646v2VxlBGIMVpVlanMCH24PIfInUnkwn
         Counter64,
      pr1646v2VxlBGIMVpVlanMCH24PInDropEx
         Counter64,
      pr1646v2VxlBGIMVpVlanMCH24PInDropNoMac
         Counter64,
      pr1646v2VxlBGIMVpVlanMCH24PInDropNUCast
         Counter64,
      pr1646v2VxlBGIMVpVlanMCH24PInDropFilter
         Counter64,
      pr1646v2VxlBGIMVpVlanMCH24PIfInBandwidth
         Integer32,
      pr1646v2VxlBGIMVpVlanMCH24PIfOutOctets
         Counter64,
      pr1646v2VxlBGIMVpVlanMCH24PIfOutUCPkts
         Counter64,
      pr1646v2VxlBGIMVpVlanMCH24PIfOutNUCPkts
         Counter64,
      pr1646v2VxlBGIMVpVlanMCH24PIfOutBCPkts
         Counter64,
      pr1646v2VxlBGIMVpVlanMCH24PIfOutMCPkts
         Counter64,
      pr1646v2VxlBGIMVpVlanMCH24PIfOutDiscards
         Counter64,
      pr1646v2VxlBGIMVpVlanMCH24PIfOutErrors
         Counter64,
      pr1646v2VxlBGIMVpVlanMCH24POutDropEx
         Counter64,
      pr1646v2VxlBGIMVpVlanMCH24POutDropNoArp
         Counter64,
      pr1646v2VxlBGIMVpVlanMCH24POutDropFilter
         Counter64,
      pr1646v2VxlBGIMVpVlanMCH24PIfOutBandwidth
         Integer32,
      pr1646v2VxlBGIMVpVlanMCH24PIfErrSec
         Counter32
      }

pr1646v2VxlBGIMVpVlanMCH24PGlobalIx OBJECT-TYPE
   SYNTAX      GlobalIndex
   MAX-ACCESS  not-accessible
   STATUS      current
   DESCRIPTION
      "The value of the tlsCntTreeGlobalIndex of the MANAGED OBJECT."
   ::= {pr1646v2VxlBGIMVpVlanMCH24PEntry 10}

pr1646v2VxlBGIMVpVlanMCH24PTableIx OBJECT-TYPE
   SYNTAX      TableIndex
   MAX-ACCESS  not-accessible
   STATUS      current
   DESCRIPTION
      ""
   ::= {pr1646v2VxlBGIMVpVlanMCH24PEntry 11}

pr1646v2VxlBGIMVpVlanMCH24PSysUpTime OBJECT-TYPE
   SYNTAX      TimeTicks
   MAX-ACCESS  read-only
   STATUS      current
   DESCRIPTION
      "Path: vxLanBridgeGroup.performance.vlan.mibCounters.h24Performance.sysUpTime

       Time in centi-second."
   ::= {pr1646v2VxlBGIMVpVlanMCH24PEntry 16777216}

pr1646v2VxlBGIMVpVlanMCH24PIfUpTime OBJECT-TYPE
   SYNTAX      TimeTicks
   MAX-ACCESS  read-only
   STATUS      current
   DESCRIPTION
      "Path: vxLanBridgeGroup.performance.vlan.mibCounters.h24Performance.ifUpTime

       Time in centi-second."
   ::= {pr1646v2VxlBGIMVpVlanMCH24PEntry 33554432}

pr1646v2VxlBGIMVpVlanMCH24PIfStatChanges OBJECT-TYPE
   SYNTAX      Counter32
   MAX-ACCESS  read-only
   STATUS      current
   DESCRIPTION
      "Path: vxLanBridgeGroup.performance.vlan.mibCounters.h24Performance.ifStatusChanges

       32 bit unsigned wrappable counter."
   ::= {pr1646v2VxlBGIMVpVlanMCH24PEntry 50331648}

pr1646v2VxlBGIMVpVlanMCH24PIfInOctets OBJECT-TYPE
   SYNTAX      Counter64
   MAX-ACCESS  read-only
   STATUS      current
   DESCRIPTION
      "Path: vxLanBridgeGroup.performance.vlan.mibCounters.h24Performance.ifInOctets

       64 bit unsigned wrappable counter."
   ::= {pr1646v2VxlBGIMVpVlanMCH24PEntry 67108864}

pr1646v2VxlBGIMVpVlanMCH24PIfInUCPkts OBJECT-TYPE
   SYNTAX      Counter64
   MAX-ACCESS  read-only
   STATUS      current
   DESCRIPTION
      "Path: vxLanBridgeGroup.performance.vlan.mibCounters.h24Performance.ifInUcastPkts

       64 bit unsigned wrappable counter."
   ::= {pr1646v2VxlBGIMVpVlanMCH24PEntry 83886080}

pr1646v2VxlBGIMVpVlanMCH24PIfInNUCPkts OBJECT-TYPE
   SYNTAX      Counter64
   MAX-ACCESS  read-only
   STATUS      current
   DESCRIPTION
      "Path: vxLanBridgeGroup.performance.vlan.mibCounters.h24Performance.ifInNUcastPkts

       64 bit unsigned wrappable counter."
   ::= {pr1646v2VxlBGIMVpVlanMCH24PEntry 100663296}

pr1646v2VxlBGIMVpVlanMCH24PIfInBCPkts OBJECT-TYPE
   SYNTAX      Counter64
   MAX-ACCESS  read-only
   STATUS      current
   DESCRIPTION
      "Path: vxLanBridgeGroup.performance.vlan.mibCounters.h24Performance.ifInBcastPkts

       64 bit unsigned wrappable counter."
   ::= {pr1646v2VxlBGIMVpVlanMCH24PEntry 419430400}

pr1646v2VxlBGIMVpVlanMCH24PIfInMCPkts OBJECT-TYPE
   SYNTAX      Counter64
   MAX-ACCESS  read-only
   STATUS      current
   DESCRIPTION
      "Path: vxLanBridgeGroup.performance.vlan.mibCounters.h24Performance.ifInMcastPkts

       64 bit unsigned wrappable counter."
   ::= {pr1646v2VxlBGIMVpVlanMCH24PEntry 436207616}

pr1646v2VxlBGIMVpVlanMCH24PIfInDiscards OBJECT-TYPE
   SYNTAX      Counter64
   MAX-ACCESS  read-only
   STATUS      current
   DESCRIPTION
      "Path: vxLanBridgeGroup.performance.vlan.mibCounters.h24Performance.ifInDiscards

       64 bit unsigned wrappable counter."
   ::= {pr1646v2VxlBGIMVpVlanMCH24PEntry 117440512}

pr1646v2VxlBGIMVpVlanMCH24PIfInErrors OBJECT-TYPE
   SYNTAX      Counter64
   MAX-ACCESS  read-only
   STATUS      current
   DESCRIPTION
      "Path: vxLanBridgeGroup.performance.vlan.mibCounters.h24Performance.ifInErrors

       64 bit unsigned wrappable counter."
   ::= {pr1646v2VxlBGIMVpVlanMCH24PEntry 134217728}

pr1646v2VxlBGIMVpVlanMCH24PIfInUnkwn OBJECT-TYPE
   SYNTAX      Counter64
   MAX-ACCESS  read-only
   STATUS      current
   DESCRIPTION
      "Path: vxLanBridgeGroup.performance.vlan.mibCounters.h24Performance.ifInUnknownProtos

       64 bit unsigned wrappable counter."
   ::= {pr1646v2VxlBGIMVpVlanMCH24PEntry 150994944}

pr1646v2VxlBGIMVpVlanMCH24PInDropEx OBJECT-TYPE
   SYNTAX      Counter64
   MAX-ACCESS  read-only
   STATUS      current
   DESCRIPTION
      "Path: vxLanBridgeGroup.performance.vlan.mibCounters.h24Performance.ifInDropLevelExceeded

       64 bit unsigned wrappable counter."
   ::= {pr1646v2VxlBGIMVpVlanMCH24PEntry 335544320}

pr1646v2VxlBGIMVpVlanMCH24PInDropNoMac OBJECT-TYPE
   SYNTAX      Counter64
   MAX-ACCESS  read-only
   STATUS      current
   DESCRIPTION
      "Path: vxLanBridgeGroup.performance.vlan.mibCounters.h24Performance.fInDiscardsNoMacFit

       64 bit unsigned wrappable counter."
   ::= {pr1646v2VxlBGIMVpVlanMCH24PEntry 301989888}

pr1646v2VxlBGIMVpVlanMCH24PInDropNUCast OBJECT-TYPE
   SYNTAX      Counter64
   MAX-ACCESS  read-only
   STATUS      current
   DESCRIPTION
      "Path: vxLanBridgeGroup.performance.vlan.mibCounters.h24Performance.fInDiscardsNUCast

       64 bit unsigned wrappable counter."
   ::= {pr1646v2VxlBGIMVpVlanMCH24PEntry 318767104}

pr1646v2VxlBGIMVpVlanMCH24PInDropFilter OBJECT-TYPE
   SYNTAX      Counter64
   MAX-ACCESS  read-only
   STATUS      current
   DESCRIPTION
      "Path: vxLanBridgeGroup.performance.vlan.mibCounters.h24Performance.fInDiscardsFilter

       64 bit unsigned wrappable counter."
   ::= {pr1646v2VxlBGIMVpVlanMCH24PEntry 385875968}

pr1646v2VxlBGIMVpVlanMCH24PIfInBandwidth OBJECT-TYPE
   SYNTAX      Integer32
   MAX-ACCESS  read-only
   STATUS      current
   DESCRIPTION
      "Path: vxLanBridgeGroup.performance.vlan.mibCounters.h24Performance.ifInBandwidth

       unit name = bps
       formula = 8 * ; 8 /"
   ::= {pr1646v2VxlBGIMVpVlanMCH24PEntry 268435456}

pr1646v2VxlBGIMVpVlanMCH24PIfOutOctets OBJECT-TYPE
   SYNTAX      Counter64
   MAX-ACCESS  read-only
   STATUS      current
   DESCRIPTION
      "Path: vxLanBridgeGroup.performance.vlan.mibCounters.h24Performance.ifOutOctets

       64 bit unsigned wrappable counter."
   ::= {pr1646v2VxlBGIMVpVlanMCH24PEntry 167772160}

pr1646v2VxlBGIMVpVlanMCH24PIfOutUCPkts OBJECT-TYPE
   SYNTAX      Counter64
   MAX-ACCESS  read-only
   STATUS      current
   DESCRIPTION
      "Path: vxLanBridgeGroup.performance.vlan.mibCounters.h24Performance.ifOutUcastPkts

       64 bit unsigned wrappable counter."
   ::= {pr1646v2VxlBGIMVpVlanMCH24PEntry 184549376}

pr1646v2VxlBGIMVpVlanMCH24PIfOutNUCPkts OBJECT-TYPE
   SYNTAX      Counter64
   MAX-ACCESS  read-only
   STATUS      current
   DESCRIPTION
      "Path: vxLanBridgeGroup.performance.vlan.mibCounters.h24Performance.ifOutNUcastPkts

       64 bit unsigned wrappable counter."
   ::= {pr1646v2VxlBGIMVpVlanMCH24PEntry 201326592}

pr1646v2VxlBGIMVpVlanMCH24PIfOutBCPkts OBJECT-TYPE
   SYNTAX      Counter64
   MAX-ACCESS  read-only
   STATUS      current
   DESCRIPTION
      "Path: vxLanBridgeGroup.performance.vlan.mibCounters.h24Performance.ifOutBcastPkts

       64 bit unsigned wrappable counter."
   ::= {pr1646v2VxlBGIMVpVlanMCH24PEntry 452984832}

pr1646v2VxlBGIMVpVlanMCH24PIfOutMCPkts OBJECT-TYPE
   SYNTAX      Counter64
   MAX-ACCESS  read-only
   STATUS      current
   DESCRIPTION
      "Path: vxLanBridgeGroup.performance.vlan.mibCounters.h24Performance.ifOutMcastPkts

       64 bit unsigned wrappable counter."
   ::= {pr1646v2VxlBGIMVpVlanMCH24PEntry 469762048}

pr1646v2VxlBGIMVpVlanMCH24PIfOutDiscards OBJECT-TYPE
   SYNTAX      Counter64
   MAX-ACCESS  read-only
   STATUS      current
   DESCRIPTION
      "Path: vxLanBridgeGroup.performance.vlan.mibCounters.h24Performance.ifOutDiscards

       64 bit unsigned wrappable counter."
   ::= {pr1646v2VxlBGIMVpVlanMCH24PEntry 218103808}

pr1646v2VxlBGIMVpVlanMCH24PIfOutErrors OBJECT-TYPE
   SYNTAX      Counter64
   MAX-ACCESS  read-only
   STATUS      current
   DESCRIPTION
      "Path: vxLanBridgeGroup.performance.vlan.mibCounters.h24Performance.ifOutErrors

       64 bit unsigned wrappable counter."
   ::= {pr1646v2VxlBGIMVpVlanMCH24PEntry 234881024}

pr1646v2VxlBGIMVpVlanMCH24POutDropEx OBJECT-TYPE
   SYNTAX      Counter64
   MAX-ACCESS  read-only
   STATUS      current
   DESCRIPTION
      "Path: vxLanBridgeGroup.performance.vlan.mibCounters.h24Performance.ifOutDropLevelExceeded

       64 bit unsigned wrappable counter."
   ::= {pr1646v2VxlBGIMVpVlanMCH24PEntry 352321536}

pr1646v2VxlBGIMVpVlanMCH24POutDropNoArp OBJECT-TYPE
   SYNTAX      Counter64
   MAX-ACCESS  read-only
   STATUS      current
   DESCRIPTION
      "Path: vxLanBridgeGroup.performance.vlan.mibCounters.h24Performance.ifOutDiscardsNoArp

       64 bit unsigned wrappable counter."
   ::= {pr1646v2VxlBGIMVpVlanMCH24PEntry 369098752}

pr1646v2VxlBGIMVpVlanMCH24POutDropFilter OBJECT-TYPE
   SYNTAX      Counter64
   MAX-ACCESS  read-only
   STATUS      current
   DESCRIPTION
      "Path: vxLanBridgeGroup.performance.vlan.mibCounters.h24Performance.ifOutDiscardsFilter

       64 bit unsigned wrappable counter."
   ::= {pr1646v2VxlBGIMVpVlanMCH24PEntry 402653184}

pr1646v2VxlBGIMVpVlanMCH24PIfOutBandwidth OBJECT-TYPE
   SYNTAX      Integer32
   MAX-ACCESS  read-only
   STATUS      current
   DESCRIPTION
      "Path: vxLanBridgeGroup.performance.vlan.mibCounters.h24Performance.ifOutBandwidth

       unit name = bps
       formula = 8 * ; 8 /"
   ::= {pr1646v2VxlBGIMVpVlanMCH24PEntry 285212672}

pr1646v2VxlBGIMVpVlanMCH24PIfErrSec OBJECT-TYPE
   SYNTAX      Counter32
   MAX-ACCESS  read-only
   STATUS      current
   DESCRIPTION
      "Path: vxLanBridgeGroup.performance.vlan.mibCounters.h24Performance.ifErrSec

       32 bit unsigned wrappable counter."
   ::= {pr1646v2VxlBGIMVpVlanMCH24PEntry 251658240}

pr1646v2VxlBGIMVpVlanMCD7P OBJECT-TYPE
   SYNTAX      SEQUENCE OF Pr1646v2VxlBGIMVpVlanMCD7PEntry
   MAX-ACCESS  not-accessible
   STATUS      current
   DESCRIPTION
      ""
   ::= {pr1646v2VxlBGIMVpVlan 41680896}

pr1646v2VxlBGIMVpVlanMCD7PEntry OBJECT-TYPE
   SYNTAX      Pr1646v2VxlBGIMVpVlanMCD7PEntry
   MAX-ACCESS  not-accessible
   STATUS      current
   DESCRIPTION
      ""
   INDEX      { pr1646v2VxlBGIMVpVlanMCD7PGlobalIx,
                pr1646v2VxlBGIMVpVlanTableIx,
                pr1646v2VxlBGIMVpVlanMCD7PTableIx }
   ::= {pr1646v2VxlBGIMVpVlanMCD7P 1}

Pr1646v2VxlBGIMVpVlanMCD7PEntry ::=
   SEQUENCE
      {
      pr1646v2VxlBGIMVpVlanMCD7PGlobalIx
         GlobalIndex,
      pr1646v2VxlBGIMVpVlanMCD7PTableIx
         TableIndex,
      pr1646v2VxlBGIMVpVlanMCD7PSysUpTime
         TimeTicks,
      pr1646v2VxlBGIMVpVlanMCD7PIfUpTime
         TimeTicks,
      pr1646v2VxlBGIMVpVlanMCD7PIfStatChanges
         Counter32,
      pr1646v2VxlBGIMVpVlanMCD7PIfInOctets
         Counter64,
      pr1646v2VxlBGIMVpVlanMCD7PIfInUCPkts
         Counter64,
      pr1646v2VxlBGIMVpVlanMCD7PIfInNUCPkts
         Counter64,
      pr1646v2VxlBGIMVpVlanMCD7PIfInBCPkts
         Counter64,
      pr1646v2VxlBGIMVpVlanMCD7PIfInMCPkts
         Counter64,
      pr1646v2VxlBGIMVpVlanMCD7PIfInDiscards
         Counter64,
      pr1646v2VxlBGIMVpVlanMCD7PIfInErrors
         Counter64,
      pr1646v2VxlBGIMVpVlanMCD7PIfInUnkwn
         Counter64,
      pr1646v2VxlBGIMVpVlanMCD7PInDropEx
         Counter64,
      pr1646v2VxlBGIMVpVlanMCD7PInDropNoMac
         Counter64,
      pr1646v2VxlBGIMVpVlanMCD7PInDropNUCast
         Counter64,
      pr1646v2VxlBGIMVpVlanMCD7PInDropFilter
         Counter64,
      pr1646v2VxlBGIMVpVlanMCD7PIfInBandwidth
         Integer32,
      pr1646v2VxlBGIMVpVlanMCD7PIfOutOctets
         Counter64,
      pr1646v2VxlBGIMVpVlanMCD7PIfOutUCPkts
         Counter64,
      pr1646v2VxlBGIMVpVlanMCD7PIfOutNUCPkts
         Counter64,
      pr1646v2VxlBGIMVpVlanMCD7PIfOutBCPkts
         Counter64,
      pr1646v2VxlBGIMVpVlanMCD7PIfOutMCPkts
         Counter64,
      pr1646v2VxlBGIMVpVlanMCD7PIfOutDiscards
         Counter64,
      pr1646v2VxlBGIMVpVlanMCD7PIfOutErrors
         Counter64,
      pr1646v2VxlBGIMVpVlanMCD7POutDropEx
         Counter64,
      pr1646v2VxlBGIMVpVlanMCD7POutDropNoArp
         Counter64,
      pr1646v2VxlBGIMVpVlanMCD7POutDropFilter
         Counter64,
      pr1646v2VxlBGIMVpVlanMCD7PIfOutBandwidth
         Integer32,
      pr1646v2VxlBGIMVpVlanMCD7PIfErrSec
         Counter32
      }

pr1646v2VxlBGIMVpVlanMCD7PGlobalIx OBJECT-TYPE
   SYNTAX      GlobalIndex
   MAX-ACCESS  not-accessible
   STATUS      current
   DESCRIPTION
      "The value of the tlsCntTreeGlobalIndex of the MANAGED OBJECT."
   ::= {pr1646v2VxlBGIMVpVlanMCD7PEntry 10}

pr1646v2VxlBGIMVpVlanMCD7PTableIx OBJECT-TYPE
   SYNTAX      TableIndex
   MAX-ACCESS  not-accessible
   STATUS      current
   DESCRIPTION
      ""
   ::= {pr1646v2VxlBGIMVpVlanMCD7PEntry 11}

pr1646v2VxlBGIMVpVlanMCD7PSysUpTime OBJECT-TYPE
   SYNTAX      TimeTicks
   MAX-ACCESS  read-only
   STATUS      current
   DESCRIPTION
      "Path: vxLanBridgeGroup.performance.vlan.mibCounters.d7Performance.sysUpTime

       Time in centi-second."
   ::= {pr1646v2VxlBGIMVpVlanMCD7PEntry 16777216}

pr1646v2VxlBGIMVpVlanMCD7PIfUpTime OBJECT-TYPE
   SYNTAX      TimeTicks
   MAX-ACCESS  read-only
   STATUS      current
   DESCRIPTION
      "Path: vxLanBridgeGroup.performance.vlan.mibCounters.d7Performance.ifUpTime

       Time in centi-second."
   ::= {pr1646v2VxlBGIMVpVlanMCD7PEntry 33554432}

pr1646v2VxlBGIMVpVlanMCD7PIfStatChanges OBJECT-TYPE
   SYNTAX      Counter32
   MAX-ACCESS  read-only
   STATUS      current
   DESCRIPTION
      "Path: vxLanBridgeGroup.performance.vlan.mibCounters.d7Performance.ifStatusChanges

       32 bit unsigned wrappable counter."
   ::= {pr1646v2VxlBGIMVpVlanMCD7PEntry 50331648}

pr1646v2VxlBGIMVpVlanMCD7PIfInOctets OBJECT-TYPE
   SYNTAX      Counter64
   MAX-ACCESS  read-only
   STATUS      current
   DESCRIPTION
      "Path: vxLanBridgeGroup.performance.vlan.mibCounters.d7Performance.ifInOctets

       64 bit unsigned wrappable counter."
   ::= {pr1646v2VxlBGIMVpVlanMCD7PEntry 67108864}

pr1646v2VxlBGIMVpVlanMCD7PIfInUCPkts OBJECT-TYPE
   SYNTAX      Counter64
   MAX-ACCESS  read-only
   STATUS      current
   DESCRIPTION
      "Path: vxLanBridgeGroup.performance.vlan.mibCounters.d7Performance.ifInUcastPkts

       64 bit unsigned wrappable counter."
   ::= {pr1646v2VxlBGIMVpVlanMCD7PEntry 83886080}

pr1646v2VxlBGIMVpVlanMCD7PIfInNUCPkts OBJECT-TYPE
   SYNTAX      Counter64
   MAX-ACCESS  read-only
   STATUS      current
   DESCRIPTION
      "Path: vxLanBridgeGroup.performance.vlan.mibCounters.d7Performance.ifInNUcastPkts

       64 bit unsigned wrappable counter."
   ::= {pr1646v2VxlBGIMVpVlanMCD7PEntry 100663296}

pr1646v2VxlBGIMVpVlanMCD7PIfInBCPkts OBJECT-TYPE
   SYNTAX      Counter64
   MAX-ACCESS  read-only
   STATUS      current
   DESCRIPTION
      "Path: vxLanBridgeGroup.performance.vlan.mibCounters.d7Performance.ifInBcastPkts

       64 bit unsigned wrappable counter."
   ::= {pr1646v2VxlBGIMVpVlanMCD7PEntry 419430400}

pr1646v2VxlBGIMVpVlanMCD7PIfInMCPkts OBJECT-TYPE
   SYNTAX      Counter64
   MAX-ACCESS  read-only
   STATUS      current
   DESCRIPTION
      "Path: vxLanBridgeGroup.performance.vlan.mibCounters.d7Performance.ifInMcastPkts

       64 bit unsigned wrappable counter."
   ::= {pr1646v2VxlBGIMVpVlanMCD7PEntry 436207616}

pr1646v2VxlBGIMVpVlanMCD7PIfInDiscards OBJECT-TYPE
   SYNTAX      Counter64
   MAX-ACCESS  read-only
   STATUS      current
   DESCRIPTION
      "Path: vxLanBridgeGroup.performance.vlan.mibCounters.d7Performance.ifInDiscards

       64 bit unsigned wrappable counter."
   ::= {pr1646v2VxlBGIMVpVlanMCD7PEntry 117440512}

pr1646v2VxlBGIMVpVlanMCD7PIfInErrors OBJECT-TYPE
   SYNTAX      Counter64
   MAX-ACCESS  read-only
   STATUS      current
   DESCRIPTION
      "Path: vxLanBridgeGroup.performance.vlan.mibCounters.d7Performance.ifInErrors

       64 bit unsigned wrappable counter."
   ::= {pr1646v2VxlBGIMVpVlanMCD7PEntry 134217728}

pr1646v2VxlBGIMVpVlanMCD7PIfInUnkwn OBJECT-TYPE
   SYNTAX      Counter64
   MAX-ACCESS  read-only
   STATUS      current
   DESCRIPTION
      "Path: vxLanBridgeGroup.performance.vlan.mibCounters.d7Performance.ifInUnknownProtos

       64 bit unsigned wrappable counter."
   ::= {pr1646v2VxlBGIMVpVlanMCD7PEntry 150994944}

pr1646v2VxlBGIMVpVlanMCD7PInDropEx OBJECT-TYPE
   SYNTAX      Counter64
   MAX-ACCESS  read-only
   STATUS      current
   DESCRIPTION
      "Path: vxLanBridgeGroup.performance.vlan.mibCounters.d7Performance.ifInDropLevelExceeded

       64 bit unsigned wrappable counter."
   ::= {pr1646v2VxlBGIMVpVlanMCD7PEntry 335544320}

pr1646v2VxlBGIMVpVlanMCD7PInDropNoMac OBJECT-TYPE
   SYNTAX      Counter64
   MAX-ACCESS  read-only
   STATUS      current
   DESCRIPTION
      "Path: vxLanBridgeGroup.performance.vlan.mibCounters.d7Performance.fInDiscardsNoMacFit

       64 bit unsigned wrappable counter."
   ::= {pr1646v2VxlBGIMVpVlanMCD7PEntry 301989888}

pr1646v2VxlBGIMVpVlanMCD7PInDropNUCast OBJECT-TYPE
   SYNTAX      Counter64
   MAX-ACCESS  read-only
   STATUS      current
   DESCRIPTION
      "Path: vxLanBridgeGroup.performance.vlan.mibCounters.d7Performance.fInDiscardsNUCast

       64 bit unsigned wrappable counter."
   ::= {pr1646v2VxlBGIMVpVlanMCD7PEntry 318767104}

pr1646v2VxlBGIMVpVlanMCD7PInDropFilter OBJECT-TYPE
   SYNTAX      Counter64
   MAX-ACCESS  read-only
   STATUS      current
   DESCRIPTION
      "Path: vxLanBridgeGroup.performance.vlan.mibCounters.d7Performance.fInDiscardsFilter

       64 bit unsigned wrappable counter."
   ::= {pr1646v2VxlBGIMVpVlanMCD7PEntry 385875968}

pr1646v2VxlBGIMVpVlanMCD7PIfInBandwidth OBJECT-TYPE
   SYNTAX      Integer32
   MAX-ACCESS  read-only
   STATUS      current
   DESCRIPTION
      "Path: vxLanBridgeGroup.performance.vlan.mibCounters.d7Performance.ifInBandwidth

       unit name = bps
       formula = 8 * ; 8 /"
   ::= {pr1646v2VxlBGIMVpVlanMCD7PEntry 268435456}

pr1646v2VxlBGIMVpVlanMCD7PIfOutOctets OBJECT-TYPE
   SYNTAX      Counter64
   MAX-ACCESS  read-only
   STATUS      current
   DESCRIPTION
      "Path: vxLanBridgeGroup.performance.vlan.mibCounters.d7Performance.ifOutOctets

       64 bit unsigned wrappable counter."
   ::= {pr1646v2VxlBGIMVpVlanMCD7PEntry 167772160}

pr1646v2VxlBGIMVpVlanMCD7PIfOutUCPkts OBJECT-TYPE
   SYNTAX      Counter64
   MAX-ACCESS  read-only
   STATUS      current
   DESCRIPTION
      "Path: vxLanBridgeGroup.performance.vlan.mibCounters.d7Performance.ifOutUcastPkts

       64 bit unsigned wrappable counter."
   ::= {pr1646v2VxlBGIMVpVlanMCD7PEntry 184549376}

pr1646v2VxlBGIMVpVlanMCD7PIfOutNUCPkts OBJECT-TYPE
   SYNTAX      Counter64
   MAX-ACCESS  read-only
   STATUS      current
   DESCRIPTION
      "Path: vxLanBridgeGroup.performance.vlan.mibCounters.d7Performance.ifOutNUcastPkts

       64 bit unsigned wrappable counter."
   ::= {pr1646v2VxlBGIMVpVlanMCD7PEntry 201326592}

pr1646v2VxlBGIMVpVlanMCD7PIfOutBCPkts OBJECT-TYPE
   SYNTAX      Counter64
   MAX-ACCESS  read-only
   STATUS      current
   DESCRIPTION
      "Path: vxLanBridgeGroup.performance.vlan.mibCounters.d7Performance.ifOutBcastPkts

       64 bit unsigned wrappable counter."
   ::= {pr1646v2VxlBGIMVpVlanMCD7PEntry 452984832}

pr1646v2VxlBGIMVpVlanMCD7PIfOutMCPkts OBJECT-TYPE
   SYNTAX      Counter64
   MAX-ACCESS  read-only
   STATUS      current
   DESCRIPTION
      "Path: vxLanBridgeGroup.performance.vlan.mibCounters.d7Performance.ifOutMcastPkts

       64 bit unsigned wrappable counter."
   ::= {pr1646v2VxlBGIMVpVlanMCD7PEntry 469762048}

pr1646v2VxlBGIMVpVlanMCD7PIfOutDiscards OBJECT-TYPE
   SYNTAX      Counter64
   MAX-ACCESS  read-only
   STATUS      current
   DESCRIPTION
      "Path: vxLanBridgeGroup.performance.vlan.mibCounters.d7Performance.ifOutDiscards

       64 bit unsigned wrappable counter."
   ::= {pr1646v2VxlBGIMVpVlanMCD7PEntry 218103808}

pr1646v2VxlBGIMVpVlanMCD7PIfOutErrors OBJECT-TYPE
   SYNTAX      Counter64
   MAX-ACCESS  read-only
   STATUS      current
   DESCRIPTION
      "Path: vxLanBridgeGroup.performance.vlan.mibCounters.d7Performance.ifOutErrors

       64 bit unsigned wrappable counter."
   ::= {pr1646v2VxlBGIMVpVlanMCD7PEntry 234881024}

pr1646v2VxlBGIMVpVlanMCD7POutDropEx OBJECT-TYPE
   SYNTAX      Counter64
   MAX-ACCESS  read-only
   STATUS      current
   DESCRIPTION
      "Path: vxLanBridgeGroup.performance.vlan.mibCounters.d7Performance.ifOutDropLevelExceeded

       64 bit unsigned wrappable counter."
   ::= {pr1646v2VxlBGIMVpVlanMCD7PEntry 352321536}

pr1646v2VxlBGIMVpVlanMCD7POutDropNoArp OBJECT-TYPE
   SYNTAX      Counter64
   MAX-ACCESS  read-only
   STATUS      current
   DESCRIPTION
      "Path: vxLanBridgeGroup.performance.vlan.mibCounters.d7Performance.ifOutDiscardsNoArp

       64 bit unsigned wrappable counter."
   ::= {pr1646v2VxlBGIMVpVlanMCD7PEntry 369098752}

pr1646v2VxlBGIMVpVlanMCD7POutDropFilter OBJECT-TYPE
   SYNTAX      Counter64
   MAX-ACCESS  read-only
   STATUS      current
   DESCRIPTION
      "Path: vxLanBridgeGroup.performance.vlan.mibCounters.d7Performance.ifOutDiscardsFilter

       64 bit unsigned wrappable counter."
   ::= {pr1646v2VxlBGIMVpVlanMCD7PEntry 402653184}

pr1646v2VxlBGIMVpVlanMCD7PIfOutBandwidth OBJECT-TYPE
   SYNTAX      Integer32
   MAX-ACCESS  read-only
   STATUS      current
   DESCRIPTION
      "Path: vxLanBridgeGroup.performance.vlan.mibCounters.d7Performance.ifOutBandwidth

       unit name = bps
       formula = 8 * ; 8 /"
   ::= {pr1646v2VxlBGIMVpVlanMCD7PEntry 285212672}

pr1646v2VxlBGIMVpVlanMCD7PIfErrSec OBJECT-TYPE
   SYNTAX      Counter32
   MAX-ACCESS  read-only
   STATUS      current
   DESCRIPTION
      "Path: vxLanBridgeGroup.performance.vlan.mibCounters.d7Performance.ifErrSec

       32 bit unsigned wrappable counter."
   ::= {pr1646v2VxlBGIMVpVlanMCD7PEntry 251658240}


pr1646v2VxlBGIMVpPPPoE OBJECT IDENTIFIER ::= {pr1646v2VxlBGIMVp 82}

pr1646v2VxlBGIMVpPPPoESSCTable OBJECT-TYPE
   SYNTAX      SEQUENCE OF Pr1646v2VxlBGIMVpPPPoEEntry
   MAX-ACCESS  not-accessible
   STATUS      current
   DESCRIPTION
      ""
   ::= {pr1646v2VxlBGIMVpPPPoE 1}

pr1646v2VxlBGIMVpPPPoEEntry OBJECT-TYPE
   SYNTAX      Pr1646v2VxlBGIMVpPPPoEEntry
   MAX-ACCESS  not-accessible
   STATUS      current
   DESCRIPTION
      ""
   INDEX      { pr1646v2VxlBGIMVpPPPoEGlobalIx,
                pr1646v2VxlBGIMVpPPPoETableIx }
   ::= {pr1646v2VxlBGIMVpPPPoESSCTable 1}

Pr1646v2VxlBGIMVpPPPoEEntry ::=
   SEQUENCE
      {
      pr1646v2VxlBGIMVpPPPoEGlobalIx
         GlobalIndex,
      pr1646v2VxlBGIMVpPPPoETableIx
         TableIndex,
      pr1646v2VxlBGIMVpPPPoEName
         DisplayString,
      pr1646v2VxlBGIMVpPPPoEMCInOctets
         Counter64,
      pr1646v2VxlBGIMVpPPPoEMCInUcast
         Counter64,
      pr1646v2VxlBGIMVpPPPoEMCInNUcastPkts
         Counter64,
      pr1646v2VxlBGIMVpPPPoEMCInBcastPkts
         Counter64,
      pr1646v2VxlBGIMVpPPPoEMCInMcastPkts
         Counter64,
      pr1646v2VxlBGIMVpPPPoEMCInDiscards
         Counter64,
      pr1646v2VxlBGIMVpPPPoEMCInErrors
         Counter64,
      pr1646v2VxlBGIMVpPPPoEMCInUnknownProtos
         Counter64,
      pr1646v2VxlBGIMVpPPPoEMCInDropEx
         Counter64,
      pr1646v2VxlBGIMVpPPPoEMCInDropNoMac
         Counter64,
      pr1646v2VxlBGIMVpPPPoEMCInDropNUCast
         Counter64,
      pr1646v2VxlBGIMVpPPPoEMCInDropFilter
         Counter64,
      pr1646v2VxlBGIMVpPPPoEMCInBandwidth15sec
         Integer32,
      pr1646v2VxlBGIMVpPPPoEMCInBandwidth30sec
         Integer32,
      pr1646v2VxlBGIMVpPPPoEMCInBandwidth1min
         Integer32,
      pr1646v2VxlBGIMVpPPPoEMCInBandwidth2min
         Integer32,
      pr1646v2VxlBGIMVpPPPoEMCInBandwidth5min
         Integer32,
      pr1646v2VxlBGIMVpPPPoEMCOutOctets
         Counter64,
      pr1646v2VxlBGIMVpPPPoEMCOutUcastPkts
         Counter64,
      pr1646v2VxlBGIMVpPPPoEMCOutNUcastPkts
         Counter64,
      pr1646v2VxlBGIMVpPPPoEMCOutBcastPkts
         Counter64,
      pr1646v2VxlBGIMVpPPPoEMCOutMcastPkts
         Counter64,
      pr1646v2VxlBGIMVpPPPoEMCOutDiscards
         Counter64,
      pr1646v2VxlBGIMVpPPPoEMCOutErrors
         Counter64,
      pr1646v2VxlBGIMVpPPPoEMCOutQLen
         Counter32,
      pr1646v2VxlBGIMVpPPPoEMCOutDropEx
         Counter64,
      pr1646v2VxlBGIMVpPPPoEMCOutDropNoArp
         Counter64,
      pr1646v2VxlBGIMVpPPPoEMCOutDropFilter
         Counter64,
      pr1646v2VxlBGIMVpPPPoEMCOutBandwidth15sec
         Integer32,
      pr1646v2VxlBGIMVpPPPoEMCOutBandwidth30sec
         Integer32,
      pr1646v2VxlBGIMVpPPPoEMCOutBandwidth1min
         Integer32,
      pr1646v2VxlBGIMVpPPPoEMCOutBandwidth2min
         Integer32,
      pr1646v2VxlBGIMVpPPPoEMCOutBandwidth5min
         Integer32,
      pr1646v2VxlBGIMVpPPPoEPppLinkMonitoringRequestsSent
         Gauge32,
      pr1646v2VxlBGIMVpPPPoEPppLinkMonitoringRepliesRcvd
         Gauge32,
      pr1646v2VxlBGIMVpPPPoEPppLinkMonitoringRequestsRcvd
         Gauge32,
      pr1646v2VxlBGIMVpPPPoEPppLinkMonitoringRepliesSent
         Gauge32
      }

pr1646v2VxlBGIMVpPPPoEGlobalIx OBJECT-TYPE
   SYNTAX      GlobalIndex
   MAX-ACCESS  not-accessible
   STATUS      current
   DESCRIPTION
      "The value of the tlsCntTreeGlobalIndex of the MANAGED OBJECT."
   ::= {pr1646v2VxlBGIMVpPPPoEEntry 10}

pr1646v2VxlBGIMVpPPPoETableIx OBJECT-TYPE
   SYNTAX      TableIndex
   MAX-ACCESS  not-accessible
   STATUS      current
   DESCRIPTION
      ""
   ::= {pr1646v2VxlBGIMVpPPPoEEntry 11}

pr1646v2VxlBGIMVpPPPoEName OBJECT-TYPE
   SYNTAX      DisplayString
   MAX-ACCESS  read-only
   STATUS      current
   DESCRIPTION
      "Path: vxLanBridgeGroup.performance.pppoEClient.name"
   ::= {pr1646v2VxlBGIMVpPPPoEEntry 16777216}

pr1646v2VxlBGIMVpPPPoEMCInOctets OBJECT-TYPE
   SYNTAX      Counter64
   MAX-ACCESS  read-only
   STATUS      current
   DESCRIPTION
      "Path: vxLanBridgeGroup.performance.pppoEClient.mibCounters.ifInOctets

       64 bit unsigned wrappable counter."
   ::= {pr1646v2VxlBGIMVpPPPoEEntry 40697856}

pr1646v2VxlBGIMVpPPPoEMCInUcast OBJECT-TYPE
   SYNTAX      Counter64
   MAX-ACCESS  read-only
   STATUS      current
   DESCRIPTION
      "Path: vxLanBridgeGroup.performance.pppoEClient.mibCounters.ifInUcastPkts

       64 bit unsigned wrappable counter."
   ::= {pr1646v2VxlBGIMVpPPPoEEntry 40763392}

pr1646v2VxlBGIMVpPPPoEMCInNUcastPkts OBJECT-TYPE
   SYNTAX      Counter64
   MAX-ACCESS  read-only
   STATUS      current
   DESCRIPTION
      "Path: vxLanBridgeGroup.performance.pppoEClient.mibCounters.ifInNUcastPkts

       64 bit unsigned wrappable counter."
   ::= {pr1646v2VxlBGIMVpPPPoEEntry 40828928}

pr1646v2VxlBGIMVpPPPoEMCInBcastPkts OBJECT-TYPE
   SYNTAX      Counter64
   MAX-ACCESS  read-only
   STATUS      current
   DESCRIPTION
      "Path: vxLanBridgeGroup.performance.pppoEClient.mibCounters.ifInBcastPkts

       64 bit unsigned wrappable counter."
   ::= {pr1646v2VxlBGIMVpPPPoEEntry 47382528}

pr1646v2VxlBGIMVpPPPoEMCInMcastPkts OBJECT-TYPE
   SYNTAX      Counter64
   MAX-ACCESS  read-only
   STATUS      current
   DESCRIPTION
      "Path: vxLanBridgeGroup.performance.pppoEClient.mibCounters.ifInMcastPkts

       64 bit unsigned wrappable counter."
   ::= {pr1646v2VxlBGIMVpPPPoEEntry 48037888}

pr1646v2VxlBGIMVpPPPoEMCInDiscards OBJECT-TYPE
   SYNTAX      Counter64
   MAX-ACCESS  read-only
   STATUS      current
   DESCRIPTION
      "Path: vxLanBridgeGroup.performance.pppoEClient.mibCounters.ifInDiscards

       64 bit unsigned wrappable counter."
   ::= {pr1646v2VxlBGIMVpPPPoEEntry 40894464}

pr1646v2VxlBGIMVpPPPoEMCInErrors OBJECT-TYPE
   SYNTAX      Counter64
   MAX-ACCESS  read-only
   STATUS      current
   DESCRIPTION
      "Path: vxLanBridgeGroup.performance.pppoEClient.mibCounters.ifInErrors

       64 bit unsigned wrappable counter."
   ::= {pr1646v2VxlBGIMVpPPPoEEntry 40960000}

pr1646v2VxlBGIMVpPPPoEMCInUnknownProtos OBJECT-TYPE
   SYNTAX      Counter64
   MAX-ACCESS  read-only
   STATUS      current
   DESCRIPTION
      "Path: vxLanBridgeGroup.performance.pppoEClient.mibCounters.ifInUnknownProtos

       64 bit unsigned wrappable counter."
   ::= {pr1646v2VxlBGIMVpPPPoEEntry 41025536}

pr1646v2VxlBGIMVpPPPoEMCInDropEx OBJECT-TYPE
   SYNTAX      Counter64
   MAX-ACCESS  read-only
   STATUS      current
   DESCRIPTION
      "Path: vxLanBridgeGroup.performance.pppoEClient.mibCounters.ifInDropLevelExceeded

       64 bit unsigned wrappable counter."
   ::= {pr1646v2VxlBGIMVpPPPoEEntry 42074112}

pr1646v2VxlBGIMVpPPPoEMCInDropNoMac OBJECT-TYPE
   SYNTAX      Counter64
   MAX-ACCESS  read-only
   STATUS      current
   DESCRIPTION
      "Path: vxLanBridgeGroup.performance.pppoEClient.mibCounters.ifInDiscardsNoMacFit

       64 bit unsigned wrappable counter."
   ::= {pr1646v2VxlBGIMVpPPPoEEntry 42270720}

pr1646v2VxlBGIMVpPPPoEMCInDropNUCast OBJECT-TYPE
   SYNTAX      Counter64
   MAX-ACCESS  read-only
   STATUS      current
   DESCRIPTION
      "Path: vxLanBridgeGroup.performance.pppoEClient.mibCounters.ifInDiscardsNUCast

       64 bit unsigned wrappable counter."
   ::= {pr1646v2VxlBGIMVpPPPoEEntry 42467328}

pr1646v2VxlBGIMVpPPPoEMCInDropFilter OBJECT-TYPE
   SYNTAX      Counter64
   MAX-ACCESS  read-only
   STATUS      current
   DESCRIPTION
      "Path: vxLanBridgeGroup.performance.pppoEClient.mibCounters.ifInDiscardsFilter

       64 bit unsigned wrappable counter."
   ::= {pr1646v2VxlBGIMVpPPPoEEntry 42532864}

pr1646v2VxlBGIMVpPPPoEMCInBandwidth15sec OBJECT-TYPE
   SYNTAX      Integer32
   MAX-ACCESS  read-only
   STATUS      current
   DESCRIPTION
      "Path: vxLanBridgeGroup.performance.pppoEClient.mibCounters.ifInBandwidth.15sec

       unit name = bps
       formula = 8 * ; 8 /"
   ::= {pr1646v2VxlBGIMVpPPPoEEntry 45417728}

pr1646v2VxlBGIMVpPPPoEMCInBandwidth30sec OBJECT-TYPE
   SYNTAX      Integer32
   MAX-ACCESS  read-only
   STATUS      current
   DESCRIPTION
      "Path: vxLanBridgeGroup.performance.pppoEClient.mibCounters.ifInBandwidth.30sec

       unit name = bps
       formula = 8 * ; 8 /"
   ::= {pr1646v2VxlBGIMVpPPPoEEntry 45419008}

pr1646v2VxlBGIMVpPPPoEMCInBandwidth1min OBJECT-TYPE
   SYNTAX      Integer32
   MAX-ACCESS  read-only
   STATUS      current
   DESCRIPTION
      "Path: vxLanBridgeGroup.performance.pppoEClient.mibCounters.ifInBandwidth.1min

       unit name = bps
       formula = 8 * ; 8 /"
   ::= {pr1646v2VxlBGIMVpPPPoEEntry 45421568}

pr1646v2VxlBGIMVpPPPoEMCInBandwidth2min OBJECT-TYPE
   SYNTAX      Integer32
   MAX-ACCESS  read-only
   STATUS      current
   DESCRIPTION
      "Path: vxLanBridgeGroup.performance.pppoEClient.mibCounters.ifInBandwidth.2min

       unit name = bps
       formula = 8 * ; 8 /"
   ::= {pr1646v2VxlBGIMVpPPPoEEntry 45426688}

pr1646v2VxlBGIMVpPPPoEMCInBandwidth5min OBJECT-TYPE
   SYNTAX      Integer32
   MAX-ACCESS  read-only
   STATUS      current
   DESCRIPTION
      "Path: vxLanBridgeGroup.performance.pppoEClient.mibCounters.ifInBandwidth.5min

       unit name = bps
       formula = 8 * ; 8 /"
   ::= {pr1646v2VxlBGIMVpPPPoEEntry 45442048}

pr1646v2VxlBGIMVpPPPoEMCOutOctets OBJECT-TYPE
   SYNTAX      Counter64
   MAX-ACCESS  read-only
   STATUS      current
   DESCRIPTION
      "Path: vxLanBridgeGroup.performance.pppoEClient.mibCounters.ifOutOctets

       64 bit unsigned wrappable counter."
   ::= {pr1646v2VxlBGIMVpPPPoEEntry 41091072}

pr1646v2VxlBGIMVpPPPoEMCOutUcastPkts OBJECT-TYPE
   SYNTAX      Counter64
   MAX-ACCESS  read-only
   STATUS      current
   DESCRIPTION
      "Path: vxLanBridgeGroup.performance.pppoEClient.mibCounters.ifOutUcastPkts

       64 bit unsigned wrappable counter."
   ::= {pr1646v2VxlBGIMVpPPPoEEntry 41156608}

pr1646v2VxlBGIMVpPPPoEMCOutNUcastPkts OBJECT-TYPE
   SYNTAX      Counter64
   MAX-ACCESS  read-only
   STATUS      current
   DESCRIPTION
      "Path: vxLanBridgeGroup.performance.pppoEClient.mibCounters.ifOutNUcastPkts

       64 bit unsigned wrappable counter."
   ::= {pr1646v2VxlBGIMVpPPPoEEntry 41222144}

pr1646v2VxlBGIMVpPPPoEMCOutBcastPkts OBJECT-TYPE
   SYNTAX      Counter64
   MAX-ACCESS  read-only
   STATUS      current
   DESCRIPTION
      "Path: vxLanBridgeGroup.performance.pppoEClient.mibCounters.ifOutBcastPkts

       64 bit unsigned wrappable counter."
   ::= {pr1646v2VxlBGIMVpPPPoEEntry 47775744}

pr1646v2VxlBGIMVpPPPoEMCOutMcastPkts OBJECT-TYPE
   SYNTAX      Counter64
   MAX-ACCESS  read-only
   STATUS      current
   DESCRIPTION
      "Path: vxLanBridgeGroup.performance.pppoEClient.mibCounters.ifOutMcastPkts

       64 bit unsigned wrappable counter."
   ::= {pr1646v2VxlBGIMVpPPPoEEntry 48431104}

pr1646v2VxlBGIMVpPPPoEMCOutDiscards OBJECT-TYPE
   SYNTAX      Counter64
   MAX-ACCESS  read-only
   STATUS      current
   DESCRIPTION
      "Path: vxLanBridgeGroup.performance.pppoEClient.mibCounters.ifOutDiscards

       64 bit unsigned wrappable counter."
   ::= {pr1646v2VxlBGIMVpPPPoEEntry 41287680}

pr1646v2VxlBGIMVpPPPoEMCOutErrors OBJECT-TYPE
   SYNTAX      Counter64
   MAX-ACCESS  read-only
   STATUS      current
   DESCRIPTION
      "Path: vxLanBridgeGroup.performance.pppoEClient.mibCounters.ifOutErrors

       64 bit unsigned wrappable counter."
   ::= {pr1646v2VxlBGIMVpPPPoEEntry 41353216}

pr1646v2VxlBGIMVpPPPoEMCOutQLen OBJECT-TYPE
   SYNTAX      Counter32
   MAX-ACCESS  read-only
   STATUS      current
   DESCRIPTION
      "Path: vxLanBridgeGroup.performance.pppoEClient.mibCounters.ifOutQLen

       32 bit unsigned wrappable counter."
   ::= {pr1646v2VxlBGIMVpPPPoEEntry 41418752}

pr1646v2VxlBGIMVpPPPoEMCOutDropEx OBJECT-TYPE
   SYNTAX      Counter64
   MAX-ACCESS  read-only
   STATUS      current
   DESCRIPTION
      "Path: vxLanBridgeGroup.performance.pppoEClient.mibCounters.ifOutDropLevelExceeded

       64 bit unsigned wrappable counter."
   ::= {pr1646v2VxlBGIMVpPPPoEEntry 41484288}

pr1646v2VxlBGIMVpPPPoEMCOutDropNoArp OBJECT-TYPE
   SYNTAX      Counter64
   MAX-ACCESS  read-only
   STATUS      current
   DESCRIPTION
      "Path: vxLanBridgeGroup.performance.pppoEClient.mibCounters.ifOutDiscardsNoArp

       64 bit unsigned wrappable counter."
   ::= {pr1646v2VxlBGIMVpPPPoEEntry 42336256}

pr1646v2VxlBGIMVpPPPoEMCOutDropFilter OBJECT-TYPE
   SYNTAX      Counter64
   MAX-ACCESS  read-only
   STATUS      current
   DESCRIPTION
      "Path: vxLanBridgeGroup.performance.pppoEClient.mibCounters.ifOutDiscardsFilter

       64 bit unsigned wrappable counter."
   ::= {pr1646v2VxlBGIMVpPPPoEEntry 42598400}

pr1646v2VxlBGIMVpPPPoEMCOutBandwidth15sec OBJECT-TYPE
   SYNTAX      Integer32
   MAX-ACCESS  read-only
   STATUS      current
   DESCRIPTION
      "Path: vxLanBridgeGroup.performance.pppoEClient.mibCounters.ifOutBandwidth.15sec

       unit name = bps
       formula = 8 * ; 8 /"
   ::= {pr1646v2VxlBGIMVpPPPoEEntry 45483264}

pr1646v2VxlBGIMVpPPPoEMCOutBandwidth30sec OBJECT-TYPE
   SYNTAX      Integer32
   MAX-ACCESS  read-only
   STATUS      current
   DESCRIPTION
      "Path: vxLanBridgeGroup.performance.pppoEClient.mibCounters.ifOutBandwidth.30sec

       unit name = bps
       formula = 8 * ; 8 /"
   ::= {pr1646v2VxlBGIMVpPPPoEEntry 45484544}

pr1646v2VxlBGIMVpPPPoEMCOutBandwidth1min OBJECT-TYPE
   SYNTAX      Integer32
   MAX-ACCESS  read-only
   STATUS      current
   DESCRIPTION
      "Path: vxLanBridgeGroup.performance.pppoEClient.mibCounters.ifOutBandwidth.1min

       unit name = bps
       formula = 8 * ; 8 /"
   ::= {pr1646v2VxlBGIMVpPPPoEEntry 45487104}

pr1646v2VxlBGIMVpPPPoEMCOutBandwidth2min OBJECT-TYPE
   SYNTAX      Integer32
   MAX-ACCESS  read-only
   STATUS      current
   DESCRIPTION
      "Path: vxLanBridgeGroup.performance.pppoEClient.mibCounters.ifOutBandwidth.2min

       unit name = bps
       formula = 8 * ; 8 /"
   ::= {pr1646v2VxlBGIMVpPPPoEEntry 45492224}

pr1646v2VxlBGIMVpPPPoEMCOutBandwidth5min OBJECT-TYPE
   SYNTAX      Integer32
   MAX-ACCESS  read-only
   STATUS      current
   DESCRIPTION
      "Path: vxLanBridgeGroup.performance.pppoEClient.mibCounters.ifOutBandwidth.5min

       unit name = bps
       formula = 8 * ; 8 /"
   ::= {pr1646v2VxlBGIMVpPPPoEEntry 45507584}

pr1646v2VxlBGIMVpPPPoEPppLinkMonitoringRequestsSent OBJECT-TYPE
   SYNTAX      Gauge32
   MAX-ACCESS  read-only
   STATUS      current
   DESCRIPTION
      "Path: vxLanBridgeGroup.performance.pppoEClient.ppp.linkMonitoring.requestsSent

       32 bit unsigned gauge value."
   ::= {pr1646v2VxlBGIMVpPPPoEEntry 50397440}

pr1646v2VxlBGIMVpPPPoEPppLinkMonitoringRepliesRcvd OBJECT-TYPE
   SYNTAX      Gauge32
   MAX-ACCESS  read-only
   STATUS      current
   DESCRIPTION
      "Path: vxLanBridgeGroup.performance.pppoEClient.ppp.linkMonitoring.repliesRcvd

       32 bit unsigned gauge value."
   ::= {pr1646v2VxlBGIMVpPPPoEEntry 50397696}

pr1646v2VxlBGIMVpPPPoEPppLinkMonitoringRequestsRcvd OBJECT-TYPE
   SYNTAX      Gauge32
   MAX-ACCESS  read-only
   STATUS      current
   DESCRIPTION
      "Path: vxLanBridgeGroup.performance.pppoEClient.ppp.linkMonitoring.requestsRcvd

       32 bit unsigned gauge value."
   ::= {pr1646v2VxlBGIMVpPPPoEEntry 50397952}

pr1646v2VxlBGIMVpPPPoEPppLinkMonitoringRepliesSent OBJECT-TYPE
   SYNTAX      Gauge32
   MAX-ACCESS  read-only
   STATUS      current
   DESCRIPTION
      "Path: vxLanBridgeGroup.performance.pppoEClient.ppp.linkMonitoring.repliesSent

       32 bit unsigned gauge value."
   ::= {pr1646v2VxlBGIMVpPPPoEEntry 50398208}

pr1646v2VxlBGIMVpPPPoEMCH2P OBJECT-TYPE
   SYNTAX      SEQUENCE OF Pr1646v2VxlBGIMVpPPPoEMCH2PEntry
   MAX-ACCESS  not-accessible
   STATUS      current
   DESCRIPTION
      ""
   ::= {pr1646v2VxlBGIMVpPPPoE 41549824}

pr1646v2VxlBGIMVpPPPoEMCH2PEntry OBJECT-TYPE
   SYNTAX      Pr1646v2VxlBGIMVpPPPoEMCH2PEntry
   MAX-ACCESS  not-accessible
   STATUS      current
   DESCRIPTION
      ""
   INDEX      { pr1646v2VxlBGIMVpPPPoEMCH2PGlobalIx,
                pr1646v2VxlBGIMVpPPPoETableIx,
                pr1646v2VxlBGIMVpPPPoEMCH2PTableIx }
   ::= {pr1646v2VxlBGIMVpPPPoEMCH2P 1}

Pr1646v2VxlBGIMVpPPPoEMCH2PEntry ::=
   SEQUENCE
      {
      pr1646v2VxlBGIMVpPPPoEMCH2PGlobalIx
         GlobalIndex,
      pr1646v2VxlBGIMVpPPPoEMCH2PTableIx
         TableIndex,
      pr1646v2VxlBGIMVpPPPoEMCH2PSysUpTime
         TimeTicks,
      pr1646v2VxlBGIMVpPPPoEMCH2PIfUpTime
         TimeTicks,
      pr1646v2VxlBGIMVpPPPoEMCH2PIfStatChanges
         Counter32,
      pr1646v2VxlBGIMVpPPPoEMCH2PIfInOctets
         Counter64,
      pr1646v2VxlBGIMVpPPPoEMCH2PIfInUCPkts
         Counter64,
      pr1646v2VxlBGIMVpPPPoEMCH2PIfInNUCPkts
         Counter64,
      pr1646v2VxlBGIMVpPPPoEMCH2PIfInBCPkts
         Counter64,
      pr1646v2VxlBGIMVpPPPoEMCH2PIfInMCPkts
         Counter64,
      pr1646v2VxlBGIMVpPPPoEMCH2PIfInDiscards
         Counter64,
      pr1646v2VxlBGIMVpPPPoEMCH2PIfInErrors
         Counter64,
      pr1646v2VxlBGIMVpPPPoEMCH2PIfInUnkwn
         Counter64,
      pr1646v2VxlBGIMVpPPPoEMCH2PInDropEx
         Counter64,
      pr1646v2VxlBGIMVpPPPoEMCH2PInDropNoMac
         Counter64,
      pr1646v2VxlBGIMVpPPPoEMCH2PInDropNUCast
         Counter64,
      pr1646v2VxlBGIMVpPPPoEMCH2PInDropFilter
         Counter64,
      pr1646v2VxlBGIMVpPPPoEMCH2PIfInBandwidth
         Integer32,
      pr1646v2VxlBGIMVpPPPoEMCH2PIfOutOctets
         Counter64,
      pr1646v2VxlBGIMVpPPPoEMCH2PIfOutUCPkts
         Counter64,
      pr1646v2VxlBGIMVpPPPoEMCH2PIfOutNUCPkts
         Counter64,
      pr1646v2VxlBGIMVpPPPoEMCH2PIfOutBCPkts
         Counter64,
      pr1646v2VxlBGIMVpPPPoEMCH2PIfOutMCPkts
         Counter64,
      pr1646v2VxlBGIMVpPPPoEMCH2PIfOutDiscards
         Counter64,
      pr1646v2VxlBGIMVpPPPoEMCH2PIfOutErrors
         Counter64,
      pr1646v2VxlBGIMVpPPPoEMCH2POutDropEx
         Counter64,
      pr1646v2VxlBGIMVpPPPoEMCH2POutDropNoArp
         Counter64,
      pr1646v2VxlBGIMVpPPPoEMCH2POutDropFilter
         Counter64,
      pr1646v2VxlBGIMVpPPPoEMCH2PIfOutBandwidth
         Integer32,
      pr1646v2VxlBGIMVpPPPoEMCH2PIfErrSec
         Counter32
      }

pr1646v2VxlBGIMVpPPPoEMCH2PGlobalIx OBJECT-TYPE
   SYNTAX      GlobalIndex
   MAX-ACCESS  not-accessible
   STATUS      current
   DESCRIPTION
      "The value of the tlsCntTreeGlobalIndex of the MANAGED OBJECT."
   ::= {pr1646v2VxlBGIMVpPPPoEMCH2PEntry 10}

pr1646v2VxlBGIMVpPPPoEMCH2PTableIx OBJECT-TYPE
   SYNTAX      TableIndex
   MAX-ACCESS  not-accessible
   STATUS      current
   DESCRIPTION
      ""
   ::= {pr1646v2VxlBGIMVpPPPoEMCH2PEntry 11}

pr1646v2VxlBGIMVpPPPoEMCH2PSysUpTime OBJECT-TYPE
   SYNTAX      TimeTicks
   MAX-ACCESS  read-only
   STATUS      current
   DESCRIPTION
      "Path: vxLanBridgeGroup.performance.pppoEClient.mibCounters.h2Performance.sysUpTime

       Time in centi-second."
   ::= {pr1646v2VxlBGIMVpPPPoEMCH2PEntry 16777216}

pr1646v2VxlBGIMVpPPPoEMCH2PIfUpTime OBJECT-TYPE
   SYNTAX      TimeTicks
   MAX-ACCESS  read-only
   STATUS      current
   DESCRIPTION
      "Path: vxLanBridgeGroup.performance.pppoEClient.mibCounters.h2Performance.ifUpTime

       Time in centi-second."
   ::= {pr1646v2VxlBGIMVpPPPoEMCH2PEntry 33554432}

pr1646v2VxlBGIMVpPPPoEMCH2PIfStatChanges OBJECT-TYPE
   SYNTAX      Counter32
   MAX-ACCESS  read-only
   STATUS      current
   DESCRIPTION
      "Path: vxLanBridgeGroup.performance.pppoEClient.mibCounters.h2Performance.ifStatusChanges

       32 bit unsigned wrappable counter."
   ::= {pr1646v2VxlBGIMVpPPPoEMCH2PEntry 50331648}

pr1646v2VxlBGIMVpPPPoEMCH2PIfInOctets OBJECT-TYPE
   SYNTAX      Counter64
   MAX-ACCESS  read-only
   STATUS      current
   DESCRIPTION
      "Path: vxLanBridgeGroup.performance.pppoEClient.mibCounters.h2Performance.ifInOctets

       64 bit unsigned wrappable counter."
   ::= {pr1646v2VxlBGIMVpPPPoEMCH2PEntry 67108864}

pr1646v2VxlBGIMVpPPPoEMCH2PIfInUCPkts OBJECT-TYPE
   SYNTAX      Counter64
   MAX-ACCESS  read-only
   STATUS      current
   DESCRIPTION
      "Path: vxLanBridgeGroup.performance.pppoEClient.mibCounters.h2Performance.ifInUcastPkts

       64 bit unsigned wrappable counter."
   ::= {pr1646v2VxlBGIMVpPPPoEMCH2PEntry 83886080}

pr1646v2VxlBGIMVpPPPoEMCH2PIfInNUCPkts OBJECT-TYPE
   SYNTAX      Counter64
   MAX-ACCESS  read-only
   STATUS      current
   DESCRIPTION
      "Path: vxLanBridgeGroup.performance.pppoEClient.mibCounters.h2Performance.ifInNUcastPkts

       64 bit unsigned wrappable counter."
   ::= {pr1646v2VxlBGIMVpPPPoEMCH2PEntry 100663296}

pr1646v2VxlBGIMVpPPPoEMCH2PIfInBCPkts OBJECT-TYPE
   SYNTAX      Counter64
   MAX-ACCESS  read-only
   STATUS      current
   DESCRIPTION
      "Path: vxLanBridgeGroup.performance.pppoEClient.mibCounters.h2Performance.ifInBcastPkts

       64 bit unsigned wrappable counter."
   ::= {pr1646v2VxlBGIMVpPPPoEMCH2PEntry 419430400}

pr1646v2VxlBGIMVpPPPoEMCH2PIfInMCPkts OBJECT-TYPE
   SYNTAX      Counter64
   MAX-ACCESS  read-only
   STATUS      current
   DESCRIPTION
      "Path: vxLanBridgeGroup.performance.pppoEClient.mibCounters.h2Performance.ifInMcastPkts

       64 bit unsigned wrappable counter."
   ::= {pr1646v2VxlBGIMVpPPPoEMCH2PEntry 436207616}

pr1646v2VxlBGIMVpPPPoEMCH2PIfInDiscards OBJECT-TYPE
   SYNTAX      Counter64
   MAX-ACCESS  read-only
   STATUS      current
   DESCRIPTION
      "Path: vxLanBridgeGroup.performance.pppoEClient.mibCounters.h2Performance.ifInDiscards

       64 bit unsigned wrappable counter."
   ::= {pr1646v2VxlBGIMVpPPPoEMCH2PEntry 117440512}

pr1646v2VxlBGIMVpPPPoEMCH2PIfInErrors OBJECT-TYPE
   SYNTAX      Counter64
   MAX-ACCESS  read-only
   STATUS      current
   DESCRIPTION
      "Path: vxLanBridgeGroup.performance.pppoEClient.mibCounters.h2Performance.ifInErrors

       64 bit unsigned wrappable counter."
   ::= {pr1646v2VxlBGIMVpPPPoEMCH2PEntry 134217728}

pr1646v2VxlBGIMVpPPPoEMCH2PIfInUnkwn OBJECT-TYPE
   SYNTAX      Counter64
   MAX-ACCESS  read-only
   STATUS      current
   DESCRIPTION
      "Path: vxLanBridgeGroup.performance.pppoEClient.mibCounters.h2Performance.ifInUnknownProtos

       64 bit unsigned wrappable counter."
   ::= {pr1646v2VxlBGIMVpPPPoEMCH2PEntry 150994944}

pr1646v2VxlBGIMVpPPPoEMCH2PInDropEx OBJECT-TYPE
   SYNTAX      Counter64
   MAX-ACCESS  read-only
   STATUS      current
   DESCRIPTION
      "Path: vxLanBridgeGroup.performance.pppoEClient.mibCounters.h2Performance.ifInDropLevelExceeded

       64 bit unsigned wrappable counter."
   ::= {pr1646v2VxlBGIMVpPPPoEMCH2PEntry 335544320}

pr1646v2VxlBGIMVpPPPoEMCH2PInDropNoMac OBJECT-TYPE
   SYNTAX      Counter64
   MAX-ACCESS  read-only
   STATUS      current
   DESCRIPTION
      "Path: vxLanBridgeGroup.performance.pppoEClient.mibCounters.h2Performance.fInDiscardsNoMacFit

       64 bit unsigned wrappable counter."
   ::= {pr1646v2VxlBGIMVpPPPoEMCH2PEntry 301989888}

pr1646v2VxlBGIMVpPPPoEMCH2PInDropNUCast OBJECT-TYPE
   SYNTAX      Counter64
   MAX-ACCESS  read-only
   STATUS      current
   DESCRIPTION
      "Path: vxLanBridgeGroup.performance.pppoEClient.mibCounters.h2Performance.fInDiscardsNUCast

       64 bit unsigned wrappable counter."
   ::= {pr1646v2VxlBGIMVpPPPoEMCH2PEntry 318767104}

pr1646v2VxlBGIMVpPPPoEMCH2PInDropFilter OBJECT-TYPE
   SYNTAX      Counter64
   MAX-ACCESS  read-only
   STATUS      current
   DESCRIPTION
      "Path: vxLanBridgeGroup.performance.pppoEClient.mibCounters.h2Performance.fInDiscardsFilter

       64 bit unsigned wrappable counter."
   ::= {pr1646v2VxlBGIMVpPPPoEMCH2PEntry 385875968}

pr1646v2VxlBGIMVpPPPoEMCH2PIfInBandwidth OBJECT-TYPE
   SYNTAX      Integer32
   MAX-ACCESS  read-only
   STATUS      current
   DESCRIPTION
      "Path: vxLanBridgeGroup.performance.pppoEClient.mibCounters.h2Performance.ifInBandwidth

       unit name = bps
       formula = 8 * ; 8 /"
   ::= {pr1646v2VxlBGIMVpPPPoEMCH2PEntry 268435456}

pr1646v2VxlBGIMVpPPPoEMCH2PIfOutOctets OBJECT-TYPE
   SYNTAX      Counter64
   MAX-ACCESS  read-only
   STATUS      current
   DESCRIPTION
      "Path: vxLanBridgeGroup.performance.pppoEClient.mibCounters.h2Performance.ifOutOctets

       64 bit unsigned wrappable counter."
   ::= {pr1646v2VxlBGIMVpPPPoEMCH2PEntry 167772160}

pr1646v2VxlBGIMVpPPPoEMCH2PIfOutUCPkts OBJECT-TYPE
   SYNTAX      Counter64
   MAX-ACCESS  read-only
   STATUS      current
   DESCRIPTION
      "Path: vxLanBridgeGroup.performance.pppoEClient.mibCounters.h2Performance.ifOutUcastPkts

       64 bit unsigned wrappable counter."
   ::= {pr1646v2VxlBGIMVpPPPoEMCH2PEntry 184549376}

pr1646v2VxlBGIMVpPPPoEMCH2PIfOutNUCPkts OBJECT-TYPE
   SYNTAX      Counter64
   MAX-ACCESS  read-only
   STATUS      current
   DESCRIPTION
      "Path: vxLanBridgeGroup.performance.pppoEClient.mibCounters.h2Performance.ifOutNUcastPkts

       64 bit unsigned wrappable counter."
   ::= {pr1646v2VxlBGIMVpPPPoEMCH2PEntry 201326592}

pr1646v2VxlBGIMVpPPPoEMCH2PIfOutBCPkts OBJECT-TYPE
   SYNTAX      Counter64
   MAX-ACCESS  read-only
   STATUS      current
   DESCRIPTION
      "Path: vxLanBridgeGroup.performance.pppoEClient.mibCounters.h2Performance.ifOutBcastPkts

       64 bit unsigned wrappable counter."
   ::= {pr1646v2VxlBGIMVpPPPoEMCH2PEntry 452984832}

pr1646v2VxlBGIMVpPPPoEMCH2PIfOutMCPkts OBJECT-TYPE
   SYNTAX      Counter64
   MAX-ACCESS  read-only
   STATUS      current
   DESCRIPTION
      "Path: vxLanBridgeGroup.performance.pppoEClient.mibCounters.h2Performance.ifOutMcastPkts

       64 bit unsigned wrappable counter."
   ::= {pr1646v2VxlBGIMVpPPPoEMCH2PEntry 469762048}

pr1646v2VxlBGIMVpPPPoEMCH2PIfOutDiscards OBJECT-TYPE
   SYNTAX      Counter64
   MAX-ACCESS  read-only
   STATUS      current
   DESCRIPTION
      "Path: vxLanBridgeGroup.performance.pppoEClient.mibCounters.h2Performance.ifOutDiscards

       64 bit unsigned wrappable counter."
   ::= {pr1646v2VxlBGIMVpPPPoEMCH2PEntry 218103808}

pr1646v2VxlBGIMVpPPPoEMCH2PIfOutErrors OBJECT-TYPE
   SYNTAX      Counter64
   MAX-ACCESS  read-only
   STATUS      current
   DESCRIPTION
      "Path: vxLanBridgeGroup.performance.pppoEClient.mibCounters.h2Performance.ifOutErrors

       64 bit unsigned wrappable counter."
   ::= {pr1646v2VxlBGIMVpPPPoEMCH2PEntry 234881024}

pr1646v2VxlBGIMVpPPPoEMCH2POutDropEx OBJECT-TYPE
   SYNTAX      Counter64
   MAX-ACCESS  read-only
   STATUS      current
   DESCRIPTION
      "Path: vxLanBridgeGroup.performance.pppoEClient.mibCounters.h2Performance.ifOutDropLevelExceeded

       64 bit unsigned wrappable counter."
   ::= {pr1646v2VxlBGIMVpPPPoEMCH2PEntry 352321536}

pr1646v2VxlBGIMVpPPPoEMCH2POutDropNoArp OBJECT-TYPE
   SYNTAX      Counter64
   MAX-ACCESS  read-only
   STATUS      current
   DESCRIPTION
      "Path: vxLanBridgeGroup.performance.pppoEClient.mibCounters.h2Performance.ifOutDiscardsNoArp

       64 bit unsigned wrappable counter."
   ::= {pr1646v2VxlBGIMVpPPPoEMCH2PEntry 369098752}

pr1646v2VxlBGIMVpPPPoEMCH2POutDropFilter OBJECT-TYPE
   SYNTAX      Counter64
   MAX-ACCESS  read-only
   STATUS      current
   DESCRIPTION
      "Path: vxLanBridgeGroup.performance.pppoEClient.mibCounters.h2Performance.ifOutDiscardsFilter

       64 bit unsigned wrappable counter."
   ::= {pr1646v2VxlBGIMVpPPPoEMCH2PEntry 402653184}

pr1646v2VxlBGIMVpPPPoEMCH2PIfOutBandwidth OBJECT-TYPE
   SYNTAX      Integer32
   MAX-ACCESS  read-only
   STATUS      current
   DESCRIPTION
      "Path: vxLanBridgeGroup.performance.pppoEClient.mibCounters.h2Performance.ifOutBandwidth

       unit name = bps
       formula = 8 * ; 8 /"
   ::= {pr1646v2VxlBGIMVpPPPoEMCH2PEntry 285212672}

pr1646v2VxlBGIMVpPPPoEMCH2PIfErrSec OBJECT-TYPE
   SYNTAX      Counter32
   MAX-ACCESS  read-only
   STATUS      current
   DESCRIPTION
      "Path: vxLanBridgeGroup.performance.pppoEClient.mibCounters.h2Performance.ifErrSec

       32 bit unsigned wrappable counter."
   ::= {pr1646v2VxlBGIMVpPPPoEMCH2PEntry 251658240}

pr1646v2VxlBGIMVpPPPoEMCH24P OBJECT-TYPE
   SYNTAX      SEQUENCE OF Pr1646v2VxlBGIMVpPPPoEMCH24PEntry
   MAX-ACCESS  not-accessible
   STATUS      current
   DESCRIPTION
      ""
   ::= {pr1646v2VxlBGIMVpPPPoE 41615360}

pr1646v2VxlBGIMVpPPPoEMCH24PEntry OBJECT-TYPE
   SYNTAX      Pr1646v2VxlBGIMVpPPPoEMCH24PEntry
   MAX-ACCESS  not-accessible
   STATUS      current
   DESCRIPTION
      ""
   INDEX      { pr1646v2VxlBGIMVpPPPoEMCH24PGlobalIx,
                pr1646v2VxlBGIMVpPPPoETableIx,
                pr1646v2VxlBGIMVpPPPoEMCH24PTableIx }
   ::= {pr1646v2VxlBGIMVpPPPoEMCH24P 1}

Pr1646v2VxlBGIMVpPPPoEMCH24PEntry ::=
   SEQUENCE
      {
      pr1646v2VxlBGIMVpPPPoEMCH24PGlobalIx
         GlobalIndex,
      pr1646v2VxlBGIMVpPPPoEMCH24PTableIx
         TableIndex,
      pr1646v2VxlBGIMVpPPPoEMCH24PSysUpTime
         TimeTicks,
      pr1646v2VxlBGIMVpPPPoEMCH24PIfUpTime
         TimeTicks,
      pr1646v2VxlBGIMVpPPPoEMCH24PIfStatChanges
         Counter32,
      pr1646v2VxlBGIMVpPPPoEMCH24PIfInOctets
         Counter64,
      pr1646v2VxlBGIMVpPPPoEMCH24PIfInUCPkts
         Counter64,
      pr1646v2VxlBGIMVpPPPoEMCH24PIfInNUCPkts
         Counter64,
      pr1646v2VxlBGIMVpPPPoEMCH24PIfInBCPkts
         Counter64,
      pr1646v2VxlBGIMVpPPPoEMCH24PIfInMCPkts
         Counter64,
      pr1646v2VxlBGIMVpPPPoEMCH24PIfInDiscards
         Counter64,
      pr1646v2VxlBGIMVpPPPoEMCH24PIfInErrors
         Counter64,
      pr1646v2VxlBGIMVpPPPoEMCH24PIfInUnkwn
         Counter64,
      pr1646v2VxlBGIMVpPPPoEMCH24PInDropEx
         Counter64,
      pr1646v2VxlBGIMVpPPPoEMCH24PInDropNoMac
         Counter64,
      pr1646v2VxlBGIMVpPPPoEMCH24PInDropNUCast
         Counter64,
      pr1646v2VxlBGIMVpPPPoEMCH24PInDropFilter
         Counter64,
      pr1646v2VxlBGIMVpPPPoEMCH24PIfInBandwidth
         Integer32,
      pr1646v2VxlBGIMVpPPPoEMCH24PIfOutOctets
         Counter64,
      pr1646v2VxlBGIMVpPPPoEMCH24PIfOutUCPkts
         Counter64,
      pr1646v2VxlBGIMVpPPPoEMCH24PIfOutNUCPkts
         Counter64,
      pr1646v2VxlBGIMVpPPPoEMCH24PIfOutBCPkts
         Counter64,
      pr1646v2VxlBGIMVpPPPoEMCH24PIfOutMCPkts
         Counter64,
      pr1646v2VxlBGIMVpPPPoEMCH24PIfOutDiscards
         Counter64,
      pr1646v2VxlBGIMVpPPPoEMCH24PIfOutErrors
         Counter64,
      pr1646v2VxlBGIMVpPPPoEMCH24POutDropEx
         Counter64,
      pr1646v2VxlBGIMVpPPPoEMCH24POutDropNoArp
         Counter64,
      pr1646v2VxlBGIMVpPPPoEMCH24POutDropFilter
         Counter64,
      pr1646v2VxlBGIMVpPPPoEMCH24PIfOutBandwidth
         Integer32,
      pr1646v2VxlBGIMVpPPPoEMCH24PIfErrSec
         Counter32
      }

pr1646v2VxlBGIMVpPPPoEMCH24PGlobalIx OBJECT-TYPE
   SYNTAX      GlobalIndex
   MAX-ACCESS  not-accessible
   STATUS      current
   DESCRIPTION
      "The value of the tlsCntTreeGlobalIndex of the MANAGED OBJECT."
   ::= {pr1646v2VxlBGIMVpPPPoEMCH24PEntry 10}

pr1646v2VxlBGIMVpPPPoEMCH24PTableIx OBJECT-TYPE
   SYNTAX      TableIndex
   MAX-ACCESS  not-accessible
   STATUS      current
   DESCRIPTION
      ""
   ::= {pr1646v2VxlBGIMVpPPPoEMCH24PEntry 11}

pr1646v2VxlBGIMVpPPPoEMCH24PSysUpTime OBJECT-TYPE
   SYNTAX      TimeTicks
   MAX-ACCESS  read-only
   STATUS      current
   DESCRIPTION
      "Path: vxLanBridgeGroup.performance.pppoEClient.mibCounters.h24Performance.sysUpTime

       Time in centi-second."
   ::= {pr1646v2VxlBGIMVpPPPoEMCH24PEntry 16777216}

pr1646v2VxlBGIMVpPPPoEMCH24PIfUpTime OBJECT-TYPE
   SYNTAX      TimeTicks
   MAX-ACCESS  read-only
   STATUS      current
   DESCRIPTION
      "Path: vxLanBridgeGroup.performance.pppoEClient.mibCounters.h24Performance.ifUpTime

       Time in centi-second."
   ::= {pr1646v2VxlBGIMVpPPPoEMCH24PEntry 33554432}

pr1646v2VxlBGIMVpPPPoEMCH24PIfStatChanges OBJECT-TYPE
   SYNTAX      Counter32
   MAX-ACCESS  read-only
   STATUS      current
   DESCRIPTION
      "Path: vxLanBridgeGroup.performance.pppoEClient.mibCounters.h24Performance.ifStatusChanges

       32 bit unsigned wrappable counter."
   ::= {pr1646v2VxlBGIMVpPPPoEMCH24PEntry 50331648}

pr1646v2VxlBGIMVpPPPoEMCH24PIfInOctets OBJECT-TYPE
   SYNTAX      Counter64
   MAX-ACCESS  read-only
   STATUS      current
   DESCRIPTION
      "Path: vxLanBridgeGroup.performance.pppoEClient.mibCounters.h24Performance.ifInOctets

       64 bit unsigned wrappable counter."
   ::= {pr1646v2VxlBGIMVpPPPoEMCH24PEntry 67108864}

pr1646v2VxlBGIMVpPPPoEMCH24PIfInUCPkts OBJECT-TYPE
   SYNTAX      Counter64
   MAX-ACCESS  read-only
   STATUS      current
   DESCRIPTION
      "Path: vxLanBridgeGroup.performance.pppoEClient.mibCounters.h24Performance.ifInUcastPkts

       64 bit unsigned wrappable counter."
   ::= {pr1646v2VxlBGIMVpPPPoEMCH24PEntry 83886080}

pr1646v2VxlBGIMVpPPPoEMCH24PIfInNUCPkts OBJECT-TYPE
   SYNTAX      Counter64
   MAX-ACCESS  read-only
   STATUS      current
   DESCRIPTION
      "Path: vxLanBridgeGroup.performance.pppoEClient.mibCounters.h24Performance.ifInNUcastPkts

       64 bit unsigned wrappable counter."
   ::= {pr1646v2VxlBGIMVpPPPoEMCH24PEntry 100663296}

pr1646v2VxlBGIMVpPPPoEMCH24PIfInBCPkts OBJECT-TYPE
   SYNTAX      Counter64
   MAX-ACCESS  read-only
   STATUS      current
   DESCRIPTION
      "Path: vxLanBridgeGroup.performance.pppoEClient.mibCounters.h24Performance.ifInBcastPkts

       64 bit unsigned wrappable counter."
   ::= {pr1646v2VxlBGIMVpPPPoEMCH24PEntry 419430400}

pr1646v2VxlBGIMVpPPPoEMCH24PIfInMCPkts OBJECT-TYPE
   SYNTAX      Counter64
   MAX-ACCESS  read-only
   STATUS      current
   DESCRIPTION
      "Path: vxLanBridgeGroup.performance.pppoEClient.mibCounters.h24Performance.ifInMcastPkts

       64 bit unsigned wrappable counter."
   ::= {pr1646v2VxlBGIMVpPPPoEMCH24PEntry 436207616}

pr1646v2VxlBGIMVpPPPoEMCH24PIfInDiscards OBJECT-TYPE
   SYNTAX      Counter64
   MAX-ACCESS  read-only
   STATUS      current
   DESCRIPTION
      "Path: vxLanBridgeGroup.performance.pppoEClient.mibCounters.h24Performance.ifInDiscards

       64 bit unsigned wrappable counter."
   ::= {pr1646v2VxlBGIMVpPPPoEMCH24PEntry 117440512}

pr1646v2VxlBGIMVpPPPoEMCH24PIfInErrors OBJECT-TYPE
   SYNTAX      Counter64
   MAX-ACCESS  read-only
   STATUS      current
   DESCRIPTION
      "Path: vxLanBridgeGroup.performance.pppoEClient.mibCounters.h24Performance.ifInErrors

       64 bit unsigned wrappable counter."
   ::= {pr1646v2VxlBGIMVpPPPoEMCH24PEntry 134217728}

pr1646v2VxlBGIMVpPPPoEMCH24PIfInUnkwn OBJECT-TYPE
   SYNTAX      Counter64
   MAX-ACCESS  read-only
   STATUS      current
   DESCRIPTION
      "Path: vxLanBridgeGroup.performance.pppoEClient.mibCounters.h24Performance.ifInUnknownProtos

       64 bit unsigned wrappable counter."
   ::= {pr1646v2VxlBGIMVpPPPoEMCH24PEntry 150994944}

pr1646v2VxlBGIMVpPPPoEMCH24PInDropEx OBJECT-TYPE
   SYNTAX      Counter64
   MAX-ACCESS  read-only
   STATUS      current
   DESCRIPTION
      "Path: vxLanBridgeGroup.performance.pppoEClient.mibCounters.h24Performance.ifInDropLevelExceeded

       64 bit unsigned wrappable counter."
   ::= {pr1646v2VxlBGIMVpPPPoEMCH24PEntry 335544320}

pr1646v2VxlBGIMVpPPPoEMCH24PInDropNoMac OBJECT-TYPE
   SYNTAX      Counter64
   MAX-ACCESS  read-only
   STATUS      current
   DESCRIPTION
      "Path: vxLanBridgeGroup.performance.pppoEClient.mibCounters.h24Performance.fInDiscardsNoMacFit

       64 bit unsigned wrappable counter."
   ::= {pr1646v2VxlBGIMVpPPPoEMCH24PEntry 301989888}

pr1646v2VxlBGIMVpPPPoEMCH24PInDropNUCast OBJECT-TYPE
   SYNTAX      Counter64
   MAX-ACCESS  read-only
   STATUS      current
   DESCRIPTION
      "Path: vxLanBridgeGroup.performance.pppoEClient.mibCounters.h24Performance.fInDiscardsNUCast

       64 bit unsigned wrappable counter."
   ::= {pr1646v2VxlBGIMVpPPPoEMCH24PEntry 318767104}

pr1646v2VxlBGIMVpPPPoEMCH24PInDropFilter OBJECT-TYPE
   SYNTAX      Counter64
   MAX-ACCESS  read-only
   STATUS      current
   DESCRIPTION
      "Path: vxLanBridgeGroup.performance.pppoEClient.mibCounters.h24Performance.fInDiscardsFilter

       64 bit unsigned wrappable counter."
   ::= {pr1646v2VxlBGIMVpPPPoEMCH24PEntry 385875968}

pr1646v2VxlBGIMVpPPPoEMCH24PIfInBandwidth OBJECT-TYPE
   SYNTAX      Integer32
   MAX-ACCESS  read-only
   STATUS      current
   DESCRIPTION
      "Path: vxLanBridgeGroup.performance.pppoEClient.mibCounters.h24Performance.ifInBandwidth

       unit name = bps
       formula = 8 * ; 8 /"
   ::= {pr1646v2VxlBGIMVpPPPoEMCH24PEntry 268435456}

pr1646v2VxlBGIMVpPPPoEMCH24PIfOutOctets OBJECT-TYPE
   SYNTAX      Counter64
   MAX-ACCESS  read-only
   STATUS      current
   DESCRIPTION
      "Path: vxLanBridgeGroup.performance.pppoEClient.mibCounters.h24Performance.ifOutOctets

       64 bit unsigned wrappable counter."
   ::= {pr1646v2VxlBGIMVpPPPoEMCH24PEntry 167772160}

pr1646v2VxlBGIMVpPPPoEMCH24PIfOutUCPkts OBJECT-TYPE
   SYNTAX      Counter64
   MAX-ACCESS  read-only
   STATUS      current
   DESCRIPTION
      "Path: vxLanBridgeGroup.performance.pppoEClient.mibCounters.h24Performance.ifOutUcastPkts

       64 bit unsigned wrappable counter."
   ::= {pr1646v2VxlBGIMVpPPPoEMCH24PEntry 184549376}

pr1646v2VxlBGIMVpPPPoEMCH24PIfOutNUCPkts OBJECT-TYPE
   SYNTAX      Counter64
   MAX-ACCESS  read-only
   STATUS      current
   DESCRIPTION
      "Path: vxLanBridgeGroup.performance.pppoEClient.mibCounters.h24Performance.ifOutNUcastPkts

       64 bit unsigned wrappable counter."
   ::= {pr1646v2VxlBGIMVpPPPoEMCH24PEntry 201326592}

pr1646v2VxlBGIMVpPPPoEMCH24PIfOutBCPkts OBJECT-TYPE
   SYNTAX      Counter64
   MAX-ACCESS  read-only
   STATUS      current
   DESCRIPTION
      "Path: vxLanBridgeGroup.performance.pppoEClient.mibCounters.h24Performance.ifOutBcastPkts

       64 bit unsigned wrappable counter."
   ::= {pr1646v2VxlBGIMVpPPPoEMCH24PEntry 452984832}

pr1646v2VxlBGIMVpPPPoEMCH24PIfOutMCPkts OBJECT-TYPE
   SYNTAX      Counter64
   MAX-ACCESS  read-only
   STATUS      current
   DESCRIPTION
      "Path: vxLanBridgeGroup.performance.pppoEClient.mibCounters.h24Performance.ifOutMcastPkts

       64 bit unsigned wrappable counter."
   ::= {pr1646v2VxlBGIMVpPPPoEMCH24PEntry 469762048}

pr1646v2VxlBGIMVpPPPoEMCH24PIfOutDiscards OBJECT-TYPE
   SYNTAX      Counter64
   MAX-ACCESS  read-only
   STATUS      current
   DESCRIPTION
      "Path: vxLanBridgeGroup.performance.pppoEClient.mibCounters.h24Performance.ifOutDiscards

       64 bit unsigned wrappable counter."
   ::= {pr1646v2VxlBGIMVpPPPoEMCH24PEntry 218103808}

pr1646v2VxlBGIMVpPPPoEMCH24PIfOutErrors OBJECT-TYPE
   SYNTAX      Counter64
   MAX-ACCESS  read-only
   STATUS      current
   DESCRIPTION
      "Path: vxLanBridgeGroup.performance.pppoEClient.mibCounters.h24Performance.ifOutErrors

       64 bit unsigned wrappable counter."
   ::= {pr1646v2VxlBGIMVpPPPoEMCH24PEntry 234881024}

pr1646v2VxlBGIMVpPPPoEMCH24POutDropEx OBJECT-TYPE
   SYNTAX      Counter64
   MAX-ACCESS  read-only
   STATUS      current
   DESCRIPTION
      "Path: vxLanBridgeGroup.performance.pppoEClient.mibCounters.h24Performance.ifOutDropLevelExceeded

       64 bit unsigned wrappable counter."
   ::= {pr1646v2VxlBGIMVpPPPoEMCH24PEntry 352321536}

pr1646v2VxlBGIMVpPPPoEMCH24POutDropNoArp OBJECT-TYPE
   SYNTAX      Counter64
   MAX-ACCESS  read-only
   STATUS      current
   DESCRIPTION
      "Path: vxLanBridgeGroup.performance.pppoEClient.mibCounters.h24Performance.ifOutDiscardsNoArp

       64 bit unsigned wrappable counter."
   ::= {pr1646v2VxlBGIMVpPPPoEMCH24PEntry 369098752}

pr1646v2VxlBGIMVpPPPoEMCH24POutDropFilter OBJECT-TYPE
   SYNTAX      Counter64
   MAX-ACCESS  read-only
   STATUS      current
   DESCRIPTION
      "Path: vxLanBridgeGroup.performance.pppoEClient.mibCounters.h24Performance.ifOutDiscardsFilter

       64 bit unsigned wrappable counter."
   ::= {pr1646v2VxlBGIMVpPPPoEMCH24PEntry 402653184}

pr1646v2VxlBGIMVpPPPoEMCH24PIfOutBandwidth OBJECT-TYPE
   SYNTAX      Integer32
   MAX-ACCESS  read-only
   STATUS      current
   DESCRIPTION
      "Path: vxLanBridgeGroup.performance.pppoEClient.mibCounters.h24Performance.ifOutBandwidth

       unit name = bps
       formula = 8 * ; 8 /"
   ::= {pr1646v2VxlBGIMVpPPPoEMCH24PEntry 285212672}

pr1646v2VxlBGIMVpPPPoEMCH24PIfErrSec OBJECT-TYPE
   SYNTAX      Counter32
   MAX-ACCESS  read-only
   STATUS      current
   DESCRIPTION
      "Path: vxLanBridgeGroup.performance.pppoEClient.mibCounters.h24Performance.ifErrSec

       32 bit unsigned wrappable counter."
   ::= {pr1646v2VxlBGIMVpPPPoEMCH24PEntry 251658240}

pr1646v2VxlBGIMVpPPPoEMCD7P OBJECT-TYPE
   SYNTAX      SEQUENCE OF Pr1646v2VxlBGIMVpPPPoEMCD7PEntry
   MAX-ACCESS  not-accessible
   STATUS      current
   DESCRIPTION
      ""
   ::= {pr1646v2VxlBGIMVpPPPoE 41680896}

pr1646v2VxlBGIMVpPPPoEMCD7PEntry OBJECT-TYPE
   SYNTAX      Pr1646v2VxlBGIMVpPPPoEMCD7PEntry
   MAX-ACCESS  not-accessible
   STATUS      current
   DESCRIPTION
      ""
   INDEX      { pr1646v2VxlBGIMVpPPPoEMCD7PGlobalIx,
                pr1646v2VxlBGIMVpPPPoETableIx,
                pr1646v2VxlBGIMVpPPPoEMCD7PTableIx }
   ::= {pr1646v2VxlBGIMVpPPPoEMCD7P 1}

Pr1646v2VxlBGIMVpPPPoEMCD7PEntry ::=
   SEQUENCE
      {
      pr1646v2VxlBGIMVpPPPoEMCD7PGlobalIx
         GlobalIndex,
      pr1646v2VxlBGIMVpPPPoEMCD7PTableIx
         TableIndex,
      pr1646v2VxlBGIMVpPPPoEMCD7PSysUpTime
         TimeTicks,
      pr1646v2VxlBGIMVpPPPoEMCD7PIfUpTime
         TimeTicks,
      pr1646v2VxlBGIMVpPPPoEMCD7PIfStatChanges
         Counter32,
      pr1646v2VxlBGIMVpPPPoEMCD7PIfInOctets
         Counter64,
      pr1646v2VxlBGIMVpPPPoEMCD7PIfInUCPkts
         Counter64,
      pr1646v2VxlBGIMVpPPPoEMCD7PIfInNUCPkts
         Counter64,
      pr1646v2VxlBGIMVpPPPoEMCD7PIfInBCPkts
         Counter64,
      pr1646v2VxlBGIMVpPPPoEMCD7PIfInMCPkts
         Counter64,
      pr1646v2VxlBGIMVpPPPoEMCD7PIfInDiscards
         Counter64,
      pr1646v2VxlBGIMVpPPPoEMCD7PIfInErrors
         Counter64,
      pr1646v2VxlBGIMVpPPPoEMCD7PIfInUnkwn
         Counter64,
      pr1646v2VxlBGIMVpPPPoEMCD7PInDropEx
         Counter64,
      pr1646v2VxlBGIMVpPPPoEMCD7PInDropNoMac
         Counter64,
      pr1646v2VxlBGIMVpPPPoEMCD7PInDropNUCast
         Counter64,
      pr1646v2VxlBGIMVpPPPoEMCD7PInDropFilter
         Counter64,
      pr1646v2VxlBGIMVpPPPoEMCD7PIfInBandwidth
         Integer32,
      pr1646v2VxlBGIMVpPPPoEMCD7PIfOutOctets
         Counter64,
      pr1646v2VxlBGIMVpPPPoEMCD7PIfOutUCPkts
         Counter64,
      pr1646v2VxlBGIMVpPPPoEMCD7PIfOutNUCPkts
         Counter64,
      pr1646v2VxlBGIMVpPPPoEMCD7PIfOutBCPkts
         Counter64,
      pr1646v2VxlBGIMVpPPPoEMCD7PIfOutMCPkts
         Counter64,
      pr1646v2VxlBGIMVpPPPoEMCD7PIfOutDiscards
         Counter64,
      pr1646v2VxlBGIMVpPPPoEMCD7PIfOutErrors
         Counter64,
      pr1646v2VxlBGIMVpPPPoEMCD7POutDropEx
         Counter64,
      pr1646v2VxlBGIMVpPPPoEMCD7POutDropNoArp
         Counter64,
      pr1646v2VxlBGIMVpPPPoEMCD7POutDropFilter
         Counter64,
      pr1646v2VxlBGIMVpPPPoEMCD7PIfOutBandwidth
         Integer32,
      pr1646v2VxlBGIMVpPPPoEMCD7PIfErrSec
         Counter32
      }

pr1646v2VxlBGIMVpPPPoEMCD7PGlobalIx OBJECT-TYPE
   SYNTAX      GlobalIndex
   MAX-ACCESS  not-accessible
   STATUS      current
   DESCRIPTION
      "The value of the tlsCntTreeGlobalIndex of the MANAGED OBJECT."
   ::= {pr1646v2VxlBGIMVpPPPoEMCD7PEntry 10}

pr1646v2VxlBGIMVpPPPoEMCD7PTableIx OBJECT-TYPE
   SYNTAX      TableIndex
   MAX-ACCESS  not-accessible
   STATUS      current
   DESCRIPTION
      ""
   ::= {pr1646v2VxlBGIMVpPPPoEMCD7PEntry 11}

pr1646v2VxlBGIMVpPPPoEMCD7PSysUpTime OBJECT-TYPE
   SYNTAX      TimeTicks
   MAX-ACCESS  read-only
   STATUS      current
   DESCRIPTION
      "Path: vxLanBridgeGroup.performance.pppoEClient.mibCounters.d7Performance.sysUpTime

       Time in centi-second."
   ::= {pr1646v2VxlBGIMVpPPPoEMCD7PEntry 16777216}

pr1646v2VxlBGIMVpPPPoEMCD7PIfUpTime OBJECT-TYPE
   SYNTAX      TimeTicks
   MAX-ACCESS  read-only
   STATUS      current
   DESCRIPTION
      "Path: vxLanBridgeGroup.performance.pppoEClient.mibCounters.d7Performance.ifUpTime

       Time in centi-second."
   ::= {pr1646v2VxlBGIMVpPPPoEMCD7PEntry 33554432}

pr1646v2VxlBGIMVpPPPoEMCD7PIfStatChanges OBJECT-TYPE
   SYNTAX      Counter32
   MAX-ACCESS  read-only
   STATUS      current
   DESCRIPTION
      "Path: vxLanBridgeGroup.performance.pppoEClient.mibCounters.d7Performance.ifStatusChanges

       32 bit unsigned wrappable counter."
   ::= {pr1646v2VxlBGIMVpPPPoEMCD7PEntry 50331648}

pr1646v2VxlBGIMVpPPPoEMCD7PIfInOctets OBJECT-TYPE
   SYNTAX      Counter64
   MAX-ACCESS  read-only
   STATUS      current
   DESCRIPTION
      "Path: vxLanBridgeGroup.performance.pppoEClient.mibCounters.d7Performance.ifInOctets

       64 bit unsigned wrappable counter."
   ::= {pr1646v2VxlBGIMVpPPPoEMCD7PEntry 67108864}

pr1646v2VxlBGIMVpPPPoEMCD7PIfInUCPkts OBJECT-TYPE
   SYNTAX      Counter64
   MAX-ACCESS  read-only
   STATUS      current
   DESCRIPTION
      "Path: vxLanBridgeGroup.performance.pppoEClient.mibCounters.d7Performance.ifInUcastPkts

       64 bit unsigned wrappable counter."
   ::= {pr1646v2VxlBGIMVpPPPoEMCD7PEntry 83886080}

pr1646v2VxlBGIMVpPPPoEMCD7PIfInNUCPkts OBJECT-TYPE
   SYNTAX      Counter64
   MAX-ACCESS  read-only
   STATUS      current
   DESCRIPTION
      "Path: vxLanBridgeGroup.performance.pppoEClient.mibCounters.d7Performance.ifInNUcastPkts

       64 bit unsigned wrappable counter."
   ::= {pr1646v2VxlBGIMVpPPPoEMCD7PEntry 100663296}

pr1646v2VxlBGIMVpPPPoEMCD7PIfInBCPkts OBJECT-TYPE
   SYNTAX      Counter64
   MAX-ACCESS  read-only
   STATUS      current
   DESCRIPTION
      "Path: vxLanBridgeGroup.performance.pppoEClient.mibCounters.d7Performance.ifInBcastPkts

       64 bit unsigned wrappable counter."
   ::= {pr1646v2VxlBGIMVpPPPoEMCD7PEntry 419430400}

pr1646v2VxlBGIMVpPPPoEMCD7PIfInMCPkts OBJECT-TYPE
   SYNTAX      Counter64
   MAX-ACCESS  read-only
   STATUS      current
   DESCRIPTION
      "Path: vxLanBridgeGroup.performance.pppoEClient.mibCounters.d7Performance.ifInMcastPkts

       64 bit unsigned wrappable counter."
   ::= {pr1646v2VxlBGIMVpPPPoEMCD7PEntry 436207616}

pr1646v2VxlBGIMVpPPPoEMCD7PIfInDiscards OBJECT-TYPE
   SYNTAX      Counter64
   MAX-ACCESS  read-only
   STATUS      current
   DESCRIPTION
      "Path: vxLanBridgeGroup.performance.pppoEClient.mibCounters.d7Performance.ifInDiscards

       64 bit unsigned wrappable counter."
   ::= {pr1646v2VxlBGIMVpPPPoEMCD7PEntry 117440512}

pr1646v2VxlBGIMVpPPPoEMCD7PIfInErrors OBJECT-TYPE
   SYNTAX      Counter64
   MAX-ACCESS  read-only
   STATUS      current
   DESCRIPTION
      "Path: vxLanBridgeGroup.performance.pppoEClient.mibCounters.d7Performance.ifInErrors

       64 bit unsigned wrappable counter."
   ::= {pr1646v2VxlBGIMVpPPPoEMCD7PEntry 134217728}

pr1646v2VxlBGIMVpPPPoEMCD7PIfInUnkwn OBJECT-TYPE
   SYNTAX      Counter64
   MAX-ACCESS  read-only
   STATUS      current
   DESCRIPTION
      "Path: vxLanBridgeGroup.performance.pppoEClient.mibCounters.d7Performance.ifInUnknownProtos

       64 bit unsigned wrappable counter."
   ::= {pr1646v2VxlBGIMVpPPPoEMCD7PEntry 150994944}

pr1646v2VxlBGIMVpPPPoEMCD7PInDropEx OBJECT-TYPE
   SYNTAX      Counter64
   MAX-ACCESS  read-only
   STATUS      current
   DESCRIPTION
      "Path: vxLanBridgeGroup.performance.pppoEClient.mibCounters.d7Performance.ifInDropLevelExceeded

       64 bit unsigned wrappable counter."
   ::= {pr1646v2VxlBGIMVpPPPoEMCD7PEntry 335544320}

pr1646v2VxlBGIMVpPPPoEMCD7PInDropNoMac OBJECT-TYPE
   SYNTAX      Counter64
   MAX-ACCESS  read-only
   STATUS      current
   DESCRIPTION
      "Path: vxLanBridgeGroup.performance.pppoEClient.mibCounters.d7Performance.fInDiscardsNoMacFit

       64 bit unsigned wrappable counter."
   ::= {pr1646v2VxlBGIMVpPPPoEMCD7PEntry 301989888}

pr1646v2VxlBGIMVpPPPoEMCD7PInDropNUCast OBJECT-TYPE
   SYNTAX      Counter64
   MAX-ACCESS  read-only
   STATUS      current
   DESCRIPTION
      "Path: vxLanBridgeGroup.performance.pppoEClient.mibCounters.d7Performance.fInDiscardsNUCast

       64 bit unsigned wrappable counter."
   ::= {pr1646v2VxlBGIMVpPPPoEMCD7PEntry 318767104}

pr1646v2VxlBGIMVpPPPoEMCD7PInDropFilter OBJECT-TYPE
   SYNTAX      Counter64
   MAX-ACCESS  read-only
   STATUS      current
   DESCRIPTION
      "Path: vxLanBridgeGroup.performance.pppoEClient.mibCounters.d7Performance.fInDiscardsFilter

       64 bit unsigned wrappable counter."
   ::= {pr1646v2VxlBGIMVpPPPoEMCD7PEntry 385875968}

pr1646v2VxlBGIMVpPPPoEMCD7PIfInBandwidth OBJECT-TYPE
   SYNTAX      Integer32
   MAX-ACCESS  read-only
   STATUS      current
   DESCRIPTION
      "Path: vxLanBridgeGroup.performance.pppoEClient.mibCounters.d7Performance.ifInBandwidth

       unit name = bps
       formula = 8 * ; 8 /"
   ::= {pr1646v2VxlBGIMVpPPPoEMCD7PEntry 268435456}

pr1646v2VxlBGIMVpPPPoEMCD7PIfOutOctets OBJECT-TYPE
   SYNTAX      Counter64
   MAX-ACCESS  read-only
   STATUS      current
   DESCRIPTION
      "Path: vxLanBridgeGroup.performance.pppoEClient.mibCounters.d7Performance.ifOutOctets

       64 bit unsigned wrappable counter."
   ::= {pr1646v2VxlBGIMVpPPPoEMCD7PEntry 167772160}

pr1646v2VxlBGIMVpPPPoEMCD7PIfOutUCPkts OBJECT-TYPE
   SYNTAX      Counter64
   MAX-ACCESS  read-only
   STATUS      current
   DESCRIPTION
      "Path: vxLanBridgeGroup.performance.pppoEClient.mibCounters.d7Performance.ifOutUcastPkts

       64 bit unsigned wrappable counter."
   ::= {pr1646v2VxlBGIMVpPPPoEMCD7PEntry 184549376}

pr1646v2VxlBGIMVpPPPoEMCD7PIfOutNUCPkts OBJECT-TYPE
   SYNTAX      Counter64
   MAX-ACCESS  read-only
   STATUS      current
   DESCRIPTION
      "Path: vxLanBridgeGroup.performance.pppoEClient.mibCounters.d7Performance.ifOutNUcastPkts

       64 bit unsigned wrappable counter."
   ::= {pr1646v2VxlBGIMVpPPPoEMCD7PEntry 201326592}

pr1646v2VxlBGIMVpPPPoEMCD7PIfOutBCPkts OBJECT-TYPE
   SYNTAX      Counter64
   MAX-ACCESS  read-only
   STATUS      current
   DESCRIPTION
      "Path: vxLanBridgeGroup.performance.pppoEClient.mibCounters.d7Performance.ifOutBcastPkts

       64 bit unsigned wrappable counter."
   ::= {pr1646v2VxlBGIMVpPPPoEMCD7PEntry 452984832}

pr1646v2VxlBGIMVpPPPoEMCD7PIfOutMCPkts OBJECT-TYPE
   SYNTAX      Counter64
   MAX-ACCESS  read-only
   STATUS      current
   DESCRIPTION
      "Path: vxLanBridgeGroup.performance.pppoEClient.mibCounters.d7Performance.ifOutMcastPkts

       64 bit unsigned wrappable counter."
   ::= {pr1646v2VxlBGIMVpPPPoEMCD7PEntry 469762048}

pr1646v2VxlBGIMVpPPPoEMCD7PIfOutDiscards OBJECT-TYPE
   SYNTAX      Counter64
   MAX-ACCESS  read-only
   STATUS      current
   DESCRIPTION
      "Path: vxLanBridgeGroup.performance.pppoEClient.mibCounters.d7Performance.ifOutDiscards

       64 bit unsigned wrappable counter."
   ::= {pr1646v2VxlBGIMVpPPPoEMCD7PEntry 218103808}

pr1646v2VxlBGIMVpPPPoEMCD7PIfOutErrors OBJECT-TYPE
   SYNTAX      Counter64
   MAX-ACCESS  read-only
   STATUS      current
   DESCRIPTION
      "Path: vxLanBridgeGroup.performance.pppoEClient.mibCounters.d7Performance.ifOutErrors

       64 bit unsigned wrappable counter."
   ::= {pr1646v2VxlBGIMVpPPPoEMCD7PEntry 234881024}

pr1646v2VxlBGIMVpPPPoEMCD7POutDropEx OBJECT-TYPE
   SYNTAX      Counter64
   MAX-ACCESS  read-only
   STATUS      current
   DESCRIPTION
      "Path: vxLanBridgeGroup.performance.pppoEClient.mibCounters.d7Performance.ifOutDropLevelExceeded

       64 bit unsigned wrappable counter."
   ::= {pr1646v2VxlBGIMVpPPPoEMCD7PEntry 352321536}

pr1646v2VxlBGIMVpPPPoEMCD7POutDropNoArp OBJECT-TYPE
   SYNTAX      Counter64
   MAX-ACCESS  read-only
   STATUS      current
   DESCRIPTION
      "Path: vxLanBridgeGroup.performance.pppoEClient.mibCounters.d7Performance.ifOutDiscardsNoArp

       64 bit unsigned wrappable counter."
   ::= {pr1646v2VxlBGIMVpPPPoEMCD7PEntry 369098752}

pr1646v2VxlBGIMVpPPPoEMCD7POutDropFilter OBJECT-TYPE
   SYNTAX      Counter64
   MAX-ACCESS  read-only
   STATUS      current
   DESCRIPTION
      "Path: vxLanBridgeGroup.performance.pppoEClient.mibCounters.d7Performance.ifOutDiscardsFilter

       64 bit unsigned wrappable counter."
   ::= {pr1646v2VxlBGIMVpPPPoEMCD7PEntry 402653184}

pr1646v2VxlBGIMVpPPPoEMCD7PIfOutBandwidth OBJECT-TYPE
   SYNTAX      Integer32
   MAX-ACCESS  read-only
   STATUS      current
   DESCRIPTION
      "Path: vxLanBridgeGroup.performance.pppoEClient.mibCounters.d7Performance.ifOutBandwidth

       unit name = bps
       formula = 8 * ; 8 /"
   ::= {pr1646v2VxlBGIMVpPPPoEMCD7PEntry 285212672}

pr1646v2VxlBGIMVpPPPoEMCD7PIfErrSec OBJECT-TYPE
   SYNTAX      Counter32
   MAX-ACCESS  read-only
   STATUS      current
   DESCRIPTION
      "Path: vxLanBridgeGroup.performance.pppoEClient.mibCounters.d7Performance.ifErrSec

       32 bit unsigned wrappable counter."
   ::= {pr1646v2VxlBGIMVpPPPoEMCD7PEntry 251658240}


pr1646v2VxlBGIMVpBridgeCache OBJECT IDENTIFIER ::= {pr1646v2VxlBGIMVp 6}

pr1646v2VxlBGIMVpBridgeCacheSSCTable OBJECT-TYPE
   SYNTAX      SEQUENCE OF Pr1646v2VxlBGIMVpBridgeCacheEntry
   MAX-ACCESS  not-accessible
   STATUS      current
   DESCRIPTION
      "cache entry performance"
   ::= {pr1646v2VxlBGIMVpBridgeCache 1}

pr1646v2VxlBGIMVpBridgeCacheEntry OBJECT-TYPE
   SYNTAX      Pr1646v2VxlBGIMVpBridgeCacheEntry
   MAX-ACCESS  not-accessible
   STATUS      current
   DESCRIPTION
      ""
   INDEX      { pr1646v2VxlBGIMVpBridgeCacheGlobalIx,
                pr1646v2VxlBGIMVpBridgeCacheTableIx }
   ::= {pr1646v2VxlBGIMVpBridgeCacheSSCTable 1}

Pr1646v2VxlBGIMVpBridgeCacheEntry ::=
   SEQUENCE
      {
      pr1646v2VxlBGIMVpBridgeCacheGlobalIx
         GlobalIndex,
      pr1646v2VxlBGIMVpBridgeCacheTableIx
         TableIndex,
      pr1646v2VxlBGIMVpBridgeCacheIf
         DisplayString,
      pr1646v2VxlBGIMVpBridgeCacheMacAddress
         OCTET STRING,
      pr1646v2VxlBGIMVpBridgeCacheVteAddress
         IpAddress,
      pr1646v2VxlBGIMVpBridgeCacheVni
         Integer32,
      pr1646v2VxlBGIMVpBridgeCacheTpid
         INTEGER,
      pr1646v2VxlBGIMVpBridgeCacheVlanId
         INTEGER,
      pr1646v2VxlBGIMVpBridgeCacheTpid2
         INTEGER,
      pr1646v2VxlBGIMVpBridgeCacheVlanId2
         INTEGER,
      pr1646v2VxlBGIMVpBridgeCacheType
         INTEGER,
      pr1646v2VxlBGIMVpBridgeCacheRxPkts
         Counter32,
      pr1646v2VxlBGIMVpBridgeCacheTxPkts
         Counter32,
      pr1646v2VxlBGIMVpBridgeCacheStatViols
         Counter32,
      pr1646v2VxlBGIMVpBridgeCacheRelearns
         Counter32,
      pr1646v2VxlBGIMVpBridgeCacheRelearnDrops
         Counter32,
      pr1646v2VxlBGIMVpBridgeCacheVteRelearns
         Counter32
      }

pr1646v2VxlBGIMVpBridgeCacheGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgeCacheEntry 10}

pr1646v2VxlBGIMVpBridgeCacheTableIx OBJECT-TYPE
   SYNTAX      TableIndex
   MAX-ACCESS  not-accessible
   STATUS      current
   DESCRIPTION
      ""
   ::= {pr1646v2VxlBGIMVpBridgeCacheEntry 11}

pr1646v2VxlBGIMVpBridgeCacheIf OBJECT-TYPE
   SYNTAX      DisplayString
   MAX-ACCESS  read-only
   STATUS      current
   DESCRIPTION
      "Path: vxLanBridgeGroup.performance.bridgeCache.interface"
   ::= {pr1646v2VxlBGIMVpBridgeCacheEntry 16777216}

pr1646v2VxlBGIMVpBridgeCacheMacAddress OBJECT-TYPE
   SYNTAX      OCTET STRING
   MAX-ACCESS  read-only
   STATUS      current
   DESCRIPTION
      "Path: vxLanBridgeGroup.performance.bridgeCache.macAddress

       MAC address."
   ::= {pr1646v2VxlBGIMVpBridgeCacheEntry 33554432}

pr1646v2VxlBGIMVpBridgeCacheVteAddress OBJECT-TYPE
   SYNTAX      IpAddress
   MAX-ACCESS  read-only
   STATUS      current
   DESCRIPTION
      "Path: vxLanBridgeGroup.performance.bridgeCache.vteAddress"
   ::= {pr1646v2VxlBGIMVpBridgeCacheEntry 167772160}

pr1646v2VxlBGIMVpBridgeCacheVni OBJECT-TYPE
   SYNTAX      Integer32
   MAX-ACCESS  read-only
   STATUS      current
   DESCRIPTION
      "Path: vxLanBridgeGroup.performance.bridgeCache.vni"
   ::= {pr1646v2VxlBGIMVpBridgeCacheEntry 201326592}

pr1646v2VxlBGIMVpBridgeCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vxLanBridgeGroup.performance.bridgeCache.tpid

       Possibilities:
               untagged   (0)
               dot1q   (33024)
               dot1ad   (34984)
               group   (65534)
               notUsed   (65535)
               dot1qOrDot1ad   (65536)"
   ::= {pr1646v2VxlBGIMVpBridgeCacheEntry 335544320}

pr1646v2VxlBGIMVpBridgeCacheVlanId OBJECT-TYPE
   SYNTAX      INTEGER
               {
               undefined (-1)
               }
   MAX-ACCESS  read-only
   STATUS      current
   DESCRIPTION
      "Path: vxLanBridgeGroup.performance.bridgeCache.vlanId

       Possibilities:
               undefined   (-1)"
   ::= {pr1646v2VxlBGIMVpBridgeCacheEntry 50331648}

pr1646v2VxlBGIMVpBridgeCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vxLanBridgeGroup.performance.bridgeCache.tpid2

       Possibilities:
               untagged   (0)
               dot1q   (33024)
               dot1ad   (34984)
               group   (65534)
               notUsed   (65535)
               dot1qOrDot1ad   (65536)"
   ::= {pr1646v2VxlBGIMVpBridgeCacheEntry 369098752}

pr1646v2VxlBGIMVpBridgeCacheVlanId2 OBJECT-TYPE
   SYNTAX      INTEGER
               {
               undefined (-1)
               }
   MAX-ACCESS  read-only
   STATUS      current
   DESCRIPTION
      "Path: vxLanBridgeGroup.performance.bridgeCache.vlanId2

       Possibilities:
               undefined   (-1)"
   ::= {pr1646v2VxlBGIMVpBridgeCacheEntry 385875968}

pr1646v2VxlBGIMVpBridgeCacheType OBJECT-TYPE
   SYNTAX      INTEGER
               {
               static (0),
               dynamic (1),
               tester (2),
               fastFlood (3)
               }
   MAX-ACCESS  read-only
   STATUS      current
   DESCRIPTION
      "Path: vxLanBridgeGroup.performance.bridgeCache.type

       Possibilities:
               static   (0)
               dynamic   (1)
               tester   (2)
               fastFlood   (3)"
   ::= {pr1646v2VxlBGIMVpBridgeCacheEntry 352321536}

pr1646v2VxlBGIMVpBridgeCacheRxPkts OBJECT-TYPE
   SYNTAX      Counter32
   MAX-ACCESS  read-only
   STATUS      current
   DESCRIPTION
      "Path: vxLanBridgeGroup.performance.bridgeCache.rxPkts

       32 bit unsigned wrappable counter."
   ::= {pr1646v2VxlBGIMVpBridgeCacheEntry 83886080}

pr1646v2VxlBGIMVpBridgeCacheTxPkts OBJECT-TYPE
   SYNTAX      Counter32
   MAX-ACCESS  read-only
   STATUS      current
   DESCRIPTION
      "Path: vxLanBridgeGroup.performance.bridgeCache.txPkts

       32 bit unsigned wrappable counter."
   ::= {pr1646v2VxlBGIMVpBridgeCacheEntry 100663296}

pr1646v2VxlBGIMVpBridgeCacheStatViols OBJECT-TYPE
   SYNTAX      Counter32
   MAX-ACCESS  read-only
   STATUS      current
   DESCRIPTION
      "Path: vxLanBridgeGroup.performance.bridgeCache.staticViolations

       32 bit unsigned wrappable counter."
   ::= {pr1646v2VxlBGIMVpBridgeCacheEntry 117440512}

pr1646v2VxlBGIMVpBridgeCacheRelearns OBJECT-TYPE
   SYNTAX      Counter32
   MAX-ACCESS  read-only
   STATUS      current
   DESCRIPTION
      "Path: vxLanBridgeGroup.performance.bridgeCache.relearns

       32 bit unsigned wrappable counter."
   ::= {pr1646v2VxlBGIMVpBridgeCacheEntry 134217728}

pr1646v2VxlBGIMVpBridgeCacheRelearnDrops OBJECT-TYPE
   SYNTAX      Counter32
   MAX-ACCESS  read-only
   STATUS      current
   DESCRIPTION
      "Path: vxLanBridgeGroup.performance.bridgeCache.relearnDrops

       32 bit unsigned wrappable counter."
   ::= {pr1646v2VxlBGIMVpBridgeCacheEntry 150994944}

pr1646v2VxlBGIMVpBridgeCacheVteRelearns OBJECT-TYPE
   SYNTAX      Counter32
   MAX-ACCESS  read-only
   STATUS      current
   DESCRIPTION
      "Path: vxLanBridgeGroup.performance.bridgeCache.vteRelearns

       32 bit unsigned wrappable counter."
   ::= {pr1646v2VxlBGIMVpBridgeCacheEntry 184549376}


pr1646v2VxlBGIMVpCacheEvents OBJECT IDENTIFIER ::= {pr1646v2VxlBGIMVp 44}

pr1646v2VxlBGIMVpCacheEventsSSCTable OBJECT-TYPE
   SYNTAX      SEQUENCE OF Pr1646v2VxlBGIMVpCacheEventsEntry
   MAX-ACCESS  not-accessible
   STATUS      current
   DESCRIPTION
      "bridge performances"
   ::= {pr1646v2VxlBGIMVpCacheEvents 1}

pr1646v2VxlBGIMVpCacheEventsEntry OBJECT-TYPE
   SYNTAX      Pr1646v2VxlBGIMVpCacheEventsEntry
   MAX-ACCESS  not-accessible
   STATUS      current
   DESCRIPTION
      ""
   INDEX      { pr1646v2VxlBGIMVpCacheEventsGlobalIx }
   ::= {pr1646v2VxlBGIMVpCacheEventsSSCTable 1}

Pr1646v2VxlBGIMVpCacheEventsEntry ::=
   SEQUENCE
      {
      pr1646v2VxlBGIMVpCacheEventsGlobalIx
         GlobalIndex,
      pr1646v2VxlBGIMVpCacheEventsSizeOverflows
         Counter32,
      pr1646v2VxlBGIMVpCacheEventsStaticViolations
         Counter32,
      pr1646v2VxlBGIMVpCacheEventsRelearns
         Counter32,
      pr1646v2VxlBGIMVpCacheEventsRelearnDrops
         Counter32,
      pr1646v2VxlBGIMVpCacheEventsVteRelearns
         Counter32,
      pr1646v2VxlBGIMVpCacheEventsLoopsDetected
         Counter32
      }

pr1646v2VxlBGIMVpCacheEventsGlobalIx OBJECT-TYPE
   SYNTAX      GlobalIndex
   MAX-ACCESS  not-accessible
   STATUS      current
   DESCRIPTION
      "The value of the tlsCntTreeGlobalIndex of the MANAGED OBJECT."
   ::= {pr1646v2VxlBGIMVpCacheEventsEntry 10}

pr1646v2VxlBGIMVpCacheEventsSizeOverflows OBJECT-TYPE
   SYNTAX      Counter32
   MAX-ACCESS  read-only
   STATUS      current
   DESCRIPTION
      "Path: vxLanBridgeGroup.performance.cacheEvents.sizeOverflows

       32 bit unsigned wrappable counter."
   ::= {pr1646v2VxlBGIMVpCacheEventsEntry 16777216}

pr1646v2VxlBGIMVpCacheEventsStaticViolations OBJECT-TYPE
   SYNTAX      Counter32
   MAX-ACCESS  read-only
   STATUS      current
   DESCRIPTION
      "Path: vxLanBridgeGroup.performance.cacheEvents.staticViolations

       32 bit unsigned wrappable counter."
   ::= {pr1646v2VxlBGIMVpCacheEventsEntry 33554432}

pr1646v2VxlBGIMVpCacheEventsRelearns OBJECT-TYPE
   SYNTAX      Counter32
   MAX-ACCESS  read-only
   STATUS      current
   DESCRIPTION
      "Path: vxLanBridgeGroup.performance.cacheEvents.relearns

       32 bit unsigned wrappable counter."
   ::= {pr1646v2VxlBGIMVpCacheEventsEntry 50331648}

pr1646v2VxlBGIMVpCacheEventsRelearnDrops OBJECT-TYPE
   SYNTAX      Counter32
   MAX-ACCESS  read-only
   STATUS      current
   DESCRIPTION
      "Path: vxLanBridgeGroup.performance.cacheEvents.relearnDrops

       32 bit unsigned wrappable counter."
   ::= {pr1646v2VxlBGIMVpCacheEventsEntry 67108864}

pr1646v2VxlBGIMVpCacheEventsVteRelearns OBJECT-TYPE
   SYNTAX      Counter32
   MAX-ACCESS  read-only
   STATUS      current
   DESCRIPTION
      "Path: vxLanBridgeGroup.performance.cacheEvents.vteRelearns

       32 bit unsigned wrappable counter."
   ::= {pr1646v2VxlBGIMVpCacheEventsEntry 83886080}

pr1646v2VxlBGIMVpCacheEventsLoopsDetected OBJECT-TYPE
   SYNTAX      Counter32
   MAX-ACCESS  read-only
   STATUS      current
   DESCRIPTION
      "Path: vxLanBridgeGroup.performance.cacheEvents.loopsDetected

       32 bit unsigned wrappable counter."
   ::= {pr1646v2VxlBGIMVpCacheEventsEntry 117440512}


pr1646v2VxlBGIMVpBridging OBJECT IDENTIFIER ::= {pr1646v2VxlBGIMVp 90}

pr1646v2VxlBGIMVpBridgingSSCTable OBJECT-TYPE
   SYNTAX      SEQUENCE OF Pr1646v2VxlBGIMVpBridgingEntry
   MAX-ACCESS  not-accessible
   STATUS      current
   DESCRIPTION
      " bridge-port performance"
   ::= {pr1646v2VxlBGIMVpBridging 1}

pr1646v2VxlBGIMVpBridgingEntry OBJECT-TYPE
   SYNTAX      Pr1646v2VxlBGIMVpBridgingEntry
   MAX-ACCESS  not-accessible
   STATUS      current
   DESCRIPTION
      ""
   INDEX      { pr1646v2VxlBGIMVpBridgingGlobalIx,
                pr1646v2VxlBGIMVpBridgingTableIx }
   ::= {pr1646v2VxlBGIMVpBridgingSSCTable 1}

Pr1646v2VxlBGIMVpBridgingEntry ::=
   SEQUENCE
      {
      pr1646v2VxlBGIMVpBridgingGlobalIx
         GlobalIndex,
      pr1646v2VxlBGIMVpBridgingTableIx
         TableIndex,
      pr1646v2VxlBGIMVpBridgingName
         DisplayString,
      pr1646v2VxlBGIMVpBridgingRxPkts
         Counter32,
      pr1646v2VxlBGIMVpBridgingTxPkts
         Counter32,
      pr1646v2VxlBGIMVpBridgingRxDiscards
         Counter32,
      pr1646v2VxlBGIMVpBridgingRxFloods
         Counter32,
      pr1646v2VxlBGIMVpBridgingRxBroadcasts
         Counter32,
      pr1646v2VxlBGIMVpBridgingRxMulticasts
         Counter32,
      pr1646v2VxlBGIMVpBridgingCacheSizeOverflows
         Counter32,
      pr1646v2VxlBGIMVpBridgingCacheStaticViolations
         Counter32,
      pr1646v2VxlBGIMVpBridgingCacheRelearns
         Counter32,
      pr1646v2VxlBGIMVpBridgingCacheRelearnDrops
         Counter32,
      pr1646v2VxlBGIMVpBridgingCacheVteRelearns
         Counter32,
      pr1646v2VxlBGIMVpBridgingCacheLoopsDetected
         Counter32,
      pr1646v2VxlBGIMVpBridgingVlanMemberShipRxDiscards
         Counter32,
      pr1646v2VxlBGIMVpBridgingVlanMemberShipTxDiscards
         Counter32,
      pr1646v2VxlBGIMVpBridgingSpanningTreeRxMstp
         Integer32,
      pr1646v2VxlBGIMVpBridgingSpanningTreeRxRstp
         Integer32,
      pr1646v2VxlBGIMVpBridgingSpanningTreeRxConfig
         Integer32,
      pr1646v2VxlBGIMVpBridgingSpanningTreeRxTcn
         Integer32,
      pr1646v2VxlBGIMVpBridgingSpanningTreeRxDiscards
         Integer32,
      pr1646v2VxlBGIMVpBridgingSpanningTreeTxMstp
         Integer32,
      pr1646v2VxlBGIMVpBridgingSpanningTreeTxRstp
         Integer32,
      pr1646v2VxlBGIMVpBridgingSpanningTreeTxConfig
         Integer32,
      pr1646v2VxlBGIMVpBridgingSpanningTreeTxTcn
         Integer32
      }

pr1646v2VxlBGIMVpBridgingGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgingEntry 10}

pr1646v2VxlBGIMVpBridgingTableIx OBJECT-TYPE
   SYNTAX      TableIndex
   MAX-ACCESS  not-accessible
   STATUS      current
   DESCRIPTION
      ""
   ::= {pr1646v2VxlBGIMVpBridgingEntry 11}

pr1646v2VxlBGIMVpBridgingName OBJECT-TYPE
   SYNTAX      DisplayString
   MAX-ACCESS  read-only
   STATUS      current
   DESCRIPTION
      "Path: vxLanBridgeGroup.performance.bridging.name"
   ::= {pr1646v2VxlBGIMVpBridgingEntry 16777216}

pr1646v2VxlBGIMVpBridgingRxPkts OBJECT-TYPE
   SYNTAX      Counter32
   MAX-ACCESS  read-only
   STATUS      current
   DESCRIPTION
      "Path: vxLanBridgeGroup.performance.bridging.rxPkts

       32 bit unsigned wrappable counter."
   ::= {pr1646v2VxlBGIMVpBridgingEntry 33554432}

pr1646v2VxlBGIMVpBridgingTxPkts OBJECT-TYPE
   SYNTAX      Counter32
   MAX-ACCESS  read-only
   STATUS      current
   DESCRIPTION
      "Path: vxLanBridgeGroup.performance.bridging.txPkts

       32 bit unsigned wrappable counter."
   ::= {pr1646v2VxlBGIMVpBridgingEntry 50331648}

pr1646v2VxlBGIMVpBridgingRxDiscards OBJECT-TYPE
   SYNTAX      Counter32
   MAX-ACCESS  read-only
   STATUS      current
   DESCRIPTION
      "Path: vxLanBridgeGroup.performance.bridging.rxDiscards

       32 bit unsigned wrappable counter."
   ::= {pr1646v2VxlBGIMVpBridgingEntry 67108864}

pr1646v2VxlBGIMVpBridgingRxFloods OBJECT-TYPE
   SYNTAX      Counter32
   MAX-ACCESS  read-only
   STATUS      current
   DESCRIPTION
      "Path: vxLanBridgeGroup.performance.bridging.rxFloods

       32 bit unsigned wrappable counter."
   ::= {pr1646v2VxlBGIMVpBridgingEntry 83886080}

pr1646v2VxlBGIMVpBridgingRxBroadcasts OBJECT-TYPE
   SYNTAX      Counter32
   MAX-ACCESS  read-only
   STATUS      current
   DESCRIPTION
      "Path: vxLanBridgeGroup.performance.bridging.rxBroadcasts

       32 bit unsigned wrappable counter."
   ::= {pr1646v2VxlBGIMVpBridgingEntry 100663296}

pr1646v2VxlBGIMVpBridgingRxMulticasts OBJECT-TYPE
   SYNTAX      Counter32
   MAX-ACCESS  read-only
   STATUS      current
   DESCRIPTION
      "Path: vxLanBridgeGroup.performance.bridging.rxMulticasts

       32 bit unsigned wrappable counter."
   ::= {pr1646v2VxlBGIMVpBridgingEntry 117440512}

pr1646v2VxlBGIMVpBridgingCacheSizeOverflows OBJECT-TYPE
   SYNTAX      Counter32
   MAX-ACCESS  read-only
   STATUS      current
   DESCRIPTION
      "Path: vxLanBridgeGroup.performance.bridging.cache.sizeOverflows

       32 bit unsigned wrappable counter."
   ::= {pr1646v2VxlBGIMVpBridgingEntry 134283264}

pr1646v2VxlBGIMVpBridgingCacheStaticViolations OBJECT-TYPE
   SYNTAX      Counter32
   MAX-ACCESS  read-only
   STATUS      current
   DESCRIPTION
      "Path: vxLanBridgeGroup.performance.bridging.cache.staticViolations

       32 bit unsigned wrappable counter."
   ::= {pr1646v2VxlBGIMVpBridgingEntry 134348800}

pr1646v2VxlBGIMVpBridgingCacheRelearns OBJECT-TYPE
   SYNTAX      Counter32
   MAX-ACCESS  read-only
   STATUS      current
   DESCRIPTION
      "Path: vxLanBridgeGroup.performance.bridging.cache.relearns

       32 bit unsigned wrappable counter."
   ::= {pr1646v2VxlBGIMVpBridgingEntry 134414336}

pr1646v2VxlBGIMVpBridgingCacheRelearnDrops OBJECT-TYPE
   SYNTAX      Counter32
   MAX-ACCESS  read-only
   STATUS      current
   DESCRIPTION
      "Path: vxLanBridgeGroup.performance.bridging.cache.relearnDrops

       32 bit unsigned wrappable counter."
   ::= {pr1646v2VxlBGIMVpBridgingEntry 134479872}

pr1646v2VxlBGIMVpBridgingCacheVteRelearns OBJECT-TYPE
   SYNTAX      Counter32
   MAX-ACCESS  read-only
   STATUS      current
   DESCRIPTION
      "Path: vxLanBridgeGroup.performance.bridging.cache.vteRelearns

       32 bit unsigned wrappable counter."
   ::= {pr1646v2VxlBGIMVpBridgingEntry 134545408}

pr1646v2VxlBGIMVpBridgingCacheLoopsDetected OBJECT-TYPE
   SYNTAX      Counter32
   MAX-ACCESS  read-only
   STATUS      current
   DESCRIPTION
      "Path: vxLanBridgeGroup.performance.bridging.cache.loopsDetected

       32 bit unsigned wrappable counter."
   ::= {pr1646v2VxlBGIMVpBridgingEntry 134676480}

pr1646v2VxlBGIMVpBridgingVlanMemberShipRxDiscards OBJECT-TYPE
   SYNTAX      Counter32
   MAX-ACCESS  read-only
   STATUS      current
   DESCRIPTION
      "Path: vxLanBridgeGroup.performance.bridging.vlanMemberShip.rxDiscards

       32 bit unsigned wrappable counter."
   ::= {pr1646v2VxlBGIMVpBridgingEntry 218169344}

pr1646v2VxlBGIMVpBridgingVlanMemberShipTxDiscards OBJECT-TYPE
   SYNTAX      Counter32
   MAX-ACCESS  read-only
   STATUS      current
   DESCRIPTION
      "Path: vxLanBridgeGroup.performance.bridging.vlanMemberShip.txDiscards

       32 bit unsigned wrappable counter."
   ::= {pr1646v2VxlBGIMVpBridgingEntry 218234880}

pr1646v2VxlBGIMVpBridgingSpanningTreeRxMstp OBJECT-TYPE
   SYNTAX      Integer32
   MAX-ACCESS  read-only
   STATUS      current
   DESCRIPTION
      "Path: vxLanBridgeGroup.performance.bridging.spanningTree.rxMstp"
   ::= {pr1646v2VxlBGIMVpBridgingEntry 201392128}

pr1646v2VxlBGIMVpBridgingSpanningTreeRxRstp OBJECT-TYPE
   SYNTAX      Integer32
   MAX-ACCESS  read-only
   STATUS      current
   DESCRIPTION
      "Path: vxLanBridgeGroup.performance.bridging.spanningTree.rxRstp"
   ::= {pr1646v2VxlBGIMVpBridgingEntry 201457664}

pr1646v2VxlBGIMVpBridgingSpanningTreeRxConfig OBJECT-TYPE
   SYNTAX      Integer32
   MAX-ACCESS  read-only
   STATUS      current
   DESCRIPTION
      "Path: vxLanBridgeGroup.performance.bridging.spanningTree.rxConfig"
   ::= {pr1646v2VxlBGIMVpBridgingEntry 201523200}

pr1646v2VxlBGIMVpBridgingSpanningTreeRxTcn OBJECT-TYPE
   SYNTAX      Integer32
   MAX-ACCESS  read-only
   STATUS      current
   DESCRIPTION
      "Path: vxLanBridgeGroup.performance.bridging.spanningTree.rxTcn"
   ::= {pr1646v2VxlBGIMVpBridgingEntry 201588736}

pr1646v2VxlBGIMVpBridgingSpanningTreeRxDiscards OBJECT-TYPE
   SYNTAX      Integer32
   MAX-ACCESS  read-only
   STATUS      current
   DESCRIPTION
      "Path: vxLanBridgeGroup.performance.bridging.spanningTree.rxDiscards"
   ::= {pr1646v2VxlBGIMVpBridgingEntry 201654272}

pr1646v2VxlBGIMVpBridgingSpanningTreeTxMstp OBJECT-TYPE
   SYNTAX      Integer32
   MAX-ACCESS  read-only
   STATUS      current
   DESCRIPTION
      "Path: vxLanBridgeGroup.performance.bridging.spanningTree.txMstp"
   ::= {pr1646v2VxlBGIMVpBridgingEntry 201719808}

pr1646v2VxlBGIMVpBridgingSpanningTreeTxRstp OBJECT-TYPE
   SYNTAX      Integer32
   MAX-ACCESS  read-only
   STATUS      current
   DESCRIPTION
      "Path: vxLanBridgeGroup.performance.bridging.spanningTree.txRstp"
   ::= {pr1646v2VxlBGIMVpBridgingEntry 201785344}

pr1646v2VxlBGIMVpBridgingSpanningTreeTxConfig OBJECT-TYPE
   SYNTAX      Integer32
   MAX-ACCESS  read-only
   STATUS      current
   DESCRIPTION
      "Path: vxLanBridgeGroup.performance.bridging.spanningTree.txConfig"
   ::= {pr1646v2VxlBGIMVpBridgingEntry 201850880}

pr1646v2VxlBGIMVpBridgingSpanningTreeTxTcn OBJECT-TYPE
   SYNTAX      Integer32
   MAX-ACCESS  read-only
   STATUS      current
   DESCRIPTION
      "Path: vxLanBridgeGroup.performance.bridging.spanningTree.txTcn"
   ::= {pr1646v2VxlBGIMVpBridgingEntry 201916416}

pr1646v2VxlBGIMVpBridgingH2Performance OBJECT-TYPE
   SYNTAX      SEQUENCE OF Pr1646v2VxlBGIMVpBridgingH2PerformanceEntry
   MAX-ACCESS  not-accessible
   STATUS      current
   DESCRIPTION
      ""
   ::= {pr1646v2VxlBGIMVpBridging 150994944}

pr1646v2VxlBGIMVpBridgingH2PerformanceEntry OBJECT-TYPE
   SYNTAX      Pr1646v2VxlBGIMVpBridgingH2PerformanceEntry
   MAX-ACCESS  not-accessible
   STATUS      current
   DESCRIPTION
      ""
   INDEX      { pr1646v2VxlBGIMVpBridgingH2PerformanceGlobalIx,
                pr1646v2VxlBGIMVpBridgingTableIx,
                pr1646v2VxlBGIMVpBridgingH2PerformanceTableIx }
   ::= {pr1646v2VxlBGIMVpBridgingH2Performance 1}

Pr1646v2VxlBGIMVpBridgingH2PerformanceEntry ::=
   SEQUENCE
      {
      pr1646v2VxlBGIMVpBridgingH2PerformanceGlobalIx
         GlobalIndex,
      pr1646v2VxlBGIMVpBridgingH2PerformanceTableIx
         TableIndex,
      pr1646v2VxlBGIMVpBridgingH2PerformanceSysUpTime
         TimeTicks,
      pr1646v2VxlBGIMVpBridgingH2PerformanceRxPkts
         Counter32,
      pr1646v2VxlBGIMVpBridgingH2PerformanceTxPkts
         Counter32,
      pr1646v2VxlBGIMVpBridgingH2PerformanceRxDiscards
         Counter32,
      pr1646v2VxlBGIMVpBridgingH2PerformanceRxFloods
         Counter32,
      pr1646v2VxlBGIMVpBridgingH2PerformanceRxBroadcasts
         Counter32,
      pr1646v2VxlBGIMVpBridgingH2PerformanceRxMulticasts
         Counter32,
      pr1646v2VxlBGIMVpBridgingH2PerformanceCacheSizeOverflows
         Counter32,
      pr1646v2VxlBGIMVpBridgingH2PerformanceStaticCacheViolations
         Counter32,
      pr1646v2VxlBGIMVpBridgingH2PerformanceCacheRelearns
         Counter32,
      pr1646v2VxlBGIMVpBridgingH2PerformanceCacheRelearnDrops
         Counter32,
      pr1646v2VxlBGIMVpBridgingH2PerformanceCacheVteRelearns
         Counter32,
      pr1646v2VxlBGIMVpBridgingH2PerformanceLoopsDetected
         Counter32
      }

pr1646v2VxlBGIMVpBridgingH2PerformanceGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgingH2PerformanceEntry 10}

pr1646v2VxlBGIMVpBridgingH2PerformanceTableIx OBJECT-TYPE
   SYNTAX      TableIndex
   MAX-ACCESS  not-accessible
   STATUS      current
   DESCRIPTION
      ""
   ::= {pr1646v2VxlBGIMVpBridgingH2PerformanceEntry 11}

pr1646v2VxlBGIMVpBridgingH2PerformanceSysUpTime OBJECT-TYPE
   SYNTAX      TimeTicks
   MAX-ACCESS  read-only
   STATUS      current
   DESCRIPTION
      "Path: vxLanBridgeGroup.performance.bridging.h2Performance.sysUpTime

       Time in centi-second."
   ::= {pr1646v2VxlBGIMVpBridgingH2PerformanceEntry 16777216}

pr1646v2VxlBGIMVpBridgingH2PerformanceRxPkts OBJECT-TYPE
   SYNTAX      Counter32
   MAX-ACCESS  read-only
   STATUS      current
   DESCRIPTION
      "Path: vxLanBridgeGroup.performance.bridging.h2Performance.rxPkts

       32 bit unsigned wrappable counter."
   ::= {pr1646v2VxlBGIMVpBridgingH2PerformanceEntry 33554432}

pr1646v2VxlBGIMVpBridgingH2PerformanceTxPkts OBJECT-TYPE
   SYNTAX      Counter32
   MAX-ACCESS  read-only
   STATUS      current
   DESCRIPTION
      "Path: vxLanBridgeGroup.performance.bridging.h2Performance.txPkts

       32 bit unsigned wrappable counter."
   ::= {pr1646v2VxlBGIMVpBridgingH2PerformanceEntry 50331648}

pr1646v2VxlBGIMVpBridgingH2PerformanceRxDiscards OBJECT-TYPE
   SYNTAX      Counter32
   MAX-ACCESS  read-only
   STATUS      current
   DESCRIPTION
      "Path: vxLanBridgeGroup.performance.bridging.h2Performance.rxDiscards

       32 bit unsigned wrappable counter."
   ::= {pr1646v2VxlBGIMVpBridgingH2PerformanceEntry 67108864}

pr1646v2VxlBGIMVpBridgingH2PerformanceRxFloods OBJECT-TYPE
   SYNTAX      Counter32
   MAX-ACCESS  read-only
   STATUS      current
   DESCRIPTION
      "Path: vxLanBridgeGroup.performance.bridging.h2Performance.rxFloods

       32 bit unsigned wrappable counter."
   ::= {pr1646v2VxlBGIMVpBridgingH2PerformanceEntry 83886080}

pr1646v2VxlBGIMVpBridgingH2PerformanceRxBroadcasts OBJECT-TYPE
   SYNTAX      Counter32
   MAX-ACCESS  read-only
   STATUS      current
   DESCRIPTION
      "Path: vxLanBridgeGroup.performance.bridging.h2Performance.rxBroadcasts

       32 bit unsigned wrappable counter."
   ::= {pr1646v2VxlBGIMVpBridgingH2PerformanceEntry 100663296}

pr1646v2VxlBGIMVpBridgingH2PerformanceRxMulticasts OBJECT-TYPE
   SYNTAX      Counter32
   MAX-ACCESS  read-only
   STATUS      current
   DESCRIPTION
      "Path: vxLanBridgeGroup.performance.bridging.h2Performance.rxMulticasts

       32 bit unsigned wrappable counter."
   ::= {pr1646v2VxlBGIMVpBridgingH2PerformanceEntry 117440512}

pr1646v2VxlBGIMVpBridgingH2PerformanceCacheSizeOverflows OBJECT-TYPE
   SYNTAX      Counter32
   MAX-ACCESS  read-only
   STATUS      current
   DESCRIPTION
      "Path: vxLanBridgeGroup.performance.bridging.h2Performance.cacheSizeOverflows

       32 bit unsigned wrappable counter."
   ::= {pr1646v2VxlBGIMVpBridgingH2PerformanceEntry 134217728}

pr1646v2VxlBGIMVpBridgingH2PerformanceStaticCacheViolations OBJECT-TYPE
   SYNTAX      Counter32
   MAX-ACCESS  read-only
   STATUS      current
   DESCRIPTION
      "Path: vxLanBridgeGroup.performance.bridging.h2Performance.staticCacheViolations

       32 bit unsigned wrappable counter."
   ::= {pr1646v2VxlBGIMVpBridgingH2PerformanceEntry 150994944}

pr1646v2VxlBGIMVpBridgingH2PerformanceCacheRelearns OBJECT-TYPE
   SYNTAX      Counter32
   MAX-ACCESS  read-only
   STATUS      current
   DESCRIPTION
      "Path: vxLanBridgeGroup.performance.bridging.h2Performance.cacheRelearns

       32 bit unsigned wrappable counter."
   ::= {pr1646v2VxlBGIMVpBridgingH2PerformanceEntry 167772160}

pr1646v2VxlBGIMVpBridgingH2PerformanceCacheRelearnDrops OBJECT-TYPE
   SYNTAX      Counter32
   MAX-ACCESS  read-only
   STATUS      current
   DESCRIPTION
      "Path: vxLanBridgeGroup.performance.bridging.h2Performance.cacheRelearnDrops

       32 bit unsigned wrappable counter."
   ::= {pr1646v2VxlBGIMVpBridgingH2PerformanceEntry 184549376}

pr1646v2VxlBGIMVpBridgingH2PerformanceCacheVteRelearns OBJECT-TYPE
   SYNTAX      Counter32
   MAX-ACCESS  read-only
   STATUS      current
   DESCRIPTION
      "Path: vxLanBridgeGroup.performance.bridging.h2Performance.cacheVteRelearns

       32 bit unsigned wrappable counter."
   ::= {pr1646v2VxlBGIMVpBridgingH2PerformanceEntry 201326592}

pr1646v2VxlBGIMVpBridgingH2PerformanceLoopsDetected OBJECT-TYPE
   SYNTAX      Counter32
   MAX-ACCESS  read-only
   STATUS      current
   DESCRIPTION
      "Path: vxLanBridgeGroup.performance.bridging.h2Performance.loopsDetected

       32 bit unsigned wrappable counter."
   ::= {pr1646v2VxlBGIMVpBridgingH2PerformanceEntry 234881024}

pr1646v2VxlBGIMVpBridgingH24Performance OBJECT-TYPE
   SYNTAX      SEQUENCE OF Pr1646v2VxlBGIMVpBridgingH24PerformanceEntry
   MAX-ACCESS  not-accessible
   STATUS      current
   DESCRIPTION
      ""
   ::= {pr1646v2VxlBGIMVpBridging 167772160}

pr1646v2VxlBGIMVpBridgingH24PerformanceEntry OBJECT-TYPE
   SYNTAX      Pr1646v2VxlBGIMVpBridgingH24PerformanceEntry
   MAX-ACCESS  not-accessible
   STATUS      current
   DESCRIPTION
      ""
   INDEX      { pr1646v2VxlBGIMVpBridgingH24PerformanceGlobalIx,
                pr1646v2VxlBGIMVpBridgingTableIx,
                pr1646v2VxlBGIMVpBridgingH24PerformanceTableIx }
   ::= {pr1646v2VxlBGIMVpBridgingH24Performance 1}

Pr1646v2VxlBGIMVpBridgingH24PerformanceEntry ::=
   SEQUENCE
      {
      pr1646v2VxlBGIMVpBridgingH24PerformanceGlobalIx
         GlobalIndex,
      pr1646v2VxlBGIMVpBridgingH24PerformanceTableIx
         TableIndex,
      pr1646v2VxlBGIMVpBridgingH24PerformanceSysUpTime
         TimeTicks,
      pr1646v2VxlBGIMVpBridgingH24PerformanceRxPkts
         Counter32,
      pr1646v2VxlBGIMVpBridgingH24PerformanceTxPkts
         Counter32,
      pr1646v2VxlBGIMVpBridgingH24PerformanceRxDiscards
         Counter32,
      pr1646v2VxlBGIMVpBridgingH24PerformanceRxFloods
         Counter32,
      pr1646v2VxlBGIMVpBridgingH24PerformanceRxBroadcasts
         Counter32,
      pr1646v2VxlBGIMVpBridgingH24PerformanceRxMulticasts
         Counter32,
      pr1646v2VxlBGIMVpBridgingH24PerformanceCacheSizeOverflows
         Counter32,
      pr1646v2VxlBGIMVpBridgingH24PerformanceStaticCacheViolations
         Counter32,
      pr1646v2VxlBGIMVpBridgingH24PerformanceCacheRelearns
         Counter32,
      pr1646v2VxlBGIMVpBridgingH24PerformanceCacheRelearnDrops
         Counter32,
      pr1646v2VxlBGIMVpBridgingH24PerformanceCacheVteRelearns
         Counter32,
      pr1646v2VxlBGIMVpBridgingH24PerformanceLoopsDetected
         Counter32
      }

pr1646v2VxlBGIMVpBridgingH24PerformanceGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgingH24PerformanceEntry 10}

pr1646v2VxlBGIMVpBridgingH24PerformanceTableIx OBJECT-TYPE
   SYNTAX      TableIndex
   MAX-ACCESS  not-accessible
   STATUS      current
   DESCRIPTION
      ""
   ::= {pr1646v2VxlBGIMVpBridgingH24PerformanceEntry 11}

pr1646v2VxlBGIMVpBridgingH24PerformanceSysUpTime OBJECT-TYPE
   SYNTAX      TimeTicks
   MAX-ACCESS  read-only
   STATUS      current
   DESCRIPTION
      "Path: vxLanBridgeGroup.performance.bridging.h24Performance.sysUpTime

       Time in centi-second."
   ::= {pr1646v2VxlBGIMVpBridgingH24PerformanceEntry 16777216}

pr1646v2VxlBGIMVpBridgingH24PerformanceRxPkts OBJECT-TYPE
   SYNTAX      Counter32
   MAX-ACCESS  read-only
   STATUS      current
   DESCRIPTION
      "Path: vxLanBridgeGroup.performance.bridging.h24Performance.rxPkts

       32 bit unsigned wrappable counter."
   ::= {pr1646v2VxlBGIMVpBridgingH24PerformanceEntry 33554432}

pr1646v2VxlBGIMVpBridgingH24PerformanceTxPkts OBJECT-TYPE
   SYNTAX      Counter32
   MAX-ACCESS  read-only
   STATUS      current
   DESCRIPTION
      "Path: vxLanBridgeGroup.performance.bridging.h24Performance.txPkts

       32 bit unsigned wrappable counter."
   ::= {pr1646v2VxlBGIMVpBridgingH24PerformanceEntry 50331648}

pr1646v2VxlBGIMVpBridgingH24PerformanceRxDiscards OBJECT-TYPE
   SYNTAX      Counter32
   MAX-ACCESS  read-only
   STATUS      current
   DESCRIPTION
      "Path: vxLanBridgeGroup.performance.bridging.h24Performance.rxDiscards

       32 bit unsigned wrappable counter."
   ::= {pr1646v2VxlBGIMVpBridgingH24PerformanceEntry 67108864}

pr1646v2VxlBGIMVpBridgingH24PerformanceRxFloods OBJECT-TYPE
   SYNTAX      Counter32
   MAX-ACCESS  read-only
   STATUS      current
   DESCRIPTION
      "Path: vxLanBridgeGroup.performance.bridging.h24Performance.rxFloods

       32 bit unsigned wrappable counter."
   ::= {pr1646v2VxlBGIMVpBridgingH24PerformanceEntry 83886080}

pr1646v2VxlBGIMVpBridgingH24PerformanceRxBroadcasts OBJECT-TYPE
   SYNTAX      Counter32
   MAX-ACCESS  read-only
   STATUS      current
   DESCRIPTION
      "Path: vxLanBridgeGroup.performance.bridging.h24Performance.rxBroadcasts

       32 bit unsigned wrappable counter."
   ::= {pr1646v2VxlBGIMVpBridgingH24PerformanceEntry 100663296}

pr1646v2VxlBGIMVpBridgingH24PerformanceRxMulticasts OBJECT-TYPE
   SYNTAX      Counter32
   MAX-ACCESS  read-only
   STATUS      current
   DESCRIPTION
      "Path: vxLanBridgeGroup.performance.bridging.h24Performance.rxMulticasts

       32 bit unsigned wrappable counter."
   ::= {pr1646v2VxlBGIMVpBridgingH24PerformanceEntry 117440512}

pr1646v2VxlBGIMVpBridgingH24PerformanceCacheSizeOverflows OBJECT-TYPE
   SYNTAX      Counter32
   MAX-ACCESS  read-only
   STATUS      current
   DESCRIPTION
      "Path: vxLanBridgeGroup.performance.bridging.h24Performance.cacheSizeOverflows

       32 bit unsigned wrappable counter."
   ::= {pr1646v2VxlBGIMVpBridgingH24PerformanceEntry 134217728}

pr1646v2VxlBGIMVpBridgingH24PerformanceStaticCacheViolations OBJECT-TYPE
   SYNTAX      Counter32
   MAX-ACCESS  read-only
   STATUS      current
   DESCRIPTION
      "Path: vxLanBridgeGroup.performance.bridging.h24Performance.staticCacheViolations

       32 bit unsigned wrappable counter."
   ::= {pr1646v2VxlBGIMVpBridgingH24PerformanceEntry 150994944}

pr1646v2VxlBGIMVpBridgingH24PerformanceCacheRelearns OBJECT-TYPE
   SYNTAX      Counter32
   MAX-ACCESS  read-only
   STATUS      current
   DESCRIPTION
      "Path: vxLanBridgeGroup.performance.bridging.h24Performance.cacheRelearns

       32 bit unsigned wrappable counter."
   ::= {pr1646v2VxlBGIMVpBridgingH24PerformanceEntry 167772160}

pr1646v2VxlBGIMVpBridgingH24PerformanceCacheRelearnDrops OBJECT-TYPE
   SYNTAX      Counter32
   MAX-ACCESS  read-only
   STATUS      current
   DESCRIPTION
      "Path: vxLanBridgeGroup.performance.bridging.h24Performance.cacheRelearnDrops

       32 bit unsigned wrappable counter."
   ::= {pr1646v2VxlBGIMVpBridgingH24PerformanceEntry 184549376}

pr1646v2VxlBGIMVpBridgingH24PerformanceCacheVteRelearns OBJECT-TYPE
   SYNTAX      Counter32
   MAX-ACCESS  read-only
   STATUS      current
   DESCRIPTION
      "Path: vxLanBridgeGroup.performance.bridging.h24Performance.cacheVteRelearns

       32 bit unsigned wrappable counter."
   ::= {pr1646v2VxlBGIMVpBridgingH24PerformanceEntry 201326592}

pr1646v2VxlBGIMVpBridgingH24PerformanceLoopsDetected OBJECT-TYPE
   SYNTAX      Counter32
   MAX-ACCESS  read-only
   STATUS      current
   DESCRIPTION
      "Path: vxLanBridgeGroup.performance.bridging.h24Performance.loopsDetected

       32 bit unsigned wrappable counter."
   ::= {pr1646v2VxlBGIMVpBridgingH24PerformanceEntry 234881024}

pr1646v2VxlBGIMVpBridgingD7Performance OBJECT-TYPE
   SYNTAX      SEQUENCE OF Pr1646v2VxlBGIMVpBridgingD7PerformanceEntry
   MAX-ACCESS  not-accessible
   STATUS      current
   DESCRIPTION
      ""
   ::= {pr1646v2VxlBGIMVpBridging 184549376}

pr1646v2VxlBGIMVpBridgingD7PerformanceEntry OBJECT-TYPE
   SYNTAX      Pr1646v2VxlBGIMVpBridgingD7PerformanceEntry
   MAX-ACCESS  not-accessible
   STATUS      current
   DESCRIPTION
      ""
   INDEX      { pr1646v2VxlBGIMVpBridgingD7PerformanceGlobalIx,
                pr1646v2VxlBGIMVpBridgingTableIx,
                pr1646v2VxlBGIMVpBridgingD7PerformanceTableIx }
   ::= {pr1646v2VxlBGIMVpBridgingD7Performance 1}

Pr1646v2VxlBGIMVpBridgingD7PerformanceEntry ::=
   SEQUENCE
      {
      pr1646v2VxlBGIMVpBridgingD7PerformanceGlobalIx
         GlobalIndex,
      pr1646v2VxlBGIMVpBridgingD7PerformanceTableIx
         TableIndex,
      pr1646v2VxlBGIMVpBridgingD7PerformanceSysUpTime
         TimeTicks,
      pr1646v2VxlBGIMVpBridgingD7PerformanceRxPkts
         Counter32,
      pr1646v2VxlBGIMVpBridgingD7PerformanceTxPkts
         Counter32,
      pr1646v2VxlBGIMVpBridgingD7PerformanceRxDiscards
         Counter32,
      pr1646v2VxlBGIMVpBridgingD7PerformanceRxFloods
         Counter32,
      pr1646v2VxlBGIMVpBridgingD7PerformanceRxBroadcasts
         Counter32,
      pr1646v2VxlBGIMVpBridgingD7PerformanceRxMulticasts
         Counter32,
      pr1646v2VxlBGIMVpBridgingD7PerformanceCacheSizeOverflows
         Counter32,
      pr1646v2VxlBGIMVpBridgingD7PerformanceStaticCacheViolations
         Counter32,
      pr1646v2VxlBGIMVpBridgingD7PerformanceCacheRelearns
         Counter32,
      pr1646v2VxlBGIMVpBridgingD7PerformanceCacheRelearnDrops
         Counter32,
      pr1646v2VxlBGIMVpBridgingD7PerformanceCacheVteRelearns
         Counter32,
      pr1646v2VxlBGIMVpBridgingD7PerformanceLoopsDetected
         Counter32
      }

pr1646v2VxlBGIMVpBridgingD7PerformanceGlobalIx OBJECT-TYPE
   SYNTAX      GlobalIndex
   MAX-ACCESS  not-accessible
   STATUS      current
   DESCRIPTION
      "The value of the tlsCntTreeGlobalIndex of the MANAGED OBJECT."
   ::= {pr1646v2VxlBGIMVpBridgingD7PerformanceEntry 10}

pr1646v2VxlBGIMVpBridgingD7PerformanceTableIx OBJECT-TYPE
   SYNTAX      TableIndex
   MAX-ACCESS  not-accessible
   STATUS      current
   DESCRIPTION
      ""
   ::= {pr1646v2VxlBGIMVpBridgingD7PerformanceEntry 11}

pr1646v2VxlBGIMVpBridgingD7PerformanceSysUpTime OBJECT-TYPE
   SYNTAX      TimeTicks
   MAX-ACCESS  read-only
   STATUS      current
   DESCRIPTION
      "Path: vxLanBridgeGroup.performance.bridging.d7Performance.sysUpTime

       Time in centi-second."
   ::= {pr1646v2VxlBGIMVpBridgingD7PerformanceEntry 16777216}

pr1646v2VxlBGIMVpBridgingD7PerformanceRxPkts OBJECT-TYPE
   SYNTAX      Counter32
   MAX-ACCESS  read-only
   STATUS      current
   DESCRIPTION
      "Path: vxLanBridgeGroup.performance.bridging.d7Performance.rxPkts

       32 bit unsigned wrappable counter."
   ::= {pr1646v2VxlBGIMVpBridgingD7PerformanceEntry 33554432}

pr1646v2VxlBGIMVpBridgingD7PerformanceTxPkts OBJECT-TYPE
   SYNTAX      Counter32
   MAX-ACCESS  read-only
   STATUS      current
   DESCRIPTION
      "Path: vxLanBridgeGroup.performance.bridging.d7Performance.txPkts

       32 bit unsigned wrappable counter."
   ::= {pr1646v2VxlBGIMVpBridgingD7PerformanceEntry 50331648}

pr1646v2VxlBGIMVpBridgingD7PerformanceRxDiscards OBJECT-TYPE
   SYNTAX      Counter32
   MAX-ACCESS  read-only
   STATUS      current
   DESCRIPTION
      "Path: vxLanBridgeGroup.performance.bridging.d7Performance.rxDiscards

       32 bit unsigned wrappable counter."
   ::= {pr1646v2VxlBGIMVpBridgingD7PerformanceEntry 67108864}

pr1646v2VxlBGIMVpBridgingD7PerformanceRxFloods OBJECT-TYPE
   SYNTAX      Counter32
   MAX-ACCESS  read-only
   STATUS      current
   DESCRIPTION
      "Path: vxLanBridgeGroup.performance.bridging.d7Performance.rxFloods

       32 bit unsigned wrappable counter."
   ::= {pr1646v2VxlBGIMVpBridgingD7PerformanceEntry 83886080}

pr1646v2VxlBGIMVpBridgingD7PerformanceRxBroadcasts OBJECT-TYPE
   SYNTAX      Counter32
   MAX-ACCESS  read-only
   STATUS      current
   DESCRIPTION
      "Path: vxLanBridgeGroup.performance.bridging.d7Performance.rxBroadcasts

       32 bit unsigned wrappable counter."
   ::= {pr1646v2VxlBGIMVpBridgingD7PerformanceEntry 100663296}

pr1646v2VxlBGIMVpBridgingD7PerformanceRxMulticasts OBJECT-TYPE
   SYNTAX      Counter32
   MAX-ACCESS  read-only
   STATUS      current
   DESCRIPTION
      "Path: vxLanBridgeGroup.performance.bridging.d7Performance.rxMulticasts

       32 bit unsigned wrappable counter."
   ::= {pr1646v2VxlBGIMVpBridgingD7PerformanceEntry 117440512}

pr1646v2VxlBGIMVpBridgingD7PerformanceCacheSizeOverflows OBJECT-TYPE
   SYNTAX      Counter32
   MAX-ACCESS  read-only
   STATUS      current
   DESCRIPTION
      "Path: vxLanBridgeGroup.performance.bridging.d7Performance.cacheSizeOverflows

       32 bit unsigned wrappable counter."
   ::= {pr1646v2VxlBGIMVpBridgingD7PerformanceEntry 134217728}

pr1646v2VxlBGIMVpBridgingD7PerformanceStaticCacheViolations OBJECT-TYPE
   SYNTAX      Counter32
   MAX-ACCESS  read-only
   STATUS      current
   DESCRIPTION
      "Path: vxLanBridgeGroup.performance.bridging.d7Performance.staticCacheViolations

       32 bit unsigned wrappable counter."
   ::= {pr1646v2VxlBGIMVpBridgingD7PerformanceEntry 150994944}

pr1646v2VxlBGIMVpBridgingD7PerformanceCacheRelearns OBJECT-TYPE
   SYNTAX      Counter32
   MAX-ACCESS  read-only
   STATUS      current
   DESCRIPTION
      "Path: vxLanBridgeGroup.performance.bridging.d7Performance.cacheRelearns

       32 bit unsigned wrappable counter."
   ::= {pr1646v2VxlBGIMVpBridgingD7PerformanceEntry 167772160}

pr1646v2VxlBGIMVpBridgingD7PerformanceCacheRelearnDrops OBJECT-TYPE
   SYNTAX      Counter32
   MAX-ACCESS  read-only
   STATUS      current
   DESCRIPTION
      "Path: vxLanBridgeGroup.performance.bridging.d7Performance.cacheRelearnDrops

       32 bit unsigned wrappable counter."
   ::= {pr1646v2VxlBGIMVpBridgingD7PerformanceEntry 184549376}

pr1646v2VxlBGIMVpBridgingD7PerformanceCacheVteRelearns OBJECT-TYPE
   SYNTAX      Counter32
   MAX-ACCESS  read-only
   STATUS      current
   DESCRIPTION
      "Path: vxLanBridgeGroup.performance.bridging.d7Performance.cacheVteRelearns

       32 bit unsigned wrappable counter."
   ::= {pr1646v2VxlBGIMVpBridgingD7PerformanceEntry 201326592}

pr1646v2VxlBGIMVpBridgingD7PerformanceLoopsDetected OBJECT-TYPE
   SYNTAX      Counter32
   MAX-ACCESS  read-only
   STATUS      current
   DESCRIPTION
      "Path: vxLanBridgeGroup.performance.bridging.d7Performance.loopsDetected

       32 bit unsigned wrappable counter."
   ::= {pr1646v2VxlBGIMVpBridgingD7PerformanceEntry 234881024}


pr1646v2VxlBGIMVpH2Perf OBJECT IDENTIFIER ::= {pr1646v2VxlBGIMVp 91}

pr1646v2VxlBGIMVpH2PerfSSCTable OBJECT-TYPE
   SYNTAX      SEQUENCE OF Pr1646v2VxlBGIMVpH2PerfEntry
   MAX-ACCESS  not-accessible
   STATUS      current
   DESCRIPTION
      "2 hour bridge stats"
   ::= {pr1646v2VxlBGIMVpH2Perf 1}

pr1646v2VxlBGIMVpH2PerfEntry OBJECT-TYPE
   SYNTAX      Pr1646v2VxlBGIMVpH2PerfEntry
   MAX-ACCESS  not-accessible
   STATUS      current
   DESCRIPTION
      ""
   INDEX      { pr1646v2VxlBGIMVpH2PerfGlobalIx,
                pr1646v2VxlBGIMVpH2PerfTableIx }
   ::= {pr1646v2VxlBGIMVpH2PerfSSCTable 1}

Pr1646v2VxlBGIMVpH2PerfEntry ::=
   SEQUENCE
      {
      pr1646v2VxlBGIMVpH2PerfGlobalIx
         GlobalIndex,
      pr1646v2VxlBGIMVpH2PerfTableIx
         TableIndex,
      pr1646v2VxlBGIMVpH2PerfSysUpTime
         TimeTicks,
      pr1646v2VxlBGIMVpH2PerfRxPkts
         Counter32,
      pr1646v2VxlBGIMVpH2PerfTxPkts
         Counter32,
      pr1646v2VxlBGIMVpH2PerfDiscards
         Counter32,
      pr1646v2VxlBGIMVpH2PerfFloods
         Counter32,
      pr1646v2VxlBGIMVpH2PerfBroadcasts
         Counter32,
      pr1646v2VxlBGIMVpH2PerfMulticasts
         Counter32,
      pr1646v2VxlBGIMVpH2PerfCacheSizeOverflows
         Counter32,
      pr1646v2VxlBGIMVpH2PerfStaticCacheViolations
         Counter32,
      pr1646v2VxlBGIMVpH2PerfCacheRelearns
         Counter32,
      pr1646v2VxlBGIMVpH2PerfCacheRelearnDrops
         Counter32,
      pr1646v2VxlBGIMVpH2PerfCacheVteRelearns
         Counter32,
      pr1646v2VxlBGIMVpH2PerfLoopsDetected
         Counter32
      }

pr1646v2VxlBGIMVpH2PerfGlobalIx OBJECT-TYPE
   SYNTAX      GlobalIndex
   MAX-ACCESS  not-accessible
   STATUS      current
   DESCRIPTION
      "The value of the tlsCntTreeGlobalIndex of the MANAGED OBJECT."
   ::= {pr1646v2VxlBGIMVpH2PerfEntry 10}

pr1646v2VxlBGIMVpH2PerfTableIx OBJECT-TYPE
   SYNTAX      TableIndex
   MAX-ACCESS  not-accessible
   STATUS      current
   DESCRIPTION
      ""
   ::= {pr1646v2VxlBGIMVpH2PerfEntry 11}

pr1646v2VxlBGIMVpH2PerfSysUpTime OBJECT-TYPE
   SYNTAX      TimeTicks
   MAX-ACCESS  read-only
   STATUS      current
   DESCRIPTION
      "Path: vxLanBridgeGroup.performance.h2Performance.sysUpTime

       Time in centi-second."
   ::= {pr1646v2VxlBGIMVpH2PerfEntry 16777216}

pr1646v2VxlBGIMVpH2PerfRxPkts OBJECT-TYPE
   SYNTAX      Counter32
   MAX-ACCESS  read-only
   STATUS      current
   DESCRIPTION
      "Path: vxLanBridgeGroup.performance.h2Performance.rxPkts

       32 bit unsigned wrappable counter."
   ::= {pr1646v2VxlBGIMVpH2PerfEntry 33554432}

pr1646v2VxlBGIMVpH2PerfTxPkts OBJECT-TYPE
   SYNTAX      Counter32
   MAX-ACCESS  read-only
   STATUS      current
   DESCRIPTION
      "Path: vxLanBridgeGroup.performance.h2Performance.txPkts

       32 bit unsigned wrappable counter."
   ::= {pr1646v2VxlBGIMVpH2PerfEntry 50331648}

pr1646v2VxlBGIMVpH2PerfDiscards OBJECT-TYPE
   SYNTAX      Counter32
   MAX-ACCESS  read-only
   STATUS      current
   DESCRIPTION
      "Path: vxLanBridgeGroup.performance.h2Performance.discards

       32 bit unsigned wrappable counter."
   ::= {pr1646v2VxlBGIMVpH2PerfEntry 67108864}

pr1646v2VxlBGIMVpH2PerfFloods OBJECT-TYPE
   SYNTAX      Counter32
   MAX-ACCESS  read-only
   STATUS      current
   DESCRIPTION
      "Path: vxLanBridgeGroup.performance.h2Performance.floods

       32 bit unsigned wrappable counter."
   ::= {pr1646v2VxlBGIMVpH2PerfEntry 83886080}

pr1646v2VxlBGIMVpH2PerfBroadcasts OBJECT-TYPE
   SYNTAX      Counter32
   MAX-ACCESS  read-only
   STATUS      current
   DESCRIPTION
      "Path: vxLanBridgeGroup.performance.h2Performance.broadcasts

       32 bit unsigned wrappable counter."
   ::= {pr1646v2VxlBGIMVpH2PerfEntry 100663296}

pr1646v2VxlBGIMVpH2PerfMulticasts OBJECT-TYPE
   SYNTAX      Counter32
   MAX-ACCESS  read-only
   STATUS      current
   DESCRIPTION
      "Path: vxLanBridgeGroup.performance.h2Performance.multicasts

       32 bit unsigned wrappable counter."
   ::= {pr1646v2VxlBGIMVpH2PerfEntry 117440512}

pr1646v2VxlBGIMVpH2PerfCacheSizeOverflows OBJECT-TYPE
   SYNTAX      Counter32
   MAX-ACCESS  read-only
   STATUS      current
   DESCRIPTION
      "Path: vxLanBridgeGroup.performance.h2Performance.cacheSizeOverflows

       32 bit unsigned wrappable counter."
   ::= {pr1646v2VxlBGIMVpH2PerfEntry 134217728}

pr1646v2VxlBGIMVpH2PerfStaticCacheViolations OBJECT-TYPE
   SYNTAX      Counter32
   MAX-ACCESS  read-only
   STATUS      current
   DESCRIPTION
      "Path: vxLanBridgeGroup.performance.h2Performance.staticCacheViolations

       32 bit unsigned wrappable counter."
   ::= {pr1646v2VxlBGIMVpH2PerfEntry 150994944}

pr1646v2VxlBGIMVpH2PerfCacheRelearns OBJECT-TYPE
   SYNTAX      Counter32
   MAX-ACCESS  read-only
   STATUS      current
   DESCRIPTION
      "Path: vxLanBridgeGroup.performance.h2Performance.cacheRelearns

       32 bit unsigned wrappable counter."
   ::= {pr1646v2VxlBGIMVpH2PerfEntry 167772160}

pr1646v2VxlBGIMVpH2PerfCacheRelearnDrops OBJECT-TYPE
   SYNTAX      Counter32
   MAX-ACCESS  read-only
   STATUS      current
   DESCRIPTION
      "Path: vxLanBridgeGroup.performance.h2Performance.cacheRelearnDrops

       32 bit unsigned wrappable counter."
   ::= {pr1646v2VxlBGIMVpH2PerfEntry 184549376}

pr1646v2VxlBGIMVpH2PerfCacheVteRelearns OBJECT-TYPE
   SYNTAX      Counter32
   MAX-ACCESS  read-only
   STATUS      current
   DESCRIPTION
      "Path: vxLanBridgeGroup.performance.h2Performance.cacheVteRelearns

       32 bit unsigned wrappable counter."
   ::= {pr1646v2VxlBGIMVpH2PerfEntry 201326592}

pr1646v2VxlBGIMVpH2PerfLoopsDetected OBJECT-TYPE
   SYNTAX      Counter32
   MAX-ACCESS  read-only
   STATUS      current
   DESCRIPTION
      "Path: vxLanBridgeGroup.performance.h2Performance.loopsDetected

       32 bit unsigned wrappable counter."
   ::= {pr1646v2VxlBGIMVpH2PerfEntry 234881024}


pr1646v2VxlBGIMVpH24Perf OBJECT IDENTIFIER ::= {pr1646v2VxlBGIMVp 92}

pr1646v2VxlBGIMVpH24PerfSSCTable OBJECT-TYPE
   SYNTAX      SEQUENCE OF Pr1646v2VxlBGIMVpH24PerfEntry
   MAX-ACCESS  not-accessible
   STATUS      current
   DESCRIPTION
      "24 hour bridge stats"
   ::= {pr1646v2VxlBGIMVpH24Perf 1}

pr1646v2VxlBGIMVpH24PerfEntry OBJECT-TYPE
   SYNTAX      Pr1646v2VxlBGIMVpH24PerfEntry
   MAX-ACCESS  not-accessible
   STATUS      current
   DESCRIPTION
      ""
   INDEX      { pr1646v2VxlBGIMVpH24PerfGlobalIx,
                pr1646v2VxlBGIMVpH24PerfTableIx }
   ::= {pr1646v2VxlBGIMVpH24PerfSSCTable 1}

Pr1646v2VxlBGIMVpH24PerfEntry ::=
   SEQUENCE
      {
      pr1646v2VxlBGIMVpH24PerfGlobalIx
         GlobalIndex,
      pr1646v2VxlBGIMVpH24PerfTableIx
         TableIndex,
      pr1646v2VxlBGIMVpH24PerfSysUpTime
         TimeTicks,
      pr1646v2VxlBGIMVpH24PerfRxPkts
         Counter32,
      pr1646v2VxlBGIMVpH24PerfTxPkts
         Counter32,
      pr1646v2VxlBGIMVpH24PerfDiscards
         Counter32,
      pr1646v2VxlBGIMVpH24PerfFloods
         Counter32,
      pr1646v2VxlBGIMVpH24PerfBroadcasts
         Counter32,
      pr1646v2VxlBGIMVpH24PerfMulticasts
         Counter32,
      pr1646v2VxlBGIMVpH24PerfCacheSizeOverflows
         Counter32,
      pr1646v2VxlBGIMVpH24PerfStaticCacheViolations
         Counter32,
      pr1646v2VxlBGIMVpH24PerfCacheRelearns
         Counter32,
      pr1646v2VxlBGIMVpH24PerfCacheRelearnDrops
         Counter32,
      pr1646v2VxlBGIMVpH24PerfCacheVteRelearns
         Counter32,
      pr1646v2VxlBGIMVpH24PerfLoopsDetected
         Counter32
      }

pr1646v2VxlBGIMVpH24PerfGlobalIx OBJECT-TYPE
   SYNTAX      GlobalIndex
   MAX-ACCESS  not-accessible
   STATUS      current
   DESCRIPTION
      "The value of the tlsCntTreeGlobalIndex of the MANAGED OBJECT."
   ::= {pr1646v2VxlBGIMVpH24PerfEntry 10}

pr1646v2VxlBGIMVpH24PerfTableIx OBJECT-TYPE
   SYNTAX      TableIndex
   MAX-ACCESS  not-accessible
   STATUS      current
   DESCRIPTION
      ""
   ::= {pr1646v2VxlBGIMVpH24PerfEntry 11}

pr1646v2VxlBGIMVpH24PerfSysUpTime OBJECT-TYPE
   SYNTAX      TimeTicks
   MAX-ACCESS  read-only
   STATUS      current
   DESCRIPTION
      "Path: vxLanBridgeGroup.performance.h24Performance.sysUpTime

       Time in centi-second."
   ::= {pr1646v2VxlBGIMVpH24PerfEntry 16777216}

pr1646v2VxlBGIMVpH24PerfRxPkts OBJECT-TYPE
   SYNTAX      Counter32
   MAX-ACCESS  read-only
   STATUS      current
   DESCRIPTION
      "Path: vxLanBridgeGroup.performance.h24Performance.rxPkts

       32 bit unsigned wrappable counter."
   ::= {pr1646v2VxlBGIMVpH24PerfEntry 33554432}

pr1646v2VxlBGIMVpH24PerfTxPkts OBJECT-TYPE
   SYNTAX      Counter32
   MAX-ACCESS  read-only
   STATUS      current
   DESCRIPTION
      "Path: vxLanBridgeGroup.performance.h24Performance.txPkts

       32 bit unsigned wrappable counter."
   ::= {pr1646v2VxlBGIMVpH24PerfEntry 50331648}

pr1646v2VxlBGIMVpH24PerfDiscards OBJECT-TYPE
   SYNTAX      Counter32
   MAX-ACCESS  read-only
   STATUS      current
   DESCRIPTION
      "Path: vxLanBridgeGroup.performance.h24Performance.discards

       32 bit unsigned wrappable counter."
   ::= {pr1646v2VxlBGIMVpH24PerfEntry 67108864}

pr1646v2VxlBGIMVpH24PerfFloods OBJECT-TYPE
   SYNTAX      Counter32
   MAX-ACCESS  read-only
   STATUS      current
   DESCRIPTION
      "Path: vxLanBridgeGroup.performance.h24Performance.floods

       32 bit unsigned wrappable counter."
   ::= {pr1646v2VxlBGIMVpH24PerfEntry 83886080}

pr1646v2VxlBGIMVpH24PerfBroadcasts OBJECT-TYPE
   SYNTAX      Counter32
   MAX-ACCESS  read-only
   STATUS      current
   DESCRIPTION
      "Path: vxLanBridgeGroup.performance.h24Performance.broadcasts

       32 bit unsigned wrappable counter."
   ::= {pr1646v2VxlBGIMVpH24PerfEntry 100663296}

pr1646v2VxlBGIMVpH24PerfMulticasts OBJECT-TYPE
   SYNTAX      Counter32
   MAX-ACCESS  read-only
   STATUS      current
   DESCRIPTION
      "Path: vxLanBridgeGroup.performance.h24Performance.multicasts

       32 bit unsigned wrappable counter."
   ::= {pr1646v2VxlBGIMVpH24PerfEntry 117440512}

pr1646v2VxlBGIMVpH24PerfCacheSizeOverflows OBJECT-TYPE
   SYNTAX      Counter32
   MAX-ACCESS  read-only
   STATUS      current
   DESCRIPTION
      "Path: vxLanBridgeGroup.performance.h24Performance.cacheSizeOverflows

       32 bit unsigned wrappable counter."
   ::= {pr1646v2VxlBGIMVpH24PerfEntry 134217728}

pr1646v2VxlBGIMVpH24PerfStaticCacheViolations OBJECT-TYPE
   SYNTAX      Counter32
   MAX-ACCESS  read-only
   STATUS      current
   DESCRIPTION
      "Path: vxLanBridgeGroup.performance.h24Performance.staticCacheViolations

       32 bit unsigned wrappable counter."
   ::= {pr1646v2VxlBGIMVpH24PerfEntry 150994944}

pr1646v2VxlBGIMVpH24PerfCacheRelearns OBJECT-TYPE
   SYNTAX      Counter32
   MAX-ACCESS  read-only
   STATUS      current
   DESCRIPTION
      "Path: vxLanBridgeGroup.performance.h24Performance.cacheRelearns

       32 bit unsigned wrappable counter."
   ::= {pr1646v2VxlBGIMVpH24PerfEntry 167772160}

pr1646v2VxlBGIMVpH24PerfCacheRelearnDrops OBJECT-TYPE
   SYNTAX      Counter32
   MAX-ACCESS  read-only
   STATUS      current
   DESCRIPTION
      "Path: vxLanBridgeGroup.performance.h24Performance.cacheRelearnDrops

       32 bit unsigned wrappable counter."
   ::= {pr1646v2VxlBGIMVpH24PerfEntry 184549376}

pr1646v2VxlBGIMVpH24PerfCacheVteRelearns OBJECT-TYPE
   SYNTAX      Counter32
   MAX-ACCESS  read-only
   STATUS      current
   DESCRIPTION
      "Path: vxLanBridgeGroup.performance.h24Performance.cacheVteRelearns

       32 bit unsigned wrappable counter."
   ::= {pr1646v2VxlBGIMVpH24PerfEntry 201326592}

pr1646v2VxlBGIMVpH24PerfLoopsDetected OBJECT-TYPE
   SYNTAX      Counter32
   MAX-ACCESS  read-only
   STATUS      current
   DESCRIPTION
      "Path: vxLanBridgeGroup.performance.h24Performance.loopsDetected

       32 bit unsigned wrappable counter."
   ::= {pr1646v2VxlBGIMVpH24PerfEntry 234881024}


pr1646v2VxlBGIMVpD7Perf OBJECT IDENTIFIER ::= {pr1646v2VxlBGIMVp 93}

pr1646v2VxlBGIMVpD7PerfSSCTable OBJECT-TYPE
   SYNTAX      SEQUENCE OF Pr1646v2VxlBGIMVpD7PerfEntry
   MAX-ACCESS  not-accessible
   STATUS      current
   DESCRIPTION
      "7 days bridge stats"
   ::= {pr1646v2VxlBGIMVpD7Perf 1}

pr1646v2VxlBGIMVpD7PerfEntry OBJECT-TYPE
   SYNTAX      Pr1646v2VxlBGIMVpD7PerfEntry
   MAX-ACCESS  not-accessible
   STATUS      current
   DESCRIPTION
      ""
   INDEX      { pr1646v2VxlBGIMVpD7PerfGlobalIx,
                pr1646v2VxlBGIMVpD7PerfTableIx }
   ::= {pr1646v2VxlBGIMVpD7PerfSSCTable 1}

Pr1646v2VxlBGIMVpD7PerfEntry ::=
   SEQUENCE
      {
      pr1646v2VxlBGIMVpD7PerfGlobalIx
         GlobalIndex,
      pr1646v2VxlBGIMVpD7PerfTableIx
         TableIndex,
      pr1646v2VxlBGIMVpD7PerfSysUpTime
         TimeTicks,
      pr1646v2VxlBGIMVpD7PerfRxPkts
         Counter32,
      pr1646v2VxlBGIMVpD7PerfTxPkts
         Counter32,
      pr1646v2VxlBGIMVpD7PerfDiscards
         Counter32,
      pr1646v2VxlBGIMVpD7PerfFloods
         Counter32,
      pr1646v2VxlBGIMVpD7PerfBroadcasts
         Counter32,
      pr1646v2VxlBGIMVpD7PerfMulticasts
         Counter32,
      pr1646v2VxlBGIMVpD7PerfCacheSizeOverflows
         Counter32,
      pr1646v2VxlBGIMVpD7PerfStaticCacheViolations
         Counter32,
      pr1646v2VxlBGIMVpD7PerfCacheRelearns
         Counter32,
      pr1646v2VxlBGIMVpD7PerfCacheRelearnDrops
         Counter32,
      pr1646v2VxlBGIMVpD7PerfCacheVteRelearns
         Counter32,
      pr1646v2VxlBGIMVpD7PerfLoopsDetected
         Counter32
      }

pr1646v2VxlBGIMVpD7PerfGlobalIx OBJECT-TYPE
   SYNTAX      GlobalIndex
   MAX-ACCESS  not-accessible
   STATUS      current
   DESCRIPTION
      "The value of the tlsCntTreeGlobalIndex of the MANAGED OBJECT."
   ::= {pr1646v2VxlBGIMVpD7PerfEntry 10}

pr1646v2VxlBGIMVpD7PerfTableIx OBJECT-TYPE
   SYNTAX      TableIndex
   MAX-ACCESS  not-accessible
   STATUS      current
   DESCRIPTION
      ""
   ::= {pr1646v2VxlBGIMVpD7PerfEntry 11}

pr1646v2VxlBGIMVpD7PerfSysUpTime OBJECT-TYPE
   SYNTAX      TimeTicks
   MAX-ACCESS  read-only
   STATUS      current
   DESCRIPTION
      "Path: vxLanBridgeGroup.performance.d7Performance.sysUpTime

       Time in centi-second."
   ::= {pr1646v2VxlBGIMVpD7PerfEntry 16777216}

pr1646v2VxlBGIMVpD7PerfRxPkts OBJECT-TYPE
   SYNTAX      Counter32
   MAX-ACCESS  read-only
   STATUS      current
   DESCRIPTION
      "Path: vxLanBridgeGroup.performance.d7Performance.rxPkts

       32 bit unsigned wrappable counter."
   ::= {pr1646v2VxlBGIMVpD7PerfEntry 33554432}

pr1646v2VxlBGIMVpD7PerfTxPkts OBJECT-TYPE
   SYNTAX      Counter32
   MAX-ACCESS  read-only
   STATUS      current
   DESCRIPTION
      "Path: vxLanBridgeGroup.performance.d7Performance.txPkts

       32 bit unsigned wrappable counter."
   ::= {pr1646v2VxlBGIMVpD7PerfEntry 50331648}

pr1646v2VxlBGIMVpD7PerfDiscards OBJECT-TYPE
   SYNTAX      Counter32
   MAX-ACCESS  read-only
   STATUS      current
   DESCRIPTION
      "Path: vxLanBridgeGroup.performance.d7Performance.discards

       32 bit unsigned wrappable counter."
   ::= {pr1646v2VxlBGIMVpD7PerfEntry 67108864}

pr1646v2VxlBGIMVpD7PerfFloods OBJECT-TYPE
   SYNTAX      Counter32
   MAX-ACCESS  read-only
   STATUS      current
   DESCRIPTION
      "Path: vxLanBridgeGroup.performance.d7Performance.floods

       32 bit unsigned wrappable counter."
   ::= {pr1646v2VxlBGIMVpD7PerfEntry 83886080}

pr1646v2VxlBGIMVpD7PerfBroadcasts OBJECT-TYPE
   SYNTAX      Counter32
   MAX-ACCESS  read-only
   STATUS      current
   DESCRIPTION
      "Path: vxLanBridgeGroup.performance.d7Performance.broadcasts

       32 bit unsigned wrappable counter."
   ::= {pr1646v2VxlBGIMVpD7PerfEntry 100663296}

pr1646v2VxlBGIMVpD7PerfMulticasts OBJECT-TYPE
   SYNTAX      Counter32
   MAX-ACCESS  read-only
   STATUS      current
   DESCRIPTION
      "Path: vxLanBridgeGroup.performance.d7Performance.multicasts

       32 bit unsigned wrappable counter."
   ::= {pr1646v2VxlBGIMVpD7PerfEntry 117440512}

pr1646v2VxlBGIMVpD7PerfCacheSizeOverflows OBJECT-TYPE
   SYNTAX      Counter32
   MAX-ACCESS  read-only
   STATUS      current
   DESCRIPTION
      "Path: vxLanBridgeGroup.performance.d7Performance.cacheSizeOverflows

       32 bit unsigned wrappable counter."
   ::= {pr1646v2VxlBGIMVpD7PerfEntry 134217728}

pr1646v2VxlBGIMVpD7PerfStaticCacheViolations OBJECT-TYPE
   SYNTAX      Counter32
   MAX-ACCESS  read-only
   STATUS      current
   DESCRIPTION
      "Path: vxLanBridgeGroup.performance.d7Performance.staticCacheViolations

       32 bit unsigned wrappable counter."
   ::= {pr1646v2VxlBGIMVpD7PerfEntry 150994944}

pr1646v2VxlBGIMVpD7PerfCacheRelearns OBJECT-TYPE
   SYNTAX      Counter32
   MAX-ACCESS  read-only
   STATUS      current
   DESCRIPTION
      "Path: vxLanBridgeGroup.performance.d7Performance.cacheRelearns

       32 bit unsigned wrappable counter."
   ::= {pr1646v2VxlBGIMVpD7PerfEntry 167772160}

pr1646v2VxlBGIMVpD7PerfCacheRelearnDrops OBJECT-TYPE
   SYNTAX      Counter32
   MAX-ACCESS  read-only
   STATUS      current
   DESCRIPTION
      "Path: vxLanBridgeGroup.performance.d7Performance.cacheRelearnDrops

       32 bit unsigned wrappable counter."
   ::= {pr1646v2VxlBGIMVpD7PerfEntry 184549376}

pr1646v2VxlBGIMVpD7PerfCacheVteRelearns OBJECT-TYPE
   SYNTAX      Counter32
   MAX-ACCESS  read-only
   STATUS      current
   DESCRIPTION
      "Path: vxLanBridgeGroup.performance.d7Performance.cacheVteRelearns

       32 bit unsigned wrappable counter."
   ::= {pr1646v2VxlBGIMVpD7PerfEntry 201326592}

pr1646v2VxlBGIMVpD7PerfLoopsDetected OBJECT-TYPE
   SYNTAX      Counter32
   MAX-ACCESS  read-only
   STATUS      current
   DESCRIPTION
      "Path: vxLanBridgeGroup.performance.d7Performance.loopsDetected

       32 bit unsigned wrappable counter."
   ::= {pr1646v2VxlBGIMVpD7PerfEntry 234881024}



fr1646v2VxlBGIMVp OBJECT IDENTIFIER ::= {r1646v2VxlBGIMVp 13}


fr1646v2VxlBGIMVpAlarm OBJECT IDENTIFIER ::= {fr1646v2VxlBGIMVp 207}

fr1646v2VxlBGIMVpAlarmSSCTable OBJECT-TYPE
   SYNTAX      SEQUENCE OF Fr1646v2VxlBGIMVpAlarmEntry
   MAX-ACCESS  not-accessible
   STATUS      current
   DESCRIPTION
      "bridge group alarmInfo"
   ::= {fr1646v2VxlBGIMVpAlarm 1}

fr1646v2VxlBGIMVpAlarmEntry OBJECT-TYPE
   SYNTAX      Fr1646v2VxlBGIMVpAlarmEntry
   MAX-ACCESS  not-accessible
   STATUS      current
   DESCRIPTION
      ""
   INDEX      { fr1646v2VxlBGIMVpAlarmGlobalIx }
   ::= {fr1646v2VxlBGIMVpAlarmSSCTable 1}

Fr1646v2VxlBGIMVpAlarmEntry ::=
   SEQUENCE
      {
      fr1646v2VxlBGIMVpAlarmGlobalIx
         GlobalIndex,
      fr1646v2VxlBGIMVpAlarmDiscriminator
         Integer32,
      fr1646v2VxlBGIMVpAlarmCurrent
         Integer32,
      fr1646v2VxlBGIMVpAlarmPrevious
         Integer32,
      fr1646v2VxlBGIMVpAlarmMask
         Integer32,
      fr1646v2VxlBGIMVpAlarmLevelLinkDown
         Integer32,
      fr1646v2VxlBGIMVpAlarmLevelLinkShutdown
         Integer32
      }

fr1646v2VxlBGIMVpAlarmGlobalIx OBJECT-TYPE
   SYNTAX      GlobalIndex
   MAX-ACCESS  not-accessible
   STATUS      current
   DESCRIPTION
      "The value of the tlsCntTreeGlobalIndex of the MANAGED OBJECT."
   ::= {fr1646v2VxlBGIMVpAlarmEntry 10}

fr1646v2VxlBGIMVpAlarmDiscriminator OBJECT-TYPE
   SYNTAX      Integer32
   MAX-ACCESS  read-only
   STATUS      current
   DESCRIPTION
      "Path: vxLanBridgeGroup.alarms.alarmInfo.discriminator"
   ::= {fr1646v2VxlBGIMVpAlarmEntry 16777216}

fr1646v2VxlBGIMVpAlarmCurrent OBJECT-TYPE
   SYNTAX      Integer32
   MAX-ACCESS  read-only
   STATUS      current
   DESCRIPTION
      "Path: vxLanBridgeGroup.alarms.alarmInfo.currentAlarms

       Bit meanings:
               bit 0 = linkDown,
               bit 1 = linkShutdown"
   ::= {fr1646v2VxlBGIMVpAlarmEntry 33554432}

fr1646v2VxlBGIMVpAlarmPrevious OBJECT-TYPE
   SYNTAX      Integer32
   MAX-ACCESS  read-only
   STATUS      current
   DESCRIPTION
      "Path: vxLanBridgeGroup.alarms.alarmInfo.previousAlarms

       Bit meanings:
               bit 0 = linkDown,
               bit 1 = linkShutdown"
   ::= {fr1646v2VxlBGIMVpAlarmEntry 50331648}

fr1646v2VxlBGIMVpAlarmMask OBJECT-TYPE
   SYNTAX      Integer32
   MAX-ACCESS  read-only
   STATUS      current
   DESCRIPTION
      "Path: vxLanBridgeGroup.alarms.alarmInfo.alarmMask

       Bit meanings:
               bit 0 = linkDown,
               bit 1 = linkShutdown"
   ::= {fr1646v2VxlBGIMVpAlarmEntry 67108864}

fr1646v2VxlBGIMVpAlarmLevelLinkDown OBJECT-TYPE
   SYNTAX      Integer32
   MAX-ACCESS  read-only
   STATUS      current
   DESCRIPTION
      "Path: vxLanBridgeGroup.alarms.alarmInfo.alarmLevel.linkDown"
   ::= {fr1646v2VxlBGIMVpAlarmEntry 83951616}

fr1646v2VxlBGIMVpAlarmLevelLinkShutdown OBJECT-TYPE
   SYNTAX      Integer32
   MAX-ACCESS  read-only
   STATUS      current
   DESCRIPTION
      "Path: vxLanBridgeGroup.alarms.alarmInfo.alarmLevel.linkShutdown"
   ::= {fr1646v2VxlBGIMVpAlarmEntry 84017152}


fr1646v2VxlBGIMVpAlarmE2 OBJECT IDENTIFIER ::= {fr1646v2VxlBGIMVpAlarm 2}

fr1646v2VxlBGIMVpAlarmE2Entry OBJECT IDENTIFIER ::= {fr1646v2VxlBGIMVpAlarmE2 1}

fr1646v2VxlBGIMVpAlarmE2LinkDown OBJECT IDENTIFIER ::= {fr1646v2VxlBGIMVpAlarmE2Entry 10}

fr1646v2VxlBGIMVpAlarmE2LinkDownPfx OBJECT IDENTIFIER ::= {fr1646v2VxlBGIMVpAlarmE2LinkDown 0}

fr1646v2VxlBGIMVpAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'vxLanBridgeGroupInstanceEth1'
                (root='router1646') has changed from the ON to the OFF state."
   ::= {fr1646v2VxlBGIMVpAlarmE2LinkDownPfx 1}

fr1646v2VxlBGIMVpAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'vxLanBridgeGroupInstanceEth1'
                (root='router1646') has changed from the OFF to the ON state."
   ::= {fr1646v2VxlBGIMVpAlarmE2LinkDownPfx 2}

fr1646v2VxlBGIMVpAlarmE2LinkShutdown OBJECT IDENTIFIER ::= {fr1646v2VxlBGIMVpAlarmE2Entry 11}

fr1646v2VxlBGIMVpAlarmE2LinkShutdownPfx OBJECT IDENTIFIER ::= {fr1646v2VxlBGIMVpAlarmE2LinkShutdown 0}

fr1646v2VxlBGIMVpAlarmE2LinkShutdownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'vxLanBridgeGroupInstanceEth1'
                (root='router1646') has changed from the ON to the OFF state."
   ::= {fr1646v2VxlBGIMVpAlarmE2LinkShutdownPfx 1}

fr1646v2VxlBGIMVpAlarmE2LinkShutdownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'vxLanBridgeGroupInstanceEth1'
                (root='router1646') has changed from the OFF to the ON state."
   ::= {fr1646v2VxlBGIMVpAlarmE2LinkShutdownPfx 2}



ar1646v2VxlBGIMVp OBJECT IDENTIFIER ::= {r1646v2VxlBGIMVp 16}


ar1646v2VxlBGIMVpClearCounters OBJECT IDENTIFIER ::= {ar1646v2VxlBGIMVp 263}

ar1646v2VxlBGIMVpClearCountersTable OBJECT-TYPE
   SYNTAX      SEQUENCE OF Ar1646v2VxlBGIMVpClearCountersEntry
   MAX-ACCESS  not-accessible
   STATUS      current
   DESCRIPTION
      "reset counters"
   ::= {ar1646v2VxlBGIMVpClearCounters 1}

ar1646v2VxlBGIMVpClearCountersEntry OBJECT-TYPE
   SYNTAX      Ar1646v2VxlBGIMVpClearCountersEntry
   MAX-ACCESS  not-accessible
   STATUS      current
   DESCRIPTION
      ""
   INDEX      { ar1646v2VxlBGIMVpClearCountersGlobalIx }
   ::= {ar1646v2VxlBGIMVpClearCountersTable 1}

Ar1646v2VxlBGIMVpClearCountersEntry ::=
   SEQUENCE
      {
      ar1646v2VxlBGIMVpClearCountersGlobalIx
         GlobalIndex,
      ar1646v2VxlBGIMVpClearCountersValue
         Integer32
      }

ar1646v2VxlBGIMVpClearCountersGlobalIx OBJECT-TYPE
   SYNTAX      GlobalIndex
   MAX-ACCESS  not-accessible
   STATUS      current
   DESCRIPTION
      "The value of the tlsCntTreeGlobalIndex of the MANAGED OBJECT."
   ::= {ar1646v2VxlBGIMVpClearCountersEntry 10}

ar1646v2VxlBGIMVpClearCountersValue OBJECT-TYPE
   SYNTAX      Integer32
   MAX-ACCESS  read-write
   STATUS      current
   DESCRIPTION
      "Path: vxLanBridgeGroup.actions.clearCounters"
   ::= {ar1646v2VxlBGIMVpClearCountersEntry 2147483648}


ar1646v2VxlBGIMVpClearBridgeCache OBJECT IDENTIFIER ::= {ar1646v2VxlBGIMVp 20}

ar1646v2VxlBGIMVpClearBridgeCacheTable OBJECT-TYPE
   SYNTAX      SEQUENCE OF Ar1646v2VxlBGIMVpClearBridgeCacheEntry
   MAX-ACCESS  not-accessible
   STATUS      current
   DESCRIPTION
      "clear all dynamic entries in bridge cache table"
   ::= {ar1646v2VxlBGIMVpClearBridgeCache 1}

ar1646v2VxlBGIMVpClearBridgeCacheEntry OBJECT-TYPE
   SYNTAX      Ar1646v2VxlBGIMVpClearBridgeCacheEntry
   MAX-ACCESS  not-accessible
   STATUS      current
   DESCRIPTION
      ""
   INDEX      { ar1646v2VxlBGIMVpClearBridgeCacheGlobalIx }
   ::= {ar1646v2VxlBGIMVpClearBridgeCacheTable 1}

Ar1646v2VxlBGIMVpClearBridgeCacheEntry ::=
   SEQUENCE
      {
      ar1646v2VxlBGIMVpClearBridgeCacheGlobalIx
         GlobalIndex,
      ar1646v2VxlBGIMVpClearBridgeCacheValue
         Integer32
      }

ar1646v2VxlBGIMVpClearBridgeCacheGlobalIx OBJECT-TYPE
   SYNTAX      GlobalIndex
   MAX-ACCESS  not-accessible
   STATUS      current
   DESCRIPTION
      "The value of the tlsCntTreeGlobalIndex of the MANAGED OBJECT."
   ::= {ar1646v2VxlBGIMVpClearBridgeCacheEntry 10}

ar1646v2VxlBGIMVpClearBridgeCacheValue OBJECT-TYPE
   SYNTAX      Integer32
   MAX-ACCESS  read-write
   STATUS      current
   DESCRIPTION
      "Path: vxLanBridgeGroup.actions.clearBridgeCache"
   ::= {ar1646v2VxlBGIMVpClearBridgeCacheEntry 2147483648}


ar1646v2VxlBGIMVpBridgeShutdown OBJECT IDENTIFIER ::= {ar1646v2VxlBGIMVp 72}

ar1646v2VxlBGIMVpBridgeShutdownTable OBJECT-TYPE
   SYNTAX      SEQUENCE OF Ar1646v2VxlBGIMVpBridgeShutdownEntry
   MAX-ACCESS  not-accessible
   STATUS      current
   DESCRIPTION
      "shutdown interface manually"
   ::= {ar1646v2VxlBGIMVpBridgeShutdown 1}

ar1646v2VxlBGIMVpBridgeShutdownEntry OBJECT-TYPE
   SYNTAX      Ar1646v2VxlBGIMVpBridgeShutdownEntry
   MAX-ACCESS  not-accessible
   STATUS      current
   DESCRIPTION
      ""
   INDEX      { ar1646v2VxlBGIMVpBridgeShutdownGlobalIx }
   ::= {ar1646v2VxlBGIMVpBridgeShutdownTable 1}

Ar1646v2VxlBGIMVpBridgeShutdownEntry ::=
   SEQUENCE
      {
      ar1646v2VxlBGIMVpBridgeShutdownGlobalIx
         GlobalIndex,
      ar1646v2VxlBGIMVpBridgeShutdownValue
         Integer32
      }

ar1646v2VxlBGIMVpBridgeShutdownGlobalIx OBJECT-TYPE
   SYNTAX      GlobalIndex
   MAX-ACCESS  not-accessible
   STATUS      current
   DESCRIPTION
      "The value of the tlsCntTreeGlobalIndex of the MANAGED OBJECT."
   ::= {ar1646v2VxlBGIMVpBridgeShutdownEntry 10}

ar1646v2VxlBGIMVpBridgeShutdownValue OBJECT-TYPE
   SYNTAX      Integer32
   MAX-ACCESS  read-write
   STATUS      current
   DESCRIPTION
      "Path: vxLanBridgeGroup.actions.bridgeShutdown"
   ::= {ar1646v2VxlBGIMVpBridgeShutdownEntry 2147483648}


ar1646v2VxlBGIMVpInterface OBJECT IDENTIFIER ::= {ar1646v2VxlBGIMVp 73}

ar1646v2VxlBGIMVpInterfaceTable OBJECT-TYPE
   SYNTAX      SEQUENCE OF Ar1646v2VxlBGIMVpInterfaceEntry
   MAX-ACCESS  not-accessible
   STATUS      current
   DESCRIPTION
      "interface name for action"
   ::= {ar1646v2VxlBGIMVpInterface 1}

ar1646v2VxlBGIMVpInterfaceEntry OBJECT-TYPE
   SYNTAX      Ar1646v2VxlBGIMVpInterfaceEntry
   MAX-ACCESS  not-accessible
   STATUS      current
   DESCRIPTION
      ""
   INDEX      { ar1646v2VxlBGIMVpInterfaceGlobalIx }
   ::= {ar1646v2VxlBGIMVpInterfaceTable 1}

Ar1646v2VxlBGIMVpInterfaceEntry ::=
   SEQUENCE
      {
      ar1646v2VxlBGIMVpInterfaceGlobalIx
         GlobalIndex,
      ar1646v2VxlBGIMVpInterfaceValue
         DisplayString
      }

ar1646v2VxlBGIMVpInterfaceGlobalIx OBJECT-TYPE
   SYNTAX      GlobalIndex
   MAX-ACCESS  not-accessible
   STATUS      current
   DESCRIPTION
      "The value of the tlsCntTreeGlobalIndex of the MANAGED OBJECT."
   ::= {ar1646v2VxlBGIMVpInterfaceEntry 10}

ar1646v2VxlBGIMVpInterfaceValue OBJECT-TYPE
   SYNTAX      DisplayString
   MAX-ACCESS  read-write
   STATUS      current
   DESCRIPTION
      "Path: vxLanBridgeGroup.actions.interface"
   ::= {ar1646v2VxlBGIMVpInterfaceEntry 2147483648}


ar1646v2VxlBGIMVpBridgeRestart OBJECT IDENTIFIER ::= {ar1646v2VxlBGIMVp 70}

ar1646v2VxlBGIMVpBridgeRestartTable OBJECT-TYPE
   SYNTAX      SEQUENCE OF Ar1646v2VxlBGIMVpBridgeRestartEntry
   MAX-ACCESS  not-accessible
   STATUS      current
   DESCRIPTION
      "restart interface blocked by security"
   ::= {ar1646v2VxlBGIMVpBridgeRestart 1}

ar1646v2VxlBGIMVpBridgeRestartEntry OBJECT-TYPE
   SYNTAX      Ar1646v2VxlBGIMVpBridgeRestartEntry
   MAX-ACCESS  not-accessible
   STATUS      current
   DESCRIPTION
      ""
   INDEX      { ar1646v2VxlBGIMVpBridgeRestartGlobalIx }
   ::= {ar1646v2VxlBGIMVpBridgeRestartTable 1}

Ar1646v2VxlBGIMVpBridgeRestartEntry ::=
   SEQUENCE
      {
      ar1646v2VxlBGIMVpBridgeRestartGlobalIx
         GlobalIndex,
      ar1646v2VxlBGIMVpBridgeRestartValue
         Integer32
      }

ar1646v2VxlBGIMVpBridgeRestartGlobalIx OBJECT-TYPE
   SYNTAX      GlobalIndex
   MAX-ACCESS  not-accessible
   STATUS      current
   DESCRIPTION
      "The value of the tlsCntTreeGlobalIndex of the MANAGED OBJECT."
   ::= {ar1646v2VxlBGIMVpBridgeRestartEntry 10}

ar1646v2VxlBGIMVpBridgeRestartValue OBJECT-TYPE
   SYNTAX      Integer32
   MAX-ACCESS  read-write
   STATUS      current
   DESCRIPTION
      "Path: vxLanBridgeGroup.actions.bridgeRestart"
   ::= {ar1646v2VxlBGIMVpBridgeRestartEntry 2147483648}


ar1646v2VxlBGIMVpBridgingInterface OBJECT IDENTIFIER ::= {ar1646v2VxlBGIMVp 71}

ar1646v2VxlBGIMVpBridgingInterfaceTable OBJECT-TYPE
   SYNTAX      SEQUENCE OF Ar1646v2VxlBGIMVpBridgingInterfaceEntry
   MAX-ACCESS  not-accessible
   STATUS      current
   DESCRIPTION
      "interface name for action"
   ::= {ar1646v2VxlBGIMVpBridgingInterface 1}

ar1646v2VxlBGIMVpBridgingInterfaceEntry OBJECT-TYPE
   SYNTAX      Ar1646v2VxlBGIMVpBridgingInterfaceEntry
   MAX-ACCESS  not-accessible
   STATUS      current
   DESCRIPTION
      ""
   INDEX      { ar1646v2VxlBGIMVpBridgingInterfaceGlobalIx }
   ::= {ar1646v2VxlBGIMVpBridgingInterfaceTable 1}

Ar1646v2VxlBGIMVpBridgingInterfaceEntry ::=
   SEQUENCE
      {
      ar1646v2VxlBGIMVpBridgingInterfaceGlobalIx
         GlobalIndex,
      ar1646v2VxlBGIMVpBridgingInterfaceValue
         DisplayString
      }

ar1646v2VxlBGIMVpBridgingInterfaceGlobalIx OBJECT-TYPE
   SYNTAX      GlobalIndex
   MAX-ACCESS  not-accessible
   STATUS      current
   DESCRIPTION
      "The value of the tlsCntTreeGlobalIndex of the MANAGED OBJECT."
   ::= {ar1646v2VxlBGIMVpBridgingInterfaceEntry 10}

ar1646v2VxlBGIMVpBridgingInterfaceValue OBJECT-TYPE
   SYNTAX      DisplayString
   MAX-ACCESS  read-write
   STATUS      current
   DESCRIPTION
      "Path: vxLanBridgeGroup.actions.bridgingInterface"
   ::= {ar1646v2VxlBGIMVpBridgingInterfaceEntry 2147483648}


ar1646v2VxlBGIMVpClearArpCache OBJECT IDENTIFIER ::= {ar1646v2VxlBGIMVp 25}

ar1646v2VxlBGIMVpClearArpCacheTable OBJECT-TYPE
   SYNTAX      SEQUENCE OF Ar1646v2VxlBGIMVpClearArpCacheEntry
   MAX-ACCESS  not-accessible
   STATUS      current
   DESCRIPTION
      "clear all dynamic enties in ARP cache table"
   ::= {ar1646v2VxlBGIMVpClearArpCache 1}

ar1646v2VxlBGIMVpClearArpCacheEntry OBJECT-TYPE
   SYNTAX      Ar1646v2VxlBGIMVpClearArpCacheEntry
   MAX-ACCESS  not-accessible
   STATUS      current
   DESCRIPTION
      ""
   INDEX      { ar1646v2VxlBGIMVpClearArpCacheGlobalIx }
   ::= {ar1646v2VxlBGIMVpClearArpCacheTable 1}

Ar1646v2VxlBGIMVpClearArpCacheEntry ::=
   SEQUENCE
      {
      ar1646v2VxlBGIMVpClearArpCacheGlobalIx
         GlobalIndex,
      ar1646v2VxlBGIMVpClearArpCacheValue
         Integer32
      }

ar1646v2VxlBGIMVpClearArpCacheGlobalIx OBJECT-TYPE
   SYNTAX      GlobalIndex
   MAX-ACCESS  not-accessible
   STATUS      current
   DESCRIPTION
      "The value of the tlsCntTreeGlobalIndex of the MANAGED OBJECT."
   ::= {ar1646v2VxlBGIMVpClearArpCacheEntry 10}

ar1646v2VxlBGIMVpClearArpCacheValue OBJECT-TYPE
   SYNTAX      Integer32
   MAX-ACCESS  read-write
   STATUS      current
   DESCRIPTION
      "Path: vxLanBridgeGroup.actions.clearArpCache"
   ::= {ar1646v2VxlBGIMVpClearArpCacheEntry 2147483648}



END
