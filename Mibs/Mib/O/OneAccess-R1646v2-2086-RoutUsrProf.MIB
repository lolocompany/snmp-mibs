OneAccess-R1646v2-2086-RoutUsrProf DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2RoutUsrProf OBJECT IDENTIFIER ::= {r1646Rootv2 2086}

r1646v2RoutUsrProfMOProp OBJECT-TYPE
   SYNTAX      SEQUENCE OF R1646v2RoutUsrProfMOPropEntry
   MAX-ACCESS  not-accessible
   STATUS      current
   DESCRIPTION
      ""
   ::= {r1646v2RoutUsrProf 1}

r1646v2RoutUsrProfMOPropEntry OBJECT-TYPE
   SYNTAX      R1646v2RoutUsrProfMOPropEntry
   MAX-ACCESS  not-accessible
   STATUS      current
   DESCRIPTION
      ""
   INDEX      { r1646v2RoutUsrProfMOPropGlobalIx }
   ::= {r1646v2RoutUsrProfMOProp 1}

R1646v2RoutUsrProfMOPropEntry ::=
   SEQUENCE
      {
      r1646v2RoutUsrProfMOPropPath
         ContainmentPath,
      r1646v2RoutUsrProfMOPropRev
         ObjectRevision,
      r1646v2RoutUsrProfMOPropGlobalIx
         GlobalIndex
      }

r1646v2RoutUsrProfMOPropPath OBJECT-TYPE
   SYNTAX      ContainmentPath
   MAX-ACCESS  read-only
   STATUS      current
   DESCRIPTION
      "Textual description of the containment tree from the instance of
       the root object down to the instance of the current object."
   ::= {r1646v2RoutUsrProfMOPropEntry 3}

r1646v2RoutUsrProfMOPropRev OBJECT-TYPE
   SYNTAX      ObjectRevision
   MAX-ACCESS  read-only
   STATUS      current
   DESCRIPTION
      "This value corresponds with the revision of the MANAGED OBJECT."
   ::= {r1646v2RoutUsrProfMOPropEntry 4}

r1646v2RoutUsrProfMOPropGlobalIx OBJECT-TYPE
   SYNTAX      GlobalIndex
   MAX-ACCESS  read-only
   STATUS      current
   DESCRIPTION
      "The value of the tlsCntTreeGlobalIndex of the MANAGED OBJECT."
   ::= {r1646v2RoutUsrProfMOPropEntry 10}



er1646v2RoutUsrProf OBJECT IDENTIFIER ::= {r1646v2RoutUsrProf 11}


er1646v2RoutUsrProfPriorityPolicy OBJECT IDENTIFIER ::= {er1646v2RoutUsrProf 4}

er1646v2RoutUsrProfPriorityPolicyTable OBJECT-TYPE
   SYNTAX      SEQUENCE OF Er1646v2RoutUsrProfPriorityPolicyEntry
   MAX-ACCESS  not-accessible
   STATUS      current
   DESCRIPTION
      "Preferred Policy"
   ::= {er1646v2RoutUsrProfPriorityPolicy 1}

er1646v2RoutUsrProfPriorityPolicyEntry OBJECT-TYPE
   SYNTAX      Er1646v2RoutUsrProfPriorityPolicyEntry
   MAX-ACCESS  not-accessible
   STATUS      current
   DESCRIPTION
      ""
   INDEX      { er1646v2RoutUsrProfPriorityPolicyGlobalIx }
   ::= {er1646v2RoutUsrProfPriorityPolicyTable 1}

Er1646v2RoutUsrProfPriorityPolicyEntry ::=
   SEQUENCE
      {
      er1646v2RoutUsrProfPriorityPolicyGlobalIx
         GlobalIndex,
      er1646v2RoutUsrProfPriorityPolicyValue
         DisplayString
      }

er1646v2RoutUsrProfPriorityPolicyGlobalIx OBJECT-TYPE
   SYNTAX      GlobalIndex
   MAX-ACCESS  not-accessible
   STATUS      current
   DESCRIPTION
      "The value of the tlsCntTreeGlobalIndex of the MANAGED OBJECT."
   ::= {er1646v2RoutUsrProfPriorityPolicyEntry 10}

er1646v2RoutUsrProfPriorityPolicyValue OBJECT-TYPE
   SYNTAX      DisplayString
   MAX-ACCESS  read-write
   STATUS      current
   DESCRIPTION
      "Path: routing.editConf.priorityPolicy"
   ::= {er1646v2RoutUsrProfPriorityPolicyEntry 2147483648}


er1646v2RoutUsrProfMaxFifoQLen OBJECT IDENTIFIER ::= {er1646v2RoutUsrProf 5}

er1646v2RoutUsrProfMaxFifoQLenTable OBJECT-TYPE
   SYNTAX      SEQUENCE OF Er1646v2RoutUsrProfMaxFifoQLenEntry
   MAX-ACCESS  not-accessible
   STATUS      current
   DESCRIPTION
      "maximun queue length for fifo"
   ::= {er1646v2RoutUsrProfMaxFifoQLen 1}

er1646v2RoutUsrProfMaxFifoQLenEntry OBJECT-TYPE
   SYNTAX      Er1646v2RoutUsrProfMaxFifoQLenEntry
   MAX-ACCESS  not-accessible
   STATUS      current
   DESCRIPTION
      ""
   INDEX      { er1646v2RoutUsrProfMaxFifoQLenGlobalIx }
   ::= {er1646v2RoutUsrProfMaxFifoQLenTable 1}

Er1646v2RoutUsrProfMaxFifoQLenEntry ::=
   SEQUENCE
      {
      er1646v2RoutUsrProfMaxFifoQLenGlobalIx
         GlobalIndex,
      er1646v2RoutUsrProfMaxFifoQLenValue
         Integer32
      }

er1646v2RoutUsrProfMaxFifoQLenGlobalIx OBJECT-TYPE
   SYNTAX      GlobalIndex
   MAX-ACCESS  not-accessible
   STATUS      current
   DESCRIPTION
      "The value of the tlsCntTreeGlobalIndex of the MANAGED OBJECT."
   ::= {er1646v2RoutUsrProfMaxFifoQLenEntry 10}

er1646v2RoutUsrProfMaxFifoQLenValue OBJECT-TYPE
   SYNTAX      Integer32
   MAX-ACCESS  read-write
   STATUS      current
   DESCRIPTION
      "Path: routing.editConf.maxFifoQLen"
   ::= {er1646v2RoutUsrProfMaxFifoQLenEntry 2147483648}


er1646v2RoutUsrProfIp OBJECT IDENTIFIER ::= {er1646v2RoutUsrProf 2}

er1646v2RoutUsrProfIpSSCTable OBJECT-TYPE
   SYNTAX      SEQUENCE OF Er1646v2RoutUsrProfIpEntry
   MAX-ACCESS  not-accessible
   STATUS      current
   DESCRIPTION
      "ip routing configuration"
   ::= {er1646v2RoutUsrProfIp 1}

er1646v2RoutUsrProfIpEntry OBJECT-TYPE
   SYNTAX      Er1646v2RoutUsrProfIpEntry
   MAX-ACCESS  not-accessible
   STATUS      current
   DESCRIPTION
      ""
   INDEX      { er1646v2RoutUsrProfIpGlobalIx }
   ::= {er1646v2RoutUsrProfIpSSCTable 1}

Er1646v2RoutUsrProfIpEntry ::=
   SEQUENCE
      {
      er1646v2RoutUsrProfIpGlobalIx
         GlobalIndex,
      er1646v2RoutUsrProfIpVrfRouter
         DisplayString,
      er1646v2RoutUsrProfIpUnnumb
         DisplayString,
      er1646v2RoutUsrProfIpAddPlList
         DisplayString,
      er1646v2RoutUsrProfIpAddPlInt
         DisplayString,
      er1646v2RoutUsrProfIpSNetName
         INTEGER,
      er1646v2RoutUsrProfIpSNetCust
         DisplayString,
      er1646v2RoutUsrProfIpAcceptLocAddr
         INTEGER,
      er1646v2RoutUsrProfIpAcceptRemAddr
         INTEGER,
      er1646v2RoutUsrProfIpGatewayPref
         Integer32,
      er1646v2RoutUsrProfIpMtu
         Integer32,
      er1646v2RoutUsrProfIpMssAdjust
         INTEGER,
      er1646v2RoutUsrProfIpRipMetric
         Integer32,
      er1646v2RoutUsrProfIpRipMetricOut
         Integer32,
      er1646v2RoutUsrProfIpRipMode
         INTEGER,
      er1646v2RoutUsrProfIpRipTxVersion
         INTEGER,
      er1646v2RoutUsrProfIpRipRxVersion
         INTEGER,
      er1646v2RoutUsrProfIpRipSplitHorizon
         INTEGER,
      er1646v2RoutUsrProfIpRipAuth
         INTEGER,
      er1646v2RoutUsrProfIpRipFilter
         DisplayString,
      er1646v2RoutUsrProfIpRipFilterIn
         DisplayString,
      er1646v2RoutUsrProfIpRipSnapshot
         INTEGER,
      er1646v2RoutUsrProfIpRipClearNextHop
         INTEGER,
      er1646v2RoutUsrProfIpDialPolicy
         DisplayString,
      er1646v2RoutUsrProfIpAccPol
         DisplayString,
      er1646v2RoutUsrProfIpTrafPol
         DisplayString,
      er1646v2RoutUsrProfIpDB
         INTEGER,
      er1646v2RoutUsrProfIpIR
         INTEGER,
      er1646v2RoutUsrProfIpIgmp
         INTEGER,
      er1646v2RoutUsrProfIpNN
         DisplayString,
      er1646v2RoutUsrProfIpPrimaryDNS
         IpAddress,
      er1646v2RoutUsrProfIpSecondaryDNS
         IpAddress,
      er1646v2RoutUsrProfIpPrimaryWINS
         IpAddress,
      er1646v2RoutUsrProfIpSecondaryWINS
         IpAddress,
      er1646v2RoutUsrProfIpIMNetworkUnreachable
         INTEGER,
      er1646v2RoutUsrProfIpIMHostUnreachable
         INTEGER,
      er1646v2RoutUsrProfIpIMProtocolUnreachable
         INTEGER,
      er1646v2RoutUsrProfIpIMPortUnreachable
         INTEGER,
      er1646v2RoutUsrProfIpIMMtuExceeded
         INTEGER,
      er1646v2RoutUsrProfIpIMAdminProhibited
         INTEGER,
      er1646v2RoutUsrProfIpIMTtlExceeded
         INTEGER,
      er1646v2RoutUsrProfIpIMRedirect
         INTEGER
      }

er1646v2RoutUsrProfIpGlobalIx OBJECT-TYPE
   SYNTAX      GlobalIndex
   MAX-ACCESS  not-accessible
   STATUS      current
   DESCRIPTION
      "The value of the tlsCntTreeGlobalIndex of the MANAGED OBJECT."
   ::= {er1646v2RoutUsrProfIpEntry 10}

er1646v2RoutUsrProfIpVrfRouter OBJECT-TYPE
   SYNTAX      DisplayString
   MAX-ACCESS  read-write
   STATUS      current
   DESCRIPTION
      "Path: routing.editConf.ip.vrfRouter"
   ::= {er1646v2RoutUsrProfIpEntry 738197504}

er1646v2RoutUsrProfIpUnnumb OBJECT-TYPE
   SYNTAX      DisplayString
   MAX-ACCESS  read-write
   STATUS      current
   DESCRIPTION
      "Path: routing.editConf.ip.unnumbered"
   ::= {er1646v2RoutUsrProfIpEntry 33554432}

er1646v2RoutUsrProfIpAddPlList OBJECT-TYPE
   SYNTAX      DisplayString
   MAX-ACCESS  read-write
   STATUS      current
   DESCRIPTION
      "Path: routing.editConf.ip.addrPool.list"
   ::= {er1646v2RoutUsrProfIpEntry 50397184}

er1646v2RoutUsrProfIpAddPlInt OBJECT-TYPE
   SYNTAX      DisplayString
   MAX-ACCESS  read-write
   STATUS      current
   DESCRIPTION
      "Path: routing.editConf.ip.addrPool.interval"
   ::= {er1646v2RoutUsrProfIpEntry 50462720}

er1646v2RoutUsrProfIpSNetName OBJECT-TYPE
   SYNTAX      INTEGER
               {
               slOPTg (0),
               corp (2),
               dmz (3),
               internet (1)
               }
   MAX-ACCESS  read-write
   STATUS      current
   DESCRIPTION
      "Path: routing.editConf.ip.sNet.name

       Possibilities:
               <OPT>   (0)
               corp   (2)
               dmz   (3)
               internet   (1)"
   ::= {er1646v2RoutUsrProfIpEntry 855703552}

er1646v2RoutUsrProfIpSNetCust OBJECT-TYPE
   SYNTAX      DisplayString
   MAX-ACCESS  read-write
   STATUS      current
   DESCRIPTION
      "Path: routing.editConf.ip.sNet.custom"
   ::= {er1646v2RoutUsrProfIpEntry 855769088}

er1646v2RoutUsrProfIpAcceptLocAddr OBJECT-TYPE
   SYNTAX      INTEGER
               {
               disabled (0),
               enabled (1)
               }
   MAX-ACCESS  read-write
   STATUS      current
   DESCRIPTION
      "Path: routing.editConf.ip.acceptLocAddr

       Possibilities:
               disabled   (0)
               enabled   (1)"
   ::= {er1646v2RoutUsrProfIpEntry 67108864}

er1646v2RoutUsrProfIpAcceptRemAddr OBJECT-TYPE
   SYNTAX      INTEGER
               {
               disabled (0),
               enabled (1)
               }
   MAX-ACCESS  read-write
   STATUS      current
   DESCRIPTION
      "Path: routing.editConf.ip.acceptRemAddr

       Possibilities:
               disabled   (0)
               enabled   (1)"
   ::= {er1646v2RoutUsrProfIpEntry 100663296}

er1646v2RoutUsrProfIpGatewayPref OBJECT-TYPE
   SYNTAX      Integer32
   MAX-ACCESS  read-write
   STATUS      current
   DESCRIPTION
      "Path: routing.editConf.ip.gatewayPreference"
   ::= {er1646v2RoutUsrProfIpEntry 603979776}

er1646v2RoutUsrProfIpMtu OBJECT-TYPE
   SYNTAX      Integer32
   MAX-ACCESS  read-write
   STATUS      current
   DESCRIPTION
      "Path: routing.editConf.ip.mtu"
   ::= {er1646v2RoutUsrProfIpEntry 671088640}

er1646v2RoutUsrProfIpMssAdjust OBJECT-TYPE
   SYNTAX      INTEGER
               {
               disabled (0),
               auto (65536)
               }
   MAX-ACCESS  read-write
   STATUS      current
   DESCRIPTION
      "Path: routing.editConf.ip.mssAdjust

       Possibilities:
               disabled   (0)
               auto   (65536)"
   ::= {er1646v2RoutUsrProfIpEntry 754974720}

er1646v2RoutUsrProfIpRipMetric OBJECT-TYPE
   SYNTAX      Integer32
   MAX-ACCESS  read-write
   STATUS      current
   DESCRIPTION
      "Path: routing.editConf.ip.rip.metric"
   ::= {er1646v2RoutUsrProfIpEntry 353566720}

er1646v2RoutUsrProfIpRipMetricOut OBJECT-TYPE
   SYNTAX      Integer32
   MAX-ACCESS  read-write
   STATUS      current
   DESCRIPTION
      "Path: routing.editConf.ip.rip.metricOut"
   ::= {er1646v2RoutUsrProfIpEntry 353632256}

er1646v2RoutUsrProfIpRipMode OBJECT-TYPE
   SYNTAX      INTEGER
               {
               disabled (0),
               passive (1),
               active (2)
               }
   MAX-ACCESS  read-write
   STATUS      current
   DESCRIPTION
      "Path: routing.editConf.ip.rip.mode

       Possibilities:
               disabled   (0)
               passive   (1)
               active   (2)"
   ::= {er1646v2RoutUsrProfIpEntry 353697792}

er1646v2RoutUsrProfIpRipTxVersion OBJECT-TYPE
   SYNTAX      INTEGER
               {
               rip1 (0),
               rip2 (1),
               rip1mcompatible (2)
               }
   MAX-ACCESS  read-write
   STATUS      current
   DESCRIPTION
      "Path: routing.editConf.ip.rip.txVersion

       Possibilities:
               rip1   (0)
               rip2   (1)
               rip1-compatible   (2)"
   ::= {er1646v2RoutUsrProfIpEntry 354615296}

er1646v2RoutUsrProfIpRipRxVersion OBJECT-TYPE
   SYNTAX      INTEGER
               {
               rip1only (0),
               rip2only (1),
               rip12 (2)
               }
   MAX-ACCESS  read-write
   STATUS      current
   DESCRIPTION
      "Path: routing.editConf.ip.rip.rxVersion

       Possibilities:
               rip1only   (0)
               rip2only   (1)
               rip1&2   (2)"
   ::= {er1646v2RoutUsrProfIpEntry 354680832}

er1646v2RoutUsrProfIpRipSplitHorizon OBJECT-TYPE
   SYNTAX      INTEGER
               {
               disabled (0),
               enabled (1),
               poisonedReverse (2)
               }
   MAX-ACCESS  read-write
   STATUS      current
   DESCRIPTION
      "Path: routing.editConf.ip.rip.splitHorizon

       Possibilities:
               disabled   (0)
               enabled   (1)
               poisonedReverse   (2)"
   ::= {er1646v2RoutUsrProfIpEntry 353828864}

er1646v2RoutUsrProfIpRipAuth OBJECT-TYPE
   SYNTAX      INTEGER
               {
               disabled (0),
               texts (1),
               md5 (2)
               }
   MAX-ACCESS  read-write
   STATUS      current
   DESCRIPTION
      "Path: routing.editConf.ip.rip.authentication

       Possibilities:
               disabled   (0)
               text    (1)
               md5   (2)"
   ::= {er1646v2RoutUsrProfIpEntry 353501184}

er1646v2RoutUsrProfIpRipFilter OBJECT-TYPE
   SYNTAX      DisplayString
   MAX-ACCESS  read-write
   STATUS      current
   DESCRIPTION
      "Path: routing.editConf.ip.rip.filter"
   ::= {er1646v2RoutUsrProfIpEntry 354418688}

er1646v2RoutUsrProfIpRipFilterIn OBJECT-TYPE
   SYNTAX      DisplayString
   MAX-ACCESS  read-write
   STATUS      current
   DESCRIPTION
      "Path: routing.editConf.ip.rip.filterIn"
   ::= {er1646v2RoutUsrProfIpEntry 354484224}

er1646v2RoutUsrProfIpRipSnapshot OBJECT-TYPE
   SYNTAX      INTEGER
               {
               disabled (0),
               enabled (1)
               }
   MAX-ACCESS  read-write
   STATUS      current
   DESCRIPTION
      "Path: routing.editConf.ip.rip.snapshot

       Possibilities:
               disabled   (0)
               enabled   (1)"
   ::= {er1646v2RoutUsrProfIpEntry 352387072}

er1646v2RoutUsrProfIpRipClearNextHop OBJECT-TYPE
   SYNTAX      INTEGER
               {
               disabled (0),
               enabled (1)
               }
   MAX-ACCESS  read-write
   STATUS      current
   DESCRIPTION
      "Path: routing.editConf.ip.rip.clearNextHop

       Possibilities:
               disabled   (0)
               enabled   (1)"
   ::= {er1646v2RoutUsrProfIpEntry 352452608}

er1646v2RoutUsrProfIpDialPolicy OBJECT-TYPE
   SYNTAX      DisplayString
   MAX-ACCESS  read-write
   STATUS      current
   DESCRIPTION
      "Path: routing.editConf.ip.dialPolicy"
   ::= {er1646v2RoutUsrProfIpEntry 687865856}

er1646v2RoutUsrProfIpAccPol OBJECT-TYPE
   SYNTAX      DisplayString
   MAX-ACCESS  read-write
   STATUS      current
   DESCRIPTION
      "Path: routing.editConf.ip.accessPolicy"
   ::= {er1646v2RoutUsrProfIpEntry 704643072}

er1646v2RoutUsrProfIpTrafPol OBJECT-TYPE
   SYNTAX      DisplayString
   MAX-ACCESS  read-write
   STATUS      current
   DESCRIPTION
      "Path: routing.editConf.ip.trafficPolicy"
   ::= {er1646v2RoutUsrProfIpEntry 234881024}

er1646v2RoutUsrProfIpDB OBJECT-TYPE
   SYNTAX      INTEGER
               {
               disabled (0),
               enabled (1)
               }
   MAX-ACCESS  read-write
   STATUS      current
   DESCRIPTION
      "Path: routing.editConf.ip.directedBroadcasts

       Possibilities:
               disabled   (0)
               enabled   (1)"
   ::= {er1646v2RoutUsrProfIpEntry 369098752}

er1646v2RoutUsrProfIpIR OBJECT-TYPE
   SYNTAX      INTEGER
               {
               disabled (0),
               enabled (1)
               }
   MAX-ACCESS  read-write
   STATUS      current
   DESCRIPTION
      "Path: routing.editConf.ip.icmpRedirects

       Possibilities:
               disabled   (0)
               enabled   (1)"
   ::= {er1646v2RoutUsrProfIpEntry 436207616}

er1646v2RoutUsrProfIpIgmp OBJECT-TYPE
   SYNTAX      INTEGER
               {
               disabled (0),
               proxy (1),
               router (2),
               v3Router (5)
               }
   MAX-ACCESS  read-write
   STATUS      current
   DESCRIPTION
      "Path: routing.editConf.ip.igmp

       Possibilities:
               disabled   (0)
               proxy   (1)
               router   (2)
               v3Router   (5)"
   ::= {er1646v2RoutUsrProfIpEntry 536870912}

er1646v2RoutUsrProfIpNN OBJECT-TYPE
   SYNTAX      DisplayString
   MAX-ACCESS  read-write
   STATUS      current
   DESCRIPTION
      "Path: routing.editConf.ip.nat"
   ::= {er1646v2RoutUsrProfIpEntry 452984832}

er1646v2RoutUsrProfIpPrimaryDNS OBJECT-TYPE
   SYNTAX      IpAddress
   MAX-ACCESS  read-write
   STATUS      current
   DESCRIPTION
      "Path: routing.editConf.ip.primaryDNS"
   ::= {er1646v2RoutUsrProfIpEntry 469762048}

er1646v2RoutUsrProfIpSecondaryDNS OBJECT-TYPE
   SYNTAX      IpAddress
   MAX-ACCESS  read-write
   STATUS      current
   DESCRIPTION
      "Path: routing.editConf.ip.secondaryDNS"
   ::= {er1646v2RoutUsrProfIpEntry 486539264}

er1646v2RoutUsrProfIpPrimaryWINS OBJECT-TYPE
   SYNTAX      IpAddress
   MAX-ACCESS  read-write
   STATUS      current
   DESCRIPTION
      "Path: routing.editConf.ip.primaryWINS"
   ::= {er1646v2RoutUsrProfIpEntry 503316480}

er1646v2RoutUsrProfIpSecondaryWINS OBJECT-TYPE
   SYNTAX      IpAddress
   MAX-ACCESS  read-write
   STATUS      current
   DESCRIPTION
      "Path: routing.editConf.ip.secondaryWINS"
   ::= {er1646v2RoutUsrProfIpEntry 520093696}

er1646v2RoutUsrProfIpIMNetworkUnreachable OBJECT-TYPE
   SYNTAX      INTEGER
               {
               disabled (0),
               enabled (1)
               }
   MAX-ACCESS  read-write
   STATUS      current
   DESCRIPTION
      "Path: routing.editConf.ip.icmpMessages.networkUnreachable

       Possibilities:
               disabled   (0)
               enabled   (1)"
   ::= {er1646v2RoutUsrProfIpEntry 788594688}

er1646v2RoutUsrProfIpIMHostUnreachable OBJECT-TYPE
   SYNTAX      INTEGER
               {
               disabled (0),
               enabled (1)
               }
   MAX-ACCESS  read-write
   STATUS      current
   DESCRIPTION
      "Path: routing.editConf.ip.icmpMessages.hostUnreachable

       Possibilities:
               disabled   (0)
               enabled   (1)"
   ::= {er1646v2RoutUsrProfIpEntry 788660224}

er1646v2RoutUsrProfIpIMProtocolUnreachable OBJECT-TYPE
   SYNTAX      INTEGER
               {
               disabled (0),
               enabled (1)
               }
   MAX-ACCESS  read-write
   STATUS      current
   DESCRIPTION
      "Path: routing.editConf.ip.icmpMessages.protocolUnreachable

       Possibilities:
               disabled   (0)
               enabled   (1)"
   ::= {er1646v2RoutUsrProfIpEntry 788725760}

er1646v2RoutUsrProfIpIMPortUnreachable OBJECT-TYPE
   SYNTAX      INTEGER
               {
               disabled (0),
               enabled (1)
               }
   MAX-ACCESS  read-write
   STATUS      current
   DESCRIPTION
      "Path: routing.editConf.ip.icmpMessages.portUnreachable

       Possibilities:
               disabled   (0)
               enabled   (1)"
   ::= {er1646v2RoutUsrProfIpEntry 788791296}

er1646v2RoutUsrProfIpIMMtuExceeded OBJECT-TYPE
   SYNTAX      INTEGER
               {
               disabled (0),
               enabled (1)
               }
   MAX-ACCESS  read-write
   STATUS      current
   DESCRIPTION
      "Path: routing.editConf.ip.icmpMessages.mtuExceeded

       Possibilities:
               disabled   (0)
               enabled   (1)"
   ::= {er1646v2RoutUsrProfIpEntry 788856832}

er1646v2RoutUsrProfIpIMAdminProhibited OBJECT-TYPE
   SYNTAX      INTEGER
               {
               disabled (0),
               enabled (1)
               }
   MAX-ACCESS  read-write
   STATUS      current
   DESCRIPTION
      "Path: routing.editConf.ip.icmpMessages.adminProhibited

       Possibilities:
               disabled   (0)
               enabled   (1)"
   ::= {er1646v2RoutUsrProfIpEntry 788922368}

er1646v2RoutUsrProfIpIMTtlExceeded OBJECT-TYPE
   SYNTAX      INTEGER
               {
               disabled (0),
               enabled (1)
               }
   MAX-ACCESS  read-write
   STATUS      current
   DESCRIPTION
      "Path: routing.editConf.ip.icmpMessages.ttlExceeded

       Possibilities:
               disabled   (0)
               enabled   (1)"
   ::= {er1646v2RoutUsrProfIpEntry 788987904}

er1646v2RoutUsrProfIpIMRedirect OBJECT-TYPE
   SYNTAX      INTEGER
               {
               disabled (0),
               enabled (1)
               }
   MAX-ACCESS  read-write
   STATUS      current
   DESCRIPTION
      "Path: routing.editConf.ip.icmpMessages.redirect

       Possibilities:
               disabled   (0)
               enabled   (1)"
   ::= {er1646v2RoutUsrProfIpEntry 789053440}


er1646v2RoutUsrProfSnmpIndexOffset OBJECT IDENTIFIER ::= {er1646v2RoutUsrProf 268}

er1646v2RoutUsrProfSnmpIndexOffsetTable OBJECT-TYPE
   SYNTAX      SEQUENCE OF Er1646v2RoutUsrProfSnmpIndexOffsetEntry
   MAX-ACCESS  not-accessible
   STATUS      current
   DESCRIPTION
      "Preferred offset in the range of SNMP indices for this SWinst, 0 means automatic"
   ::= {er1646v2RoutUsrProfSnmpIndexOffset 1}

er1646v2RoutUsrProfSnmpIndexOffsetEntry OBJECT-TYPE
   SYNTAX      Er1646v2RoutUsrProfSnmpIndexOffsetEntry
   MAX-ACCESS  not-accessible
   STATUS      current
   DESCRIPTION
      ""
   INDEX      { er1646v2RoutUsrProfSnmpIndexOffsetGlobalIx }
   ::= {er1646v2RoutUsrProfSnmpIndexOffsetTable 1}

Er1646v2RoutUsrProfSnmpIndexOffsetEntry ::=
   SEQUENCE
      {
      er1646v2RoutUsrProfSnmpIndexOffsetGlobalIx
         GlobalIndex,
      er1646v2RoutUsrProfSnmpIndexOffsetValue
         Integer32
      }

er1646v2RoutUsrProfSnmpIndexOffsetGlobalIx OBJECT-TYPE
   SYNTAX      GlobalIndex
   MAX-ACCESS  not-accessible
   STATUS      current
   DESCRIPTION
      "The value of the tlsCntTreeGlobalIndex of the MANAGED OBJECT."
   ::= {er1646v2RoutUsrProfSnmpIndexOffsetEntry 10}

er1646v2RoutUsrProfSnmpIndexOffsetValue OBJECT-TYPE
   SYNTAX      Integer32
   MAX-ACCESS  read-write
   STATUS      current
   DESCRIPTION
      "Path: routing.editConf.snmpIndexOffset"
   ::= {er1646v2RoutUsrProfSnmpIndexOffsetEntry 2147483648}



sr1646v2RoutUsrProf OBJECT IDENTIFIER ::= {r1646v2RoutUsrProf 14}


sr1646v2RoutUsrProfProfUsers OBJECT IDENTIFIER ::= {sr1646v2RoutUsrProf 40}

sr1646v2RoutUsrProfProfUsersSSCTable OBJECT-TYPE
   SYNTAX      SEQUENCE OF Sr1646v2RoutUsrProfProfUsersEntry
   MAX-ACCESS  not-accessible
   STATUS      current
   DESCRIPTION
      "users of the different profiles"
   ::= {sr1646v2RoutUsrProfProfUsers 1}

sr1646v2RoutUsrProfProfUsersEntry OBJECT-TYPE
   SYNTAX      Sr1646v2RoutUsrProfProfUsersEntry
   MAX-ACCESS  not-accessible
   STATUS      current
   DESCRIPTION
      ""
   INDEX      { sr1646v2RoutUsrProfProfUsersGlobalIx,
                sr1646v2RoutUsrProfProfUsersTableIx }
   ::= {sr1646v2RoutUsrProfProfUsersSSCTable 1}

Sr1646v2RoutUsrProfProfUsersEntry ::=
   SEQUENCE
      {
      sr1646v2RoutUsrProfProfUsersGlobalIx
         GlobalIndex,
      sr1646v2RoutUsrProfProfUsersTableIx
         TableIndex,
      sr1646v2RoutUsrProfProfUsersType
         INTEGER,
      sr1646v2RoutUsrProfProfUsersName
         DisplayString
      }

sr1646v2RoutUsrProfProfUsersGlobalIx OBJECT-TYPE
   SYNTAX      GlobalIndex
   MAX-ACCESS  not-accessible
   STATUS      current
   DESCRIPTION
      "The value of the tlsCntTreeGlobalIndex of the MANAGED OBJECT."
   ::= {sr1646v2RoutUsrProfProfUsersEntry 10}

sr1646v2RoutUsrProfProfUsersTableIx OBJECT-TYPE
   SYNTAX      TableIndex
   MAX-ACCESS  not-accessible
   STATUS      current
   DESCRIPTION
      ""
   ::= {sr1646v2RoutUsrProfProfUsersEntry 11}

sr1646v2RoutUsrProfProfUsersType OBJECT-TYPE
   SYNTAX      INTEGER
               {
               dialmap (1),
               pppoE (104)
               }
   MAX-ACCESS  read-only
   STATUS      current
   DESCRIPTION
      "Path: routing.status.profileUsers.type

       Possibilities:
               dialmap   (1)
               pppoE   (104)"
   ::= {sr1646v2RoutUsrProfProfUsersEntry 16777216}

sr1646v2RoutUsrProfProfUsersName OBJECT-TYPE
   SYNTAX      DisplayString
   MAX-ACCESS  read-only
   STATUS      current
   DESCRIPTION
      "Path: routing.status.profileUsers.name"
   ::= {sr1646v2RoutUsrProfProfUsersEntry 33554432}


sr1646v2RoutUsrProfSnmpIndex OBJECT IDENTIFIER ::= {sr1646v2RoutUsrProf 269}

sr1646v2RoutUsrProfSnmpIndexTable OBJECT-TYPE
   SYNTAX      SEQUENCE OF Sr1646v2RoutUsrProfSnmpIndexEntry
   MAX-ACCESS  not-accessible
   STATUS      current
   DESCRIPTION
      "SNMP index assigned to this object"
   ::= {sr1646v2RoutUsrProfSnmpIndex 1}

sr1646v2RoutUsrProfSnmpIndexEntry OBJECT-TYPE
   SYNTAX      Sr1646v2RoutUsrProfSnmpIndexEntry
   MAX-ACCESS  not-accessible
   STATUS      current
   DESCRIPTION
      ""
   INDEX      { sr1646v2RoutUsrProfSnmpIndexGlobalIx }
   ::= {sr1646v2RoutUsrProfSnmpIndexTable 1}

Sr1646v2RoutUsrProfSnmpIndexEntry ::=
   SEQUENCE
      {
      sr1646v2RoutUsrProfSnmpIndexGlobalIx
         GlobalIndex,
      sr1646v2RoutUsrProfSnmpIndexValue
         Integer32
      }

sr1646v2RoutUsrProfSnmpIndexGlobalIx OBJECT-TYPE
   SYNTAX      GlobalIndex
   MAX-ACCESS  not-accessible
   STATUS      current
   DESCRIPTION
      "The value of the tlsCntTreeGlobalIndex of the MANAGED OBJECT."
   ::= {sr1646v2RoutUsrProfSnmpIndexEntry 10}

sr1646v2RoutUsrProfSnmpIndexValue OBJECT-TYPE
   SYNTAX      Integer32
   MAX-ACCESS  read-only
   STATUS      current
   DESCRIPTION
      "Path: routing.status.snmpIndex"
   ::= {sr1646v2RoutUsrProfSnmpIndexEntry 2147483648}



END
